TIMETRA-OAM-PM-MIB DEFINITIONS ::= BEGIN

IMPORTS
    Dot1agCfmMepIdOrZero
                                                         FROM IEEE8021-CFM-MIB
    InetAddress, InetAddressPrefixLength,
    InetAddressType, InetPortNumber
                                                         FROM INET-ADDRESS-MIB
    MODULE-COMPLIANCE, NOTIFICATION-GROUP,
    OBJECT-GROUP
                                                         FROM SNMPv2-CONF
    Counter32, Counter64, Gauge32,
    Integer32, MODULE-IDENTITY,
    NOTIFICATION-TYPE, OBJECT-TYPE,
    Unsigned32
                                                         FROM SNMPv2-SMI
    DateAndTime, MacAddress, RowStatus,
    TEXTUAL-CONVENTION, TimeStamp,
    TruthValue
                                                         FROM SNMPv2-TC
    timetraSRMIBModules, tmnxSRConfs,
    tmnxSRNotifyPrefix, tmnxSRObjs
                                                         FROM TIMETRA-GLOBAL-MIB
    svcId
                                                         FROM TIMETRA-SERV-MIB
    TDSCPName, TDSCPNameOrEmpty, TFCName,
    TItemDescription, TLNamedItem,
    TLNamedItemOrEmpty, TNamedItem,
    TNamedItemOrEmpty, TProfile,
    TmnxCreateOrigin, TmnxEnabledDisabled,
    TmnxEnabledDisabledOrNA,
    TmnxFlexAlgoIdOrZero, TmnxIgpInstance
                                                         FROM TIMETRA-TC-MIB
    ;

timetraOamPmMIBModule            MODULE-IDENTITY
    LAST-UPDATED "201803310000Z"
    ORGANIZATION "Nokia"
    CONTACT-INFO
        "Nokia SROS Support
         Web: http://www.nokia.com"
    DESCRIPTION
        "This document is the SNMP MIB module for the Nokia SROS implementation
         of OAM Performance Monitoring (OAM-PM).

         A subset of MEF 35 ('Service OAM Performance Monitoring Implementation
         Agreement') is supported, plus extensions.

         Copyright 2013-2024 Nokia. All rights reserved. Reproduction of this
         document is authorized on the condition that the foregoing copyright
         notice is included.

         This SNMP MIB module (Specification) embodies Nokia's
         proprietary intellectual property.  Nokia retains all title
         and ownership in the Specification, including any revisions.

         Nokia grants all interested parties a non-exclusive license to use and
         distribute an unmodified copy of this Specification in connection with
         management of Nokia products, and without fee, provided this copyright
         notice and license appear on all copies.

         This Specification is supplied `as is', and Nokia makes no warranty,
         either express or implied, as to the use, operation, condition, or
         performance of the Specification."

    REVISION    "201803310000Z"
    DESCRIPTION
        "Rev 16.0                31 March 2018 00:00
         16.0 release of the TIMETRA-OAM-PM-MIB."

    REVISION    "201701010000Z"
    DESCRIPTION
        "Rev 15.0                1 Jan 2017 00:00
         15.0 release of the TIMETRA-OAM-PM-MIB."

    REVISION    "201601010000Z"
    DESCRIPTION
        "Rev 14.0                1 Jan 2016 00:00
         14.0 release of the TIMETRA-OAM-PM-MIB."

    REVISION    "201501010000Z"
    DESCRIPTION
        "Rev 13.0                1 Jan 2015 00:00
         13.0 release of the TIMETRA-OAM-PM-MIB."

    REVISION    "201307040000Z"
    DESCRIPTION
        "Rev 12.0                4 Jul 2013 00:00
         Initial release of the TIMETRA-OAM-PM-MIB."

    ::= { timetraSRMIBModules 92 }

TmnxOamPmBinGroupId              ::= TEXTUAL-CONVENTION
    STATUS      current
    DESCRIPTION
        "An object of type TmnxOamPmBinGroupId identifies an OAM Performance
         Monitoring bin group."
    SYNTAX      Unsigned32 (1..255)

TmxnOamPmBinNums                 ::= TEXTUAL-CONVENTION
    STATUS      current
    DESCRIPTION
        "An object of type TmxnOamPmBinNums specifies a set of OAM Performance
         Monitoring delay bin numbers."
    REFERENCE
        "MEF-35, 'Service OAM Performance Monitoring Implementation Agreement',
         Metro Ethernet Forum, April 2012, Section 9.2.2 'Measurement Bins'"
    SYNTAX      BITS {
        bin0 (0),
        bin1 (1),
        bin2 (2),
        bin3 (3),
        bin4 (4),
        bin5 (5),
        bin6 (6),
        bin7 (7),
        bin8 (8),
        bin9 (9)
    }

TmnxOamPmBinType                 ::= TEXTUAL-CONVENTION
    STATUS      current
    DESCRIPTION
        "An object of type TmnxOamPmBinType specifies the type of an OAM
         Performance Monitoring bin.

         Values:
            fd(1)
                A Frame Delay (FD) bin, as defined in MEF-35.
            fdr(2)
                A Frame Delay Range (FDR) bin, as defined in MEF-35.
            ifdv(3)
                An Inter-Frame Delay Variation (IFDV) bin, as defined in
                MEF-35."
    REFERENCE
        "MEF-35, 'Service OAM Performance Monitoring Implementation Agreement',
         Metro Ethernet Forum, April 2012, Section 9.2.2 'Measurement Bins'"
    SYNTAX      INTEGER {
        fd   (1),
        fdr  (2),
        ifdv (3)
    }

TmnxOamPmCfgBinNum               ::= TEXTUAL-CONVENTION
    STATUS      current
    DESCRIPTION
        "An object of type TmnxOamPmCfgBinNum specifies the bin number of a
         configurable OAM Performance Monitoring delay bin.

         Bin zero is defined, but it is not configurable."
    REFERENCE
        "MEF-35, 'Service OAM Performance Monitoring Implementation Agreement',
         Metro Ethernet Forum, April 2012, Section 9.2.2 'Measurement Bins'"
    SYNTAX      Unsigned32 (1..9)

TmnxOamPmCfgBinNumOrNone         ::= TEXTUAL-CONVENTION
    STATUS      current
    DESCRIPTION
        "An object of type TmnxOamPmCfgBinNumOrNone specifies the bin number of
         a configurable OAM Performance Monitoring delay bin, or indicates that
         no bin is specified.

         Bin zero is defined, but it is not configurable."
    REFERENCE
        "MEF-35, 'Service OAM Performance Monitoring Implementation Agreement',
         Metro Ethernet Forum, April 2012, Section 9.2.2 'Measurement Bins'"
    SYNTAX      Integer32 (-1 | 1..9)

TmnxOamPmDetectableTxError       ::= TEXTUAL-CONVENTION
    STATUS      current
    DESCRIPTION
        "An object of type TmnxOamPmDetectableTxError indicates the reason for
         the inability (if any) to launch test frames for the specified test.

         The code points are as follows.
         none                (1) - no transmit failure has been detected
         txPortDown          (2) - the transmit port is operationally down
         noTxPort            (3) - an egress has not been found
         ethParentAdminDown  (4) - the parent (e.g. the SAP, SDP, service, or
            port) of the MEP is administratively down
         ethNoMepOrAdminDown (5) - the test's MEP is not fully configured or the
            MEP is administratively down
         unexpectedError     (6) - transmission failed due to unexpected
            conditions, such as failed memory allocation, traffic congestion,
            or failure to obtain the necessary resources
         noService           (7) - the service associated with this test session
            was not found
         serviceAdminDown    (8) - the service associated with this test session
            is administratively down
         serviceOperDown     (9) - the service associated with this test session
            is operationally down
         noRoute             (10) - there is no IP route to the destination
            address
         noInterface         (11) - there is no IP interface that matches the
            configured forwarding interface
         noDirectInterface   (12) - there is no appropriate IP interface for
            bypass-routing to the destination address
         sourceInterfaceDown (13) - the IP interface associated with the source
            address is down
         sourceIpNotLocal    (14) - the source address is not local
         nextHopIpIsLocal    (15) - the next-hop address is local
         destMacResolveFail  (16) - unable to resolve the remote-mepid to a
            unicast layer2 MAC address
         mplsDmSystemDisable (17) - MPLS-DM disabled at system level
         lspNotAvailable     (18) - LSP not available (e.g. not configured)
         lspOperDown         (19) - LSP is operationally down
         udpReturnIpNotLocal (20) - UDP Return IP address is not local
         ethCfmUnsupportedTestType (21) - the test type is not valid on the MEP"
    SYNTAX      INTEGER {
        none                      (1),
        txPortDown                (2),
        noTxPort                  (3),
        ethParentAdminDown        (4),
        ethNoMepOrAdminDown       (5),
        unexpectedError           (6),
        noService                 (7),
        serviceAdminDown          (8),
        serviceOperDown           (9),
        noRoute                   (10),
        noInterface               (11),
        noDirectInterface         (12),
        sourceInterfaceDown       (13),
        sourceIpNotLocal          (14),
        nextHopIpIsLocal          (15),
        destMacResolveFail        (16),
        mplsDmSystemDisable       (17),
        lspNotAvailable           (18),
        lspOperDown               (19),
        udpReturnIpNotLocal       (20),
        ethCfmUnsupportedTestType (21)
    }

TmnxOamPmForwardBackward         ::= TEXTUAL-CONVENTION
    STATUS      current
    DESCRIPTION
        "An object of type TmnxOamPmForwardBackward specifies the MEF-35
         traffic flow direction of an OAM-PM loss test.

         The code points are as follows.
         forward  (1) - refers to the loss of traffic flowing away from the test
            originator.
         backward (2) - refers to the loss of traffic flowing toward the test
            originator."
    REFERENCE
        "MEF-35, 'Service OAM Performance Monitoring Implementation Agreement',
         Metro Ethernet Forum, April 2012, Section 8.1 'PM-1: Single-Ended
         Point-to-Point or Multipoint Delay and Synthetic Loss Measurements'."
    SYNTAX      INTEGER {
        forward  (1),
        backward (2)
    }

TmnxOamPmForwardBackwardAggr     ::= TEXTUAL-CONVENTION
    STATUS      current
    DESCRIPTION
        "An object of type TmnxOamPmForwardBackwardAggr specifies the traffic
         flow direction type of an OAM-PM loss threshold.

         The code points are as follows.
         forward  (1) - apply the threshold to the counter for traffic flowing
            away from the test originator.
         backward (2) - apply the threshold to the counter for traffic flowing
            toward the test originator.
         aggregate(3) - apply the threshold to the sum of the forward and
            backward counters."
    SYNTAX      INTEGER {
        forward   (1),
        backward  (2),
        aggregate (3)
    }

TmnxOamPmForwardBackwardTwoWay   ::= TEXTUAL-CONVENTION
    STATUS      current
    DESCRIPTION
        "An object of type TmnxOamPmForwardBackwardTwoWay specifies the MEF-35
         traffic flow direction of an OAM-PM delay test.

         The code points are as follows.
         forward  (1) - refers to the one-way delay of traffic flowing away from
            the test originator.
         backward (2) - refers to the one-way delay of traffic flowing toward
            the test originator.
         twoWay   (3) - refers to two way delay."
    REFERENCE
        "MEF-35, 'Service OAM Performance Monitoring Implementation Agreement',
         Metro Ethernet Forum, April 2012, Section 9.2.2 'Measurement Bins'"
    SYNTAX      INTEGER {
        forward  (1),
        backward (2),
        twoWay   (3)
    }

TmnxOamPmMeasIntervalDuration    ::= TEXTUAL-CONVENTION
    STATUS      current
    DESCRIPTION
        "An object of type TmnxOamPmMeasIntervalDuration specifies the duration
         of an OAM Performance Monitoring measurement interval.

         Values:
            miRaw(1)
                A raw measurement interval starts when the associated test
                starts, and ends when the associated test ends.
            mi15Minutes(2)
                A 15 minute measurement interval, as defined in MEF-35 Section
                9.1.6.
            mi1Hour(3)
                A one hour measurement interval.
            mi1Day(4)
                A one day measurement interval.
            mi5Minutes(5)
                A five minute measurement interval.
            mi1Minute (6)
                A one minute measurement interval."
    REFERENCE
        "MEF-35, 'Service OAM Performance Monitoring Implementation Agreement',
         Metro Ethernet Forum, April 2012, Section 9.1.6 'Measurement
         Intervals'"
    SYNTAX      INTEGER {
        miRaw       (1),
        mi15Minutes (2),
        mi1Hour     (3),
        mi1Day      (4),
        mi5Minutes  (5),
        mi1Minute   (6)
    }

TmnxOamPmCfgMeasIntervalDuration ::= TEXTUAL-CONVENTION
    STATUS      current
    DESCRIPTION
        "An object of type TmnxOamPmCfgMeasIntervalDuration specifies the
         duration of a configurable OAM Performance Monitoring measurement
         interval.

         This TEXTUAL-CONVENTION is the same as TmnxOamPmMeasIntervalDuration,
         except the 'miRaw(1)' code point is absent here (because raw
         measurement intervals are not configurable)."
    REFERENCE
        "MEF-35, 'Service OAM Performance Monitoring Implementation Agreement',
         Metro Ethernet Forum, April 2012, Section 9.1.6 'Measurement
         Intervals'"
    SYNTAX      INTEGER {
        mi15Minutes (2),
        mi1Hour     (3),
        mi1Day      (4),
        mi5Minutes  (5),
        mi1Minute   (6)
    }

TmnxOamPmMplsLspType             ::= TEXTUAL-CONVENTION
    STATUS      current
    DESCRIPTION
        "An object of type TmnxOamPmMplsLspType specifies the type of LSP to be
         tested by an OAM-PM MPLS test.

         The code points are as follows.
         none        (1) - the LSP type is unknown.
         mplsTpStatic(2) - the LSP was created using Multiprotocol Label
             Switching Transport Profile (MPLS-TP).
         rsvp        (3) - The LSP was manually created using the Resource
             Reservation Protocol (RSVP).
         rsvpAuto    (4) - The LSP was automatically created using RSVP and an
             LSP template."
    REFERENCE
        "RFC 6374, 'Packet Loss and Delay Measurement for MPLS Networks',
         September 2011.
         RFC 6375, 'A Packet Loss and Delay Measurement Profile for MPLS-Based
         Transport Networks', September 2011."
    SYNTAX      INTEGER {
        none         (1),
        mplsTpStatic (2),
        rsvp         (3),
        rsvpAuto     (4)
    }

TmnxOamPmMplsTestRxStatus        ::= TEXTUAL-CONVENTION
    STATUS      current
    DESCRIPTION
        "An object of type TmnxOamPmMplsTestRxStatus indicates the most recent
         receive status for an OAM-PM MPLS-DM test.

         A value less than 256 was copied from the Control Code field of
         the most recent MPLS-DM response message.  The value indicates
         whether or not the most recent query message (sent by this node as
         part of an MPLS-DM test) was processed successfully by the far-end
         node.

         'none(256)' is a proprietary code point, indicating the receive status
         is irrelevant or unknown (e.g. the test has not been started).

         'errorTimeout(257)' is a proprietary code point, indicating the most
         recent receive event for a running test was an internal timeout,
         rather than the expected receipt of an MPLS-DM response message."
    REFERENCE
        "RFC 6374, 'Packet Loss and Delay Measurement for MPLS Networks',
         September 2011, Section 3.2, 'Delay Measurement Message Format'."
    SYNTAX      INTEGER {
        success                         (1),
        notifDataFormatInvalid          (2),
        notifInitializationinProgress   (3),
        notifDataResetOccurred          (4),
        notifResourceTemporarilyUnavail (5),
        errorUnspecifiedError           (16),
        errorUnsupportedVersion         (17),
        errorUnsupportedControlCode     (18),
        errorUnsupportedDataFormat      (19),
        errorAuthenticationFailure      (20),
        errorInvalidDestinationNodeId   (21),
        errorConnectionMismatch         (22),
        errorUnsupportedMandTLVObject   (23),
        errorUnsupportedQueryInterval   (24),
        errorAdministrativeBlock        (25),
        errorResourceUnavailable        (26),
        errorResourceReleased           (27),
        errorInvalidMessage             (28),
        errorProtocolError              (29),
        none                            (256),
        errorTimeout                    (257)
    }

TmnxOamPmSessionType             ::= TEXTUAL-CONVENTION
    STATUS      current
    DESCRIPTION
        "An object of type TmnxOamPmSessionType specifies the type of an OAM
         Performance Monitoring session.

         Values:
            proactive(1)
                Test the service using a proactive session, as specified in
                MEF-35 Section 9.1.2.
            onDemand(2)
                Test the service using an on-demand session, as specified in
                MEF-35 Section 9.1.2."
    REFERENCE
        "MEF-35, 'Service OAM Performance Monitoring Implementation Agreement',
         Metro Ethernet Forum, April 2012, Section 9.1.2 'Proactive and
         On-Demand PM Sessions'"
    SYNTAX      INTEGER {
        proactive (1),
        onDemand  (2)
    }

TmnxOamPmStrMetric               ::= TEXTUAL-CONVENTION
    STATUS      current
    DESCRIPTION
        "An object of type TmnxOamPmStrMetric specifies the type of an OAM
         Performance Monitoring streaming metric.

         Values:
            fdAvg(1)
                Average Frame Delay (FD).
            ifdvAvg(2)
                Average Inter-Frame Delay Variation (IFDV)."
    SYNTAX      INTEGER {
        fdAvg   (1),
        ifdvAvg (2)
    }

TmnxOamPmStsIntvlNum             ::= TEXTUAL-CONVENTION
    STATUS      current
    DESCRIPTION
        "An object of type TmnxOamPmStsIntvlNum specifies the interval number
         of a Measurement Interval Data Set."
    REFERENCE
        "MEF-35, 'Service OAM Performance Monitoring Implementation Agreement',
         Metro Ethernet Forum, April 2012, Section 9.2.1 'Measurement Interval
         Data Sets'"
    SYNTAX      Unsigned32 (1..4294967295)

TmnxOamPmStsTcaOperState         ::= TEXTUAL-CONVENTION
    STATUS      current
    DESCRIPTION
        "An object of type TmnxOamPmStsTcaOperState indicates the operational
         state of the Threshold Crossing Alerts (TCAs) for the specified
         indices.

         The code points are as follows.  The conditions are evaluated in the
         order shown.
         pending(1)
            'pending(1)' is returned if the threshold configuration for the
            specified indices changed during the current measurement interval.
         active(2)
            If the specified indices have a default clear threshold configured,
            'active(2)' is returned if the current measurement interval has
            generated a Raise TCA (i.e. tmnxOamPmThrRaise).
            If the specified indices have a non-default clear threshold
            configured, 'active(2)' is returned if the most recent TCA generated
            was a Raise (i.e. tmnxOamPmThrRaise).
         notActive(3)
            'notActive(3)' is returned for all other conditions (e.g.
            thresholding is not configured for the specified indices)."
    SYNTAX      INTEGER {
        pending   (1),
        active    (2),
        notActive (3)
    }

TmnxOamPmTestFamily              ::= TEXTUAL-CONVENTION
    STATUS      current
    DESCRIPTION
        "An object of type TmnxOamPmTestFamily specifies the type of the
         service to be tested by an OAM Performance Monitoring test.

         Values:
            ethernet(1)
                Test an Ethernet service, as specified in MEF-35 Section 7.
            ip(2)
                Test an IP service.
            mpls(3)
                Test an MPLS service, as specified by RFC 6374."
    REFERENCE
        "MEF-35, 'Service OAM Performance Monitoring Implementation Agreement',
         Metro Ethernet Forum, April 2012, Section 7 'PM Considerations'.
         RFC 6374, 'Packet Loss and Delay Measurement for MPLS Networks',
         September 2011."
    SYNTAX      INTEGER {
        ethernet (1),
        ip       (2),
        mpls     (3)
    }

TmnxOamPmTestType                ::= TEXTUAL-CONVENTION
    STATUS      current
    DESCRIPTION
        "An object of type TmnxOamPmTestType specifies the type of an OAM
         Performance Monitoring test.

         Values:
            dmm(1)
                An Ethernet Delay Measurement test, as specified in MEF-35
                Section 10.1.
            slm(2)
                An Ethernet Synthetic Loss Measurement test, as specified in
                MEF-35 Section 10.2.
            twampLight(3)
                An IP/UDP delay and/or loss test, using either
                a) the TWAMP-Light protocol defined in RFC 5357, Appendix I, or
                b) the STAMP protocol defined in RFC 8762.

                Any reference in this MIB to twampLight, TWAMP-Light, or
                abbreviations (e.g. the object name component 'Twl') implicitly
                includes the STAMP alternative (except as noted).
            lmm(4)
                An ETH-LM test, as specified in Y.1731 Section 8.1.
            mplsDm(5)
                An MPLS Delay Measurement test, as specified in RFC 6374."
    REFERENCE
        "MEF-35, 'Service OAM Performance Monitoring Implementation Agreement',
         Metro Ethernet Forum, April 2012, Section 10.1, 'Single-Ended Delay
         Function for Delay, Frame Delay Range, and Inter Delay Variation'.
         MEF-35, 'Service OAM Performance Monitoring Implementation Agreement',
         Metro Ethernet Forum, April 2012, Section 10.2, 'Single-Ended Synthetic
         Loss Function for Frame Loss Ratio (FLR) and Availability'.
         RFC 5357, 'A Two-Way Active Measurement Protocol (TWAMP)', Appendix I,
         'TWAMP Light'.
         ITU-T G.8013/Y.1731, 'OAM functions and mechanisms for Ethernet based
         networks', 07/2011, Section 8.1 'Frame loss measurement (ETH-LM)'.
         RFC 6374, 'Packet Loss and Delay Measurement for MPLS Networks',
         September 2011.
         RFC 8762, 'Simple Two-Way Active Measurement Protocol', March 2020."
    SYNTAX      INTEGER {
        dmm        (1),
        slm        (2),
        twampLight (3),
        lmm        (4),
        mplsDm     (5)
    }

tmnxOamPmObjs                    OBJECT IDENTIFIER ::= { tmnxSRObjs 92 }

tmnxOamPmCfgObjs                 OBJECT IDENTIFIER ::= { tmnxOamPmObjs 1 }

tmnxOamPmCfgScalarObjs           OBJECT IDENTIFIER ::= { tmnxOamPmCfgObjs 1 }

tmnxOamPmCfgTwlRflInactTimer     OBJECT-TYPE
    SYNTAX      Unsigned32 (10..100)
    UNITS       "seconds"
    MAX-ACCESS  read-write
    STATUS      current
    DESCRIPTION
        "The value of tmnxOamPmCfgTwlRflInactTimer specifies the system
         inactivity timeout for TWAMP-Light reflectors.

         A TWAMP-Light reflector replies to TWAMP-Test PDUs.  When a reflector
         sees a TWAMP-Test PDU for a new session (i.e. a {source IP address,
         source UDP port, destination IP address} triple which is not known to
         the reflector), the reflector allocates a record for the session.  The
         record is used to ensure that reply PDUs sent for the session have
         consecutive sequence numbers.

         When a reflector sees tmnxOamPmCfgTwlRflInactTimer seconds pass
         without receiving a TWAMP-Test PDU for a particular session, an
         inactivity timeout has occurred, so the record allocated to the
         session is freed."
    DEFVAL      { 100 }
    ::= { tmnxOamPmCfgScalarObjs 1 }

tmnxOamPmCfgMplsDmAdminStatus    OBJECT-TYPE
    SYNTAX      TmnxEnabledDisabled
    MAX-ACCESS  read-write
    STATUS      current
    DESCRIPTION
        "The value of tmnxOamPmCfgMplsDmAdminStatus specifies whether or not:
         1.  Received MPLS-DM Query messages are processed.
         2.  Received MPLS-DM Response messages are processed.
         3.  Transmitting MPLS-DM Query messages (as part of a test created
             using tmnxOamPmCfgDelayMplsTable) is allowed.

         Received messages which are not processed are dropped.

         Disallowed message transmission is reported using
         tmnxOamPmStsTestDetectTxError"
    REFERENCE
        "RFC 6374, 'Packet Loss and Delay Measurement for MPLS Networks',
         September 2011, Section 8, 'Security Considerations'."
    DEFVAL      { disabled }
    ::= { tmnxOamPmCfgScalarObjs 2 }

tmnxOamPmTableLastChgObjs        OBJECT IDENTIFIER ::= { tmnxOamPmCfgObjs 2 }

tmnxOamPmCfgBinGroupTableLastChg OBJECT-TYPE
    SYNTAX      TimeStamp
    MAX-ACCESS  read-only
    STATUS      current
    DESCRIPTION
        "The value of tmnxOamPmCfgBinGroupTableLastChg indicates the time,
         since system startup, when tmnxOamPmCfgBinGroupTable last changed.

         If tmnxOamPmCfgBinGroupTable has not changed since system startup,
         zero is returned."
    ::= { tmnxOamPmTableLastChgObjs 1 }

tmnxOamPmCfgBinTableLastChg      OBJECT-TYPE
    SYNTAX      TimeStamp
    MAX-ACCESS  read-only
    STATUS      current
    DESCRIPTION
        "The value of tmnxOamPmCfgBinTableLastChg indicates the time, since
         system startup, when tmnxOamPmCfgBinTable last changed.

         If tmnxOamPmCfgBinTable has not changed since system startup, zero is
         returned."
    ::= { tmnxOamPmTableLastChgObjs 2 }

tmnxOamPmCfgSessTableLastChg     OBJECT-TYPE
    SYNTAX      TimeStamp
    MAX-ACCESS  read-only
    STATUS      current
    DESCRIPTION
        "The value of tmnxOamPmCfgSessTableLastChg indicates the time, since
         system startup, when tmnxOamPmCfgSessTable last changed.

         If tmnxOamPmCfgSessTable has not changed since system startup, zero is
         returned."
    ::= { tmnxOamPmTableLastChgObjs 3 }

tmnxOamPmCfgSessEthTableLastChg  OBJECT-TYPE
    SYNTAX      TimeStamp
    MAX-ACCESS  read-only
    STATUS      current
    DESCRIPTION
        "The value of tmnxOamPmCfgSessEthTableLastChg indicates the time, since
         system startup, when tmnxOamPmCfgSessEthTable last changed.

         If tmnxOamPmCfgSessEthTable has not changed since system startup, zero
         is returned."
    ::= { tmnxOamPmTableLastChgObjs 4 }

tmnxOamPmCfgDelayDmmTableLastChg OBJECT-TYPE
    SYNTAX      TimeStamp
    MAX-ACCESS  read-only
    STATUS      current
    DESCRIPTION
        "The value of tmnxOamPmCfgDelayDmmTableLastChg indicates the time,
         since system startup, when tmnxOamPmCfgDelayDmmTable last changed.

         If tmnxOamPmCfgDelayDmmTable has not changed since system startup,
         zero is returned."
    ::= { tmnxOamPmTableLastChgObjs 5 }

tmnxOamPmCfgLossSlmTableLastChg  OBJECT-TYPE
    SYNTAX      TimeStamp
    MAX-ACCESS  read-only
    STATUS      current
    DESCRIPTION
        "The value of tmnxOamPmCfgLossSlmTableLastChg indicates the time, since
         system startup, when tmnxOamPmCfgLossSlmTable last changed.

         If tmnxOamPmCfgLossSlmTable has not changed since system startup, zero
         is returned."
    ::= { tmnxOamPmTableLastChgObjs 6 }

tmnxOamPmCfgMeasIntvlTableLstChg OBJECT-TYPE
    SYNTAX      TimeStamp
    MAX-ACCESS  read-only
    STATUS      current
    DESCRIPTION
        "The value of tmnxOamPmCfgMeasIntvlTableLstChg indicates the time,
         since system startup, when tmnxOamPmCfgMeasIntvlTable last changed.

         If tmnxOamPmCfgMeasIntvlTable has not changed since system startup,
         zero is returned."
    ::= { tmnxOamPmTableLastChgObjs 7 }

tmnxOamPmCfgSessIpTableLastChg   OBJECT-TYPE
    SYNTAX      TimeStamp
    MAX-ACCESS  read-only
    STATUS      current
    DESCRIPTION
        "The value of tmnxOamPmCfgSessIpTableLastChg indicates the time, since
         system startup, when tmnxOamPmCfgSessIpTable last changed.

         If tmnxOamPmCfgSessIpTable has not changed since system startup, zero
         is returned."
    ::= { tmnxOamPmTableLastChgObjs 8 }

tmnxOamPmCfgTwampLtTableLastChg  OBJECT-TYPE
    SYNTAX      TimeStamp
    MAX-ACCESS  read-only
    STATUS      current
    DESCRIPTION
        "The value of tmnxOamPmCfgTwampLtTableLastChg indicates the time, since
         system startup, when tmnxOamPmCfgTwampLtTable last changed.

         If tmnxOamPmCfgTwampLtTable has not changed since system startup, zero
         is returned."
    ::= { tmnxOamPmTableLastChgObjs 9 }

tmnxOamPmCfgTwlRflTableLastChg   OBJECT-TYPE
    SYNTAX      TimeStamp
    MAX-ACCESS  read-only
    STATUS      current
    DESCRIPTION
        "The value of tmnxOamPmCfgTwlRflTableLastChg indicates the time, since
         system startup, when tmnxOamPmCfgTwlRflTable last changed.

         If tmnxOamPmCfgTwlRflTable has not changed since system startup, zero
         is returned."
    ::= { tmnxOamPmTableLastChgObjs 10 }

tmnxOamPmCfgTwlRflPfxTableLstChg OBJECT-TYPE
    SYNTAX      TimeStamp
    MAX-ACCESS  read-only
    STATUS      current
    DESCRIPTION
        "The value of tmnxOamPmCfgTwlRflPfxTableLstChg indicates the time,
         since system startup, when tmnxOamPmCfgTwlRflPfxTable last changed.

         If tmnxOamPmCfgTwlRflPfxTable has not changed since system startup,
         zero is returned."
    ::= { tmnxOamPmTableLastChgObjs 11 }

tmnxOamPmCfgLossLmmTableLastChg  OBJECT-TYPE
    SYNTAX      TimeStamp
    MAX-ACCESS  read-only
    STATUS      current
    DESCRIPTION
        "The value of tmnxOamPmCfgLossLmmTableLastChg indicates the time, since
         system startup, when tmnxOamPmCfgLossLmmTable last changed.

         If tmnxOamPmCfgLossLmmTable has not changed since system startup, zero
         is returned."
    ::= { tmnxOamPmTableLastChgObjs 12 }

tmnxOamPmCfgThrLossFwBwTableLChg OBJECT-TYPE
    SYNTAX      TimeStamp
    MAX-ACCESS  read-only
    STATUS      current
    DESCRIPTION
        "The value of tmnxOamPmCfgThrLossFwBwTableLChg indicates the time,
         since system startup, when tmnxOamPmCfgThrLossFwBwTable last changed.

         If tmnxOamPmCfgThrLossFwBwTable has not changed since system startup,
         zero is returned."
    ::= { tmnxOamPmTableLastChgObjs 13 }

tmnxOamPmCfgThrLossFwBwAgTableLC OBJECT-TYPE
    SYNTAX      TimeStamp
    MAX-ACCESS  read-only
    STATUS      current
    DESCRIPTION
        "The value of tmnxOamPmCfgThrLossFwBwAgTableLC indicates the time,
         since system startup, when tmnxOamPmCfgThrLossFwBwAgTable last
         changed.

         If tmnxOamPmCfgThrLossFwBwAgTable has not changed since system
         startup, zero is returned."
    ::= { tmnxOamPmTableLastChgObjs 14 }

tmnxOamPmCfgThrDelayTableLastChg OBJECT-TYPE
    SYNTAX      TimeStamp
    MAX-ACCESS  read-only
    STATUS      current
    DESCRIPTION
        "The value of tmnxOamPmCfgThrDelayTableLastChg indicates the time,
         since system startup, when tmnxOamPmCfgThrDelayTable last changed.

         If tmnxOamPmCfgThrDelayTable has not changed since system startup,
         zero is returned."
    ::= { tmnxOamPmTableLastChgObjs 15 }

tmnxOamPmCfgBinGrpTypeDirTableLC OBJECT-TYPE
    SYNTAX      TimeStamp
    MAX-ACCESS  read-only
    STATUS      current
    DESCRIPTION
        "The value of tmnxOamPmCfgBinGrpTypeDirTableLC indicates the time,
         since system startup, when tmnxOamPmCfgBinGrpTypeDirTable last
         changed.

         If tmnxOamPmCfgBinGrpTypeDirTable has not changed since system
         startup, zero is returned."
    ::= { tmnxOamPmTableLastChgObjs 16 }

tmnxOamPmCfgSessMplsTableLastChg OBJECT-TYPE
    SYNTAX      TimeStamp
    MAX-ACCESS  read-only
    STATUS      current
    DESCRIPTION
        "The value of tmnxOamPmCfgSessMplsTableLastChg indicates the time,
         since system startup, when tmnxOamPmCfgSessMplsTable last changed.

         If tmnxOamPmCfgSessMplsTable has not changed since system startup,
         zero is returned."
    ::= { tmnxOamPmTableLastChgObjs 17 }

tmnxOamPmCfgSessMplsRsvpTableLC  OBJECT-TYPE
    SYNTAX      TimeStamp
    MAX-ACCESS  read-only
    STATUS      current
    DESCRIPTION
        "The value of tmnxOamPmCfgSessMplsRsvpTableLC indicates the time, since
         system startup, when tmnxOamPmCfgSessMplsRsvpTable last changed.

         If tmnxOamPmCfgSessMplsRsvpTable has not changed since system startup,
         zero is returned."
    ::= { tmnxOamPmTableLastChgObjs 18 }

tmnxOamPmCfgSessMplsRsvpAutTblLC OBJECT-TYPE
    SYNTAX      TimeStamp
    MAX-ACCESS  read-only
    STATUS      current
    DESCRIPTION
        "The value of tmnxOamPmCfgSessMplsRsvpAutTblLC indicates the time,
         since system startup, when tmnxOamPmCfgSessMplsRsvpAutTable last
         changed.

         If tmnxOamPmCfgSessMplsRsvpAutTable has not changed since system
         startup, zero is returned."
    ::= { tmnxOamPmTableLastChgObjs 19 }

tmnxOamPmCfgSessMplsTpTableLChg  OBJECT-TYPE
    SYNTAX      TimeStamp
    MAX-ACCESS  read-only
    STATUS      current
    DESCRIPTION
        "The value of tmnxOamPmCfgSessMplsTpTableLChg indicates the time, since
         system startup, when tmnxOamPmCfgSessMplsTpTable last changed.

         If tmnxOamPmCfgSessMplsTpTable has not changed since system startup,
         zero is returned."
    ::= { tmnxOamPmTableLastChgObjs 20 }

tmnxOamPmCfgDelayMplsTableLstChg OBJECT-TYPE
    SYNTAX      TimeStamp
    MAX-ACCESS  read-only
    STATUS      current
    DESCRIPTION
        "The value of tmnxOamPmCfgDelayMplsTableLstChg indicates the time,
         since system startup, when tmnxOamPmCfgDelayMplsTable last changed.

         If tmnxOamPmCfgDelayMplsTable has not changed since system startup,
         zero is returned."
    ::= { tmnxOamPmTableLastChgObjs 21 }

tmnxOamPmCfgStrTmplTableLastChg  OBJECT-TYPE
    SYNTAX      TimeStamp
    MAX-ACCESS  read-only
    STATUS      current
    DESCRIPTION
        "The value of tmnxOamPmCfgStrTmplTableLastChg indicates the time, since
         system startup, when tmnxOamPmCfgStrTmplTable last changed.

         If tmnxOamPmCfgStrTmplTable has not changed since system startup, zero
         is returned."
    ::= { tmnxOamPmTableLastChgObjs 22 }

tmnxOamPmCfgStrMeasTableLastChg  OBJECT-TYPE
    SYNTAX      TimeStamp
    MAX-ACCESS  read-only
    STATUS      current
    DESCRIPTION
        "The value of tmnxOamPmCfgStrMeasTableLastChg indicates the time, since
         system startup, when tmnxOamPmCfgStrMeasTable last changed.

         If tmnxOamPmCfgStrMeasTable has not changed since system startup, zero
         is returned."
    ::= { tmnxOamPmTableLastChgObjs 23 }

tmnxOamPmCfgTableObjs            OBJECT IDENTIFIER ::= { tmnxOamPmCfgObjs 3 }

tmnxOamPmCfgBinGroupTable        OBJECT-TYPE
    SYNTAX      SEQUENCE OF TmnxOamPmCfgBinGroupEntry
    MAX-ACCESS  not-accessible
    STATUS      current
    DESCRIPTION
        "tmnxOamPmCfgBinGroupTable contains the configuration information for
         OAM Performance Monitoring bin groups."
    REFERENCE
        "MEF-35, 'Service OAM Performance Monitoring Implementation Agreement',
         Metro Ethernet Forum, April 2012, Section 9.2.2 'Measurement Bins'"
    ::= { tmnxOamPmCfgTableObjs 1 }

tmnxOamPmCfgBinGroupEntry        OBJECT-TYPE
    SYNTAX      TmnxOamPmCfgBinGroupEntry
    MAX-ACCESS  not-accessible
    STATUS      current
    DESCRIPTION
        "tmnxOamPmCfgBinGroupEntry contains the configuration information for
         one OAM Performance Monitoring bin group.

         Bin group 1 is created by the system on a CPM restart.

         The configuration of bin group 1 is shown in the following table.

         Object                             Value
         --------------------------------   ------------------------------
         tmnxOamPmCfgBinGroupId             1
         tmnxOamPmCfgBinGroupRowStatus      active(1)
         tmnxOamPmCfgBinGroupAdminStatus    enabled(1)
         tmnxOamPmCfgBinGroupDescription    'OAM PM default bin group (not
                                             modifiable)'
         tmnxOamPmCfgBinGroupFdBinCount     3
         tmnxOamPmCfgBinGroupFdrBinCount    2
         tmnxOamPmCfgBinGroupIfdvBinCount   2

         Bin group 1 cannot be changed or destroyed.

         The rest of the rows in this table are created or destroyed using
         tmnxOamPmCfgBinGroupRowStatus.

         When a row is created, the following objects must be set in the SNMP
         Set PDU:
            tmnxOamPmCfgBinGroupRowStatus
            tmnxOamPmCfgBinGroupFdBinCount
            tmnxOamPmCfgBinGroupFdrBinCount
            tmnxOamPmCfgBinGroupIfdvBinCount

         The value of the following objects cannot be changed after their row is
         created:
            tmnxOamPmCfgBinGroupFdBinCount
            tmnxOamPmCfgBinGroupFdrBinCount
            tmnxOamPmCfgBinGroupIfdvBinCount

         A row can be destroyed if its administrative status
         (tmnxOamPmCfgBinGroupAdminStatus) is disabled, and no OAM Performance
         Monitoring sessions refer to the bin group."
    INDEX       { tmnxOamPmCfgBinGroupId }
    ::= { tmnxOamPmCfgBinGroupTable 1 }

TmnxOamPmCfgBinGroupEntry        ::= SEQUENCE
{
    tmnxOamPmCfgBinGroupId           TmnxOamPmBinGroupId,
    tmnxOamPmCfgBinGroupRowStatus    RowStatus,
    tmnxOamPmCfgBinGroupAdminStatus  TmnxEnabledDisabled,
    tmnxOamPmCfgBinGroupDescription  TItemDescription,
    tmnxOamPmCfgBinGroupFdBinCount   Unsigned32,
    tmnxOamPmCfgBinGroupFdrBinCount  Unsigned32,
    tmnxOamPmCfgBinGroupIfdvBinCount Unsigned32
}

tmnxOamPmCfgBinGroupId           OBJECT-TYPE
    SYNTAX      TmnxOamPmBinGroupId
    MAX-ACCESS  not-accessible
    STATUS      current
    DESCRIPTION
        "The value of tmnxOamPmCfgBinGroupId specifies the bin group to be
         configured or read."
    ::= { tmnxOamPmCfgBinGroupEntry 1 }

tmnxOamPmCfgBinGroupRowStatus    OBJECT-TYPE
    SYNTAX      RowStatus
    MAX-ACCESS  read-create
    STATUS      current
    DESCRIPTION
        "The value of tmnxOamPmCfgBinGroupRowStatus specifies the status of the
         configuration row for the specified bin group."
    ::= { tmnxOamPmCfgBinGroupEntry 2 }

tmnxOamPmCfgBinGroupAdminStatus  OBJECT-TYPE
    SYNTAX      TmnxEnabledDisabled
    MAX-ACCESS  read-create
    STATUS      current
    DESCRIPTION
        "The value of tmnxOamPmCfgBinGroupAdminStatus specifies whether or not
         the specified bin group is administratively enabled.

         An attempt to set this object to 'disabled(2)' will be rejected if
         tests referring to the specified bin group are enabled.

         An attempt to set this object to 'enabled(1)' will be rejected if one
         (or more) of the three sets of lower bounds for the specified bin
         group (as configured using tmnxOamPmCfgBinLowerBound) is not in
         strictly ascending order.

         For example, tmnxOamPmCfgBinGroupAdminStatus.255 cannot be set to
         'enabled(1)' if the following lower bound values are configured.

         Object ID                               Value (in microseconds)
         -------------------------------------   -----------------------
         tmnxOamPmCfgBinLowerBound.255.fd(1).1                      5000
         tmnxOamPmCfgBinLowerBound.255.fd(1).2                      5000
         tmnxOamPmCfgBinLowerBound.255.fd(1).3                      5002

         Setting this object to 'disabled(2)' deletes ALL the OAM-PM statistics
         for each test belonging to each session which refers to the specified
         bin group.  For example, if session 'Sess1' has a DMM test and an SLM
         test configured, and 'Sess1' uses bin-group 255, then disabling
         bin-group 255 will delete all the DMM and SLM statistics for 'Sess1'."
    DEFVAL      { disabled }
    ::= { tmnxOamPmCfgBinGroupEntry 3 }

tmnxOamPmCfgBinGroupDescription  OBJECT-TYPE
    SYNTAX      TItemDescription
    MAX-ACCESS  read-create
    STATUS      current
    DESCRIPTION
        "The value of tmnxOamPmCfgBinGroupDescription specifies the descriptive
         text for the specified bin group."
    DEFVAL      { "" }
    ::= { tmnxOamPmCfgBinGroupEntry 4 }

tmnxOamPmCfgBinGroupFdBinCount   OBJECT-TYPE
    SYNTAX      Unsigned32 (2..10)
    MAX-ACCESS  read-create
    STATUS      current
    DESCRIPTION
        "The value of tmnxOamPmCfgBinGroupFdBinCount specifies the number of
         Frame Delay bins to be created for the specified bin group.

         There is no default value for this object.  A value must be provided on
         row creation.  See the DESCRIPTION clause for tmnxOamPmCfgBinGroupEntry
         for more information."
    ::= { tmnxOamPmCfgBinGroupEntry 5 }

tmnxOamPmCfgBinGroupFdrBinCount  OBJECT-TYPE
    SYNTAX      Unsigned32 (2..10)
    MAX-ACCESS  read-create
    STATUS      current
    DESCRIPTION
        "The value of tmnxOamPmCfgBinGroupFdrBinCount specifies the number of
         Frame Delay Range bins to be created for the specified bin group.

         There is no default value for this object.  A value must be provided on
         row creation.  See the DESCRIPTION clause for tmnxOamPmCfgBinGroupEntry
         for more information."
    ::= { tmnxOamPmCfgBinGroupEntry 6 }

tmnxOamPmCfgBinGroupIfdvBinCount OBJECT-TYPE
    SYNTAX      Unsigned32 (2..10)
    MAX-ACCESS  read-create
    STATUS      current
    DESCRIPTION
        "The value of tmnxOamPmCfgBinGroupIfdvBinCount specifies the number of
         Inter-Frame Delay Variation bins to be created for the specified bin
         group.

         There is no default value for this object.  A value must be provided on
         row creation.  See the DESCRIPTION clause for tmnxOamPmCfgBinGroupEntry
         for more information."
    ::= { tmnxOamPmCfgBinGroupEntry 7 }

tmnxOamPmCfgBinTable             OBJECT-TYPE
    SYNTAX      SEQUENCE OF TmnxOamPmCfgBinEntry
    MAX-ACCESS  not-accessible
    STATUS      current
    DESCRIPTION
        "tmnxOamPmCfgBinTable contains the configuration information for OAM
         Performance Monitoring bins."
    REFERENCE
        "MEF-35, 'Service OAM Performance Monitoring Implementation Agreement',
         Metro Ethernet Forum, April 2012, Section 9.2.2 'Measurement Bins'"
    ::= { tmnxOamPmCfgTableObjs 2 }

tmnxOamPmCfgBinEntry             OBJECT-TYPE
    SYNTAX      TmnxOamPmCfgBinEntry
    MAX-ACCESS  not-accessible
    STATUS      current
    DESCRIPTION
        "tmnxOamPmCfgBinEntry contains the configuration information for one
         OAM Performance Monitoring bin.

         Rows are created in this table when one (or more) of the following
         objects is set:
            tmnxOamPmCfgBinGroupFdBinCount,
            tmnxOamPmCfgBinGroupFdrBinCount, or
            tmnxOamPmCfgBinGroupIfdvBinCount.

         Suppose, for example, that the following values are set for bin group
         255.

         Object                               Value
         ------------------------------------ -----
         tmnxOamPmCfgBinGroupFdBinCount.255       4
         tmnxOamPmCfgBinGroupFdrBinCount.255      3
         tmnxOamPmCfgBinGroupIfdvBinCount.255     2

         Then, the following rows will be created in this table (where index
         columns are underlined with '#', column names have been abbreviated by
         replacing 'tmnxOamPmCfg' with '_', and the _BinLowerBound column shows
         the default values).

         _BinGroupId _BinGroupType _BinId _BinLowerBound (microsec)
         ########### ############# ###### -------------------------
         255                 fd(1)      1                      5000
         255                 fd(1)      2                     10000
         255                 fd(1)      3                     15000
         255                fdr(2)      1                      5000
         255                fdr(2)      2                     10000
         255               ifdv(3)      1                      5000

         Note that tmnxOamPmCfgBinGroupFdBinCount.255 is 4, but there are only
         three corresponding rows in this table.  The fourth bin is bin 0, which
         has a hard coded lower bound of 0 microseconds.  Bin 0 never has a row
         in this table.

         The lower bounds for a particular {tmnxOamPmCfgBinGroupId,
         tmnxOamPmCfgBinType} pair must be strictly ascending.  See the
         tmnxOamPmCfgBinGroupAdminStatus DESCRIPTION clause for more
         information."
    INDEX       {
        tmnxOamPmCfgBinGroupId,
        tmnxOamPmCfgBinType,
        tmnxOamPmCfgBinNum
    }
    ::= { tmnxOamPmCfgBinTable 1 }

TmnxOamPmCfgBinEntry             ::= SEQUENCE
{
    tmnxOamPmCfgBinType              TmnxOamPmBinType,
    tmnxOamPmCfgBinNum               TmnxOamPmCfgBinNum,
    tmnxOamPmCfgBinLowerBound        Unsigned32
}

tmnxOamPmCfgBinType              OBJECT-TYPE
    SYNTAX      TmnxOamPmBinType
    MAX-ACCESS  not-accessible
    STATUS      current
    DESCRIPTION
        "The value of tmnxOamPmCfgBinType specifies the type of the bin to be
         configured or read."
    ::= { tmnxOamPmCfgBinEntry 1 }

tmnxOamPmCfgBinNum               OBJECT-TYPE
    SYNTAX      TmnxOamPmCfgBinNum
    MAX-ACCESS  not-accessible
    STATUS      current
    DESCRIPTION
        "The value of tmnxOamPmCfgBinNum specifies the number of the bin to be
         configured or read."
    ::= { tmnxOamPmCfgBinEntry 2 }

tmnxOamPmCfgBinLowerBound        OBJECT-TYPE
    SYNTAX      Unsigned32 (1..4294967295)
    UNITS       "microseconds"
    MAX-ACCESS  read-write
    STATUS      current
    DESCRIPTION
        "The value of tmnxOamPmCfgBinLowerBound specifies the lower bound (in
         microseconds) for the specified bin.

         A lower bound can be changed if the administrative state (i.e.
         tmnxOamPmCfgBinGroupAdminStatus) for the parent bin group is disabled.
         Please see additional restrictions on setting lower bounds in the
         tmnxOamPmCfgBinEntry DESCRIPTION clause.

         The default lower bound for bin number 1 is 5000 microseconds.  The
         default lower bound for a subsequent bin number is computed using
            defLowerBound(n) = defLowerBound(n-1) + (5000 microseconds)."
    ::= { tmnxOamPmCfgBinEntry 3 }

tmnxOamPmCfgSessTable            OBJECT-TYPE
    SYNTAX      SEQUENCE OF TmnxOamPmCfgSessEntry
    MAX-ACCESS  not-accessible
    STATUS      current
    DESCRIPTION
        "tmnxOamPmCfgSessTable contains the configuration information for OAM
         Performance Monitoring sessions."
    REFERENCE
        "MEF-35, 'Service OAM Performance Monitoring Implementation Agreement',
         Metro Ethernet Forum, April 2012, Section 9.1.2 'Proactive and
         On-Demand PM Sessions'"
    ::= { tmnxOamPmCfgTableObjs 3 }

tmnxOamPmCfgSessEntry            OBJECT-TYPE
    SYNTAX      TmnxOamPmCfgSessEntry
    MAX-ACCESS  not-accessible
    STATUS      current
    DESCRIPTION
        "tmnxOamPmCfgSessEntry contains the configuration information for one
         OAM Performance Monitoring session.

         Rows are created or destroyed by SNMP Set operations on
         tmnxOamPmCfgSessRowStatus.

         An attempt to change the tmnxOamPmCfgSessBinGroupId value in a row (or
         an attempt to destroy the row) for a particular session will be
         rejected if an administratively enabled test (e.g. an SLM test) exists
         for the session."
    INDEX       { tmnxOamPmCfgSessName }
    ::= { tmnxOamPmCfgSessTable 1 }

TmnxOamPmCfgSessEntry            ::= SEQUENCE
{
    tmnxOamPmCfgSessName             TNamedItem,
    tmnxOamPmCfgSessRowStatus        RowStatus,
    tmnxOamPmCfgSessTestFamily       TmnxOamPmTestFamily,
    tmnxOamPmCfgSessType             TmnxOamPmSessionType,
    tmnxOamPmCfgSessBinGroupId       TmnxOamPmBinGroupId,
    tmnxOamPmCfgSessDescription      TItemDescription,
    tmnxOamPmCfgSessOrigin           TmnxCreateOrigin
}

tmnxOamPmCfgSessName             OBJECT-TYPE
    SYNTAX      TNamedItem
    MAX-ACCESS  not-accessible
    STATUS      current
    DESCRIPTION
        "The value of tmnxOamPmCfgSessName specifies the name of the session to
         be configured or read."
    ::= { tmnxOamPmCfgSessEntry 1 }

tmnxOamPmCfgSessRowStatus        OBJECT-TYPE
    SYNTAX      RowStatus
    MAX-ACCESS  read-create
    STATUS      current
    DESCRIPTION
        "The value of tmnxOamPmCfgSessRowStatus specifies the status of the
         configuration row for the specified session."
    ::= { tmnxOamPmCfgSessEntry 2 }

tmnxOamPmCfgSessTestFamily       OBJECT-TYPE
    SYNTAX      TmnxOamPmTestFamily
    MAX-ACCESS  read-create
    STATUS      current
    DESCRIPTION
        "The value of tmnxOamPmCfgSessTestFamily specifies the type of service
         (e.g. 'ethernet(1)') to be tested by the specified session.

         When a session is created, tmnxOamPmCfgSessRowStatus and
         tmnxOamPmCfgSessTestFamily must be specified in the same SNMP Set PDU.

         After a session is created, tmnxOamPmCfgSessTestFamily cannot be
         changed."
    ::= { tmnxOamPmCfgSessEntry 3 }

tmnxOamPmCfgSessType             OBJECT-TYPE
    SYNTAX      TmnxOamPmSessionType
    MAX-ACCESS  read-create
    STATUS      current
    DESCRIPTION
        "The value of tmnxOamPmCfgSessType specifies the type (e.g.
         'onDemand(2)') of the specified session.

         When a session is created, tmnxOamPmCfgSessRowStatus and
         tmnxOamPmCfgSessType can be specified in the same SNMP Set PDU.  Or,
         tmnxOamPmCfgSessType can be left at its default value.

         After a session is created, tmnxOamPmCfgSessType cannot be changed."
    DEFVAL      { proactive }
    ::= { tmnxOamPmCfgSessEntry 4 }

tmnxOamPmCfgSessBinGroupId       OBJECT-TYPE
    SYNTAX      TmnxOamPmBinGroupId
    MAX-ACCESS  read-create
    STATUS      current
    DESCRIPTION
        "The value of tmnxOamPmCfgSessBinGroupId specifies the bin group to be
         used by the specified session.

         Changing the bin group for a session deletes ALL the OAM-PM statistics
         for the session's tests."
    DEFVAL      { 1 }
    ::= { tmnxOamPmCfgSessEntry 5 }

tmnxOamPmCfgSessDescription      OBJECT-TYPE
    SYNTAX      TItemDescription
    MAX-ACCESS  read-create
    STATUS      current
    DESCRIPTION
        "The value of tmnxOamPmCfgSessDescription specifies the descriptive
         text for the specified session."
    DEFVAL      { "" }
    ::= { tmnxOamPmCfgSessEntry 6 }

tmnxOamPmCfgSessOrigin           OBJECT-TYPE
    SYNTAX      TmnxCreateOrigin
    MAX-ACCESS  read-only
    STATUS      current
    DESCRIPTION
        "The value of tmnxOamPmCfgSessOrigin indicates the mechanism used to
         create this session."
    ::= { tmnxOamPmCfgSessEntry 7 }

tmnxOamPmCfgSessEthTable         OBJECT-TYPE
    SYNTAX      SEQUENCE OF TmnxOamPmCfgSessEthEntry
    MAX-ACCESS  not-accessible
    STATUS      current
    DESCRIPTION
        "tmnxOamPmCfgSessEthTable contains the Ethernet endpoint configuration
         information for OAM Performance Monitoring sessions."
    REFERENCE
        "ITU-T G.8013/Y.1731, 'OAM functions and mechanisms for Ethernet based
         networks', 07/2011.
         MEF-35, 'Service OAM Performance Monitoring Implementation Agreement',
         Metro Ethernet Forum, April 2012, Section 9.4 'MEP Placement'."
    ::= { tmnxOamPmCfgTableObjs 4 }

tmnxOamPmCfgSessEthEntry         OBJECT-TYPE
    SYNTAX      TmnxOamPmCfgSessEthEntry
    MAX-ACCESS  not-accessible
    STATUS      current
    DESCRIPTION
        "tmnxOamPmCfgSessEthEntry contains the Ethernet endpoint configuration
         information for one OAM Performance Monitoring session.

         A row is created when a tmnxOamPmCfgSessTable row is created with
         tmnxOamPmCfgSessTestFamily = 'ethernet(1)'.

         A row is destroyed when a tmnxOamPmCfgSessTable row with
         tmnxOamPmCfgSessTestFamily = 'ethernet(1)' is destroyed.

         An attempt to change a value in a row for a particular session will be
         rejected if an administratively enabled test (e.g. an SLM test) exists
         for the session."
    INDEX       { tmnxOamPmCfgSessName }
    ::= { tmnxOamPmCfgSessEthTable 1 }

TmnxOamPmCfgSessEthEntry         ::= SEQUENCE
{
    tmnxOamPmCfgSessEthSrcMepId      Dot1agCfmMepIdOrZero,
    tmnxOamPmCfgSessEthSrcMdIndex    Unsigned32,
    tmnxOamPmCfgSessEthSrcMaIndex    Unsigned32,
    tmnxOamPmCfgSessEthPriority      Unsigned32,
    tmnxOamPmCfgSessEthDestMacAddr   MacAddress,
    tmnxOamPmCfgSessEthRemoteMepId   Dot1agCfmMepIdOrZero,
    tmnxOamPmCfgSessEthSrcMdName     TLNamedItemOrEmpty,
    tmnxOamPmCfgSessEthSrcMaName     TLNamedItemOrEmpty
}

tmnxOamPmCfgSessEthSrcMepId      OBJECT-TYPE
    SYNTAX      Dot1agCfmMepIdOrZero
    MAX-ACCESS  read-write
    STATUS      current
    DESCRIPTION
        "The value of tmnxOamPmCfgSessEthSrcMepId specifies the source Ethernet
         Maintenance association End Point (MEP) identifier to be used by the
         specified session.

         Zero indicates a value has not been configured."
    DEFVAL      { 0 }
    ::= { tmnxOamPmCfgSessEthEntry 1 }

tmnxOamPmCfgSessEthSrcMdIndex    OBJECT-TYPE
    SYNTAX      Unsigned32
    MAX-ACCESS  read-write
    STATUS      current
    DESCRIPTION
        "The value of tmnxOamPmCfgSessEthSrcMdIndex specifies the source
         Ethernet Maintenance Domain (MD) index to be used by the specified
         session.

         The source domain can be specified using tmnxOamPmCfgSessEthSrcMdName
         or tmnxOamPmCfgSessEthSrcMdIndex (not both).
         tmnxOamPmCfgSessEthSrcMdName is the preferred object for specifying
         the source domain.

         One of tmnxOamPmCfgSessEthSrcMdName and tmnxOamPmCfgSessEthSrcMdIndex
         should be assigned a non-default value. Otherwise, an attempt to start
         any test belonging to the session will fail.

         If specified, tmnxOamPmCfgSessEthSrcMdIndex should match a domain
         created using TIMETRA-IEEE8021-CFM-MIB::tmnxDot1agCfmMdMgmtRowStatus.
         Otherwise, the session's tests will fail.

         An attempt to change TIMETRA-SYSTEM-MIB::tmnxSysMgmtIfWriteMode.0 away
         from 'classic(1)' is blocked if any tmnxOamPmCfgSessEthSrcMdIndex has
         a non-default value.

         Zero indicates a value has not been configured."
    DEFVAL      { 0 }
    ::= { tmnxOamPmCfgSessEthEntry 2 }

tmnxOamPmCfgSessEthSrcMaIndex    OBJECT-TYPE
    SYNTAX      Unsigned32
    MAX-ACCESS  read-write
    STATUS      current
    DESCRIPTION
        "The value of tmnxOamPmCfgSessEthSrcMaIndex specifies the source
         Ethernet Maintenance Association (MA) index to be used by the
         specified session.

         The source association can be specified using
         tmnxOamPmCfgSessEthSrcMaName or tmnxOamPmCfgSessEthSrcMaIndex (not
         both).  tmnxOamPmCfgSessEthSrcMaName is the preferred object for
         specifying the source association.

         One of tmnxOamPmCfgSessEthSrcMaName and tmnxOamPmCfgSessEthSrcMaIndex
         should be assigned a non-default value. Otherwise, an attempt to start
         any test belonging to the session will fail.

         If specified, tmnxOamPmCfgSessEthSrcMaIndex should match an
         association created using
         TIMETRA-IEEE8021-CFM-MIB::tmnxDot1agCfmMaMgmtRowStatus. Otherwise, the
         session's tests will fail.

         An attempt to change TIMETRA-SYSTEM-MIB::tmnxSysMgmtIfWriteMode.0 away
         from 'classic(1)' is blocked if any tmnxOamPmCfgSessEthSrcMaIndex has
         a non-default value.

         Zero indicates a value has not been configured."
    DEFVAL      { 0 }
    ::= { tmnxOamPmCfgSessEthEntry 3 }

tmnxOamPmCfgSessEthPriority      OBJECT-TYPE
    SYNTAX      Unsigned32 (0..7)
    MAX-ACCESS  read-write
    STATUS      current
    DESCRIPTION
        "The value of tmnxOamPmCfgSessEthPriority specifies the value to be
         copied into the priority field when launching a test PDU for the
         specified session.

         The priority value also selects the forwarding class used to queue the
         launched test PDU on egress.  The mapping between forwarding class
         names and priority numbers is provided by TIMETRA-QOS-MIB::tFCValue."
    DEFVAL      { 0 }
    ::= { tmnxOamPmCfgSessEthEntry 4 }

tmnxOamPmCfgSessEthDestMacAddr   OBJECT-TYPE
    SYNTAX      MacAddress
    MAX-ACCESS  read-write
    STATUS      current
    DESCRIPTION
        "The value of tmnxOamPmCfgSessEthDestMacAddr specifies the destination
         MAC address for the specified session.

         A non-zero unicast destination MAC address is required in each test
         frame sent by each test belonging to the specified session.  The
         destination MAC address can be specified directly (using this object),
         or indirectly (using tmnxOamPmCfgSessEthRemoteMepId).

         Exactly one of tmnxOamPmCfgSessEthDestMacAddr and
         tmnxOamPmCfgSessEthRemoteMepId must be assigned a non-default value."
    DEFVAL      { '000000000000'H }
    ::= { tmnxOamPmCfgSessEthEntry 5 }

tmnxOamPmCfgSessEthRemoteMepId   OBJECT-TYPE
    SYNTAX      Dot1agCfmMepIdOrZero
    MAX-ACCESS  read-write
    STATUS      current
    DESCRIPTION
        "The value of tmnxOamPmCfgSessEthRemoteMepId specifies the remote
         Ethernet Maintenance association End Point (MEP) identifier to be used
         by the specified session.

         Zero indicates a value has not been configured.

         A non-zero unicast destination MAC address is required in each test
         frame sent by each test belonging to the specified session.  The
         destination MAC address can be specified directly (using
         tmnxOamPmCfgSessEthDestMacAddr), or indirectly (using this object).

         Exactly one of tmnxOamPmCfgSessEthDestMacAddr and
         tmnxOamPmCfgSessEthRemoteMepId must be assigned a non-default value.

         If this object is assigned a non-default value, SROS periodically
         searches TIMETRA-IEEE8021-CFM-MIB::tmnxDot1agCfmLearnedRmtMacTable to
         find the destination MAC address to use for each test belonging to
         this session.

         The search key is as follows: tmnxOamPmCfgSessEthSrcMdIndex,
         tmnxOamPmCfgSessEthSrcMaIndex, tmnxOamPmCfgSessEthSrcMepId,
         tmnxOamPmCfgSessEthRemoteMepId.

         If a search fails to find a destination MAC address, no test frames
         will be sent for the tests belonging to this session (at least until
         the next search is conducted).

         Using tmnxOamPmCfgSessEthRemoteMepId (instead of
         tmnxOamPmCfgSessEthDestMacAddr) has the following advantage: if the
         hardware hosting a test's far end is replaced (meaning a new
         destination MAC address is present), the test does not need to be
         reconfigured."
    DEFVAL      { 0 }
    ::= { tmnxOamPmCfgSessEthEntry 6 }

tmnxOamPmCfgSessEthSrcMdName     OBJECT-TYPE
    SYNTAX      TLNamedItemOrEmpty
    MAX-ACCESS  read-write
    STATUS      current
    DESCRIPTION
        "The value of tmnxOamPmCfgSessEthSrcMdName specifies the name of the
         source Ethernet Maintenance Domain (MD) to be used by the specified
         session.

         The source domain can be specified using tmnxOamPmCfgSessEthSrcMdName
         or tmnxOamPmCfgSessEthSrcMdIndex (not both).
         tmnxOamPmCfgSessEthSrcMdName is the preferred object for specifying
         the source domain.

         One of tmnxOamPmCfgSessEthSrcMdName and tmnxOamPmCfgSessEthSrcMdIndex
         should be assigned a non-default value. Otherwise, an attempt to start
         any test belonging to the session will fail.

         If specified, tmnxOamPmCfgSessEthSrcMdName should match a name
         configured using
         TIMETRA-IEEE8021-CFM-MIB::tmnxDot1agCfmMdMgmtAdminName.  Otherwise, the
         session's tests will fail.

         An empty string indicates a name has not been configured."
    DEFVAL      { "" }
    ::= { tmnxOamPmCfgSessEthEntry 7 }

tmnxOamPmCfgSessEthSrcMaName     OBJECT-TYPE
    SYNTAX      TLNamedItemOrEmpty
    MAX-ACCESS  read-write
    STATUS      current
    DESCRIPTION
        "The value of tmnxOamPmCfgSessEthSrcMaName specifies the name of the
         source Ethernet Maintenance Association (MA) to be used by the
         specified session.

         The source association can be specified using
         tmnxOamPmCfgSessEthSrcMaName or tmnxOamPmCfgSessEthSrcMaIndex (not
         both).  tmnxOamPmCfgSessEthSrcMaName is the preferred object for
         specifying the source association.

         One of tmnxOamPmCfgSessEthSrcMaName and tmnxOamPmCfgSessEthSrcMaIndex
         should be assigned a non-default value. Otherwise, an attempt to start
         any test belonging to the session will fail.

         If specified, tmnxOamPmCfgSessEthSrcMaName should match a name
         configured using
         TIMETRA-IEEE8021-CFM-MIB::tmnxDot1agCfmMaMgmtAdminName. Otherwise, the
         session's tests will fail.

         An empty string indicates a name has not been configured."
    DEFVAL      { "" }
    ::= { tmnxOamPmCfgSessEthEntry 8 }

tmnxOamPmCfgDelayDmmTable        OBJECT-TYPE
    SYNTAX      SEQUENCE OF TmnxOamPmCfgDelayDmmEntry
    MAX-ACCESS  not-accessible
    STATUS      current
    DESCRIPTION
        "tmnxOamPmCfgDelayDmmTable contains the configuration information for
         OAM Performance Monitoring Delay Measurement Message (DMM) tests."
    REFERENCE
        "MEF-35, 'Service OAM Performance Monitoring Implementation Agreement',
         Metro Ethernet Forum, April 2012, Section 7.1 'Frame Delay
         Measurements'"
    ::= { tmnxOamPmCfgTableObjs 5 }

tmnxOamPmCfgDelayDmmEntry        OBJECT-TYPE
    SYNTAX      TmnxOamPmCfgDelayDmmEntry
    MAX-ACCESS  not-accessible
    STATUS      current
    DESCRIPTION
        "tmnxOamPmCfgDelayDmmEntry contains the configuration information for
         one OAM Performance Monitoring Delay Measurement Message (DMM) test.

         Rows are created or destroyed by SNMP Set operations on
         tmnxOamPmCfgDelayDmmRowStatus.

         An attempt to change any value in a row (except
         tmnxOamPmCfgDelayDmmAdminStatus and tmnxOamPmCfgDelayDmmOnDmndStatus)
         will be rejected if tmnxOamPmCfgDelayDmmAdminStatus is 'enabled(1)'."
    INDEX       { tmnxOamPmCfgSessName }
    ::= { tmnxOamPmCfgDelayDmmTable 1 }

TmnxOamPmCfgDelayDmmEntry        ::= SEQUENCE
{
    tmnxOamPmCfgDelayDmmRowStatus    RowStatus,
    tmnxOamPmCfgDelayDmmAdminStatus  TmnxEnabledDisabled,
    tmnxOamPmCfgDelayDmmOnDmndStatus TmnxEnabledDisabledOrNA,
    tmnxOamPmCfgDelayDmmTestId       Unsigned32,
    tmnxOamPmCfgDelayDmmInterval     Unsigned32,
    tmnxOamPmCfgDelayDmmDataTlvSize  Unsigned32,
    tmnxOamPmCfgDelayDmmTestDuration Unsigned32,
    tmnxOamPmCfgDelayDmmRunTimeLeft  Unsigned32,
    tmnxOamPmCfgDelayDmmStrTmplName  TLNamedItemOrEmpty,
    tmnxOamPmCfgDelayDmmIsAutoTestId TruthValue,
    tmnxOamPmCfgDelayDmmTestIdInUse  Unsigned32
}

tmnxOamPmCfgDelayDmmRowStatus    OBJECT-TYPE
    SYNTAX      RowStatus
    MAX-ACCESS  read-create
    STATUS      current
    DESCRIPTION
        "The value of tmnxOamPmCfgDelayDmmRowStatus specifies the status of the
         configuration row for the specified session's DMM test.

         An attempt to create a row for a session with
         tmnxOamPmCfgSessTestFamily other than 'ethernet(1)' will be rejected."
    ::= { tmnxOamPmCfgDelayDmmEntry 1 }

tmnxOamPmCfgDelayDmmAdminStatus  OBJECT-TYPE
    SYNTAX      TmnxEnabledDisabled
    MAX-ACCESS  read-create
    STATUS      current
    DESCRIPTION
        "The value of tmnxOamPmCfgDelayDmmAdminStatus specifies whether or not
         the specified session's DMM test is administratively enabled.

         If the session type (tmnxOamPmCfgSessType) is 'proactive(1)', setting
         tmnxOamPmCfgDelayDmmAdminStatus to 'enabled(1)'/'disabled(2)'
         starts/stops the test.

         If the session type is 'onDemand(2)', see the DESCRIPTION clause for
         tmnxOamPmCfgDelayDmmOnDmndStatus for information on starting/stopping
         the test.

         An attempt to set this object to 'enabled(1)' will be rejected if the
         tmnxOamPmCfgSessEthTable row for the specified session has incomplete
         endpoint information for the test (e.g. if
         tmnxOamPmCfgSessEthDestMacAddr is the all-zeroes MAC address)."
    DEFVAL      { disabled }
    ::= { tmnxOamPmCfgDelayDmmEntry 2 }

tmnxOamPmCfgDelayDmmOnDmndStatus OBJECT-TYPE
    SYNTAX      TmnxEnabledDisabledOrNA
    MAX-ACCESS  read-create
    STATUS      current
    DESCRIPTION
        "The value of tmnxOamPmCfgDelayDmmOnDmndStatus specifies the status of
         the on-demand DMM test for the specified session.

         Values:
            'enabled(1)'
                Set by an SNMP manager to start an on-demand DMM test.  The test
                will start if tmnxOamPmCfgDelayDmmAdminStatus is 'enabled(1)'.
            'disabled(2)'
                Set by an SNMP manager to stop an on-demand DMM test.
                Set by SROS to indicate an on-demand DMM test has stopped
                running because the configured period for the test (i.e.
                tmnxOamPmCfgDelayDmmTestDuration) has ended.
                Set by SROS for an on-demand DMM test when
                tmnxOamPmCfgDelayDmmAdminStatus is set to 'disabled(2)'.
            'notApplicable(3)'
                This code point is the only acceptable value for a proactive
                DMM test.  An attempt to set this code point for an on-demand
                DMM test will be rejected.

         The default value is 'disabled(2)' for an on-demand DMM test, and
         'notApplicable(3)' for a proactive DMM test."
    ::= { tmnxOamPmCfgDelayDmmEntry 3 }

tmnxOamPmCfgDelayDmmTestId       OBJECT-TYPE
    SYNTAX      Unsigned32 (0..2147483647)
    MAX-ACCESS  read-create
    STATUS      current
    DESCRIPTION
        "The value of tmnxOamPmCfgDelayDmmTestId specifies the test identifier
         for the specified session's DMM test.

         When a Y.1731 DMM PDU is being built, the test identifier is copied
         into the PDU's Test ID TLV.

         When tmnxOamPmCfgDelayDmmIsAutoTestId is being set 'true(1)', the
         value of tmnxOamPmCfgDelayDmmTestId is not used and it must be set to
         0.

         An attempt to add a duplicate test identifier to this table will be
         rejected.

         Test identifier values larger than 2147483647 are reserved for
         internal use."
    REFERENCE
        "ITU-T G.8013/Y.1731, 'OAM functions and mechanisms for Ethernet based
         networks', 07/2011, Figure 9.14-3, 'Test ID TLV format', and Section
         9.15, 'DMM PDU'."
    DEFVAL      { 0 }
    ::= { tmnxOamPmCfgDelayDmmEntry 4 }

tmnxOamPmCfgDelayDmmInterval     OBJECT-TYPE
    SYNTAX      Unsigned32 (50 | 100 | 200 | 300 | 400 | 500 | 600 | 700 | 800 | 900 | 1000 | 10000)
    UNITS       "milliseconds"
    MAX-ACCESS  read-create
    STATUS      current
    DESCRIPTION
        "The value of tmnxOamPmCfgDelayDmmInterval specifies the elapsed time
         between transmission of Y.1731 DMM PDUs for the specified session's
         DMM test."
    DEFVAL      { 1000 }
    ::= { tmnxOamPmCfgDelayDmmEntry 5 }

tmnxOamPmCfgDelayDmmDataTlvSize  OBJECT-TYPE
    SYNTAX      Unsigned32 (0 | 3..2000)
    UNITS       "octets"
    MAX-ACCESS  read-create
    STATUS      current
    DESCRIPTION
        "The value of tmnxOamPmCfgDelayDmmDataTlvSize specifies the amount of
         padding to be added to each launched Y.1731 DMM PDU for the specified
         session's DMM test.

         Zero specifies that a Data TLV should not be added to each launched
         Y.1731 DMM PDU.

         A value larger than zero specifies the total size (including the
         header) of the Data TLV added to each launched Y.1731 DMM PDU."
    REFERENCE
        "ITU-T G.8013/Y.1731, 'OAM functions and mechanisms for Ethernet based
         networks', 07/2011, Figure 9.3-3, 'Data TLV format', and Section
         9.15, 'DMM PDU'."
    DEFVAL      { 0 }
    ::= { tmnxOamPmCfgDelayDmmEntry 6 }

tmnxOamPmCfgDelayDmmTestDuration OBJECT-TYPE
    SYNTAX      Unsigned32 (0..86400)
    UNITS       "seconds"
    MAX-ACCESS  read-create
    STATUS      current
    DESCRIPTION
        "The value of tmnxOamPmCfgDelayDmmTestDuration specifies the test
         duration for the specified session's DMM test.

         Zero specifies a test which runs until it is manually stopped.

         An attempt to set a non-zero value will be rejected if
         tmnxOamPmCfgSessType is 'proactive(1)'."
    DEFVAL      { 0 }
    ::= { tmnxOamPmCfgDelayDmmEntry 7 }

tmnxOamPmCfgDelayDmmRunTimeLeft  OBJECT-TYPE
    SYNTAX      Unsigned32 (0..86400)
    UNITS       "seconds"
    MAX-ACCESS  read-only
    STATUS      current
    DESCRIPTION
        "The value of tmnxOamPmCfgDelayDmmRunTimeLeft indicates the run time
         remaining for the specified session's DMM test.

         For example, suppose a DMM test has the following configuration:

         tmnxOamPmCfgSessType   tmnxOamPmCfgDelayDmmTestDuration
         --------------------   --------------------------------
         'onDemand(2)'          1000 (seconds)

         Then, when the DMM test is started (see
         tmnxOamPmCfgDelayDmmOnDmndStatus), tmnxOamPmCfgDelayDmmRunTimeLeft is
         initialized to 1000 seconds.  After a minute,
         tmnxOamPmCfgDelayDmmRunTimeLeft is 940 seconds.

         If tmnxOamPmCfgSessType is 'proactive(1)', zero is always returned
         (because a proactive test runs until it is manually stopped).

         If tmnxOamPmCfgSessType is 'onDemand(2)' and the test is stopped (see
         tmnxOamPmCfgDelayDmmOnDmndStatus), zero is returned (because the test
         is not running)."
    ::= { tmnxOamPmCfgDelayDmmEntry 8 }

tmnxOamPmCfgDelayDmmStrTmplName  OBJECT-TYPE
    SYNTAX      TLNamedItemOrEmpty
    MAX-ACCESS  read-create
    STATUS      current
    DESCRIPTION
        "The value of tmnxOamPmCfgDelayDmmStrTmplName specifies the name of the
         OAM-PM streaming template used by the specified DMM test.

         Streaming functionality is described in the DESCRIPTION clause of
         tmnxOamPmCfgStrTmplTable.

         If specified, tmnxOamPmCfgDelayDmmStrTmplName should match a template
         name created using tmnxOamPmCfgStrTmplRowStatus.  Otherwise,
         streaming will not work.

         An empty string indicates a template name has not been configured."
    DEFVAL      { "" }
    ::= { tmnxOamPmCfgDelayDmmEntry 9 }

tmnxOamPmCfgDelayDmmIsAutoTestId OBJECT-TYPE
    SYNTAX      TruthValue
    MAX-ACCESS  read-create
    STATUS      current
    DESCRIPTION
        "The value of the object tmnxOamPmCfgDelayDmmIsAutoTestId specifies
         whether the system auto assigns an available test identifier to be
         used for this session's DMM test."
    DEFVAL      { false }
    ::= { tmnxOamPmCfgDelayDmmEntry 10 }

tmnxOamPmCfgDelayDmmTestIdInUse  OBJECT-TYPE
    SYNTAX      Unsigned32 (0..4294967295)
    MAX-ACCESS  read-only
    STATUS      current
    DESCRIPTION
        "The value of tmnxOamPmCfgDelayDmmTestIdInUse indicates the test
         identifier copied into the Test ID TLV of the Y.1731 DMM PDUs."
    REFERENCE
        "ITU-T G.8013/Y.1731, 'OAM functions and mechanisms for Ethernet based
         networks', 07/2011, Figure 9.14-3, 'Test ID TLV format', and Section
         9.15, 'DMM PDU'."
    ::= { tmnxOamPmCfgDelayDmmEntry 11 }

tmnxOamPmCfgLossSlmTable         OBJECT-TYPE
    SYNTAX      SEQUENCE OF TmnxOamPmCfgLossSlmEntry
    MAX-ACCESS  not-accessible
    STATUS      current
    DESCRIPTION
        "tmnxOamPmCfgLossSlmTable contains the configuration information for
         OAM Performance Monitoring Synthetic Loss Message (SLM) tests."
    REFERENCE
        "MEF-35, 'Service OAM Performance Monitoring Implementation Agreement',
         Metro Ethernet Forum, April 2012, Section 7.2 'Frame Loss
         Measurements'"
    ::= { tmnxOamPmCfgTableObjs 6 }

tmnxOamPmCfgLossSlmEntry         OBJECT-TYPE
    SYNTAX      TmnxOamPmCfgLossSlmEntry
    MAX-ACCESS  not-accessible
    STATUS      current
    DESCRIPTION
        "tmnxOamPmCfgLossSlmEntry contains the configuration information for
         one OAM Performance Monitoring Synthetic Loss Message (SLM) test.

         Rows are created or destroyed by SNMP Set operations on
         tmnxOamPmCfgLossSlmRowStatus.

         An attempt to change any value in a row (except
         tmnxOamPmCfgLossSlmAdminStatus and tmnxOamPmCfgLossSlmOnDmndStatus)
         will be rejected if tmnxOamPmCfgLossSlmAdminStatus is 'enabled(1)'.

         The following objects must all be set together in one SNMP Set PDU:
            tmnxOamPmCfgLossSlmChliThreshold,
            tmnxOamPmCfgLossSlmConsecDeltaTs,
            tmnxOamPmCfgLossSlmInterval, and
            tmnxOamPmCfgLossSlmTxFrmsPerDelT."
    INDEX       { tmnxOamPmCfgSessName }
    ::= { tmnxOamPmCfgLossSlmTable 1 }

TmnxOamPmCfgLossSlmEntry         ::= SEQUENCE
{
    tmnxOamPmCfgLossSlmRowStatus     RowStatus,
    tmnxOamPmCfgLossSlmAdminStatus   TmnxEnabledDisabled,
    tmnxOamPmCfgLossSlmOnDmndStatus  TmnxEnabledDisabledOrNA,
    tmnxOamPmCfgLossSlmTestId        Unsigned32,
    tmnxOamPmCfgLossSlmInterval      Unsigned32,
    tmnxOamPmCfgLossSlmDataTlvSize   Unsigned32,
    tmnxOamPmCfgLossSlmTxFrmsPerDelT Unsigned32,
    tmnxOamPmCfgLossSlmConsecDeltaTs Unsigned32,
    tmnxOamPmCfgLossSlmChliThreshold Unsigned32,
    tmnxOamPmCfgLossSlmFlrThreshold  Unsigned32,
    tmnxOamPmCfgLossSlmTestDuration  Unsigned32,
    tmnxOamPmCfgLossSlmRunTimeLeft   Unsigned32,
    tmnxOamPmCfgLossSlmHliForceCount TruthValue,
    tmnxOamPmCfgLossSlmIsAutoTestId  TruthValue,
    tmnxOamPmCfgLossSlmTestIdInUse   Unsigned32
}

tmnxOamPmCfgLossSlmRowStatus     OBJECT-TYPE
    SYNTAX      RowStatus
    MAX-ACCESS  read-create
    STATUS      current
    DESCRIPTION
        "The value of tmnxOamPmCfgLossSlmRowStatus specifies the status of the
         configuration row for the specified session's SLM test.

         An attempt to create a row for a session with
         tmnxOamPmCfgSessTestFamily other than 'ethernet(1)' will be rejected."
    ::= { tmnxOamPmCfgLossSlmEntry 1 }

tmnxOamPmCfgLossSlmAdminStatus   OBJECT-TYPE
    SYNTAX      TmnxEnabledDisabled
    MAX-ACCESS  read-create
    STATUS      current
    DESCRIPTION
        "The value of tmnxOamPmCfgLossSlmAdminStatus specifies whether or not
         the specified session's SLM test is administratively enabled.

         If the session type (tmnxOamPmCfgSessType) is 'proactive(1)', setting
         tmnxOamPmCfgLossSlmAdminStatus to 'enabled(1)'/'disabled(2)'
         starts/stops the test.

         If the session type is 'onDemand(2)', see the DESCRIPTION clause for
         tmnxOamPmCfgLossSlmOnDmndStatus for information on starting/stopping
         the test.

         An attempt to set this object to 'enabled(1)' will be rejected if the
         tmnxOamPmCfgSessEthTable row for the specified session has incomplete
         endpoint information for the test (e.g. if
         tmnxOamPmCfgSessEthDestMacAddr is the all-zeroes MAC address)."
    DEFVAL      { disabled }
    ::= { tmnxOamPmCfgLossSlmEntry 2 }

tmnxOamPmCfgLossSlmOnDmndStatus  OBJECT-TYPE
    SYNTAX      TmnxEnabledDisabledOrNA
    MAX-ACCESS  read-create
    STATUS      current
    DESCRIPTION
        "The value of tmnxOamPmCfgLossSlmOnDmndStatus specifies the status of
         the on-demand SLM test for the specified session.

         Values:
            'enabled(1)'
                Set by an SNMP manager to start an on-demand SLM test.  The test
                will start if tmnxOamPmCfgLossSlmAdminStatus is 'enabled(1)'.
            'disabled(2)'
                Set by an SNMP manager to stop an on-demand SLM test.
                Set by SROS to indicate an on-demand SLM test has stopped
                running because the configured period for the test (i.e.
                tmnxOamPmCfgLossSlmTestDuration) has ended.
                Set by SROS for an on-demand SLM test when
                tmnxOamPmCfgLossSlmAdminStatus is set to 'disabled(2)'.
            'notApplicable(3)'
                This code point is the only acceptable value for a proactive SLM
                test.  An attempt to set this code point for an on-demand SLM
                test will be rejected.

         The default value is 'disabled(2)' for an on-demand SLM test, and
         'notApplicable(3)' for a proactive SLM test."
    ::= { tmnxOamPmCfgLossSlmEntry 3 }

tmnxOamPmCfgLossSlmTestId        OBJECT-TYPE
    SYNTAX      Unsigned32 (0..2147483647)
    MAX-ACCESS  read-create
    STATUS      current
    DESCRIPTION
        "The value of tmnxOamPmCfgLossSlmTestId specifies the test identifier
         for the specified session's SLM test.

         When a Y.1731 SLM PDU is being built, the test identifier is copied
         into the PDU's Test ID field.

         When tmnxOamPmCfgLossSlmIsAutoTestId is being set 'true(1)', the value
         of tmnxOamPmCfgLossSlmTestId is not used and it must be set to 0.

         An attempt to add a duplicate test identifier to this table will be
         rejected.

         Test identifier values larger than 2147483647 are reserved for
         internal use."
    REFERENCE
        "ITU-T G.8013/Y.1731, 'OAM functions and mechanisms for Ethernet based
         networks', 07/2011, Section 9.22, 'SLM PDU'."
    DEFVAL      { 0 }
    ::= { tmnxOamPmCfgLossSlmEntry 4 }

tmnxOamPmCfgLossSlmInterval      OBJECT-TYPE
    SYNTAX      Unsigned32 (50 | 100 | 200 | 300 | 400 | 500 | 600 | 700 | 800 | 900 | 1000)
    UNITS       "milliseconds"
    MAX-ACCESS  read-create
    STATUS      current
    DESCRIPTION
        "The value of tmnxOamPmCfgLossSlmInterval specifies the elapsed time
         between transmission of Y.1731 SLM PDUs for the specified session's
         SLM test."
    DEFVAL      { 100 }
    ::= { tmnxOamPmCfgLossSlmEntry 5 }

tmnxOamPmCfgLossSlmDataTlvSize   OBJECT-TYPE
    SYNTAX      Unsigned32 (0 | 3..2000)
    UNITS       "octets"
    MAX-ACCESS  read-create
    STATUS      current
    DESCRIPTION
        "The value of tmnxOamPmCfgLossSlmDataTlvSize specifies the amount of
         padding to be added to each launched Y.1731 SLM PDU for the specified
         session's SLM test.

         Zero specifies that a Data TLV should not be added to each launched
         Y.1731 SLM PDU.

         A value larger than zero specifies the total size (including the
         header) of the Data TLV added to each launched Y.1731 SLM PDU."
    REFERENCE
        "ITU-T G.8013/Y.1731, 'OAM functions and mechanisms for Ethernet based
         networks', 07/2011, Figure 9.3-3, 'Data TLV format', and Section
         9.22, 'SLM PDU'."
    DEFVAL      { 0 }
    ::= { tmnxOamPmCfgLossSlmEntry 6 }

tmnxOamPmCfgLossSlmTxFrmsPerDelT OBJECT-TYPE
    SYNTAX      Unsigned32 (1..50)
    UNITS       "frames"
    MAX-ACCESS  read-create
    STATUS      current
    DESCRIPTION
        "The value of tmnxOamPmCfgLossSlmTxFrmsPerDelT specifies the number of
         Y.1731 SLM frames to send in one MEF-35 'delta_t' (also known as
         'Small Time Interval') for the specified session's SLM test.

         Expressed in milliseconds,
         delta_t =
            tmnxOamPmCfgLossSlmTxFrmsPerDelT *
            tmnxOamPmCfgLossSlmInterval."
    REFERENCE
        "MEF-35, 'Service OAM Performance Monitoring Implementation Agreement',
         Metro Ethernet Forum, April 2012, Section 10.2 'Single-Ended Synthetic
         Loss Function for Frame Loss Ratio (FLR) and Availability'."
    DEFVAL      { 10 }
    ::= { tmnxOamPmCfgLossSlmEntry 7 }

tmnxOamPmCfgLossSlmConsecDeltaTs OBJECT-TYPE
    SYNTAX      Unsigned32 (2..10)
    MAX-ACCESS  read-create
    STATUS      current
    DESCRIPTION
        "The value of tmnxOamPmCfgLossSlmConsecDeltaTs specifies the number of
         consecutive MEF-35 'delta_t's (also known as 'Small Time Intervals')
         which constitute a MEF-35 'Availability Window' for the specified
         session's SLM test.

         The duration of an Availability Window (in milliseconds) is
         tmnxOamPmCfgLossSlmTxFrmsPerDelT * tmnxOamPmCfgLossSlmInterval *
         tmnxOamPmCfgLossSlmConsecDeltaTs.  An attempt to change the duration of
         an Availability Window to more than 10,000 milliseconds will be
         rejected.

         An attempt to change tmnxOamPmCfgLossSlmConsecDeltaTs to a value less
         than or equal to tmnxOamPmCfgLossSlmChliThreshold will be rejected."
    REFERENCE
        "MEF-35, 'Service OAM Performance Monitoring Implementation Agreement',
         Metro Ethernet Forum, April 2012, Section 10.2 'Single-Ended Synthetic
         Loss Function for Frame Loss Ratio (FLR) and Availability'."
    DEFVAL      { 10 }
    ::= { tmnxOamPmCfgLossSlmEntry 8 }

tmnxOamPmCfgLossSlmChliThreshold OBJECT-TYPE
    SYNTAX      Unsigned32 (1..9)
    MAX-ACCESS  read-create
    STATUS      current
    DESCRIPTION
        "The value of tmnxOamPmCfgLossSlmChliThreshold specifies the MEF-35
         Consecutive High Loss Interval (CHLI) threshold for the specified
         session's SLM test.

         An attempt to change tmnxOamPmCfgLossSlmChliThreshold to a value
         greater than or equal to tmnxOamPmCfgLossSlmConsecDeltaTs will be
         rejected."
    REFERENCE
        "MEF-35, 'Service OAM Performance Monitoring Implementation Agreement',
         Metro Ethernet Forum, April 2012, Section 10.2 'Single-Ended Synthetic
         Loss Function for Frame Loss Ratio (FLR) and Availability'."
    DEFVAL      { 5 }
    ::= { tmnxOamPmCfgLossSlmEntry 9 }

tmnxOamPmCfgLossSlmFlrThreshold  OBJECT-TYPE
    SYNTAX      Unsigned32 (0..100)
    UNITS       "percent"
    MAX-ACCESS  read-create
    STATUS      current
    DESCRIPTION
        "The value of tmnxOamPmCfgLossSlmFlrThreshold specifies the MEF-35
         Frame Loss Ratio (FLR) threshold for the specified session's SLM test.

         The FLR threshold is used to decide if a MEF-35 Small Time Interval
         (also known as delta_t) is Available or Unavailable."
    REFERENCE
        "MEF-35, 'Service OAM Performance Monitoring Implementation Agreement',
         Metro Ethernet Forum, April 2012, Section 10.2 'Single-Ended Synthetic
         Loss Function for Frame Loss Ratio (FLR) and Availability'."
    DEFVAL      { 50 }
    ::= { tmnxOamPmCfgLossSlmEntry 10 }

tmnxOamPmCfgLossSlmTestDuration  OBJECT-TYPE
    SYNTAX      Unsigned32 (0..86400)
    UNITS       "seconds"
    MAX-ACCESS  read-create
    STATUS      current
    DESCRIPTION
        "The value of tmnxOamPmCfgLossSlmTestDuration specifies the test
         duration for the specified session's SLM test.

         Zero specifies a test which runs until it is manually stopped.

         An attempt to set a non-zero value will be rejected if
         tmnxOamPmCfgSessType is 'proactive(1)'."
    DEFVAL      { 0 }
    ::= { tmnxOamPmCfgLossSlmEntry 11 }

tmnxOamPmCfgLossSlmRunTimeLeft   OBJECT-TYPE
    SYNTAX      Unsigned32 (0..86400)
    UNITS       "seconds"
    MAX-ACCESS  read-only
    STATUS      current
    DESCRIPTION
        "The value of tmnxOamPmCfgLossSlmRunTimeLeft indicates the run time
         remaining for the specified session's SLM test.

         For example, suppose an SLM test has the following configuration:

         tmnxOamPmCfgSessType   tmnxOamPmCfgLossSlmTestDuration
         --------------------   --------------------------------
         'onDemand(2)'          1000 (seconds)

         Then, when the SLM test is started (see
         tmnxOamPmCfgLossSlmOnDmndStatus), tmnxOamPmCfgLossSlmRunTimeLeft is
         initialized to 1000 seconds.  After a minute,
         tmnxOamPmCfgLossSlmRunTimeLeft is 940 seconds.

         If tmnxOamPmCfgSessType is 'proactive(1)', zero is always returned
         (because a proactive test runs until it is manually stopped).

         If tmnxOamPmCfgSessType is 'onDemand(2)' and the test is stopped (see
         tmnxOamPmCfgLossSlmOnDmndStatus), zero is returned (because the test
         is not running)."
    ::= { tmnxOamPmCfgLossSlmEntry 12 }

tmnxOamPmCfgLossSlmHliForceCount OBJECT-TYPE
    SYNTAX      TruthValue
    MAX-ACCESS  read-create
    STATUS      current
    DESCRIPTION
        "The value of tmnxOamPmCfgLossSlmHliForceCount specifies whether or not
         to count High Loss Intervals (HLIs) and Consecutive High Loss
         Intervals (CHLIs) when the SLM test's MEF-35 Availability state is
         Unavailable.

         'true(1)' breaks compliance with MEF-35 by ensuring HLIs and CHLIs are
         counted in Unavailable periods.

         'false(2)' maintains compliance with MEF-35 by preventing HLIs and
         CHLIs from being counted in Unavailable periods.

         SLM HLI and CHLI counts can be read using the following objects:
            tmnxOamPmStsLossSlmChliBwd,
            tmnxOamPmStsLossSlmChliFwd,
            tmnxOamPmStsLossSlmHliBwd,
            tmnxOamPmStsLossSlmHliFwd."
    REFERENCE
        "MEF-35, 'Service OAM Performance Monitoring Implementation Agreement',
         Metro Ethernet Forum, April 2012, Section 9.2.5 'Measurement Behavior
         During Periods of Unavailability and Maintenance Intervals'"
    DEFVAL      { false }
    ::= { tmnxOamPmCfgLossSlmEntry 13 }

tmnxOamPmCfgLossSlmIsAutoTestId  OBJECT-TYPE
    SYNTAX      TruthValue
    MAX-ACCESS  read-create
    STATUS      current
    DESCRIPTION
        "The value of the object tmnxOamPmCfgLossSlmIsAutoTestId specifies
         whether the system auto assigns an available test identifier to be
         used for this session's SLM test."
    DEFVAL      { false }
    ::= { tmnxOamPmCfgLossSlmEntry 14 }

tmnxOamPmCfgLossSlmTestIdInUse   OBJECT-TYPE
    SYNTAX      Unsigned32 (0..4294967295)
    MAX-ACCESS  read-only
    STATUS      current
    DESCRIPTION
        "The value of tmnxOamPmCfgLossSlmTestIdInUse indicates the test
         identifier copied into the Test ID field of the Y.1731 SLM PDUs."
    REFERENCE
        "ITU-T G.8013/Y.1731, 'OAM functions and mechanisms for Ethernet based
         networks', 07/2011, Section 9.22, 'SLM PDU'."
    ::= { tmnxOamPmCfgLossSlmEntry 15 }

tmnxOamPmCfgMeasIntvlTable       OBJECT-TYPE
    SYNTAX      SEQUENCE OF TmnxOamPmCfgMeasIntvlEntry
    MAX-ACCESS  not-accessible
    STATUS      current
    DESCRIPTION
        "tmnxOamPmCfgMeasIntvlTable contains the configuration information for
         OAM Performance Monitoring measurement intervals."
    REFERENCE
        "MEF-35, 'Service OAM Performance Monitoring Implementation Agreement',
         Metro Ethernet Forum, April 2012, Section 9.1.6, 'Measurement
         Intervals'"
    ::= { tmnxOamPmCfgTableObjs 7 }

tmnxOamPmCfgMeasIntvlEntry       OBJECT-TYPE
    SYNTAX      TmnxOamPmCfgMeasIntvlEntry
    MAX-ACCESS  not-accessible
    STATUS      current
    DESCRIPTION
        "tmnxOamPmCfgMeasIntvlEntry contains the configuration information for
         the OAM Performance Monitoring measurement interval associated with
         the specified session and measurement interval duration.

         Rows are created or destroyed by SNMP Set operations on
         tmnxOamPmCfgMeasIntvlRowStatus."
    INDEX       {
        tmnxOamPmCfgSessName,
        tmnxOamPmCfgMeasIntvlDuration
    }
    ::= { tmnxOamPmCfgMeasIntvlTable 1 }

TmnxOamPmCfgMeasIntvlEntry       ::= SEQUENCE
{
    tmnxOamPmCfgMeasIntvlDuration    TmnxOamPmCfgMeasIntervalDuration,
    tmnxOamPmCfgMeasIntvlRowStatus   RowStatus,
    tmnxOamPmCfgMeasIntvlAccntPolicy Unsigned32,
    tmnxOamPmCfgMeasIntvlsStored     Unsigned32,
    tmnxOamPmCfgMeasIntvlBoundaryTyp INTEGER,
    tmnxOamPmCfgMeasIntvlClockOffset Unsigned32,
    tmnxOamPmCfgMeasIntvlDelayTCAs   TmnxEnabledDisabled,
    tmnxOamPmCfgMeasIntvlLossTCAs    TmnxEnabledDisabled,
    tmnxOamPmCfgMeasIntvlTCAs        TmnxEnabledDisabled
}

tmnxOamPmCfgMeasIntvlDuration    OBJECT-TYPE
    SYNTAX      TmnxOamPmCfgMeasIntervalDuration
    MAX-ACCESS  not-accessible
    STATUS      current
    DESCRIPTION
        "The value of tmnxOamPmCfgMeasIntvlDuration specifies the duration of
         the measurement interval (e.g. 'mi15Minutes(2)') to be read or
         configured."
    ::= { tmnxOamPmCfgMeasIntvlEntry 1 }

tmnxOamPmCfgMeasIntvlRowStatus   OBJECT-TYPE
    SYNTAX      RowStatus
    MAX-ACCESS  read-create
    STATUS      current
    DESCRIPTION
        "The value of tmnxOamPmCfgMeasIntvlRowStatus specifies the status of
         the configuration row for the specified session and measurement
         interval duration."
    ::= { tmnxOamPmCfgMeasIntvlEntry 2 }

tmnxOamPmCfgMeasIntvlAccntPolicy OBJECT-TYPE
    SYNTAX      Unsigned32 (0 | 1..99)
    MAX-ACCESS  read-create
    STATUS      current
    DESCRIPTION
        "The value of tmnxOamPmCfgMeasIntvlAccntPolicy specifies the accounting
         policy for the specified session and measurement interval duration.

         Zero specifies that the specified session and measurement interval
         duration has no associated accounting policy."
    DEFVAL      { 0 }
    ::= { tmnxOamPmCfgMeasIntvlEntry 3 }

tmnxOamPmCfgMeasIntvlsStored     OBJECT-TYPE
    SYNTAX      Unsigned32 (1..96)
    MAX-ACCESS  read-create
    STATUS      current
    DESCRIPTION
        "The value of tmnxOamPmCfgMeasIntvlsStored specifies the maximum number
         of historical measurement intervals which can be read using SNMP Get
         operations.

         For example, suppose tmnxOamPmCfgMeasIntvlsStored is 32 in the row
         indexed by {'mySess1', 'mi15Minutes(2)'}.  Suppose 'mySess1' has a DMM
         test which has been running for at least 8 hours (i.e. 15
         minutes/interval * 32 intervals).  Then, the number of SNMP accessible
         15 minute intervals for the test is shown in the following table.

         Test State  Number of SNMP Accessible 15 Minute Intervals
         ----------  -----------------------------------------------------------
         running     33 (i.e. 32 historical intervals, and the current interval)
         stopped     32 (i.e. 32 historical intervals)

         At the moment when a test is stopped, the current interval becomes the
         newest historical interval.  If that makes the total number of
         historical intervals larger than tmnxOamPmCfgMeasIntvlsStored, the
         oldest historical interval is made SNMP inaccessible.

         In a typical configuration, older statistics are recorded in a local
         file (see tmnxOamPmCfgMeasIntvlAccntPolicy).  Statistics in the file
         are not SNMP accessible.

         The range and default of tmnxOamPmCfgMeasIntvlsStored varies with the
         row's measurement interval duration index value, as follows.

         tmnxOamPmCfgMeasIntvlDuration Intvls Stored Range Intvls Stored Default
         ----------------------------- ------------------- ---------------------
         'mi1Minute(6)'                              1..96                    32
         'mi5Minutes(5)'                             1..96                    32
         'mi15Minutes(2)'                            1..96                    32
         'mi1Hour(3)'                                1..24                     8
         'mi1Day(4)'                                  1..1                     1

         The following limit is enforced per session (where 'S' is the session
         name):
            tmnxOamPmCfgMeasIntvlsStored.S.mi1Minute(6) +
            tmnxOamPmCfgMeasIntvlsStored.S.mi5Minutes(5) +
            tmnxOamPmCfgMeasIntvlsStored.S.mi15Minutes(2) <= 96."
    ::= { tmnxOamPmCfgMeasIntvlEntry 4 }

tmnxOamPmCfgMeasIntvlBoundaryTyp OBJECT-TYPE
    SYNTAX      INTEGER {
        clockAligned (1),
        testRelative (2)
    }
    MAX-ACCESS  read-create
    STATUS      current
    DESCRIPTION
        "The value of tmnxOamPmCfgMeasIntvlBoundaryTyp specifies whether or not
         the start of each measurement interval is aligned to the wall clock.

         Values:
            clockAligned(1)
                For example, if the specified tmnxOamPmCfgMeasIntvlDuration is
                'mi1Day(4)', the first measurement interval for the test will
                start at midnight (UTC).  See the DESCRIPTION clause for
                tmnxOamPmCfgMeasIntvlClockOffset for additional information.
            testRelative(2)
                The first measurement interval for the test will start when the
                test starts."
    DEFVAL      { clockAligned }
    ::= { tmnxOamPmCfgMeasIntvlEntry 5 }

tmnxOamPmCfgMeasIntvlClockOffset OBJECT-TYPE
    SYNTAX      Unsigned32 (0..86399)
    UNITS       "seconds"
    MAX-ACCESS  read-create
    STATUS      current
    DESCRIPTION
        "The value of tmnxOamPmCfgMeasIntvlClockOffset specifies the offset (in
         seconds) for the start of a measurement interval.

         For example, the following set of values will result in each one day
         measurement interval for the specified session starting 6 seconds
         after midnight (UTC).

         Object                            Value
         --------------------------------  -----------------
         tmnxOamPmCfgMeasIntvlDuration     'mi1Day(4)'
         tmnxOamPmCfgMeasIntvlBoundaryTyp  'clockAligned(1)'
         tmnxOamPmCfgMeasIntvlClockOffset  6

         This value must be less than tmnxOamPmCfgMeasIntvlDuration (expressed
         in seconds).  For example, if tmnxOamPmCfgMeasIntvlDuration is
         'mi15Minutes(2)' (i.e. 900 seconds), this value must be in the range
         0..899.

         An attempt to set this object to a non-zero value when
         tmnxOamPmCfgMeasIntvlBoundaryTyp is 'testRelative(2)' will be
         rejected."
    DEFVAL      { 0 }
    ::= { tmnxOamPmCfgMeasIntvlEntry 6 }

tmnxOamPmCfgMeasIntvlDelayTCAs   OBJECT-TYPE
    SYNTAX      TmnxEnabledDisabled
    MAX-ACCESS  read-create
    STATUS      current
    DESCRIPTION
        "The value of tmnxOamPmCfgMeasIntvlDelayTCAs specifies the
         administrative state of delay Threshold Crossing Alerts (TCAs) for
         this measurement interval.

         Delay TCAs are administratively enabled if both
         tmnxOamPmCfgMeasIntvlDelayTCAs and tmnxOamPmCfgMeasIntvlTCAs are
         'enabled(1)'.

         Delay TCAs are configured using tmnxOamPmCfgThrDelayTable."
    DEFVAL      { disabled }
    ::= { tmnxOamPmCfgMeasIntvlEntry 7 }

tmnxOamPmCfgMeasIntvlLossTCAs    OBJECT-TYPE
    SYNTAX      TmnxEnabledDisabled
    MAX-ACCESS  read-create
    STATUS      current
    DESCRIPTION
        "The value of tmnxOamPmCfgMeasIntvlLossTCAs specifies the
         administrative state of loss Threshold Crossing Alerts (TCAs) for this
         measurement interval.

         Loss TCAs are administratively enabled if both
         tmnxOamPmCfgMeasIntvlLossTCAs and tmnxOamPmCfgMeasIntvlTCAs are
         'enabled(1)'.

         Loss TCAs are configured using tmnxOamPmCfgThrLossFwBwTable and
         tmnxOamPmCfgThrLossFwBwAgTable."
    DEFVAL      { disabled }
    ::= { tmnxOamPmCfgMeasIntvlEntry 8 }

tmnxOamPmCfgMeasIntvlTCAs        OBJECT-TYPE
    SYNTAX      TmnxEnabledDisabled
    MAX-ACCESS  read-create
    STATUS      current
    DESCRIPTION
        "The value of tmnxOamPmCfgMeasIntvlTCAs specifies the administrative
         state of Threshold Crossing Alerts (TCAs) for this measurement
         interval.

         Delay TCAs are administratively enabled if both
         tmnxOamPmCfgMeasIntvlDelayTCAs and tmnxOamPmCfgMeasIntvlTCAs are
         'enabled(1)'.

         Loss TCAs are administratively enabled if both
         tmnxOamPmCfgMeasIntvlLossTCAs and tmnxOamPmCfgMeasIntvlTCAs are
         'enabled(1)'."
    DEFVAL      { disabled }
    ::= { tmnxOamPmCfgMeasIntvlEntry 9 }

tmnxOamPmCfgSessIpTable          OBJECT-TYPE
    SYNTAX      SEQUENCE OF TmnxOamPmCfgSessIpEntry
    MAX-ACCESS  not-accessible
    STATUS      current
    DESCRIPTION
        "tmnxOamPmCfgSessIpTable contains configuration for OAM Performance
         Monitoring IP sessions."
    ::= { tmnxOamPmCfgTableObjs 8 }

tmnxOamPmCfgSessIpEntry          OBJECT-TYPE
    SYNTAX      TmnxOamPmCfgSessIpEntry
    MAX-ACCESS  not-accessible
    STATUS      current
    DESCRIPTION
        "tmnxOamPmCfgSessIpEntry contains configuration shared by
         tests belonging to the specified OAM Performance Monitoring
         IP session.  Currently, an IP session can only have one test
         (i.e. a TWAMP-Light or STAMP test), so there is no sharing.

         A row is created when a tmnxOamPmCfgSessTable row is created with
         tmnxOamPmCfgSessTestFamily = 'ip(2)'.

         A row is destroyed when a tmnxOamPmCfgSessTable row with
         tmnxOamPmCfgSessTestFamily = 'ip(2)' is destroyed.

         An attempt to change a value in a row for a particular session will be
         rejected if an administratively enabled test (e.g. a TWAMP-Light test)
         exists for the session."
    INDEX       { tmnxOamPmCfgSessName }
    ::= { tmnxOamPmCfgSessIpTable 1 }

TmnxOamPmCfgSessIpEntry          ::= SEQUENCE
{
    tmnxOamPmCfgSessIpServiceId      Unsigned32,
    tmnxOamPmCfgSessIpSrcAddressType InetAddressType,
    tmnxOamPmCfgSessIpSrcAddress     InetAddress,
    tmnxOamPmCfgSessIpDstAddressType InetAddressType,
    tmnxOamPmCfgSessIpDstAddress     InetAddress,
    tmnxOamPmCfgSessIpDstUdpPort     InetPortNumber,
    tmnxOamPmCfgSessIpBypassRouting  TruthValue,
    tmnxOamPmCfgSessIpEgressIfName   TNamedItemOrEmpty,
    tmnxOamPmCfgSessIpNhAddressType  InetAddressType,
    tmnxOamPmCfgSessIpNhAddress      InetAddress,
    tmnxOamPmCfgSessIpForwardClass   TFCName,
    tmnxOamPmCfgSessIpProfile        TProfile,
    tmnxOamPmCfgSessIpTtl            Unsigned32,
    tmnxOamPmCfgSessIpSrcUdpPort     InetPortNumber,
    tmnxOamPmCfgSessIpDoNotFragment  TruthValue,
    tmnxOamPmCfgSessIpDscpName       TDSCPNameOrEmpty,
    tmnxOamPmCfgSessIpDscpEgrRemark  TruthValue,
    tmnxOamPmCfgSessIpPadPattern     Integer32,
    tmnxOamPmCfgSessIpRouterInstName TLNamedItemOrEmpty,
    tmnxOamPmCfgSessIpTunnelType     INTEGER,
    tmnxOamPmCfgSessIpTunnelTypeMpls INTEGER,
    tmnxOamPmCfgSessIpLspName        TLNamedItemOrEmpty,
    tmnxOamPmCfgSessIpLspTemplName   TNamedItemOrEmpty,
    tmnxOamPmCfgSessIpLspFromAddrTyp InetAddressType,
    tmnxOamPmCfgSessIpLspFromAddress InetAddress,
    tmnxOamPmCfgSessIpLspToAddrType  InetAddressType,
    tmnxOamPmCfgSessIpLspToAddress   InetAddress,
    tmnxOamPmCfgSessIpLspIgpInstance TmnxIgpInstance,
    tmnxOamPmCfgSessIpLspDstPfxType  InetAddressType,
    tmnxOamPmCfgSessIpLspDstPfx      InetAddress,
    tmnxOamPmCfgSessIpLspDstPfxLen   InetAddressPrefixLength,
    tmnxOamPmCfgSessIpFlexAlgoId     TmnxFlexAlgoIdOrZero,
    tmnxOamPmCfgSessIpSrPolicyColor  Unsigned32,
    tmnxOamPmCfgSessIpSrPlcyEnPtAddT InetAddressType,
    tmnxOamPmCfgSessIpSrPlcyEnPtAddr InetAddress,
    tmnxOamPmCfgSessIpSrPlcySegList  Unsigned32
}

tmnxOamPmCfgSessIpServiceId      OBJECT-TYPE
    SYNTAX      Unsigned32 (0..2147483647)
    MAX-ACCESS  read-write
    STATUS      current
    DESCRIPTION
        "The value of tmnxOamPmCfgSessIpServiceId specifies the virtual router
         to be used by IP tests belonging to the specified session.

         Zero specifies the Base virtual router, as defined in
         TIMETRA-VRTR-MIB::vRtrConfTable.

         A value larger than zero should be the service identifier of a VPRN
         service (as configured by setting TIMETRA-SERV-MIB::svcType to
         'vprn(4)').

         The virtual router to be used by the session's tests can be specified
         using tmnxOamPmCfgSessIpServiceId or tmnxOamPmCfgSessIpRouterInstName
         (not both).  tmnxOamPmCfgSessIpRouterInstName is the preferred
         parameter for specifying the virtual router.

         MPLS tunneling can only be configured with the Base router.
         So, the following combination is not supported:
             tmnxOamPmCfgSessIpTunnelType = 'mpls(2)'
             AND (
             tmnxOamPmCfgSessIpRouterInstName != 'Base' OR
             tmnxOamPmCfgSessIpServiceId != 0)."
    DEFVAL      { 0 }
    ::= { tmnxOamPmCfgSessIpEntry 1 }

tmnxOamPmCfgSessIpSrcAddressType OBJECT-TYPE
    SYNTAX      InetAddressType
    MAX-ACCESS  read-write
    STATUS      current
    DESCRIPTION
        "The value of tmnxOamPmCfgSessIpSrcAddressType specifies the address
         type of tmnxOamPmCfgSessIpSrcAddress."
    DEFVAL      { unknown }
    ::= { tmnxOamPmCfgSessIpEntry 2 }

tmnxOamPmCfgSessIpSrcAddress     OBJECT-TYPE
    SYNTAX      InetAddress (SIZE (0|4|16))
    MAX-ACCESS  read-write
    STATUS      current
    DESCRIPTION
        "The value of tmnxOamPmCfgSessIpSrcAddress specifies the source IP
         address to be used by IP tests belonging to the specified session.

         tmnxOamPmCfgSessIpSrcAddressType and tmnxOamPmCfgSessIpSrcAddress must
         be set in one SNMP PDU."
    DEFVAL      { ''H }
    ::= { tmnxOamPmCfgSessIpEntry 3 }

tmnxOamPmCfgSessIpDstAddressType OBJECT-TYPE
    SYNTAX      InetAddressType
    MAX-ACCESS  read-write
    STATUS      current
    DESCRIPTION
        "The value of tmnxOamPmCfgSessIpDstAddressType specifies the address
         type of tmnxOamPmCfgSessIpDstAddress."
    DEFVAL      { unknown }
    ::= { tmnxOamPmCfgSessIpEntry 4 }

tmnxOamPmCfgSessIpDstAddress     OBJECT-TYPE
    SYNTAX      InetAddress (SIZE (0|4|16))
    MAX-ACCESS  read-write
    STATUS      current
    DESCRIPTION
        "The value of tmnxOamPmCfgSessIpDstAddress specifies the destination IP
         address to be used by IP tests belonging to the specified session.

         tmnxOamPmCfgSessIpDstAddressType and tmnxOamPmCfgSessIpDstAddress must
         be set in one SNMP PDU."
    DEFVAL      { ''H }
    ::= { tmnxOamPmCfgSessIpEntry 5 }

tmnxOamPmCfgSessIpDstUdpPort     OBJECT-TYPE
    SYNTAX      InetPortNumber
    MAX-ACCESS  read-write
    STATUS      current
    DESCRIPTION
        "The value of tmnxOamPmCfgSessIpDstUdpPort specifies the destination
         UDP port to be used by IP tests belonging to the specified session.

         Zero indicates that no destination UDP port has been configured."
    DEFVAL      { 0 }
    ::= { tmnxOamPmCfgSessIpEntry 6 }

tmnxOamPmCfgSessIpBypassRouting  OBJECT-TYPE
    SYNTAX      TruthValue
    MAX-ACCESS  read-write
    STATUS      current
    DESCRIPTION
        "The value of tmnxOamPmCfgSessIpBypassRouting specifies whether or not
         to bypass the routing table when sending each ping request (for an IP
         test which belongs to the specified session).

         If bypass is selected, the source IP address for the test (i.e.
         tmnxOamPmCfgSessIpSrcAddress) is used to determine the egress
         interface to be used by the test.

         At most one of the following objects can be changed away from default:
             tmnxOamPmCfgSessIpBypassRouting,
             tmnxOamPmCfgSessIpEgressIfName,
             tmnxOamPmCfgSessIpNhAddressType,
             tmnxOamPmCfgSessIpTunnelType."
    DEFVAL      { false }
    ::= { tmnxOamPmCfgSessIpEntry 7 }

tmnxOamPmCfgSessIpEgressIfName   OBJECT-TYPE
    SYNTAX      TNamedItemOrEmpty
    MAX-ACCESS  read-write
    STATUS      current
    DESCRIPTION
        "The value of tmnxOamPmCfgSessIpEgressIfName specifies the name of the
         interface to be used to transmit a ping request (for an IP test which
         belongs to the specified session).

         At most one of the following objects can be changed away from default:
             tmnxOamPmCfgSessIpBypassRouting,
             tmnxOamPmCfgSessIpEgressIfName,
             tmnxOamPmCfgSessIpNhAddressType,
             tmnxOamPmCfgSessIpTunnelType."
    DEFVAL      { ''H }
    ::= { tmnxOamPmCfgSessIpEntry 8 }

tmnxOamPmCfgSessIpNhAddressType  OBJECT-TYPE
    SYNTAX      InetAddressType
    MAX-ACCESS  read-write
    STATUS      current
    DESCRIPTION
        "The value of tmnxOamPmCfgSessIpNhAddressType specifies the address
         type of tmnxOamPmCfgSessIpNhAddress.

         At most one of the following objects can be changed away from default:
             tmnxOamPmCfgSessIpBypassRouting,
             tmnxOamPmCfgSessIpEgressIfName,
             tmnxOamPmCfgSessIpNhAddressType,
             tmnxOamPmCfgSessIpTunnelType."
    DEFVAL      { unknown }
    ::= { tmnxOamPmCfgSessIpEntry 9 }

tmnxOamPmCfgSessIpNhAddress      OBJECT-TYPE
    SYNTAX      InetAddress (SIZE (0|4|16))
    MAX-ACCESS  read-write
    STATUS      current
    DESCRIPTION
        "The value of tmnxOamPmCfgSessIpNhAddress specifies the next-hop IP
         address to be used to look up the egress port for IP tests belonging
         to the specified session.

         tmnxOamPmCfgSessIpNhAddressType and tmnxOamPmCfgSessIpNhAddress must
         be set in one SNMP PDU."
    DEFVAL      { ''H }
    ::= { tmnxOamPmCfgSessIpEntry 10 }

tmnxOamPmCfgSessIpForwardClass   OBJECT-TYPE
    SYNTAX      TFCName
    MAX-ACCESS  read-write
    STATUS      current
    DESCRIPTION
        "The value of tmnxOamPmCfgSessIpForwardClass specifies the forwarding
         class name to be used when launching a ping request for an IP test
         belonging to the specified session.  The forwarding class name must be
         present in the index column of TIMETRA-QOS-MIB::tFCNameTable."
    DEFVAL      { "be" }
    ::= { tmnxOamPmCfgSessIpEntry 11 }

tmnxOamPmCfgSessIpProfile        OBJECT-TYPE
    SYNTAX      TProfile
    MAX-ACCESS  read-write
    STATUS      current
    DESCRIPTION
        "The value of tmnxOamPmCfgSessIpProfile specifies the Quality of
         Service profile to be used when launching a ping request for an IP
         test belonging to the specified session."
    DEFVAL      { out }
    ::= { tmnxOamPmCfgSessIpEntry 12 }

tmnxOamPmCfgSessIpTtl            OBJECT-TYPE
    SYNTAX      Unsigned32 (1..255)
    MAX-ACCESS  read-write
    STATUS      current
    DESCRIPTION
        "The value of tmnxOamPmCfgSessIpTtl specifies the time-to-live to be
         used when launching a ping request for an IP test belonging to the
         specified session."
    DEFVAL      { 255 }
    ::= { tmnxOamPmCfgSessIpEntry 13 }

tmnxOamPmCfgSessIpSrcUdpPort     OBJECT-TYPE
    SYNTAX      InetPortNumber (0 | 64374..64383)
    MAX-ACCESS  read-write
    STATUS      current
    DESCRIPTION
        "The value of tmnxOamPmCfgSessIpSrcUdpPort specifies the source UDP
         port to be used by IP tests belonging to the specified session.

         A source UDP port is allocated when the TWAMP-Light test for the
         specified session has its administrative status (i.e.
         tmnxOamPmCfgTwampLtAdminStatus) changed to 'enabled(1)'.  The port is
         deallocated when the TWAMP-Light test has its administrative status
         changed to 'disabled(2)'.

         When allocating a source UDP port:
         1.  If tmnxOamPmCfgSessIpSrcUdpPort is zero, the source UDP port is
         allocated from the dynamic pool of UDP ports.
         2.  If tmnxOamPmCfgSessIpSrcUdpPort is non-zero, the source UDP port
         with port number equal to tmnxOamPmCfgSessIpSrcUdpPort is allocated.

         The read-only object tmnxOamPmStsSessIpSrcUdpPort indicates the
         allocated UDP port number."
    DEFVAL      { 0 }
    ::= { tmnxOamPmCfgSessIpEntry 14 }

tmnxOamPmCfgSessIpDoNotFragment  OBJECT-TYPE
    SYNTAX      TruthValue
    MAX-ACCESS  read-write
    STATUS      current
    DESCRIPTION
        "The value of tmnxOamPmCfgSessIpDoNotFragment specifies whether or not
         the IPv4 Don't Fragment (DF) bit is set in each echo request packet
         launched for each test belonging to the specified session.

         When tmnxOamPmCfgSessIpDoNotFragment is 'true(1)', the DF bit is set.

         This object is significant if the destination address type for the
         specified session (i.e. tmnxOamPmCfgSessIpDstAddressType) is
         'ipv4(1)'. Otherwise, this object is ignored."
    REFERENCE
        "RFC 791, 'Internet Protocol', September 1981, Section 3.1, 'Internet
         Header Format'."
    DEFVAL      { false }
    ::= { tmnxOamPmCfgSessIpEntry 15 }

tmnxOamPmCfgSessIpDscpName       OBJECT-TYPE
    SYNTAX      TDSCPNameOrEmpty
    MAX-ACCESS  read-write
    STATUS      current
    DESCRIPTION
        "The value of tmnxOamPmCfgSessIpDscpName specifies the Differentiated
         Services Code Point (DSCP) to be copied into the IP header of each
         echo request packet launched for each test belonging to the specified
         session.

         The specified DSCP name must match a TIMETRA-QOS-MIB::tDSCPName
         defined in TIMETRA-QOS-MIB::tDSCPNameTable.

         The mapping between the specified DSCP name (e.g. 'af43') and the
         numeric value needed in the IP header (e.g. 38) is provided by
         TIMETRA-QOS-MIB::tDSCPNameDscpValue.

         If the value of this object is the empty string, the DSCP copied into
         the IP header is derived by SROS from the specified session's
         forwarding class and profile (i.e. tmnxOamPmCfgSessIpForwardClass and
         tmnxOamPmCfgSessIpProfile), using
         TIMETRA-QOS-MIB::tNetworkEgressFCDSCPInProfile and
         TIMETRA-QOS-MIB::tNetworkEgressFCDSCPOutProfile for network Quality of
         Service (QoS) policy 1.

         The interaction with tmnxOamPmCfgSessIpDscpEgrRemark is explained in
         the tmnxOamPmCfgSessIpDscpEgrRemark DESCRIPTION clause."
    REFERENCE
        "RFC 3260, 'New Terminology and Clarifications for Diffserv', April
         2002, Section 4, 'Definition of the DS Field'."
    DEFVAL      { ''H }
    ::= { tmnxOamPmCfgSessIpEntry 16 }

tmnxOamPmCfgSessIpDscpEgrRemark  OBJECT-TYPE
    SYNTAX      TruthValue
    MAX-ACCESS  read-write
    STATUS      current
    DESCRIPTION
        "The value of tmnxOamPmCfgSessIpDscpEgrRemark specifies whether or not
         to allow each echo request packet's IP header Differentiated Services
         Code Point (DSCP) to be overwritten in accordance with the egress
         port's Quality of Service (QoS) policy.  The echo request packets are
         launched for each test belonging to the specified session.

         If the value of this object is 'true(1)', the IP header's DSCP (as
         computed using tmnxOamPmCfgSessIpDscpName,
         tmnxOamPmCfgSessIpForwardClass and/or tmnxOamPmCfgSessIpProfile) may
         be overwritten.

         If TIMETRA-QOS-MIB::tNetworkPolicyEgressRemark and
         TIMETRA-QOS-MIB::tNetworkPolicyEgressRemarkDscp are both set to
         'true(1)', the DSCP may be overwritten regardless of the value of this
         object."
    DEFVAL      { false }
    ::= { tmnxOamPmCfgSessIpEntry 17 }

tmnxOamPmCfgSessIpPadPattern     OBJECT-TYPE
    SYNTAX      Integer32 (-1 | 0..65535)
    MAX-ACCESS  read-write
    STATUS      current
    DESCRIPTION
        "The value of tmnxOamPmCfgSessIpPadPattern specifies a two octet pattern
         to be repeated to fill the padding field of each echo request packet
         launched for each test belonging to the specified session.  For
         example, if 255 is specified, the padding field is filled with the
         octet values 00, FF, 00, FF, ... (hexadecimal).

         When the value of this object is -1, the padding field will be filled
         with the octet values 00, 01, 02, 03, ... (hexadecimal).

         This object must be left at default when the session has a test with
         tmnxOamPmCfgTwampLtTestSubType = 'subTypeSTAMP'."
    REFERENCE
        "RFC 5357, 'A Two-Way Active Measurement Protocol (TWAMP)', October
         2008, Section 4.2.1, 'TWAMP-Test Packet Format and Content'."
    DEFVAL      { 0 }
    ::= { tmnxOamPmCfgSessIpEntry 18 }

tmnxOamPmCfgSessIpRouterInstName OBJECT-TYPE
    SYNTAX      TLNamedItemOrEmpty
    MAX-ACCESS  read-write
    STATUS      current
    DESCRIPTION
        "The value of tmnxOamPmCfgSessIpRouterInstName specifies the name of
         the virtual router to be used by tests belonging to the specified
         session.

         The following values are supported:
         1.  '' (i.e. the empty string),
         2.  'Base',
         3.  A VPRN service name (i.e. a TIMETRA-SERV-MIB::svcName, with
             TIMETRA-SERV-MIB::svcType = 'vprn(4)').

         Names other than the names listed above are accepted, but will not
         lead to a successful test.

         The virtual router to be used by the session's tests can be specified
         using tmnxOamPmCfgSessIpServiceId or tmnxOamPmCfgSessIpRouterInstName
         (not both).  If tmnxOamPmCfgSessIpRouterInstName is the empty string,
         tmnxOamPmCfgSessIpServiceId is used.  Otherwise,
         tmnxOamPmCfgSessIpRouterInstName is used.

         An attempt to change TIMETRA-SYSTEM-MIB::tmnxSysMgmtIfWriteMode.0 away
         from 'classic(1)' is blocked if any tmnxOamPmCfgSessIpRouterInstName
         is the empty string.

         When TIMETRA-SYSTEM-MIB::tmnxSysMgmtIfWriteMode.0 is not 'classic(1)',
         each tmnxOamPmCfgSessIpRouterInstName must continue to be a not-empty
         string.

         When TIMETRA-SYSTEM-MIB::tmnxSysMgmtIfWriteMode.0 is 'classic(1)',
         the default router instance is ''.  Otherwise, the default is
         'Base'.

         MPLS tunneling can only be configured with the Base router.
         So, the following combination is not supported:
             tmnxOamPmCfgSessIpTunnelType = 'mpls(2)'
             AND (
             tmnxOamPmCfgSessIpRouterInstName != 'Base' OR
             tmnxOamPmCfgSessIpServiceId != 0)."
    ::= { tmnxOamPmCfgSessIpEntry 19 }

tmnxOamPmCfgSessIpTunnelType     OBJECT-TYPE
    SYNTAX      INTEGER {
        none (1),
        mpls (2)
    }
    MAX-ACCESS  read-write
    STATUS      current
    DESCRIPTION
        "The value of tmnxOamPmCfgSessIpTunnelType specifies the type of
         tunneling to be applied to IP packets sent by the tests belonging to
         the session.

         Code points:
             none(1) - no tunneling.
             mpls(2) - MPLS tunneling.

         At most one of the following objects can be changed away from default:
             tmnxOamPmCfgSessIpBypassRouting,
             tmnxOamPmCfgSessIpEgressIfName,
             tmnxOamPmCfgSessIpNhAddressType,
             tmnxOamPmCfgSessIpTunnelType.

         MPLS tunneling can only be configured with the Base router.
         So, the following combination is not supported:
             tmnxOamPmCfgSessIpTunnelType = 'mpls(2)'
             AND (
             tmnxOamPmCfgSessIpRouterInstName != 'Base' OR
             tmnxOamPmCfgSessIpServiceId != 0)."
    DEFVAL      { none }
    ::= { tmnxOamPmCfgSessIpEntry 20 }

tmnxOamPmCfgSessIpTunnelTypeMpls OBJECT-TYPE
    SYNTAX      INTEGER {
        none       (1),
        rsvpTe     (2),
        rsvpTeAuto (3),
        srIsis     (4),
        srOspf     (5),
        srOspf3    (6),
        srTe       (7),
        srPolicy   (8)
    }
    MAX-ACCESS  read-write
    STATUS      current
    DESCRIPTION
        "The value of tmnxOamPmCfgSessIpTunnelTypeMpls specifies the type of
         MPLS tunneling to be applied to IP packets sent by the tests belonging
         to the session.

         Code points:
             none(1)       - no MPLS tunnel.
             rsvpTe(2)     - MPLS RSVP Traffic Engineered tunnel.
             rsvpTeAuto(3) - MPLS RSVP Traffic Engineered tunnel with
                 automated LSP creation.
             srIsis(4)     - MPLS Segment Routing ISIS tunnel.
             srOspf(5)     - MPLS Segment Routing OSPF tunnel.
             srOspf3(6)    - MPLS Segment Routing OSPFv3 tunnel.
             srTe(7)       - MPLS Segment Routing Traffic Engineered tunnel.
             srPolicy(8)   - MPLS Segment Routing Policy tunnel.

          The value of this object must be 'none(1)' when
          tmnxOamPmCfgSessIpTunnelType != 'mpls(2)'.

          The tunneling configuration objects applicable to a
          particular MPLS tunneling type are shown in the following table.

          tmnxOamPmCfgSessIpTunnelTypeMpls  Applicable Tunneling Objects
          --------------------------------  -------------------------------
          'none'                            None
          'rsvpTe', 'srTe'                  tmnxOamPmCfgSessIpLspName
          'rsvpTeAuto'                      tmnxOamPmCfgSessIpLspTemplName
                                            tmnxOamPmCfgSessIpLspFromAddrTyp
                                            tmnxOamPmCfgSessIpLspFromAddress
                                            tmnxOamPmCfgSessIpLspToAddrType
                                            tmnxOamPmCfgSessIpLspToAddress
          'srIsis', 'srOspf'                tmnxOamPmCfgSessIpLspDstPfx
                                            tmnxOamPmCfgSessIpLspDstPfxLen
                                            tmnxOamPmCfgSessIpLspDstPfxType
                                            tmnxOamPmCfgSessIpLspIgpInstance
                                            tmnxOamPmCfgSessIpFlexAlgoId

          'srOspf3'                         tmnxOamPmCfgSessIpLspDstPfx
                                            tmnxOamPmCfgSessIpLspDstPfxLen
                                            tmnxOamPmCfgSessIpLspDstPfxType
                                            tmnxOamPmCfgSessIpLspIgpInstance

          'srPolicy'                        tmnxOamPmCfgSessIpSrPlcyEnPtAddT;
                                            tmnxOamPmCfgSessIpSrPlcyEnPtAddr;
                                            tmnxOamPmCfgSessIpSrPolicyColor;
                                            tmnxOamPmCfgSessIpSrPlcySegList;

          Inapplicable tunneling objects should not be changed away from
          default."
    DEFVAL      { none }
    ::= { tmnxOamPmCfgSessIpEntry 21 }

tmnxOamPmCfgSessIpLspName        OBJECT-TYPE
    SYNTAX      TLNamedItemOrEmpty
    MAX-ACCESS  read-write
    STATUS      current
    DESCRIPTION
        "The value of tmnxOamPmCfgSessIpLspName specifies the name of the LSP
         used to tunnel the IP packets sent by the tests belonging to the
         specified session.

         For a successful test, the LSP name must match a
         TIMETRA-MPLS-MIB::vRtrMplsLspName.

         The rules for changing this value away from default are shown in the
         DESCRIPTION clause for tmnxOamPmCfgSessIpTunnelTypeMpls."
    DEFVAL      { "" }
    ::= { tmnxOamPmCfgSessIpEntry 22 }

tmnxOamPmCfgSessIpLspTemplName   OBJECT-TYPE
    SYNTAX      TNamedItemOrEmpty
    MAX-ACCESS  read-write
    STATUS      current
    DESCRIPTION
        "The value of tmnxOamPmCfgSessIpLspTemplName specifies the name of the
         LSP Template used to tunnel the IP packets sent by the tests belonging
         to the specified session.

         For a successful test, the template name must match a
         TIMETRA-MPLS-MIB::vRtrMplsLspTemplateName.

         The rules for changing this value away from default are shown in the
         DESCRIPTION clause for tmnxOamPmCfgSessIpTunnelTypeMpls."
    DEFVAL      { "" }
    ::= { tmnxOamPmCfgSessIpEntry 23 }

tmnxOamPmCfgSessIpLspFromAddrTyp OBJECT-TYPE
    SYNTAX      InetAddressType
    MAX-ACCESS  read-write
    STATUS      current
    DESCRIPTION
        "The value of tmnxOamPmCfgSessIpLspFromAddrTyp specifies the address
         type of tmnxOamPmCfgSessIpLspFromAddress."
    DEFVAL      { unknown }
    ::= { tmnxOamPmCfgSessIpEntry 24 }

tmnxOamPmCfgSessIpLspFromAddress OBJECT-TYPE
    SYNTAX      InetAddress (SIZE (0|4|16))
    MAX-ACCESS  read-write
    STATUS      current
    DESCRIPTION
        "The value of tmnxOamPmCfgSessIpLspFromAddress specifies the IP head
         address used with tmnxOamPmCfgSessIpLspTemplName to tunnel the IP
         packets sent by the tests belonging to the specified session.

         The rules for changing this value away from default are shown in the
         DESCRIPTION clause for tmnxOamPmCfgSessIpTunnelTypeMpls."
    DEFVAL      { ''H }
    ::= { tmnxOamPmCfgSessIpEntry 25 }

tmnxOamPmCfgSessIpLspToAddrType  OBJECT-TYPE
    SYNTAX      InetAddressType
    MAX-ACCESS  read-write
    STATUS      current
    DESCRIPTION
        "The value of tmnxOamPmCfgSessIpLspToAddrType specifies the address
         type of tmnxOamPmCfgSessIpLspToAddress."
    DEFVAL      { unknown }
    ::= { tmnxOamPmCfgSessIpEntry 26 }

tmnxOamPmCfgSessIpLspToAddress   OBJECT-TYPE
    SYNTAX      InetAddress (SIZE (0|4|16))
    MAX-ACCESS  read-write
    STATUS      current
    DESCRIPTION
        "The value of tmnxOamPmCfgSessIpLspToAddress specifies the IP tail
         address used with tmnxOamPmCfgSessIpLspTemplName to tunnel the IP
         packets sent by the tests belonging to the specified session.

         The rules for changing this value away from default are shown in the
         DESCRIPTION clause for tmnxOamPmCfgSessIpTunnelTypeMpls."
    DEFVAL      { ''H }
    ::= { tmnxOamPmCfgSessIpEntry 27 }

tmnxOamPmCfgSessIpLspIgpInstance OBJECT-TYPE
    SYNTAX      TmnxIgpInstance
    MAX-ACCESS  read-write
    STATUS      current
    DESCRIPTION
        "The value of tmnxOamPmCfgSessIpLspIgpInstance specifies the Interior
         Gateway Protocol (IGP) instance used to tunnel the IP packets sent by
         the tests belonging to the specified session.

         The rules for changing this value away from default are shown in the
         DESCRIPTION clause for tmnxOamPmCfgSessIpTunnelTypeMpls."
    DEFVAL      { 0 }
    ::= { tmnxOamPmCfgSessIpEntry 28 }

tmnxOamPmCfgSessIpLspDstPfxType  OBJECT-TYPE
    SYNTAX      InetAddressType
    MAX-ACCESS  read-write
    STATUS      current
    DESCRIPTION
        "The value of tmnxOamPmCfgSessIpLspDstPfxType specifies the type of IP
         address stored in tmnxOamPmCfgSessIpLspDstPfx.

         When any one of the following objects is set, all three must be set
         in the same SNMP Set PDU:
             tmnxOamPmCfgSessIpLspDstPfxType,
             tmnxOamPmCfgSessIpLspDstPfx,
             tmnxOamPmCfgSessIpLspDstPfxLen.

         The following combination is not supported:
             tmnxOamPmCfgSessIpLspDstPfxType = ipv6(2)
             tmnxOamPmCfgSessIpTunnelTypeMpls = srOspf(5).

         More rules for changing this value away from default are shown in the
         DESCRIPTION clause for tmnxOamPmCfgSessIpTunnelTypeMpls."
    DEFVAL      { unknown }
    ::= { tmnxOamPmCfgSessIpEntry 29 }

tmnxOamPmCfgSessIpLspDstPfx      OBJECT-TYPE
    SYNTAX      InetAddress (SIZE (0|4|16))
    MAX-ACCESS  read-write
    STATUS      current
    DESCRIPTION
        "The value of tmnxOamPmCfgSessIpLspDstPfx, along with
         tmnxOamPmCfgSessIpLspDstPfxType and tmnxOamPmCfgSessIpLspDstPfxLen,
         specifies the IP destination prefix used to tunnel the IP packets sent
         by the tests belonging to the specified session.

         The rules for changing this value away from default are shown in the
         DESCRIPTION clause for tmnxOamPmCfgSessIpTunnelTypeMpls."
    DEFVAL      { ''H }
    ::= { tmnxOamPmCfgSessIpEntry 30 }

tmnxOamPmCfgSessIpLspDstPfxLen   OBJECT-TYPE
    SYNTAX      InetAddressPrefixLength (0 | 32 | 128)
    UNITS       "bits"
    MAX-ACCESS  read-write
    STATUS      current
    DESCRIPTION
        "The value of tmnxOamPmCfgSessIpLspDstPfxLen specifies the IP address
         prefix length of tmnxOamPmCfgSessIpLspDstPfx.

         The acceptable value is dictated by the prefix type, as follows.

         tmnxOamPmCfgSessIpLspDstPfxType  tmnxOamPmCfgSessIpLspDstPfxLen
         -------------------------------  ------------------------------
         'unknown'                                                     0
         'ipv4'                                                       32
         'ipv6'                                                      128

         More rules for changing this value away from default are shown in the
         DESCRIPTION clause for tmnxOamPmCfgSessIpTunnelTypeMpls."
    DEFVAL      { 0 }
    ::= { tmnxOamPmCfgSessIpEntry 31 }

tmnxOamPmCfgSessIpFlexAlgoId     OBJECT-TYPE
    SYNTAX      TmnxFlexAlgoIdOrZero
    MAX-ACCESS  read-write
    STATUS      current
    DESCRIPTION
        "The value of tmnxOamPmCfgSessIpFlexAlgoId specifies the IGP Flexible
         Algorithm used to tunnel the IP packets sent by the tests belonging to
         the specified session.

         Zero indicates no Flexible Algorithm has been specified.

         The rules for changing this value away from default are shown in the
         DESCRIPTION clause for tmnxOamPmCfgSessIpTunnelTypeMpls."
    REFERENCE
        "RFC 9350, 'IGP Flexible Algorithm', Feb-2023."
    DEFVAL      { 0 }
    ::= { tmnxOamPmCfgSessIpEntry 32 }

tmnxOamPmCfgSessIpSrPolicyColor  OBJECT-TYPE
    SYNTAX      Unsigned32
    MAX-ACCESS  read-write
    STATUS      current
    DESCRIPTION
        "The value of tmnxOamPmCfgSessIpSrPolicyColor specifies the Segment
         Routing (SR) policy color to be used to tunnel the IP packets sent by
         the tests belonging to the specified session.

         A color associates an SR policy with an intent (e.g. low latency).

         tmnxOamPmCfgSessIpSrPolicyColor, tmnxOamPmCfgSessIpSrPlcyEnPtAddT, and
         tmnxOamPmCfgSessIpSrPlcyEnPtAddr must identify a known SR policy.
         Otherwise, the test will fail.  The color of a static SR policy is
         defined using TIMETRA-SR-POLICY-MIB::vRtrSrStaticPlcyColor.

         The rules for changing this value away from default are shown in the
         DESCRIPTION clause for tmnxOamPmCfgSessIpTunnelTypeMpls."
    REFERENCE
        "RFC 9256, 'Segment Routing Policy Architecture', Section 2.1,
         'Identification of an SR Policy'."
    DEFVAL      { 0 }
    ::= { tmnxOamPmCfgSessIpEntry 33 }

tmnxOamPmCfgSessIpSrPlcyEnPtAddT OBJECT-TYPE
    SYNTAX      InetAddressType
    MAX-ACCESS  read-write
    STATUS      current
    DESCRIPTION
        "The value of tmnxOamPmCfgSessIpSrPlcyEnPtAddT specifies the type of IP
         address stored in tmnxOamPmCfgSessIpSrPlcyEnPtAddr.

         The rules for changing this value away from default are shown in the
         DESCRIPTION clause for tmnxOamPmCfgSessIpTunnelTypeMpls."
    DEFVAL      { unknown }
    ::= { tmnxOamPmCfgSessIpEntry 34 }

tmnxOamPmCfgSessIpSrPlcyEnPtAddr OBJECT-TYPE
    SYNTAX      InetAddress (SIZE (0|4|16))
    MAX-ACCESS  read-write
    STATUS      current
    DESCRIPTION
        "The value of tmnxOamPmCfgSessIpSrPlcyEnPtAddr specifies the Segment
         Routing (SR) policy endpoint address to be used for the test.

         The rules for changing this value away from default are shown in the
         DESCRIPTION clause for tmnxOamPmCfgSessIpTunnelTypeMpls."
    REFERENCE
        "RFC 9256, 'Segment Routing Policy Architecture', Section 2.1,
         'Identification of an SR Policy'."
    DEFVAL      { ''H }
    ::= { tmnxOamPmCfgSessIpEntry 35 }

tmnxOamPmCfgSessIpSrPlcySegList  OBJECT-TYPE
    SYNTAX      Unsigned32 (0 | 1..32)
    MAX-ACCESS  read-write
    STATUS      current
    DESCRIPTION
        "The value of tmnxOamPmCfgSessIpSrPlcySegList specifies the Segment
         Routing (SR) policy segment list to be used for the test.

         Zero indicates no segment list is configured.

         The rules for changing this value away from default are shown in the
         DESCRIPTION clause for tmnxOamPmCfgSessIpTunnelTypeMpls."
    REFERENCE
        "RFC 9256, 'Segment Routing Policy Architecture', Section 2.2,
         'Candidate Path and Segment List'."
    DEFVAL      { 0 }
    ::= { tmnxOamPmCfgSessIpEntry 36 }

tmnxOamPmCfgTwampLtTable         OBJECT-TYPE
    SYNTAX      SEQUENCE OF TmnxOamPmCfgTwampLtEntry
    MAX-ACCESS  not-accessible
    STATUS      current
    DESCRIPTION
        "tmnxOamPmCfgTwampLtTable contains the configuration information for
         OAM Performance Monitoring TWAMP-Light (Two-Way Active Measurement
         Protocol, Light) tests."
    REFERENCE
        "RFC 5357, 'A Two-Way Active Measurement Protocol (TWAMP)', Appendix I,
         'TWAMP Light'."
    ::= { tmnxOamPmCfgTableObjs 9 }

tmnxOamPmCfgTwampLtEntry         OBJECT-TYPE
    SYNTAX      TmnxOamPmCfgTwampLtEntry
    MAX-ACCESS  not-accessible
    STATUS      current
    DESCRIPTION
        "tmnxOamPmCfgTwampLtEntry contains the configuration information for
         the OAM Performance Monitoring TWAMP-Light test for the specified
         session.

         Rows are created or destroyed by SNMP Set operations on
         tmnxOamPmCfgTwampLtRowStatus.

         An attempt to change any value in a row (except
         tmnxOamPmCfgTwampLtAdminStatus and tmnxOamPmCfgTwampLtOnDmndStatus)
         will be rejected if tmnxOamPmCfgTwampLtAdminStatus is 'enabled(1)'."
    INDEX       { tmnxOamPmCfgSessName }
    ::= { tmnxOamPmCfgTwampLtTable 1 }

TmnxOamPmCfgTwampLtEntry         ::= SEQUENCE
{
    tmnxOamPmCfgTwampLtRowStatus     RowStatus,
    tmnxOamPmCfgTwampLtAdminStatus   TmnxEnabledDisabled,
    tmnxOamPmCfgTwampLtOnDmndStatus  TmnxEnabledDisabledOrNA,
    tmnxOamPmCfgTwampLtTestId        Unsigned32,
    tmnxOamPmCfgTwampLtInterval      Unsigned32,
    tmnxOamPmCfgTwampLtPadSize       Unsigned32,
    tmnxOamPmCfgTwampLtTestDuration  Unsigned32,
    tmnxOamPmCfgTwampLtRunTimeLeft   Unsigned32,
    tmnxOamPmCfgTwampLtCollectStats  INTEGER,
    tmnxOamPmCfgTwampLtTxFrmsPerDelT Unsigned32,
    tmnxOamPmCfgTwampLtConsecDeltaTs Unsigned32,
    tmnxOamPmCfgTwampLtChliThreshold Unsigned32,
    tmnxOamPmCfgTwampLtFlrThreshold  Unsigned32,
    tmnxOamPmCfgTwampLtHliForceCount TruthValue,
    tmnxOamPmCfgTwampLtStrTmplName   TLNamedItemOrEmpty,
    tmnxOamPmCfgTwampLtIPv6UdpCsZero TruthValue,
    tmnxOamPmCfgTwampLtTestSubType   INTEGER,
    tmnxOamPmCfgTwampLtStpPadTlvSize Unsigned32,
    tmnxOamPmCfgTwampLtTimestampFmt  INTEGER,
    tmnxOamPmCfgTwampLtIsAutoTestId  TruthValue,
    tmnxOamPmCfgTwampLtTestIdInUse   Unsigned32
}

tmnxOamPmCfgTwampLtRowStatus     OBJECT-TYPE
    SYNTAX      RowStatus
    MAX-ACCESS  read-create
    STATUS      current
    DESCRIPTION
        "The value of tmnxOamPmCfgTwampLtRowStatus specifies the status of the
         configuration row for the specified session's TWAMP-Light test.

         An attempt to create a row for a session with
         tmnxOamPmCfgSessTestFamily other than 'ip(2)' will be rejected."
    ::= { tmnxOamPmCfgTwampLtEntry 1 }

tmnxOamPmCfgTwampLtAdminStatus   OBJECT-TYPE
    SYNTAX      TmnxEnabledDisabled
    MAX-ACCESS  read-create
    STATUS      current
    DESCRIPTION
        "The value of tmnxOamPmCfgTwampLtAdminStatus specifies whether or not
         the specified session's TWAMP-Light test is administratively enabled.

         If the session type (tmnxOamPmCfgSessType) is 'proactive(1)', setting
         tmnxOamPmCfgTwampLtAdminStatus to 'enabled(1)'/'disabled(2)'
         starts/stops the test.

         If the session type is 'onDemand(2)', see the DESCRIPTION clause for
         tmnxOamPmCfgTwampLtOnDmndStatus for information on starting/stopping
         the test.

         An attempt to set this object to 'enabled(1)' will be rejected if the
         tmnxOamPmCfgSessIpTable row for the specified session has incomplete
         information for the test (e.g. if tmnxOamPmCfgSessIpSrcAddressType is
         'unknown(0)')."
    DEFVAL      { disabled }
    ::= { tmnxOamPmCfgTwampLtEntry 2 }

tmnxOamPmCfgTwampLtOnDmndStatus  OBJECT-TYPE
    SYNTAX      TmnxEnabledDisabledOrNA
    MAX-ACCESS  read-create
    STATUS      current
    DESCRIPTION
        "The value of tmnxOamPmCfgTwampLtOnDmndStatus specifies the status of
         the on-demand TWAMP-Light test for the specified session.

         Values:
            'enabled(1)'
                Set by an SNMP manager to start an on-demand TWAMP-Light test.
                The test will start if tmnxOamPmCfgTwampLtAdminStatus is
                'enabled(1)'.
            'disabled(2)'
                Set by an SNMP manager to stop an on-demand TWAMP-Light test.
                Set by SROS to indicate an on-demand TWAMP-Light test has
                stopped running because the configured period for the test (i.e.
                tmnxOamPmCfgTwampLtTestDuration) has ended.
                Set by SROS for an on-demand TWAMP-Light test when
                tmnxOamPmCfgTwampLtAdminStatus is set to 'disabled(2)'.
            'notApplicable(3)'
                This code point is the only acceptable value for a proactive
                TWAMP-Light test.  An attempt to set this code point for an
                on-demand TWAMP-Light test will be rejected.

         The default value is 'disabled(2)' for an on-demand TWAMP-Light test,
         and 'notApplicable(3)' for a proactive TWAMP-Light test."
    ::= { tmnxOamPmCfgTwampLtEntry 3 }

tmnxOamPmCfgTwampLtTestId        OBJECT-TYPE
    SYNTAX      Unsigned32 (0..2147483647)
    MAX-ACCESS  read-create
    STATUS      current
    DESCRIPTION
        "The value of tmnxOamPmCfgTwampLtTestId specifies the test identifier
         for the specified session's TWAMP-Light test.

         When tmnxOamPmCfgTwampLtIsAutoTestId is being set 'true(1)', the value
         of tmnxOamPmCfgTwampLtTestId is not used and it must be set to 0.

         An attempt to add a duplicate test identifier to this table will be
         rejected.

         Test identifier values larger than 2147483647 are reserved for
         internal use."
    DEFVAL      { 0 }
    ::= { tmnxOamPmCfgTwampLtEntry 4 }

tmnxOamPmCfgTwampLtInterval      OBJECT-TYPE
    SYNTAX      Unsigned32 (50 | 100 | 200 | 300 | 400 | 500 | 600 | 700 | 800 | 900 | 1000 | 10000)
    UNITS       "milliseconds"
    MAX-ACCESS  read-create
    STATUS      current
    DESCRIPTION
        "The value of tmnxOamPmCfgTwampLtInterval specifies the elapsed time
         between transmission of TWAMP-Test PDUs for the specified session's
         TWAMP-Light test."
    DEFVAL      { 1000 }
    ::= { tmnxOamPmCfgTwampLtEntry 5 }

tmnxOamPmCfgTwampLtPadSize       OBJECT-TYPE
    SYNTAX      Unsigned32 (0..2000)
    UNITS       "octets"
    MAX-ACCESS  read-create
    STATUS      current
    DESCRIPTION
        "The value of tmnxOamPmCfgTwampLtPadSize specifies the amount of
         padding added to each launched TWAMP-Test PDU for the specified
         session's TWAMP-Light test.

         This object is applicable to tests with tmnxOamPmCfgTwampLtTestSubType
         = 'subTypeTwampLight'.

         See the DESCRIPTION clause for tmnxOamPmCfgTwampLtStpPadTlvSize for
         more information."
    REFERENCE
        "RFC 5357, 'A Two-Way Active Measurement Protocol (TWAMP)', Section
         4.1.2, 'Packet Format and Content'."
    DEFVAL      { 0 }
    ::= { tmnxOamPmCfgTwampLtEntry 6 }

tmnxOamPmCfgTwampLtTestDuration  OBJECT-TYPE
    SYNTAX      Unsigned32 (0..86400)
    UNITS       "seconds"
    MAX-ACCESS  read-create
    STATUS      current
    DESCRIPTION
        "The value of tmnxOamPmCfgTwampLtTestDuration specifies the test
         duration for the specified session's TWAMP-Light test.

         Zero specifies a test which runs until it is manually stopped.

         An attempt to set a non-zero value will be rejected if
         tmnxOamPmCfgSessType is 'proactive(1)'."
    DEFVAL      { 0 }
    ::= { tmnxOamPmCfgTwampLtEntry 7 }

tmnxOamPmCfgTwampLtRunTimeLeft   OBJECT-TYPE
    SYNTAX      Unsigned32 (0..86400)
    UNITS       "seconds"
    MAX-ACCESS  read-only
    STATUS      current
    DESCRIPTION
        "The value of tmnxOamPmCfgTwampLtRunTimeLeft indicates the run time
         remaining for the specified session's TWAMP-Light test.

         For example, suppose a TWAMP-Light test has the following
         configuration:

         tmnxOamPmCfgSessType   tmnxOamPmCfgTwampLtTestDuration
         --------------------   -------------------------------
         'onDemand(2)'          1000 (seconds)

         Then, when the TWAMP-Light test is started (see
         tmnxOamPmCfgTwampLtOnDmndStatus), tmnxOamPmCfgTwampLtRunTimeLeft is
         initialized to 1000 seconds.  After a minute,
         tmnxOamPmCfgTwampLtRunTimeLeft is 940 seconds.

         If tmnxOamPmCfgSessType is 'proactive(1)', zero is always returned
         (because a proactive test runs until it is manually stopped).

         If tmnxOamPmCfgSessType is 'onDemand(2)' and the test is stopped (see
         tmnxOamPmCfgTwampLtOnDmndStatus), zero is returned (because the test
         is not running)."
    ::= { tmnxOamPmCfgTwampLtEntry 8 }

tmnxOamPmCfgTwampLtCollectStats  OBJECT-TYPE
    SYNTAX      INTEGER {
        collectDelayStats        (1),
        collectLossStats         (2),
        collectDelayAndLossStats (3)
    }
    MAX-ACCESS  read-create
    STATUS      current
    DESCRIPTION
        "The value of tmnxOamPmCfgTwampLtCollectStats specifies the type(s) of
         statistics to collect while the TWAMP-Light test is running.

         Code points:
            collectDelayStats(1) - collect TWAMP-Light delay statistics
                (readable using tmnxOamPmStsDelayTwlTable and
                tmnxOamPmStsDelayTwlBinTable)
            collectLossStats(2) - collect TWAMP-Light loss statistics
                (readable using tmnxOamPmStsLossTwlTable)
            collectDelayAndLossStats(3) - collectDelayStats(1) and
                collectLossStats(2), simultaneously"
    DEFVAL      { collectDelayStats }
    ::= { tmnxOamPmCfgTwampLtEntry 9 }

tmnxOamPmCfgTwampLtTxFrmsPerDelT OBJECT-TYPE
    SYNTAX      Unsigned32 (1..50)
    UNITS       "frames"
    MAX-ACCESS  read-create
    STATUS      current
    DESCRIPTION
        "The value of tmnxOamPmCfgTwampLtTxFrmsPerDelT specifies the number of
         TWAMP-Light frames to send in one MEF-35 'delta_t' (also known as
         'Small Time Interval') when computing loss statistics for the
         specified session's TWAMP-Light test.

         The loss parameters used by SROS for TWAMP-Light tests (e.g.
         tmnxOamPmCfgTwampLtTxFrmsPerDelT) are modelled after the MEF-35 loss
         parameters defined for Synthetic Loss Measurement (SLM) tests.  Hence,
         the REFERENCE text for this object is a MEF-35 SLM section.

         Expressed in milliseconds,
         delta_t =
            tmnxOamPmCfgTwampLtTxFrmsPerDelT *
            tmnxOamPmCfgTwampLtInterval."
    REFERENCE
        "MEF-35, 'Service OAM Performance Monitoring Implementation Agreement',
         Metro Ethernet Forum, April 2012, Section 10.2 'Single-Ended Synthetic
         Loss Function for Frame Loss Ratio (FLR) and Availability'."
    DEFVAL      { 1 }
    ::= { tmnxOamPmCfgTwampLtEntry 10 }

tmnxOamPmCfgTwampLtConsecDeltaTs OBJECT-TYPE
    SYNTAX      Unsigned32 (2..10)
    MAX-ACCESS  read-create
    STATUS      current
    DESCRIPTION
        "The value of tmnxOamPmCfgTwampLtConsecDeltaTs specifies the number of
         consecutive MEF-35 'delta_t's (also known as 'Small Time Intervals')
         which constitute a MEF-35 'Availability Window' when computing loss
         statistics for the specified session's TWAMP-Light test.

         The loss parameters used by SROS for TWAMP-Light tests (e.g.
         tmnxOamPmCfgTwampLtConsecDeltaTs) are modelled after the MEF-35 loss
         parameters defined for Synthetic Loss Measurement (SLM) tests.  Hence,
         the REFERENCE text for this object is a MEF-35 SLM section.

         The duration of an Availability Window (in milliseconds) is
         tmnxOamPmCfgTwampLtTxFrmsPerDelT * tmnxOamPmCfgTwampLtInterval *
         tmnxOamPmCfgTwampLtConsecDeltaTs.  An attempt to change the duration of
         an Availability Window to more than 100,000 milliseconds will be
         rejected.

         An attempt to change tmnxOamPmCfgTwampLtConsecDeltaTs to a value less
         than or equal to tmnxOamPmCfgTwampLtChliThreshold will be rejected."
    REFERENCE
        "MEF-35, 'Service OAM Performance Monitoring Implementation Agreement',
         Metro Ethernet Forum, April 2012, Section 10.2 'Single-Ended Synthetic
         Loss Function for Frame Loss Ratio (FLR) and Availability'."
    DEFVAL      { 10 }
    ::= { tmnxOamPmCfgTwampLtEntry 11 }

tmnxOamPmCfgTwampLtChliThreshold OBJECT-TYPE
    SYNTAX      Unsigned32 (1..9)
    MAX-ACCESS  read-create
    STATUS      current
    DESCRIPTION
        "The value of tmnxOamPmCfgTwampLtChliThreshold specifies the MEF-35
         Consecutive High Loss Interval (CHLI) threshold for the specified
         session's TWAMP-Light test.

         The loss parameters used by SROS for TWAMP-Light tests (e.g.
         tmnxOamPmCfgTwampLtChliThreshold) are modelled after the MEF-35 loss
         parameters defined for Synthetic Loss Measurement (SLM) tests.  Hence,
         the REFERENCE text for this object is a MEF-35 SLM section.

         An attempt to change tmnxOamPmCfgTwampLtChliThreshold to a value
         greater than or equal to tmnxOamPmCfgTwampLtConsecDeltaTs will be
         rejected."
    REFERENCE
        "MEF-35, 'Service OAM Performance Monitoring Implementation Agreement',
         Metro Ethernet Forum, April 2012, Section 10.2 'Single-Ended Synthetic
         Loss Function for Frame Loss Ratio (FLR) and Availability'."
    DEFVAL      { 5 }
    ::= { tmnxOamPmCfgTwampLtEntry 12 }

tmnxOamPmCfgTwampLtFlrThreshold  OBJECT-TYPE
    SYNTAX      Unsigned32 (0..100)
    UNITS       "percent"
    MAX-ACCESS  read-create
    STATUS      current
    DESCRIPTION
        "The value of tmnxOamPmCfgTwampLtFlrThreshold specifies the MEF-35
         Frame Loss Ratio (FLR) threshold for the specified session's
         TWAMP-Light test.

         The FLR threshold is used to decide if a MEF-35 Small Time Interval
         (also known as delta_t) is Available or Unavailable.

         The loss parameters used by SROS for TWAMP-Light tests (e.g.
         tmnxOamPmCfgTwampLtFlrThreshold) are modelled after the MEF-35 loss
         parameters defined for Synthetic Loss Measurement (SLM) tests.  Hence,
         the REFERENCE text for this object is a MEF-35 SLM section."
    REFERENCE
        "MEF-35, 'Service OAM Performance Monitoring Implementation Agreement',
         Metro Ethernet Forum, April 2012, Section 10.2 'Single-Ended Synthetic
         Loss Function for Frame Loss Ratio (FLR) and Availability'."
    DEFVAL      { 50 }
    ::= { tmnxOamPmCfgTwampLtEntry 13 }

tmnxOamPmCfgTwampLtHliForceCount OBJECT-TYPE
    SYNTAX      TruthValue
    MAX-ACCESS  read-create
    STATUS      current
    DESCRIPTION
        "The value of tmnxOamPmCfgTwampLtHliForceCount specifies whether or not
         to count High Loss Intervals (HLIs) and Consecutive High Loss
         Intervals (CHLIs) when the TWAMP-Light test's MEF-35 Availability
         state is Unavailable.

         'true(1)' breaks compliance with MEF-35 by ensuring HLIs and CHLIs are
         counted in Unavailable periods.

         'false(2)' maintains compliance with MEF-35 by preventing HLIs and
         CHLIs from being counted in Unavailable periods.

         TWAMP-Light HLI and CHLI counts can be read using the following
         objects:
            tmnxOamPmStsLossTwlChliBwd,
            tmnxOamPmStsLossTwlChliFwd,
            tmnxOamPmStsLossTwlHliBwd,
            tmnxOamPmStsLossTwlHliFwd."
    REFERENCE
        "MEF-35, 'Service OAM Performance Monitoring Implementation Agreement',
         Metro Ethernet Forum, April 2012, Section 9.2.5 'Measurement Behavior
         During Periods of Unavailability and Maintenance Intervals'"
    DEFVAL      { false }
    ::= { tmnxOamPmCfgTwampLtEntry 14 }

tmnxOamPmCfgTwampLtStrTmplName   OBJECT-TYPE
    SYNTAX      TLNamedItemOrEmpty
    MAX-ACCESS  read-create
    STATUS      current
    DESCRIPTION
        "The value of tmnxOamPmCfgTwampLtStrTmplName specifies the name of the
         OAM-PM streaming template used by the specified TWAMP-Light test.

         Streaming functionality is described in the DESCRIPTION clause of
         tmnxOamPmCfgStrTmplTable.

         If specified, tmnxOamPmCfgTwampLtStrTmplName should match a template
         name created using tmnxOamPmCfgStrTmplRowStatus.  Otherwise,
         streaming will not work.

         An empty string indicates a template name has not been configured."
    DEFVAL      { "" }
    ::= { tmnxOamPmCfgTwampLtEntry 15 }

tmnxOamPmCfgTwampLtIPv6UdpCsZero OBJECT-TYPE
    SYNTAX      TruthValue
    MAX-ACCESS  read-create
    STATUS      current
    DESCRIPTION
        "The value of tmnxOamPmCfgTwampLtIPv6UdpCsZero specifies whether or not
         to allow the processing of IPv6 packets received with a UDP checksum
         of zero for the specified TWAMP-Light test.

         When tmnxOamPmCfgTwampLtIPv6UdpCsZero is false, IPv6 packets received
         with a UDP checksum of zero are discarded."
    DEFVAL      { false }
    ::= { tmnxOamPmCfgTwampLtEntry 16 }

tmnxOamPmCfgTwampLtTestSubType   OBJECT-TYPE
    SYNTAX      INTEGER {
        subTypeTwampLight (1),
        subTypeSTAMP      (2)
    }
    MAX-ACCESS  read-create
    STATUS      current
    DESCRIPTION
        "The value of tmnxOamPmCfgTwampLtTestSubType specifies the sub-type of
         the 'twampLight(3)' test.

         Code points:
             subTypeTwampLight(1) - the test uses the TWAMP-Light protocol
                 specified in RFC 5357, Appendix I.
             subTypeSTAMP(2)      - the test uses the STAMP protocol
                 specified in RFC 8762."
    REFERENCE
        "RFC 5357, 'A Two-Way Active Measurement Protocol (TWAMP)', Appendix I,
         'TWAMP Light'.
         RFC 8762, 'Simple Two-Way Active Measurement Protocol'."
    DEFVAL      { subTypeTwampLight }
    ::= { tmnxOamPmCfgTwampLtEntry 17 }

tmnxOamPmCfgTwampLtStpPadTlvSize OBJECT-TYPE
    SYNTAX      Unsigned32 (0 | 4..2000)
    UNITS       "octets"
    MAX-ACCESS  read-create
    STATUS      current
    DESCRIPTION
        "The value of tmnxOamPmCfgTwampLtStpPadTlvSize specifies the amount of
         padding added to each launched STAMP Session-Sender Packet for the
         specified session's STAMP test.

         Zero specifies that a Pad TLV should not be added.

         A value larger than zero specifies the total size (including the four
         octet header) of the Pad TLV added.

         The object used to specify the amount of padding for packets launched
         for a 'twampLight(3)' test varies with the test's sub-type, as shown
         in the following table.

         tmnxOamPmCfgTwampLtTestSubType    Padding Size Object
         ------------------------------    --------------------------------
         'subTypeTwampLight'               tmnxOamPmCfgTwampLtPadSize
         'subTypeSTAMP'                    tmnxOamPmCfgTwampLtStpPadTlvSize"
    REFERENCE
        "RFC 8762, 'Simple Two-Way Active Measurement Protocol', March 2020.
         RFC 8972, 'Simple Two-Way Active Measurement Protocol Optional
         Extensions', January 2021."
    DEFVAL      { 0 }
    ::= { tmnxOamPmCfgTwampLtEntry 18 }

tmnxOamPmCfgTwampLtTimestampFmt  OBJECT-TYPE
    SYNTAX      INTEGER {
        ntp (0),
        ptp (1)
    }
    MAX-ACCESS  read-create
    STATUS      current
    DESCRIPTION
        "The value of tmnxOamPmCfgTwampLtTimestampFmt specifies the timestamp
         format used in packets sent for the 'twampLight(3)' test.

         Code points:
             ntp(0) - send Network Time Protocol (NTP) timestamps.
             ptp(1) - send Precision Time Protocol Version 2 (PTPv2)
                 timestamps.

         This object is applicable to tests with
             tmnxOamPmCfgTwampLtTestSubType = 'subTypeTwampLight'
         and
             tmnxOamPmCfgTwampLtTestSubType = 'subTypeSTAMP'."
    REFERENCE
        "RFC 8186, 'Support of the IEEE 1588 Timestamp Format in a
         Two-Way Active Measurement Protocol (TWAMP)'.
         RFC 8762, 'Simple Two-Way Active Measurement Protocol', Section
         4.2.1, 'Session-Sender Behavior and Packet Format'."
    DEFVAL      { ntp }
    ::= { tmnxOamPmCfgTwampLtEntry 19 }

tmnxOamPmCfgTwampLtIsAutoTestId  OBJECT-TYPE
    SYNTAX      TruthValue
    MAX-ACCESS  read-create
    STATUS      current
    DESCRIPTION
        "The value of the object tmnxOamPmCfgTwampLtIsAutoTestId specifies
         whether the system auto assigns an available test identifier to be
         used for this session's TWAMP-Light test."
    DEFVAL      { false }
    ::= { tmnxOamPmCfgTwampLtEntry 20 }

tmnxOamPmCfgTwampLtTestIdInUse   OBJECT-TYPE
    SYNTAX      Unsigned32 (0..4294967295)
    MAX-ACCESS  read-only
    STATUS      current
    DESCRIPTION
        "The value of tmnxOamPmCfgTwampLtTestIdInUse indicates the test
         identifier copied into the Test ID field of the TWAMP-test PDUs."
    ::= { tmnxOamPmCfgTwampLtEntry 21 }

tmnxOamPmCfgTwlRflTable          OBJECT-TYPE
    SYNTAX      SEQUENCE OF TmnxOamPmCfgTwlRflEntry
    MAX-ACCESS  not-accessible
    STATUS      current
    DESCRIPTION
        "tmnxOamPmCfgTwlRflTable contains the configuration information for OAM
         Performance Monitoring TWAMP-Light (Two-Way Active Measurement
         Protocol, Light) reflectors.

         A TWAMP-Light reflector responds to TWAMP-Test frames."
    REFERENCE
        "RFC 5357, 'A Two-Way Active Measurement Protocol (TWAMP)', Appendix I,
         'TWAMP Light'."
    ::= { tmnxOamPmCfgTableObjs 10 }

tmnxOamPmCfgTwlRflEntry          OBJECT-TYPE
    SYNTAX      TmnxOamPmCfgTwlRflEntry
    MAX-ACCESS  not-accessible
    STATUS      current
    DESCRIPTION
        "tmnxOamPmCfgTwlRflEntry contains the configuration information for the
         OAM Performance Monitoring TWAMP-Light reflector for the virtual
         router specified by the given service identifier.

         Service identifier zero specifies the Base virtual router (i.e. the
         virtual router with TIMETRA-VRTR-MIB::vRtrName = 'Base').

         A service identifier larger than zero must be the service identifier
         of a VPRN service (i.e. a service with TIMETRA-SERV-MIB::svcType =
         'vprn(4)').

         Rows are created or destroyed by SNMP Set operations on
         tmnxOamPmCfgTwlRflRowStatus.

         A row indexed by a VPRN service identifier is destroyed when the VPRN
         service is destroyed."
    INDEX       { svcId }
    ::= { tmnxOamPmCfgTwlRflTable 1 }

TmnxOamPmCfgTwlRflEntry          ::= SEQUENCE
{
    tmnxOamPmCfgTwlRflRowStatus      RowStatus,
    tmnxOamPmCfgTwlRflAdminStatus    TmnxEnabledDisabled,
    tmnxOamPmCfgTwlRflDescription    TItemDescription,
    tmnxOamPmCfgTwlRflListenUdpPort  Unsigned32,
    tmnxOamPmCfgTwlRflIpv6UdpZero    TruthValue,
    tmnxOamPmCfgTwlRflType           INTEGER,
    tmnxOamPmCfgTwlRflLagMeasEnabled TruthValue
}

tmnxOamPmCfgTwlRflRowStatus      OBJECT-TYPE
    SYNTAX      RowStatus
    MAX-ACCESS  read-create
    STATUS      current
    DESCRIPTION
        "The value of tmnxOamPmCfgTwlRflRowStatus specifies the status of the
         configuration row for the TWAMP-Light reflector for the virtual router
         specified by the given service identifier.

         When a reflector is created, tmnxOamPmCfgTwlRflRowStatus and
         tmnxOamPmCfgTwlRflListenUdpPort must be specified in the same SNMP Set
         PDU."
    ::= { tmnxOamPmCfgTwlRflEntry 1 }

tmnxOamPmCfgTwlRflAdminStatus    OBJECT-TYPE
    SYNTAX      TmnxEnabledDisabled
    MAX-ACCESS  read-create
    STATUS      current
    DESCRIPTION
        "The value of tmnxOamPmCfgTwlRflAdminStatus specifies whether or not
         the specified TWAMP-Light reflector is administratively enabled.

         tmnxOamPmCfgTwlRflListenUdpPort cannot be changed while
         tmnxOamPmCfgTwlRflAdminStatus is 'enabled(1)'."
    DEFVAL      { disabled }
    ::= { tmnxOamPmCfgTwlRflEntry 2 }

tmnxOamPmCfgTwlRflDescription    OBJECT-TYPE
    SYNTAX      TItemDescription
    MAX-ACCESS  read-create
    STATUS      current
    DESCRIPTION
        "The value of tmnxOamPmCfgTwlRflDescription specifies the descriptive
         text for the specified TWAMP-Light reflector."
    DEFVAL      { "" }
    ::= { tmnxOamPmCfgTwlRflEntry 3 }

tmnxOamPmCfgTwlRflListenUdpPort  OBJECT-TYPE
    SYNTAX      Unsigned32 (862 | 1024..65535)
    MAX-ACCESS  read-create
    STATUS      current
    DESCRIPTION
        "The value of tmnxOamPmCfgTwlRflListenUdpPort specifies the UDP port on
         which the specified TWAMP-Light reflector listens for TWAMP PDUs.

         When a reflector is created, tmnxOamPmCfgTwlRflRowStatus and
         tmnxOamPmCfgTwlRflListenUdpPort must be specified in the same SNMP Set
         PDU.

         tmnxOamPmCfgTwlRflListenUdpPort cannot be changed while
         tmnxOamPmCfgTwlRflAdminStatus is 'enabled(1)'.

         The valid range is 862|64364..64373.  A wider range appears in the
         SYNTAX clause (above), for backward compatibility.

         IANA has standardized the use of UDP port 862 for TWAMP Control
         services."
    REFERENCE
        "IANA Service Name and Transport Protocol Port Number Registry,
         2017-12-29, https://www.iana.org/assignments/
         service-names-port-numbers/ service-names-port-numbers.xhtml."
    ::= { tmnxOamPmCfgTwlRflEntry 4 }

tmnxOamPmCfgTwlRflIpv6UdpZero    OBJECT-TYPE
    SYNTAX      TruthValue
    MAX-ACCESS  read-create
    STATUS      current
    DESCRIPTION
        "The value of tmnxOamPmCfgTwlRflIpv6UdpZero specifies whether or not to
         allow the processing of IPv6 packets received with a UDP checksum of
         zero.

         When tmnxOamPmCfgTwlRflIpv6UdpZero is false, IPv6 packets received
         with a UDP checksum of zero are discarded."
    DEFVAL      { false }
    ::= { tmnxOamPmCfgTwlRflEntry 5 }

tmnxOamPmCfgTwlRflType           OBJECT-TYPE
    SYNTAX      INTEGER {
        stamp      (1),
        twampLight (2)
    }
    MAX-ACCESS  read-create
    STATUS      current
    DESCRIPTION
        "The value of tmnxOamPmCfgTwlRflType specifies this reflector's packet
         processing behavior.

         When set to 'twampLight', the reflector will follow standard
         TWAMP-Light reflector behavior. The reflector will do no TLV
         processing and will treat all additional bytes as padding to be
         reflected.

         When set to 'stamp', TLV processing will occur. Given a valid STAMP
         TLV, the packet will be processed according to the STAMP options and
         appropriately reflected."
    REFERENCE
        "RFC 8972, 'Simple Two-Way Active Measurement Protocol Optional
         Extensions', January 2021."
    DEFVAL      { twampLight }
    ::= { tmnxOamPmCfgTwlRflEntry 6 }

tmnxOamPmCfgTwlRflLagMeasEnabled OBJECT-TYPE
    SYNTAX      TruthValue
    MAX-ACCESS  read-create
    STATUS      current
    DESCRIPTION
        "The value of tmnxOamPmCfgTwlRflLagMeasEnabled specifies whether or not
         to enable the processing of the 'Sender Micro-session ID' and
         'Reflector Micro-session ID' fields of TWAMP-Light LAG Measurement
         packets by the reflector.

         This value can be changed away from default for the Base router only."
    REFERENCE
        "IETF draft-ietf-ippm-otwamp-on-lag-08, 'One-way/Two-way Active
         Measurement Protocol Extensions for Performance Measurement on LAG',
         11-Dec-2023, Section 4.2.1 'Sender Packet Format and Content'."
    DEFVAL      { false }
    ::= { tmnxOamPmCfgTwlRflEntry 7 }

tmnxOamPmCfgTwlRflPfxTable       OBJECT-TYPE
    SYNTAX      SEQUENCE OF TmnxOamPmCfgTwlRflPfxEntry
    MAX-ACCESS  not-accessible
    STATUS      current
    DESCRIPTION
        "tmnxOamPmCfgTwlRflPfxTable contains the configuration information for
         OAM Performance Monitoring TWAMP-Light (Two-Way Active Measurement
         Protocol, Light) reflector prefixes.

         The set of prefixes configured for a TWAMP-Light reflector defines a
         set of valid source addresses for the reflector.  When the reflector is
         validating an incoming TWAMP-Test PDU, the PDU is rejected (and
         counted) if its source address is invalid."
    REFERENCE
        "RFC 5357, 'A Two-Way Active Measurement Protocol (TWAMP)', Appendix I,
         'TWAMP Light'."
    ::= { tmnxOamPmCfgTableObjs 11 }

tmnxOamPmCfgTwlRflPfxEntry       OBJECT-TYPE
    SYNTAX      TmnxOamPmCfgTwlRflPfxEntry
    MAX-ACCESS  not-accessible
    STATUS      current
    DESCRIPTION
        "tmnxOamPmCfgTwlRflPfxEntry contains the configuration information for
         the OAM Performance Monitoring TWAMP-Light reflector prefix specified
         by the indices.

         Rows are created or destroyed by SNMP Set operations on
         tmnxOamPmCfgTwlRflPfxRowStatus.

         Rows are destroyed when the corresponding tmnxOamPmCfgTwlRflTable row
         is destroyed."
    INDEX       {
        svcId,
        tmnxOamPmCfgTwlRflPfxPrefixType,
        tmnxOamPmCfgTwlRflPfxPrefix,
        tmnxOamPmCfgTwlRflPfxPrefixLen
    }
    ::= { tmnxOamPmCfgTwlRflPfxTable 1 }

TmnxOamPmCfgTwlRflPfxEntry       ::= SEQUENCE
{
    tmnxOamPmCfgTwlRflPfxPrefixType  InetAddressType,
    tmnxOamPmCfgTwlRflPfxPrefix      InetAddress,
    tmnxOamPmCfgTwlRflPfxPrefixLen   InetAddressPrefixLength,
    tmnxOamPmCfgTwlRflPfxRowStatus   RowStatus,
    tmnxOamPmCfgTwlRflPfxDescription TItemDescription
}

tmnxOamPmCfgTwlRflPfxPrefixType  OBJECT-TYPE
    SYNTAX      InetAddressType
    MAX-ACCESS  not-accessible
    STATUS      current
    DESCRIPTION
        "The value of tmnxOamPmCfgTwlRflPfxPrefixType specifies the prefix type
         of tmnxOamPmCfgTwlRflPfxPrefix."
    ::= { tmnxOamPmCfgTwlRflPfxEntry 1 }

tmnxOamPmCfgTwlRflPfxPrefix      OBJECT-TYPE
    SYNTAX      InetAddress (SIZE (4|16))
    MAX-ACCESS  not-accessible
    STATUS      current
    DESCRIPTION
        "The value of tmnxOamPmCfgTwlRflPfxPrefix (in combination with
         tmnxOamPmCfgTwlRflPfxPrefixType and tmnxOamPmCfgTwlRflPfxPrefixLen)
         specifies a valid source prefix for the TWAMP-Light reflector
         specified by the given service identifier.

         A TWAMP-Test PDU with an invalid source address (i.e. a source address
         which matches none of the prefixes configured against the reflector)
         will be counted and dropped by the reflector.  Therefore, if no
         prefixes are configured against a reflector, the reflector will drop
         and count all incoming PDUs.

         Configuring the prefix 0.0.0.0/0 instructs the reflector to accept the
         source address in each incoming IPv4 TWAMP-Test PDU.

         Configuring the prefix 0::0/0 instructs the reflector to accept the
         source address in each incoming IPv6 TWAMP-Test PDU."
    ::= { tmnxOamPmCfgTwlRflPfxEntry 2 }

tmnxOamPmCfgTwlRflPfxPrefixLen   OBJECT-TYPE
    SYNTAX      InetAddressPrefixLength (0..128)
    UNITS       "bits"
    MAX-ACCESS  not-accessible
    STATUS      current
    DESCRIPTION
        "The value of tmnxOamPmCfgTwlRflPfxPrefixLen (in combination with
         tmnxOamPmCfgTwlRflPfxPrefixType and tmnxOamPmCfgTwlRflPfxPrefix)
         specifies a valid source prefix for the TWAMP-Light reflector
         specified by the given service identifier."
    ::= { tmnxOamPmCfgTwlRflPfxEntry 3 }

tmnxOamPmCfgTwlRflPfxRowStatus   OBJECT-TYPE
    SYNTAX      RowStatus
    MAX-ACCESS  read-create
    STATUS      current
    DESCRIPTION
        "The value of tmnxOamPmCfgTwlRflPfxRowStatus specifies the status of
         the configuration row for the specified TWAMP-Light reflector prefix.

         An attempt to create a row will be rejected if there is no row with
         the same svcId in tmnxOamPmCfgTwlRflTable."
    ::= { tmnxOamPmCfgTwlRflPfxEntry 4 }

tmnxOamPmCfgTwlRflPfxDescription OBJECT-TYPE
    SYNTAX      TItemDescription
    MAX-ACCESS  read-create
    STATUS      current
    DESCRIPTION
        "The value of tmnxOamPmCfgTwlRflPfxDescription specifies the
         descriptive text for the specified TWAMP-Light reflector prefix."
    DEFVAL      { "" }
    ::= { tmnxOamPmCfgTwlRflPfxEntry 5 }

tmnxOamPmCfgLossLmmTable         OBJECT-TYPE
    SYNTAX      SEQUENCE OF TmnxOamPmCfgLossLmmEntry
    MAX-ACCESS  not-accessible
    STATUS      current
    DESCRIPTION
        "tmnxOamPmCfgLossLmmTable contains the configuration information for
         OAM Performance Monitoring Loss Measurement Message (LMM) tests."
    REFERENCE
        "ITU-T G.8013/Y.1731, 'OAM functions and mechanisms for Ethernet based
         networks', 07/2011, Section 8.1 'Frame loss measurement (ETH-LM)'."
    ::= { tmnxOamPmCfgTableObjs 12 }

tmnxOamPmCfgLossLmmEntry         OBJECT-TYPE
    SYNTAX      TmnxOamPmCfgLossLmmEntry
    MAX-ACCESS  not-accessible
    STATUS      current
    DESCRIPTION
        "tmnxOamPmCfgLossLmmEntry contains the configuration information for
         one OAM Performance Monitoring Loss Measurement Message (LMM) test.

         Rows are created or destroyed by SNMP Set operations on
         tmnxOamPmCfgLossLmmRowStatus.

         An attempt to change any value in a row (except
         tmnxOamPmCfgLossLmmAdminStatus and tmnxOamPmCfgLossLmmOnDmndStatus)
         will be rejected if tmnxOamPmCfgLossLmmAdminStatus is 'enabled(1)'.

         The following objects must all be set together in one SNMP Set PDU:
            tmnxOamPmCfgLossLmmChliThreshold,
            tmnxOamPmCfgLossLmmConsecDeltaTs, and
            tmnxOamPmCfgLossLmmTxFrmsPerDelT."
    INDEX       { tmnxOamPmCfgSessName }
    ::= { tmnxOamPmCfgLossLmmTable 1 }

TmnxOamPmCfgLossLmmEntry         ::= SEQUENCE
{
    tmnxOamPmCfgLossLmmRowStatus     RowStatus,
    tmnxOamPmCfgLossLmmAdminStatus   TmnxEnabledDisabled,
    tmnxOamPmCfgLossLmmOnDmndStatus  TmnxEnabledDisabledOrNA,
    tmnxOamPmCfgLossLmmTestId        Unsigned32,
    tmnxOamPmCfgLossLmmInterval      Unsigned32,
    tmnxOamPmCfgLossLmmTestDuration  Unsigned32,
    tmnxOamPmCfgLossLmmRunTimeLeft   Unsigned32,
    tmnxOamPmCfgLossLmmTxFrmsPerDelT Unsigned32,
    tmnxOamPmCfgLossLmmConsecDeltaTs Unsigned32,
    tmnxOamPmCfgLossLmmChliThreshold Unsigned32,
    tmnxOamPmCfgLossLmmFlrThreshold  Unsigned32,
    tmnxOamPmCfgLossLmmAvAdminStatus TmnxEnabledDisabled,
    tmnxOamPmCfgLossLmmHliForceCount TruthValue,
    tmnxOamPmCfgLossLmmCollFcAdminSt TmnxEnabledDisabled,
    tmnxOamPmCfgLossLmmIsAutoTestId  TruthValue,
    tmnxOamPmCfgLossLmmTestIdInUse   Unsigned32
}

tmnxOamPmCfgLossLmmRowStatus     OBJECT-TYPE
    SYNTAX      RowStatus
    MAX-ACCESS  read-create
    STATUS      current
    DESCRIPTION
        "The value of tmnxOamPmCfgLossLmmRowStatus specifies the status of the
         configuration row for the specified session's LMM test.

         An attempt to create a row for a session with
         tmnxOamPmCfgSessTestFamily other than 'ethernet(1)' will be rejected."
    ::= { tmnxOamPmCfgLossLmmEntry 1 }

tmnxOamPmCfgLossLmmAdminStatus   OBJECT-TYPE
    SYNTAX      TmnxEnabledDisabled
    MAX-ACCESS  read-create
    STATUS      current
    DESCRIPTION
        "The value of tmnxOamPmCfgLossLmmAdminStatus specifies whether or not
         the specified session's LMM test is administratively enabled.

         If the session type (tmnxOamPmCfgSessType) is 'proactive(1)', setting
         tmnxOamPmCfgLossLmmAdminStatus to 'enabled(1)'/'disabled(2)'
         starts/stops the test.

         If the session type is 'onDemand(2)', see the DESCRIPTION clause for
         tmnxOamPmCfgLossLmmOnDmndStatus for information on starting/stopping
         the test.

         An attempt to set this object to 'enabled(1)' will be rejected if the
         tmnxOamPmCfgSessEthTable row for the specified session has incomplete
         endpoint information for the test (e.g. if
         tmnxOamPmCfgSessEthDestMacAddr is the all-zeroes MAC address)."
    DEFVAL      { disabled }
    ::= { tmnxOamPmCfgLossLmmEntry 2 }

tmnxOamPmCfgLossLmmOnDmndStatus  OBJECT-TYPE
    SYNTAX      TmnxEnabledDisabledOrNA
    MAX-ACCESS  read-create
    STATUS      current
    DESCRIPTION
        "The value of tmnxOamPmCfgLossLmmOnDmndStatus specifies the status of
         the on-demand LMM test for the specified session.

         Values:
            'enabled(1)'
                Set by an SNMP manager to start an on-demand LMM test.  The test
                will start if tmnxOamPmCfgLossLmmAdminStatus is 'enabled(1)'.
            'disabled(2)'
                Set by an SNMP manager to stop an on-demand LMM test.
                Set by SROS to indicate an on-demand LMM test has stopped
                running because the configured period for the test (i.e.
                tmnxOamPmCfgLossLmmTestDuration) has ended.
                Set by SROS for an on-demand LMM test when
                tmnxOamPmCfgLossLmmAdminStatus is set to 'disabled(2)'.
            'notApplicable(3)'
                This code point is the only acceptable value for a proactive LMM
                test.  An attempt to set this code point for an on-demand LMM
                test will be rejected.

         The default value is 'disabled(2)' for an on-demand LMM test, and
         'notApplicable(3)' for a proactive LMM test."
    ::= { tmnxOamPmCfgLossLmmEntry 3 }

tmnxOamPmCfgLossLmmTestId        OBJECT-TYPE
    SYNTAX      Unsigned32 (0..2147483647)
    MAX-ACCESS  read-create
    STATUS      current
    DESCRIPTION
        "The value of tmnxOamPmCfgLossLmmTestId specifies the test identifier
         for the specified session's LMM test.

         When tmnxOamPmCfgLossLmmIsAutoTestId is being set 'true(1)', the value
         of tmnxOamPmCfgLossLmmTestId is not used and it must be set to 0.

         An attempt to add a duplicate test identifier to this table will be
         rejected.

         Test identifier values larger than 2147483647 are reserved for
         internal use."
    DEFVAL      { 0 }
    ::= { tmnxOamPmCfgLossLmmEntry 4 }

tmnxOamPmCfgLossLmmInterval      OBJECT-TYPE
    SYNTAX      Unsigned32 (100 | 1000 | 10000)
    UNITS       "milliseconds"
    MAX-ACCESS  read-create
    STATUS      current
    DESCRIPTION
        "The value of tmnxOamPmCfgLossLmmInterval specifies the elapsed time
         between transmission of Y.1731 LMM PDUs for the specified session's
         LMM test."
    DEFVAL      { 1000 }
    ::= { tmnxOamPmCfgLossLmmEntry 5 }

tmnxOamPmCfgLossLmmTestDuration  OBJECT-TYPE
    SYNTAX      Unsigned32 (0..86400)
    UNITS       "seconds"
    MAX-ACCESS  read-create
    STATUS      current
    DESCRIPTION
        "The value of tmnxOamPmCfgLossLmmTestDuration specifies the test
         duration for the specified session's LMM test.

         Zero specifies a test which runs until it is manually stopped.

         An attempt to set a non-zero value will be rejected if
         tmnxOamPmCfgSessType is 'proactive(1)'."
    DEFVAL      { 0 }
    ::= { tmnxOamPmCfgLossLmmEntry 6 }

tmnxOamPmCfgLossLmmRunTimeLeft   OBJECT-TYPE
    SYNTAX      Unsigned32 (0..86400)
    UNITS       "seconds"
    MAX-ACCESS  read-only
    STATUS      current
    DESCRIPTION
        "The value of tmnxOamPmCfgLossLmmRunTimeLeft indicates the run time
         remaining for the specified session's LMM test.

         For example, suppose an LMM test has the following configuration:

         tmnxOamPmCfgSessType   tmnxOamPmCfgLossLmmTestDuration
         --------------------   --------------------------------
         'onDemand(2)'          1000 (seconds)

         Then, when the LMM test is started (see
         tmnxOamPmCfgLossLmmOnDmndStatus), tmnxOamPmCfgLossLmmRunTimeLeft is
         initialized to 1000 seconds.  After a minute,
         tmnxOamPmCfgLossLmmRunTimeLeft is 940 seconds.

         If tmnxOamPmCfgSessType is 'proactive(1)', zero is always returned
         (because a proactive test runs until it is manually stopped).

         If tmnxOamPmCfgSessType is 'onDemand(2)' and the test is stopped (see
         tmnxOamPmCfgLossLmmOnDmndStatus), zero is returned (because the test
         is not running)."
    ::= { tmnxOamPmCfgLossLmmEntry 7 }

tmnxOamPmCfgLossLmmTxFrmsPerDelT OBJECT-TYPE
    SYNTAX      Unsigned32 (1..50)
    UNITS       "frames"
    MAX-ACCESS  read-create
    STATUS      current
    DESCRIPTION
        "The value of tmnxOamPmCfgLossLmmTxFrmsPerDelT specifies the number of
         LMM frames to send in one MEF-35 'delta_t' (also known as 'Small Time
         Interval') when computing availability statistics for the specified
         session's LMM test.

         The availability parameters used by SROS for LMM tests (e.g.
         tmnxOamPmCfgLossLmmTxFrmsPerDelT) are modelled after the MEF-35
         availability parameters defined for Synthetic Loss Measurement (SLM)
         tests.  Hence, the REFERENCE text for this object is a MEF-35 SLM
         section.

         Expressed in milliseconds,
         delta_t =
            tmnxOamPmCfgLossLmmTxFrmsPerDelT *
            tmnxOamPmCfgLossLmmInterval."
    REFERENCE
        "MEF-35, 'Service OAM Performance Monitoring Implementation Agreement',
         Metro Ethernet Forum, April 2012, Section 10.2 'Single-Ended Synthetic
         Loss Function for Frame Loss Ratio (FLR) and Availability'."
    DEFVAL      { 10 }
    ::= { tmnxOamPmCfgLossLmmEntry 8 }

tmnxOamPmCfgLossLmmConsecDeltaTs OBJECT-TYPE
    SYNTAX      Unsigned32 (2..10)
    MAX-ACCESS  read-create
    STATUS      current
    DESCRIPTION
        "The value of tmnxOamPmCfgLossLmmConsecDeltaTs specifies the number of
         consecutive MEF-35 'delta_t's (also known as 'Small Time Intervals')
         which constitute a MEF-35 'Availability Window' when computing
         availability statistics for the specified session's LMM test.

         The availability parameters used by SROS for LMM tests (e.g.
         tmnxOamPmCfgLossLmmConsecDeltaTs) are modelled after the MEF-35
         availability parameters defined for Synthetic Loss Measurement (SLM)
         tests.  Hence, the REFERENCE text for this object is a MEF-35 SLM
         section.

         The duration of an Availability Window (in milliseconds) is
         tmnxOamPmCfgLossLmmTxFrmsPerDelT * tmnxOamPmCfgLossLmmInterval *
         tmnxOamPmCfgLossLmmConsecDeltaTs.  An attempt to change the duration of
         an Availability Window to more than 100,000 milliseconds will be
         rejected.

         An attempt to change tmnxOamPmCfgLossLmmConsecDeltaTs to a value less
         than or equal to tmnxOamPmCfgLossLmmChliThreshold will be rejected."
    REFERENCE
        "MEF-35, 'Service OAM Performance Monitoring Implementation Agreement',
         Metro Ethernet Forum, April 2012, Section 10.2 'Single-Ended Synthetic
         Loss Function for Frame Loss Ratio (FLR) and Availability'."
    DEFVAL      { 10 }
    ::= { tmnxOamPmCfgLossLmmEntry 9 }

tmnxOamPmCfgLossLmmChliThreshold OBJECT-TYPE
    SYNTAX      Unsigned32 (1..9)
    MAX-ACCESS  read-create
    STATUS      current
    DESCRIPTION
        "The value of tmnxOamPmCfgLossLmmChliThreshold specifies the MEF-35
         Consecutive High Loss Interval (CHLI) threshold for the specified
         session's LMM test.

         The availability parameters used by SROS for LMM tests (e.g.
         tmnxOamPmCfgLossLmmChliThreshold) are modelled after the MEF-35
         availability parameters defined for Synthetic Loss Measurement (SLM)
         tests.  Hence, the REFERENCE text for this object is a MEF-35 SLM
         section.

         An attempt to change tmnxOamPmCfgLossLmmChliThreshold to a value
         greater than or equal to tmnxOamPmCfgLossLmmConsecDeltaTs will be
         rejected."
    REFERENCE
        "MEF-35, 'Service OAM Performance Monitoring Implementation Agreement',
         Metro Ethernet Forum, April 2012, Section 10.2 'Single-Ended Synthetic
         Loss Function for Frame Loss Ratio (FLR) and Availability'."
    DEFVAL      { 5 }
    ::= { tmnxOamPmCfgLossLmmEntry 10 }

tmnxOamPmCfgLossLmmFlrThreshold  OBJECT-TYPE
    SYNTAX      Unsigned32 (0..100)
    UNITS       "percent"
    MAX-ACCESS  read-create
    STATUS      current
    DESCRIPTION
        "The value of tmnxOamPmCfgLossLmmFlrThreshold specifies the MEF-35
         Frame Loss Ratio (FLR) threshold for the specified session's LMM test.

         The FLR threshold is used to decide if a MEF-35 'delta_t' (also known
         as 'Small Time Interval') is Available or Unavailable.

         The availability parameters used by SROS for LMM tests (e.g.
         tmnxOamPmCfgLossLmmFlrThreshold) are modelled after the MEF-35
         availability parameters defined for Synthetic Loss Measurement (SLM)
         tests.  Hence, the REFERENCE text for this object is a MEF-35 SLM
         section."
    REFERENCE
        "MEF-35, 'Service OAM Performance Monitoring Implementation Agreement',
         Metro Ethernet Forum, April 2012, Section 10.2 'Single-Ended Synthetic
         Loss Function for Frame Loss Ratio (FLR) and Availability'."
    DEFVAL      { 50 }
    ::= { tmnxOamPmCfgLossLmmEntry 11 }

tmnxOamPmCfgLossLmmAvAdminStatus OBJECT-TYPE
    SYNTAX      TmnxEnabledDisabled
    MAX-ACCESS  read-create
    STATUS      current
    DESCRIPTION
        "The value of tmnxOamPmCfgLossLmmAvAdminStatus specifies whether or not
         collection of availability statistics is enabled for the specified
         session's LMM test.

         When the value of tmnxOamPmCfgLossLmmAvAdminStatus is 'disabled(2)',
         the following configuration objects are ignored:
            tmnxOamPmCfgLossLmmChliThreshold,
            tmnxOamPmCfgLossLmmConsecDeltaTs,
            tmnxOamPmCfgLossLmmFlrThreshold, and
            tmnxOamPmCfgLossLmmTxFrmsPerDelT.

         When the value of tmnxOamPmCfgLossLmmAvAdminStatus is 'disabled(2)',
         the value of each of the following counters is always zero:
            tmnxOamPmStsLossLmmAvailIndBwd,
            tmnxOamPmStsLossLmmAvailIndFwd,
            tmnxOamPmStsLossLmmChliBwd,
            tmnxOamPmStsLossLmmChliFwd,
            tmnxOamPmStsLossLmmHliBwd,
            tmnxOamPmStsLossLmmHliFwd,
            tmnxOamPmStsLossLmmUnavlIndBwd,
            tmnxOamPmStsLossLmmUnavlIndFwd,
            tmnxOamPmStsLossLmmUndetDelTsBwd,
            tmnxOamPmStsLossLmmUndetDelTsFwd,
            tmnxOamPmStsLossLmmUndtAvlBwd,
            tmnxOamPmStsLossLmmUndtAvlFwd,
            tmnxOamPmStsLossLmmUndtUnavlBwd, and
            tmnxOamPmStsLossLmmUndtUnavlFwd.

         When the counters listed above are stuck at zero, the corresponding
         TCA raise thresholds (for the specified LMM test) are never met or
         exceeded.  The corresponding TCA raise thresholds are configured using
         the following objects:
            tmnxOamPmCfgThrLossChliRaise,
            tmnxOamPmCfgThrLossHliRaise,
            tmnxOamPmCfgThrLossUnavlIndRaise,
            tmnxOamPmCfgThrLossUndtAvlRaise, or
            tmnxOamPmCfgThrLossUndtUnavlRais."
    DEFVAL      { disabled }
    ::= { tmnxOamPmCfgLossLmmEntry 12 }

tmnxOamPmCfgLossLmmHliForceCount OBJECT-TYPE
    SYNTAX      TruthValue
    MAX-ACCESS  read-create
    STATUS      current
    DESCRIPTION
        "The value of tmnxOamPmCfgLossLmmHliForceCount specifies whether or not
         to count High Loss Intervals (HLIs) and Consecutive High Loss
         Intervals (CHLIs) when the LMM test's MEF-35 Availability state is
         Unavailable.

         'true(1)' breaks compliance with MEF-35 by ensuring HLIs and CHLIs are
         counted in Unavailable periods.

         'false(2)' maintains compliance with MEF-35 by preventing HLIs and
         CHLIs from being counted in Unavailable periods.

         LMM HLI and CHLI counts can be read using the following objects:
            tmnxOamPmStsLossLmmChliBwd,
            tmnxOamPmStsLossLmmChliFwd,
            tmnxOamPmStsLossLmmHliBwd,
            tmnxOamPmStsLossLmmHliFwd."
    REFERENCE
        "MEF-35, 'Service OAM Performance Monitoring Implementation Agreement',
         Metro Ethernet Forum, April 2012, Section 9.2.5 'Measurement Behavior
         During Periods of Unavailability and Maintenance Intervals'"
    DEFVAL      { false }
    ::= { tmnxOamPmCfgLossLmmEntry 13 }

tmnxOamPmCfgLossLmmCollFcAdminSt OBJECT-TYPE
    SYNTAX      TmnxEnabledDisabled
    MAX-ACCESS  read-create
    STATUS      current
    DESCRIPTION
        "The value of tmnxOamPmCfgLossLmmCollFcAdminSt specifies the
         administrative state of the collection of Forwarding Class (FC)
         statistics for the specified LMM test.

         Successful collection of FC statistics can occur if the LMM test's
         Ethernet priority (i.e. tmnxOamPmCfgSessEthPriority) matches one of
         the Forwarding Classes counted at a collection point.

         The mapping between an Ethernet priority and a Forwarding Class is
         defined by the TIMETRA-TC-MIB::TFCType TEXTUAL-CONVENTION.

         The set of Forwarding Classes counted at a collection point is
         configured using one of the following objects:
            TIMETRA-IEEE8021-CFM-MIB:tmnxDot1agCfmMepCollLmmFcSts,
            TIMETRA-IEEE8021-CFM-MIB:tmnxDot1agCfmMepCollLmmFcStsInP,
            TIMETRA-SAP-MIB:sapEthCfmCollLmmFcSts,
            TIMETRA-SAP-MIB:sapEthCfmCollLmmFcStsInP,
            TIMETRA-SDP-MIB:sdpBindEthCfmCollLmmFcSts,
            TIMETRA-SDP-MIB:sdpBindEthCfmCollLmmFcStsInP."
    DEFVAL      { disabled }
    ::= { tmnxOamPmCfgLossLmmEntry 14 }

tmnxOamPmCfgLossLmmIsAutoTestId  OBJECT-TYPE
    SYNTAX      TruthValue
    MAX-ACCESS  read-create
    STATUS      current
    DESCRIPTION
        "The value of the object tmnxOamPmCfgLossLmmIsAutoTestId specifies
         whether the system auto assigns an available test identifier to be
         used for this session's LMM test."
    DEFVAL      { false }
    ::= { tmnxOamPmCfgLossLmmEntry 15 }

tmnxOamPmCfgLossLmmTestIdInUse   OBJECT-TYPE
    SYNTAX      Unsigned32 (0..4294967295)
    MAX-ACCESS  read-only
    STATUS      current
    DESCRIPTION
        "The value of tmnxOamPmCfgLossLmmTestIdInUse indicates the test
         identifier copied into the Test ID TLV of the Y.1731 LMM PDUs."
    ::= { tmnxOamPmCfgLossLmmEntry 16 }

tmnxOamPmCfgThrLossFwBwTable     OBJECT-TYPE
    SYNTAX      SEQUENCE OF TmnxOamPmCfgThrLossFwBwEntry
    MAX-ACCESS  not-accessible
    STATUS      current
    DESCRIPTION
        "tmnxOamPmCfgThrLossFwBwTable contains configured thresholds for OAM
         Performance Monitoring loss TCAs.  The subset of the loss thresholds
         that are only configurable in the forward and backward directions is
         configured using this table."
    REFERENCE
        "MEF-35, 'Service OAM Performance Monitoring Implementation Agreement',
         Metro Ethernet Forum, April 2012, Section 10.2, 'Single-Ended Synthetic
         Loss Function for Frame Loss Ratio (FLR) and Availability'."
    ::= { tmnxOamPmCfgTableObjs 13 }

tmnxOamPmCfgThrLossFwBwEntry     OBJECT-TYPE
    SYNTAX      TmnxOamPmCfgThrLossFwBwEntry
    MAX-ACCESS  not-accessible
    STATUS      current
    DESCRIPTION
        "tmnxOamPmCfgThrLossFwBwEntry contains the configured thresholds for the
         forward or backward direction of one OAM-PM loss test.  For example, a
         row may contain the configurable thresholds for the forward direction
         for the SLM test belonging to OAM-PM session OAM_PM_Eth_session_1.

         SROS creates/destroys two rows (forward and backward) in this table for
         each OAM-PM loss test created/destroyed.  A manager creates a loss test
         using:
            tmnxOamPmCfgLossLmmRowStatus,
            tmnxOamPmCfgLossSlmRowStatus, or
            tmnxOamPmCfgTwampLtRowStatus."
    INDEX       {
        tmnxOamPmCfgSessName,
        tmnxOamPmCfgTestType,
        tmnxOamPmCfgForwardBackward
    }
    ::= { tmnxOamPmCfgThrLossFwBwTable 1 }

TmnxOamPmCfgThrLossFwBwEntry     ::= SEQUENCE
{
    tmnxOamPmCfgTestType             TmnxOamPmTestType,
    tmnxOamPmCfgForwardBackward      TmnxOamPmForwardBackward,
    tmnxOamPmCfgThrLossAvgFlrRaise   Integer32,
    tmnxOamPmCfgThrLossAvgFlrClear   Integer32
}

tmnxOamPmCfgTestType             OBJECT-TYPE
    SYNTAX      TmnxOamPmTestType
    MAX-ACCESS  not-accessible
    STATUS      current
    DESCRIPTION
        "The value of tmnxOamPmCfgTestType specifies the test type index of the
         row.

         The test types supporting loss thresholds are 'slm(2)',
         'twampLight(3)', and 'lmm(4)'."
    ::= { tmnxOamPmCfgThrLossFwBwEntry 1 }

tmnxOamPmCfgForwardBackward      OBJECT-TYPE
    SYNTAX      TmnxOamPmForwardBackward
    MAX-ACCESS  not-accessible
    STATUS      current
    DESCRIPTION
        "The value of tmnxOamPmCfgForwardBackward specifies the direction index
         of the row."
    ::= { tmnxOamPmCfgThrLossFwBwEntry 2 }

tmnxOamPmCfgThrLossAvgFlrRaise   OBJECT-TYPE
    SYNTAX      Integer32 (-1 | 1..100000)
    UNITS       "milli-percent"
    MAX-ACCESS  read-write
    STATUS      current
    DESCRIPTION
        "The value of tmnxOamPmCfgThrLossAvgFlrRaise specifies the raise
         threshold for the average Frame Loss Ratio (FLR).

         Depending on the specified indices, tmnxOamPmCfgThrLossAvgFlrRaise is
         the raise threshold for:
            tmnxOamPmStsLossSlmAvgFlrFwd,
            tmnxOamPmStsLossSlmAvgFlrBwd,
            tmnxOamPmStsLossLmmAvgFlrFwd,
            tmnxOamPmStsLossLmmAvgFlrBwd,
            tmnxOamPmStsLossTwlAvgFlrFwd, or
            tmnxOamPmStsLossTwlAvgFlrBwd.

         For example, suppose:
         1.  OAM-PM loss TCAs are enabled for the 'mi15minutes(2)' measurement
         interval of the OAM-PM session OAM_PM_Eth_session_1 (using
         tmnxOamPmCfgMeasIntvlLossTCAs and tmnxOamPmCfgMeasIntvlTCAs).
         2.  tmnxOamPmCfgThrLossAvgFlrRaise is set to 5000 (i.e. 5.000%) for the
         indices {OAM_PM_Eth_session_1, 'slm(2)', 'forward(1)'}.
         3.  At the end of a 15 minute interval belonging to
         OAM_PM_Eth_session_1's SLM test, the average FLR (i.e.
         tmnxOamPmStsLossSlmAvgFlrFwd) is 5000 (i.e. 5.000%) or more.
         4.  Generating an average FLR Raise TCA is allowed (e.g. the most
         recent average FLR TCA for the specified indices was a Clear).

         Then, SROS generates an average FLR Raise TCA (using
         tmnxOamPmThrRaise) at the end of the 15-minute interval, for the
         forward direction.

         Negative one specifies that average FLR thresholding is disabled for
         the specified indices (i.e. SROS will not generate a Raise TCA, or a
         Clear TCA).

         tmnxOamPmCfgThrLossAvgFlrRaise must be greater than
         tmnxOamPmCfgThrLossAvgFlrClear.  Exception: the combination
         tmnxOamPmCfgThrLossAvgFlrRaise=-1 and tmnxOamPmCfgThrLossAvgFlrClear=-1
         is supported.

         tmnxOamPmCfgThrLossAvgFlrRaise and tmnxOamPmCfgThrLossAvgFlrClear must
         be set in the same SNMP Set PDU."
    DEFVAL      { -1 }
    ::= { tmnxOamPmCfgThrLossFwBwEntry 3 }

tmnxOamPmCfgThrLossAvgFlrClear   OBJECT-TYPE
    SYNTAX      Integer32 (-1 | 0..99999)
    UNITS       "milli-percent"
    MAX-ACCESS  read-write
    STATUS      current
    DESCRIPTION
        "The value of tmnxOamPmCfgThrLossAvgFlrClear specifies the clear
         threshold for the average Frame Loss Ratio (FLR).

         Depending on the specified indices, tmnxOamPmCfgThrLossAvgFlrClear is
         the clear threshold for:
            tmnxOamPmStsLossSlmAvgFlrFwd,
            tmnxOamPmStsLossSlmAvgFlrBwd,
            tmnxOamPmStsLossLmmAvgFlrFwd,
            tmnxOamPmStsLossLmmAvgFlrBwd,
            tmnxOamPmStsLossTwlAvgFlrFwd, or
            tmnxOamPmStsLossTwlAvgFlrBwd.

         For example, suppose:
         1.  OAM-PM loss TCAs are enabled for the 'mi15minutes(2)' measurement
         interval of the OAM-PM session OAM_PM_Eth_session_1 (using
         tmnxOamPmCfgMeasIntvlLossTCAs and tmnxOamPmCfgMeasIntvlTCAs).
         2.  tmnxOamPmCfgThrLossAvgFlrClear is set to 4000 (i.e. 4.000%) for the
         indices {OAM_PM_Eth_session_1, 'slm(2)', 'forward(1)'}.
         3.  A previous 15 minute interval belonging to OAM_PM_Eth_session_1's
         SLM test generated an average FLR Raise TCA for the forward direction
         (see tmnxOamPmCfgThrLossAvgFlrRaise).  The TCA has not been cleared.
         4.  The just-closed 15-minute interval has an average forward FLR for
         the forward direction (i.e. tmnxOamPmStsLossSlmAvgFlrFwd) of 4000 (i.e.
         4.000%), or less.

         Then, SROS generates an average FLR Clear TCA (using
         tmnxOamPmThrClear) at the end of the 15-minute interval, for the
         forward direction.

         If tmnxOamPmCfgThrLossAvgFlrRaise > 0 AND
         tmnxOamPmCfgThrLossAvgFlrClear >= 0, average FLR Clear TCAs can be
         generated for the specified indices.  In this case, the maximum number
         of average FLR TCAs that will be generated for the specified indices
         across (for example) two 15 minute intervals is two: Raise and Clear.

         If tmnxOamPmCfgThrLossAvgFlrRaise > 0 AND
         tmnxOamPmCfgThrLossAvgFlrClear = -1, no average FLR Clear TCAs
         will be generated for the specified indices.  In this case, the maximum
         number of average FLR TCAs that will be generated for the specified
         indices across (for example) two 15 minute intervals is two: Raise and
         Raise.

         tmnxOamPmCfgThrLossAvgFlrRaise must be greater than
         tmnxOamPmCfgThrLossAvgFlrClear.  Exception: the combination
         tmnxOamPmCfgThrLossAvgFlrRaise=-1 and tmnxOamPmCfgThrLossAvgFlrClear=-1
         is supported.

         tmnxOamPmCfgThrLossAvgFlrClear and tmnxOamPmCfgThrLossAvgFlrClear must
         be set in the same SNMP Set PDU."
    DEFVAL      { -1 }
    ::= { tmnxOamPmCfgThrLossFwBwEntry 4 }

tmnxOamPmCfgThrLossFwBwAgTable   OBJECT-TYPE
    SYNTAX      SEQUENCE OF TmnxOamPmCfgThrLossFwBwAgEntry
    MAX-ACCESS  not-accessible
    STATUS      current
    DESCRIPTION
        "tmnxOamPmCfgThrLossFwBwAgTable contains configured thresholds for OAM
         Performance Monitoring loss TCAs.  The subset of the loss thresholds
         that are configurable in the forward, backward, and aggregate
         directions is configured using this table.  An aggregate loss
         threshold applies to the sum of a forward loss counter and a backward
         loss counter."
    REFERENCE
        "MEF-35, 'Service OAM Performance Monitoring Implementation Agreement',
         Metro Ethernet Forum, April 2012, Section 10.2 'Single-Ended Synthetic
         Loss Function for Frame Loss Ratio (FLR) and Availability'."
    ::= { tmnxOamPmCfgTableObjs 14 }

tmnxOamPmCfgThrLossFwBwAgEntry   OBJECT-TYPE
    SYNTAX      TmnxOamPmCfgThrLossFwBwAgEntry
    MAX-ACCESS  not-accessible
    STATUS      current
    DESCRIPTION
        "tmnxOamPmCfgThrLossFwBwAgEntry contains the configured thresholds for
         the forward, backward, or aggregate direction of one OAM-PM loss test.
         For example, a row may contain the configurable thresholds for the
         forward direction for the SLM test belonging to OAM-PM session
         OAM_PM_Eth_session_1.

         SROS creates/destroys three rows (forward, backward, and aggregate) in
         this table for each OAM-PM LMM, SLM or TWAMP-Light test
         created/destroyed.  A manager creates an LMM, SLM or TWAMP-Light test
         using:
            tmnxOamPmCfgLossLmmRowStatus,
            tmnxOamPmCfgLossSlmRowStatus, or
            tmnxOamPmCfgTwampLtRowStatus."
    INDEX       {
        tmnxOamPmCfgSessName,
        tmnxOamPmCfgTestType,
        tmnxOamPmCfgForwardBackwardAggr
    }
    ::= { tmnxOamPmCfgThrLossFwBwAgTable 1 }

TmnxOamPmCfgThrLossFwBwAgEntry   ::= SEQUENCE
{
    tmnxOamPmCfgForwardBackwardAggr  TmnxOamPmForwardBackwardAggr,
    tmnxOamPmCfgThrLossChliRaise     Integer32,
    tmnxOamPmCfgThrLossChliClear     Integer32,
    tmnxOamPmCfgThrLossHliRaise      Integer32,
    tmnxOamPmCfgThrLossHliClear      Integer32,
    tmnxOamPmCfgThrLossUnavlIndRaise Integer32,
    tmnxOamPmCfgThrLossUnavlIndClear Integer32,
    tmnxOamPmCfgThrLossUndtAvlRaise  Integer32,
    tmnxOamPmCfgThrLossUndtAvlClear  Integer32,
    tmnxOamPmCfgThrLossUndtUnavlRais Integer32,
    tmnxOamPmCfgThrLossUndtUnavlClr  Integer32
}

tmnxOamPmCfgForwardBackwardAggr  OBJECT-TYPE
    SYNTAX      TmnxOamPmForwardBackwardAggr
    MAX-ACCESS  not-accessible
    STATUS      current
    DESCRIPTION
        "The value of tmnxOamPmCfgForwardBackwardAggr specifies the direction
         index of the row."
    ::= { tmnxOamPmCfgThrLossFwBwAgEntry 1 }

tmnxOamPmCfgThrLossChliRaise     OBJECT-TYPE
    SYNTAX      Integer32 (-1 | 1..864000)
    MAX-ACCESS  read-write
    STATUS      current
    DESCRIPTION
        "The value of tmnxOamPmCfgThrLossChliRaise specifies the raise
         threshold for Consecutive High Loss Intervals (CHLIs).

         Depending on the specified indices, tmnxOamPmCfgThrLossChliRaise is the
         raise threshold for:
            tmnxOamPmStsLossLmmChliBwd,
            tmnxOamPmStsLossLmmChliFwd + tmnxOamPmStsLossLmmChliBwd,
            tmnxOamPmStsLossLmmChliFwd,
            tmnxOamPmStsLossSlmChliBwd,
            tmnxOamPmStsLossSlmChliFwd + tmnxOamPmStsLossSlmChliBwd,
            tmnxOamPmStsLossSlmChliFwd,
            tmnxOamPmStsLossTwlChliBwd,
            tmnxOamPmStsLossTwlChliFwd + tmnxOamPmStsLossTwlChliBwd, or
            tmnxOamPmStsLossTwlChliFwd.

         For example, suppose:
         1.  OAM-PM loss TCAs are enabled for the 'mi15minutes(2)' measurement
         interval of the OAM-PM session OAM_PM_Eth_session_1 (using
         tmnxOamPmCfgMeasIntvlLossTCAs and tmnxOamPmCfgMeasIntvlTCAs).
         2.  tmnxOamPmCfgThrLossChliRaise is set to 7 for the indices
         {OAM_PM_Eth_session_1, 'slm(2)', 'forward(1)'}.
         3.  A 15 minute interval belonging to OAM_PM_Eth_session_1's SLM test
         has its forward CHLI count (i.e. tmnxOamPmStsLossSlmChliFwd) increase
         to 7.
         4.  Generating a CHLI Raise TCA is allowed (e.g. the most recent CHLI
         TCA for the specified indices was a Clear).

         Then, SROS immediately generates a CHLI Raise TCA (using
         tmnxOamPmThrRaise) for the 15-minute interval, for the forward
         direction.

         Negative one specifies that CHLI thresholding is disabled for the
         specified indices (i.e. SROS will not generate a Raise TCA, or a Clear
         TCA).

         tmnxOamPmCfgThrLossChliRaise must be greater than
         tmnxOamPmCfgThrLossChliClear.  Exception: the combination
         tmnxOamPmCfgThrLossChliRaise=-1 and tmnxOamPmCfgThrLossChliClear=-1 is
         supported.

         tmnxOamPmCfgThrLossChliRaise and tmnxOamPmCfgThrLossChliClear must be
         set in the same SNMP Set PDU.

         The upper bound of this object is the maximum number of MEF-35
         'delta_t' time intervals (also known as 'Small Time Intervals') which
         can occur in a 24 hour measurement interval."
    REFERENCE
        "MEF-35, 'Service OAM Performance Monitoring Implementation Agreement',
         Metro Ethernet Forum, April 2012, Section 10.2 'Single-Ended Synthetic
         Loss Function for Frame Loss Ratio (FLR) and Availability'."
    DEFVAL      { -1 }
    ::= { tmnxOamPmCfgThrLossFwBwAgEntry 2 }

tmnxOamPmCfgThrLossChliClear     OBJECT-TYPE
    SYNTAX      Integer32 (-1 | 0..863999)
    MAX-ACCESS  read-write
    STATUS      current
    DESCRIPTION
        "The value of tmnxOamPmCfgThrLossChliClear specifies the clear
         threshold for Consecutive High Loss Intervals (CHLIs).

         tmnxOamPmCfgThrLossChliClear is the clear threshold for the list of
         counters specified in the tmnxOamPmCfgThrLossChliRaise DESCRIPTION
         clause.

         For example, suppose:
         1.  OAM-PM loss TCAs are enabled for the 'mi15minutes(2)' measurement
         interval of the OAM-PM session OAM_PM_Eth_session_1 (using
         tmnxOamPmCfgMeasIntvlLossTCAs and tmnxOamPmCfgMeasIntvlTCAs).
         2.  tmnxOamPmCfgThrLossChliClear is set to 5 for the indices
         {OAM_PM_Eth_session_1, 'slm(2)', 'forward(1)'}.
         3.  A previous 15 minute interval belonging to OAM_PM_Eth_session_1's
         SLM test generated a CHLI Raise TCA for the forward direction (see
         tmnxOamPmCfgThrLossChliRaise).  The TCA has not been cleared.
         4.  The just-closed 15-minute interval has an forward CHLI count for
         the forward direction (i.e. tmnxOamPmStsLossSlmChliFwd) of 5, or less.

         Then, SROS generates a CHLI Clear TCA (using tmnxOamPmThrClear) for
         the 15-minute interval, for the forward direction.

         If tmnxOamPmCfgThrLossChliRaise>0 AND tmnxOamPmCfgThrLossChliClear>=0,
         CHLI Clear TCAs can be generated for the specified indices.  In this
         case, the maximum number of CHLI TCAs that will be generated for the
         specified indices across (for example) two 15 minute intervals is two:
         Raise and Clear.

         If tmnxOamPmCfgThrLossChliRaise>0 AND tmnxOamPmCfgThrLossChliClear=-1,
         no CHLI Clear TCAs will be generated for the specified indices.  In
         this case, the maximum number of CHLI TCAs that will be generated for
         the specified indices across (for example) two 15 minute intervals is
         two: Raise and Raise.

         tmnxOamPmCfgThrLossChliRaise must be greater than
         tmnxOamPmCfgThrLossChliClear.  Exception: the combination
         tmnxOamPmCfgThrLossChliRaise=-1 and tmnxOamPmCfgThrLossChliClear=-1 is
         supported.

         tmnxOamPmCfgThrLossChliClear and tmnxOamPmCfgThrLossChliClear must be
         set in the same SNMP Set PDU."
    DEFVAL      { -1 }
    ::= { tmnxOamPmCfgThrLossFwBwAgEntry 3 }

tmnxOamPmCfgThrLossHliRaise      OBJECT-TYPE
    SYNTAX      Integer32 (-1 | 1..864000)
    MAX-ACCESS  read-write
    STATUS      current
    DESCRIPTION
        "The value of tmnxOamPmCfgThrLossHliRaise specifies the raise threshold
         for High Loss Intervals (HLIs).

         tmnxOamPmCfgThrLossHliRaise has the same operating principles as
         tmnxOamPmCfgThrLossChliRaise.

         Depending on the specified indices, tmnxOamPmCfgThrLossHliRaise is the
         raise threshold for:
            tmnxOamPmStsLossLmmHliBwd,
            tmnxOamPmStsLossLmmHliFwd + tmnxOamPmStsLossLmmHliBwd,
            tmnxOamPmStsLossLmmHliFwd,
            tmnxOamPmStsLossSlmHliBwd,
            tmnxOamPmStsLossSlmHliFwd + tmnxOamPmStsLossSlmHliBwd,
            tmnxOamPmStsLossSlmHliFwd,
            tmnxOamPmStsLossTwlHliBwd,
            tmnxOamPmStsLossTwlHliFwd + tmnxOamPmStsLossTwlHliBwd, or
            tmnxOamPmStsLossTwlHliFwd."
    DEFVAL      { -1 }
    ::= { tmnxOamPmCfgThrLossFwBwAgEntry 4 }

tmnxOamPmCfgThrLossHliClear      OBJECT-TYPE
    SYNTAX      Integer32 (-1 | 0..863999)
    MAX-ACCESS  read-write
    STATUS      current
    DESCRIPTION
        "The value of tmnxOamPmCfgThrLossHliClear specifies the clear threshold
         for High Loss Intervals (HLIs).

         tmnxOamPmCfgThrLossHliClear has the same operating principles as
         tmnxOamPmCfgThrLossChliClear.

         tmnxOamPmCfgThrLossHliClear is the clear threshold for the list of
         counters specified in the tmnxOamPmCfgThrLossHliRaise DESCRIPTION
         clause."
    DEFVAL      { -1 }
    ::= { tmnxOamPmCfgThrLossFwBwAgEntry 5 }

tmnxOamPmCfgThrLossUnavlIndRaise OBJECT-TYPE
    SYNTAX      Integer32 (-1 | 1..864000)
    MAX-ACCESS  read-write
    STATUS      current
    DESCRIPTION
        "The value of tmnxOamPmCfgThrLossUnavlIndRaise specifies the raise
         threshold for the number of availability indicators evaluated as
         Unavailable.

         tmnxOamPmCfgThrLossUnavlIndRaise has the same operating principles as
         tmnxOamPmCfgThrLossChliRaise.

         Depending on the specified indices, tmnxOamPmCfgThrLossUnavlIndRaise is
         the raise threshold for:
            tmnxOamPmStsLossLmmUnavlIndBwd,
            tmnxOamPmStsLossLmmUnavlIndFwd + tmnxOamPmStsLossLmmUnavlIndBwd,
            tmnxOamPmStsLossLmmUnavlIndFwd,
            tmnxOamPmStsLossSlmUnavlIndBwd,
            tmnxOamPmStsLossSlmUnavlIndFwd + tmnxOamPmStsLossSlmUnavlIndBwd,
            tmnxOamPmStsLossSlmUnavlIndFwd,
            tmnxOamPmStsLossTwlUnavlIndBwd,
            tmnxOamPmStsLossTwlUnavlIndFwd + tmnxOamPmStsLossTwlUnavlIndBwd, or
            tmnxOamPmStsLossTwlUnavlIndFwd."
    DEFVAL      { -1 }
    ::= { tmnxOamPmCfgThrLossFwBwAgEntry 6 }

tmnxOamPmCfgThrLossUnavlIndClear OBJECT-TYPE
    SYNTAX      Integer32 (-1 | 0..863999)
    MAX-ACCESS  read-write
    STATUS      current
    DESCRIPTION
        "The value of tmnxOamPmCfgThrLossUnavlIndClear specifies the clear
         threshold for the number of availability indicators evaluated as
         Unavailable.

         tmnxOamPmCfgThrLossUnavlIndClear has the same operating principles as
         tmnxOamPmCfgThrLossChliClear.

         tmnxOamPmCfgThrLossUnavlIndClear is the clear threshold for the list
         of counters specified in the tmnxOamPmCfgThrLossUnavlIndRaise
         DESCRIPTION clause."
    DEFVAL      { -1 }
    ::= { tmnxOamPmCfgThrLossFwBwAgEntry 7 }

tmnxOamPmCfgThrLossUndtAvlRaise  OBJECT-TYPE
    SYNTAX      Integer32 (-1 | 1..864000)
    MAX-ACCESS  read-write
    STATUS      current
    DESCRIPTION
        "The value of tmnxOamPmCfgThrLossUndtAvlRaise specifies the raise
         threshold for the number of availability indicators evaluated as
         Available based on extrapolation from the previous state.

         tmnxOamPmCfgThrLossUndtAvlRaise has the same operating principles as
         tmnxOamPmCfgThrLossChliRaise.

         Depending on the specified indices, tmnxOamPmCfgThrLossUndtAvlRaise is
         the raise threshold for:
            tmnxOamPmStsLossLmmUndtAvlBwd,
            tmnxOamPmStsLossLmmUndtAvlFwd + tmnxOamPmStsLossLmmUndtAvlBwd,
            tmnxOamPmStsLossLmmUndtAvlFwd,
            tmnxOamPmStsLossSlmUndtAvlBwd,
            tmnxOamPmStsLossSlmUndtAvlFwd + tmnxOamPmStsLossSlmUndtAvlBwd,
            tmnxOamPmStsLossSlmUndtAvlFwd,
            tmnxOamPmStsLossTwlUndtAvlBwd,
            tmnxOamPmStsLossTwlUndtAvlFwd + tmnxOamPmStsLossTwlUndtAvlBwd, or
            tmnxOamPmStsLossTwlUndtAvlFwd."
    DEFVAL      { -1 }
    ::= { tmnxOamPmCfgThrLossFwBwAgEntry 8 }

tmnxOamPmCfgThrLossUndtAvlClear  OBJECT-TYPE
    SYNTAX      Integer32 (-1 | 0..863999)
    MAX-ACCESS  read-write
    STATUS      current
    DESCRIPTION
        "The value of tmnxOamPmCfgThrLossUndtAvlClear specifies the clear
         threshold for the number of availability indicators evaluated as
         Available based on extrapolation from the previous state.

         tmnxOamPmCfgThrLossUndtAvlClear has the same operating principles as
         tmnxOamPmCfgThrLossChliClear.

         tmnxOamPmCfgThrLossUndtAvlClear is the clear threshold for the list of
         counters specified in the tmnxOamPmCfgThrLossUndtAvlRaise DESCRIPTION
         clause.  "
    DEFVAL      { -1 }
    ::= { tmnxOamPmCfgThrLossFwBwAgEntry 9 }

tmnxOamPmCfgThrLossUndtUnavlRais OBJECT-TYPE
    SYNTAX      Integer32 (-1 | 1..864000)
    MAX-ACCESS  read-write
    STATUS      current
    DESCRIPTION
        "The value of tmnxOamPmCfgThrLossUndtUnavlRais specifies the raise
         threshold for the number of availability indicators evaluated as
         Unavailable based on extrapolation from the previous state.

         tmnxOamPmCfgThrLossUndtUnavlRais has the same operating principles as
         tmnxOamPmCfgThrLossChliRaise.

         Depending on the specified indices, tmnxOamPmCfgThrLossUndtUnavlRais is
         the raise threshold for:
            tmnxOamPmStsLossLmmUndtUnavlBwd,
            tmnxOamPmStsLossLmmUndtUnavlFwd + tmnxOamPmStsLossLmmUndtUnavlBwd,
            tmnxOamPmStsLossLmmUndtUnavlFwd,
            tmnxOamPmStsLossSlmUndtUnavlBwd,
            tmnxOamPmStsLossSlmUndtUnavlFwd + tmnxOamPmStsLossSlmUndtUnavlBwd,
            tmnxOamPmStsLossSlmUndtUnavlFwd,
            tmnxOamPmStsLossTwlUndtUnavlBwd,
            tmnxOamPmStsLossTwlUndtUnavlFwd + tmnxOamPmStsLossTwlUndtUnavlBwd,
            or
            tmnxOamPmStsLossTwlUndtUnavlFwd."
    DEFVAL      { -1 }
    ::= { tmnxOamPmCfgThrLossFwBwAgEntry 10 }

tmnxOamPmCfgThrLossUndtUnavlClr  OBJECT-TYPE
    SYNTAX      Integer32 (-1 | 0..863999)
    MAX-ACCESS  read-write
    STATUS      current
    DESCRIPTION
        "The value of tmnxOamPmCfgThrLossUndtUnavlClr specifies the clear
         threshold for the number of availability indicators evaluated as
         Unavailable based on extrapolation from the previous state.

         tmnxOamPmCfgThrLossUndtUnavlClr has the same operating principles as
         tmnxOamPmCfgThrLossChliClear.

         tmnxOamPmCfgThrLossUndtUnavlClr is the clear threshold for the list of
         counters specified in the tmnxOamPmCfgThrLossUndtUnavlRais DESCRIPTION
         clause."
    DEFVAL      { -1 }
    ::= { tmnxOamPmCfgThrLossFwBwAgEntry 11 }

tmnxOamPmCfgThrDelayTable        OBJECT-TYPE
    SYNTAX      SEQUENCE OF TmnxOamPmCfgThrDelayEntry
    MAX-ACCESS  not-accessible
    STATUS      current
    DESCRIPTION
        "tmnxOamPmCfgThrDelayTable contains threshold configuration for OAM
         Performance Monitoring delay TCAs."
    REFERENCE
        "MEF-35, 'Service OAM Performance Monitoring Implementation Agreement',
         Metro Ethernet Forum, April 2012, Section 9.2.2 'Measurement Bins'"
    ::= { tmnxOamPmCfgTableObjs 15 }

tmnxOamPmCfgThrDelayEntry        OBJECT-TYPE
    SYNTAX      TmnxOamPmCfgThrDelayEntry
    MAX-ACCESS  not-accessible
    STATUS      current
    DESCRIPTION
        "tmnxOamPmCfgThrDelayEntry contains the threshold configuration for one
         OAM-PM bin group, bin type, and direction.

         For example, a row may contain the threshold configuration for bin
         group 255, bin type 'ifdv(3)', and direction 'twoWay(3)'.

         SROS creates/destroys nine rows (i.e. {'fd(1)', 'fdr(2)', 'ifdv(3)'} x
         {'forward(1)', 'backward(2)', 'twoWay(3)'}) when an OAM-PM bin group is
         created/destroyed.  A manager creates/destroys an OAM-PM bin group
         using tmnxOamPmCfgBinGroupRowStatus.

         The objects in this table cannot be changed from the default value
         when the index value tmnxOamPmCfgBinGroupId is 1."
    INDEX       {
        tmnxOamPmCfgBinGroupId,
        tmnxOamPmCfgBinType,
        tmnxOamPmCfgForwardBackward2Way
    }
    ::= { tmnxOamPmCfgThrDelayTable 1 }

TmnxOamPmCfgThrDelayEntry        ::= SEQUENCE
{
    tmnxOamPmCfgForwardBackward2Way  TmnxOamPmForwardBackwardTwoWay,
    tmnxOamPmCfgThrDelayLowestBin    Unsigned32,
    tmnxOamPmCfgThrDelayRaise        Integer32,
    tmnxOamPmCfgThrDelayClear        Integer32,
    tmnxOamPmCfgThrDelayExclBinFrTca TmnxOamPmCfgBinNumOrNone
}

tmnxOamPmCfgForwardBackward2Way  OBJECT-TYPE
    SYNTAX      TmnxOamPmForwardBackwardTwoWay
    MAX-ACCESS  not-accessible
    STATUS      current
    DESCRIPTION
        "The value of tmnxOamPmCfgForwardBackward2Way specifies the direction
         of the row to be configured or read."
    ::= { tmnxOamPmCfgThrDelayEntry 1 }

tmnxOamPmCfgThrDelayLowestBin    OBJECT-TYPE
    SYNTAX      Unsigned32 (0..9)
    MAX-ACCESS  read-write
    STATUS      current
    DESCRIPTION
        "The value of tmnxOamPmCfgThrDelayLowestBin specifies the lowest OAM-PM
         delay bin to be used when applying a configured Raise or Clear delay
         threshold.

         The usage is described in the tmnxOamPmCfgThrDelayRaise and
         tmnxOamPmCfgThrDelayClear DESCRIPTION clauses."
    DEFVAL      { 0 }
    ::= { tmnxOamPmCfgThrDelayEntry 2 }

tmnxOamPmCfgThrDelayRaise        OBJECT-TYPE
    SYNTAX      Integer32 (-1 | 1..864000)
    MAX-ACCESS  read-write
    STATUS      current
    DESCRIPTION
        "The value of tmnxOamPmCfgThrDelayRaise specifies the OAM-PM raise
         threshold for excessive delay.

         For example, suppose:
         1.  tmnxOamPmCfgThrDelayRaise=1000 and tmnxOamPmCfgThrDelayLowestBin=7
         for the index values 255, 'ifdv(3)', 'twoWay(3)'.
         2.  Bin group 255 has been configured with 10 Inter-Frame Delay
         Variation (IFDV) bins (numbered 0..9), using
         tmnxOamPmCfgBinGroupIfdvBinCount.
         3.  The OAM-PM session 'oamPmSession1' is configured to use bin group
         255 (using tmnxOamPmCfgSessBinGroupId).
         4.  OAM-PM delay TCAs are enabled for the measurement interval with
         indices 'oamPmSession1', 'mi15Minutes(2)' (using
         tmnxOamPmCfgMeasIntvlDelayTCAs and tmnxOamPmCfgMeasIntvlTCAs).
         5.  During a 15 minute interval belonging to a DMM test which belongs
         to 'oamPmSession1', the following inequality becomes true (where only
         the last two indices of the object are shown, and the last index is a
         bin number):
            tmnxOamPmStsDelayDmmBin2wyCount.ifdv(3).7 +
            tmnxOamPmStsDelayDmmBin2wyCount.ifdv(3).8 +
            tmnxOamPmStsDelayDmmBin2wyCount.ifdv(3).9 >= 1000

         Then, a delay Raise TCA (using tmnxOamPmThrRaise) will be generated
         immediately.

         The TCA suppression and configuration rules for
         tmnxOamPmCfgThrDelayRaise and tmnxOamPmCfgThrDelayClear are the same
         as the rules for tmnxOamPmCfgThrLossChliRaise and
         tmnxOamPmCfgThrLossChliClear.

         The upper bound of this object allows the threshold to be set to 10
         failures/second for the longest measurement interval (i.e. 24 hours)."
    DEFVAL      { -1 }
    ::= { tmnxOamPmCfgThrDelayEntry 3 }

tmnxOamPmCfgThrDelayClear        OBJECT-TYPE
    SYNTAX      Integer32 (-1 | 0..863999)
    MAX-ACCESS  read-write
    STATUS      current
    DESCRIPTION
        "The value of tmnxOamPmCfgThrDelayClear specifies the OAM-PM clear
         threshold for excessive delay.

         For example, suppose:
         1.  tmnxOamPmCfgThrDelayClear=900 and tmnxOamPmCfgThrDelayLowestBin=7
         for the index values 255, 'ifdv(3)', 'twoWay(3)'.
         2.  Bin group 255 has been configured with 10 Inter-Frame Delay
         Variation (IFDV) bins (numbered 0..9), using
         tmnxOamPmCfgBinGroupIfdvBinCount.
         3.  The OAM-PM session 'oamPmSession1' is configured to use bin group
         255 (using tmnxOamPmCfgSessBinGroupId).
         4.  OAM-PM delay TCAs are enabled for the measurement interval with
         indices 'oamPmSession1', 'mi15Minutes(2)' (using
         tmnxOamPmCfgMeasIntvlDelayTCAs and tmnxOamPmCfgMeasIntvlTCAs).
         5.  At the end of a 15 minute interval belonging to a DMM test which
         belongs to 'oamPmSession1', the following inequality is true (where
         only the last two indices of the object are shown, and the last index
         is a bin number):
            tmnxOamPmStsDelayDmmBin2wyCount.ifdv(3).7 +
            tmnxOamPmStsDelayDmmBin2wyCount.ifdv(3).8 +
            tmnxOamPmStsDelayDmmBin2wyCount.ifdv(3).9 <= 900
         6. Generating a delay Clear TCA is allowed (i.e. the most recent delay
            TCA for the specified indices was a Raise).

         Then, a delay Clear TCA (using tmnxOamPmThrClear) will be generated.

         The TCA suppression and configuration rules for
         tmnxOamPmCfgThrDelayRaise and tmnxOamPmCfgThrDelayClear are the same
         as the rules for tmnxOamPmCfgThrLossChliRaise and
         tmnxOamPmCfgThrLossChliClear."
    DEFVAL      { -1 }
    ::= { tmnxOamPmCfgThrDelayEntry 4 }

tmnxOamPmCfgThrDelayExclBinFrTca OBJECT-TYPE
    SYNTAX      TmnxOamPmCfgBinNumOrNone
    MAX-ACCESS  read-write
    STATUS      current
    DESCRIPTION
        "The value of tmnxOamPmCfgThrDelayExclBinFrTca specifies the bin number
         of the lowest delay bin to be excluded from the OAM-PM TCA
         calculations for the specified bin group, bin type, and direction.

         Configuring tmnxOamPmCfgThrDelayExclBinFrTca allows outlier high delay
         frames to be ignored when deciding to raise or clear a delay TCA.

         For example, suppose the following values are configured for bin group
         255.

         Object                                                 Value
         ----------------------------------------------------   -----
         tmnxOamPmCfgBinGroupFdBinCount.255                        10
         tmnxOamPmCfgThrDelayLowestBin.255.fd(1).forward(1)         6
         tmnxOamPmCfgThrDelayExclBinFrTca.255.fd(1).forward(1)      8

         Then, the decision to raise or clear a Frame Delay (FD) TCA for the
         forward direction will be made based on the packet counts in bins 6
         and 7 (while ignoring the packet counts in bins 8 and 9).

         Configuring tmnxOamPmCfgThrDelayExclBinFrTca to the value -1 specifies
         that no bins are to be excluded.

         Configuring tmnxOamPmCfgThrDelayExclBinFrTca does not affect the value
         of delay bin packet counters (e.g. tmnxOamPmStsDelayDmmBinFwdCount).

         An attempt to change tmnxOamPmCfgThrDelayExclBinFrTca to a non-default
         value will be rejected if the specified bin does not exist.  Bins are
         created using:
            tmnxOamPmCfgBinGroupFdBinCount,
            tmnxOamPmCfgBinGroupFdrBinCount,
            tmnxOamPmCfgBinGroupIfdvBinCount, and
            tmnxOamPmCfgBinGroupRowStatus.

         An attempt to change tmnxOamPmCfgThrDelayExclBinFrTca to a non-default
         value will be rejected if tmnxOamPmCfgThrDelayExclBinFrTca is less
         than or equal to tmnxOamPmCfgThrDelayLowestBin.

         An attempt to change tmnxOamPmCfgThrDelayExclBinFrTca will be rejected
         if the specified bin group (i.e. tmnxOamPmCfgBinGroupId) is 1.

         tmnxOamPmCfgThrDelayExclBinFrTca can be changed regardless of the
         specified bin group's administrative status (i.e.
         tmnxOamPmCfgBinGroupAdminStatus)."
    DEFVAL      { -1 }
    ::= { tmnxOamPmCfgThrDelayEntry 5 }

tmnxOamPmCfgBinGrpTypeDirTable   OBJECT-TYPE
    SYNTAX      SEQUENCE OF TmnxOamPmCfgBinGrpTypeDirEntry
    MAX-ACCESS  not-accessible
    STATUS      current
    DESCRIPTION
        "tmnxOamPmCfgBinGrpTypeDirTable contains configuration information for
         the delay bins to be excluded from OAM Performance Monitoring average
         delay calculations."
    REFERENCE
        "MEF-35, 'Service OAM Performance Monitoring Implementation Agreement',
         Metro Ethernet Forum, April 2012, Section 9.2.2 'Measurement Bins'"
    ::= { tmnxOamPmCfgTableObjs 16 }

tmnxOamPmCfgBinGrpTypeDirEntry   OBJECT-TYPE
    SYNTAX      TmnxOamPmCfgBinGrpTypeDirEntry
    MAX-ACCESS  not-accessible
    STATUS      current
    DESCRIPTION
        "tmnxOamPmCfgBinGrpTypeDirEntry contains the delay bins to be excluded
         from OAM-PM average delay calculations for one OAM-PM bin group, bin
         type, and direction."
    AUGMENTS    { tmnxOamPmCfgThrDelayEntry }
    ::= { tmnxOamPmCfgBinGrpTypeDirTable 1 }

TmnxOamPmCfgBinGrpTypeDirEntry   ::= SEQUENCE
{ tmnxOamPmCfgBgTyDirExclBinsFrAvg TmxnOamPmBinNums }

tmnxOamPmCfgBgTyDirExclBinsFrAvg OBJECT-TYPE
    SYNTAX      TmxnOamPmBinNums
    MAX-ACCESS  read-write
    STATUS      current
    DESCRIPTION
        "The value of tmnxOamPmCfgBgTyDirExclBinsFrAvg specifies the set of
         delay bins to be excluded from OAM-PM average delay calculations for
         the specified bin group, bin type, and direction.

         Configuring a set of delay bins using tmnxOamPmCfgBgTyDirExclBinsFrAvg
         allows outlier delay values to be excluded from average delay
         calculations.

         For example, suppose tmnxOamPmCfgBgTyDirExclBinsFrAvg has the value
         { bin0, bin9 } for bin group 255, bin type 'ifdv(3)', and the forward
         direction.  Suppose the configured lower bounds for {bin group 255, bin
         type 'ifdv(3)'} are as follows.

            Bin Number    Lower Bound (microseconds)
            ----------    --------------------------
            0                                      0  (not configurable)
            1                                      1
            2                                   5000
            3                                  10000
            4                                  15000
            5                                  20000
            6                                  25000
            7                                  30000
            8                                  35000
            9                                  40000

         Then, the average forward IFDV delay calculations for tests using bin
         group 255 will ignore any delay measurement that is less than 1
         microsecond, or greater than or equal to 40000 microseconds.

         The following objects present the result of an average delay
         calculation:
            tmnxOamPmStsDelayDmmFwdAvg,
            tmnxOamPmStsDelayDmmBwdAvg,
            tmnxOamPmStsDelayDmm2wyAvg,
            tmnxOamPmStsDelayTwlFwdAvg,
            tmnxOamPmStsDelayTwlBwdAvg, and
            tmnxOamPmStsDelayTwl2wyAvg.

         Configuring tmnxOamPmCfgBgTyDirExclBinsFrAvg does not affect minimum
         delay or maximum delay calculations.

         An attempt to change tmnxOamPmCfgBgTyDirExclBinsFrAvg will be rejected
         if the specified bin group (i.e. tmnxOamPmCfgBinGroupId) is 1.

         An attempt to change tmnxOamPmCfgBgTyDirExclBinsFrAvg will be rejected
         if the specified bin group's administrative status (i.e.
         tmnxOamPmCfgBinGroupAdminStatus) is enabled."
    DEFVAL      { {} }
    ::= { tmnxOamPmCfgBinGrpTypeDirEntry 1 }

tmnxOamPmCfgSessMplsTable        OBJECT-TYPE
    SYNTAX      SEQUENCE OF TmnxOamPmCfgSessMplsEntry
    MAX-ACCESS  not-accessible
    STATUS      current
    DESCRIPTION
        "tmnxOamPmCfgSessMplsTable contains the MPLS configuration for the MPLS
         tests belonging to OAM Performance Monitoring sessions."
    REFERENCE
        "RFC 6374, 'Packet Loss and Delay Measurement for MPLS Networks',
         September 2011."
    ::= { tmnxOamPmCfgTableObjs 17 }

tmnxOamPmCfgSessMplsEntry        OBJECT-TYPE
    SYNTAX      TmnxOamPmCfgSessMplsEntry
    MAX-ACCESS  not-accessible
    STATUS      current
    DESCRIPTION
        "tmnxOamPmCfgSessMplsEntry contains the MPLS configuration for the MPLS
         tests belonging to one OAM Performance Monitoring session.

         A row is created when a tmnxOamPmCfgSessTable row is created with
         tmnxOamPmCfgSessTestFamily = 'mpls(3)'.

         A row is destroyed when a tmnxOamPmCfgSessTable row with
         tmnxOamPmCfgSessTestFamily = 'mpls(3)' is destroyed.

         An attempt to change a value in a row for a particular session will be
         rejected if an administratively enabled test (e.g. an MPLS Delay test)
         exists for the session."
    INDEX       { tmnxOamPmCfgSessName }
    ::= { tmnxOamPmCfgSessMplsTable 1 }

TmnxOamPmCfgSessMplsEntry        ::= SEQUENCE
{
    tmnxOamPmCfgSessMplsForwardClass TFCName,
    tmnxOamPmCfgSessMplsProfile      TProfile,
    tmnxOamPmCfgSessMplsTtl          Unsigned32,
    tmnxOamPmCfgSessMplsDscpName     TDSCPName,
    tmnxOamPmCfgSessMplsPadPattern   Integer32,
    tmnxOamPmCfgSessMplsLspType      TmnxOamPmMplsLspType
}

tmnxOamPmCfgSessMplsForwardClass OBJECT-TYPE
    SYNTAX      TFCName
    MAX-ACCESS  read-write
    STATUS      current
    DESCRIPTION
        "The value of tmnxOamPmCfgSessMplsForwardClass specifies the forwarding
         class name to be used when launching an MPLS Delay Measurement (DM)
         query for each test belonging to the specified session.  The forwarding
         class name must be present in the index column of
         TIMETRA-QOS-MIB::tFCNameTable."
    DEFVAL      { "be" }
    ::= { tmnxOamPmCfgSessMplsEntry 1 }

tmnxOamPmCfgSessMplsProfile      OBJECT-TYPE
    SYNTAX      TProfile
    MAX-ACCESS  read-write
    STATUS      current
    DESCRIPTION
        "The value of tmnxOamPmCfgSessMplsProfile specifies the Quality of
         Service profile to be used when launching an MPLS Delay Measurement
         (DM) query for each test belonging to the specified session."
    DEFVAL      { out }
    ::= { tmnxOamPmCfgSessMplsEntry 2 }

tmnxOamPmCfgSessMplsTtl          OBJECT-TYPE
    SYNTAX      Unsigned32 (1..255)
    MAX-ACCESS  read-write
    STATUS      current
    DESCRIPTION
        "The value of tmnxOamPmCfgSessMplsTtl specifies the value to be copied
         into the Time To Live field of the MPLS header when launching an MPLS
         Delay Measurement (DM) query for each test belonging to the specified
         session."
    DEFVAL      { 255 }
    ::= { tmnxOamPmCfgSessMplsEntry 3 }

tmnxOamPmCfgSessMplsDscpName     OBJECT-TYPE
    SYNTAX      TDSCPName
    MAX-ACCESS  read-write
    STATUS      current
    DESCRIPTION
        "The value of tmnxOamPmCfgSessMplsDscpName specifies the Differentiated
         Services Code Point (DSCP) to be copied into the Differentiated
         Services (DS) field of the MPLS DM PDU of each query launched for each
         test belonging to the specified session.

         The specified DSCP name must match a TIMETRA-QOS-MIB::tDSCPName
         defined in TIMETRA-QOS-MIB::tDSCPNameTable.

         The mapping between the specified DSCP name (e.g. 'af43') and the
         numeric value needed in the MPLS DM PDU (e.g. 38) is provided by
         TIMETRA-QOS-MIB::tDSCPNameDscpValue."
    REFERENCE
        "RFC 3260, 'New Terminology and Clarifications for Diffserv', April
         2002, Section 4, 'Definition of the DS Field'.
         RFC 6374, 'Packet Loss and Delay Measurement for MPLS Networks',
         September 2011, Section 3.2, 'Delay Measurement Message Format'."
    DEFVAL      { "be" }
    ::= { tmnxOamPmCfgSessMplsEntry 4 }

tmnxOamPmCfgSessMplsPadPattern   OBJECT-TYPE
    SYNTAX      Integer32 (-1 | 0..65535)
    MAX-ACCESS  read-write
    STATUS      current
    DESCRIPTION
        "The value of tmnxOamPmCfgSessMplsPadPattern specifies a two octet
         pattern to be repeated to fill the Value field of the Padding TLV(s)
         of the MPLS DM PDU of each query launched for each test belonging to
         the specified session.  For example, if 65534 is specified, the Value
         field is filled with the octet values FF, FE, FF, FE, ...
         (hexadecimal).

         When the value of this object is -1, the Value field will be filled
         with the octet values 00, 01, 02, 03, ... (hexadecimal)."
    REFERENCE
        "RFC 6374, 'Packet Loss and Delay Measurement for MPLS Networks',
         September 2011, Section 3.5.1, 'Padding'."
    DEFVAL      { 0 }
    ::= { tmnxOamPmCfgSessMplsEntry 5 }

tmnxOamPmCfgSessMplsLspType      OBJECT-TYPE
    SYNTAX      TmnxOamPmMplsLspType
    MAX-ACCESS  read-write
    STATUS      current
    DESCRIPTION
        "The value of tmnxOamPmCfgSessMplsLspType specifies the type of the LSP
         to be tested by OAM-PM.

         tmnxOamPmCfgSessMplsLspType can be changed:
         1.  From 'none(1)' to another value, or
         2.  From another value to 'none(1)'.
         Other changes are rejected."
    DEFVAL      { none }
    ::= { tmnxOamPmCfgSessMplsEntry 6 }

tmnxOamPmCfgSessMplsRsvpTable    OBJECT-TYPE
    SYNTAX      SEQUENCE OF TmnxOamPmCfgSessMplsRsvpEntry
    MAX-ACCESS  not-accessible
    STATUS      current
    DESCRIPTION
        "tmnxOamPmCfgSessMplsRsvpTable contains configuration information for
         manually created RSVP LSPs to be tested by OAM-PM."
    REFERENCE
        "RFC 6374, 'Packet Loss and Delay Measurement for MPLS Networks',
         September 2011."
    ::= { tmnxOamPmCfgTableObjs 18 }

tmnxOamPmCfgSessMplsRsvpEntry    OBJECT-TYPE
    SYNTAX      TmnxOamPmCfgSessMplsRsvpEntry
    MAX-ACCESS  not-accessible
    STATUS      current
    DESCRIPTION
        "tmnxOamPmCfgSessMplsRsvpEntry contains configuration information for
         one manually created RSVP LSP to be tested by OAM-PM.

         A row is created when tmnxOamPmCfgSessMplsLspType is set to 'rsvp(3)'.

         A row is destroyed when tmnxOamPmCfgSessMplsLspType is set to
         'none(1)', or the session is destroyed."
    INDEX       { tmnxOamPmCfgSessName }
    ::= { tmnxOamPmCfgSessMplsRsvpTable 1 }

TmnxOamPmCfgSessMplsRsvpEntry    ::= SEQUENCE
{
    tmnxOamPmCfgSessMplsRsvpLspName  TLNamedItemOrEmpty,
    tmnxOamPmCfgSessMplsRsvpRetAddrT InetAddressType,
    tmnxOamPmCfgSessMplsRsvpRetAddr  InetAddress
}

tmnxOamPmCfgSessMplsRsvpLspName  OBJECT-TYPE
    SYNTAX      TLNamedItemOrEmpty
    MAX-ACCESS  read-write
    STATUS      current
    DESCRIPTION
        "The value of tmnxOamPmCfgSessMplsRsvpLspName specifies the name of the
         RSVP LSP to be tested by OAM-PM.

         For a successful test, the LSP name must match a
         TIMETRA-MPLS-MIB::vRtrMplsLspName, with
         TIMETRA-MPLS-MIB::vRtrMplsLspType != 'mplsTp(7)'."
    DEFVAL      { "" }
    ::= { tmnxOamPmCfgSessMplsRsvpEntry 1 }

tmnxOamPmCfgSessMplsRsvpRetAddrT OBJECT-TYPE
    SYNTAX      InetAddressType
    MAX-ACCESS  read-write
    STATUS      current
    DESCRIPTION
        "The value of tmnxOamPmCfgSessMplsRsvpRetAddrT specifies the address
         type of tmnxOamPmCfgSessMplsRsvpRetAddr."
    DEFVAL      { unknown }
    ::= { tmnxOamPmCfgSessMplsRsvpEntry 2 }

tmnxOamPmCfgSessMplsRsvpRetAddr  OBJECT-TYPE
    SYNTAX      InetAddress (SIZE (0|4|16))
    MAX-ACCESS  read-write
    STATUS      current
    DESCRIPTION
        "The value of tmnxOamPmCfgSessMplsRsvpRetAddr specifies the destination
         IP address to be used by an OAM-PM MPLS test when sending a UDP
         response from the tail end of a uni-directional LSP back to this
         system.

         tmnxOamPmCfgSessMplsRsvpRetAddrT and tmnxOamPmCfgSessMplsRsvpRetAddr
         must be set in one SNMP PDU."
    DEFVAL      { ''H }
    ::= { tmnxOamPmCfgSessMplsRsvpEntry 3 }

tmnxOamPmCfgSessMplsRsvpAutTable OBJECT-TYPE
    SYNTAX      SEQUENCE OF TmnxOamPmCfgSessMplsRsvpAutEntry
    MAX-ACCESS  not-accessible
    STATUS      current
    DESCRIPTION
        "tmnxOamPmCfgSessMplsRsvpAutTable contains configuration information
         for automatically created RSVP LSPs to be tested by OAM-PM."
    REFERENCE
        "RFC 6374, 'Packet Loss and Delay Measurement for MPLS Networks',
         September 2011."
    ::= { tmnxOamPmCfgTableObjs 19 }

tmnxOamPmCfgSessMplsRsvpAutEntry OBJECT-TYPE
    SYNTAX      TmnxOamPmCfgSessMplsRsvpAutEntry
    MAX-ACCESS  not-accessible
    STATUS      current
    DESCRIPTION
        "tmnxOamPmCfgSessMplsRsvpAutEntry contains configuration information
         for one automatically created RSVP LSP to be tested by OAM-PM.

         A row is created when tmnxOamPmCfgSessMplsLspType is set to
         'rsvpAuto(4)'.

         A row is destroyed when tmnxOamPmCfgSessMplsLspType is set to
         'none(1)', or the session is destroyed."
    INDEX       { tmnxOamPmCfgSessName }
    ::= { tmnxOamPmCfgSessMplsRsvpAutTable 1 }

TmnxOamPmCfgSessMplsRsvpAutEntry ::= SEQUENCE
{
    tmnxOamPmCfgSessMplsRaTemplName  TNamedItemOrEmpty,
    tmnxOamPmCfgSessMplsRaFrAddrType InetAddressType,
    tmnxOamPmCfgSessMplsRaFrAddress  InetAddress,
    tmnxOamPmCfgSessMplsRaToAddrType InetAddressType,
    tmnxOamPmCfgSessMplsRaToAddress  InetAddress,
    tmnxOamPmCfgSessMplsRaRetAddrTyp InetAddressType,
    tmnxOamPmCfgSessMplsRaRetAddress InetAddress
}

tmnxOamPmCfgSessMplsRaTemplName  OBJECT-TYPE
    SYNTAX      TNamedItemOrEmpty
    MAX-ACCESS  read-write
    STATUS      current
    DESCRIPTION
        "The value of tmnxOamPmCfgSessMplsRaTemplName specifies the name of the
         LSP Template used to identify the LSP to be tested by OAM-PM.

         The LSP to be tested is fully identified by
             tmnxOamPmCfgSessMplsRaTemplName
             tmnxOamPmCfgSessMplsRaFrAddrType
             tmnxOamPmCfgSessMplsRaFrAddress
             tmnxOamPmCfgSessMplsRaToAddrType
             tmnxOamPmCfgSessMplsRaToAddress.

         For a successful test, the template name must match a
         TIMETRA-MPLS-MIB::vRtrMplsLspTemplateName."
    DEFVAL      { "" }
    ::= { tmnxOamPmCfgSessMplsRsvpAutEntry 1 }

tmnxOamPmCfgSessMplsRaFrAddrType OBJECT-TYPE
    SYNTAX      InetAddressType
    MAX-ACCESS  read-write
    STATUS      current
    DESCRIPTION
        "The value of tmnxOamPmCfgSessMplsRaFrAddrType specifies the address
         type of tmnxOamPmCfgSessMplsRaFrAddress."
    DEFVAL      { unknown }
    ::= { tmnxOamPmCfgSessMplsRsvpAutEntry 2 }

tmnxOamPmCfgSessMplsRaFrAddress  OBJECT-TYPE
    SYNTAX      InetAddress (SIZE (0|4))
    MAX-ACCESS  read-write
    STATUS      current
    DESCRIPTION
        "The value of tmnxOamPmCfgSessMplsRaFrAddress specifies the IP address
         of the ingress router used to identify the LSP to be tested by OAM-PM.

         The LSP to be tested is fully identified by
             tmnxOamPmCfgSessMplsRaTemplName
             tmnxOamPmCfgSessMplsRaFrAddrType
             tmnxOamPmCfgSessMplsRaFrAddress
             tmnxOamPmCfgSessMplsRaToAddrType
             tmnxOamPmCfgSessMplsRaToAddress.

         tmnxOamPmCfgSessMplsRaFrAddrType and tmnxOamPmCfgSessMplsRaFrAddress
         must be set in one SNMP PDU."
    DEFVAL      { ''H }
    ::= { tmnxOamPmCfgSessMplsRsvpAutEntry 3 }

tmnxOamPmCfgSessMplsRaToAddrType OBJECT-TYPE
    SYNTAX      InetAddressType
    MAX-ACCESS  read-write
    STATUS      current
    DESCRIPTION
        "The value of tmnxOamPmCfgSessMplsRaToAddrType specifies the address
         type of tmnxOamPmCfgSessMplsRaToAddress."
    DEFVAL      { unknown }
    ::= { tmnxOamPmCfgSessMplsRsvpAutEntry 4 }

tmnxOamPmCfgSessMplsRaToAddress  OBJECT-TYPE
    SYNTAX      InetAddress (SIZE (0|4))
    MAX-ACCESS  read-write
    STATUS      current
    DESCRIPTION
        "The value of tmnxOamPmCfgSessMplsRaToAddress specifies the IP address
         of the egress router used to identify the LSP to be tested by OAM-PM.

         The LSP to be tested is fully identified by
             tmnxOamPmCfgSessMplsRaTemplName
             tmnxOamPmCfgSessMplsRaFrAddrType
             tmnxOamPmCfgSessMplsRaFrAddress
             tmnxOamPmCfgSessMplsRaToAddrType
             tmnxOamPmCfgSessMplsRaToAddress.

         tmnxOamPmCfgSessMplsRaToAddrType and tmnxOamPmCfgSessMplsRaToAddress
         must be set in one SNMP PDU."
    DEFVAL      { ''H }
    ::= { tmnxOamPmCfgSessMplsRsvpAutEntry 5 }

tmnxOamPmCfgSessMplsRaRetAddrTyp OBJECT-TYPE
    SYNTAX      InetAddressType
    MAX-ACCESS  read-write
    STATUS      current
    DESCRIPTION
        "The value of tmnxOamPmCfgSessMplsRaRetAddrTyp specifies the address
         type of tmnxOamPmCfgSessMplsRaRetAddress."
    DEFVAL      { unknown }
    ::= { tmnxOamPmCfgSessMplsRsvpAutEntry 6 }

tmnxOamPmCfgSessMplsRaRetAddress OBJECT-TYPE
    SYNTAX      InetAddress (SIZE (0|4|16))
    MAX-ACCESS  read-write
    STATUS      current
    DESCRIPTION
        "The value of tmnxOamPmCfgSessMplsRaRetAddress specifies the
         destination IP address to be used by an OAM-PM MPLS test when sending
         a UDP response from the tail end of a uni-directional LSP back to this
         system.

         tmnxOamPmCfgSessMplsRaRetAddrTyp and tmnxOamPmCfgSessMplsRaRetAddress
         must be set in one SNMP PDU."
    DEFVAL      { ''H }
    ::= { tmnxOamPmCfgSessMplsRsvpAutEntry 7 }

tmnxOamPmCfgSessMplsTpTable      OBJECT-TYPE
    SYNTAX      SEQUENCE OF TmnxOamPmCfgSessMplsTpEntry
    MAX-ACCESS  not-accessible
    STATUS      current
    DESCRIPTION
        "tmnxOamPmCfgSessMplsTpTable contains configuration information for
         MPLS Transport Profile (MPLS-TP) LSPs to be tested by OAM-PM."
    REFERENCE
        "RFC 6374, 'Packet Loss and Delay Measurement for MPLS Networks',
         September 2011."
    ::= { tmnxOamPmCfgTableObjs 20 }

tmnxOamPmCfgSessMplsTpEntry      OBJECT-TYPE
    SYNTAX      TmnxOamPmCfgSessMplsTpEntry
    MAX-ACCESS  not-accessible
    STATUS      current
    DESCRIPTION
        "tmnxOamPmCfgSessMplsTpEntry contains configuration information for one
         MPLS Transport Profile (MPLS-TP) LSP to be tested by OAM-PM.

         A row is created when tmnxOamPmCfgSessMplsLspType is set to
         'mplsTpStatic(2)'.

         A row is destroyed when tmnxOamPmCfgSessMplsLspType is set to
         'none(1)', or the session is destroyed."
    INDEX       { tmnxOamPmCfgSessName }
    ::= { tmnxOamPmCfgSessMplsTpTable 1 }

TmnxOamPmCfgSessMplsTpEntry      ::= SEQUENCE
{ tmnxOamPmCfgSessMplsTpLspName    TLNamedItemOrEmpty }

tmnxOamPmCfgSessMplsTpLspName    OBJECT-TYPE
    SYNTAX      TLNamedItemOrEmpty
    MAX-ACCESS  read-write
    STATUS      current
    DESCRIPTION
        "The value of tmnxOamPmCfgSessMplsTpLspName specifies the name of the
         MPLS-TP LSP to be tested by OAM-PM.

         For a successful test, the LSP name must match a
         TIMETRA-MPLS-MIB::vRtrMplsLspName, with
         TIMETRA-MPLS-MIB::vRtrMplsLspType = 'mplsTp(7)'."
    DEFVAL      { "" }
    ::= { tmnxOamPmCfgSessMplsTpEntry 1 }

tmnxOamPmCfgDelayMplsTable       OBJECT-TYPE
    SYNTAX      SEQUENCE OF TmnxOamPmCfgDelayMplsEntry
    MAX-ACCESS  not-accessible
    STATUS      current
    DESCRIPTION
        "tmnxOamPmCfgDelayMplsTable contains the configuration information for
         OAM-PM MPLS Delay Measurement (DM) tests."
    REFERENCE
        "RFC 6374, 'Packet Loss and Delay Measurement for MPLS Networks',
         September 2011."
    ::= { tmnxOamPmCfgTableObjs 21 }

tmnxOamPmCfgDelayMplsEntry       OBJECT-TYPE
    SYNTAX      TmnxOamPmCfgDelayMplsEntry
    MAX-ACCESS  not-accessible
    STATUS      current
    DESCRIPTION
        "tmnxOamPmCfgDelayMplsEntry contains the configuration information for
         one OAM-PM MPLS DM test.

         Rows are created or destroyed by SNMP Set operations on
         tmnxOamPmCfgDelayMplsRowStatus.

         An attempt to change any value in a row (except
         tmnxOamPmCfgDelayMplsAdminStatus and tmnxOamPmCfgDelayMplsOnDmdStatus)
         will be rejected if tmnxOamPmCfgDelayMplsAdminStatus is 'enabled(1)'."
    INDEX       { tmnxOamPmCfgSessName }
    ::= { tmnxOamPmCfgDelayMplsTable 1 }

TmnxOamPmCfgDelayMplsEntry       ::= SEQUENCE
{
    tmnxOamPmCfgDelayMplsRowStatus   RowStatus,
    tmnxOamPmCfgDelayMplsAdminStatus TmnxEnabledDisabled,
    tmnxOamPmCfgDelayMplsOnDmdStatus TmnxEnabledDisabledOrNA,
    tmnxOamPmCfgDelayMplsTestId      Unsigned32,
    tmnxOamPmCfgDelayMplsInterval    Unsigned32,
    tmnxOamPmCfgDelayMplsPadTlvSize  Unsigned32,
    tmnxOamPmCfgDelayMplsReflectPad  TruthValue,
    tmnxOamPmCfgDelayMplsTstDuration Unsigned32,
    tmnxOamPmCfgDelayMplsRunTimeLeft Unsigned32,
    tmnxOamPmCfgDelayMplsStrTmplName TLNamedItemOrEmpty
}

tmnxOamPmCfgDelayMplsRowStatus   OBJECT-TYPE
    SYNTAX      RowStatus
    MAX-ACCESS  read-create
    STATUS      current
    DESCRIPTION
        "The value of tmnxOamPmCfgDelayMplsRowStatus specifies the status of
         the configuration row for the specified session's MPLS DM test.

         An attempt to create a row for a session with
         tmnxOamPmCfgSessTestFamily other than 'mpls(3)' will be rejected."
    ::= { tmnxOamPmCfgDelayMplsEntry 1 }

tmnxOamPmCfgDelayMplsAdminStatus OBJECT-TYPE
    SYNTAX      TmnxEnabledDisabled
    MAX-ACCESS  read-create
    STATUS      current
    DESCRIPTION
        "The value of tmnxOamPmCfgDelayMplsAdminStatus specifies whether or not
         the specified session's MPLS DM test is administratively enabled.

         If the session type (tmnxOamPmCfgSessType) is 'proactive(1)', setting
         tmnxOamPmCfgDelayMplsAdminStatus to 'enabled(1)'/'disabled(2)'
         starts/stops the test.

         If the session type is 'onDemand(2)', see the DESCRIPTION clause for
         tmnxOamPmCfgDelayMplsOnDmdStatus for information on starting/stopping
         the test.

         An attempt to set this object to 'enabled(1)' will be rejected if the
         tmnxOamPmCfgSessMplsTable row for the specified session has incomplete
         configuration for the test (e.g. if tmnxOamPmCfgSessMplsLspType is
         'none(1)')."
    DEFVAL      { disabled }
    ::= { tmnxOamPmCfgDelayMplsEntry 2 }

tmnxOamPmCfgDelayMplsOnDmdStatus OBJECT-TYPE
    SYNTAX      TmnxEnabledDisabledOrNA
    MAX-ACCESS  read-create
    STATUS      current
    DESCRIPTION
        "The value of tmnxOamPmCfgDelayMplsOnDmdStatus specifies the status of
         the on-demand MPLS DM test for the specified session.

         Values:
            'enabled(1)'
                Set by an SNMP manager to start an on-demand MPLS DM test.  The
                test will start if tmnxOamPmCfgDelayMplsAdminStatus is
                'enabled(1)'.
            'disabled(2)'
                Set by an SNMP manager to stop an on-demand MPLS DM test.
                Set by SROS to indicate an on-demand MPLS DM test has stopped
                running because the configured period for the test (i.e.
                tmnxOamPmCfgDelayMplsTstDuration) has ended.
                Set by SROS for an on-demand MPLS DM test when
                tmnxOamPmCfgDelayMplsAdminStatus is set to 'disabled(2)'.
            'notApplicable(3)'
                This code point is the only acceptable value for a proactive
                MPLS DM test.  An attempt to set this code point for an
                on-demand MPLS DM test will be rejected.

         The default value is 'disabled(2)' for an on-demand MPLS DM test, and
         'notApplicable(3)' for a proactive MPLS DM test."
    ::= { tmnxOamPmCfgDelayMplsEntry 3 }

tmnxOamPmCfgDelayMplsTestId      OBJECT-TYPE
    SYNTAX      Unsigned32 (0..67108863)
    MAX-ACCESS  read-create
    STATUS      current
    DESCRIPTION
        "The value of tmnxOamPmCfgDelayMplsTestId specifies the test identifier
         for the specified session's MPLS DM test.

         When a MPLS DM test is created, tmnxOamPmCfgDelayMplsRowStatus and
         tmnxOamPmCfgDelayMplsTestId must be specified in the same SNMP Set
         PDU.

         When an MPLS DM query is being built, the test identifier is copied
         into the query's Session Identifier field.

         An attempt to add a duplicate test identifier to this table will be
         rejected."
    REFERENCE
        "RFC 6374, 'Packet Loss and Delay Measurement for MPLS Networks',
         September 2011, Section 3.2, 'Delay Measurement Message Format'."
    ::= { tmnxOamPmCfgDelayMplsEntry 4 }

tmnxOamPmCfgDelayMplsInterval    OBJECT-TYPE
    SYNTAX      Unsigned32 (1000 | 2000 | 3000 | 4000 | 5000 | 6000 | 7000 | 8000 | 9000 | 10000)
    UNITS       "milliseconds"
    MAX-ACCESS  read-create
    STATUS      current
    DESCRIPTION
        "The value of tmnxOamPmCfgDelayMplsInterval specifies the elapsed time
         between transmission of MPLS DM queries for the specified session's
         MPLS DM test."
    DEFVAL      { 1000 }
    ::= { tmnxOamPmCfgDelayMplsEntry 5 }

tmnxOamPmCfgDelayMplsPadTlvSize  OBJECT-TYPE
    SYNTAX      Unsigned32 (0 | 2..257)
    UNITS       "octets"
    MAX-ACCESS  read-create
    STATUS      current
    DESCRIPTION
        "The value of tmnxOamPmCfgDelayMplsPadTlvSize specifies the amount of
         padding to be added to each launched MPLS DM query for the specified
         session's MPLS DM test.

         Zero specifies that a Pad TLV should not be added to each launched
         MPLS DM query.

         A value larger than zero specifies the total size (including the two
         octet header) of the Pad TLV added to each launched MPLS DM query."
    REFERENCE
        "RFC 6374, 'Packet Loss and Delay Measurement for MPLS Networks',
         September 2011, Section 3.5.1, 'Padding'."
    DEFVAL      { 0 }
    ::= { tmnxOamPmCfgDelayMplsEntry 6 }

tmnxOamPmCfgDelayMplsReflectPad  OBJECT-TYPE
    SYNTAX      TruthValue
    MAX-ACCESS  read-create
    STATUS      current
    DESCRIPTION
        "The value of tmnxOamPmCfgDelayMplsReflectPad specifies whether or not
         to copy the Padding TLV from an MPLS DM query to the response.

         Within the MPLS DM protocol, this value controls whether the Type field
         of each transmitted Padding TLV of each MPLS DM query is
               0: Padding - copy in response, or
             128: Padding - do not copy in response."
    REFERENCE
        "RFC 6374, 'Packet Loss and Delay Measurement for MPLS Networks',
         September 2011, Section 3.5.1, 'Padding'."
    DEFVAL      { false }
    ::= { tmnxOamPmCfgDelayMplsEntry 7 }

tmnxOamPmCfgDelayMplsTstDuration OBJECT-TYPE
    SYNTAX      Unsigned32 (0..86400)
    UNITS       "seconds"
    MAX-ACCESS  read-create
    STATUS      current
    DESCRIPTION
        "The value of tmnxOamPmCfgDelayMplsTstDuration specifies the test
         duration for the specified session's MPLS DM test.

         Zero specifies a test which runs until it is manually stopped.

         An attempt to set a non-zero value will be rejected if
         tmnxOamPmCfgSessType is 'proactive(1)'."
    DEFVAL      { 0 }
    ::= { tmnxOamPmCfgDelayMplsEntry 8 }

tmnxOamPmCfgDelayMplsRunTimeLeft OBJECT-TYPE
    SYNTAX      Unsigned32 (0..86400)
    UNITS       "seconds"
    MAX-ACCESS  read-only
    STATUS      current
    DESCRIPTION
        "The value of tmnxOamPmCfgDelayMplsRunTimeLeft indicates the run time
         remaining for the specified session's MPLS DM test.

         For example, suppose a MPLS DM test has the following configuration:

         tmnxOamPmCfgSessType   tmnxOamPmCfgDelayMplsTstDuration
         --------------------   --------------------------------
         'onDemand(2)'          1000 (seconds)

         Then, when the MPLS DM test is started (see
         tmnxOamPmCfgDelayMplsOnDmdStatus), tmnxOamPmCfgDelayMplsRunTimeLeft is
         initialized to 1000 seconds.  After a minute,
         tmnxOamPmCfgDelayMplsRunTimeLeft is 940 seconds.

         If tmnxOamPmCfgSessType is 'proactive(1)', zero is always returned
         (because a proactive test runs until it is manually stopped).

         If tmnxOamPmCfgSessType is 'onDemand(2)' and the test is stopped (see
         tmnxOamPmCfgDelayMplsOnDmdStatus), zero is returned (because the test
         is not running)."
    ::= { tmnxOamPmCfgDelayMplsEntry 9 }

tmnxOamPmCfgDelayMplsStrTmplName OBJECT-TYPE
    SYNTAX      TLNamedItemOrEmpty
    MAX-ACCESS  read-create
    STATUS      current
    DESCRIPTION
        "The value of tmnxOamPmCfgDelayMplsStrTmplName specifies the name of
         the OAM-PM streaming template used by the specified MPLS-DM test.

         Streaming functionality is described in the DESCRIPTION clause of
         tmnxOamPmCfgStrTmplTable.

         If specified, tmnxOamPmCfgDelayMplsStrTmplName should match a template
         name created using tmnxOamPmCfgStrTmplRowStatus.  Otherwise,
         streaming will not work.

         An empty string indicates a template name has not been configured."
    DEFVAL      { "" }
    ::= { tmnxOamPmCfgDelayMplsEntry 10 }

tmnxOamPmCfgStrTmplTable         OBJECT-TYPE
    SYNTAX      SEQUENCE OF TmnxOamPmCfgStrTmplEntry
    MAX-ACCESS  not-accessible
    STATUS      current
    DESCRIPTION
        "tmnxOamPmCfgStrTmplTable contains the configuration information for
         OAM-PM streaming templates.

         A streaming template is used to send telemetry reports to a network
         management station.  A telemetry report can contain (for example) the
         average round-trip Frame Delay (FD) computed using a DMM test across a
         10 second interval.

         A streaming template defined using this table can be referenced by an
         OAM-PM test (e.g. a DMM test)."
    ::= { tmnxOamPmCfgTableObjs 22 }

tmnxOamPmCfgStrTmplEntry         OBJECT-TYPE
    SYNTAX      TmnxOamPmCfgStrTmplEntry
    MAX-ACCESS  not-accessible
    STATUS      current
    DESCRIPTION
        "tmnxOamPmCfgStrTmplEntry contains the configuration information for
         one OAM-PM streaming template.

         Rows are created or destroyed by SNMP Set operations on
         tmnxOamPmCfgStrTmplRowStatus."
    INDEX       { tmnxOamPmCfgStrTmplName }
    ::= { tmnxOamPmCfgStrTmplTable 1 }

TmnxOamPmCfgStrTmplEntry         ::= SEQUENCE
{
    tmnxOamPmCfgStrTmplName          TLNamedItem,
    tmnxOamPmCfgStrTmplRowStatus     RowStatus,
    tmnxOamPmCfgStrTmplDescription   TItemDescription,
    tmnxOamPmCfgStrTmplAdminStatus   TmnxEnabledDisabled,
    tmnxOamPmCfgStrTmplSampleWindow  Unsigned32,
    tmnxOamPmCfgStrTmplWindowInteg   Unsigned32
}

tmnxOamPmCfgStrTmplName          OBJECT-TYPE
    SYNTAX      TLNamedItem
    MAX-ACCESS  not-accessible
    STATUS      current
    DESCRIPTION
        "The value of tmnxOamPmCfgStrTmplName specifies the name of the
         streaming template to be configured or read."
    ::= { tmnxOamPmCfgStrTmplEntry 1 }

tmnxOamPmCfgStrTmplRowStatus     OBJECT-TYPE
    SYNTAX      RowStatus
    MAX-ACCESS  read-create
    STATUS      current
    DESCRIPTION
        "The value of tmnxOamPmCfgStrTmplRowStatus specifies the status of the
         configuration row for the specified streaming template."
    ::= { tmnxOamPmCfgStrTmplEntry 2 }

tmnxOamPmCfgStrTmplDescription   OBJECT-TYPE
    SYNTAX      TItemDescription
    MAX-ACCESS  read-create
    STATUS      current
    DESCRIPTION
        "The value of tmnxOamPmCfgStrTmplDescription specifies the descriptive
         text for the specified streaming template."
    DEFVAL      { "" }
    ::= { tmnxOamPmCfgStrTmplEntry 3 }

tmnxOamPmCfgStrTmplAdminStatus   OBJECT-TYPE
    SYNTAX      TmnxEnabledDisabled
    MAX-ACCESS  read-create
    STATUS      current
    DESCRIPTION
        "The value of tmnxOamPmCfgStrTmplAdminStatus specifies whether or not
         the specified streaming template is administratively enabled.

         When a streaming template is disabled, a test which refers to the
         template does not send telemetry reports.

         The following objects belonging to the specified streaming template
         cannot be modified when tmnxOamPmCfgStrTmplAdminStatus is 'enabled(1)':
             tmnxOamPmCfgStrTmplSampleWindow
             tmnxOamPmCfgStrTmplWindowInteg
             tmnxOamPmCfgStrMeasRowStatus"
    DEFVAL      { disabled }
    ::= { tmnxOamPmCfgStrTmplEntry 4 }

tmnxOamPmCfgStrTmplSampleWindow  OBJECT-TYPE
    SYNTAX      Unsigned32 (10..60)
    UNITS       "seconds"
    MAX-ACCESS  read-create
    STATUS      current
    DESCRIPTION
        "The value of tmnxOamPmCfgStrTmplSampleWindow specifies the duration of
         the sampling window for the specified streaming template.

         When a sampling window closes, a telemetry report is sent."
    DEFVAL      { 60 }
    ::= { tmnxOamPmCfgStrTmplEntry 5 }

tmnxOamPmCfgStrTmplWindowInteg   OBJECT-TYPE
    SYNTAX      Unsigned32 (1..100)
    UNITS       "percent"
    MAX-ACCESS  read-create
    STATUS      current
    DESCRIPTION
        "The value of tmnxOamPmCfgStrTmplWindowInteg specifies the percentage
         of valid measurements in the sampling window needed to declare the
         window valid (i.e. not suspect).

         A sampling window is reported as suspect using tmnxOamPmStsStrSuspect."
    DEFVAL      { 50 }
    ::= { tmnxOamPmCfgStrTmplEntry 6 }

tmnxOamPmCfgStrMeasTable         OBJECT-TYPE
    SYNTAX      SEQUENCE OF TmnxOamPmCfgStrMeasEntry
    MAX-ACCESS  not-accessible
    STATUS      current
    DESCRIPTION
        "tmnxOamPmCfgStrMeasTable contains the configuration of the
         measurements to be collected for OAM-PM streaming templates.

         Streaming functionality is described in the DESCRIPTION clause of
         tmnxOamPmCfgStrTmplTable."
    ::= { tmnxOamPmCfgTableObjs 23 }

tmnxOamPmCfgStrMeasEntry         OBJECT-TYPE
    SYNTAX      TmnxOamPmCfgStrMeasEntry
    MAX-ACCESS  not-accessible
    STATUS      current
    DESCRIPTION
        "tmnxOamPmCfgStrMeasEntry contains the configuration of one measurement
         to be collected for one OAM-PM streaming template.

         For example, suppose the table contains the following rows (where
         INDEX columns are underlined with octothorpes, and column names are
         abbreviated).

         Tmpl Name     Metric       Direction    Row Status
         ###########   ##########   ##########   ----------
         'strTmpl_1'   fdAvg(1)     twoWay(3)    active(1)
         'strTmpl_1'   ifdvAvg(2)   forward(1)   active(1)

         Then, an OAM-PM test which refers to 'strTmpl_1' will collect streaming
         measurements for
         1.  Average two-way Frame Delay (FD), and
         2.  Average Inter-Frame Delay Variation (IFDV) in the forward
             direction.

         Rows are created and destroyed using tmnxOamPmCfgStrMeasRowStatus."
    INDEX       {
        tmnxOamPmCfgStrTmplName,
        tmnxOamPmCfgStrMetric,
        tmnxOamPmCfgStrDir
    }
    ::= { tmnxOamPmCfgStrMeasTable 1 }

TmnxOamPmCfgStrMeasEntry         ::= SEQUENCE
{
    tmnxOamPmCfgStrMetric            TmnxOamPmStrMetric,
    tmnxOamPmCfgStrDir               TmnxOamPmForwardBackwardTwoWay,
    tmnxOamPmCfgStrMeasRowStatus     RowStatus
}

tmnxOamPmCfgStrMetric            OBJECT-TYPE
    SYNTAX      TmnxOamPmStrMetric
    MAX-ACCESS  not-accessible
    STATUS      current
    DESCRIPTION
        "The value of tmnxOamPmCfgStrMetric specifies the metric to be
         collected (e.g. average Frame Delay, 'fdAvg(1)')."
    ::= { tmnxOamPmCfgStrMeasEntry 1 }

tmnxOamPmCfgStrDir               OBJECT-TYPE
    SYNTAX      TmnxOamPmForwardBackwardTwoWay
    MAX-ACCESS  not-accessible
    STATUS      current
    DESCRIPTION
        "The value of tmnxOamPmCfgStrDir specifies the direction to be measured
         (e.g. 'forward(1)')."
    ::= { tmnxOamPmCfgStrMeasEntry 2 }

tmnxOamPmCfgStrMeasRowStatus     OBJECT-TYPE
    SYNTAX      RowStatus
    MAX-ACCESS  read-create
    STATUS      current
    DESCRIPTION
        "The value of tmnxOamPmCfgStrMeasRowStatus specifies the status of the
         configuration row for the specified streaming measurement."
    ::= { tmnxOamPmCfgStrMeasEntry 3 }

tmnxOamPmStatsObjs               OBJECT IDENTIFIER ::= { tmnxOamPmObjs 2 }

tmnxOamPmStatsScalarObjs         OBJECT IDENTIFIER ::= { tmnxOamPmStatsObjs 1 }

tmnxOamPmStsMplsDmUdpPort        OBJECT-TYPE
    SYNTAX      InetPortNumber
    MAX-ACCESS  read-only
    STATUS      current
    DESCRIPTION
        "The value of tmnxOamPmStsMplsDmUdpPort indicates the UDP port used to
         receive all out-of-band MPLS-DM responses."
    REFERENCE
        "RFC 6374, 'Packet Loss and Delay Measurement for MPLS Networks',
         September 2011, Section 4.3.4, 'Receiving a Delay Measurement
         Response'."
    ::= { tmnxOamPmStatsScalarObjs 1 }

tmnxOamPmStsTestLimit            OBJECT-TYPE
    SYNTAX      Gauge32
    UNITS       "tests"
    MAX-ACCESS  read-only
    STATUS      current
    DESCRIPTION
        "The value of tmnxOamPmStsTestLimit indicates the maximum number of
         OAM-PM tests.

         See the tmnxOamPmStsTestCount DESCRIPTION clause for more information."
    ::= { tmnxOamPmStatsScalarObjs 2 }

tmnxOamPmStsTestCount            OBJECT-TYPE
    SYNTAX      Gauge32
    UNITS       "tests"
    MAX-ACCESS  read-only
    STATUS      current
    DESCRIPTION
        "The value of tmnxOamPmStsTestCount indicates the current number of
         OAM-PM tests.

         The count is incremented when a test is created (e.g. using
         tmnxOamPmCfgDelayDmmRowStatus).

         The count is decremented when a test is destroyed.

         Creation of a test fails when tmnxOamPmStsTestCount equals
         tmnxOamPmStsTestLimit."
    ::= { tmnxOamPmStatsScalarObjs 3 }

tmnxOamPmStsTxLimit              OBJECT-TYPE
    SYNTAX      Gauge32
    UNITS       "echo request packets per second"
    MAX-ACCESS  read-only
    STATUS      current
    DESCRIPTION
        "The value of tmnxOamPmStsTxLimit indicates this node's
         upper bound on the total configured echo request packet transmission
         rate for OAM-PM.  The upper bound is enforced to avoid echo
         request packet transmit overload, i.e. to ensure each enabled test can
         transmit echo request packets at the test's configured rate.

         Echo reply packets are not affected by this limit."
    ::= { tmnxOamPmStatsScalarObjs 4 }

tmnxOamPmStsTxTotal              OBJECT-TYPE
    SYNTAX      Gauge32
    UNITS       "echo request packets per second"
    MAX-ACCESS  read-only
    STATUS      current
    DESCRIPTION
        "The value of tmnxOamPmStsTxTotal indicates this node's current total
         configured echo request packet transmission rate for OAM-PM.

         The total transmission rate changes when a proactive test is
         administratively enabled or disabled (e.g. using
         tmnxOamPmCfgDelayDmmAdminStatus).

         Administratively enabling a test fails if it would result in
         tmnxOamPmStsTxTotal > tmnxOamPmStsTxLimit."
    ::= { tmnxOamPmStatsScalarObjs 5 }

tmnxOamPmStatsTableObjs          OBJECT IDENTIFIER ::= { tmnxOamPmStatsObjs 2 }

tmnxOamPmStsBaseTable            OBJECT-TYPE
    SYNTAX      SEQUENCE OF TmnxOamPmStsBaseEntry
    MAX-ACCESS  not-accessible
    STATUS      current
    DESCRIPTION
        "tmnxOamPmStsBaseTable contains the base statistics for OAM
         Performance Monitoring Measurement Interval Data Sets.  The statistics
         in this table are common to all test types (e.g. DMM and SLM tests)."
    REFERENCE
        "MEF-35, 'Service OAM Performance Monitoring Implementation Agreement',
         Metro Ethernet Forum, April 2012, Section 9.2.1 'Measurement Interval
         Data Sets'"
    ::= { tmnxOamPmStatsTableObjs 1 }

tmnxOamPmStsBaseEntry            OBJECT-TYPE
    SYNTAX      TmnxOamPmStsBaseEntry
    MAX-ACCESS  not-accessible
    STATUS      current
    DESCRIPTION
        "tmnxOamPmStsBaseEntry contains the base statistics for one OAM
         Performance Monitoring Measurement Interval Data Set.

         Rows are created in this table when a test is started (e.g. using
         tmnxOamPmCfgDelayDmmAdminStatus and tmnxOamPmCfgDelayDmmOnDmndStatus).
         At that time, a row for the current interval (with the index value
         tmnxOamPmStsIntvlNum=1) is created for each row with a matching session
         name in tmnxOamPmCfgMeasIntvlTable.  In addition, a row is created in
         this table for the test's 'miRaw(1)' interval.

         After that, the timed creation and destruction of rows in this table
         is explained using the following example.

         Suppose the configured number of intervals to be retained is as
         follows (where index columns are underlined with octothorpes, and
         'tmnxOamPm' is abbreviated as '_'):

         _CfgSessName  _CfgMeasIntvlDuration  _CfgMeasIntvlsStored
         ############  #####################  --------------------
         'mySess1'     'mi15Minutes(2)'                          3

         Suppose statistics collection started at t = 0 (minutes).

         Suppose the following rows exist in tmnxOamPmStsBaseTable at t = 59
         (minutes):

         _CfgSessName  _StsBaseTestType  _StsIntvlDuration  _StsIntvlNum
         ############  ################  #################  ############
         'mySess1'     'dmm(1)'          'mi15Minutes(2)'              1
         'mySess1'     'dmm(1)'          'mi15Minutes(2)'              2
         'mySess1'     'dmm(1)'          'mi15Minutes(2)'              3
         'mySess1'     'dmm(1)'          'mi15Minutes(2)'              4

         The interval numbers are assigned as follows:
             1 - the historical interval ended at t = 15 minutes
             2 - the historical interval ended at t = 30 minutes
             3 - the historical interval ended at t = 45 minutes
             4 - the current interval

         Then, after the next 15 minute interval ends (e.g. at t = 61 minutes),
         the following rows will exist:

         _CfgSessName  _StsBaseTestType  _StsIntvlDuration  _StsIntvlNum
         ############  ################  #################  ############
         'mySess1'     'dmm(1)'          'mi15Minutes(2)'              2
         'mySess1'     'dmm(1)'          'mi15Minutes(2)'              3
         'mySess1'     'dmm(1)'          'mi15Minutes(2)'              4
         'mySess1'     'dmm(1)'          'mi15Minutes(2)'              5

         The interval numbers are assigned as follows:
             2 - the historical interval ended at t = 30 minutes
             3 - the historical interval ended at t = 45 minutes
             4 - the historical interval ended at t = 60 minutes
             5 - the current interval

         The row with interval number 1 was destroyed, because
         tmnxOamPmCfgMeasIntvlsStored=3 specifies that at most three historical
         intervals be retained.

         Rows are also destroyed in this table when the corresponding
         tmnxOamPmCfgMeasIntvlTable row is destroyed.

         When the index value tmnxOamPmStsMeasIntvlDuration is 'miRaw(1)', only
         one interval is available (i.e. tmnxOamPmStsIntvlNum = 1).

         When a test is running, the measurement interval data set for a test's
         'miRaw(1)' measurement interval duration can be cleared using
         TIMETRA-CLEAR-MIB::tmnxClearAction and tmnxClearParams.  The change to
         the objects in the specified row is as follows.

         Object                        Change on Clear Operation
         ----------------------------  --------------------------------------
         tmnxOamPmStsBaseOperStatus    No change
         tmnxOamPmStsBaseSuspect       Set to 'true(1)'
         tmnxOamPmStsBaseStartTime     Set to UTC time of the clear operation
         tmnxOamPmStsBaseElapsedTime   Set to zero
         tmnxOamPmStsBaseTestFramesTx  Set to zero
         tmnxOamPmStsBaseTestFramesRx  Set to zero

         Measurement interval data sets for  measurement interval durations
         other than 'miRaw(1)' cannot be cleared."
    INDEX       {
        tmnxOamPmCfgSessName,
        tmnxOamPmStsBaseTestType,
        tmnxOamPmStsMeasIntvlDuration,
        tmnxOamPmStsIntvlNum
    }
    ::= { tmnxOamPmStsBaseTable 1 }

TmnxOamPmStsBaseEntry            ::= SEQUENCE
{
    tmnxOamPmStsBaseTestType         TmnxOamPmTestType,
    tmnxOamPmStsMeasIntvlDuration    TmnxOamPmMeasIntervalDuration,
    tmnxOamPmStsIntvlNum             TmnxOamPmStsIntvlNum,
    tmnxOamPmStsBaseOperStatus       INTEGER,
    tmnxOamPmStsBaseSuspect          TruthValue,
    tmnxOamPmStsBaseStartTime        DateAndTime,
    tmnxOamPmStsBaseElapsedTime      Unsigned32,
    tmnxOamPmStsBaseTestFramesTx     Unsigned32,
    tmnxOamPmStsBaseTestFramesRx     Unsigned32
}

tmnxOamPmStsBaseTestType         OBJECT-TYPE
    SYNTAX      TmnxOamPmTestType
    MAX-ACCESS  not-accessible
    STATUS      current
    DESCRIPTION
        "The value of tmnxOamPmStsBaseTestType specifies the type of test for
         which statistics are to be read (e.g. 'dmm(1)')."
    ::= { tmnxOamPmStsBaseEntry 1 }

tmnxOamPmStsMeasIntvlDuration    OBJECT-TYPE
    SYNTAX      TmnxOamPmMeasIntervalDuration
    MAX-ACCESS  not-accessible
    STATUS      current
    DESCRIPTION
        "The value of tmnxOamPmStsMeasIntvlDuration specifies the duration of
         the interval of the statistics to be read (e.g. 'mi15Minutes(2)')."
    ::= { tmnxOamPmStsBaseEntry 2 }

tmnxOamPmStsIntvlNum             OBJECT-TYPE
    SYNTAX      TmnxOamPmStsIntvlNum
    MAX-ACCESS  not-accessible
    STATUS      current
    DESCRIPTION
        "The value of tmnxOamPmStsIntvlNum specifies the interval number of the
         statistics to be read.

         The system's creation and destruction of interval numbers is described
         in the tmnxOamPmStsBaseEntry DESCRIPTION clause."
    ::= { tmnxOamPmStsBaseEntry 3 }

tmnxOamPmStsBaseOperStatus       OBJECT-TYPE
    SYNTAX      INTEGER {
        inProgress (1),
        completed  (2)
    }
    MAX-ACCESS  read-only
    STATUS      current
    DESCRIPTION
        "The value of tmnxOamPmStsBaseOperStatus indicates the operational
         status of the specified measurement interval data set.

         If the interval is historical and the operational status is
         'inProgress(1)', the interval is closing (i.e. waiting for a response
         for the final test request sent)."
    ::= { tmnxOamPmStsBaseEntry 4 }

tmnxOamPmStsBaseSuspect          OBJECT-TYPE
    SYNTAX      TruthValue
    MAX-ACCESS  read-only
    STATUS      current
    DESCRIPTION
        "The value of tmnxOamPmStsBaseSuspect indicates whether or not the
         specified measurement interval data set contains suspect information."
    REFERENCE
        "MEF-35, 'Service OAM Performance Monitoring Implementation Agreement',
         Metro Ethernet Forum, April 2012, Section 9.2.4, 'Measurement Interval
         Status'."
    ::= { tmnxOamPmStsBaseEntry 5 }

tmnxOamPmStsBaseStartTime        OBJECT-TYPE
    SYNTAX      DateAndTime (SIZE (8))
    MAX-ACCESS  read-only
    STATUS      current
    DESCRIPTION
        "The value of tmnxOamPmStsBaseStartTime indicates the start time (in
         UTC) of the specified measurement interval data set."
    ::= { tmnxOamPmStsBaseEntry 6 }

tmnxOamPmStsBaseElapsedTime      OBJECT-TYPE
    SYNTAX      Unsigned32
    UNITS       "seconds"
    MAX-ACCESS  read-only
    STATUS      current
    DESCRIPTION
        "The value of tmnxOamPmStsBaseElapsedTime indicates the time elapsed
         since data collection started for the specified measurement interval
         data set."
    ::= { tmnxOamPmStsBaseEntry 7 }

tmnxOamPmStsBaseTestFramesTx     OBJECT-TYPE
    SYNTAX      Unsigned32
    UNITS       "frames"
    MAX-ACCESS  read-only
    STATUS      current
    DESCRIPTION
        "The value of tmnxOamPmStsBaseTestFramesTx indicates the number of test
         frames sent for the specified measurement interval data set."
    ::= { tmnxOamPmStsBaseEntry 8 }

tmnxOamPmStsBaseTestFramesRx     OBJECT-TYPE
    SYNTAX      Unsigned32
    UNITS       "frames"
    MAX-ACCESS  read-only
    STATUS      current
    DESCRIPTION
        "The value of tmnxOamPmStsBaseTestFramesRx indicates the number of test
         frames received for the specified measurement interval data set."
    ::= { tmnxOamPmStsBaseEntry 9 }

tmnxOamPmStsMeasIntvlIndexTable  OBJECT-TYPE
    SYNTAX      SEQUENCE OF TmnxOamPmStsMeasIntvlIndexEntry
    MAX-ACCESS  not-accessible
    STATUS      current
    DESCRIPTION
        "tmnxOamPmStsMeasIntvlIndexTable contains the interval number of the
         newest interval for all the active combinations of session, test type
         (e.g. 'dmm(1)'), and interval duration (e.g. 'mi15Minutes(2)')."
    ::= { tmnxOamPmStatsTableObjs 2 }

tmnxOamPmStsMeasIntvlIndexEntry  OBJECT-TYPE
    SYNTAX      TmnxOamPmStsMeasIntvlIndexEntry
    MAX-ACCESS  not-accessible
    STATUS      current
    DESCRIPTION
        "tmnxOamPmStsMeasIntvlIndexEntry contains the interval number of the
         newest interval for the specified combination of session, test type
         (e.g. 'dmm(1)'), and interval duration (e.g. 'mi15Minutes(2)').

         Rows are created in this table when a test is enabled (e.g. using
         tmnxOamPmCfgDelayDmmAdminStatus and tmnxOamPmCfgDelayDmmOnDmndStatus).

         A row is destroyed in this table when the corresponding
         tmnxOamPmCfgMeasIntvlTable row is destroyed."
    INDEX       {
        tmnxOamPmCfgSessName,
        tmnxOamPmStsBaseTestType,
        tmnxOamPmStsMeasIntvlDuration
    }
    ::= { tmnxOamPmStsMeasIntvlIndexTable 1 }

TmnxOamPmStsMeasIntvlIndexEntry  ::= SEQUENCE
{ tmnxOamPmStsMeasIntvlIndexNewest TmnxOamPmStsIntvlNum }

tmnxOamPmStsMeasIntvlIndexNewest OBJECT-TYPE
    SYNTAX      TmnxOamPmStsIntvlNum
    MAX-ACCESS  read-only
    STATUS      current
    DESCRIPTION
        "The value of tmnxOamPmStsMeasIntvlIndexNewest indicates the interval
         number of the newest interval for the specified session, test type
         (e.g. 'dmm(1)'), and interval duration (e.g. 'mi15Minutes(2)').  This
         value is provided as the tmnxOamPmStsIntvlNum index value when reading
         a row for the newest interval in an OAM-PM statistics table.

         For a running test, the newest interval is the current interval.

         For a stopped test, the newest interval is the most recent historical
         interval.  A stopped test does not have a current interval.

         The interval number of the oldest interval for the specified session,
         test type, and interval duration can be computed from this value.

         For a running test, the formula is
         interval_number_of_the_oldest_interval =
         MAX(tmnxOamPmStsMeasIntvlIndexNewest-tmnxOamPmCfgMeasIntvlsStored,  1).

         For a stopped test, the formula is
         interval_number_of_the_oldest_interval =
         MAX(tmnxOamPmStsMeasIntvlIndexNewest-tmnxOamPmCfgMeasIntvlsStored+1,1)."
    ::= { tmnxOamPmStsMeasIntvlIndexEntry 1 }

tmnxOamPmStsLossSlmTable         OBJECT-TYPE
    SYNTAX      SEQUENCE OF TmnxOamPmStsLossSlmEntry
    MAX-ACCESS  not-accessible
    STATUS      current
    DESCRIPTION
        "tmnxOamPmStsLossSlmTable contains the frame loss statistics for OAM
         Performance Monitoring SLM (Synthetic Loss Measurement) tests."
    REFERENCE
        "MEF-35, 'Service OAM Performance Monitoring Implementation Agreement',
         Metro Ethernet Forum, April 2012, Section 10.2, 'Single-Ended Synthetic
         Loss Function for Frame Loss Ratio (FLR) and Availability'."
    ::= { tmnxOamPmStatsTableObjs 3 }

tmnxOamPmStsLossSlmEntry         OBJECT-TYPE
    SYNTAX      TmnxOamPmStsLossSlmEntry
    MAX-ACCESS  not-accessible
    STATUS      current
    DESCRIPTION
        "tmnxOamPmStsLossSlmEntry contains the SLM test statistics for one OAM
         Performance Monitoring Measurement Interval Data Set.

         A row is created in this table when a tmnxOamPmStsBaseTable row is
         created with tmnxOamPmStsBaseTestType = 'slm(2)'.

         A row is destroyed in this table when the corresponding
         tmnxOamPmStsBaseTable row is destroyed.

         When a test is running, the SLM statistics for a test's raw (i.e.
         'miRaw(1)') measurement interval duration can be cleared using
         TIMETRA-CLEAR-MIB::tmnxClearAction and tmnxClearParams.  A successful
         clear operation zeros all the raw SLM statistics for the specified
         session."
    INDEX       {
        tmnxOamPmCfgSessName,
        tmnxOamPmStsMeasIntvlDuration,
        tmnxOamPmStsIntvlNum
    }
    ::= { tmnxOamPmStsLossSlmTable 1 }

TmnxOamPmStsLossSlmEntry         ::= SEQUENCE
{
    tmnxOamPmStsLossSlmTxFwd         Unsigned32,
    tmnxOamPmStsLossSlmRxFwd         Unsigned32,
    tmnxOamPmStsLossSlmTxBwd         Unsigned32,
    tmnxOamPmStsLossSlmRxBwd         Unsigned32,
    tmnxOamPmStsLossSlmAvailIndFwd   Unsigned32,
    tmnxOamPmStsLossSlmAvailIndBwd   Unsigned32,
    tmnxOamPmStsLossSlmUnavlIndFwd   Unsigned32,
    tmnxOamPmStsLossSlmUnavlIndBwd   Unsigned32,
    tmnxOamPmStsLossSlmUndtAvlFwd    Unsigned32,
    tmnxOamPmStsLossSlmUndtUnavlFwd  Unsigned32,
    tmnxOamPmStsLossSlmUndtAvlBwd    Unsigned32,
    tmnxOamPmStsLossSlmUndtUnavlBwd  Unsigned32,
    tmnxOamPmStsLossSlmHliFwd        Unsigned32,
    tmnxOamPmStsLossSlmHliBwd        Unsigned32,
    tmnxOamPmStsLossSlmChliFwd       Unsigned32,
    tmnxOamPmStsLossSlmChliBwd       Unsigned32,
    tmnxOamPmStsLossSlmMinFlrFwd     Unsigned32,
    tmnxOamPmStsLossSlmMaxFlrFwd     Unsigned32,
    tmnxOamPmStsLossSlmAvgFlrFwd     Unsigned32,
    tmnxOamPmStsLossSlmMinFlrBwd     Unsigned32,
    tmnxOamPmStsLossSlmMaxFlrBwd     Unsigned32,
    tmnxOamPmStsLossSlmAvgFlrBwd     Unsigned32
}

tmnxOamPmStsLossSlmTxFwd         OBJECT-TYPE
    SYNTAX      Unsigned32
    UNITS       "SLM frames"
    MAX-ACCESS  read-only
    STATUS      current
    DESCRIPTION
        "The value of tmnxOamPmStsLossSlmTxFwd indicates the number of SLM
         request frames transmitted in the forward direction for the specified
         measurement interval data set.

         A frame is counted if the SLM Availability state is Available at
         transmit time (as specified in MEF-35 Section 9.2.5).

         A simple count of the frames transmitted for the test is available in
         tmnxOamPmStsBaseTestFramesTx."
    REFERENCE
        "MEF-35, 'Service OAM Performance Monitoring Implementation Agreement',
         Metro Ethernet Forum, April 2012, Section 9.2.5, 'Measurement Behavior
         During Periods of Unavailability and Maintenance Intervals'"
    ::= { tmnxOamPmStsLossSlmEntry 1 }

tmnxOamPmStsLossSlmRxFwd         OBJECT-TYPE
    SYNTAX      Unsigned32
    UNITS       "SLM frames"
    MAX-ACCESS  read-only
    STATUS      current
    DESCRIPTION
        "The value of tmnxOamPmStsLossSlmRxFwd indicates the number of SLM
         request frames received in the forward direction for the specified
         measurement interval data set.

         A frame is counted if the SLM Availability state is Available at
         receive time (as specified in MEF-35 Section 9.2.5).

         A simple count of the frames received for the test is available in
         tmnxOamPmStsBaseTestFramesRx."
    REFERENCE
        "MEF-35, 'Service OAM Performance Monitoring Implementation Agreement',
         Metro Ethernet Forum, April 2012, Section 9.2.5, 'Measurement Behavior
         During Periods of Unavailability and Maintenance Intervals'"
    ::= { tmnxOamPmStsLossSlmEntry 2 }

tmnxOamPmStsLossSlmTxBwd         OBJECT-TYPE
    SYNTAX      Unsigned32
    UNITS       "SLR frames"
    MAX-ACCESS  read-only
    STATUS      current
    DESCRIPTION
        "The value of tmnxOamPmStsLossSlmTxBwd indicates the number of SLR
         reply frames transmitted in the backward direction for the specified
         measurement interval data set.

         A frame is counted if the SLM Availability state is Available at
         transmit time (as specified in MEF-35 Section 9.2.5).

         A simple count of the frames transmitted for the test is available in
         tmnxOamPmStsBaseTestFramesTx."
    REFERENCE
        "MEF-35, 'Service OAM Performance Monitoring Implementation Agreement',
         Metro Ethernet Forum, April 2012, Section 9.2.5, 'Measurement Behavior
         During Periods of Unavailability and Maintenance Intervals'"
    ::= { tmnxOamPmStsLossSlmEntry 3 }

tmnxOamPmStsLossSlmRxBwd         OBJECT-TYPE
    SYNTAX      Unsigned32
    UNITS       "SLR frames"
    MAX-ACCESS  read-only
    STATUS      current
    DESCRIPTION
        "The value of tmnxOamPmStsLossSlmRxBwd indicates the number of SLR
         reply frames received in the backward direction for the specified
         measurement interval data set.

         A frame is counted if the SLM Availability state is Available at
         receive time (as specified in MEF-35 Section 9.2.5).

         A simple count of the frames received for the test is available in
         tmnxOamPmStsBaseTestFramesRx."
    REFERENCE
        "MEF-35, 'Service OAM Performance Monitoring Implementation Agreement',
         Metro Ethernet Forum, April 2012, Section 9.2.5, 'Measurement Behavior
         During Periods of Unavailability and Maintenance Intervals'"
    ::= { tmnxOamPmStsLossSlmEntry 4 }

tmnxOamPmStsLossSlmAvailIndFwd   OBJECT-TYPE
    SYNTAX      Unsigned32
    MAX-ACCESS  read-only
    STATUS      current
    DESCRIPTION
        "The value of tmnxOamPmStsLossSlmAvailIndFwd indicates the number of
         availability indicators evaluated as Available in the forward
         direction for the specified measurement interval data set."
    ::= { tmnxOamPmStsLossSlmEntry 5 }

tmnxOamPmStsLossSlmAvailIndBwd   OBJECT-TYPE
    SYNTAX      Unsigned32
    MAX-ACCESS  read-only
    STATUS      current
    DESCRIPTION
        "The value of tmnxOamPmStsLossSlmAvailIndBwd indicates the number of
         availability indicators evaluated as Available in the backward
         direction for the specified measurement interval data set."
    ::= { tmnxOamPmStsLossSlmEntry 6 }

tmnxOamPmStsLossSlmUnavlIndFwd   OBJECT-TYPE
    SYNTAX      Unsigned32
    MAX-ACCESS  read-only
    STATUS      current
    DESCRIPTION
        "The value of tmnxOamPmStsLossSlmUnavlIndFwd indicates the number of
         availability indicators evaluated as Unavailable in the forward
         direction for the specified measurement interval data set."
    ::= { tmnxOamPmStsLossSlmEntry 7 }

tmnxOamPmStsLossSlmUnavlIndBwd   OBJECT-TYPE
    SYNTAX      Unsigned32
    MAX-ACCESS  read-only
    STATUS      current
    DESCRIPTION
        "The value of tmnxOamPmStsLossSlmUnavlIndBwd indicates the number of
         availability indicators evaluated as Unavailable in the backward
         direction for the specified measurement interval data set."
    ::= { tmnxOamPmStsLossSlmEntry 8 }

tmnxOamPmStsLossSlmUndtAvlFwd    OBJECT-TYPE
    SYNTAX      Unsigned32
    MAX-ACCESS  read-only
    STATUS      current
    DESCRIPTION
        "The value of tmnxOamPmStsLossSlmUndtAvlFwd indicates the number of
         availability indicators evaluated as Available in the forward
         direction based on extrapolation from the previous state.

         For example, this counter will be incremented when:
         1.  It is time to calculate an availability indicator, and
         2.  All the probe requests used to calculate the availability indicator
         have timed out, and
         3.  The most recently declared availability indicator in the forward
         direction was Available.

         In that case, the result is considered undetermined because no
         information is available to indicate if the problem is in the forward
         direction or the backward direction."
    ::= { tmnxOamPmStsLossSlmEntry 9 }

tmnxOamPmStsLossSlmUndtUnavlFwd  OBJECT-TYPE
    SYNTAX      Unsigned32
    MAX-ACCESS  read-only
    STATUS      current
    DESCRIPTION
        "The value of tmnxOamPmStsLossSlmUndtUnavlFwd indicates the number of
         availability indicators evaluated as Unavailable in the forward
         direction based on extrapolation from the previous state.

         For example, this counter will be incremented when:
         1.  It is time to calculate an availability indicator, and
         2.  All the probe requests used to calculate the availability indicator
         have timed out, and
         3.  The most recently declared availability indicator in the forward
         direction was Unavailable.

         In that case, the result is considered undetermined because no
         information is available to indicate if the problem is in the forward
         direction or the backward direction."
    ::= { tmnxOamPmStsLossSlmEntry 10 }

tmnxOamPmStsLossSlmUndtAvlBwd    OBJECT-TYPE
    SYNTAX      Unsigned32
    MAX-ACCESS  read-only
    STATUS      current
    DESCRIPTION
        "The value of tmnxOamPmStsLossSlmUndtAvlBwd indicates the number of
         availability indicators evaluated as Available in the backward
         direction based on extrapolation from the previous state.

         For example, this counter will be incremented when:
         1.  It is time to calculate an availability indicator, and
         2.  All the probe requests used to calculate the availability indicator
         have timed out, and
         3.  The most recently declared availability indicator in the backward
         direction was Available.

         In that case, the result is considered undetermined because no
         information is available to indicate if the problem is in the forward
         direction or the backward direction."
    ::= { tmnxOamPmStsLossSlmEntry 11 }

tmnxOamPmStsLossSlmUndtUnavlBwd  OBJECT-TYPE
    SYNTAX      Unsigned32
    MAX-ACCESS  read-only
    STATUS      current
    DESCRIPTION
        "The value of tmnxOamPmStsLossSlmUndtUnavlBwd indicates the number of
         availability indicators evaluated as Unavailable in the backward
         direction based on extrapolation from the previous state.

         For example, this counter will be incremented when:
         1.  It is time to calculate an availability indicator, and
         2.  All the probe requests used to calculate the availability indicator
         have timed out, and
         3.  The most recently declared availability indicator in the backward
         direction was Unavailable.

         In that case, the result is considered undetermined because no
         information is available to indicate if the problem is in the forward
         direction or the backward direction."
    ::= { tmnxOamPmStsLossSlmEntry 12 }

tmnxOamPmStsLossSlmHliFwd        OBJECT-TYPE
    SYNTAX      Unsigned32
    MAX-ACCESS  read-only
    STATUS      current
    DESCRIPTION
        "The value of tmnxOamPmStsLossSlmHliFwd indicates the number of High
         Loss Intervals (HLIs) in the forward direction for the specified
         measurement interval data set."
    ::= { tmnxOamPmStsLossSlmEntry 13 }

tmnxOamPmStsLossSlmHliBwd        OBJECT-TYPE
    SYNTAX      Unsigned32
    MAX-ACCESS  read-only
    STATUS      current
    DESCRIPTION
        "The value of tmnxOamPmStsLossSlmHliBwd indicates the number of High
         Loss Intervals (HLIs) in the backward direction for the specified
         measurement interval data set."
    ::= { tmnxOamPmStsLossSlmEntry 14 }

tmnxOamPmStsLossSlmChliFwd       OBJECT-TYPE
    SYNTAX      Unsigned32
    MAX-ACCESS  read-only
    STATUS      current
    DESCRIPTION
        "The value of tmnxOamPmStsLossSlmChliFwd indicates the number of
         Consecutive High Loss Intervals (CHLIs) in the forward direction for
         the specified measurement interval data set."
    ::= { tmnxOamPmStsLossSlmEntry 15 }

tmnxOamPmStsLossSlmChliBwd       OBJECT-TYPE
    SYNTAX      Unsigned32
    MAX-ACCESS  read-only
    STATUS      current
    DESCRIPTION
        "The value of tmnxOamPmStsLossSlmChliBwd indicates the number of
         Consecutive High Loss Intervals (CHLIs) in the backward direction for
         the specified measurement interval data set."
    ::= { tmnxOamPmStsLossSlmEntry 16 }

tmnxOamPmStsLossSlmMinFlrFwd     OBJECT-TYPE
    SYNTAX      Unsigned32 (0..100000)
    UNITS       "milli-percent"
    MAX-ACCESS  read-only
    STATUS      current
    DESCRIPTION
        "The value of tmnxOamPmStsLossSlmMinFlrFwd indicates the minimum Frame
         Loss Ratio (FLR) in the forward direction for the specified
         measurement interval data set."
    ::= { tmnxOamPmStsLossSlmEntry 17 }

tmnxOamPmStsLossSlmMaxFlrFwd     OBJECT-TYPE
    SYNTAX      Unsigned32 (0..100000)
    UNITS       "milli-percent"
    MAX-ACCESS  read-only
    STATUS      current
    DESCRIPTION
        "The value of tmnxOamPmStsLossSlmMaxFlrFwd indicates the maximum Frame
         Loss Ratio (FLR) in the forward direction for the specified
         measurement interval data set."
    ::= { tmnxOamPmStsLossSlmEntry 18 }

tmnxOamPmStsLossSlmAvgFlrFwd     OBJECT-TYPE
    SYNTAX      Unsigned32 (0..100000)
    UNITS       "milli-percent"
    MAX-ACCESS  read-only
    STATUS      current
    DESCRIPTION
        "The value of tmnxOamPmStsLossSlmAvgFlrFwd indicates the average Frame
         Loss Ratio (FLR) in the forward direction for the specified
         measurement interval data set."
    ::= { tmnxOamPmStsLossSlmEntry 19 }

tmnxOamPmStsLossSlmMinFlrBwd     OBJECT-TYPE
    SYNTAX      Unsigned32 (0..100000)
    UNITS       "milli-percent"
    MAX-ACCESS  read-only
    STATUS      current
    DESCRIPTION
        "The value of tmnxOamPmStsLossSlmMinFlrBwd indicates the minimum Frame
         Loss Ratio (FLR) in the backward direction for the specified
         measurement interval data set."
    ::= { tmnxOamPmStsLossSlmEntry 20 }

tmnxOamPmStsLossSlmMaxFlrBwd     OBJECT-TYPE
    SYNTAX      Unsigned32 (0..100000)
    UNITS       "milli-percent"
    MAX-ACCESS  read-only
    STATUS      current
    DESCRIPTION
        "The value of tmnxOamPmStsLossSlmMaxFlrBwd indicates the maximum Frame
         Loss Ratio (FLR) in the backward direction for the specified
         measurement interval data set."
    ::= { tmnxOamPmStsLossSlmEntry 21 }

tmnxOamPmStsLossSlmAvgFlrBwd     OBJECT-TYPE
    SYNTAX      Unsigned32 (0..100000)
    UNITS       "milli-percent"
    MAX-ACCESS  read-only
    STATUS      current
    DESCRIPTION
        "The value of tmnxOamPmStsLossSlmAvgFlrBwd indicates the average Frame
         Loss Ratio (FLR) in the backward direction for the specified
         measurement interval data set."
    ::= { tmnxOamPmStsLossSlmEntry 22 }

tmnxOamPmStsDelayDmmTable        OBJECT-TYPE
    SYNTAX      SEQUENCE OF TmnxOamPmStsDelayDmmEntry
    MAX-ACCESS  not-accessible
    STATUS      current
    DESCRIPTION
        "tmnxOamPmStsDelayDmmTable contains the summarized DMM (Delay
         Measurement Message) statistics for OAM Performance Monitoring
         Measurement Interval Data Sets."
    REFERENCE
        "MEF-35, 'Service OAM Performance Monitoring Implementation Agreement',
         Metro Ethernet Forum, April 2012, Section 10.1, 'Single-Ended Delay
         Function for Delay, Frame Delay Range, and Inter Delay Variation'."
    ::= { tmnxOamPmStatsTableObjs 4 }

tmnxOamPmStsDelayDmmEntry        OBJECT-TYPE
    SYNTAX      TmnxOamPmStsDelayDmmEntry
    MAX-ACCESS  not-accessible
    STATUS      current
    DESCRIPTION
        "tmnxOamPmStsDelayDmmEntry contains the summarized DMM (Delay
         Measurement Message) statistics for one OAM Performance Monitoring
         Measurement Interval Data Set.

         When a row is created in tmnxOamPmStsBaseTable with
         tmnxOamPmStsBaseTestType = 'dmm(1)', three rows are created in this
         table.  The three rows have the following values in the
         tmnxOamPmCfgBinType index column: 'fd(1)', 'fdr(2)', and 'ifdv(3)'.

         Rows are destroyed in this table when the corresponding
         tmnxOamPmStsBaseTable row is destroyed.

         When a test is running, the DMM statistics for a test's raw (i.e.
         'miRaw(1)') measurement interval duration can be cleared using
         TIMETRA-CLEAR-MIB::tmnxClearAction and tmnxClearParams.  A successful
         clear operation zeros all the raw DMM statistics for the specified
         session."
    INDEX       {
        tmnxOamPmCfgSessName,
        tmnxOamPmStsMeasIntvlDuration,
        tmnxOamPmStsIntvlNum,
        tmnxOamPmCfgBinType
    }
    ::= { tmnxOamPmStsDelayDmmTable 1 }

TmnxOamPmStsDelayDmmEntry        ::= SEQUENCE
{
    tmnxOamPmStsDelayDmmFwdMin       Unsigned32,
    tmnxOamPmStsDelayDmmFwdMax       Unsigned32,
    tmnxOamPmStsDelayDmmFwdAvg       Unsigned32,
    tmnxOamPmStsDelayDmmBwdMin       Unsigned32,
    tmnxOamPmStsDelayDmmBwdMax       Unsigned32,
    tmnxOamPmStsDelayDmmBwdAvg       Unsigned32,
    tmnxOamPmStsDelayDmm2wyMin       Unsigned32,
    tmnxOamPmStsDelayDmm2wyMax       Unsigned32,
    tmnxOamPmStsDelayDmm2wyAvg       Unsigned32
}

tmnxOamPmStsDelayDmmFwdMin       OBJECT-TYPE
    SYNTAX      Unsigned32
    UNITS       "microseconds"
    MAX-ACCESS  read-only
    STATUS      current
    DESCRIPTION
        "The value of tmnxOamPmStsDelayDmmFwdMin indicates the minimum delay in
         the forward direction for the specified session, interval duration
         (e.g. 'mi15Minutes(2)'), interval number, and bin type (e.g. 'fd(1)')."
    ::= { tmnxOamPmStsDelayDmmEntry 1 }

tmnxOamPmStsDelayDmmFwdMax       OBJECT-TYPE
    SYNTAX      Unsigned32
    UNITS       "microseconds"
    MAX-ACCESS  read-only
    STATUS      current
    DESCRIPTION
        "The value of tmnxOamPmStsDelayDmmFwdMax indicates the maximum delay in
         the forward direction for the specified session, interval duration
         (e.g. 'mi15Minutes(2)'), interval number, and bin type (e.g. 'fd(1)')."
    ::= { tmnxOamPmStsDelayDmmEntry 2 }

tmnxOamPmStsDelayDmmFwdAvg       OBJECT-TYPE
    SYNTAX      Unsigned32
    UNITS       "microseconds"
    MAX-ACCESS  read-only
    STATUS      current
    DESCRIPTION
        "The value of tmnxOamPmStsDelayDmmFwdAvg indicates the average delay in
         the forward direction for the specified session, interval duration
         (e.g. 'mi15Minutes(2)'), interval number, and bin type (e.g. 'fd(1)')."
    ::= { tmnxOamPmStsDelayDmmEntry 3 }

tmnxOamPmStsDelayDmmBwdMin       OBJECT-TYPE
    SYNTAX      Unsigned32
    UNITS       "microseconds"
    MAX-ACCESS  read-only
    STATUS      current
    DESCRIPTION
        "The value of tmnxOamPmStsDelayDmmBwdMin indicates the minimum delay in
         the backward direction for the specified session, interval duration
         (e.g. 'mi15Minutes(2)'), interval number, and bin type (e.g. 'fd(1)')."
    ::= { tmnxOamPmStsDelayDmmEntry 4 }

tmnxOamPmStsDelayDmmBwdMax       OBJECT-TYPE
    SYNTAX      Unsigned32
    UNITS       "microseconds"
    MAX-ACCESS  read-only
    STATUS      current
    DESCRIPTION
        "The value of tmnxOamPmStsDelayDmmBwdMax indicates the maximum delay in
         the backward direction for the specified session, interval duration
         (e.g. 'mi15Minutes(2)'), interval number, and bin type (e.g. 'fd(1)')."
    ::= { tmnxOamPmStsDelayDmmEntry 5 }

tmnxOamPmStsDelayDmmBwdAvg       OBJECT-TYPE
    SYNTAX      Unsigned32
    UNITS       "microseconds"
    MAX-ACCESS  read-only
    STATUS      current
    DESCRIPTION
        "The value of tmnxOamPmStsDelayDmmBwdAvg indicates the average delay in
         the backward direction for the specified session, interval duration
         (e.g. 'mi15Minutes(2)'), interval number, and bin type (e.g. 'fd(1)')."
    ::= { tmnxOamPmStsDelayDmmEntry 6 }

tmnxOamPmStsDelayDmm2wyMin       OBJECT-TYPE
    SYNTAX      Unsigned32
    UNITS       "microseconds"
    MAX-ACCESS  read-only
    STATUS      current
    DESCRIPTION
        "The value of tmnxOamPmStsDelayDmm2wyMin indicates the minimum two-way
         delay for the specified session, interval duration (e.g.
         'mi15Minutes(2)'), interval number, and bin type (e.g. 'fd(1)')."
    ::= { tmnxOamPmStsDelayDmmEntry 7 }

tmnxOamPmStsDelayDmm2wyMax       OBJECT-TYPE
    SYNTAX      Unsigned32
    UNITS       "microseconds"
    MAX-ACCESS  read-only
    STATUS      current
    DESCRIPTION
        "The value of tmnxOamPmStsDelayDmm2wyMax indicates the maximum two-way
         delay for the specified session, interval duration (e.g.
         'mi15Minutes(2)'), interval number, and bin type (e.g. 'fd(1)')."
    ::= { tmnxOamPmStsDelayDmmEntry 8 }

tmnxOamPmStsDelayDmm2wyAvg       OBJECT-TYPE
    SYNTAX      Unsigned32
    UNITS       "microseconds"
    MAX-ACCESS  read-only
    STATUS      current
    DESCRIPTION
        "The value of tmnxOamPmStsDelayDmm2wyAvg indicates the average two-way
         delay for the specified session, interval duration (e.g.
         'mi15Minutes(2)'), interval number, and bin type (e.g. 'fd(1)')."
    ::= { tmnxOamPmStsDelayDmmEntry 9 }

tmnxOamPmStsDelayDmmBinTable     OBJECT-TYPE
    SYNTAX      SEQUENCE OF TmnxOamPmStsDelayDmmBinEntry
    MAX-ACCESS  not-accessible
    STATUS      current
    DESCRIPTION
        "tmnxOamPmStsDelayDmmBinTable contains the per-bin DMM (Delay
         Measurement Message) statistics for OAM Performance Monitoring
         Measurement Interval Data Sets."
    REFERENCE
        "MEF-35, 'Service OAM Performance Monitoring Implementation Agreement',
         Metro Ethernet Forum, April 2012, Section 10.1, 'Single-Ended Delay
         Function for Delay, Frame Delay Range, and Inter Delay Variation'."
    ::= { tmnxOamPmStatsTableObjs 5 }

tmnxOamPmStsDelayDmmBinEntry     OBJECT-TYPE
    SYNTAX      TmnxOamPmStsDelayDmmBinEntry
    MAX-ACCESS  not-accessible
    STATUS      current
    DESCRIPTION
        "tmnxOamPmStsDelayDmmBinEntry contains the per-bin DMM (Delay
         Measurement Message) statistics for one OAM Performance Monitoring
         Measurement Interval Data Set.

         Rows are created in this table when a corresponding row is created in
         tmnxOamPmStsDelayDmmTable.  If the tmnxOamPmStsDelayDmmTable row is
         created with the index value tmnxOamPmCfgBinType = 'fd(1)', then the
         the number of rows created in this table is
         tmnxOamPmCfgBinGroupFdBinCount.  Similarly, 'fdr(2)' and 'ifdv(3)'.

         Rows are destroyed in this table when the corresponding
         tmnxOamPmStsDelayDmmTable row is destroyed.

         When a test is running, the DMM statistics for a test's raw (i.e.
         'miRaw(1)') measurement interval duration can be cleared using
         TIMETRA-CLEAR-MIB::tmnxClearAction and tmnxClearParams.  A successful
         clear operation zeros all the raw DMM statistics for the specified
         session."
    INDEX       {
        tmnxOamPmCfgSessName,
        tmnxOamPmStsMeasIntvlDuration,
        tmnxOamPmStsIntvlNum,
        tmnxOamPmCfgBinType,
        tmnxOamPmStsDelayDmmBinNum
    }
    ::= { tmnxOamPmStsDelayDmmBinTable 1 }

TmnxOamPmStsDelayDmmBinEntry     ::= SEQUENCE
{
    tmnxOamPmStsDelayDmmBinNum       Unsigned32,
    tmnxOamPmStsDelayDmmBinFwdCount  Unsigned32,
    tmnxOamPmStsDelayDmmBinBwdCount  Unsigned32,
    tmnxOamPmStsDelayDmmBin2wyCount  Unsigned32
}

tmnxOamPmStsDelayDmmBinNum       OBJECT-TYPE
    SYNTAX      Unsigned32 (0..9)
    MAX-ACCESS  not-accessible
    STATUS      current
    DESCRIPTION
        "The value of tmnxOamPmStsDelayDmmBinNum specifies the bin number of
         the statistics to be read."
    ::= { tmnxOamPmStsDelayDmmBinEntry 1 }

tmnxOamPmStsDelayDmmBinFwdCount  OBJECT-TYPE
    SYNTAX      Unsigned32
    MAX-ACCESS  read-only
    STATUS      current
    DESCRIPTION
        "The value of tmnxOamPmStsDelayDmmBinFwdCount indicates the number of
         measurements in the forward direction that fall within the configured
         range (in microseconds) of the specified bin.

         For example, suppose the index values for this object are as follows
         (where the index names are abbreviated, and index columns are
         underlined with octothorpes).

         _SessName   _IntvlDuration    _IntvlNum  _BinType  _BinNum
         ##########  ################  #########  ########  #######
         'dmmSess1'  'mi15Minutes(2)'          1  'fd(1)'         9

         Then, the value of this object indicates the number of DMM
         measurements (in microseconds) in the forward direction in the first
         interval of 'dmmSess1' that fit in the highest configured delay range
         (as configured using tmnxOamPmCfgBinLowerBound)."
    ::= { tmnxOamPmStsDelayDmmBinEntry 2 }

tmnxOamPmStsDelayDmmBinBwdCount  OBJECT-TYPE
    SYNTAX      Unsigned32
    MAX-ACCESS  read-only
    STATUS      current
    DESCRIPTION
        "The value of tmnxOamPmStsDelayDmmBinBwdCount indicates the number of
         measurements in the backward direction that fall within the configured
         range (in microseconds) of the specified bin.

         For example, suppose the index values for this object are as follows
         (where the index names are abbreviated, and index columns are
         underlined with octothorpes).

         _SessName   _IntvlDuration    _IntvlNum  _BinType  _BinNum
         ##########  ################  #########  ########  #######
         'dmmSess1'  'mi15Minutes(2)'          1  'fd(1)'         0

         Then, the value of this object indicates the number of DMM
         measurements (in microseconds) in the backward direction in the first
         interval of 'dmmSess1' that fit in the lowest configured delay range
         (as configured using tmnxOamPmCfgBinLowerBound)."
    ::= { tmnxOamPmStsDelayDmmBinEntry 3 }

tmnxOamPmStsDelayDmmBin2wyCount  OBJECT-TYPE
    SYNTAX      Unsigned32
    MAX-ACCESS  read-only
    STATUS      current
    DESCRIPTION
        "The value of tmnxOamPmStsDelayDmmBin2wyCount indicates the number of
         two-way measurements that fall within the configured range (in
         microseconds) of the specified bin.

         For example, suppose the index values for this object are as follows
         (where the index names are abbreviated, and index columns are
         underlined with octothorpes).

         _SessName   _IntvlDuration    _IntvlNum  _BinType  _BinNum
         ##########  ################  #########  ########  #######
         'dmmSess1'  'mi15Minutes(2)'          1  'fd(1)'         0

         Then, the value of this object indicates the number of two-way DMM
         measurements (in microseconds) in the first interval of 'dmmSess1'
         that fit in the lowest configured delay range (as configured using
         tmnxOamPmCfgBinLowerBound)."
    ::= { tmnxOamPmStsDelayDmmBinEntry 4 }

tmnxOamPmStsTwlRflTable          OBJECT-TYPE
    SYNTAX      SEQUENCE OF TmnxOamPmStsTwlRflEntry
    MAX-ACCESS  not-accessible
    STATUS      current
    DESCRIPTION
        "tmnxOamPmStsTwlRflTable contains the statistics for OAM Performance
         Monitoring TWAMP-Light reflectors."
    ::= { tmnxOamPmStatsTableObjs 6 }

tmnxOamPmStsTwlRflEntry          OBJECT-TYPE
    SYNTAX      TmnxOamPmStsTwlRflEntry
    MAX-ACCESS  not-accessible
    STATUS      current
    DESCRIPTION
        "tmnxOamPmStsTwlRflEntry contains the statistics for the specified OAM
         Performance Monitoring TWAMP-Light reflector.

         SROS creates a row in this table when a corresponding row is created
         in tmnxOamPmCfgTwlRflTable.

         SROS destroys a row in this table when a corresponding row is
         destroyed in tmnxOamPmCfgTwlRflTable.

         The encoding of the index is explained in the DESCRIPTION clause for
         tmnxOamPmCfgTwlRflEntry."
    AUGMENTS    { tmnxOamPmCfgTwlRflEntry }
    ::= { tmnxOamPmStsTwlRflTable 1 }

TmnxOamPmStsTwlRflEntry          ::= SEQUENCE
{
    tmnxOamPmStsTwlRflUpTime         Unsigned32,
    tmnxOamPmStsTwlRflFramesRx       Unsigned32,
    tmnxOamPmStsTwlRflFramesTx       Unsigned32
}

tmnxOamPmStsTwlRflUpTime         OBJECT-TYPE
    SYNTAX      Unsigned32
    UNITS       "seconds"
    MAX-ACCESS  read-only
    STATUS      current
    DESCRIPTION
        "The value of tmnxOamPmStsTwlRflUpTime indicates the time elapsed since
         the most recent transition of the reflector's administrative status to
         'enabled(1)'.

         Zero is returned if the reflector's administrative status is
         'disabled(2)'."
    ::= { tmnxOamPmStsTwlRflEntry 1 }

tmnxOamPmStsTwlRflFramesRx       OBJECT-TYPE
    SYNTAX      Unsigned32
    MAX-ACCESS  read-only
    STATUS      current
    DESCRIPTION
        "The value of tmnxOamPmStsTwlRflFramesRx indicates the number of
         TWAMP-Test frames received by the specified reflector."
    ::= { tmnxOamPmStsTwlRflEntry 2 }

tmnxOamPmStsTwlRflFramesTx       OBJECT-TYPE
    SYNTAX      Unsigned32
    MAX-ACCESS  read-only
    STATUS      current
    DESCRIPTION
        "The value of tmnxOamPmStsTwlRflFramesTx indicates the number of
         TWAMP-Test frames transmitted by the specified reflector."
    ::= { tmnxOamPmStsTwlRflEntry 3 }

tmnxOamPmStsDelayTwlTable        OBJECT-TYPE
    SYNTAX      SEQUENCE OF TmnxOamPmStsDelayTwlEntry
    MAX-ACCESS  not-accessible
    STATUS      current
    DESCRIPTION
        "tmnxOamPmStsDelayTwlTable contains TWAMP-Light (Two-Way Active
         Measurement Protocol, Light) frame delay summary statistics.  The frame
         delay summary statistics kept for TWAMP-Light tests are the same as the
         frame delay summary statistics specified for Ethernet DMM (Delay
         Measurement Message) tests in MEF-35 requirement R66."
    REFERENCE
        "MEF-35, 'Service OAM Performance Monitoring Implementation Agreement',
         Metro Ethernet Forum, April 2012, Section 10.1, 'Single-Ended Delay
         Function for Delay, Frame Delay Range, and Inter Delay Variation',
         requirement R66.
         RFC 5357, 'A Two-Way Active Measurement Protocol (TWAMP)', Appendix I,
         'TWAMP Light'."
    ::= { tmnxOamPmStatsTableObjs 7 }

tmnxOamPmStsDelayTwlEntry        OBJECT-TYPE
    SYNTAX      TmnxOamPmStsDelayTwlEntry
    MAX-ACCESS  not-accessible
    STATUS      current
    DESCRIPTION
        "tmnxOamPmStsDelayTwlEntry contains the TWAMP-Light frame delay summary
         statistics for one OAM Performance Monitoring Measurement Interval
         Data Set.

         When a row is created in tmnxOamPmStsBaseTable with
         tmnxOamPmStsBaseTestType = 'twampLight(3)' (provided
         tmnxOamPmCfgTwampLtCollectStats is 'collectDelayStats(1)' or
         'collectDelayAndLossStats(3)'), three rows are created in this table.
         The three rows have the following values in the tmnxOamPmCfgBinType
         index column: 'fd(1)', 'fdr(2)', and 'ifdv(3)'.

         Rows are destroyed in this table when the corresponding
         tmnxOamPmStsBaseTable row is destroyed.

         When a TWAMP-Light test is running, all the test's raw statistics can
         be cleared using TIMETRA-CLEAR-MIB::tmnxClearAction and
         tmnxClearParams.  A successful clear operation zeros the TWAMP-Light
         delay and TWAMP-Light loss raw statistics for the specified session."
    REFERENCE
        "MEF-35, 'Service OAM Performance Monitoring Implementation Agreement',
         Metro Ethernet Forum, April 2012, Section 9.2.1 'Measurement Interval
         Data Sets'."
    INDEX       {
        tmnxOamPmCfgSessName,
        tmnxOamPmStsMeasIntvlDuration,
        tmnxOamPmStsIntvlNum,
        tmnxOamPmCfgBinType
    }
    ::= { tmnxOamPmStsDelayTwlTable 1 }

TmnxOamPmStsDelayTwlEntry        ::= SEQUENCE
{
    tmnxOamPmStsDelayTwlFwdMin       Unsigned32,
    tmnxOamPmStsDelayTwlFwdMax       Unsigned32,
    tmnxOamPmStsDelayTwlFwdAvg       Unsigned32,
    tmnxOamPmStsDelayTwlBwdMin       Unsigned32,
    tmnxOamPmStsDelayTwlBwdMax       Unsigned32,
    tmnxOamPmStsDelayTwlBwdAvg       Unsigned32,
    tmnxOamPmStsDelayTwl2wyMin       Unsigned32,
    tmnxOamPmStsDelayTwl2wyMax       Unsigned32,
    tmnxOamPmStsDelayTwl2wyAvg       Unsigned32
}

tmnxOamPmStsDelayTwlFwdMin       OBJECT-TYPE
    SYNTAX      Unsigned32
    UNITS       "microseconds"
    MAX-ACCESS  read-only
    STATUS      current
    DESCRIPTION
        "The value of tmnxOamPmStsDelayTwlFwdMin indicates the minimum delay in
         the forward direction for the specified session, interval duration
         (e.g. 'mi15Minutes(2)'), interval number, and bin type (e.g. 'fd(1)')."
    ::= { tmnxOamPmStsDelayTwlEntry 1 }

tmnxOamPmStsDelayTwlFwdMax       OBJECT-TYPE
    SYNTAX      Unsigned32
    UNITS       "microseconds"
    MAX-ACCESS  read-only
    STATUS      current
    DESCRIPTION
        "The value of tmnxOamPmStsDelayTwlFwdMax indicates the maximum delay in
         the forward direction for the specified session, interval duration
         (e.g. 'mi15Minutes(2)'), interval number, and bin type (e.g. 'fd(1)')."
    ::= { tmnxOamPmStsDelayTwlEntry 2 }

tmnxOamPmStsDelayTwlFwdAvg       OBJECT-TYPE
    SYNTAX      Unsigned32
    UNITS       "microseconds"
    MAX-ACCESS  read-only
    STATUS      current
    DESCRIPTION
        "The value of tmnxOamPmStsDelayTwlFwdAvg indicates the average delay in
         the forward direction for the specified session, interval duration
         (e.g. 'mi15Minutes(2)'), interval number, and bin type (e.g. 'fd(1)')."
    ::= { tmnxOamPmStsDelayTwlEntry 3 }

tmnxOamPmStsDelayTwlBwdMin       OBJECT-TYPE
    SYNTAX      Unsigned32
    UNITS       "microseconds"
    MAX-ACCESS  read-only
    STATUS      current
    DESCRIPTION
        "The value of tmnxOamPmStsDelayTwlBwdMin indicates the minimum delay in
         the backward direction for the specified session, interval duration
         (e.g. 'mi15Minutes(2)'), interval number, and bin type (e.g. 'fd(1)')."
    ::= { tmnxOamPmStsDelayTwlEntry 4 }

tmnxOamPmStsDelayTwlBwdMax       OBJECT-TYPE
    SYNTAX      Unsigned32
    UNITS       "microseconds"
    MAX-ACCESS  read-only
    STATUS      current
    DESCRIPTION
        "The value of tmnxOamPmStsDelayTwlBwdMax indicates the maximum delay in
         the backward direction for the specified session, interval duration
         (e.g. 'mi15Minutes(2)'), interval number, and bin type (e.g. 'fd(1)')."
    ::= { tmnxOamPmStsDelayTwlEntry 5 }

tmnxOamPmStsDelayTwlBwdAvg       OBJECT-TYPE
    SYNTAX      Unsigned32
    UNITS       "microseconds"
    MAX-ACCESS  read-only
    STATUS      current
    DESCRIPTION
        "The value of tmnxOamPmStsDelayTwlBwdAvg indicates the average delay in
         the backward direction for the specified session, interval duration
         (e.g. 'mi15Minutes(2)'), interval number, and bin type (e.g. 'fd(1)')."
    ::= { tmnxOamPmStsDelayTwlEntry 6 }

tmnxOamPmStsDelayTwl2wyMin       OBJECT-TYPE
    SYNTAX      Unsigned32
    UNITS       "microseconds"
    MAX-ACCESS  read-only
    STATUS      current
    DESCRIPTION
        "The value of tmnxOamPmStsDelayTwl2wyMin indicates the minimum two-way
         delay for the specified session, interval duration (e.g.
         'mi15Minutes(2)'), interval number, and bin type (e.g. 'fd(1)')."
    ::= { tmnxOamPmStsDelayTwlEntry 7 }

tmnxOamPmStsDelayTwl2wyMax       OBJECT-TYPE
    SYNTAX      Unsigned32
    UNITS       "microseconds"
    MAX-ACCESS  read-only
    STATUS      current
    DESCRIPTION
        "The value of tmnxOamPmStsDelayTwl2wyMax indicates the maximum two-way
         delay for the specified session, interval duration (e.g.
         'mi15Minutes(2)'), interval number, and bin type (e.g. 'fd(1)')."
    ::= { tmnxOamPmStsDelayTwlEntry 8 }

tmnxOamPmStsDelayTwl2wyAvg       OBJECT-TYPE
    SYNTAX      Unsigned32
    UNITS       "microseconds"
    MAX-ACCESS  read-only
    STATUS      current
    DESCRIPTION
        "The value of tmnxOamPmStsDelayTwl2wyAvg indicates the average two-way
         delay for the specified session, interval duration (e.g.
         'mi15Minutes(2)'), interval number, and bin type (e.g. 'fd(1)')."
    ::= { tmnxOamPmStsDelayTwlEntry 9 }

tmnxOamPmStsDelayTwlBinTable     OBJECT-TYPE
    SYNTAX      SEQUENCE OF TmnxOamPmStsDelayTwlBinEntry
    MAX-ACCESS  not-accessible
    STATUS      current
    DESCRIPTION
        "tmnxOamPmStsDelayTwlBinTable contains TWAMP-Light (Two-Way Active
         Measurement Protocol, Light) frame delay per-bin statistics.  The frame
         delay per-bin statistics kept for TWAMP-Light tests are the same as the
         frame delay per-bin statistics specified for Ethernet DMM (Delay
         Measurement Message) tests in MEF-35 requirement R66."
    REFERENCE
        "MEF-35, 'Service OAM Performance Monitoring Implementation Agreement',
         Metro Ethernet Forum, April 2012, Section 10.1, 'Single-Ended Delay
         Function for Delay, Frame Delay Range, and Inter Delay Variation',
         requirement R66.
         RFC 5357, 'A Two-Way Active Measurement Protocol (TWAMP)', Appendix I,
         'TWAMP Light'."
    ::= { tmnxOamPmStatsTableObjs 8 }

tmnxOamPmStsDelayTwlBinEntry     OBJECT-TYPE
    SYNTAX      TmnxOamPmStsDelayTwlBinEntry
    MAX-ACCESS  not-accessible
    STATUS      current
    DESCRIPTION
        "tmnxOamPmStsDelayTwlBinEntry contains the TWAMP-Light frame delay
         per-bin statistics for one OAM Performance Monitoring Measurement
         Interval Data Set.

         Rows are created in this table when a corresponding row is created in
         tmnxOamPmStsDelayTwlTable.  If the tmnxOamPmStsDelayTwlTable row is
         created with the index value tmnxOamPmCfgBinType = 'fd(1)', then the
         the number of rows created in this table is
         tmnxOamPmCfgBinGroupFdBinCount.  Similarly, 'fdr(2)' and 'ifdv(3)'.

         Rows are destroyed in this table when the corresponding
         tmnxOamPmStsDelayTwlTable row is destroyed.

         When a test is running, the TWAMP-Light statistics for a test's raw
         (i.e.  'miRaw(1)') measurement interval duration can be cleared using
         TIMETRA-CLEAR-MIB::tmnxClearAction and tmnxClearParams.  A successful
         clear operation zeros the TWAMP-Light delay and TWAMP-Light loss raw
         statistics for the specified session.."
    REFERENCE
        "MEF-35, 'Service OAM Performance Monitoring Implementation Agreement',
         Metro Ethernet Forum, April 2012, Section 9.2.1 'Measurement Interval
         Data Sets'."
    INDEX       {
        tmnxOamPmCfgSessName,
        tmnxOamPmStsMeasIntvlDuration,
        tmnxOamPmStsIntvlNum,
        tmnxOamPmCfgBinType,
        tmnxOamPmStsDelayTwlBinNum
    }
    ::= { tmnxOamPmStsDelayTwlBinTable 1 }

TmnxOamPmStsDelayTwlBinEntry     ::= SEQUENCE
{
    tmnxOamPmStsDelayTwlBinNum       Unsigned32,
    tmnxOamPmStsDelayTwlBinFwdCount  Unsigned32,
    tmnxOamPmStsDelayTwlBinBwdCount  Unsigned32,
    tmnxOamPmStsDelayTwlBin2wyCount  Unsigned32
}

tmnxOamPmStsDelayTwlBinNum       OBJECT-TYPE
    SYNTAX      Unsigned32 (0..9)
    MAX-ACCESS  not-accessible
    STATUS      current
    DESCRIPTION
        "The value of tmnxOamPmStsDelayTwlBinNum specifies the bin number of
         the statistics to be read."
    ::= { tmnxOamPmStsDelayTwlBinEntry 1 }

tmnxOamPmStsDelayTwlBinFwdCount  OBJECT-TYPE
    SYNTAX      Unsigned32
    MAX-ACCESS  read-only
    STATUS      current
    DESCRIPTION
        "The value of tmnxOamPmStsDelayTwlBinFwdCount indicates the number of
         TWAMP-Light frame delay measurements in the forward direction that
         fall within the configured range (in microseconds) of the specified
         bin.

         For example, suppose the index values for this object are as follows
         (where the index names are abbreviated, and index columns are
         underlined with octothorpes).

         _SessName   _IntvlDuration    _IntvlNum  _BinType  _BinNum
         ##########  ################  #########  ########  #######
         'twlSess1'  'mi15Minutes(2)'          1  'fd(1)'         9

         Then, the value of this object indicates the number of TWAMP-Light
         frame delay measurements (in microseconds) in the forward direction in
         the first interval of 'twlSess1' that fit in the highest configured
         delay range (as configured using tmnxOamPmCfgBinLowerBound)."
    ::= { tmnxOamPmStsDelayTwlBinEntry 2 }

tmnxOamPmStsDelayTwlBinBwdCount  OBJECT-TYPE
    SYNTAX      Unsigned32
    MAX-ACCESS  read-only
    STATUS      current
    DESCRIPTION
        "The value of tmnxOamPmStsDelayTwlBinBwdCount indicates the number of
         TWAMP-Light frame delay measurements in the backward direction that
         fall within the configured range (in microseconds) of the specified
         bin.

         For example, suppose the index values for this object are as follows
         (where the index names are abbreviated, and index columns are
         underlined with octothorpes).

         _SessName   _IntvlDuration    _IntvlNum  _BinType  _BinNum
         ##########  ################  #########  ########  #######
         'twlSess1'  'mi15Minutes(2)'          1  'fd(1)'         0

         Then, the value of this object indicates the number of TWAMP-Light
         frame delay measurements (in microseconds) in the backward direction
         in the first interval of 'twlSess1' that fit in the lowest configured
         delay range (as configured using tmnxOamPmCfgBinLowerBound)."
    ::= { tmnxOamPmStsDelayTwlBinEntry 3 }

tmnxOamPmStsDelayTwlBin2wyCount  OBJECT-TYPE
    SYNTAX      Unsigned32
    MAX-ACCESS  read-only
    STATUS      current
    DESCRIPTION
        "The value of tmnxOamPmStsDelayTwlBin2wyCount indicates the number of
         TWAMP-Light two-way frame delay measurements that fall within the
         configured range (in microseconds) of the specified bin.

         For example, suppose the index values for this object are as follows
         (where the index names are abbreviated, and index columns are
         underlined with octothorpes).

         _SessName   _IntvlDuration    _IntvlNum  _BinType  _BinNum
         ##########  ################  #########  ########  #######
         'twlSess1'  'mi15Minutes(2)'          1  'fd(1)'         0

         Then, the value of this object indicates the number of TWAMP-Light
         two-way frame delay measurements (in microseconds) in the first
         interval of 'twlSess1' that fit in the lowest configured delay range
         (as configured using tmnxOamPmCfgBinLowerBound)."
    ::= { tmnxOamPmStsDelayTwlBinEntry 4 }

tmnxOamPmStsLossLmmTable         OBJECT-TYPE
    SYNTAX      SEQUENCE OF TmnxOamPmStsLossLmmEntry
    MAX-ACCESS  not-accessible
    STATUS      current
    DESCRIPTION
        "tmnxOamPmStsLossLmmTable contains the frame loss statistics for OAM
         Performance Monitoring LMM (Loss Measurement Message) tests."
    REFERENCE
        "ITU-T G.8013/Y.1731, 'OAM functions and mechanisms for Ethernet based
         networks', 07/2011, Section 8.1 'Frame loss measurement (ETH-LM)'.
         MEF-35, 'Service OAM Performance Monitoring Implementation Agreement',
         Metro Ethernet Forum, April 2012, Section 12.1 'Single-Ended Service
         Loss Function'."
    ::= { tmnxOamPmStatsTableObjs 9 }

tmnxOamPmStsLossLmmEntry         OBJECT-TYPE
    SYNTAX      TmnxOamPmStsLossLmmEntry
    MAX-ACCESS  not-accessible
    STATUS      current
    DESCRIPTION
        "tmnxOamPmStsLossLmmEntry contains the LMM test statistics for one OAM
         Performance Monitoring Measurement Interval Data Set.

         A row is created in this table when a tmnxOamPmStsBaseTable row is
         created with tmnxOamPmStsBaseTestType = 'lmm(4)'.

         A row is destroyed in this table when the corresponding
         tmnxOamPmStsBaseTable row is destroyed.

         The following objects are modelled after the MEF-35 loss parameters
         defined for Synthetic Loss Measurement (SLM) tests:
            tmnxOamPmStsLossLmmAvailIndBwd,
            tmnxOamPmStsLossLmmAvailIndFwd,
            tmnxOamPmStsLossLmmChliBwd,
            tmnxOamPmStsLossLmmChliFwd,
            tmnxOamPmStsLossLmmHliBwd,
            tmnxOamPmStsLossLmmHliFwd,
            tmnxOamPmStsLossLmmUnavlIndBwd, and
            tmnxOamPmStsLossLmmUnavlIndFwd.
         Hence, the REFERENCE text for this object is a MEF-35 SLM section.

         The value of tmnxOamPmCfgLossLmmAvAdminStatus controls the value of
         several objects in this table.  See the
         tmnxOamPmCfgLossLmmAvAdminStatus DESCRIPTION clause for more
         information.

         When a test is running, the LMM statistics for a test's raw (i.e.
         'miRaw(1)') measurement interval duration can be cleared using
         TIMETRA-CLEAR-MIB::tmnxClearAction and tmnxClearParams.  A successful
         clear operation zeros all raw LMM statistics for the specified
         session."
    REFERENCE
        "MEF-35, 'Service OAM Performance Monitoring Implementation Agreement',
         Metro Ethernet Forum, April 2012, Section 10.2, 'Single-Ended Synthetic
         Loss Function for Frame Loss Ratio (FLR) and Availability'."
    INDEX       {
        tmnxOamPmCfgSessName,
        tmnxOamPmStsMeasIntvlDuration,
        tmnxOamPmStsIntvlNum
    }
    ::= { tmnxOamPmStsLossLmmTable 1 }

TmnxOamPmStsLossLmmEntry         ::= SEQUENCE
{
    tmnxOamPmStsLossLmmTxFwd         Counter64,
    tmnxOamPmStsLossLmmRxFwd         Counter64,
    tmnxOamPmStsLossLmmTxBwd         Counter64,
    tmnxOamPmStsLossLmmRxBwd         Counter64,
    tmnxOamPmStsLossLmmMinFlrFwd     Unsigned32,
    tmnxOamPmStsLossLmmMaxFlrFwd     Unsigned32,
    tmnxOamPmStsLossLmmAvgFlrFwd     Unsigned32,
    tmnxOamPmStsLossLmmMinFlrBwd     Unsigned32,
    tmnxOamPmStsLossLmmMaxFlrBwd     Unsigned32,
    tmnxOamPmStsLossLmmAvgFlrBwd     Unsigned32,
    tmnxOamPmStsLossLmmAvailIndFwd   Counter32,
    tmnxOamPmStsLossLmmAvailIndBwd   Counter32,
    tmnxOamPmStsLossLmmUnavlIndFwd   Counter32,
    tmnxOamPmStsLossLmmUnavlIndBwd   Counter32,
    tmnxOamPmStsLossLmmUndtAvlFwd    Counter32,
    tmnxOamPmStsLossLmmUndtUnavlFwd  Counter32,
    tmnxOamPmStsLossLmmUndtAvlBwd    Counter32,
    tmnxOamPmStsLossLmmUndtUnavlBwd  Counter32,
    tmnxOamPmStsLossLmmHliFwd        Counter32,
    tmnxOamPmStsLossLmmHliBwd        Counter32,
    tmnxOamPmStsLossLmmChliFwd       Counter32,
    tmnxOamPmStsLossLmmChliBwd       Counter32,
    tmnxOamPmStsLossLmmUndetDelTsFwd Counter32,
    tmnxOamPmStsLossLmmUndetDelTsBwd Counter32
}

tmnxOamPmStsLossLmmTxFwd         OBJECT-TYPE
    SYNTAX      Counter64
    UNITS       "frames"
    MAX-ACCESS  read-only
    STATUS      current
    DESCRIPTION
        "The value of tmnxOamPmStsLossLmmTxFwd indicates the number of service
         frames transmitted in the forward direction for the specified
         measurement interval data set.

         This counter is computed using the procedures in Y.1731 Section 8.1."
    REFERENCE
        "ITU-T G.8013/Y.1731, 'OAM functions and mechanisms for Ethernet based
         networks', 07/2011, Section 8.1 'Frame loss measurement (ETH-LM)'.
         MEF-35, 'Service OAM Performance Monitoring Implementation Agreement',
         Metro Ethernet Forum, April 2012, Section 12.1 'Single-Ended Service
         Loss Function', R112."
    ::= { tmnxOamPmStsLossLmmEntry 1 }

tmnxOamPmStsLossLmmRxFwd         OBJECT-TYPE
    SYNTAX      Counter64
    UNITS       "frames"
    MAX-ACCESS  read-only
    STATUS      current
    DESCRIPTION
        "The value of tmnxOamPmStsLossLmmRxFwd indicates the number of service
         frames received in the forward direction for the specified measurement
         interval data set.

         This counter is computed using the procedures in Y.1731 Section 8.1."
    REFERENCE
        "ITU-T G.8013/Y.1731, 'OAM functions and mechanisms for Ethernet based
         networks', 07/2011, Section 8.1 'Frame loss measurement (ETH-LM)'.
         MEF-35, 'Service OAM Performance Monitoring Implementation Agreement',
         Metro Ethernet Forum, April 2012, Section 12.1 'Single-Ended Service
         Loss Function', R112."
    ::= { tmnxOamPmStsLossLmmEntry 2 }

tmnxOamPmStsLossLmmTxBwd         OBJECT-TYPE
    SYNTAX      Counter64
    UNITS       "frames"
    MAX-ACCESS  read-only
    STATUS      current
    DESCRIPTION
        "The value of tmnxOamPmStsLossLmmTxBwd indicates the number of service
         frames transmitted in the backward direction for the specified
         measurement interval data set.

         This counter is computed using the procedures in Y.1731 Section 8.1."
    REFERENCE
        "ITU-T G.8013/Y.1731, 'OAM functions and mechanisms for Ethernet based
         networks', 07/2011, Section 8.1 'Frame loss measurement (ETH-LM)'.
         MEF-35, 'Service OAM Performance Monitoring Implementation Agreement',
         Metro Ethernet Forum, April 2012, Section 12.1 'Single-Ended Service
         Loss Function', R112."
    ::= { tmnxOamPmStsLossLmmEntry 3 }

tmnxOamPmStsLossLmmRxBwd         OBJECT-TYPE
    SYNTAX      Counter64
    UNITS       "frames"
    MAX-ACCESS  read-only
    STATUS      current
    DESCRIPTION
        "The value of tmnxOamPmStsLossLmmRxBwd indicates the number of service
         frames received in the backward direction for the specified
         measurement interval data set.

         This counter is computed using the procedures in Y.1731 Section 8.1."
    REFERENCE
        "ITU-T G.8013/Y.1731, 'OAM functions and mechanisms for Ethernet based
         networks', 07/2011, Section 8.1 'Frame loss measurement (ETH-LM)'.
         MEF-35, 'Service OAM Performance Monitoring Implementation Agreement',
         Metro Ethernet Forum, April 2012, Section 12.1 'Single-Ended Service
         Loss Function', R112."
    ::= { tmnxOamPmStsLossLmmEntry 4 }

tmnxOamPmStsLossLmmMinFlrFwd     OBJECT-TYPE
    SYNTAX      Unsigned32 (0..100000)
    UNITS       "milli-percent"
    MAX-ACCESS  read-only
    STATUS      current
    DESCRIPTION
        "The value of tmnxOamPmStsLossLmmMinFlrFwd indicates the minimum Frame
         Loss Ratio (FLR) in the forward direction for the specified
         measurement interval data set.

         This value is computed using the procedures in Y.1731 Section 8.1."
    REFERENCE
        "ITU-T G.8013/Y.1731, 'OAM functions and mechanisms for Ethernet based
         networks', 07/2011, Section 8.1 'Frame loss measurement (ETH-LM)'."
    ::= { tmnxOamPmStsLossLmmEntry 5 }

tmnxOamPmStsLossLmmMaxFlrFwd     OBJECT-TYPE
    SYNTAX      Unsigned32 (0..100000)
    UNITS       "milli-percent"
    MAX-ACCESS  read-only
    STATUS      current
    DESCRIPTION
        "The value of tmnxOamPmStsLossLmmMaxFlrFwd indicates the maximum Frame
         Loss Ratio (FLR) in the forward direction for the specified
         measurement interval data set.

         This value is computed using the procedures in Y.1731 Section 8.1."
    REFERENCE
        "ITU-T G.8013/Y.1731, 'OAM functions and mechanisms for Ethernet based
         networks', 07/2011, Section 8.1 'Frame loss measurement (ETH-LM)'."
    ::= { tmnxOamPmStsLossLmmEntry 6 }

tmnxOamPmStsLossLmmAvgFlrFwd     OBJECT-TYPE
    SYNTAX      Unsigned32 (0..100000)
    UNITS       "milli-percent"
    MAX-ACCESS  read-only
    STATUS      current
    DESCRIPTION
        "The value of tmnxOamPmStsLossLmmAvgFlrFwd indicates the average Frame
         Loss Ratio (FLR) in the forward direction for the specified
         measurement interval data set.

         This value is computed using the procedures in Y.1731 Section 8.1."
    REFERENCE
        "ITU-T G.8013/Y.1731, 'OAM functions and mechanisms for Ethernet based
         networks', 07/2011, Section 8.1 'Frame loss measurement (ETH-LM)'."
    ::= { tmnxOamPmStsLossLmmEntry 7 }

tmnxOamPmStsLossLmmMinFlrBwd     OBJECT-TYPE
    SYNTAX      Unsigned32 (0..100000)
    UNITS       "milli-percent"
    MAX-ACCESS  read-only
    STATUS      current
    DESCRIPTION
        "The value of tmnxOamPmStsLossLmmMinFlrBwd indicates the minimum Frame
         Loss Ratio (FLR) in the backward direction for the specified
         measurement interval data set.

         This value is computed using the procedures in Y.1731 Section 8.1."
    REFERENCE
        "ITU-T G.8013/Y.1731, 'OAM functions and mechanisms for Ethernet based
         networks', 07/2011, Section 8.1 'Frame loss measurement (ETH-LM)'."
    ::= { tmnxOamPmStsLossLmmEntry 8 }

tmnxOamPmStsLossLmmMaxFlrBwd     OBJECT-TYPE
    SYNTAX      Unsigned32 (0..100000)
    UNITS       "milli-percent"
    MAX-ACCESS  read-only
    STATUS      current
    DESCRIPTION
        "The value of tmnxOamPmStsLossLmmMaxFlrBwd indicates the maximum Frame
         Loss Ratio (FLR) in the backward direction for the specified
         measurement interval data set.

         This value is computed using the procedures in Y.1731 Section 8.1."
    REFERENCE
        "ITU-T G.8013/Y.1731, 'OAM functions and mechanisms for Ethernet based
         networks', 07/2011, Section 8.1 'Frame loss measurement (ETH-LM)'."
    ::= { tmnxOamPmStsLossLmmEntry 9 }

tmnxOamPmStsLossLmmAvgFlrBwd     OBJECT-TYPE
    SYNTAX      Unsigned32 (0..100000)
    UNITS       "milli-percent"
    MAX-ACCESS  read-only
    STATUS      current
    DESCRIPTION
        "The value of tmnxOamPmStsLossLmmAvgFlrBwd indicates the average Frame
         Loss Ratio (FLR) in the backward direction for the specified
         measurement interval data set.

         This value is computed using the procedures in Y.1731 Section 8.1."
    REFERENCE
        "ITU-T G.8013/Y.1731, 'OAM functions and mechanisms for Ethernet based
         networks', 07/2011, Section 8.1 'Frame loss measurement (ETH-LM)'."
    ::= { tmnxOamPmStsLossLmmEntry 10 }

tmnxOamPmStsLossLmmAvailIndFwd   OBJECT-TYPE
    SYNTAX      Counter32
    MAX-ACCESS  read-only
    STATUS      current
    DESCRIPTION
        "The value of tmnxOamPmStsLossLmmAvailIndFwd indicates the number of
         availability indicators evaluated as Available in the forward
         direction for the specified measurement interval data set."
    ::= { tmnxOamPmStsLossLmmEntry 11 }

tmnxOamPmStsLossLmmAvailIndBwd   OBJECT-TYPE
    SYNTAX      Counter32
    MAX-ACCESS  read-only
    STATUS      current
    DESCRIPTION
        "The value of tmnxOamPmStsLossLmmAvailIndBwd indicates the number of
         availability indicators evaluated as Available in the backward
         direction for the specified measurement interval data set."
    ::= { tmnxOamPmStsLossLmmEntry 12 }

tmnxOamPmStsLossLmmUnavlIndFwd   OBJECT-TYPE
    SYNTAX      Counter32
    MAX-ACCESS  read-only
    STATUS      current
    DESCRIPTION
        "The value of tmnxOamPmStsLossLmmUnavlIndFwd indicates the number of
         availability indicators evaluated as Unavailable in the forward
         direction for the specified measurement interval data set."
    ::= { tmnxOamPmStsLossLmmEntry 13 }

tmnxOamPmStsLossLmmUnavlIndBwd   OBJECT-TYPE
    SYNTAX      Counter32
    MAX-ACCESS  read-only
    STATUS      current
    DESCRIPTION
        "The value of tmnxOamPmStsLossLmmUnavlIndBwd indicates the number of
         availability indicators evaluated as Unavailable in the backward
         direction for the specified measurement interval data set."
    ::= { tmnxOamPmStsLossLmmEntry 14 }

tmnxOamPmStsLossLmmUndtAvlFwd    OBJECT-TYPE
    SYNTAX      Counter32
    MAX-ACCESS  read-only
    STATUS      current
    DESCRIPTION
        "The value of tmnxOamPmStsLossLmmUndtAvlFwd indicates the number of
         availability indicators evaluated as Undetermined Available, in the
         forward direction.

         This counter is incremented when:
         1.  It is time to calculate an availability indicator, and
         2.  No Loss Measurement Replies (LMRs) have been received within the
         availability window, and
         3.  The most recently declared availability indicator in the forward
         direction was Available.

         In that case, the availability indicator is Undetermined Available
         because:
         1.  No information is available to indicate if the problem is in the
         forward direction or the backward direction, and
         2.  We extrapolate from the previous state (i.e. Available)."
    ::= { tmnxOamPmStsLossLmmEntry 15 }

tmnxOamPmStsLossLmmUndtUnavlFwd  OBJECT-TYPE
    SYNTAX      Counter32
    MAX-ACCESS  read-only
    STATUS      current
    DESCRIPTION
        "The value of tmnxOamPmStsLossLmmUndtUnavlFwd indicates the number of
         availability indicators evaluated as Undetermined Unavailable, in the
         forward direction.

         This counter is incremented when:
         1.  It is time to calculate an availability indicator, and
         2.  No Loss Measurement Replies (LMRs) have been received within the
         availability window, and
         3.  The most recently declared availability indicator in the forward
         direction was Unavailable.

         In that case, the availability indicator is Undetermined Unavailable
         because:
         1.  No information is available to indicate if the problem is in the
         forward direction or the backward direction, and
         2.  We extrapolate from the previous state (i.e. Unavailable)."
    ::= { tmnxOamPmStsLossLmmEntry 16 }

tmnxOamPmStsLossLmmUndtAvlBwd    OBJECT-TYPE
    SYNTAX      Counter32
    MAX-ACCESS  read-only
    STATUS      current
    DESCRIPTION
        "The value of tmnxOamPmStsLossLmmUndtAvlBwd indicates the number of
         availability indicators evaluated as Undetermined Available, in the
         backward direction.

         This counter is incremented when:
         1.  It is time to calculate an availability indicator, and
         2.  No Loss Measurement Replies (LMRs) have been received within the
         availability window, and
         3.  The most recently declared availability indicator in the backward
         direction was Available.

         In that case, the availability indicator is Undetermined Available
         because:
         1.  No information is available to indicate if the problem is in the
         forward direction or the backward direction, and
         2.  We extrapolate from the previous state (i.e. Available)."
    ::= { tmnxOamPmStsLossLmmEntry 17 }

tmnxOamPmStsLossLmmUndtUnavlBwd  OBJECT-TYPE
    SYNTAX      Counter32
    MAX-ACCESS  read-only
    STATUS      current
    DESCRIPTION
        "The value of tmnxOamPmStsLossLmmUndtUnavlBwd indicates the number of
         availability indicators evaluated as Undetermined Unavailable, in the
         backward direction.

         This counter is incremented when:
         1.  It is time to calculate an availability indicator, and
         2.  No Loss Measurement Replies (LMRs) have been received within the
         availability window, and
         3.  The most recently declared availability indicator in the backward
         direction was Unavailable.

         In that case, the availability indicator is Undetermined Unavailable
         because:
         1.  No information is available to indicate if the problem is in the
         forward direction or the backward direction, and
         2.  We extrapolate from the previous state (i.e. Unavailable)."
    ::= { tmnxOamPmStsLossLmmEntry 18 }

tmnxOamPmStsLossLmmHliFwd        OBJECT-TYPE
    SYNTAX      Counter32
    MAX-ACCESS  read-only
    STATUS      current
    DESCRIPTION
        "The value of tmnxOamPmStsLossLmmHliFwd indicates the number of High
         Loss Intervals (HLIs) in the forward direction for the specified
         measurement interval data set."
    ::= { tmnxOamPmStsLossLmmEntry 19 }

tmnxOamPmStsLossLmmHliBwd        OBJECT-TYPE
    SYNTAX      Counter32
    MAX-ACCESS  read-only
    STATUS      current
    DESCRIPTION
        "The value of tmnxOamPmStsLossLmmHliBwd indicates the number of High
         Loss Intervals (HLIs) in the backward direction for the specified
         measurement interval data set."
    ::= { tmnxOamPmStsLossLmmEntry 20 }

tmnxOamPmStsLossLmmChliFwd       OBJECT-TYPE
    SYNTAX      Counter32
    MAX-ACCESS  read-only
    STATUS      current
    DESCRIPTION
        "The value of tmnxOamPmStsLossLmmChliFwd indicates the number of
         Consecutive High Loss Intervals (CHLIs) in the forward direction for
         the specified measurement interval data set."
    ::= { tmnxOamPmStsLossLmmEntry 21 }

tmnxOamPmStsLossLmmChliBwd       OBJECT-TYPE
    SYNTAX      Counter32
    MAX-ACCESS  read-only
    STATUS      current
    DESCRIPTION
        "The value of tmnxOamPmStsLossLmmChliBwd indicates the number of
         Consecutive High Loss Intervals (CHLIs) in the backward direction for
         the specified measurement interval data set."
    ::= { tmnxOamPmStsLossLmmEntry 22 }

tmnxOamPmStsLossLmmUndetDelTsFwd OBJECT-TYPE
    SYNTAX      Counter32
    MAX-ACCESS  read-only
    STATUS      current
    DESCRIPTION
        "The value of tmnxOamPmStsLossLmmUndetDelTsFwd indicates the number of
         undetermined MEF-35 'delta_t's (also known as 'Small Time Intervals')
         for the forward direction for the specified measurement interval data
         set.

         An undetermined delta_t occurs when no Loss Measurement Reply (LMR)
         PDUs are received during the time interval.

         This counter is incremented because of a problem with the data path, or
         because the MEF-35 delta_t for this test is too short.  delta_t is
         configured using tmnxOamPmCfgLossLmmInterval and
         tmnxOamPmCfgLossLmmTxFrmsPerDelT."
    REFERENCE
        "MEF-35, 'Service OAM Performance Monitoring Implementation Agreement',
         Metro Ethernet Forum, April 2012, Section 6.3 'MEF 10.2.1'."
    ::= { tmnxOamPmStsLossLmmEntry 23 }

tmnxOamPmStsLossLmmUndetDelTsBwd OBJECT-TYPE
    SYNTAX      Counter32
    MAX-ACCESS  read-only
    STATUS      current
    DESCRIPTION
        "The value of tmnxOamPmStsLossLmmUndetDelTsBwd indicates the number of
         undetermined MEF-35 'delta_t's (also known as 'Small Time Intervals')
         for the backward direction for the specified measurement interval data
         set.

         An undetermined delta_t occurs when no Loss Measurement Reply (LMR)
         PDUs are received during the time interval.

         This counter is incremented because of a problem with the data path, or
         because the MEF-35 delta_t for this test is too short.  delta_t is
         configured using tmnxOamPmCfgLossLmmInterval and
         tmnxOamPmCfgLossLmmTxFrmsPerDelT."
    REFERENCE
        "MEF-35, 'Service OAM Performance Monitoring Implementation Agreement',
         Metro Ethernet Forum, April 2012, Section 6.3 'MEF 10.2.1'."
    ::= { tmnxOamPmStsLossLmmEntry 24 }

tmnxOamPmStsLossTwlTable         OBJECT-TYPE
    SYNTAX      SEQUENCE OF TmnxOamPmStsLossTwlEntry
    MAX-ACCESS  not-accessible
    STATUS      current
    DESCRIPTION
        "tmnxOamPmStsLossTwlTable contains TWAMP-Light (Two-Way Active
         Measurement Protocol, Light) frame loss statistics.  The frame loss
         statistics kept for TWAMP-Light tests are the same as the frame loss
         statistics specified for Ethernet SLM (Synthetic Loss Measurement)
         tests in MEF-35 section 10.2."
    REFERENCE
        "MEF-35, 'Service OAM Performance Monitoring Implementation Agreement',
         Metro Ethernet Forum, April 2012, Section 10.2, 'Single-Ended Synthetic
         Loss Function for Frame Loss Ratio (FLR) and Availability'.
         RFC 5357, 'A Two-Way Active Measurement Protocol (TWAMP)', Appendix I,
         'TWAMP Light'."
    ::= { tmnxOamPmStatsTableObjs 10 }

tmnxOamPmStsLossTwlEntry         OBJECT-TYPE
    SYNTAX      TmnxOamPmStsLossTwlEntry
    MAX-ACCESS  not-accessible
    STATUS      current
    DESCRIPTION
        "tmnxOamPmStsLossTwlEntry contains the TWAMP-Light loss test statistics
         for one OAM Performance Monitoring Measurement Interval Data Set.

         A row is created in this table when a tmnxOamPmStsBaseTable row is
         created with tmnxOamPmStsBaseTestType = 'twampLight(3)' (provided
         tmnxOamPmCfgTwampLtCollectStats is 'collectLossStats(2)' or
         'collectDelayAndLossStats(3)').

         A row is destroyed in this table when the corresponding
         tmnxOamPmStsBaseTable row is destroyed.

         When a TWAMP-Light test is running, all the test's raw statistics can
         be cleared using TIMETRA-CLEAR-MIB::tmnxClearAction and
         tmnxClearParams.  A successful clear operation zeros the TWAMP-Light
         delay and TWAMP-Light loss raw statistics for the specified session."
    INDEX       {
        tmnxOamPmCfgSessName,
        tmnxOamPmStsMeasIntvlDuration,
        tmnxOamPmStsIntvlNum
    }
    ::= { tmnxOamPmStsLossTwlTable 1 }

TmnxOamPmStsLossTwlEntry         ::= SEQUENCE
{
    tmnxOamPmStsLossTwlTxFwd         Counter32,
    tmnxOamPmStsLossTwlRxFwd         Counter32,
    tmnxOamPmStsLossTwlTxBwd         Counter32,
    tmnxOamPmStsLossTwlRxBwd         Counter32,
    tmnxOamPmStsLossTwlAvailIndFwd   Counter32,
    tmnxOamPmStsLossTwlAvailIndBwd   Counter32,
    tmnxOamPmStsLossTwlUnavlIndFwd   Counter32,
    tmnxOamPmStsLossTwlUnavlIndBwd   Counter32,
    tmnxOamPmStsLossTwlUndtAvlFwd    Counter32,
    tmnxOamPmStsLossTwlUndtUnavlFwd  Counter32,
    tmnxOamPmStsLossTwlUndtAvlBwd    Counter32,
    tmnxOamPmStsLossTwlUndtUnavlBwd  Counter32,
    tmnxOamPmStsLossTwlHliFwd        Counter32,
    tmnxOamPmStsLossTwlHliBwd        Counter32,
    tmnxOamPmStsLossTwlChliFwd       Counter32,
    tmnxOamPmStsLossTwlChliBwd       Counter32,
    tmnxOamPmStsLossTwlMinFlrFwd     Unsigned32,
    tmnxOamPmStsLossTwlMaxFlrFwd     Unsigned32,
    tmnxOamPmStsLossTwlAvgFlrFwd     Unsigned32,
    tmnxOamPmStsLossTwlMinFlrBwd     Unsigned32,
    tmnxOamPmStsLossTwlMaxFlrBwd     Unsigned32,
    tmnxOamPmStsLossTwlAvgFlrBwd     Unsigned32
}

tmnxOamPmStsLossTwlTxFwd         OBJECT-TYPE
    SYNTAX      Counter32
    UNITS       "TWAMP-Light request frames"
    MAX-ACCESS  read-only
    STATUS      current
    DESCRIPTION
        "The value of tmnxOamPmStsLossTwlTxFwd indicates the number of
         TWAMP-Light request frames transmitted in the forward direction for
         the specified measurement interval data set.

         A frame is counted if the TWAMP-Light Availability state is Available
         at transmit time (as specified in MEF-35 Section 9.2.5).

         A simple count of the frames transmitted for the test is available in
         tmnxOamPmStsBaseTestFramesTx."
    REFERENCE
        "MEF-35, 'Service OAM Performance Monitoring Implementation Agreement',
         Metro Ethernet Forum, April 2012, Section 9.2.5, 'Measurement Behavior
         During Periods of Unavailability and Maintenance Intervals'"
    ::= { tmnxOamPmStsLossTwlEntry 1 }

tmnxOamPmStsLossTwlRxFwd         OBJECT-TYPE
    SYNTAX      Counter32
    UNITS       "TWAMP-Light request frames"
    MAX-ACCESS  read-only
    STATUS      current
    DESCRIPTION
        "The value of tmnxOamPmStsLossTwlRxFwd indicates the number of
         TWAMP-Light request frames received in the forward direction for the
         specified measurement interval data set.

         A frame is counted if the TWAMP-Light Availability state is Available
         at receive time (as specified in MEF-35 Section 9.2.5).

         A simple count of the frames received for the test is available in
         tmnxOamPmStsBaseTestFramesRx."
    REFERENCE
        "MEF-35, 'Service OAM Performance Monitoring Implementation Agreement',
         Metro Ethernet Forum, April 2012, Section 9.2.5, 'Measurement Behavior
         During Periods of Unavailability and Maintenance Intervals'"
    ::= { tmnxOamPmStsLossTwlEntry 2 }

tmnxOamPmStsLossTwlTxBwd         OBJECT-TYPE
    SYNTAX      Counter32
    UNITS       "TWAMP-Light reply frames"
    MAX-ACCESS  read-only
    STATUS      current
    DESCRIPTION
        "The value of tmnxOamPmStsLossTwlTxBwd indicates the number of
         TWAMP-Light reply frames transmitted in the backward direction for the
         specified measurement interval data set.

         A frame is counted if the TWAMP-Light Availability state is Available
         at transmit time (as specified in MEF-35 Section 9.2.5).

         A simple count of the frames transmitted for the test is available in
         tmnxOamPmStsBaseTestFramesTx."
    REFERENCE
        "MEF-35, 'Service OAM Performance Monitoring Implementation Agreement',
         Metro Ethernet Forum, April 2012, Section 9.2.5, 'Measurement Behavior
         During Periods of Unavailability and Maintenance Intervals'"
    ::= { tmnxOamPmStsLossTwlEntry 3 }

tmnxOamPmStsLossTwlRxBwd         OBJECT-TYPE
    SYNTAX      Counter32
    UNITS       "TWAMP-Light reply frames"
    MAX-ACCESS  read-only
    STATUS      current
    DESCRIPTION
        "The value of tmnxOamPmStsLossTwlRxBwd indicates the number of
         TWAMP-Light reply frames received in the backward direction for the
         specified measurement interval data set.

         A frame is counted if the TWAMP-Light Availability state is Available
         at receive time (as specified in MEF-35 Section 9.2.5).

         A simple count of the frames received for the test is available in
         tmnxOamPmStsBaseTestFramesRx."
    REFERENCE
        "MEF-35, 'Service OAM Performance Monitoring Implementation Agreement',
         Metro Ethernet Forum, April 2012, Section 9.2.5, 'Measurement Behavior
         During Periods of Unavailability and Maintenance Intervals'"
    ::= { tmnxOamPmStsLossTwlEntry 4 }

tmnxOamPmStsLossTwlAvailIndFwd   OBJECT-TYPE
    SYNTAX      Counter32
    MAX-ACCESS  read-only
    STATUS      current
    DESCRIPTION
        "The value of tmnxOamPmStsLossTwlAvailIndFwd indicates the number of
         availability indicators evaluated as Available in the forward
         direction for the specified measurement interval data set."
    ::= { tmnxOamPmStsLossTwlEntry 5 }

tmnxOamPmStsLossTwlAvailIndBwd   OBJECT-TYPE
    SYNTAX      Counter32
    MAX-ACCESS  read-only
    STATUS      current
    DESCRIPTION
        "The value of tmnxOamPmStsLossTwlAvailIndBwd indicates the number of
         availability indicators evaluated as Available in the backward
         direction for the specified measurement interval data set."
    ::= { tmnxOamPmStsLossTwlEntry 6 }

tmnxOamPmStsLossTwlUnavlIndFwd   OBJECT-TYPE
    SYNTAX      Counter32
    MAX-ACCESS  read-only
    STATUS      current
    DESCRIPTION
        "The value of tmnxOamPmStsLossTwlUnavlIndFwd indicates the number of
         availability indicators evaluated as Unavailable in the forward
         direction for the specified measurement interval data set."
    ::= { tmnxOamPmStsLossTwlEntry 7 }

tmnxOamPmStsLossTwlUnavlIndBwd   OBJECT-TYPE
    SYNTAX      Counter32
    MAX-ACCESS  read-only
    STATUS      current
    DESCRIPTION
        "The value of tmnxOamPmStsLossTwlUnavlIndBwd indicates the number of
         availability indicators evaluated as Unavailable in the backward
         direction for the specified measurement interval data set."
    ::= { tmnxOamPmStsLossTwlEntry 8 }

tmnxOamPmStsLossTwlUndtAvlFwd    OBJECT-TYPE
    SYNTAX      Counter32
    MAX-ACCESS  read-only
    STATUS      current
    DESCRIPTION
        "The value of tmnxOamPmStsLossTwlUndtAvlFwd indicates the number of
         availability indicators evaluated as Available in the forward
         direction, based on extrapolation from the previous state.

         For example, this counter will be incremented when:
         1.  It is time to calculate an availability indicator, and
         2.  All the probe requests used to calculate the availability indicator
         have timed out, and
         3.  The most recently declared availability indicator in the forward
         direction was Available.

         In that case, the result is considered undetermined because no
         information is available to indicate if the problem is in the forward
         direction or the backward direction."
    ::= { tmnxOamPmStsLossTwlEntry 9 }

tmnxOamPmStsLossTwlUndtUnavlFwd  OBJECT-TYPE
    SYNTAX      Counter32
    MAX-ACCESS  read-only
    STATUS      current
    DESCRIPTION
        "The value of tmnxOamPmStsLossTwlUndtUnavlFwd indicates the number of
         availability indicators evaluated as Unavailable in the forward
         direction, based on extrapolation from the previous state.

         For example, this counter will be incremented when:
         1.  It is time to calculate an availability indicator, and
         2.  All the probe requests used to calculate the availability indicator
         have timed out, and
         3.  The most recently declared availability indicator in the forward
         direction was Unavailable.

         In that case, the result is considered undetermined because no
         information is available to indicate if the problem is in the forward
         direction or the backward direction."
    ::= { tmnxOamPmStsLossTwlEntry 10 }

tmnxOamPmStsLossTwlUndtAvlBwd    OBJECT-TYPE
    SYNTAX      Counter32
    MAX-ACCESS  read-only
    STATUS      current
    DESCRIPTION
        "The value of tmnxOamPmStsLossTwlUndtAvlBwd indicates the number of
         availability indicators evaluated as Available in the backward
         direction, based on extrapolation from the previous state.

         For example, this counter will be incremented when:
         1.  It is time to calculate an availability indicator, and
         2.  All the probe requests used to calculate the availability indicator
         have timed out, and
         3.  The most recently declared availability indicator in the backward
         direction was Available.

         In that case, the result is considered undetermined because no
         information is available to indicate if the problem is in the forward
         direction or the backward direction."
    ::= { tmnxOamPmStsLossTwlEntry 11 }

tmnxOamPmStsLossTwlUndtUnavlBwd  OBJECT-TYPE
    SYNTAX      Counter32
    MAX-ACCESS  read-only
    STATUS      current
    DESCRIPTION
        "The value of tmnxOamPmStsLossTwlUndtUnavlBwd indicates the number of
         availability indicators evaluated as Unavailable in the backward
         direction, based on extrapolation from the previous state.

         For example, this counter will be incremented when:
         1.  It is time to calculate an availability indicator, and
         2.  All the probe requests used to calculate the availability indicator
         have timed out, and
         3.  The most recently declared availability indicator in the backward
         direction was Unavailable.

         In that case, the result is considered undetermined because no
         information is available to indicate if the problem is in the forward
         direction or the backward direction."
    ::= { tmnxOamPmStsLossTwlEntry 12 }

tmnxOamPmStsLossTwlHliFwd        OBJECT-TYPE
    SYNTAX      Counter32
    MAX-ACCESS  read-only
    STATUS      current
    DESCRIPTION
        "The value of tmnxOamPmStsLossTwlHliFwd indicates the number of High
         Loss Intervals (HLIs) in the forward direction for the specified
         measurement interval data set."
    ::= { tmnxOamPmStsLossTwlEntry 13 }

tmnxOamPmStsLossTwlHliBwd        OBJECT-TYPE
    SYNTAX      Counter32
    MAX-ACCESS  read-only
    STATUS      current
    DESCRIPTION
        "The value of tmnxOamPmStsLossTwlHliBwd indicates the number of High
         Loss Intervals (HLIs) in the backward direction for the specified
         measurement interval data set."
    ::= { tmnxOamPmStsLossTwlEntry 14 }

tmnxOamPmStsLossTwlChliFwd       OBJECT-TYPE
    SYNTAX      Counter32
    MAX-ACCESS  read-only
    STATUS      current
    DESCRIPTION
        "The value of tmnxOamPmStsLossTwlChliFwd indicates the number of
         Consecutive High Loss Intervals (CHLIs) in the forward direction for
         the specified measurement interval data set."
    ::= { tmnxOamPmStsLossTwlEntry 15 }

tmnxOamPmStsLossTwlChliBwd       OBJECT-TYPE
    SYNTAX      Counter32
    MAX-ACCESS  read-only
    STATUS      current
    DESCRIPTION
        "The value of tmnxOamPmStsLossTwlChliBwd indicates the number of
         Consecutive High Loss Intervals (CHLIs) in the backward direction for
         the specified measurement interval data set."
    ::= { tmnxOamPmStsLossTwlEntry 16 }

tmnxOamPmStsLossTwlMinFlrFwd     OBJECT-TYPE
    SYNTAX      Unsigned32 (0..100000)
    UNITS       "milli-percent"
    MAX-ACCESS  read-only
    STATUS      current
    DESCRIPTION
        "The value of tmnxOamPmStsLossTwlMinFlrFwd indicates the minimum Frame
         Loss Ratio (FLR) in the forward direction for the specified
         measurement interval data set."
    ::= { tmnxOamPmStsLossTwlEntry 17 }

tmnxOamPmStsLossTwlMaxFlrFwd     OBJECT-TYPE
    SYNTAX      Unsigned32 (0..100000)
    UNITS       "milli-percent"
    MAX-ACCESS  read-only
    STATUS      current
    DESCRIPTION
        "The value of tmnxOamPmStsLossTwlMaxFlrFwd indicates the maximum Frame
         Loss Ratio (FLR) in the forward direction for the specified
         measurement interval data set."
    ::= { tmnxOamPmStsLossTwlEntry 18 }

tmnxOamPmStsLossTwlAvgFlrFwd     OBJECT-TYPE
    SYNTAX      Unsigned32 (0..100000)
    UNITS       "milli-percent"
    MAX-ACCESS  read-only
    STATUS      current
    DESCRIPTION
        "The value of tmnxOamPmStsLossTwlAvgFlrFwd indicates the average Frame
         Loss Ratio (FLR) in the forward direction for the specified
         measurement interval data set."
    ::= { tmnxOamPmStsLossTwlEntry 19 }

tmnxOamPmStsLossTwlMinFlrBwd     OBJECT-TYPE
    SYNTAX      Unsigned32 (0..100000)
    UNITS       "milli-percent"
    MAX-ACCESS  read-only
    STATUS      current
    DESCRIPTION
        "The value of tmnxOamPmStsLossTwlMinFlrBwd indicates the minimum Frame
         Loss Ratio (FLR) in the backward direction for the specified
         measurement interval data set."
    ::= { tmnxOamPmStsLossTwlEntry 20 }

tmnxOamPmStsLossTwlMaxFlrBwd     OBJECT-TYPE
    SYNTAX      Unsigned32 (0..100000)
    UNITS       "milli-percent"
    MAX-ACCESS  read-only
    STATUS      current
    DESCRIPTION
        "The value of tmnxOamPmStsLossTwlMaxFlrBwd indicates the maximum Frame
         Loss Ratio (FLR) in the backward direction for the specified
         measurement interval data set."
    ::= { tmnxOamPmStsLossTwlEntry 21 }

tmnxOamPmStsLossTwlAvgFlrBwd     OBJECT-TYPE
    SYNTAX      Unsigned32 (0..100000)
    UNITS       "milli-percent"
    MAX-ACCESS  read-only
    STATUS      current
    DESCRIPTION
        "The value of tmnxOamPmStsLossTwlAvgFlrBwd indicates the average Frame
         Loss Ratio (FLR) in the backward direction for the specified
         measurement interval data set."
    ::= { tmnxOamPmStsLossTwlEntry 22 }

tmnxOamPmStsTcaDelayTable        OBJECT-TYPE
    SYNTAX      SEQUENCE OF TmnxOamPmStsTcaDelayEntry
    MAX-ACCESS  not-accessible
    STATUS      current
    DESCRIPTION
        "tmnxOamPmStsTcaDelayTable contains statistics for delay-based OAM-PM
         Threshold Crossing Alerts (TCAs)."
    ::= { tmnxOamPmStatsTableObjs 11 }

tmnxOamPmStsTcaDelayEntry        OBJECT-TYPE
    SYNTAX      TmnxOamPmStsTcaDelayEntry
    MAX-ACCESS  not-accessible
    STATUS      current
    DESCRIPTION
        "tmnxOamPmStsTcaDelayEntry contains the OAM-PM delay TCA statistics for
         the combination of an OAM-PM session name, test type, bin type, and
         direction (e.g. {'oam_pm_sess_1', 'dmm(1)', 'ifdv(3)', 'twoWay(3)'}).

         Nine rows are created/destroyed in this table when a delay test is
         created/destroyed.

         The nine rows are indexed by the session name, the test type, and the
         nine combinations of bin type and direction.

         A delay test is created/destroyed using
             tmnxOamPmCfgDelayDmmRowStatus,
             tmnxOamPmCfgDelayMplsRowStatus, or
             tmnxOamPmCfgTwampLtRowStatus."
    INDEX       {
        tmnxOamPmCfgSessName,
        tmnxOamPmCfgTestType,
        tmnxOamPmCfgBinType,
        tmnxOamPmCfgForwardBackward2Way
    }
    ::= { tmnxOamPmStsTcaDelayTable 1 }

TmnxOamPmStsTcaDelayEntry        ::= SEQUENCE
{
    tmnxOamPmStsTcaDelayLastTime     DateAndTime,
    tmnxOamPmStsTcaDelayOperState    TmnxOamPmStsTcaOperState
}

tmnxOamPmStsTcaDelayLastTime     OBJECT-TYPE
    SYNTAX      DateAndTime (SIZE (8))
    MAX-ACCESS  read-only
    STATUS      current
    DESCRIPTION
        "The value of tmnxOamPmStsTcaDelayLastTime indicates the UTC date and
         time at the start of the measurement interval which generated the most
         recent delay-based Raise or Clear TCA for the specified indices.
         Measurement interval start times are reported using
         tmnxOamPmStsBaseStartTime.  The TCAs are tmnxOamPmThrRaise and
         tmnxOamPmThrClear.

         DateAndTime.year = 0 is returned if no TCAs have been generated for
         the specified indices since system start up."
    ::= { tmnxOamPmStsTcaDelayEntry 1 }

tmnxOamPmStsTcaDelayOperState    OBJECT-TYPE
    SYNTAX      TmnxOamPmStsTcaOperState
    MAX-ACCESS  read-only
    STATUS      current
    DESCRIPTION
        "The value of tmnxOamPmStsTcaDelayOperState indicates the operational
         state of delay-based TCAs for the specified indices."
    ::= { tmnxOamPmStsTcaDelayEntry 2 }

tmnxOamPmStsTcaLossFwBwAgTable   OBJECT-TYPE
    SYNTAX      SEQUENCE OF TmnxOamPmStsTcaLossFwBwAgEntry
    MAX-ACCESS  not-accessible
    STATUS      current
    DESCRIPTION
        "tmnxOamPmStsTcaLossFwBwAgTable contains statistics for loss-based
         OAM-PM Threshold Crossing Alerts (TCAs).  The subset of the TCA loss
         statistics that are kept in the forward, backward, and aggregate
         directions is available using this table."
    ::= { tmnxOamPmStatsTableObjs 12 }

tmnxOamPmStsTcaLossFwBwAgEntry   OBJECT-TYPE
    SYNTAX      TmnxOamPmStsTcaLossFwBwAgEntry
    MAX-ACCESS  not-accessible
    STATUS      current
    DESCRIPTION
        "tmnxOamPmStsTcaLossFwBwAgEntry contains the TCA statistics for the
         forward, backward, or aggregate direction of one OAM-PM loss test.  For
         example, a row may contain TCA statistics for the forward direction for
         the SLM test belonging to OAM-PM session OAM_PM_Eth_session_1."
    AUGMENTS    { tmnxOamPmCfgThrLossFwBwAgEntry }
    ::= { tmnxOamPmStsTcaLossFwBwAgTable 1 }

TmnxOamPmStsTcaLossFwBwAgEntry   ::= SEQUENCE
{
    tmnxOamPmStsTcaLossChliLastTime  DateAndTime,
    tmnxOamPmStsTcaLossChliOperState TmnxOamPmStsTcaOperState,
    tmnxOamPmStsTcaLossHliLastTime   DateAndTime,
    tmnxOamPmStsTcaLossHliOperState  TmnxOamPmStsTcaOperState,
    tmnxOamPmStsTcaLossUnavlIndLTime DateAndTime,
    tmnxOamPmStsTcaLossUnavlIndOprSt TmnxOamPmStsTcaOperState,
    tmnxOamPmStsTcaLossUndtAvlLTime  DateAndTime,
    tmnxOamPmStsTcaLossUndtAvlOperSt TmnxOamPmStsTcaOperState,
    tmnxOamPmStsTcaLossUndtUnavlLTim DateAndTime,
    tmnxOamPmStsTcaLossUndtUnavlOpSt TmnxOamPmStsTcaOperState
}

tmnxOamPmStsTcaLossChliLastTime  OBJECT-TYPE
    SYNTAX      DateAndTime (SIZE (8))
    MAX-ACCESS  read-only
    STATUS      current
    DESCRIPTION
        "The value of tmnxOamPmStsTcaLossChliLastTime indicates the UTC date and
         time at the start of the measurement interval which generated the most
         recent Consecutive High Loss Interval (CHLI) Raise or Clear TCA for the
         specified indices.  Measurement interval start times are reported using
         tmnxOamPmStsBaseStartTime.  The TCAs are tmnxOamPmThrRaise and
         tmnxOamPmThrClear.

         DateAndTime.year = 0 is returned if no CHLI TCAs have been generated
         for the specified indices since system start up."
    ::= { tmnxOamPmStsTcaLossFwBwAgEntry 1 }

tmnxOamPmStsTcaLossChliOperState OBJECT-TYPE
    SYNTAX      TmnxOamPmStsTcaOperState
    MAX-ACCESS  read-only
    STATUS      current
    DESCRIPTION
        "The value of tmnxOamPmStsTcaLossChliOperState indicates the
         operational state of Consecutive High Loss Interval (CHLI) TCAs for
         the specified indices."
    ::= { tmnxOamPmStsTcaLossFwBwAgEntry 2 }

tmnxOamPmStsTcaLossHliLastTime   OBJECT-TYPE
    SYNTAX      DateAndTime (SIZE (8))
    MAX-ACCESS  read-only
    STATUS      current
    DESCRIPTION
        "The value of tmnxOamPmStsTcaLossHliLastTime indicates the UTC date and
         time at the start of the measurement interval which generated the most
         recent High Loss Interval (HLI) Raise or Clear TCA for the specified
         indices.  Measurement interval start times are reported using
         tmnxOamPmStsBaseStartTime.  The TCAs are tmnxOamPmThrRaise and
         tmnxOamPmThrClear.

         DateAndTime.year = 0 is returned if no HLI TCAs have been generated
         for the specified indices since system start up."
    ::= { tmnxOamPmStsTcaLossFwBwAgEntry 3 }

tmnxOamPmStsTcaLossHliOperState  OBJECT-TYPE
    SYNTAX      TmnxOamPmStsTcaOperState
    MAX-ACCESS  read-only
    STATUS      current
    DESCRIPTION
        "The value of tmnxOamPmStsTcaLossHliOperState indicates the operational
         state of High Loss Interval (HLI) TCAs for the specified indices."
    ::= { tmnxOamPmStsTcaLossFwBwAgEntry 4 }

tmnxOamPmStsTcaLossUnavlIndLTime OBJECT-TYPE
    SYNTAX      DateAndTime (SIZE (8))
    MAX-ACCESS  read-only
    STATUS      current
    DESCRIPTION
        "The value of tmnxOamPmStsTcaLossUnavlIndLTime indicates the UTC date
         and time at the start of the measurement interval which generated the
         most recent Unavailability Indicator Raise or Clear TCA for the
         specified indices.  Measurement interval start times are reported using
         tmnxOamPmStsBaseStartTime.  The TCAs are tmnxOamPmThrRaise and
         tmnxOamPmThrClear.

         DateAndTime.year = 0 is returned if no Unavailability Indicator TCAs
         have been generated for the specified indices since system start up."
    ::= { tmnxOamPmStsTcaLossFwBwAgEntry 5 }

tmnxOamPmStsTcaLossUnavlIndOprSt OBJECT-TYPE
    SYNTAX      TmnxOamPmStsTcaOperState
    MAX-ACCESS  read-only
    STATUS      current
    DESCRIPTION
        "The value of tmnxOamPmStsTcaLossUnavlIndOprSt indicates the
         operational state of Unavailability Indicator TCAs for the specified
         indices."
    ::= { tmnxOamPmStsTcaLossFwBwAgEntry 6 }

tmnxOamPmStsTcaLossUndtAvlLTime  OBJECT-TYPE
    SYNTAX      DateAndTime (SIZE (8))
    MAX-ACCESS  read-only
    STATUS      current
    DESCRIPTION
        "The value of tmnxOamPmStsTcaLossUndtAvlLTime indicates the UTC date
         and time at the start of the measurement interval which generated the
         most recent Undetermined Availability Indicator Raise or Clear TCA for
         the specified indices.  Measurement interval start times are reported
         using tmnxOamPmStsBaseStartTime.  The TCAs are tmnxOamPmThrRaise and
         tmnxOamPmThrClear.

         DateAndTime.year = 0 is returned if no Undetermined Availability
         Indicator TCAs have been generated for the specified indices since
         system start up."
    ::= { tmnxOamPmStsTcaLossFwBwAgEntry 7 }

tmnxOamPmStsTcaLossUndtAvlOperSt OBJECT-TYPE
    SYNTAX      TmnxOamPmStsTcaOperState
    MAX-ACCESS  read-only
    STATUS      current
    DESCRIPTION
        "The value of tmnxOamPmStsTcaLossUndtAvlOperSt indicates the
         operational state of Undetermined Availability Indicator TCAs for the
         specified indices."
    ::= { tmnxOamPmStsTcaLossFwBwAgEntry 8 }

tmnxOamPmStsTcaLossUndtUnavlLTim OBJECT-TYPE
    SYNTAX      DateAndTime (SIZE (8))
    MAX-ACCESS  read-only
    STATUS      current
    DESCRIPTION
        "The value of tmnxOamPmStsTcaLossUndtUnavlLTim indicates the UTC date
         and time at the start of the measurement interval which generated the
         most recent Undetermined Unavailability Indicator Raise or Clear TCA
         for the specified indices.  Measurement interval start times are
         reported using tmnxOamPmStsBaseStartTime.  The TCAs are
         tmnxOamPmThrRaise and tmnxOamPmThrClear.

         DateAndTime.year = 0 is returned if no Undetermined Unavailability
         Indicator TCAs have been generated for the specified indices since
         system start up."
    ::= { tmnxOamPmStsTcaLossFwBwAgEntry 9 }

tmnxOamPmStsTcaLossUndtUnavlOpSt OBJECT-TYPE
    SYNTAX      TmnxOamPmStsTcaOperState
    MAX-ACCESS  read-only
    STATUS      current
    DESCRIPTION
        "The value of tmnxOamPmStsTcaLossUndtUnavlOpSt indicates the
         operational state of Undetermined Unavailability Indicator TCAs for
         the specified indices."
    ::= { tmnxOamPmStsTcaLossFwBwAgEntry 10 }

tmnxOamPmStsTcaLossFwBwTable     OBJECT-TYPE
    SYNTAX      SEQUENCE OF TmnxOamPmStsTcaLossFwBwEntry
    MAX-ACCESS  not-accessible
    STATUS      current
    DESCRIPTION
        "tmnxOamPmStsTcaLossFwBwTable contains statistics for loss-based OAM-PM
         Threshold Crossing Alerts (TCAs).  The subset of the TCA loss
         statistics that are kept in the forward and backward directions is
         available using this table."
    ::= { tmnxOamPmStatsTableObjs 13 }

tmnxOamPmStsTcaLossFwBwEntry     OBJECT-TYPE
    SYNTAX      TmnxOamPmStsTcaLossFwBwEntry
    MAX-ACCESS  not-accessible
    STATUS      current
    DESCRIPTION
        "tmnxOamPmStsTcaLossFwBwEntry contains TCA statistics for the forward or
         backward direction of one OAM-PM loss test.  For example, a row may
         contain TCA statistics for the forward direction for the SLM test
         belonging to OAM-PM session OAM_PM_Eth_session_1."
    AUGMENTS    { tmnxOamPmCfgThrLossFwBwEntry }
    ::= { tmnxOamPmStsTcaLossFwBwTable 1 }

TmnxOamPmStsTcaLossFwBwEntry     ::= SEQUENCE
{
    tmnxOamPmStsTcaLossAvgFlrLstTime DateAndTime,
    tmnxOamPmStsTcaLossAvgFlrOperSt  TmnxOamPmStsTcaOperState
}

tmnxOamPmStsTcaLossAvgFlrLstTime OBJECT-TYPE
    SYNTAX      DateAndTime (SIZE (8))
    MAX-ACCESS  read-only
    STATUS      current
    DESCRIPTION
        "The value of tmnxOamPmStsTcaLossAvgFlrLstTime indicates the UTC date
         and time at the start of the measurement interval which generated the
         most recent Average Frame Loss Ratio (FLR) Raise or Clear TCA for the
         specified indices.  Measurement interval start times are reported using
         tmnxOamPmStsBaseStartTime.  The TCAs are tmnxOamPmThrRaise and
         tmnxOamPmThrClear.

         DateAndTime.year = 0 is returned if no Average FLR TCAs have been
         generated for the specified indices since system start up."
    ::= { tmnxOamPmStsTcaLossFwBwEntry 1 }

tmnxOamPmStsTcaLossAvgFlrOperSt  OBJECT-TYPE
    SYNTAX      TmnxOamPmStsTcaOperState
    MAX-ACCESS  read-only
    STATUS      current
    DESCRIPTION
        "The value of tmnxOamPmStsTcaLossAvgFlrOperSt indicates the operational
         state of Average Frame Loss Ratio (FLR) TCAs for the specified
         indices."
    ::= { tmnxOamPmStsTcaLossFwBwEntry 2 }

tmnxOamPmStsSessIpTable          OBJECT-TYPE
    SYNTAX      SEQUENCE OF TmnxOamPmStsSessIpEntry
    MAX-ACCESS  not-accessible
    STATUS      current
    DESCRIPTION
        "tmnxOamPmStsSessIpTable contains status information for OAM-PM
         sessions with tmnxOamPmCfgSessTestFamily equal to 'ip(2)'."
    ::= { tmnxOamPmStatsTableObjs 14 }

tmnxOamPmStsSessIpEntry          OBJECT-TYPE
    SYNTAX      TmnxOamPmStsSessIpEntry
    MAX-ACCESS  not-accessible
    STATUS      current
    DESCRIPTION
        "tmnxOamPmStsSessIpEntry contains status information for an OAM-PM
         session with tmnxOamPmCfgSessTestFamily equal to 'ip(2)'."
    AUGMENTS    { tmnxOamPmCfgSessIpEntry }
    ::= { tmnxOamPmStsSessIpTable 1 }

TmnxOamPmStsSessIpEntry          ::= SEQUENCE
{ tmnxOamPmStsSessIpSrcUdpPort     InetPortNumber }

tmnxOamPmStsSessIpSrcUdpPort     OBJECT-TYPE
    SYNTAX      InetPortNumber
    MAX-ACCESS  read-only
    STATUS      current
    DESCRIPTION
        "The value of tmnxOamPmStsSessIpSrcUdpPort indicates the source UDP
         port allocated for the specified OAM-PM IP session.

         The allocation of source UDP ports is described in the DESCRIPTION
         clause of tmnxOamPmCfgSessIpSrcUdpPort.

         If the source UDP port has not been successfully allocated (or has
         been deallocated), tmnxOamPmStsSessIpSrcUdpPort is zero."
    ::= { tmnxOamPmStsSessIpEntry 1 }

tmnxOamPmStsTestTable            OBJECT-TYPE
    SYNTAX      SEQUENCE OF TmnxOamPmStsTestEntry
    MAX-ACCESS  not-accessible
    STATUS      current
    DESCRIPTION
        "tmnxOamPmStsTestTable contains status information for OAM-PM tests.

         Additional test status information is available in
            tmnxOamPmCfgDelayDmmTable,
            tmnxOamPmCfgDelayMplsTable,
            tmnxOamPmCfgLossLmmTable,
            tmnxOamPmCfgLossSlmTable, and
            tmnxOamPmCfgTwampLtTable."
    ::= { tmnxOamPmStatsTableObjs 15 }

tmnxOamPmStsTestEntry            OBJECT-TYPE
    SYNTAX      TmnxOamPmStsTestEntry
    MAX-ACCESS  not-accessible
    STATUS      current
    DESCRIPTION
        "tmnxOamPmStsTestEntry contains status information for the OAM-PM test
         specified by the indices.

         A row is created/destroyed in this table when an OAM-PM test is
         created/destroyed.

         An OAM-PM test is created/destroyed using
            tmnxOamPmCfgDelayDmmRowStatus,
            tmnxOamPmCfgDelayMplsRowStatus,
            tmnxOamPmCfgLossLmmRowStatus,
            tmnxOamPmCfgLossSlmRowStatus, or
            tmnxOamPmCfgTwampLtRowStatus."
    INDEX       {
        tmnxOamPmCfgSessName,
        tmnxOamPmStsBaseTestType
    }
    ::= { tmnxOamPmStsTestTable 1 }

TmnxOamPmStsTestEntry            ::= SEQUENCE
{ tmnxOamPmStsTestDetectTxError    TmnxOamPmDetectableTxError }

tmnxOamPmStsTestDetectTxError    OBJECT-TYPE
    SYNTAX      TmnxOamPmDetectableTxError
    MAX-ACCESS  read-only
    STATUS      current
    DESCRIPTION
        "The value of tmnxOamPmStsTestDetectTxError indicates a reason for the
         specified test's current inability (if any) to launch request frames.

         For example, 'ethParentAdminDown(4)' could be returned for an SLM test
         if the MEP to be tested is associated with a SAP which is
         administratively down.

         Not all request frame transmit failures are detected by this
         mechanism. It is possible that 'none(1)' will be returned when the
         test is unable to transmit frames."
    ::= { tmnxOamPmStsTestEntry 1 }

tmnxOamPmStsDelayMplsTable       OBJECT-TYPE
    SYNTAX      SEQUENCE OF TmnxOamPmStsDelayMplsEntry
    MAX-ACCESS  not-accessible
    STATUS      current
    DESCRIPTION
        "tmnxOamPmStsDelayMplsTable contains the summarized MPLS DM (Delay
         Measurement) statistics for OAM Performance Monitoring Measurement
         Interval Data Sets.  The packet delay summary statistics kept for
         MPLS DM tests are the same as the frame delay summary statistics
         specified for Ethernet DMM (Delay Measurement Message) tests in
         MEF-35 requirement R66."
    REFERENCE
        "RFC 6374, 'Packet Loss and Delay Measurement for MPLS Networks',
         September 2011.
         MEF-35, 'Service OAM Performance Monitoring Implementation Agreement',
         Metro Ethernet Forum, April 2012, Section 10.1, 'Single-Ended Delay
         Function for Delay, Frame Delay Range, and Inter Delay Variation',
         requirement R66."
    ::= { tmnxOamPmStatsTableObjs 16 }

tmnxOamPmStsDelayMplsEntry       OBJECT-TYPE
    SYNTAX      TmnxOamPmStsDelayMplsEntry
    MAX-ACCESS  not-accessible
    STATUS      current
    DESCRIPTION
        "tmnxOamPmStsDelayMplsEntry contains the summarized MPLS DM (Delay
         Measurement) statistics for one OAM Performance Monitoring Measurement
         Interval Data Set.

         When a row is created in tmnxOamPmStsBaseTable with
         tmnxOamPmStsBaseTestType = 'mplsDm(5)', three rows are created in
         this table.  The three rows have the following values in the
         tmnxOamPmCfgBinType index column: 'fd(1)', 'fdr(2)', and 'ifdv(3)'.

         Rows are destroyed in this table when the corresponding
         tmnxOamPmStsBaseTable row is destroyed.

         When a test is running, the MPLS DM statistics for a test's raw (i.e.
         'miRaw(1)') measurement interval duration can be cleared using
         TIMETRA-CLEAR-MIB::tmnxClearAction and tmnxClearParams.  A successful
         clear operation zeros all the raw MPLS DM statistics for the specified
         session."
    INDEX       {
        tmnxOamPmCfgSessName,
        tmnxOamPmStsMeasIntvlDuration,
        tmnxOamPmStsIntvlNum,
        tmnxOamPmCfgBinType
    }
    ::= { tmnxOamPmStsDelayMplsTable 1 }

TmnxOamPmStsDelayMplsEntry       ::= SEQUENCE
{
    tmnxOamPmStsDelayMplsFwdMin      Unsigned32,
    tmnxOamPmStsDelayMplsFwdMax      Unsigned32,
    tmnxOamPmStsDelayMplsFwdAvg      Unsigned32,
    tmnxOamPmStsDelayMplsBwdMin      Unsigned32,
    tmnxOamPmStsDelayMplsBwdMax      Unsigned32,
    tmnxOamPmStsDelayMplsBwdAvg      Unsigned32,
    tmnxOamPmStsDelayMpls2wyMin      Unsigned32,
    tmnxOamPmStsDelayMpls2wyMax      Unsigned32,
    tmnxOamPmStsDelayMpls2wyAvg      Unsigned32
}

tmnxOamPmStsDelayMplsFwdMin      OBJECT-TYPE
    SYNTAX      Unsigned32
    UNITS       "microseconds"
    MAX-ACCESS  read-only
    STATUS      current
    DESCRIPTION
        "The value of tmnxOamPmStsDelayMplsFwdMin indicates the minimum delay
         in the forward direction for the specified session, interval duration
         (e.g. 'mi15Minutes(2)'), interval number, and bin type (e.g. 'fd(1)')."
    ::= { tmnxOamPmStsDelayMplsEntry 1 }

tmnxOamPmStsDelayMplsFwdMax      OBJECT-TYPE
    SYNTAX      Unsigned32
    UNITS       "microseconds"
    MAX-ACCESS  read-only
    STATUS      current
    DESCRIPTION
        "The value of tmnxOamPmStsDelayMplsFwdMax indicates the maximum delay
         in the forward direction for the specified session, interval duration
         (e.g. 'mi15Minutes(2)'), interval number, and bin type (e.g. 'fd(1)')."
    ::= { tmnxOamPmStsDelayMplsEntry 2 }

tmnxOamPmStsDelayMplsFwdAvg      OBJECT-TYPE
    SYNTAX      Unsigned32
    UNITS       "microseconds"
    MAX-ACCESS  read-only
    STATUS      current
    DESCRIPTION
        "The value of tmnxOamPmStsDelayMplsFwdAvg indicates the average delay
         in the forward direction for the specified session, interval duration
         (e.g. 'mi15Minutes(2)'), interval number, and bin type (e.g. 'fd(1)')."
    ::= { tmnxOamPmStsDelayMplsEntry 3 }

tmnxOamPmStsDelayMplsBwdMin      OBJECT-TYPE
    SYNTAX      Unsigned32
    UNITS       "microseconds"
    MAX-ACCESS  read-only
    STATUS      current
    DESCRIPTION
        "The value of tmnxOamPmStsDelayMplsBwdMin indicates the minimum delay
         in the backward direction for the specified session, interval duration
         (e.g. 'mi15Minutes(2)'), interval number, and bin type (e.g. 'fd(1)')."
    ::= { tmnxOamPmStsDelayMplsEntry 4 }

tmnxOamPmStsDelayMplsBwdMax      OBJECT-TYPE
    SYNTAX      Unsigned32
    UNITS       "microseconds"
    MAX-ACCESS  read-only
    STATUS      current
    DESCRIPTION
        "The value of tmnxOamPmStsDelayMplsBwdMax indicates the maximum delay
         in the backward direction for the specified session, interval duration
         (e.g. 'mi15Minutes(2)'), interval number, and bin type (e.g. 'fd(1)')."
    ::= { tmnxOamPmStsDelayMplsEntry 5 }

tmnxOamPmStsDelayMplsBwdAvg      OBJECT-TYPE
    SYNTAX      Unsigned32
    UNITS       "microseconds"
    MAX-ACCESS  read-only
    STATUS      current
    DESCRIPTION
        "The value of tmnxOamPmStsDelayMplsBwdAvg indicates the average delay
         in the backward direction for the specified session, interval duration
         (e.g. 'mi15Minutes(2)'), interval number, and bin type (e.g. 'fd(1)')."
    ::= { tmnxOamPmStsDelayMplsEntry 6 }

tmnxOamPmStsDelayMpls2wyMin      OBJECT-TYPE
    SYNTAX      Unsigned32
    UNITS       "microseconds"
    MAX-ACCESS  read-only
    STATUS      current
    DESCRIPTION
        "The value of tmnxOamPmStsDelayMpls2wyMin indicates the minimum two-way
         delay for the specified session, interval duration (e.g.
         'mi15Minutes(2)'), interval number, and bin type (e.g. 'fd(1)')."
    ::= { tmnxOamPmStsDelayMplsEntry 7 }

tmnxOamPmStsDelayMpls2wyMax      OBJECT-TYPE
    SYNTAX      Unsigned32
    UNITS       "microseconds"
    MAX-ACCESS  read-only
    STATUS      current
    DESCRIPTION
        "The value of tmnxOamPmStsDelayMpls2wyMax indicates the maximum two-way
         delay for the specified session, interval duration (e.g.
         'mi15Minutes(2)'), interval number, and bin type (e.g. 'fd(1)')."
    ::= { tmnxOamPmStsDelayMplsEntry 8 }

tmnxOamPmStsDelayMpls2wyAvg      OBJECT-TYPE
    SYNTAX      Unsigned32
    UNITS       "microseconds"
    MAX-ACCESS  read-only
    STATUS      current
    DESCRIPTION
        "The value of tmnxOamPmStsDelayMpls2wyAvg indicates the average two-way
         delay for the specified session, interval duration (e.g.
         'mi15Minutes(2)'), interval number, and bin type (e.g. 'fd(1)')."
    ::= { tmnxOamPmStsDelayMplsEntry 9 }

tmnxOamPmStsDelayMplsBinTable    OBJECT-TYPE
    SYNTAX      SEQUENCE OF TmnxOamPmStsDelayMplsBinEntry
    MAX-ACCESS  not-accessible
    STATUS      current
    DESCRIPTION
        "tmnxOamPmStsDelayMplsBinTable contains the per-bin MPLS DM (Delay
         Measurement) statistics for OAM Performance Monitoring Measurement
         Interval Data Sets.  The packet delay statistics kept for MPLS DM
         tests are the same as the frame delay summary statistics specified
         for Ethernet DMM (Delay Measurement Message) tests in MEF-35
         requirement R66."
    REFERENCE
        "RFC 6374, 'Packet Loss and Delay Measurement for MPLS Networks',
         September 2011.
         MEF-35, 'Service OAM Performance Monitoring Implementation Agreement',
         Metro Ethernet Forum, April 2012, Section 10.1, 'Single-Ended Delay
         Function for Delay, Frame Delay Range, and Inter Delay Variation',
         requirement R66."
    ::= { tmnxOamPmStatsTableObjs 17 }

tmnxOamPmStsDelayMplsBinEntry    OBJECT-TYPE
    SYNTAX      TmnxOamPmStsDelayMplsBinEntry
    MAX-ACCESS  not-accessible
    STATUS      current
    DESCRIPTION
        "tmnxOamPmStsDelayMplsBinEntry contains the per-bin MPLS DM (Delay
         Measurement) statistics for one OAM Performance Monitoring Measurement
         Interval Data Set.

         Rows are created in this table when a corresponding row is created in
         tmnxOamPmStsDelayMplsTable.  If the tmnxOamPmStsDelayMplsTable row is
         created with the index value tmnxOamPmCfgBinType = 'fd(1)', then the
         the number of rows created in this table is
         tmnxOamPmCfgBinGroupFdBinCount.  Similarly, 'fdr(2)' and 'ifdv(3)'.

         Rows are destroyed in this table when the corresponding
         tmnxOamPmStsDelayMplsTable row is destroyed.

         When a test is running, the MPLS DM statistics for a test's raw (i.e.
         'miRaw(1)') measurement interval duration can be cleared using
         TIMETRA-CLEAR-MIB::tmnxClearAction and tmnxClearParams.  A successful
         clear operation zeros all the raw MPLS DM statistics for the specified
         session."
    INDEX       {
        tmnxOamPmCfgSessName,
        tmnxOamPmStsMeasIntvlDuration,
        tmnxOamPmStsIntvlNum,
        tmnxOamPmCfgBinType,
        tmnxOamPmStsDelayMplsBinNum
    }
    ::= { tmnxOamPmStsDelayMplsBinTable 1 }

TmnxOamPmStsDelayMplsBinEntry    ::= SEQUENCE
{
    tmnxOamPmStsDelayMplsBinNum      Unsigned32,
    tmnxOamPmStsDelayMplsBinFwdCount Counter32,
    tmnxOamPmStsDelayMplsBinBwdCount Counter32,
    tmnxOamPmStsDelayMplsBin2wyCount Counter32
}

tmnxOamPmStsDelayMplsBinNum      OBJECT-TYPE
    SYNTAX      Unsigned32 (0..9)
    MAX-ACCESS  not-accessible
    STATUS      current
    DESCRIPTION
        "The value of tmnxOamPmStsDelayMplsBinNum specifies the bin number of
         the statistics to be read."
    ::= { tmnxOamPmStsDelayMplsBinEntry 1 }

tmnxOamPmStsDelayMplsBinFwdCount OBJECT-TYPE
    SYNTAX      Counter32
    MAX-ACCESS  read-only
    STATUS      current
    DESCRIPTION
        "The value of tmnxOamPmStsDelayMplsBinFwdCount indicates the number of
         measurements in the forward direction that fall within the configured
         range (in microseconds) of the specified bin.

         For example, suppose the index values for this object are as follows
         (where the index names are abbreviated, and index columns are
         underlined with octothorpes).

         _SessName   _IntvlDuration    _IntvlNum  _BinType  _BinNum
         ##########  ################  #########  ########  #######
         'dmmSess1'  'mi15Minutes(2)'          1  'fd(1)'         9

         Then, the value of this object indicates the number of MPLS DM
         measurements (in microseconds) in the forward direction in the first
         interval of 'dmmSess1' that fit in the highest configured delay range
         (as configured using tmnxOamPmCfgBinLowerBound)."
    ::= { tmnxOamPmStsDelayMplsBinEntry 2 }

tmnxOamPmStsDelayMplsBinBwdCount OBJECT-TYPE
    SYNTAX      Counter32
    MAX-ACCESS  read-only
    STATUS      current
    DESCRIPTION
        "The value of tmnxOamPmStsDelayMplsBinBwdCount indicates the number of
         measurements in the backward direction that fall within the configured
         range (in microseconds) of the specified bin.

         For example, suppose the index values for this object are as follows
         (where the index names are abbreviated, and index columns are
         underlined with octothorpes).

         _SessName   _IntvlDuration    _IntvlNum  _BinType  _BinNum
         ##########  ################  #########  ########  #######
         'dmmSess1'  'mi15Minutes(2)'          1  'fd(1)'         0

         Then, the value of this object indicates the number of MPLS DM
         measurements (in microseconds) in the backward direction in the first
         interval of 'dmmSess1' that fit in the lowest configured delay range
         (as configured using tmnxOamPmCfgBinLowerBound)."
    ::= { tmnxOamPmStsDelayMplsBinEntry 3 }

tmnxOamPmStsDelayMplsBin2wyCount OBJECT-TYPE
    SYNTAX      Counter32
    MAX-ACCESS  read-only
    STATUS      current
    DESCRIPTION
        "The value of tmnxOamPmStsDelayMplsBin2wyCount indicates the number of
         two-way measurements that fall within the configured range (in
         microseconds) of the specified bin.

         For example, suppose the index values for this object are as follows
         (where the index names are abbreviated, and index columns are
         underlined with octothorpes).

         _SessName   _IntvlDuration    _IntvlNum  _BinType  _BinNum
         ##########  ################  #########  ########  #######
         'dmmSess1'  'mi15Minutes(2)'          1  'fd(1)'         0

         Then, the value of this object indicates the number of two-way MPLS DM
         measurements (in microseconds) in the first interval of 'dmmSess1'
         that fit in the lowest configured delay range (as configured using
         tmnxOamPmCfgBinLowerBound)."
    ::= { tmnxOamPmStsDelayMplsBinEntry 4 }

tmnxOamPmStsMplsTestTable        OBJECT-TYPE
    SYNTAX      SEQUENCE OF TmnxOamPmStsMplsTestEntry
    MAX-ACCESS  not-accessible
    STATUS      current
    DESCRIPTION
        "tmnxOamPmStsMplsTestTable contains status information for OAM-PM MPLS
         tests.

         Additional status information for OAM-PM MPLS tests is available in
         tmnxOamPmCfgDelayMplsTable and tmnxOamPmStsTestTable."
    REFERENCE
        "RFC 6374, 'Packet Loss and Delay Measurement for MPLS Networks',
         September 2011."
    ::= { tmnxOamPmStatsTableObjs 18 }

tmnxOamPmStsMplsTestEntry        OBJECT-TYPE
    SYNTAX      TmnxOamPmStsMplsTestEntry
    MAX-ACCESS  not-accessible
    STATUS      current
    DESCRIPTION
        "tmnxOamPmStsMplsTestEntry contains status information for the OAM-PM
         MPLS test specified by the indices.

         A row is created/destroyed in this table when an OAM-PM MPLS test is
         created/destroyed.

         An OAM-PM MPLS test is created/destroyed using
         tmnxOamPmCfgDelayMplsRowStatus."
    INDEX       {
        tmnxOamPmCfgSessName,
        tmnxOamPmStsBaseTestType
    }
    ::= { tmnxOamPmStsMplsTestTable 1 }

TmnxOamPmStsMplsTestEntry        ::= SEQUENCE
{ tmnxOamPmStsMplsTestRxStatus     TmnxOamPmMplsTestRxStatus }

tmnxOamPmStsMplsTestRxStatus     OBJECT-TYPE
    SYNTAX      TmnxOamPmMplsTestRxStatus
    MAX-ACCESS  read-only
    STATUS      current
    DESCRIPTION
        "The value of tmnxOamPmStsMplsTestRxStatus indicates the most recent
         status received in an MPLS-DM response for the specified MPLS-DM test."
    REFERENCE
        "RFC 6374, 'Packet Loss and Delay Measurement for MPLS Networks',
         September 2011, Section 3.2, 'Delay Measurement Message Format'."
    ::= { tmnxOamPmStsMplsTestEntry 1 }

tmnxOamPmStsStrTable             OBJECT-TYPE
    SYNTAX      SEQUENCE OF TmnxOamPmStsStrEntry
    MAX-ACCESS  not-accessible
    STATUS      current
    DESCRIPTION
        "tmnxOamPmStsStrTable contains statistics for OAM-PM streaming sample
         windows.

         Streaming functionality is described in the DESCRIPTION clause of
         tmnxOamPmCfgStrTmplTable."
    ::= { tmnxOamPmStatsTableObjs 19 }

tmnxOamPmStsStrEntry             OBJECT-TYPE
    SYNTAX      TmnxOamPmStsStrEntry
    MAX-ACCESS  not-accessible
    STATUS      current
    DESCRIPTION
        "tmnxOamPmStsStrEntry contains statistics for one OAM-PM streaming
         sample window.

         A row can be indexed by, for example,
             {'oam_pm_sess_1', 'dmm(1)', 'fdAvg(1)', 'twoWay(3)'}.

         When a row is read, the statistics for the most recently closed sample
         window for the specified indices are returned.  Older statistics are
         not retained.

         SROS creates rows when an OAM-PM test starts (provided the test has a
         reference to an enabled OAM-PM streaming template).

         SROS updates rows when a streaming sampling window closes.

         SROS destroys rows when:
         1.  The row's test stops, or
         2.  The streaming template for the row's test is disabled."
    INDEX       {
        tmnxOamPmCfgSessName,
        tmnxOamPmCfgTestType,
        tmnxOamPmCfgStrMetric,
        tmnxOamPmCfgForwardBackward2Way
    }
    ::= { tmnxOamPmStsStrTable 1 }

TmnxOamPmStsStrEntry             ::= SEQUENCE
{
    tmnxOamPmStsStrCloseTime         DateAndTime,
    tmnxOamPmStsStrSampleCount       Unsigned32,
    tmnxOamPmStsStrSuspect           TruthValue,
    tmnxOamPmStsStrDelay             Unsigned32
}

tmnxOamPmStsStrCloseTime         OBJECT-TYPE
    SYNTAX      DateAndTime (SIZE (8))
    MAX-ACCESS  read-only
    STATUS      current
    DESCRIPTION
        "The value of tmnxOamPmStsStrCloseTime indicates the UTC date and time
         when the reported sample window closed."
    ::= { tmnxOamPmStsStrEntry 1 }

tmnxOamPmStsStrSampleCount       OBJECT-TYPE
    SYNTAX      Unsigned32
    MAX-ACCESS  read-only
    STATUS      current
    DESCRIPTION
        "The value of tmnxOamPmStsStrSampleCount indicates the number of valid
         measurements in the sample window."
    ::= { tmnxOamPmStsStrEntry 2 }

tmnxOamPmStsStrSuspect           OBJECT-TYPE
    SYNTAX      TruthValue
    MAX-ACCESS  read-only
    STATUS      current
    DESCRIPTION
        "The value of tmnxOamPmStsStrSuspect indicates whether or not the value
         read using tmnxOamPmStsStrDelay is suspect.

         A value is suspect if the number of valid measurements in the sampling
         window (i.e. tmnxOamPmStsStrSampleCount) is below the threshold (as
         configured using tmnxOamPmCfgStrTmplWindowInteg)."
    ::= { tmnxOamPmStsStrEntry 3 }

tmnxOamPmStsStrDelay             OBJECT-TYPE
    SYNTAX      Unsigned32
    UNITS       "microseconds"
    MAX-ACCESS  read-only
    STATUS      current
    DESCRIPTION
        "The value of tmnxOamPmStsStrDelay indicates the delay measurement
         specified by the tmnxOamPmCfgStrMetric INDEX for the sample window.

         For example, if tmnxOamPmCfgStrMetric is 'fdAvg(1)', then
         tmnxOamPmStsStrDelay is the average frame delay for the sample window."
    ::= { tmnxOamPmStsStrEntry 4 }

tmnxOamPmStsTwampLtTable         OBJECT-TYPE
    SYNTAX      SEQUENCE OF TmnxOamPmStsTwampLtEntry
    MAX-ACCESS  not-accessible
    STATUS      current
    DESCRIPTION
        "tmnxOamPmStsTwampLtTable contains the read-only information for OAM
         Performance Monitoring TWAMP-Light (Two-Way Active Measurement
         Protocol, Light) tests."
    REFERENCE
        "RFC 5357, 'A Two-Way Active Measurement Protocol (TWAMP)', Appendix I,
         'TWAMP Light'.
         RFC 8762, 'Simple Two-Way Active Measurement Protocol'."
    ::= { tmnxOamPmStatsTableObjs 20 }

tmnxOamPmStsTwampLtEntry         OBJECT-TYPE
    SYNTAX      TmnxOamPmStsTwampLtEntry
    MAX-ACCESS  not-accessible
    STATUS      current
    DESCRIPTION
        "tmnxOamPmStsTwampLtEntry contains the read-only information for the
         OAM Performance Monitoring TWAMP-Light test for the specified session.

         A row is created when a test is created, by setting
         tmnxOamPmCfgTwampLtRowStatus to createAndGo(4).

         A row is destroyed when the test is destroyed."
    AUGMENTS    { tmnxOamPmCfgTwampLtEntry }
    ::= { tmnxOamPmStsTwampLtTable 1 }

TmnxOamPmStsTwampLtEntry         ::= SEQUENCE
{
    tmnxOamPmStsTwampLtStampUFlagRx  Counter32,
    tmnxOamPmStsTwampLtStampMFlagRx  Counter32,
    tmnxOamPmStsTwampLtStampSSID     Unsigned32
}

tmnxOamPmStsTwampLtStampUFlagRx  OBJECT-TYPE
    SYNTAX      Counter32
    MAX-ACCESS  read-only
    STATUS      current
    DESCRIPTION
        "The value of tmnxOamPmStsTwampLtStampUFlagRx indicates the count of
         STAMP TLVs with the Unrecognized (U) flag set received from the STAMP
         Session-Reflector."
    REFERENCE
        "RFC 8762, 'Simple Two-Way Active Measurement Protocol'.
         RFC 8972, 'Simple Two-Way Active Measurement Protocol Optional
         Extensions', Section 4 'TLV Extensions to STAMP'."
    ::= { tmnxOamPmStsTwampLtEntry 1 }

tmnxOamPmStsTwampLtStampMFlagRx  OBJECT-TYPE
    SYNTAX      Counter32
    MAX-ACCESS  read-only
    STATUS      current
    DESCRIPTION
        "The value of tmnxOamPmStsTwampLtStampMFlagRx indicates the count of
         STAMP TLVs with the Malformed (M) flag set received from the STAMP
         Session-Reflector."
    REFERENCE
        "RFC 8762, 'Simple Two-Way Active Measurement Protocol'.
         RFC 8972, 'Simple Two-Way Active Measurement Protocol Optional
         Extensions', Section 4 'TLV Extensions to STAMP'."
    ::= { tmnxOamPmStsTwampLtEntry 2 }

tmnxOamPmStsTwampLtStampSSID     OBJECT-TYPE
    SYNTAX      Unsigned32 (0 | 1..65535)
    MAX-ACCESS  read-only
    STATUS      current
    DESCRIPTION
        "The value of tmnxOamPmStsTwampLtStampSSID indicates the Session Sender
         Identifier (SSID) for the session's STAMP test.

         Zero indicates an SSID is not available.
         For example:
         1.  The session does not have an active test (i.e.
             tmnxOamPmCfgTwampLtAdminStatus = disabled(2)), or
         2.  The session's test has the wrong type (i.e.
             tmnxOamPmCfgTwampLtTestSubType = subTypeTwampLight(1))."
    REFERENCE
        "RFC 8972, 'Simple Two-Way Active Measurement Protocol Optional
         Extensions', Section 3 'STAMP Test Session Identifier'."
    ::= { tmnxOamPmStsTwampLtEntry 3 }

tmnxOamPmNotificationObjs        OBJECT IDENTIFIER ::= { tmnxOamPmObjs 3 }

tmnxOamPmNotifThrType            OBJECT-TYPE
    SYNTAX      INTEGER {
        delay            (1),
        lossAvgFlr       (2),
        lossChli         (3),
        lossHli          (4),
        lossUnavail      (5),
        lossUndetAvail   (6),
        lossUndetUnavail (7)
    }
    MAX-ACCESS  accessible-for-notify
    STATUS      current
    DESCRIPTION
        "The value of tmnxOamPmNotifThrType indicates the type of the OAM-PM
         threshold crossing being reported.

         The code points are as follows.
         delay           (1)  - a threshold (e.g. tmnxOamPmCfgThrDelayRaise) on
                                a MEF-35 delay count has been crossed
         lossAvgFlr      (2)  - a threshold (e.g.
                                tmnxOamPmCfgThrLossAvgFlrClear) on a MEF-35
                                Average Frame Loss Ratio (FLR) has been crossed
         lossChli        (3)  - a threshold (e.g. tmnxOamPmCfgThrLossChliRaise)
                                on a MEF-35 Consecutive High Loss Interval
                                (CHLI) count has been crossed
         lossHlii        (4)  - a threshold (e.g. tmnxOamPmCfgThrLossHliClear)
                                on a MEF-35 High Loss Interval (HLI) count has
                                been crossed
         lossUnavail     (5)  - a threshold (e.g.
                                tmnxOamPmCfgThrLossUnavlIndRaise) on a MEF-35
                                Unavailability Indicator count has been crossed
         lossUndetAvail  (6)  - a threshold (e.g.
                                tmnxOamPmCfgThrLossUndtAvlClear) on an
                                Undetermined Availability Indicator count has
                                been crossed
         lossUndetUnavail(7)  - a threshold (e.g.
                                tmnxOamPmCfgThrLossUndtUnavlRais) on an
                                Undetermined Unavailability Indicator count has
                                been crossed"
    REFERENCE
        "MEF-35, 'Service OAM Performance Monitoring Implementation Agreement',
         Metro Ethernet Forum, April 2012"
    ::= { tmnxOamPmNotificationObjs 1 }

tmnxOamPmNotifThrDirection       OBJECT-TYPE
    SYNTAX      INTEGER {
        forward   (1),
        backward  (2),
        twoWay    (3),
        aggregate (4)
    }
    MAX-ACCESS  accessible-for-notify
    STATUS      current
    DESCRIPTION
        "The value of tmnxOamPmNotifThrDirection indicates the traffic flow
         direction of the OAM-PM threshold crossing being reported.

         The semantics of the code points are documented in the DESCRIPTION
         clauses of TmnxOamPmForwardBackwardAggr and
         TmnxOamPmForwardBackwardTwoWay."
    ::= { tmnxOamPmNotificationObjs 2 }

tmnxOamPmNotifThrDelayBinType    OBJECT-TYPE
    SYNTAX      INTEGER {
        notApplicable (0),
        fd            (1),
        fdr           (2),
        ifdv          (3)
    }
    MAX-ACCESS  accessible-for-notify
    STATUS      current
    DESCRIPTION
        "The value of tmnxOamPmNotifThrDelayBinType indicates the bin type of
         the OAM-PM delay threshold crossing being reported.

         'notApplicable(0)' is used for loss tests (i.e. when
         tmnxOamPmNotifThrType is not 'delay(1)').

         The semantics of the other code points are documented in the
         DESCRIPTION clause of TmnxOamPmBinType."
    ::= { tmnxOamPmNotificationObjs 3 }

tmnxOamPmNotifThrStateType       OBJECT-TYPE
    SYNTAX      INTEGER {
        stateful  (1),
        stateless (2)
    }
    MAX-ACCESS  accessible-for-notify
    STATUS      current
    DESCRIPTION
        "The value of tmnxOamPmNotifThrStateType indicates whether or not the
         OAM-PM threshold crossing being reported is stateful.

         The code points are as follows.
             stateful (1) - a clearing threshold is defined for the condition.
             stateless(2) - a clearing threshold is not defined for the
                 condition.

         The DESCRIPTION clause of tmnxOamPmCfgThrLossChliClear explains the
         change in behavior when a clearing threshold is defined."
    ::= { tmnxOamPmNotificationObjs 4 }

tmnxOamPmNotifThrCfgRaise        OBJECT-TYPE
    SYNTAX      Unsigned32
    MAX-ACCESS  accessible-for-notify
    STATUS      current
    DESCRIPTION
        "The value of tmnxOamPmNotifThrCfgRaise indicates the configured raise
         threshold for the OAM-PM Raise trap being reported.

         The value reported is one of the following (where the selection is
         made by other objects in the trap):
            tmnxOamPmCfgThrDelayRaise,
            tmnxOamPmCfgThrLossAvgFlrRaise,
            tmnxOamPmCfgThrLossChliRaise,
            tmnxOamPmCfgThrLossHliRaise,
            tmnxOamPmCfgThrLossUnavlIndRaise,
            tmnxOamPmCfgThrLossUndtAvlRaise, or
            tmnxOamPmCfgThrLossUndtUnavlRais."
    ::= { tmnxOamPmNotificationObjs 5 }

tmnxOamPmNotifThrCfgClear        OBJECT-TYPE
    SYNTAX      Unsigned32
    MAX-ACCESS  accessible-for-notify
    STATUS      current
    DESCRIPTION
        "The value of tmnxOamPmNotifThrCfgClear indicates the configured clear
         threshold for the OAM-PM Clear trap being reported.

         The value reported is one of the following (where the selection is
         made by other objects in the trap):
            tmnxOamPmCfgThrDelayClear,
            tmnxOamPmCfgThrLossAvgFlrClear,
            tmnxOamPmCfgThrLossChliClear,
            tmnxOamPmCfgThrLossHliClear,
            tmnxOamPmCfgThrLossUnavlIndClear,
            tmnxOamPmCfgThrLossUndtAvlClear, or
            tmnxOamPmCfgThrLossUndtUnavlClr."
    ::= { tmnxOamPmNotificationObjs 6 }

tmnxOamPmNotifThrOperRaise       OBJECT-TYPE
    SYNTAX      Unsigned32
    MAX-ACCESS  accessible-for-notify
    STATUS      current
    DESCRIPTION
        "The value of tmnxOamPmNotifThrOperRaise indicates the value of the
         delay or loss counter which met or exceeded tmnxOamPmNotifThrCfgRaise,
         resulting in the OAM-PM Raise trap being reported.

         The value reported is one of the following (where the selection is
         made by other objects in the trap):
            tmnxOamPmStsDelayDmmBin2wyCount,
            tmnxOamPmStsDelayDmmBinBwdCount,
            tmnxOamPmStsDelayDmmBinFwdCount,
            tmnxOamPmStsDelayMplsBin2wyCount,
            tmnxOamPmStsDelayMplsBinBwdCount,
            tmnxOamPmStsDelayMplsBinFwdCount,
            tmnxOamPmStsDelayTwlBin2wyCount,
            tmnxOamPmStsDelayTwlBinBwdCount,
            tmnxOamPmStsDelayTwlBinFwdCount,
            tmnxOamPmStsLossLmmAvgFlrBwd,
            tmnxOamPmStsLossLmmAvgFlrFwd,
            tmnxOamPmStsLossLmmChliBwd,
            tmnxOamPmStsLossLmmChliFwd + tmnxOamPmStsLossLmmChliBwd,
            tmnxOamPmStsLossLmmChliFwd,
            tmnxOamPmStsLossLmmHliBwd,
            tmnxOamPmStsLossLmmHliFwd + tmnxOamPmStsLossLmmHliBwd,
            tmnxOamPmStsLossLmmHliFwd,
            tmnxOamPmStsLossLmmUnavlIndBwd,
            tmnxOamPmStsLossLmmUnavlIndFwd + tmnxOamPmStsLossLmmUnavlIndBwd,
            tmnxOamPmStsLossLmmUnavlIndFwd,
            tmnxOamPmStsLossLmmUndtAvlBwd,
            tmnxOamPmStsLossLmmUndtAvlFwd + tmnxOamPmStsLossLmmUndtAvlBwd,
            tmnxOamPmStsLossLmmUndtAvlFwd,
            tmnxOamPmStsLossLmmUndtUnavlBwd,
            tmnxOamPmStsLossLmmUndtUnavlFwd + tmnxOamPmStsLossLmmUndtUnavlBwd,
            tmnxOamPmStsLossLmmUndtUnavlFwd,
            tmnxOamPmStsLossSlmAvgFlrBwd,
            tmnxOamPmStsLossSlmAvgFlrFwd,
            tmnxOamPmStsLossSlmChliBwd,
            tmnxOamPmStsLossSlmChliFwd + tmnxOamPmStsLossSlmChliBwd,
            tmnxOamPmStsLossSlmChliFwd,
            tmnxOamPmStsLossSlmHliBwd,
            tmnxOamPmStsLossSlmHliFwd + tmnxOamPmStsLossSlmHliBwd,
            tmnxOamPmStsLossSlmHliFwd,
            tmnxOamPmStsLossSlmUnavlIndBwd,
            tmnxOamPmStsLossSlmUnavlIndFwd + tmnxOamPmStsLossSlmUnavlIndBwd,
            tmnxOamPmStsLossSlmUnavlIndFwd,
            tmnxOamPmStsLossSlmUndtAvlBwd,
            tmnxOamPmStsLossSlmUndtAvlFwd + tmnxOamPmStsLossSlmUndtAvlBwd,
            tmnxOamPmStsLossSlmUndtAvlFwd,
            tmnxOamPmStsLossSlmUndtUnavlBwd,
            tmnxOamPmStsLossSlmUndtUnavlFwd + tmnxOamPmStsLossSlmUndtUnavlBwd,
            tmnxOamPmStsLossSlmUndtUnavlFwd,
            tmnxOamPmStsLossTwlAvgFlrBwd,
            tmnxOamPmStsLossTwlAvgFlrFwd,
            tmnxOamPmStsLossTwlChliBwd,
            tmnxOamPmStsLossTwlChliFwd + tmnxOamPmStsLossTwlChliBwd,
            tmnxOamPmStsLossTwlChliFwd,
            tmnxOamPmStsLossTwlHliBwd,
            tmnxOamPmStsLossTwlHliFwd + tmnxOamPmStsLossTwlHliBwd,
            tmnxOamPmStsLossTwlHliFwd,
            tmnxOamPmStsLossTwlUnavlIndBwd,
            tmnxOamPmStsLossTwlUnavlIndFwd + tmnxOamPmStsLossTwlUnavlIndBwd,
            tmnxOamPmStsLossTwlUnavlIndFwd,
            tmnxOamPmStsLossTwlUndtAvlBwd,
            tmnxOamPmStsLossTwlUndtAvlFwd + tmnxOamPmStsLossTwlUndtAvlBwd,
            tmnxOamPmStsLossTwlUndtAvlFwd,
            tmnxOamPmStsLossTwlUndtUnavlBwd,
            tmnxOamPmStsLossTwlUndtUnavlFwd + tmnxOamPmStsLossTwlUndtUnavlBwd,
            or
            tmnxOamPmStsLossTwlUndtUnavlFwd.

         One of the '2wy' values is reported when tmnxOamPmNotifThrDirection is
         'twoWay(3)'.

         One of the summed values is reported when tmnxOamPmNotifThrDirection
         is 'aggregate(4)'."
    ::= { tmnxOamPmNotificationObjs 7 }

tmnxOamPmNotifThrOperClear       OBJECT-TYPE
    SYNTAX      Unsigned32
    MAX-ACCESS  accessible-for-notify
    STATUS      current
    DESCRIPTION
        "The value of tmnxOamPmNotifThrOperClear indicates the value of the
         delay or loss counter which met or fell below
         tmnxOamPmNotifThrCfgClear, resulting in the OAM-PM Clear trap being
         reported.

         The value reported is one of the values shown in the
         tmnxOamPmNotifThrOperRaise DESCRIPTION clause."
    ::= { tmnxOamPmNotificationObjs 8 }

tmnxOamPmNotifThrBinLowerBound   OBJECT-TYPE
    SYNTAX      Unsigned32
    UNITS       "microseconds"
    MAX-ACCESS  accessible-for-notify
    STATUS      current
    DESCRIPTION
        "The value of tmnxOamPmNotifThrBinLowerBound indicates the configured
         lower bound (in microseconds) of the MEF-35 delay bin which is the
         subject of the enclosing notification.

         When this object is part of a tmnxOamPmThrRaise notification, the
         notification was raised because the number of PDUs with delay greater
         than or equal to tmnxOamPmNotifThrBinLowerBound (in the specified
         measurement interval) met or exceeded the configured threshold
         tmnxOamPmCfgThrDelayRaise.

         When this object is part of a tmnxOamPmThrClear notification, the
         notification was raised because the number of PDUs with delay greater
         than or equal to tmnxOamPmNotifThrBinLowerBound (in the specified
         measurement interval) was less than or equal to the configured
         threshold tmnxOamPmCfgThrDelayClear.

         For example, suppose an OAM-PM delay raise threshold is configured with
         tmnxOamPmCfgThrDelayRaise = 1000 and tmnxOamPmCfgThrDelayLowestBin = 6.
         Suppose the configured lower bound (i.e. tmnxOamPmCfgBinLowerBound) for
         the specified bin 6 is 30,000 microseconds.  Then, if the count of PDUs
         with delay at or above 30,000 microseconds (e.g.
         tmnxOamPmStsDelayDmmBin2wyCount) is 1000, and a TCA is raised, this
         object will report 30,000.

         This value must be ignored if the enclosing notification is a loss TCA
         (i.e. when tmnxOamPmNotifThrType is not 'delay(1)')."
    REFERENCE
        "MEF-35, 'Service OAM Performance Monitoring Implementation Agreement',
         Metro Ethernet Forum, April 2012, Section 9.2.2 'Measurement Bins'"
    ::= { tmnxOamPmNotificationObjs 9 }

tmnxOamPmConformance             OBJECT IDENTIFIER ::= { tmnxSRConfs 92 }

tmnxOamPmCompliances             OBJECT IDENTIFIER ::= { tmnxOamPmConformance 1 }

tmnxOamPmV12v0Compliance         MODULE-COMPLIANCE
    STATUS      obsolete
    DESCRIPTION
        "The compliance statement for management of OAM Performance Monitoring
         on Nokia SROS series systems, release 12.0."
    MODULE
        MANDATORY-GROUPS {
            tmnxOamPmV12v0ObjGroup
        }
    ::= { tmnxOamPmCompliances 1 }

tmnxOamPmV13v0Compliance         MODULE-COMPLIANCE
    STATUS      obsolete
    DESCRIPTION
        "The compliance statement for management of additional OAM Performance
         Monitoring objects on Nokia SROS series systems, release 13.0."
    MODULE
        MANDATORY-GROUPS {
            tmnxOamPmV13v0NotifGroup,
            tmnxOamPmV13v0ObjGroup
        }
    ::= { tmnxOamPmCompliances 2 }

tmnxOamPmV14v0Compliance         MODULE-COMPLIANCE
    STATUS      obsolete
    DESCRIPTION
        "The compliance statement for management of additional OAM Performance
         Monitoring objects on Nokia SROS series systems, release 14.0."
    MODULE
        MANDATORY-GROUPS {
            tmnxOamPmV14v0NotifyObjsGroup,
            tmnxOamPmV14v0ObjGroup
        }
    ::= { tmnxOamPmCompliances 3 }

tmnxOamPmV15v0Compliance         MODULE-COMPLIANCE
    STATUS      obsolete
    DESCRIPTION
        "The compliance statement for management of additional OAM Performance
         Monitoring objects on Nokia SROS series systems, release 15.0."
    MODULE
        MANDATORY-GROUPS {
            tmnxOamPmV15v0ObjGroup
        }
    ::= { tmnxOamPmCompliances 4 }

tmnxOamPmV16v0Compliance         MODULE-COMPLIANCE
    STATUS      obsolete
    DESCRIPTION
        "The compliance statement for management of additional OAM Performance
         Monitoring objects on Nokia SROS series systems, release 16.0."
    MODULE
        MANDATORY-GROUPS {
            tmnxOamPmV16v0ObjGroup
        }
    ::= { tmnxOamPmCompliances 5 }

tmnxOamPmV19v0Compliance         MODULE-COMPLIANCE
    STATUS      current
    DESCRIPTION
        "The compliance statement for management of OAM Performance Monitoring
         objects on Nokia SROS series systems, release 19.0."
    MODULE
        MANDATORY-GROUPS {
            tmnxOamPmV12v0ObjGroup,
            tmnxOamPmV13v0NotifGroup,
            tmnxOamPmV13v0ObjGroup,
            tmnxOamPmV14v0NotifyObjsGroup,
            tmnxOamPmV14v0ObjGroup,
            tmnxOamPmV15v0ObjGroup,
            tmnxOamPmV16v0ObjGroup,
            tmnxOamPmStrDlyAvgV19v0ObjGroup
        }
    ::= { tmnxOamPmCompliances 6 }

tmnxOamPmV20v0Compliance         MODULE-COMPLIANCE
    STATUS      current
    DESCRIPTION
        "The compliance statement for management of additional OAM Performance
         Monitoring objects on Nokia SROS series systems, release 20."
    MODULE
        MANDATORY-GROUPS {
            tmnxOamPmLimitsV20v0ObjGroup
        }
    ::= { tmnxOamPmCompliances 7 }

tmnxOamPmV21v0Compliance         MODULE-COMPLIANCE
    STATUS      current
    DESCRIPTION
        "The compliance statement for management of additional OAM Performance
         Monitoring objects on Nokia SROS series systems, release 21."
    MODULE
        MANDATORY-GROUPS {
            tmnxOamPmTwlRflV21v0ObjGroup
        }
    ::= { tmnxOamPmCompliances 8 }

tmnxOamPmV22v0Compliance         MODULE-COMPLIANCE
    STATUS      current
    DESCRIPTION
        "The compliance statement for management of additional OAM Performance
         Monitoring objects on Nokia SROS series systems, release 22."
    MODULE
        MANDATORY-GROUPS {
            tmnxOamPmTwampLightV22v0ObjGroup,
            tmnxOamPmTwlRflV22v0ObjGroup
        }
    ::= { tmnxOamPmCompliances 9 }

tmnxOamPmV23v0Compliance         MODULE-COMPLIANCE
    STATUS      current
    DESCRIPTION
        "The compliance statement for management of additional OAM Performance
         Monitoring objects on Nokia SROS series systems, release 23."
    MODULE
        MANDATORY-GROUPS {
            tmnxOamPmStampTestV23v0ObjGroup,
            tmnxOamPmAutoTestIdV23v0ObjGroup
        }
    ::= { tmnxOamPmCompliances 10 }

tmnxOamPmV24v0Compliance         MODULE-COMPLIANCE
    STATUS      current
    DESCRIPTION
        "The compliance statement for management of additional OAM Performance
         Monitoring objects on Nokia SROS series systems, release 24."
    MODULE
        MANDATORY-GROUPS {
            tmnxOamPmIpTnMplsSRPV24v0ObjGrp,
            tmnxOamPmLagMeasV24v0ObjGroup,
            tmnxOamPmStampV24v0ObjGroup
        }
    ::= { tmnxOamPmCompliances 11 }

tmnxOamPmObjGroups               OBJECT IDENTIFIER ::= { tmnxOamPmConformance 2 }

tmnxOamPmV12v0ObjGroups          OBJECT IDENTIFIER ::= { tmnxOamPmObjGroups 1 }

tmnxOamPmV12v0ObjGroup           OBJECT-GROUP
    OBJECTS     {
        tmnxOamPmCfgBinGroupAdminStatus,
        tmnxOamPmCfgBinGroupDescription,
        tmnxOamPmCfgBinGroupFdBinCount,
        tmnxOamPmCfgBinGroupFdrBinCount,
        tmnxOamPmCfgBinGroupIfdvBinCount,
        tmnxOamPmCfgBinGroupRowStatus,
        tmnxOamPmCfgBinGroupTableLastChg,
        tmnxOamPmCfgBinLowerBound,
        tmnxOamPmCfgBinTableLastChg,
        tmnxOamPmCfgDelayDmmAdminStatus,
        tmnxOamPmCfgDelayDmmDataTlvSize,
        tmnxOamPmCfgDelayDmmInterval,
        tmnxOamPmCfgDelayDmmOnDmndStatus,
        tmnxOamPmCfgDelayDmmRowStatus,
        tmnxOamPmCfgDelayDmmRunTimeLeft,
        tmnxOamPmCfgDelayDmmTableLastChg,
        tmnxOamPmCfgDelayDmmTestDuration,
        tmnxOamPmCfgDelayDmmTestId,
        tmnxOamPmCfgLossSlmAdminStatus,
        tmnxOamPmCfgLossSlmChliThreshold,
        tmnxOamPmCfgLossSlmConsecDeltaTs,
        tmnxOamPmCfgLossSlmDataTlvSize,
        tmnxOamPmCfgLossSlmFlrThreshold,
        tmnxOamPmCfgLossSlmInterval,
        tmnxOamPmCfgLossSlmOnDmndStatus,
        tmnxOamPmCfgLossSlmRowStatus,
        tmnxOamPmCfgLossSlmRunTimeLeft,
        tmnxOamPmCfgLossSlmTableLastChg,
        tmnxOamPmCfgLossSlmTestDuration,
        tmnxOamPmCfgLossSlmTestId,
        tmnxOamPmCfgLossSlmTxFrmsPerDelT,
        tmnxOamPmCfgMeasIntvlAccntPolicy,
        tmnxOamPmCfgMeasIntvlBoundaryTyp,
        tmnxOamPmCfgMeasIntvlClockOffset,
        tmnxOamPmCfgMeasIntvlRowStatus,
        tmnxOamPmCfgMeasIntvlTableLstChg,
        tmnxOamPmCfgMeasIntvlsStored,
        tmnxOamPmCfgSessBinGroupId,
        tmnxOamPmCfgSessDescription,
        tmnxOamPmCfgSessEthDestMacAddr,
        tmnxOamPmCfgSessEthPriority,
        tmnxOamPmCfgSessEthSrcMaIndex,
        tmnxOamPmCfgSessEthSrcMdIndex,
        tmnxOamPmCfgSessEthSrcMepId,
        tmnxOamPmCfgSessEthTableLastChg,
        tmnxOamPmCfgSessRowStatus,
        tmnxOamPmCfgSessTableLastChg,
        tmnxOamPmCfgSessTestFamily,
        tmnxOamPmCfgSessType,
        tmnxOamPmStsBaseElapsedTime,
        tmnxOamPmStsBaseOperStatus,
        tmnxOamPmStsBaseStartTime,
        tmnxOamPmStsBaseSuspect,
        tmnxOamPmStsBaseTestFramesRx,
        tmnxOamPmStsBaseTestFramesTx,
        tmnxOamPmStsDelayDmm2wyAvg,
        tmnxOamPmStsDelayDmm2wyMax,
        tmnxOamPmStsDelayDmm2wyMin,
        tmnxOamPmStsDelayDmmBin2wyCount,
        tmnxOamPmStsDelayDmmBinBwdCount,
        tmnxOamPmStsDelayDmmBinFwdCount,
        tmnxOamPmStsDelayDmmBwdAvg,
        tmnxOamPmStsDelayDmmBwdMax,
        tmnxOamPmStsDelayDmmBwdMin,
        tmnxOamPmStsDelayDmmFwdAvg,
        tmnxOamPmStsDelayDmmFwdMax,
        tmnxOamPmStsDelayDmmFwdMin,
        tmnxOamPmStsLossSlmAvailIndBwd,
        tmnxOamPmStsLossSlmAvailIndFwd,
        tmnxOamPmStsLossSlmAvgFlrBwd,
        tmnxOamPmStsLossSlmAvgFlrFwd,
        tmnxOamPmStsLossSlmChliBwd,
        tmnxOamPmStsLossSlmChliFwd,
        tmnxOamPmStsLossSlmHliBwd,
        tmnxOamPmStsLossSlmHliFwd,
        tmnxOamPmStsLossSlmMaxFlrBwd,
        tmnxOamPmStsLossSlmMaxFlrFwd,
        tmnxOamPmStsLossSlmMinFlrBwd,
        tmnxOamPmStsLossSlmMinFlrFwd,
        tmnxOamPmStsLossSlmRxBwd,
        tmnxOamPmStsLossSlmRxFwd,
        tmnxOamPmStsLossSlmTxBwd,
        tmnxOamPmStsLossSlmTxFwd,
        tmnxOamPmStsLossSlmUnavlIndBwd,
        tmnxOamPmStsLossSlmUnavlIndFwd,
        tmnxOamPmStsLossSlmUndtAvlBwd,
        tmnxOamPmStsLossSlmUndtAvlFwd,
        tmnxOamPmStsLossSlmUndtUnavlBwd,
        tmnxOamPmStsLossSlmUndtUnavlFwd,
        tmnxOamPmStsMeasIntvlIndexNewest,
        tmnxOamPmCfgSessIpBypassRouting,
        tmnxOamPmCfgSessIpDstAddress,
        tmnxOamPmCfgSessIpDstAddressType,
        tmnxOamPmCfgSessIpDstUdpPort,
        tmnxOamPmCfgSessIpEgressIfName,
        tmnxOamPmCfgSessIpForwardClass,
        tmnxOamPmCfgSessIpNhAddress,
        tmnxOamPmCfgSessIpNhAddressType,
        tmnxOamPmCfgSessIpProfile,
        tmnxOamPmCfgSessIpServiceId,
        tmnxOamPmCfgSessIpSrcAddress,
        tmnxOamPmCfgSessIpSrcAddressType,
        tmnxOamPmCfgSessIpSrcUdpPort,
        tmnxOamPmCfgSessIpTableLastChg,
        tmnxOamPmCfgSessIpTtl,
        tmnxOamPmCfgTwampLtAdminStatus,
        tmnxOamPmCfgTwampLtInterval,
        tmnxOamPmCfgTwampLtOnDmndStatus,
        tmnxOamPmCfgTwampLtPadSize,
        tmnxOamPmCfgTwampLtRowStatus,
        tmnxOamPmCfgTwampLtRunTimeLeft,
        tmnxOamPmCfgTwampLtTableLastChg,
        tmnxOamPmCfgTwampLtTestDuration,
        tmnxOamPmCfgTwampLtTestId,
        tmnxOamPmCfgTwlRflAdminStatus,
        tmnxOamPmCfgTwlRflDescription,
        tmnxOamPmCfgTwlRflInactTimer,
        tmnxOamPmCfgTwlRflListenUdpPort,
        tmnxOamPmCfgTwlRflPfxDescription,
        tmnxOamPmCfgTwlRflPfxRowStatus,
        tmnxOamPmCfgTwlRflPfxTableLstChg,
        tmnxOamPmCfgTwlRflRowStatus,
        tmnxOamPmCfgTwlRflTableLastChg,
        tmnxOamPmStsDelayTwl2wyAvg,
        tmnxOamPmStsDelayTwl2wyMax,
        tmnxOamPmStsDelayTwl2wyMin,
        tmnxOamPmStsDelayTwlBin2wyCount,
        tmnxOamPmStsDelayTwlBinBwdCount,
        tmnxOamPmStsDelayTwlBinFwdCount,
        tmnxOamPmStsDelayTwlBwdAvg,
        tmnxOamPmStsDelayTwlBwdMax,
        tmnxOamPmStsDelayTwlBwdMin,
        tmnxOamPmStsDelayTwlFwdAvg,
        tmnxOamPmStsDelayTwlFwdMax,
        tmnxOamPmStsDelayTwlFwdMin,
        tmnxOamPmStsTwlRflFramesRx,
        tmnxOamPmStsTwlRflFramesTx,
        tmnxOamPmStsTwlRflUpTime,
        tmnxOamPmCfgLossLmmAdminStatus,
        tmnxOamPmCfgLossLmmInterval,
        tmnxOamPmCfgLossLmmOnDmndStatus,
        tmnxOamPmCfgLossLmmRowStatus,
        tmnxOamPmCfgLossLmmRunTimeLeft,
        tmnxOamPmCfgLossLmmTableLastChg,
        tmnxOamPmCfgLossLmmTestDuration,
        tmnxOamPmCfgLossLmmTestId,
        tmnxOamPmStsLossLmmAvgFlrBwd,
        tmnxOamPmStsLossLmmAvgFlrFwd,
        tmnxOamPmStsLossLmmMaxFlrBwd,
        tmnxOamPmStsLossLmmMaxFlrFwd,
        tmnxOamPmStsLossLmmMinFlrBwd,
        tmnxOamPmStsLossLmmMinFlrFwd,
        tmnxOamPmStsLossLmmRxBwd,
        tmnxOamPmStsLossLmmRxFwd,
        tmnxOamPmStsLossLmmTxBwd,
        tmnxOamPmStsLossLmmTxFwd
    }
    STATUS      current
    DESCRIPTION
        "The group of objects supporting the OAM Performance Monitoring
         functionality on Nokia SROS Release 12.0."
    ::= { tmnxOamPmV12v0ObjGroups 1 }

tmnxOamPmV13v0ObjGroups          OBJECT IDENTIFIER ::= { tmnxOamPmObjGroups 2 }

tmnxOamPmV13v0ObjGroup           OBJECT-GROUP
    OBJECTS     {
        tmnxOamPmCfgMeasIntvlDelayTCAs,
        tmnxOamPmCfgMeasIntvlLossTCAs,
        tmnxOamPmCfgMeasIntvlTCAs,
        tmnxOamPmCfgThrDelayClear,
        tmnxOamPmCfgThrDelayLowestBin,
        tmnxOamPmCfgThrDelayRaise,
        tmnxOamPmCfgThrDelayTableLastChg,
        tmnxOamPmCfgThrLossAvgFlrClear,
        tmnxOamPmCfgThrLossAvgFlrRaise,
        tmnxOamPmCfgThrLossChliClear,
        tmnxOamPmCfgThrLossChliRaise,
        tmnxOamPmCfgThrLossFwBwAgTableLC,
        tmnxOamPmCfgThrLossFwBwTableLChg,
        tmnxOamPmCfgThrLossHliClear,
        tmnxOamPmCfgThrLossHliRaise,
        tmnxOamPmCfgThrLossUnavlIndClear,
        tmnxOamPmCfgThrLossUnavlIndRaise,
        tmnxOamPmCfgThrLossUndtAvlClear,
        tmnxOamPmCfgThrLossUndtAvlRaise,
        tmnxOamPmCfgThrLossUndtUnavlClr,
        tmnxOamPmCfgThrLossUndtUnavlRais,
        tmnxOamPmCfgTwampLtChliThreshold,
        tmnxOamPmCfgTwampLtCollectStats,
        tmnxOamPmCfgTwampLtConsecDeltaTs,
        tmnxOamPmCfgTwampLtFlrThreshold,
        tmnxOamPmCfgTwampLtTxFrmsPerDelT,
        tmnxOamPmStsLossTwlAvailIndBwd,
        tmnxOamPmStsLossTwlAvailIndFwd,
        tmnxOamPmStsLossTwlAvgFlrBwd,
        tmnxOamPmStsLossTwlAvgFlrFwd,
        tmnxOamPmStsLossTwlChliBwd,
        tmnxOamPmStsLossTwlChliFwd,
        tmnxOamPmStsLossTwlHliBwd,
        tmnxOamPmStsLossTwlHliFwd,
        tmnxOamPmStsLossTwlMaxFlrBwd,
        tmnxOamPmStsLossTwlMaxFlrFwd,
        tmnxOamPmStsLossTwlMinFlrBwd,
        tmnxOamPmStsLossTwlMinFlrFwd,
        tmnxOamPmStsLossTwlRxBwd,
        tmnxOamPmStsLossTwlRxFwd,
        tmnxOamPmStsLossTwlTxBwd,
        tmnxOamPmStsLossTwlTxFwd,
        tmnxOamPmStsLossTwlUnavlIndBwd,
        tmnxOamPmStsLossTwlUnavlIndFwd,
        tmnxOamPmStsLossTwlUndtAvlBwd,
        tmnxOamPmStsLossTwlUndtAvlFwd,
        tmnxOamPmStsLossTwlUndtUnavlBwd,
        tmnxOamPmStsLossTwlUndtUnavlFwd,
        tmnxOamPmStsSessIpSrcUdpPort,
        tmnxOamPmStsTcaDelayLastTime,
        tmnxOamPmStsTcaDelayOperState,
        tmnxOamPmStsTcaLossAvgFlrLstTime,
        tmnxOamPmStsTcaLossAvgFlrOperSt,
        tmnxOamPmStsTcaLossChliLastTime,
        tmnxOamPmStsTcaLossChliOperState,
        tmnxOamPmStsTcaLossHliLastTime,
        tmnxOamPmStsTcaLossHliOperState,
        tmnxOamPmStsTcaLossUnavlIndLTime,
        tmnxOamPmStsTcaLossUnavlIndOprSt,
        tmnxOamPmStsTcaLossUndtAvlLTime,
        tmnxOamPmStsTcaLossUndtAvlOperSt,
        tmnxOamPmStsTcaLossUndtUnavlLTim,
        tmnxOamPmStsTcaLossUndtUnavlOpSt
    }
    STATUS      current
    DESCRIPTION
        "The group of additional objects supporting the OAM Performance
         Monitoring functionality on Nokia SROS Release 13.0."
    ::= { tmnxOamPmV13v0ObjGroups 1 }

tmnxOamPmV14v0ObjGroups          OBJECT IDENTIFIER ::= { tmnxOamPmObjGroups 3 }

tmnxOamPmV14v0ObjGroup           OBJECT-GROUP
    OBJECTS     {
        tmnxOamPmCfgBgTyDirExclBinsFrAvg,
        tmnxOamPmCfgBinGrpTypeDirTableLC,
        tmnxOamPmCfgThrDelayExclBinFrTca,
        tmnxOamPmStsTestDetectTxError,
        tmnxOamPmCfgLossLmmAvAdminStatus,
        tmnxOamPmCfgLossLmmChliThreshold,
        tmnxOamPmCfgLossLmmConsecDeltaTs,
        tmnxOamPmCfgLossLmmFlrThreshold,
        tmnxOamPmCfgLossLmmTxFrmsPerDelT,
        tmnxOamPmStsLossLmmAvailIndBwd,
        tmnxOamPmStsLossLmmAvailIndFwd,
        tmnxOamPmStsLossLmmChliBwd,
        tmnxOamPmStsLossLmmChliFwd,
        tmnxOamPmStsLossLmmHliBwd,
        tmnxOamPmStsLossLmmHliFwd,
        tmnxOamPmStsLossLmmUnavlIndBwd,
        tmnxOamPmStsLossLmmUnavlIndFwd,
        tmnxOamPmStsLossLmmUndetDelTsBwd,
        tmnxOamPmStsLossLmmUndetDelTsFwd,
        tmnxOamPmStsLossLmmUndtAvlBwd,
        tmnxOamPmStsLossLmmUndtAvlFwd,
        tmnxOamPmStsLossLmmUndtUnavlBwd,
        tmnxOamPmStsLossLmmUndtUnavlFwd
    }
    STATUS      current
    DESCRIPTION
        "The group of additional objects supporting the OAM Performance
         Monitoring functionality on Nokia SROS Release 14.0."
    ::= { tmnxOamPmV14v0ObjGroups 1 }

tmnxOamPmV15v0ObjGroups          OBJECT IDENTIFIER ::= { tmnxOamPmObjGroups 4 }

tmnxOamPmV15v0ObjGroup           OBJECT-GROUP
    OBJECTS     {
        tmnxOamPmCfgLossLmmCollFcAdminSt,
        tmnxOamPmCfgLossLmmHliForceCount,
        tmnxOamPmCfgLossSlmHliForceCount,
        tmnxOamPmCfgSessEthRemoteMepId,
        tmnxOamPmCfgSessIpDoNotFragment,
        tmnxOamPmCfgSessIpDscpEgrRemark,
        tmnxOamPmCfgSessIpDscpName,
        tmnxOamPmCfgSessIpPadPattern,
        tmnxOamPmCfgTwampLtHliForceCount
    }
    STATUS      current
    DESCRIPTION
        "The group of additional objects supporting the OAM Performance
         Monitoring functionality on Nokia SROS Release 15.0."
    ::= { tmnxOamPmV15v0ObjGroups 1 }

tmnxOamPmV16v0ObjGroups          OBJECT IDENTIFIER ::= { tmnxOamPmObjGroups 5 }

tmnxOamPmV16v0ObjGroup           OBJECT-GROUP
    OBJECTS     {
        tmnxOamPmCfgDelayMplsAdminStatus,
        tmnxOamPmCfgDelayMplsInterval,
        tmnxOamPmCfgDelayMplsOnDmdStatus,
        tmnxOamPmCfgDelayMplsPadTlvSize,
        tmnxOamPmCfgDelayMplsReflectPad,
        tmnxOamPmCfgDelayMplsRowStatus,
        tmnxOamPmCfgDelayMplsRunTimeLeft,
        tmnxOamPmCfgDelayMplsTableLstChg,
        tmnxOamPmCfgDelayMplsTestId,
        tmnxOamPmCfgDelayMplsTstDuration,
        tmnxOamPmCfgMplsDmAdminStatus,
        tmnxOamPmCfgSessEthSrcMaName,
        tmnxOamPmCfgSessEthSrcMdName,
        tmnxOamPmCfgSessIpRouterInstName,
        tmnxOamPmCfgSessMplsDscpName,
        tmnxOamPmCfgSessMplsForwardClass,
        tmnxOamPmCfgSessMplsLspType,
        tmnxOamPmCfgSessMplsPadPattern,
        tmnxOamPmCfgSessMplsProfile,
        tmnxOamPmCfgSessMplsRaFrAddrType,
        tmnxOamPmCfgSessMplsRaFrAddress,
        tmnxOamPmCfgSessMplsRaRetAddrTyp,
        tmnxOamPmCfgSessMplsRaRetAddress,
        tmnxOamPmCfgSessMplsRaTemplName,
        tmnxOamPmCfgSessMplsRaToAddrType,
        tmnxOamPmCfgSessMplsRaToAddress,
        tmnxOamPmCfgSessMplsRsvpAutTblLC,
        tmnxOamPmCfgSessMplsRsvpLspName,
        tmnxOamPmCfgSessMplsRsvpRetAddr,
        tmnxOamPmCfgSessMplsRsvpRetAddrT,
        tmnxOamPmCfgSessMplsRsvpTableLC,
        tmnxOamPmCfgSessMplsTableLastChg,
        tmnxOamPmCfgSessMplsTpLspName,
        tmnxOamPmCfgSessMplsTpTableLChg,
        tmnxOamPmCfgSessMplsTtl,
        tmnxOamPmCfgSessOrigin,
        tmnxOamPmStsDelayMpls2wyAvg,
        tmnxOamPmStsDelayMpls2wyMax,
        tmnxOamPmStsDelayMpls2wyMin,
        tmnxOamPmStsDelayMplsBin2wyCount,
        tmnxOamPmStsDelayMplsBinBwdCount,
        tmnxOamPmStsDelayMplsBinFwdCount,
        tmnxOamPmStsDelayMplsBwdAvg,
        tmnxOamPmStsDelayMplsBwdMax,
        tmnxOamPmStsDelayMplsBwdMin,
        tmnxOamPmStsDelayMplsFwdAvg,
        tmnxOamPmStsDelayMplsFwdMax,
        tmnxOamPmStsDelayMplsFwdMin,
        tmnxOamPmStsMplsDmUdpPort,
        tmnxOamPmStsMplsTestRxStatus
    }
    STATUS      current
    DESCRIPTION
        "The group of additional objects supporting the OAM Performance
         Monitoring functionality on Nokia SROS Release 16.0."
    ::= { tmnxOamPmV16v0ObjGroups 1 }

tmnxOamPmV19v0ObjGroups          OBJECT IDENTIFIER ::= { tmnxOamPmObjGroups 6 }

tmnxOamPmStrDlyAvgV19v0ObjGroup  OBJECT-GROUP
    OBJECTS     {
        tmnxOamPmCfgDelayDmmStrTmplName,
        tmnxOamPmCfgDelayMplsStrTmplName,
        tmnxOamPmCfgStrMeasRowStatus,
        tmnxOamPmCfgStrMeasTableLastChg,
        tmnxOamPmCfgStrTmplAdminStatus,
        tmnxOamPmCfgStrTmplDescription,
        tmnxOamPmCfgStrTmplRowStatus,
        tmnxOamPmCfgStrTmplSampleWindow,
        tmnxOamPmCfgStrTmplTableLastChg,
        tmnxOamPmCfgStrTmplWindowInteg,
        tmnxOamPmCfgTwampLtStrTmplName,
        tmnxOamPmStsStrCloseTime,
        tmnxOamPmStsStrDelay,
        tmnxOamPmStsStrSampleCount,
        tmnxOamPmStsStrSuspect
    }
    STATUS      current
    DESCRIPTION
        "The group of additional objects supporting the OAM Performance
         Monitoring streaming delay averaging functionality on Nokia SROS
         Release 19.0."
    ::= { tmnxOamPmV19v0ObjGroups 1 }

tmnxOamPmLimitsV20v0ObjGroups    OBJECT IDENTIFIER ::= { tmnxOamPmObjGroups 7 }

tmnxOamPmLimitsV20v0ObjGroup     OBJECT-GROUP
    OBJECTS     {
        tmnxOamPmStsTestCount,
        tmnxOamPmStsTestLimit,
        tmnxOamPmStsTxLimit,
        tmnxOamPmStsTxTotal
    }
    STATUS      current
    DESCRIPTION
        "The group of additional objects supporting the OAM Performance
         Monitoring session and transmit limits on Nokia SROS Release 20."
    ::= { tmnxOamPmLimitsV20v0ObjGroups 1 }

tmnxOamPmV21v0ObjGroups          OBJECT IDENTIFIER ::= { tmnxOamPmObjGroups 8 }

tmnxOamPmTwlRflV21v0ObjGroup     OBJECT-GROUP
    OBJECTS     {
        tmnxOamPmCfgTwlRflIpv6UdpZero
    }
    STATUS      current
    DESCRIPTION
        "The group of additional objects supporting the OAM Performance
         Monitoring TWAMP-Light Reflector functionality on Nokia SROS Release
         21."
    ::= { tmnxOamPmV21v0ObjGroups 1 }

tmnxOamPmV22v0ObjGroups          OBJECT IDENTIFIER ::= { tmnxOamPmObjGroups 9 }

tmnxOamPmTwampLightV22v0ObjGroup OBJECT-GROUP
    OBJECTS     {
        tmnxOamPmCfgTwampLtIPv6UdpCsZero
    }
    STATUS      current
    DESCRIPTION
        "The group of additional objects supporting the OAM Performance
         Monitoring TWAMP-Light functionality on Nokia SROS Release 22."
    ::= { tmnxOamPmV22v0ObjGroups 1 }

tmnxOamPmTwlRflV22v0ObjGroup     OBJECT-GROUP
    OBJECTS     {
        tmnxOamPmCfgTwlRflType
    }
    STATUS      current
    DESCRIPTION
        "The group of additional objects supporting the OAM Performance
         Monitoring TWAMP-Light Reflector STAMP Performance Measurement
         functionality on Nokia SROS Release 22."
    ::= { tmnxOamPmV22v0ObjGroups 2 }

tmnxOamPmV23v0ObjGroups          OBJECT IDENTIFIER ::= { tmnxOamPmObjGroups 10 }

tmnxOamPmStampTestV23v0ObjGroup  OBJECT-GROUP
    OBJECTS     {
        tmnxOamPmCfgSessIpLspDstPfx,
        tmnxOamPmCfgSessIpLspDstPfxLen,
        tmnxOamPmCfgSessIpLspDstPfxType,
        tmnxOamPmCfgSessIpLspFromAddrTyp,
        tmnxOamPmCfgSessIpLspFromAddress,
        tmnxOamPmCfgSessIpLspIgpInstance,
        tmnxOamPmCfgSessIpLspName,
        tmnxOamPmCfgSessIpLspTemplName,
        tmnxOamPmCfgSessIpLspToAddrType,
        tmnxOamPmCfgSessIpLspToAddress,
        tmnxOamPmCfgSessIpTunnelType,
        tmnxOamPmCfgSessIpTunnelTypeMpls,
        tmnxOamPmCfgTwampLtStpPadTlvSize,
        tmnxOamPmCfgTwampLtTestSubType,
        tmnxOamPmCfgTwampLtTimestampFmt,
        tmnxOamPmStsTwampLtStampMFlagRx,
        tmnxOamPmStsTwampLtStampUFlagRx
    }
    STATUS      current
    DESCRIPTION
        "The group of additional objects supporting the OAM Performance
         Monitoring STAMP tests on Nokia SROS Release 23."
    ::= { tmnxOamPmV23v0ObjGroups 1 }

tmnxOamPmAutoTestIdV23v0ObjGroup OBJECT-GROUP
    OBJECTS     {
        tmnxOamPmCfgDelayDmmIsAutoTestId,
        tmnxOamPmCfgDelayDmmTestIdInUse,
        tmnxOamPmCfgLossSlmIsAutoTestId,
        tmnxOamPmCfgLossSlmTestIdInUse,
        tmnxOamPmCfgTwampLtIsAutoTestId,
        tmnxOamPmCfgTwampLtTestIdInUse,
        tmnxOamPmCfgLossLmmIsAutoTestId,
        tmnxOamPmCfgLossLmmTestIdInUse
    }
    STATUS      current
    DESCRIPTION
        "The group of additional objects supporting the OAM Performance
         Monitoring automatic generation of the test identifiers on Nokia SROS
         Release 23."
    ::= { tmnxOamPmV23v0ObjGroups 2 }

tmnxOamPmV24v0ObjGroups          OBJECT IDENTIFIER ::= { tmnxOamPmObjGroups 11 }

tmnxOamPmLagMeasV24v0ObjGroup    OBJECT-GROUP
    OBJECTS     {
        tmnxOamPmCfgTwlRflLagMeasEnabled
    }
    STATUS      current
    DESCRIPTION
        "The group of additional objects supporting OAM LAG Measurement on
         Nokia SROS Release 24."
    ::= { tmnxOamPmV24v0ObjGroups 1 }

tmnxOamPmIpTnMplsSRPV24v0ObjGrp  OBJECT-GROUP
    OBJECTS     {
        tmnxOamPmCfgSessIpFlexAlgoId,
        tmnxOamPmCfgSessIpSrPlcyEnPtAddT,
        tmnxOamPmCfgSessIpSrPlcyEnPtAddr,
        tmnxOamPmCfgSessIpSrPolicyColor,
        tmnxOamPmCfgSessIpSrPlcySegList
    }
    STATUS      current
    DESCRIPTION
        "The group of additional objects supporting OAM-PM IP MPLS Segment
         Routing Policy tunneling on Nokia SROS Release 24."
    ::= { tmnxOamPmV24v0ObjGroups 2 }

tmnxOamPmStampV24v0ObjGroup      OBJECT-GROUP
    OBJECTS     {
        tmnxOamPmStsTwampLtStampSSID
    }
    STATUS      current
    DESCRIPTION
        "The group of additional objects supporting OAM-PM STAMP tests on Nokia
         SROS Release 24."
    ::= { tmnxOamPmV24v0ObjGroups 3 }

tmnxOamPmNotifGroups             OBJECT IDENTIFIER ::= { tmnxOamPmConformance 3 }

tmnxOamPmV12v0NotifGroups        OBJECT IDENTIFIER ::= { tmnxOamPmNotifGroups 1 }

tmnxOamPmV13v0NotifGroups        OBJECT IDENTIFIER ::= { tmnxOamPmNotifGroups 2 }

tmnxOamPmV13v0NotifGroup         NOTIFICATION-GROUP
    NOTIFICATIONS {
        tmnxOamPmThrClear,
        tmnxOamPmThrRaise
    }
    STATUS      current
    DESCRIPTION
        "The group of OAM Performance Monitoring notifications supported by
         Nokia SROS Release 13.0."
    ::= { tmnxOamPmV13v0NotifGroups 1 }

tmnxOamPmNfyObjGroups            OBJECT IDENTIFIER ::= { tmnxOamPmConformance 4 }

tmnxOamPmV12v0NfyObjGroups       OBJECT IDENTIFIER ::= { tmnxOamPmNfyObjGroups 1 }

tmnxOamPmV13v0NfyObjGroups       OBJECT IDENTIFIER ::= { tmnxOamPmNfyObjGroups 2 }

tmnxOamPmV13v0NotifyObjsGroup    OBJECT-GROUP
    OBJECTS     {
        tmnxOamPmNotifThrCfgClear,
        tmnxOamPmNotifThrCfgRaise,
        tmnxOamPmNotifThrDelayBinType,
        tmnxOamPmNotifThrDirection,
        tmnxOamPmNotifThrOperClear,
        tmnxOamPmNotifThrOperRaise,
        tmnxOamPmNotifThrStateType,
        tmnxOamPmNotifThrType
    }
    STATUS      current
    DESCRIPTION
        "The group of accessible-for-notify objects supporting the OAM
         Performance Monitoring functionality on Nokia SROS Release 13.0."
    ::= { tmnxOamPmV13v0NfyObjGroups 1 }

tmnxOamPmV14v0NfyObjGroups       OBJECT IDENTIFIER ::= { tmnxOamPmNfyObjGroups 3 }

tmnxOamPmV14v0NotifyObjsGroup    OBJECT-GROUP
    OBJECTS     {
        tmnxOamPmNotifThrBinLowerBound
    }
    STATUS      current
    DESCRIPTION
        "The group of accessible-for-notify objects supporting the OAM
         Performance Monitoring functionality on Nokia SROS Release 14.0."
    ::= { tmnxOamPmV14v0NfyObjGroups 1 }

tmnxOamPmNotifyPrefix            OBJECT IDENTIFIER ::= { tmnxSRNotifyPrefix 92 }

tmnxOamPmNotifications           OBJECT IDENTIFIER ::= { tmnxOamPmNotifyPrefix 0 }

tmnxOamPmThrRaise                NOTIFICATION-TYPE
    OBJECTS     {
        tmnxOamPmStsBaseStartTime,
        tmnxOamPmStsBaseSuspect,
        tmnxOamPmNotifThrType,
        tmnxOamPmNotifThrDirection,
        tmnxOamPmNotifThrDelayBinType,
        tmnxOamPmNotifThrStateType,
        tmnxOamPmNotifThrCfgRaise,
        tmnxOamPmNotifThrOperRaise,
        tmnxOamPmNotifThrBinLowerBound
    }
    STATUS      current
    DESCRIPTION
        "[CAUSE] A tmnxOamPmThrRaise trap is sent when an OAM-PM loss or delay
         counter meets or exceeds its configured raise threshold.

         If an Average Frame Loss Ratio (FLR) threshold (i.e.
         tmnxOamPmCfgThrLossAvgFlrRaise) is met or exceeded, the
         tmnxOamPmThrRaise trap is sent at the end of the measurement interval.
         If another type of threshold (e.g. tmnxOamPmCfgThrLossHliRaise) is met
         or exceeded, the tmnxOamPmThrRaise trap is sent when the problem is
         detected.  The Average FLR threshold is a special case because the
         measured Average FLR can fluctuate during a measurement interval.

         At most one tmnxOamPmThrRaise trap is sent per threshold type during
         one OAM-PM measurement interval.  For example, at most one
         tmnxOamPmThrRaise trap is sent to record an excessive High Loss
         Indicator (HLI) count in the forward direction seen in a particular 15
         minute interval belonging to the SLM test belonging to OAM-PM session
         'oamPmSession1'.

         OAM-PM thresholds are explained in the DESCRIPTION clauses of
         tmnxOamPmCfgThrDelayTable, tmnxOamPmCfgThrLossFwBwAgTable, and
         tmnxOamPmCfgThrLossFwBwTable.

         OAM-PM counters are explained in the DESCRIPTION clauses of the
         tmnxOamPmStatsTableObjs tables.

         [EFFECT] For an LMM test, the loss of live traffic has met or exceeded
         a configured threshold.  For the other test types, the loss or delay of
         OAM-PM test probes has met or exceeded a configured threshold,
         indicating possible excessive loss or excessive delay of live traffic.

         [RECOVERY] Fix the cause of the excessive loss or excessive delay."
    ::= { tmnxOamPmNotifications 1 }

tmnxOamPmThrClear                NOTIFICATION-TYPE
    OBJECTS     {
        tmnxOamPmStsBaseStartTime,
        tmnxOamPmStsBaseSuspect,
        tmnxOamPmNotifThrType,
        tmnxOamPmNotifThrDirection,
        tmnxOamPmNotifThrDelayBinType,
        tmnxOamPmNotifThrStateType,
        tmnxOamPmNotifThrCfgClear,
        tmnxOamPmNotifThrOperClear,
        tmnxOamPmNotifThrBinLowerBound
    }
    STATUS      current
    DESCRIPTION
        "[CAUSE] A tmnxOamPmThrClear trap is sent at the end of an OAM-PM
         measurement interval when a loss or delay counter meets or falls below
         its configured clear threshold.

         At most one tmnxOamPmThrClear trap is sent per tmnxOamPmThrRaise trap.

         OAM-PM thresholds are explained in the DESCRIPTION clauses of
         tmnxOamPmCfgThrDelayTable, tmnxOamPmCfgThrLossFwBwAgTable, and
         tmnxOamPmCfgThrLossFwBwTable.

         OAM-PM counters are explained in the DESCRIPTION clauses of the
         tmnxOamPmStatsTableObjs tables.

         [EFFECT] For an LMM test, the loss of live traffic has met or fallen
         below a configured threshold.  For other test types, the loss or delay
         of OAM-PM test probes has met or fallen below a configured threshold,
         indicating a possible improvement in the loss or delay of live traffic.

         [RECOVERY] No recovery is required for this trap."
    ::= { tmnxOamPmNotifications 2 }

END
