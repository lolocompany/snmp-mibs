TIMETRA-ROUTE-POLICY-MIB DEFINITIONS ::= BEGIN

IMPORTS
    InterfaceIndexOrZero
                                                         FROM IF-MIB
    InetAddress, InetAddressPrefixLength,
    InetAddressType,
    InetAutonomousSystemNumber
                                                         FROM INET-ADDRESS-MIB
    MODULE-COMPLIANCE, OBJECT-GROUP
                                                         FROM SNMPv2-CONF
    Integer32, IpAddress, MODULE-IDENTITY,
    OBJECT-TYPE, Unsigned32
                                                         FROM SNMPv2-SMI
    DisplayString, RowStatus,
    TEXTUAL-CONVENTION, TimeInterval,
    TimeStamp, TruthValue
                                                         FROM SNMPv2-TC
    timetraSRMIBModules, tmnxSRConfs,
    tmnxSRNotifyPrefix, tmnxSRObjs
                                                         FROM TIMETRA-GLOBAL-MIB
    ClassIndexOrNone, IpAddressPrefixLength,
    TItemDescription, TLNamedItem,
    TLNamedItemOrEmpty, TNamedItem,
    TNamedItemOrEmpty, TPriorityOrUndefined,
    TXLPolicyNameOrExpOrEmpty,
    TmnxAddressAndPrefixAddress,
    TmnxAddressAndPrefixPrefix,
    TmnxAddressAndPrefixType,
    TmnxBGPFamilyType,
    TmnxBgpAutonomousSystem,
    TmnxBgpLocalPreference,
    TmnxBgpPreference, TmnxCreateOrigin,
    TmnxEnabledDisabled, TmnxServId
                                                         FROM TIMETRA-TC-MIB
    ;

timetraRoutePolicyMIBModule      MODULE-IDENTITY
    LAST-UPDATED "202302010000Z"
    ORGANIZATION "Nokia"
    CONTACT-INFO
        "Nokia SROS Support
         Web: http://www.nokia.com"
    DESCRIPTION
        "This is the SNMP MIB module to manage and provision route policies on
         Nokia SROS equipment.

         Copyright 2003-2023 Nokia. All rights reserved. Reproduction of this
         document is authorized on the condition that the foregoing copyright
         notice is included.

         This SNMP MIB module (Specification) embodies Nokia's
         proprietary intellectual property.  Nokia retains
         all title and ownership in the Specification, including any
         revisions.

         Nokia grants all interested parties a non-exclusive license to use and
         distribute an unmodified copy of this Specification in connection with
         management of Nokia products, and without fee, provided this copyright
         notice and license appear on all copies.

         This Specification is supplied 'as is', and Nokia makes no warranty,
         either express or implied, as to the use, operation, condition, or
         performance of the Specification."

    REVISION    "202302010000Z"
    DESCRIPTION
        "Rev 23.0               01 Feb 2023 00:00
         23.0 release of the TIMETRA-ROUTE-POLICY-MIB."

    REVISION    "202202010000Z"
    DESCRIPTION
        "Rev 22.0               01 Feb 2022 00:00
         22.0 release of the TIMETRA-ROUTE-POLICY-MIB."

    REVISION    "202102010000Z"
    DESCRIPTION
        "Rev 21.0               01 Feb 2021 00:00
         21.0 release of the TIMETRA-ROUTE-POLICY-MIB."

    REVISION    "202002010000Z"
    DESCRIPTION
        "Rev 20.0               01 Feb 2020 00:00
         20.0 release of the TIMETRA-ROUTE-POLICY-MIB."

    REVISION    "201904010000Z"
    DESCRIPTION
        "Rev 19.0               01 April 2019 00:00
         19.0 release of the TIMETRA-ROUTE-POLICY-MIB."

    REVISION    "201709010000Z"
    DESCRIPTION
        "Rev 16.0               01 Sept 2017 00:00
         16.0 release of the TIMETRA-ROUTE-POLICY-MIB."

    REVISION    "201605010000Z"
    DESCRIPTION
        "Rev 15.0               01 May 2016 00:00
         15.0 release of the TIMETRA-ROUTE-POLICY-MIB."

    REVISION    "201601010000Z"
    DESCRIPTION
        "Rev 14.0               01 Jan 2016 00:00
         14.0 release of the TIMETRA-ROUTE-POLICY-MIB."

    REVISION    "201405010000Z"
    DESCRIPTION
        "Rev 13.0               01 May 2014 00:00
         13.0 release of the TIMETRA-ROUTE-POLICY-MIB."

    REVISION    "201401010000Z"
    DESCRIPTION
        "Rev 12.0               01 Jan 2014 00:00
         12.0 release of the TIMETRA-ROUTE-POLICY-MIB."

    REVISION    "201301010000Z"
    DESCRIPTION
        "Rev 11.0               01 Jan 2013 00:00
         11.0 release of the TIMETRA-ROUTE-POLICY-MIB."

    REVISION    "201202280000Z"
    DESCRIPTION
        "Rev 10.0               28 Feb 2012 12:00
         10.0 release of the TIMETRA-ROUTE-POLICY-MIB."

    REVISION    "201102010000Z"
    DESCRIPTION
        "Rev 9.0                1 Feb 2011 00:00
         9.0 release of the TIMETRA-ROUTE-POLICY-MIB."

    REVISION    "200902280000Z"
    DESCRIPTION
        "Rev 7.0                28 Feb 2009 00:00
         7.0 release of the TIMETRA-ROUTE-POLICY-MIB."

    REVISION    "200801010000Z"
    DESCRIPTION
        "Rev 6.0                01 Jan 2008 00:00
         6.0 release of the TIMETRA-ROUTE-POLICY-MIB."

    REVISION    "200603230000Z"
    DESCRIPTION
        "Rev 4.0                23 Mar 2006 00:00
         4.0 release of the TIMETRA-ROUTE-POLICY-MIB."

    REVISION    "200501240000Z"
    DESCRIPTION
        "Rev 2.1                24 Jan 2005 00:00
         2.1 release of the TIMETRA-ROUTE-POLICY-MIB."

    REVISION    "200401150000Z"
    DESCRIPTION
        "Rev 2.0                15 Jan 2004 00:00
         2.0 release of the TIMETRA-ROUTE-POLICY-MIB."

    REVISION    "200308150000Z"
    DESCRIPTION
        "Rev 1.2                15 Aug 2003 00:00
         1.2 release of the TIMETRA-ROUTE-POLICY-MIB."

    REVISION    "200301200000Z"
    DESCRIPTION
        "Rev 1.0                20 Jan 2003 00:00
         1.0 Release of the TIMETRA-ROUTE-POLICY-MIB."

    REVISION    "200104300000Z"
    DESCRIPTION
        "Rev 0.1                30 Apr 2001 00:00
         Initial version of the TIMETRA-ROUTE-POLICY-MIB."

    ::= { timetraSRMIBModules 17 }

TASPathName                      ::= TEXTUAL-CONVENTION
    STATUS      current
    DESCRIPTION
        "The name of an AS path. An empty string indicates that no AS Path has
         been specified and is invalid when used as an index for a table."
    SYNTAX      TNamedItemOrEmpty

TASPathGroupName                 ::= TEXTUAL-CONVENTION
    STATUS      current
    DESCRIPTION
        "The name of an AS path group. An empty string indicates that no AS
         Path group has been specified and is invalid when used as an index for
         a table."
    SYNTAX      TNamedItemOrEmpty

TCommunityName                   ::= TEXTUAL-CONVENTION
    STATUS      current
    DESCRIPTION
        "The name of a community. An empty string indicates that no community
         has been specified and is invalid when used as an index for a table."
    SYNTAX      TNamedItemOrEmpty

TLCommunityName                  ::= TEXTUAL-CONVENTION
    STATUS      current
    DESCRIPTION
        "The name of a community. An empty string indicates that no community
         has been specified and is invalid when used as an index for a table."
    SYNTAX      TLNamedItemOrEmpty

TCommunityMember                 ::= TEXTUAL-CONVENTION
    STATUS      current
    DESCRIPTION
        "The member of a community. Can be one of the following:
         1) [1..65535]:[0..65535]
         2) An extended community in one of the following formats
            - target:[0..65535]:[0..4294967295]
            - origin:[0..65535]:[0..4294967295]
            - target:<ip-address>:[0..65535]
            - origin:<ip-address>:[0..65535]
            - target:[4-byte AS number]:[0..65535]
            - origin:[4-byte AS number]:[0..65535]
                4-byte AS number - [0..4294967295]
            - target:<regular-expression>&<regular-expression>
            - origin:<regular-expression>&<regular-expression>
            - target:<ip-address>&<regular-expression>
            - origin:<ip-address>&<regular-expression>
            - bandwidth:[0..65535]:[0..16777215]
            - ext:xx[yy]:value
                xx - type value
                yy - sub type
                value - Value of the extended community
                    value = 0 - Valid
                    value = 1 - Not-Found
                    value = 2 - Invalid
            - ext:[4300]:[0..2]
            - flowspec-set:[0..4294967295]:[0..16383]
            - flowspec-set-trans:[0..4294967295]:[0..16383]
            - ipv6-redirect:<ipv6-addr>
            - color:<co-bits>:<color-value>
                co-bits - 00, 01, 10 or 11
                color-value - [0..4294967295]
         3) A regular expression
         4) A well known community i.e. one of the following keywords
            - llgr-stale
            - no-advertise
            - no-export
            - no-export-subconfed
            - no-llgr
            - null
         5) A large community in one of the following formats:
            - [4-byte AS number]:[local-data]:[local-data]
                 4-byte AS number - [0..4294967295]
                 local-data - [0..4294967295]
            - <regular-expression>&<regular-expression>&<regular-expression>"
    SYNTAX      DisplayString (SIZE (1..72))

TCommunityMemberExpression       ::= TEXTUAL-CONVENTION
    STATUS      current
    DESCRIPTION
        "TCommunityMemberExpression specifies a logical expression containing
         terms and operators. It can contain sub-expressions enclosed in round
         brackets.

         A term is a string of type TCommunityMember.

         An operator can be the string 'AND', 'OR', and 'NOT'."
    SYNTAX      DisplayString

TCommunityNameExpression         ::= TEXTUAL-CONVENTION
    STATUS      current
    DESCRIPTION
        "TCommunityNameExpression specifies a logical expression containing
         terms and operators. It can contain sub-expressions enclosed in round
         brackets.

         A term is a string of type TCommunityName. A term is enclosed in
         square brackets.

         An operator can be the string 'AND', 'OR', and 'NOT'."
    SYNTAX      DisplayString

TDampingName                     ::= TEXTUAL-CONVENTION
    STATUS      current
    DESCRIPTION
        "The name of a route damping policy. An empty string indicates that no
         damping policy has been specified and is invalid when used as an index
         for a table."
    SYNTAX      TNamedItemOrEmpty

TRouteDistinguisherListName      ::= TEXTUAL-CONVENTION
    STATUS      current
    DESCRIPTION
        "The name of a Route Distinguisher (RD) list. An empty string indicates
         that no RD list has been specified and is invalid when used as an
         index for a table."
    SYNTAX      TLNamedItemOrEmpty

TPrefixListName                  ::= TEXTUAL-CONVENTION
    STATUS      current
    DESCRIPTION
        "The name of a prefix list. An empty string indicates that no prefix
         list has been specified and is invalid when used as an index for a
         table."
    SYNTAX      TNamedItemOrEmpty

TLPrefixListName                 ::= TEXTUAL-CONVENTION
    STATUS      current
    DESCRIPTION
        "The name of a prefix list. An empty string indicates that no prefix
         list has been specified and is invalid when used as an index for a
         table."
    SYNTAX      TLNamedItemOrEmpty

TLPolicyStatementName            ::= TEXTUAL-CONVENTION
    STATUS      current
    DESCRIPTION
        "The long name of a policy statement when used as an index to a table."
    SYNTAX      TLNamedItem

PolicyStatementNameOrEmpty       ::= TEXTUAL-CONVENTION
    STATUS      current
    DESCRIPTION
        "The name of a policy statement when used as an index to a table."
    SYNTAX      TNamedItemOrEmpty

TRoutePolicyRegex                ::= TEXTUAL-CONVENTION
    STATUS      current
    DESCRIPTION
        "A regular expression string.

         The Regular expression string matches against
         1) an AS_PATH string e.g. '100 200 300',
         2) a community string e.g. '100:200' where 100 is the as-number,
            and 200 is the community-value.

         The regular expression is expressed in terms of a TERM, and an
         OPERATOR:

         A term is either:
         1) an AS Number
         2) a community value e.g. in 100:200, we have three tokens:
             (i)   100 is the as-number,
             (ii)  ':' is the separator token, and
             (iii) 200 is the community-value
         3) '.' - DOT is a wild card token which matches with either an AS Number
            or a Community.

         The list of operators are:
         1)  '|' - suggests an alternation.
         2)  '*' - multiple occurrences of the token.
         3)  '?' - 0 or 1 occurrence of token.
         4)  '+' - 1 or more occurrences of token.
         5)  '(' - is used to parenthesize so that a regular expression is
                   considered as one token.
         6)  ')' - closes the parenthesis.
         7)  '[' - used to demarcate range.
         8)  ']' - closes the box bracket.
         9)  '{m, [n]}' - suggest that the term can occur anywhere between m, and n
                          times.
         10) '^' - matches the beginning of the string - only allowed for
                   communities.
         11) '$' - matches the end of the string - only allowed for communities.

         Note, use only NVT ASCII displayable characters here, no control
         characters, no UTF-8, etc.

         The EBNF description for the regular expression string are:
         1) reg_ex ::= empty_string | non-empty_reg_ex
         2) non-empty_reg_ex ::= bounded_element | ( bounded_element '|'
            non-empty_reg_ex )
         3) bounded_element ::= ['^'] element ['$']
         4) element ::= ( '(' list ')' | atomic ) ['*' | '?' | '+' | '{'
         integer
            ',' [ integer ] '}' ] [element]
         5) list ::= element | (element '|' list)
         6) atomic ::=  '.' | ':' | '<' | '>' | atom_list
         7) atom_list ::= atom | ( '[' atom_list_boxed )
         8) atom_list_boxed ::= ( atom ']' ) | ( atom atom_list_boxed )
         9) (for as-path reg-ex)    atom ::= integer [ '-' integer ]
            an atom is essentially EQUIVALENT to a TERM
            (for community reg-ex)  atom ::= digit[ '-' digit ]
         NOTE -> atom_list_boxed is a list of integers ending in box bracket -
                 BNF description is error-free."
    SYNTAX      DisplayString

TPolicyStatementEntryID          ::= TEXTUAL-CONVENTION
    STATUS      current
    DESCRIPTION
        "Identification number for a policy statement entry. Entries are sorted
         by ID number. Matching entries are evaluated in order from lowest ID
         to highest ID.

         We suggest ordering policy statement entry IDs by 10s:  10, 20, 30,
         etc., so entry insertions are easy."
    SYNTAX      Unsigned32

TRoutePolicyProtocol             ::= TEXTUAL-CONVENTION
    STATUS      current
    DESCRIPTION
        "A list of routing protocols, for -to and -from policies."
    SYNTAX      INTEGER {
        none            (1),
        direct          (2),
        static          (3),
        bgp             (4),
        isis            (5),
        ospf            (6),
        rip             (7),
        aggregate       (8),
        bgpVpn          (9),
        igmp            (10),
        pim             (11),
        ospf3           (12),
        ldp             (13),
        subscriber      (14),
        mld             (15),
        managed         (16),
        msdp            (17),
        vpnLeak         (18),
        mobileHost      (19),
        tms             (20),
        nat             (21),
        periodic        (22),
        ipsec           (23),
        mpls            (24),
        dhcpv6Pd        (25),
        dhcpv6Na        (26),
        dhcpv6Ta        (27),
        dhcpv6PdExcl    (28),
        ripng           (29),
        bgpEvpn         (30),
        bgpLabel        (31),
        directInterface (32),
        arpNd           (33),
        ribApi          (34),
        ndRa            (35),
        dhcpClient      (36),
        evpnIfl         (37),
        reserved38      (38),
        srv6            (39),
        video           (40),
        evpnIflHost     (41)
    }

TRoutePolicyProtocolBits         ::= TEXTUAL-CONVENTION
    STATUS      current
    DESCRIPTION
        "TRoutePolicyProtocolBits is a BITS construct that specifies routing
         protocols for -to and -from policies."
    SYNTAX      BITS {
        invalid         (0),
        none            (1),
        direct          (2),
        static          (3),
        bgp             (4),
        isis            (5),
        ospf            (6),
        rip             (7),
        aggregate       (8),
        bgpVpn          (9),
        igmp            (10),
        pim             (11),
        ospf3           (12),
        ldp             (13),
        subscriber      (14),
        mld             (15),
        managed         (16),
        msdp            (17),
        vpnLeak         (18),
        mobileHost      (19),
        tms             (20),
        nat             (21),
        periodic        (22),
        ipsec           (23),
        mpls            (24),
        dhcpv6Pd        (25),
        dhcpv6Na        (26),
        dhcpv6Ta        (27),
        dhcpv6PdExcl    (28),
        ripng           (29),
        bgpEvpn         (30),
        bgpLabel        (31),
        directInterface (32),
        arpNd           (33),
        ribApi          (34),
        ndRa            (35),
        dhcpClient      (36),
        evpnIfl         (37),
        reserved38      (38),
        srv6            (39),
        video           (40),
        evpnIflHost     (41)
    }

TOspfRouteType                   ::= TEXTUAL-CONVENTION
    STATUS      current
    DESCRIPTION
        "The OSPF route type. Set to zero to disable."
    SYNTAX      Integer32 (0 | 1 | 2)

TIsisLevel                       ::= TEXTUAL-CONVENTION
    STATUS      current
    DESCRIPTION
        "Indicates the ISIS Route Level match criterion. A value of 0 indicates
         no IS-IS route match criterion is configured.

         There are two types of areas in IS-IS, namely Level 1 areas and Level
         2 areas. Routers within a Level 1 area route to other routers in that
         area. If the destination does not exist within the area, the Level 1
         router will route toward a Level 2 router. Level 2 routers route
         between areas and toward other ASs."
    SYNTAX      Integer32 (0 | 1 | 2)

TPolicyEntryAction               ::= TEXTUAL-CONVENTION
    STATUS      current
    DESCRIPTION
        "Action to take when route matches the entry's match criteria.

         accept(1) - perform the accept-action modifications,
              advertise the route, do not evaluate any more policy entries.

         reject(2) - perform the reject-action modifications,
              do not advertise the route, do not evaluate any more
              policy entries.

         continue(3) - perform the accept-action modifications,
              evaluate the next policy entry in the policy statement.

         nextPolicy(4) - perform the accept-action modifications,
              evaluate the next policy statement."
    SYNTAX      INTEGER {
        none       (0),
        accept     (1),
        reject     (2),
        continue   (3),
        nextPolicy (4)
    }

TPolicyEntryEdit                 ::= TEXTUAL-CONVENTION
    STATUS      current
    DESCRIPTION
        "Editing action to take when route matches the entry's match criteria.

         none(1) - do not change the value in the route

         add(2) - add the corresponding objects to the route

         remove(3) - remove the corresponding objects to the route

         replace(4) - replace the value in the route with the
                      corresponding object."
    SYNTAX      INTEGER {
        none    (1),
        add     (2),
        remove  (3),
        replace (4)
    }

TPolicyEntryCriteriaOrigin       ::= TEXTUAL-CONVENTION
    STATUS      current
    DESCRIPTION
        "Origin of the route.

         none(1) - ignore this criteria

         igp(2) - learned from an Interior Gateway Protocol (OSPF, ISIS, etc.)

         egp(3) - learned from an Exterior Gateway Protocol (BGP)

         incomplete(4) - Route origin is unknown (usually due to aggregation)

         any(5) - to or from either igp or egp

         aaa(6) - subscriber host address originated from aaa

         dynamic(7) - subscriber host address originated from a dynamic source

         static(8) - subscriber host address originated from a static source

         bonding(9) - subscriber host address originated from a bonding source

         pfcp(10) - learned from Packet Forwarding Control Protocol (PFCP) "
    SYNTAX      INTEGER {
        none       (1),
        igp        (2),
        egp        (3),
        incomplete (4),
        any        (5),
        aaa        (6),
        dynamic    (7),
        static     (8),
        bonding    (9),
        pfcp       (10)
    }

TPolicyActionTag                 ::= TEXTUAL-CONVENTION
    STATUS      current
    DESCRIPTION
        "Tag value to set. Zero means disabled, no tag value will be set."
    SYNTAX      Unsigned32 (0..4294967295)

TPolicyEntryCriteriaState        ::= TEXTUAL-CONVENTION
    STATUS      current
    DESCRIPTION
        "Generic criteria state.

         none(1) - ignore this criteria

         srrpMaster(2) - srrp-master

         srrpNonMaster(3) - srrp-non-master

         mobileMaster (4), - Identifies routes that are in mobile-master state
         mobileSlave (5), - Identifies routes that are in mobile-slave state.
         ipsecMaster (6), - Routes that are in ipsec-master with peer state
         ipsecMasterNoPeer (7), - Routes that are ipsec-master-without-peer
         ipsecNonMaster (8) - Routes that in ipsec-non-master state
         mobilePreSlave (9) - Identifies routes that are in mobile-pre-slave
         state fsgActive (10) - Identifies routes that are in fsg-active state
         fsgStandby (11) - Identifies routes that are in fsg-standby state
         fsgActivePathRestoration (12) - Identifies routes that are in
         fsg-active-path-restoration state"
    SYNTAX      INTEGER {
        none                     (1),
        srrpMaster               (2),
        srrpNonMaster            (3),
        mobileMaster             (4),
        mobileSlave              (5),
        ipsecMaster              (6),
        ipsecMasterNoPeer        (7),
        ipsecNonMaster           (8),
        mobilePreSlave           (9),
        fsgActive                (10),
        fsgStandby               (11),
        fsgActivePathRestoration (12)
    }

TPolicyActionMetricSource        ::= TEXTUAL-CONVENTION
    STATUS      current
    DESCRIPTION
        "The source of the Action Metric."
    SYNTAX      INTEGER {
        igpCost     (1),
        metricVal   (2),
        metricParam (3)
    }

TPolicyEntryAigpMetricEdit       ::= TEXTUAL-CONVENTION
    STATUS      current
    DESCRIPTION
        "Editing action to take when route matches the entry's match criteria.

         none(1)    - do not change the value in the route.
         add(2)     - add the corresponding object value to the aigp value
                      in the received route.
         replace(3) - replace the aigp value in the route with the
                      corresponding object value.
         useIgp(4) - replace the aigp value in the route with the IGP cost."
    SYNTAX      INTEGER {
        none    (1),
        add     (2),
        replace (3),
        useIgp  (4)
    }

TPolicyEntryCriteriaMvpnType     ::= TEXTUAL-CONVENTION
    STATUS      current
    DESCRIPTION
        "BGP MVPN Route types.

         none(0) - ignore this criterion

         intraAsIpmsiAutoDiscovery(1) - Intra-AS I-PMSI Auto Discovery

         interAsIpmsiAutoDiscovery(2) - Inter-AS I-PMSI Auto Discovery

         sPmsiAutoDiscovery(3) - S-PMSI Auto discovery

         intraAsSegmentLeafAutoDiscovery(4) - Intra-AS Segment Leaf Auto
                                              Discovery

         sourceActiveAutoDiscovery(5) - Source Active Auto Discovery

         sharedTreeJoin(6) - Shared Tree Join (C-multicast)

         sourceTreeJoin(7) - Source Tree Join (C-multicast)"
    SYNTAX      INTEGER {
        none                            (0),
        intraAsIpmsiAutoDiscovery       (1),
        interAsIpmsiAutoDiscovery       (2),
        sPmsiAutoDiscovery              (3),
        intraAsSegmentLeafAutoDiscovery (4),
        sourceActiveAutoDiscovery       (5),
        sharedTreeJoin                  (6),
        sourceTreeJoin                  (7)
    }

TPolicyEntryCriteriaEvpnType     ::= TEXTUAL-CONVENTION
    STATUS      current
    DESCRIPTION
        "BGP EVPN Route types.

         none(0) - ignore this criterion

         ethernetAutoDiscovery(1) - Ethernet Auto Discovery

         macIpAdvertisement(2) - MAC/IP advertisement

         inclusiveMulticast(3) - Inclusive Multicast

         ethernetSegment(4) - Ethernet Segment

         ipPrefix(5) - IP Prefix

         selectiveMulticast(6) - Selective Multicast Ethernet Tag (SMET)

         multicastJoinSync(7) - Multicast Join Sync

         multicastLeaveSync(8) - Multicast Leave Sync

         selectivePmsiAutoDiscovery(10) - Selective PMSI Auto Discovery"
    SYNTAX      INTEGER {
        none                       (0),
        ethernetAutoDiscovery      (1),
        macIpAdvertisement         (2),
        inclusiveMulticast         (3),
        ethernetSegment            (4),
        ipPrefix                   (5),
        selectiveMulticast         (6),
        multicastJoinSync          (7),
        multicastLeaveSync         (8),
        selectivePmsiAutoDiscovery (10)
    }

TPolicyVariableName              ::= TEXTUAL-CONVENTION
    STATUS      current
    DESCRIPTION
        "TPolicyVariableName specifies a variable that is used as TASPathName,
         TASPathGroupName, TPrefixListName, TCommunityName ,
         TRouteDistinguisherListName or TDampingName.

         The first and last character of a variable is the at-sign (@)."
    SYNTAX      TNamedItem

TPolicyAdvertiseLabelMode        ::= TEXTUAL-CONVENTION
    STATUS      current
    DESCRIPTION
        "The value of TPolicyAdvertiseLabelMode specifies the advertisement
         label mode.

         none(0)          - use the label mode of the VRF, i.e. label-per-nexthop (LPN) or label-per-VRF.
         perPrefix(1)     - use label-per-prefix (LPP) mode for routes that match the policy.
         pop(2)           - use POP label for importing routes from the route table (RTM).
         popAndForward(3) - use POP and forward without IP FIB lookup."
    SYNTAX      INTEGER {
        none          (0),
        perPrefix     (1),
        pop           (2),
        popAndForward (3)
    }

TPolicyVariableType              ::= TEXTUAL-CONVENTION
    STATUS      current
    DESCRIPTION
        "The value of TPolicyVariableType specifies to which type the
         TPolicyVariableName is to be resolved."
    SYNTAX      INTEGER {
        string  (1),
        integer (2),
        address (3),
        decimal (4),
        prefix  (5)
    }

TPolicyDecimal                   ::= TEXTUAL-CONVENTION
    STATUS      current
    DESCRIPTION
        "TPolicyDecimal specifies a floating-point value  with maximum 3 digits
         behind the decimal point, e.g. '0.125'.

         The configured value will always be returned as a decimal with 3
         digits behind the decimal point;  e.g. '150' will be returned as
         '150.000'.

         The supported decimal range is '0.000..4294967295.000'."
    SYNTAX      DisplayString (SIZE (1..14))

TPolicyVariableNameOrEmpty       ::= TEXTUAL-CONVENTION
    STATUS      current
    DESCRIPTION
        "The value of TPolicyVariableNameOrEmpty specifies a variable name
         TPolicyVariableName that is used as parameter.

         An empty string indicates that no parameter has been specified.

         The first and last character of a variable name is the at-sign (@)."
    SYNTAX      TNamedItemOrEmpty

TPolicyActionSource              ::= TEXTUAL-CONVENTION
    STATUS      current
    DESCRIPTION
        "The source of the Action item."
    SYNTAX      INTEGER {
        actionValue (1),
        actionParam (2)
    }

TPrefixListNameExpression        ::= TEXTUAL-CONVENTION
    STATUS      current
    DESCRIPTION
        "TPrefixListNameExpression specifies a logical expression containing
         terms and operators.

         A term is a string of type TLPrefixListName. A term is enclosed in
         square brackets.

         The string 'all' or 'none' can be added after the term.

         If 'all' is specified, all of the entries in the prefix list should
         match a route in the route table (RTM) for the expression to be
         considered 'TRUE'.

         If 'none' is specified, none of the entries in the prefix list may
         match a route in the route table (RTM) for the expression to be
         considered 'TRUE'.

         If neither 'none' nor 'all' is specified, at least one entry in the
         prefix list should match a route in the route table (RTM) for the
         expression to be considered 'TRUE'."
    SYNTAX      DisplayString

TPolicyCritPathType              ::= TEXTUAL-CONVENTION
    STATUS      current
    DESCRIPTION
        "The path type of a BGP route to be used as match criteria.

         none(1) - the criteria is disabled. ibgp(2) - match on routes learned
         from an IBGP or confed-EBGP peer. ebgp(3) - match on routes learned
         from an EBGP peer."
    SYNTAX      INTEGER {
        none (1),
        ibgp (2),
        ebgp (3)
    }

TPolicyCritCommunityType         ::= TEXTUAL-CONVENTION
    STATUS      current
    DESCRIPTION
        "The community type of a BGP route to be counted as match criteria.

         all      (1) - all communities are counted.
         standard (2) - only the standard communities are counted.
         extended (3) - only the extended communities are counted.
         large    (4) - only the large communities are counted."
    SYNTAX      INTEGER {
        all      (1),
        standard (2),
        extended (3),
        large    (4)
    }

TPolicyValueOrVarNameOrEmpty     ::= TEXTUAL-CONVENTION
    STATUS      current
    DESCRIPTION
        "TPolicyValueOrVarNameOrEmpty specifies a value or a variable name
         TPolicyVariableName that needs to be resolved to get the value.

         An empty string indicates that no value has been specified.

         The first and last character of a variable name is the at-sign (@)."
    SYNTAX      TNamedItemOrEmpty

TPolicyMatchIndicator            ::= TEXTUAL-CONVENTION
    STATUS      current
    DESCRIPTION
        "TPolicyMatchIndicator specifies whether higher or lower values are
         accepted for the related match criteria.

         equal (1)    - it must be an exact match.
         orHigher (2) - equal or greater values result in a match.
         orLower (3)  - equal or less values result in a match."
    SYNTAX      INTEGER {
        equal    (1),
        orHigher (2),
        orLower  (3)
    }

TPolicyAddPathSendLimit          ::= TEXTUAL-CONVENTION
    STATUS      current
    DESCRIPTION
        "TPolicyAddPathSendLimit specifies the maximum number of paths that can
         be advertised to ADD-PATH peers per prefix.

         The value -1 indicates that BGP must send exactly the number of best
         multipaths it has for each NLRI."
    SYNTAX      Integer32 (-1 | 0..16)

TPolicyAdminTagPolicyOrVarName   ::= TEXTUAL-CONVENTION
    STATUS      current
    DESCRIPTION
        "TPolicyAdminTagPolicyOrVarName specifies the administrative tag policy
         or a variable name that needs to be resolved to get the
         administrative tag policy.

         The first and last character of a variable name is the at-sign (@).

         A variable name can also be used as mid-string in the  administrative
         tag policy.

         An empty string indicates that no administrative tag policy or
         variable name has been specified."
    SYNTAX      TLNamedItemOrEmpty

TPolicyBgpMedSource              ::= TEXTUAL-CONVENTION
    STATUS      current
    DESCRIPTION
        "TPolicyBgpMedSource specifies the source of the BGP MED.

         none (0)       - ignore this action.
         igp (1)        - use the IGP cost as BGP MED.
         minIgp (2)     - use the minimum IGP cost as BGP MED.
         medValue (3)   - use the configured value as BGP MED.
         expression (4) - use the value resolved from the expression as BGP MED."
    SYNTAX      INTEGER {
        none       (0),
        igp        (1),
        minIgp     (2),
        medValue   (3),
        expression (4)
    }

TPolicyBgpMedExpression          ::= TEXTUAL-CONVENTION
    STATUS      current
    DESCRIPTION
        "TPolicyBgpMedExpression specifies an expression containing terms and
         operators.

         A term is either: 1) _igp_ (predefined variable holding the IGP cost)
         2) _med_ (predefined variable holding the received MED value) 3) a
         floating point value 4) a policy variable 5) another expression
         surrounded by parentheses()

         A BGP MED expression must contain at least one occurrence of either
         '_igp_' or '_med'.

         The list of supported operators are:
         1)  '*' - multiply
         2)  '+' - add
         3)  '-' - subtract

         BGP MED expression examples:
         - '_med_ * 0.125'
         - '(_igp + 100) * @med-multiplier@'
         - '_med_ + _igp_ + 50'"
    SYNTAX      DisplayString (SIZE (0..64))

TPolicyRouteDistinguisher        ::= TEXTUAL-CONVENTION
    STATUS      current
    DESCRIPTION
        "TPolicyRouteDistinguisher specifies a route distinguisher (RD) that
         can be used to match on.

         The RD entry contains an ipv4-address or ASN and the assigned number
         in any of the following formats:
         1) 'a.b.c.d/m:n'
            e.g. '10.0.0.2/32:666' - type-1 RDs with 10.0.0.2 as the administrator
            and 666 as the assigned number

         2) 'a.b.c.d/m:*'
            e.g. '10.0.0.0/16:*' - type-1 RDs with 10.0.*.* as the administrator
            and any value 0-65535 as the assigned number

         3) 'asn:n'
            e.g. '65000:666' - type-0 or type-2 RDs with 65000 as the administrator and
            666 as the assigned number

         4) 'asn:*'
            e.g. '65000:*' - type-0 or type-2 RDs with 65000 as the administrator and
            any value 0-4294967295 (type-0) or 0-65535 (type-2) as the assigned number"
    SYNTAX      DisplayString (SIZE (3..28))

tRoutePolicyObjects              OBJECT IDENTIFIER ::= { tmnxSRObjs 17 }

tRPOperObjects                   OBJECT IDENTIFIER ::= { tRoutePolicyObjects 1 }

tRPOperValueObjects              OBJECT IDENTIFIER ::= { tRPOperObjects 1 }

tRPOperASPathTableLastChanged    OBJECT-TYPE
    SYNTAX      TimeStamp
    MAX-ACCESS  read-only
    STATUS      obsolete
    DESCRIPTION
        "Timestamp of last change to tRPOperASPathTable.

         tRPOperASPathTableLastChanged is obsoleted in release 5.0.
         TIMETRA-SYSTEM-MIB::tmnxConfigModify notification is used instead."
    ::= { tRPOperValueObjects 1 }

tRPOperASPathTable               OBJECT-TYPE
    SYNTAX      SEQUENCE OF TRPOperASPathEntry
    MAX-ACCESS  not-accessible
    STATUS      current
    DESCRIPTION
        "A list of AS Path names and corresponding regular expressions."
    ::= { tRPOperValueObjects 2 }

tRPOperASPathEntry               OBJECT-TYPE
    SYNTAX      TRPOperASPathEntry
    MAX-ACCESS  not-accessible
    STATUS      current
    DESCRIPTION
        "Information about a particular AS Path Name.

         Entries are created and deleted by the user via tRPAdminASPathTable."
    INDEX       { tRPOperASPathName }
    ::= { tRPOperASPathTable 1 }

TRPOperASPathEntry               ::= SEQUENCE
{
    tRPOperASPathName                TASPathName,
    tRPOperASPathRowStatus           RowStatus,
    tRPOperASPathRegEx               TRoutePolicyRegex,
    tRPOperASPathEntryLastChanged    TimeStamp,
    tRPOperASPathCreationOrigin      TmnxCreateOrigin
}

tRPOperASPathName                OBJECT-TYPE
    SYNTAX      TASPathName (SIZE (1..32))
    MAX-ACCESS  not-accessible
    STATUS      current
    DESCRIPTION
        "The name of the AS Path entry used to uniquely identify an AS Path."
    ::= { tRPOperASPathEntry 1 }

tRPOperASPathRowStatus           OBJECT-TYPE
    SYNTAX      RowStatus
    MAX-ACCESS  read-only
    STATUS      current
    DESCRIPTION
        "The value of tRPOperASPathRowStatus indicates the RowStatus for this
         row.

         To create or destroy entries in this table, use the
         tRPAdminASPathTable."
    ::= { tRPOperASPathEntry 2 }

tRPOperASPathRegEx               OBJECT-TYPE
    SYNTAX      TRoutePolicyRegex
    MAX-ACCESS  read-only
    STATUS      current
    DESCRIPTION
        "The regular expression for the AS Path entry."
    ::= { tRPOperASPathEntry 3 }

tRPOperASPathEntryLastChanged    OBJECT-TYPE
    SYNTAX      TimeStamp
    MAX-ACCESS  read-only
    STATUS      obsolete
    DESCRIPTION
        "Timestamp of last change to this entry.

         tRPOperASPathEntryLastChanged is obsoleted in release 5.0.
         TIMETRA-SYSTEM-MIB::tmnxConfigModify notification is used instead."
    ::= { tRPOperASPathEntry 4 }

tRPOperASPathCreationOrigin      OBJECT-TYPE
    SYNTAX      TmnxCreateOrigin
    MAX-ACCESS  read-only
    STATUS      current
    DESCRIPTION
        "The value of the object tRPOperASPathCreationOrigin indicates the
         mechanism used to create this entry."
    ::= { tRPOperASPathEntry 5 }

tRPOperCommunityTableLastChanged OBJECT-TYPE
    SYNTAX      TimeStamp
    MAX-ACCESS  read-only
    STATUS      obsolete
    DESCRIPTION
        "Timestamp of last change to tRPOperCommunityTable.

         tRPOperCommunityTableLastChanged is obsoleted in release 5.0.
         TIMETRA-SYSTEM-MIB::tmnxConfigModify notification is used instead."
    ::= { tRPOperValueObjects 3 }

tRPOperCommunityTable            OBJECT-TYPE
    SYNTAX      SEQUENCE OF TRPOperCommunityEntry
    MAX-ACCESS  not-accessible
    STATUS      current
    DESCRIPTION
        "A table of community entries."
    ::= { tRPOperValueObjects 4 }

tRPOperCommunityEntry            OBJECT-TYPE
    SYNTAX      TRPOperCommunityEntry
    MAX-ACCESS  not-accessible
    STATUS      current
    DESCRIPTION
        "Information about a particular community member.

         Entries are created and deleted by the user via
         tRPAdminCommunityTable."
    INDEX       {
        tRPOperCommunityName,
        tRPOperCommunityMember
    }
    ::= { tRPOperCommunityTable 1 }

TRPOperCommunityEntry            ::= SEQUENCE
{
    tRPOperCommunityName             TLCommunityName,
    tRPOperCommunityMember           TCommunityMember,
    tRPOperCommunityRowStatus        RowStatus,
    tRPOperCommunityEntryLastChanged TimeStamp,
    tRPOperCommunityCreationOrigin   TmnxCreateOrigin
}

tRPOperCommunityName             OBJECT-TYPE
    SYNTAX      TLCommunityName (SIZE (1..64))
    MAX-ACCESS  not-accessible
    STATUS      current
    DESCRIPTION
        "The name of the community used as an index for this table."
    ::= { tRPOperCommunityEntry 1 }

tRPOperCommunityMember           OBJECT-TYPE
    SYNTAX      TCommunityMember
    MAX-ACCESS  not-accessible
    STATUS      current
    DESCRIPTION
        "The AS Number or Community ID of the community member. The community
         name and the member name uniquely identify a row in this table."
    ::= { tRPOperCommunityEntry 2 }

tRPOperCommunityRowStatus        OBJECT-TYPE
    SYNTAX      RowStatus
    MAX-ACCESS  read-only
    STATUS      current
    DESCRIPTION
        "The value of tRPOperCommunityRowStatus indicates the RowStatus for
         this row.

         To create or destroy entries in this table, use the
         tRPAdminCommunityTable."
    ::= { tRPOperCommunityEntry 3 }

tRPOperCommunityEntryLastChanged OBJECT-TYPE
    SYNTAX      TimeStamp
    MAX-ACCESS  read-only
    STATUS      obsolete
    DESCRIPTION
        "Timestamp of last change to this entry.

         tRPOperCommunityEntryLastChanged is obsoleted in release 5.0.
         TIMETRA-SYSTEM-MIB::tmnxConfigModify notification is used instead."
    ::= { tRPOperCommunityEntry 4 }

tRPOperCommunityCreationOrigin   OBJECT-TYPE
    SYNTAX      TmnxCreateOrigin
    MAX-ACCESS  read-only
    STATUS      current
    DESCRIPTION
        "The value of the object tRPOperCommunityCreationOrigin indicates the
         mechanism used to create this entry."
    ::= { tRPOperCommunityEntry 5 }

tRPOperDampingTableLastChanged   OBJECT-TYPE
    SYNTAX      TimeStamp
    MAX-ACCESS  read-only
    STATUS      obsolete
    DESCRIPTION
        "Timestamp of last change to tRPOperDampingTable.

         tRPOperDampingTableLastChanged is obsoleted in release 5.0.
         TIMETRA-SYSTEM-MIB::tmnxConfigModify notification is used instead."
    ::= { tRPOperValueObjects 5 }

tRPOperDampingTable              OBJECT-TYPE
    SYNTAX      SEQUENCE OF TRPOperDampingEntry
    MAX-ACCESS  not-accessible
    STATUS      current
    DESCRIPTION
        "A table of route damping control entries."
    ::= { tRPOperValueObjects 6 }

tRPOperDampingEntry              OBJECT-TYPE
    SYNTAX      TRPOperDampingEntry
    MAX-ACCESS  not-accessible
    STATUS      current
    DESCRIPTION
        "Information about a particular Damping entry.

         Entries are created and deleted by the user via tRPAdminDampingTable."
    INDEX       { tRPOperDampingName }
    ::= { tRPOperDampingTable 1 }

TRPOperDampingEntry              ::= SEQUENCE
{
    tRPOperDampingName               TDampingName,
    tRPOperDampingRowStatus          RowStatus,
    tRPOperDampingHalfLife           Unsigned32,
    tRPOperDampingMaxSuppress        Unsigned32,
    tRPOperDampingReuse              Unsigned32,
    tRPOperDampingSuppress           Unsigned32,
    tRPOperDampingEntryLastChanged   TimeStamp,
    tRPOperDampingCreationOrigin     TmnxCreateOrigin
}

tRPOperDampingName               OBJECT-TYPE
    SYNTAX      TDampingName (SIZE (1..32))
    MAX-ACCESS  not-accessible
    STATUS      current
    DESCRIPTION
        "The name of the damping entry used to uniquely identify a row in this
         table."
    ::= { tRPOperDampingEntry 1 }

tRPOperDampingRowStatus          OBJECT-TYPE
    SYNTAX      RowStatus
    MAX-ACCESS  read-only
    STATUS      current
    DESCRIPTION
        "RowStatus for this row.

         To create or destroy entries in this table, use the
         tRPAdminDampingTable."
    ::= { tRPOperDampingEntry 2 }

tRPOperDampingHalfLife           OBJECT-TYPE
    SYNTAX      Unsigned32 (0..45)
    UNITS       "minutes"
    MAX-ACCESS  read-only
    STATUS      current
    DESCRIPTION
        "Specifies the half-life, in minutes, for a routes figure-of-merit
         after it has been dampened. If a route's half-life is set to 15
         minutes and has a figure-of-merit of 1500, after 15 minutes, the
         route's figure-of-merit will have decayed to 750. Set to 0 to disable."
    ::= { tRPOperDampingEntry 3 }

tRPOperDampingMaxSuppress        OBJECT-TYPE
    SYNTAX      Unsigned32 (0..720)
    UNITS       "minutes"
    MAX-ACCESS  read-only
    STATUS      current
    DESCRIPTION
        "Specifies the maximum amount of time, in minutes, that a route can be
         suppressed for. Set to 0 to disable."
    ::= { tRPOperDampingEntry 4 }

tRPOperDampingReuse              OBJECT-TYPE
    SYNTAX      Unsigned32 (0..20000)
    MAX-ACCESS  read-only
    STATUS      current
    DESCRIPTION
        "Specifies the reuse threshold. If a route's figure-of-merit falls
         below the reuse threshold, the route can be reused. Set to 0 to
         disable."
    ::= { tRPOperDampingEntry 5 }

tRPOperDampingSuppress           OBJECT-TYPE
    SYNTAX      Unsigned32 (0..20000)
    MAX-ACCESS  read-only
    STATUS      current
    DESCRIPTION
        "Specifies the suppress threshold. If a route's figure-of-merit goes
         above the suppress threshold, the route should be suppressed. Set to 0
         to disable."
    ::= { tRPOperDampingEntry 6 }

tRPOperDampingEntryLastChanged   OBJECT-TYPE
    SYNTAX      TimeStamp
    MAX-ACCESS  read-only
    STATUS      obsolete
    DESCRIPTION
        "Timestamp of last change to this entry.

         tRPOperDampingEntryLastChanged is obsoleted in release 5.0.
         TIMETRA-SYSTEM-MIB::tmnxConfigModify notification is used instead."
    ::= { tRPOperDampingEntry 7 }

tRPOperDampingCreationOrigin     OBJECT-TYPE
    SYNTAX      TmnxCreateOrigin
    MAX-ACCESS  read-only
    STATUS      current
    DESCRIPTION
        "The value of the object tRPOperDampingCreationOrigin indicates the
         mechanism used to create this entry."
    ::= { tRPOperDampingEntry 8 }

tRPOperPrefixListTableLastChanged OBJECT-TYPE
    SYNTAX      TimeStamp
    MAX-ACCESS  read-only
    STATUS      obsolete
    DESCRIPTION
        "Timestamp of last change to tRPOperPrefixListTable.

         tRPOperPrefixListTableLastChanged is obsoleted in release 5.0.
         TIMETRA-SYSTEM-MIB::tmnxConfigModify notification is used instead."
    ::= { tRPOperValueObjects 7 }

tRPOperPrefixListTable           OBJECT-TYPE
    SYNTAX      SEQUENCE OF TRPOperPrefixListEntry
    MAX-ACCESS  not-accessible
    STATUS      current
    DESCRIPTION
        "A table of prefix lists."
    ::= { tRPOperValueObjects 8 }

tRPOperPrefixListEntry           OBJECT-TYPE
    SYNTAX      TRPOperPrefixListEntry
    MAX-ACCESS  not-accessible
    STATUS      current
    DESCRIPTION
        "Information about a particular prefix list.

         Entries are created and deleted by the user via
         tRPAdminPrefixListTable."
    INDEX       {
        tRPOperPrefixListName,
        tRPOperPrefixListIpPrefix,
        tRPOperPrefixListMask,
        tRPOperPrefixListType
    }
    ::= { tRPOperPrefixListTable 1 }

TRPOperPrefixListEntry           ::= SEQUENCE
{
    tRPOperPrefixListName            TLPrefixListName,
    tRPOperPrefixListIpPrefix        IpAddress,
    tRPOperPrefixListMask            IpAddressPrefixLength,
    tRPOperPrefixListRowStatus       RowStatus,
    tRPOperPrefixListType            INTEGER,
    tRPOperPrefixListThroughLength   IpAddressPrefixLength,
    tRPOperPrefixListEntryLastChanged TimeStamp,
    tRPOperPrefixListBeginLength     IpAddressPrefixLength
}

tRPOperPrefixListName            OBJECT-TYPE
    SYNTAX      TLPrefixListName (SIZE (1..64))
    MAX-ACCESS  not-accessible
    STATUS      current
    DESCRIPTION
        "The name of the prefix list entry."
    ::= { tRPOperPrefixListEntry 1 }

tRPOperPrefixListIpPrefix        OBJECT-TYPE
    SYNTAX      IpAddress
    MAX-ACCESS  not-accessible
    STATUS      current
    DESCRIPTION
        "The IP prefix of the prefix list entry."
    ::= { tRPOperPrefixListEntry 2 }

tRPOperPrefixListMask            OBJECT-TYPE
    SYNTAX      IpAddressPrefixLength
    MAX-ACCESS  not-accessible
    STATUS      current
    DESCRIPTION
        "The IP mask length of the prefix list entry."
    ::= { tRPOperPrefixListEntry 3 }

tRPOperPrefixListRowStatus       OBJECT-TYPE
    SYNTAX      RowStatus
    MAX-ACCESS  read-only
    STATUS      current
    DESCRIPTION
        "RowStatus for this row.

         To create or destroy entries in this table, use the
         tRPAdminPrefixListTable."
    ::= { tRPOperPrefixListEntry 4 }

tRPOperPrefixListType            OBJECT-TYPE
    SYNTAX      INTEGER {
        exact       (1),
        longer      (2),
        through     (3),
        range       (4),
        to          (5),
        addressMask (6)
    }
    MAX-ACCESS  not-accessible
    STATUS      current
    DESCRIPTION
        "The type of the prefix length entry.

         exact (1) - a route's prefix/length must match the prefix list entry
         exactly in order for an entry to be considered a match.

         longer (2) - a route's prefix/length must match the defined prefix AND
         have a length that is an exact match or longer in order for an entry
         to be considered a match.

         through (3) - a route's prefix/length must match the defined prefix
         AND have a length that is an exact match or longer up to and including
         the defined maximum length in order for an entry to be considered a
         match.

         range (4) - a route's prefix/length must match the defined prefix AND
         have a length that is greater than or equal to the length defined by
         tRPOperPrefixListBeginLength and less than or equal to the length
         defined by tRPOperPrefixListThroughLength in order for an entry to be
         considered a match.

         to (5) - a route's prefix/length must match the condition  from a
         start prefix/length to an end prefix/length. The  end prefix/length is
         indicated in the corresponding entry in  the tRPOperPfxListToTable.

         addressMask (6) - a route's prefix/length must match the prefix length
         of the prefix-list entry and the bitwise logical AND of the route
         address and the mask must match the bitwise  logical AND from the
         prefix-list address and the mask. The  address mask must be specified
         in a corresponding entry in the tRPOperPfxListAddressMaskTable."
    ::= { tRPOperPrefixListEntry 5 }

tRPOperPrefixListThroughLength   OBJECT-TYPE
    SYNTAX      IpAddressPrefixLength
    MAX-ACCESS  read-only
    STATUS      current
    DESCRIPTION
        "When tRPOperPrefixListType set to through(3), the mask length to use.
         Must be larger than tRPOperPrefixListMask."
    ::= { tRPOperPrefixListEntry 6 }

tRPOperPrefixListEntryLastChanged OBJECT-TYPE
    SYNTAX      TimeStamp
    MAX-ACCESS  read-only
    STATUS      obsolete
    DESCRIPTION
        "Timestamp of last change to this entry.

         tRPOperPrefixListEntryLastChanged is obsoleted in release 5.0.
         TIMETRA-SYSTEM-MIB::tmnxConfigModify notification is used instead."
    ::= { tRPOperPrefixListEntry 7 }

tRPOperPrefixListBeginLength     OBJECT-TYPE
    SYNTAX      IpAddressPrefixLength
    MAX-ACCESS  read-only
    STATUS      current
    DESCRIPTION
        "When tRPOperPrefixListType set to range(4), the mask length to use as
         the lower limit for the mask range. Must be larger than
         tRPOperPrefixListMask and less than tRPOperPrefixListThroughLength."
    ::= { tRPOperPrefixListEntry 8 }

tRPOperPolicyStatementTableLastChanged OBJECT-TYPE
    SYNTAX      TimeStamp
    MAX-ACCESS  read-only
    STATUS      obsolete
    DESCRIPTION
        "Timestamp of last change to tRPOperPolicyStatementTable.

         tRPOperPolicyStatementTableLastChanged is obsoleted in release 5.0.
         TIMETRA-SYSTEM-MIB::tmnxConfigModify notification is used instead."
    ::= { tRPOperValueObjects 9 }

tRPOperPolicyStatementTable      OBJECT-TYPE
    SYNTAX      SEQUENCE OF TRPOperPolicyStatementEntry
    MAX-ACCESS  not-accessible
    STATUS      current
    DESCRIPTION
        "Control table for policy statements."
    ::= { tRPOperValueObjects 10 }

tRPOperPolicyStatementEntry      OBJECT-TYPE
    SYNTAX      TRPOperPolicyStatementEntry
    MAX-ACCESS  not-accessible
    STATUS      current
    DESCRIPTION
        "Information about a particular policy statement.

         Entries are created by user via tRPAdminPolicyStatementTable. Entries
         are deleted by user via tRPAdminPolicyStatementTable."
    INDEX       { tRPOperPolicyStatementName }
    ::= { tRPOperPolicyStatementTable 1 }

TRPOperPolicyStatementEntry      ::= SEQUENCE
{
    tRPOperPolicyStatementName       TLPolicyStatementName,
    tRPOperPolicyStatementRowStatus  RowStatus,
    tRPOperPolicyStatementDescription TItemDescription,
    tRPOperPolicyStatementDefaultAction TPolicyEntryAction,
    tRPOperPolicyStatementEntryLastChanged TimeStamp,
    tRPOperPolicyStatementCrOrigin   TmnxCreateOrigin
}

tRPOperPolicyStatementName       OBJECT-TYPE
    SYNTAX      TLPolicyStatementName
    MAX-ACCESS  not-accessible
    STATUS      current
    DESCRIPTION
        "The name of this policy statement that uniquely identifies an entry in
         this table."
    ::= { tRPOperPolicyStatementEntry 1 }

tRPOperPolicyStatementRowStatus  OBJECT-TYPE
    SYNTAX      RowStatus
    MAX-ACCESS  read-only
    STATUS      current
    DESCRIPTION
        "The value of tRPOperPolicyStatementRowStatus indicates the RowStatus
         for this row.

         To create or destroy entries in this table, use the
         tRPAdminPolicyStatementTable."
    ::= { tRPOperPolicyStatementEntry 2 }

tRPOperPolicyStatementDescription OBJECT-TYPE
    SYNTAX      TItemDescription
    MAX-ACCESS  read-only
    STATUS      current
    DESCRIPTION
        "Description for this policy statement."
    ::= { tRPOperPolicyStatementEntry 3 }

tRPOperPolicyStatementDefaultAction OBJECT-TYPE
    SYNTAX      TPolicyEntryAction
    MAX-ACCESS  read-only
    STATUS      current
    DESCRIPTION
        "The default action for the policy statement indicates what happens to
         the route if none of the policy statement entries match."
    ::= { tRPOperPolicyStatementEntry 4 }

tRPOperPolicyStatementEntryLastChanged OBJECT-TYPE
    SYNTAX      TimeStamp
    MAX-ACCESS  read-only
    STATUS      obsolete
    DESCRIPTION
        "Timestamp of last change to this entry.

         tRPOperPolicyStatementEntryLastChanged is obsoleted in release 5.0.
         TIMETRA-SYSTEM-MIB::tmnxConfigModify notification is used instead."
    ::= { tRPOperPolicyStatementEntry 5 }

tRPOperPolicyStatementCrOrigin   OBJECT-TYPE
    SYNTAX      TmnxCreateOrigin
    MAX-ACCESS  read-only
    STATUS      current
    DESCRIPTION
        "The value of the object tRPOperPolicyStatementCrOrigin indicates the
         mechanism used to create this entry."
    ::= { tRPOperPolicyStatementEntry 6 }

tRPOperPSDefaultActionParamsTableLastChanged OBJECT-TYPE
    SYNTAX      TimeStamp
    MAX-ACCESS  read-only
    STATUS      obsolete
    DESCRIPTION
        "Timestamp of last change to tRPOperPSDefaultActionParamsTable.

         tRPOperPSDefaultActionParamsTableLastChanged is obsoleted in release
         5.0. TIMETRA-SYSTEM-MIB::tmnxConfigModify notification is used
         instead."
    ::= { tRPOperValueObjects 11 }

tRPOperPSDefaultActionParamsTable OBJECT-TYPE
    SYNTAX      SEQUENCE OF TRPOperPSDefaultActionParamsEntry
    MAX-ACCESS  not-accessible
    STATUS      current
    DESCRIPTION
        "Default action parameters for a policy statement."
    ::= { tRPOperValueObjects 12 }

tRPOperPSDefaultActionParamsEntry OBJECT-TYPE
    SYNTAX      TRPOperPSDefaultActionParamsEntry
    MAX-ACCESS  not-accessible
    STATUS      current
    DESCRIPTION
        "Default action information about a particular policy statement.

         These parameters are applied when the default action for the policy
         statement (tRPOperPolicyStatementDefaultAction) is 'accept(1)'.

         Entries are created when tRPOperPolicyStatementDefaultAction is
         'accept(1)', 'reject(2)', 'continue(3)' or 'nextPolicy(4)'. Entries
         are deleted when a policy statement is destroyed or
         tRPOperPolicyStatementDefaultAction is 'none(0)'."
    INDEX       { tRPOperPolicyStatementName }
    ::= { tRPOperPSDefaultActionParamsTable 1 }

TRPOperPSDefaultActionParamsEntry ::= SEQUENCE
{
    tRPOperPSDefaultActionASPath     TPolicyEntryEdit,
    tRPOperPSDefaultActionASPathName TASPathName,
    tRPOperPSDefaultActionASPathPrependAS TmnxBgpAutonomousSystem,
    tRPOperPSDefaultActionASPathPrependCount Integer32,
    tRPOperPSDefaultActionCommunity1 TPolicyEntryEdit,
    tRPOperPSDefaultActionCommunityName1 TCommunityName,
    tRPOperPSDefaultActionCommunity2 TPolicyEntryEdit,
    tRPOperPSDefaultActionCommunityName2 TCommunityName,
    tRPOperPSDefaultActionOrigin     TPolicyEntryCriteriaOrigin,
    tRPOperPSDefaultActionLocalPreferenceSet TruthValue,
    tRPOperPSDefaultActionLocalPreference TmnxBgpLocalPreference,
    tRPOperPSDefaultActionMetric     TPolicyEntryEdit,
    tRPOperPSDefaultActionMetricValue Unsigned32,
    tRPOperPSDefaultActionPreference TmnxBgpPreference,
    tRPOperPSDefaultActionDamping    TDampingName,
    tRPOperPSDefaultActionNextHopSelf TruthValue,
    tRPOperPSDefaultActionNextHop    IpAddress,
    tRPOperPSDefaultActionTag        TPolicyActionTag,
    tRPOperPSDefaultActionOspfType   TOspfRouteType,
    tRPOperPSDefaultActionParamsEntryLastChanged TimeStamp,
    tRPOperPSDefActInetNextHopType   InetAddressType,
    tRPOperPSDefActInetNextHop       InetAddress,
    tRPOperPSDefaultActionASPathPend InetAutonomousSystemNumber,
    tRPOperPSDefActMcRedirSvcId      TmnxServId,
    tRPOperPSDefActMcRedirIfIndex    InterfaceIndexOrZero,
    tRPOperPSDefActionMetricSource   TPolicyActionMetricSource,
    tRPOperPSDefActionAigpMetric     TPolicyEntryAigpMetricEdit,
    tRPOperPSDefActnAigpMetricVal    Unsigned32,
    tRPOperPSDefActnSrcClassIndex    ClassIndexOrNone,
    tRPOperPSDefActnDstClassIndex    ClassIndexOrNone,
    tRPOperPSDefActnOrigValidState   INTEGER
}

tRPOperPSDefaultActionASPath     OBJECT-TYPE
    SYNTAX      TPolicyEntryEdit
    MAX-ACCESS  read-only
    STATUS      current
    DESCRIPTION
        "The AS Path rewrite information for the route."
    ::= { tRPOperPSDefaultActionParamsEntry 1 }

tRPOperPSDefaultActionASPathName OBJECT-TYPE
    SYNTAX      TASPathName
    MAX-ACCESS  read-only
    STATUS      current
    DESCRIPTION
        "The AS Path name to use for add, remove, or replace operation
         specified by tRPOperPSDefaultActionASPath.  Ignored when
         tRPOperPSDefaultActionASPath is none(1)."
    ::= { tRPOperPSDefaultActionParamsEntry 2 }

tRPOperPSDefaultActionASPathPrependAS OBJECT-TYPE
    SYNTAX      TmnxBgpAutonomousSystem
    MAX-ACCESS  read-only
    STATUS      obsolete
    DESCRIPTION
        "AS Number to prepend to the AS-Path attribute of the route. Ignored
         when tRPOperPSDefaultActionASPathPrependCount is zero.

         This object was obsoleted in release 7.0.  It is replaced with the
         4-byte AS number defined by tRPOperPSDefaultActionASPathPend."
    ::= { tRPOperPSDefaultActionParamsEntry 3 }

tRPOperPSDefaultActionASPathPrependCount OBJECT-TYPE
    SYNTAX      Integer32 (0..50)
    MAX-ACCESS  read-only
    STATUS      current
    DESCRIPTION
        "Number of times tRPOperPSDefaultActionASPathPend is prepended to the
         AS-Path attribute of the route.

         Set to zero to disable.

         The value of this object tRPOperPSDefaultActionASPathPrependCount is
         ignored when the object tRPOperPSDefActASPPendCountSrc has a value
         different from actionValue(1)."
    ::= { tRPOperPSDefaultActionParamsEntry 4 }

tRPOperPSDefaultActionCommunity1 OBJECT-TYPE
    SYNTAX      TPolicyEntryEdit
    MAX-ACCESS  read-only
    STATUS      obsolete
    DESCRIPTION
        "How to apply tRPOperPSDefaultActionCommunityName1 to the communities
         for the route.

         Set to none(1) to disable this feature.

         This object is obsoleted in release 11.0. It is replaced by
         tRPOperPSDefActionAddCommEntry, tRPOperPSDefActionRemCommEntry, and
         tRPOperPSDefActionRepCommEntry."
    ::= { tRPOperPSDefaultActionParamsEntry 5 }

tRPOperPSDefaultActionCommunityName1 OBJECT-TYPE
    SYNTAX      TCommunityName
    MAX-ACCESS  read-only
    STATUS      obsolete
    DESCRIPTION
        "Community name to add, remove, or replace, to any
         existing community for the route.  Ignored when
         tRPOperPSDefaultActionCommunity1 is none(1).

         This object is obsoleted in release 11.0. It is replaced by
         tRPOperPSDefActionAddCommEntry, tRPOperPSDefActionRemCommEntry, and
         tRPOperPSDefActionRepCommEntry."
    ::= { tRPOperPSDefaultActionParamsEntry 6 }

tRPOperPSDefaultActionCommunity2 OBJECT-TYPE
    SYNTAX      TPolicyEntryEdit
    MAX-ACCESS  read-only
    STATUS      obsolete
    DESCRIPTION
        "How to apply tRPOperPSDefaultActionCommunityName2 to the communities
         for the route.

         Set to none(1) to disable this feature.

         This object is obsoleted in release 11.0. It is replaced by
         tRPOperPSDefActionAddCommEntry, tRPOperPSDefActionRemCommEntry, and
         tRPOperPSDefActionRepCommEntry."
    ::= { tRPOperPSDefaultActionParamsEntry 7 }

tRPOperPSDefaultActionCommunityName2 OBJECT-TYPE
    SYNTAX      TCommunityName
    MAX-ACCESS  read-only
    STATUS      obsolete
    DESCRIPTION
        "Community name to add, remove, or replace, to any
         existing community for the route.  Ignored when
         tRPOperPSDefaultActionCommunity2 is none(1).

         This object is obsoleted in release 11.0. It is replaced by
         tRPOperPSDefActionAddCommEntry, tRPOperPSDefActionRemCommEntry, and
         tRPOperPSDefActionRepCommEntry."
    ::= { tRPOperPSDefaultActionParamsEntry 8 }

tRPOperPSDefaultActionOrigin     OBJECT-TYPE
    SYNTAX      TPolicyEntryCriteriaOrigin
    MAX-ACCESS  read-only
    STATUS      current
    DESCRIPTION
        "The value of tRPOperPSDefaultActionOrigin indicates the origin of the
         route exported into BGP if it does not match an entry.

         The value of this object tRPOperPSDefaultActionOrigin is ignored when
         the object tRPOperPSDefActOriginSource has a value different from
         actionValue(1)."
    ::= { tRPOperPSDefaultActionParamsEntry 9 }

tRPOperPSDefaultActionLocalPreferenceSet OBJECT-TYPE
    SYNTAX      TruthValue
    MAX-ACCESS  read-only
    STATUS      current
    DESCRIPTION
        "When set to true(1), use the value of
         tRPOperPSDefaultActionLocalPreference for local preference.

         When the value of tRPOperPSDefActLocalPrefSource has a value different
         from actionValue(1), the value of
         tRPOperPSDefaultActionLocalPreferenceSet and
         tRPOperPSDefaultActionLocalPreference are ignored."
    ::= { tRPOperPSDefaultActionParamsEntry 10 }

tRPOperPSDefaultActionLocalPreference OBJECT-TYPE
    SYNTAX      TmnxBgpLocalPreference
    MAX-ACCESS  read-only
    STATUS      current
    DESCRIPTION
        "Local preference to apply to the route. Set
         tRPOperPSDefaultActionLocalPreferenceSet to false(2) to disable.

         The value of this object tRPOperPSDefaultActionLocalPreference is
         ignored when the object tRPOperPSDefActLocalPrefSource has a value
         different from actionValue(1)."
    ::= { tRPOperPSDefaultActionParamsEntry 11 }

tRPOperPSDefaultActionMetric     OBJECT-TYPE
    SYNTAX      TPolicyEntryEdit
    MAX-ACCESS  read-only
    STATUS      current
    DESCRIPTION
        "Action for tRPOperPSDefaultActionMetricValue or the metric value
         resolved from tRPOperPSDefActMetricParam depending on the
         tRPOperPSDefActionMetricSource."
    ::= { tRPOperPSDefaultActionParamsEntry 12 }

tRPOperPSDefaultActionMetricValue OBJECT-TYPE
    SYNTAX      Unsigned32
    MAX-ACCESS  read-only
    STATUS      current
    DESCRIPTION
        "Add, subtract, or set metric value.  Ignored when
         tRPOperPSDefaultActionMetric is none(1).

         The value of this object tRPOperPSDefaultActionMetricValue is ignored
         when the object tRPOperPSDefActionMetricSource has a value different
         from metricVal(2)."
    ::= { tRPOperPSDefaultActionParamsEntry 13 }

tRPOperPSDefaultActionPreference OBJECT-TYPE
    SYNTAX      TmnxBgpPreference
    MAX-ACCESS  read-only
    STATUS      current
    DESCRIPTION
        "Preference to apply to the route.

         The value of this object tRPOperPSDefaultActionPreference is ignored
         when the object tRPOperPSDefActPreferenceSource has a value different
         from actionValue(1)."
    ::= { tRPOperPSDefaultActionParamsEntry 15 }

tRPOperPSDefaultActionDamping    OBJECT-TYPE
    SYNTAX      TDampingName
    MAX-ACCESS  read-only
    STATUS      current
    DESCRIPTION
        "Damping to apply to route.  Set to empty string to disable."
    ::= { tRPOperPSDefaultActionParamsEntry 16 }

tRPOperPSDefaultActionNextHopSelf OBJECT-TYPE
    SYNTAX      TruthValue
    MAX-ACCESS  read-only
    STATUS      current
    DESCRIPTION
        "The value of tRPOperPSDefaultActionNextHopSelf indicates the
         next-hop-self on the route.

         Next-hop-self cannot be 'true' when the other next-hop objects have a
         non-default value.

         When this object has a value of 'true' then
         tRPOperPSDefActNextHopPeerAddr, tRPOperPSDefaultActionNextHop,
         tRPOperPSDefActInetNextHopType, tRPOperPSDefActInetNextHop
         tRPOperPSDefActNextHopSource and tRPOperPSDefActNextHopParam objects
         are disabled."
    ::= { tRPOperPSDefaultActionParamsEntry 17 }

tRPOperPSDefaultActionNextHop    OBJECT-TYPE
    SYNTAX      IpAddress
    MAX-ACCESS  read-only
    STATUS      current
    DESCRIPTION
        "The value of tRPOperPSDefaultActionNextHop indicates the next-hop IPv4
         address in the route.

         The object is disabled if it holds the value 255.255.255.255.

         Next-hop cannot be a valid IP address when the next-hop-self or
         peer-address is 'true'. When this object has a valid IP address then
         tRPOperPSDefaultActionNextHopSelf and tRPOperPSDefActNextHopPeerAddr
         are 'false'.

         This object is the same as tRPOperPSDefActInetNextHop when a valid
         IPv4 address is set. Please use tRPOperPSDefActInetNextHopType,
         tRPOperPSDefActInetNextHop, tRPOperPSDefActNextHopSource and
         tRPOperPSDefActNextHopParam for extended next-hop address support."
    ::= { tRPOperPSDefaultActionParamsEntry 18 }

tRPOperPSDefaultActionTag        OBJECT-TYPE
    SYNTAX      TPolicyActionTag
    MAX-ACCESS  read-only
    STATUS      current
    DESCRIPTION
        "The value of tRPOperPSDefaultActionTag indicates the operational tag
         for the route.

         A value of 0 for tRPOperPSDefaultActionTag indicates that tagging is
         disabled.

         The value of this object tRPOperPSDefaultActionTag is ignored when the
         object tRPOperPSDefActTagSource has a value different from
         actionValue(1)."
    ::= { tRPOperPSDefaultActionParamsEntry 19 }

tRPOperPSDefaultActionOspfType   OBJECT-TYPE
    SYNTAX      TOspfRouteType
    MAX-ACCESS  read-only
    STATUS      current
    DESCRIPTION
        "OSPF route type for the route.

         The value of this object tRPOperPSDefaultActionOspfType is ignored
         when the object tRPOperPSDefActOspfTypeSource has a value different
         from actionValue(1)."
    ::= { tRPOperPSDefaultActionParamsEntry 20 }

tRPOperPSDefaultActionParamsEntryLastChanged OBJECT-TYPE
    SYNTAX      TimeStamp
    MAX-ACCESS  read-only
    STATUS      obsolete
    DESCRIPTION
        "Timestamp of last change to this entry.

         tRPOperPSDefaultActionParamsEntryLastChanged is obsoleted in release
         5.0. TIMETRA-SYSTEM-MIB::tmnxConfigModify notification is used
         instead."
    ::= { tRPOperPSDefaultActionParamsEntry 21 }

tRPOperPSDefActInetNextHopType   OBJECT-TYPE
    SYNTAX      InetAddressType
    MAX-ACCESS  read-only
    STATUS      current
    DESCRIPTION
        "The value of tRPOperPSDefActInetNextHopType indicates the type of
         tRPOperPSDefActInetNextHop address, as defined in the InetAddress MIB.

         The value of this object tRPOperPSDefActInetNextHopType and
         tRPOperPSDefActInetNextHop are ignored when the object
         tRPOperPSDefActNextHopSource has a value different then
         actionValue(1)."
    ::= { tRPOperPSDefaultActionParamsEntry 22 }

tRPOperPSDefActInetNextHop       OBJECT-TYPE
    SYNTAX      InetAddress (SIZE (4|16))
    MAX-ACCESS  read-only
    STATUS      current
    DESCRIPTION
        "The value of tRPOperPSDefActInetNextHop indicates the next-hop IP
         address in the route. The object tRPOperPSDefActInetNextHop is
         disabled if it holds the value
         ffff:ffff:ffff:ffff:ffff:ffff:ffff:ffff.

         The type of this address is determined by the value of
         tRPOperPSDefActInetNextHopType object.

         Next-hop cannot be a valid IP address when the next-hop-self or
         peer-address is 'true'. When this object has a valid IP address then
         tRPOperPSDefaultActionNextHopSelf and tRPOperPSDefActNextHopPeerAddr
         are 'false'.

         tRPOperPSDefActInetNextHop object replaces
         tRPOperPSDefaultActionNextHop that supports only IPv4 address style
         next-hop.

         The value of this object tRPOperPSDefActInetNextHop is ignored when
         the object tRPOperPSDefActNextHopSource has a value different from
         actionValue(1)."
    ::= { tRPOperPSDefaultActionParamsEntry 23 }

tRPOperPSDefaultActionASPathPend OBJECT-TYPE
    SYNTAX      InetAutonomousSystemNumber
    MAX-ACCESS  read-only
    STATUS      current
    DESCRIPTION
        "The value of tRPOperPSDefaultActionASPathPend indicates the AS Number
         to prepend to the AS-Path attribute of the route.

         The AS-Path prepending is disabled when the repeat count is set to
         zero; i.e. when tRPOperPSDefaultActionASPathPrependCount is zero and
         tRPOperPSDefActASPPendCountSrc is set to actionValue(1).

         The value of this object tRPOperPSDefaultActionASPathPend is ignored
         when the object tRPOperPSDefActASPathPendSource has a value different
         from actionValue(1)."
    ::= { tRPOperPSDefaultActionParamsEntry 24 }

tRPOperPSDefActMcRedirSvcId      OBJECT-TYPE
    SYNTAX      TmnxServId
    MAX-ACCESS  read-only
    STATUS      current
    DESCRIPTION
        "The value of tRPOperPSDefActMcRedirSvcId indicates the service ID of
         the service where to redirect IGMP/MLD multicast traffic to.

         The value zero means that no multicast redirection is configured."
    ::= { tRPOperPSDefaultActionParamsEntry 30 }

tRPOperPSDefActMcRedirIfIndex    OBJECT-TYPE
    SYNTAX      InterfaceIndexOrZero
    MAX-ACCESS  read-only
    STATUS      current
    DESCRIPTION
        "The value of tRPOperPSDefActMcRedirIfIndex indicates the interface
         index of the interface where to redirect IGMP/MLD multicast traffic
         to.

         The value zero means that no multicast redirection is configured."
    ::= { tRPOperPSDefaultActionParamsEntry 31 }

tRPOperPSDefActionMetricSource   OBJECT-TYPE
    SYNTAX      TPolicyActionMetricSource
    MAX-ACCESS  read-only
    STATUS      current
    DESCRIPTION
        "The value of tRPOperPSDefActionMetricSource indicates the source of
         the default action metric.

         The value 'igpCost(1)' means that the value of MED (Multi Exit
         Discriminator) or the metric value is derived from the IGP (Interior
         Gateway Protocol) cost of the route and the value of the object
         tRPOperPSDefaultActionMetricValue and the object
         tRPOperPSDefActMetricParam are ignored.

         The value 'metricVal(2)' means the metric value is the value of
         tRPOperPSDefaultActionMetricValue. The value of the object
         tRPOperPSDefActMetricParam is ignored.

         The value 'metricParam(3) means the metric value is derived from the
         object tRPOperPSDefActMetricParam; the value of the object
         tRPOperPSDefaultActionMetricValue is ignored."
    ::= { tRPOperPSDefaultActionParamsEntry 32 }

tRPOperPSDefActionAigpMetric     OBJECT-TYPE
    SYNTAX      TPolicyEntryAigpMetricEdit
    MAX-ACCESS  read-only
    STATUS      current
    DESCRIPTION
        "The value of tRPOperPSDefActionAigpMetric indicates the editing action
         to be taken for the AIGP (Accumulated IGP) attribute when the route
         satisfies the match criteria of the policy.

         When the value of tRPOperPSDefActionAigpMetric is set to 'none(1)' or
         'useIgp(4)', the value of tRPOperPSDefActnAigpMetricVal,
         tRPOperPSDefActAigpMetricSource and tRPOperPSDefActAigpMetricParam are
         ignored."
    ::= { tRPOperPSDefaultActionParamsEntry 33 }

tRPOperPSDefActnAigpMetricVal    OBJECT-TYPE
    SYNTAX      Unsigned32
    MAX-ACCESS  read-only
    STATUS      current
    DESCRIPTION
        "The value of tRPOperPSDefActnAigpMetricVal indicates the value to be
         added or set for the route AIGP(Accumulated IGP) metric.

         When the value of tRPOperPSDefActionAigpMetric is set to 'none(1)' or
         'useIgp(4)', the value of tRPOperPSDefActnAigpMetricVal is ignored.

         The value of this object tRPOperPSDefActnAigpMetricVal is ignored when
         the object tRPOperPSDefActAigpMetricSource has a value different from
         actionValue(1)."
    ::= { tRPOperPSDefaultActionParamsEntry 34 }

tRPOperPSDefActnSrcClassIndex    OBJECT-TYPE
    SYNTAX      ClassIndexOrNone
    MAX-ACCESS  read-only
    STATUS      current
    DESCRIPTION
        "The value of tRPOperPSDefActnSrcClassIndex specifies the default
         operational source-class for this policy statement.

         A value of 0 means no source-class."
    DEFVAL      { 0 }
    ::= { tRPOperPSDefaultActionParamsEntry 35 }

tRPOperPSDefActnDstClassIndex    OBJECT-TYPE
    SYNTAX      ClassIndexOrNone
    MAX-ACCESS  read-only
    STATUS      current
    DESCRIPTION
        "The value of tRPOperPSDefActnDstClassIndex specifies the default
         operational dest-class for this policy statement.

         A value of 0 means no dest-class."
    DEFVAL      { 0 }
    ::= { tRPOperPSDefaultActionParamsEntry 36 }

tRPOperPSDefActnOrigValidState   OBJECT-TYPE
    SYNTAX      INTEGER {
        notApplicable (0),
        valid         (1),
        notFound      (2),
        invalid       (3)
    }
    MAX-ACCESS  read-only
    STATUS      current
    DESCRIPTION
        "The value of tRPOperPSDefActnOrigValidState indicates the default
         operational origin validation state for this policy statement.

         The value of this object tRPOperPSDefActnOrigValidState is ignored
         when the object tRPOperPSDefActOrigValStateSrc has a value different
         from actionValue(1)."
    DEFVAL      { notApplicable }
    ::= { tRPOperPSDefaultActionParamsEntry 37 }

tRPOperPSParamsTableLastChanged  OBJECT-TYPE
    SYNTAX      TimeStamp
    MAX-ACCESS  read-only
    STATUS      obsolete
    DESCRIPTION
        "Timestamp of last change to tRPOperPSParamsTable.

         tRPOperPSParamsTableLastChanged is obsoleted in release 5.0.
         TIMETRA-SYSTEM-MIB::tmnxConfigModify notification is used instead."
    ::= { tRPOperValueObjects 13 }

tRPOperPSParamsTable             OBJECT-TYPE
    SYNTAX      SEQUENCE OF TRPOperPSParamsEntry
    MAX-ACCESS  not-accessible
    STATUS      current
    DESCRIPTION
        "A table of policy statement entries."
    ::= { tRPOperValueObjects 14 }

tRPOperPSParamsEntry             OBJECT-TYPE
    SYNTAX      TRPOperPSParamsEntry
    MAX-ACCESS  not-accessible
    STATUS      current
    DESCRIPTION
        "Information about a particular policy statement entry.

         Entries are created when a policy statement parameters entry is
         created. Entries are deleted when a policy statement parameters entry
         is destroyed."
    INDEX       {
        tRPOperPolicyStatementName,
        tRPOperPSNameEntryIndex
    }
    ::= { tRPOperPSParamsTable 1 }

TRPOperPSParamsEntry             ::= SEQUENCE
{
    tRPOperPSNameEntryIndex          TPolicyStatementEntryID,
    tRPOperPSParamsRowStatus         RowStatus,
    tRPOperPSParamsDescription       TItemDescription,
    tRPOperPSParamsAction            TPolicyEntryAction,
    tRPOperPSParamsEntryLastChanged  TimeStamp,
    tRPOperPSParamsCreationOrigin    TmnxCreateOrigin
}

tRPOperPSNameEntryIndex          OBJECT-TYPE
    SYNTAX      TPolicyStatementEntryID
    MAX-ACCESS  not-accessible
    STATUS      current
    DESCRIPTION
        "Identifier for this policy statement entry."
    ::= { tRPOperPSParamsEntry 1 }

tRPOperPSParamsRowStatus         OBJECT-TYPE
    SYNTAX      RowStatus
    MAX-ACCESS  read-only
    STATUS      current
    DESCRIPTION
        "RowStatus for this row.

         To create or destroy entries in this table, use the
         tRPAdminPSParamsTable."
    ::= { tRPOperPSParamsEntry 2 }

tRPOperPSParamsDescription       OBJECT-TYPE
    SYNTAX      TItemDescription
    MAX-ACCESS  read-only
    STATUS      current
    DESCRIPTION
        "Description for this policy statement entry."
    ::= { tRPOperPSParamsEntry 3 }

tRPOperPSParamsAction            OBJECT-TYPE
    SYNTAX      TPolicyEntryAction
    MAX-ACCESS  read-only
    STATUS      current
    DESCRIPTION
        "The action to take when a route matches this policy statement entry's
         to or from criteria."
    ::= { tRPOperPSParamsEntry 4 }

tRPOperPSParamsEntryLastChanged  OBJECT-TYPE
    SYNTAX      TimeStamp
    MAX-ACCESS  read-only
    STATUS      obsolete
    DESCRIPTION
        "Timestamp of last change to this entry.

         tRPOperPSParamsEntryLastChanged is obsoleted in release 5.0.
         TIMETRA-SYSTEM-MIB::tmnxConfigModify notification is used instead."
    ::= { tRPOperPSParamsEntry 5 }

tRPOperPSParamsCreationOrigin    OBJECT-TYPE
    SYNTAX      TmnxCreateOrigin
    MAX-ACCESS  read-only
    STATUS      current
    DESCRIPTION
        "The value of the object tRPOperPSParamsCreationOrigin indicates the
         mechanism used to create this entry."
    ::= { tRPOperPSParamsEntry 6 }

tRPOperPSAcceptActionParamsTableLastChanged OBJECT-TYPE
    SYNTAX      TimeStamp
    MAX-ACCESS  read-only
    STATUS      obsolete
    DESCRIPTION
        "Timestamp of last change to tRPOperPSAcceptActionParamsTable.

         tRPOperPSAcceptActionParamsTableLastChanged is obsoleted in release
         5.0. TIMETRA-SYSTEM-MIB::tmnxConfigModify notification is used
         instead."
    ::= { tRPOperValueObjects 15 }

tRPOperPSAcceptActionParamsTable OBJECT-TYPE
    SYNTAX      SEQUENCE OF TRPOperPSAcceptActionParamsEntry
    MAX-ACCESS  not-accessible
    STATUS      current
    DESCRIPTION
        "Accept-action parameters for a policy statement."
    ::= { tRPOperValueObjects 16 }

tRPOperPSAcceptActionParamsEntry OBJECT-TYPE
    SYNTAX      TRPOperPSAcceptActionParamsEntry
    MAX-ACCESS  not-accessible
    STATUS      current
    DESCRIPTION
        "Accept-action information for a policy statement entry.

         Entries are created when tRPOperPSParamsAction is 'accept(1)',
         'reject(2)', 'continue(3)' or 'nextPolicy(4)'. Entries are deleted
         when a policy statement is destroyed or tRPOperPSParamsAction is
         'none(0)'."
    INDEX       {
        tRPOperPolicyStatementName,
        tRPOperPSNameEntryIndex
    }
    ::= { tRPOperPSAcceptActionParamsTable 1 }

TRPOperPSAcceptActionParamsEntry ::= SEQUENCE
{
    tRPOperPSAcceptActionASPath      TPolicyEntryEdit,
    tRPOperPSAcceptActionASPathName  TASPathName,
    tRPOperPSAcceptActionASPathPrependAS TmnxBgpAutonomousSystem,
    tRPOperPSAcceptActionASPathPrependCount Integer32,
    tRPOperPSAcceptActionCommunity1  TPolicyEntryEdit,
    tRPOperPSAcceptActionCommunityName1 TCommunityName,
    tRPOperPSAcceptActionCommunity2  TPolicyEntryEdit,
    tRPOperPSAcceptActionCommunityName2 TCommunityName,
    tRPOperPSAcceptActionOrigin      TPolicyEntryCriteriaOrigin,
    tRPOperPSAcceptActionLocalPreferenceSet TruthValue,
    tRPOperPSAcceptActionLocalPreference TmnxBgpLocalPreference,
    tRPOperPSAcceptActionMetric      TPolicyEntryEdit,
    tRPOperPSAcceptActionMetricValue Unsigned32,
    tRPOperPSAcceptActionPreference  TmnxBgpPreference,
    tRPOperPSAcceptActionDamping     TDampingName,
    tRPOperPSAcceptActionNextHopSelf TruthValue,
    tRPOperPSAcceptActionNextHop     IpAddress,
    tRPOperPSAcceptActionTag         TPolicyActionTag,
    tRPOperPSAcceptActionOspfType    TOspfRouteType,
    tRPOperPSAcceptActionParamsEntryLastChanged TimeStamp,
    tRPOperPSAcptActInetNextHopType  InetAddressType,
    tRPOperPSAcptActInetNextHop      InetAddress,
    tRPOperPSAcceptActionASPathPend  InetAutonomousSystemNumber,
    tRPOperPSAcceptActionFC          TNamedItemOrEmpty,
    tRPOperPSAcceptActionFCPriority  TPriorityOrUndefined,
    tRPOperPSAcptActMcRedirSvcId     TmnxServId,
    tRPOperPSAcptActMcRedirIfIndex   InterfaceIndexOrZero,
    tRPOperPSAcptActnMetricSource    TPolicyActionMetricSource,
    tRPOperPSAcptActionAigpMetric    TPolicyEntryAigpMetricEdit,
    tRPOperPSAcptActnAigpMetricVal   Unsigned32,
    tRPOperPSAcptActnSrcClassIndex   ClassIndexOrNone,
    tRPOperPSAcptActnDstClassIndex   ClassIndexOrNone,
    tRPOperPSAcptActnOrigValidState  INTEGER
}

tRPOperPSAcceptActionASPath      OBJECT-TYPE
    SYNTAX      TPolicyEntryEdit
    MAX-ACCESS  read-only
    STATUS      current
    DESCRIPTION
        "The AS Path rewrite information for the route."
    ::= { tRPOperPSAcceptActionParamsEntry 1 }

tRPOperPSAcceptActionASPathName  OBJECT-TYPE
    SYNTAX      TASPathName
    MAX-ACCESS  read-only
    STATUS      current
    DESCRIPTION
        "AS Path Name to add, remove, or replace. Ignored when
         tRPOperPSAcceptActionASPath is none(1)"
    ::= { tRPOperPSAcceptActionParamsEntry 2 }

tRPOperPSAcceptActionASPathPrependAS OBJECT-TYPE
    SYNTAX      TmnxBgpAutonomousSystem
    MAX-ACCESS  read-only
    STATUS      obsolete
    DESCRIPTION
        "AS Number to prepend to the AS-Path attribute of the route. Ignored
         when tRPOperPSAcceptActionASPathPrependCount is zero.

         This object was obsoleted in release 7.0.  It is replaced with the
         4-byte AS number defined by tRPOperPSAcceptActionASPathPend."
    ::= { tRPOperPSAcceptActionParamsEntry 3 }

tRPOperPSAcceptActionASPathPrependCount OBJECT-TYPE
    SYNTAX      Integer32 (0..50)
    MAX-ACCESS  read-only
    STATUS      current
    DESCRIPTION
        "Number of times to prepend tRPOperPSAcceptActionASPathPend to the
         route.

         Set to zero to disable this feature.

         The value of this object tRPOperPSAcceptActionASPathPrependCount is
         ignored when the object tRPOperPSAcptActASPPendCountSrc has a value
         different from actionValue(1)."
    ::= { tRPOperPSAcceptActionParamsEntry 4 }

tRPOperPSAcceptActionCommunity1  OBJECT-TYPE
    SYNTAX      TPolicyEntryEdit
    MAX-ACCESS  read-only
    STATUS      obsolete
    DESCRIPTION
        "How to apply tRPOperPSAcceptActionCommunityName1 to the route.

         This object is obsoleted in release 11.0. It is replaced by
         tRPOperPSAccActionAddCommEntry, tRPOperPSAccActionRemCommEntry, and
         tRPOperPSAccActionRepCommEntry."
    ::= { tRPOperPSAcceptActionParamsEntry 5 }

tRPOperPSAcceptActionCommunityName1 OBJECT-TYPE
    SYNTAX      TCommunityName
    MAX-ACCESS  read-only
    STATUS      obsolete
    DESCRIPTION
        "Community to apply to the route.  Ignored when
         tRPOperPSAcceptActionCommunity1 is set to none(1).

         This object is obsoleted in release 11.0. It is replaced by
         tRPOperPSAccActionAddCommEntry, tRPOperPSAccActionRemCommEntry, and
         tRPOperPSAccActionRepCommEntry."
    ::= { tRPOperPSAcceptActionParamsEntry 6 }

tRPOperPSAcceptActionCommunity2  OBJECT-TYPE
    SYNTAX      TPolicyEntryEdit
    MAX-ACCESS  read-only
    STATUS      obsolete
    DESCRIPTION
        "How to apply tRPOperPSAcceptActionCommunityName2 to the route.

         This object is obsoleted in release 11.0. It is replaced by
         tRPOperPSAccActionAddCommEntry, tRPOperPSAccActionRemCommEntry, and
         tRPOperPSAccActionRepCommEntry."
    ::= { tRPOperPSAcceptActionParamsEntry 7 }

tRPOperPSAcceptActionCommunityName2 OBJECT-TYPE
    SYNTAX      TCommunityName
    MAX-ACCESS  read-only
    STATUS      obsolete
    DESCRIPTION
        "Community to apply to the route.  Ignored when
         tRPOperPSAcceptActionCommunity2 is set to none(1).

         This object is obsoleted in release 11.0. It is replaced by
         tRPOperPSAccActionAddCommEntry, tRPOperPSAccActionRemCommEntry, and
         tRPOperPSAccActionRepCommEntry."
    ::= { tRPOperPSAcceptActionParamsEntry 8 }

tRPOperPSAcceptActionOrigin      OBJECT-TYPE
    SYNTAX      TPolicyEntryCriteriaOrigin
    MAX-ACCESS  read-only
    STATUS      current
    DESCRIPTION
        "The value of tRPOperPSAcceptActionOrigin indicates the origin of the
         route exported into BGP if it matches an entry.

         The value of this object tRPOperPSAcceptActionOrigin is ignored when
         the object tRPOperPSAcptActOriginSource has a value different from
         actionValue(1)."
    ::= { tRPOperPSAcceptActionParamsEntry 9 }

tRPOperPSAcceptActionLocalPreferenceSet OBJECT-TYPE
    SYNTAX      TruthValue
    MAX-ACCESS  read-only
    STATUS      current
    DESCRIPTION
        "When set to true(1), use tRPOperPSAcceptActionLocalPreference for the
         local preference for the route.

         When the value of tRPOperPSAcptActLocalPrefSource has a value
         different from actionValue(1), the value of
         tRPOperPSAcceptActionLocalPreferenceSet and
         tRPOperPSAcceptActionLocalPreference are ignored."
    ::= { tRPOperPSAcceptActionParamsEntry 10 }

tRPOperPSAcceptActionLocalPreference OBJECT-TYPE
    SYNTAX      TmnxBgpLocalPreference
    MAX-ACCESS  read-only
    STATUS      current
    DESCRIPTION
        "Local preference for the route. Ignored when
         tRPOperPSAcceptActionLocalPreferenceSet is false(2).

         The value of this object tRPOperPSAcceptActionLocalPreference is
         ignored when the object tRPOperPSAcptActLocalPrefSource has a value
         different from actionValue(1)."
    ::= { tRPOperPSAcceptActionParamsEntry 11 }

tRPOperPSAcceptActionMetric      OBJECT-TYPE
    SYNTAX      TPolicyEntryEdit
    MAX-ACCESS  read-only
    STATUS      current
    DESCRIPTION
        "How to apply the metric value to the route.

         The metric value is obtained from tRPOperPSAcceptActionMetricValue or
         tRPOperPSAcptActMetricParam depending on the value of
         tRPOperPSAcptActnMetricSource ."
    ::= { tRPOperPSAcceptActionParamsEntry 12 }

tRPOperPSAcceptActionMetricValue OBJECT-TYPE
    SYNTAX      Unsigned32
    MAX-ACCESS  read-only
    STATUS      current
    DESCRIPTION
        "Value to add, subtract, or set for the route metric. Ignored when
         tRPOperPSAcceptActionMetric is none(1).

         The value of this object tRPOperPSAcceptActionMetricValue is ignored
         when the object tRPOperPSAcptActnMetricSource has a value different
         from metricVal(2)."
    ::= { tRPOperPSAcceptActionParamsEntry 13 }

tRPOperPSAcceptActionPreference  OBJECT-TYPE
    SYNTAX      TmnxBgpPreference
    MAX-ACCESS  read-only
    STATUS      current
    DESCRIPTION
        "Preference to set in route.

         The value of this object tRPOperPSAcceptActionPreference is ignored
         when the object tRPOperPSAcptActPreferenceSource has a value different
         from actionValue(1)."
    ::= { tRPOperPSAcceptActionParamsEntry 15 }

tRPOperPSAcceptActionDamping     OBJECT-TYPE
    SYNTAX      TDampingName
    MAX-ACCESS  read-only
    STATUS      current
    DESCRIPTION
        "Damping to apply to route.  Set to empty string to disable."
    ::= { tRPOperPSAcceptActionParamsEntry 16 }

tRPOperPSAcceptActionNextHopSelf OBJECT-TYPE
    SYNTAX      TruthValue
    MAX-ACCESS  read-only
    STATUS      current
    DESCRIPTION
        "The value of tRPOperPSAcceptActionNextHopSelf indicates the
         next-hop-self on the route.

         Next-hop-self cannot be 'true' when the other next-hop objects have a
         non-default value.

         When this object has a value of 'true' then
         tRPOperPSAcptActNextHopPeerAddr, tRPOperPSAcceptActionNextHop,
         tRPOperPSAcptActInetNextHopType, tRPOperPSAcptActInetNextHop,
         tRPOperPSAcptActNextHopSource and tRPOperPSAcptActNextHopParam objects
         are disabled."
    ::= { tRPOperPSAcceptActionParamsEntry 17 }

tRPOperPSAcceptActionNextHop     OBJECT-TYPE
    SYNTAX      IpAddress
    MAX-ACCESS  read-only
    STATUS      current
    DESCRIPTION
        "The value of tRPOperPSAcceptActionNextHop indicates the next-hop IPv4
         address in the route.

         The object is disabled if it holds the value 255.255.255.255.

         Next-hop cannot be a valid IP address when the next-hop-self or
         peer-address is 'true'. When this object has a valid IP address then
         tRPOperPSAcceptActionNextHopSelf and tRPOperPSAcptActNextHopPeerAddr
         are 'false'.

         This object is the same as tRPOperPSAcptActInetNextHop when a valid
         IPv4 address is set. Please use tRPOperPSAcptActInetNextHopType,
         tRPOperPSAcptActInetNextHop, tRPOperPSAcptActNextHopSource and
         tRPOperPSAcptActNextHopParam for extended next-hop address support."
    ::= { tRPOperPSAcceptActionParamsEntry 18 }

tRPOperPSAcceptActionTag         OBJECT-TYPE
    SYNTAX      TPolicyActionTag
    MAX-ACCESS  read-only
    STATUS      current
    DESCRIPTION
        "The value of tRPOperPSAcceptActionTag indicates the operational tag
         for the route.

         A value of 0 for tRPOperPSAcceptActionTag indicates that tagging is
         disabled.

         The value of this object tRPOperPSAcceptActionTag is ignored when the
         object tRPOperPSAcptActTagSource has a value different from
         actionValue(1)."
    ::= { tRPOperPSAcceptActionParamsEntry 19 }

tRPOperPSAcceptActionOspfType    OBJECT-TYPE
    SYNTAX      TOspfRouteType
    MAX-ACCESS  read-only
    STATUS      current
    DESCRIPTION
        "OSPF route type to set in route.

         The value of this object tRPOperPSAcceptActionOspfType is ignored when
         the object tRPOperPSAcptActOspfTypeSource has a value different from
         actionValue(1)."
    ::= { tRPOperPSAcceptActionParamsEntry 20 }

tRPOperPSAcceptActionParamsEntryLastChanged OBJECT-TYPE
    SYNTAX      TimeStamp
    MAX-ACCESS  read-only
    STATUS      obsolete
    DESCRIPTION
        "Timestamp of last change to this entry.

         tRPOperPSAcceptActionParamsEntryLastChanged is obsoleted in release
         5.0. TIMETRA-SYSTEM-MIB::tmnxConfigModify notification is used
         instead."
    ::= { tRPOperPSAcceptActionParamsEntry 21 }

tRPOperPSAcptActInetNextHopType  OBJECT-TYPE
    SYNTAX      InetAddressType
    MAX-ACCESS  read-only
    STATUS      current
    DESCRIPTION
        "The value of tRPOperPSAcptActInetNextHopType indicates the type of
         tRPOperPSAcptActInetNextHop address, as defined in the InetAddress
         MIB.

         The value of this object tRPOperPSAcptActInetNextHopType and
         tRPOperPSAcptActInetNextHop are ignored when the object
         tRPOperPSAcptActNextHopSource has a value different then
         actionValue(1)."
    ::= { tRPOperPSAcceptActionParamsEntry 22 }

tRPOperPSAcptActInetNextHop      OBJECT-TYPE
    SYNTAX      InetAddress (SIZE (4|16))
    MAX-ACCESS  read-only
    STATUS      current
    DESCRIPTION
        "The value of tRPOperPSAcptActInetNextHop indicates the next-hop IP
         address in the route. Next-hop is disabled if the value of
         tRPOperPSAcptActInetNextHopType is 'ipv6' and the value of
         tRPOperPSAcptActInetNextHop is
         ffff:ffff:ffff:ffff:ffff:ffff:ffff:ffff.

         The type of this address is determined by the value of
         tRPOperPSAcptActInetNextHopType object.

         Next-hop cannot be a valid IP address when the next-hop-self or
         peer-address is 'true'. When this object has a valid IP address then
         tRPOperPSAcceptActionNextHopSelf and tRPOperPSAcptActNextHopPeerAddr
         are 'false'.

         tRPOperPSAcptActInetNextHop object replaces
         tRPOperPSAcceptActionNextHop that supports only IPv4 address style
         next-hop.

         The value of this object tRPOperPSAcptActInetNextHop is ignored when
         the object tRPOperPSAcptActNextHopSource has a value different from
         actionValue(1)."
    ::= { tRPOperPSAcceptActionParamsEntry 23 }

tRPOperPSAcceptActionASPathPend  OBJECT-TYPE
    SYNTAX      InetAutonomousSystemNumber
    MAX-ACCESS  read-only
    STATUS      current
    DESCRIPTION
        "The value of tRPOperPSAcceptActionASPathPend indicates the AS Number
         to prepend to the AS-Path attribute of the route.

         The AS-Path prepending is disabled when the repeat count is set to
         zero; i.e. when tRPOperPSAcceptActionASPathPrependCount is zero and
         tRPOperPSAcptActASPPendCountSrc is set to actionValue(1).

         The value of this object tRPOperPSAcceptActionASPathPend is ignored
         when the object tRPOperPSAcptActASPathPendSource has a value different
         from actionValue(1)."
    ::= { tRPOperPSAcceptActionParamsEntry 24 }

tRPOperPSAcceptActionFC          OBJECT-TYPE
    SYNTAX      TNamedItemOrEmpty
    MAX-ACCESS  read-only
    STATUS      current
    DESCRIPTION
        "The value of tRPOperPSAcceptActionFC indicates the forwarding class
         associated with the routes matched by this route policy entry."
    ::= { tRPOperPSAcceptActionParamsEntry 25 }

tRPOperPSAcceptActionFCPriority  OBJECT-TYPE
    SYNTAX      TPriorityOrUndefined
    MAX-ACCESS  read-only
    STATUS      current
    DESCRIPTION
        "The value of tRPOperPSAcceptActionFCPriority indicates the priority to
         be assigned to the routes matched by this route policy entry."
    ::= { tRPOperPSAcceptActionParamsEntry 26 }

tRPOperPSAcptActMcRedirSvcId     OBJECT-TYPE
    SYNTAX      TmnxServId
    MAX-ACCESS  read-only
    STATUS      current
    DESCRIPTION
        "The value of tRPOperPSAcptActMcRedirSvcId indicates the service ID of
         the service where to redirect IGMP/MLD multicast traffic to.

         The value zero means that no multicast redirection is configured."
    DEFVAL      { 0 }
    ::= { tRPOperPSAcceptActionParamsEntry 30 }

tRPOperPSAcptActMcRedirIfIndex   OBJECT-TYPE
    SYNTAX      InterfaceIndexOrZero
    MAX-ACCESS  read-only
    STATUS      current
    DESCRIPTION
        "The value of tRPOperPSAcptActMcRedirIfIndex indicates the interface
         index of the interface where to redirect IGMP/MLD multicast traffic
         to.

         The value zero means that no multicast redirection is configured."
    DEFVAL      { 0 }
    ::= { tRPOperPSAcceptActionParamsEntry 31 }

tRPOperPSAcptActnMetricSource    OBJECT-TYPE
    SYNTAX      TPolicyActionMetricSource
    MAX-ACCESS  read-only
    STATUS      current
    DESCRIPTION
        "The value of tRPOperPSAcptActnMetricSource indicates the source of the
         accept action metric.

         The value 'igpCost(1)' means that the value of MED (Multi Exit
         Discriminator) or the metric value is derived from the IGP (Interior
         Gateway Protocol) cost of the route and the value of the object
         tRPOperPSAcceptActionMetricValue and the object
         tRPOperPSAcptActMetricParam are ignored.

         The value 'metricVal(2)' means the metric value is the value of
         tRPOperPSAcceptActionMetricValue. The value of the object
         tRPOperPSAcptActMetricParam is ignored.

         The value 'metricParam(3) means the metric value is derived from the
         object tRPOperPSAcptActMetricParam; the value of the object
         tRPOperPSAcceptActionMetricValue is ignored."
    DEFVAL      { metricVal }
    ::= { tRPOperPSAcceptActionParamsEntry 32 }

tRPOperPSAcptActionAigpMetric    OBJECT-TYPE
    SYNTAX      TPolicyEntryAigpMetricEdit
    MAX-ACCESS  read-only
    STATUS      current
    DESCRIPTION
        "The value of tRPOperPSAcptActionAigpMetric indicates the editing
         action to be taken for the AIGP (Accumulated IGP) attribute when the
         route satisfies the match criteria of the policy.

         When the value of tRPOperPSAcptActionAigpMetric is set to 'none(1)' or
         'useIgp(4)', the value of tRPOperPSAcptActnAigpMetricVal,
         tRPOperPSAcptActAigpMetricSource and tRPOperPSAcptActAigpMetricParam
         are ignored."
    ::= { tRPOperPSAcceptActionParamsEntry 33 }

tRPOperPSAcptActnAigpMetricVal   OBJECT-TYPE
    SYNTAX      Unsigned32
    MAX-ACCESS  read-only
    STATUS      current
    DESCRIPTION
        "The value of tRPOperPSAcptActnAigpMetricVal indicates the value to be
         added or set for the route AIGP(Accumulated IGP) metric.

         When the value of tRPOperPSAcptActionAigpMetric is set to 'none(1)' or
         'useIgp(4)', the value of tRPOperPSAcptActnAigpMetricVal is ignored.

         The value of this object tRPOperPSAcptActnAigpMetricVal is ignored
         when the object tRPOperPSAcptActAigpMetricSource has a value different
         from actionValue(1)."
    ::= { tRPOperPSAcceptActionParamsEntry 34 }

tRPOperPSAcptActnSrcClassIndex   OBJECT-TYPE
    SYNTAX      ClassIndexOrNone
    MAX-ACCESS  read-only
    STATUS      current
    DESCRIPTION
        "The value of tRPOperPSAcptActnSrcClassIndex specifies the operational
         source-class for this policy statement.

         A value of 0 means no source-class."
    DEFVAL      { 0 }
    ::= { tRPOperPSAcceptActionParamsEntry 35 }

tRPOperPSAcptActnDstClassIndex   OBJECT-TYPE
    SYNTAX      ClassIndexOrNone
    MAX-ACCESS  read-only
    STATUS      current
    DESCRIPTION
        "The value of tRPOperPSAcptActnDstClassIndex specifies the operational
         dest-class for this policy statement.

         A value of 0 means no dest-class."
    DEFVAL      { 0 }
    ::= { tRPOperPSAcceptActionParamsEntry 36 }

tRPOperPSAcptActnOrigValidState  OBJECT-TYPE
    SYNTAX      INTEGER {
        notApplicable (0),
        valid         (1),
        notFound      (2),
        invalid       (3)
    }
    MAX-ACCESS  read-only
    STATUS      current
    DESCRIPTION
        "The value of tRPOperPSAcptActnOrigValidState indicates the operational
         value for origin validation state for this policy statement.

         The value of this object tRPOperPSAcptActnOrigValidState is ignored
         when the object tRPOperPSAcptActOrigValStateSrc has a value different
         from actionValue(1)."
    DEFVAL      { notApplicable }
    ::= { tRPOperPSAcceptActionParamsEntry 37 }

tRPOperPSToCriteriaTableLastChanged OBJECT-TYPE
    SYNTAX      TimeStamp
    MAX-ACCESS  read-only
    STATUS      obsolete
    DESCRIPTION
        "Timestamp of last change to tRPOperPSToCriteriaTable.

         tRPOperPSToCriteriaTableLastChanged is obsoleted in release 5.0.
         TIMETRA-SYSTEM-MIB::tmnxConfigModify notification is used instead."
    ::= { tRPOperValueObjects 17 }

tRPOperPSToCriteriaTable         OBJECT-TYPE
    SYNTAX      SEQUENCE OF TRPOperPSToCriteriaEntry
    MAX-ACCESS  not-accessible
    STATUS      current
    DESCRIPTION
        "A table of policy statement entry 'to' criteria"
    ::= { tRPOperValueObjects 18 }

tRPOperPSToCriteriaEntry         OBJECT-TYPE
    SYNTAX      TRPOperPSToCriteriaEntry
    MAX-ACCESS  not-accessible
    STATUS      current
    DESCRIPTION
        "Information about a policy statement entry's -to- criteria. Entries
         are created when a policy statement entry is created. Entries are
         deleted when a policy statement entry is destroyed."
    INDEX       {
        tRPOperPolicyStatementName,
        tRPOperPSToCriteriaIndex
    }
    ::= { tRPOperPSToCriteriaTable 1 }

TRPOperPSToCriteriaEntry         ::= SEQUENCE
{
    tRPOperPSToCriteriaIndex         TPolicyStatementEntryID,
    tRPOperPSToCriteriaRowStatus     RowStatus,
    tRPOperPSToCriteriaProtocol      TRoutePolicyProtocol,
    tRPOperPSToCriteriaNeighborIpAddr IpAddress,
    tRPOperPSToCriteriaNeighborPrefixList TLPrefixListName,
    tRPOperPSToCriteriaEntryLastChanged TimeStamp,
    tRPOperPSToCriteriaIsisLevel     TIsisLevel,
    tRPOperPSToCriteriaPrefixList1   TLPrefixListName,
    tRPOperPSToCriteriaPrefixList2   TLPrefixListName,
    tRPOperPSToCriteriaPrefixList3   TLPrefixListName,
    tRPOperPSToCriteriaPrefixList4   TLPrefixListName,
    tRPOperPSToCriteriaPrefixList5   TLPrefixListName,
    tRPOperPSToCritNbrInetAddrType   InetAddressType,
    tRPOperPSToCritNbrInetAddr       InetAddress,
    tRPOperPSToCriteriaInstanceId    Unsigned32,
    tRPOperPSToCritProtocolBits      TRoutePolicyProtocolBits
}

tRPOperPSToCriteriaIndex         OBJECT-TYPE
    SYNTAX      TPolicyStatementEntryID
    MAX-ACCESS  not-accessible
    STATUS      current
    DESCRIPTION
        "The policy statement entry ID"
    ::= { tRPOperPSToCriteriaEntry 1 }

tRPOperPSToCriteriaRowStatus     OBJECT-TYPE
    SYNTAX      RowStatus
    MAX-ACCESS  read-only
    STATUS      current
    DESCRIPTION
        "RowStatus for this row.

         To create or destroy entries in this table, use the
         tRPAdminPSToCriteriaTable."
    ::= { tRPOperPSToCriteriaEntry 2 }

tRPOperPSToCriteriaProtocol      OBJECT-TYPE
    SYNTAX      TRoutePolicyProtocol
    MAX-ACCESS  read-only
    STATUS      deprecated
    DESCRIPTION
        "The protocol name to match on. Set to none(1) to disable.

         This object is deprecated, please use the object
         tRPOperPSToCritProtocolBits instead."
    ::= { tRPOperPSToCriteriaEntry 3 }

tRPOperPSToCriteriaNeighborIpAddr OBJECT-TYPE
    SYNTAX      IpAddress
    MAX-ACCESS  read-only
    STATUS      current
    DESCRIPTION
        "The IP address of neighbor to match on. Set to 255.255.255.255 to
         disable."
    ::= { tRPOperPSToCriteriaEntry 4 }

tRPOperPSToCriteriaNeighborPrefixList OBJECT-TYPE
    SYNTAX      TLPrefixListName
    MAX-ACCESS  read-only
    STATUS      current
    DESCRIPTION
        "The name of a neighbor prefix list to match on. Set to empty string to
         disable."
    ::= { tRPOperPSToCriteriaEntry 5 }

tRPOperPSToCriteriaEntryLastChanged OBJECT-TYPE
    SYNTAX      TimeStamp
    MAX-ACCESS  read-only
    STATUS      obsolete
    DESCRIPTION
        "Timestamp of last change to this entry.

         tRPOperPSToCriteriaEntryLastChanged is obsoleted in release 5.0.
         TIMETRA-SYSTEM-MIB::tmnxConfigModify notification is used instead."
    ::= { tRPOperPSToCriteriaEntry 6 }

tRPOperPSToCriteriaIsisLevel     OBJECT-TYPE
    SYNTAX      TIsisLevel
    MAX-ACCESS  read-only
    STATUS      current
    DESCRIPTION
        "The value for tRPOperPSToCriteriaIsisLevel defines the IS-IS route
         level match criterion. A value of 0 indicates that no IS-IS route
         level match criterion has been configured."
    ::= { tRPOperPSToCriteriaEntry 7 }

tRPOperPSToCriteriaPrefixList1   OBJECT-TYPE
    SYNTAX      TLPrefixListName
    MAX-ACCESS  read-only
    STATUS      current
    DESCRIPTION
        "The value of tRPOperPSToCriteriaPrefixList1 indicates the name of the
         first prefix list to match on. Setting this value to an empty string
         disables this prefix list as a match criteria.

         This object is the same as tRPOperPSToCritPrefixList1, please use
         tRPOperPSToCritPfxListTable to match on more prefix lists."
    ::= { tRPOperPSToCriteriaEntry 8 }

tRPOperPSToCriteriaPrefixList2   OBJECT-TYPE
    SYNTAX      TLPrefixListName
    MAX-ACCESS  read-only
    STATUS      current
    DESCRIPTION
        "The value of tRPOperPSToCriteriaPrefixList2 indicates the name of the
         second prefix list to match on. Setting this value to an empty string
         disables this prefix list as a match criteria.

         This object is the same as tRPOperPSToCritPrefixList2, please use
         tRPOperPSToCritPfxListTable to match on more prefix lists."
    ::= { tRPOperPSToCriteriaEntry 9 }

tRPOperPSToCriteriaPrefixList3   OBJECT-TYPE
    SYNTAX      TLPrefixListName
    MAX-ACCESS  read-only
    STATUS      current
    DESCRIPTION
        "The value of tRPOperPSToCriteriaPrefixList3 indicates the name of the
         third prefix list to match on. Setting this value to an empty string
         disables this prefix list as a match criteria.

         This object is the same as tRPOperPSToCritPrefixList3, please use
         tRPOperPSToCritPfxListTable to match on more prefix lists."
    ::= { tRPOperPSToCriteriaEntry 10 }

tRPOperPSToCriteriaPrefixList4   OBJECT-TYPE
    SYNTAX      TLPrefixListName
    MAX-ACCESS  read-only
    STATUS      current
    DESCRIPTION
        "The value of tRPOperPSToCriteriaPrefixList4 indicates the name of the
         fourth prefix list to match on. Setting this value to an empty string
         disables this prefix list as a match criteria.

         This object is the same as tRPOperPSToCritPrefixList4, please use
         tRPOperPSToCritPfxListTable to match on more prefix lists."
    ::= { tRPOperPSToCriteriaEntry 11 }

tRPOperPSToCriteriaPrefixList5   OBJECT-TYPE
    SYNTAX      TLPrefixListName
    MAX-ACCESS  read-only
    STATUS      current
    DESCRIPTION
        "The value of tRPOperPSToCriteriaPrefixList5 indicates the name of the
         fifth prefix list to match on. Setting this value to an empty string
         disables this prefix list as a match criteria.

         This object is the same as tRPOperPSToCritPrefixList5, please use
         tRPOperPSToCritPfxListTable to match on more prefix lists."
    ::= { tRPOperPSToCriteriaEntry 12 }

tRPOperPSToCritNbrInetAddrType   OBJECT-TYPE
    SYNTAX      InetAddressType
    MAX-ACCESS  read-only
    STATUS      current
    DESCRIPTION
        "The value of tRPOperPSToCritNbrInetAddrType indicates the type of
         tRPOperPSToCritNbrInetAddr address, as defined in the InetAddress MIB."
    ::= { tRPOperPSToCriteriaEntry 13 }

tRPOperPSToCritNbrInetAddr       OBJECT-TYPE
    SYNTAX      InetAddress (SIZE (4|16|20))
    MAX-ACCESS  read-only
    STATUS      current
    DESCRIPTION
        "The value of tRPOperPSToCritNbrInetAddr indicates the IP address of
         neighbor to match on. The object tRPOperPSToCritNbrInetAddr is
         disabled if it holds the value ff:ff:ff:ff.

         The type of this address is determined by the value of
         tRPOperPSToCritNbrInetAddrType object.

         tRPOperPSToCritNbrInetAddr object replaces
         tRPOperPSToCriteriaNeighborIpAddr that supports only IPv4 address
         style neighbor."
    ::= { tRPOperPSToCriteriaEntry 14 }

tRPOperPSToCriteriaInstanceId    OBJECT-TYPE
    SYNTAX      Unsigned32 (0..127 | 4294967295)
    MAX-ACCESS  read-only
    STATUS      current
    DESCRIPTION
        "The value of tRPOperPSToCriteriaInstanceId indicates the instance
         identifier of the ISIS or OSPF(v3) protocol running in the router
         instance.

         The value of tRPOperPSToCriteriaInstanceId will be 0 in case
         tRPOperPSToCritProtocolBits has bits set different from isis(5),
         ospf(6) and ospf3(12).

         The supported instance range depends on the protocol that is set in
         tRPOperPSToCritProtocolBits:
         protocol isis  - instance range 0..127.
         protocol ospf  - instance range 0..31.
         protocol ospf3 - instance range 0..31|64..95.

         If the value of tRPOperPSToCriteriaInstanceId is 4294967295, all
         instances of the ISIS or OSPF(v3) protocol are leaked into BGP."
    ::= { tRPOperPSToCriteriaEntry 15 }

tRPOperPSToCritProtocolBits      OBJECT-TYPE
    SYNTAX      TRoutePolicyProtocolBits
    MAX-ACCESS  read-only
    STATUS      current
    DESCRIPTION
        "The value of tRPOperPSToCritProtocolBits indicates the protocol name
         to match on.

         When the 'none' bit is set, the protocol match criteria is disabled."
    ::= { tRPOperPSToCriteriaEntry 16 }

tRPOperPSFromCriteriaTableLastChanged OBJECT-TYPE
    SYNTAX      TimeStamp
    MAX-ACCESS  read-only
    STATUS      obsolete
    DESCRIPTION
        "Timestamp of last change to tRPOperPSFromCriteriaTable.

         tRPOperPSFromCriteriaTableLastChanged is obsoleted in release 5.0.
         TIMETRA-SYSTEM-MIB::tmnxConfigModify notification is used instead."
    ::= { tRPOperValueObjects 19 }

tRPOperPSFromCriteriaTable       OBJECT-TYPE
    SYNTAX      SEQUENCE OF TRPOperPSFromCriteriaEntry
    MAX-ACCESS  not-accessible
    STATUS      current
    DESCRIPTION
        "A table of from filter criteria for each policy statement entry."
    ::= { tRPOperValueObjects 20 }

tRPOperPSFromCriteriaEntry       OBJECT-TYPE
    SYNTAX      TRPOperPSFromCriteriaEntry
    MAX-ACCESS  not-accessible
    STATUS      current
    DESCRIPTION
        "Information about policy statement entry -from- criteria.

         Entries are created when a policy statement entry is created. Entries
         are deleted when a policy statement entry is destroyed."
    INDEX       {
        tRPOperPolicyStatementName,
        tRPOperPSFromCriteriaIndex
    }
    ::= { tRPOperPSFromCriteriaTable 1 }

TRPOperPSFromCriteriaEntry       ::= SEQUENCE
{
    tRPOperPSFromCriteriaIndex       TPolicyStatementEntryID,
    tRPOperPSFromCriteriaRowStatus   RowStatus,
    tRPOperPSFromCriteriaProtocol    TRoutePolicyProtocol,
    tRPOperPSFromCriteriaNeighborIpAddr IpAddress,
    tRPOperPSFromCriteriaNeighborPrefixList TLPrefixListName,
    tRPOperPSFromCriteriaPrefixList1 TLPrefixListName,
    tRPOperPSFromCriteriaPrefixList2 TLPrefixListName,
    tRPOperPSFromCriteriaPrefixList3 TLPrefixListName,
    tRPOperPSFromCriteriaPrefixList4 TLPrefixListName,
    tRPOperPSFromCriteriaPrefixList5 TLPrefixListName,
    tRPOperPSFromCriteriaASPath      TASPathName,
    tRPOperPSFromCriteriaCommunity   TLCommunityName,
    tRPOperPSFromCriteriaOrigin      TPolicyEntryCriteriaOrigin,
    tRPOperPSFromCriteriaOspfRouteType TOspfRouteType,
    tRPOperPSFromCriteriaEntryLastChanged TimeStamp,
    tRPOperPSFromCriteriaArea        IpAddress,
    tRPOperPSFromCriteriaAreaConfigured TruthValue,
    tRPOperPSFromCriteriaIsisLevel   TIsisLevel,
    tRPOperPSFromCriteriaIsisExternal TruthValue,
    tRPOperPSFromCriteriaIgmpHostPrefixList TLPrefixListName,
    tRPOperPSFromCriteriaGrpAddrPrefixList TLPrefixListName,
    tRPOperPSFromCriteriaSrcAddr     IpAddress,
    tRPOperPSFromCriteriaInterface   TNamedItemOrEmpty,
    tRPOperPSFromCriteriaTag         TPolicyActionTag,
    tRPOperPSFromCritNbrInetAddrType InetAddressType,
    tRPOperPSFromCritNbrInetAddr     InetAddress,
    tRPOperPSFromCritSrcInetAddrType InetAddressType,
    tRPOperPSFromCritSrcInetAddr     InetAddress,
    tRPOperPSFromCriteriaFamily      TmnxBGPFamilyType,
    tRPOperPSFromCriteriaInstanceId  Unsigned32,
    tRPOperPSFromCriteriaMatchTag    TmnxEnabledDisabled,
    tRPOperPSFromCriteriaState       TPolicyEntryCriteriaState,
    tRPOperPSFromCritASPathGroup     TASPathGroupName,
    tRPOperPSFromCriteriaPolicy      TXLPolicyNameOrExpOrEmpty,
    tRPOperPSFromCritCreationOrigin  TmnxCreateOrigin,
    tRPOperPSFromCritProtocolBits    TRoutePolicyProtocolBits
}

tRPOperPSFromCriteriaIndex       OBJECT-TYPE
    SYNTAX      TPolicyStatementEntryID
    MAX-ACCESS  not-accessible
    STATUS      current
    DESCRIPTION
        "The policy statement entry ID"
    ::= { tRPOperPSFromCriteriaEntry 1 }

tRPOperPSFromCriteriaRowStatus   OBJECT-TYPE
    SYNTAX      RowStatus
    MAX-ACCESS  read-only
    STATUS      current
    DESCRIPTION
        "RowStatus for this row.

         To create or destroy entries in this table, use the
         tRPAdminPSFromCriteriaTable."
    ::= { tRPOperPSFromCriteriaEntry 2 }

tRPOperPSFromCriteriaProtocol    OBJECT-TYPE
    SYNTAX      TRoutePolicyProtocol
    MAX-ACCESS  read-only
    STATUS      deprecated
    DESCRIPTION
        "The protocol name to match on. Set to none(1) to disable.

         This object is deprecated, please use the object
         tRPOperPSFromCritProtocolBits instead."
    ::= { tRPOperPSFromCriteriaEntry 3 }

tRPOperPSFromCriteriaNeighborIpAddr OBJECT-TYPE
    SYNTAX      IpAddress
    MAX-ACCESS  read-only
    STATUS      current
    DESCRIPTION
        "The IP address of neighbor to match on. Set to 255.255.255.255 to
         disable."
    ::= { tRPOperPSFromCriteriaEntry 4 }

tRPOperPSFromCriteriaNeighborPrefixList OBJECT-TYPE
    SYNTAX      TLPrefixListName
    MAX-ACCESS  read-only
    STATUS      current
    DESCRIPTION
        "The name of a neighbor prefix list to match on. Set to empty string to
         disable."
    ::= { tRPOperPSFromCriteriaEntry 5 }

tRPOperPSFromCriteriaPrefixList1 OBJECT-TYPE
    SYNTAX      TLPrefixListName
    MAX-ACCESS  read-only
    STATUS      current
    DESCRIPTION
        "The name of the first prefix list to match on. Set to empty string to
         disable.

         This object is the same as tRPOperPSFromCritPrefixList1, please use
         tRPOperPSFromCritPfxListTable to match on more prefix lists."
    ::= { tRPOperPSFromCriteriaEntry 6 }

tRPOperPSFromCriteriaPrefixList2 OBJECT-TYPE
    SYNTAX      TLPrefixListName
    MAX-ACCESS  read-only
    STATUS      current
    DESCRIPTION
        "The name of the second prefix list to match on. Set to empty string to
         disable.

         This object is the same as tRPOperPSFromCritPrefixList2, please use
         tRPOperPSFromCritPfxListTable to match on more prefix lists."
    ::= { tRPOperPSFromCriteriaEntry 7 }

tRPOperPSFromCriteriaPrefixList3 OBJECT-TYPE
    SYNTAX      TLPrefixListName
    MAX-ACCESS  read-only
    STATUS      current
    DESCRIPTION
        "The name of the third prefix list to match on. Set to empty string to
         disable.

         This object is the same as tRPOperPSFromCritPrefixList3, please use
         tRPOperPSFromCritPfxListTable to match on more prefix lists."
    ::= { tRPOperPSFromCriteriaEntry 8 }

tRPOperPSFromCriteriaPrefixList4 OBJECT-TYPE
    SYNTAX      TLPrefixListName
    MAX-ACCESS  read-only
    STATUS      current
    DESCRIPTION
        "The name of the fourth prefix list to match on. Set to empty string to
         disable.

         This object is the same as tRPOperPSFromCritPrefixList4, please use
         tRPOperPSFromCritPfxListTable to match on more prefix lists."
    ::= { tRPOperPSFromCriteriaEntry 9 }

tRPOperPSFromCriteriaPrefixList5 OBJECT-TYPE
    SYNTAX      TLPrefixListName
    MAX-ACCESS  read-only
    STATUS      current
    DESCRIPTION
        "The name of the fifth prefix list to match on. Set to empty string to
         disable.

         This object is the same as tRPOperPSFromCritPrefixList5, please use
         tRPOperPSFromCritPfxListTable to match on more prefix lists."
    ::= { tRPOperPSFromCriteriaEntry 10 }

tRPOperPSFromCriteriaASPath      OBJECT-TYPE
    SYNTAX      TASPathName
    MAX-ACCESS  read-only
    STATUS      current
    DESCRIPTION
        "The name of the AS Path to match on. Set to empty string to disable."
    ::= { tRPOperPSFromCriteriaEntry 11 }

tRPOperPSFromCriteriaCommunity   OBJECT-TYPE
    SYNTAX      TLCommunityName
    MAX-ACCESS  read-only
    STATUS      current
    DESCRIPTION
        "The name of the community to match on. Set to empty string to disable."
    ::= { tRPOperPSFromCriteriaEntry 12 }

tRPOperPSFromCriteriaOrigin      OBJECT-TYPE
    SYNTAX      TPolicyEntryCriteriaOrigin
    MAX-ACCESS  read-only
    STATUS      current
    DESCRIPTION
        "The value of tRPOperPSFromCriteriaOrigin indicates the route match
         criterion for an entry."
    ::= { tRPOperPSFromCriteriaEntry 13 }

tRPOperPSFromCriteriaOspfRouteType OBJECT-TYPE
    SYNTAX      TOspfRouteType
    MAX-ACCESS  read-only
    STATUS      current
    DESCRIPTION
        "The OSPF route type to match on. Set to zero to disable."
    ::= { tRPOperPSFromCriteriaEntry 14 }

tRPOperPSFromCriteriaEntryLastChanged OBJECT-TYPE
    SYNTAX      TimeStamp
    MAX-ACCESS  read-only
    STATUS      obsolete
    DESCRIPTION
        "Timestamp of last change to this entry.

         tRPOperPSFromCriteriaEntryLastChanged is obsoleted in release 5.0.
         TIMETRA-SYSTEM-MIB::tmnxConfigModify notification is used instead."
    ::= { tRPOperPSFromCriteriaEntry 15 }

tRPOperPSFromCriteriaArea        OBJECT-TYPE
    SYNTAX      IpAddress
    MAX-ACCESS  read-only
    STATUS      current
    DESCRIPTION
        "Used when redistributing OSPF routes into other protocols. Specifies
         the OSPF area that must be matched in filtered routes."
    ::= { tRPOperPSFromCriteriaEntry 16 }

tRPOperPSFromCriteriaAreaConfigured OBJECT-TYPE
    SYNTAX      TruthValue
    MAX-ACCESS  read-only
    STATUS      current
    DESCRIPTION
        "Specifies if the tRPOperPSFromCriteriaArea has been configured"
    ::= { tRPOperPSFromCriteriaEntry 17 }

tRPOperPSFromCriteriaIsisLevel   OBJECT-TYPE
    SYNTAX      TIsisLevel
    MAX-ACCESS  read-only
    STATUS      current
    DESCRIPTION
        "The value for tRPOperPSFromCriteriaIsisLevel defines the IS-IS route
         level match criterion. A value of 0 indicates that no IS-IS route
         level match criterion has been configured."
    ::= { tRPOperPSFromCriteriaEntry 18 }

tRPOperPSFromCriteriaIsisExternal OBJECT-TYPE
    SYNTAX      TruthValue
    MAX-ACCESS  read-only
    STATUS      current
    DESCRIPTION
        "When tRPOperPSFromCriteriaIsisExternal is 'true', match only External
         IS-IS routes. If 'false', match all routes. External IS-IS routes are
         those routes that have been learned from outside the IS-IS domain."
    ::= { tRPOperPSFromCriteriaEntry 19 }

tRPOperPSFromCriteriaIgmpHostPrefixList OBJECT-TYPE
    SYNTAX      TLPrefixListName
    MAX-ACCESS  read-only
    STATUS      current
    DESCRIPTION
        "tRPOperPSFromCriteriaIgmpHostPrefixList contains the name of the
         prefix list that is used to match the IGMP/MLD host IP address. The
         value of the object will be an empty string if it not set."
    ::= { tRPOperPSFromCriteriaEntry 20 }

tRPOperPSFromCriteriaGrpAddrPrefixList OBJECT-TYPE
    SYNTAX      TLPrefixListName
    MAX-ACCESS  read-only
    STATUS      current
    DESCRIPTION
        "tRPOperPSFromCriteriaGrpAddrPrefixList contains the name of the prefix
         list that is used to match the multicast group address. The value of
         the object will be an empty string if it not set."
    ::= { tRPOperPSFromCriteriaEntry 21 }

tRPOperPSFromCriteriaSrcAddr     OBJECT-TYPE
    SYNTAX      IpAddress
    MAX-ACCESS  read-only
    STATUS      current
    DESCRIPTION
        "tRPOperPSFromCriteriaSrcAddr contains the IP address of the source to
         match on. This object will be used by multicast protocols like PIM and
         IGMP/MLD. The value of this object will be 0.0.0.0 if it is not set."
    ::= { tRPOperPSFromCriteriaEntry 22 }

tRPOperPSFromCriteriaInterface   OBJECT-TYPE
    SYNTAX      TNamedItemOrEmpty
    MAX-ACCESS  read-only
    STATUS      current
    DESCRIPTION
        "tRPOperPSFromCriteriaInterface contains the name of the interface to
         match on. PIM Bootstrap route policy will use this object to
         accept/reject bootstrap messages coming on the interface specified by
         this object. The value of the object will be an empty string if it not
         set."
    ::= { tRPOperPSFromCriteriaEntry 23 }

tRPOperPSFromCriteriaTag         OBJECT-TYPE
    SYNTAX      TPolicyActionTag
    MAX-ACCESS  read-only
    STATUS      current
    DESCRIPTION
        "The value of tRPOperPSFromCriteriaTag indicates the operational tag to
         match on. It will only be valid when tRPOperPSFromCriteriaMatchTag is
         enabled which indicates that route matching based on tags is enabled.

         A value of 0 for tRPOperPSFromCriteriaTag when
         tRPOperPSFromCriteriaMatchTag is enabled indicates untagged routes are
         matched."
    ::= { tRPOperPSFromCriteriaEntry 24 }

tRPOperPSFromCritNbrInetAddrType OBJECT-TYPE
    SYNTAX      InetAddressType
    MAX-ACCESS  read-only
    STATUS      current
    DESCRIPTION
        "The value of tRPOperPSFromCritNbrInetAddrType indicates the type of
         tRPOperPSFromCritNbrInetAddr address, as defined in the InetAddress
         MIB."
    ::= { tRPOperPSFromCriteriaEntry 25 }

tRPOperPSFromCritNbrInetAddr     OBJECT-TYPE
    SYNTAX      InetAddress (SIZE (4|16|20))
    MAX-ACCESS  read-only
    STATUS      current
    DESCRIPTION
        "The value of tRPOperPSFromCritNbrInetAddr indicates the IP address of
         neighbor to match on. The object tRPOperPSFromCritNbrInetAddr is
         disabled if it holds the value ff:ff:ff:ff.

         The type of this address is determined by the value of the
         tRPOperPSFromCritNbrInetAddrType object.

         tRPOperPSFromCritNbrInetAddr object replaces
         tRPOperPSFromCriteriaNeighborIpAddr that supports only IPv4 address
         style neighbor."
    ::= { tRPOperPSFromCriteriaEntry 26 }

tRPOperPSFromCritSrcInetAddrType OBJECT-TYPE
    SYNTAX      InetAddressType
    MAX-ACCESS  read-only
    STATUS      current
    DESCRIPTION
        "The value of tRPOperPSFromCritSrcInetAddrType indicates the type of
         tRPOperPSFromCritSrcInetAddr address, as defined in the InetAddress
         MIB."
    ::= { tRPOperPSFromCriteriaEntry 27 }

tRPOperPSFromCritSrcInetAddr     OBJECT-TYPE
    SYNTAX      InetAddress (SIZE (4|16))
    MAX-ACCESS  read-only
    STATUS      current
    DESCRIPTION
        "The value of tRPOperPSFromCritSrcInetAddr indicates the IP address of
         the source to match on. This object will be used by multicast
         protocols like PIM and IGMP/MLD and is disabled if it holds the value
         ffff:ffff:ffff:ffff:ffff:ffff:ffff:ffff.

         The type of this address is determined by the value of the
         tRPOperPSFromCritSrcInetAddrType object.

         tRPOperPSFromCritSrcInetAddr object replaces
         tRPOperPSFromCriteriaSrcAddr that supports only IPv4 address style
         source."
    ::= { tRPOperPSFromCriteriaEntry 28 }

tRPOperPSFromCriteriaFamily      OBJECT-TYPE
    SYNTAX      TmnxBGPFamilyType
    MAX-ACCESS  read-only
    STATUS      current
    DESCRIPTION
        "The  bits set in the value of tRPAdminPSFromCriteriaFamily indicate
         the address families that this condition would match against."
    ::= { tRPOperPSFromCriteriaEntry 29 }

tRPOperPSFromCriteriaInstanceId  OBJECT-TYPE
    SYNTAX      Unsigned32 (0..127 | 4294967295)
    MAX-ACCESS  read-only
    STATUS      current
    DESCRIPTION
        "The value of tRPOperPSFromCriteriaInstanceId indicates the instance
         identifier of the ISIS or OSPF(v3) protocol running in the router
         instance.

         The value of tRPOperPSFromCriteriaInstanceId will be 0 in case
         tRPOperPSFromCritProtocolBits has bits set different from isis(5),
         ospf(6) and ospf3(12).

         The supported instance range depends on the protocol that is set in
         tRPOperPSFromCritProtocolBits:
         protocol isis  - instance range 0..127.
         protocol ospf  - instance range 0..31.
         protocol ospf3 - instance range 0..31|64..95.

         If the value of tRPOperPSFromCriteriaInstanceId is 4294967295, all
         instances of the ISIS or OSPF(v3) protocol are leaked into BGP."
    ::= { tRPOperPSFromCriteriaEntry 30 }

tRPOperPSFromCriteriaMatchTag    OBJECT-TYPE
    SYNTAX      TmnxEnabledDisabled
    MAX-ACCESS  read-only
    STATUS      current
    DESCRIPTION
        "The value of tRPOperPSFromCriteriaMatchTag indicates if tag matching
         is enabled or disabled."
    ::= { tRPOperPSFromCriteriaEntry 31 }

tRPOperPSFromCriteriaState       OBJECT-TYPE
    SYNTAX      TPolicyEntryCriteriaState
    MAX-ACCESS  read-only
    STATUS      current
    DESCRIPTION
        "The value of tRPOperPSFromCriteriaState indicates the route state
         match criterion for this entry."
    ::= { tRPOperPSFromCriteriaEntry 32 }

tRPOperPSFromCritASPathGroup     OBJECT-TYPE
    SYNTAX      TASPathGroupName
    MAX-ACCESS  read-only
    STATUS      current
    DESCRIPTION
        "The value of tRPOperPSFromCritASPathGroup indicates the AS-Path Group
         match criterion for this entry."
    ::= { tRPOperPSFromCriteriaEntry 33 }

tRPOperPSFromCriteriaPolicy      OBJECT-TYPE
    SYNTAX      TXLPolicyNameOrExpOrEmpty
    MAX-ACCESS  read-only
    STATUS      current
    DESCRIPTION
        "The value of tRPOperPSFromCriteriaPolicy indicates the policy match
         criterion for this entry."
    ::= { tRPOperPSFromCriteriaEntry 34 }

tRPOperPSFromCritCreationOrigin  OBJECT-TYPE
    SYNTAX      TmnxCreateOrigin
    MAX-ACCESS  read-only
    STATUS      current
    DESCRIPTION
        "The value of the object tRPOperPSFromCritCreationOrigin indicates the
         mechanism used to create this entry."
    ::= { tRPOperPSFromCriteriaEntry 35 }

tRPOperPSFromCritProtocolBits    OBJECT-TYPE
    SYNTAX      TRoutePolicyProtocolBits
    MAX-ACCESS  read-only
    STATUS      current
    DESCRIPTION
        "The value of tRPOperPSFromCritProtocolBits indicates the protocol name
         to match on.

         When the 'none' bit is set, the protocol match criteria is disabled."
    ::= { tRPOperPSFromCriteriaEntry 36 }

tRPOperInetPrefixListTblLastChg  OBJECT-TYPE
    SYNTAX      TimeStamp
    MAX-ACCESS  read-only
    STATUS      obsolete
    DESCRIPTION
        "The value of tRPOperInetPrefixListTblLastChg indicates the timestamp
         of last change to tRPOperInetPrefixListTable.

         tRPOperInetPrefixListTblLastChg is obsoleted in release 5.0.
         TIMETRA-SYSTEM-MIB::tmnxConfigModify notification is used instead."
    ::= { tRPOperValueObjects 21 }

tRPOperInetPrefixListTable       OBJECT-TYPE
    SYNTAX      SEQUENCE OF TRPOperInetPrefixListEntry
    MAX-ACCESS  not-accessible
    STATUS      current
    DESCRIPTION
        "The table of IPv4 and IPv6 operational prefix lists."
    ::= { tRPOperValueObjects 22 }

tRPOperInetPrefixListEntry       OBJECT-TYPE
    SYNTAX      TRPOperInetPrefixListEntry
    MAX-ACCESS  not-accessible
    STATUS      current
    DESCRIPTION
        "Each row entry in the tRPOperInetPrefixListTable represents
         information about a particular prefix list.

         Entries are created and deleted by the user via
         tRPAdminInetPrefixListTable."
    INDEX       {
        tRPOperInetPrefixListName,
        tRPOperInetPrefixListPrefixType,
        tRPOperInetPrefixListPrefix,
        tRPOperInetPrefixListPrefixLen,
        tRPOperInetPrefixListType
    }
    ::= { tRPOperInetPrefixListTable 1 }

TRPOperInetPrefixListEntry       ::= SEQUENCE
{
    tRPOperInetPrefixListName        TLPrefixListName,
    tRPOperInetPrefixListPrefixType  InetAddressType,
    tRPOperInetPrefixListPrefix      InetAddress,
    tRPOperInetPrefixListPrefixLen   InetAddressPrefixLength,
    tRPOperInetPrefixListType        INTEGER,
    tRPOperInetPrefixListRowStatus   RowStatus,
    tRPOperInetPrefixListThroughLen  InetAddressPrefixLength,
    tRPOperInetPrefixListLastChg     TimeStamp,
    tRPOperInetPrefixListBeginLen    InetAddressPrefixLength,
    tRPOperInetPrefixListCrOrigin    TmnxCreateOrigin
}

tRPOperInetPrefixListName        OBJECT-TYPE
    SYNTAX      TLPrefixListName (SIZE (1..64))
    MAX-ACCESS  not-accessible
    STATUS      current
    DESCRIPTION
        "The value of tRPOperInetPrefixListName indicates the name of the
         prefix list entry."
    ::= { tRPOperInetPrefixListEntry 1 }

tRPOperInetPrefixListPrefixType  OBJECT-TYPE
    SYNTAX      InetAddressType
    MAX-ACCESS  not-accessible
    STATUS      current
    DESCRIPTION
        "The value of tRPOperInetPrefixListPrefixType indicates the address
         type of tRPOperInetPrefixListPrefix."
    ::= { tRPOperInetPrefixListEntry 2 }

tRPOperInetPrefixListPrefix      OBJECT-TYPE
    SYNTAX      InetAddress (SIZE (4|16))
    MAX-ACCESS  not-accessible
    STATUS      current
    DESCRIPTION
        "The value of tRPOperInetPrefixListPrefix indicates the IP prefix of
         the prefix list entry."
    ::= { tRPOperInetPrefixListEntry 3 }

tRPOperInetPrefixListPrefixLen   OBJECT-TYPE
    SYNTAX      InetAddressPrefixLength
    MAX-ACCESS  not-accessible
    STATUS      current
    DESCRIPTION
        "The value of tRPOperInetPrefixListPrefixLen indicates the IP prefix
         length of the prefix list entry."
    ::= { tRPOperInetPrefixListEntry 4 }

tRPOperInetPrefixListType        OBJECT-TYPE
    SYNTAX      INTEGER {
        exact       (1),
        longer      (2),
        through     (3),
        range       (4),
        to          (5),
        addressMask (6)
    }
    MAX-ACCESS  not-accessible
    STATUS      current
    DESCRIPTION
        "The value of tRPOperInetPrefixListType indicates the type of the
         prefix length entry.

         exact (1) - a route's prefix/length must match the prefix list entry
         exactly in order for an entry to be considered a match.

         longer (2) - a route's prefix/length must match the defined prefix AND
         have a length that is an exact match or longer in order for an entry
         to be considered a match.

         through (3) - a route's prefix/length must match the defined prefix
         AND have a length that is an exact match or longer up to and including
         the defined maximum length in order for an entry to be considered a
         match.

         range (4) - a route's prefix/length must match the defined prefix AND
         have a length that is greater than or equal to the length defined by
         tRPOperInetPrefixListBeginLen and less than or equal to the length
         defined by tRPOperInetPrefixListThroughLen in order for an entry to be
         considered a match.

         to (5) - a route's prefix/length must match the condition  from a
         start prefix/length to an end prefix/length. The  end prefix/length is
         indicated in the corresponding entry in  the tRPOperPfxListToTable.

         addressMask (6) - a route's prefix/length must match the prefix length
         of the prefix-list entry and the bitwise logical AND of the route
         address and the mask must match the bitwise  logical AND from the
         prefix-list address and the mask. The  address mask must be specified
         in a corresponding entry in the tRPOperPfxListAddressMaskTable."
    ::= { tRPOperInetPrefixListEntry 5 }

tRPOperInetPrefixListRowStatus   OBJECT-TYPE
    SYNTAX      RowStatus
    MAX-ACCESS  read-only
    STATUS      current
    DESCRIPTION
        "RowStatus for this row.

         To create or destroy entries in this table, use the
         tRPAdminInetPrefixListTable."
    ::= { tRPOperInetPrefixListEntry 6 }

tRPOperInetPrefixListThroughLen  OBJECT-TYPE
    SYNTAX      InetAddressPrefixLength
    MAX-ACCESS  read-only
    STATUS      current
    DESCRIPTION
        "The value of tRPOperInetPrefixListThroughLen indicates the prefix
         length to use when tRPOperInetPrefixListType set to through(3). The
         value must be larger than tRPOperInetPrefixListPrefixLen."
    ::= { tRPOperInetPrefixListEntry 7 }

tRPOperInetPrefixListLastChg     OBJECT-TYPE
    SYNTAX      TimeStamp
    MAX-ACCESS  read-only
    STATUS      obsolete
    DESCRIPTION
        "The value of tRPOperInetPrefixListLastChg indicates the timestamp of
         last change to this entry.

         tRPOperInetPrefixListLastChg is obsoleted in release 5.0.
         TIMETRA-SYSTEM-MIB::tmnxConfigModify notification is used instead."
    ::= { tRPOperInetPrefixListEntry 8 }

tRPOperInetPrefixListBeginLen    OBJECT-TYPE
    SYNTAX      InetAddressPrefixLength
    MAX-ACCESS  read-only
    STATUS      current
    DESCRIPTION
        "The value of tRPOperInetPrefixListBeginLen indicates the prefix length
         to use as the lower limit for the prefix range when
         tRPOperInetPrefixListType set to range(4). The value must be larger
         than tRPOperInetPrefixListPrefixLen and less than
         tRPOperInetPrefixListThroughLen."
    ::= { tRPOperInetPrefixListEntry 9 }

tRPOperInetPrefixListCrOrigin    OBJECT-TYPE
    SYNTAX      TmnxCreateOrigin
    MAX-ACCESS  read-only
    STATUS      current
    DESCRIPTION
        "The value of the object tRPOperInetPrefixListCrOrigin indicates the
         mechanism used to create this entry."
    ::= { tRPOperInetPrefixListEntry 10 }

tRPOperCommunityExprTable        OBJECT-TYPE
    SYNTAX      SEQUENCE OF TRPOperCommunityExprEntry
    MAX-ACCESS  not-accessible
    STATUS      current
    DESCRIPTION
        "A table of community entries."
    ::= { tRPOperValueObjects 25 }

tRPOperCommunityExprEntry        OBJECT-TYPE
    SYNTAX      TRPOperCommunityExprEntry
    MAX-ACCESS  not-accessible
    STATUS      current
    DESCRIPTION
        "Information about a particular community member. Entries are created
         by user, via tRPAdminCommunityExprTable. Entries are deleted by user,
         via tRPAdminCommunityExprTable."
    INDEX       { tRPOperCommunityExprName }
    ::= { tRPOperCommunityExprTable 1 }

TRPOperCommunityExprEntry        ::= SEQUENCE
{
    tRPOperCommunityExprName         TLCommunityName,
    tRPOperCommunityExprRowStatus    RowStatus,
    tRPOperCommunityExprString1      TCommunityMemberExpression,
    tRPOperCommunityExprString2      TCommunityMemberExpression,
    tRPOperCommunityExprString3      TCommunityMemberExpression,
    tRPOperCommunityExprString4      TCommunityMemberExpression,
    tRPOperCommunityExprExactMatch   TruthValue
}

tRPOperCommunityExprName         OBJECT-TYPE
    SYNTAX      TLCommunityName (SIZE (1..64))
    MAX-ACCESS  not-accessible
    STATUS      current
    DESCRIPTION
        "The value of object tRPOperCommunityExprName indicates the name of the
         community used as an index for this table."
    ::= { tRPOperCommunityExprEntry 1 }

tRPOperCommunityExprRowStatus    OBJECT-TYPE
    SYNTAX      RowStatus
    MAX-ACCESS  read-only
    STATUS      current
    DESCRIPTION
        "The value of object tRPOperCommunityExprRowStatus indicates the
         RowStatus for this row.

         To create or destroy entries in this table, use the
         tRPAdminCommunityExprTable."
    ::= { tRPOperCommunityExprEntry 2 }

tRPOperCommunityExprString1      OBJECT-TYPE
    SYNTAX      TCommunityMemberExpression
    MAX-ACCESS  read-only
    STATUS      current
    DESCRIPTION
        "The value of object tRPOperCommunityExprString1 indicates an
         expression that matches AS Numbers or Community ID's.

         The objects tRPOperCommunityExprString1, tRPOperCommunityExprString2,
         tRPOperCommunityExprString3 and tRPOperCommunityExprString4 are
         substrings that form one string of type TCommunityMemberExpression."
    ::= { tRPOperCommunityExprEntry 3 }

tRPOperCommunityExprString2      OBJECT-TYPE
    SYNTAX      TCommunityMemberExpression
    MAX-ACCESS  read-only
    STATUS      current
    DESCRIPTION
        "The value of object tRPOperCommunityExprString2 indicates an
         expression that matches AS Numbers or Community ID's.

         The objects tRPOperCommunityExprString1, tRPOperCommunityExprString2,
         tRPOperCommunityExprString3 and tRPOperCommunityExprString4 are
         substrings that form one string of type TCommunityMemberExpression."
    ::= { tRPOperCommunityExprEntry 4 }

tRPOperCommunityExprString3      OBJECT-TYPE
    SYNTAX      TCommunityMemberExpression
    MAX-ACCESS  read-only
    STATUS      current
    DESCRIPTION
        "The value of object tRPOperCommunityExprString3 indicates an
         expression that matches AS Numbers or Community ID's.

         The objects tRPOperCommunityExprString1, tRPOperCommunityExprString2,
         tRPOperCommunityExprString3 and tRPOperCommunityExprString4 are
         substrings that form one string of type TCommunityMemberExpression."
    ::= { tRPOperCommunityExprEntry 5 }

tRPOperCommunityExprString4      OBJECT-TYPE
    SYNTAX      TCommunityMemberExpression
    MAX-ACCESS  read-only
    STATUS      current
    DESCRIPTION
        "The value of object tRPOperCommunityExprString4 indicates an
         expression that matches AS Numbers or Community ID's.

         The objects tRPOperCommunityExprString1, tRPOperCommunityExprString2,
         tRPOperCommunityExprString3 and tRPOperCommunityExprString4 are
         substrings that form one string of type TCommunityMemberExpression."
    ::= { tRPOperCommunityExprEntry 6 }

tRPOperCommunityExprExactMatch   OBJECT-TYPE
    SYNTAX      TruthValue
    MAX-ACCESS  read-only
    STATUS      current
    DESCRIPTION
        "The value of object tRPOperCommunityExprExactMatch indicates whether
         the expression in this table entry is only evaluated on an exact
         match.

         If the value of this object is 'true', then the community expression
         only matches a given route if all communities attached to the route
         are strictly required to match the expression and no redundant
         communities are present."
    ::= { tRPOperCommunityExprEntry 7 }

tRPOperASPathGroupTable          OBJECT-TYPE
    SYNTAX      SEQUENCE OF TRPOperASPathGroupEntry
    MAX-ACCESS  not-accessible
    STATUS      current
    DESCRIPTION
        "The table of AS-Path Groups."
    ::= { tRPOperValueObjects 26 }

tRPOperASPathGroupEntry          OBJECT-TYPE
    SYNTAX      TRPOperASPathGroupEntry
    MAX-ACCESS  not-accessible
    STATUS      current
    DESCRIPTION
        "Each row entry in the tRPOperASPathGroupTable represents information
         about a particular AS-Path Group.

         Entries are created by user via tRPAdminASPathGroupTable. Entries are
         deleted by user via tRPAdminASPathGroupTable."
    INDEX       {
        tRPOperASPathGroupName,
        tRPOperASPathGroupEntryIndex
    }
    ::= { tRPOperASPathGroupTable 1 }

TRPOperASPathGroupEntry          ::= SEQUENCE
{
    tRPOperASPathGroupName           TASPathGroupName,
    tRPOperASPathGroupEntryIndex     Unsigned32,
    tRPOperASPathGroupRowStatus      RowStatus,
    tRPOperASPathGroupASPathName     TASPathName,
    tRPOperASPathGroupASPathRegEx    TRoutePolicyRegex,
    tRPOperASPathGroupCrOrigin       TmnxCreateOrigin
}

tRPOperASPathGroupName           OBJECT-TYPE
    SYNTAX      TASPathGroupName (SIZE (1..32))
    MAX-ACCESS  not-accessible
    STATUS      current
    DESCRIPTION
        "The value of tRPOperASPathGroupName indicates the name of the AS-Path
         Group."
    ::= { tRPOperASPathGroupEntry 1 }

tRPOperASPathGroupEntryIndex     OBJECT-TYPE
    SYNTAX      Unsigned32 (1..128)
    MAX-ACCESS  not-accessible
    STATUS      current
    DESCRIPTION
        "The value of tRPOperASPathGroupEntryIndex indicates the index of the
         entry in the AS-Path Group."
    ::= { tRPOperASPathGroupEntry 2 }

tRPOperASPathGroupRowStatus      OBJECT-TYPE
    SYNTAX      RowStatus
    MAX-ACCESS  read-only
    STATUS      current
    DESCRIPTION
        "The value of tRPOperASPathGroupRowStatus indicates the RowStatus for
         this entry. To create or destroy entries in this table, use the
         tRPAdminASPathGroupTable."
    ::= { tRPOperASPathGroupEntry 3 }

tRPOperASPathGroupASPathName     OBJECT-TYPE
    SYNTAX      TASPathName (SIZE (1..32))
    MAX-ACCESS  read-only
    STATUS      obsolete
    DESCRIPTION
        "The value of tRPOperASPathGroupASPathName indicates the name of the
         AS-Path from the tRPOperASPathTable.

         This object is made obsolete in release 14.0."
    ::= { tRPOperASPathGroupEntry 4 }

tRPOperASPathGroupASPathRegEx    OBJECT-TYPE
    SYNTAX      TRoutePolicyRegex
    MAX-ACCESS  read-only
    STATUS      current
    DESCRIPTION
        "The value of tRPOperASPathGroupASPathRegEx indicates the regular
         expression for this AS-Path Group entry."
    ::= { tRPOperASPathGroupEntry 5 }

tRPOperASPathGroupCrOrigin       OBJECT-TYPE
    SYNTAX      TmnxCreateOrigin
    MAX-ACCESS  read-only
    STATUS      current
    DESCRIPTION
        "The value of the object tRPOperASPathGroupCrOrigin indicates the
         mechanism used to create this entry."
    ::= { tRPOperASPathGroupEntry 6 }

tRPOperPSFromCommExprTable       OBJECT-TYPE
    SYNTAX      SEQUENCE OF TRPOperPSFromCommExprEntry
    MAX-ACCESS  not-accessible
    STATUS      current
    DESCRIPTION
        "A table of from filter criteria to match on Community ID's for each
         policy statement entry."
    ::= { tRPOperValueObjects 27 }

tRPOperPSFromCommExprEntry       OBJECT-TYPE
    SYNTAX      TRPOperPSFromCommExprEntry
    MAX-ACCESS  not-accessible
    STATUS      current
    DESCRIPTION
        "Information about a particular community name expression to use as
         match criterion for this policy statement entry.

         Entries are created and deleted by creating and deleting entries in
         tRPAdminPSFromCommExprTable."
    INDEX       {
        tRPOperPolicyStatementName,
        tRPOperPSFromCriteriaIndex
    }
    ::= { tRPOperPSFromCommExprTable 1 }

TRPOperPSFromCommExprEntry       ::= SEQUENCE
{
    tRPOperPSFromCommExprRowStatus   RowStatus,
    tRPOperPSFromCommExprString1     TCommunityNameExpression,
    tRPOperPSFromCommExprString2     TCommunityNameExpression,
    tRPOperPSFromCommExprString3     TCommunityNameExpression,
    tRPOperPSFromCommExprString4     TCommunityNameExpression
}

tRPOperPSFromCommExprRowStatus   OBJECT-TYPE
    SYNTAX      RowStatus
    MAX-ACCESS  read-only
    STATUS      current
    DESCRIPTION
        "The value of object tRPOperPSFromCommExprRowStatus indicates the
         RowStatus for this row.

         To create or destroy entries in this table, use the
         tRPAdminPSFromCommExprTable."
    ::= { tRPOperPSFromCommExprEntry 1 }

tRPOperPSFromCommExprString1     OBJECT-TYPE
    SYNTAX      TCommunityNameExpression
    MAX-ACCESS  read-only
    STATUS      current
    DESCRIPTION
        "The value of object tRPOperPSFromCommExprString1 indicates an
         expression that matches Community ID's.

         The objects tRPOperPSFromCommExprString1,
         tRPOperPSFromCommExprString2, tRPOperPSFromCommExprString3 and
         tRPOperPSFromCommExprString4 are substrings that form one string of
         type TCommunityNameExpression."
    ::= { tRPOperPSFromCommExprEntry 2 }

tRPOperPSFromCommExprString2     OBJECT-TYPE
    SYNTAX      TCommunityNameExpression
    MAX-ACCESS  read-only
    STATUS      current
    DESCRIPTION
        "The value of object tRPOperPSFromCommExprString2 indicates an
         expression that matches Community ID's.

         The objects tRPOperPSFromCommExprString1,
         tRPOperPSFromCommExprString2, tRPOperPSFromCommExprString3 and
         tRPOperPSFromCommExprString4 are substrings that form one string of
         type TCommunityNameExpression."
    ::= { tRPOperPSFromCommExprEntry 3 }

tRPOperPSFromCommExprString3     OBJECT-TYPE
    SYNTAX      TCommunityNameExpression
    MAX-ACCESS  read-only
    STATUS      current
    DESCRIPTION
        "The value of object tRPOperPSFromCommExprString3 indicates an
         expression that matches Community ID's.

         The objects tRPOperPSFromCommExprString1,
         tRPOperPSFromCommExprString2, tRPOperPSFromCommExprString3 and
         tRPOperPSFromCommExprString4 are substrings that form one string of
         type TCommunityNameExpression."
    ::= { tRPOperPSFromCommExprEntry 4 }

tRPOperPSFromCommExprString4     OBJECT-TYPE
    SYNTAX      TCommunityNameExpression
    MAX-ACCESS  read-only
    STATUS      current
    DESCRIPTION
        "The value of object tRPOperPSFromCommExprString4 indicates an
         expression that matches Community ID's.

         The objects tRPOperPSFromCommExprString1,
         tRPOperPSFromCommExprString2, tRPOperPSFromCommExprString3 and
         tRPOperPSFromCommExprString4 are substrings that form one string of
         type TCommunityNameExpression."
    ::= { tRPOperPSFromCommExprEntry 5 }

tRPOperPSDefActionAddCommTable   OBJECT-TYPE
    SYNTAX      SEQUENCE OF TRPOperPSDefActionAddCommEntry
    MAX-ACCESS  not-accessible
    STATUS      current
    DESCRIPTION
        "Default community names for a policy statement to add to routes."
    ::= { tRPOperValueObjects 28 }

tRPOperPSDefActionAddCommEntry   OBJECT-TYPE
    SYNTAX      TRPOperPSDefActionAddCommEntry
    MAX-ACCESS  not-accessible
    STATUS      current
    DESCRIPTION
        "Default action information about a particular policy statement.

         These communities are applied when the default action for the policy
         statement (tRPOperPolicyStatementDefaultAction) is 'accept(1)'.

         These communities are ignored when the default action for the policy
         statement (tRPOperPolicyStatementDefaultAction) is 'reject(2)'.

         Entries are created when a policy statement is created. Entries are
         deleted when a policy statement is destroyed."
    INDEX       { tRPOperPolicyStatementName }
    ::= { tRPOperPSDefActionAddCommTable 1 }

TRPOperPSDefActionAddCommEntry   ::= SEQUENCE
{
    tRPOperPSDefActionAddComm1       TLCommunityName,
    tRPOperPSDefActionAddComm2       TLCommunityName,
    tRPOperPSDefActionAddComm3       TLCommunityName,
    tRPOperPSDefActionAddComm4       TLCommunityName,
    tRPOperPSDefActionAddComm5       TLCommunityName,
    tRPOperPSDefActionAddComm6       TLCommunityName,
    tRPOperPSDefActionAddComm7       TLCommunityName,
    tRPOperPSDefActionAddComm8       TLCommunityName,
    tRPOperPSDefActionAddComm9       TLCommunityName,
    tRPOperPSDefActionAddComm10      TLCommunityName,
    tRPOperPSDefActionAddComm11      TLCommunityName,
    tRPOperPSDefActionAddComm12      TLCommunityName,
    tRPOperPSDefActionAddComm13      TLCommunityName,
    tRPOperPSDefActionAddComm14      TLCommunityName,
    tRPOperPSDefActionAddComm15      TLCommunityName,
    tRPOperPSDefActionAddComm16      TLCommunityName,
    tRPOperPSDefActionAddComm17      TLCommunityName,
    tRPOperPSDefActionAddComm18      TLCommunityName,
    tRPOperPSDefActionAddComm19      TLCommunityName,
    tRPOperPSDefActionAddComm20      TLCommunityName,
    tRPOperPSDefActionAddComm21      TLCommunityName,
    tRPOperPSDefActionAddComm22      TLCommunityName,
    tRPOperPSDefActionAddComm23      TLCommunityName,
    tRPOperPSDefActionAddComm24      TLCommunityName,
    tRPOperPSDefActionAddComm25      TLCommunityName,
    tRPOperPSDefActionAddComm26      TLCommunityName,
    tRPOperPSDefActionAddComm27      TLCommunityName,
    tRPOperPSDefActionAddComm28      TLCommunityName
}

tRPOperPSDefActionAddComm1       OBJECT-TYPE
    SYNTAX      TLCommunityName
    MAX-ACCESS  read-only
    STATUS      current
    DESCRIPTION
        "The value of tRPOperPSDefActionAddComm1 indicates a community name to
         add to any existing community for the route."
    ::= { tRPOperPSDefActionAddCommEntry 1 }

tRPOperPSDefActionAddComm2       OBJECT-TYPE
    SYNTAX      TLCommunityName
    MAX-ACCESS  read-only
    STATUS      current
    DESCRIPTION
        "The value of tRPOperPSDefActionAddComm2 indicates a community name to
         add to any existing community for the route."
    ::= { tRPOperPSDefActionAddCommEntry 2 }

tRPOperPSDefActionAddComm3       OBJECT-TYPE
    SYNTAX      TLCommunityName
    MAX-ACCESS  read-only
    STATUS      current
    DESCRIPTION
        "The value of tRPOperPSDefActionAddComm3 indicates a community name to
         add to any existing community for the route."
    ::= { tRPOperPSDefActionAddCommEntry 3 }

tRPOperPSDefActionAddComm4       OBJECT-TYPE
    SYNTAX      TLCommunityName
    MAX-ACCESS  read-only
    STATUS      current
    DESCRIPTION
        "The value of tRPOperPSDefActionAddComm4 indicates a community name to
         add to any existing community for the route."
    ::= { tRPOperPSDefActionAddCommEntry 4 }

tRPOperPSDefActionAddComm5       OBJECT-TYPE
    SYNTAX      TLCommunityName
    MAX-ACCESS  read-only
    STATUS      current
    DESCRIPTION
        "The value of tRPOperPSDefActionAddComm5 indicates a community name to
         add to any existing community for the route."
    ::= { tRPOperPSDefActionAddCommEntry 5 }

tRPOperPSDefActionAddComm6       OBJECT-TYPE
    SYNTAX      TLCommunityName
    MAX-ACCESS  read-only
    STATUS      current
    DESCRIPTION
        "The value of tRPOperPSDefActionAddComm6 indicates a community name to
         add to any existing community for the route."
    ::= { tRPOperPSDefActionAddCommEntry 6 }

tRPOperPSDefActionAddComm7       OBJECT-TYPE
    SYNTAX      TLCommunityName
    MAX-ACCESS  read-only
    STATUS      current
    DESCRIPTION
        "The value of tRPOperPSDefActionAddComm7 indicates a community name to
         add to any existing community for the route."
    ::= { tRPOperPSDefActionAddCommEntry 7 }

tRPOperPSDefActionAddComm8       OBJECT-TYPE
    SYNTAX      TLCommunityName
    MAX-ACCESS  read-only
    STATUS      current
    DESCRIPTION
        "The value of tRPOperPSDefActionAddComm8 indicates a community name to
         add to any existing community for the route."
    ::= { tRPOperPSDefActionAddCommEntry 8 }

tRPOperPSDefActionAddComm9       OBJECT-TYPE
    SYNTAX      TLCommunityName
    MAX-ACCESS  read-only
    STATUS      current
    DESCRIPTION
        "The value of tRPOperPSDefActionAddComm9 indicates a community name to
         add to any existing community for the route."
    ::= { tRPOperPSDefActionAddCommEntry 9 }

tRPOperPSDefActionAddComm10      OBJECT-TYPE
    SYNTAX      TLCommunityName
    MAX-ACCESS  read-only
    STATUS      current
    DESCRIPTION
        "The value of tRPOperPSDefActionAddComm10 indicates a community name to
         add to any existing community for the route."
    ::= { tRPOperPSDefActionAddCommEntry 10 }

tRPOperPSDefActionAddComm11      OBJECT-TYPE
    SYNTAX      TLCommunityName
    MAX-ACCESS  read-only
    STATUS      current
    DESCRIPTION
        "The value of tRPOperPSDefActionAddComm11 indicates a community name to
         add to any existing community for the route."
    ::= { tRPOperPSDefActionAddCommEntry 11 }

tRPOperPSDefActionAddComm12      OBJECT-TYPE
    SYNTAX      TLCommunityName
    MAX-ACCESS  read-only
    STATUS      current
    DESCRIPTION
        "The value of tRPOperPSDefActionAddComm12 indicates a community name to
         add to any existing community for the route."
    ::= { tRPOperPSDefActionAddCommEntry 12 }

tRPOperPSDefActionAddComm13      OBJECT-TYPE
    SYNTAX      TLCommunityName
    MAX-ACCESS  read-only
    STATUS      current
    DESCRIPTION
        "The value of tRPOperPSDefActionAddComm13 indicates a community name to
         add to any existing community for the route."
    ::= { tRPOperPSDefActionAddCommEntry 13 }

tRPOperPSDefActionAddComm14      OBJECT-TYPE
    SYNTAX      TLCommunityName
    MAX-ACCESS  read-only
    STATUS      current
    DESCRIPTION
        "The value of tRPOperPSDefActionAddComm14 indicates a community name to
         add to any existing community for the route."
    ::= { tRPOperPSDefActionAddCommEntry 14 }

tRPOperPSDefActionAddComm15      OBJECT-TYPE
    SYNTAX      TLCommunityName
    MAX-ACCESS  read-only
    STATUS      current
    DESCRIPTION
        "The value of tRPOperPSDefActionAddComm15 indicates a community name to
         add to any existing community for the route."
    ::= { tRPOperPSDefActionAddCommEntry 15 }

tRPOperPSDefActionAddComm16      OBJECT-TYPE
    SYNTAX      TLCommunityName
    MAX-ACCESS  read-only
    STATUS      current
    DESCRIPTION
        "The value of tRPOperPSDefActionAddComm16 indicates a community name to
         add to any existing community for the route."
    ::= { tRPOperPSDefActionAddCommEntry 16 }

tRPOperPSDefActionAddComm17      OBJECT-TYPE
    SYNTAX      TLCommunityName
    MAX-ACCESS  read-only
    STATUS      current
    DESCRIPTION
        "The value of tRPOperPSDefActionAddComm17 indicates a community name to
         add to any existing community for the route."
    ::= { tRPOperPSDefActionAddCommEntry 17 }

tRPOperPSDefActionAddComm18      OBJECT-TYPE
    SYNTAX      TLCommunityName
    MAX-ACCESS  read-only
    STATUS      current
    DESCRIPTION
        "The value of tRPOperPSDefActionAddComm18 indicates a community name to
         add to any existing community for the route."
    ::= { tRPOperPSDefActionAddCommEntry 18 }

tRPOperPSDefActionAddComm19      OBJECT-TYPE
    SYNTAX      TLCommunityName
    MAX-ACCESS  read-only
    STATUS      current
    DESCRIPTION
        "The value of tRPOperPSDefActionAddComm19 indicates a community name to
         add to any existing community for the route."
    ::= { tRPOperPSDefActionAddCommEntry 19 }

tRPOperPSDefActionAddComm20      OBJECT-TYPE
    SYNTAX      TLCommunityName
    MAX-ACCESS  read-only
    STATUS      current
    DESCRIPTION
        "The value of tRPOperPSDefActionAddComm20 indicates a community name to
         add to any existing community for the route."
    ::= { tRPOperPSDefActionAddCommEntry 20 }

tRPOperPSDefActionAddComm21      OBJECT-TYPE
    SYNTAX      TLCommunityName
    MAX-ACCESS  read-only
    STATUS      current
    DESCRIPTION
        "The value of tRPOperPSDefActionAddComm21 indicates a community name to
         add to any existing community for the route."
    ::= { tRPOperPSDefActionAddCommEntry 21 }

tRPOperPSDefActionAddComm22      OBJECT-TYPE
    SYNTAX      TLCommunityName
    MAX-ACCESS  read-only
    STATUS      current
    DESCRIPTION
        "The value of tRPOperPSDefActionAddComm22 indicates a community name to
         add to any existing community for the route."
    ::= { tRPOperPSDefActionAddCommEntry 22 }

tRPOperPSDefActionAddComm23      OBJECT-TYPE
    SYNTAX      TLCommunityName
    MAX-ACCESS  read-only
    STATUS      current
    DESCRIPTION
        "The value of tRPOperPSDefActionAddComm23 indicates a community name to
         add to any existing community for the route."
    ::= { tRPOperPSDefActionAddCommEntry 23 }

tRPOperPSDefActionAddComm24      OBJECT-TYPE
    SYNTAX      TLCommunityName
    MAX-ACCESS  read-only
    STATUS      current
    DESCRIPTION
        "The value of tRPOperPSDefActionAddComm24 indicates a community name to
         add to any existing community for the route."
    ::= { tRPOperPSDefActionAddCommEntry 24 }

tRPOperPSDefActionAddComm25      OBJECT-TYPE
    SYNTAX      TLCommunityName
    MAX-ACCESS  read-only
    STATUS      current
    DESCRIPTION
        "The value of tRPOperPSDefActionAddComm25 indicates a community name to
         add to any existing community for the route."
    ::= { tRPOperPSDefActionAddCommEntry 25 }

tRPOperPSDefActionAddComm26      OBJECT-TYPE
    SYNTAX      TLCommunityName
    MAX-ACCESS  read-only
    STATUS      current
    DESCRIPTION
        "The value of tRPOperPSDefActionAddComm26 indicates a community name to
         add to any existing community for the route."
    ::= { tRPOperPSDefActionAddCommEntry 26 }

tRPOperPSDefActionAddComm27      OBJECT-TYPE
    SYNTAX      TLCommunityName
    MAX-ACCESS  read-only
    STATUS      current
    DESCRIPTION
        "The value of tRPOperPSDefActionAddComm27 indicates a community name to
         add to any existing community for the route."
    ::= { tRPOperPSDefActionAddCommEntry 27 }

tRPOperPSDefActionAddComm28      OBJECT-TYPE
    SYNTAX      TLCommunityName
    MAX-ACCESS  read-only
    STATUS      current
    DESCRIPTION
        "The value of tRPOperPSDefActionAddComm28 indicates a community name to
         add to any existing community for the route."
    ::= { tRPOperPSDefActionAddCommEntry 28 }

tRPOperPSDefActionRemCommTable   OBJECT-TYPE
    SYNTAX      SEQUENCE OF TRPOperPSDefActionRemCommEntry
    MAX-ACCESS  not-accessible
    STATUS      current
    DESCRIPTION
        "Default community names for a policy statement to remove from routes."
    ::= { tRPOperValueObjects 29 }

tRPOperPSDefActionRemCommEntry   OBJECT-TYPE
    SYNTAX      TRPOperPSDefActionRemCommEntry
    MAX-ACCESS  not-accessible
    STATUS      current
    DESCRIPTION
        "Default action information about a particular policy statement.

         These communities are applied when the default action for the policy
         statement (tRPOperPolicyStatementDefaultAction) is 'accept(1)'.

         Entries are created or deleted when an entry in
         tRPOperPSDefaultActionParamsTable is created or deleted."
    AUGMENTS    { tRPOperPSDefaultActionParamsEntry }
    ::= { tRPOperPSDefActionRemCommTable 1 }

TRPOperPSDefActionRemCommEntry   ::= SEQUENCE
{
    tRPOperPSDefActionRemoveComm1    TLCommunityName,
    tRPOperPSDefActionRemoveComm2    TLCommunityName,
    tRPOperPSDefActionRemoveComm3    TLCommunityName,
    tRPOperPSDefActionRemoveComm4    TLCommunityName,
    tRPOperPSDefActionRemoveComm5    TLCommunityName,
    tRPOperPSDefActionRemoveComm6    TLCommunityName,
    tRPOperPSDefActionRemoveComm7    TLCommunityName,
    tRPOperPSDefActionRemoveComm8    TLCommunityName,
    tRPOperPSDefActionRemoveComm9    TLCommunityName,
    tRPOperPSDefActionRemoveComm10   TLCommunityName,
    tRPOperPSDefActionRemoveComm11   TLCommunityName,
    tRPOperPSDefActionRemoveComm12   TLCommunityName,
    tRPOperPSDefActionRemoveComm13   TLCommunityName,
    tRPOperPSDefActionRemoveComm14   TLCommunityName,
    tRPOperPSDefActionRemoveComm15   TLCommunityName,
    tRPOperPSDefActionRemoveComm16   TLCommunityName,
    tRPOperPSDefActionRemoveComm17   TLCommunityName,
    tRPOperPSDefActionRemoveComm18   TLCommunityName,
    tRPOperPSDefActionRemoveComm19   TLCommunityName,
    tRPOperPSDefActionRemoveComm20   TLCommunityName,
    tRPOperPSDefActionRemoveComm21   TLCommunityName,
    tRPOperPSDefActionRemoveComm22   TLCommunityName,
    tRPOperPSDefActionRemoveComm23   TLCommunityName,
    tRPOperPSDefActionRemoveComm24   TLCommunityName,
    tRPOperPSDefActionRemoveComm25   TLCommunityName,
    tRPOperPSDefActionRemoveComm26   TLCommunityName,
    tRPOperPSDefActionRemoveComm27   TLCommunityName,
    tRPOperPSDefActionRemoveComm28   TLCommunityName
}

tRPOperPSDefActionRemoveComm1    OBJECT-TYPE
    SYNTAX      TLCommunityName
    MAX-ACCESS  read-only
    STATUS      current
    DESCRIPTION
        "The value of tRPOperPSDefActionRemoveComm1 indicates a community name
         to remove from any existing community for the route."
    ::= { tRPOperPSDefActionRemCommEntry 1 }

tRPOperPSDefActionRemoveComm2    OBJECT-TYPE
    SYNTAX      TLCommunityName
    MAX-ACCESS  read-only
    STATUS      current
    DESCRIPTION
        "The value of tRPOperPSDefActionRemoveComm2 indicates a community name
         to remove from any existing community for the route."
    ::= { tRPOperPSDefActionRemCommEntry 2 }

tRPOperPSDefActionRemoveComm3    OBJECT-TYPE
    SYNTAX      TLCommunityName
    MAX-ACCESS  read-only
    STATUS      current
    DESCRIPTION
        "The value of tRPOperPSDefActionRemoveComm3 indicates a community name
         to remove from any existing community for the route."
    ::= { tRPOperPSDefActionRemCommEntry 3 }

tRPOperPSDefActionRemoveComm4    OBJECT-TYPE
    SYNTAX      TLCommunityName
    MAX-ACCESS  read-only
    STATUS      current
    DESCRIPTION
        "The value of tRPOperPSDefActionRemoveComm4 indicates a community name
         to remove from any existing community for the route."
    ::= { tRPOperPSDefActionRemCommEntry 4 }

tRPOperPSDefActionRemoveComm5    OBJECT-TYPE
    SYNTAX      TLCommunityName
    MAX-ACCESS  read-only
    STATUS      current
    DESCRIPTION
        "The value of tRPOperPSDefActionRemoveComm5 indicates a community name
         to remove from any existing community for the route."
    ::= { tRPOperPSDefActionRemCommEntry 5 }

tRPOperPSDefActionRemoveComm6    OBJECT-TYPE
    SYNTAX      TLCommunityName
    MAX-ACCESS  read-only
    STATUS      current
    DESCRIPTION
        "The value of tRPOperPSDefActionRemoveComm6 indicates a community name
         to remove from any existing community for the route."
    ::= { tRPOperPSDefActionRemCommEntry 6 }

tRPOperPSDefActionRemoveComm7    OBJECT-TYPE
    SYNTAX      TLCommunityName
    MAX-ACCESS  read-only
    STATUS      current
    DESCRIPTION
        "The value of tRPOperPSDefActionRemoveComm7 indicates a community name
         to remove from any existing community for the route."
    ::= { tRPOperPSDefActionRemCommEntry 7 }

tRPOperPSDefActionRemoveComm8    OBJECT-TYPE
    SYNTAX      TLCommunityName
    MAX-ACCESS  read-only
    STATUS      current
    DESCRIPTION
        "The value of tRPOperPSDefActionRemoveComm8 indicates a community name
         to remove from any existing community for the route."
    ::= { tRPOperPSDefActionRemCommEntry 8 }

tRPOperPSDefActionRemoveComm9    OBJECT-TYPE
    SYNTAX      TLCommunityName
    MAX-ACCESS  read-only
    STATUS      current
    DESCRIPTION
        "The value of tRPOperPSDefActionRemoveComm9 indicates a community name
         to remove from any existing community for the route."
    ::= { tRPOperPSDefActionRemCommEntry 9 }

tRPOperPSDefActionRemoveComm10   OBJECT-TYPE
    SYNTAX      TLCommunityName
    MAX-ACCESS  read-only
    STATUS      current
    DESCRIPTION
        "The value of tRPOperPSDefActionRemoveComm10 indicates a community name
         to remove from any existing community for the route."
    ::= { tRPOperPSDefActionRemCommEntry 10 }

tRPOperPSDefActionRemoveComm11   OBJECT-TYPE
    SYNTAX      TLCommunityName
    MAX-ACCESS  read-only
    STATUS      current
    DESCRIPTION
        "The value of tRPOperPSDefActionRemoveComm11 indicates a community name
         to remove from any existing community for the route."
    ::= { tRPOperPSDefActionRemCommEntry 11 }

tRPOperPSDefActionRemoveComm12   OBJECT-TYPE
    SYNTAX      TLCommunityName
    MAX-ACCESS  read-only
    STATUS      current
    DESCRIPTION
        "The value of tRPOperPSDefActionRemoveComm12 indicates a community name
         to remove from any existing community for the route."
    ::= { tRPOperPSDefActionRemCommEntry 12 }

tRPOperPSDefActionRemoveComm13   OBJECT-TYPE
    SYNTAX      TLCommunityName
    MAX-ACCESS  read-only
    STATUS      current
    DESCRIPTION
        "The value of tRPOperPSDefActionRemoveComm13 indicates a community name
         to remove from any existing community for the route."
    ::= { tRPOperPSDefActionRemCommEntry 13 }

tRPOperPSDefActionRemoveComm14   OBJECT-TYPE
    SYNTAX      TLCommunityName
    MAX-ACCESS  read-only
    STATUS      current
    DESCRIPTION
        "The value of tRPOperPSDefActionRemoveComm14 indicates a community name
         to remove from any existing community for the route."
    ::= { tRPOperPSDefActionRemCommEntry 14 }

tRPOperPSDefActionRemoveComm15   OBJECT-TYPE
    SYNTAX      TLCommunityName
    MAX-ACCESS  read-only
    STATUS      current
    DESCRIPTION
        "The value of tRPOperPSDefActionRemoveComm15 indicates a community name
         to remove from any existing community for the route."
    ::= { tRPOperPSDefActionRemCommEntry 15 }

tRPOperPSDefActionRemoveComm16   OBJECT-TYPE
    SYNTAX      TLCommunityName
    MAX-ACCESS  read-only
    STATUS      current
    DESCRIPTION
        "The value of tRPOperPSDefActionRemoveComm16 indicates a community name
         to remove from any existing community for the route."
    ::= { tRPOperPSDefActionRemCommEntry 16 }

tRPOperPSDefActionRemoveComm17   OBJECT-TYPE
    SYNTAX      TLCommunityName
    MAX-ACCESS  read-only
    STATUS      current
    DESCRIPTION
        "The value of tRPOperPSDefActionRemoveComm17 indicates a community name
         to remove from any existing community for the route."
    ::= { tRPOperPSDefActionRemCommEntry 17 }

tRPOperPSDefActionRemoveComm18   OBJECT-TYPE
    SYNTAX      TLCommunityName
    MAX-ACCESS  read-only
    STATUS      current
    DESCRIPTION
        "The value of tRPOperPSDefActionRemoveComm18 indicates a community name
         to remove from any existing community for the route."
    ::= { tRPOperPSDefActionRemCommEntry 18 }

tRPOperPSDefActionRemoveComm19   OBJECT-TYPE
    SYNTAX      TLCommunityName
    MAX-ACCESS  read-only
    STATUS      current
    DESCRIPTION
        "The value of tRPOperPSDefActionRemoveComm19 indicates a community name
         to remove from any existing community for the route."
    ::= { tRPOperPSDefActionRemCommEntry 19 }

tRPOperPSDefActionRemoveComm20   OBJECT-TYPE
    SYNTAX      TLCommunityName
    MAX-ACCESS  read-only
    STATUS      current
    DESCRIPTION
        "The value of tRPOperPSDefActionRemoveComm20 indicates a community name
         to remove from any existing community for the route."
    ::= { tRPOperPSDefActionRemCommEntry 20 }

tRPOperPSDefActionRemoveComm21   OBJECT-TYPE
    SYNTAX      TLCommunityName
    MAX-ACCESS  read-only
    STATUS      current
    DESCRIPTION
        "The value of tRPOperPSDefActionRemoveComm21 indicates a community name
         to remove from any existing community for the route."
    ::= { tRPOperPSDefActionRemCommEntry 21 }

tRPOperPSDefActionRemoveComm22   OBJECT-TYPE
    SYNTAX      TLCommunityName
    MAX-ACCESS  read-only
    STATUS      current
    DESCRIPTION
        "The value of tRPOperPSDefActionRemoveComm22 indicates a community name
         to remove from any existing community for the route."
    ::= { tRPOperPSDefActionRemCommEntry 22 }

tRPOperPSDefActionRemoveComm23   OBJECT-TYPE
    SYNTAX      TLCommunityName
    MAX-ACCESS  read-only
    STATUS      current
    DESCRIPTION
        "The value of tRPOperPSDefActionRemoveComm23 indicates a community name
         to remove from any existing community for the route."
    ::= { tRPOperPSDefActionRemCommEntry 23 }

tRPOperPSDefActionRemoveComm24   OBJECT-TYPE
    SYNTAX      TLCommunityName
    MAX-ACCESS  read-only
    STATUS      current
    DESCRIPTION
        "The value of tRPOperPSDefActionRemoveComm24 indicates a community name
         to remove from any existing community for the route."
    ::= { tRPOperPSDefActionRemCommEntry 24 }

tRPOperPSDefActionRemoveComm25   OBJECT-TYPE
    SYNTAX      TLCommunityName
    MAX-ACCESS  read-only
    STATUS      current
    DESCRIPTION
        "The value of tRPOperPSDefActionRemoveComm25 indicates a community name
         to remove from any existing community for the route."
    ::= { tRPOperPSDefActionRemCommEntry 25 }

tRPOperPSDefActionRemoveComm26   OBJECT-TYPE
    SYNTAX      TLCommunityName
    MAX-ACCESS  read-only
    STATUS      current
    DESCRIPTION
        "The value of tRPOperPSDefActionRemoveComm26 indicates a community name
         to remove from any existing community for the route."
    ::= { tRPOperPSDefActionRemCommEntry 26 }

tRPOperPSDefActionRemoveComm27   OBJECT-TYPE
    SYNTAX      TLCommunityName
    MAX-ACCESS  read-only
    STATUS      current
    DESCRIPTION
        "The value of tRPOperPSDefActionRemoveComm27 indicates a community name
         to remove from any existing community for the route."
    ::= { tRPOperPSDefActionRemCommEntry 27 }

tRPOperPSDefActionRemoveComm28   OBJECT-TYPE
    SYNTAX      TLCommunityName
    MAX-ACCESS  read-only
    STATUS      current
    DESCRIPTION
        "The value of tRPOperPSDefActionRemoveComm28 indicates a community name
         to remove from any existing community for the route."
    ::= { tRPOperPSDefActionRemCommEntry 28 }

tRPOperPSDefActionRepCommTable   OBJECT-TYPE
    SYNTAX      SEQUENCE OF TRPOperPSDefActionRepCommEntry
    MAX-ACCESS  not-accessible
    STATUS      current
    DESCRIPTION
        "Default community names for a policy statement to replace in routes."
    ::= { tRPOperValueObjects 30 }

tRPOperPSDefActionRepCommEntry   OBJECT-TYPE
    SYNTAX      TRPOperPSDefActionRepCommEntry
    MAX-ACCESS  not-accessible
    STATUS      current
    DESCRIPTION
        "Default action information about a particular policy statement.

         These communities are applied when the default action for the policy
         statement (tRPOperPolicyStatementDefaultAction) is 'accept(1)'.

         Entries are created or deleted when an entry in
         tRPOperPSDefaultActionParamsTable is created or deleted."
    AUGMENTS    { tRPOperPSDefaultActionParamsEntry }
    ::= { tRPOperPSDefActionRepCommTable 1 }

TRPOperPSDefActionRepCommEntry   ::= SEQUENCE
{
    tRPOperPSDefActionReplaceComm1   TLCommunityName,
    tRPOperPSDefActionReplaceComm2   TLCommunityName,
    tRPOperPSDefActionReplaceComm3   TLCommunityName,
    tRPOperPSDefActionReplaceComm4   TLCommunityName,
    tRPOperPSDefActionReplaceComm5   TLCommunityName,
    tRPOperPSDefActionReplaceComm6   TLCommunityName,
    tRPOperPSDefActionReplaceComm7   TLCommunityName,
    tRPOperPSDefActionReplaceComm8   TLCommunityName,
    tRPOperPSDefActionReplaceComm9   TLCommunityName,
    tRPOperPSDefActionReplaceComm10  TLCommunityName,
    tRPOperPSDefActionReplaceComm11  TLCommunityName,
    tRPOperPSDefActionReplaceComm12  TLCommunityName,
    tRPOperPSDefActionReplaceComm13  TLCommunityName,
    tRPOperPSDefActionReplaceComm14  TLCommunityName,
    tRPOperPSDefActionReplaceComm15  TLCommunityName,
    tRPOperPSDefActionReplaceComm16  TLCommunityName,
    tRPOperPSDefActionReplaceComm17  TLCommunityName,
    tRPOperPSDefActionReplaceComm18  TLCommunityName,
    tRPOperPSDefActionReplaceComm19  TLCommunityName,
    tRPOperPSDefActionReplaceComm20  TLCommunityName,
    tRPOperPSDefActionReplaceComm21  TLCommunityName,
    tRPOperPSDefActionReplaceComm22  TLCommunityName,
    tRPOperPSDefActionReplaceComm23  TLCommunityName,
    tRPOperPSDefActionReplaceComm24  TLCommunityName,
    tRPOperPSDefActionReplaceComm25  TLCommunityName,
    tRPOperPSDefActionReplaceComm26  TLCommunityName,
    tRPOperPSDefActionReplaceComm27  TLCommunityName,
    tRPOperPSDefActionReplaceComm28  TLCommunityName
}

tRPOperPSDefActionReplaceComm1   OBJECT-TYPE
    SYNTAX      TLCommunityName
    MAX-ACCESS  read-only
    STATUS      current
    DESCRIPTION
        "The value of tRPOperPSDefActionReplaceComm1 indicates a community name
         to replace in any existing community for the route."
    ::= { tRPOperPSDefActionRepCommEntry 1 }

tRPOperPSDefActionReplaceComm2   OBJECT-TYPE
    SYNTAX      TLCommunityName
    MAX-ACCESS  read-only
    STATUS      current
    DESCRIPTION
        "The value of tRPOperPSDefActionReplaceComm2 indicates a community name
         to replace in any existing community for the route."
    ::= { tRPOperPSDefActionRepCommEntry 2 }

tRPOperPSDefActionReplaceComm3   OBJECT-TYPE
    SYNTAX      TLCommunityName
    MAX-ACCESS  read-only
    STATUS      current
    DESCRIPTION
        "The value of tRPOperPSDefActionReplaceComm3 indicates a community name
         to replace in any existing community for the route."
    ::= { tRPOperPSDefActionRepCommEntry 3 }

tRPOperPSDefActionReplaceComm4   OBJECT-TYPE
    SYNTAX      TLCommunityName
    MAX-ACCESS  read-only
    STATUS      current
    DESCRIPTION
        "The value of tRPOperPSDefActionReplaceComm4 indicates a community name
         to replace in any existing community for the route."
    ::= { tRPOperPSDefActionRepCommEntry 4 }

tRPOperPSDefActionReplaceComm5   OBJECT-TYPE
    SYNTAX      TLCommunityName
    MAX-ACCESS  read-only
    STATUS      current
    DESCRIPTION
        "The value of tRPOperPSDefActionReplaceComm5 indicates a community name
         to replace in any existing community for the route."
    ::= { tRPOperPSDefActionRepCommEntry 5 }

tRPOperPSDefActionReplaceComm6   OBJECT-TYPE
    SYNTAX      TLCommunityName
    MAX-ACCESS  read-only
    STATUS      current
    DESCRIPTION
        "The value of tRPOperPSDefActionReplaceComm6 indicates a community name
         to replace in any existing community for the route."
    ::= { tRPOperPSDefActionRepCommEntry 6 }

tRPOperPSDefActionReplaceComm7   OBJECT-TYPE
    SYNTAX      TLCommunityName
    MAX-ACCESS  read-only
    STATUS      current
    DESCRIPTION
        "The value of tRPOperPSDefActionReplaceComm7 indicates a community name
         to replace in any existing community for the route."
    ::= { tRPOperPSDefActionRepCommEntry 7 }

tRPOperPSDefActionReplaceComm8   OBJECT-TYPE
    SYNTAX      TLCommunityName
    MAX-ACCESS  read-only
    STATUS      current
    DESCRIPTION
        "The value of tRPOperPSDefActionReplaceComm8 indicates a community name
         to replace in any existing community for the route."
    ::= { tRPOperPSDefActionRepCommEntry 8 }

tRPOperPSDefActionReplaceComm9   OBJECT-TYPE
    SYNTAX      TLCommunityName
    MAX-ACCESS  read-only
    STATUS      current
    DESCRIPTION
        "The value of tRPOperPSDefActionReplaceComm9 indicates a community name
         to replace in any existing community for the route."
    ::= { tRPOperPSDefActionRepCommEntry 9 }

tRPOperPSDefActionReplaceComm10  OBJECT-TYPE
    SYNTAX      TLCommunityName
    MAX-ACCESS  read-only
    STATUS      current
    DESCRIPTION
        "The value of tRPOperPSDefActionReplaceComm10 indicates a community
         name to replace in any existing community for the route."
    ::= { tRPOperPSDefActionRepCommEntry 10 }

tRPOperPSDefActionReplaceComm11  OBJECT-TYPE
    SYNTAX      TLCommunityName
    MAX-ACCESS  read-only
    STATUS      current
    DESCRIPTION
        "The value of tRPOperPSDefActionReplaceComm11 indicates a community
         name to replace in any existing community for the route."
    ::= { tRPOperPSDefActionRepCommEntry 11 }

tRPOperPSDefActionReplaceComm12  OBJECT-TYPE
    SYNTAX      TLCommunityName
    MAX-ACCESS  read-only
    STATUS      current
    DESCRIPTION
        "The value of tRPOperPSDefActionReplaceComm12 indicates a community
         name to replace in any existing community for the route."
    ::= { tRPOperPSDefActionRepCommEntry 12 }

tRPOperPSDefActionReplaceComm13  OBJECT-TYPE
    SYNTAX      TLCommunityName
    MAX-ACCESS  read-only
    STATUS      current
    DESCRIPTION
        "The value of tRPOperPSDefActionReplaceComm13 indicates a community
         name to replace in any existing community for the route."
    ::= { tRPOperPSDefActionRepCommEntry 13 }

tRPOperPSDefActionReplaceComm14  OBJECT-TYPE
    SYNTAX      TLCommunityName
    MAX-ACCESS  read-only
    STATUS      current
    DESCRIPTION
        "The value of tRPOperPSDefActionReplaceComm14 indicates a community
         name to replace in any existing community for the route."
    ::= { tRPOperPSDefActionRepCommEntry 14 }

tRPOperPSDefActionReplaceComm15  OBJECT-TYPE
    SYNTAX      TLCommunityName
    MAX-ACCESS  read-only
    STATUS      current
    DESCRIPTION
        "The value of tRPOperPSDefActionReplaceComm15 indicates a community
         name to replace in any existing community for the route."
    ::= { tRPOperPSDefActionRepCommEntry 15 }

tRPOperPSDefActionReplaceComm16  OBJECT-TYPE
    SYNTAX      TLCommunityName
    MAX-ACCESS  read-only
    STATUS      current
    DESCRIPTION
        "The value of tRPOperPSDefActionReplaceComm16 indicates a community
         name to replace in any existing community for the route."
    ::= { tRPOperPSDefActionRepCommEntry 16 }

tRPOperPSDefActionReplaceComm17  OBJECT-TYPE
    SYNTAX      TLCommunityName
    MAX-ACCESS  read-only
    STATUS      current
    DESCRIPTION
        "The value of tRPOperPSDefActionReplaceComm17 indicates a community
         name to replace in any existing community for the route."
    ::= { tRPOperPSDefActionRepCommEntry 17 }

tRPOperPSDefActionReplaceComm18  OBJECT-TYPE
    SYNTAX      TLCommunityName
    MAX-ACCESS  read-only
    STATUS      current
    DESCRIPTION
        "The value of tRPOperPSDefActionReplaceComm18 indicates a community
         name to replace in any existing community for the route."
    ::= { tRPOperPSDefActionRepCommEntry 18 }

tRPOperPSDefActionReplaceComm19  OBJECT-TYPE
    SYNTAX      TLCommunityName
    MAX-ACCESS  read-only
    STATUS      current
    DESCRIPTION
        "The value of tRPOperPSDefActionReplaceComm19 indicates a community
         name to replace in any existing community for the route."
    ::= { tRPOperPSDefActionRepCommEntry 19 }

tRPOperPSDefActionReplaceComm20  OBJECT-TYPE
    SYNTAX      TLCommunityName
    MAX-ACCESS  read-only
    STATUS      current
    DESCRIPTION
        "The value of tRPOperPSDefActionReplaceComm20 indicates a community
         name to replace in any existing community for the route."
    ::= { tRPOperPSDefActionRepCommEntry 20 }

tRPOperPSDefActionReplaceComm21  OBJECT-TYPE
    SYNTAX      TLCommunityName
    MAX-ACCESS  read-only
    STATUS      current
    DESCRIPTION
        "The value of tRPOperPSDefActionReplaceComm21 indicates a community
         name to replace in any existing community for the route."
    ::= { tRPOperPSDefActionRepCommEntry 21 }

tRPOperPSDefActionReplaceComm22  OBJECT-TYPE
    SYNTAX      TLCommunityName
    MAX-ACCESS  read-only
    STATUS      current
    DESCRIPTION
        "The value of tRPOperPSDefActionReplaceComm22 indicates a community
         name to replace in any existing community for the route."
    ::= { tRPOperPSDefActionRepCommEntry 22 }

tRPOperPSDefActionReplaceComm23  OBJECT-TYPE
    SYNTAX      TLCommunityName
    MAX-ACCESS  read-only
    STATUS      current
    DESCRIPTION
        "The value of tRPOperPSDefActionReplaceComm23 indicates a community
         name to replace in any existing community for the route."
    ::= { tRPOperPSDefActionRepCommEntry 23 }

tRPOperPSDefActionReplaceComm24  OBJECT-TYPE
    SYNTAX      TLCommunityName
    MAX-ACCESS  read-only
    STATUS      current
    DESCRIPTION
        "The value of tRPOperPSDefActionReplaceComm24 indicates a community
         name to replace in any existing community for the route."
    ::= { tRPOperPSDefActionRepCommEntry 24 }

tRPOperPSDefActionReplaceComm25  OBJECT-TYPE
    SYNTAX      TLCommunityName
    MAX-ACCESS  read-only
    STATUS      current
    DESCRIPTION
        "The value of tRPOperPSDefActionReplaceComm25 indicates a community
         name to replace in any existing community for the route."
    ::= { tRPOperPSDefActionRepCommEntry 25 }

tRPOperPSDefActionReplaceComm26  OBJECT-TYPE
    SYNTAX      TLCommunityName
    MAX-ACCESS  read-only
    STATUS      current
    DESCRIPTION
        "The value of tRPOperPSDefActionReplaceComm26 indicates a community
         name to replace in any existing community for the route."
    ::= { tRPOperPSDefActionRepCommEntry 26 }

tRPOperPSDefActionReplaceComm27  OBJECT-TYPE
    SYNTAX      TLCommunityName
    MAX-ACCESS  read-only
    STATUS      current
    DESCRIPTION
        "The value of tRPOperPSDefActionReplaceComm27 indicates a community
         name to replace in any existing community for the route."
    ::= { tRPOperPSDefActionRepCommEntry 27 }

tRPOperPSDefActionReplaceComm28  OBJECT-TYPE
    SYNTAX      TLCommunityName
    MAX-ACCESS  read-only
    STATUS      current
    DESCRIPTION
        "The value of tRPOperPSDefActionReplaceComm28 indicates a community
         name to replace in any existing community for the route."
    ::= { tRPOperPSDefActionRepCommEntry 28 }

tRPOperPSAccActionAddCommTable   OBJECT-TYPE
    SYNTAX      SEQUENCE OF TRPOperPSAccActionAddCommEntry
    MAX-ACCESS  not-accessible
    STATUS      current
    DESCRIPTION
        "Community names for a policy statement entry to add to routes."
    ::= { tRPOperValueObjects 31 }

tRPOperPSAccActionAddCommEntry   OBJECT-TYPE
    SYNTAX      TRPOperPSAccActionAddCommEntry
    MAX-ACCESS  not-accessible
    STATUS      current
    DESCRIPTION
        "Accept-action information about a particular policy statement entry.

         These communities are applied when the action for the policy statement
         entry (tRPOperPSParamsAction) is 'accept(1)'.

         Entries are created or deleted when an entry in
         tRPOperPSAcceptActionParamsTable is created or deleted."
    AUGMENTS    { tRPOperPSAcceptActionParamsEntry }
    ::= { tRPOperPSAccActionAddCommTable 1 }

TRPOperPSAccActionAddCommEntry   ::= SEQUENCE
{
    tRPOperPSAccActionAddComm1       TLCommunityName,
    tRPOperPSAccActionAddComm2       TLCommunityName,
    tRPOperPSAccActionAddComm3       TLCommunityName,
    tRPOperPSAccActionAddComm4       TLCommunityName,
    tRPOperPSAccActionAddComm5       TLCommunityName,
    tRPOperPSAccActionAddComm6       TLCommunityName,
    tRPOperPSAccActionAddComm7       TLCommunityName,
    tRPOperPSAccActionAddComm8       TLCommunityName,
    tRPOperPSAccActionAddComm9       TLCommunityName,
    tRPOperPSAccActionAddComm10      TLCommunityName,
    tRPOperPSAccActionAddComm11      TLCommunityName,
    tRPOperPSAccActionAddComm12      TLCommunityName,
    tRPOperPSAccActionAddComm13      TLCommunityName,
    tRPOperPSAccActionAddComm14      TLCommunityName,
    tRPOperPSAccActionAddComm15      TLCommunityName,
    tRPOperPSAccActionAddComm16      TLCommunityName,
    tRPOperPSAccActionAddComm17      TLCommunityName,
    tRPOperPSAccActionAddComm18      TLCommunityName,
    tRPOperPSAccActionAddComm19      TLCommunityName,
    tRPOperPSAccActionAddComm20      TLCommunityName,
    tRPOperPSAccActionAddComm21      TLCommunityName,
    tRPOperPSAccActionAddComm22      TLCommunityName,
    tRPOperPSAccActionAddComm23      TLCommunityName,
    tRPOperPSAccActionAddComm24      TLCommunityName,
    tRPOperPSAccActionAddComm25      TLCommunityName,
    tRPOperPSAccActionAddComm26      TLCommunityName,
    tRPOperPSAccActionAddComm27      TLCommunityName,
    tRPOperPSAccActionAddComm28      TLCommunityName,
    tRPOperPSAccActionAddCommCrOrig  TmnxCreateOrigin
}

tRPOperPSAccActionAddComm1       OBJECT-TYPE
    SYNTAX      TLCommunityName
    MAX-ACCESS  read-only
    STATUS      current
    DESCRIPTION
        "The value of tRPOperPSAccActionAddComm1 indicates a community name to
         add to any existing community for the route."
    ::= { tRPOperPSAccActionAddCommEntry 1 }

tRPOperPSAccActionAddComm2       OBJECT-TYPE
    SYNTAX      TLCommunityName
    MAX-ACCESS  read-only
    STATUS      current
    DESCRIPTION
        "The value of tRPOperPSAccActionAddComm2 indicates a community name to
         add to any existing community for the route."
    ::= { tRPOperPSAccActionAddCommEntry 2 }

tRPOperPSAccActionAddComm3       OBJECT-TYPE
    SYNTAX      TLCommunityName
    MAX-ACCESS  read-only
    STATUS      current
    DESCRIPTION
        "The value of tRPOperPSAccActionAddComm3 indicates a community name to
         add to any existing community for the route."
    ::= { tRPOperPSAccActionAddCommEntry 3 }

tRPOperPSAccActionAddComm4       OBJECT-TYPE
    SYNTAX      TLCommunityName
    MAX-ACCESS  read-only
    STATUS      current
    DESCRIPTION
        "The value of tRPOperPSAccActionAddComm4 indicates a community name to
         add to any existing community for the route."
    ::= { tRPOperPSAccActionAddCommEntry 4 }

tRPOperPSAccActionAddComm5       OBJECT-TYPE
    SYNTAX      TLCommunityName
    MAX-ACCESS  read-only
    STATUS      current
    DESCRIPTION
        "The value of tRPOperPSAccActionAddComm5 indicates a community name to
         add to any existing community for the route."
    ::= { tRPOperPSAccActionAddCommEntry 5 }

tRPOperPSAccActionAddComm6       OBJECT-TYPE
    SYNTAX      TLCommunityName
    MAX-ACCESS  read-only
    STATUS      current
    DESCRIPTION
        "The value of tRPOperPSAccActionAddComm6 indicates a community name to
         add to any existing community for the route."
    ::= { tRPOperPSAccActionAddCommEntry 6 }

tRPOperPSAccActionAddComm7       OBJECT-TYPE
    SYNTAX      TLCommunityName
    MAX-ACCESS  read-only
    STATUS      current
    DESCRIPTION
        "The value of tRPOperPSAccActionAddComm7 indicates a community name to
         add to any existing community for the route."
    ::= { tRPOperPSAccActionAddCommEntry 7 }

tRPOperPSAccActionAddComm8       OBJECT-TYPE
    SYNTAX      TLCommunityName
    MAX-ACCESS  read-only
    STATUS      current
    DESCRIPTION
        "The value of tRPOperPSAccActionAddComm8 indicates a community name to
         add to any existing community for the route."
    ::= { tRPOperPSAccActionAddCommEntry 8 }

tRPOperPSAccActionAddComm9       OBJECT-TYPE
    SYNTAX      TLCommunityName
    MAX-ACCESS  read-only
    STATUS      current
    DESCRIPTION
        "The value of tRPOperPSAccActionAddComm9 indicates a community name to
         add to any existing community for the route."
    ::= { tRPOperPSAccActionAddCommEntry 9 }

tRPOperPSAccActionAddComm10      OBJECT-TYPE
    SYNTAX      TLCommunityName
    MAX-ACCESS  read-only
    STATUS      current
    DESCRIPTION
        "The value of tRPOperPSAccActionAddComm10 indicates a community name to
         add to any existing community for the route."
    ::= { tRPOperPSAccActionAddCommEntry 10 }

tRPOperPSAccActionAddComm11      OBJECT-TYPE
    SYNTAX      TLCommunityName
    MAX-ACCESS  read-only
    STATUS      current
    DESCRIPTION
        "The value of tRPOperPSAccActionAddComm11 indicates a community name to
         add to any existing community for the route."
    ::= { tRPOperPSAccActionAddCommEntry 11 }

tRPOperPSAccActionAddComm12      OBJECT-TYPE
    SYNTAX      TLCommunityName
    MAX-ACCESS  read-only
    STATUS      current
    DESCRIPTION
        "The value of tRPOperPSAccActionAddComm12 indicates a community name to
         add to any existing community for the route."
    ::= { tRPOperPSAccActionAddCommEntry 12 }

tRPOperPSAccActionAddComm13      OBJECT-TYPE
    SYNTAX      TLCommunityName
    MAX-ACCESS  read-only
    STATUS      current
    DESCRIPTION
        "The value of tRPOperPSAccActionAddComm13 indicates a community name to
         add to any existing community for the route."
    ::= { tRPOperPSAccActionAddCommEntry 13 }

tRPOperPSAccActionAddComm14      OBJECT-TYPE
    SYNTAX      TLCommunityName
    MAX-ACCESS  read-only
    STATUS      current
    DESCRIPTION
        "The value of tRPOperPSAccActionAddComm14 indicates a community name to
         add to any existing community for the route."
    ::= { tRPOperPSAccActionAddCommEntry 14 }

tRPOperPSAccActionAddComm15      OBJECT-TYPE
    SYNTAX      TLCommunityName
    MAX-ACCESS  read-only
    STATUS      current
    DESCRIPTION
        "The value of tRPOperPSAccActionAddComm15 indicates a community name to
         add to any existing community for the route."
    ::= { tRPOperPSAccActionAddCommEntry 15 }

tRPOperPSAccActionAddComm16      OBJECT-TYPE
    SYNTAX      TLCommunityName
    MAX-ACCESS  read-only
    STATUS      current
    DESCRIPTION
        "The value of tRPOperPSAccActionAddComm16 indicates a community name to
         add to any existing community for the route."
    ::= { tRPOperPSAccActionAddCommEntry 16 }

tRPOperPSAccActionAddComm17      OBJECT-TYPE
    SYNTAX      TLCommunityName
    MAX-ACCESS  read-only
    STATUS      current
    DESCRIPTION
        "The value of tRPOperPSAccActionAddComm17 indicates a community name to
         add to any existing community for the route."
    ::= { tRPOperPSAccActionAddCommEntry 17 }

tRPOperPSAccActionAddComm18      OBJECT-TYPE
    SYNTAX      TLCommunityName
    MAX-ACCESS  read-only
    STATUS      current
    DESCRIPTION
        "The value of tRPOperPSAccActionAddComm18 indicates a community name to
         add to any existing community for the route."
    ::= { tRPOperPSAccActionAddCommEntry 18 }

tRPOperPSAccActionAddComm19      OBJECT-TYPE
    SYNTAX      TLCommunityName
    MAX-ACCESS  read-only
    STATUS      current
    DESCRIPTION
        "The value of tRPOperPSAccActionAddComm19 indicates a community name to
         add to any existing community for the route."
    ::= { tRPOperPSAccActionAddCommEntry 19 }

tRPOperPSAccActionAddComm20      OBJECT-TYPE
    SYNTAX      TLCommunityName
    MAX-ACCESS  read-only
    STATUS      current
    DESCRIPTION
        "The value of tRPOperPSAccActionAddComm20 indicates a community name to
         add to any existing community for the route."
    ::= { tRPOperPSAccActionAddCommEntry 20 }

tRPOperPSAccActionAddComm21      OBJECT-TYPE
    SYNTAX      TLCommunityName
    MAX-ACCESS  read-only
    STATUS      current
    DESCRIPTION
        "The value of tRPOperPSAccActionAddComm21 indicates a community name to
         add to any existing community for the route."
    ::= { tRPOperPSAccActionAddCommEntry 21 }

tRPOperPSAccActionAddComm22      OBJECT-TYPE
    SYNTAX      TLCommunityName
    MAX-ACCESS  read-only
    STATUS      current
    DESCRIPTION
        "The value of tRPOperPSAccActionAddComm22 indicates a community name to
         add to any existing community for the route."
    ::= { tRPOperPSAccActionAddCommEntry 22 }

tRPOperPSAccActionAddComm23      OBJECT-TYPE
    SYNTAX      TLCommunityName
    MAX-ACCESS  read-only
    STATUS      current
    DESCRIPTION
        "The value of tRPOperPSAccActionAddComm23 indicates a community name to
         add to any existing community for the route."
    ::= { tRPOperPSAccActionAddCommEntry 23 }

tRPOperPSAccActionAddComm24      OBJECT-TYPE
    SYNTAX      TLCommunityName
    MAX-ACCESS  read-only
    STATUS      current
    DESCRIPTION
        "The value of tRPOperPSAccActionAddComm24 indicates a community name to
         add to any existing community for the route."
    ::= { tRPOperPSAccActionAddCommEntry 24 }

tRPOperPSAccActionAddComm25      OBJECT-TYPE
    SYNTAX      TLCommunityName
    MAX-ACCESS  read-only
    STATUS      current
    DESCRIPTION
        "The value of tRPOperPSAccActionAddComm25 indicates a community name to
         add to any existing community for the route."
    ::= { tRPOperPSAccActionAddCommEntry 25 }

tRPOperPSAccActionAddComm26      OBJECT-TYPE
    SYNTAX      TLCommunityName
    MAX-ACCESS  read-only
    STATUS      current
    DESCRIPTION
        "The value of tRPOperPSAccActionAddComm26 indicates a community name to
         add to any existing community for the route."
    ::= { tRPOperPSAccActionAddCommEntry 26 }

tRPOperPSAccActionAddComm27      OBJECT-TYPE
    SYNTAX      TLCommunityName
    MAX-ACCESS  read-only
    STATUS      current
    DESCRIPTION
        "The value of tRPOperPSAccActionAddComm27 indicates a community name to
         add to any existing community for the route."
    ::= { tRPOperPSAccActionAddCommEntry 27 }

tRPOperPSAccActionAddComm28      OBJECT-TYPE
    SYNTAX      TLCommunityName
    MAX-ACCESS  read-only
    STATUS      current
    DESCRIPTION
        "The value of tRPOperPSAccActionAddComm28 indicates a community name to
         add to any existing community for the route."
    ::= { tRPOperPSAccActionAddCommEntry 28 }

tRPOperPSAccActionAddCommCrOrig  OBJECT-TYPE
    SYNTAX      TmnxCreateOrigin
    MAX-ACCESS  read-only
    STATUS      current
    DESCRIPTION
        "The value of the object tRPOperPSAccActionAddCommCrOrig indicates the
         mechanism used to create this entry."
    ::= { tRPOperPSAccActionAddCommEntry 29 }

tRPOperPSAccActionRemCommTable   OBJECT-TYPE
    SYNTAX      SEQUENCE OF TRPOperPSAccActionRemCommEntry
    MAX-ACCESS  not-accessible
    STATUS      current
    DESCRIPTION
        "Community names for a policy statement entry to remove from routes."
    ::= { tRPOperValueObjects 32 }

tRPOperPSAccActionRemCommEntry   OBJECT-TYPE
    SYNTAX      TRPOperPSAccActionRemCommEntry
    MAX-ACCESS  not-accessible
    STATUS      current
    DESCRIPTION
        "Accept-action information about a particular policy statement entry.

         These communities are applied when the action for the policy statement
         entry (tRPOperPSParamsAction) is 'accept(1)'.

         Entries are created or deleted when an entry in
         tRPOperPSAcceptActionParamsTable is created or deleted."
    AUGMENTS    { tRPOperPSAcceptActionParamsEntry }
    ::= { tRPOperPSAccActionRemCommTable 1 }

TRPOperPSAccActionRemCommEntry   ::= SEQUENCE
{
    tRPOperPSAccActionRemoveComm1    TLCommunityName,
    tRPOperPSAccActionRemoveComm2    TLCommunityName,
    tRPOperPSAccActionRemoveComm3    TLCommunityName,
    tRPOperPSAccActionRemoveComm4    TLCommunityName,
    tRPOperPSAccActionRemoveComm5    TLCommunityName,
    tRPOperPSAccActionRemoveComm6    TLCommunityName,
    tRPOperPSAccActionRemoveComm7    TLCommunityName,
    tRPOperPSAccActionRemoveComm8    TLCommunityName,
    tRPOperPSAccActionRemoveComm9    TLCommunityName,
    tRPOperPSAccActionRemoveComm10   TLCommunityName,
    tRPOperPSAccActionRemoveComm11   TLCommunityName,
    tRPOperPSAccActionRemoveComm12   TLCommunityName,
    tRPOperPSAccActionRemoveComm13   TLCommunityName,
    tRPOperPSAccActionRemoveComm14   TLCommunityName,
    tRPOperPSAccActionRemoveComm15   TLCommunityName,
    tRPOperPSAccActionRemoveComm16   TLCommunityName,
    tRPOperPSAccActionRemoveComm17   TLCommunityName,
    tRPOperPSAccActionRemoveComm18   TLCommunityName,
    tRPOperPSAccActionRemoveComm19   TLCommunityName,
    tRPOperPSAccActionRemoveComm20   TLCommunityName,
    tRPOperPSAccActionRemoveComm21   TLCommunityName,
    tRPOperPSAccActionRemoveComm22   TLCommunityName,
    tRPOperPSAccActionRemoveComm23   TLCommunityName,
    tRPOperPSAccActionRemoveComm24   TLCommunityName,
    tRPOperPSAccActionRemoveComm25   TLCommunityName,
    tRPOperPSAccActionRemoveComm26   TLCommunityName,
    tRPOperPSAccActionRemoveComm27   TLCommunityName,
    tRPOperPSAccActionRemoveComm28   TLCommunityName
}

tRPOperPSAccActionRemoveComm1    OBJECT-TYPE
    SYNTAX      TLCommunityName
    MAX-ACCESS  read-only
    STATUS      current
    DESCRIPTION
        "The value of tRPOperPSAccActionRemoveComm1 indicates a community name
         to remove from any existing community for the route."
    ::= { tRPOperPSAccActionRemCommEntry 1 }

tRPOperPSAccActionRemoveComm2    OBJECT-TYPE
    SYNTAX      TLCommunityName
    MAX-ACCESS  read-only
    STATUS      current
    DESCRIPTION
        "The value of tRPOperPSAccActionRemoveComm2 indicates a community name
         to remove from any existing community for the route."
    ::= { tRPOperPSAccActionRemCommEntry 2 }

tRPOperPSAccActionRemoveComm3    OBJECT-TYPE
    SYNTAX      TLCommunityName
    MAX-ACCESS  read-only
    STATUS      current
    DESCRIPTION
        "The value of tRPOperPSAccActionRemoveComm3 indicates a community name
         to remove from any existing community for the route."
    ::= { tRPOperPSAccActionRemCommEntry 3 }

tRPOperPSAccActionRemoveComm4    OBJECT-TYPE
    SYNTAX      TLCommunityName
    MAX-ACCESS  read-only
    STATUS      current
    DESCRIPTION
        "The value of tRPOperPSAccActionRemoveComm4 indicates a community name
         to remove from any existing community for the route."
    ::= { tRPOperPSAccActionRemCommEntry 4 }

tRPOperPSAccActionRemoveComm5    OBJECT-TYPE
    SYNTAX      TLCommunityName
    MAX-ACCESS  read-only
    STATUS      current
    DESCRIPTION
        "The value of tRPOperPSAccActionRemoveComm5 indicates a community name
         to remove from any existing community for the route."
    ::= { tRPOperPSAccActionRemCommEntry 5 }

tRPOperPSAccActionRemoveComm6    OBJECT-TYPE
    SYNTAX      TLCommunityName
    MAX-ACCESS  read-only
    STATUS      current
    DESCRIPTION
        "The value of tRPOperPSAccActionRemoveComm6 indicates a community name
         to remove from any existing community for the route."
    ::= { tRPOperPSAccActionRemCommEntry 6 }

tRPOperPSAccActionRemoveComm7    OBJECT-TYPE
    SYNTAX      TLCommunityName
    MAX-ACCESS  read-only
    STATUS      current
    DESCRIPTION
        "The value of tRPOperPSAccActionRemoveComm7 indicates a community name
         to remove from any existing community for the route."
    ::= { tRPOperPSAccActionRemCommEntry 7 }

tRPOperPSAccActionRemoveComm8    OBJECT-TYPE
    SYNTAX      TLCommunityName
    MAX-ACCESS  read-only
    STATUS      current
    DESCRIPTION
        "The value of tRPOperPSAccActionRemoveComm8 indicates a community name
         to remove from any existing community for the route."
    ::= { tRPOperPSAccActionRemCommEntry 8 }

tRPOperPSAccActionRemoveComm9    OBJECT-TYPE
    SYNTAX      TLCommunityName
    MAX-ACCESS  read-only
    STATUS      current
    DESCRIPTION
        "The value of tRPOperPSAccActionRemoveComm9 indicates a community name
         to remove from any existing community for the route."
    ::= { tRPOperPSAccActionRemCommEntry 9 }

tRPOperPSAccActionRemoveComm10   OBJECT-TYPE
    SYNTAX      TLCommunityName
    MAX-ACCESS  read-only
    STATUS      current
    DESCRIPTION
        "The value of tRPOperPSAccActionRemoveComm10 indicates a community name
         to remove from any existing community for the route."
    ::= { tRPOperPSAccActionRemCommEntry 10 }

tRPOperPSAccActionRemoveComm11   OBJECT-TYPE
    SYNTAX      TLCommunityName
    MAX-ACCESS  read-only
    STATUS      current
    DESCRIPTION
        "The value of tRPOperPSAccActionRemoveComm11 indicates a community name
         to remove from any existing community for the route."
    ::= { tRPOperPSAccActionRemCommEntry 11 }

tRPOperPSAccActionRemoveComm12   OBJECT-TYPE
    SYNTAX      TLCommunityName
    MAX-ACCESS  read-only
    STATUS      current
    DESCRIPTION
        "The value of tRPOperPSAccActionRemoveComm12 indicates a community name
         to remove from any existing community for the route."
    ::= { tRPOperPSAccActionRemCommEntry 12 }

tRPOperPSAccActionRemoveComm13   OBJECT-TYPE
    SYNTAX      TLCommunityName
    MAX-ACCESS  read-only
    STATUS      current
    DESCRIPTION
        "The value of tRPOperPSAccActionRemoveComm13 indicates a community name
         to remove from any existing community for the route."
    ::= { tRPOperPSAccActionRemCommEntry 13 }

tRPOperPSAccActionRemoveComm14   OBJECT-TYPE
    SYNTAX      TLCommunityName
    MAX-ACCESS  read-only
    STATUS      current
    DESCRIPTION
        "The value of tRPOperPSAccActionRemoveComm14 indicates a community name
         to remove from any existing community for the route."
    ::= { tRPOperPSAccActionRemCommEntry 14 }

tRPOperPSAccActionRemoveComm15   OBJECT-TYPE
    SYNTAX      TLCommunityName
    MAX-ACCESS  read-only
    STATUS      current
    DESCRIPTION
        "The value of tRPOperPSAccActionRemoveComm15 indicates a community name
         to remove from any existing community for the route."
    ::= { tRPOperPSAccActionRemCommEntry 15 }

tRPOperPSAccActionRemoveComm16   OBJECT-TYPE
    SYNTAX      TLCommunityName
    MAX-ACCESS  read-only
    STATUS      current
    DESCRIPTION
        "The value of tRPOperPSAccActionRemoveComm16 indicates a community name
         to remove from any existing community for the route."
    ::= { tRPOperPSAccActionRemCommEntry 16 }

tRPOperPSAccActionRemoveComm17   OBJECT-TYPE
    SYNTAX      TLCommunityName
    MAX-ACCESS  read-only
    STATUS      current
    DESCRIPTION
        "The value of tRPOperPSAccActionRemoveComm17 indicates a community name
         to remove from any existing community for the route."
    ::= { tRPOperPSAccActionRemCommEntry 17 }

tRPOperPSAccActionRemoveComm18   OBJECT-TYPE
    SYNTAX      TLCommunityName
    MAX-ACCESS  read-only
    STATUS      current
    DESCRIPTION
        "The value of tRPOperPSAccActionRemoveComm18 indicates a community name
         to remove from any existing community for the route."
    ::= { tRPOperPSAccActionRemCommEntry 18 }

tRPOperPSAccActionRemoveComm19   OBJECT-TYPE
    SYNTAX      TLCommunityName
    MAX-ACCESS  read-only
    STATUS      current
    DESCRIPTION
        "The value of tRPOperPSAccActionRemoveComm19 indicates a community name
         to remove from any existing community for the route."
    ::= { tRPOperPSAccActionRemCommEntry 19 }

tRPOperPSAccActionRemoveComm20   OBJECT-TYPE
    SYNTAX      TLCommunityName
    MAX-ACCESS  read-only
    STATUS      current
    DESCRIPTION
        "The value of tRPOperPSAccActionRemoveComm20 indicates a community name
         to remove from any existing community for the route."
    ::= { tRPOperPSAccActionRemCommEntry 20 }

tRPOperPSAccActionRemoveComm21   OBJECT-TYPE
    SYNTAX      TLCommunityName
    MAX-ACCESS  read-only
    STATUS      current
    DESCRIPTION
        "The value of tRPOperPSAccActionRemoveComm21 indicates a community name
         to remove from any existing community for the route."
    ::= { tRPOperPSAccActionRemCommEntry 21 }

tRPOperPSAccActionRemoveComm22   OBJECT-TYPE
    SYNTAX      TLCommunityName
    MAX-ACCESS  read-only
    STATUS      current
    DESCRIPTION
        "The value of tRPOperPSAccActionRemoveComm22 indicates a community name
         to remove from any existing community for the route."
    ::= { tRPOperPSAccActionRemCommEntry 22 }

tRPOperPSAccActionRemoveComm23   OBJECT-TYPE
    SYNTAX      TLCommunityName
    MAX-ACCESS  read-only
    STATUS      current
    DESCRIPTION
        "The value of tRPOperPSAccActionRemoveComm23 indicates a community name
         to remove from any existing community for the route."
    ::= { tRPOperPSAccActionRemCommEntry 23 }

tRPOperPSAccActionRemoveComm24   OBJECT-TYPE
    SYNTAX      TLCommunityName
    MAX-ACCESS  read-only
    STATUS      current
    DESCRIPTION
        "The value of tRPOperPSAccActionRemoveComm24 indicates a community name
         to remove from any existing community for the route."
    ::= { tRPOperPSAccActionRemCommEntry 24 }

tRPOperPSAccActionRemoveComm25   OBJECT-TYPE
    SYNTAX      TLCommunityName
    MAX-ACCESS  read-only
    STATUS      current
    DESCRIPTION
        "The value of tRPOperPSAccActionRemoveComm25 indicates a community name
         to remove from any existing community for the route."
    ::= { tRPOperPSAccActionRemCommEntry 25 }

tRPOperPSAccActionRemoveComm26   OBJECT-TYPE
    SYNTAX      TLCommunityName
    MAX-ACCESS  read-only
    STATUS      current
    DESCRIPTION
        "The value of tRPOperPSAccActionRemoveComm26 indicates a community name
         to remove from any existing community for the route."
    ::= { tRPOperPSAccActionRemCommEntry 26 }

tRPOperPSAccActionRemoveComm27   OBJECT-TYPE
    SYNTAX      TLCommunityName
    MAX-ACCESS  read-only
    STATUS      current
    DESCRIPTION
        "The value of tRPOperPSAccActionRemoveComm27 indicates a community name
         to remove from any existing community for the route."
    ::= { tRPOperPSAccActionRemCommEntry 27 }

tRPOperPSAccActionRemoveComm28   OBJECT-TYPE
    SYNTAX      TLCommunityName
    MAX-ACCESS  read-only
    STATUS      current
    DESCRIPTION
        "The value of tRPOperPSAccActionRemoveComm28 indicates a community name
         to remove from any existing community for the route."
    ::= { tRPOperPSAccActionRemCommEntry 28 }

tRPOperPSAccActionRepCommTable   OBJECT-TYPE
    SYNTAX      SEQUENCE OF TRPOperPSAccActionRepCommEntry
    MAX-ACCESS  not-accessible
    STATUS      current
    DESCRIPTION
        "Community names for a policy statement entry to replace in routes."
    ::= { tRPOperValueObjects 33 }

tRPOperPSAccActionRepCommEntry   OBJECT-TYPE
    SYNTAX      TRPOperPSAccActionRepCommEntry
    MAX-ACCESS  not-accessible
    STATUS      current
    DESCRIPTION
        "Accept-action information about a particular policy statement entry.

         These communities are applied when the action for the policy statement
         entry (tRPOperPSParamsAction) is 'accept(1)'.

         Entries are created or deleted when an entry in
         tRPOperPSAcceptActionParamsTable is created or deleted."
    AUGMENTS    { tRPOperPSAcceptActionParamsEntry }
    ::= { tRPOperPSAccActionRepCommTable 1 }

TRPOperPSAccActionRepCommEntry   ::= SEQUENCE
{
    tRPOperPSAccActionReplaceComm1   TLCommunityName,
    tRPOperPSAccActionReplaceComm2   TLCommunityName,
    tRPOperPSAccActionReplaceComm3   TLCommunityName,
    tRPOperPSAccActionReplaceComm4   TLCommunityName,
    tRPOperPSAccActionReplaceComm5   TLCommunityName,
    tRPOperPSAccActionReplaceComm6   TLCommunityName,
    tRPOperPSAccActionReplaceComm7   TLCommunityName,
    tRPOperPSAccActionReplaceComm8   TLCommunityName,
    tRPOperPSAccActionReplaceComm9   TLCommunityName,
    tRPOperPSAccActionReplaceComm10  TLCommunityName,
    tRPOperPSAccActionReplaceComm11  TLCommunityName,
    tRPOperPSAccActionReplaceComm12  TLCommunityName,
    tRPOperPSAccActionReplaceComm13  TLCommunityName,
    tRPOperPSAccActionReplaceComm14  TLCommunityName,
    tRPOperPSAccActionReplaceComm15  TLCommunityName,
    tRPOperPSAccActionReplaceComm16  TLCommunityName,
    tRPOperPSAccActionReplaceComm17  TLCommunityName,
    tRPOperPSAccActionReplaceComm18  TLCommunityName,
    tRPOperPSAccActionReplaceComm19  TLCommunityName,
    tRPOperPSAccActionReplaceComm20  TLCommunityName,
    tRPOperPSAccActionReplaceComm21  TLCommunityName,
    tRPOperPSAccActionReplaceComm22  TLCommunityName,
    tRPOperPSAccActionReplaceComm23  TLCommunityName,
    tRPOperPSAccActionReplaceComm24  TLCommunityName,
    tRPOperPSAccActionReplaceComm25  TLCommunityName,
    tRPOperPSAccActionReplaceComm26  TLCommunityName,
    tRPOperPSAccActionReplaceComm27  TLCommunityName,
    tRPOperPSAccActionReplaceComm28  TLCommunityName
}

tRPOperPSAccActionReplaceComm1   OBJECT-TYPE
    SYNTAX      TLCommunityName
    MAX-ACCESS  read-only
    STATUS      current
    DESCRIPTION
        "The value of tRPOperPSAccActionReplaceComm1 indicates a community name
         to replace in any existing community for the route."
    ::= { tRPOperPSAccActionRepCommEntry 1 }

tRPOperPSAccActionReplaceComm2   OBJECT-TYPE
    SYNTAX      TLCommunityName
    MAX-ACCESS  read-only
    STATUS      current
    DESCRIPTION
        "The value of tRPOperPSAccActionReplaceComm2 indicates a community name
         to replace in any existing community for the route."
    ::= { tRPOperPSAccActionRepCommEntry 2 }

tRPOperPSAccActionReplaceComm3   OBJECT-TYPE
    SYNTAX      TLCommunityName
    MAX-ACCESS  read-only
    STATUS      current
    DESCRIPTION
        "The value of tRPOperPSAccActionReplaceComm3 indicates a community name
         to replace in any existing community for the route."
    ::= { tRPOperPSAccActionRepCommEntry 3 }

tRPOperPSAccActionReplaceComm4   OBJECT-TYPE
    SYNTAX      TLCommunityName
    MAX-ACCESS  read-only
    STATUS      current
    DESCRIPTION
        "The value of tRPOperPSAccActionReplaceComm4 indicates a community name
         to replace in any existing community for the route."
    ::= { tRPOperPSAccActionRepCommEntry 4 }

tRPOperPSAccActionReplaceComm5   OBJECT-TYPE
    SYNTAX      TLCommunityName
    MAX-ACCESS  read-only
    STATUS      current
    DESCRIPTION
        "The value of tRPOperPSAccActionReplaceComm5 indicates a community name
         to replace in any existing community for the route."
    ::= { tRPOperPSAccActionRepCommEntry 5 }

tRPOperPSAccActionReplaceComm6   OBJECT-TYPE
    SYNTAX      TLCommunityName
    MAX-ACCESS  read-only
    STATUS      current
    DESCRIPTION
        "The value of tRPOperPSAccActionReplaceComm6 indicates a community name
         to replace in any existing community for the route."
    ::= { tRPOperPSAccActionRepCommEntry 6 }

tRPOperPSAccActionReplaceComm7   OBJECT-TYPE
    SYNTAX      TLCommunityName
    MAX-ACCESS  read-only
    STATUS      current
    DESCRIPTION
        "The value of tRPOperPSAccActionReplaceComm7 indicates a community name
         to replace in any existing community for the route."
    ::= { tRPOperPSAccActionRepCommEntry 7 }

tRPOperPSAccActionReplaceComm8   OBJECT-TYPE
    SYNTAX      TLCommunityName
    MAX-ACCESS  read-only
    STATUS      current
    DESCRIPTION
        "The value of tRPOperPSAccActionReplaceComm8 indicates a community name
         to replace in any existing community for the route."
    ::= { tRPOperPSAccActionRepCommEntry 8 }

tRPOperPSAccActionReplaceComm9   OBJECT-TYPE
    SYNTAX      TLCommunityName
    MAX-ACCESS  read-only
    STATUS      current
    DESCRIPTION
        "The value of tRPOperPSAccActionReplaceComm9 indicates a community name
         to replace in any existing community for the route."
    ::= { tRPOperPSAccActionRepCommEntry 9 }

tRPOperPSAccActionReplaceComm10  OBJECT-TYPE
    SYNTAX      TLCommunityName
    MAX-ACCESS  read-only
    STATUS      current
    DESCRIPTION
        "The value of tRPOperPSAccActionReplaceComm10 indicates a community
         name to replace in any existing community for the route."
    ::= { tRPOperPSAccActionRepCommEntry 10 }

tRPOperPSAccActionReplaceComm11  OBJECT-TYPE
    SYNTAX      TLCommunityName
    MAX-ACCESS  read-only
    STATUS      current
    DESCRIPTION
        "The value of tRPOperPSAccActionReplaceComm11 indicates a community
         name to replace in any existing community for the route."
    ::= { tRPOperPSAccActionRepCommEntry 11 }

tRPOperPSAccActionReplaceComm12  OBJECT-TYPE
    SYNTAX      TLCommunityName
    MAX-ACCESS  read-only
    STATUS      current
    DESCRIPTION
        "The value of tRPOperPSAccActionReplaceComm12 indicates a community
         name to replace in any existing community for the route."
    ::= { tRPOperPSAccActionRepCommEntry 12 }

tRPOperPSAccActionReplaceComm13  OBJECT-TYPE
    SYNTAX      TLCommunityName
    MAX-ACCESS  read-only
    STATUS      current
    DESCRIPTION
        "The value of tRPOperPSAccActionReplaceComm13 indicates a community
         name to replace in any existing community for the route."
    ::= { tRPOperPSAccActionRepCommEntry 13 }

tRPOperPSAccActionReplaceComm14  OBJECT-TYPE
    SYNTAX      TLCommunityName
    MAX-ACCESS  read-only
    STATUS      current
    DESCRIPTION
        "The value of tRPOperPSAccActionReplaceComm14 indicates a community
         name to replace in any existing community for the route."
    ::= { tRPOperPSAccActionRepCommEntry 14 }

tRPOperPSAccActionReplaceComm15  OBJECT-TYPE
    SYNTAX      TLCommunityName
    MAX-ACCESS  read-only
    STATUS      current
    DESCRIPTION
        "The value of tRPOperPSAccActionReplaceComm15 indicates a community
         name to replace in any existing community for the route."
    ::= { tRPOperPSAccActionRepCommEntry 15 }

tRPOperPSAccActionReplaceComm16  OBJECT-TYPE
    SYNTAX      TLCommunityName
    MAX-ACCESS  read-only
    STATUS      current
    DESCRIPTION
        "The value of tRPOperPSAccActionReplaceComm16 indicates a community
         name to replace in any existing community for the route."
    ::= { tRPOperPSAccActionRepCommEntry 16 }

tRPOperPSAccActionReplaceComm17  OBJECT-TYPE
    SYNTAX      TLCommunityName
    MAX-ACCESS  read-only
    STATUS      current
    DESCRIPTION
        "The value of tRPOperPSAccActionReplaceComm17 indicates a community
         name to replace in any existing community for the route."
    ::= { tRPOperPSAccActionRepCommEntry 17 }

tRPOperPSAccActionReplaceComm18  OBJECT-TYPE
    SYNTAX      TLCommunityName
    MAX-ACCESS  read-only
    STATUS      current
    DESCRIPTION
        "The value of tRPOperPSAccActionReplaceComm18 indicates a community
         name to replace in any existing community for the route."
    ::= { tRPOperPSAccActionRepCommEntry 18 }

tRPOperPSAccActionReplaceComm19  OBJECT-TYPE
    SYNTAX      TLCommunityName
    MAX-ACCESS  read-only
    STATUS      current
    DESCRIPTION
        "The value of tRPOperPSAccActionReplaceComm19 indicates a community
         name to replace in any existing community for the route."
    ::= { tRPOperPSAccActionRepCommEntry 19 }

tRPOperPSAccActionReplaceComm20  OBJECT-TYPE
    SYNTAX      TLCommunityName
    MAX-ACCESS  read-only
    STATUS      current
    DESCRIPTION
        "The value of tRPOperPSAccActionReplaceComm20 indicates a community
         name to replace in any existing community for the route."
    ::= { tRPOperPSAccActionRepCommEntry 20 }

tRPOperPSAccActionReplaceComm21  OBJECT-TYPE
    SYNTAX      TLCommunityName
    MAX-ACCESS  read-only
    STATUS      current
    DESCRIPTION
        "The value of tRPOperPSAccActionReplaceComm21 indicates a community
         name to replace in any existing community for the route."
    ::= { tRPOperPSAccActionRepCommEntry 21 }

tRPOperPSAccActionReplaceComm22  OBJECT-TYPE
    SYNTAX      TLCommunityName
    MAX-ACCESS  read-only
    STATUS      current
    DESCRIPTION
        "The value of tRPOperPSAccActionReplaceComm22 indicates a community
         name to replace in any existing community for the route."
    ::= { tRPOperPSAccActionRepCommEntry 22 }

tRPOperPSAccActionReplaceComm23  OBJECT-TYPE
    SYNTAX      TLCommunityName
    MAX-ACCESS  read-only
    STATUS      current
    DESCRIPTION
        "The value of tRPOperPSAccActionReplaceComm23 indicates a community
         name to replace in any existing community for the route."
    ::= { tRPOperPSAccActionRepCommEntry 23 }

tRPOperPSAccActionReplaceComm24  OBJECT-TYPE
    SYNTAX      TLCommunityName
    MAX-ACCESS  read-only
    STATUS      current
    DESCRIPTION
        "The value of tRPOperPSAccActionReplaceComm24 indicates a community
         name to replace in any existing community for the route."
    ::= { tRPOperPSAccActionRepCommEntry 24 }

tRPOperPSAccActionReplaceComm25  OBJECT-TYPE
    SYNTAX      TLCommunityName
    MAX-ACCESS  read-only
    STATUS      current
    DESCRIPTION
        "The value of tRPOperPSAccActionReplaceComm25 indicates a community
         name to replace in any existing community for the route."
    ::= { tRPOperPSAccActionRepCommEntry 25 }

tRPOperPSAccActionReplaceComm26  OBJECT-TYPE
    SYNTAX      TLCommunityName
    MAX-ACCESS  read-only
    STATUS      current
    DESCRIPTION
        "The value of tRPOperPSAccActionReplaceComm26 indicates a community
         name to replace in any existing community for the route."
    ::= { tRPOperPSAccActionRepCommEntry 26 }

tRPOperPSAccActionReplaceComm27  OBJECT-TYPE
    SYNTAX      TLCommunityName
    MAX-ACCESS  read-only
    STATUS      current
    DESCRIPTION
        "The value of tRPOperPSAccActionReplaceComm27 indicates a community
         name to replace in any existing community for the route."
    ::= { tRPOperPSAccActionRepCommEntry 27 }

tRPOperPSAccActionReplaceComm28  OBJECT-TYPE
    SYNTAX      TLCommunityName
    MAX-ACCESS  read-only
    STATUS      current
    DESCRIPTION
        "The value of tRPOperPSAccActionReplaceComm28 indicates a community
         name to replace in any existing community for the route."
    ::= { tRPOperPSAccActionRepCommEntry 28 }

tRPOperPSFromCriteriaExtTable    OBJECT-TYPE
    SYNTAX      SEQUENCE OF TRPOperPSFromCriteriaExtEntry
    MAX-ACCESS  not-accessible
    STATUS      current
    DESCRIPTION
        "An extension table of tRPOperPSFromCriteriaTable containing extra from
         filter criteria for each policy statement entry."
    ::= { tRPOperValueObjects 34 }

tRPOperPSFromCriteriaExtEntry    OBJECT-TYPE
    SYNTAX      TRPOperPSFromCriteriaExtEntry
    MAX-ACCESS  not-accessible
    STATUS      current
    DESCRIPTION
        "Information about policy statement entry from criteria."
    AUGMENTS    { tRPOperPSFromCriteriaEntry }
    ::= { tRPOperPSFromCriteriaExtTable 1 }

TRPOperPSFromCriteriaExtEntry    ::= SEQUENCE
{
    tRPOperPSFromCritExtMvpnType     TPolicyEntryCriteriaMvpnType,
    tRPOperPSFromCritSrcAddrPfxList  TLPrefixListName,
    tRPOperPSFromCritOrigValidState  INTEGER,
    tRPOperPSFromCritFlowSrcPfxList  TLPrefixListName,
    tRPOperPSFromCritFlowDstPfxList  TLPrefixListName,
    tRPOperPSFromCritPathType        TPolicyCritPathType,
    tRPOperPSFromCritASPathLength    TPolicyValueOrVarNameOrEmpty,
    tRPOperPSFromCritASPathLenInd    TPolicyMatchIndicator,
    tRPOperPSFromCritASPLenUnique    TruthValue,
    tRPOperPSFromCritCommunityCount  TPolicyValueOrVarNameOrEmpty,
    tRPOperPSFromCritCommCountInd    TPolicyMatchIndicator,
    tRPOperPSFromCritCommCountType   TPolicyCritCommunityType,
    tRPOperPSFromCritMetric          TPolicyValueOrVarNameOrEmpty,
    tRPOperPSFromCritMetricInd       TPolicyMatchIndicator,
    tRPOperPSFromCritLocalPref       TPolicyValueOrVarNameOrEmpty,
    tRPOperPSFromCritLocalPrefInd    TPolicyMatchIndicator,
    tRPOperPSFromCritClusterAddrTp1  InetAddressType,
    tRPOperPSFromCritClusterAddr1    InetAddress,
    tRPOperPSFromCritClusterPfxLen1  InetAddressPrefixLength,
    tRPOperPSFromCritClusterAddrTp2  InetAddressType,
    tRPOperPSFromCritClusterAddr2    InetAddress,
    tRPOperPSFromCritClusterPfxLen2  InetAddressPrefixLength,
    tRPOperPSFromCritClusterAddrTp3  InetAddressType,
    tRPOperPSFromCritClusterAddr3    InetAddress,
    tRPOperPSFromCritClusterPfxLen3  InetAddressPrefixLength,
    tRPOperPSFromCritClusterAddrTp4  InetAddressType,
    tRPOperPSFromCritClusterAddr4    InetAddress,
    tRPOperPSFromCritClusterPfxLen4  InetAddressPrefixLength,
    tRPOperPSFromCritClusterAddrTp5  InetAddressType,
    tRPOperPSFromCritClusterAddr5    InetAddress,
    tRPOperPSFromCritClusterPfxLen5  InetAddressPrefixLength,
    tRPOperPSFromCritClusterIdNone   TruthValue,
    tRPOperPSFromCritNextHopAddrTyp  InetAddressType,
    tRPOperPSFromCritNextHopAddr     InetAddress,
    tRPOperPSFromCritNextHopPfxList  TLPrefixListName,
    tRPOperPSFromCritExtEvpnType     TPolicyEntryCriteriaEvpnType,
    tRPOperPSFromCrAggrContributor   TruthValue,
    tRPOperPSFromCrEndpointAddrTyp   InetAddressType,
    tRPOperPSFromCrEndpointAddr      InetAddress,
    tRPOperPSFromCritColor           TNamedItemOrEmpty,
    tRPOperPSFromCritDistinguisher   TNamedItemOrEmpty,
    tRPOperPSFromCritRDList          TRouteDistinguisherListName,
    tRPOperPSFromCritSrv6Tlv         INTEGER,
    tRPOperPSFromCritSrv6SidPfxSrc   TPolicyActionSource,
    tRPOperPSFromCritSrv6SidPfxType  InetAddressType,
    tRPOperPSFromCritSrv6SidPfxAddr  InetAddress,
    tRPOperPSFromCritSrv6SidPfxLen   InetAddressPrefixLength,
    tRPOperPSFromCritSrv6SidPfxPar   TPolicyVariableNameOrEmpty
}

tRPOperPSFromCritExtMvpnType     OBJECT-TYPE
    SYNTAX      TPolicyEntryCriteriaMvpnType
    MAX-ACCESS  read-only
    STATUS      current
    DESCRIPTION
        "The value of tRPOperPSFromCritExtMvpnType indicates the BGP route MVPN
         type to match on."
    ::= { tRPOperPSFromCriteriaExtEntry 1 }

tRPOperPSFromCritSrcAddrPfxList  OBJECT-TYPE
    SYNTAX      TLPrefixListName
    MAX-ACCESS  read-only
    STATUS      current
    DESCRIPTION
        "The value of tRPOperPSFromCritSrcAddrPfxList indicates the prefix list
         that is used to match the source address."
    ::= { tRPOperPSFromCriteriaExtEntry 2 }

tRPOperPSFromCritOrigValidState  OBJECT-TYPE
    SYNTAX      INTEGER {
        notApplicable (0),
        valid         (1),
        notFound      (2),
        invalid       (3)
    }
    MAX-ACCESS  read-only
    STATUS      current
    DESCRIPTION
        "The value of tRPOperPSFromCritOrigValidState indicates the origin
         validation state criteria for this policy statement."
    DEFVAL      { notApplicable }
    ::= { tRPOperPSFromCriteriaExtEntry 3 }

tRPOperPSFromCritFlowSrcPfxList  OBJECT-TYPE
    SYNTAX      TLPrefixListName
    MAX-ACCESS  read-only
    STATUS      current
    DESCRIPTION
        "The value of tRPOperPSFromCritFlowSrcPfxList indicates the prefix list
         that is used to match the flow-spec source."
    ::= { tRPOperPSFromCriteriaExtEntry 4 }

tRPOperPSFromCritFlowDstPfxList  OBJECT-TYPE
    SYNTAX      TLPrefixListName
    MAX-ACCESS  read-only
    STATUS      current
    DESCRIPTION
        "The value of tRPOperPSFromCritFlowDstPfxList indicates the prefix list
         that is used to match the flow-spec destination."
    ::= { tRPOperPSFromCriteriaExtEntry 5 }

tRPOperPSFromCritPathType        OBJECT-TYPE
    SYNTAX      TPolicyCritPathType
    MAX-ACCESS  read-only
    STATUS      current
    DESCRIPTION
        "The value of tRPOperPSFromCritPathType indicates the path type to
         match the BGP route on."
    ::= { tRPOperPSFromCriteriaExtEntry 6 }

tRPOperPSFromCritASPathLength    OBJECT-TYPE
    SYNTAX      TPolicyValueOrVarNameOrEmpty
    MAX-ACCESS  read-only
    STATUS      current
    DESCRIPTION
        "The value of tRPOperPSFromCritASPathLength indicates the number of AS
         numbers in the AS-Path to match the BGP route on.

         The tRPOperPSFromCritASPathLength can be a string containing the
         AS-Path length in the range [0-255] or a variable name that needs to
         be resolved to get the AS-Path length."
    ::= { tRPOperPSFromCriteriaExtEntry 7 }

tRPOperPSFromCritASPathLenInd    OBJECT-TYPE
    SYNTAX      TPolicyMatchIndicator
    MAX-ACCESS  read-only
    STATUS      current
    DESCRIPTION
        "The value of tRPOperPSFromCritASPathLenInd indicates whether higher or
         lower AS-Path lengths are accepted for the
         tRPOperPSFromCritASPathLength criteria to match on."
    ::= { tRPOperPSFromCriteriaExtEntry 8 }

tRPOperPSFromCritASPLenUnique    OBJECT-TYPE
    SYNTAX      TruthValue
    MAX-ACCESS  read-only
    STATUS      current
    DESCRIPTION
        "The value of tRPOperPSFromCritASPLenUnique indicates whether only
         unique AS numbers should be considered for the
         tRPOperPSFromCritASPathLength criteria to match on.

         When the value is true, multiple occurrences of the same AS number in
         the AS-Path count as 1 for calculating the AS-Path length."
    ::= { tRPOperPSFromCriteriaExtEntry 9 }

tRPOperPSFromCritCommunityCount  OBJECT-TYPE
    SYNTAX      TPolicyValueOrVarNameOrEmpty
    MAX-ACCESS  read-only
    STATUS      current
    DESCRIPTION
        "The value of tRPOperPSFromCritCommunityCount indicates the number of
         BGP communities to match the BGP route on.

         The tRPOperPSFromCritCommunityCount can be a string containing the
         number of communities in the range [0-1024] or a variable name that
         needs to be resolved to get the community count."
    ::= { tRPOperPSFromCriteriaExtEntry 10 }

tRPOperPSFromCritCommCountInd    OBJECT-TYPE
    SYNTAX      TPolicyMatchIndicator
    MAX-ACCESS  read-only
    STATUS      current
    DESCRIPTION
        "The value of tRPOperPSFromCritCommCountInd indicates whether higher or
         lower community counts are accepted for the
         tRPOperPSFromCritCommunityCount criteria to match on."
    ::= { tRPOperPSFromCriteriaExtEntry 11 }

tRPOperPSFromCritCommCountType   OBJECT-TYPE
    SYNTAX      TPolicyCritCommunityType
    MAX-ACCESS  read-only
    STATUS      current
    DESCRIPTION
        "The value of tRPOperPSFromCritCommCountType indicates which
         communities should be counted for the tRPOperPSFromCritCommunityCount
         criteria to match on."
    ::= { tRPOperPSFromCriteriaExtEntry 12 }

tRPOperPSFromCritMetric          OBJECT-TYPE
    SYNTAX      TPolicyValueOrVarNameOrEmpty
    MAX-ACCESS  read-only
    STATUS      current
    DESCRIPTION
        "The value of tRPOperPSFromCritMetric indicates the metric to match the
         BGP route on.

         The tRPOperPSFromCritMetric can be a string containing the metric
         value in the range [0..4294967295] or a variable name that needs to be
         resolved to get the metric value."
    ::= { tRPOperPSFromCriteriaExtEntry 13 }

tRPOperPSFromCritMetricInd       OBJECT-TYPE
    SYNTAX      TPolicyMatchIndicator
    MAX-ACCESS  read-only
    STATUS      current
    DESCRIPTION
        "The value of tRPOperPSFromCritMetricInd indicates whether higher or
         lower metric values are accepted for the tRPOperPSFromCritMetric
         criteria to match on."
    ::= { tRPOperPSFromCriteriaExtEntry 14 }

tRPOperPSFromCritLocalPref       OBJECT-TYPE
    SYNTAX      TPolicyValueOrVarNameOrEmpty
    MAX-ACCESS  read-only
    STATUS      current
    DESCRIPTION
        "The value of tRPOperPSFromCritLocalPref indicates the local preference
         to match the BGP route on.

         The tRPOperPSFromCritLocalPref can be a string containing the local
         preference value in the range [0..4294967295] or a variable name that
         needs to be resolved to get the local preference value."
    ::= { tRPOperPSFromCriteriaExtEntry 15 }

tRPOperPSFromCritLocalPrefInd    OBJECT-TYPE
    SYNTAX      TPolicyMatchIndicator
    MAX-ACCESS  read-only
    STATUS      current
    DESCRIPTION
        "The value of tRPOperPSFromCritLocalPrefInd indicates whether higher or
         lower local preference values are accepted for the
         tRPOperPSFromCritLocalPref criteria to match on."
    ::= { tRPOperPSFromCriteriaExtEntry 16 }

tRPOperPSFromCritClusterAddrTp1  OBJECT-TYPE
    SYNTAX      InetAddressType
    MAX-ACCESS  read-only
    STATUS      current
    DESCRIPTION
        "The value of tRPOperPSFromCritClusterAddrTp1 indicates the address
         type of tRPOperPSFromCritClusterAddr1."
    ::= { tRPOperPSFromCriteriaExtEntry 17 }

tRPOperPSFromCritClusterAddr1    OBJECT-TYPE
    SYNTAX      InetAddress (SIZE (0|4))
    MAX-ACCESS  read-only
    STATUS      current
    DESCRIPTION
        "The value of tRPOperPSFromCritClusterAddr1 indicates the first IP
         address encoded within the cluster list attribute to match the BGP
         route on.

         The first IP address mask pair is matched against the most recently
         added cluster id."
    ::= { tRPOperPSFromCriteriaExtEntry 18 }

tRPOperPSFromCritClusterPfxLen1  OBJECT-TYPE
    SYNTAX      InetAddressPrefixLength (0..32)
    MAX-ACCESS  read-only
    STATUS      current
    DESCRIPTION
        "The value of tRPOperPSFromCritClusterPfxLen1 indicates the length of
         the first IP address encoded within the cluster list attribute to
         match the BGP route on."
    ::= { tRPOperPSFromCriteriaExtEntry 19 }

tRPOperPSFromCritClusterAddrTp2  OBJECT-TYPE
    SYNTAX      InetAddressType
    MAX-ACCESS  read-only
    STATUS      current
    DESCRIPTION
        "The value of tRPOperPSFromCritClusterAddrTp2 indicates the address
         type of tRPOperPSFromCritClusterAddr2."
    ::= { tRPOperPSFromCriteriaExtEntry 20 }

tRPOperPSFromCritClusterAddr2    OBJECT-TYPE
    SYNTAX      InetAddress (SIZE (0|4))
    MAX-ACCESS  read-only
    STATUS      current
    DESCRIPTION
        "The value of tRPOperPSFromCritClusterAddr2 indicates the second IP
         address encoded within the cluster list attribute to match the BGP
         route on.

         The second IP address mask pair is matched against the second most
         recent added cluster id."
    ::= { tRPOperPSFromCriteriaExtEntry 21 }

tRPOperPSFromCritClusterPfxLen2  OBJECT-TYPE
    SYNTAX      InetAddressPrefixLength (0..32)
    MAX-ACCESS  read-only
    STATUS      current
    DESCRIPTION
        "The value of tRPOperPSFromCritClusterPfxLen2 indicates the length of
         the second IP address encoded within the cluster list attribute to
         match the BGP route on."
    ::= { tRPOperPSFromCriteriaExtEntry 22 }

tRPOperPSFromCritClusterAddrTp3  OBJECT-TYPE
    SYNTAX      InetAddressType
    MAX-ACCESS  read-only
    STATUS      current
    DESCRIPTION
        "The value of tRPOperPSFromCritClusterAddrTp3 indicates the address
         type of tRPOperPSFromCritClusterAddr3."
    ::= { tRPOperPSFromCriteriaExtEntry 23 }

tRPOperPSFromCritClusterAddr3    OBJECT-TYPE
    SYNTAX      InetAddress (SIZE (0|4))
    MAX-ACCESS  read-only
    STATUS      current
    DESCRIPTION
        "The value of tRPOperPSFromCritClusterAddr3 indicates the third IP
         address encoded within the cluster list attribute to match the BGP
         route on.

         The third IP address mask pair is matched against the third most
         recent added cluster id."
    ::= { tRPOperPSFromCriteriaExtEntry 24 }

tRPOperPSFromCritClusterPfxLen3  OBJECT-TYPE
    SYNTAX      InetAddressPrefixLength (0..32)
    MAX-ACCESS  read-only
    STATUS      current
    DESCRIPTION
        "The value of tRPOperPSFromCritClusterPfxLen3 indicates the length of
         the third IP address encoded within the cluster list attribute to
         match the BGP route on."
    ::= { tRPOperPSFromCriteriaExtEntry 25 }

tRPOperPSFromCritClusterAddrTp4  OBJECT-TYPE
    SYNTAX      InetAddressType
    MAX-ACCESS  read-only
    STATUS      current
    DESCRIPTION
        "The value of tRPOperPSFromCritClusterAddrTp4 indicates the address
         type of tRPOperPSFromCritClusterAddr4."
    ::= { tRPOperPSFromCriteriaExtEntry 26 }

tRPOperPSFromCritClusterAddr4    OBJECT-TYPE
    SYNTAX      InetAddress (SIZE (0|4))
    MAX-ACCESS  read-only
    STATUS      current
    DESCRIPTION
        "The value of tRPOperPSFromCritClusterAddr4 indicates the fourth IP
         address encoded within the cluster list attribute to match the BGP
         route on.

         The fourth IP address mask pair is matched against the fourth most
         recent added cluster id."
    ::= { tRPOperPSFromCriteriaExtEntry 27 }

tRPOperPSFromCritClusterPfxLen4  OBJECT-TYPE
    SYNTAX      InetAddressPrefixLength (0..32)
    MAX-ACCESS  read-only
    STATUS      current
    DESCRIPTION
        "The value of tRPOperPSFromCritClusterPfxLen4 indicates the length of
         the fourth IP address encoded within the cluster list attribute to
         match the BGP route on."
    ::= { tRPOperPSFromCriteriaExtEntry 28 }

tRPOperPSFromCritClusterAddrTp5  OBJECT-TYPE
    SYNTAX      InetAddressType
    MAX-ACCESS  read-only
    STATUS      current
    DESCRIPTION
        "The value of tRPOperPSFromCritClusterAddrTp5 indicates the address
         type of tRPOperPSFromCritClusterAddr5."
    ::= { tRPOperPSFromCriteriaExtEntry 29 }

tRPOperPSFromCritClusterAddr5    OBJECT-TYPE
    SYNTAX      InetAddress (SIZE (0|4))
    MAX-ACCESS  read-only
    STATUS      current
    DESCRIPTION
        "The value of tRPOperPSFromCritClusterAddr5 indicates the fifth IP
         address encoded within the cluster list attribute to match the BGP
         route on.

         The fifth IP address mask pair is matched against the fifth most
         recent added cluster id."
    ::= { tRPOperPSFromCriteriaExtEntry 30 }

tRPOperPSFromCritClusterPfxLen5  OBJECT-TYPE
    SYNTAX      InetAddressPrefixLength (0..32)
    MAX-ACCESS  read-only
    STATUS      current
    DESCRIPTION
        "The value of tRPOperPSFromCritClusterPfxLen5 indicates the length of
         the fifth IP address encoded within the cluster list attribute to
         match the BGP route on."
    ::= { tRPOperPSFromCriteriaExtEntry 31 }

tRPOperPSFromCritClusterIdNone   OBJECT-TYPE
    SYNTAX      TruthValue
    MAX-ACCESS  read-only
    STATUS      current
    DESCRIPTION
        "The value of tRPOperPSFromCritClusterIdNone indicates whether only
         routes without any cluster list attribute should be matched on.

         When tRPOperPSFromCritClusterIdNone is set to true, only routes
         without any cluster list attribute are matched.

         The cluster id none criteria is ignored when a cluster id IP address
         criteria is configured."
    ::= { tRPOperPSFromCriteriaExtEntry 32 }

tRPOperPSFromCritNextHopAddrTyp  OBJECT-TYPE
    SYNTAX      InetAddressType
    MAX-ACCESS  read-only
    STATUS      current
    DESCRIPTION
        "The value of tRPOperPSFromCritNextHopAddrTyp indicates the address
         type of tRPOperPSFromCritNextHopAddr."
    ::= { tRPOperPSFromCriteriaExtEntry 33 }

tRPOperPSFromCritNextHopAddr     OBJECT-TYPE
    SYNTAX      InetAddress (SIZE (0|4|16))
    MAX-ACCESS  read-only
    STATUS      current
    DESCRIPTION
        "The value of tRPOperPSFromCritNextHopAddr indicates the next-hop IP
         address to match the BGP route on."
    ::= { tRPOperPSFromCriteriaExtEntry 34 }

tRPOperPSFromCritNextHopPfxList  OBJECT-TYPE
    SYNTAX      TLPrefixListName
    MAX-ACCESS  read-only
    STATUS      current
    DESCRIPTION
        "The value of tRPOperPSFromCritNextHopPfxList indicates the next-hop
         prefix list to match the BGP route on.

         The next-hop prefix list criteria is ignored when a next-hop IP
         address criteria is configured in object tRPOperPSFromCritNextHopAddr."
    ::= { tRPOperPSFromCriteriaExtEntry 35 }

tRPOperPSFromCritExtEvpnType     OBJECT-TYPE
    SYNTAX      TPolicyEntryCriteriaEvpnType
    MAX-ACCESS  read-only
    STATUS      current
    DESCRIPTION
        "The value of tRPOperPSFromCritExtEvpnType indicates the BGP route EVPN
         type to match on."
    ::= { tRPOperPSFromCriteriaExtEntry 37 }

tRPOperPSFromCrAggrContributor   OBJECT-TYPE
    SYNTAX      TruthValue
    MAX-ACCESS  read-only
    STATUS      current
    DESCRIPTION
        "The value of tRPOperPSFromCrAggrContributor indicates whether
         aggregate contributor routes should be matched on.

         When the value is 'true', only the more-specific prefixes that are
         actually contributors are matched."
    ::= { tRPOperPSFromCriteriaExtEntry 38 }

tRPOperPSFromCrEndpointAddrTyp   OBJECT-TYPE
    SYNTAX      InetAddressType
    MAX-ACCESS  read-only
    STATUS      current
    DESCRIPTION
        "The value of tRPOperPSFromCrEndpointAddrTyp indicates the address type
         of tRPOperPSFromCrEndpointAddr."
    ::= { tRPOperPSFromCriteriaExtEntry 39 }

tRPOperPSFromCrEndpointAddr      OBJECT-TYPE
    SYNTAX      InetAddress (SIZE (0|4|16))
    MAX-ACCESS  read-only
    STATUS      current
    DESCRIPTION
        "The value of tRPOperPSFromCrEndpointAddr indicates the SR policy
         endpoint IP address to match the route on.

         This match criterion is only used in import policies."
    ::= { tRPOperPSFromCriteriaExtEntry 40 }

tRPOperPSFromCritColor           OBJECT-TYPE
    SYNTAX      TNamedItemOrEmpty
    MAX-ACCESS  read-only
    STATUS      current
    DESCRIPTION
        "The value of tRPOperPSFromCritColor indicates the SR policy color ID
         to match the route on.

         The value of this object can be a string containing the SR policy
         color ID value in the range [0..4294967295]. An empty string means
         that it is disabled.

         This match criterion is only used in import policies."
    ::= { tRPOperPSFromCriteriaExtEntry 41 }

tRPOperPSFromCritDistinguisher   OBJECT-TYPE
    SYNTAX      TNamedItemOrEmpty
    MAX-ACCESS  read-only
    STATUS      current
    DESCRIPTION
        "The value of tRPOperPSFromCritDistinguisher indicates the SR policy
         distinguisher to match the route on.

         The value of this object can be a string containing the SR policy
         distinguisher value in the range [0..4294967295]. An empty string
         means that it is disabled.

         This match criterion is only used in import policies."
    ::= { tRPOperPSFromCriteriaExtEntry 42 }

tRPOperPSFromCritRDList          OBJECT-TYPE
    SYNTAX      TRouteDistinguisherListName
    MAX-ACCESS  read-only
    STATUS      current
    DESCRIPTION
        "The value of tRPOperPSFromCritRDList indicates the route distinguisher
         (RD) list to match the route on.

         The value of this object can be a string containing the name of the RD
         list or a variable name that needs to be resolved to get the name of
         the RD list. The RD list name must exist in tRPOperRDListTable.

         An empty string means that it is disabled."
    ::= { tRPOperPSFromCriteriaExtEntry 43 }

tRPOperPSFromCritSrv6Tlv         OBJECT-TYPE
    SYNTAX      INTEGER {
        none       (0),
        present    (1),
        notPresent (2)
    }
    MAX-ACCESS  read-only
    STATUS      current
    DESCRIPTION
        "The value of tRPOperPSFromCritSrv6Tlv indicates whether BGP routes
         should be matched with or without any SRv6 TLV present in the prefix
         SID attribute.

         none (0)       - match condition is disabled
         present (1)    - match only the BGP routes with a SRv6 TLV present
         notPresent (2) - match only the BGP routes without any SRv6 TLV"
    ::= { tRPOperPSFromCriteriaExtEntry 44 }

tRPOperPSFromCritSrv6SidPfxSrc   OBJECT-TYPE
    SYNTAX      TPolicyActionSource
    MAX-ACCESS  read-only
    STATUS      current
    DESCRIPTION
        "The value of tRPOperPSFromCritSrv6SidPfxSrc indicates the source of
         the SRv6 SID prefix to match the BGP route on.

         The value 'actionValue(1)' means the SID prefix is the value of
         tRPOperPSFromCritSrv6SidPfxAddr with address type defined by
         tRPOperPSFromCritSrv6SidPfxType and prefix length defined by
         tRPOperPSFromCritSrv6SidPfxLen; the value of the object
         tRPOperPSFromCritSrv6SidPfxPar is ignored.

         The value 'actionParam(2) means the SID prefix is derived from the
         object tRPOperPSFromCritSrv6SidPfxPar; the value of the object
         tRPOperPSFromCritSrv6SidPfxType, tRPOperPSFromCritSrv6SidPfxAddr and
         tRPOperPSFromCritSrv6SidPfxLen are ignored."
    ::= { tRPOperPSFromCriteriaExtEntry 45 }

tRPOperPSFromCritSrv6SidPfxType  OBJECT-TYPE
    SYNTAX      InetAddressType
    MAX-ACCESS  read-only
    STATUS      current
    DESCRIPTION
        "The value of tRPOperPSFromCritSrv6SidPfxType indicates the type of
         tRPOperPSFromCritSrv6SidPfxAddr.

         The value of this object is ignored when the object
         tRPOperPSFromCritSrv6SidPfxSrc has a value different from
         actionValue(1)."
    ::= { tRPOperPSFromCriteriaExtEntry 46 }

tRPOperPSFromCritSrv6SidPfxAddr  OBJECT-TYPE
    SYNTAX      InetAddress (SIZE (0|16))
    MAX-ACCESS  read-only
    STATUS      current
    DESCRIPTION
        "The value of tRPOperPSFromCritSrv6SidPfxAddr indicates the SRv6 SID
         prefix to match the BGP route on.

         The value of this object is ignored when the object
         tRPOperPSFromCritSrv6SidPfxSrc has a value different from
         actionValue(1)."
    ::= { tRPOperPSFromCriteriaExtEntry 47 }

tRPOperPSFromCritSrv6SidPfxLen   OBJECT-TYPE
    SYNTAX      InetAddressPrefixLength (0..128)
    MAX-ACCESS  read-only
    STATUS      current
    DESCRIPTION
        "The value of tRPOperPSFromCritSrv6SidPfxLen indicates the the prefix
         length of the SRv6 SID prefix.

         The value of this object is ignored when the object
         tRPOperPSFromCritSrv6SidPfxSrc has a value different from
         actionValue(1)."
    ::= { tRPOperPSFromCriteriaExtEntry 48 }

tRPOperPSFromCritSrv6SidPfxPar   OBJECT-TYPE
    SYNTAX      TPolicyVariableNameOrEmpty
    MAX-ACCESS  read-only
    STATUS      current
    DESCRIPTION
        "The value of tRPOperPSFromCritSrv6SidPfxPar indicates the variable
         name that must be resolved to get the SRv6 SID prefix to match on.

         The value of this object is ignored when the object
         tRPOperPSFromCritSrv6SidPfxSrc has a value different from
         actionParam(2)."
    ::= { tRPOperPSFromCriteriaExtEntry 49 }

tRPOperPSPolicyVariableTable     OBJECT-TYPE
    SYNTAX      SEQUENCE OF TRPOperPSPolicyVariableEntry
    MAX-ACCESS  not-accessible
    STATUS      current
    DESCRIPTION
        "Information to resolve variables used in tRPOperPSFromCriteriaTable."
    ::= { tRPOperValueObjects 35 }

tRPOperPSPolicyVariableEntry     OBJECT-TYPE
    SYNTAX      TRPOperPSPolicyVariableEntry
    MAX-ACCESS  not-accessible
    STATUS      current
    DESCRIPTION
        "This entry maps a variable to a name for the corresponding entry in
         tRPOperPSFromCriteriaEntry if tRPOperPSFromCriteriaPolicy refers to a
         policy statement that uses variables in its
         tRPOperPSFromCriteriaTable, tRPOperPSAcceptActionParamsTable,
         tRPOperPSDefaultActionParamsTable, tRPOperPSAcptActParamsExtTable or
         tRPOperPSDefActParamsExtTable entries."
    INDEX       {
        tRPOperPolicyStatementName,
        tRPOperPSFromCriteriaIndex,
        tRPOperPSPolicyVarName
    }
    ::= { tRPOperPSPolicyVariableTable 1 }

TRPOperPSPolicyVariableEntry     ::= SEQUENCE
{
    tRPOperPSPolicyVarName           TPolicyVariableName,
    tRPOperPSPolicyVarRowStatus      RowStatus,
    tRPOperPSPolicyVarValue          TNamedItemOrEmpty,
    tRPOperPSPolicyVarNumber         Integer32,
    tRPOperPSPolicyVarType           TPolicyVariableType,
    tRPOperPSPolicyVarAddressType    InetAddressType,
    tRPOperPSPolicyVarAddress        InetAddress,
    tRPOperPSPolicyVarDecimal        TPolicyDecimal,
    tRPOperPSPolicyVarPrefixLength   InetAddressPrefixLength
}

tRPOperPSPolicyVarName           OBJECT-TYPE
    SYNTAX      TPolicyVariableName
    MAX-ACCESS  not-accessible
    STATUS      current
    DESCRIPTION
        "The value of tRPOperPSPolicyVarName indicates a variable name used in
         the tRPOperPSFromCriteriaTable, tRPOperPSAcceptActionParamsTable,
         tRPOperPSDefaultActionParamsTable, tRPOperPSAcptActParamsExtTable or
         tRPOperPSDefActParamsExtTable entry defined by
         tRPOperPSFromCriteriaPolicy.

         That entry uses this string as value for AS-path, AS-path-group,
         prefix list, community or damping objects."
    ::= { tRPOperPSPolicyVariableEntry 1 }

tRPOperPSPolicyVarRowStatus      OBJECT-TYPE
    SYNTAX      RowStatus
    MAX-ACCESS  read-only
    STATUS      current
    DESCRIPTION
        "The value of tRPOperPSPolicyVarRowStatus indicates the RowStatus for
         this row."
    ::= { tRPOperPSPolicyVariableEntry 2 }

tRPOperPSPolicyVarValue          OBJECT-TYPE
    SYNTAX      TNamedItemOrEmpty
    MAX-ACCESS  read-only
    STATUS      current
    DESCRIPTION
        "The value of tRPOperPSPolicyVarValue indicates the actual as-path
         name, as-path group name, prefix list name or community name to which
         tRPOperPSPolicyVarName is resolved.

         This object tRPOperPSPolicyVarValue is ignored when the object
         tRPOperPSPolicyVarType has a value different from string(1)."
    ::= { tRPOperPSPolicyVariableEntry 3 }

tRPOperPSPolicyVarNumber         OBJECT-TYPE
    SYNTAX      Integer32
    MAX-ACCESS  read-only
    STATUS      current
    DESCRIPTION
        "The value of tRPOperPSPolicyVarNumber indicates the actual aigp metric
         value, as-path prepend value, local preference value, metric value or
         next-hop value to which tRPOperPSPolicyVarName is resolved.

         This object tRPOperPSPolicyVarNumber is ignored when the object
         tRPOperPSPolicyVarType has a value different from integer(2)."
    ::= { tRPOperPSPolicyVariableEntry 4 }

tRPOperPSPolicyVarType           OBJECT-TYPE
    SYNTAX      TPolicyVariableType
    MAX-ACCESS  read-only
    STATUS      current
    DESCRIPTION
        "The value of tRPOperPSPolicyVarType indicates how to resolve the
         tRPOperPSPolicyVarName.

         string(1)  - indicates that tRPOperPSPolicyVarValue is to be used
         integer(2) - indicates that tRPOperPSPolicyVarNumber is to be used
         address(3) - indicates that tRPOperPSPolicyVarAddressType and
                      tRPOperPSPolicyVarAddress are to be used
         decimal(4) - indicates that tRPOperPSPolicyVarDecimal is to be used
         prefix (5) - indicates that tRPOperPSPolicyVarAddressType,
                      tRPOperPSPolicyVarAddress and tRPOperPSPolicyVarPrefixLength
                      are to be used"
    ::= { tRPOperPSPolicyVariableEntry 5 }

tRPOperPSPolicyVarAddressType    OBJECT-TYPE
    SYNTAX      InetAddressType
    MAX-ACCESS  read-only
    STATUS      current
    DESCRIPTION
        "The value of tRPOperPSPolicyVarAddressType indicates the actual IP
         address type of the tRPOperPSPolicyVarAddress to which
         tRPOperPSPolicyVarName is resolved.

         This object tRPOperPSPolicyVarAddressType is ignored when the object
         tRPOperPSPolicyVarType has a value different from address(3) or prefix
         (5)."
    ::= { tRPOperPSPolicyVariableEntry 6 }

tRPOperPSPolicyVarAddress        OBJECT-TYPE
    SYNTAX      InetAddress (SIZE (0|4|16|20))
    MAX-ACCESS  read-only
    STATUS      current
    DESCRIPTION
        "The value of tRPOperPSPolicyVarAddress indicates the actual next-hop
         address to which tRPOperPSPolicyVarName is resolved.

         This object tRPOperPSPolicyVarAddress is ignored when the object
         tRPOperPSPolicyVarType has a value different from address(3) or prefix
         (5)."
    ::= { tRPOperPSPolicyVariableEntry 7 }

tRPOperPSPolicyVarDecimal        OBJECT-TYPE
    SYNTAX      TPolicyDecimal
    MAX-ACCESS  read-only
    STATUS      current
    DESCRIPTION
        "The value of tRPOperPSPolicyVarDecimal indicates the actual decimal
         value to which tRPOperPSPolicyVarName is resolved.

         This object tRPOperPSPolicyVarDecimal is ignored when the object
         tRPOperPSPolicyVarType has a value different from decimal(4)."
    ::= { tRPOperPSPolicyVariableEntry 8 }

tRPOperPSPolicyVarPrefixLength   OBJECT-TYPE
    SYNTAX      InetAddressPrefixLength (0..128)
    MAX-ACCESS  read-only
    STATUS      current
    DESCRIPTION
        "The value of tRPOperPSPolicyVarPrefixLength indicates the prefix
         length of the prefix to which tRPOperPSPolicyVarName is resolved.

         This object tRPOperPSPolicyVarPrefixLength is ignored when the object
         tRPOperPSPolicyVarType has a value different from prefix (5)."
    ::= { tRPOperPSPolicyVariableEntry 9 }

tRPOperPSAcptActParamsExtTable   OBJECT-TYPE
    SYNTAX      SEQUENCE OF TRPOperPSAcptActParamsExtEntry
    MAX-ACCESS  not-accessible
    STATUS      current
    DESCRIPTION
        "An extension table of tRPOperPSAcceptActionParamsTable containing
         extra accept-action parameters for each policy statement entry."
    ::= { tRPOperValueObjects 36 }

tRPOperPSAcptActParamsExtEntry   OBJECT-TYPE
    SYNTAX      TRPOperPSAcptActParamsExtEntry
    MAX-ACCESS  not-accessible
    STATUS      current
    DESCRIPTION
        "Accept-action information for a policy statement entry."
    AUGMENTS    { tRPOperPSAcceptActionParamsEntry }
    ::= { tRPOperPSAcptActParamsExtTable 1 }

TRPOperPSAcptActParamsExtEntry   ::= SEQUENCE
{
    tRPOperPSAcptActStickyEcmp       TruthValue,
    tRPOperPSAcptActAddPathSendLimit TPolicyAddPathSendLimit,
    tRPOperPSAcptActInstBackupPath   TruthValue,
    tRPOperPSAcptActAdvertiseLabel   TPolicyAdvertiseLabelMode,
    tRPOperPSAcptActBgpLeaking       TruthValue,
    tRPOperPSAcptActAigpMetricSource TPolicyActionSource,
    tRPOperPSAcptActAigpMetricParam  TPolicyVariableNameOrEmpty,
    tRPOperPSAcptActASPathPendSource TPolicyActionSource,
    tRPOperPSAcptActASPathPendParam  TPolicyVariableNameOrEmpty,
    tRPOperPSAcptActLocalPrefSource  TPolicyActionSource,
    tRPOperPSAcptActLocalPrefParam   TPolicyVariableNameOrEmpty,
    tRPOperPSAcptActMetricParam      TPolicyVariableNameOrEmpty,
    tRPOperPSAcptActNextHopSource    TPolicyActionSource,
    tRPOperPSAcptActNextHopParam     TPolicyVariableNameOrEmpty,
    tRPOperPSAcptActOriginSource     TPolicyActionSource,
    tRPOperPSAcptActOriginParam      TPolicyVariableNameOrEmpty,
    tRPOperPSAcptActOrigValStateSrc  TPolicyActionSource,
    tRPOperPSAcptActOrigValStatePar  TPolicyVariableNameOrEmpty,
    tRPOperPSAcptActPreferenceSource TPolicyActionSource,
    tRPOperPSAcptActPreferenceParam  TPolicyVariableNameOrEmpty,
    tRPOperPSAcptActTagSource        TPolicyActionSource,
    tRPOperPSAcptActTagParam         TPolicyVariableNameOrEmpty,
    tRPOperPSAcptActOspfTypeSource   TPolicyActionSource,
    tRPOperPSAcptActOspfTypeParam    TPolicyVariableNameOrEmpty,
    tRPOperPSAcptActASPPendCountSrc  TPolicyActionSource,
    tRPOperPSAcptActASPPendCountPar  TPolicyVariableNameOrEmpty,
    tRPOperPSAcptActASPPndMstRecent  TruthValue,
    tRPOperPSAcptActCreateUdpTunnel  TruthValue,
    tRPOperPSAcptActResolveStatic    TruthValue,
    tRPOperPSAcptActAdminTagPolicy   TPolicyAdminTagPolicyOrVarName,
    tRPOperPSAcptActBgpMedSource     TPolicyBgpMedSource,
    tRPOperPSAcptActBgpMedValue      TPolicyValueOrVarNameOrEmpty,
    tRPOperPSAcptActBgpMedExpr       TPolicyBgpMedExpression,
    tRPOperPSAcptActDisableRtInstall TruthValue,
    tRPOperPSAcptActSrLabelIndex     TPolicyValueOrVarNameOrEmpty,
    tRPOperPSAcptActSrLblIndPrefIgp  TruthValue,
    tRPOperPSAcptActNextHopPeerAddr  TruthValue,
    tRPOperPSAcptActBgpHighPriority  TruthValue,
    tRPOperPSAcptActFlexAlgo         TPolicyValueOrVarNameOrEmpty,
    tRPOperPSAcptActBgpTunnelMetric  TPolicyValueOrVarNameOrEmpty,
    tRPOperPSAcptActBgpTMetPrefAigp  TruthValue,
    tRPOperPSAcptActEgressStats      TruthValue,
    tRPOperPSAcptActIngressStats     TruthValue,
    tRPOperPSAcptActSrMaintPolicy    TNamedItemOrEmpty,
    tRPOperPSAcptActNatPolicy        TNamedItemOrEmpty,
    tRPOperPSAcptActCreateMplsTunl   TruthValue,
    tRPOperPSAcptActBgpTMetPrefMed   TruthValue,
    tRPOperPSAcptActPrefTransFrr     TruthValue,
    tRPOperPSAcptActSrv6Locator      TLNamedItemOrEmpty,
    tRPOperPSAActSrv6RPathBfdSidSrc  TPolicyActionSource,
    tRPOperPSAActSrv6RPathBfdSidTyp  InetAddressType,
    tRPOperPSAActSrv6RPathBfdSid     InetAddress,
    tRPOperPSAActSrv6RPathBfdSidPar  TPolicyVariableNameOrEmpty,
    tRPOperPSAActSrReturnPathBfdLbl  TPolicyValueOrVarNameOrEmpty,
    tRPOperPSAcptActSrv6MSLocator    TLNamedItemOrEmpty
}

tRPOperPSAcptActStickyEcmp       OBJECT-TYPE
    SYNTAX      TruthValue
    MAX-ACCESS  read-only
    STATUS      current
    DESCRIPTION
        "The value of tRPOperPSAcptActStickyEcmp indicates whether sticky ECMP
         hash is applied to the route.

         When the value of tRPOperPSAcptActStickyEcmp is true and one or more
         of the multiple ECMP next-hops go down, then the unaffected traffic
         flows continues to be hashed to the same next-hops as prior to the
         failures; the affected traffic flows are redistributed as evenly as
         possible to the remaining next-hops."
    ::= { tRPOperPSAcptActParamsExtEntry 1 }

tRPOperPSAcptActAddPathSendLimit OBJECT-TYPE
    SYNTAX      TPolicyAddPathSendLimit
    MAX-ACCESS  read-only
    STATUS      current
    DESCRIPTION
        "The value of tRPOperPSAcptActAddPathSendLimit indicates the
         operational value for the ADD-PATH send limit for this policy
         statement."
    ::= { tRPOperPSAcptActParamsExtEntry 2 }

tRPOperPSAcptActInstBackupPath   OBJECT-TYPE
    SYNTAX      TruthValue
    MAX-ACCESS  read-only
    STATUS      current
    DESCRIPTION
        "The value of tRPOperPSAcptActInstBackupPath indicates whether the
         installation of a backup path is desired for the route matching this
         entry."
    ::= { tRPOperPSAcptActParamsExtEntry 3 }

tRPOperPSAcptActAdvertiseLabel   OBJECT-TYPE
    SYNTAX      TPolicyAdvertiseLabelMode
    MAX-ACCESS  read-only
    STATUS      current
    DESCRIPTION
        "The value of tRPOperPSAcptActAdvertiseLabel indicates the
         advertisement label mode for the route matching this entry."
    ::= { tRPOperPSAcptActParamsExtEntry 4 }

tRPOperPSAcptActBgpLeaking       OBJECT-TYPE
    SYNTAX      TruthValue
    MAX-ACCESS  read-only
    STATUS      current
    DESCRIPTION
        "The value of tRPOperPSAcptActBgpLeaking indicates whether BGP leaking
         is applied for the route matching this entry.

         When the value of tRPOperPSAcptActBgpLeaking is true, the BGP route is
         leaked into a VPRN according to the user configured policies."
    ::= { tRPOperPSAcptActParamsExtEntry 5 }

tRPOperPSAcptActAigpMetricSource OBJECT-TYPE
    SYNTAX      TPolicyActionSource
    MAX-ACCESS  read-only
    STATUS      current
    DESCRIPTION
        "The value of tRPOperPSAcptActAigpMetricSource indicates the source of
         the accept action AIGP (Accumulated IGP) metric.

         The value 'actionValue(1)' means the AIGP metric value is the value of
         tRPOperPSAcptActnAigpMetricVal; the value of the object
         tRPOperPSAcptActAigpMetricParam is ignored.

         The value 'actionParam(2) means the AIGP metric value is derived from
         the object tRPOperPSAcptActAigpMetricParam; the value of the object
         tRPOperPSAcptActnAigpMetricVal is ignored.

         When the value of tRPOperPSAcptActionAigpMetric is set to 'none(1)' or
         'useIgp(4)', the value of tRPOperPSAcptActAigpMetricSource is ignored."
    ::= { tRPOperPSAcptActParamsExtEntry 6 }

tRPOperPSAcptActAigpMetricParam  OBJECT-TYPE
    SYNTAX      TPolicyVariableNameOrEmpty
    MAX-ACCESS  read-only
    STATUS      current
    DESCRIPTION
        "The value of tRPOperPSAcptActAigpMetricParam indicates the variable
         name that must be resolved to get the value to be added or set for the
         route AIGP(Accumulated IGP) metric.

         The value of this object tRPOperPSAcptActAigpMetricParam is ignored
         when the object tRPOperPSAcptActAigpMetricSource has a value different
         from actionParam(2).

         When the value of tRPOperPSAcptActionAigpMetric is set to 'none(1)' or
         'useIgp(4)', the value of tRPOperPSAcptActAigpMetricParam is ignored."
    ::= { tRPOperPSAcptActParamsExtEntry 7 }

tRPOperPSAcptActASPathPendSource OBJECT-TYPE
    SYNTAX      TPolicyActionSource
    MAX-ACCESS  read-only
    STATUS      current
    DESCRIPTION
        "The value of tRPOperPSAcptActASPathPendSource indicates the source of
         the accept action AS Path prepend.

         The value 'actionValue(1)' means the AS Path prepend value is the
         value of tRPOperPSAcceptActionASPathPend; the value of the object
         tRPOperPSAcptActASPathPendParam is ignored.

         The value 'actionParam(2) means the AS Path prepend value is derived
         from the object tRPOperPSAcptActASPathPendParam; the value of the
         object tRPOperPSAcceptActionASPathPend is ignored."
    ::= { tRPOperPSAcptActParamsExtEntry 8 }

tRPOperPSAcptActASPathPendParam  OBJECT-TYPE
    SYNTAX      TPolicyVariableNameOrEmpty
    MAX-ACCESS  read-only
    STATUS      current
    DESCRIPTION
        "The value of tRPOperPSAcptActASPathPendParam indicates the variable
         name that must be resolved to get the AS Number to prepend to the
         AS-Path attribute of the route.

         The value of this object tRPOperPSAcptActASPathPendParam is ignored
         when the object tRPOperPSAcptActASPathPendSource has a value different
         from actionParam(2).

         The AS-Path prepending is disabled when the repeat count is set to
         zero; i.e. when tRPOperPSAcceptActionASPathPrependCount is zero and
         tRPOperPSAcptActASPPendCountSrc is set to actionValue(1)."
    ::= { tRPOperPSAcptActParamsExtEntry 9 }

tRPOperPSAcptActLocalPrefSource  OBJECT-TYPE
    SYNTAX      TPolicyActionSource
    MAX-ACCESS  read-only
    STATUS      current
    DESCRIPTION
        "The value of tRPOperPSAcptActLocalPrefSource indicates the source of
         the accept action local preference.

         The value 'actionValue(1)' means the local preference value is the
         value of tRPOperPSAcceptActionLocalPreference; the value of the object
         tRPOperPSAcptActLocalPrefParam is ignored.

         The value 'actionParam(2) means the local preference value is derived
         from the object tRPOperPSAcptActLocalPrefParam; the value of the
         object tRPOperPSAcceptActionLocalPreference is ignored."
    ::= { tRPOperPSAcptActParamsExtEntry 10 }

tRPOperPSAcptActLocalPrefParam   OBJECT-TYPE
    SYNTAX      TPolicyVariableNameOrEmpty
    MAX-ACCESS  read-only
    STATUS      current
    DESCRIPTION
        "The value of tRPOperPSAcptActLocalPrefParam indicates the variable
         name that must be resolved to get the local preference for the route.

         The value of this object tRPOperPSAcptActLocalPrefParam is ignored
         when the object tRPOperPSAcptActLocalPrefSource has a value different
         from actionParam(2)."
    ::= { tRPOperPSAcptActParamsExtEntry 11 }

tRPOperPSAcptActMetricParam      OBJECT-TYPE
    SYNTAX      TPolicyVariableNameOrEmpty
    MAX-ACCESS  read-only
    STATUS      current
    DESCRIPTION
        "The value of tRPOperPSAcptActMetricParam indicates the variable name
         that must be resolved to get the metric value for the route.

         The value of this object tRPOperPSAcptActMetricParam is ignored when
         the object tRPOperPSAcptActnMetricSource has a value different from
         metricParam(3)."
    ::= { tRPOperPSAcptActParamsExtEntry 12 }

tRPOperPSAcptActNextHopSource    OBJECT-TYPE
    SYNTAX      TPolicyActionSource
    MAX-ACCESS  read-only
    STATUS      current
    DESCRIPTION
        "The value of tRPOperPSAcptActNextHopSource indicates the source of the
         accept action next-hop.

         The value 'actionValue(1)' means the next-hop address is the value of
         tRPOperPSAcptActInetNextHop and the address type is defined by
         tRPOperPSAcptActInetNextHopType; the value of the object
         tRPOperPSAcptActNextHopParam is ignored.

         The value 'actionParam(2) means the next-hop value is derived from the
         object tRPOperPSAcptActNextHopParam; the value of the object
         tRPOperPSAcptActInetNextHop and tRPOperPSAcptActInetNextHopType are
         ignored."
    ::= { tRPOperPSAcptActParamsExtEntry 13 }

tRPOperPSAcptActNextHopParam     OBJECT-TYPE
    SYNTAX      TPolicyVariableNameOrEmpty
    MAX-ACCESS  read-only
    STATUS      current
    DESCRIPTION
        "The value of tRPOperPSAcptActNextHopParam indicates the variable name
         that must be resolved to get the next-hop IP address in the route.

         The value of this object tRPOperPSAcptActNextHopParam is ignored when
         the object tRPOperPSAcptActNextHopSource has a value different from
         actionParam(2)."
    ::= { tRPOperPSAcptActParamsExtEntry 14 }

tRPOperPSAcptActOriginSource     OBJECT-TYPE
    SYNTAX      TPolicyActionSource
    MAX-ACCESS  read-only
    STATUS      current
    DESCRIPTION
        "The value of tRPOperPSAcptActOriginSource indicates the source of the
         route origin accept action.

         The value 'actionValue(1)' means the origin is the value of
         tRPOperPSAcceptActionOrigin; the value of the object
         tRPOperPSAcptActOriginParam is ignored.

         The value 'actionParam(2) means the origin value is derived from the
         object tRPOperPSAcptActOriginParam; the value of the object
         tRPOperPSAcceptActionOrigin is ignored."
    ::= { tRPOperPSAcptActParamsExtEntry 15 }

tRPOperPSAcptActOriginParam      OBJECT-TYPE
    SYNTAX      TPolicyVariableNameOrEmpty
    MAX-ACCESS  read-only
    STATUS      current
    DESCRIPTION
        "The value of tRPOperPSAcptActOriginParam indicates the variable name
         that must be resolved to get the origin of the route exported into BGP
         if it does not match an entry.

         The value of this object tRPOperPSAcptActOriginParam is ignored when
         the object tRPOperPSAcptActOriginSource has a value different from
         actionParam(2)."
    ::= { tRPOperPSAcptActParamsExtEntry 16 }

tRPOperPSAcptActOrigValStateSrc  OBJECT-TYPE
    SYNTAX      TPolicyActionSource
    MAX-ACCESS  read-only
    STATUS      current
    DESCRIPTION
        "The value of tRPOperPSAcptActOrigValStateSrc indicates the source of
         the origin validation state.

         The value 'actionValue(1)' means the origin validation state is the
         value of tRPOperPSAcptActnOrigValidState; the value of the object
         tRPOperPSAcptActOrigValStatePar is ignored.

         The value 'actionParam(2) means the origin validation state value is
         derived from the object tRPOperPSAcptActOrigValStatePar; the value of
         the object tRPOperPSAcptActnOrigValidState is ignored."
    ::= { tRPOperPSAcptActParamsExtEntry 17 }

tRPOperPSAcptActOrigValStatePar  OBJECT-TYPE
    SYNTAX      TPolicyVariableNameOrEmpty
    MAX-ACCESS  read-only
    STATUS      current
    DESCRIPTION
        "The value of tRPOperPSAcptActOrigValStatePar indicates the variable
         name that must be resolved to get the origin validation state.

         The value of this object tRPOperPSAcptActOrigValStatePar is ignored
         when the object tRPOperPSAcptActOrigValStateSrc has a value different
         from actionParam(2)."
    ::= { tRPOperPSAcptActParamsExtEntry 18 }

tRPOperPSAcptActPreferenceSource OBJECT-TYPE
    SYNTAX      TPolicyActionSource
    MAX-ACCESS  read-only
    STATUS      current
    DESCRIPTION
        "The value of tRPOperPSAcptActPreferenceSource indicates the source of
         the preference accept action.

         The value 'actionValue(1)' means the preference is the value of
         tRPOperPSAcceptActionPreference; the value of the object
         tRPOperPSAcptActPreferenceParam is ignored.

         The value 'actionParam(2) means the preference value is derived from
         the object tRPOperPSAcptActPreferenceParam; the value of the object
         tRPOperPSAcceptActionPreference is ignored."
    ::= { tRPOperPSAcptActParamsExtEntry 19 }

tRPOperPSAcptActPreferenceParam  OBJECT-TYPE
    SYNTAX      TPolicyVariableNameOrEmpty
    MAX-ACCESS  read-only
    STATUS      current
    DESCRIPTION
        "The value of tRPOperPSAcptActPreferenceParam indicates the variable
         name that must be resolved to get the preference.

         The value of this object tRPOperPSAcptActPreferenceParam is ignored
         when the object tRPOperPSAcptActPreferenceSource has a value different
         from actionParam(2)."
    ::= { tRPOperPSAcptActParamsExtEntry 20 }

tRPOperPSAcptActTagSource        OBJECT-TYPE
    SYNTAX      TPolicyActionSource
    MAX-ACCESS  read-only
    STATUS      current
    DESCRIPTION
        "The value of tRPOperPSAcptActTagSource indicates the source of the tag
         accept action.

         The value 'actionValue(1)' means the tag is the value of
         tRPOperPSAcceptActionTag; the value of the object
         tRPOperPSAcptActTagParam is ignored.

         The value 'actionParam(2) means the tag value is derived from the
         object tRPOperPSAcptActTagParam; the value of the object
         tRPOperPSAcceptActionTag is ignored."
    ::= { tRPOperPSAcptActParamsExtEntry 21 }

tRPOperPSAcptActTagParam         OBJECT-TYPE
    SYNTAX      TPolicyVariableNameOrEmpty
    MAX-ACCESS  read-only
    STATUS      current
    DESCRIPTION
        "The value of tRPOperPSAcptActTagParam indicates the variable name that
         must be resolved to get the tag for the route.

         The value of this object tRPOperPSAcptActTagParam is ignored when the
         object tRPOperPSAcptActTagSource has a value different from
         actionParam(2)."
    ::= { tRPOperPSAcptActParamsExtEntry 22 }

tRPOperPSAcptActOspfTypeSource   OBJECT-TYPE
    SYNTAX      TPolicyActionSource
    MAX-ACCESS  read-only
    STATUS      current
    DESCRIPTION
        "The value of tRPOperPSAcptActOspfTypeSource indicates the source of
         the OSPF route type accept action.

         The value 'actionValue(1)' means the OSPF route type is the value of
         tRPOperPSAcceptActionOspfType; the value of the object
         tRPOperPSAcptActOspfTypeParam is ignored.

         The value 'actionParam(2) means the OSPF route type value is derived
         from the object tRPOperPSAcptActOspfTypeParam; the value of the object
         tRPOperPSAcceptActionOspfType is ignored."
    ::= { tRPOperPSAcptActParamsExtEntry 23 }

tRPOperPSAcptActOspfTypeParam    OBJECT-TYPE
    SYNTAX      TPolicyVariableNameOrEmpty
    MAX-ACCESS  read-only
    STATUS      current
    DESCRIPTION
        "The value of tRPOperPSAcptActOspfTypeParam indicates the variable name
         that must be resolved to get the OSPF route type to set in the route.

         The value of this object tRPOperPSAcptActOspfTypeParam is ignored when
         the object tRPOperPSAcptActOspfTypeSource has a value different from
         actionParam(2)."
    ::= { tRPOperPSAcptActParamsExtEntry 24 }

tRPOperPSAcptActASPPendCountSrc  OBJECT-TYPE
    SYNTAX      TPolicyActionSource
    MAX-ACCESS  read-only
    STATUS      current
    DESCRIPTION
        "The value of tRPOperPSAcptActASPPendCountSrc indicates the source of
         the accept action AS Path prepend repeat count.

         The value 'actionValue(1)' means the AS Path prepend count is the
         value of tRPOperPSAcceptActionASPathPrependCount; the value of the
         object tRPOperPSAcptActASPPendCountPar is ignored.

         The value 'actionParam(2) means the AS Path prepend count is derived
         from the object tRPOperPSAcptActASPPendCountPar; the value of the
         object tRPOperPSAcceptActionASPathPrependCount is ignored."
    ::= { tRPOperPSAcptActParamsExtEntry 26 }

tRPOperPSAcptActASPPendCountPar  OBJECT-TYPE
    SYNTAX      TPolicyVariableNameOrEmpty
    MAX-ACCESS  read-only
    STATUS      current
    DESCRIPTION
        "The value of tRPOperPSAcptActASPPendCountPar indicates the variable
         name that must be resolved to get the number of times to prepend the
         AS number to the AS-Path attribute of the route.

         The value of this object is ignored when the object
         tRPOperPSAcptActASPPendCountSrc has a value different from
         actionParam(2)."
    ::= { tRPOperPSAcptActParamsExtEntry 27 }

tRPOperPSAcptActASPPndMstRecent  OBJECT-TYPE
    SYNTAX      TruthValue
    MAX-ACCESS  read-only
    STATUS      current
    DESCRIPTION
        "The value of tRPOperPSAcptActASPPndMstRecent indicates whether the
         most recent AS number must be prepended to the AS-Path attribute of
         the route.

         When the value of tRPOperPSAcptActASPPndMstRecent is true the last
         (most recent) ASN in the AS path is used to prepend to the AS-Path;
         tRPOperPSAcceptActionASPathPend and tRPOperPSAcptActASPathPendParam
         are ignored."
    ::= { tRPOperPSAcptActParamsExtEntry 28 }

tRPOperPSAcptActCreateUdpTunnel  OBJECT-TYPE
    SYNTAX      TruthValue
    MAX-ACCESS  read-only
    STATUS      current
    DESCRIPTION
        "The value of tRPOperPSAcptActCreateUdpTunnel indicates whether a UDP
         tunnel must be instantiated for the route matching this entry."
    ::= { tRPOperPSAcptActParamsExtEntry 29 }

tRPOperPSAcptActResolveStatic    OBJECT-TYPE
    SYNTAX      TruthValue
    MAX-ACCESS  read-only
    STATUS      current
    DESCRIPTION
        "The value of tRPOperPSAcptActResolveStatic indicates whether the BGP
         next-hop for the route matching this entry is the resolved next-hop of
         the static route.

         This object has only effect in BGP export policies and applies only to
         BGP routes created by exporting static routes with indirect next-hops.

         When the value of tRPOperPSAcptActResolveStatic is true, the BGP
         next-hop is the resolved next-hop of the static route. When the value
         is false, the BGP next-hop is copied from the indirect next-hop."
    ::= { tRPOperPSAcptActParamsExtEntry 30 }

tRPOperPSAcptActAdminTagPolicy   OBJECT-TYPE
    SYNTAX      TPolicyAdminTagPolicyOrVarName
    MAX-ACCESS  read-only
    STATUS      current
    DESCRIPTION
        "The value of tRPOperPSAcptActAdminTagPolicy indicates the
         administrative tag policy for the route matching this entry.

         The tRPOperPSAcptActAdminTagPolicy can be a string containing the
         administrative tag policy or a variable name that needs to be resolved
         to get the administrative tag policy.

         The internal colour value assigned to the tag is associated with the
         route. If one or more tags are specified in the policy in an
         include/exclude, then the internal colours associated with those tags
         are assigned to the include/exclude list.

         Set to empty string to disable."
    ::= { tRPOperPSAcptActParamsExtEntry 31 }

tRPOperPSAcptActBgpMedSource     OBJECT-TYPE
    SYNTAX      TPolicyBgpMedSource
    MAX-ACCESS  read-only
    STATUS      current
    DESCRIPTION
        "The value of tRPOperPSAcptActBgpMedSource indicates the source to
         resolve to get the BGP MED value.

         When the value is 'igp', the BGP MED value is set to the  IGP cost of
         the route or tunnel that resolves the BGP next-hop of the received BGP
         route.

         When the value is 'minIgp', the BGP MED value is set to the minimum
         IGP cost; i.e. if the cost of the resolving route or tunnel increases
         the advertised MED is not changed.

         When the value is 'medValue', the BGP MED value is set to the value of
         tRPOperPSAcptActBgpMedValue.

         When the value is 'expression', the BGP MED value is set based on a
         calculation of the provided expression in tRPOperPSAcptActBgpMedExpr."
    ::= { tRPOperPSAcptActParamsExtEntry 32 }

tRPOperPSAcptActBgpMedValue      OBJECT-TYPE
    SYNTAX      TPolicyValueOrVarNameOrEmpty
    MAX-ACCESS  read-only
    STATUS      current
    DESCRIPTION
        "The value of tRPOperPSAcptActBgpMedValue indicates the the BGP MED
         value.

         The value of this object can be a string containing the BGP MED value
         in the range [0..4294967295] or a variable name that needs to be
         resolved to get the BGP MED value.

         The value of this object is ignored when the object
         tRPOperPSAcptActBgpMedSource has a value different from 'medValue'."
    ::= { tRPOperPSAcptActParamsExtEntry 33 }

tRPOperPSAcptActBgpMedExpr       OBJECT-TYPE
    SYNTAX      TPolicyBgpMedExpression
    MAX-ACCESS  read-only
    STATUS      current
    DESCRIPTION
        "The value of tRPOperPSAcptActBgpMedExpr indicates the expression that
         is used to calculate the BGP MED value.

         The value of this object is ignored when the object
         tRPOperPSAcptActBgpMedSource has a value different from 'expression'."
    ::= { tRPOperPSAcptActParamsExtEntry 34 }

tRPOperPSAcptActDisableRtInstall OBJECT-TYPE
    SYNTAX      TruthValue
    MAX-ACCESS  read-only
    STATUS      current
    DESCRIPTION
        "The value of tRPOperPSAcptActDisableRtInstall indicates whether to
         disable the installation of a BGP route in the Routing Table and the
         Forwarding Information Base (FIB)."
    ::= { tRPOperPSAcptActParamsExtEntry 35 }

tRPOperPSAcptActSrLabelIndex     OBJECT-TYPE
    SYNTAX      TPolicyValueOrVarNameOrEmpty
    MAX-ACCESS  read-only
    STATUS      current
    DESCRIPTION
        "The value of tRPOperPSAcptActSrLabelIndex indicates the the Segment
         Routing (SR) Label Index value.

         The value of this object can be a string containing the SR label Index
         value in the range [0..524287] or [0..1048575] (max label value
         depends on the platform) or a variable name that needs to be resolved
         to get the SR Label Index."
    ::= { tRPOperPSAcptActParamsExtEntry 36 }

tRPOperPSAcptActSrLblIndPrefIgp  OBJECT-TYPE
    SYNTAX      TruthValue
    MAX-ACCESS  read-only
    STATUS      current
    DESCRIPTION
        "The value of tRPOperPSAcptActSrLblIndPrefIgp indicates whether it is
         preferred to use the SR Label Index from the IGP route.

         When the value is 'true', BGP will use the SR Label Index from the IGP
         route when present else it will use the value from
         tRPOperPSAcptActSrLabelIndex. When the value is 'false', BGP will
         always use the  tRPOperPSAcptActSrLabelIndex.

         The value of this object is ignored when the object
         tRPOperPSAcptActSrLabelIndex is empty."
    ::= { tRPOperPSAcptActParamsExtEntry 37 }

tRPOperPSAcptActNextHopPeerAddr  OBJECT-TYPE
    SYNTAX      TruthValue
    MAX-ACCESS  read-only
    STATUS      current
    DESCRIPTION
        "The value of tRPOperPSAcptActNextHopPeerAddr indicates whether the
         next-hop must be set to the peer address.

         This object cannot be 'true' when the other next-hop objects have a
         non-default value.

         When this object has a value of 'true' then
         tRPOperPSAcceptActionNextHopSelf, tRPOperPSAcceptActionNextHop,
         tRPOperPSAcptActInetNextHopType, tRPOperPSAcptActInetNextHop,
         tRPOperPSAcptActNextHopSource and tRPOperPSAcptActNextHopParam objects
         are disabled."
    ::= { tRPOperPSAcptActParamsExtEntry 38 }

tRPOperPSAcptActBgpHighPriority  OBJECT-TYPE
    SYNTAX      TruthValue
    MAX-ACCESS  read-only
    STATUS      current
    DESCRIPTION
        "The value of tRPOperPSAcptActBgpHighPriority indicates whether the
         corresponding prefix must be marked in BGP as needing high priority
         treatment."
    ::= { tRPOperPSAcptActParamsExtEntry 39 }

tRPOperPSAcptActFlexAlgo         OBJECT-TYPE
    SYNTAX      TPolicyValueOrVarNameOrEmpty
    MAX-ACCESS  read-only
    STATUS      current
    DESCRIPTION
        "The value of tRPOperPSAcptActFlexAlgo indicates the identifier of the
         Flexible Algorithm.

         The value of this object can be a string containing the Flex Algo Id
         value in the range [128..255] or a variable name that needs to be
         resolved to get the Flex Algo Id."
    ::= { tRPOperPSAcptActParamsExtEntry 40 }

tRPOperPSAcptActBgpTunnelMetric  OBJECT-TYPE
    SYNTAX      TPolicyValueOrVarNameOrEmpty
    MAX-ACCESS  read-only
    STATUS      current
    DESCRIPTION
        "The value of tRPOperPSAcptActBgpTunnelMetric indicates the the BGP
         Tunnel Metric value.

         The value of this object can be a string containing the BGP Tunnel
         Metric value in the range [0..4294967295] or a  variable name that
         needs to be resolved to get the  BGP Tunnel Metric."
    ::= { tRPOperPSAcptActParamsExtEntry 41 }

tRPOperPSAcptActBgpTMetPrefAigp  OBJECT-TYPE
    SYNTAX      TruthValue
    MAX-ACCESS  read-only
    STATUS      current
    DESCRIPTION
        "The value of tRPOperPSAcptActBgpTMetPrefAigp indicates whether it is
         preferred to use the value of the received AIGP attribute as BGP
         Tunnel Metric.

         If the value is 'true', the TTM metric is set to the value of the
         AIGP attribute if attached.
         If an AIGP metric is not attached or if the value is 'false',
         the TTM metric is based on the attached MED metric (if  preferred)
         or set to tRPOperPSAcptActBgpTunnelMetric.

         The value of this object is ignored if the object
         tRPOperPSAcptActBgpTunnelMetric is empty."
    ::= { tRPOperPSAcptActParamsExtEntry 42 }

tRPOperPSAcptActEgressStats      OBJECT-TYPE
    SYNTAX      TruthValue
    MAX-ACCESS  read-only
    STATUS      current
    DESCRIPTION
        "The value of tRPOperPSAcptActEgressStats indicates whether to collect
         egress statistics for BGP Labeled Unicast routes.

         If the value is 'true', the system is instructed to allocate a
         statistical index."
    ::= { tRPOperPSAcptActParamsExtEntry 43 }

tRPOperPSAcptActIngressStats     OBJECT-TYPE
    SYNTAX      TruthValue
    MAX-ACCESS  read-only
    STATUS      current
    DESCRIPTION
        "The value of tRPOperPSAcptActIngressStats indicates whether to collect
         ingress statistics for BGP Labeled Unicast routes.

         If the value is 'true', the system is instructed to allocate a
         statistical index."
    ::= { tRPOperPSAcptActParamsExtEntry 44 }

tRPOperPSAcptActSrMaintPolicy    OBJECT-TYPE
    SYNTAX      TNamedItemOrEmpty
    MAX-ACCESS  read-only
    STATUS      current
    DESCRIPTION
        "The value of tRPOperPSAcptActSrMaintPolicy indicates the named segment
         routing (SR) maintenance policy for SR policy routes.

         The maintenance policy must exist in
         TIMETRA-SR-POLICY-MIB::vRtrSrMainPlcyTable.

         The value of this object can be a string containing the
         maintenance policy or a variable name that needs to be
         resolved to get the maintenance policy. An empty string
         means that it is disabled."
    ::= { tRPOperPSAcptActParamsExtEntry 45 }

tRPOperPSAcptActNatPolicy        OBJECT-TYPE
    SYNTAX      TNamedItemOrEmpty
    MAX-ACCESS  read-only
    STATUS      current
    DESCRIPTION
        "The value of tRPOperPSAcptActNatPolicy indicates the Network Address
         Translator (NAT) policy for the route matching this entry.

         The NAT policy must exist in TIMETRA-NAT-MIB::tmnxNatPlcyTable.

         The value of this object can be a string containing the
         NAT policy or a variable name that needs to be
         resolved to get the NAT policy. An empty string
         means that it is disabled."
    ::= { tRPOperPSAcptActParamsExtEntry 46 }

tRPOperPSAcptActCreateMplsTunl   OBJECT-TYPE
    SYNTAX      TruthValue
    MAX-ACCESS  read-only
    STATUS      current
    DESCRIPTION
        "The value of tRPOperPSAcptActCreateMplsTunl indicates whether a MPLS
         tunnel must be instantiated for the route matching this entry.

         When the value is 'true', BGP sends the next hop and  (optionally if
         configured) admin-tag-policy name to MPLS if the route is accepted."
    ::= { tRPOperPSAcptActParamsExtEntry 47 }

tRPOperPSAcptActBgpTMetPrefMed   OBJECT-TYPE
    SYNTAX      TruthValue
    MAX-ACCESS  read-only
    STATUS      current
    DESCRIPTION
        "The value of tRPOperPSAcptActBgpTMetPrefMed indicates whether it is
         preferred to use the value of the received MED attribute as BGP Tunnel
         Metric.

         If the value is 'true', the attached MED attribute is preferred to use
         as TTM metric above the tRPOperPSAcptActBgpTunnelMetric. If a MED
         metric is not attached or if the value is 'false' or if AIGP metric is
         preferred, the TTM metric is set based on the attached AIGP metric or
         set to tRPOperPSAcptActBgpTunnelMetric.

         The value of this object is ignored if the object
         tRPOperPSAcptActBgpTunnelMetric is empty."
    ::= { tRPOperPSAcptActParamsExtEntry 48 }

tRPOperPSAcptActPrefTransFrr     OBJECT-TYPE
    SYNTAX      TruthValue
    MAX-ACCESS  read-only
    STATUS      current
    DESCRIPTION
        "The value of tRPOperPSAcptActPrefTransFrr indicates whether transport
         fast-re-route should be preferred.

         The value of this object is ignored if the object
         tRPOperPSFromCriteriaFamily is not srplcyIpv4, srplcyIpv6,
         ipv4MplsLabel or ipv6MplsLabel."
    ::= { tRPOperPSAcptActParamsExtEntry 49 }

tRPOperPSAcptActSrv6Locator      OBJECT-TYPE
    SYNTAX      TLNamedItemOrEmpty
    MAX-ACCESS  read-only
    STATUS      current
    DESCRIPTION
        "The value of tRPOperPSAcptActSrv6Locator indicates the Segment Routing
         over IPv6 (SRv6) locator to advertise for the route matching this
         entry.

         The locator name must exist in  TIMETRA-SRV6:vRtrSrv6LocatorTable.

         The value of this object can be a string containing the
         locator or a variable name TPolicyVariableName that needs
         to be resolved to get the locator. An empty string
         means that it is disabled."
    ::= { tRPOperPSAcptActParamsExtEntry 50 }

tRPOperPSAActSrv6RPathBfdSidSrc  OBJECT-TYPE
    SYNTAX      TPolicyActionSource
    MAX-ACCESS  read-only
    STATUS      current
    DESCRIPTION
        "The value of tRPOperPSAActSrv6RPathBfdSidSrc indicates the source of
         the SRv6 Return Path BFD SID accept action.

         The SID can only be set if tRPOperPSAcptActSrMaintPolicy is set.

         The value 'actionValue(1)' means the Return Path SID is the value of
         tRPOperPSAActSrv6RPathBfdSid and the address type is defined by
         tRPOperPSAActSrv6RPathBfdSidTyp; the value of the object
         tRPOperPSAActSrv6RPathBfdSidPar is ignored.

         The value 'actionParam(2) means the Return Path SID is derived from
         the object tRPOperPSAActSrv6RPathBfdSidPar; the value of the object
         tRPOperPSAActSrv6RPathBfdSid and tRPOperPSAActSrv6RPathBfdSidTyp are
         ignored."
    ::= { tRPOperPSAcptActParamsExtEntry 51 }

tRPOperPSAActSrv6RPathBfdSidTyp  OBJECT-TYPE
    SYNTAX      InetAddressType
    MAX-ACCESS  read-only
    STATUS      current
    DESCRIPTION
        "The value of tRPOperPSAActSrv6RPathBfdSidTyp indicates the type of
         tRPOperPSAActSrv6RPathBfdSid."
    ::= { tRPOperPSAcptActParamsExtEntry 52 }

tRPOperPSAActSrv6RPathBfdSid     OBJECT-TYPE
    SYNTAX      InetAddress (SIZE (0|16))
    MAX-ACCESS  read-only
    STATUS      current
    DESCRIPTION
        "The value of tRPOperPSAActSrv6RPathBfdSid indicates the the SRv6
         Return Path BFD SID.

         The SID can only be set if tRPOperPSAcptActSrMaintPolicy is set."
    ::= { tRPOperPSAcptActParamsExtEntry 53 }

tRPOperPSAActSrv6RPathBfdSidPar  OBJECT-TYPE
    SYNTAX      TPolicyVariableNameOrEmpty
    MAX-ACCESS  read-only
    STATUS      current
    DESCRIPTION
        "The value of tRPOperPSAActSrv6RPathBfdSidPar indicates the variable
         name that must be resolved to get the SRv6 Return Path BFD SID to set
         in route.

         The value of this object tRPOperPSAActSrv6RPathBfdSidPar is ignored
         when the object tRPOperPSAActSrv6RPathBfdSidSrc has a value different
         from actionParam(2)."
    ::= { tRPOperPSAcptActParamsExtEntry 54 }

tRPOperPSAActSrReturnPathBfdLbl  OBJECT-TYPE
    SYNTAX      TPolicyValueOrVarNameOrEmpty
    MAX-ACCESS  read-only
    STATUS      current
    DESCRIPTION
        "The value of tRPOperPSAActSrReturnPathBfdLbl indicates the Return Path
         MPLS label for the BFD packet from the route matching this entry.

         The SID can only be set if tRPOperPSAcptActSrMaintPolicy is set.

         The value of this object can be a string containing the label value in
         the range [32..1048575] or a variable name TPolicyVariableName that
         needs to be resolved to get the label. An empty string means that it
         is disabled."
    ::= { tRPOperPSAcptActParamsExtEntry 55 }

tRPOperPSAcptActSrv6MSLocator    OBJECT-TYPE
    SYNTAX      TLNamedItemOrEmpty
    MAX-ACCESS  read-only
    STATUS      current
    DESCRIPTION
        "The value of tRPOperPSAcptActSrv6MSLocator indicates the Segment
         Routing over IPv6 (SRv6) Micro Segment locator to advertise for the
         route matching this entry.

         The locator name must exist in  TIMETRA-SRV6:vRtrSrv6MSLocatorTable.

         The value of this object can be a string containing the
         locator or a variable name TPolicyVariableName that needs
         to be resolved to get the locator. An empty string
         means that it is disabled."
    ::= { tRPOperPSAcptActParamsExtEntry 56 }

tRPOperPSDefActParamsExtTable    OBJECT-TYPE
    SYNTAX      SEQUENCE OF TRPOperPSDefActParamsExtEntry
    MAX-ACCESS  not-accessible
    STATUS      current
    DESCRIPTION
        "An extension table of tRPOperPSDefaultActionParamsTable containing
         extra default action parameters for each policy statement entry."
    ::= { tRPOperValueObjects 37 }

tRPOperPSDefActParamsExtEntry    OBJECT-TYPE
    SYNTAX      TRPOperPSDefActParamsExtEntry
    MAX-ACCESS  not-accessible
    STATUS      current
    DESCRIPTION
        "Default action information for a policy statement entry."
    AUGMENTS    { tRPOperPSDefaultActionParamsEntry }
    ::= { tRPOperPSDefActParamsExtTable 1 }

TRPOperPSDefActParamsExtEntry    ::= SEQUENCE
{
    tRPOperPSDefActStickyEcmp        TruthValue,
    tRPOperPSDefActAddPathSendLimit  TPolicyAddPathSendLimit,
    tRPOperPSDefActInstBackupPath    TruthValue,
    tRPOperPSDefActAdvertiseLabel    TPolicyAdvertiseLabelMode,
    tRPOperPSDefActBgpLeaking        TruthValue,
    tRPOperPSDefActAigpMetricSource  TPolicyActionSource,
    tRPOperPSDefActAigpMetricParam   TPolicyVariableNameOrEmpty,
    tRPOperPSDefActASPathPendSource  TPolicyActionSource,
    tRPOperPSDefActASPathPendParam   TPolicyVariableNameOrEmpty,
    tRPOperPSDefActLocalPrefSource   TPolicyActionSource,
    tRPOperPSDefActLocalPrefParam    TPolicyVariableNameOrEmpty,
    tRPOperPSDefActMetricParam       TPolicyVariableNameOrEmpty,
    tRPOperPSDefActNextHopSource     TPolicyActionSource,
    tRPOperPSDefActNextHopParam      TPolicyVariableNameOrEmpty,
    tRPOperPSDefActOriginSource      TPolicyActionSource,
    tRPOperPSDefActOriginParam       TPolicyVariableNameOrEmpty,
    tRPOperPSDefActOrigValStateSrc   TPolicyActionSource,
    tRPOperPSDefActOrigValStatePar   TPolicyVariableNameOrEmpty,
    tRPOperPSDefActPreferenceSource  TPolicyActionSource,
    tRPOperPSDefActPreferenceParam   TPolicyVariableNameOrEmpty,
    tRPOperPSDefActTagSource         TPolicyActionSource,
    tRPOperPSDefActTagParam          TPolicyVariableNameOrEmpty,
    tRPOperPSDefActOspfTypeSource    TPolicyActionSource,
    tRPOperPSDefActOspfTypeParam     TPolicyVariableNameOrEmpty,
    tRPOperPSDefActASPPendCountSrc   TPolicyActionSource,
    tRPOperPSDefActASPPendCountPar   TPolicyVariableNameOrEmpty,
    tRPOperPSDefActASPPndMstRecent   TruthValue,
    tRPOperPSDefActCreateUdpTunnel   TruthValue,
    tRPOperPSDefActResolveStatic     TruthValue,
    tRPOperPSDefActAdminTagPolicy    TPolicyAdminTagPolicyOrVarName,
    tRPOperPSDefActBgpMedSource      TPolicyBgpMedSource,
    tRPOperPSDefActBgpMedValue       TPolicyValueOrVarNameOrEmpty,
    tRPOperPSDefActBgpMedExpr        TPolicyBgpMedExpression,
    tRPOperPSDefActDisableRtInstall  TruthValue,
    tRPOperPSDefActSrLabelIndex      TPolicyValueOrVarNameOrEmpty,
    tRPOperPSDefActSrLblIndPrefIgp   TruthValue,
    tRPOperPSDefActNextHopPeerAddr   TruthValue,
    tRPOperPSDefActBgpHighPriority   TruthValue,
    tRPOperPSDefActFlexAlgo          TPolicyValueOrVarNameOrEmpty,
    tRPOperPSDefActBgpTunnelMetric   TPolicyValueOrVarNameOrEmpty,
    tRPOperPSDefActBgpTMetPrefAigp   TruthValue,
    tRPOperPSDefActEgressStats       TruthValue,
    tRPOperPSDefActIngressStats      TruthValue,
    tRPOperPSDefActSrMaintPolicy     TNamedItemOrEmpty,
    tRPOperPSDefActNatPolicy         TNamedItemOrEmpty,
    tRPOperPSDefActCreateMplsTunl    TruthValue,
    tRPOperPSDefActBgpTMetPrefMed    TruthValue,
    tRPOperPSDefActPrefTransFrr      TruthValue,
    tRPOperPSDefActSrv6Locator       TLNamedItemOrEmpty,
    tRPOperPSDActSrv6RPathBfdSidSrc  TPolicyActionSource,
    tRPOperPSDActSrv6RPathBfdSidTyp  InetAddressType,
    tRPOperPSDActSrv6RPathBfdSid     InetAddress,
    tRPOperPSDActSrv6RPathBfdSidPar  TPolicyVariableNameOrEmpty,
    tRPOperPSDActSrReturnPathBfdLbl  TPolicyValueOrVarNameOrEmpty,
    tRPOperPSDefActSrv6MSLocator     TLNamedItemOrEmpty
}

tRPOperPSDefActStickyEcmp        OBJECT-TYPE
    SYNTAX      TruthValue
    MAX-ACCESS  read-only
    STATUS      current
    DESCRIPTION
        "The value of tRPOperPSDefActStickyEcmp indicates whether sticky ECMP
         hash is applied to the route.

         When the value of tRPOperPSDefActStickyEcmp is true and one or more of
         the multiple ECMP next-hops go down, then the unaffected traffic flows
         continues to be hashed to the same next-hops as prior to the failures;
         the affected traffic flows are redistributed as evenly as possible to
         the remaining next-hops."
    ::= { tRPOperPSDefActParamsExtEntry 1 }

tRPOperPSDefActAddPathSendLimit  OBJECT-TYPE
    SYNTAX      TPolicyAddPathSendLimit
    MAX-ACCESS  read-only
    STATUS      current
    DESCRIPTION
        "The value of tRPOperPSDefActAddPathSendLimit indicates the default
         operational ADD-PATH send limit for this policy statement."
    ::= { tRPOperPSDefActParamsExtEntry 2 }

tRPOperPSDefActInstBackupPath    OBJECT-TYPE
    SYNTAX      TruthValue
    MAX-ACCESS  read-only
    STATUS      current
    DESCRIPTION
        "The value of tRPOperPSDefActInstBackupPath indicates whether the
         installation of a backup path is desired for the route matching this
         entry."
    ::= { tRPOperPSDefActParamsExtEntry 3 }

tRPOperPSDefActAdvertiseLabel    OBJECT-TYPE
    SYNTAX      TPolicyAdvertiseLabelMode
    MAX-ACCESS  read-only
    STATUS      current
    DESCRIPTION
        "The value of tRPOperPSDefActAdvertiseLabel indicates the operational
         advertisement label mode for the route matching this entry."
    ::= { tRPOperPSDefActParamsExtEntry 4 }

tRPOperPSDefActBgpLeaking        OBJECT-TYPE
    SYNTAX      TruthValue
    MAX-ACCESS  read-only
    STATUS      current
    DESCRIPTION
        "The value of tRPOperPSDefActBgpLeaking indicates whether BGP leaking
         is applied for the route matching this entry.

         When the value of tRPOperPSDefActBgpLeaking is true, the BGP route is
         leaked into a VPRN according to the user configured policies."
    ::= { tRPOperPSDefActParamsExtEntry 5 }

tRPOperPSDefActAigpMetricSource  OBJECT-TYPE
    SYNTAX      TPolicyActionSource
    MAX-ACCESS  read-only
    STATUS      current
    DESCRIPTION
        "The value of tRPOperPSDefActAigpMetricSource indicates the source of
         the accept action AIGP (Accumulated IGP) metric.

         The value 'actionValue(1)' means the AIGP metric value is the value of
         tRPOperPSDefActnAigpMetricVal; the value of the object
         tRPOperPSDefActAigpMetricParam is ignored.

         The value 'actionParam(2) means the AIGP metric value is derived from
         the object tRPOperPSDefActAigpMetricParam; the value of the object
         tRPOperPSDefActnAigpMetricVal is ignored.

         When the value of tRPOperPSDefActionAigpMetric is set to 'none(1)' or
         'useIgp(4)', the value of tRPOperPSDefActAigpMetricSource is ignored."
    ::= { tRPOperPSDefActParamsExtEntry 6 }

tRPOperPSDefActAigpMetricParam   OBJECT-TYPE
    SYNTAX      TPolicyVariableNameOrEmpty
    MAX-ACCESS  read-only
    STATUS      current
    DESCRIPTION
        "The value of tRPOperPSDefActAigpMetricParam indicates the variable
         name that must be resolved to get the value to be added or set for the
         route AIGP(Accumulated IGP) metric.

         The value of this object tRPOperPSDefActAigpMetricParam is ignored
         when the object tRPOperPSDefActAigpMetricSource has a value different
         from actionParam(2).

         When the value of tRPOperPSDefActionAigpMetric is set to 'none(1)' or
         'useIgp(4)', the value of tRPOperPSDefActAigpMetricParam is ignored."
    ::= { tRPOperPSDefActParamsExtEntry 7 }

tRPOperPSDefActASPathPendSource  OBJECT-TYPE
    SYNTAX      TPolicyActionSource
    MAX-ACCESS  read-only
    STATUS      current
    DESCRIPTION
        "The value of tRPOperPSDefActASPathPendSource indicates the source of
         the default action AS Path prepend.

         The value 'actionValue(1)' means the AS Path prepend value is the
         value of tRPOperPSDefaultActionASPathPend; the value of the object
         tRPOperPSDefActASPathPendParam is ignored.

         The value 'actionParam(2) means the AS Path prepend value is derived
         from the object tRPOperPSDefActASPathPendParam; the value of the
         object tRPOperPSDefaultActionASPathPend is ignored."
    ::= { tRPOperPSDefActParamsExtEntry 8 }

tRPOperPSDefActASPathPendParam   OBJECT-TYPE
    SYNTAX      TPolicyVariableNameOrEmpty
    MAX-ACCESS  read-only
    STATUS      current
    DESCRIPTION
        "The value of tRPOperPSDefActASPathPendParam indicates the variable
         name that must be resolved to get the AS Number to prepend to the
         AS-Path attribute of the route.

         The value of this object tRPOperPSDefActASPathPendParam is ignored
         when the object tRPOperPSDefActASPathPendSource has a value different
         from actionParam(2).

         The AS-Path prepending is disabled when the repeat count is set to
         zero; i.e. when tRPOperPSDefaultActionASPathPrependCount is zero and
         tRPOperPSDefActASPPendCountSrc is set to actionValue(1)."
    ::= { tRPOperPSDefActParamsExtEntry 9 }

tRPOperPSDefActLocalPrefSource   OBJECT-TYPE
    SYNTAX      TPolicyActionSource
    MAX-ACCESS  read-only
    STATUS      current
    DESCRIPTION
        "The value of tRPOperPSDefActLocalPrefSource indicates the source of
         the default action local preference.

         The value 'actionValue(1)' means the local preference value is the
         value of tRPOperPSDefaultActionLocalPreference; the value of the
         object tRPOperPSDefActLocalPrefParam is ignored.

         The value 'actionParam(2) means the local preference value is derived
         from the object tRPOperPSDefActLocalPrefParam; the value of the object
         tRPOperPSDefaultActionLocalPreference is ignored."
    ::= { tRPOperPSDefActParamsExtEntry 10 }

tRPOperPSDefActLocalPrefParam    OBJECT-TYPE
    SYNTAX      TPolicyVariableNameOrEmpty
    MAX-ACCESS  read-only
    STATUS      current
    DESCRIPTION
        "The value of tRPOperPSDefActLocalPrefParam indicates the variable name
         that must be resolved to get the local preference for the route.

         The value of this object tRPOperPSDefActLocalPrefParam is ignored when
         the object tRPOperPSDefActLocalPrefSource has a value different from
         actionParam(2)."
    ::= { tRPOperPSDefActParamsExtEntry 11 }

tRPOperPSDefActMetricParam       OBJECT-TYPE
    SYNTAX      TPolicyVariableNameOrEmpty
    MAX-ACCESS  read-only
    STATUS      current
    DESCRIPTION
        "The value of tRPOperPSDefActMetricParam indicates the variable name
         that must be resolved to get the metric value for the route.

         The value of this object tRPOperPSDefActMetricParam is ignored when
         the object tRPOperPSDefActionMetricSource has a value different from
         metricParam(3)."
    ::= { tRPOperPSDefActParamsExtEntry 12 }

tRPOperPSDefActNextHopSource     OBJECT-TYPE
    SYNTAX      TPolicyActionSource
    MAX-ACCESS  read-only
    STATUS      current
    DESCRIPTION
        "The value of tRPOperPSDefActNextHopSource indicates the source of the
         default action next-hop.

         The value 'actionValue(1)' means the next-hop address is the value of
         tRPOperPSDefActInetNextHop and the address type is defined by
         tRPOperPSDefActInetNextHopType; the value of the object
         tRPOperPSDefActNextHopParam is ignored.

         The value 'actionParam(2) means the next-hop value is derived from the
         object tRPOperPSDefActNextHopParam; the value of the object
         tRPOperPSDefActInetNextHop and tRPOperPSDefActInetNextHopType are
         ignored."
    ::= { tRPOperPSDefActParamsExtEntry 13 }

tRPOperPSDefActNextHopParam      OBJECT-TYPE
    SYNTAX      TPolicyVariableNameOrEmpty
    MAX-ACCESS  read-only
    STATUS      current
    DESCRIPTION
        "The value of tRPOperPSDefActNextHopParam indicates the variable name
         that must be resolved to get the next-hop IP address in the route.

         The value of this object tRPOperPSDefActNextHopParam is ignored when
         the object tRPOperPSDefActNextHopSource has a value different from
         actionParam(2).

         Next-hop cannot refer to an address when the next-hop-self or
         peer-address is 'true'. When this object is set to a variable name
         then tRPOperPSDefaultActionNextHopSelf and
         tRPOperPSDefActNextHopPeerAddr are 'false'."
    ::= { tRPOperPSDefActParamsExtEntry 14 }

tRPOperPSDefActOriginSource      OBJECT-TYPE
    SYNTAX      TPolicyActionSource
    MAX-ACCESS  read-only
    STATUS      current
    DESCRIPTION
        "The value of tRPOperPSDefActOriginSource indicates the source of the
         route origin default action.

         The value 'actionValue(1)' means the origin is the value of
         tRPOperPSDefaultActionOrigin; the value of the object
         tRPOperPSDefActOriginParam is ignored.

         The value 'actionParam(2) means the origin value is derived from the
         object tRPOperPSDefActOriginParam; the value of the object
         tRPOperPSDefaultActionOrigin is ignored."
    ::= { tRPOperPSDefActParamsExtEntry 15 }

tRPOperPSDefActOriginParam       OBJECT-TYPE
    SYNTAX      TPolicyVariableNameOrEmpty
    MAX-ACCESS  read-only
    STATUS      current
    DESCRIPTION
        "The value of tRPOperPSDefActOriginParam indicates the variable name
         that must be resolved to get the origin of the route exported into BGP
         if it does not match an entry.

         The value of this object tRPOperPSDefActOriginParam is ignored when
         the object tRPOperPSDefActOriginSource has a value different from
         actionParam(2)."
    ::= { tRPOperPSDefActParamsExtEntry 16 }

tRPOperPSDefActOrigValStateSrc   OBJECT-TYPE
    SYNTAX      TPolicyActionSource
    MAX-ACCESS  read-only
    STATUS      current
    DESCRIPTION
        "The value of tRPOperPSDefActOrigValStateSrc indicates the source of
         the origin validation state.

         The value 'actionValue(1)' means the origin validation state is the
         value of tRPOperPSDefActnOrigValidState; the value of the object
         tRPOperPSDefActOrigValStatePar is ignored.

         The value 'actionParam(2) means the origin validation state value is
         derived from the object tRPOperPSDefActOrigValStatePar; the value of
         the object tRPOperPSDefActnOrigValidState is ignored."
    ::= { tRPOperPSDefActParamsExtEntry 17 }

tRPOperPSDefActOrigValStatePar   OBJECT-TYPE
    SYNTAX      TPolicyVariableNameOrEmpty
    MAX-ACCESS  read-only
    STATUS      current
    DESCRIPTION
        "The value of tRPOperPSDefActOrigValStatePar indicates the variable
         name that must be resolved to get the origin validation state.

         The value of this object tRPOperPSDefActOrigValStatePar is ignored
         when the object tRPOperPSDefActOrigValStateSrc has a value different
         from actionParam(2)."
    ::= { tRPOperPSDefActParamsExtEntry 18 }

tRPOperPSDefActPreferenceSource  OBJECT-TYPE
    SYNTAX      TPolicyActionSource
    MAX-ACCESS  read-only
    STATUS      current
    DESCRIPTION
        "The value of tRPOperPSDefActPreferenceSource indicates the source of
         the preference default action.

         The value 'actionValue(1)' means the preference is the value of
         tRPOperPSDefaultActionPreference; the value of the object
         tRPOperPSDefActPreferenceParam is ignored.

         The value 'actionParam(2) means the preference value is derived from
         the object tRPOperPSDefActPreferenceParam; the value of the object
         tRPOperPSDefaultActionPreference is ignored."
    ::= { tRPOperPSDefActParamsExtEntry 19 }

tRPOperPSDefActPreferenceParam   OBJECT-TYPE
    SYNTAX      TPolicyVariableNameOrEmpty
    MAX-ACCESS  read-only
    STATUS      current
    DESCRIPTION
        "The value of tRPOperPSDefActPreferenceParam indicates the variable
         name that must be resolved to get the preference.

         The value of this object tRPOperPSDefActPreferenceParam is ignored
         when the object tRPOperPSDefActPreferenceSource has a value different
         from actionParam(2)."
    ::= { tRPOperPSDefActParamsExtEntry 20 }

tRPOperPSDefActTagSource         OBJECT-TYPE
    SYNTAX      TPolicyActionSource
    MAX-ACCESS  read-only
    STATUS      current
    DESCRIPTION
        "The value of tRPOperPSDefActTagSource indicates the source of the tag
         default action.

         The value 'actionValue(1)' means the tag is the value of
         tRPOperPSDefaultActionTag; the value of the object
         tRPOperPSDefActTagParam is ignored.

         The value 'actionParam(2) means the tag value is derived from the
         object tRPOperPSDefActTagParam; the value of the object
         tRPOperPSDefaultActionTag is ignored."
    ::= { tRPOperPSDefActParamsExtEntry 21 }

tRPOperPSDefActTagParam          OBJECT-TYPE
    SYNTAX      TPolicyVariableNameOrEmpty
    MAX-ACCESS  read-only
    STATUS      current
    DESCRIPTION
        "The value of tRPOperPSDefActTagParam indicates the variable name that
         must be resolved to get the tag for the route.

         The value of this object tRPOperPSDefActTagParam is ignored when the
         object tRPOperPSDefActTagSource has a value different from
         actionParam(2)."
    ::= { tRPOperPSDefActParamsExtEntry 22 }

tRPOperPSDefActOspfTypeSource    OBJECT-TYPE
    SYNTAX      TPolicyActionSource
    MAX-ACCESS  read-only
    STATUS      current
    DESCRIPTION
        "The value of tRPOperPSDefActOspfTypeSource indicates the source of the
         OSPF route type default action.

         The value 'actionValue(1)' means the OSPF route type is the value of
         tRPOperPSDefaultActionOspfType; the value of the object
         tRPOperPSDefActOspfTypeParam is ignored.

         The value 'actionParam(2) means the OSPF route type value is derived
         from the object tRPOperPSDefActOspfTypeParam; the value of the object
         tRPOperPSDefaultActionOspfType is ignored."
    ::= { tRPOperPSDefActParamsExtEntry 23 }

tRPOperPSDefActOspfTypeParam     OBJECT-TYPE
    SYNTAX      TPolicyVariableNameOrEmpty
    MAX-ACCESS  read-only
    STATUS      current
    DESCRIPTION
        "The value of tRPOperPSDefActOspfTypeParam indicates the variable name
         that must be resolved to get the OSPF route type for the route.

         The value of this object tRPOperPSDefActOspfTypeParam is ignored when
         the object tRPOperPSDefActOspfTypeSource has a value different from
         actionParam(2)."
    ::= { tRPOperPSDefActParamsExtEntry 24 }

tRPOperPSDefActASPPendCountSrc   OBJECT-TYPE
    SYNTAX      TPolicyActionSource
    MAX-ACCESS  read-only
    STATUS      current
    DESCRIPTION
        "The value of tRPOperPSDefActASPPendCountSrc indicates the source of
         the default action AS Path prepend repeat count.

         The value 'actionValue(1)' means the AS Path prepend count is the
         value of tRPOperPSDefaultActionASPathPrependCount; the value of the
         object tRPOperPSDefActASPPendCountPar is ignored.

         The value 'actionParam(2) means the AS Path prepend count is derived
         from the object tRPOperPSDefActASPPendCountPar; the value of the
         object tRPOperPSDefaultActionASPathPrependCount is ignored."
    ::= { tRPOperPSDefActParamsExtEntry 26 }

tRPOperPSDefActASPPendCountPar   OBJECT-TYPE
    SYNTAX      TPolicyVariableNameOrEmpty
    MAX-ACCESS  read-only
    STATUS      current
    DESCRIPTION
        "The value of tRPOperPSDefActASPPendCountPar indicates the variable
         name that must be resolved to get the number of times to prepend the
         AS number to the AS-Path attribute of the route.

         The value of this object is ignored when the object
         tRPOperPSDefActASPPendCountSrc has a value different from
         actionParam(2)."
    ::= { tRPOperPSDefActParamsExtEntry 27 }

tRPOperPSDefActASPPndMstRecent   OBJECT-TYPE
    SYNTAX      TruthValue
    MAX-ACCESS  read-only
    STATUS      current
    DESCRIPTION
        "The value of tRPOperPSDefActASPPndMstRecent indicates whether the most
         recent AS number must be prepended to the AS-Path attribute of the
         route.

         When the value of tRPOperPSDefActASPPndMstRecent is true the last
         (most recent) ASN in the AS path is used to prepend to the AS-Path;
         tRPOperPSDefaultActionASPathPend and tRPOperPSDefActASPathPendParam
         are ignored."
    ::= { tRPOperPSDefActParamsExtEntry 28 }

tRPOperPSDefActCreateUdpTunnel   OBJECT-TYPE
    SYNTAX      TruthValue
    MAX-ACCESS  read-only
    STATUS      current
    DESCRIPTION
        "The value of tRPOperPSDefActCreateUdpTunnel indicates whether a UDP
         tunnel must be instantiated for the route matching this entry."
    ::= { tRPOperPSDefActParamsExtEntry 29 }

tRPOperPSDefActResolveStatic     OBJECT-TYPE
    SYNTAX      TruthValue
    MAX-ACCESS  read-only
    STATUS      current
    DESCRIPTION
        "The value of tRPOperPSDefActResolveStatic indicates whether the BGP
         next-hop for the route is the resolved next-hop of the static route.

         This object has only effect in BGP export policies and applies only to
         BGP routes created by exporting static routes with indirect next-hops.

         When the value of tRPOperPSDefActResolveStatic is true, the BGP
         next-hop is the resolved next-hop of the static route. When the value
         is false, the BGP next-hop is copied from the indirect next-hop."
    ::= { tRPOperPSDefActParamsExtEntry 30 }

tRPOperPSDefActAdminTagPolicy    OBJECT-TYPE
    SYNTAX      TPolicyAdminTagPolicyOrVarName
    MAX-ACCESS  read-only
    STATUS      current
    DESCRIPTION
        "The value of tRPOperPSDefActAdminTagPolicy indicates the
         administrative tag policy for the route.

         The tRPOperPSDefActAdminTagPolicy can be a string containing the
         administrative tag policy or a variable name that needs to be resolved
         to get the administrative tag policy.

         The internal colour value assigned to the tag is associated with the
         route. If one or more tags are specified in the policy in an
         include/exclude, then the internal colours associated with those tags
         are assigned to the include/exclude list.

         Set to empty string to disable."
    ::= { tRPOperPSDefActParamsExtEntry 31 }

tRPOperPSDefActBgpMedSource      OBJECT-TYPE
    SYNTAX      TPolicyBgpMedSource
    MAX-ACCESS  read-only
    STATUS      current
    DESCRIPTION
        "The value of tRPOperPSDefActBgpMedSource indicates the source to
         resolve to get the BGP MED value.

         When the value is 'igp', the BGP MED value is set to the  IGP cost of
         the route or tunnel that resolves the BGP next-hop of the received BGP
         route.

         When the value is 'minIgp', the BGP MED value is set to the minimum
         IGP cost; i.e. if the cost of the resolving route or tunnel increases
         the advertised MED is not changed.

         When the value is 'medValue', the BGP MED value is set to the value of
         tRPOperPSDefActBgpMedValue.

         When the value is 'expression', the BGP MED value is set based on a
         calculation of the provided expression in tRPOperPSDefActBgpMedExpr."
    ::= { tRPOperPSDefActParamsExtEntry 32 }

tRPOperPSDefActBgpMedValue       OBJECT-TYPE
    SYNTAX      TPolicyValueOrVarNameOrEmpty
    MAX-ACCESS  read-only
    STATUS      current
    DESCRIPTION
        "The value of tRPOperPSDefActBgpMedValue indicates the the BGP MED
         value.

         The value of this object can be a string containing the BGP MED value
         in the range [0..4294967295] or a variable name that needs to be
         resolved to get the BGP MED value.

         The value of this object is ignored when the object
         tRPOperPSDefActBgpMedSource has a value different from 'medValue'."
    ::= { tRPOperPSDefActParamsExtEntry 33 }

tRPOperPSDefActBgpMedExpr        OBJECT-TYPE
    SYNTAX      TPolicyBgpMedExpression
    MAX-ACCESS  read-only
    STATUS      current
    DESCRIPTION
        "The value of tRPOperPSDefActBgpMedExpr indicates the expression that
         is used to calculate the BGP MED value.

         The value of this object is ignored when the object
         tRPOperPSDefActBgpMedSource has a value different from 'expression'."
    ::= { tRPOperPSDefActParamsExtEntry 34 }

tRPOperPSDefActDisableRtInstall  OBJECT-TYPE
    SYNTAX      TruthValue
    MAX-ACCESS  read-only
    STATUS      current
    DESCRIPTION
        "The value of tRPOperPSDefActDisableRtInstall indicates whether to
         disable the installation of a BGP route in the Routing Table and the
         Forwarding Information Base (FIB)."
    ::= { tRPOperPSDefActParamsExtEntry 35 }

tRPOperPSDefActSrLabelIndex      OBJECT-TYPE
    SYNTAX      TPolicyValueOrVarNameOrEmpty
    MAX-ACCESS  read-only
    STATUS      current
    DESCRIPTION
        "The value of tRPOperPSDefActSrLabelIndex indicates the the Segment
         Routing (SR) Label Index value.

         The value of this object can be a string containing the SR label Index
         value in the range [0..1048575] or [0..1048575] (max label value
         depends on the platform) or a variable name that needs to be resolved
         to get the SR Label Index."
    ::= { tRPOperPSDefActParamsExtEntry 36 }

tRPOperPSDefActSrLblIndPrefIgp   OBJECT-TYPE
    SYNTAX      TruthValue
    MAX-ACCESS  read-only
    STATUS      current
    DESCRIPTION
        "The value of tRPOperPSDefActSrLblIndPrefIgp indicates whether it is
         preferred to use the SR Label Index from the IGP route.

         When the value is 'true', BGP will use the SR Label Index form the IGP
         route when present else it will use the value from
         tRPOperPSDefActSrLabelIndex. When the value is 'false', BGP will
         always use the  tRPOperPSDefActSrLabelIndex.

         The value of this object is ignored when the object
         tRPOperPSDefActSrLabelIndex is empty."
    ::= { tRPOperPSDefActParamsExtEntry 37 }

tRPOperPSDefActNextHopPeerAddr   OBJECT-TYPE
    SYNTAX      TruthValue
    MAX-ACCESS  read-only
    STATUS      current
    DESCRIPTION
        "The value of tRPOperPSDefActNextHopPeerAddr indicates whether the
         next-hop must be set to the peer address.

         This object cannot be 'true' when the other next-hop objects have a
         non-default value.

         When this object has a value of 'true' then
         tRPOperPSDefaultActionNextHopSelf, tRPOperPSDefaultActionNextHop,
         tRPOperPSDefActInetNextHopType, tRPOperPSDefActInetNextHop,
         tRPOperPSDefActNextHopSource and tRPOperPSDefActNextHopParam objects
         are disabled."
    ::= { tRPOperPSDefActParamsExtEntry 38 }

tRPOperPSDefActBgpHighPriority   OBJECT-TYPE
    SYNTAX      TruthValue
    MAX-ACCESS  read-only
    STATUS      current
    DESCRIPTION
        "The value of tRPOperPSDefActBgpHighPriority indicates whether the
         corresponding prefix must be marked in BGP as needing high priority
         treatment."
    ::= { tRPOperPSDefActParamsExtEntry 39 }

tRPOperPSDefActFlexAlgo          OBJECT-TYPE
    SYNTAX      TPolicyValueOrVarNameOrEmpty
    MAX-ACCESS  read-only
    STATUS      current
    DESCRIPTION
        "The value of tRPOperPSDefActFlexAlgo indicates the identifier of the
         Flexible Algorithm.

         The value of this object can be a string containing the Flex Algo Id
         value in the range [128..255] or a variable name that needs to be
         resolved to get the Flex Algo Id."
    ::= { tRPOperPSDefActParamsExtEntry 40 }

tRPOperPSDefActBgpTunnelMetric   OBJECT-TYPE
    SYNTAX      TPolicyValueOrVarNameOrEmpty
    MAX-ACCESS  read-only
    STATUS      current
    DESCRIPTION
        "The value of tRPOperPSDefActBgpTunnelMetric indicates the the BGP
         Tunnel Metric value.

         The value of this object can be a string containing the BGP Tunnel
         Metric value in the range [0..4294967295] or a  variable name that
         needs to be resolved to get the  BGP Tunnel Metric."
    ::= { tRPOperPSDefActParamsExtEntry 41 }

tRPOperPSDefActBgpTMetPrefAigp   OBJECT-TYPE
    SYNTAX      TruthValue
    MAX-ACCESS  read-only
    STATUS      current
    DESCRIPTION
        "The value of tRPOperPSDefActBgpTMetPrefAigp indicates whether it is
         preferred to use the value of the received AIGP attribute as BGP
         Tunnel Metric.

         If the value is 'true', the TTM metric is set to the value of the AIGP
         attribute if attached.

         If an AIGP metric is not attached or if the value is 'false',
         the TTM metric is based on the attached MED metric (if  preferred)
         or set to tRPOperPSDefActBgpTunnelMetric.

         The value of this object is ignored if the object
         tRPOperPSDefActBgpTunnelMetric is empty."
    ::= { tRPOperPSDefActParamsExtEntry 42 }

tRPOperPSDefActEgressStats       OBJECT-TYPE
    SYNTAX      TruthValue
    MAX-ACCESS  read-only
    STATUS      current
    DESCRIPTION
        "The value of tRPOperPSDefActEgressStats indicates whether to collect
         egress statistics for BGP Labeled Unicast routes.

         If the value is 'true', the system is instructed to allocate a
         statistical index."
    ::= { tRPOperPSDefActParamsExtEntry 43 }

tRPOperPSDefActIngressStats      OBJECT-TYPE
    SYNTAX      TruthValue
    MAX-ACCESS  read-only
    STATUS      current
    DESCRIPTION
        "The value of tRPOperPSDefActIngressStats indicates whether to collect
         ingress statistics for BGP Labeled Unicast routes.

         If the value is 'true', the system is instructed to allocate a
         statistical index."
    ::= { tRPOperPSDefActParamsExtEntry 44 }

tRPOperPSDefActSrMaintPolicy     OBJECT-TYPE
    SYNTAX      TNamedItemOrEmpty
    MAX-ACCESS  read-only
    STATUS      current
    DESCRIPTION
        "The value of tRPOperPSDefActSrMaintPolicy indicates the named segment
         routing (SR) maintenance policy for SR policy routes.

         The maintenance policy must exist in
         TIMETRA-SR-POLICY-MIB::vRtrSrMainPlcyTable.

         The value of this object can be a string containing the
         maintenance policy or a variable name that needs to be
         resolved to get the maintenance policy. An empty string
         means that it is disabled."
    ::= { tRPOperPSDefActParamsExtEntry 45 }

tRPOperPSDefActNatPolicy         OBJECT-TYPE
    SYNTAX      TNamedItemOrEmpty
    MAX-ACCESS  read-only
    STATUS      current
    DESCRIPTION
        "The value of tRPOperPSDefActNatPolicy indicates the Network Address
         Translator (NAT) policy for the route matching this entry.

         The NAT policy must exist in TIMETRA-NAT-MIB::tmnxNatPlcyTable.

         The value of this object can be a string containing the
         NAT policy or a variable name that needs to be
         resolved to get the NAT policy. An empty string
         means that it is disabled."
    ::= { tRPOperPSDefActParamsExtEntry 46 }

tRPOperPSDefActCreateMplsTunl    OBJECT-TYPE
    SYNTAX      TruthValue
    MAX-ACCESS  read-only
    STATUS      current
    DESCRIPTION
        "The value of tRPOperPSDefActCreateMplsTunl indicates whether a MPLS
         tunnel must be instantiated for the route matching this entry.

         When the value is 'true', BGP sends the next hop and  (optionally if
         configured) admin-tag-policy name to MPLS if the route is accepted."
    ::= { tRPOperPSDefActParamsExtEntry 47 }

tRPOperPSDefActBgpTMetPrefMed    OBJECT-TYPE
    SYNTAX      TruthValue
    MAX-ACCESS  read-only
    STATUS      current
    DESCRIPTION
        "The value of tRPOperPSDefActBgpTMetPrefMed indicates whether it is
         preferred to use the value of the received MED attribute as BGP Tunnel
         Metric.

         If the value is 'true', the attached MED attribute is preferred to use
         as TTM metric above the tRPOperPSDefActBgpTunnelMetric. If a MED
         metric is not attached or if the value is 'false' or if AIGP metric is
         preferred, the TTM metric is set based on the attached AIGP metric or
         set to tRPOperPSDefActBgpTunnelMetric.

         The value of this object is ignored if the object
         tRPOperPSDefActBgpTunnelMetric is empty."
    ::= { tRPOperPSDefActParamsExtEntry 48 }

tRPOperPSDefActPrefTransFrr      OBJECT-TYPE
    SYNTAX      TruthValue
    MAX-ACCESS  read-only
    STATUS      current
    DESCRIPTION
        "The value of tRPOperPSDefActPrefTransFrr indicates whether transport
         fast-re-route should be preferred.

         The value of this object is ignored if the object
         tRPOperPSFromCriteriaFamily is not srplcyIpv4, srplcyIpv6,
         ipv4MplsLabel or ipv6MplsLabel."
    ::= { tRPOperPSDefActParamsExtEntry 49 }

tRPOperPSDefActSrv6Locator       OBJECT-TYPE
    SYNTAX      TLNamedItemOrEmpty
    MAX-ACCESS  read-only
    STATUS      current
    DESCRIPTION
        "The value of tRPOperPSDefActSrv6Locator indicates the Segment Routing
         over IPv6 (SRv6) locator to advertise for the route matching this
         entry.

         The locator name must exist in  TIMETRA-SRV6:vRtrSrv6LocatorTable.

         The value of this object can be a string containing the
         locator or a variable name TPolicyVariableName that needs
         to be resolved to get the locator. An empty string
         means that it is disabled."
    ::= { tRPOperPSDefActParamsExtEntry 50 }

tRPOperPSDActSrv6RPathBfdSidSrc  OBJECT-TYPE
    SYNTAX      TPolicyActionSource
    MAX-ACCESS  read-only
    STATUS      current
    DESCRIPTION
        "The value of tRPOperPSDActSrv6RPathBfdSidSrc indicates the source of
         the SRv6 Return Path BFD SID default action.

         The SID can only be set if tRPOperPSDefActSrMaintPolicy is set.

         The value 'actionValue(1)' means the Return Path SID is the value of
         tRPOperPSDActSrv6RPathBfdSid and the address type is defined by
         tRPOperPSDActSrv6RPathBfdSidTyp; the value of the object
         tRPOperPSDActSrv6RPathBfdSidPar is ignored.

         The value 'actionParam(2) means the Return Path SID is derived from
         the object tRPOperPSDActSrv6RPathBfdSidPar; the value of the object
         tRPOperPSDActSrv6RPathBfdSid and tRPOperPSDActSrv6RPathBfdSidTyp are
         ignored."
    ::= { tRPOperPSDefActParamsExtEntry 51 }

tRPOperPSDActSrv6RPathBfdSidTyp  OBJECT-TYPE
    SYNTAX      InetAddressType
    MAX-ACCESS  read-only
    STATUS      current
    DESCRIPTION
        "The value of tRPOperPSDActSrv6RPathBfdSidTyp indicates the type of
         tRPOperPSDActSrv6RPathBfdSid."
    ::= { tRPOperPSDefActParamsExtEntry 52 }

tRPOperPSDActSrv6RPathBfdSid     OBJECT-TYPE
    SYNTAX      InetAddress (SIZE (0|16))
    MAX-ACCESS  read-only
    STATUS      current
    DESCRIPTION
        "The value of tRPOperPSDActSrv6RPathBfdSid indicates the the SRv6
         Return Path BFD SID.

         The SID can only be set if tRPOperPSDefActSrMaintPolicy is set."
    ::= { tRPOperPSDefActParamsExtEntry 53 }

tRPOperPSDActSrv6RPathBfdSidPar  OBJECT-TYPE
    SYNTAX      TPolicyVariableNameOrEmpty
    MAX-ACCESS  read-only
    STATUS      current
    DESCRIPTION
        "The value of tRPOperPSDActSrv6RPathBfdSidPar indicates the variable
         name that must be resolved to get the SRv6 Return Path BFD SID to set
         in route.

         The value of this object tRPOperPSDActSrv6RPathBfdSidPar is ignored
         when the object tRPOperPSDActSrv6RPathBfdSidSrc has a value different
         from actionParam(2)."
    ::= { tRPOperPSDefActParamsExtEntry 54 }

tRPOperPSDActSrReturnPathBfdLbl  OBJECT-TYPE
    SYNTAX      TPolicyValueOrVarNameOrEmpty
    MAX-ACCESS  read-only
    STATUS      current
    DESCRIPTION
        "The value of tRPOperPSDActSrReturnPathBfdLbl indicates the Return Path
         MPLS label for the BFD packet from the route matching this entry.

         The label can only be set if tRPOperPSDefActSrMaintPolicy is set.

         The value of this object can be a string containing the label value in
         the range [32..1048575] or a variable name TPolicyVariableName that
         needs to be resolved to get the label. An empty string means that it
         is disabled."
    ::= { tRPOperPSDefActParamsExtEntry 55 }

tRPOperPSDefActSrv6MSLocator     OBJECT-TYPE
    SYNTAX      TLNamedItemOrEmpty
    MAX-ACCESS  read-only
    STATUS      current
    DESCRIPTION
        "The value of tRPOperPSDefActSrv6MSLocator indicates the Segment
         Routing over IPv6 (SRv6) Micro Segment locator to advertise for the
         route matching this entry.

         The locator name must exist in  TIMETRA-SRV6:vRtrSrv6MSLocatorTable.

         The value of this object can be a string containing the
         locator or a variable name TPolicyVariableName that needs
         to be resolved to get the locator. An empty string
         means that it is disabled."
    ::= { tRPOperPSDefActParamsExtEntry 56 }

tRPOperPfxListNameTable          OBJECT-TYPE
    SYNTAX      SEQUENCE OF TRPOperPfxListNameEntry
    MAX-ACCESS  not-accessible
    STATUS      current
    DESCRIPTION
        "The table of operational prefix list names."
    ::= { tRPOperValueObjects 38 }

tRPOperPfxListNameEntry          OBJECT-TYPE
    SYNTAX      TRPOperPfxListNameEntry
    MAX-ACCESS  not-accessible
    STATUS      current
    DESCRIPTION
        "Each row entry in the tRPOperPfxListNameTable represents information
         about a particular prefix list name.

         Entries are created and deleted by the user via
         tRPAdminPfxListNameTable.

         In case the prefix list is empty, i.e. no referring object
         tRPOperInetPrefixListName exists in the tRPOperInetPrefixListTable,
         the prefix list will never match."
    INDEX       { tRPOperPfxListName }
    ::= { tRPOperPfxListNameTable 1 }

TRPOperPfxListNameEntry          ::= SEQUENCE
{
    tRPOperPfxListName               TLPrefixListName,
    tRPOperPfxListNameRowStatus      RowStatus,
    tRPOperPfxListNameCrOrigin       TmnxCreateOrigin
}

tRPOperPfxListName               OBJECT-TYPE
    SYNTAX      TLPrefixListName (SIZE (1..64))
    MAX-ACCESS  not-accessible
    STATUS      current
    DESCRIPTION
        "The value of tRPOperPfxListName indicates the name of the prefix list
         entry."
    ::= { tRPOperPfxListNameEntry 1 }

tRPOperPfxListNameRowStatus      OBJECT-TYPE
    SYNTAX      RowStatus
    MAX-ACCESS  read-only
    STATUS      current
    DESCRIPTION
        "RowStatus for this row.

         To create or destroy entries in this table, use the
         tRPAdminPfxListNameTable."
    ::= { tRPOperPfxListNameEntry 2 }

tRPOperPfxListNameCrOrigin       OBJECT-TYPE
    SYNTAX      TmnxCreateOrigin
    MAX-ACCESS  read-only
    STATUS      current
    DESCRIPTION
        "The value of the object tRPOperPfxListNameCrOrigin indicates the
         mechanism used to create this entry."
    ::= { tRPOperPfxListNameEntry 3 }

tRPOperPSCondExprTable           OBJECT-TYPE
    SYNTAX      SEQUENCE OF TRPOperPSCondExprEntry
    MAX-ACCESS  not-accessible
    STATUS      current
    DESCRIPTION
        "A table of conditional expressions for a policy statement."
    ::= { tRPOperValueObjects 39 }

tRPOperPSCondExprEntry           OBJECT-TYPE
    SYNTAX      TRPOperPSCondExprEntry
    MAX-ACCESS  not-accessible
    STATUS      current
    DESCRIPTION
        "Information about a particular conditional expression for a policy
         statement entry.

         The conditional expressions decides whether an entry should be
         evaluated. If the result of the conditional expression is 'TRUE' the
         entry is fully evaluated; if the result is 'FALSE' the entry is
         skipped and evaluations continues to the next entry or the default
         action is applied in case no next entry exists.

         Entries are created and deleted by creating and deleting entries in
         tRPAdminPSCondExprTable."
    INDEX       {
        tRPOperPolicyStatementName,
        tRPOperPSNameEntryIndex
    }
    ::= { tRPOperPSCondExprTable 1 }

TRPOperPSCondExprEntry           ::= SEQUENCE
{
    tRPOperPSCondExprRowStatus       RowStatus,
    tRPOperPSCondExprRtExistString1  TPrefixListNameExpression
}

tRPOperPSCondExprRowStatus       OBJECT-TYPE
    SYNTAX      RowStatus
    MAX-ACCESS  read-only
    STATUS      current
    DESCRIPTION
        "The value of object tRPOperPSCondExprRowStatus indicates the RowStatus
         for this row.

         To create or destroy entries in this table, use the
         tRPAdminPSCondExprTable."
    ::= { tRPOperPSCondExprEntry 1 }

tRPOperPSCondExprRtExistString1  OBJECT-TYPE
    SYNTAX      TPrefixListNameExpression
    MAX-ACCESS  read-only
    STATUS      current
    DESCRIPTION
        "The value of object tRPOperPSCondExprRtExistString1 indicates an
         expression that contains a prefix list name and is used to test the
         route existence.

         The expression tests for the presence or absence of routes in the IP
         routing table that matches any of the entries in the prefix list.

         When tRPOperPSCondExprRtExistString1 contains an empty string there is
         no route existence test and the expression is automatically considered
         'TRUE'."
    ::= { tRPOperPSCondExprEntry 2 }

tRPOperASPathGroupNameTable      OBJECT-TYPE
    SYNTAX      SEQUENCE OF TRPOperASPathGroupNameEntry
    MAX-ACCESS  not-accessible
    STATUS      current
    DESCRIPTION
        "The table of operational AS-Path Group names."
    ::= { tRPOperValueObjects 40 }

tRPOperASPathGroupNameEntry      OBJECT-TYPE
    SYNTAX      TRPOperASPathGroupNameEntry
    MAX-ACCESS  not-accessible
    STATUS      current
    DESCRIPTION
        "Each row entry in the tRPOperASPathGroupNameTable represents
         information about a particular AS-Path Group name.

         Entries are created and deleted by the user via
         tRPAdminASPathGroupNameTable.

         In case the AS-Path Group is empty, i.e. no referring object
         tRPOperASPathGroupName exists in the tRPOperASPathGroupTable, the
         AS-Path Group will never match."
    INDEX       { tRPOperASPGroupName }
    ::= { tRPOperASPathGroupNameTable 1 }

TRPOperASPathGroupNameEntry      ::= SEQUENCE
{
    tRPOperASPGroupName              TASPathGroupName,
    tRPOperASPGroupNameRowStatus     RowStatus,
    tRPOperASPGroupNameCrOrigin      TmnxCreateOrigin
}

tRPOperASPGroupName              OBJECT-TYPE
    SYNTAX      TASPathGroupName (SIZE (1..32))
    MAX-ACCESS  not-accessible
    STATUS      current
    DESCRIPTION
        "The value of tRPOperASPGroupName indicates the name of the AS-Path
         Group entry."
    ::= { tRPOperASPathGroupNameEntry 1 }

tRPOperASPGroupNameRowStatus     OBJECT-TYPE
    SYNTAX      RowStatus
    MAX-ACCESS  read-only
    STATUS      current
    DESCRIPTION
        "RowStatus for this row.

         To create or destroy entries in this table, use the
         tRPAdminASPathGroupNameTable."
    ::= { tRPOperASPathGroupNameEntry 2 }

tRPOperASPGroupNameCrOrigin      OBJECT-TYPE
    SYNTAX      TmnxCreateOrigin
    MAX-ACCESS  read-only
    STATUS      current
    DESCRIPTION
        "The value of the object tRPOperASPGroupNameCrOrigin indicates the
         mechanism used to create this entry."
    ::= { tRPOperASPathGroupNameEntry 3 }

tRPOperCommunityNameTable        OBJECT-TYPE
    SYNTAX      SEQUENCE OF TRPOperCommunityNameEntry
    MAX-ACCESS  not-accessible
    STATUS      current
    DESCRIPTION
        "The table of operational community names."
    ::= { tRPOperValueObjects 41 }

tRPOperCommunityNameEntry        OBJECT-TYPE
    SYNTAX      TRPOperCommunityNameEntry
    MAX-ACCESS  not-accessible
    STATUS      current
    DESCRIPTION
        "Each row entry in the tRPOperCommunityNameTable represents information
         about a particular community name.

         Entries are created and deleted by the user via
         tRPAdminCommunityNameTable.

         In case the community is empty, i.e. no referring object
         tRPOperCommunityName exists in the tRPOperCommunityTable, the
         community will never match."
    INDEX       { tRPOperCommName }
    ::= { tRPOperCommunityNameTable 1 }

TRPOperCommunityNameEntry        ::= SEQUENCE
{
    tRPOperCommName                  TLCommunityName,
    tRPOperCommNameRowStatus         RowStatus,
    tRPOperCommNameCrOrigin          TmnxCreateOrigin
}

tRPOperCommName                  OBJECT-TYPE
    SYNTAX      TLCommunityName (SIZE (1..64))
    MAX-ACCESS  not-accessible
    STATUS      current
    DESCRIPTION
        "The value of tRPOperCommName indicates the name of the community
         entry."
    ::= { tRPOperCommunityNameEntry 1 }

tRPOperCommNameRowStatus         OBJECT-TYPE
    SYNTAX      RowStatus
    MAX-ACCESS  read-only
    STATUS      current
    DESCRIPTION
        "RowStatus for this row.

         To create or destroy entries in this table, use the
         tRPAdminCommunityNameTable."
    ::= { tRPOperCommunityNameEntry 2 }

tRPOperCommNameCrOrigin          OBJECT-TYPE
    SYNTAX      TmnxCreateOrigin
    MAX-ACCESS  read-only
    STATUS      current
    DESCRIPTION
        "The value of the object tRPOperCommNameCrOrigin indicates the
         mechanism used to create this entry."
    ::= { tRPOperCommunityNameEntry 3 }

tRPOperGlobalVariableTable       OBJECT-TYPE
    SYNTAX      SEQUENCE OF TRPOperGlobalVariableEntry
    MAX-ACCESS  not-accessible
    STATUS      current
    DESCRIPTION
        "Information to resolve global variables used in policy."
    ::= { tRPOperValueObjects 42 }

tRPOperGlobalVariableEntry       OBJECT-TYPE
    SYNTAX      TRPOperGlobalVariableEntry
    MAX-ACCESS  not-accessible
    STATUS      current
    DESCRIPTION
        "This entry maps a global variable to a name which can be used in
         tRPOperPSFromCriteriaTable, tRPOperPSAcceptActionParamsTable,
         tRPOperPSDefaultActionParamsTable, tRPOperPSAcptActParamsExtTable or
         tRPOperPSDefActParamsExtTable entries.

         If a local variable with the same name exists in
         tRPOperPSPolicyVariableTable for the corresponding entry, the local
         variable is used to resolve the name."
    INDEX       { tRPOperGlobalVarName }
    ::= { tRPOperGlobalVariableTable 1 }

TRPOperGlobalVariableEntry       ::= SEQUENCE
{
    tRPOperGlobalVarName             TPolicyVariableName,
    tRPOperGlobalVarRowStatus        RowStatus,
    tRPOperGlobalVarType             TPolicyVariableType,
    tRPOperGlobalVarString           TNamedItemOrEmpty,
    tRPOperGlobalVarNumber           Unsigned32,
    tRPOperGlobalVarAddressType      InetAddressType,
    tRPOperGlobalVarAddress          InetAddress,
    tRPOperGlobalVarDecimal          TPolicyDecimal,
    tRPOperGlobalVarPrefixLength     InetAddressPrefixLength
}

tRPOperGlobalVarName             OBJECT-TYPE
    SYNTAX      TPolicyVariableName
    MAX-ACCESS  not-accessible
    STATUS      current
    DESCRIPTION
        "The value of tRPOperGlobalVarName specifies a variable name that can
         be used in the tRPOperPSFromCriteriaTable,
         tRPOperPSAcceptActionParamsTable, tRPOperPSDefaultActionParamsTable,
         tRPOperPSAcptActParamsExtTable or tRPOperPSDefActParamsExtTable."
    ::= { tRPOperGlobalVariableEntry 1 }

tRPOperGlobalVarRowStatus        OBJECT-TYPE
    SYNTAX      RowStatus
    MAX-ACCESS  read-only
    STATUS      current
    DESCRIPTION
        "The value of tRPOperGlobalVarRowStatus specifies the RowStatus for
         this row."
    ::= { tRPOperGlobalVariableEntry 2 }

tRPOperGlobalVarType             OBJECT-TYPE
    SYNTAX      TPolicyVariableType
    MAX-ACCESS  read-only
    STATUS      current
    DESCRIPTION
        "The value of tRPOperGlobalVarType specifies how to resolve the
         tRPOperGlobalVarName.

         string(1)  - indicates that tRPOperGlobalVarString is to be used
         integer(2) - indicates that tRPOperGlobalVarNumber is to be used
         address(3) - indicates that tRPOperGlobalVarAddressType and
                      tRPOperGlobalVarAddress are to be used
         decimal(4) - indicates that tRPOperGlobalVarDecimal is to be used
         prefix (5) - indicates that tRPOperGlobalVarAddressType,
                      tRPOperGlobalVarAddress and tRPOperGlobalVarPrefixLength
                      are to be used"
    ::= { tRPOperGlobalVariableEntry 3 }

tRPOperGlobalVarString           OBJECT-TYPE
    SYNTAX      TNamedItemOrEmpty
    MAX-ACCESS  read-only
    STATUS      current
    DESCRIPTION
        "The value of tRPOperGlobalVarString specifies e.g. the actual as-path
         name to which tRPOperGlobalVarName is resolved.

         This object tRPOperGlobalVarString is ignored when the object
         tRPOperGlobalVarType has a value different then string(1)."
    ::= { tRPOperGlobalVariableEntry 4 }

tRPOperGlobalVarNumber           OBJECT-TYPE
    SYNTAX      Unsigned32
    MAX-ACCESS  read-only
    STATUS      current
    DESCRIPTION
        "The value of tRPOperGlobalVarNumber specifies e.g. the actual metric
         value to which tRPOperGlobalVarName is resolved.

         This object tRPOperGlobalVarNumber is ignored when the object
         tRPOperGlobalVarType has a value different then integer(2)."
    ::= { tRPOperGlobalVariableEntry 5 }

tRPOperGlobalVarAddressType      OBJECT-TYPE
    SYNTAX      InetAddressType
    MAX-ACCESS  read-only
    STATUS      current
    DESCRIPTION
        "The value of tRPOperGlobalVarAddressType specifies the actual IP
         address type of the tRPOperGlobalVarAddress to which
         tRPOperGlobalVarName is resolved.

         This object tRPOperGlobalVarAddressType is ignored when the object
         tRPOperGlobalVarType has a value different from address(3) or prefix
         (5)."
    ::= { tRPOperGlobalVariableEntry 6 }

tRPOperGlobalVarAddress          OBJECT-TYPE
    SYNTAX      InetAddress (SIZE (0|4|16|20))
    MAX-ACCESS  read-only
    STATUS      current
    DESCRIPTION
        "The value of tRPOperGlobalVarAddress indicates e.g. the actual
         next-hop address to which tRPOperGlobalVarName is resolved.

         This object tRPOperGlobalVarAddress is ignored when the object
         tRPOperGlobalVarType has a value different from address(3) or prefix
         (5)."
    ::= { tRPOperGlobalVariableEntry 7 }

tRPOperGlobalVarDecimal          OBJECT-TYPE
    SYNTAX      TPolicyDecimal
    MAX-ACCESS  read-only
    STATUS      current
    DESCRIPTION
        "The value of tRPOperGlobalVarDecimal indicates the actual decimal
         value to which tRPOperGlobalVarName is resolved.

         This object tRPOperGlobalVarDecimal is ignored when the object
         tRPOperGlobalVarType has a value different then decimal(4)."
    ::= { tRPOperGlobalVariableEntry 8 }

tRPOperGlobalVarPrefixLength     OBJECT-TYPE
    SYNTAX      InetAddressPrefixLength (0..128)
    MAX-ACCESS  read-only
    STATUS      current
    DESCRIPTION
        "The value of tRPOperGlobalVarPrefixLength indicates the prefix length
         of the prefix to which tRPOperGlobalVarName is resolved.

         This object tRPOperGlobalVarPrefixLength is ignored when the object
         tRPOperGlobalVarType has a value different from prefix (5)."
    ::= { tRPOperGlobalVariableEntry 9 }

tRPOperPSToCritPfxListTable      OBJECT-TYPE
    SYNTAX      SEQUENCE OF TRPOperPSToCritPfxListEntry
    MAX-ACCESS  not-accessible
    STATUS      current
    DESCRIPTION
        "A table of prefix list names to match on as 'to' criteria for each
         policy statement entry."
    ::= { tRPOperValueObjects 43 }

tRPOperPSToCritPfxListEntry      OBJECT-TYPE
    SYNTAX      TRPOperPSToCritPfxListEntry
    MAX-ACCESS  not-accessible
    STATUS      current
    DESCRIPTION
        "Information about policy statement entry to prefix list criteria..

         Entries are created or deleted when an entry in
         tRPOperPSToCriteriaTable is created or deleted."
    AUGMENTS    { tRPOperPSToCriteriaEntry }
    ::= { tRPOperPSToCritPfxListTable 1 }

TRPOperPSToCritPfxListEntry      ::= SEQUENCE
{
    tRPOperPSToCritPrefixList1       TLPrefixListName,
    tRPOperPSToCritPrefixList2       TLPrefixListName,
    tRPOperPSToCritPrefixList3       TLPrefixListName,
    tRPOperPSToCritPrefixList4       TLPrefixListName,
    tRPOperPSToCritPrefixList5       TLPrefixListName,
    tRPOperPSToCritPrefixList6       TLPrefixListName,
    tRPOperPSToCritPrefixList7       TLPrefixListName,
    tRPOperPSToCritPrefixList8       TLPrefixListName,
    tRPOperPSToCritPrefixList9       TLPrefixListName,
    tRPOperPSToCritPrefixList10      TLPrefixListName,
    tRPOperPSToCritPrefixList11      TLPrefixListName,
    tRPOperPSToCritPrefixList12      TLPrefixListName,
    tRPOperPSToCritPrefixList13      TLPrefixListName,
    tRPOperPSToCritPrefixList14      TLPrefixListName,
    tRPOperPSToCritPrefixList15      TLPrefixListName,
    tRPOperPSToCritPrefixList16      TLPrefixListName,
    tRPOperPSToCritPrefixList17      TLPrefixListName,
    tRPOperPSToCritPrefixList18      TLPrefixListName,
    tRPOperPSToCritPrefixList19      TLPrefixListName,
    tRPOperPSToCritPrefixList20      TLPrefixListName,
    tRPOperPSToCritPrefixList21      TLPrefixListName,
    tRPOperPSToCritPrefixList22      TLPrefixListName,
    tRPOperPSToCritPrefixList23      TLPrefixListName,
    tRPOperPSToCritPrefixList24      TLPrefixListName,
    tRPOperPSToCritPrefixList25      TLPrefixListName,
    tRPOperPSToCritPrefixList26      TLPrefixListName,
    tRPOperPSToCritPrefixList27      TLPrefixListName,
    tRPOperPSToCritPrefixList28      TLPrefixListName
}

tRPOperPSToCritPrefixList1       OBJECT-TYPE
    SYNTAX      TLPrefixListName
    MAX-ACCESS  read-only
    STATUS      current
    DESCRIPTION
        "The value of tRPOperPSToCritPrefixList1 indicates the name of the
         first prefix list to match on. Setting this value to an empty string
         disables this prefix list as a match criteria."
    ::= { tRPOperPSToCritPfxListEntry 1 }

tRPOperPSToCritPrefixList2       OBJECT-TYPE
    SYNTAX      TLPrefixListName
    MAX-ACCESS  read-only
    STATUS      current
    DESCRIPTION
        "The value of tRPOperPSToCritPrefixList2 indicates the name of the
         second prefix list to match on. Setting this value to an empty string
         disables this prefix list as a match criteria."
    ::= { tRPOperPSToCritPfxListEntry 2 }

tRPOperPSToCritPrefixList3       OBJECT-TYPE
    SYNTAX      TLPrefixListName
    MAX-ACCESS  read-only
    STATUS      current
    DESCRIPTION
        "The value of tRPOperPSToCritPrefixList3 indicates the name of the
         third prefix list to match on. Setting this value to an empty string
         disables this prefix list as a match criteria."
    ::= { tRPOperPSToCritPfxListEntry 3 }

tRPOperPSToCritPrefixList4       OBJECT-TYPE
    SYNTAX      TLPrefixListName
    MAX-ACCESS  read-only
    STATUS      current
    DESCRIPTION
        "The value of tRPOperPSToCritPrefixList4 indicates the name of the
         fourth prefix list to match on. Setting this value to an empty string
         disables this prefix list as a match criteria."
    ::= { tRPOperPSToCritPfxListEntry 4 }

tRPOperPSToCritPrefixList5       OBJECT-TYPE
    SYNTAX      TLPrefixListName
    MAX-ACCESS  read-only
    STATUS      current
    DESCRIPTION
        "The value of tRPOperPSToCritPrefixList5 indicates the name of the
         fifth prefix list to match on. Setting this value to an empty string
         disables this prefix list as a match criteria."
    ::= { tRPOperPSToCritPfxListEntry 5 }

tRPOperPSToCritPrefixList6       OBJECT-TYPE
    SYNTAX      TLPrefixListName
    MAX-ACCESS  read-only
    STATUS      current
    DESCRIPTION
        "The value of tRPOperPSToCritPrefixList6 indicates the name of the
         sixth prefix list to match on. Setting this value to an empty string
         disables this prefix list as a match criteria."
    ::= { tRPOperPSToCritPfxListEntry 6 }

tRPOperPSToCritPrefixList7       OBJECT-TYPE
    SYNTAX      TLPrefixListName
    MAX-ACCESS  read-only
    STATUS      current
    DESCRIPTION
        "The value of tRPOperPSToCritPrefixList7 indicates the name of the
         seventh prefix list to match on. Setting this value to an empty string
         disables this prefix list as a match criteria."
    ::= { tRPOperPSToCritPfxListEntry 7 }

tRPOperPSToCritPrefixList8       OBJECT-TYPE
    SYNTAX      TLPrefixListName
    MAX-ACCESS  read-only
    STATUS      current
    DESCRIPTION
        "The value of tRPOperPSToCritPrefixList8 indicates the name of the
         eight prefix list to match on. Setting this value to an empty string
         disables this prefix list as a match criteria."
    ::= { tRPOperPSToCritPfxListEntry 8 }

tRPOperPSToCritPrefixList9       OBJECT-TYPE
    SYNTAX      TLPrefixListName
    MAX-ACCESS  read-only
    STATUS      current
    DESCRIPTION
        "The value of tRPOperPSToCritPrefixList9 indicates the name of the
         ninth prefix list to match on. Setting this value to an empty string
         disables this prefix list as a match criteria."
    ::= { tRPOperPSToCritPfxListEntry 9 }

tRPOperPSToCritPrefixList10      OBJECT-TYPE
    SYNTAX      TLPrefixListName
    MAX-ACCESS  read-only
    STATUS      current
    DESCRIPTION
        "The value of tRPOperPSToCritPrefixList10 indicates the name of the
         10th prefix list to match on. Setting this value to an empty string
         disables this prefix list as a match criteria."
    ::= { tRPOperPSToCritPfxListEntry 10 }

tRPOperPSToCritPrefixList11      OBJECT-TYPE
    SYNTAX      TLPrefixListName
    MAX-ACCESS  read-only
    STATUS      current
    DESCRIPTION
        "The value of tRPOperPSToCritPrefixList11 indicates the name of the
         11th prefix list to match on. Setting this value to an empty string
         disables this prefix list as a match criteria."
    ::= { tRPOperPSToCritPfxListEntry 11 }

tRPOperPSToCritPrefixList12      OBJECT-TYPE
    SYNTAX      TLPrefixListName
    MAX-ACCESS  read-only
    STATUS      current
    DESCRIPTION
        "The value of tRPOperPSToCritPrefixList12 indicates the name of the
         12th prefix list to match on. Setting this value to an empty string
         disables this prefix list as a match criteria."
    ::= { tRPOperPSToCritPfxListEntry 12 }

tRPOperPSToCritPrefixList13      OBJECT-TYPE
    SYNTAX      TLPrefixListName
    MAX-ACCESS  read-only
    STATUS      current
    DESCRIPTION
        "The value of tRPOperPSToCritPrefixList13 indicates the name of the
         13th prefix list to match on. Setting this value to an empty string
         disables this prefix list as a match criteria."
    ::= { tRPOperPSToCritPfxListEntry 13 }

tRPOperPSToCritPrefixList14      OBJECT-TYPE
    SYNTAX      TLPrefixListName
    MAX-ACCESS  read-only
    STATUS      current
    DESCRIPTION
        "The value of tRPOperPSToCritPrefixList14 indicates the name of the
         14th prefix list to match on. Setting this value to an empty string
         disables this prefix list as a match criteria."
    ::= { tRPOperPSToCritPfxListEntry 14 }

tRPOperPSToCritPrefixList15      OBJECT-TYPE
    SYNTAX      TLPrefixListName
    MAX-ACCESS  read-only
    STATUS      current
    DESCRIPTION
        "The value of tRPOperPSToCritPrefixList15 indicates the name of the
         15th prefix list to match on. Setting this value to an empty string
         disables this prefix list as a match criteria."
    ::= { tRPOperPSToCritPfxListEntry 15 }

tRPOperPSToCritPrefixList16      OBJECT-TYPE
    SYNTAX      TLPrefixListName
    MAX-ACCESS  read-only
    STATUS      current
    DESCRIPTION
        "The value of tRPOperPSToCritPrefixList16 indicates the name of the
         16th prefix list to match on. Setting this value to an empty string
         disables this prefix list as a match criteria."
    ::= { tRPOperPSToCritPfxListEntry 16 }

tRPOperPSToCritPrefixList17      OBJECT-TYPE
    SYNTAX      TLPrefixListName
    MAX-ACCESS  read-only
    STATUS      current
    DESCRIPTION
        "The value of tRPOperPSToCritPrefixList17 indicates the name of the
         17th prefix list to match on. Setting this value to an empty string
         disables this prefix list as a match criteria."
    ::= { tRPOperPSToCritPfxListEntry 17 }

tRPOperPSToCritPrefixList18      OBJECT-TYPE
    SYNTAX      TLPrefixListName
    MAX-ACCESS  read-only
    STATUS      current
    DESCRIPTION
        "The value of tRPOperPSToCritPrefixList18 indicates the name of the
         18th prefix list to match on. Setting this value to an empty string
         disables this prefix list as a match criteria."
    ::= { tRPOperPSToCritPfxListEntry 18 }

tRPOperPSToCritPrefixList19      OBJECT-TYPE
    SYNTAX      TLPrefixListName
    MAX-ACCESS  read-only
    STATUS      current
    DESCRIPTION
        "The value of tRPOperPSToCritPrefixList19 indicates the name of the
         19th prefix list to match on. Setting this value to an empty string
         disables this prefix list as a match criteria."
    ::= { tRPOperPSToCritPfxListEntry 19 }

tRPOperPSToCritPrefixList20      OBJECT-TYPE
    SYNTAX      TLPrefixListName
    MAX-ACCESS  read-only
    STATUS      current
    DESCRIPTION
        "The value of tRPOperPSToCritPrefixList20 indicates the name of the
         20th prefix list to match on. Setting this value to an empty string
         disables this prefix list as a match criteria."
    ::= { tRPOperPSToCritPfxListEntry 20 }

tRPOperPSToCritPrefixList21      OBJECT-TYPE
    SYNTAX      TLPrefixListName
    MAX-ACCESS  read-only
    STATUS      current
    DESCRIPTION
        "The value of tRPOperPSToCritPrefixList21 indicates the name of the
         21th prefix list to match on. Setting this value to an empty string
         disables this prefix list as a match criteria."
    ::= { tRPOperPSToCritPfxListEntry 21 }

tRPOperPSToCritPrefixList22      OBJECT-TYPE
    SYNTAX      TLPrefixListName
    MAX-ACCESS  read-only
    STATUS      current
    DESCRIPTION
        "The value of tRPOperPSToCritPrefixList22 indicates the name of the
         22th prefix list to match on. Setting this value to an empty string
         disables this prefix list as a match criteria."
    ::= { tRPOperPSToCritPfxListEntry 22 }

tRPOperPSToCritPrefixList23      OBJECT-TYPE
    SYNTAX      TLPrefixListName
    MAX-ACCESS  read-only
    STATUS      current
    DESCRIPTION
        "The value of tRPOperPSToCritPrefixList23 indicates the name of the
         23th prefix list to match on. Setting this value to an empty string
         disables this prefix list as a match criteria."
    ::= { tRPOperPSToCritPfxListEntry 23 }

tRPOperPSToCritPrefixList24      OBJECT-TYPE
    SYNTAX      TLPrefixListName
    MAX-ACCESS  read-only
    STATUS      current
    DESCRIPTION
        "The value of tRPOperPSToCritPrefixList24 indicates the name of the
         24th prefix list to match on. Setting this value to an empty string
         disables this prefix list as a match criteria."
    ::= { tRPOperPSToCritPfxListEntry 24 }

tRPOperPSToCritPrefixList25      OBJECT-TYPE
    SYNTAX      TLPrefixListName
    MAX-ACCESS  read-only
    STATUS      current
    DESCRIPTION
        "The value of tRPOperPSToCritPrefixList25 indicates the name of the
         25th prefix list to match on. Setting this value to an empty string
         disables this prefix list as a match criteria."
    ::= { tRPOperPSToCritPfxListEntry 25 }

tRPOperPSToCritPrefixList26      OBJECT-TYPE
    SYNTAX      TLPrefixListName
    MAX-ACCESS  read-only
    STATUS      current
    DESCRIPTION
        "The value of tRPOperPSToCritPrefixList26 indicates the name of the
         26th prefix list to match on. Setting this value to an empty string
         disables this prefix list as a match criteria."
    ::= { tRPOperPSToCritPfxListEntry 26 }

tRPOperPSToCritPrefixList27      OBJECT-TYPE
    SYNTAX      TLPrefixListName
    MAX-ACCESS  read-only
    STATUS      current
    DESCRIPTION
        "The value of tRPOperPSToCritPrefixList27 indicates the name of the
         27th prefix list to match on. Setting this value to an empty string
         disables this prefix list as a match criteria."
    ::= { tRPOperPSToCritPfxListEntry 27 }

tRPOperPSToCritPrefixList28      OBJECT-TYPE
    SYNTAX      TLPrefixListName
    MAX-ACCESS  read-only
    STATUS      current
    DESCRIPTION
        "The value of tRPOperPSToCritPrefixList28 indicates the name of the
         28th prefix list to match on. Setting this value to an empty string
         disables this prefix list as a match criteria."
    ::= { tRPOperPSToCritPfxListEntry 28 }

tRPOperPSFromCritPfxListTable    OBJECT-TYPE
    SYNTAX      SEQUENCE OF TRPOperPSFromCritPfxListEntry
    MAX-ACCESS  not-accessible
    STATUS      current
    DESCRIPTION
        "A table of prefix list names to match on as 'from' criteria for each
         policy statement entry"
    ::= { tRPOperValueObjects 44 }

tRPOperPSFromCritPfxListEntry    OBJECT-TYPE
    SYNTAX      TRPOperPSFromCritPfxListEntry
    MAX-ACCESS  not-accessible
    STATUS      current
    DESCRIPTION
        "Information about policy statement entry from prefix list criteria.

         Entries are created or deleted when an entry in
         tRPOperPSFromCriteriaTable is created or deleted."
    AUGMENTS    { tRPOperPSFromCriteriaEntry }
    ::= { tRPOperPSFromCritPfxListTable 1 }

TRPOperPSFromCritPfxListEntry    ::= SEQUENCE
{
    tRPOperPSFromCritPrefixList1     TLPrefixListName,
    tRPOperPSFromCritPrefixList2     TLPrefixListName,
    tRPOperPSFromCritPrefixList3     TLPrefixListName,
    tRPOperPSFromCritPrefixList4     TLPrefixListName,
    tRPOperPSFromCritPrefixList5     TLPrefixListName,
    tRPOperPSFromCritPrefixList6     TLPrefixListName,
    tRPOperPSFromCritPrefixList7     TLPrefixListName,
    tRPOperPSFromCritPrefixList8     TLPrefixListName,
    tRPOperPSFromCritPrefixList9     TLPrefixListName,
    tRPOperPSFromCritPrefixList10    TLPrefixListName,
    tRPOperPSFromCritPrefixList11    TLPrefixListName,
    tRPOperPSFromCritPrefixList12    TLPrefixListName,
    tRPOperPSFromCritPrefixList13    TLPrefixListName,
    tRPOperPSFromCritPrefixList14    TLPrefixListName,
    tRPOperPSFromCritPrefixList15    TLPrefixListName,
    tRPOperPSFromCritPrefixList16    TLPrefixListName,
    tRPOperPSFromCritPrefixList17    TLPrefixListName,
    tRPOperPSFromCritPrefixList18    TLPrefixListName,
    tRPOperPSFromCritPrefixList19    TLPrefixListName,
    tRPOperPSFromCritPrefixList20    TLPrefixListName,
    tRPOperPSFromCritPrefixList21    TLPrefixListName,
    tRPOperPSFromCritPrefixList22    TLPrefixListName,
    tRPOperPSFromCritPrefixList23    TLPrefixListName,
    tRPOperPSFromCritPrefixList24    TLPrefixListName,
    tRPOperPSFromCritPrefixList25    TLPrefixListName,
    tRPOperPSFromCritPrefixList26    TLPrefixListName,
    tRPOperPSFromCritPrefixList27    TLPrefixListName,
    tRPOperPSFromCritPrefixList28    TLPrefixListName
}

tRPOperPSFromCritPrefixList1     OBJECT-TYPE
    SYNTAX      TLPrefixListName
    MAX-ACCESS  read-only
    STATUS      current
    DESCRIPTION
        "The value of tRPOperPSFromCritPrefixList1 indicates the name of the
         first prefix list to match on. Setting this value to an empty string
         disables this prefix list as a match criteria."
    ::= { tRPOperPSFromCritPfxListEntry 1 }

tRPOperPSFromCritPrefixList2     OBJECT-TYPE
    SYNTAX      TLPrefixListName
    MAX-ACCESS  read-only
    STATUS      current
    DESCRIPTION
        "The value of tRPOperPSFromCritPrefixList2 indicates the name of the
         second prefix list to match on. Setting this value to an empty string
         disables this prefix list as a match criteria."
    ::= { tRPOperPSFromCritPfxListEntry 2 }

tRPOperPSFromCritPrefixList3     OBJECT-TYPE
    SYNTAX      TLPrefixListName
    MAX-ACCESS  read-only
    STATUS      current
    DESCRIPTION
        "The value of tRPOperPSFromCritPrefixList3 indicates the name of the
         third prefix list to match on. Setting this value to an empty string
         disables this prefix list as a match criteria."
    ::= { tRPOperPSFromCritPfxListEntry 3 }

tRPOperPSFromCritPrefixList4     OBJECT-TYPE
    SYNTAX      TLPrefixListName
    MAX-ACCESS  read-only
    STATUS      current
    DESCRIPTION
        "The value of tRPOperPSFromCritPrefixList4 indicates the name of the
         fourth prefix list to match on. Setting this value to an empty string
         disables this prefix list as a match criteria."
    ::= { tRPOperPSFromCritPfxListEntry 4 }

tRPOperPSFromCritPrefixList5     OBJECT-TYPE
    SYNTAX      TLPrefixListName
    MAX-ACCESS  read-only
    STATUS      current
    DESCRIPTION
        "The value of tRPOperPSFromCritPrefixList5 indicates the name of the
         fifth prefix list to match on. Setting this value to an empty string
         disables this prefix list as a match criteria."
    ::= { tRPOperPSFromCritPfxListEntry 5 }

tRPOperPSFromCritPrefixList6     OBJECT-TYPE
    SYNTAX      TLPrefixListName
    MAX-ACCESS  read-only
    STATUS      current
    DESCRIPTION
        "The value of tRPOperPSFromCritPrefixList6 indicates the name of the
         sixth prefix list to match on. Setting this value to an empty string
         disables this prefix list as a match criteria."
    ::= { tRPOperPSFromCritPfxListEntry 6 }

tRPOperPSFromCritPrefixList7     OBJECT-TYPE
    SYNTAX      TLPrefixListName
    MAX-ACCESS  read-only
    STATUS      current
    DESCRIPTION
        "The value of tRPOperPSFromCritPrefixList7 indicates the name of the
         seventh prefix list to match on. Setting this value to an empty string
         disables this prefix list as a match criteria."
    ::= { tRPOperPSFromCritPfxListEntry 7 }

tRPOperPSFromCritPrefixList8     OBJECT-TYPE
    SYNTAX      TLPrefixListName
    MAX-ACCESS  read-only
    STATUS      current
    DESCRIPTION
        "The value of tRPOperPSFromCritPrefixList8 indicates the name of the
         eight prefix list to match on. Setting this value to an empty string
         disables this prefix list as a match criteria."
    ::= { tRPOperPSFromCritPfxListEntry 8 }

tRPOperPSFromCritPrefixList9     OBJECT-TYPE
    SYNTAX      TLPrefixListName
    MAX-ACCESS  read-only
    STATUS      current
    DESCRIPTION
        "The value of tRPOperPSFromCritPrefixList9 indicates the name of the
         ninth prefix list to match on. Setting this value to an empty string
         disables this prefix list as a match criteria."
    ::= { tRPOperPSFromCritPfxListEntry 9 }

tRPOperPSFromCritPrefixList10    OBJECT-TYPE
    SYNTAX      TLPrefixListName
    MAX-ACCESS  read-only
    STATUS      current
    DESCRIPTION
        "The value of tRPOperPSFromCritPrefixList10 indicates the name of the
         10th prefix list to match on. Setting this value to an empty string
         disables this prefix list as a match criteria."
    ::= { tRPOperPSFromCritPfxListEntry 10 }

tRPOperPSFromCritPrefixList11    OBJECT-TYPE
    SYNTAX      TLPrefixListName
    MAX-ACCESS  read-only
    STATUS      current
    DESCRIPTION
        "The value of tRPOperPSFromCritPrefixList11 indicates the name of the
         11th prefix list to match on. Setting this value to an empty string
         disables this prefix list as a match criteria."
    ::= { tRPOperPSFromCritPfxListEntry 11 }

tRPOperPSFromCritPrefixList12    OBJECT-TYPE
    SYNTAX      TLPrefixListName
    MAX-ACCESS  read-only
    STATUS      current
    DESCRIPTION
        "The value of tRPOperPSFromCritPrefixList12 indicates the name of the
         12th prefix list to match on. Setting this value to an empty string
         disables this prefix list as a match criteria."
    ::= { tRPOperPSFromCritPfxListEntry 12 }

tRPOperPSFromCritPrefixList13    OBJECT-TYPE
    SYNTAX      TLPrefixListName
    MAX-ACCESS  read-only
    STATUS      current
    DESCRIPTION
        "The value of tRPOperPSFromCritPrefixList13 indicates the name of the
         13th prefix list to match on. Setting this value to an empty string
         disables this prefix list as a match criteria."
    ::= { tRPOperPSFromCritPfxListEntry 13 }

tRPOperPSFromCritPrefixList14    OBJECT-TYPE
    SYNTAX      TLPrefixListName
    MAX-ACCESS  read-only
    STATUS      current
    DESCRIPTION
        "The value of tRPOperPSFromCritPrefixList14 indicates the name of the
         14th prefix list to match on. Setting this value to an empty string
         disables this prefix list as a match criteria."
    ::= { tRPOperPSFromCritPfxListEntry 14 }

tRPOperPSFromCritPrefixList15    OBJECT-TYPE
    SYNTAX      TLPrefixListName
    MAX-ACCESS  read-only
    STATUS      current
    DESCRIPTION
        "The value of tRPOperPSFromCritPrefixList15 indicates the name of the
         15th prefix list to match on. Setting this value to an empty string
         disables this prefix list as a match criteria."
    ::= { tRPOperPSFromCritPfxListEntry 15 }

tRPOperPSFromCritPrefixList16    OBJECT-TYPE
    SYNTAX      TLPrefixListName
    MAX-ACCESS  read-only
    STATUS      current
    DESCRIPTION
        "The value of tRPOperPSFromCritPrefixList16 indicates the name of the
         16th prefix list to match on. Setting this value to an empty string
         disables this prefix list as a match criteria."
    ::= { tRPOperPSFromCritPfxListEntry 16 }

tRPOperPSFromCritPrefixList17    OBJECT-TYPE
    SYNTAX      TLPrefixListName
    MAX-ACCESS  read-only
    STATUS      current
    DESCRIPTION
        "The value of tRPOperPSFromCritPrefixList17 indicates the name of the
         17th prefix list to match on. Setting this value to an empty string
         disables this prefix list as a match criteria."
    ::= { tRPOperPSFromCritPfxListEntry 17 }

tRPOperPSFromCritPrefixList18    OBJECT-TYPE
    SYNTAX      TLPrefixListName
    MAX-ACCESS  read-only
    STATUS      current
    DESCRIPTION
        "The value of tRPOperPSFromCritPrefixList18 indicates the name of the
         18th prefix list to match on. Setting this value to an empty string
         disables this prefix list as a match criteria."
    ::= { tRPOperPSFromCritPfxListEntry 18 }

tRPOperPSFromCritPrefixList19    OBJECT-TYPE
    SYNTAX      TLPrefixListName
    MAX-ACCESS  read-only
    STATUS      current
    DESCRIPTION
        "The value of tRPOperPSFromCritPrefixList19 indicates the name of the
         19th prefix list to match on. Setting this value to an empty string
         disables this prefix list as a match criteria."
    ::= { tRPOperPSFromCritPfxListEntry 19 }

tRPOperPSFromCritPrefixList20    OBJECT-TYPE
    SYNTAX      TLPrefixListName
    MAX-ACCESS  read-only
    STATUS      current
    DESCRIPTION
        "The value of tRPOperPSFromCritPrefixList20 indicates the name of the
         20th prefix list to match on. Setting this value to an empty string
         disables this prefix list as a match criteria."
    ::= { tRPOperPSFromCritPfxListEntry 20 }

tRPOperPSFromCritPrefixList21    OBJECT-TYPE
    SYNTAX      TLPrefixListName
    MAX-ACCESS  read-only
    STATUS      current
    DESCRIPTION
        "The value of tRPOperPSFromCritPrefixList21 indicates the name of the
         21th prefix list to match on. Setting this value to an empty string
         disables this prefix list as a match criteria."
    ::= { tRPOperPSFromCritPfxListEntry 21 }

tRPOperPSFromCritPrefixList22    OBJECT-TYPE
    SYNTAX      TLPrefixListName
    MAX-ACCESS  read-only
    STATUS      current
    DESCRIPTION
        "The value of tRPOperPSFromCritPrefixList22 indicates the name of the
         22th prefix list to match on. Setting this value to an empty string
         disables this prefix list as a match criteria."
    ::= { tRPOperPSFromCritPfxListEntry 22 }

tRPOperPSFromCritPrefixList23    OBJECT-TYPE
    SYNTAX      TLPrefixListName
    MAX-ACCESS  read-only
    STATUS      current
    DESCRIPTION
        "The value of tRPOperPSFromCritPrefixList23 indicates the name of the
         23th prefix list to match on. Setting this value to an empty string
         disables this prefix list as a match criteria."
    ::= { tRPOperPSFromCritPfxListEntry 23 }

tRPOperPSFromCritPrefixList24    OBJECT-TYPE
    SYNTAX      TLPrefixListName
    MAX-ACCESS  read-only
    STATUS      current
    DESCRIPTION
        "The value of tRPOperPSFromCritPrefixList24 indicates the name of the
         24th prefix list to match on. Setting this value to an empty string
         disables this prefix list as a match criteria."
    ::= { tRPOperPSFromCritPfxListEntry 24 }

tRPOperPSFromCritPrefixList25    OBJECT-TYPE
    SYNTAX      TLPrefixListName
    MAX-ACCESS  read-only
    STATUS      current
    DESCRIPTION
        "The value of tRPOperPSFromCritPrefixList25 indicates the name of the
         25th prefix list to match on. Setting this value to an empty string
         disables this prefix list as a match criteria."
    ::= { tRPOperPSFromCritPfxListEntry 25 }

tRPOperPSFromCritPrefixList26    OBJECT-TYPE
    SYNTAX      TLPrefixListName
    MAX-ACCESS  read-only
    STATUS      current
    DESCRIPTION
        "The value of tRPOperPSFromCritPrefixList26 indicates the name of the
         26th prefix list to match on. Setting this value to an empty string
         disables this prefix list as a match criteria."
    ::= { tRPOperPSFromCritPfxListEntry 26 }

tRPOperPSFromCritPrefixList27    OBJECT-TYPE
    SYNTAX      TLPrefixListName
    MAX-ACCESS  read-only
    STATUS      current
    DESCRIPTION
        "The value of tRPOperPSFromCritPrefixList27 indicates the name of the
         27th prefix list to match on. Setting this value to an empty string
         disables this prefix list as a match criteria."
    ::= { tRPOperPSFromCritPfxListEntry 27 }

tRPOperPSFromCritPrefixList28    OBJECT-TYPE
    SYNTAX      TLPrefixListName
    MAX-ACCESS  read-only
    STATUS      current
    DESCRIPTION
        "The value of tRPOperPSFromCritPrefixList28 indicates the name of the
         28th prefix list to match on. Setting this value to an empty string
         disables this prefix list as a match criteria."
    ::= { tRPOperPSFromCritPfxListEntry 28 }

tRPOperPfxListToTable            OBJECT-TYPE
    SYNTAX      SEQUENCE OF TRPOperPfxListToEntry
    MAX-ACCESS  not-accessible
    STATUS      current
    DESCRIPTION
        "The table of IPv4 and IPv6 admin prefix lists specifying a match
         condition from a start prefix/length to an end prefix/length."
    ::= { tRPOperValueObjects 45 }

tRPOperPfxListToEntry            OBJECT-TYPE
    SYNTAX      TRPOperPfxListToEntry
    MAX-ACCESS  not-accessible
    STATUS      current
    DESCRIPTION
        "Each row entry in the tRPOperPfxListToEntry represents information
         about a particular prefix list to prefix.

         A route's prefix/length is considered a match if all of the
         following are true:
         - the start prefix-length most-significant bits of the route
           matches the start prefix
         - the end prefix-length most-significant bits of the route
           matches the end prefix
         - the prefix-length of the route is between start prefix-length and
           end prefix-length (inclusive).

         Entries are created and deleted by the user via
         tRPAdminPfxListToTable."
    INDEX       {
        tRPOperPfxListName,
        tRPOperInetPrefixListPrefixType,
        tRPOperInetPrefixListPrefix,
        tRPOperInetPrefixListPrefixLen,
        tRPOperPfxListToEndPrefixType,
        tRPOperPfxListToEndPrefix,
        tRPOperPfxListToEndPrefixLen
    }
    ::= { tRPOperPfxListToTable 1 }

TRPOperPfxListToEntry            ::= SEQUENCE
{
    tRPOperPfxListToEndPrefixType    TmnxAddressAndPrefixType,
    tRPOperPfxListToEndPrefix        TmnxAddressAndPrefixAddress,
    tRPOperPfxListToEndPrefixLen     TmnxAddressAndPrefixPrefix,
    tRPOperPfxListToRowStatus        RowStatus,
    tRPOperPfxListToCrOrigin         TmnxCreateOrigin
}

tRPOperPfxListToEndPrefixType    OBJECT-TYPE
    SYNTAX      TmnxAddressAndPrefixType
    MAX-ACCESS  not-accessible
    STATUS      current
    DESCRIPTION
        "The value of tRPOperPfxListToEndPrefixType specifies the address type
         of tRPOperPfxListToEndPrefix."
    ::= { tRPOperPfxListToEntry 1 }

tRPOperPfxListToEndPrefix        OBJECT-TYPE
    SYNTAX      TmnxAddressAndPrefixAddress (SIZE (4|16))
    MAX-ACCESS  not-accessible
    STATUS      current
    DESCRIPTION
        "The value of tRPOperPfxListToEndPrefix specifies the end IP prefix of
         the prefix list entry."
    ::= { tRPOperPfxListToEntry 2 }

tRPOperPfxListToEndPrefixLen     OBJECT-TYPE
    SYNTAX      TmnxAddressAndPrefixPrefix
    MAX-ACCESS  not-accessible
    STATUS      current
    DESCRIPTION
        "The value of tRPOperPfxListToEndPrefixLen specifies the end IP prefix
         length of the prefix list entry."
    ::= { tRPOperPfxListToEntry 3 }

tRPOperPfxListToRowStatus        OBJECT-TYPE
    SYNTAX      RowStatus
    MAX-ACCESS  read-only
    STATUS      current
    DESCRIPTION
        "The value of the object tRPOperPfxListToRowStatus indicates the
         RowStatus for this row.

         To create or destroy entries in this table, use the
         tRPAdminPfxListToTable."
    ::= { tRPOperPfxListToEntry 4 }

tRPOperPfxListToCrOrigin         OBJECT-TYPE
    SYNTAX      TmnxCreateOrigin
    MAX-ACCESS  read-only
    STATUS      current
    DESCRIPTION
        "The value of the object tRPOperPfxListToCrOrigin indicates the
         mechanism used to create this entry."
    ::= { tRPOperPfxListToEntry 5 }

tRPOperPfxListAddressMaskTable   OBJECT-TYPE
    SYNTAX      SEQUENCE OF TRPOperPfxListAddressMaskEntry
    MAX-ACCESS  not-accessible
    STATUS      current
    DESCRIPTION
        "The table of admin prefix lists specifying a match condition that does
         not require contiguous network mask bits."
    ::= { tRPOperValueObjects 46 }

tRPOperPfxListAddressMaskEntry   OBJECT-TYPE
    SYNTAX      TRPOperPfxListAddressMaskEntry
    MAX-ACCESS  not-accessible
    STATUS      current
    DESCRIPTION
        "Each row entry in the tRPOperPfxListAddressMaskEntry represents
         information about a particular prefix list address mask.

         A route's prefix/length is considered a match if all of the
         following are true:
         - the bitwise logical AND of the prefix-list address and the mask
           equals the bitwise logical AND of the route address and the mask
         - the prefix length of the route matches the prefix length of
           the prefix-list entry

         Entries are created and deleted by the user via
         tRPAdminPfxListAddressMaskTable."
    INDEX       {
        tRPOperPfxListName,
        tRPOperInetPrefixListPrefixType,
        tRPOperInetPrefixListPrefix,
        tRPOperInetPrefixListPrefixLen,
        tRPOperPfxListAddressMaskType,
        tRPOperPfxListAddressMask
    }
    ::= { tRPOperPfxListAddressMaskTable 1 }

TRPOperPfxListAddressMaskEntry   ::= SEQUENCE
{
    tRPOperPfxListAddressMaskType    InetAddressType,
    tRPOperPfxListAddressMask        InetAddress,
    tRPOperPfxListAddrMaskRowStatus  RowStatus,
    tRPOperPfxListAddrMaskCrOrigin   TmnxCreateOrigin
}

tRPOperPfxListAddressMaskType    OBJECT-TYPE
    SYNTAX      InetAddressType
    MAX-ACCESS  not-accessible
    STATUS      current
    DESCRIPTION
        "The value of tRPOperPfxListAddressMaskType specifies the address type
         of tRPOperPfxListAddressMask."
    ::= { tRPOperPfxListAddressMaskEntry 1 }

tRPOperPfxListAddressMask        OBJECT-TYPE
    SYNTAX      InetAddress (SIZE (4|16))
    MAX-ACCESS  not-accessible
    STATUS      current
    DESCRIPTION
        "The value of tRPOperPfxListAddressMask specifies the address mask of
         the prefix list entry."
    ::= { tRPOperPfxListAddressMaskEntry 2 }

tRPOperPfxListAddrMaskRowStatus  OBJECT-TYPE
    SYNTAX      RowStatus
    MAX-ACCESS  read-only
    STATUS      current
    DESCRIPTION
        "The value of the object tRPOperPfxListAddrMaskRowStatus indicates the
         RowStatus for this row.

         To create or destroy entries in this table, use the
         tRPAdminPfxListAddressMaskTable."
    ::= { tRPOperPfxListAddressMaskEntry 3 }

tRPOperPfxListAddrMaskCrOrigin   OBJECT-TYPE
    SYNTAX      TmnxCreateOrigin
    MAX-ACCESS  read-only
    STATUS      current
    DESCRIPTION
        "The value of the object tRPOperPfxListAddrMaskCrOrigin indicates the
         mechanism used to create this entry."
    ::= { tRPOperPfxListAddressMaskEntry 4 }

tRPOperPSFromCritInterfaceTable  OBJECT-TYPE
    SYNTAX      SEQUENCE OF TRPOperPSFromCritInterfaceEntry
    MAX-ACCESS  not-accessible
    STATUS      current
    DESCRIPTION
        "A table of interface subnets to match on as 'from' criteria for each
         policy statement entry"
    ::= { tRPOperValueObjects 47 }

tRPOperPSFromCritInterfaceEntry  OBJECT-TYPE
    SYNTAX      TRPOperPSFromCritInterfaceEntry
    MAX-ACCESS  not-accessible
    STATUS      current
    DESCRIPTION
        "Information about policy statement entry from interface subnet
         criteria.

         Entries are created or deleted when an entry in
         tRPOperPSFromCriteriaTable is created or deleted."
    AUGMENTS    { tRPOperPSFromCriteriaEntry }
    ::= { tRPOperPSFromCritInterfaceTable 1 }

TRPOperPSFromCritInterfaceEntry  ::= SEQUENCE
{
    tRPOperPSFromCritIntfServiceId   TNamedItemOrEmpty,
    tRPOperPSFromCritInterface1      TNamedItemOrEmpty,
    tRPOperPSFromCritInterface2      TNamedItemOrEmpty,
    tRPOperPSFromCritInterface3      TNamedItemOrEmpty,
    tRPOperPSFromCritInterface4      TNamedItemOrEmpty,
    tRPOperPSFromCritInterface5      TNamedItemOrEmpty,
    tRPOperPSFromCritInterface6      TNamedItemOrEmpty,
    tRPOperPSFromCritInterface7      TNamedItemOrEmpty,
    tRPOperPSFromCritInterface8      TNamedItemOrEmpty,
    tRPOperPSFromCritInterface9      TNamedItemOrEmpty,
    tRPOperPSFromCritInterface10     TNamedItemOrEmpty
}

tRPOperPSFromCritIntfServiceId   OBJECT-TYPE
    SYNTAX      TNamedItemOrEmpty
    MAX-ACCESS  read-only
    STATUS      current
    DESCRIPTION
        "The value of tRPOperPSFromCritIntfServiceId indicates the
         service ID of the interface subnets to match on.

         The value of this object can be a string containing the service ID
         value. An empty string means that no service ID is configured.

         If interface subnets are configured without service ID,
         it is assumed they belong to the BASE routing instance."
    ::= { tRPOperPSFromCritInterfaceEntry 1 }

tRPOperPSFromCritInterface1      OBJECT-TYPE
    SYNTAX      TNamedItemOrEmpty
    MAX-ACCESS  read-only
    STATUS      current
    DESCRIPTION
        "The value of tRPOperPSFromCritInterface1 indicates the name of the
         first interface to match on. Setting this value to an empty string
         disables this interface as a match criteria."
    ::= { tRPOperPSFromCritInterfaceEntry 2 }

tRPOperPSFromCritInterface2      OBJECT-TYPE
    SYNTAX      TNamedItemOrEmpty
    MAX-ACCESS  read-only
    STATUS      current
    DESCRIPTION
        "The value of tRPOperPSFromCritInterface2 indicates the name of the
         second interface to match on. Setting this value to an empty string
         disables this interface as a match criteria."
    ::= { tRPOperPSFromCritInterfaceEntry 3 }

tRPOperPSFromCritInterface3      OBJECT-TYPE
    SYNTAX      TNamedItemOrEmpty
    MAX-ACCESS  read-only
    STATUS      current
    DESCRIPTION
        "The value of tRPOperPSFromCritInterface3 indicates the name of the
         third interface to match on. Setting this value to an empty string
         disables this interface as a match criteria."
    ::= { tRPOperPSFromCritInterfaceEntry 4 }

tRPOperPSFromCritInterface4      OBJECT-TYPE
    SYNTAX      TNamedItemOrEmpty
    MAX-ACCESS  read-only
    STATUS      current
    DESCRIPTION
        "The value of tRPOperPSFromCritInterface4 indicates the name of the
         fourth interface to match on. Setting this value to an empty string
         disables this interface as a match criteria."
    ::= { tRPOperPSFromCritInterfaceEntry 5 }

tRPOperPSFromCritInterface5      OBJECT-TYPE
    SYNTAX      TNamedItemOrEmpty
    MAX-ACCESS  read-only
    STATUS      current
    DESCRIPTION
        "The value of tRPOperPSFromCritInterface5 indicates the name of the
         fifth interface to match on. Setting this value to an empty string
         disables this interface as a match criteria."
    ::= { tRPOperPSFromCritInterfaceEntry 6 }

tRPOperPSFromCritInterface6      OBJECT-TYPE
    SYNTAX      TNamedItemOrEmpty
    MAX-ACCESS  read-only
    STATUS      current
    DESCRIPTION
        "The value of tRPOperPSFromCritInterface6 indicates the name of the
         sixth interface to match on. Setting this value to an empty string
         disables this interface as a match criteria."
    ::= { tRPOperPSFromCritInterfaceEntry 7 }

tRPOperPSFromCritInterface7      OBJECT-TYPE
    SYNTAX      TNamedItemOrEmpty
    MAX-ACCESS  read-only
    STATUS      current
    DESCRIPTION
        "The value of tRPOperPSFromCritInterface7 indicates the name of the
         seventh interface to match on. Setting this value to an empty string
         disables this interface as a match criteria."
    ::= { tRPOperPSFromCritInterfaceEntry 8 }

tRPOperPSFromCritInterface8      OBJECT-TYPE
    SYNTAX      TNamedItemOrEmpty
    MAX-ACCESS  read-only
    STATUS      current
    DESCRIPTION
        "The value of tRPOperPSFromCritInterface8 indicates the name of the
         eight interface to match on. Setting this value to an empty string
         disables this interface as a match criteria."
    ::= { tRPOperPSFromCritInterfaceEntry 9 }

tRPOperPSFromCritInterface9      OBJECT-TYPE
    SYNTAX      TNamedItemOrEmpty
    MAX-ACCESS  read-only
    STATUS      current
    DESCRIPTION
        "The value of tRPOperPSFromCritInterface9 indicates the name of the 9th
         interface to match on. Setting this value to an empty string disables
         this interface as a match criteria."
    ::= { tRPOperPSFromCritInterfaceEntry 10 }

tRPOperPSFromCritInterface10     OBJECT-TYPE
    SYNTAX      TNamedItemOrEmpty
    MAX-ACCESS  read-only
    STATUS      current
    DESCRIPTION
        "The value of tRPOperPSFromCritInterface10 indicates the name of the
         10th interface to match on. Setting this value to an empty string
         disables this interface as a match criteria."
    ::= { tRPOperPSFromCritInterfaceEntry 11 }

tRPOperRDListTable               OBJECT-TYPE
    SYNTAX      SEQUENCE OF TRPOperRDListEntry
    MAX-ACCESS  not-accessible
    STATUS      current
    DESCRIPTION
        "The table contains the operational information pertaining to  a route
         distinguisher (RD) list."
    ::= { tRPOperValueObjects 48 }

tRPOperRDListEntry               OBJECT-TYPE
    SYNTAX      TRPOperRDListEntry
    MAX-ACCESS  not-accessible
    STATUS      current
    DESCRIPTION
        "Each conceptual row represents a particular route distinguisher (RD)
         list.

         Rows in the table tRPOperRDListTable are created and deleted by the
         user via tRPAdminRDListTable.

         In case the RD list is empty, i.e. no referring entry exists in the
         tRPOperRouteDistinguisherTable, the RD list will never match."
    INDEX       { tRPOperRDListName }
    ::= { tRPOperRDListTable 1 }

TRPOperRDListEntry               ::= SEQUENCE
{
    tRPOperRDListName                TRouteDistinguisherListName,
    tRPOperRDListRowStatus           RowStatus,
    tRPOperRDListCrOrigin            TmnxCreateOrigin
}

tRPOperRDListName                OBJECT-TYPE
    SYNTAX      TRouteDistinguisherListName (SIZE (1..64))
    MAX-ACCESS  not-accessible
    STATUS      current
    DESCRIPTION
        "The value of tRPOperRDListName indicates the name of  the route
         distinguisher (RD) list entry."
    ::= { tRPOperRDListEntry 1 }

tRPOperRDListRowStatus           OBJECT-TYPE
    SYNTAX      RowStatus
    MAX-ACCESS  read-only
    STATUS      current
    DESCRIPTION
        "The value of the object tRPOperRDListRowStatus indicates the RowStatus
         for this row.

         To create or destroy entries in this table, use the
         tRPAdminRDListTable."
    ::= { tRPOperRDListEntry 2 }

tRPOperRDListCrOrigin            OBJECT-TYPE
    SYNTAX      TmnxCreateOrigin
    MAX-ACCESS  read-only
    STATUS      current
    DESCRIPTION
        "The value of the object tRPOperRDListCrOrigin indicates the mechanism
         used to create this entry."
    ::= { tRPOperRDListEntry 3 }

tRPOperRouteDistinguisherTable   OBJECT-TYPE
    SYNTAX      SEQUENCE OF TRPOperRouteDistinguisherEntry
    MAX-ACCESS  not-accessible
    STATUS      current
    DESCRIPTION
        "The table contains the information pertaining to  a route
         distinguisher (RD) entry in a RD list."
    ::= { tRPOperValueObjects 49 }

tRPOperRouteDistinguisherEntry   OBJECT-TYPE
    SYNTAX      TRPOperRouteDistinguisherEntry
    MAX-ACCESS  not-accessible
    STATUS      current
    DESCRIPTION
        "Each conceptual row represents a particular route distinguisher (RD)
         entry in the RD list.

         Rows in the table tRPOperRouteDistinguisherTable are created and
         deleted by the user via tRPAdminRouteDistinguisherTable."
    INDEX       {
        tRPOperRDListName,
        tRPOperRouteDistinguisher
    }
    ::= { tRPOperRouteDistinguisherTable 1 }

TRPOperRouteDistinguisherEntry   ::= SEQUENCE
{
    tRPOperRouteDistinguisher        TPolicyRouteDistinguisher,
    tRPOperRDRowStatus               RowStatus,
    tRPOperRDCrOrigin                TmnxCreateOrigin
}

tRPOperRouteDistinguisher        OBJECT-TYPE
    SYNTAX      TPolicyRouteDistinguisher
    MAX-ACCESS  not-accessible
    STATUS      current
    DESCRIPTION
        "The value of tRPOperRouteDistinguisher indicates the route
         distinguisher entry of the RD list."
    ::= { tRPOperRouteDistinguisherEntry 1 }

tRPOperRDRowStatus               OBJECT-TYPE
    SYNTAX      RowStatus
    MAX-ACCESS  read-only
    STATUS      current
    DESCRIPTION
        "The value of the object tRPOperRDRowStatus indicates the RowStatus for
         this row.

         To create or destroy entries in this table, use the
         tRPAdminRouteDistinguisherTable."
    ::= { tRPOperRouteDistinguisherEntry 2 }

tRPOperRDCrOrigin                OBJECT-TYPE
    SYNTAX      TmnxCreateOrigin
    MAX-ACCESS  read-only
    STATUS      current
    DESCRIPTION
        "The value of the object tRPOperRDCrOrigin indicates the mechanism used
         to create this entry."
    ::= { tRPOperRouteDistinguisherEntry 3 }

tRPOperPSFromCrPfxListOvrTable   OBJECT-TYPE
    SYNTAX      SEQUENCE OF TRPOperPSFromCrPfxListOvrEntry
    MAX-ACCESS  not-accessible
    STATUS      current
    DESCRIPTION
        "The table contains the information pertaining to  a prefix-list
         override to match on as 'from' criteria for each policy statement
         entry."
    ::= { tRPOperValueObjects 50 }

tRPOperPSFromCrPfxListOvrEntry   OBJECT-TYPE
    SYNTAX      TRPOperPSFromCrPfxListOvrEntry
    MAX-ACCESS  not-accessible
    STATUS      current
    DESCRIPTION
        "Each conceptual row represents a particular prefix list override match
         criteria.

         Rows in the table tRPOperPSFromCrPfxListOvrTable are created and
         deleted by the user via tRPAdminPSFromCrPfxListOvrTable.

         Only 1 prefix-list override is supported per match condition entry."
    INDEX       {
        tRPOperPolicyStatementName,
        tRPOperPSFromCriteriaIndex,
        tRPOperPSFromCrPLOvrPfxListName
    }
    ::= { tRPOperPSFromCrPfxListOvrTable 1 }

TRPOperPSFromCrPfxListOvrEntry   ::= SEQUENCE
{
    tRPOperPSFromCrPLOvrPfxListName  TLPrefixListName,
    tRPOperPSFromCrPLOvrRowStatus    RowStatus,
    tRPOperPSFromCrPLOvrType         INTEGER,
    tRPOperPSFromCrPLOvrCrOrigin     TmnxCreateOrigin,
    tRPOperPSFromCrPLOvrThroughLen   InetAddressPrefixLength,
    tRPOperPSFromCrPLOvrBeginLen     InetAddressPrefixLength
}

tRPOperPSFromCrPLOvrPfxListName  OBJECT-TYPE
    SYNTAX      TLPrefixListName (SIZE (1..64))
    MAX-ACCESS  not-accessible
    STATUS      current
    DESCRIPTION
        "The value of tRPOperPSFromCrPLOvrPfxListName specifies the name of the
         prefix-list from which the type must be overridden to match the route
         on.

         The value of this object can be a string containing the name of the
         prefix-list or a variable name that needs to be resolved to get the
         name of the prefix-list. The prefix-list name must exist in
         tRPOperPfxListNameTable.

         The prefix-list override match condition is mutually exclusive with
         the prefix list match condition, i.e. no prefix-list can be
         overridden if a prefix-list is set in tRPOperPSFromCritPfxListTable."
    ::= { tRPOperPSFromCrPfxListOvrEntry 1 }

tRPOperPSFromCrPLOvrRowStatus    OBJECT-TYPE
    SYNTAX      RowStatus
    MAX-ACCESS  read-only
    STATUS      current
    DESCRIPTION
        "The value of the object tRPOperPSFromCrPLOvrRowStatus indicates the
         RowStatus for this row.

         To create or destroy entries in this table, use the
         tRPAdminPSFromCrPfxListOvrTable."
    ::= { tRPOperPSFromCrPfxListOvrEntry 2 }

tRPOperPSFromCrPLOvrType         OBJECT-TYPE
    SYNTAX      INTEGER {
        exact   (1),
        longer  (2),
        through (3),
        range   (4)
    }
    MAX-ACCESS  read-only
    STATUS      current
    DESCRIPTION
        "The value of tRPOperPSFromCrPLOvrType indicates the prefix-list
         override type to match the route on.

         exact (1) - a route's prefix/length must match the prefix list entry
         exactly in order for an entry to be considered a match.

         longer (2) - a route's prefix/length must match the defined prefix AND
         have a length that is an exact match or longer in order for an entry
         to be considered a match.

         through (3) - a route's prefix/length must match the defined prefix
         AND have a length that is an exact match or longer up to and including
         the defined maximum length  tRPOperPSFromCrPLOvrThroughLen in order
         for an entry to be considered a match.

         range (4) - a route's prefix/length must match the defined prefix AND
         have a length that is greater than or equal to the length defined by
         tRPOperPSFromCrPLOvrBeginLen and less than or equal to the length
         defined by tRPOperPSFromCrPLOvrThroughLen in order for an entry to be
         considered a match."
    ::= { tRPOperPSFromCrPfxListOvrEntry 3 }

tRPOperPSFromCrPLOvrCrOrigin     OBJECT-TYPE
    SYNTAX      TmnxCreateOrigin
    MAX-ACCESS  read-only
    STATUS      current
    DESCRIPTION
        "The value of the object tRPOperPSFromCrPLOvrCrOrigin indicates the
         mechanism used to create this entry."
    ::= { tRPOperPSFromCrPfxListOvrEntry 4 }

tRPOperPSFromCrPLOvrThroughLen   OBJECT-TYPE
    SYNTAX      InetAddressPrefixLength
    MAX-ACCESS  read-only
    STATUS      current
    DESCRIPTION
        "The value of tRPOperPSFromCrPLOvrThroughLen indicates the maximum mask
         length to use when tRPOperPSFromCrPLOvrType is set to 'through(3)' or
         'range(4)'.

         The mask length must be larger than the corresponding
         tRPOperPrefixListMask from the prefix-list."
    ::= { tRPOperPSFromCrPfxListOvrEntry 5 }

tRPOperPSFromCrPLOvrBeginLen     OBJECT-TYPE
    SYNTAX      InetAddressPrefixLength
    MAX-ACCESS  read-only
    STATUS      current
    DESCRIPTION
        "The value of tRPOperPSFromCrPLOvrBeginLen indicates the mask length to
         use as the lower limit for the mask range when
         tRPOperPSFromCrPLOvrType is set to 'range(4)'.

         The mask length must be larger than the corresponding
         tRPOperPrefixListMask and less than tRPOperPSFromCrPLOvrThroughLen."
    ::= { tRPOperPSFromCrPfxListOvrEntry 6 }

tRPAdminObjects                  OBJECT IDENTIFIER ::= { tRoutePolicyObjects 2 }

tRPAdminControlObjects           OBJECT IDENTIFIER ::= { tRPAdminObjects 1 }

tRPAdminOwner                    OBJECT-TYPE
    SYNTAX      TNamedItemOrEmpty
    MAX-ACCESS  read-only
    STATUS      current
    DESCRIPTION
        "Who has last initialized the administrative tables, who is making all
         the changes, and who is expected to either commit or re-initialize
         (ABORT-TRANSACTION).

         The value of tRPAdminOwner is set when tRPAdminControlApply is set so
         that other users will be advised to not make changes to the Admin
         tables.

         Agent sets tRPAdminOwner to empty string after tRPAdminControlApply is
         set - either by user initializing or committing, or by agent timing
         out the uncommitted transactions (tRPAdminLastSetTimer)."
    ::= { tRPAdminControlObjects 1 }

tRPAdminControlApply             OBJECT-TYPE
    SYNTAX      INTEGER {
        none       (1),
        initialize (2),
        commit     (3),
        exclusive  (4)
    }
    MAX-ACCESS  read-write
    STATUS      current
    DESCRIPTION
        "This object controls the use of tRPAdminValueObjects tables.

         This object always reads none(1) after setting it to commit(3).

         When set to initialize(2), the objects in tRPAdminValueObjects tables
         are set to the current Operational values, from the
         corresponding tRPOperValueObjects tables.  Any uncommitted changes are
         lost, so setting this value corresponds to both BEGIN-TRANSACTION
         and ABORT-TRANSACTION.
         The value of this object must be initialize(2) when changing
         the values of objects in tRPAdminValueObjects tables.

         When set to commit(3) (END-TRANSACTION), all of the objects from
         tRPAdminValueObjects tables are copied to the corresponding
         tRPOperValueObjects table objects.  Then, all routes are re-evaluated
         with the new policies.  Later arriving routes are evaluated with the
         new policies.

         Value exclusive(4) initializes the transaction like initialize(2), but
         when the value is set to exclusive(4), only the user who started this
         transaction (tRPAdminOwner) can change the configuration.

         In this way, the (expensive) route re-evaluation can be performed at
         one time, with a coherent route policy configuration."
    ::= { tRPAdminControlObjects 2 }

tRPAdminLastSetTimer             OBJECT-TYPE
    SYNTAX      TimeInterval
    UNITS       "centiseconds"
    MAX-ACCESS  read-only
    STATUS      current
    DESCRIPTION
        "The time remaining until the agent re-initializes the administrative
         tables.

         If tRPAdminControlApply is currently set to exclusive(4) and is not
         set to commit(3) within tRPAdminLastSetTimer centiseconds, the agent
         will set it to none(1) and all uncommitted changes will be lost.

         This way, uncommitted changes from failed (uncompleted) change sets
         will eventually be removed, and another transaction can safely begin.

         This object is reset to tRPAdminLastSetTimeout after GET or SET
         operation to any of the tRPAdminValueObjects tables by the current
         owner of the exclusive lock."
    ::= { tRPAdminControlObjects 3 }

tRPAdminLastSetTimeout           OBJECT-TYPE
    SYNTAX      Integer32 (1..3600)
    UNITS       "seconds"
    MAX-ACCESS  read-write
    STATUS      current
    DESCRIPTION
        "The value of tRPAdminLastSetTimeout specifies the timeout interval for
         transactions started with an exclusive lock."
    DEFVAL      { 300 }
    ::= { tRPAdminControlObjects 4 }

tRPAdminControlResetExclusive    OBJECT-TYPE
    SYNTAX      TruthValue
    MAX-ACCESS  read-write
    STATUS      current
    DESCRIPTION
        "This value of object tRPAdminControlResetExclusive specifies whether
         the exclusive lock should be aborted.

         When the value of tRPAdminControlResetExclusive is set to true(1), the
         exclusive lock, taken by setting tRPAdminControlApply to exclusive(4),
         is aborted. This corresponds with ABORT-TRANSACTION."
    DEFVAL      { false }
    ::= { tRPAdminControlObjects 5 }

tRPAdminValueObjects             OBJECT IDENTIFIER ::= { tRPAdminObjects 2 }

tRPAdminASPathTable              OBJECT-TYPE
    SYNTAX      SEQUENCE OF TRPAdminASPathEntry
    MAX-ACCESS  not-accessible
    STATUS      current
    DESCRIPTION
        "A list of AS Path names and corresponding regular expressions."
    ::= { tRPAdminValueObjects 1 }

tRPAdminASPathEntry              OBJECT-TYPE
    SYNTAX      TRPAdminASPathEntry
    MAX-ACCESS  not-accessible
    STATUS      current
    DESCRIPTION
        "Information about a particular AS Path Name. Entries are created and
         deleted by the user."
    INDEX       { tRPAdminASPathName }
    ::= { tRPAdminASPathTable 1 }

TRPAdminASPathEntry              ::= SEQUENCE
{
    tRPAdminASPathName               TASPathName,
    tRPAdminASPathRowStatus          RowStatus,
    tRPAdminASPathRegEx              TRoutePolicyRegex,
    tRPAdminASPathCreationOrigin     TmnxCreateOrigin
}

tRPAdminASPathName               OBJECT-TYPE
    SYNTAX      TASPathName (SIZE (1..32))
    MAX-ACCESS  not-accessible
    STATUS      current
    DESCRIPTION
        "The name of the AS Path entry used to uniquely identify an AS Path."
    ::= { tRPAdminASPathEntry 1 }

tRPAdminASPathRowStatus          OBJECT-TYPE
    SYNTAX      RowStatus
    MAX-ACCESS  read-create
    STATUS      current
    DESCRIPTION
        "The value of tRPAdminASPathRowStatus specifies the RowStatus for this
         row.

         To create a row, set this object to createAndGo(4). The value of
         tRPAdminASPathRegEx must also be set to a valid non-empty string for
         the row creation to succeed. When tRPAdminControlApply is set to
         commit(3), the row will actually be created in the tRPOperASPathTable.

         To destroy a row, set this object to destroy(6). When
         tRPAdminControlApply is set to commit(3) the row will actually be
         removed from the tRPOperASPathTable."
    ::= { tRPAdminASPathEntry 2 }

tRPAdminASPathRegEx              OBJECT-TYPE
    SYNTAX      TRoutePolicyRegex
    MAX-ACCESS  read-create
    STATUS      current
    DESCRIPTION
        "The regular expression for the AS Path entry."
    DEFVAL      { ''H }
    ::= { tRPAdminASPathEntry 3 }

tRPAdminASPathCreationOrigin     OBJECT-TYPE
    SYNTAX      TmnxCreateOrigin
    MAX-ACCESS  read-only
    STATUS      current
    DESCRIPTION
        "The value of the object tRPAdminASPathCreationOrigin indicates the
         mechanism used to create this entry."
    ::= { tRPAdminASPathEntry 4 }

tRPAdminCommunityTable           OBJECT-TYPE
    SYNTAX      SEQUENCE OF TRPAdminCommunityEntry
    MAX-ACCESS  not-accessible
    STATUS      current
    DESCRIPTION
        "A table of community entries."
    ::= { tRPAdminValueObjects 2 }

tRPAdminCommunityEntry           OBJECT-TYPE
    SYNTAX      TRPAdminCommunityEntry
    MAX-ACCESS  not-accessible
    STATUS      current
    DESCRIPTION
        "Information about a particular community name member.

         Entries are created and deleted by the user.

         When a community entry is created with a name that doesn't exist in
         the tRPAdminCommunityNameTable, a corresponding entry will be created
         automatically in tRPAdminCommunityNameTable.

         When a corresponding entry is deleted from tRPAdminCommunityNameTable,
         the entry in this table will be deleted automatically."
    INDEX       {
        tRPAdminCommunityName,
        tRPAdminCommunityMember
    }
    ::= { tRPAdminCommunityTable 1 }

TRPAdminCommunityEntry           ::= SEQUENCE
{
    tRPAdminCommunityName            TLCommunityName,
    tRPAdminCommunityMember          TCommunityMember,
    tRPAdminCommunityRowStatus       RowStatus,
    tRPAdminCommunityCreationOrigin  TmnxCreateOrigin
}

tRPAdminCommunityName            OBJECT-TYPE
    SYNTAX      TLCommunityName (SIZE (1..64))
    MAX-ACCESS  not-accessible
    STATUS      current
    DESCRIPTION
        "The name of the community used as an index for this table.

         This object refers to the object tRPAdminCommName in
         tRPAdminCommunityNameTable."
    ::= { tRPAdminCommunityEntry 1 }

tRPAdminCommunityMember          OBJECT-TYPE
    SYNTAX      TCommunityMember
    MAX-ACCESS  not-accessible
    STATUS      current
    DESCRIPTION
        "The AS Number or Community ID of the community member. The community
         name and the member name uniquely identify a row in this table."
    ::= { tRPAdminCommunityEntry 2 }

tRPAdminCommunityRowStatus       OBJECT-TYPE
    SYNTAX      RowStatus
    MAX-ACCESS  read-create
    STATUS      current
    DESCRIPTION
        "The value of tRPAdminCommunityRowStatus specifies the RowStatus for
         this row.

         To create a row, set this object to createAndGo(4). When
         tRPAdminControlApply is set to commit(3), the row will actually be
         created in the tRPOperCommunityTable.

         To destroy a row, set this object to destroy(6). When
         tRPAdminControlApply is set to commit(3) the row will actually be
         removed from the tRPOperCommunityTable."
    ::= { tRPAdminCommunityEntry 3 }

tRPAdminCommunityCreationOrigin  OBJECT-TYPE
    SYNTAX      TmnxCreateOrigin
    MAX-ACCESS  read-only
    STATUS      current
    DESCRIPTION
        "The value of the object tRPAdminCommunityCreationOrigin indicates the
         mechanism used to create this entry."
    ::= { tRPAdminCommunityEntry 4 }

tRPAdminDampingTable             OBJECT-TYPE
    SYNTAX      SEQUENCE OF TRPAdminDampingEntry
    MAX-ACCESS  not-accessible
    STATUS      current
    DESCRIPTION
        "A table of route damping control entries."
    ::= { tRPAdminValueObjects 3 }

tRPAdminDampingEntry             OBJECT-TYPE
    SYNTAX      TRPAdminDampingEntry
    MAX-ACCESS  not-accessible
    STATUS      current
    DESCRIPTION
        "Information about a particular Damping entry. Entries are created and
         deleted by the user."
    INDEX       { tRPAdminDampingName }
    ::= { tRPAdminDampingTable 1 }

TRPAdminDampingEntry             ::= SEQUENCE
{
    tRPAdminDampingName              TDampingName,
    tRPAdminDampingRowStatus         RowStatus,
    tRPAdminDampingHalfLife          Unsigned32,
    tRPAdminDampingMaxSuppress       Unsigned32,
    tRPAdminDampingReuse             Unsigned32,
    tRPAdminDampingSuppress          Unsigned32,
    tRPAdminDampingCreationOrigin    TmnxCreateOrigin
}

tRPAdminDampingName              OBJECT-TYPE
    SYNTAX      TDampingName (SIZE (1..32))
    MAX-ACCESS  not-accessible
    STATUS      current
    DESCRIPTION
        "The name of the damping entry used to uniquely identify a row in this
         table."
    ::= { tRPAdminDampingEntry 1 }

tRPAdminDampingRowStatus         OBJECT-TYPE
    SYNTAX      RowStatus
    MAX-ACCESS  read-create
    STATUS      current
    DESCRIPTION
        "tRPAdminDampingRowStatus specifies the RowStatus for this row.

         To create a row, set this object to createAndGo(4). When
         tRPAdminControlApply is set to commit(3), the row will actually be
         created in the tRPOperDampingTable.

         To destroy a row, set this object to destroy(6). When
         tRPAdminControlApply is set to commit(3) the row will actually be
         removed from the tRPOperDampingTable."
    ::= { tRPAdminDampingEntry 2 }

tRPAdminDampingHalfLife          OBJECT-TYPE
    SYNTAX      Unsigned32 (0..45)
    UNITS       "minutes"
    MAX-ACCESS  read-create
    STATUS      current
    DESCRIPTION
        "Specifies the half-life, in minutes, for a routes figure-of-merit
         after it has been dampened. If a route's half-life is set to 15
         minutes and has a figure-of-merit of 1500, after 15 minutes, the
         route's figure-of-merit will have decayed to 750. Set to 0 to disable."
    DEFVAL      { 0 }
    ::= { tRPAdminDampingEntry 3 }

tRPAdminDampingMaxSuppress       OBJECT-TYPE
    SYNTAX      Unsigned32 (0..720)
    UNITS       "minutes"
    MAX-ACCESS  read-create
    STATUS      current
    DESCRIPTION
        "Specifies the maximum amount of time, in minutes, that a route can be
         suppressed for. Set to 0 to disable."
    DEFVAL      { 0 }
    ::= { tRPAdminDampingEntry 4 }

tRPAdminDampingReuse             OBJECT-TYPE
    SYNTAX      Unsigned32 (0..20000)
    MAX-ACCESS  read-create
    STATUS      current
    DESCRIPTION
        "Specifies the reuse threshold. If a route's figure-of-merit falls
         below the reuse threshold, the route can be reused. Set to 0 to
         disable."
    DEFVAL      { 0 }
    ::= { tRPAdminDampingEntry 5 }

tRPAdminDampingSuppress          OBJECT-TYPE
    SYNTAX      Unsigned32 (0..20000)
    MAX-ACCESS  read-create
    STATUS      current
    DESCRIPTION
        "Specifies the suppress threshold. If a route's figure-of-merit goes
         above the suppress threshold, the route should be suppressed. Set to 0
         to disable."
    DEFVAL      { 0 }
    ::= { tRPAdminDampingEntry 6 }

tRPAdminDampingCreationOrigin    OBJECT-TYPE
    SYNTAX      TmnxCreateOrigin
    MAX-ACCESS  read-only
    STATUS      current
    DESCRIPTION
        "The value of the object tRPAdminDampingCreationOrigin indicates the
         mechanism used to create this entry."
    ::= { tRPAdminDampingEntry 7 }

tRPAdminPrefixListTable          OBJECT-TYPE
    SYNTAX      SEQUENCE OF TRPAdminPrefixListEntry
    MAX-ACCESS  not-accessible
    STATUS      current
    DESCRIPTION
        "A table of prefix lists."
    ::= { tRPAdminValueObjects 4 }

tRPAdminPrefixListEntry          OBJECT-TYPE
    SYNTAX      TRPAdminPrefixListEntry
    MAX-ACCESS  not-accessible
    STATUS      current
    DESCRIPTION
        "Information about a particular prefix list.

         Entries are created and deleted by the user.

         When a prefix list entry is created with a name that doesn't exist in
         the tRPAdminPfxListNameTable, a corresponding entry will be created
         automatically in tRPAdminPfxListNameTable.

         When a corresponding entry is deleted from tRPAdminPfxListNameTable,
         the entry in this table will be deleted automatically."
    INDEX       {
        tRPAdminPrefixListName,
        tRPAdminPrefixListIpPrefix,
        tRPAdminPrefixListMask,
        tRPAdminPrefixListType
    }
    ::= { tRPAdminPrefixListTable 1 }

TRPAdminPrefixListEntry          ::= SEQUENCE
{
    tRPAdminPrefixListName           TLPrefixListName,
    tRPAdminPrefixListIpPrefix       IpAddress,
    tRPAdminPrefixListMask           IpAddressPrefixLength,
    tRPAdminPrefixListRowStatus      RowStatus,
    tRPAdminPrefixListType           INTEGER,
    tRPAdminPrefixListThroughLength  IpAddressPrefixLength,
    tRPAdminPrefixListBeginLength    IpAddressPrefixLength
}

tRPAdminPrefixListName           OBJECT-TYPE
    SYNTAX      TLPrefixListName (SIZE (1..64))
    MAX-ACCESS  not-accessible
    STATUS      current
    DESCRIPTION
        "The name of the prefix list entry."
    ::= { tRPAdminPrefixListEntry 1 }

tRPAdminPrefixListIpPrefix       OBJECT-TYPE
    SYNTAX      IpAddress
    MAX-ACCESS  not-accessible
    STATUS      current
    DESCRIPTION
        "The IP prefix of the prefix list entry."
    ::= { tRPAdminPrefixListEntry 2 }

tRPAdminPrefixListMask           OBJECT-TYPE
    SYNTAX      IpAddressPrefixLength
    MAX-ACCESS  not-accessible
    STATUS      current
    DESCRIPTION
        "The IP mask length of the prefix list entry."
    ::= { tRPAdminPrefixListEntry 3 }

tRPAdminPrefixListRowStatus      OBJECT-TYPE
    SYNTAX      RowStatus
    MAX-ACCESS  read-create
    STATUS      current
    DESCRIPTION
        "RowStatus for this row.

         To create a row, set this object to createAndGo or createAndWait. When
         tRPAdminControlApply is set to commit(3), the row will actually be
         created in the tRPOperPrefixListTable.

         To destroy a row, set this object to destroy(6). When
         tRPAdminControlApply is set to commit(3) the row will actually be
         removed from the tRPOperPrefixListTable."
    ::= { tRPAdminPrefixListEntry 4 }

tRPAdminPrefixListType           OBJECT-TYPE
    SYNTAX      INTEGER {
        exact       (1),
        longer      (2),
        through     (3),
        range       (4),
        to          (5),
        addressMask (6)
    }
    MAX-ACCESS  not-accessible
    STATUS      current
    DESCRIPTION
        "The type of the prefix length entry.

         exact (1) - a route's prefix/length must match the prefix list entry
         exactly in order for an entry to be considered a match.

         longer (2) - a route's prefix/length must match the defined prefix AND
         have a length that is an exact match or longer in order for an entry
         to be considered a match.

         through (3) - a route's prefix/length must match the defined prefix
         AND have a length that is an exact match or longer up to and including
         the defined maximum length in order for an entry to be considered a
         match.

         range (4) - a route's prefix/length must match the defined prefix AND
         have a length that is greater than or equal to the length defined by
         tRPAdminPrefixListBeginLength and less than or equal to the length
         defined by tRPAdminPrefixListThroughLength in order for an entry to be
         considered a match.

         to (5) - a route's prefix/length must match the condition  from a
         start prefix/length to an end prefix/length. The  end prefix/length is
         indicated in the corresponding entry in  the tRPAdminPfxListToTable.

         addressMask (6) - a route's prefix/length must match the prefix length
         of the prefix-list entry and the bitwise logical AND of the route
         address and the mask must match the bitwise  logical AND from the
         prefix-list address and the mask. The  address mask must be specified
         in a corresponding entry in the tRPAdminPfxListAddressMaskTable."
    ::= { tRPAdminPrefixListEntry 5 }

tRPAdminPrefixListThroughLength  OBJECT-TYPE
    SYNTAX      IpAddressPrefixLength
    MAX-ACCESS  read-create
    STATUS      current
    DESCRIPTION
        "When tRPAdminPrefixListType set to through(3), the mask length to use.
         Must be larger than tRPAdminPrefixListMask."
    DEFVAL      { 0 }
    ::= { tRPAdminPrefixListEntry 6 }

tRPAdminPrefixListBeginLength    OBJECT-TYPE
    SYNTAX      IpAddressPrefixLength
    MAX-ACCESS  read-create
    STATUS      current
    DESCRIPTION
        "When tRPAdminPrefixListType set to range(4), the mask length to use as
         the lower limit for the mask range. Must be larger than
         tRPAdminPrefixListMask and less than tRPAdminPrefixListThroughLength."
    DEFVAL      { 0 }
    ::= { tRPAdminPrefixListEntry 8 }

tRPAdminPolicyStatementTable     OBJECT-TYPE
    SYNTAX      SEQUENCE OF TRPAdminPolicyStatementEntry
    MAX-ACCESS  not-accessible
    STATUS      current
    DESCRIPTION
        "Control table for policy statements."
    ::= { tRPAdminValueObjects 5 }

tRPAdminPolicyStatementEntry     OBJECT-TYPE
    SYNTAX      TRPAdminPolicyStatementEntry
    MAX-ACCESS  not-accessible
    STATUS      current
    DESCRIPTION
        "Information about a particular policy statement. Entries are created
         and deleted by the user."
    INDEX       { tRPAdminPolicyStatementName }
    ::= { tRPAdminPolicyStatementTable 1 }

TRPAdminPolicyStatementEntry     ::= SEQUENCE
{
    tRPAdminPolicyStatementName      TLPolicyStatementName,
    tRPAdminPolicyStatementRowStatus RowStatus,
    tRPAdminPolicyStatementDescription TItemDescription,
    tRPAdminPolicyStatementDefaultAction TPolicyEntryAction,
    tRPAdminPolicyStatementCrOrigin  TmnxCreateOrigin
}

tRPAdminPolicyStatementName      OBJECT-TYPE
    SYNTAX      TLPolicyStatementName
    MAX-ACCESS  not-accessible
    STATUS      current
    DESCRIPTION
        "The name of this policy statement that uniquely identifies an entry in
         this table."
    ::= { tRPAdminPolicyStatementEntry 1 }

tRPAdminPolicyStatementRowStatus OBJECT-TYPE
    SYNTAX      RowStatus
    MAX-ACCESS  read-create
    STATUS      current
    DESCRIPTION
        "The value of tRPAdminPolicyStatementRowStatus specifies the RowStatus
         for this row.

         To create a row, set this object to createAndGo(4). When
         tRPAdminControlApply is set to commit(3), the row will actually be
         created in the tRPOperPolicyStatementTable.

         To destroy a row, set this object to destroy(6). When
         tRPAdminControlApply is set to commit(3) the row will actually be
         removed from the tRPOperPolicyStatementTable."
    ::= { tRPAdminPolicyStatementEntry 2 }

tRPAdminPolicyStatementDescription OBJECT-TYPE
    SYNTAX      TItemDescription
    MAX-ACCESS  read-create
    STATUS      current
    DESCRIPTION
        "Description for this policy statement."
    DEFVAL      { ''H }
    ::= { tRPAdminPolicyStatementEntry 3 }

tRPAdminPolicyStatementDefaultAction OBJECT-TYPE
    SYNTAX      TPolicyEntryAction
    MAX-ACCESS  read-create
    STATUS      current
    DESCRIPTION
        "The default action for the policy statement specifies what happens to
         the route if none of the policy statement entries match."
    DEFVAL      { reject }
    ::= { tRPAdminPolicyStatementEntry 4 }

tRPAdminPolicyStatementCrOrigin  OBJECT-TYPE
    SYNTAX      TmnxCreateOrigin
    MAX-ACCESS  read-only
    STATUS      current
    DESCRIPTION
        "The value of the object tRPAdminPolicyStatementCrOrigin indicates the
         mechanism used to create this entry."
    ::= { tRPAdminPolicyStatementEntry 5 }

tRPAdminPSDefaultActionParamsTable OBJECT-TYPE
    SYNTAX      SEQUENCE OF TRPAdminPSDefaultActionParamsEntry
    MAX-ACCESS  not-accessible
    STATUS      current
    DESCRIPTION
        "Default action parameters for a policy statement."
    ::= { tRPAdminValueObjects 6 }

tRPAdminPSDefaultActionParamsEntry OBJECT-TYPE
    SYNTAX      TRPAdminPSDefaultActionParamsEntry
    MAX-ACCESS  not-accessible
    STATUS      current
    DESCRIPTION
        "Default action information about a particular policy statement. When
         tRPAdminPolicyStatementDefaultAction for the policy statement is
         'accept(1)', and no policy statement entry matches the route, the
         following default actions are applied to the route.

         Entries are created when tRPAdminPolicyStatementDefaultAction is set
         to 'accept(1)', 'reject(2)', 'continue(3)' or 'nextPolicy(4)'. Entries
         are deleted when a policy statement is destroyed or
         tRPAdminPolicyStatementDefaultAction is set to value 'none(0)'."
    INDEX       { tRPAdminPolicyStatementName }
    ::= { tRPAdminPSDefaultActionParamsTable 1 }

TRPAdminPSDefaultActionParamsEntry ::= SEQUENCE
{
    tRPAdminPSDefaultActionASPath    TPolicyEntryEdit,
    tRPAdminPSDefaultActionASPathName TASPathName,
    tRPAdminPSDefaultActionASPathPrependAS TmnxBgpAutonomousSystem,
    tRPAdminPSDefaultActionASPathPrependCount Integer32,
    tRPAdminPSDefaultActionCommunity1 TPolicyEntryEdit,
    tRPAdminPSDefaultActionCommunityName1 TCommunityName,
    tRPAdminPSDefaultActionCommunity2 TPolicyEntryEdit,
    tRPAdminPSDefaultActionCommunityName2 TCommunityName,
    tRPAdminPSDefaultActionOrigin    TPolicyEntryCriteriaOrigin,
    tRPAdminPSDefaultActionLocalPreferenceSet TruthValue,
    tRPAdminPSDefaultActionLocalPreference TmnxBgpLocalPreference,
    tRPAdminPSDefaultActionMetric    TPolicyEntryEdit,
    tRPAdminPSDefaultActionMetricValue Unsigned32,
    tRPAdminPSDefaultActionPreference TmnxBgpPreference,
    tRPAdminPSDefaultActionDamping   TDampingName,
    tRPAdminPSDefaultActionNextHopSelf TruthValue,
    tRPAdminPSDefaultActionNextHop   IpAddress,
    tRPAdminPSDefaultActionTag       TPolicyActionTag,
    tRPAdminPSDefaultActionOspfType  TOspfRouteType,
    tRPAdminPSDefActInetNextHopType  InetAddressType,
    tRPAdminPSDefActInetNextHop      InetAddress,
    tRPAdminPSDefaultActionASPathPnd InetAutonomousSystemNumber,
    tRPAdminPSDefActMcRedirSvcId     TmnxServId,
    tRPAdminPSDefActMcRedirIfIndex   InterfaceIndexOrZero,
    tRPAdminPSDefActionMetricSource  TPolicyActionMetricSource,
    tRPAdminPSDefActionAigpMetric    TPolicyEntryAigpMetricEdit,
    tRPAdminPSDefActnAigpMetricVal   Unsigned32,
    tRPAdminPSDefActnSrcClassIndex   ClassIndexOrNone,
    tRPAdminPSDefActnDstClassIndex   ClassIndexOrNone,
    tRPAdminPSDefActnOrigValidState  INTEGER
}

tRPAdminPSDefaultActionASPath    OBJECT-TYPE
    SYNTAX      TPolicyEntryEdit
    MAX-ACCESS  read-create
    STATUS      current
    DESCRIPTION
        "The value of tRPAdminPSDefaultActionASPath specifies the AS Path
         rewrite information for the route.

         This object must be set together with
         tRPAdminPSDefaultActionASPathName."
    DEFVAL      { none }
    ::= { tRPAdminPSDefaultActionParamsEntry 1 }

tRPAdminPSDefaultActionASPathName OBJECT-TYPE
    SYNTAX      TASPathName
    MAX-ACCESS  read-create
    STATUS      current
    DESCRIPTION
        "The value of tRPAdminPSDefaultActionASPathName specifies the AS Path
         name to use for add, remove, or replace operation specified by
         tRPAdminPSDefaultActionASPath.

         This object must be set together with tRPAdminPSDefaultActionASPath
         and is ignored when tRPAdminPSDefaultActionASPath is none(1)."
    DEFVAL      { ''H }
    ::= { tRPAdminPSDefaultActionParamsEntry 2 }

tRPAdminPSDefaultActionASPathPrependAS OBJECT-TYPE
    SYNTAX      TmnxBgpAutonomousSystem
    MAX-ACCESS  read-create
    STATUS      obsolete
    DESCRIPTION
        "AS Number to prepend to the AS-Path attribute of the route. Ignored
         when tRPAdminPSDefaultActionASPathPrependCount is zero.

         This object was obsoleted in release 7.0.  It is replaced with the
         4-byte AS number defined by tRPAdminPSDefaultActionASPathPnd."
    DEFVAL      { 0 }
    ::= { tRPAdminPSDefaultActionParamsEntry 3 }

tRPAdminPSDefaultActionASPathPrependCount OBJECT-TYPE
    SYNTAX      Integer32 (0..50)
    MAX-ACCESS  read-create
    STATUS      current
    DESCRIPTION
        "Number of times tRPAdminPSDefaultActionASPathPnd is prepended to the
         AS-Path attribute of the route.

         Set to zero to disable.

         The value of this object tRPAdminPSDefaultActionASPathPrependCount is
         ignored when the object tRPAdminPSDefActASPPendCountSrc has a value
         different from actionValue(1)."
    DEFVAL      { 0 }
    ::= { tRPAdminPSDefaultActionParamsEntry 4 }

tRPAdminPSDefaultActionCommunity1 OBJECT-TYPE
    SYNTAX      TPolicyEntryEdit
    MAX-ACCESS  read-create
    STATUS      obsolete
    DESCRIPTION
        "How to apply tRPAdminPSDefaultActionCommunityName1 to the communities
         for the route.

         Set to none(1) to disable this feature.

         This object is obsoleted in release 11.0. It is replaced by
         tRPAdminPSDefActionAddCommEntry, tRPAdminPSDefActionRemCommEntry, and
         tRPAdminPSDefActionRepCommEntry."
    DEFVAL      { none }
    ::= { tRPAdminPSDefaultActionParamsEntry 5 }

tRPAdminPSDefaultActionCommunityName1 OBJECT-TYPE
    SYNTAX      TCommunityName
    MAX-ACCESS  read-create
    STATUS      obsolete
    DESCRIPTION
        "Community name to add, remove, or replace, to any
         existing community for the route.  Ignored when
         tRPAdminPSDefaultActionCommunity1 is none(1).

         This object is obsoleted in release 11.0. It is replaced by
         tRPAdminPSDefActionAddCommEntry, tRPAdminPSDefActionRemCommEntry, and
         tRPAdminPSDefActionRepCommEntry."
    DEFVAL      { ''H }
    ::= { tRPAdminPSDefaultActionParamsEntry 6 }

tRPAdminPSDefaultActionCommunity2 OBJECT-TYPE
    SYNTAX      TPolicyEntryEdit
    MAX-ACCESS  read-create
    STATUS      obsolete
    DESCRIPTION
        "How to apply tRPAdminPSDefaultActionCommunityName2 to the communities
         for the route.

         Set to none(1) to disable this feature.

         This object is obsoleted in release 11.0. It is replaced by
         tRPAdminPSDefActionAddCommEntry, tRPAdminPSDefActionRemCommEntry, and
         tRPAdminPSDefActionRepCommEntry."
    DEFVAL      { none }
    ::= { tRPAdminPSDefaultActionParamsEntry 7 }

tRPAdminPSDefaultActionCommunityName2 OBJECT-TYPE
    SYNTAX      TCommunityName
    MAX-ACCESS  read-create
    STATUS      obsolete
    DESCRIPTION
        "Community name to add, remove, or replace, to any
         existing community for the route.  Ignored when
         tRPAdminPSDefaultActionCommunity2 is none(1).

         This object is obsoleted in release 11.0. It is replaced by
         tRPAdminPSDefActionAddCommEntry, tRPAdminPSDefActionRemCommEntry, and
         tRPAdminPSDefActionRepCommEntry."
    DEFVAL      { ''H }
    ::= { tRPAdminPSDefaultActionParamsEntry 8 }

tRPAdminPSDefaultActionOrigin    OBJECT-TYPE
    SYNTAX      TPolicyEntryCriteriaOrigin
    MAX-ACCESS  read-create
    STATUS      current
    DESCRIPTION
        "The value of tRPAdminPSDefaultActionOrigin specifies the origin of the
         route exported into BGP if it does not match an entry.

         The value of this object tRPAdminPSDefaultActionOrigin is ignored when
         the object tRPAdminPSDefActOriginSource has a value different from
         actionValue(1)."
    DEFVAL      { none }
    ::= { tRPAdminPSDefaultActionParamsEntry 9 }

tRPAdminPSDefaultActionLocalPreferenceSet OBJECT-TYPE
    SYNTAX      TruthValue
    MAX-ACCESS  read-create
    STATUS      current
    DESCRIPTION
        "When set to true(1), use the value of
         tRPAdminPSDefaultActionLocalPreference for local preference.

         When the value of tRPAdminPSDefActLocalPrefSource has a value
         different from actionValue(1), the value of
         tRPAdminPSDefaultActionLocalPreferenceSet and
         tRPAdminPSDefActLocalPrefSource are ignored."
    DEFVAL      { false }
    ::= { tRPAdminPSDefaultActionParamsEntry 10 }

tRPAdminPSDefaultActionLocalPreference OBJECT-TYPE
    SYNTAX      TmnxBgpLocalPreference
    MAX-ACCESS  read-create
    STATUS      current
    DESCRIPTION
        "Local preference to apply to the route. Set
         tRPAdminPSDefaultActionLocalPreferenceSet to false(2) to disable.

         The value of this object tRPAdminPSDefaultActionLocalPreference is
         ignored when the object tRPAdminPSDefActLocalPrefSource has a value
         different from actionValue(1)."
    DEFVAL      { 0 }
    ::= { tRPAdminPSDefaultActionParamsEntry 11 }

tRPAdminPSDefaultActionMetric    OBJECT-TYPE
    SYNTAX      TPolicyEntryEdit
    MAX-ACCESS  read-create
    STATUS      current
    DESCRIPTION
        "Action for tRPAdminPSDefaultActionMetricValue or the metric value
         resolved from tRPAdminPSDefActMetricParam depending on the
         tRPAdminPSDefActionMetricSource."
    DEFVAL      { none }
    ::= { tRPAdminPSDefaultActionParamsEntry 12 }

tRPAdminPSDefaultActionMetricValue OBJECT-TYPE
    SYNTAX      Unsigned32
    MAX-ACCESS  read-create
    STATUS      current
    DESCRIPTION
        "Add, subtract, or set metric value.  Ignored when
         tRPAdminPSDefaultActionMetric is none(1).

         The value of this object tRPAdminPSDefaultActionMetricValue is ignored
         when the object tRPAdminPSDefActionMetricSource is set to a value
         different from metricVal(2)."
    DEFVAL      { 0 }
    ::= { tRPAdminPSDefaultActionParamsEntry 13 }

tRPAdminPSDefaultActionPreference OBJECT-TYPE
    SYNTAX      TmnxBgpPreference
    MAX-ACCESS  read-create
    STATUS      current
    DESCRIPTION
        "Preference to apply to the route.

         The value of this object tRPAdminPSDefaultActionPreference is ignored
         when the object tRPAdminPSDefActPreferenceSource has a value different
         from actionValue(1)."
    DEFVAL      { 0 }
    ::= { tRPAdminPSDefaultActionParamsEntry 15 }

tRPAdminPSDefaultActionDamping   OBJECT-TYPE
    SYNTAX      TDampingName
    MAX-ACCESS  read-create
    STATUS      current
    DESCRIPTION
        "Damping to apply to route.  Set to empty string to disable."
    DEFVAL      { ''H }
    ::= { tRPAdminPSDefaultActionParamsEntry 16 }

tRPAdminPSDefaultActionNextHopSelf OBJECT-TYPE
    SYNTAX      TruthValue
    MAX-ACCESS  read-create
    STATUS      current
    DESCRIPTION
        "The value of tRPAdminPSDefaultActionNextHopSelf specifies the
         next-hop-self on the route.

         Next-hop-self cannot be set to 'true' at the same time as setting the
         other next-hop objects to a non-default value.

         Setting this object to 'true' will reset
         tRPAdminPSDefActNextHopPeerAddr, tRPAdminPSDefaultActionNextHop,
         tRPAdminPSDefActInetNextHopType, tRPAdminPSDefActInetNextHop,
         tRPAdminPSDefActNextHopSource and tRPAdminPSDefActNextHopParam."
    DEFVAL      { false }
    ::= { tRPAdminPSDefaultActionParamsEntry 17 }

tRPAdminPSDefaultActionNextHop   OBJECT-TYPE
    SYNTAX      IpAddress
    MAX-ACCESS  read-create
    STATUS      current
    DESCRIPTION
        "The value of tRPAdminPSDefaultActionNextHop indicates the next-hop
         IPv4 address in the route.

         The object is disabled if it holds the value 255.255.255.255.

         Next-hop cannot be set to a valid IP address at the same time as
         setting next-hop-self or peer-address to 'true'. Setting this object
         to a valid IP address will reset tRPAdminPSDefaultActionNextHopSelf
         and tRPAdminPSDefActNextHopPeerAddr to 'false'.

         This object is the same as tRPAdminPSDefActInetNextHop when a valid
         IPv4 address is set. Please use tRPAdminPSDefActInetNextHop,
         tRPAdminPSDefActInetNextHop, tRPAdminPSDefActNextHopSource and
         tRPAdminPSDefActNextHopParam for extended next-hop address support."
    DEFVAL      { 'FFFFFFFF'H }
    ::= { tRPAdminPSDefaultActionParamsEntry 18 }

tRPAdminPSDefaultActionTag       OBJECT-TYPE
    SYNTAX      TPolicyActionTag
    MAX-ACCESS  read-create
    STATUS      current
    DESCRIPTION
        "The value of tRPAdminPSDefaultActionTag specifies the tag for the
         route.

         A value of 0 for tRPAdminPSDefaultActionTag specifies that tagging is
         disabled.

         The value of this object tRPAdminPSDefaultActionTag is ignored when
         the object tRPAdminPSDefActTagSource has a value different from
         actionValue(1)."
    DEFVAL      { 0 }
    ::= { tRPAdminPSDefaultActionParamsEntry 19 }

tRPAdminPSDefaultActionOspfType  OBJECT-TYPE
    SYNTAX      TOspfRouteType
    MAX-ACCESS  read-create
    STATUS      current
    DESCRIPTION
        "OSPF route type for the route.

         The value of this object tRPAdminPSDefaultActionOspfType is ignored
         when the object tRPAdminPSDefActOspfTypeSource has a value different
         from actionValue(1)."
    DEFVAL      { 0 }
    ::= { tRPAdminPSDefaultActionParamsEntry 20 }

tRPAdminPSDefActInetNextHopType  OBJECT-TYPE
    SYNTAX      InetAddressType
    MAX-ACCESS  read-create
    STATUS      current
    DESCRIPTION
        "The value of tRPAdminPSDefActInetNextHopType specifies the type of
         tRPAdminPSDefActInetNextHop address, as defined in the InetAddress
         MIB.

         The value of this object tRPAdminPSDefActInetNextHopType and
         tRPAdminPSDefActInetNextHop are ignored when the object
         tRPAdminPSDefActNextHopSource has a value different then
         actionValue(1)."
    ::= { tRPAdminPSDefaultActionParamsEntry 21 }

tRPAdminPSDefActInetNextHop      OBJECT-TYPE
    SYNTAX      InetAddress (SIZE (4|16))
    MAX-ACCESS  read-create
    STATUS      current
    DESCRIPTION
        "The value of tRPAdminPSDefActInetNextHop specifies the next-hop IP
         address in the route. To disable, tRPAdminPSDefActInetNextHopType
         should be set to 'ipv6' and tRPAdminPSDefActInetNextHop should be set
         to ffff:ffff:ffff:ffff:ffff:ffff:ffff:ffff.

         The type of this address is determined by the value of
         tRPAdminPSDefActInetNextHopType object.

         Next-hop cannot be set to a valid IP address at the same time as
         setting the next-hop-self or peer-address to 'true'. Setting this
         object to a valid IP address will reset
         tRPAdminPSDefaultActionNextHopSelf and
         tRPAdminPSDefActNextHopPeerAddr to 'false'.

         tRPAdminPSDefActInetNextHop object replaces
         tRPAdminPSDefaultActionNextHop that supports only IPv4 address style
         next-hop.

         The value of this object tRPAdminPSDefActInetNextHop is ignored when
         the object tRPAdminPSDefActNextHopSource has a value different from
         actionValue(1)."
    ::= { tRPAdminPSDefaultActionParamsEntry 22 }

tRPAdminPSDefaultActionASPathPnd OBJECT-TYPE
    SYNTAX      InetAutonomousSystemNumber
    MAX-ACCESS  read-create
    STATUS      current
    DESCRIPTION
        "The value of tRPAdminPSDefaultActionASPathPnd specifies the AS Number
         to prepend to the AS-Path attribute of the route.

         The AS-Path prepending is disabled when the repeat count is set to
         zero; i.e. when tRPAdminPSDefaultActionASPathPrependCount is zero and
         tRPAdminPSDefActASPPendCountSrc is set to actionValue(1).

         The value of this object tRPAdminPSDefaultActionASPathPnd is ignored
         when the object tRPAdminPSDefActASPathPendSource has a value different
         from actionValue(1)."
    DEFVAL      { 0 }
    ::= { tRPAdminPSDefaultActionParamsEntry 23 }

tRPAdminPSDefActMcRedirSvcId     OBJECT-TYPE
    SYNTAX      TmnxServId
    MAX-ACCESS  read-create
    STATUS      current
    DESCRIPTION
        "The value of tRPAdminPSDefActMcRedirSvcId specifies the service ID of
         the service where to redirect IGMP/MLD multicast traffic to.

         The value zero means that no multicast redirection is configured."
    DEFVAL      { 0 }
    ::= { tRPAdminPSDefaultActionParamsEntry 30 }

tRPAdminPSDefActMcRedirIfIndex   OBJECT-TYPE
    SYNTAX      InterfaceIndexOrZero
    MAX-ACCESS  read-create
    STATUS      current
    DESCRIPTION
        "The value of tRPAdminPSDefActMcRedirIfIndex specifies the interface
         index of the interface where to redirect IGMP/MLD multicast traffic
         to.

         The value zero means that no multicast redirection is configured."
    DEFVAL      { 0 }
    ::= { tRPAdminPSDefaultActionParamsEntry 31 }

tRPAdminPSDefActionMetricSource  OBJECT-TYPE
    SYNTAX      TPolicyActionMetricSource
    MAX-ACCESS  read-create
    STATUS      current
    DESCRIPTION
        "The value of tRPAdminPSDefActionMetricSource specifies the source of
         the default action metric.

         This object should only be set to igpCost(1) when the object
         tRPAdminPSDefaultActionMetric is set to replace(4).

         When the value of tRPAdminPSDefActionMetricSource is set to
         'igpCost(1)', the value of tRPAdminPSDefaultActionMetricValue and
         tRPAdminPSDefActMetricParam are ignored; and the value of MED (Multi
         Exit Discriminator) or the metric value is derived from the IGP
         (Interior Gateway Protocol) cost of the route.

         The default value of tRPAdminPSDefActionMetricSource is 'metricVal(2)'
         which means the metric value is the value of
         tRPAdminPSDefaultActionMetricValue. The value of the object
         tRPAdminPSDefActMetricParam is ignored.

         The value 'metricParam(3) means the metric value is derived from the
         object tRPAdminPSDefActMetricParam; the value of the object
         tRPAdminPSDefaultActionMetricValue is ignored."
    DEFVAL      { metricVal }
    ::= { tRPAdminPSDefaultActionParamsEntry 32 }

tRPAdminPSDefActionAigpMetric    OBJECT-TYPE
    SYNTAX      TPolicyEntryAigpMetricEdit
    MAX-ACCESS  read-create
    STATUS      current
    DESCRIPTION
        "The value of tRPAdminPSDefActionAigpMetric specifies the editing
         action to be taken for the AIGP (Accumulated IGP) attribute when the
         route satisfies the match criteria of the policy.

         The value of tRPAdminPSDefActionAigpMetric decides how to apply
         tRPAdminPSDefActnAigpMetricVal to the route. When the value of
         tRPAdminPSDefActionAigpMetric is set to 'none(1)' or 'useIgp(4)', the
         value of tRPAdminPSDefActnAigpMetricVal,
         tRPAdminPSDefActAigpMetricSource and tRPAdminPSDefActAigpMetricParam
         are ignored."
    DEFVAL      { none }
    ::= { tRPAdminPSDefaultActionParamsEntry 33 }

tRPAdminPSDefActnAigpMetricVal   OBJECT-TYPE
    SYNTAX      Unsigned32
    MAX-ACCESS  read-create
    STATUS      current
    DESCRIPTION
        "The value of tRPAdminPSDefActnAigpMetricVal specifies the value to add
         or set for the route AIGP(Accumulated IGP) metric.

         When the value of tRPAdminPSDefActionAigpMetric is set to 'none(1)' or
         'useIgp(4)', the value of tRPAdminPSDefActnAigpMetricVal is ignored.

         The value of this object tRPAdminPSDefActnAigpMetricVal is ignored
         when the object tRPAdminPSDefActAigpMetricSource has a value different
         from actionValue(1)."
    DEFVAL      { 0 }
    ::= { tRPAdminPSDefaultActionParamsEntry 34 }

tRPAdminPSDefActnSrcClassIndex   OBJECT-TYPE
    SYNTAX      ClassIndexOrNone
    MAX-ACCESS  read-create
    STATUS      current
    DESCRIPTION
        "The value of tRPAdminPSDefActnSrcClassIndex specifies the default
         admin source-class for this policy statement.

         A value of 0 means no source-class."
    DEFVAL      { 0 }
    ::= { tRPAdminPSDefaultActionParamsEntry 35 }

tRPAdminPSDefActnDstClassIndex   OBJECT-TYPE
    SYNTAX      ClassIndexOrNone
    MAX-ACCESS  read-create
    STATUS      current
    DESCRIPTION
        "The value of tRPAdminPSDefActnDstClassIndex specifies the default
         admin dest-class for this policy statement.

         A value of 0 means no dest-class."
    DEFVAL      { 0 }
    ::= { tRPAdminPSDefaultActionParamsEntry 36 }

tRPAdminPSDefActnOrigValidState  OBJECT-TYPE
    SYNTAX      INTEGER {
        notApplicable (0),
        valid         (1),
        notFound      (2),
        invalid       (3)
    }
    MAX-ACCESS  read-create
    STATUS      current
    DESCRIPTION
        "The value of tRPAdminPSDefActnOrigValidState specifies the default
         origin validation state for this policy statement.

         The value of this object tRPAdminPSDefActnOrigValidState is ignored
         when the object tRPAdminPSDefActOrigValStateSrc has a value different
         from actionValue(1)."
    DEFVAL      { notApplicable }
    ::= { tRPAdminPSDefaultActionParamsEntry 37 }

tRPAdminPSParamsTable            OBJECT-TYPE
    SYNTAX      SEQUENCE OF TRPAdminPSParamsEntry
    MAX-ACCESS  not-accessible
    STATUS      current
    DESCRIPTION
        "A table of policy statement entries."
    ::= { tRPAdminValueObjects 7 }

tRPAdminPSParamsEntry            OBJECT-TYPE
    SYNTAX      TRPAdminPSParamsEntry
    MAX-ACCESS  not-accessible
    STATUS      current
    DESCRIPTION
        "Information about a particular policy statement entry.

         Entries are created and deleted by the user."
    INDEX       {
        tRPAdminPolicyStatementName,
        tRPAdminPSNameEntryIndex
    }
    ::= { tRPAdminPSParamsTable 1 }

TRPAdminPSParamsEntry            ::= SEQUENCE
{
    tRPAdminPSNameEntryIndex         TPolicyStatementEntryID,
    tRPAdminPSParamsRowStatus        RowStatus,
    tRPAdminPSParamsDescription      TItemDescription,
    tRPAdminPSParamsAction           TPolicyEntryAction,
    tRPAdminPSParamsCreationOrigin   TmnxCreateOrigin
}

tRPAdminPSNameEntryIndex         OBJECT-TYPE
    SYNTAX      TPolicyStatementEntryID
    MAX-ACCESS  not-accessible
    STATUS      current
    DESCRIPTION
        "The ID of this policy statement entry."
    ::= { tRPAdminPSParamsEntry 1 }

tRPAdminPSParamsRowStatus        OBJECT-TYPE
    SYNTAX      RowStatus
    MAX-ACCESS  read-create
    STATUS      current
    DESCRIPTION
        "tRPAdminPSParamsRowStatus specifies the RowStatus for this row.

         To Create a row, set this object to createAndGo(4). When
         tRPAdminControlApply is set to commit(3), the row will actually be
         created in the tRPOperPSParamsTable.

         To destroy a row, set this object to destroy(6). When
         tRPAdminControlApply is set to commit(3) the row will actually be
         removed from the tRPOperPSParamsTable."
    ::= { tRPAdminPSParamsEntry 2 }

tRPAdminPSParamsDescription      OBJECT-TYPE
    SYNTAX      TItemDescription
    MAX-ACCESS  read-create
    STATUS      current
    DESCRIPTION
        "Description for this policy statement entry."
    DEFVAL      { ''H }
    ::= { tRPAdminPSParamsEntry 3 }

tRPAdminPSParamsAction           OBJECT-TYPE
    SYNTAX      TPolicyEntryAction
    MAX-ACCESS  read-create
    STATUS      current
    DESCRIPTION
        "The action to take when a route matches this policy statement entry's
         to or from criteria."
    ::= { tRPAdminPSParamsEntry 4 }

tRPAdminPSParamsCreationOrigin   OBJECT-TYPE
    SYNTAX      TmnxCreateOrigin
    MAX-ACCESS  read-only
    STATUS      current
    DESCRIPTION
        "The value of the object tRPAdminPSParamsCreationOrigin indicates the
         mechanism used to create this entry."
    ::= { tRPAdminPSParamsEntry 5 }

tRPAdminPSAcceptActionParamsTable OBJECT-TYPE
    SYNTAX      SEQUENCE OF TRPAdminPSAcceptActionParamsEntry
    MAX-ACCESS  not-accessible
    STATUS      current
    DESCRIPTION
        "Accept-action parameters for a policy statement."
    ::= { tRPAdminValueObjects 8 }

tRPAdminPSAcceptActionParamsEntry OBJECT-TYPE
    SYNTAX      TRPAdminPSAcceptActionParamsEntry
    MAX-ACCESS  not-accessible
    STATUS      current
    DESCRIPTION
        "Accept-action information for a particular policy statement entry.

         Entries are created when tRPAdminPSParamsAction is set to 'accept(1)',
         'reject(2)', 'continue(3)' or 'nextPolicy(4)'. Entries are deleted
         when a policy statement is destroyed or tRPAdminPSParamsAction is set
         to value 'none(0)'."
    INDEX       {
        tRPAdminPolicyStatementName,
        tRPAdminPSNameEntryIndex
    }
    ::= { tRPAdminPSAcceptActionParamsTable 1 }

TRPAdminPSAcceptActionParamsEntry ::= SEQUENCE
{
    tRPAdminPSAcceptActionASPath     TPolicyEntryEdit,
    tRPAdminPSAcceptActionASPathName TASPathName,
    tRPAdminPSAcceptActionASPathPrependAS TmnxBgpAutonomousSystem,
    tRPAdminPSAcceptActionASPathPrependCount Integer32,
    tRPAdminPSAcceptActionCommunity1 TPolicyEntryEdit,
    tRPAdminPSAcceptActionCommunityName1 TCommunityName,
    tRPAdminPSAcceptActionCommunity2 TPolicyEntryEdit,
    tRPAdminPSAcceptActionCommunityName2 TCommunityName,
    tRPAdminPSAcceptActionOrigin     TPolicyEntryCriteriaOrigin,
    tRPAdminPSAcceptActionLocalPreferenceSet TruthValue,
    tRPAdminPSAcceptActionLocalPreference TmnxBgpLocalPreference,
    tRPAdminPSAcceptActionMetric     TPolicyEntryEdit,
    tRPAdminPSAcceptActionMetricValue Unsigned32,
    tRPAdminPSAcceptActionPreference TmnxBgpPreference,
    tRPAdminPSAcceptActionDamping    TDampingName,
    tRPAdminPSAcceptActionNextHopSelf TruthValue,
    tRPAdminPSAcceptActionNextHop    IpAddress,
    tRPAdminPSAcceptActionTag        TPolicyActionTag,
    tRPAdminPSAcceptActionOspfType   TOspfRouteType,
    tRPAdminPSAcptActInetNextHopType InetAddressType,
    tRPAdminPSAcptActInetNextHop     InetAddress,
    tRPAdminPSAcceptActionASPathPend InetAutonomousSystemNumber,
    tRPAdminPSAcceptActionFC         TNamedItemOrEmpty,
    tRPAdminPSAcceptActionFCPriority TPriorityOrUndefined,
    tRPAdminPSAcptActMcRedirSvcId    TmnxServId,
    tRPAdminPSAcptActMcRedirIfIndex  InterfaceIndexOrZero,
    tRPAdminPSAcptActnMetricSource   TPolicyActionMetricSource,
    tRPAdminPSAcptActionAigpMetric   TPolicyEntryAigpMetricEdit,
    tRPAdminPSAcptActnAigpMetricVal  Unsigned32,
    tRPAdminPSAcptActnSrcClassIndex  ClassIndexOrNone,
    tRPAdminPSAcptActnDstClassIndex  ClassIndexOrNone,
    tRPAdminPSAcptActnOrigValidState INTEGER
}

tRPAdminPSAcceptActionASPath     OBJECT-TYPE
    SYNTAX      TPolicyEntryEdit
    MAX-ACCESS  read-create
    STATUS      current
    DESCRIPTION
        "The AS Path rewrite information for the route."
    DEFVAL      { none }
    ::= { tRPAdminPSAcceptActionParamsEntry 1 }

tRPAdminPSAcceptActionASPathName OBJECT-TYPE
    SYNTAX      TASPathName
    MAX-ACCESS  read-create
    STATUS      current
    DESCRIPTION
        "AS Path Name to add, remove, or replace. Ignored when
         tRPAdminPSAcceptActionASPath is none(1)"
    DEFVAL      { ''H }
    ::= { tRPAdminPSAcceptActionParamsEntry 2 }

tRPAdminPSAcceptActionASPathPrependAS OBJECT-TYPE
    SYNTAX      TmnxBgpAutonomousSystem
    MAX-ACCESS  read-create
    STATUS      obsolete
    DESCRIPTION
        "AS Number to prepend to the AS-Path attribute of the route. Ignored
         when tRPAdminPSAcceptActionASPathPrependCount is zero.

         This object was obsoleted in release 7.0.  It is replaced with the
         4-byte AS number defined by tRPAdminPSAcceptActionASPathPend."
    DEFVAL      { 0 }
    ::= { tRPAdminPSAcceptActionParamsEntry 3 }

tRPAdminPSAcceptActionASPathPrependCount OBJECT-TYPE
    SYNTAX      Integer32 (0..50)
    MAX-ACCESS  read-create
    STATUS      current
    DESCRIPTION
        "Number of times to prepend tRPAdminPSAcceptActionASPathPend to the
         route.

         Set to zero to disable this feature.

         The value of this object tRPAdminPSAcceptActionASPathPrependCount is
         ignored when the object tRPAdminPSAcptActASPPendCountSrc has a value
         different from actionValue(1)."
    DEFVAL      { 0 }
    ::= { tRPAdminPSAcceptActionParamsEntry 4 }

tRPAdminPSAcceptActionCommunity1 OBJECT-TYPE
    SYNTAX      TPolicyEntryEdit
    MAX-ACCESS  read-create
    STATUS      obsolete
    DESCRIPTION
        "How to apply tRPAdminPSAcceptActionCommunityName1 to the route.

         This object is obsoleted in release 11.0. It is replaced by
         tRPAdminPSAccActionAddCommEntry, tRPAdminPSAccActionRemCommEntry, and
         tRPAdminPSAccActionRepCommEntry."
    DEFVAL      { none }
    ::= { tRPAdminPSAcceptActionParamsEntry 5 }

tRPAdminPSAcceptActionCommunityName1 OBJECT-TYPE
    SYNTAX      TCommunityName
    MAX-ACCESS  read-create
    STATUS      obsolete
    DESCRIPTION
        "Community to apply to the route.  Ignored when
         tRPAdminPSAcceptActionCommunity1 is set to none(1).

         This object is obsoleted in release 11.0. It is replaced by
         tRPAdminPSAccActionAddCommEntry, tRPAdminPSAccActionRemCommEntry, and
         tRPAdminPSAccActionRepCommEntry."
    DEFVAL      { ''H }
    ::= { tRPAdminPSAcceptActionParamsEntry 6 }

tRPAdminPSAcceptActionCommunity2 OBJECT-TYPE
    SYNTAX      TPolicyEntryEdit
    MAX-ACCESS  read-create
    STATUS      obsolete
    DESCRIPTION
        "How to apply tRPAdminPSAcceptActionCommunityName2 to the route.

         This object is obsoleted in release 11.0. It is replaced by
         tRPAdminPSAccActionAddCommEntry, tRPAdminPSAccActionRemCommEntry, and
         tRPAdminPSAccActionRepCommEntry."
    DEFVAL      { none }
    ::= { tRPAdminPSAcceptActionParamsEntry 7 }

tRPAdminPSAcceptActionCommunityName2 OBJECT-TYPE
    SYNTAX      TCommunityName
    MAX-ACCESS  read-create
    STATUS      obsolete
    DESCRIPTION
        "Community to apply to the route.  Ignored when
         tRPAdminPSAcceptActionCommunity2 is set to none(1).

         This object is obsoleted in release 11.0. It is replaced by
         tRPAdminPSAccActionAddCommEntry, tRPAdminPSAccActionRemCommEntry, and
         tRPAdminPSAccActionRepCommEntry."
    DEFVAL      { ''H }
    ::= { tRPAdminPSAcceptActionParamsEntry 8 }

tRPAdminPSAcceptActionOrigin     OBJECT-TYPE
    SYNTAX      TPolicyEntryCriteriaOrigin
    MAX-ACCESS  read-create
    STATUS      current
    DESCRIPTION
        "The value of tRPAdminPSAcceptActionOrigin specifies the origin of the
         route exported into BGP if it matches an entry.

         The value of this object tRPAdminPSAcceptActionOrigin is ignored when
         the object tRPAdminPSAcptActOriginSource has a value different from
         actionValue(1)."
    DEFVAL      { none }
    ::= { tRPAdminPSAcceptActionParamsEntry 9 }

tRPAdminPSAcceptActionLocalPreferenceSet OBJECT-TYPE
    SYNTAX      TruthValue
    MAX-ACCESS  read-create
    STATUS      current
    DESCRIPTION
        "When set to true(1), use tRPAdminPSAcceptActionLocalPreference for the
         local preference for the route.

         When the value of tRPAdminPSAcptActLocalPrefSource has a value
         different from actionValue(1), the value of
         tRPAdminPSAcceptActionLocalPreferenceSet and
         tRPAdminPSAcceptActionLocalPreference are ignored."
    DEFVAL      { false }
    ::= { tRPAdminPSAcceptActionParamsEntry 10 }

tRPAdminPSAcceptActionLocalPreference OBJECT-TYPE
    SYNTAX      TmnxBgpLocalPreference
    MAX-ACCESS  read-create
    STATUS      current
    DESCRIPTION
        "Local preference for the route. Ignored when
         tRPAdminPSAcceptActionLocalPreferenceSet is false(2).

         The value of this object tRPAdminPSAcceptActionLocalPreference is
         ignored when the object tRPAdminPSAcptActLocalPrefSource has a value
         different from actionValue(1)."
    DEFVAL      { 0 }
    ::= { tRPAdminPSAcceptActionParamsEntry 11 }

tRPAdminPSAcceptActionMetric     OBJECT-TYPE
    SYNTAX      TPolicyEntryEdit
    MAX-ACCESS  read-create
    STATUS      current
    DESCRIPTION
        "How to apply the metric value to the route.

         The metric value is obtained from tRPAdminPSAcceptActionMetricValue or
         tRPAdminPSAcptActMetricParam depending on the value of
         tRPAdminPSAcptActnMetricSource."
    DEFVAL      { none }
    ::= { tRPAdminPSAcceptActionParamsEntry 12 }

tRPAdminPSAcceptActionMetricValue OBJECT-TYPE
    SYNTAX      Unsigned32
    MAX-ACCESS  read-create
    STATUS      current
    DESCRIPTION
        "Value to add, subtract, or set for the route metric. Ignored when
         tRPAdminPSAcceptActionMetric is none(1).

         The value of this object tRPAdminPSAcceptActionMetricValue is ignored
         when the object tRPAdminPSAcptActnMetricSource is set to a value
         different from metricVal(2)."
    DEFVAL      { 0 }
    ::= { tRPAdminPSAcceptActionParamsEntry 13 }

tRPAdminPSAcceptActionPreference OBJECT-TYPE
    SYNTAX      TmnxBgpPreference
    MAX-ACCESS  read-create
    STATUS      current
    DESCRIPTION
        "Preference to set in route.

         The value of this object tRPAdminPSAcceptActionPreference is ignored
         when the object tRPAdminPSAcptActPreferenceSrc has a value different
         from actionValue(1)."
    DEFVAL      { 0 }
    ::= { tRPAdminPSAcceptActionParamsEntry 15 }

tRPAdminPSAcceptActionDamping    OBJECT-TYPE
    SYNTAX      TDampingName
    MAX-ACCESS  read-create
    STATUS      current
    DESCRIPTION
        "Damping to apply to route.  Set to empty string to disable."
    DEFVAL      { ''H }
    ::= { tRPAdminPSAcceptActionParamsEntry 16 }

tRPAdminPSAcceptActionNextHopSelf OBJECT-TYPE
    SYNTAX      TruthValue
    MAX-ACCESS  read-create
    STATUS      current
    DESCRIPTION
        "The value of tRPAdminPSAcceptActionNextHopSelf specifies the
         next-hop-self on the route.

         Next-hop-self cannot be set to 'true' at the same time as setting the
         other next-hop objects to a non-default value.

         Setting this object to 'true' will reset
         tRPAdminPSAcptActNextHopPeerAddr, tRPAdminPSAcceptActionNextHop,
         tRPAdminPSAcptActInetNextHopType, tRPAdminPSAcptActInetNextHop,
         tRPAdminPSAcptActNextHopSource and tRPAdminPSAcptActNextHopParam."
    DEFVAL      { false }
    ::= { tRPAdminPSAcceptActionParamsEntry 17 }

tRPAdminPSAcceptActionNextHop    OBJECT-TYPE
    SYNTAX      IpAddress
    MAX-ACCESS  read-create
    STATUS      current
    DESCRIPTION
        "The value of tRPAdminPSAcceptActionNextHop indicates the next-hop IPv4
         address in the route.

         The object is disabled if it holds the value 255.255.255.255.

         Next-hop cannot be set to a valid IP address at the same time as
         setting next-hop-self or peer-address to 'true'. Setting this object
         to a valid IP address will reset tRPAdminPSAcceptActionNextHopSelf and
         tRPAdminPSAcptActNextHopPeerAddr to 'false'.

         This object is the same as tRPAdminPSAcptActInetNextHop when a valid
         IPv4 address is set. Please use tRPAdminPSAcptActInetNextHop,
         tRPAdminPSAcptActInetNextHopType, tRPAdminPSAcptActNextHopSource and
         tRPAdminPSAcptActNextHopParam for extended next-hop address support."
    DEFVAL      { 'FFFFFFFF'H }
    ::= { tRPAdminPSAcceptActionParamsEntry 18 }

tRPAdminPSAcceptActionTag        OBJECT-TYPE
    SYNTAX      TPolicyActionTag
    MAX-ACCESS  read-create
    STATUS      current
    DESCRIPTION
        "The value of tRPAdminPSAcceptActionTag specifies the tag for the
         route.

         A value of 0 for tRPAdminPSAcceptActionTag when specifies that tagging
         is disabled."
    DEFVAL      { 0 }
    ::= { tRPAdminPSAcceptActionParamsEntry 19 }

tRPAdminPSAcceptActionOspfType   OBJECT-TYPE
    SYNTAX      TOspfRouteType
    MAX-ACCESS  read-create
    STATUS      current
    DESCRIPTION
        "OSPF route type to set in route."
    DEFVAL      { 0 }
    ::= { tRPAdminPSAcceptActionParamsEntry 20 }

tRPAdminPSAcptActInetNextHopType OBJECT-TYPE
    SYNTAX      InetAddressType
    MAX-ACCESS  read-create
    STATUS      current
    DESCRIPTION
        "The value of tRPAdminPSAcptActInetNextHopType specifies the type of
         tRPAdminPSAcptActInetNextHop address, as defined in the InetAddress
         MIB.

         The value of this object tRPAdminPSAcptActInetNextHopType and
         tRPAdminPSAcptActInetNextHop are ignored when the object
         tRPAdminPSAcptActNextHopSource has a value different then
         actionValue(1)."
    ::= { tRPAdminPSAcceptActionParamsEntry 21 }

tRPAdminPSAcptActInetNextHop     OBJECT-TYPE
    SYNTAX      InetAddress (SIZE (4|16))
    MAX-ACCESS  read-create
    STATUS      current
    DESCRIPTION
        "The value of tRPAdminPSAcptActInetNextHop specifies the next-hop IP
         address in the route. To disable, tRPAdminPSAcptActInetNextHopType
         should be set to 'ipv6' and tRPAdminPSAcptActInetNextHop should be set
         to ffff:ffff:ffff:ffff:ffff:ffff:ffff:ffff.

         The type of this address is determined by the value of the
         tRPAdminPSAcptActInetNextHopType object.

         Next-hop cannot be set to a valid IP address at the same time as
         setting the next-hop-self or peer-address to 'true'. Setting this
         object to a valid IP address will reset
         tRPAdminPSAcceptActionNextHopSelf and
         tRPAdminPSAcptActNextHopPeerAddr to 'false'.

         tRPAdminPSAcptActInetNextHop object replaces
         tRPAdminPSAcceptActionNextHop that supports only IPv4 address style
         next-hop.

         The value of this object tRPAdminPSAcptActInetNextHop is ignored when
         the object tRPAdminPSAcptActNextHopSource has a value different from
         actionValue(1)."
    ::= { tRPAdminPSAcceptActionParamsEntry 22 }

tRPAdminPSAcceptActionASPathPend OBJECT-TYPE
    SYNTAX      InetAutonomousSystemNumber
    MAX-ACCESS  read-create
    STATUS      current
    DESCRIPTION
        "The value of tRPAdminPSAcceptActionASPathPend specifies the AS Number
         to prepend to the AS-Path attribute of the route.

         The AS-Path prepending is disabled when the repeat count is set to
         zero; i.e. when tRPAdminPSAcceptActionASPathPrependCount is zero and
         tRPAdminPSAcptActASPPendCountSrc is set to actionValue(1).

         The value of this object tRPAdminPSAcceptActionASPathPend is ignored
         when the object tRPAdminPSAcptActASPathPendSrc has a value different
         from actionValue(1)."
    DEFVAL      { 0 }
    ::= { tRPAdminPSAcceptActionParamsEntry 23 }

tRPAdminPSAcceptActionFC         OBJECT-TYPE
    SYNTAX      TNamedItemOrEmpty
    MAX-ACCESS  read-create
    STATUS      current
    DESCRIPTION
        "The value of tRPAdminPSAcceptActionFC specifies the forwarding class
         associated with the routes matched by this route policy entry."
    DEFVAL      { ''H }
    ::= { tRPAdminPSAcceptActionParamsEntry 24 }

tRPAdminPSAcceptActionFCPriority OBJECT-TYPE
    SYNTAX      TPriorityOrUndefined
    MAX-ACCESS  read-create
    STATUS      current
    DESCRIPTION
        "The value of tRPAdminPSAcceptActionFCPriority specifies the priority
         to be assigned to the routes matched by this route policy entry."
    DEFVAL      { undefined }
    ::= { tRPAdminPSAcceptActionParamsEntry 25 }

tRPAdminPSAcptActMcRedirSvcId    OBJECT-TYPE
    SYNTAX      TmnxServId
    MAX-ACCESS  read-create
    STATUS      current
    DESCRIPTION
        "The value of tRPAdminPSAcptActMcRedirSvcId specifies the service ID of
         the service where to redirect IGMP/MLD multicast traffic to.

         The value zero means that no multicast redirection is configured."
    DEFVAL      { 0 }
    ::= { tRPAdminPSAcceptActionParamsEntry 30 }

tRPAdminPSAcptActMcRedirIfIndex  OBJECT-TYPE
    SYNTAX      InterfaceIndexOrZero
    MAX-ACCESS  read-create
    STATUS      current
    DESCRIPTION
        "The value of tRPAdminPSAcptActMcRedirIfIndex specifies the interface
         index of the interface where to redirect IGMP/MLD multicast traffic
         to.

         The value zero means that no multicast redirection is configured."
    DEFVAL      { 0 }
    ::= { tRPAdminPSAcceptActionParamsEntry 31 }

tRPAdminPSAcptActnMetricSource   OBJECT-TYPE
    SYNTAX      TPolicyActionMetricSource
    MAX-ACCESS  read-create
    STATUS      current
    DESCRIPTION
        "The value of tRPAdminPSAcptActnMetricSource specifies the source of
         the accept action metric.

         When the value of tRPAdminPSAcptActnMetricSource is set to
         'igpCost(1)' the value of tRPAdminPSAcceptActionMetricValue and
         tRPAdminPSAcptActMetricParam are ignored; and the value of MED (Multi
         Exit Discriminator) or the metric value is derived from the IGP
         (Interior Gateway Protocol) cost of the route.

         The default value of tRPAdminPSAcptActnMetricSource is 'metricVal(2)'
         which means the metric value is the value of
         tRPAdminPSAcceptActionMetricValue. The value of the object
         tRPAdminPSAcptActMetricParam is ignored.

         The value 'metricParam(3) means the metric value is derived from the
         object tRPAdminPSAcptActMetricParam; the value of the object
         tRPAdminPSAcceptActionMetricValue is ignored."
    DEFVAL      { metricVal }
    ::= { tRPAdminPSAcceptActionParamsEntry 32 }

tRPAdminPSAcptActionAigpMetric   OBJECT-TYPE
    SYNTAX      TPolicyEntryAigpMetricEdit
    MAX-ACCESS  read-create
    STATUS      current
    DESCRIPTION
        "The value of tRPAdminPSAcptActionAigpMetric specifies the editing
         action to be taken for the AIGP (Accumulated IGP) attribute when the
         route satisfies the match criteria of the policy.

         The value of tRPAdminPSAcptActionAigpMetric decides how to apply
         tRPAdminPSAcptActnAigpMetricVal to the route.

         When the value of tRPAdminPSAcptActionAigpMetric is set to 'none(1)'
         or 'useIgp(4)', the value of tRPAdminPSAcptActnAigpMetricVal,
         tRPAdminPSAcptActAigpMetricSrc and tRPAdminPSAcptActAigpMetricParam
         are ignored."
    DEFVAL      { none }
    ::= { tRPAdminPSAcceptActionParamsEntry 33 }

tRPAdminPSAcptActnAigpMetricVal  OBJECT-TYPE
    SYNTAX      Unsigned32
    MAX-ACCESS  read-create
    STATUS      current
    DESCRIPTION
        "The value of tRPAdminPSAcptActnAigpMetricVal specifies the value to
         add or set for the route AIGP(Accumulated IGP) metric.

         When the value of tRPAdminPSAcptActionAigpMetric is set to 'none(1)'
         or 'useIgp(4)', the value of tRPAdminPSAcptActnAigpMetricVal is
         ignored.

         The value of this object tRPAdminPSAcptActnAigpMetricVal is ignored
         when the object tRPAdminPSAcptActAigpMetricSrc has a value different
         from actionValue(1)."
    DEFVAL      { 0 }
    ::= { tRPAdminPSAcceptActionParamsEntry 34 }

tRPAdminPSAcptActnSrcClassIndex  OBJECT-TYPE
    SYNTAX      ClassIndexOrNone
    MAX-ACCESS  read-create
    STATUS      current
    DESCRIPTION
        "The value of tRPAdminPSAcptActnSrcClassIndex specifies the admin
         source-class for this policy statement.

         A value of 0 means no source-class."
    DEFVAL      { 0 }
    ::= { tRPAdminPSAcceptActionParamsEntry 35 }

tRPAdminPSAcptActnDstClassIndex  OBJECT-TYPE
    SYNTAX      ClassIndexOrNone
    MAX-ACCESS  read-create
    STATUS      current
    DESCRIPTION
        "The value of tRPAdminPSAcptActnDstClassIndex specifies the admin
         dest-class for this policy statement.

         A value of 0 means no dest-class."
    DEFVAL      { 0 }
    ::= { tRPAdminPSAcceptActionParamsEntry 36 }

tRPAdminPSAcptActnOrigValidState OBJECT-TYPE
    SYNTAX      INTEGER {
        notApplicable (0),
        valid         (1),
        notFound      (2),
        invalid       (3)
    }
    MAX-ACCESS  read-create
    STATUS      current
    DESCRIPTION
        "The value of tRPAdminPSAcptActnOrigValidState specifies the admin
         origin validation state for this policy statement.

         The value of this object tRPAdminPSAcptActnOrigValidState is ignored
         when the object tRPAdminPSAcptActOrigValStateSrc has a value different
         from actionValue(1)."
    DEFVAL      { notApplicable }
    ::= { tRPAdminPSAcceptActionParamsEntry 37 }

tRPAdminPSToCriteriaTable        OBJECT-TYPE
    SYNTAX      SEQUENCE OF TRPAdminPSToCriteriaEntry
    MAX-ACCESS  not-accessible
    STATUS      current
    DESCRIPTION
        "A table of policy statement entry 'to' criteria"
    ::= { tRPAdminValueObjects 9 }

tRPAdminPSToCriteriaEntry        OBJECT-TYPE
    SYNTAX      TRPAdminPSToCriteriaEntry
    MAX-ACCESS  not-accessible
    STATUS      current
    DESCRIPTION
        "Information about policy statement entry -to- criteria.

         Entries are created when a policy statement entry is created. Entries
         are deleted when a policy statement entry is destroyed."
    INDEX       {
        tRPAdminPolicyStatementName,
        tRPAdminPSToCriteriaIndex
    }
    ::= { tRPAdminPSToCriteriaTable 1 }

TRPAdminPSToCriteriaEntry        ::= SEQUENCE
{
    tRPAdminPSToCriteriaIndex        TPolicyStatementEntryID,
    tRPAdminPSToCriteriaRowStatus    RowStatus,
    tRPAdminPSToCriteriaProtocol     TRoutePolicyProtocol,
    tRPAdminPSToCriteriaNeighborIpAddr IpAddress,
    tRPAdminPSToCriteriaNeighborPrefixList TLPrefixListName,
    tRPAdminPSToCriteriaIsisLevel    TIsisLevel,
    tRPAdminPSToCriteriaPrefixList1  TLPrefixListName,
    tRPAdminPSToCriteriaPrefixList2  TLPrefixListName,
    tRPAdminPSToCriteriaPrefixList3  TLPrefixListName,
    tRPAdminPSToCriteriaPrefixList4  TLPrefixListName,
    tRPAdminPSToCriteriaPrefixList5  TLPrefixListName,
    tRPAdminPSToCritNbrInetAddrType  InetAddressType,
    tRPAdminPSToCritNbrInetAddr      InetAddress,
    tRPAdminPSToCriteriaInstanceId   Unsigned32,
    tRPAdminPSToCritProtocolBits     TRoutePolicyProtocolBits
}

tRPAdminPSToCriteriaIndex        OBJECT-TYPE
    SYNTAX      TPolicyStatementEntryID
    MAX-ACCESS  not-accessible
    STATUS      current
    DESCRIPTION
        "The policy statement entry ID"
    ::= { tRPAdminPSToCriteriaEntry 1 }

tRPAdminPSToCriteriaRowStatus    OBJECT-TYPE
    SYNTAX      RowStatus
    MAX-ACCESS  read-create
    STATUS      current
    DESCRIPTION
        "tRPAdminPSToCriteriaRowStatus specifies the RowStatus for this row.

         To Create a row, set this object to createAndGo(4). When
         tRPAdminControlApply is set to commit(3), the row will actually be
         created in the tRPOperPSToCriteriaTable.

         To destroy a row, set this object to destroy(6). When
         tRPAdminControlApply is set to commit(3) the row will actually be
         removed from the tRPOperPSToCriteriaTable."
    ::= { tRPAdminPSToCriteriaEntry 2 }

tRPAdminPSToCriteriaProtocol     OBJECT-TYPE
    SYNTAX      TRoutePolicyProtocol
    MAX-ACCESS  read-create
    STATUS      deprecated
    DESCRIPTION
        "The protocol name to match on. Set to none(1) to disable.

         This object is deprecated, please use the object
         tRPAdminPSToCritProtocolBits instead."
    DEFVAL      { none }
    ::= { tRPAdminPSToCriteriaEntry 3 }

tRPAdminPSToCriteriaNeighborIpAddr OBJECT-TYPE
    SYNTAX      IpAddress
    MAX-ACCESS  read-create
    STATUS      current
    DESCRIPTION
        "The IP address of neighbor to match on. Set to 255.255.255.255 to
         disable."
    DEFVAL      { 'FFFFFFFF'H }
    ::= { tRPAdminPSToCriteriaEntry 4 }

tRPAdminPSToCriteriaNeighborPrefixList OBJECT-TYPE
    SYNTAX      TLPrefixListName
    MAX-ACCESS  read-create
    STATUS      current
    DESCRIPTION
        "The name of a neighbor prefix list to match on. Set to empty string to
         disable."
    DEFVAL      { ''H }
    ::= { tRPAdminPSToCriteriaEntry 5 }

tRPAdminPSToCriteriaIsisLevel    OBJECT-TYPE
    SYNTAX      TIsisLevel
    MAX-ACCESS  read-create
    STATUS      current
    DESCRIPTION
        "The value for tRPAdminPSToCriteriaIsisLevel defines the IS-IS route
         level match criterion. A value of 0 indicates that no IS-IS route
         level match criterion has been configured."
    DEFVAL      { 0 }
    ::= { tRPAdminPSToCriteriaEntry 7 }

tRPAdminPSToCriteriaPrefixList1  OBJECT-TYPE
    SYNTAX      TLPrefixListName
    MAX-ACCESS  read-create
    STATUS      current
    DESCRIPTION
        "The value of tRPAdminPSToCriteriaPrefixList1 specifies the name of the
         first prefix list to match on. Setting this value to an empty string
         disables this prefix list as a match criteria.

         This object is the same as tRPAdminPSToCritPrefixList1, please use
         tRPAdminPSToCritPfxListTable to match on more prefix lists."
    DEFVAL      { ''H }
    ::= { tRPAdminPSToCriteriaEntry 8 }

tRPAdminPSToCriteriaPrefixList2  OBJECT-TYPE
    SYNTAX      TLPrefixListName
    MAX-ACCESS  read-create
    STATUS      current
    DESCRIPTION
        "The value of tRPAdminPSToCriteriaPrefixList2 specifies the name of the
         second prefix list to match on. Setting this value to an empty string
         disables this prefix list as a match criteria.

         This object is the same as tRPAdminPSToCritPrefixList2, please use
         tRPAdminPSToCritPfxListTable to match on more prefix lists."
    DEFVAL      { ''H }
    ::= { tRPAdminPSToCriteriaEntry 9 }

tRPAdminPSToCriteriaPrefixList3  OBJECT-TYPE
    SYNTAX      TLPrefixListName
    MAX-ACCESS  read-create
    STATUS      current
    DESCRIPTION
        "The value of tRPAdminPSToCriteriaPrefixList3 specifies the name of the
         third prefix list to match on. Setting this value to an empty string
         disables this prefix list as a match criteria.

         This object is the same as tRPAdminPSToCritPrefixList3, please use
         tRPAdminPSToCritPfxListTable to match on more prefix lists."
    DEFVAL      { ''H }
    ::= { tRPAdminPSToCriteriaEntry 10 }

tRPAdminPSToCriteriaPrefixList4  OBJECT-TYPE
    SYNTAX      TLPrefixListName
    MAX-ACCESS  read-create
    STATUS      current
    DESCRIPTION
        "The value of tRPAdminPSToCriteriaPrefixList4 specifies the name of the
         fourth prefix list to match on. Setting this value to an empty string
         disables this prefix list as a match criteria.

         This object is the same as tRPAdminPSToCritPrefixList4, please use
         tRPAdminPSToCritPfxListTable to match on more prefix lists."
    DEFVAL      { ''H }
    ::= { tRPAdminPSToCriteriaEntry 11 }

tRPAdminPSToCriteriaPrefixList5  OBJECT-TYPE
    SYNTAX      TLPrefixListName
    MAX-ACCESS  read-create
    STATUS      current
    DESCRIPTION
        "The value of tRPAdminPSToCriteriaPrefixList5 specifies the name of the
         fifth prefix list to match on. Setting this value to an empty string
         disables this prefix list as a match criteria.

         This object is the same as tRPAdminPSToCritPrefixList5, please use
         tRPAdminPSToCritPfxListTable to match on more prefix lists."
    DEFVAL      { ''H }
    ::= { tRPAdminPSToCriteriaEntry 12 }

tRPAdminPSToCritNbrInetAddrType  OBJECT-TYPE
    SYNTAX      InetAddressType
    MAX-ACCESS  read-create
    STATUS      current
    DESCRIPTION
        "The value of tRPAdminPSToCritNbrInetAddrType specifies the type of
         tRPAdminPSToCritNbrInetAddr address, as defined in the InetAddress
         MIB."
    ::= { tRPAdminPSToCriteriaEntry 13 }

tRPAdminPSToCritNbrInetAddr      OBJECT-TYPE
    SYNTAX      InetAddress (SIZE (4|16|20))
    MAX-ACCESS  read-create
    STATUS      current
    DESCRIPTION
        "The value of tRPAdminPSToCritNbrInetAddr specifies the IP address of
         neighbor to match on. To disable, tRPAdminPSToCritNbrInetAddrType
         should be set to 'ipv4' and tRPAdminPSToCritNbrInetAddr should be set
         to ff:ff:ff:ff.

         The type of this address is determined by the value of the
         tRPAdminPSToCritNbrInetAddrType object.

         tRPAdminPSToCritNbrInetAddr object replaces
         tRPAdminPSToCriteriaNeighborIpAddr that supports only IPv4 address
         style neighbor."
    ::= { tRPAdminPSToCriteriaEntry 14 }

tRPAdminPSToCriteriaInstanceId   OBJECT-TYPE
    SYNTAX      Unsigned32 (0..127 | 4294967295)
    MAX-ACCESS  read-create
    STATUS      current
    DESCRIPTION
        "The value of tRPAdminPSToCriteriaInstanceId specifies the instance
         identifier of the ISIS or OSPF(v3) protocol running in the router
         instance.

         The value of tRPAdminPSToCriteriaInstanceId will be 0 in case
         tRPAdminPSToCritProtocolBits has bits set different from isis(5),
         ospf(6) and ospf3(12).

         The supported instance range depends on the protocol that is set in
         tRPAdminPSToCritProtocolBits:
         protocol isis  - instance range 0..127.
         protocol ospf  - instance range 0..31.
         protocol ospf3 - instance range 0..31|64..95.

         If the value of tRPAdminPSToCriteriaInstanceId is 4294967295, all
         instances of the ISIS or OSPF(v3) protocol are leaked into BGP."
    DEFVAL      { 0 }
    ::= { tRPAdminPSToCriteriaEntry 15 }

tRPAdminPSToCritProtocolBits     OBJECT-TYPE
    SYNTAX      TRoutePolicyProtocolBits
    MAX-ACCESS  read-create
    STATUS      current
    DESCRIPTION
        "The value of tRPAdminPSToCritProtocolBits specifies the protocol name
         to match on.

         When the 'none' bit is set, the protocol match criteria is disabled."
    DEFVAL      { {none} }
    ::= { tRPAdminPSToCriteriaEntry 16 }

tRPAdminPSFromCriteriaTable      OBJECT-TYPE
    SYNTAX      SEQUENCE OF TRPAdminPSFromCriteriaEntry
    MAX-ACCESS  not-accessible
    STATUS      current
    DESCRIPTION
        "A table of from filter criteria for each policy statement entry."
    ::= { tRPAdminValueObjects 10 }

tRPAdminPSFromCriteriaEntry      OBJECT-TYPE
    SYNTAX      TRPAdminPSFromCriteriaEntry
    MAX-ACCESS  not-accessible
    STATUS      current
    DESCRIPTION
        "Information about policy statement entry from criteria."
    INDEX       {
        tRPAdminPolicyStatementName,
        tRPAdminPSFromCriteriaIndex
    }
    ::= { tRPAdminPSFromCriteriaTable 1 }

TRPAdminPSFromCriteriaEntry      ::= SEQUENCE
{
    tRPAdminPSFromCriteriaIndex      TPolicyStatementEntryID,
    tRPAdminPSFromCriteriaRowStatus  RowStatus,
    tRPAdminPSFromCriteriaProtocol   TRoutePolicyProtocol,
    tRPAdminPSFromCriteriaNeighborIpAddr IpAddress,
    tRPAdminPSFromCriteriaNeighborPrefixList TLPrefixListName,
    tRPAdminPSFromCriteriaPrefixList1 TLPrefixListName,
    tRPAdminPSFromCriteriaPrefixList2 TLPrefixListName,
    tRPAdminPSFromCriteriaPrefixList3 TLPrefixListName,
    tRPAdminPSFromCriteriaPrefixList4 TLPrefixListName,
    tRPAdminPSFromCriteriaPrefixList5 TLPrefixListName,
    tRPAdminPSFromCriteriaASPath     TASPathName,
    tRPAdminPSFromCriteriaCommunity  TLCommunityName,
    tRPAdminPSFromCriteriaOrigin     TPolicyEntryCriteriaOrigin,
    tRPAdminPSFromCriteriaOspfRouteType TOspfRouteType,
    tRPAdminPSFromCriteriaArea       IpAddress,
    tRPAdminPSFromCriteriaAreaConfigured TruthValue,
    tRPAdminPSFromCriteriaIsisLevel  TIsisLevel,
    tRPAdminPSFromCriteriaIsisExternal TruthValue,
    tRPAdminPSFromCriteriaIgmpHostPrefixList TLPrefixListName,
    tRPAdminPSFromCriteriaGrpAddrPrefixList TLPrefixListName,
    tRPAdminPSFromCriteriaSrcAddr    IpAddress,
    tRPAdminPSFromCriteriaInterface  TNamedItemOrEmpty,
    tRPAdminPSFromCriteriaTag        TPolicyActionTag,
    tRPAdminPSFromCritNbrInetAddrType InetAddressType,
    tRPAdminPSFromCritNbrInetAddr    InetAddress,
    tRPAdminPSFromCritSrcInetAddrType InetAddressType,
    tRPAdminPSFromCritSrcInetAddr    InetAddress,
    tRPAdminPSFromCriteriaFamily     TmnxBGPFamilyType,
    tRPAdminPSFromCriteriaInstanceId Unsigned32,
    tRPAdminPSFromCriteriaMatchTag   TmnxEnabledDisabled,
    tRPAdminPSFromCriteriaState      TPolicyEntryCriteriaState,
    tRPAdminPSFromCritASPathGroup    TASPathGroupName,
    tRPAdminPSFromCriteriaPolicy     TXLPolicyNameOrExpOrEmpty,
    tRPAdminPSFromCritCreationOrigin TmnxCreateOrigin,
    tRPAdminPSFromCritProtocolBits   TRoutePolicyProtocolBits
}

tRPAdminPSFromCriteriaIndex      OBJECT-TYPE
    SYNTAX      TPolicyStatementEntryID
    MAX-ACCESS  not-accessible
    STATUS      current
    DESCRIPTION
        "The policy statement entry ID"
    ::= { tRPAdminPSFromCriteriaEntry 1 }

tRPAdminPSFromCriteriaRowStatus  OBJECT-TYPE
    SYNTAX      RowStatus
    MAX-ACCESS  read-create
    STATUS      current
    DESCRIPTION
        "The value of tRPAdminPSFromCriteriaRowStatus specifies the RowStatus
         for this row.

         To Create a row, set this object to 'createAndGo(4)'. When
         tRPAdminControlApply is set to 'commit(3)', the row will actually be
         created in the tRPOperPSFromCriteriaTable.

         To destroy a row, set this object to 'destroy(6)'. When
         tRPAdminControlApply is set to 'commit(3)', the row will actually be
         removed from the tRPOperPSFromCriteriaTable."
    ::= { tRPAdminPSFromCriteriaEntry 2 }

tRPAdminPSFromCriteriaProtocol   OBJECT-TYPE
    SYNTAX      TRoutePolicyProtocol
    MAX-ACCESS  read-create
    STATUS      deprecated
    DESCRIPTION
        "The protocol name to match on. Set to none(1) to disable.

         This object is deprecated, please use the object
         tRPAdminPSFromCritProtocolBits instead."
    DEFVAL      { none }
    ::= { tRPAdminPSFromCriteriaEntry 3 }

tRPAdminPSFromCriteriaNeighborIpAddr OBJECT-TYPE
    SYNTAX      IpAddress
    MAX-ACCESS  read-create
    STATUS      current
    DESCRIPTION
        "The IP address of neighbor to match on. Set to 255.255.255.255 to
         disable."
    DEFVAL      { 'FFFFFFFF'H }
    ::= { tRPAdminPSFromCriteriaEntry 4 }

tRPAdminPSFromCriteriaNeighborPrefixList OBJECT-TYPE
    SYNTAX      TLPrefixListName
    MAX-ACCESS  read-create
    STATUS      current
    DESCRIPTION
        "The name of a neighbor prefix list to match on. Set to empty string to
         disable."
    DEFVAL      { ''H }
    ::= { tRPAdminPSFromCriteriaEntry 5 }

tRPAdminPSFromCriteriaPrefixList1 OBJECT-TYPE
    SYNTAX      TLPrefixListName
    MAX-ACCESS  read-create
    STATUS      current
    DESCRIPTION
        "The name of the first prefix list to match on. Set to empty string to
         disable.

         This object is the same as tRPAdminPSFromCritPrefixList1, please use
         tRPAdminPSFromCritPfxListTable to match on more prefix lists."
    DEFVAL      { ''H }
    ::= { tRPAdminPSFromCriteriaEntry 6 }

tRPAdminPSFromCriteriaPrefixList2 OBJECT-TYPE
    SYNTAX      TLPrefixListName
    MAX-ACCESS  read-create
    STATUS      current
    DESCRIPTION
        "The name of the second prefix list to match on. Set to empty string to
         disable.

         This object is the same as tRPAdminPSFromCritPrefixList2, please use
         tRPAdminPSFromCritPfxListTable to match on more prefix lists."
    DEFVAL      { ''H }
    ::= { tRPAdminPSFromCriteriaEntry 7 }

tRPAdminPSFromCriteriaPrefixList3 OBJECT-TYPE
    SYNTAX      TLPrefixListName
    MAX-ACCESS  read-create
    STATUS      current
    DESCRIPTION
        "The name of the third prefix list to match on. Set to empty string to
         disable.

         This object is the same as tRPAdminPSFromCritPrefixList3, please use
         tRPAdminPSFromCritPfxListTable to match on more prefix lists."
    DEFVAL      { ''H }
    ::= { tRPAdminPSFromCriteriaEntry 8 }

tRPAdminPSFromCriteriaPrefixList4 OBJECT-TYPE
    SYNTAX      TLPrefixListName
    MAX-ACCESS  read-create
    STATUS      current
    DESCRIPTION
        "The name of the fourth prefix list to match on. Set to empty string to
         disable.

         This object is the same as tRPAdminPSFromCritPrefixList4, please use
         tRPAdminPSFromCritPfxListTable to match on more prefix lists."
    DEFVAL      { ''H }
    ::= { tRPAdminPSFromCriteriaEntry 9 }

tRPAdminPSFromCriteriaPrefixList5 OBJECT-TYPE
    SYNTAX      TLPrefixListName
    MAX-ACCESS  read-create
    STATUS      current
    DESCRIPTION
        "The name of the fifth prefix list to match on. Set to empty string to
         disable.

         This object is the same as tRPAdminPSFromCritPrefixList5, please use
         tRPAdminPSFromCritPfxListTable to match on more prefix lists."
    DEFVAL      { ''H }
    ::= { tRPAdminPSFromCriteriaEntry 10 }

tRPAdminPSFromCriteriaASPath     OBJECT-TYPE
    SYNTAX      TASPathName
    MAX-ACCESS  read-create
    STATUS      current
    DESCRIPTION
        "The name of the AS Path to match on. Set to empty string to disable."
    DEFVAL      { ''H }
    ::= { tRPAdminPSFromCriteriaEntry 11 }

tRPAdminPSFromCriteriaCommunity  OBJECT-TYPE
    SYNTAX      TLCommunityName
    MAX-ACCESS  read-create
    STATUS      current
    DESCRIPTION
        "The name of the community to match on. Set to empty string to disable."
    DEFVAL      { ''H }
    ::= { tRPAdminPSFromCriteriaEntry 12 }

tRPAdminPSFromCriteriaOrigin     OBJECT-TYPE
    SYNTAX      TPolicyEntryCriteriaOrigin
    MAX-ACCESS  read-create
    STATUS      current
    DESCRIPTION
        "The value of tRPAdminPSFromCriteriaOrigin specifies the route match
         criterion for an entry."
    DEFVAL      { none }
    ::= { tRPAdminPSFromCriteriaEntry 13 }

tRPAdminPSFromCriteriaOspfRouteType OBJECT-TYPE
    SYNTAX      TOspfRouteType
    MAX-ACCESS  read-create
    STATUS      current
    DESCRIPTION
        "The OSPF route type to match on. Set to zero to disable."
    DEFVAL      { 0 }
    ::= { tRPAdminPSFromCriteriaEntry 14 }

tRPAdminPSFromCriteriaArea       OBJECT-TYPE
    SYNTAX      IpAddress
    MAX-ACCESS  read-create
    STATUS      current
    DESCRIPTION
        "Used when redistributing OSPF routes into other protocols. Specifies
         the OSPF area that must be matched in filtered routes."
    ::= { tRPAdminPSFromCriteriaEntry 16 }

tRPAdminPSFromCriteriaAreaConfigured OBJECT-TYPE
    SYNTAX      TruthValue
    MAX-ACCESS  read-create
    STATUS      current
    DESCRIPTION
        "Specifies if the tRPAdminPSFromCriteriaArea has been configured"
    ::= { tRPAdminPSFromCriteriaEntry 17 }

tRPAdminPSFromCriteriaIsisLevel  OBJECT-TYPE
    SYNTAX      TIsisLevel
    MAX-ACCESS  read-create
    STATUS      current
    DESCRIPTION
        "The value for tRPAdminPSFromCriteriaIsisLevel defines the IS-IS route
         level match criterion. A value of 0 indicates that no IS-IS route
         level match criterion has been configured."
    DEFVAL      { 0 }
    ::= { tRPAdminPSFromCriteriaEntry 18 }

tRPAdminPSFromCriteriaIsisExternal OBJECT-TYPE
    SYNTAX      TruthValue
    MAX-ACCESS  read-create
    STATUS      current
    DESCRIPTION
        "When tRPAdminPSFromCriteriaIsisExternal is 'true', match only External
         IS-IS routes. If 'false', match all routes. External IS-IS routes are
         those routes that have been learned from outside the IS-IS domain."
    DEFVAL      { false }
    ::= { tRPAdminPSFromCriteriaEntry 19 }

tRPAdminPSFromCriteriaIgmpHostPrefixList OBJECT-TYPE
    SYNTAX      TLPrefixListName
    MAX-ACCESS  read-create
    STATUS      current
    DESCRIPTION
        "tRPAdminPSFromCriteriaIgmpHostPrefixList contains the name of the
         prefix list that is used to match the IGMP/MLD host IP address. This
         object is set to empty string to disable."
    ::= { tRPAdminPSFromCriteriaEntry 20 }

tRPAdminPSFromCriteriaGrpAddrPrefixList OBJECT-TYPE
    SYNTAX      TLPrefixListName
    MAX-ACCESS  read-create
    STATUS      current
    DESCRIPTION
        "tRPAdminPSFromCriteriaGrpAddrPrefixList contains the name of the
         prefix list that is used to match the multicast group address. This
         object is set to empty string to disable."
    ::= { tRPAdminPSFromCriteriaEntry 21 }

tRPAdminPSFromCriteriaSrcAddr    OBJECT-TYPE
    SYNTAX      IpAddress
    MAX-ACCESS  read-create
    STATUS      current
    DESCRIPTION
        "tRPAdminPSFromCriteriaSrcAddr contains the IP address of the source to
         match on. It is used by multicast protocols like IGMP/MLD and PIM.
         This object is set to 0.0.0.0 to disable."
    ::= { tRPAdminPSFromCriteriaEntry 22 }

tRPAdminPSFromCriteriaInterface  OBJECT-TYPE
    SYNTAX      TNamedItemOrEmpty
    MAX-ACCESS  read-create
    STATUS      current
    DESCRIPTION
        "tRPAdminPSFromCriteriaInterface contains the name of the interface to
         match on. PIM Bootstrap route policy will use this object to
         accept/reject bootstrap messages coming on the interface specified by
         this object. This object is set to empty string to disable."
    ::= { tRPAdminPSFromCriteriaEntry 23 }

tRPAdminPSFromCriteriaTag        OBJECT-TYPE
    SYNTAX      TPolicyActionTag
    MAX-ACCESS  read-create
    STATUS      current
    DESCRIPTION
        "The value of tRPAdminPSFromCriteriaTag specifies the route tag to
         match on. Routes will only be matched on this value when
         tRPAdminPSFromCriteriaMatchTag is enabled.

         A value of 0 for tRPAdminPSFromCriteriaTag when
         tRPAdminPSFromCriteriaMatchTag is enabled would match untagged routes."
    DEFVAL      { 0 }
    ::= { tRPAdminPSFromCriteriaEntry 24 }

tRPAdminPSFromCritNbrInetAddrType OBJECT-TYPE
    SYNTAX      InetAddressType
    MAX-ACCESS  read-create
    STATUS      current
    DESCRIPTION
        "The value of tRPAdminPSFromCritNbrInetAddrType specifies the type of
         tRPAdminPSFromCritNbrInetAddr address, as defined in the InetAddress
         MIB."
    ::= { tRPAdminPSFromCriteriaEntry 25 }

tRPAdminPSFromCritNbrInetAddr    OBJECT-TYPE
    SYNTAX      InetAddress (SIZE (4|16|20))
    MAX-ACCESS  read-create
    STATUS      current
    DESCRIPTION
        "The value of tRPAdminPSFromCritNbrInetAddr specifies the IP address of
         neighbor to match on. To disable, tRPAdminPSFromCritNbrInetAddrType
         should be set to 'ipv4' and tRPAdminPSFromCritNbrInetAddr should be
         set to ff:ff:ff:ff.

         The type of this address is determined by the value of the
         tRPAdminPSFromCritNbrInetAddrType object.

         tRPAdminPSFromCritNbrInetAddr object replaces
         tRPAdminPSFromCriteriaNeighborIpAddr that supports only IPv4 address
         style neighbor."
    ::= { tRPAdminPSFromCriteriaEntry 26 }

tRPAdminPSFromCritSrcInetAddrType OBJECT-TYPE
    SYNTAX      InetAddressType
    MAX-ACCESS  read-create
    STATUS      current
    DESCRIPTION
        "The value of tRPAdminPSFromCritSrcInetAddrType specifies the type of
         tRPAdminPSFromCritSrcInetAddr address, as defined in the InetAddress
         MIB."
    ::= { tRPAdminPSFromCriteriaEntry 27 }

tRPAdminPSFromCritSrcInetAddr    OBJECT-TYPE
    SYNTAX      InetAddress (SIZE (4|16))
    MAX-ACCESS  read-create
    STATUS      current
    DESCRIPTION
        "The value of tRPAdminPSFromCritSrcInetAddr specifies the IP address of
         the source to match on. This object will be used by multicast
         protocols like PIM and IGMP/MLD. To disable,
         tRPAdminPSFromCritSrcInetAddrType should be set to 'ipv4' and
         tRPAdminPSFromCritSrcInetAddr should be set to 255.255.255.255.

         The type of this address is determined by the value of the
         tRPAdminPSFromCritSrcInetAddrType object.

         tRPAdminPSFromCritSrcInetAddr object replaces
         tRPAdminPSFromCriteriaSrcAddr that supports only IPv4 address style
         source."
    ::= { tRPAdminPSFromCriteriaEntry 28 }

tRPAdminPSFromCriteriaFamily     OBJECT-TYPE
    SYNTAX      TmnxBGPFamilyType
    MAX-ACCESS  read-create
    STATUS      current
    DESCRIPTION
        "The  bits set in the value of tRPAdminPSFromCriteriaFamily specifies
         the address families that this condition would match against."
    DEFVAL      { {} }
    ::= { tRPAdminPSFromCriteriaEntry 29 }

tRPAdminPSFromCriteriaInstanceId OBJECT-TYPE
    SYNTAX      Unsigned32 (0..127 | 4294967295)
    MAX-ACCESS  read-create
    STATUS      current
    DESCRIPTION
        "The value of tRPAdminPSFromCriteriaInstanceId specifies the instance
         identifier of the ISIS or OSPF(v3) protocol running in the router
         instance.

         The value of tRPAdminPSFromCriteriaInstanceId must be 0 in case
         tRPAdminPSFromCritProtocolBits has a value different from isis(5),
         ospf(6) and ospf3(12).

         The supported instance range depends on the protocol that is set in
         tRPAdminPSFromCritProtocolBits:
         protocol isis  - instance range 0..127.
         protocol ospf  - instance range 0..31.
         protocol ospf3 - instance range 0..31|64..95.

         If the value of tRPAdminPSFromCriteriaInstanceId is 4294967295, all
         instances of the ISIS or OSPF(v3) protocol are leaked into BGP."
    DEFVAL      { 0 }
    ::= { tRPAdminPSFromCriteriaEntry 30 }

tRPAdminPSFromCriteriaMatchTag   OBJECT-TYPE
    SYNTAX      TmnxEnabledDisabled
    MAX-ACCESS  read-create
    STATUS      current
    DESCRIPTION
        "The value of tRPAdminPSFromCriteriaMatchTag specifies if tag matching
         is enabled or disabled. Disabling of this object will set
         tRPAdminPSFromCriteriaTag to zero."
    DEFVAL      { disabled }
    ::= { tRPAdminPSFromCriteriaEntry 31 }

tRPAdminPSFromCriteriaState      OBJECT-TYPE
    SYNTAX      TPolicyEntryCriteriaState
    MAX-ACCESS  read-create
    STATUS      current
    DESCRIPTION
        "The value of tRPAdminPSFromCriteriaState specifies the route state
         match criterion for this entry."
    DEFVAL      { none }
    ::= { tRPAdminPSFromCriteriaEntry 32 }

tRPAdminPSFromCritASPathGroup    OBJECT-TYPE
    SYNTAX      TASPathGroupName
    MAX-ACCESS  read-create
    STATUS      current
    DESCRIPTION
        "The value of tRPAdminPSFromCritASPathGroup specifies the AS-Path Group
         match criterion for this entry."
    DEFVAL      { "" }
    ::= { tRPAdminPSFromCriteriaEntry 33 }

tRPAdminPSFromCriteriaPolicy     OBJECT-TYPE
    SYNTAX      TXLPolicyNameOrExpOrEmpty
    MAX-ACCESS  read-create
    STATUS      current
    DESCRIPTION
        "The value of tRPAdminPSFromCriteriaPolicy specifies the policy match
         criterion for this entry.

         The value of this object is used to link match criteria over multiple
         policy entries, to implement more complex match conditions."
    DEFVAL      { "" }
    ::= { tRPAdminPSFromCriteriaEntry 34 }

tRPAdminPSFromCritCreationOrigin OBJECT-TYPE
    SYNTAX      TmnxCreateOrigin
    MAX-ACCESS  read-only
    STATUS      current
    DESCRIPTION
        "The value of the object tRPAdminPSFromCritCreationOrigin indicates the
         mechanism used to create this entry."
    ::= { tRPAdminPSFromCriteriaEntry 35 }

tRPAdminPSFromCritProtocolBits   OBJECT-TYPE
    SYNTAX      TRoutePolicyProtocolBits
    MAX-ACCESS  read-create
    STATUS      current
    DESCRIPTION
        "The value of tRPAdminPSFromCritProtocolBits specifies the protocol
         name to match on.

         When the 'none' bit is set, the protocol match criteria is disabled."
    DEFVAL      { {none} }
    ::= { tRPAdminPSFromCriteriaEntry 36 }

tRPAdminInetPrefixListTable      OBJECT-TYPE
    SYNTAX      SEQUENCE OF TRPAdminInetPrefixListEntry
    MAX-ACCESS  not-accessible
    STATUS      current
    DESCRIPTION
        "The table of IPv4 and IPv6 admin prefix lists."
    ::= { tRPAdminValueObjects 11 }

tRPAdminInetPrefixListEntry      OBJECT-TYPE
    SYNTAX      TRPAdminInetPrefixListEntry
    MAX-ACCESS  not-accessible
    STATUS      current
    DESCRIPTION
        "Each row entry in the tRPAdminInetPrefixListEntry represents
         information about a particular prefix list.

         Entries are created and deleted by the user.

         When a prefix list entry is created with a name that doesn't exist in
         the tRPAdminPfxListNameTable, a corresponding entry will be created
         automatically in tRPAdminPfxListNameTable.

         When a corresponding entry is deleted from tRPAdminPfxListNameTable,
         the entry in this table will be deleted automatically."
    INDEX       {
        tRPAdminInetPrefixListName,
        tRPAdminInetPrefixListPrefixType,
        tRPAdminInetPrefixListPrefix,
        tRPAdminInetPrefixListPrefixLen,
        tRPAdminInetPrefixListType
    }
    ::= { tRPAdminInetPrefixListTable 1 }

TRPAdminInetPrefixListEntry      ::= SEQUENCE
{
    tRPAdminInetPrefixListName       TLPrefixListName,
    tRPAdminInetPrefixListPrefixType TmnxAddressAndPrefixType,
    tRPAdminInetPrefixListPrefix     TmnxAddressAndPrefixAddress,
    tRPAdminInetPrefixListPrefixLen  TmnxAddressAndPrefixPrefix,
    tRPAdminInetPrefixListType       INTEGER,
    tRPAdminInetPrefixListRowStatus  RowStatus,
    tRPAdminInetPrefixListThroughLen InetAddressPrefixLength,
    tRPAdminInetPrefixListBeginLen   InetAddressPrefixLength,
    tRPAdminInetPrefixListCrOrigin   TmnxCreateOrigin
}

tRPAdminInetPrefixListName       OBJECT-TYPE
    SYNTAX      TLPrefixListName (SIZE (1..64))
    MAX-ACCESS  not-accessible
    STATUS      current
    DESCRIPTION
        "The value of tRPAdminInetPrefixListName indicates the name of the
         prefix list entry.

         This object refers to the object tRPAdminPfxListName in
         tRPAdminPfxListNameTable."
    ::= { tRPAdminInetPrefixListEntry 1 }

tRPAdminInetPrefixListPrefixType OBJECT-TYPE
    SYNTAX      TmnxAddressAndPrefixType
    MAX-ACCESS  not-accessible
    STATUS      current
    DESCRIPTION
        "The value of tRPAdminInetPrefixListPrefixType indicates the address
         type of tRPAdminInetPrefixListPrefix."
    ::= { tRPAdminInetPrefixListEntry 2 }

tRPAdminInetPrefixListPrefix     OBJECT-TYPE
    SYNTAX      TmnxAddressAndPrefixAddress (SIZE (4|16))
    MAX-ACCESS  not-accessible
    STATUS      current
    DESCRIPTION
        "The value of tRPAdminInetPrefixListPrefix indicates the IP prefix of
         the prefix list entry."
    ::= { tRPAdminInetPrefixListEntry 3 }

tRPAdminInetPrefixListPrefixLen  OBJECT-TYPE
    SYNTAX      TmnxAddressAndPrefixPrefix
    MAX-ACCESS  not-accessible
    STATUS      current
    DESCRIPTION
        "The value of tRPAdminInetPrefixListPrefixLen indicates the IP prefix
         length of the prefix list entry."
    ::= { tRPAdminInetPrefixListEntry 4 }

tRPAdminInetPrefixListType       OBJECT-TYPE
    SYNTAX      INTEGER {
        exact       (1),
        longer      (2),
        through     (3),
        range       (4),
        to          (5),
        addressMask (6)
    }
    MAX-ACCESS  not-accessible
    STATUS      current
    DESCRIPTION
        "The value of tRPAdminInetPrefixListType indicates the type of the
         prefix length entry.

         exact (1) - a route's prefix/length must match the prefix list entry
         exactly in order for an entry to be considered a match.

         longer (2) - a route's prefix/length must match the defined prefix AND
         have a length that is an exact match or longer in order for an entry
         to be considered a match.

         through (3) - a route's prefix/length must match the defined prefix
         AND have a length that is an exact match or longer up to and including
         the defined maximum length in order for an entry to be considered a
         match.

         range (4) - a route's prefix/length must match the defined prefix AND
         have a length that is greater than or equal to the length defined by
         tRPAdminInetPrefixListBeginLen and less than or equal to the length
         defined by tRPAdminInetPrefixListThroughLen in order for an entry to
         be considered a match.

         to (5) - a route's prefix/length must match the condition  from a
         start prefix/length to an end prefix/length. The  end prefix/length
         must be specified in a corresponding entry  in the
         tRPAdminPfxListToTable.

         addressMask (6) - a route's prefix/length must match the prefix length
         of the prefix-list entry and the bitwise logical AND of the route
         address and the mask must match the bitwise  logical AND from the
         prefix-list address and the mask. The  address mask must be specified
         in a corresponding entry in the tRPAdminPfxListAddressMaskTable."
    ::= { tRPAdminInetPrefixListEntry 5 }

tRPAdminInetPrefixListRowStatus  OBJECT-TYPE
    SYNTAX      RowStatus
    MAX-ACCESS  read-create
    STATUS      current
    DESCRIPTION
        "RowStatus for this row.

         To create a row, set this object to createAndGo or createAndWait. When
         tRPAdminControlApply is set to commit(3), the row will actually be
         created in the tRPOperInetPrefixListTable.

         To destroy a row, set this object to destroy(6). When
         tRPAdminControlApply is set to commit(3) the row will actually be
         removed from the tRPOperInetPrefixListTable."
    ::= { tRPAdminInetPrefixListEntry 6 }

tRPAdminInetPrefixListThroughLen OBJECT-TYPE
    SYNTAX      InetAddressPrefixLength
    MAX-ACCESS  read-create
    STATUS      current
    DESCRIPTION
        "The value of tRPAdminInetPrefixListThroughLen specifies the prefix
         length to use when tRPAdminPrefixListType set to through(3). The value
         must be larger than tRPAdminInetPrefixListPrefixLen."
    DEFVAL      { 0 }
    ::= { tRPAdminInetPrefixListEntry 7 }

tRPAdminInetPrefixListBeginLen   OBJECT-TYPE
    SYNTAX      InetAddressPrefixLength
    MAX-ACCESS  read-create
    STATUS      current
    DESCRIPTION
        "The value of tRPAdminInetPrefixListBeginLen specifies the prefix
         length to use as the lower limit for the prefix range when
         tRPAdminInetPrefixListType set to range(4). The value must be larger
         than tRPAdminInetPrefixListPrefixLen and less than
         tRPAdminInetPrefixListThroughLen."
    DEFVAL      { 0 }
    ::= { tRPAdminInetPrefixListEntry 8 }

tRPAdminInetPrefixListCrOrigin   OBJECT-TYPE
    SYNTAX      TmnxCreateOrigin
    MAX-ACCESS  read-only
    STATUS      current
    DESCRIPTION
        "The value of the object tRPAdminInetPrefixListCrOrigin indicates the
         mechanism used to create this entry."
    ::= { tRPAdminInetPrefixListEntry 9 }

tRPAdminCommunityExprTable       OBJECT-TYPE
    SYNTAX      SEQUENCE OF TRPAdminCommunityExprEntry
    MAX-ACCESS  not-accessible
    STATUS      current
    DESCRIPTION
        "A table of community entries."
    ::= { tRPAdminValueObjects 12 }

tRPAdminCommunityExprEntry       OBJECT-TYPE
    SYNTAX      TRPAdminCommunityExprEntry
    MAX-ACCESS  not-accessible
    STATUS      current
    DESCRIPTION
        "Information about a particular community name member. Entries are
         created and deleted by the user."
    INDEX       { tRPAdminCommunityExprName }
    ::= { tRPAdminCommunityExprTable 1 }

TRPAdminCommunityExprEntry       ::= SEQUENCE
{
    tRPAdminCommunityExprName        TLCommunityName,
    tRPAdminCommunityExprRowStatus   RowStatus,
    tRPAdminCommunityExprString1     TCommunityMemberExpression,
    tRPAdminCommunityExprString2     TCommunityMemberExpression,
    tRPAdminCommunityExprString3     TCommunityMemberExpression,
    tRPAdminCommunityExprString4     TCommunityMemberExpression,
    tRPAdminCommunityExprExactMatch  TruthValue
}

tRPAdminCommunityExprName        OBJECT-TYPE
    SYNTAX      TLCommunityName (SIZE (1..64))
    MAX-ACCESS  not-accessible
    STATUS      current
    DESCRIPTION
        "The value of tRPAdminCommunityExprName indicates the name of the
         community used as an index for this table."
    ::= { tRPAdminCommunityExprEntry 1 }

tRPAdminCommunityExprRowStatus   OBJECT-TYPE
    SYNTAX      RowStatus
    MAX-ACCESS  read-create
    STATUS      current
    DESCRIPTION
        "The value of tRPAdminCommunityExprRowStatus specifies the RowStatus
         for this row.

         To create a row, set this object to 'createAndGo(4)'. The value of
         tRPAdminCommunityExprString1 must be set to a non-empty string in the
         same SNMP SET PDU for the row creation to succeed. When
         tRPAdminControlApply is set to 'commit(3)', the row will actually be
         created in the tRPOperCommunityExprTable.

         When the value of this object is set to 'createAndWait(5)', a new
         entry is created with value of this object set to 'notInService(2)'
         and the tRPAdminCommunityExprString1-4 strings can be configured
         separately. When the value of this object is set to 'active(1)', the
         values of objects tRPAdminCommunityExprString1-4, are concatenated to
         form one expression of at most 900 characters. When
         tRPAdminControlApply is set to 'commit(3)', the row will actually be
         created in the tRPOperCommunityExprTable.

         To destroy a row, set this object to 'destroy(6)'. When
         tRPAdminControlApply is set to 'commit(3)', the row will actually be
         removed from the tRPOperCommunityExprTable."
    ::= { tRPAdminCommunityExprEntry 2 }

tRPAdminCommunityExprString1     OBJECT-TYPE
    SYNTAX      TCommunityMemberExpression
    MAX-ACCESS  read-create
    STATUS      current
    DESCRIPTION
        "The value of object tRPAdminCommunityExprString1 specifies an
         expression that matches AS Numbers or Community ID's.

         The objects tRPAdminCommunityExprString1,
         tRPAdminCommunityExprString2, tRPAdminCommunityExprString3 and
         tRPAdminCommunityExprString4 are substrings that form one string of
         type TCommunityMemberExpression. Substrings can only be set to a
         non-empty string if the previous substrings are non-empty."
    DEFVAL      { "" }
    ::= { tRPAdminCommunityExprEntry 3 }

tRPAdminCommunityExprString2     OBJECT-TYPE
    SYNTAX      TCommunityMemberExpression
    MAX-ACCESS  read-create
    STATUS      current
    DESCRIPTION
        "The value of object tRPAdminCommunityExprString2 specifies an
         expression that matches AS Numbers or Community ID's.

         The objects tRPAdminCommunityExprString1,
         tRPAdminCommunityExprString2, tRPAdminCommunityExprString3 and
         tRPAdminCommunityExprString4 are substrings that form one string of
         type TCommunityMemberExpression. Substrings can only be set to a
         non-empty string if the previous substrings are non-empty."
    DEFVAL      { "" }
    ::= { tRPAdminCommunityExprEntry 4 }

tRPAdminCommunityExprString3     OBJECT-TYPE
    SYNTAX      TCommunityMemberExpression
    MAX-ACCESS  read-create
    STATUS      current
    DESCRIPTION
        "The value of object tRPAdminCommunityExprString3 specifies an
         expression that matches AS Numbers or Community ID's.

         The objects tRPAdminCommunityExprString1,
         tRPAdminCommunityExprString2, tRPAdminCommunityExprString3 and
         tRPAdminCommunityExprString4 are substrings that form one string of
         type TCommunityMemberExpression. Substrings can only be set to a
         non-empty string if the previous substrings are non-empty."
    DEFVAL      { "" }
    ::= { tRPAdminCommunityExprEntry 5 }

tRPAdminCommunityExprString4     OBJECT-TYPE
    SYNTAX      TCommunityMemberExpression
    MAX-ACCESS  read-create
    STATUS      current
    DESCRIPTION
        "The value of object tRPAdminCommunityExprString4 specifies an
         expression that matches AS Numbers or Community ID's.

         The objects tRPAdminCommunityExprString1,
         tRPAdminCommunityExprString2, tRPAdminCommunityExprString3 and
         tRPAdminCommunityExprString4 are substrings that form one string of
         type TCommunityMemberExpression. Substrings can only be set to a
         non-empty string if the previous substrings are non-empty."
    DEFVAL      { "" }
    ::= { tRPAdminCommunityExprEntry 6 }

tRPAdminCommunityExprExactMatch  OBJECT-TYPE
    SYNTAX      TruthValue
    MAX-ACCESS  read-create
    STATUS      current
    DESCRIPTION
        "The value of object tRPAdminCommunityExprExactMatch specifies whether
         the expression in this table entry is only evaluated on an exact
         match.

         If the value of this object is 'true', then the community expression
         only matches a given route if all communities attached to the route
         are strictly required to match the expression and no redundant
         communities are present."
    DEFVAL      { false }
    ::= { tRPAdminCommunityExprEntry 7 }

tRPAdminASPathGroupTable         OBJECT-TYPE
    SYNTAX      SEQUENCE OF TRPAdminASPathGroupEntry
    MAX-ACCESS  not-accessible
    STATUS      current
    DESCRIPTION
        "The table of AS-Path Groups."
    ::= { tRPAdminValueObjects 13 }

tRPAdminASPathGroupEntry         OBJECT-TYPE
    SYNTAX      TRPAdminASPathGroupEntry
    MAX-ACCESS  not-accessible
    STATUS      current
    DESCRIPTION
        "Each row entry in the tRPAdminASPathGroupTable represents information
         about a particular AS-Path Group.

         When an AS-Path Group entry is created with a name that doesn't exist
         in the tRPAdminASPathGroupNameTable, a corresponding entry will be
         created automatically in tRPAdminASPathGroupNameTable.

         When a corresponding entry is deleted from
         tRPAdminASPathGroupNameTable, the entry in this table will be deleted
         automatically."
    INDEX       {
        tRPAdminASPathGroupName,
        tRPAdminASPathGroupEntryIndex
    }
    ::= { tRPAdminASPathGroupTable 1 }

TRPAdminASPathGroupEntry         ::= SEQUENCE
{
    tRPAdminASPathGroupName          TASPathGroupName,
    tRPAdminASPathGroupEntryIndex    Unsigned32,
    tRPAdminASPathGroupRowStatus     RowStatus,
    tRPAdminASPathGroupASPathName    TASPathName,
    tRPAdminASPathGroupASPathRegEx   TRoutePolicyRegex,
    tRPAdminASPathGroupCrOrigin      TmnxCreateOrigin
}

tRPAdminASPathGroupName          OBJECT-TYPE
    SYNTAX      TASPathGroupName (SIZE (1..32))
    MAX-ACCESS  not-accessible
    STATUS      current
    DESCRIPTION
        "The value of tRPAdminASPathGroupName specifies the name of the AS-Path
         Group.

         This object refers to the object tRPAdminASPGroupName in
         tRPAdminASPathGroupNameTable."
    ::= { tRPAdminASPathGroupEntry 1 }

tRPAdminASPathGroupEntryIndex    OBJECT-TYPE
    SYNTAX      Unsigned32 (1..128)
    MAX-ACCESS  not-accessible
    STATUS      current
    DESCRIPTION
        "The value of tRPAdminASPathGroupEntryIndex specifies the index of the
         entry in the AS-Path Group."
    ::= { tRPAdminASPathGroupEntry 2 }

tRPAdminASPathGroupRowStatus     OBJECT-TYPE
    SYNTAX      RowStatus
    MAX-ACCESS  read-create
    STATUS      current
    DESCRIPTION
        "The value of tRPAdminASPathGroupRowStatus specifies the RowStatus for
         this row.

         To create a row, set this object to 'createAndGo(4)'. When
         tRPAdminControlApply is set to 'commit(3)', the row will actually be
         created in the tRPOperASPathGroupTable.

         To destroy a row, set this object to 'destroy(6)'. When
         tRPAdminControlApply is set to 'commit(3)', the row will actually be
         removed from the tRPOperASPathGroupTable."
    ::= { tRPAdminASPathGroupEntry 3 }

tRPAdminASPathGroupASPathName    OBJECT-TYPE
    SYNTAX      TASPathName (SIZE (1..32))
    MAX-ACCESS  read-create
    STATUS      obsolete
    DESCRIPTION
        "The value of tRPAdminASPathGroupASPathName specifies the name of the
         AS-Path from the tRPAdminASPathTable.

         This object is made obsolete in release 14.0."
    ::= { tRPAdminASPathGroupEntry 4 }

tRPAdminASPathGroupASPathRegEx   OBJECT-TYPE
    SYNTAX      TRoutePolicyRegex
    MAX-ACCESS  read-create
    STATUS      current
    DESCRIPTION
        "The value of tRPAdminASPathGroupASPathRegEx specifies the regular
         expression for this AS-Path Group entry.

         This object must be set to a valid non-empty string for the row
         creation to succeed."
    ::= { tRPAdminASPathGroupEntry 5 }

tRPAdminASPathGroupCrOrigin      OBJECT-TYPE
    SYNTAX      TmnxCreateOrigin
    MAX-ACCESS  read-only
    STATUS      current
    DESCRIPTION
        "The value of the object tRPAdminASPathGroupCrOrigin indicates the
         mechanism used to create this entry."
    ::= { tRPAdminASPathGroupEntry 6 }

tRPAdminPSFromCommExprTable      OBJECT-TYPE
    SYNTAX      SEQUENCE OF TRPAdminPSFromCommExprEntry
    MAX-ACCESS  not-accessible
    STATUS      current
    DESCRIPTION
        "A table of from filter criteria to match on Community ID's for each
         policy statement entry."
    ::= { tRPAdminValueObjects 14 }

tRPAdminPSFromCommExprEntry      OBJECT-TYPE
    SYNTAX      TRPAdminPSFromCommExprEntry
    MAX-ACCESS  not-accessible
    STATUS      current
    DESCRIPTION
        "Information about a particular community name expression to use as
         match criterion for this policy statement entry."
    INDEX       {
        tRPAdminPolicyStatementName,
        tRPAdminPSFromCriteriaIndex
    }
    ::= { tRPAdminPSFromCommExprTable 1 }

TRPAdminPSFromCommExprEntry      ::= SEQUENCE
{
    tRPAdminPSFromCommExprRowStatus  RowStatus,
    tRPAdminPSFromCommExprString1    TCommunityNameExpression,
    tRPAdminPSFromCommExprString2    TCommunityNameExpression,
    tRPAdminPSFromCommExprString3    TCommunityNameExpression,
    tRPAdminPSFromCommExprString4    TCommunityNameExpression
}

tRPAdminPSFromCommExprRowStatus  OBJECT-TYPE
    SYNTAX      RowStatus
    MAX-ACCESS  read-create
    STATUS      current
    DESCRIPTION
        "The value of tRPAdminPSFromCommExprRowStatus specifies the RowStatus
         for this row.

         To create a row, set this object to 'createAndGo(4)'. The value of
         tRPAdminPSFromCommExprString1 must be set to a non-empty string in the
         same SNMP SET PDU for the row creation to succeed. When
         tRPAdminControlApply is set to 'commit(3)', the row will actually be
         created in the tRPOperPSFromCommExprTable.

         When the value of this object is set to 'createAndWait(5)', a new
         entry is created with value of this object set to 'notInService(2)'
         and the tRPAdminPSFromCommExprString1-4 strings can be configured
         separately. When the value of this object is set to 'active(1)', the
         values of objects tRPAdminPSFromCommExprString1-4, are concatenated to
         form one expression of at most 900 characters. When
         tRPAdminControlApply is set to 'commit(3)', the row will actually be
         created in the tRPOperPSFromCommExprTable.

         To destroy a row, set this object to 'destroy(6)'. When
         tRPAdminControlApply is set to 'commit(3)', the row will actually be
         removed from the tRPOperPSFromCommExprTable."
    ::= { tRPAdminPSFromCommExprEntry 1 }

tRPAdminPSFromCommExprString1    OBJECT-TYPE
    SYNTAX      TCommunityNameExpression
    MAX-ACCESS  read-create
    STATUS      current
    DESCRIPTION
        "The value of object tRPAdminPSFromCommExprString1 specifies an
         expression that matches Community ID's.

         The objects tRPAdminPSFromCommExprString1,
         tRPAdminPSFromCommExprString2, tRPAdminPSFromCommExprString3 and
         tRPAdminPSFromCommExprString4 are substrings that form one string of
         type TCommunityNameExpression. Substrings can only be set to a
         non-empty string if the previous substrings are non-empty."
    DEFVAL      { "" }
    ::= { tRPAdminPSFromCommExprEntry 2 }

tRPAdminPSFromCommExprString2    OBJECT-TYPE
    SYNTAX      TCommunityNameExpression
    MAX-ACCESS  read-create
    STATUS      current
    DESCRIPTION
        "The value of object tRPAdminPSFromCommExprString2 specifies an
         expression that matches Community ID's.

         The objects tRPAdminPSFromCommExprString1,
         tRPAdminPSFromCommExprString2, tRPAdminPSFromCommExprString3 and
         tRPAdminPSFromCommExprString4 are substrings that form one string of
         type TCommunityNameExpression. Substrings can only be set to a
         non-empty string if the previous substrings are non-empty."
    DEFVAL      { "" }
    ::= { tRPAdminPSFromCommExprEntry 3 }

tRPAdminPSFromCommExprString3    OBJECT-TYPE
    SYNTAX      TCommunityNameExpression
    MAX-ACCESS  read-create
    STATUS      current
    DESCRIPTION
        "The value of object tRPAdminPSFromCommExprString3 specifies an
         expression that matches Community ID's.

         The objects tRPAdminPSFromCommExprString1,
         tRPAdminPSFromCommExprString2, tRPAdminPSFromCommExprString3 and
         tRPAdminPSFromCommExprString4 are substrings that form one string of
         type TCommunityNameExpression. Substrings can only be set to a
         non-empty string if the previous substrings are non-empty."
    DEFVAL      { "" }
    ::= { tRPAdminPSFromCommExprEntry 4 }

tRPAdminPSFromCommExprString4    OBJECT-TYPE
    SYNTAX      TCommunityNameExpression
    MAX-ACCESS  read-create
    STATUS      current
    DESCRIPTION
        "The value of object tRPAdminPSFromCommExprString4 specifies an
         expression that matches Community ID's.

         The objects tRPAdminPSFromCommExprString1,
         tRPAdminPSFromCommExprString2, tRPAdminPSFromCommExprString3 and
         tRPAdminPSFromCommExprString4 are substrings that form one string of
         type TCommunityNameExpression. Substrings can only be set to a
         non-empty string if the previous substrings are non-empty."
    DEFVAL      { "" }
    ::= { tRPAdminPSFromCommExprEntry 5 }

tRPAdminPSDefActionAddCommTable  OBJECT-TYPE
    SYNTAX      SEQUENCE OF TRPAdminPSDefActionAddCommEntry
    MAX-ACCESS  not-accessible
    STATUS      current
    DESCRIPTION
        "Default community names for a policy statement to add to routes."
    ::= { tRPAdminValueObjects 15 }

tRPAdminPSDefActionAddCommEntry  OBJECT-TYPE
    SYNTAX      TRPAdminPSDefActionAddCommEntry
    MAX-ACCESS  not-accessible
    STATUS      current
    DESCRIPTION
        "Default action information about a particular policy statement.

         These communities are applied when the default action for the policy
         statement (tRPAdminPolicyStatementDefaultAction) is 'accept(1)'.

         Entries are created or deleted when an entry in
         tRPAdminPSDefaultActionParamsTable is created or deleted."
    AUGMENTS    { tRPAdminPSDefaultActionParamsEntry }
    ::= { tRPAdminPSDefActionAddCommTable 1 }

TRPAdminPSDefActionAddCommEntry  ::= SEQUENCE
{
    tRPAdminPSDefActionAddComm1      TLCommunityName,
    tRPAdminPSDefActionAddComm2      TLCommunityName,
    tRPAdminPSDefActionAddComm3      TLCommunityName,
    tRPAdminPSDefActionAddComm4      TLCommunityName,
    tRPAdminPSDefActionAddComm5      TLCommunityName,
    tRPAdminPSDefActionAddComm6      TLCommunityName,
    tRPAdminPSDefActionAddComm7      TLCommunityName,
    tRPAdminPSDefActionAddComm8      TLCommunityName,
    tRPAdminPSDefActionAddComm9      TLCommunityName,
    tRPAdminPSDefActionAddComm10     TLCommunityName,
    tRPAdminPSDefActionAddComm11     TLCommunityName,
    tRPAdminPSDefActionAddComm12     TLCommunityName,
    tRPAdminPSDefActionAddComm13     TLCommunityName,
    tRPAdminPSDefActionAddComm14     TLCommunityName,
    tRPAdminPSDefActionAddComm15     TLCommunityName,
    tRPAdminPSDefActionAddComm16     TLCommunityName,
    tRPAdminPSDefActionAddComm17     TLCommunityName,
    tRPAdminPSDefActionAddComm18     TLCommunityName,
    tRPAdminPSDefActionAddComm19     TLCommunityName,
    tRPAdminPSDefActionAddComm20     TLCommunityName,
    tRPAdminPSDefActionAddComm21     TLCommunityName,
    tRPAdminPSDefActionAddComm22     TLCommunityName,
    tRPAdminPSDefActionAddComm23     TLCommunityName,
    tRPAdminPSDefActionAddComm24     TLCommunityName,
    tRPAdminPSDefActionAddComm25     TLCommunityName,
    tRPAdminPSDefActionAddComm26     TLCommunityName,
    tRPAdminPSDefActionAddComm27     TLCommunityName,
    tRPAdminPSDefActionAddComm28     TLCommunityName
}

tRPAdminPSDefActionAddComm1      OBJECT-TYPE
    SYNTAX      TLCommunityName
    MAX-ACCESS  read-create
    STATUS      current
    DESCRIPTION
        "The value of tRPAdminPSDefActionAddComm1 specifies a community name to
         add to any existing community for the route."
    DEFVAL      { "" }
    ::= { tRPAdminPSDefActionAddCommEntry 1 }

tRPAdminPSDefActionAddComm2      OBJECT-TYPE
    SYNTAX      TLCommunityName
    MAX-ACCESS  read-create
    STATUS      current
    DESCRIPTION
        "The value of tRPAdminPSDefActionAddComm2 specifies a community name to
         add to any existing community for the route."
    DEFVAL      { "" }
    ::= { tRPAdminPSDefActionAddCommEntry 2 }

tRPAdminPSDefActionAddComm3      OBJECT-TYPE
    SYNTAX      TLCommunityName
    MAX-ACCESS  read-create
    STATUS      current
    DESCRIPTION
        "The value of tRPAdminPSDefActionAddComm3 specifies a community name to
         add to any existing community for the route."
    DEFVAL      { "" }
    ::= { tRPAdminPSDefActionAddCommEntry 3 }

tRPAdminPSDefActionAddComm4      OBJECT-TYPE
    SYNTAX      TLCommunityName
    MAX-ACCESS  read-create
    STATUS      current
    DESCRIPTION
        "The value of tRPAdminPSDefActionAddComm4 specifies a community name to
         add to any existing community for the route."
    DEFVAL      { "" }
    ::= { tRPAdminPSDefActionAddCommEntry 4 }

tRPAdminPSDefActionAddComm5      OBJECT-TYPE
    SYNTAX      TLCommunityName
    MAX-ACCESS  read-create
    STATUS      current
    DESCRIPTION
        "The value of tRPAdminPSDefActionAddComm5 specifies a community name to
         add to any existing community for the route."
    DEFVAL      { "" }
    ::= { tRPAdminPSDefActionAddCommEntry 5 }

tRPAdminPSDefActionAddComm6      OBJECT-TYPE
    SYNTAX      TLCommunityName
    MAX-ACCESS  read-create
    STATUS      current
    DESCRIPTION
        "The value of tRPAdminPSDefActionAddComm6 specifies a community name to
         add to any existing community for the route."
    DEFVAL      { "" }
    ::= { tRPAdminPSDefActionAddCommEntry 6 }

tRPAdminPSDefActionAddComm7      OBJECT-TYPE
    SYNTAX      TLCommunityName
    MAX-ACCESS  read-create
    STATUS      current
    DESCRIPTION
        "The value of tRPAdminPSDefActionAddComm7 specifies a community name to
         add to any existing community for the route."
    DEFVAL      { "" }
    ::= { tRPAdminPSDefActionAddCommEntry 7 }

tRPAdminPSDefActionAddComm8      OBJECT-TYPE
    SYNTAX      TLCommunityName
    MAX-ACCESS  read-create
    STATUS      current
    DESCRIPTION
        "The value of tRPAdminPSDefActionAddComm8 specifies a community name to
         add to any existing community for the route."
    DEFVAL      { "" }
    ::= { tRPAdminPSDefActionAddCommEntry 8 }

tRPAdminPSDefActionAddComm9      OBJECT-TYPE
    SYNTAX      TLCommunityName
    MAX-ACCESS  read-create
    STATUS      current
    DESCRIPTION
        "The value of tRPAdminPSDefActionAddComm9 specifies a community name to
         add to any existing community for the route."
    DEFVAL      { "" }
    ::= { tRPAdminPSDefActionAddCommEntry 9 }

tRPAdminPSDefActionAddComm10     OBJECT-TYPE
    SYNTAX      TLCommunityName
    MAX-ACCESS  read-create
    STATUS      current
    DESCRIPTION
        "The value of tRPAdminPSDefActionAddComm10 specifies a community name
         to add to any existing community for the route."
    DEFVAL      { "" }
    ::= { tRPAdminPSDefActionAddCommEntry 10 }

tRPAdminPSDefActionAddComm11     OBJECT-TYPE
    SYNTAX      TLCommunityName
    MAX-ACCESS  read-create
    STATUS      current
    DESCRIPTION
        "The value of tRPAdminPSDefActionAddComm11 specifies a community name
         to add to any existing community for the route."
    DEFVAL      { "" }
    ::= { tRPAdminPSDefActionAddCommEntry 11 }

tRPAdminPSDefActionAddComm12     OBJECT-TYPE
    SYNTAX      TLCommunityName
    MAX-ACCESS  read-create
    STATUS      current
    DESCRIPTION
        "The value of tRPAdminPSDefActionAddComm12 specifies a community name
         to add to any existing community for the route."
    DEFVAL      { "" }
    ::= { tRPAdminPSDefActionAddCommEntry 12 }

tRPAdminPSDefActionAddComm13     OBJECT-TYPE
    SYNTAX      TLCommunityName
    MAX-ACCESS  read-create
    STATUS      current
    DESCRIPTION
        "The value of tRPAdminPSDefActionAddComm13 specifies a community name
         to add to any existing community for the route."
    DEFVAL      { "" }
    ::= { tRPAdminPSDefActionAddCommEntry 13 }

tRPAdminPSDefActionAddComm14     OBJECT-TYPE
    SYNTAX      TLCommunityName
    MAX-ACCESS  read-create
    STATUS      current
    DESCRIPTION
        "The value of tRPAdminPSDefActionAddComm14 specifies a community name
         to add to any existing community for the route."
    DEFVAL      { "" }
    ::= { tRPAdminPSDefActionAddCommEntry 14 }

tRPAdminPSDefActionAddComm15     OBJECT-TYPE
    SYNTAX      TLCommunityName
    MAX-ACCESS  read-create
    STATUS      current
    DESCRIPTION
        "The value of tRPAdminPSDefActionAddComm15 specifies a community name
         to add to any existing community for the route."
    DEFVAL      { "" }
    ::= { tRPAdminPSDefActionAddCommEntry 15 }

tRPAdminPSDefActionAddComm16     OBJECT-TYPE
    SYNTAX      TLCommunityName
    MAX-ACCESS  read-create
    STATUS      current
    DESCRIPTION
        "The value of tRPAdminPSDefActionAddComm16 specifies a community name
         to add to any existing community for the route."
    DEFVAL      { "" }
    ::= { tRPAdminPSDefActionAddCommEntry 16 }

tRPAdminPSDefActionAddComm17     OBJECT-TYPE
    SYNTAX      TLCommunityName
    MAX-ACCESS  read-create
    STATUS      current
    DESCRIPTION
        "The value of tRPAdminPSDefActionAddComm17 specifies a community name
         to add to any existing community for the route."
    DEFVAL      { "" }
    ::= { tRPAdminPSDefActionAddCommEntry 17 }

tRPAdminPSDefActionAddComm18     OBJECT-TYPE
    SYNTAX      TLCommunityName
    MAX-ACCESS  read-create
    STATUS      current
    DESCRIPTION
        "The value of tRPAdminPSDefActionAddComm18 specifies a community name
         to add to any existing community for the route."
    DEFVAL      { "" }
    ::= { tRPAdminPSDefActionAddCommEntry 18 }

tRPAdminPSDefActionAddComm19     OBJECT-TYPE
    SYNTAX      TLCommunityName
    MAX-ACCESS  read-create
    STATUS      current
    DESCRIPTION
        "The value of tRPAdminPSDefActionAddComm19 specifies a community name
         to add to any existing community for the route."
    DEFVAL      { "" }
    ::= { tRPAdminPSDefActionAddCommEntry 19 }

tRPAdminPSDefActionAddComm20     OBJECT-TYPE
    SYNTAX      TLCommunityName
    MAX-ACCESS  read-create
    STATUS      current
    DESCRIPTION
        "The value of tRPAdminPSDefActionAddComm20 specifies a community name
         to add to any existing community for the route."
    DEFVAL      { "" }
    ::= { tRPAdminPSDefActionAddCommEntry 20 }

tRPAdminPSDefActionAddComm21     OBJECT-TYPE
    SYNTAX      TLCommunityName
    MAX-ACCESS  read-create
    STATUS      current
    DESCRIPTION
        "The value of tRPAdminPSDefActionAddComm21 specifies a community name
         to add to any existing community for the route."
    DEFVAL      { "" }
    ::= { tRPAdminPSDefActionAddCommEntry 21 }

tRPAdminPSDefActionAddComm22     OBJECT-TYPE
    SYNTAX      TLCommunityName
    MAX-ACCESS  read-create
    STATUS      current
    DESCRIPTION
        "The value of tRPAdminPSDefActionAddComm22 specifies a community name
         to add to any existing community for the route."
    DEFVAL      { "" }
    ::= { tRPAdminPSDefActionAddCommEntry 22 }

tRPAdminPSDefActionAddComm23     OBJECT-TYPE
    SYNTAX      TLCommunityName
    MAX-ACCESS  read-create
    STATUS      current
    DESCRIPTION
        "The value of tRPAdminPSDefActionAddComm23 specifies a community name
         to add to any existing community for the route."
    DEFVAL      { "" }
    ::= { tRPAdminPSDefActionAddCommEntry 23 }

tRPAdminPSDefActionAddComm24     OBJECT-TYPE
    SYNTAX      TLCommunityName
    MAX-ACCESS  read-create
    STATUS      current
    DESCRIPTION
        "The value of tRPAdminPSDefActionAddComm24 specifies a community name
         to add to any existing community for the route."
    DEFVAL      { "" }
    ::= { tRPAdminPSDefActionAddCommEntry 24 }

tRPAdminPSDefActionAddComm25     OBJECT-TYPE
    SYNTAX      TLCommunityName
    MAX-ACCESS  read-create
    STATUS      current
    DESCRIPTION
        "The value of tRPAdminPSDefActionAddComm25 specifies a community name
         to add to any existing community for the route."
    DEFVAL      { "" }
    ::= { tRPAdminPSDefActionAddCommEntry 25 }

tRPAdminPSDefActionAddComm26     OBJECT-TYPE
    SYNTAX      TLCommunityName
    MAX-ACCESS  read-create
    STATUS      current
    DESCRIPTION
        "The value of tRPAdminPSDefActionAddComm26 specifies a community name
         to add to any existing community for the route."
    DEFVAL      { "" }
    ::= { tRPAdminPSDefActionAddCommEntry 26 }

tRPAdminPSDefActionAddComm27     OBJECT-TYPE
    SYNTAX      TLCommunityName
    MAX-ACCESS  read-create
    STATUS      current
    DESCRIPTION
        "The value of tRPAdminPSDefActionAddComm27 specifies a community name
         to add to any existing community for the route."
    DEFVAL      { "" }
    ::= { tRPAdminPSDefActionAddCommEntry 27 }

tRPAdminPSDefActionAddComm28     OBJECT-TYPE
    SYNTAX      TLCommunityName
    MAX-ACCESS  read-create
    STATUS      current
    DESCRIPTION
        "The value of tRPAdminPSDefActionAddComm28 specifies a community name
         to add to any existing community for the route."
    DEFVAL      { "" }
    ::= { tRPAdminPSDefActionAddCommEntry 28 }

tRPAdminPSDefActionRemCommTable  OBJECT-TYPE
    SYNTAX      SEQUENCE OF TRPAdminPSDefActionRemCommEntry
    MAX-ACCESS  not-accessible
    STATUS      current
    DESCRIPTION
        "Default community names for a policy statement to remove from routes."
    ::= { tRPAdminValueObjects 16 }

tRPAdminPSDefActionRemCommEntry  OBJECT-TYPE
    SYNTAX      TRPAdminPSDefActionRemCommEntry
    MAX-ACCESS  not-accessible
    STATUS      current
    DESCRIPTION
        "Default action information about a particular policy statement.

         These communities are applied when the default action for the policy
         statement (tRPAdminPolicyStatementDefaultAction) is 'accept(1)'.

         Entries are created or deleted when an entry in
         tRPAdminPSDefaultActionParamsTable is created or deleted."
    AUGMENTS    { tRPAdminPSDefaultActionParamsEntry }
    ::= { tRPAdminPSDefActionRemCommTable 1 }

TRPAdminPSDefActionRemCommEntry  ::= SEQUENCE
{
    tRPAdminPSDefActionRemoveComm1   TLCommunityName,
    tRPAdminPSDefActionRemoveComm2   TLCommunityName,
    tRPAdminPSDefActionRemoveComm3   TLCommunityName,
    tRPAdminPSDefActionRemoveComm4   TLCommunityName,
    tRPAdminPSDefActionRemoveComm5   TLCommunityName,
    tRPAdminPSDefActionRemoveComm6   TLCommunityName,
    tRPAdminPSDefActionRemoveComm7   TLCommunityName,
    tRPAdminPSDefActionRemoveComm8   TLCommunityName,
    tRPAdminPSDefActionRemoveComm9   TLCommunityName,
    tRPAdminPSDefActionRemoveComm10  TLCommunityName,
    tRPAdminPSDefActionRemoveComm11  TLCommunityName,
    tRPAdminPSDefActionRemoveComm12  TLCommunityName,
    tRPAdminPSDefActionRemoveComm13  TLCommunityName,
    tRPAdminPSDefActionRemoveComm14  TLCommunityName,
    tRPAdminPSDefActionRemoveComm15  TLCommunityName,
    tRPAdminPSDefActionRemoveComm16  TLCommunityName,
    tRPAdminPSDefActionRemoveComm17  TLCommunityName,
    tRPAdminPSDefActionRemoveComm18  TLCommunityName,
    tRPAdminPSDefActionRemoveComm19  TLCommunityName,
    tRPAdminPSDefActionRemoveComm20  TLCommunityName,
    tRPAdminPSDefActionRemoveComm21  TLCommunityName,
    tRPAdminPSDefActionRemoveComm22  TLCommunityName,
    tRPAdminPSDefActionRemoveComm23  TLCommunityName,
    tRPAdminPSDefActionRemoveComm24  TLCommunityName,
    tRPAdminPSDefActionRemoveComm25  TLCommunityName,
    tRPAdminPSDefActionRemoveComm26  TLCommunityName,
    tRPAdminPSDefActionRemoveComm27  TLCommunityName,
    tRPAdminPSDefActionRemoveComm28  TLCommunityName
}

tRPAdminPSDefActionRemoveComm1   OBJECT-TYPE
    SYNTAX      TLCommunityName
    MAX-ACCESS  read-create
    STATUS      current
    DESCRIPTION
        "The value of tRPAdminPSDefActionRemoveComm1 specifies a community name
         to remove from any existing community for the route."
    DEFVAL      { "" }
    ::= { tRPAdminPSDefActionRemCommEntry 1 }

tRPAdminPSDefActionRemoveComm2   OBJECT-TYPE
    SYNTAX      TLCommunityName
    MAX-ACCESS  read-create
    STATUS      current
    DESCRIPTION
        "The value of tRPAdminPSDefActionRemoveComm2 specifies a community name
         to remove from any existing community for the route."
    DEFVAL      { "" }
    ::= { tRPAdminPSDefActionRemCommEntry 2 }

tRPAdminPSDefActionRemoveComm3   OBJECT-TYPE
    SYNTAX      TLCommunityName
    MAX-ACCESS  read-create
    STATUS      current
    DESCRIPTION
        "The value of tRPAdminPSDefActionRemoveComm3 specifies a community name
         to remove from any existing community for the route."
    DEFVAL      { "" }
    ::= { tRPAdminPSDefActionRemCommEntry 3 }

tRPAdminPSDefActionRemoveComm4   OBJECT-TYPE
    SYNTAX      TLCommunityName
    MAX-ACCESS  read-create
    STATUS      current
    DESCRIPTION
        "The value of tRPAdminPSDefActionRemoveComm4 specifies a community name
         to remove from any existing community for the route."
    DEFVAL      { "" }
    ::= { tRPAdminPSDefActionRemCommEntry 4 }

tRPAdminPSDefActionRemoveComm5   OBJECT-TYPE
    SYNTAX      TLCommunityName
    MAX-ACCESS  read-create
    STATUS      current
    DESCRIPTION
        "The value of tRPAdminPSDefActionRemoveComm5 specifies a community name
         to remove from any existing community for the route."
    DEFVAL      { "" }
    ::= { tRPAdminPSDefActionRemCommEntry 5 }

tRPAdminPSDefActionRemoveComm6   OBJECT-TYPE
    SYNTAX      TLCommunityName
    MAX-ACCESS  read-create
    STATUS      current
    DESCRIPTION
        "The value of tRPAdminPSDefActionRemoveComm6 specifies a community name
         to remove from any existing community for the route."
    DEFVAL      { "" }
    ::= { tRPAdminPSDefActionRemCommEntry 6 }

tRPAdminPSDefActionRemoveComm7   OBJECT-TYPE
    SYNTAX      TLCommunityName
    MAX-ACCESS  read-create
    STATUS      current
    DESCRIPTION
        "The value of tRPAdminPSDefActionRemoveComm7 specifies a community name
         to remove from any existing community for the route."
    DEFVAL      { "" }
    ::= { tRPAdminPSDefActionRemCommEntry 7 }

tRPAdminPSDefActionRemoveComm8   OBJECT-TYPE
    SYNTAX      TLCommunityName
    MAX-ACCESS  read-create
    STATUS      current
    DESCRIPTION
        "The value of tRPAdminPSDefActionRemoveComm8 specifies a community name
         to remove from any existing community for the route."
    DEFVAL      { "" }
    ::= { tRPAdminPSDefActionRemCommEntry 8 }

tRPAdminPSDefActionRemoveComm9   OBJECT-TYPE
    SYNTAX      TLCommunityName
    MAX-ACCESS  read-create
    STATUS      current
    DESCRIPTION
        "The value of tRPAdminPSDefActionRemoveComm9 specifies a community name
         to remove from any existing community for the route."
    DEFVAL      { "" }
    ::= { tRPAdminPSDefActionRemCommEntry 9 }

tRPAdminPSDefActionRemoveComm10  OBJECT-TYPE
    SYNTAX      TLCommunityName
    MAX-ACCESS  read-create
    STATUS      current
    DESCRIPTION
        "The value of tRPAdminPSDefActionRemoveComm10 specifies a community
         name to remove from any existing community for the route."
    DEFVAL      { "" }
    ::= { tRPAdminPSDefActionRemCommEntry 10 }

tRPAdminPSDefActionRemoveComm11  OBJECT-TYPE
    SYNTAX      TLCommunityName
    MAX-ACCESS  read-create
    STATUS      current
    DESCRIPTION
        "The value of tRPAdminPSDefActionRemoveComm11 specifies a community
         name to remove from any existing community for the route."
    DEFVAL      { "" }
    ::= { tRPAdminPSDefActionRemCommEntry 11 }

tRPAdminPSDefActionRemoveComm12  OBJECT-TYPE
    SYNTAX      TLCommunityName
    MAX-ACCESS  read-create
    STATUS      current
    DESCRIPTION
        "The value of tRPAdminPSDefActionRemoveComm12 specifies a community
         name to remove from any existing community for the route."
    DEFVAL      { "" }
    ::= { tRPAdminPSDefActionRemCommEntry 12 }

tRPAdminPSDefActionRemoveComm13  OBJECT-TYPE
    SYNTAX      TLCommunityName
    MAX-ACCESS  read-create
    STATUS      current
    DESCRIPTION
        "The value of tRPAdminPSDefActionRemoveComm13 specifies a community
         name to remove from any existing community for the route."
    DEFVAL      { "" }
    ::= { tRPAdminPSDefActionRemCommEntry 13 }

tRPAdminPSDefActionRemoveComm14  OBJECT-TYPE
    SYNTAX      TLCommunityName
    MAX-ACCESS  read-create
    STATUS      current
    DESCRIPTION
        "The value of tRPAdminPSDefActionRemoveComm14 specifies a community
         name to remove from any existing community for the route."
    DEFVAL      { "" }
    ::= { tRPAdminPSDefActionRemCommEntry 14 }

tRPAdminPSDefActionRemoveComm15  OBJECT-TYPE
    SYNTAX      TLCommunityName
    MAX-ACCESS  read-create
    STATUS      current
    DESCRIPTION
        "The value of tRPAdminPSDefActionRemoveComm15 specifies a community
         name to remove from any existing community for the route."
    DEFVAL      { "" }
    ::= { tRPAdminPSDefActionRemCommEntry 15 }

tRPAdminPSDefActionRemoveComm16  OBJECT-TYPE
    SYNTAX      TLCommunityName
    MAX-ACCESS  read-create
    STATUS      current
    DESCRIPTION
        "The value of tRPAdminPSDefActionRemoveComm16 specifies a community
         name to remove from any existing community for the route."
    DEFVAL      { "" }
    ::= { tRPAdminPSDefActionRemCommEntry 16 }

tRPAdminPSDefActionRemoveComm17  OBJECT-TYPE
    SYNTAX      TLCommunityName
    MAX-ACCESS  read-create
    STATUS      current
    DESCRIPTION
        "The value of tRPAdminPSDefActionRemoveComm17 specifies a community
         name to remove from any existing community for the route."
    DEFVAL      { "" }
    ::= { tRPAdminPSDefActionRemCommEntry 17 }

tRPAdminPSDefActionRemoveComm18  OBJECT-TYPE
    SYNTAX      TLCommunityName
    MAX-ACCESS  read-create
    STATUS      current
    DESCRIPTION
        "The value of tRPAdminPSDefActionRemoveComm18 specifies a community
         name to remove from any existing community for the route."
    DEFVAL      { "" }
    ::= { tRPAdminPSDefActionRemCommEntry 18 }

tRPAdminPSDefActionRemoveComm19  OBJECT-TYPE
    SYNTAX      TLCommunityName
    MAX-ACCESS  read-create
    STATUS      current
    DESCRIPTION
        "The value of tRPAdminPSDefActionRemoveComm19 specifies a community
         name to remove from any existing community for the route."
    DEFVAL      { "" }
    ::= { tRPAdminPSDefActionRemCommEntry 19 }

tRPAdminPSDefActionRemoveComm20  OBJECT-TYPE
    SYNTAX      TLCommunityName
    MAX-ACCESS  read-create
    STATUS      current
    DESCRIPTION
        "The value of tRPAdminPSDefActionRemoveComm20 specifies a community
         name to remove from any existing community for the route."
    DEFVAL      { "" }
    ::= { tRPAdminPSDefActionRemCommEntry 20 }

tRPAdminPSDefActionRemoveComm21  OBJECT-TYPE
    SYNTAX      TLCommunityName
    MAX-ACCESS  read-create
    STATUS      current
    DESCRIPTION
        "The value of tRPAdminPSDefActionRemoveComm21 specifies a community
         name to remove from any existing community for the route."
    DEFVAL      { "" }
    ::= { tRPAdminPSDefActionRemCommEntry 21 }

tRPAdminPSDefActionRemoveComm22  OBJECT-TYPE
    SYNTAX      TLCommunityName
    MAX-ACCESS  read-create
    STATUS      current
    DESCRIPTION
        "The value of tRPAdminPSDefActionRemoveComm22 specifies a community
         name to remove from any existing community for the route."
    DEFVAL      { "" }
    ::= { tRPAdminPSDefActionRemCommEntry 22 }

tRPAdminPSDefActionRemoveComm23  OBJECT-TYPE
    SYNTAX      TLCommunityName
    MAX-ACCESS  read-create
    STATUS      current
    DESCRIPTION
        "The value of tRPAdminPSDefActionRemoveComm23 specifies a community
         name to remove from any existing community for the route."
    DEFVAL      { "" }
    ::= { tRPAdminPSDefActionRemCommEntry 23 }

tRPAdminPSDefActionRemoveComm24  OBJECT-TYPE
    SYNTAX      TLCommunityName
    MAX-ACCESS  read-create
    STATUS      current
    DESCRIPTION
        "The value of tRPAdminPSDefActionRemoveComm24 specifies a community
         name to remove from any existing community for the route."
    DEFVAL      { "" }
    ::= { tRPAdminPSDefActionRemCommEntry 24 }

tRPAdminPSDefActionRemoveComm25  OBJECT-TYPE
    SYNTAX      TLCommunityName
    MAX-ACCESS  read-create
    STATUS      current
    DESCRIPTION
        "The value of tRPAdminPSDefActionRemoveComm25 specifies a community
         name to remove from any existing community for the route."
    DEFVAL      { "" }
    ::= { tRPAdminPSDefActionRemCommEntry 25 }

tRPAdminPSDefActionRemoveComm26  OBJECT-TYPE
    SYNTAX      TLCommunityName
    MAX-ACCESS  read-create
    STATUS      current
    DESCRIPTION
        "The value of tRPAdminPSDefActionRemoveComm26 specifies a community
         name to remove from any existing community for the route."
    DEFVAL      { "" }
    ::= { tRPAdminPSDefActionRemCommEntry 26 }

tRPAdminPSDefActionRemoveComm27  OBJECT-TYPE
    SYNTAX      TLCommunityName
    MAX-ACCESS  read-create
    STATUS      current
    DESCRIPTION
        "The value of tRPAdminPSDefActionRemoveComm27 specifies a community
         name to remove from any existing community for the route."
    DEFVAL      { "" }
    ::= { tRPAdminPSDefActionRemCommEntry 27 }

tRPAdminPSDefActionRemoveComm28  OBJECT-TYPE
    SYNTAX      TLCommunityName
    MAX-ACCESS  read-create
    STATUS      current
    DESCRIPTION
        "The value of tRPAdminPSDefActionRemoveComm28 specifies a community
         name to remove from any existing community for the route."
    DEFVAL      { "" }
    ::= { tRPAdminPSDefActionRemCommEntry 28 }

tRPAdminPSDefActionRepCommTable  OBJECT-TYPE
    SYNTAX      SEQUENCE OF TRPAdminPSDefActionRepCommEntry
    MAX-ACCESS  not-accessible
    STATUS      current
    DESCRIPTION
        "Default community names for a policy statement to replace in routes."
    ::= { tRPAdminValueObjects 17 }

tRPAdminPSDefActionRepCommEntry  OBJECT-TYPE
    SYNTAX      TRPAdminPSDefActionRepCommEntry
    MAX-ACCESS  not-accessible
    STATUS      current
    DESCRIPTION
        "Default action information about a particular policy statement.

         These communities are applied when the default action for the policy
         statement (tRPAdminPolicyStatementDefaultAction) is 'accept(1)'.

         Entries are created or deleted when an entry in
         tRPAdminPSDefaultActionParamsTable is created or deleted."
    AUGMENTS    { tRPAdminPSDefaultActionParamsEntry }
    ::= { tRPAdminPSDefActionRepCommTable 1 }

TRPAdminPSDefActionRepCommEntry  ::= SEQUENCE
{
    tRPAdminPSDefActionReplaceComm1  TLCommunityName,
    tRPAdminPSDefActionReplaceComm2  TLCommunityName,
    tRPAdminPSDefActionReplaceComm3  TLCommunityName,
    tRPAdminPSDefActionReplaceComm4  TLCommunityName,
    tRPAdminPSDefActionReplaceComm5  TLCommunityName,
    tRPAdminPSDefActionReplaceComm6  TLCommunityName,
    tRPAdminPSDefActionReplaceComm7  TLCommunityName,
    tRPAdminPSDefActionReplaceComm8  TLCommunityName,
    tRPAdminPSDefActionReplaceComm9  TLCommunityName,
    tRPAdminPSDefActionReplaceComm10 TLCommunityName,
    tRPAdminPSDefActionReplaceComm11 TLCommunityName,
    tRPAdminPSDefActionReplaceComm12 TLCommunityName,
    tRPAdminPSDefActionReplaceComm13 TLCommunityName,
    tRPAdminPSDefActionReplaceComm14 TLCommunityName,
    tRPAdminPSDefActionReplaceComm15 TLCommunityName,
    tRPAdminPSDefActionReplaceComm16 TLCommunityName,
    tRPAdminPSDefActionReplaceComm17 TLCommunityName,
    tRPAdminPSDefActionReplaceComm18 TLCommunityName,
    tRPAdminPSDefActionReplaceComm19 TLCommunityName,
    tRPAdminPSDefActionReplaceComm20 TLCommunityName,
    tRPAdminPSDefActionReplaceComm21 TLCommunityName,
    tRPAdminPSDefActionReplaceComm22 TLCommunityName,
    tRPAdminPSDefActionReplaceComm23 TLCommunityName,
    tRPAdminPSDefActionReplaceComm24 TLCommunityName,
    tRPAdminPSDefActionReplaceComm25 TLCommunityName,
    tRPAdminPSDefActionReplaceComm26 TLCommunityName,
    tRPAdminPSDefActionReplaceComm27 TLCommunityName,
    tRPAdminPSDefActionReplaceComm28 TLCommunityName
}

tRPAdminPSDefActionReplaceComm1  OBJECT-TYPE
    SYNTAX      TLCommunityName
    MAX-ACCESS  read-create
    STATUS      current
    DESCRIPTION
        "The value of tRPAdminPSDefActionReplaceComm1 specifies a community
         name to replace in any existing community for the route."
    DEFVAL      { "" }
    ::= { tRPAdminPSDefActionRepCommEntry 1 }

tRPAdminPSDefActionReplaceComm2  OBJECT-TYPE
    SYNTAX      TLCommunityName
    MAX-ACCESS  read-create
    STATUS      current
    DESCRIPTION
        "The value of tRPAdminPSDefActionReplaceComm2 specifies a community
         name to replace in any existing community for the route."
    DEFVAL      { "" }
    ::= { tRPAdminPSDefActionRepCommEntry 2 }

tRPAdminPSDefActionReplaceComm3  OBJECT-TYPE
    SYNTAX      TLCommunityName
    MAX-ACCESS  read-create
    STATUS      current
    DESCRIPTION
        "The value of tRPAdminPSDefActionReplaceComm3 specifies a community
         name to replace in any existing community for the route."
    DEFVAL      { "" }
    ::= { tRPAdminPSDefActionRepCommEntry 3 }

tRPAdminPSDefActionReplaceComm4  OBJECT-TYPE
    SYNTAX      TLCommunityName
    MAX-ACCESS  read-create
    STATUS      current
    DESCRIPTION
        "The value of tRPAdminPSDefActionReplaceComm4 specifies a community
         name to replace in any existing community for the route."
    DEFVAL      { "" }
    ::= { tRPAdminPSDefActionRepCommEntry 4 }

tRPAdminPSDefActionReplaceComm5  OBJECT-TYPE
    SYNTAX      TLCommunityName
    MAX-ACCESS  read-create
    STATUS      current
    DESCRIPTION
        "The value of tRPAdminPSDefActionReplaceComm5 specifies a community
         name to replace in any existing community for the route."
    DEFVAL      { "" }
    ::= { tRPAdminPSDefActionRepCommEntry 5 }

tRPAdminPSDefActionReplaceComm6  OBJECT-TYPE
    SYNTAX      TLCommunityName
    MAX-ACCESS  read-create
    STATUS      current
    DESCRIPTION
        "The value of tRPAdminPSDefActionReplaceComm6 specifies a community
         name to replace in any existing community for the route."
    DEFVAL      { "" }
    ::= { tRPAdminPSDefActionRepCommEntry 6 }

tRPAdminPSDefActionReplaceComm7  OBJECT-TYPE
    SYNTAX      TLCommunityName
    MAX-ACCESS  read-create
    STATUS      current
    DESCRIPTION
        "The value of tRPAdminPSDefActionReplaceComm7 specifies a community
         name to replace in any existing community for the route."
    DEFVAL      { "" }
    ::= { tRPAdminPSDefActionRepCommEntry 7 }

tRPAdminPSDefActionReplaceComm8  OBJECT-TYPE
    SYNTAX      TLCommunityName
    MAX-ACCESS  read-create
    STATUS      current
    DESCRIPTION
        "The value of tRPAdminPSDefActionReplaceComm8 specifies a community
         name to replace in any existing community for the route."
    DEFVAL      { "" }
    ::= { tRPAdminPSDefActionRepCommEntry 8 }

tRPAdminPSDefActionReplaceComm9  OBJECT-TYPE
    SYNTAX      TLCommunityName
    MAX-ACCESS  read-create
    STATUS      current
    DESCRIPTION
        "The value of tRPAdminPSDefActionReplaceComm9 specifies a community
         name to replace in any existing community for the route."
    DEFVAL      { "" }
    ::= { tRPAdminPSDefActionRepCommEntry 9 }

tRPAdminPSDefActionReplaceComm10 OBJECT-TYPE
    SYNTAX      TLCommunityName
    MAX-ACCESS  read-create
    STATUS      current
    DESCRIPTION
        "The value of tRPAdminPSDefActionReplaceComm10 specifies a community
         name to replace in any existing community for the route."
    DEFVAL      { "" }
    ::= { tRPAdminPSDefActionRepCommEntry 10 }

tRPAdminPSDefActionReplaceComm11 OBJECT-TYPE
    SYNTAX      TLCommunityName
    MAX-ACCESS  read-create
    STATUS      current
    DESCRIPTION
        "The value of tRPAdminPSDefActionReplaceComm11 specifies a community
         name to replace in any existing community for the route."
    DEFVAL      { "" }
    ::= { tRPAdminPSDefActionRepCommEntry 11 }

tRPAdminPSDefActionReplaceComm12 OBJECT-TYPE
    SYNTAX      TLCommunityName
    MAX-ACCESS  read-create
    STATUS      current
    DESCRIPTION
        "The value of tRPAdminPSDefActionReplaceComm12 specifies a community
         name to replace in any existing community for the route."
    DEFVAL      { "" }
    ::= { tRPAdminPSDefActionRepCommEntry 12 }

tRPAdminPSDefActionReplaceComm13 OBJECT-TYPE
    SYNTAX      TLCommunityName
    MAX-ACCESS  read-create
    STATUS      current
    DESCRIPTION
        "The value of tRPAdminPSDefActionReplaceComm13 specifies a community
         name to replace in any existing community for the route."
    DEFVAL      { "" }
    ::= { tRPAdminPSDefActionRepCommEntry 13 }

tRPAdminPSDefActionReplaceComm14 OBJECT-TYPE
    SYNTAX      TLCommunityName
    MAX-ACCESS  read-create
    STATUS      current
    DESCRIPTION
        "The value of tRPAdminPSDefActionReplaceComm14 specifies a community
         name to replace in any existing community for the route."
    DEFVAL      { "" }
    ::= { tRPAdminPSDefActionRepCommEntry 14 }

tRPAdminPSDefActionReplaceComm15 OBJECT-TYPE
    SYNTAX      TLCommunityName
    MAX-ACCESS  read-create
    STATUS      current
    DESCRIPTION
        "The value of tRPAdminPSDefActionReplaceComm15 specifies a community
         name to replace in any existing community for the route."
    DEFVAL      { "" }
    ::= { tRPAdminPSDefActionRepCommEntry 15 }

tRPAdminPSDefActionReplaceComm16 OBJECT-TYPE
    SYNTAX      TLCommunityName
    MAX-ACCESS  read-create
    STATUS      current
    DESCRIPTION
        "The value of tRPAdminPSDefActionReplaceComm16 specifies a community
         name to replace in any existing community for the route."
    DEFVAL      { "" }
    ::= { tRPAdminPSDefActionRepCommEntry 16 }

tRPAdminPSDefActionReplaceComm17 OBJECT-TYPE
    SYNTAX      TLCommunityName
    MAX-ACCESS  read-create
    STATUS      current
    DESCRIPTION
        "The value of tRPAdminPSDefActionReplaceComm17 specifies a community
         name to replace in any existing community for the route."
    DEFVAL      { "" }
    ::= { tRPAdminPSDefActionRepCommEntry 17 }

tRPAdminPSDefActionReplaceComm18 OBJECT-TYPE
    SYNTAX      TLCommunityName
    MAX-ACCESS  read-create
    STATUS      current
    DESCRIPTION
        "The value of tRPAdminPSDefActionReplaceComm18 specifies a community
         name to replace in any existing community for the route."
    DEFVAL      { "" }
    ::= { tRPAdminPSDefActionRepCommEntry 18 }

tRPAdminPSDefActionReplaceComm19 OBJECT-TYPE
    SYNTAX      TLCommunityName
    MAX-ACCESS  read-create
    STATUS      current
    DESCRIPTION
        "The value of tRPAdminPSDefActionReplaceComm19 specifies a community
         name to replace in any existing community for the route."
    DEFVAL      { "" }
    ::= { tRPAdminPSDefActionRepCommEntry 19 }

tRPAdminPSDefActionReplaceComm20 OBJECT-TYPE
    SYNTAX      TLCommunityName
    MAX-ACCESS  read-create
    STATUS      current
    DESCRIPTION
        "The value of tRPAdminPSDefActionReplaceComm20 specifies a community
         name to replace in any existing community for the route."
    DEFVAL      { "" }
    ::= { tRPAdminPSDefActionRepCommEntry 20 }

tRPAdminPSDefActionReplaceComm21 OBJECT-TYPE
    SYNTAX      TLCommunityName
    MAX-ACCESS  read-create
    STATUS      current
    DESCRIPTION
        "The value of tRPAdminPSDefActionReplaceComm21 specifies a community
         name to replace in any existing community for the route."
    DEFVAL      { "" }
    ::= { tRPAdminPSDefActionRepCommEntry 21 }

tRPAdminPSDefActionReplaceComm22 OBJECT-TYPE
    SYNTAX      TLCommunityName
    MAX-ACCESS  read-create
    STATUS      current
    DESCRIPTION
        "The value of tRPAdminPSDefActionReplaceComm22 specifies a community
         name to replace in any existing community for the route."
    DEFVAL      { "" }
    ::= { tRPAdminPSDefActionRepCommEntry 22 }

tRPAdminPSDefActionReplaceComm23 OBJECT-TYPE
    SYNTAX      TLCommunityName
    MAX-ACCESS  read-create
    STATUS      current
    DESCRIPTION
        "The value of tRPAdminPSDefActionReplaceComm23 specifies a community
         name to replace in any existing community for the route."
    DEFVAL      { "" }
    ::= { tRPAdminPSDefActionRepCommEntry 23 }

tRPAdminPSDefActionReplaceComm24 OBJECT-TYPE
    SYNTAX      TLCommunityName
    MAX-ACCESS  read-create
    STATUS      current
    DESCRIPTION
        "The value of tRPAdminPSDefActionReplaceComm24 specifies a community
         name to replace in any existing community for the route."
    DEFVAL      { "" }
    ::= { tRPAdminPSDefActionRepCommEntry 24 }

tRPAdminPSDefActionReplaceComm25 OBJECT-TYPE
    SYNTAX      TLCommunityName
    MAX-ACCESS  read-create
    STATUS      current
    DESCRIPTION
        "The value of tRPAdminPSDefActionReplaceComm25 specifies a community
         name to replace in any existing community for the route."
    DEFVAL      { "" }
    ::= { tRPAdminPSDefActionRepCommEntry 25 }

tRPAdminPSDefActionReplaceComm26 OBJECT-TYPE
    SYNTAX      TLCommunityName
    MAX-ACCESS  read-create
    STATUS      current
    DESCRIPTION
        "The value of tRPAdminPSDefActionReplaceComm26 specifies a community
         name to replace in any existing community for the route."
    DEFVAL      { "" }
    ::= { tRPAdminPSDefActionRepCommEntry 26 }

tRPAdminPSDefActionReplaceComm27 OBJECT-TYPE
    SYNTAX      TLCommunityName
    MAX-ACCESS  read-create
    STATUS      current
    DESCRIPTION
        "The value of tRPAdminPSDefActionReplaceComm27 specifies a community
         name to replace in any existing community for the route."
    DEFVAL      { "" }
    ::= { tRPAdminPSDefActionRepCommEntry 27 }

tRPAdminPSDefActionReplaceComm28 OBJECT-TYPE
    SYNTAX      TLCommunityName
    MAX-ACCESS  read-create
    STATUS      current
    DESCRIPTION
        "The value of tRPAdminPSDefActionReplaceComm28 specifies a community
         name to replace in any existing community for the route."
    DEFVAL      { "" }
    ::= { tRPAdminPSDefActionRepCommEntry 28 }

tRPAdminPSAccActionAddCommTable  OBJECT-TYPE
    SYNTAX      SEQUENCE OF TRPAdminPSAccActionAddCommEntry
    MAX-ACCESS  not-accessible
    STATUS      current
    DESCRIPTION
        "Community names for a policy statement entry to add to routes."
    ::= { tRPAdminValueObjects 18 }

tRPAdminPSAccActionAddCommEntry  OBJECT-TYPE
    SYNTAX      TRPAdminPSAccActionAddCommEntry
    MAX-ACCESS  not-accessible
    STATUS      current
    DESCRIPTION
        "Accept-action information about a particular policy statement entry.

         These communities are applied when the action for the policy statement
         entry (tRPAdminPSParamsAction) is 'accept(1)'.

         Entries are created or deleted when an entry in
         tRPAdminPSAcceptActionParamsTable is created or deleted."
    AUGMENTS    { tRPAdminPSAcceptActionParamsEntry }
    ::= { tRPAdminPSAccActionAddCommTable 1 }

TRPAdminPSAccActionAddCommEntry  ::= SEQUENCE
{
    tRPAdminPSAccActionAddComm1      TLCommunityName,
    tRPAdminPSAccActionAddComm2      TLCommunityName,
    tRPAdminPSAccActionAddComm3      TLCommunityName,
    tRPAdminPSAccActionAddComm4      TLCommunityName,
    tRPAdminPSAccActionAddComm5      TLCommunityName,
    tRPAdminPSAccActionAddComm6      TLCommunityName,
    tRPAdminPSAccActionAddComm7      TLCommunityName,
    tRPAdminPSAccActionAddComm8      TLCommunityName,
    tRPAdminPSAccActionAddComm9      TLCommunityName,
    tRPAdminPSAccActionAddComm10     TLCommunityName,
    tRPAdminPSAccActionAddComm11     TLCommunityName,
    tRPAdminPSAccActionAddComm12     TLCommunityName,
    tRPAdminPSAccActionAddComm13     TLCommunityName,
    tRPAdminPSAccActionAddComm14     TLCommunityName,
    tRPAdminPSAccActionAddComm15     TLCommunityName,
    tRPAdminPSAccActionAddComm16     TLCommunityName,
    tRPAdminPSAccActionAddComm17     TLCommunityName,
    tRPAdminPSAccActionAddComm18     TLCommunityName,
    tRPAdminPSAccActionAddComm19     TLCommunityName,
    tRPAdminPSAccActionAddComm20     TLCommunityName,
    tRPAdminPSAccActionAddComm21     TLCommunityName,
    tRPAdminPSAccActionAddComm22     TLCommunityName,
    tRPAdminPSAccActionAddComm23     TLCommunityName,
    tRPAdminPSAccActionAddComm24     TLCommunityName,
    tRPAdminPSAccActionAddComm25     TLCommunityName,
    tRPAdminPSAccActionAddComm26     TLCommunityName,
    tRPAdminPSAccActionAddComm27     TLCommunityName,
    tRPAdminPSAccActionAddComm28     TLCommunityName,
    tRPAdminPSAccActionAddCommCrOrig TmnxCreateOrigin
}

tRPAdminPSAccActionAddComm1      OBJECT-TYPE
    SYNTAX      TLCommunityName
    MAX-ACCESS  read-create
    STATUS      current
    DESCRIPTION
        "The value of tRPAdminPSAccActionAddComm1 specifies a community name to
         add to any existing community for the route."
    DEFVAL      { "" }
    ::= { tRPAdminPSAccActionAddCommEntry 1 }

tRPAdminPSAccActionAddComm2      OBJECT-TYPE
    SYNTAX      TLCommunityName
    MAX-ACCESS  read-create
    STATUS      current
    DESCRIPTION
        "The value of tRPAdminPSAccActionAddComm2 specifies a community name to
         add to any existing community for the route."
    DEFVAL      { "" }
    ::= { tRPAdminPSAccActionAddCommEntry 2 }

tRPAdminPSAccActionAddComm3      OBJECT-TYPE
    SYNTAX      TLCommunityName
    MAX-ACCESS  read-create
    STATUS      current
    DESCRIPTION
        "The value of tRPAdminPSAccActionAddComm3 specifies a community name to
         add to any existing community for the route."
    DEFVAL      { "" }
    ::= { tRPAdminPSAccActionAddCommEntry 3 }

tRPAdminPSAccActionAddComm4      OBJECT-TYPE
    SYNTAX      TLCommunityName
    MAX-ACCESS  read-create
    STATUS      current
    DESCRIPTION
        "The value of tRPAdminPSAccActionAddComm4 specifies a community name to
         add to any existing community for the route."
    DEFVAL      { "" }
    ::= { tRPAdminPSAccActionAddCommEntry 4 }

tRPAdminPSAccActionAddComm5      OBJECT-TYPE
    SYNTAX      TLCommunityName
    MAX-ACCESS  read-create
    STATUS      current
    DESCRIPTION
        "The value of tRPAdminPSAccActionAddComm5 specifies a community name to
         add to any existing community for the route."
    DEFVAL      { "" }
    ::= { tRPAdminPSAccActionAddCommEntry 5 }

tRPAdminPSAccActionAddComm6      OBJECT-TYPE
    SYNTAX      TLCommunityName
    MAX-ACCESS  read-create
    STATUS      current
    DESCRIPTION
        "The value of tRPAdminPSAccActionAddComm6 specifies a community name to
         add to any existing community for the route."
    DEFVAL      { "" }
    ::= { tRPAdminPSAccActionAddCommEntry 6 }

tRPAdminPSAccActionAddComm7      OBJECT-TYPE
    SYNTAX      TLCommunityName
    MAX-ACCESS  read-create
    STATUS      current
    DESCRIPTION
        "The value of tRPAdminPSAccActionAddComm7 specifies a community name to
         add to any existing community for the route."
    DEFVAL      { "" }
    ::= { tRPAdminPSAccActionAddCommEntry 7 }

tRPAdminPSAccActionAddComm8      OBJECT-TYPE
    SYNTAX      TLCommunityName
    MAX-ACCESS  read-create
    STATUS      current
    DESCRIPTION
        "The value of tRPAdminPSAccActionAddComm8 specifies a community name to
         add to any existing community for the route."
    DEFVAL      { "" }
    ::= { tRPAdminPSAccActionAddCommEntry 8 }

tRPAdminPSAccActionAddComm9      OBJECT-TYPE
    SYNTAX      TLCommunityName
    MAX-ACCESS  read-create
    STATUS      current
    DESCRIPTION
        "The value of tRPAdminPSAccActionAddComm9 specifies a community name to
         add to any existing community for the route."
    DEFVAL      { "" }
    ::= { tRPAdminPSAccActionAddCommEntry 9 }

tRPAdminPSAccActionAddComm10     OBJECT-TYPE
    SYNTAX      TLCommunityName
    MAX-ACCESS  read-create
    STATUS      current
    DESCRIPTION
        "The value of tRPAdminPSAccActionAddComm10 specifies a community name
         to add to any existing community for the route."
    DEFVAL      { "" }
    ::= { tRPAdminPSAccActionAddCommEntry 10 }

tRPAdminPSAccActionAddComm11     OBJECT-TYPE
    SYNTAX      TLCommunityName
    MAX-ACCESS  read-create
    STATUS      current
    DESCRIPTION
        "The value of tRPAdminPSAccActionAddComm11 specifies a community name
         to add to any existing community for the route."
    DEFVAL      { "" }
    ::= { tRPAdminPSAccActionAddCommEntry 11 }

tRPAdminPSAccActionAddComm12     OBJECT-TYPE
    SYNTAX      TLCommunityName
    MAX-ACCESS  read-create
    STATUS      current
    DESCRIPTION
        "The value of tRPAdminPSAccActionAddComm12 specifies a community name
         to add to any existing community for the route."
    DEFVAL      { "" }
    ::= { tRPAdminPSAccActionAddCommEntry 12 }

tRPAdminPSAccActionAddComm13     OBJECT-TYPE
    SYNTAX      TLCommunityName
    MAX-ACCESS  read-create
    STATUS      current
    DESCRIPTION
        "The value of tRPAdminPSAccActionAddComm13 specifies a community name
         to add to any existing community for the route."
    DEFVAL      { "" }
    ::= { tRPAdminPSAccActionAddCommEntry 13 }

tRPAdminPSAccActionAddComm14     OBJECT-TYPE
    SYNTAX      TLCommunityName
    MAX-ACCESS  read-create
    STATUS      current
    DESCRIPTION
        "The value of tRPAdminPSAccActionAddComm14 specifies a community name
         to add to any existing community for the route."
    DEFVAL      { "" }
    ::= { tRPAdminPSAccActionAddCommEntry 14 }

tRPAdminPSAccActionAddComm15     OBJECT-TYPE
    SYNTAX      TLCommunityName
    MAX-ACCESS  read-create
    STATUS      current
    DESCRIPTION
        "The value of tRPAdminPSAccActionAddComm15 specifies a community name
         to add to any existing community for the route."
    DEFVAL      { "" }
    ::= { tRPAdminPSAccActionAddCommEntry 15 }

tRPAdminPSAccActionAddComm16     OBJECT-TYPE
    SYNTAX      TLCommunityName
    MAX-ACCESS  read-create
    STATUS      current
    DESCRIPTION
        "The value of tRPAdminPSAccActionAddComm16 specifies a community name
         to add to any existing community for the route."
    DEFVAL      { "" }
    ::= { tRPAdminPSAccActionAddCommEntry 16 }

tRPAdminPSAccActionAddComm17     OBJECT-TYPE
    SYNTAX      TLCommunityName
    MAX-ACCESS  read-create
    STATUS      current
    DESCRIPTION
        "The value of tRPAdminPSAccActionAddComm17 specifies a community name
         to add to any existing community for the route."
    DEFVAL      { "" }
    ::= { tRPAdminPSAccActionAddCommEntry 17 }

tRPAdminPSAccActionAddComm18     OBJECT-TYPE
    SYNTAX      TLCommunityName
    MAX-ACCESS  read-create
    STATUS      current
    DESCRIPTION
        "The value of tRPAdminPSAccActionAddComm18 specifies a community name
         to add to any existing community for the route."
    DEFVAL      { "" }
    ::= { tRPAdminPSAccActionAddCommEntry 18 }

tRPAdminPSAccActionAddComm19     OBJECT-TYPE
    SYNTAX      TLCommunityName
    MAX-ACCESS  read-create
    STATUS      current
    DESCRIPTION
        "The value of tRPAdminPSAccActionAddComm19 specifies a community name
         to add to any existing community for the route."
    DEFVAL      { "" }
    ::= { tRPAdminPSAccActionAddCommEntry 19 }

tRPAdminPSAccActionAddComm20     OBJECT-TYPE
    SYNTAX      TLCommunityName
    MAX-ACCESS  read-create
    STATUS      current
    DESCRIPTION
        "The value of tRPAdminPSAccActionAddComm20 specifies a community name
         to add to any existing community for the route."
    DEFVAL      { "" }
    ::= { tRPAdminPSAccActionAddCommEntry 20 }

tRPAdminPSAccActionAddComm21     OBJECT-TYPE
    SYNTAX      TLCommunityName
    MAX-ACCESS  read-create
    STATUS      current
    DESCRIPTION
        "The value of tRPAdminPSAccActionAddComm21 specifies a community name
         to add to any existing community for the route."
    DEFVAL      { "" }
    ::= { tRPAdminPSAccActionAddCommEntry 21 }

tRPAdminPSAccActionAddComm22     OBJECT-TYPE
    SYNTAX      TLCommunityName
    MAX-ACCESS  read-create
    STATUS      current
    DESCRIPTION
        "The value of tRPAdminPSAccActionAddComm22 specifies a community name
         to add to any existing community for the route."
    DEFVAL      { "" }
    ::= { tRPAdminPSAccActionAddCommEntry 22 }

tRPAdminPSAccActionAddComm23     OBJECT-TYPE
    SYNTAX      TLCommunityName
    MAX-ACCESS  read-create
    STATUS      current
    DESCRIPTION
        "The value of tRPAdminPSAccActionAddComm23 specifies a community name
         to add to any existing community for the route."
    DEFVAL      { "" }
    ::= { tRPAdminPSAccActionAddCommEntry 23 }

tRPAdminPSAccActionAddComm24     OBJECT-TYPE
    SYNTAX      TLCommunityName
    MAX-ACCESS  read-create
    STATUS      current
    DESCRIPTION
        "The value of tRPAdminPSAccActionAddComm24 specifies a community name
         to add to any existing community for the route."
    DEFVAL      { "" }
    ::= { tRPAdminPSAccActionAddCommEntry 24 }

tRPAdminPSAccActionAddComm25     OBJECT-TYPE
    SYNTAX      TLCommunityName
    MAX-ACCESS  read-create
    STATUS      current
    DESCRIPTION
        "The value of tRPAdminPSAccActionAddComm25 specifies a community name
         to add to any existing community for the route."
    DEFVAL      { "" }
    ::= { tRPAdminPSAccActionAddCommEntry 25 }

tRPAdminPSAccActionAddComm26     OBJECT-TYPE
    SYNTAX      TLCommunityName
    MAX-ACCESS  read-create
    STATUS      current
    DESCRIPTION
        "The value of tRPAdminPSAccActionAddComm26 specifies a community name
         to add to any existing community for the route."
    DEFVAL      { "" }
    ::= { tRPAdminPSAccActionAddCommEntry 26 }

tRPAdminPSAccActionAddComm27     OBJECT-TYPE
    SYNTAX      TLCommunityName
    MAX-ACCESS  read-create
    STATUS      current
    DESCRIPTION
        "The value of tRPAdminPSAccActionAddComm27 specifies a community name
         to add to any existing community for the route."
    DEFVAL      { "" }
    ::= { tRPAdminPSAccActionAddCommEntry 27 }

tRPAdminPSAccActionAddComm28     OBJECT-TYPE
    SYNTAX      TLCommunityName
    MAX-ACCESS  read-create
    STATUS      current
    DESCRIPTION
        "The value of tRPAdminPSAccActionAddComm28 specifies a community name
         to add to any existing community for the route."
    DEFVAL      { "" }
    ::= { tRPAdminPSAccActionAddCommEntry 28 }

tRPAdminPSAccActionAddCommCrOrig OBJECT-TYPE
    SYNTAX      TmnxCreateOrigin
    MAX-ACCESS  read-only
    STATUS      current
    DESCRIPTION
        "The value of the object tRPAdminPSAccActionAddCommCrOrig indicates the
         mechanism used to create this entry."
    ::= { tRPAdminPSAccActionAddCommEntry 29 }

tRPAdminPSAccActionRemCommTable  OBJECT-TYPE
    SYNTAX      SEQUENCE OF TRPAdminPSAccActionRemCommEntry
    MAX-ACCESS  not-accessible
    STATUS      current
    DESCRIPTION
        "Community names for a policy statement entry to remove from routes."
    ::= { tRPAdminValueObjects 19 }

tRPAdminPSAccActionRemCommEntry  OBJECT-TYPE
    SYNTAX      TRPAdminPSAccActionRemCommEntry
    MAX-ACCESS  not-accessible
    STATUS      current
    DESCRIPTION
        "Accept-action information about a particular policy statement entry.

         These communities are applied when the action for the policy statement
         entry (tRPAdminPSParamsAction) is 'accept(1)'.

         Entries are created or deleted when an entry in
         tRPAdminPSAcceptActionParamsTable is created or deleted."
    AUGMENTS    { tRPAdminPSAcceptActionParamsEntry }
    ::= { tRPAdminPSAccActionRemCommTable 1 }

TRPAdminPSAccActionRemCommEntry  ::= SEQUENCE
{
    tRPAdminPSAccActionRemoveComm1   TLCommunityName,
    tRPAdminPSAccActionRemoveComm2   TLCommunityName,
    tRPAdminPSAccActionRemoveComm3   TLCommunityName,
    tRPAdminPSAccActionRemoveComm4   TLCommunityName,
    tRPAdminPSAccActionRemoveComm5   TLCommunityName,
    tRPAdminPSAccActionRemoveComm6   TLCommunityName,
    tRPAdminPSAccActionRemoveComm7   TLCommunityName,
    tRPAdminPSAccActionRemoveComm8   TLCommunityName,
    tRPAdminPSAccActionRemoveComm9   TLCommunityName,
    tRPAdminPSAccActionRemoveComm10  TLCommunityName,
    tRPAdminPSAccActionRemoveComm11  TLCommunityName,
    tRPAdminPSAccActionRemoveComm12  TLCommunityName,
    tRPAdminPSAccActionRemoveComm13  TLCommunityName,
    tRPAdminPSAccActionRemoveComm14  TLCommunityName,
    tRPAdminPSAccActionRemoveComm15  TLCommunityName,
    tRPAdminPSAccActionRemoveComm16  TLCommunityName,
    tRPAdminPSAccActionRemoveComm17  TLCommunityName,
    tRPAdminPSAccActionRemoveComm18  TLCommunityName,
    tRPAdminPSAccActionRemoveComm19  TLCommunityName,
    tRPAdminPSAccActionRemoveComm20  TLCommunityName,
    tRPAdminPSAccActionRemoveComm21  TLCommunityName,
    tRPAdminPSAccActionRemoveComm22  TLCommunityName,
    tRPAdminPSAccActionRemoveComm23  TLCommunityName,
    tRPAdminPSAccActionRemoveComm24  TLCommunityName,
    tRPAdminPSAccActionRemoveComm25  TLCommunityName,
    tRPAdminPSAccActionRemoveComm26  TLCommunityName,
    tRPAdminPSAccActionRemoveComm27  TLCommunityName,
    tRPAdminPSAccActionRemoveComm28  TLCommunityName
}

tRPAdminPSAccActionRemoveComm1   OBJECT-TYPE
    SYNTAX      TLCommunityName
    MAX-ACCESS  read-create
    STATUS      current
    DESCRIPTION
        "The value of tRPAdminPSAccActionRemoveComm1 specifies a community name
         to remove from any existing community for the route."
    DEFVAL      { "" }
    ::= { tRPAdminPSAccActionRemCommEntry 1 }

tRPAdminPSAccActionRemoveComm2   OBJECT-TYPE
    SYNTAX      TLCommunityName
    MAX-ACCESS  read-create
    STATUS      current
    DESCRIPTION
        "The value of tRPAdminPSAccActionRemoveComm2 specifies a community name
         to remove from any existing community for the route."
    DEFVAL      { "" }
    ::= { tRPAdminPSAccActionRemCommEntry 2 }

tRPAdminPSAccActionRemoveComm3   OBJECT-TYPE
    SYNTAX      TLCommunityName
    MAX-ACCESS  read-create
    STATUS      current
    DESCRIPTION
        "The value of tRPAdminPSAccActionRemoveComm3 specifies a community name
         to remove from any existing community for the route."
    DEFVAL      { "" }
    ::= { tRPAdminPSAccActionRemCommEntry 3 }

tRPAdminPSAccActionRemoveComm4   OBJECT-TYPE
    SYNTAX      TLCommunityName
    MAX-ACCESS  read-create
    STATUS      current
    DESCRIPTION
        "The value of tRPAdminPSAccActionRemoveComm4 specifies a community name
         to remove from any existing community for the route."
    DEFVAL      { "" }
    ::= { tRPAdminPSAccActionRemCommEntry 4 }

tRPAdminPSAccActionRemoveComm5   OBJECT-TYPE
    SYNTAX      TLCommunityName
    MAX-ACCESS  read-create
    STATUS      current
    DESCRIPTION
        "The value of tRPAdminPSAccActionRemoveComm5 specifies a community name
         to remove from any existing community for the route."
    DEFVAL      { "" }
    ::= { tRPAdminPSAccActionRemCommEntry 5 }

tRPAdminPSAccActionRemoveComm6   OBJECT-TYPE
    SYNTAX      TLCommunityName
    MAX-ACCESS  read-create
    STATUS      current
    DESCRIPTION
        "The value of tRPAdminPSAccActionRemoveComm6 specifies a community name
         to remove from any existing community for the route."
    DEFVAL      { "" }
    ::= { tRPAdminPSAccActionRemCommEntry 6 }

tRPAdminPSAccActionRemoveComm7   OBJECT-TYPE
    SYNTAX      TLCommunityName
    MAX-ACCESS  read-create
    STATUS      current
    DESCRIPTION
        "The value of tRPAdminPSAccActionRemoveComm7 specifies a community name
         to remove from any existing community for the route."
    DEFVAL      { "" }
    ::= { tRPAdminPSAccActionRemCommEntry 7 }

tRPAdminPSAccActionRemoveComm8   OBJECT-TYPE
    SYNTAX      TLCommunityName
    MAX-ACCESS  read-create
    STATUS      current
    DESCRIPTION
        "The value of tRPAdminPSAccActionRemoveComm8 specifies a community name
         to remove from any existing community for the route."
    DEFVAL      { "" }
    ::= { tRPAdminPSAccActionRemCommEntry 8 }

tRPAdminPSAccActionRemoveComm9   OBJECT-TYPE
    SYNTAX      TLCommunityName
    MAX-ACCESS  read-create
    STATUS      current
    DESCRIPTION
        "The value of tRPAdminPSAccActionRemoveComm9 specifies a community name
         to remove from any existing community for the route."
    DEFVAL      { "" }
    ::= { tRPAdminPSAccActionRemCommEntry 9 }

tRPAdminPSAccActionRemoveComm10  OBJECT-TYPE
    SYNTAX      TLCommunityName
    MAX-ACCESS  read-create
    STATUS      current
    DESCRIPTION
        "The value of tRPAdminPSAccActionRemoveComm10 specifies a community
         name to remove from any existing community for the route."
    DEFVAL      { "" }
    ::= { tRPAdminPSAccActionRemCommEntry 10 }

tRPAdminPSAccActionRemoveComm11  OBJECT-TYPE
    SYNTAX      TLCommunityName
    MAX-ACCESS  read-create
    STATUS      current
    DESCRIPTION
        "The value of tRPAdminPSAccActionRemoveComm11 specifies a community
         name to remove from any existing community for the route."
    DEFVAL      { "" }
    ::= { tRPAdminPSAccActionRemCommEntry 11 }

tRPAdminPSAccActionRemoveComm12  OBJECT-TYPE
    SYNTAX      TLCommunityName
    MAX-ACCESS  read-create
    STATUS      current
    DESCRIPTION
        "The value of tRPAdminPSAccActionRemoveComm12 specifies a community
         name to remove from any existing community for the route."
    DEFVAL      { "" }
    ::= { tRPAdminPSAccActionRemCommEntry 12 }

tRPAdminPSAccActionRemoveComm13  OBJECT-TYPE
    SYNTAX      TLCommunityName
    MAX-ACCESS  read-create
    STATUS      current
    DESCRIPTION
        "The value of tRPAdminPSAccActionRemoveComm13 specifies a community
         name to remove from any existing community for the route."
    DEFVAL      { "" }
    ::= { tRPAdminPSAccActionRemCommEntry 13 }

tRPAdminPSAccActionRemoveComm14  OBJECT-TYPE
    SYNTAX      TLCommunityName
    MAX-ACCESS  read-create
    STATUS      current
    DESCRIPTION
        "The value of tRPAdminPSAccActionRemoveComm14 specifies a community
         name to remove from any existing community for the route."
    DEFVAL      { "" }
    ::= { tRPAdminPSAccActionRemCommEntry 14 }

tRPAdminPSAccActionRemoveComm15  OBJECT-TYPE
    SYNTAX      TLCommunityName
    MAX-ACCESS  read-create
    STATUS      current
    DESCRIPTION
        "The value of tRPAdminPSAccActionRemoveComm15 specifies a community
         name to remove from any existing community for the route."
    DEFVAL      { "" }
    ::= { tRPAdminPSAccActionRemCommEntry 15 }

tRPAdminPSAccActionRemoveComm16  OBJECT-TYPE
    SYNTAX      TLCommunityName
    MAX-ACCESS  read-create
    STATUS      current
    DESCRIPTION
        "The value of tRPAdminPSAccActionRemoveComm16 specifies a community
         name to remove from any existing community for the route."
    DEFVAL      { "" }
    ::= { tRPAdminPSAccActionRemCommEntry 16 }

tRPAdminPSAccActionRemoveComm17  OBJECT-TYPE
    SYNTAX      TLCommunityName
    MAX-ACCESS  read-create
    STATUS      current
    DESCRIPTION
        "The value of tRPAdminPSAccActionRemoveComm17 specifies a community
         name to remove from any existing community for the route."
    DEFVAL      { "" }
    ::= { tRPAdminPSAccActionRemCommEntry 17 }

tRPAdminPSAccActionRemoveComm18  OBJECT-TYPE
    SYNTAX      TLCommunityName
    MAX-ACCESS  read-create
    STATUS      current
    DESCRIPTION
        "The value of tRPAdminPSAccActionRemoveComm18 specifies a community
         name to remove from any existing community for the route."
    DEFVAL      { "" }
    ::= { tRPAdminPSAccActionRemCommEntry 18 }

tRPAdminPSAccActionRemoveComm19  OBJECT-TYPE
    SYNTAX      TLCommunityName
    MAX-ACCESS  read-create
    STATUS      current
    DESCRIPTION
        "The value of tRPAdminPSAccActionRemoveComm19 specifies a community
         name to remove from any existing community for the route."
    DEFVAL      { "" }
    ::= { tRPAdminPSAccActionRemCommEntry 19 }

tRPAdminPSAccActionRemoveComm20  OBJECT-TYPE
    SYNTAX      TLCommunityName
    MAX-ACCESS  read-create
    STATUS      current
    DESCRIPTION
        "The value of tRPAdminPSAccActionRemoveComm20 specifies a community
         name to remove from any existing community for the route."
    DEFVAL      { "" }
    ::= { tRPAdminPSAccActionRemCommEntry 20 }

tRPAdminPSAccActionRemoveComm21  OBJECT-TYPE
    SYNTAX      TLCommunityName
    MAX-ACCESS  read-create
    STATUS      current
    DESCRIPTION
        "The value of tRPAdminPSAccActionRemoveComm21 specifies a community
         name to remove from any existing community for the route."
    DEFVAL      { "" }
    ::= { tRPAdminPSAccActionRemCommEntry 21 }

tRPAdminPSAccActionRemoveComm22  OBJECT-TYPE
    SYNTAX      TLCommunityName
    MAX-ACCESS  read-create
    STATUS      current
    DESCRIPTION
        "The value of tRPAdminPSAccActionRemoveComm22 specifies a community
         name to remove from any existing community for the route."
    DEFVAL      { "" }
    ::= { tRPAdminPSAccActionRemCommEntry 22 }

tRPAdminPSAccActionRemoveComm23  OBJECT-TYPE
    SYNTAX      TLCommunityName
    MAX-ACCESS  read-create
    STATUS      current
    DESCRIPTION
        "The value of tRPAdminPSAccActionRemoveComm23 specifies a community
         name to remove from any existing community for the route."
    DEFVAL      { "" }
    ::= { tRPAdminPSAccActionRemCommEntry 23 }

tRPAdminPSAccActionRemoveComm24  OBJECT-TYPE
    SYNTAX      TLCommunityName
    MAX-ACCESS  read-create
    STATUS      current
    DESCRIPTION
        "The value of tRPAdminPSAccActionRemoveComm24 specifies a community
         name to remove from any existing community for the route."
    DEFVAL      { "" }
    ::= { tRPAdminPSAccActionRemCommEntry 24 }

tRPAdminPSAccActionRemoveComm25  OBJECT-TYPE
    SYNTAX      TLCommunityName
    MAX-ACCESS  read-create
    STATUS      current
    DESCRIPTION
        "The value of tRPAdminPSAccActionRemoveComm25 specifies a community
         name to remove from any existing community for the route."
    DEFVAL      { "" }
    ::= { tRPAdminPSAccActionRemCommEntry 25 }

tRPAdminPSAccActionRemoveComm26  OBJECT-TYPE
    SYNTAX      TLCommunityName
    MAX-ACCESS  read-create
    STATUS      current
    DESCRIPTION
        "The value of tRPAdminPSAccActionRemoveComm26 specifies a community
         name to remove from any existing community for the route."
    DEFVAL      { "" }
    ::= { tRPAdminPSAccActionRemCommEntry 26 }

tRPAdminPSAccActionRemoveComm27  OBJECT-TYPE
    SYNTAX      TLCommunityName
    MAX-ACCESS  read-create
    STATUS      current
    DESCRIPTION
        "The value of tRPAdminPSAccActionRemoveComm27 specifies a community
         name to remove from any existing community for the route."
    DEFVAL      { "" }
    ::= { tRPAdminPSAccActionRemCommEntry 27 }

tRPAdminPSAccActionRemoveComm28  OBJECT-TYPE
    SYNTAX      TLCommunityName
    MAX-ACCESS  read-create
    STATUS      current
    DESCRIPTION
        "The value of tRPAdminPSAccActionRemoveComm28 specifies a community
         name to remove from any existing community for the route."
    DEFVAL      { "" }
    ::= { tRPAdminPSAccActionRemCommEntry 28 }

tRPAdminPSAccActionRepCommTable  OBJECT-TYPE
    SYNTAX      SEQUENCE OF TRPAdminPSAccActionRepCommEntry
    MAX-ACCESS  not-accessible
    STATUS      current
    DESCRIPTION
        "Community names for a policy statement entry to replace in routes."
    ::= { tRPAdminValueObjects 20 }

tRPAdminPSAccActionRepCommEntry  OBJECT-TYPE
    SYNTAX      TRPAdminPSAccActionRepCommEntry
    MAX-ACCESS  not-accessible
    STATUS      current
    DESCRIPTION
        "Accept-action information about a particular policy statement entry.

         These communities are applied when the action for the policy statement
         entry (tRPAdminPSParamsAction) is 'accept(1)'.

         Entries are created or deleted when an entry in
         tRPAdminPSAcceptActionParamsTable is created or deleted."
    AUGMENTS    { tRPAdminPSAcceptActionParamsEntry }
    ::= { tRPAdminPSAccActionRepCommTable 1 }

TRPAdminPSAccActionRepCommEntry  ::= SEQUENCE
{
    tRPAdminPSAccActionReplaceComm1  TLCommunityName,
    tRPAdminPSAccActionReplaceComm2  TLCommunityName,
    tRPAdminPSAccActionReplaceComm3  TLCommunityName,
    tRPAdminPSAccActionReplaceComm4  TLCommunityName,
    tRPAdminPSAccActionReplaceComm5  TLCommunityName,
    tRPAdminPSAccActionReplaceComm6  TLCommunityName,
    tRPAdminPSAccActionReplaceComm7  TLCommunityName,
    tRPAdminPSAccActionReplaceComm8  TLCommunityName,
    tRPAdminPSAccActionReplaceComm9  TLCommunityName,
    tRPAdminPSAccActionReplaceComm10 TLCommunityName,
    tRPAdminPSAccActionReplaceComm11 TLCommunityName,
    tRPAdminPSAccActionReplaceComm12 TLCommunityName,
    tRPAdminPSAccActionReplaceComm13 TLCommunityName,
    tRPAdminPSAccActionReplaceComm14 TLCommunityName,
    tRPAdminPSAccActionReplaceComm15 TLCommunityName,
    tRPAdminPSAccActionReplaceComm16 TLCommunityName,
    tRPAdminPSAccActionReplaceComm17 TLCommunityName,
    tRPAdminPSAccActionReplaceComm18 TLCommunityName,
    tRPAdminPSAccActionReplaceComm19 TLCommunityName,
    tRPAdminPSAccActionReplaceComm20 TLCommunityName,
    tRPAdminPSAccActionReplaceComm21 TLCommunityName,
    tRPAdminPSAccActionReplaceComm22 TLCommunityName,
    tRPAdminPSAccActionReplaceComm23 TLCommunityName,
    tRPAdminPSAccActionReplaceComm24 TLCommunityName,
    tRPAdminPSAccActionReplaceComm25 TLCommunityName,
    tRPAdminPSAccActionReplaceComm26 TLCommunityName,
    tRPAdminPSAccActionReplaceComm27 TLCommunityName,
    tRPAdminPSAccActionReplaceComm28 TLCommunityName
}

tRPAdminPSAccActionReplaceComm1  OBJECT-TYPE
    SYNTAX      TLCommunityName
    MAX-ACCESS  read-create
    STATUS      current
    DESCRIPTION
        "The value of tRPAdminPSAccActionReplaceComm1 specifies a community
         name to replace in any existing community for the route."
    DEFVAL      { "" }
    ::= { tRPAdminPSAccActionRepCommEntry 1 }

tRPAdminPSAccActionReplaceComm2  OBJECT-TYPE
    SYNTAX      TLCommunityName
    MAX-ACCESS  read-create
    STATUS      current
    DESCRIPTION
        "The value of tRPAdminPSAccActionReplaceComm2 specifies a community
         name to replace in any existing community for the route."
    DEFVAL      { "" }
    ::= { tRPAdminPSAccActionRepCommEntry 2 }

tRPAdminPSAccActionReplaceComm3  OBJECT-TYPE
    SYNTAX      TLCommunityName
    MAX-ACCESS  read-create
    STATUS      current
    DESCRIPTION
        "The value of tRPAdminPSAccActionReplaceComm3 specifies a community
         name to replace in any existing community for the route."
    DEFVAL      { "" }
    ::= { tRPAdminPSAccActionRepCommEntry 3 }

tRPAdminPSAccActionReplaceComm4  OBJECT-TYPE
    SYNTAX      TLCommunityName
    MAX-ACCESS  read-create
    STATUS      current
    DESCRIPTION
        "The value of tRPAdminPSAccActionReplaceComm4 specifies a community
         name to replace in any existing community for the route."
    DEFVAL      { "" }
    ::= { tRPAdminPSAccActionRepCommEntry 4 }

tRPAdminPSAccActionReplaceComm5  OBJECT-TYPE
    SYNTAX      TLCommunityName
    MAX-ACCESS  read-create
    STATUS      current
    DESCRIPTION
        "The value of tRPAdminPSAccActionReplaceComm5 specifies a community
         name to replace in any existing community for the route."
    DEFVAL      { "" }
    ::= { tRPAdminPSAccActionRepCommEntry 5 }

tRPAdminPSAccActionReplaceComm6  OBJECT-TYPE
    SYNTAX      TLCommunityName
    MAX-ACCESS  read-create
    STATUS      current
    DESCRIPTION
        "The value of tRPAdminPSAccActionReplaceComm6 specifies a community
         name to replace in any existing community for the route."
    DEFVAL      { "" }
    ::= { tRPAdminPSAccActionRepCommEntry 6 }

tRPAdminPSAccActionReplaceComm7  OBJECT-TYPE
    SYNTAX      TLCommunityName
    MAX-ACCESS  read-create
    STATUS      current
    DESCRIPTION
        "The value of tRPAdminPSAccActionReplaceComm7 specifies a community
         name to replace in any existing community for the route."
    DEFVAL      { "" }
    ::= { tRPAdminPSAccActionRepCommEntry 7 }

tRPAdminPSAccActionReplaceComm8  OBJECT-TYPE
    SYNTAX      TLCommunityName
    MAX-ACCESS  read-create
    STATUS      current
    DESCRIPTION
        "The value of tRPAdminPSAccActionReplaceComm8 specifies a community
         name to replace in any existing community for the route."
    DEFVAL      { "" }
    ::= { tRPAdminPSAccActionRepCommEntry 8 }

tRPAdminPSAccActionReplaceComm9  OBJECT-TYPE
    SYNTAX      TLCommunityName
    MAX-ACCESS  read-create
    STATUS      current
    DESCRIPTION
        "The value of tRPAdminPSAccActionReplaceComm9 specifies a community
         name to replace in any existing community for the route."
    DEFVAL      { "" }
    ::= { tRPAdminPSAccActionRepCommEntry 9 }

tRPAdminPSAccActionReplaceComm10 OBJECT-TYPE
    SYNTAX      TLCommunityName
    MAX-ACCESS  read-create
    STATUS      current
    DESCRIPTION
        "The value of tRPAdminPSAccActionReplaceComm10 specifies a community
         name to replace in any existing community for the route."
    DEFVAL      { "" }
    ::= { tRPAdminPSAccActionRepCommEntry 10 }

tRPAdminPSAccActionReplaceComm11 OBJECT-TYPE
    SYNTAX      TLCommunityName
    MAX-ACCESS  read-create
    STATUS      current
    DESCRIPTION
        "The value of tRPAdminPSAccActionReplaceComm11 specifies a community
         name to replace in any existing community for the route."
    DEFVAL      { "" }
    ::= { tRPAdminPSAccActionRepCommEntry 11 }

tRPAdminPSAccActionReplaceComm12 OBJECT-TYPE
    SYNTAX      TLCommunityName
    MAX-ACCESS  read-create
    STATUS      current
    DESCRIPTION
        "The value of tRPAdminPSAccActionReplaceComm12 specifies a community
         name to replace in any existing community for the route."
    DEFVAL      { "" }
    ::= { tRPAdminPSAccActionRepCommEntry 12 }

tRPAdminPSAccActionReplaceComm13 OBJECT-TYPE
    SYNTAX      TLCommunityName
    MAX-ACCESS  read-create
    STATUS      current
    DESCRIPTION
        "The value of tRPAdminPSAccActionReplaceComm13 specifies a community
         name to replace in any existing community for the route."
    DEFVAL      { "" }
    ::= { tRPAdminPSAccActionRepCommEntry 13 }

tRPAdminPSAccActionReplaceComm14 OBJECT-TYPE
    SYNTAX      TLCommunityName
    MAX-ACCESS  read-create
    STATUS      current
    DESCRIPTION
        "The value of tRPAdminPSAccActionReplaceComm14 specifies a community
         name to replace in any existing community for the route."
    DEFVAL      { "" }
    ::= { tRPAdminPSAccActionRepCommEntry 14 }

tRPAdminPSAccActionReplaceComm15 OBJECT-TYPE
    SYNTAX      TLCommunityName
    MAX-ACCESS  read-create
    STATUS      current
    DESCRIPTION
        "The value of tRPAdminPSAccActionReplaceComm15 specifies a community
         name to replace in any existing community for the route."
    DEFVAL      { "" }
    ::= { tRPAdminPSAccActionRepCommEntry 15 }

tRPAdminPSAccActionReplaceComm16 OBJECT-TYPE
    SYNTAX      TLCommunityName
    MAX-ACCESS  read-create
    STATUS      current
    DESCRIPTION
        "The value of tRPAdminPSAccActionReplaceComm16 specifies a community
         name to replace in any existing community for the route."
    DEFVAL      { "" }
    ::= { tRPAdminPSAccActionRepCommEntry 16 }

tRPAdminPSAccActionReplaceComm17 OBJECT-TYPE
    SYNTAX      TLCommunityName
    MAX-ACCESS  read-create
    STATUS      current
    DESCRIPTION
        "The value of tRPAdminPSAccActionReplaceComm17 specifies a community
         name to replace in any existing community for the route."
    DEFVAL      { "" }
    ::= { tRPAdminPSAccActionRepCommEntry 17 }

tRPAdminPSAccActionReplaceComm18 OBJECT-TYPE
    SYNTAX      TLCommunityName
    MAX-ACCESS  read-create
    STATUS      current
    DESCRIPTION
        "The value of tRPAdminPSAccActionReplaceComm18 specifies a community
         name to replace in any existing community for the route."
    DEFVAL      { "" }
    ::= { tRPAdminPSAccActionRepCommEntry 18 }

tRPAdminPSAccActionReplaceComm19 OBJECT-TYPE
    SYNTAX      TLCommunityName
    MAX-ACCESS  read-create
    STATUS      current
    DESCRIPTION
        "The value of tRPAdminPSAccActionReplaceComm19 specifies a community
         name to replace in any existing community for the route."
    DEFVAL      { "" }
    ::= { tRPAdminPSAccActionRepCommEntry 19 }

tRPAdminPSAccActionReplaceComm20 OBJECT-TYPE
    SYNTAX      TLCommunityName
    MAX-ACCESS  read-create
    STATUS      current
    DESCRIPTION
        "The value of tRPAdminPSAccActionReplaceComm20 specifies a community
         name to replace in any existing community for the route."
    DEFVAL      { "" }
    ::= { tRPAdminPSAccActionRepCommEntry 20 }

tRPAdminPSAccActionReplaceComm21 OBJECT-TYPE
    SYNTAX      TLCommunityName
    MAX-ACCESS  read-create
    STATUS      current
    DESCRIPTION
        "The value of tRPAdminPSAccActionReplaceComm21 specifies a community
         name to replace in any existing community for the route."
    DEFVAL      { "" }
    ::= { tRPAdminPSAccActionRepCommEntry 21 }

tRPAdminPSAccActionReplaceComm22 OBJECT-TYPE
    SYNTAX      TLCommunityName
    MAX-ACCESS  read-create
    STATUS      current
    DESCRIPTION
        "The value of tRPAdminPSAccActionReplaceComm22 specifies a community
         name to replace in any existing community for the route."
    DEFVAL      { "" }
    ::= { tRPAdminPSAccActionRepCommEntry 22 }

tRPAdminPSAccActionReplaceComm23 OBJECT-TYPE
    SYNTAX      TLCommunityName
    MAX-ACCESS  read-create
    STATUS      current
    DESCRIPTION
        "The value of tRPAdminPSAccActionReplaceComm23 specifies a community
         name to replace in any existing community for the route."
    DEFVAL      { "" }
    ::= { tRPAdminPSAccActionRepCommEntry 23 }

tRPAdminPSAccActionReplaceComm24 OBJECT-TYPE
    SYNTAX      TLCommunityName
    MAX-ACCESS  read-create
    STATUS      current
    DESCRIPTION
        "The value of tRPAdminPSAccActionReplaceComm24 specifies a community
         name to replace in any existing community for the route."
    DEFVAL      { "" }
    ::= { tRPAdminPSAccActionRepCommEntry 24 }

tRPAdminPSAccActionReplaceComm25 OBJECT-TYPE
    SYNTAX      TLCommunityName
    MAX-ACCESS  read-create
    STATUS      current
    DESCRIPTION
        "The value of tRPAdminPSAccActionReplaceComm25 specifies a community
         name to replace in any existing community for the route."
    DEFVAL      { "" }
    ::= { tRPAdminPSAccActionRepCommEntry 25 }

tRPAdminPSAccActionReplaceComm26 OBJECT-TYPE
    SYNTAX      TLCommunityName
    MAX-ACCESS  read-create
    STATUS      current
    DESCRIPTION
        "The value of tRPAdminPSAccActionReplaceComm26 specifies a community
         name to replace in any existing community for the route."
    DEFVAL      { "" }
    ::= { tRPAdminPSAccActionRepCommEntry 26 }

tRPAdminPSAccActionReplaceComm27 OBJECT-TYPE
    SYNTAX      TLCommunityName
    MAX-ACCESS  read-create
    STATUS      current
    DESCRIPTION
        "The value of tRPAdminPSAccActionReplaceComm27 specifies a community
         name to replace in any existing community for the route."
    DEFVAL      { "" }
    ::= { tRPAdminPSAccActionRepCommEntry 27 }

tRPAdminPSAccActionReplaceComm28 OBJECT-TYPE
    SYNTAX      TLCommunityName
    MAX-ACCESS  read-create
    STATUS      current
    DESCRIPTION
        "The value of tRPAdminPSAccActionReplaceComm28 specifies a community
         name to replace in any existing community for the route."
    DEFVAL      { "" }
    ::= { tRPAdminPSAccActionRepCommEntry 28 }

tRPAdminPSFromCriteriaExtTable   OBJECT-TYPE
    SYNTAX      SEQUENCE OF TRPAdminPSFromCriteriaExtEntry
    MAX-ACCESS  not-accessible
    STATUS      current
    DESCRIPTION
        "An extension table of tRPAdminPSFromCriteriaTable to configure extra
         from filter criteria for each policy statement entry."
    ::= { tRPAdminValueObjects 21 }

tRPAdminPSFromCriteriaExtEntry   OBJECT-TYPE
    SYNTAX      TRPAdminPSFromCriteriaExtEntry
    MAX-ACCESS  not-accessible
    STATUS      current
    DESCRIPTION
        "Information about policy statement entry from criteria."
    AUGMENTS    { tRPAdminPSFromCriteriaEntry }
    ::= { tRPAdminPSFromCriteriaExtTable 1 }

TRPAdminPSFromCriteriaExtEntry   ::= SEQUENCE
{
    tRPAdminPSFromCritExtMvpnType    TPolicyEntryCriteriaMvpnType,
    tRPAdminPSFromCritSrcAddrPfxList TLPrefixListName,
    tRPAdminPSFromCritOrigValidState INTEGER,
    tRPAdminPSFromCritFlowSrcPfxList TLPrefixListName,
    tRPAdminPSFromCritFlowDstPfxList TLPrefixListName,
    tRPAdminPSFromCritPathType       TPolicyCritPathType,
    tRPAdminPSFromCritASPathLength   TPolicyValueOrVarNameOrEmpty,
    tRPAdminPSFromCritASPathLenInd   TPolicyMatchIndicator,
    tRPAdminPSFromCritASPLenUnique   TruthValue,
    tRPAdminPSFromCritCommunityCount TPolicyValueOrVarNameOrEmpty,
    tRPAdminPSFromCritCommCountInd   TPolicyMatchIndicator,
    tRPAdminPSFromCritCommCountType  TPolicyCritCommunityType,
    tRPAdminPSFromCritMetric         TPolicyValueOrVarNameOrEmpty,
    tRPAdminPSFromCritMetricInd      TPolicyMatchIndicator,
    tRPAdminPSFromCritLocalPref      TPolicyValueOrVarNameOrEmpty,
    tRPAdminPSFromCritLocalPrefInd   TPolicyMatchIndicator,
    tRPAdminPSFromCritClusterAddrTp1 InetAddressType,
    tRPAdminPSFromCritClusterAddr1   InetAddress,
    tRPAdminPSFromCritClusterPfxLen1 InetAddressPrefixLength,
    tRPAdminPSFromCritClusterAddrTp2 InetAddressType,
    tRPAdminPSFromCritClusterAddr2   InetAddress,
    tRPAdminPSFromCritClusterPfxLen2 InetAddressPrefixLength,
    tRPAdminPSFromCritClusterAddrTp3 InetAddressType,
    tRPAdminPSFromCritClusterAddr3   InetAddress,
    tRPAdminPSFromCritClusterPfxLen3 InetAddressPrefixLength,
    tRPAdminPSFromCritClusterAddrTp4 InetAddressType,
    tRPAdminPSFromCritClusterAddr4   InetAddress,
    tRPAdminPSFromCritClusterPfxLen4 InetAddressPrefixLength,
    tRPAdminPSFromCritClusterAddrTp5 InetAddressType,
    tRPAdminPSFromCritClusterAddr5   InetAddress,
    tRPAdminPSFromCritClusterPfxLen5 InetAddressPrefixLength,
    tRPAdminPSFromCritClusterIdNone  TruthValue,
    tRPAdminPSFromCritNextHopAddrTyp InetAddressType,
    tRPAdminPSFromCritNextHopAddr    InetAddress,
    tRPAdminPSFromCritNextHopPfxList TLPrefixListName,
    tRPAdminPSFromCritExtEvpnType    TPolicyEntryCriteriaEvpnType,
    tRPAdminPSFromCrAggrContributor  TruthValue,
    tRPAdminPSFromCrEndpointAddrTyp  InetAddressType,
    tRPAdminPSFromCrEndpointAddr     InetAddress,
    tRPAdminPSFromCritColor          TNamedItemOrEmpty,
    tRPAdminPSFromCritDistinguisher  TNamedItemOrEmpty,
    tRPAdminPSFromCritRDList         TRouteDistinguisherListName,
    tRPAdminPSFromCritSrv6Tlv        INTEGER,
    tRPAdminPSFromCritSrv6SidPfxSrc  TPolicyActionSource,
    tRPAdminPSFromCritSrv6SidPfxType InetAddressType,
    tRPAdminPSFromCritSrv6SidPfxAddr InetAddress,
    tRPAdminPSFromCritSrv6SidPfxLen  InetAddressPrefixLength,
    tRPAdminPSFromCritSrv6SidPfxPar  TPolicyVariableNameOrEmpty
}

tRPAdminPSFromCritExtMvpnType    OBJECT-TYPE
    SYNTAX      TPolicyEntryCriteriaMvpnType
    MAX-ACCESS  read-create
    STATUS      current
    DESCRIPTION
        "The value of tRPAdminPSFromCritExtMvpnType specifies the BGP route
         MVPN type to match on. Set to none(0) to disable."
    DEFVAL      { none }
    ::= { tRPAdminPSFromCriteriaExtEntry 1 }

tRPAdminPSFromCritSrcAddrPfxList OBJECT-TYPE
    SYNTAX      TLPrefixListName
    MAX-ACCESS  read-create
    STATUS      current
    DESCRIPTION
        "The value of tRPAdminPSFromCritSrcAddrPfxList contains the name of the
         source address prefix list to match on.

         This object can only be set when tRPAdminPSFromCritSrcInetAddr is not
         configured."
    DEFVAL      { "" }
    ::= { tRPAdminPSFromCriteriaExtEntry 2 }

tRPAdminPSFromCritOrigValidState OBJECT-TYPE
    SYNTAX      INTEGER {
        notApplicable (0),
        valid         (1),
        notFound      (2),
        invalid       (3)
    }
    MAX-ACCESS  read-create
    STATUS      current
    DESCRIPTION
        "The value of tRPAdminPSFromCritOrigValidState specifies the origin
         validation state criteria for this policy statement."
    DEFVAL      { notApplicable }
    ::= { tRPAdminPSFromCriteriaExtEntry 3 }

tRPAdminPSFromCritFlowSrcPfxList OBJECT-TYPE
    SYNTAX      TLPrefixListName
    MAX-ACCESS  read-create
    STATUS      current
    DESCRIPTION
        "The value of tRPAdminPSFromCritFlowSrcPfxList contains the name of the
         flow-spec source prefix list to match on."
    DEFVAL      { "" }
    ::= { tRPAdminPSFromCriteriaExtEntry 4 }

tRPAdminPSFromCritFlowDstPfxList OBJECT-TYPE
    SYNTAX      TLPrefixListName
    MAX-ACCESS  read-create
    STATUS      current
    DESCRIPTION
        "The value of tRPAdminPSFromCritFlowDstPfxList contains the name of the
         flow-spec destination prefix list to match on."
    DEFVAL      { "" }
    ::= { tRPAdminPSFromCriteriaExtEntry 5 }

tRPAdminPSFromCritPathType       OBJECT-TYPE
    SYNTAX      TPolicyCritPathType
    MAX-ACCESS  read-create
    STATUS      current
    DESCRIPTION
        "The value of tRPAdminPSFromCritPathType specifies the path type to
         match the BGP route on."
    DEFVAL      { none }
    ::= { tRPAdminPSFromCriteriaExtEntry 6 }

tRPAdminPSFromCritASPathLength   OBJECT-TYPE
    SYNTAX      TPolicyValueOrVarNameOrEmpty
    MAX-ACCESS  read-create
    STATUS      current
    DESCRIPTION
        "The value of tRPAdminPSFromCritASPathLength specifies the number of AS
         numbers in the AS-Path to match the BGP route on.

         The tRPAdminPSFromCritASPathLength can be a string containing the
         AS-Path length in the range [0-255] or a variable name that needs to
         be resolved to get the AS-Path length."
    DEFVAL      { "" }
    ::= { tRPAdminPSFromCriteriaExtEntry 7 }

tRPAdminPSFromCritASPathLenInd   OBJECT-TYPE
    SYNTAX      TPolicyMatchIndicator
    MAX-ACCESS  read-create
    STATUS      current
    DESCRIPTION
        "The value of tRPAdminPSFromCritASPathLenInd specifies whether higher
         or lower AS-Path lengths are accepted for the
         tRPAdminPSFromCritASPathLength criteria to match on."
    DEFVAL      { equal }
    ::= { tRPAdminPSFromCriteriaExtEntry 8 }

tRPAdminPSFromCritASPLenUnique   OBJECT-TYPE
    SYNTAX      TruthValue
    MAX-ACCESS  read-create
    STATUS      current
    DESCRIPTION
        "The value of tRPAdminPSFromCritASPLenUnique specifies whether only
         unique AS numbers should be considered for the
         tRPAdminPSFromCritASPathLength criteria to match on.

         When the value is true, multiple occurrences of the same AS number in
         the AS-Path count as 1 for calculating the AS-Path length."
    DEFVAL      { false }
    ::= { tRPAdminPSFromCriteriaExtEntry 9 }

tRPAdminPSFromCritCommunityCount OBJECT-TYPE
    SYNTAX      TPolicyValueOrVarNameOrEmpty
    MAX-ACCESS  read-create
    STATUS      current
    DESCRIPTION
        "The value of tRPAdminPSFromCritCommunityCount specifies the number of
         BGP communities to match the BGP route on.

         The tRPAdminPSFromCritCommunityCount can be a string containing the
         number of communities in the range [0-1024] or a variable name that
         needs to be resolved to get the community count."
    DEFVAL      { "" }
    ::= { tRPAdminPSFromCriteriaExtEntry 10 }

tRPAdminPSFromCritCommCountInd   OBJECT-TYPE
    SYNTAX      TPolicyMatchIndicator
    MAX-ACCESS  read-create
    STATUS      current
    DESCRIPTION
        "The value of tRPAdminPSFromCritCommCountInd specifies whether higher
         or lower community counts are accepted for the
         tRPAdminPSFromCritCommunityCount criteria to match on."
    DEFVAL      { equal }
    ::= { tRPAdminPSFromCriteriaExtEntry 11 }

tRPAdminPSFromCritCommCountType  OBJECT-TYPE
    SYNTAX      TPolicyCritCommunityType
    MAX-ACCESS  read-create
    STATUS      current
    DESCRIPTION
        "The value of tRPAdminPSFromCritCommCountType specifies which
         communities should be counted for the tRPAdminPSFromCritCommunityCount
         criteria to match on."
    DEFVAL      { all }
    ::= { tRPAdminPSFromCriteriaExtEntry 12 }

tRPAdminPSFromCritMetric         OBJECT-TYPE
    SYNTAX      TPolicyValueOrVarNameOrEmpty
    MAX-ACCESS  read-create
    STATUS      current
    DESCRIPTION
        "The value of tRPAdminPSFromCritMetric specifies the metric to match
         the BGP route on.

         The tRPAdminPSFromCritMetric can be a string containing the metric
         value in the range [0..4294967295] or a variable name that needs to be
         resolved to get the metric value."
    DEFVAL      { "" }
    ::= { tRPAdminPSFromCriteriaExtEntry 13 }

tRPAdminPSFromCritMetricInd      OBJECT-TYPE
    SYNTAX      TPolicyMatchIndicator
    MAX-ACCESS  read-create
    STATUS      current
    DESCRIPTION
        "The value of tRPAdminPSFromCritMetricInd specifies whether higher or
         lower metric values are accepted for the tRPAdminPSFromCritMetric
         criteria to match on."
    DEFVAL      { equal }
    ::= { tRPAdminPSFromCriteriaExtEntry 14 }

tRPAdminPSFromCritLocalPref      OBJECT-TYPE
    SYNTAX      TPolicyValueOrVarNameOrEmpty
    MAX-ACCESS  read-create
    STATUS      current
    DESCRIPTION
        "The value of tRPAdminPSFromCritLocalPref specifies the local
         preference to match the BGP route on.

         The tRPAdminPSFromCritLocalPref can be a string containing the local
         preference value in the range [0..4294967295] or a variable name that
         needs to be resolved to get the local preference value."
    DEFVAL      { "" }
    ::= { tRPAdminPSFromCriteriaExtEntry 15 }

tRPAdminPSFromCritLocalPrefInd   OBJECT-TYPE
    SYNTAX      TPolicyMatchIndicator
    MAX-ACCESS  read-create
    STATUS      current
    DESCRIPTION
        "The value of tRPAdminPSFromCritLocalPrefInd specifies whether higher
         or lower local preference values are accepted for the
         tRPAdminPSFromCritLocalPref criteria to match on."
    DEFVAL      { equal }
    ::= { tRPAdminPSFromCriteriaExtEntry 16 }

tRPAdminPSFromCritClusterAddrTp1 OBJECT-TYPE
    SYNTAX      InetAddressType
    MAX-ACCESS  read-create
    STATUS      current
    DESCRIPTION
        "The value of tRPAdminPSFromCritClusterAddrTp1 specifies the address
         type of tRPAdminPSFromCritClusterAddr1."
    DEFVAL      { unknown }
    ::= { tRPAdminPSFromCriteriaExtEntry 17 }

tRPAdminPSFromCritClusterAddr1   OBJECT-TYPE
    SYNTAX      InetAddress (SIZE (0|4))
    MAX-ACCESS  read-create
    STATUS      current
    DESCRIPTION
        "The value of tRPAdminPSFromCritClusterAddr1 specifies the first IP
         address encoded within the cluster list attribute to match the BGP
         route on.

         The first IP address mask pair is matched against the most recently
         added cluster id."
    DEFVAL      { ''H }
    ::= { tRPAdminPSFromCriteriaExtEntry 18 }

tRPAdminPSFromCritClusterPfxLen1 OBJECT-TYPE
    SYNTAX      InetAddressPrefixLength (0..32)
    MAX-ACCESS  read-create
    STATUS      current
    DESCRIPTION
        "The value of tRPAdminPSFromCritClusterPfxLen1 specifies the length of
         the first IP address encoded within the cluster list attribute to
         match the BGP route on."
    DEFVAL      { 0 }
    ::= { tRPAdminPSFromCriteriaExtEntry 19 }

tRPAdminPSFromCritClusterAddrTp2 OBJECT-TYPE
    SYNTAX      InetAddressType
    MAX-ACCESS  read-create
    STATUS      current
    DESCRIPTION
        "The value of tRPAdminPSFromCritClusterAddrTp2 specifies the address
         type of tRPAdminPSFromCritClusterAddr2."
    DEFVAL      { unknown }
    ::= { tRPAdminPSFromCriteriaExtEntry 20 }

tRPAdminPSFromCritClusterAddr2   OBJECT-TYPE
    SYNTAX      InetAddress (SIZE (0|4))
    MAX-ACCESS  read-create
    STATUS      current
    DESCRIPTION
        "The value of tRPAdminPSFromCritClusterAddr2 specifies the second IP
         address encoded within the cluster list attribute to match the BGP
         route on.

         The second IP address mask pair is matched against the second most
         recent added cluster id."
    DEFVAL      { ''H }
    ::= { tRPAdminPSFromCriteriaExtEntry 21 }

tRPAdminPSFromCritClusterPfxLen2 OBJECT-TYPE
    SYNTAX      InetAddressPrefixLength (0..32)
    MAX-ACCESS  read-create
    STATUS      current
    DESCRIPTION
        "The value of tRPAdminPSFromCritClusterPfxLen2 specifies the length of
         the second IP address encoded within the cluster list attribute to
         match the BGP route on."
    DEFVAL      { 0 }
    ::= { tRPAdminPSFromCriteriaExtEntry 22 }

tRPAdminPSFromCritClusterAddrTp3 OBJECT-TYPE
    SYNTAX      InetAddressType
    MAX-ACCESS  read-create
    STATUS      current
    DESCRIPTION
        "The value of tRPAdminPSFromCritClusterAddrTp3 specifies the address
         type of tRPAdminPSFromCritClusterAddr3."
    DEFVAL      { unknown }
    ::= { tRPAdminPSFromCriteriaExtEntry 23 }

tRPAdminPSFromCritClusterAddr3   OBJECT-TYPE
    SYNTAX      InetAddress (SIZE (0|4))
    MAX-ACCESS  read-create
    STATUS      current
    DESCRIPTION
        "The value of tRPAdminPSFromCritClusterAddr3 specifies the third IP
         address encoded within the cluster list attribute to match the BGP
         route on.

         The third IP address mask pair is matched against the third most
         recent added cluster id."
    DEFVAL      { ''H }
    ::= { tRPAdminPSFromCriteriaExtEntry 24 }

tRPAdminPSFromCritClusterPfxLen3 OBJECT-TYPE
    SYNTAX      InetAddressPrefixLength (0..32)
    MAX-ACCESS  read-create
    STATUS      current
    DESCRIPTION
        "The value of tRPAdminPSFromCritClusterPfxLen3 specifies the length of
         the third IP address encoded within the cluster list attribute to
         match the BGP route on."
    DEFVAL      { 0 }
    ::= { tRPAdminPSFromCriteriaExtEntry 25 }

tRPAdminPSFromCritClusterAddrTp4 OBJECT-TYPE
    SYNTAX      InetAddressType
    MAX-ACCESS  read-create
    STATUS      current
    DESCRIPTION
        "The value of tRPAdminPSFromCritClusterAddrTp4 specifies the address
         type of tRPAdminPSFromCritClusterAddr4."
    DEFVAL      { unknown }
    ::= { tRPAdminPSFromCriteriaExtEntry 26 }

tRPAdminPSFromCritClusterAddr4   OBJECT-TYPE
    SYNTAX      InetAddress (SIZE (0|4))
    MAX-ACCESS  read-create
    STATUS      current
    DESCRIPTION
        "The value of tRPAdminPSFromCritClusterAddr4 specifies the fourth IP
         address encoded within the cluster list attribute to match the BGP
         route on.

         The fourth IP address mask pair is matched against the fourth most
         recent added cluster id."
    DEFVAL      { ''H }
    ::= { tRPAdminPSFromCriteriaExtEntry 27 }

tRPAdminPSFromCritClusterPfxLen4 OBJECT-TYPE
    SYNTAX      InetAddressPrefixLength (0..32)
    MAX-ACCESS  read-create
    STATUS      current
    DESCRIPTION
        "The value of tRPAdminPSFromCritClusterPfxLen4 specifies the length of
         the fourth IP address encoded within the cluster list attribute to
         match the BGP route on."
    DEFVAL      { 0 }
    ::= { tRPAdminPSFromCriteriaExtEntry 28 }

tRPAdminPSFromCritClusterAddrTp5 OBJECT-TYPE
    SYNTAX      InetAddressType
    MAX-ACCESS  read-create
    STATUS      current
    DESCRIPTION
        "The value of tRPAdminPSFromCritClusterAddrTp5 specifies the address
         type of tRPAdminPSFromCritClusterAddr5."
    DEFVAL      { unknown }
    ::= { tRPAdminPSFromCriteriaExtEntry 29 }

tRPAdminPSFromCritClusterAddr5   OBJECT-TYPE
    SYNTAX      InetAddress (SIZE (0|4))
    MAX-ACCESS  read-create
    STATUS      current
    DESCRIPTION
        "The value of tRPAdminPSFromCritClusterAddr5 specifies the fifth IP
         address encoded within the cluster list attribute to match the BGP
         route on.

         The fifth IP address mask pair is matched against the fifth most
         recent added cluster id."
    DEFVAL      { ''H }
    ::= { tRPAdminPSFromCriteriaExtEntry 30 }

tRPAdminPSFromCritClusterPfxLen5 OBJECT-TYPE
    SYNTAX      InetAddressPrefixLength (0..32)
    MAX-ACCESS  read-create
    STATUS      current
    DESCRIPTION
        "The value of tRPAdminPSFromCritClusterPfxLen5 specifies the length of
         the fifth IP address encoded within the cluster list attribute to
         match the BGP route on."
    DEFVAL      { 0 }
    ::= { tRPAdminPSFromCriteriaExtEntry 31 }

tRPAdminPSFromCritClusterIdNone  OBJECT-TYPE
    SYNTAX      TruthValue
    MAX-ACCESS  read-create
    STATUS      current
    DESCRIPTION
        "The value of tRPAdminPSFromCritClusterIdNone specifies whether only
         routes without any cluster list attribute should be matched on.

         When tRPAdminPSFromCritClusterIdNone is set to true, only routes
         without any cluster list attribute are matched.

         The cluster id none criteria is ignored when a cluster id IP address
         criteria is configured."
    DEFVAL      { false }
    ::= { tRPAdminPSFromCriteriaExtEntry 32 }

tRPAdminPSFromCritNextHopAddrTyp OBJECT-TYPE
    SYNTAX      InetAddressType
    MAX-ACCESS  read-create
    STATUS      current
    DESCRIPTION
        "The value of tRPAdminPSFromCritNextHopAddrTyp specifies the address
         type of tRPAdminPSFromCritNextHopAddr."
    DEFVAL      { unknown }
    ::= { tRPAdminPSFromCriteriaExtEntry 33 }

tRPAdminPSFromCritNextHopAddr    OBJECT-TYPE
    SYNTAX      InetAddress (SIZE (0|4|16))
    MAX-ACCESS  read-create
    STATUS      current
    DESCRIPTION
        "The value of tRPAdminPSFromCritNextHopAddr specifies the next-hop IP
         address to match the BGP route on."
    DEFVAL      { ''H }
    ::= { tRPAdminPSFromCriteriaExtEntry 34 }

tRPAdminPSFromCritNextHopPfxList OBJECT-TYPE
    SYNTAX      TLPrefixListName
    MAX-ACCESS  read-create
    STATUS      current
    DESCRIPTION
        "The value of tRPAdminPSFromCritNextHopPfxList specifies the next-hop
         prefix list to match the BGP route on.

         The next-hop prefix list criteria is ignored when a next-hop IP
         address criteria is configured in object
         tRPAdminPSFromCritNextHopAddr."
    DEFVAL      { "" }
    ::= { tRPAdminPSFromCriteriaExtEntry 35 }

tRPAdminPSFromCritExtEvpnType    OBJECT-TYPE
    SYNTAX      TPolicyEntryCriteriaEvpnType
    MAX-ACCESS  read-create
    STATUS      current
    DESCRIPTION
        "The value of tRPAdminPSFromCritExtEvpnType specifies the BGP route
         EVPN type to match on. Set to none(0) to disable."
    DEFVAL      { none }
    ::= { tRPAdminPSFromCriteriaExtEntry 37 }

tRPAdminPSFromCrAggrContributor  OBJECT-TYPE
    SYNTAX      TruthValue
    MAX-ACCESS  read-create
    STATUS      current
    DESCRIPTION
        "The value of tRPAdminPSFromCrAggrContributor specifies whether
         aggregate contributor routes should be matched on.

         When the value is 'true', only the more-specific prefixes that are
         actually contributors are matched."
    DEFVAL      { false }
    ::= { tRPAdminPSFromCriteriaExtEntry 38 }

tRPAdminPSFromCrEndpointAddrTyp  OBJECT-TYPE
    SYNTAX      InetAddressType
    MAX-ACCESS  read-create
    STATUS      current
    DESCRIPTION
        "The value of tRPAdminPSFromCrEndpointAddrTyp specifies the address
         type of tRPAdminPSFromCrEndpointAddr."
    DEFVAL      { unknown }
    ::= { tRPAdminPSFromCriteriaExtEntry 39 }

tRPAdminPSFromCrEndpointAddr     OBJECT-TYPE
    SYNTAX      InetAddress (SIZE (0|4|16))
    MAX-ACCESS  read-create
    STATUS      current
    DESCRIPTION
        "The value of tRPAdminPSFromCrEndpointAddr specifies the SR policy
         endpoint IP address to match the route on.

         This match criterion is only used in import policies."
    DEFVAL      { ''H }
    ::= { tRPAdminPSFromCriteriaExtEntry 40 }

tRPAdminPSFromCritColor          OBJECT-TYPE
    SYNTAX      TNamedItemOrEmpty
    MAX-ACCESS  read-create
    STATUS      current
    DESCRIPTION
        "The value of tRPAdminPSFromCritColor specifies the SR policy color ID
         to match the route on.

         The value of this object can be a string containing the SR policy
         color ID value in the range [0..4294967295]. An empty string means
         that it is disabled.

         This match criterion is only used in import policies."
    DEFVAL      { "" }
    ::= { tRPAdminPSFromCriteriaExtEntry 41 }

tRPAdminPSFromCritDistinguisher  OBJECT-TYPE
    SYNTAX      TNamedItemOrEmpty
    MAX-ACCESS  read-create
    STATUS      current
    DESCRIPTION
        "The value of tRPAdminPSFromCritDistinguisher specifies the SR policy
         distinguisher to match the route on.

         The value of this object can be a string containing the SR policy
         distinguisher value in the range [0..4294967295]. An empty string
         means that it is disabled.

         This match criterion is only used in import policies."
    DEFVAL      { "" }
    ::= { tRPAdminPSFromCriteriaExtEntry 42 }

tRPAdminPSFromCritRDList         OBJECT-TYPE
    SYNTAX      TRouteDistinguisherListName
    MAX-ACCESS  read-create
    STATUS      current
    DESCRIPTION
        "The value of tRPAdminPSFromCritRDList specifies the route
         distinguisher (RD) list to match the route on.

         The value of this object can be a string containing the name of the RD
         list or a variable name that needs to be resolved to get the name of
         the RD list. The RD list name must exist in tRPAdminRDListTable.

         An empty string means that it is disabled."
    DEFVAL      { ''H }
    ::= { tRPAdminPSFromCriteriaExtEntry 43 }

tRPAdminPSFromCritSrv6Tlv        OBJECT-TYPE
    SYNTAX      INTEGER {
        none       (0),
        present    (1),
        notPresent (2)
    }
    MAX-ACCESS  read-create
    STATUS      current
    DESCRIPTION
        "The value of tRPAdminPSFromCritSrv6Tlv specifies whether BGP routes
         should be matched with or without any SRv6 TLV present in the prefix
         SID attribute.

         none (0)       - match condition is disabled
         present (1)    - match only the BGP routes with a SRv6 TLV present
         notPresent (2) - match only the BGP routes without any SRv6 TLV"
    DEFVAL      { none }
    ::= { tRPAdminPSFromCriteriaExtEntry 44 }

tRPAdminPSFromCritSrv6SidPfxSrc  OBJECT-TYPE
    SYNTAX      TPolicyActionSource
    MAX-ACCESS  read-create
    STATUS      current
    DESCRIPTION
        "The value of tRPAdminPSFromCritSrv6SidPfxSrc specifies the source of
         the SRv6 SID prefix to match the BGP route on.

         The value 'actionValue(1)' means the SID prefix is the value of
         tRPAdminPSFromCritSrv6SidPfxAddr with address type defined by
         tRPAdminPSFromCritSrv6SidPfxType and prefix length defined by
         tRPAdminPSFromCritSrv6SidPfxLen; the value of the object
         tRPAdminPSFromCritSrv6SidPfxPar is ignored.

         The value 'actionParam(2) means the SID prefix is derived from the
         object tRPAdminPSFromCritSrv6SidPfxPar; the value of the object
         tRPAdminPSFromCritSrv6SidPfxType, tRPAdminPSFromCritSrv6SidPfxAddr and
         tRPAdminPSFromCritSrv6SidPfxLen are ignored."
    DEFVAL      { actionValue }
    ::= { tRPAdminPSFromCriteriaExtEntry 45 }

tRPAdminPSFromCritSrv6SidPfxType OBJECT-TYPE
    SYNTAX      InetAddressType
    MAX-ACCESS  read-create
    STATUS      current
    DESCRIPTION
        "The value of tRPAdminPSFromCritSrv6SidPfxType specifies the type of
         tRPAdminPSFromCritSrv6SidPfxAddr.

         The value of this object is ignored when the object
         tRPAdminPSFromCritSrv6SidPfxSrc has a value different from
         actionValue(1)."
    DEFVAL      { unknown }
    ::= { tRPAdminPSFromCriteriaExtEntry 46 }

tRPAdminPSFromCritSrv6SidPfxAddr OBJECT-TYPE
    SYNTAX      InetAddress (SIZE (0|16))
    MAX-ACCESS  read-create
    STATUS      current
    DESCRIPTION
        "The value of tRPAdminPSFromCritSrv6SidPfxAddr specifies the SRv6 SID
         prefix to match the BGP route on.

         The value of this object is ignored when the object
         tRPAdminPSFromCritSrv6SidPfxSrc has a value different from
         actionValue(1)."
    DEFVAL      { ''H }
    ::= { tRPAdminPSFromCriteriaExtEntry 47 }

tRPAdminPSFromCritSrv6SidPfxLen  OBJECT-TYPE
    SYNTAX      InetAddressPrefixLength (0..128)
    MAX-ACCESS  read-create
    STATUS      current
    DESCRIPTION
        "The value of tRPAdminPSFromCritSrv6SidPfxLen specifies the the prefix
         length of the SRv6 SID prefix.

         The value of this object is ignored when the object
         tRPAdminPSFromCritSrv6SidPfxSrc has a value different from
         actionValue(1)."
    DEFVAL      { 0 }
    ::= { tRPAdminPSFromCriteriaExtEntry 48 }

tRPAdminPSFromCritSrv6SidPfxPar  OBJECT-TYPE
    SYNTAX      TPolicyVariableNameOrEmpty
    MAX-ACCESS  read-create
    STATUS      current
    DESCRIPTION
        "The value of tRPAdminPSFromCritSrv6SidPfxPar specifies the variable
         name that must be resolved to get the SRv6 SID prefix to match on.

         The value of this object is ignored when the object
         tRPAdminPSFromCritSrv6SidPfxSrc has a value different from
         actionParam(2)."
    DEFVAL      { ''H }
    ::= { tRPAdminPSFromCriteriaExtEntry 49 }

tRPAdminPSPolicyVariableTable    OBJECT-TYPE
    SYNTAX      SEQUENCE OF TRPAdminPSPolicyVariableEntry
    MAX-ACCESS  not-accessible
    STATUS      current
    DESCRIPTION
        "Information to resolve variables used in tRPAdminPSFromCriteriaTable."
    ::= { tRPAdminValueObjects 22 }

tRPAdminPSPolicyVariableEntry    OBJECT-TYPE
    SYNTAX      TRPAdminPSPolicyVariableEntry
    MAX-ACCESS  not-accessible
    STATUS      current
    DESCRIPTION
        "This entry maps a variable to a name for the corresponding entry in
         tRPAdminPSFromCriteriaEntry if tRPAdminPSFromCriteriaPolicy refers to
         a policy statement that uses variables in its
         tRPAdminPSFromCriteriaTable, tRPAdminPSAcceptActionParamsTable,
         tRPAdminPSDefaultActionParamsTable, tRPAdminPSAcptActParamsExtTable or
         tRPAdminPSDefActParamsExtTable entries."
    INDEX       {
        tRPAdminPolicyStatementName,
        tRPAdminPSFromCriteriaIndex,
        tRPAdminPSPolicyVarName
    }
    ::= { tRPAdminPSPolicyVariableTable 1 }

TRPAdminPSPolicyVariableEntry    ::= SEQUENCE
{
    tRPAdminPSPolicyVarName          TPolicyVariableName,
    tRPAdminPSPolicyVarRowStatus     RowStatus,
    tRPAdminPSPolicyVarValue         TNamedItemOrEmpty,
    tRPAdminPSPolicyVarNumber        Integer32,
    tRPAdminPSPolicyVarType          TPolicyVariableType,
    tRPAdminPSPolicyVarAddressType   InetAddressType,
    tRPAdminPSPolicyVarAddress       InetAddress,
    tRPAdminPSPolicyVarDecimal       TPolicyDecimal,
    tRPAdminPSPolicyVarPrefixLength  InetAddressPrefixLength
}

tRPAdminPSPolicyVarName          OBJECT-TYPE
    SYNTAX      TPolicyVariableName
    MAX-ACCESS  not-accessible
    STATUS      current
    DESCRIPTION
        "The value of tRPAdminPSPolicyVarName specifies a variable name used in
         the tRPAdminPSFromCriteriaTable, tRPAdminPSAcceptActionParamsTable,
         tRPAdminPSDefaultActionParamsTable, tRPAdminPSAcptActParamsExtTable or
         tRPAdminPSDefActParamsExtTable entry defined by
         tRPAdminPSFromCriteriaPolicy.

         That entry uses this string as value for tAS-path, AS-path-group,
         prefix list, community or damping objects."
    ::= { tRPAdminPSPolicyVariableEntry 1 }

tRPAdminPSPolicyVarRowStatus     OBJECT-TYPE
    SYNTAX      RowStatus
    MAX-ACCESS  read-create
    STATUS      current
    DESCRIPTION
        "The value of tRPAdminPSPolicyVarRowStatus specifies the RowStatus for
         this row."
    ::= { tRPAdminPSPolicyVariableEntry 2 }

tRPAdminPSPolicyVarValue         OBJECT-TYPE
    SYNTAX      TNamedItemOrEmpty
    MAX-ACCESS  read-create
    STATUS      current
    DESCRIPTION
        "The value of tRPAdminPSPolicyVarValue specifies the actual as-path
         name, as-path group name, prefix list name or community name to which
         tRPAdminPSPolicyVarName is resolved.

         This object tRPAdminPSPolicyVarValue is ignored when the object
         tRPAdminPSPolicyVarType has a value different then string(1)."
    DEFVAL      { ''H }
    ::= { tRPAdminPSPolicyVariableEntry 3 }

tRPAdminPSPolicyVarNumber        OBJECT-TYPE
    SYNTAX      Integer32
    MAX-ACCESS  read-create
    STATUS      current
    DESCRIPTION
        "The value of tRPAdminPSPolicyVarNumber specifies the actual aigp
         metric value, as-path prepend value, local preference value, metric
         value or next-hop value to which tRPAdminPSPolicyVarName is resolved.

         This object tRPAdminPSPolicyVarNumber is ignored when the object
         tRPAdminPSPolicyVarType has a value different then integer(2)."
    DEFVAL      { 0 }
    ::= { tRPAdminPSPolicyVariableEntry 4 }

tRPAdminPSPolicyVarType          OBJECT-TYPE
    SYNTAX      TPolicyVariableType
    MAX-ACCESS  read-create
    STATUS      current
    DESCRIPTION
        "The value of tRPAdminPSPolicyVarType specifies how to resolve the
         tRPAdminPSPolicyVarName.

         string(1)  - indicates that tRPAdminPSPolicyVarValue is to be used
         integer(2) - indicates that tRPAdminPSPolicyVarNumber is to be used
         address(3) - indicates that tRPAdminPSPolicyVarAddressType and
                      tRPAdminPSPolicyVarAddress are to be used
         decimal(4) - indicates that tRPAdminPSPolicyVarDecimal is to be used
         prefix (5) - indicates that tRPAdminPSPolicyVarAddressType,
                      tRPAdminPSPolicyVarAddress and tRPAdminPSPolicyVarPrefixLength
                      are to be used"
    DEFVAL      { string }
    ::= { tRPAdminPSPolicyVariableEntry 5 }

tRPAdminPSPolicyVarAddressType   OBJECT-TYPE
    SYNTAX      InetAddressType
    MAX-ACCESS  read-create
    STATUS      current
    DESCRIPTION
        "The value of tRPAdminPSPolicyVarAddressType specifies the actual IP
         address type of the tRPAdminPSPolicyVarAddress to which
         tRPAdminPSPolicyVarName is resolved.

         This object tRPAdminPSPolicyVarAddressType is ignored when the object
         tRPAdminPSPolicyVarType has a value different from address(3) or
         prefix (5)."
    DEFVAL      { unknown }
    ::= { tRPAdminPSPolicyVariableEntry 6 }

tRPAdminPSPolicyVarAddress       OBJECT-TYPE
    SYNTAX      InetAddress (SIZE (0|4|16|20))
    MAX-ACCESS  read-create
    STATUS      current
    DESCRIPTION
        "The value of tRPAdminPSPolicyVarAddress specifies the actual next-hop
         address to which tRPAdminPSPolicyVarName is resolved.

         This object tRPAdminPSPolicyVarAddress is ignored when the object
         tRPAdminPSPolicyVarType has a value different from address(3) or
         prefix (5)."
    DEFVAL      { ''H }
    ::= { tRPAdminPSPolicyVariableEntry 7 }

tRPAdminPSPolicyVarDecimal       OBJECT-TYPE
    SYNTAX      TPolicyDecimal
    MAX-ACCESS  read-create
    STATUS      current
    DESCRIPTION
        "The value of tRPAdminPSPolicyVarDecimal specifies the actual decimal
         value to which tRPAdminPSPolicyVarName is resolved.

         This object tRPAdminPSPolicyVarDecimal is ignored when the object
         tRPAdminPSPolicyVarType has a value different then decimal(4)."
    DEFVAL      { "0" }
    ::= { tRPAdminPSPolicyVariableEntry 8 }

tRPAdminPSPolicyVarPrefixLength  OBJECT-TYPE
    SYNTAX      InetAddressPrefixLength (0..128)
    MAX-ACCESS  read-create
    STATUS      current
    DESCRIPTION
        "The value of tRPAdminPSPolicyVarPrefixLength specifies the prefix
         length of the prefix to which tRPAdminPSPolicyVarName is resolved.

         This object tRPAdminPSPolicyVarPrefixLength is ignored when the object
         tRPAdminPSPolicyVarType has a value different from prefix (5)."
    DEFVAL      { 0 }
    ::= { tRPAdminPSPolicyVariableEntry 9 }

tRPAdminPSAcptActParamsExtTable  OBJECT-TYPE
    SYNTAX      SEQUENCE OF TRPAdminPSAcptActParamsExtEntry
    MAX-ACCESS  not-accessible
    STATUS      current
    DESCRIPTION
        "An extension table of tRPAdminPSAcceptActionParamsTable containing
         extra accept-action parameters for each policy statement entry."
    ::= { tRPAdminValueObjects 23 }

tRPAdminPSAcptActParamsExtEntry  OBJECT-TYPE
    SYNTAX      TRPAdminPSAcptActParamsExtEntry
    MAX-ACCESS  not-accessible
    STATUS      current
    DESCRIPTION
        "Accept-action information for a policy statement entry."
    AUGMENTS    { tRPAdminPSAcceptActionParamsEntry }
    ::= { tRPAdminPSAcptActParamsExtTable 1 }

TRPAdminPSAcptActParamsExtEntry  ::= SEQUENCE
{
    tRPAdminPSAcptActStickyEcmp      TruthValue,
    tRPAdminPSAcptActAddPathSndLimit TPolicyAddPathSendLimit,
    tRPAdminPSAcptActInstBackupPath  TruthValue,
    tRPAdminPSAcptActAdvertiseLabel  TPolicyAdvertiseLabelMode,
    tRPAdminPSAcptActBgpLeaking      TruthValue,
    tRPAdminPSAcptActAigpMetricSrc   TPolicyActionSource,
    tRPAdminPSAcptActAigpMetricParam TPolicyVariableNameOrEmpty,
    tRPAdminPSAcptActASPathPendSrc   TPolicyActionSource,
    tRPAdminPSAcptActASPathPendParam TPolicyVariableNameOrEmpty,
    tRPAdminPSAcptActLocalPrefSource TPolicyActionSource,
    tRPAdminPSAcptActLocalPrefParam  TPolicyVariableNameOrEmpty,
    tRPAdminPSAcptActMetricParam     TPolicyVariableNameOrEmpty,
    tRPAdminPSAcptActNextHopSource   TPolicyActionSource,
    tRPAdminPSAcptActNextHopParam    TPolicyVariableNameOrEmpty,
    tRPAdminPSAcptActOriginSource    TPolicyActionSource,
    tRPAdminPSAcptActOriginParam     TPolicyVariableNameOrEmpty,
    tRPAdminPSAcptActOrigValStateSrc TPolicyActionSource,
    tRPAdminPSAcptActOrigValStatePar TPolicyVariableNameOrEmpty,
    tRPAdminPSAcptActPreferenceSrc   TPolicyActionSource,
    tRPAdminPSAcptActPreferenceParam TPolicyVariableNameOrEmpty,
    tRPAdminPSAcptActTagSource       TPolicyActionSource,
    tRPAdminPSAcptActTagParam        TPolicyVariableNameOrEmpty,
    tRPAdminPSAcptActOspfTypeSource  TPolicyActionSource,
    tRPAdminPSAcptActOspfTypeParam   TPolicyVariableNameOrEmpty,
    tRPAdminPSAcptActASPPendCountSrc TPolicyActionSource,
    tRPAdminPSAcptActASPPendCountPar TPolicyVariableNameOrEmpty,
    tRPAdminPSAcptActASPPndMstRecent TruthValue,
    tRPAdminPSAcptActCreateUdpTunnel TruthValue,
    tRPAdminPSAcptActResolveStatic   TruthValue,
    tRPAdminPSAcptActAdminTagPolicy  TPolicyAdminTagPolicyOrVarName,
    tRPAdminPSAcptActBgpMedSource    TPolicyBgpMedSource,
    tRPAdminPSAcptActBgpMedValue     TPolicyValueOrVarNameOrEmpty,
    tRPAdminPSAcptActBgpMedExpr      TPolicyBgpMedExpression,
    tRPAdminPSAcptActDisableRtInst   TruthValue,
    tRPAdminPSAcptActSrLabelIndex    TPolicyValueOrVarNameOrEmpty,
    tRPAdminPSAcptActSrLblIndPrefIgp TruthValue,
    tRPAdminPSAcptActNextHopPeerAddr TruthValue,
    tRPAdminPSAcptActBgpHighPriority TruthValue,
    tRPAdminPSAcptActFlexAlgo        TPolicyValueOrVarNameOrEmpty,
    tRPAdminPSAcptActBgpTunnelMetric TPolicyValueOrVarNameOrEmpty,
    tRPAdminPSAcptActBgpTMetPrefAigp TruthValue,
    tRPAdminPSAcptActEgressStats     TruthValue,
    tRPAdminPSAcptActIngressStats    TruthValue,
    tRPAdminPSAcptActSrMaintPolicy   TNamedItemOrEmpty,
    tRPAdminPSAcptActNatPolicy       TNamedItemOrEmpty,
    tRPAdminPSAcptActCreateMplsTunl  TruthValue,
    tRPAdminPSAcptActBgpTMetPrefMed  TruthValue,
    tRPAdminPSAcptActPrefTransFrr    TruthValue,
    tRPAdminPSAcptActSrv6Locator     TLNamedItemOrEmpty,
    tRPAdminPSAActSrv6RPathBfdSidSrc TPolicyActionSource,
    tRPAdminPSAActSrv6RPathBfdSidTyp InetAddressType,
    tRPAdminPSAActSrv6RPathBfdSid    InetAddress,
    tRPAdminPSAActSrv6RPathBfdSidPar TPolicyVariableNameOrEmpty,
    tRPAdminPSAActSrReturnPathBfdLbl TPolicyValueOrVarNameOrEmpty,
    tRPAdminPSAcptActSrv6MSLocator   TLNamedItemOrEmpty
}

tRPAdminPSAcptActStickyEcmp      OBJECT-TYPE
    SYNTAX      TruthValue
    MAX-ACCESS  read-create
    STATUS      current
    DESCRIPTION
        "The value of tRPAdminPSAcptActStickyEcmp specifies whether to apply
         sticky ECMP hash to the route or not.

         When the value of tRPAdminPSAcptActStickyEcmp is true and one or more
         of the multiple ECMP next-hops go down, then the unaffected traffic
         flows continues to be hashed to the same next-hops as prior to the
         failures; the affected traffic flows are redistributed as evenly as
         possible to the remaining next-hops."
    DEFVAL      { false }
    ::= { tRPAdminPSAcptActParamsExtEntry 1 }

tRPAdminPSAcptActAddPathSndLimit OBJECT-TYPE
    SYNTAX      TPolicyAddPathSendLimit
    MAX-ACCESS  read-create
    STATUS      current
    DESCRIPTION
        "The value of tRPAdminPSAcptActAddPathSndLimit specifies the admin
         ADD-PATH send limit for this policy statement."
    DEFVAL      { 0 }
    ::= { tRPAdminPSAcptActParamsExtEntry 2 }

tRPAdminPSAcptActInstBackupPath  OBJECT-TYPE
    SYNTAX      TruthValue
    MAX-ACCESS  read-create
    STATUS      current
    DESCRIPTION
        "The value of tRPAdminPSAcptActInstBackupPath specifies whether the
         installation of a backup path is desired for the route matching this
         entry."
    DEFVAL      { false }
    ::= { tRPAdminPSAcptActParamsExtEntry 3 }

tRPAdminPSAcptActAdvertiseLabel  OBJECT-TYPE
    SYNTAX      TPolicyAdvertiseLabelMode
    MAX-ACCESS  read-create
    STATUS      current
    DESCRIPTION
        "The value of tRPAdminPSAcptActAdvertiseLabel specifies the
         advertisement label mode for the route matching this entry."
    DEFVAL      { none }
    ::= { tRPAdminPSAcptActParamsExtEntry 4 }

tRPAdminPSAcptActBgpLeaking      OBJECT-TYPE
    SYNTAX      TruthValue
    MAX-ACCESS  read-create
    STATUS      current
    DESCRIPTION
        "The value of tRPAdminPSAcptActBgpLeaking specifies whether to apply
         BGP leaking to the route or not.

         When the value of tRPAdminPSAcptActBgpLeaking is true, the BGP route
         is leaked into a VPRN according to the user configured policies."
    DEFVAL      { false }
    ::= { tRPAdminPSAcptActParamsExtEntry 5 }

tRPAdminPSAcptActAigpMetricSrc   OBJECT-TYPE
    SYNTAX      TPolicyActionSource
    MAX-ACCESS  read-create
    STATUS      current
    DESCRIPTION
        "The value of tRPAdminPSAcptActAigpMetricSrc specifies the source of
         the accept action AIGP (Accumulated IGP) metric.

         The value 'actionValue(1)' means the AIGP metric value is the value of
         tRPAdminPSAcptActnAigpMetricVal; the value of the object
         tRPAdminPSAcptActAigpMetricParam is ignored.

         The value 'actionParam(2) means the AIGP metric value is derived from
         the object tRPAdminPSAcptActAigpMetricParam; the value of the object
         tRPAdminPSAcptActnAigpMetricVal is ignored.

         When the value of tRPAdminPSAcptActionAigpMetric is set to 'none(1)'
         or 'useIgp(4)', the value of tRPAdminPSAcptActAigpMetricSrc is
         ignored."
    DEFVAL      { actionValue }
    ::= { tRPAdminPSAcptActParamsExtEntry 6 }

tRPAdminPSAcptActAigpMetricParam OBJECT-TYPE
    SYNTAX      TPolicyVariableNameOrEmpty
    MAX-ACCESS  read-create
    STATUS      current
    DESCRIPTION
        "The value of tRPAdminPSAcptActAigpMetricParam specifies the variable
         name that must be resolved to get the value to be added or set for the
         route AIGP(Accumulated IGP) metric.

         The value of this object tRPAdminPSAcptActAigpMetricParam is ignored
         when the object tRPAdminPSAcptActAigpMetricSrc has a value different
         from actionParam(2).

         When the value of tRPAdminPSAcptActionAigpMetric is set to 'none(1)'
         or 'useIgp(4)', the value of tRPAdminPSAcptActAigpMetricParam is
         ignored."
    DEFVAL      { ''H }
    ::= { tRPAdminPSAcptActParamsExtEntry 7 }

tRPAdminPSAcptActASPathPendSrc   OBJECT-TYPE
    SYNTAX      TPolicyActionSource
    MAX-ACCESS  read-create
    STATUS      current
    DESCRIPTION
        "The value of tRPAdminPSAcptActASPathPendSrc specifies the source of
         the accept action AS Path prepend.

         The value 'actionValue(1)' means the AS Path prepend value is the
         value of tRPAdminPSAcceptActionASPathPend; the value of the object
         tRPAdminPSAcptActASPathPendParam is ignored.

         The value 'actionParam(2) means the AS Path prepend value is derived
         from the object tRPAdminPSAcptActASPathPendParam; the value of the
         object tRPAdminPSAcceptActionASPathPend is ignored."
    DEFVAL      { actionValue }
    ::= { tRPAdminPSAcptActParamsExtEntry 8 }

tRPAdminPSAcptActASPathPendParam OBJECT-TYPE
    SYNTAX      TPolicyVariableNameOrEmpty
    MAX-ACCESS  read-create
    STATUS      current
    DESCRIPTION
        "The value of tRPAdminPSAcptActASPathPendParam specifies the variable
         name that must be resolved to get the AS Number to prepend to the
         AS-Path attribute of the route.

         The value of this object tRPAdminPSAcptActASPathPendParam is ignored
         when the object tRPAdminPSAcptActASPathPendSrc has a value different
         from actionParam(2).

         The AS-Path prepending is disabled when the repeat count is set to
         zero; i.e. when tRPAdminPSAcceptActionASPathPrependCount is zero and
         tRPAdminPSAcptActASPPendCountSrc is set to actionValue(1)."
    DEFVAL      { ''H }
    ::= { tRPAdminPSAcptActParamsExtEntry 9 }

tRPAdminPSAcptActLocalPrefSource OBJECT-TYPE
    SYNTAX      TPolicyActionSource
    MAX-ACCESS  read-create
    STATUS      current
    DESCRIPTION
        "The value of tRPAdminPSAcptActLocalPrefSource specifies  the
         source of the accept action local preference.

         The value 'actionValue(1)' means the local preference value is the
         value of tRPAdminPSAcceptActionLocalPreference; the value of the
         object tRPAdminPSAcptActLocalPrefParam is ignored.

         The value 'actionParam(2) means the local preference value is derived
         from the object tRPAdminPSAcptActLocalPrefParam; the value of the
         object tRPAdminPSAcceptActionLocalPreference is ignored."
    DEFVAL      { actionValue }
    ::= { tRPAdminPSAcptActParamsExtEntry 10 }

tRPAdminPSAcptActLocalPrefParam  OBJECT-TYPE
    SYNTAX      TPolicyVariableNameOrEmpty
    MAX-ACCESS  read-create
    STATUS      current
    DESCRIPTION
        "The value of tRPAdminPSAcptActLocalPrefParam specifies the variable
         name that must be resolved to get the local preference for the route.

         The value of this object tRPAdminPSAcptActLocalPrefParam is ignored
         when the object tRPAdminPSAcptActLocalPrefSource has a value different
         from actionParam(2)."
    DEFVAL      { ''H }
    ::= { tRPAdminPSAcptActParamsExtEntry 11 }

tRPAdminPSAcptActMetricParam     OBJECT-TYPE
    SYNTAX      TPolicyVariableNameOrEmpty
    MAX-ACCESS  read-create
    STATUS      current
    DESCRIPTION
        "The value of tRPAdminPSAcptActMetricParam specifies the variable name
         that must be resolved to get the metric value for the route.

         The value of this object tRPAdminPSAcptActMetricParam is ignored when
         the object tRPAdminPSAcptActnMetricSource has a value different from
         metricParam(3)."
    DEFVAL      { ''H }
    ::= { tRPAdminPSAcptActParamsExtEntry 12 }

tRPAdminPSAcptActNextHopSource   OBJECT-TYPE
    SYNTAX      TPolicyActionSource
    MAX-ACCESS  read-create
    STATUS      current
    DESCRIPTION
        "The value of tRPAdminPSAcptActNextHopSource specifies the source of
         the accept action next-hop.

         The value 'actionValue(1)' means the next-hop address is the value of
         tRPAdminPSAcptActInetNextHop and the address type is defined by
         tRPAdminPSAcptActInetNextHopType; the value of the object
         tRPAdminPSAcptActNextHopParam is ignored.

         The value 'actionParam(2) means the next-hop value is derived from the
         object tRPAdminPSAcptActNextHopParam; the value of the object
         tRPAdminPSAcptActInetNextHop and tRPAdminPSAcptActInetNextHopType are
         ignored."
    DEFVAL      { actionValue }
    ::= { tRPAdminPSAcptActParamsExtEntry 13 }

tRPAdminPSAcptActNextHopParam    OBJECT-TYPE
    SYNTAX      TPolicyVariableNameOrEmpty
    MAX-ACCESS  read-create
    STATUS      current
    DESCRIPTION
        "The value of tRPAdminPSAcptActNextHopParam specifies the variable name
         that must be resolved to get the next-hop IP address in the route.

         The value of this object tRPAdminPSAcptActNextHopParam is ignored when
         the object tRPAdminPSAcptActNextHopSource has a value different from
         actionParam(2)."
    DEFVAL      { ''H }
    ::= { tRPAdminPSAcptActParamsExtEntry 14 }

tRPAdminPSAcptActOriginSource    OBJECT-TYPE
    SYNTAX      TPolicyActionSource
    MAX-ACCESS  read-create
    STATUS      current
    DESCRIPTION
        "The value of tRPAdminPSAcptActOriginSource specifies the source of the
         route origin accept action.

         The value 'actionValue(1)' means the origin is the value of
         tRPAdminPSAcceptActionOrigin; the value of the object
         tRPAdminPSAcptActOriginParam is ignored.

         The value 'actionParam(2) means the origin value is derived from the
         object tRPAdminPSAcptActOriginParam; the value of the object
         tRPAdminPSAcceptActionOrigin is ignored."
    DEFVAL      { actionValue }
    ::= { tRPAdminPSAcptActParamsExtEntry 15 }

tRPAdminPSAcptActOriginParam     OBJECT-TYPE
    SYNTAX      TPolicyVariableNameOrEmpty
    MAX-ACCESS  read-create
    STATUS      current
    DESCRIPTION
        "The value of tRPAdminPSAcptActOriginParam specifies the variable name
         that must be resolved to get the origin of the route exported into BGP
         if it does not match an entry.

         The value of this object tRPAdminPSAcptActOriginParam is ignored when
         the object tRPAdminPSAcptActOriginSource has a value different from
         actionParam(2)."
    DEFVAL      { ''H }
    ::= { tRPAdminPSAcptActParamsExtEntry 16 }

tRPAdminPSAcptActOrigValStateSrc OBJECT-TYPE
    SYNTAX      TPolicyActionSource
    MAX-ACCESS  read-create
    STATUS      current
    DESCRIPTION
        "The value of tRPAdminPSAcptActOrigValStateSrc specifies the source of
         the origin validation state.

         The value 'actionValue(1)' means the origin validation state is the
         value of tRPAdminPSAcptActnOrigValidState; the value of the object
         tRPAdminPSAcptActOrigValStatePar is ignored.

         The value 'actionParam(2) means the origin validation state value is
         derived from the object tRPAdminPSAcptActOrigValStatePar; the value of
         the object tRPAdminPSAcptActnOrigValidState is ignored."
    DEFVAL      { actionValue }
    ::= { tRPAdminPSAcptActParamsExtEntry 17 }

tRPAdminPSAcptActOrigValStatePar OBJECT-TYPE
    SYNTAX      TPolicyVariableNameOrEmpty
    MAX-ACCESS  read-create
    STATUS      current
    DESCRIPTION
        "The value of tRPAdminPSAcptActOrigValStatePar specifies the variable
         name that must be resolved to get the origin validation state.

         The value of this object tRPAdminPSAcptActOrigValStatePar is ignored
         when the object tRPAdminPSAcptActOrigValStateSrc has a value different
         from actionParam(2)."
    DEFVAL      { ''H }
    ::= { tRPAdminPSAcptActParamsExtEntry 18 }

tRPAdminPSAcptActPreferenceSrc   OBJECT-TYPE
    SYNTAX      TPolicyActionSource
    MAX-ACCESS  read-create
    STATUS      current
    DESCRIPTION
        "The value of tRPAdminPSAcptActPreferenceSrc specifies the source of
         the preference accept action.

         The value 'actionValue(1)' means the preference is the value of
         tRPAdminPSAcceptActionPreference; the value of the object
         tRPAdminPSAcptActPreferenceParam is ignored.

         The value 'actionParam(2) means the preference value is derived from
         the object tRPAdminPSAcptActPreferenceParam; the value of the object
         tRPAdminPSAcceptActionPreference is ignored."
    DEFVAL      { actionValue }
    ::= { tRPAdminPSAcptActParamsExtEntry 19 }

tRPAdminPSAcptActPreferenceParam OBJECT-TYPE
    SYNTAX      TPolicyVariableNameOrEmpty
    MAX-ACCESS  read-create
    STATUS      current
    DESCRIPTION
        "The value of tRPAdminPSAcptActPreferenceParam specifies the variable
         name that must be resolved to get the preference.

         The value of this object tRPAdminPSAcptActPreferenceParam is ignored
         when the object tRPAdminPSAcptActPreferenceSrc has a value different
         from actionParam(2)."
    DEFVAL      { ''H }
    ::= { tRPAdminPSAcptActParamsExtEntry 20 }

tRPAdminPSAcptActTagSource       OBJECT-TYPE
    SYNTAX      TPolicyActionSource
    MAX-ACCESS  read-create
    STATUS      current
    DESCRIPTION
        "The value of tRPAdminPSAcptActTagSource specifies the source of the
         tag accept action.

         The value 'actionValue(1)' means the tag is the value of
         tRPAdminPSAcceptActionTag; the value of the object
         tRPAdminPSAcptActTagParam is ignored.

         The value 'actionParam(2) means the tag value is derived from the
         object tRPAdminPSAcptActTagParam; the value of the object
         tRPAdminPSAcceptActionTag is ignored."
    DEFVAL      { actionValue }
    ::= { tRPAdminPSAcptActParamsExtEntry 21 }

tRPAdminPSAcptActTagParam        OBJECT-TYPE
    SYNTAX      TPolicyVariableNameOrEmpty
    MAX-ACCESS  read-create
    STATUS      current
    DESCRIPTION
        "The value of tRPAdminPSAcptActTagParam specifies the variable name
         that must be resolved to get the tag for the route.

         The value of this object tRPAdminPSAcptActTagParam is ignored when the
         object tRPAdminPSAcptActTagSource has a value different from
         actionParam(2)."
    DEFVAL      { ''H }
    ::= { tRPAdminPSAcptActParamsExtEntry 22 }

tRPAdminPSAcptActOspfTypeSource  OBJECT-TYPE
    SYNTAX      TPolicyActionSource
    MAX-ACCESS  read-create
    STATUS      current
    DESCRIPTION
        "The value of tRPAdminPSAcptActOspfTypeSource specifies the source of
         the OSPF route type accept action.

         The value 'actionValue(1)' means the OSPF route type is the value of
         tRPAdminPSAcceptActionOspfType; the value of the object
         tRPAdminPSAcptActOspfTypeParam is ignored.

         The value 'actionParam(2) means the OSPF route type value is derived
         from the object tRPAdminPSAcptActOspfTypeParam; the value of the
         object tRPAdminPSAcceptActionOspfType is ignored."
    DEFVAL      { actionValue }
    ::= { tRPAdminPSAcptActParamsExtEntry 23 }

tRPAdminPSAcptActOspfTypeParam   OBJECT-TYPE
    SYNTAX      TPolicyVariableNameOrEmpty
    MAX-ACCESS  read-create
    STATUS      current
    DESCRIPTION
        "The value of tRPAdminPSAcptActOspfTypeParam specifies the variable
         name that must be resolved to get the OSPF route type to set in route.

         The value of this object tRPAdminPSAcptActOspfTypeParam is ignored
         when the object tRPAdminPSAcptActOspfTypeSource has a value different
         from actionParam(2)."
    DEFVAL      { ''H }
    ::= { tRPAdminPSAcptActParamsExtEntry 24 }

tRPAdminPSAcptActASPPendCountSrc OBJECT-TYPE
    SYNTAX      TPolicyActionSource
    MAX-ACCESS  read-create
    STATUS      current
    DESCRIPTION
        "The value of tRPAdminPSAcptActASPPendCountSrc specifies the source of
         the accept action AS Path prepend repeat count.

         The value 'actionValue(1)' means the AS Path prepend count is the
         value of tRPAdminPSAcceptActionASPathPrependCount; the value of the
         object tRPAdminPSAcptActASPPendCountPar is ignored.

         The value 'actionParam(2) means the AS Path prepend count is derived
         from the object tRPAdminPSAcptActASPPendCountPar; the value of the
         object tRPAdminPSAcceptActionASPathPrependCount is ignored."
    DEFVAL      { actionValue }
    ::= { tRPAdminPSAcptActParamsExtEntry 26 }

tRPAdminPSAcptActASPPendCountPar OBJECT-TYPE
    SYNTAX      TPolicyVariableNameOrEmpty
    MAX-ACCESS  read-create
    STATUS      current
    DESCRIPTION
        "The value of tRPAdminPSAcptActASPPendCountPar specifies the variable
         name that must be resolved to get the number of times to prepend the
         AS number to the AS-Path attribute of the route.

         The value of this object is ignored when the object
         tRPAdminPSAcptActASPPendCountSrc has a value different from
         actionParam(2)."
    DEFVAL      { ''H }
    ::= { tRPAdminPSAcptActParamsExtEntry 27 }

tRPAdminPSAcptActASPPndMstRecent OBJECT-TYPE
    SYNTAX      TruthValue
    MAX-ACCESS  read-create
    STATUS      current
    DESCRIPTION
        "The value of tRPAdminPSAcptActASPPndMstRecent specifies whether the
         most recent AS number must be prepended to the AS-Path attribute of
         the route.

         When the value of tRPAdminPSAcptActASPPndMstRecent is true the last
         (most recent) ASN in the AS path is used to prepend to the AS-Path;
         tRPAdminPSAcceptActionASPathPend and tRPAdminPSAcptActASPathPendParam
         are ignored."
    DEFVAL      { false }
    ::= { tRPAdminPSAcptActParamsExtEntry 28 }

tRPAdminPSAcptActCreateUdpTunnel OBJECT-TYPE
    SYNTAX      TruthValue
    MAX-ACCESS  read-create
    STATUS      current
    DESCRIPTION
        "The value of tRPAdminPSAcptActCreateUdpTunnel specifies whether a UDP
         tunnel must be instantiated for the route matching this entry."
    DEFVAL      { false }
    ::= { tRPAdminPSAcptActParamsExtEntry 29 }

tRPAdminPSAcptActResolveStatic   OBJECT-TYPE
    SYNTAX      TruthValue
    MAX-ACCESS  read-create
    STATUS      current
    DESCRIPTION
        "The value of tRPAdminPSAcptActResolveStatic specifies whether the BGP
         next-hop for the route matching this entry is the resolved next-hop of
         the static route.

         This object has only effect in BGP export policies and applies only to
         BGP routes created by exporting static routes with indirect next-hops.

         When the value of tRPAdminPSAcptActResolveStatic is true, the BGP
         next-hop is the resolved next-hop of the static route. When the value
         is false, the BGP next-hop is copied from the indirect next-hop."
    DEFVAL      { false }
    ::= { tRPAdminPSAcptActParamsExtEntry 30 }

tRPAdminPSAcptActAdminTagPolicy  OBJECT-TYPE
    SYNTAX      TPolicyAdminTagPolicyOrVarName
    MAX-ACCESS  read-create
    STATUS      current
    DESCRIPTION
        "The value of tRPAdminPSAcptActAdminTagPolicy specifies the
         administrative tag policy for the route matching this entry.

         The tRPAdminPSAcptActAdminTagPolicy can be a string containing the
         administrative tag policy or a variable name that needs to be resolved
         to get the administrative tag policy.

         The internal colour value assigned to the tag is associated with the
         route. If one or more tags are specified in the policy in an
         include/exclude, then the internal colours associated with those tags
         are assigned to the include/exclude list.

         Set to empty string to disable."
    DEFVAL      { ''H }
    ::= { tRPAdminPSAcptActParamsExtEntry 31 }

tRPAdminPSAcptActBgpMedSource    OBJECT-TYPE
    SYNTAX      TPolicyBgpMedSource
    MAX-ACCESS  read-create
    STATUS      current
    DESCRIPTION
        "The value of tRPAdminPSAcptActBgpMedSource specifies the source to
         resolve to get the BGP MED value.

         When the value is 'igp', the BGP MED value is set to the  IGP cost of
         the route or tunnel that resolves the BGP next-hop of the received BGP
         route.

         When the value is 'minIgp', the BGP MED value is set to the minimum
         IGP cost; i.e. if the cost of the resolving route or tunnel increases
         the advertised MED is not changed.

         When the value is 'medValue', the BGP MED value is set to the value of
         tRPAdminPSAcptActBgpMedValue.

         When the value is 'expression', the BGP MED value is set based on a
         calculation of the provided expression in tRPAdminPSAcptActBgpMedExpr."
    DEFVAL      { none }
    ::= { tRPAdminPSAcptActParamsExtEntry 32 }

tRPAdminPSAcptActBgpMedValue     OBJECT-TYPE
    SYNTAX      TPolicyValueOrVarNameOrEmpty
    MAX-ACCESS  read-create
    STATUS      current
    DESCRIPTION
        "The value of tRPAdminPSAcptActBgpMedValue specifies the the BGP MED
         value.

         The value of this object can be a string containing the BGP MED value
         in the range [0..4294967295] or a variable name that needs to be
         resolved to get the BGP MED value.

         The value of this object is ignored when the object
         tRPAdminPSAcptActBgpMedSource has a value different from 'medValue'."
    DEFVAL      { "" }
    ::= { tRPAdminPSAcptActParamsExtEntry 33 }

tRPAdminPSAcptActBgpMedExpr      OBJECT-TYPE
    SYNTAX      TPolicyBgpMedExpression
    MAX-ACCESS  read-create
    STATUS      current
    DESCRIPTION
        "The value of tRPAdminPSAcptActBgpMedExpr specifies the expression that
         is used to calculate the BGP MED value.

         The value of this object is ignored when the object
         tRPAdminPSAcptActBgpMedSource has a value different from 'expression'."
    DEFVAL      { "" }
    ::= { tRPAdminPSAcptActParamsExtEntry 34 }

tRPAdminPSAcptActDisableRtInst   OBJECT-TYPE
    SYNTAX      TruthValue
    MAX-ACCESS  read-create
    STATUS      current
    DESCRIPTION
        "The value of tRPAdminPSAcptActDisableRtInst specifies whether to
         disable the installation of a BGP route in the Routing Table and the
         Forwarding Information Base (FIB)."
    DEFVAL      { false }
    ::= { tRPAdminPSAcptActParamsExtEntry 35 }

tRPAdminPSAcptActSrLabelIndex    OBJECT-TYPE
    SYNTAX      TPolicyValueOrVarNameOrEmpty
    MAX-ACCESS  read-create
    STATUS      current
    DESCRIPTION
        "The value of tRPAdminPSAcptActSrLabelIndex specifies the the Segment
         Routing (SR) Label Index value.

         The value of this object can be a string containing the SR label Index
         value in the range [1..1048575] or [0..1048575] (max label value
         depends on the platform) or a variable name that needs to be resolved
         to get the SR Label Index."
    DEFVAL      { "" }
    ::= { tRPAdminPSAcptActParamsExtEntry 36 }

tRPAdminPSAcptActSrLblIndPrefIgp OBJECT-TYPE
    SYNTAX      TruthValue
    MAX-ACCESS  read-create
    STATUS      current
    DESCRIPTION
        "The value of tRPAdminPSAcptActSrLblIndPrefIgp specifies whether it is
         preferred to use the SR Label Index from the IGP route.

         When the value is 'true', BGP will use the SR Label Index form the IGP
         route when present else it will use the value from
         tRPAdminPSAcptActSrLabelIndex. When the value is 'false', BGP will
         always use the  tRPAdminPSAcptActSrLabelIndex.

         The value of this object is ignored when the object
         tRPAdminPSAcptActSrLabelIndex is empty."
    DEFVAL      { false }
    ::= { tRPAdminPSAcptActParamsExtEntry 37 }

tRPAdminPSAcptActNextHopPeerAddr OBJECT-TYPE
    SYNTAX      TruthValue
    MAX-ACCESS  read-create
    STATUS      current
    DESCRIPTION
        "The value of tRPAdminPSAcptActNextHopPeerAddr specifies whether the
         next-hop must be set to the peer address.

         This object cannot be set to 'true' at the same time as setting the
         other next-hop objects to a non-default value.

         When this object is set to 'true' then
         tRPAdminPSAcceptActionNextHopSelf, tRPAdminPSAcceptActionNextHop,
         tRPAdminPSAcptActInetNextHopType, tRPAdminPSAcptActInetNextHop,
         tRPAdminPSAcptActNextHopSource and tRPAdminPSAcptActNextHopParam
         objects are reset."
    DEFVAL      { false }
    ::= { tRPAdminPSAcptActParamsExtEntry 38 }

tRPAdminPSAcptActBgpHighPriority OBJECT-TYPE
    SYNTAX      TruthValue
    MAX-ACCESS  read-create
    STATUS      current
    DESCRIPTION
        "The value of tRPAdminPSAcptActBgpHighPriority specifies whether the
         corresponding prefix must be marked in BGP as needing high priority
         treatment."
    DEFVAL      { false }
    ::= { tRPAdminPSAcptActParamsExtEntry 39 }

tRPAdminPSAcptActFlexAlgo        OBJECT-TYPE
    SYNTAX      TPolicyValueOrVarNameOrEmpty
    MAX-ACCESS  read-create
    STATUS      current
    DESCRIPTION
        "The value of tRPAdminPSAcptActFlexAlgo specifies the identifier of the
         Flexible Algorithm.

         The value of this object can be a string containing the Flex Algo Id
         value in the range [128..255] or a variable name that needs to be
         resolved to get the Flex Algo Id."
    DEFVAL      { "" }
    ::= { tRPAdminPSAcptActParamsExtEntry 40 }

tRPAdminPSAcptActBgpTunnelMetric OBJECT-TYPE
    SYNTAX      TPolicyValueOrVarNameOrEmpty
    MAX-ACCESS  read-create
    STATUS      current
    DESCRIPTION
        "The value of tRPAdminPSAcptActBgpTunnelMetric specifies the the BGP
         Tunnel Metric value.

         The value of this object can be a string containing the BGP Tunnel
         Metric value in the range [0..4294967295] or a  variable name that
         needs to be resolved to get the  BGP Tunnel Metric."
    DEFVAL      { "" }
    ::= { tRPAdminPSAcptActParamsExtEntry 41 }

tRPAdminPSAcptActBgpTMetPrefAigp OBJECT-TYPE
    SYNTAX      TruthValue
    MAX-ACCESS  read-create
    STATUS      current
    DESCRIPTION
        "The value of tRPAdminPSAcptActBgpTMetPrefAigp specifies whether it is
         preferred to use the value of the received AIGP attribute as BGP
         Tunnel Metric.

         If the value is 'true', the TTM metric is set to the value of the
         AIGP attribute if attached.
         If an AIGP metric is not attached or if the value is 'false',
         the TTM metric is based on the attached MED metric (if  preferred)
         or set to tRPAdminPSAcptActBgpTunnelMetric.

         The value of this object is ignored if the object
         tRPAdminPSAcptActBgpTunnelMetric is empty."
    DEFVAL      { false }
    ::= { tRPAdminPSAcptActParamsExtEntry 42 }

tRPAdminPSAcptActEgressStats     OBJECT-TYPE
    SYNTAX      TruthValue
    MAX-ACCESS  read-create
    STATUS      current
    DESCRIPTION
        "The value of tRPAdminPSAcptActEgressStats specifies whether to collect
         egress statistics for BGP Labeled Unicast routes.

         If the value is 'true', the system is instructed to allocate a
         statistical index."
    DEFVAL      { false }
    ::= { tRPAdminPSAcptActParamsExtEntry 43 }

tRPAdminPSAcptActIngressStats    OBJECT-TYPE
    SYNTAX      TruthValue
    MAX-ACCESS  read-create
    STATUS      current
    DESCRIPTION
        "The value of tRPAdminPSAcptActIngressStats specifies whether to
         collect ingress statistics for BGP Labeled Unicast routes.

         If the value is 'true', the system is instructed to allocate a
         statistical index."
    DEFVAL      { false }
    ::= { tRPAdminPSAcptActParamsExtEntry 44 }

tRPAdminPSAcptActSrMaintPolicy   OBJECT-TYPE
    SYNTAX      TNamedItemOrEmpty
    MAX-ACCESS  read-create
    STATUS      current
    DESCRIPTION
        "The value of tRPAdminPSAcptActSrMaintPolicy specifies the named
         segment routing (SR) maintenance policy for SR policy routes.

         The maintenance policy must exist in
         TIMETRA-SR-POLICY-MIB::vRtrSrMainPlcyTable.

         The value of this object can be a string containing the
         maintenance policy or a variable name that needs to be
         resolved to get the maintenance policy. An empty string
         means that it is disabled."
    DEFVAL      { ''H }
    ::= { tRPAdminPSAcptActParamsExtEntry 45 }

tRPAdminPSAcptActNatPolicy       OBJECT-TYPE
    SYNTAX      TNamedItemOrEmpty
    MAX-ACCESS  read-create
    STATUS      current
    DESCRIPTION
        "The value of tRPAdminPSAcptActNatPolicy specifies the Network Address
         Translator (NAT) policy for the route matching this entry.

         The NAT policy must exist in TIMETRA-NAT-MIB::tmnxNatPlcyTable.

         The value of this object can be a string containing the
         NAT policy or a variable name that needs to be
         resolved to get the NAT policy. An empty string
         means that it is disabled."
    DEFVAL      { ''H }
    ::= { tRPAdminPSAcptActParamsExtEntry 46 }

tRPAdminPSAcptActCreateMplsTunl  OBJECT-TYPE
    SYNTAX      TruthValue
    MAX-ACCESS  read-create
    STATUS      current
    DESCRIPTION
        "The value of tRPAdminPSAcptActCreateMplsTunl specifies whether a MPLS
         tunnel must be instantiated for the route matching this entry.

         When the value is 'true', BGP sends the next hop and  (optionally if
         configured) admin-tag-policy name to MPLS if the route is accepted."
    DEFVAL      { false }
    ::= { tRPAdminPSAcptActParamsExtEntry 47 }

tRPAdminPSAcptActBgpTMetPrefMed  OBJECT-TYPE
    SYNTAX      TruthValue
    MAX-ACCESS  read-create
    STATUS      current
    DESCRIPTION
        "The value of tRPAdminPSAcptActBgpTMetPrefMed specifies whether it is
         preferred to use the value of the received MED attribute as BGP Tunnel
         Metric.

         If the value is 'true', the attached MED attribute is preferred to use
         as TTM metric above the tRPAdminPSAcptActBgpTunnelMetric. If a MED
         metric is not attached or if the value is 'false' or if AIGP metric is
         preferred, the TTM metric is set based on the attached AIGP metric or
         set to tRPAdminPSAcptActBgpTunnelMetric.

         The value of this object is ignored if the object
         tRPAdminPSAcptActBgpTunnelMetric is empty."
    DEFVAL      { false }
    ::= { tRPAdminPSAcptActParamsExtEntry 48 }

tRPAdminPSAcptActPrefTransFrr    OBJECT-TYPE
    SYNTAX      TruthValue
    MAX-ACCESS  read-create
    STATUS      current
    DESCRIPTION
        "The value of tRPAdminPSAcptActPrefTransFrr specifies whether transport
         fast-re-route should be preferred.

         The value of this object is ignored if the corresponding object
         tRPAdminPSFromCriteriaFamily is not srplcyIpv4, srplcyIpv6,
         ipv4MplsLabel or ipv6MplsLabel."
    DEFVAL      { false }
    ::= { tRPAdminPSAcptActParamsExtEntry 49 }

tRPAdminPSAcptActSrv6Locator     OBJECT-TYPE
    SYNTAX      TLNamedItemOrEmpty
    MAX-ACCESS  read-create
    STATUS      current
    DESCRIPTION
        "The value of tRPAdminPSAcptActSrv6Locator specifies the Segment
         Routing over IPv6 (SRv6) locator to advertise for the route matching
         this entry.

         The locator name must exist in  TIMETRA-SRV6:vRtrSrv6LocatorTable.

         The value of this object can be a string containing the
         locator or a variable name TPolicyVariableName that needs
         to be resolved to get the locator. An empty string
         means that it is disabled.

         The objects tRPAdminPSAcptActSrv6Locator and
         tRPAdminPSAcptActSrv6MSLocator are mutually exclusive."
    DEFVAL      { ''H }
    ::= { tRPAdminPSAcptActParamsExtEntry 50 }

tRPAdminPSAActSrv6RPathBfdSidSrc OBJECT-TYPE
    SYNTAX      TPolicyActionSource
    MAX-ACCESS  read-create
    STATUS      current
    DESCRIPTION
        "The value of tRPAdminPSAActSrv6RPathBfdSidSrc specifies the source of
         the SRv6 Return Path BFD SID accept action.

         The SID can only be set if tRPAdminPSAcptActSrMaintPolicy is set.

         The value 'actionValue(1)' means the Return Path SID is the value of
         tRPAdminPSAActSrv6RPathBfdSid and the address type is defined by
         tRPAdminPSAActSrv6RPathBfdSidTyp; the value of the object
         tRPAdminPSAActSrv6RPathBfdSidPar is ignored.

         The value 'actionParam(2) means the Return Path SID is derived from
         the object tRPAdminPSAActSrv6RPathBfdSidPar; the value of the object
         tRPAdminPSAActSrv6RPathBfdSid and tRPAdminPSAActSrv6RPathBfdSidTyp are
         ignored."
    DEFVAL      { actionValue }
    ::= { tRPAdminPSAcptActParamsExtEntry 51 }

tRPAdminPSAActSrv6RPathBfdSidTyp OBJECT-TYPE
    SYNTAX      InetAddressType
    MAX-ACCESS  read-create
    STATUS      current
    DESCRIPTION
        "The value of tRPAdminPSAActSrv6RPathBfdSidTyp specifies the type of
         tRPAdminPSAActSrv6RPathBfdSid."
    DEFVAL      { unknown }
    ::= { tRPAdminPSAcptActParamsExtEntry 52 }

tRPAdminPSAActSrv6RPathBfdSid    OBJECT-TYPE
    SYNTAX      InetAddress (SIZE (0|16))
    MAX-ACCESS  read-create
    STATUS      current
    DESCRIPTION
        "The value of tRPAdminPSAActSrv6RPathBfdSid specifies the the SRv6
         Return Path BFD SID.

         The SID can only be set if tRPAdminPSAcptActSrMaintPolicy is set."
    DEFVAL      { ''H }
    ::= { tRPAdminPSAcptActParamsExtEntry 53 }

tRPAdminPSAActSrv6RPathBfdSidPar OBJECT-TYPE
    SYNTAX      TPolicyVariableNameOrEmpty
    MAX-ACCESS  read-create
    STATUS      current
    DESCRIPTION
        "The value of tRPAdminPSAActSrv6RPathBfdSidPar specifies the variable
         name that must be resolved to get the SRv6 Return Path BFD SID to set
         in route.

         The value of this object tRPAdminPSAActSrv6RPathBfdSidPar is ignored
         when the object tRPAdminPSAActSrv6RPathBfdSidSrc has a value different
         from actionParam(2)."
    DEFVAL      { ''H }
    ::= { tRPAdminPSAcptActParamsExtEntry 54 }

tRPAdminPSAActSrReturnPathBfdLbl OBJECT-TYPE
    SYNTAX      TPolicyValueOrVarNameOrEmpty
    MAX-ACCESS  read-create
    STATUS      current
    DESCRIPTION
        "The value of tRPAdminPSAActSrReturnPathBfdLbl specifies the Return
         Path MPLS label for the BFD packet from the route matching this entry.

         The SID can only be set if tRPAdminPSAcptActSrMaintPolicy is set.

         The value of this object can be a string containing the label value in
         the range [32..1048575] or a variable name TPolicyVariableName that
         needs to be resolved to get the label. An empty string means that it
         is disabled."
    DEFVAL      { "" }
    ::= { tRPAdminPSAcptActParamsExtEntry 55 }

tRPAdminPSAcptActSrv6MSLocator   OBJECT-TYPE
    SYNTAX      TLNamedItemOrEmpty
    MAX-ACCESS  read-create
    STATUS      current
    DESCRIPTION
        "The value of tRPAdminPSAcptActSrv6MSLocator specifies the Segment
         Routing over IPv6 (SRv6) Micro Segment locator  to advertise for the
         route matching this entry.

         The locator name must exist in  TIMETRA-SRV6:vRtrSrv6MSLocatorTable.

         The value of this object can be a string containing the locator or a
         variable name TPolicyVariableName that needs  to be resolved to get
         the locator. An empty string means that it is disabled.

         The objects tRPAdminPSAcptActSrv6Locator and
         tRPAdminPSAcptActSrv6MSLocator are mutually exclusive."
    DEFVAL      { ''H }
    ::= { tRPAdminPSAcptActParamsExtEntry 56 }

tRPAdminPSDefActParamsExtTable   OBJECT-TYPE
    SYNTAX      SEQUENCE OF TRPAdminPSDefActParamsExtEntry
    MAX-ACCESS  not-accessible
    STATUS      current
    DESCRIPTION
        "An extension table of tRPAdminPSDefaultActionParamsTable containing
         extra default action parameters for each policy statement entry."
    ::= { tRPAdminValueObjects 24 }

tRPAdminPSDefActParamsExtEntry   OBJECT-TYPE
    SYNTAX      TRPAdminPSDefActParamsExtEntry
    MAX-ACCESS  not-accessible
    STATUS      current
    DESCRIPTION
        "Default action information for a policy statement entry."
    AUGMENTS    { tRPAdminPSDefaultActionParamsEntry }
    ::= { tRPAdminPSDefActParamsExtTable 1 }

TRPAdminPSDefActParamsExtEntry   ::= SEQUENCE
{
    tRPAdminPSDefActStickyEcmp       TruthValue,
    tRPAdminPSDefActAddPathSendLimit TPolicyAddPathSendLimit,
    tRPAdminPSDefActInstBackupPath   TruthValue,
    tRPAdminPSDefActAdvertiseLabel   TPolicyAdvertiseLabelMode,
    tRPAdminPSDefActBgpLeaking       TruthValue,
    tRPAdminPSDefActAigpMetricSource TPolicyActionSource,
    tRPAdminPSDefActAigpMetricParam  TPolicyVariableNameOrEmpty,
    tRPAdminPSDefActASPathPendSource TPolicyActionSource,
    tRPAdminPSDefActASPathPendParam  TPolicyVariableNameOrEmpty,
    tRPAdminPSDefActLocalPrefSource  TPolicyActionSource,
    tRPAdminPSDefActLocalPrefParam   TPolicyVariableNameOrEmpty,
    tRPAdminPSDefActMetricParam      TPolicyVariableNameOrEmpty,
    tRPAdminPSDefActNextHopSource    TPolicyActionSource,
    tRPAdminPSDefActNextHopParam     TPolicyVariableNameOrEmpty,
    tRPAdminPSDefActOriginSource     TPolicyActionSource,
    tRPAdminPSDefActOriginParam      TPolicyVariableNameOrEmpty,
    tRPAdminPSDefActOrigValStateSrc  TPolicyActionSource,
    tRPAdminPSDefActOrigValStatePar  TPolicyVariableNameOrEmpty,
    tRPAdminPSDefActPreferenceSource TPolicyActionSource,
    tRPAdminPSDefActPreferenceParam  TPolicyVariableNameOrEmpty,
    tRPAdminPSDefActTagSource        TPolicyActionSource,
    tRPAdminPSDefActTagParam         TPolicyVariableNameOrEmpty,
    tRPAdminPSDefActOspfTypeSource   TPolicyActionSource,
    tRPAdminPSDefActOspfTypeParam    TPolicyVariableNameOrEmpty,
    tRPAdminPSDefActASPPendCountSrc  TPolicyActionSource,
    tRPAdminPSDefActASPPendCountPar  TPolicyVariableNameOrEmpty,
    tRPAdminPSDefActASPPndMstRecent  TruthValue,
    tRPAdminPSDefActCreateUdpTunnel  TruthValue,
    tRPAdminPSDefActResolveStatic    TruthValue,
    tRPAdminPSDefActAdminTagPolicy   TPolicyAdminTagPolicyOrVarName,
    tRPAdminPSDefActBgpMedSource     TPolicyBgpMedSource,
    tRPAdminPSDefActBgpMedValue      TPolicyValueOrVarNameOrEmpty,
    tRPAdminPSDefActBgpMedExpr       TPolicyBgpMedExpression,
    tRPAdminPSDefActDisableRtInstall TruthValue,
    tRPAdminPSDefActSrLabelIndex     TPolicyValueOrVarNameOrEmpty,
    tRPAdminPSDefActSrLblIndPrefIgp  TruthValue,
    tRPAdminPSDefActNextHopPeerAddr  TruthValue,
    tRPAdminPSDefActBgpHighPriority  TruthValue,
    tRPAdminPSDefActFlexAlgo         TPolicyValueOrVarNameOrEmpty,
    tRPAdminPSDefActBgpTunnelMetric  TPolicyValueOrVarNameOrEmpty,
    tRPAdminPSDefActBgpTMetPrefAigp  TruthValue,
    tRPAdminPSDefActEgressStats      TruthValue,
    tRPAdminPSDefActIngressStats     TruthValue,
    tRPAdminPSDefActSrMaintPolicy    TNamedItemOrEmpty,
    tRPAdminPSDefActNatPolicy        TNamedItemOrEmpty,
    tRPAdminPSDefActCreateMplsTunl   TruthValue,
    tRPAdminPSDefActBgpTMetPrefMed   TruthValue,
    tRPAdminPSDefActPrefTransFrr     TruthValue,
    tRPAdminPSDefActSrv6Locator      TLNamedItemOrEmpty,
    tRPAdminPSDActSrv6RPathBfdSidSrc TPolicyActionSource,
    tRPAdminPSDActSrv6RPathBfdSidTyp InetAddressType,
    tRPAdminPSDActSrv6RPathBfdSid    InetAddress,
    tRPAdminPSDActSrv6RPathBfdSidPar TPolicyVariableNameOrEmpty,
    tRPAdminPSDActSrReturnPathBfdLbl TPolicyValueOrVarNameOrEmpty,
    tRPAdminPSDefActSrv6MSLocator    TLNamedItemOrEmpty
}

tRPAdminPSDefActStickyEcmp       OBJECT-TYPE
    SYNTAX      TruthValue
    MAX-ACCESS  read-create
    STATUS      current
    DESCRIPTION
        "The value of tRPAdminPSDefActStickyEcmp specifies whether sticky ECMP
         hash has to be applied to the route.

         When the value of tRPAdminPSDefActStickyEcmp is true and one or more
         of the multiple ECMP next-hops go down, then the unaffected traffic
         flows continues to be hashed to the same next-hops as prior to the
         failures; the affected traffic flows are redistributed as evenly as
         possible to the remaining next-hops."
    DEFVAL      { false }
    ::= { tRPAdminPSDefActParamsExtEntry 1 }

tRPAdminPSDefActAddPathSendLimit OBJECT-TYPE
    SYNTAX      TPolicyAddPathSendLimit
    MAX-ACCESS  read-create
    STATUS      current
    DESCRIPTION
        "The value of tRPAdminPSDefActAddPathSendLimit specifies the default
         ADD-PATH send limit for this policy statement."
    DEFVAL      { 0 }
    ::= { tRPAdminPSDefActParamsExtEntry 2 }

tRPAdminPSDefActInstBackupPath   OBJECT-TYPE
    SYNTAX      TruthValue
    MAX-ACCESS  read-create
    STATUS      current
    DESCRIPTION
        "The value of tRPAdminPSDefActInstBackupPath specifies whether the
         installation of a backup path is desired for the route matching this
         entry."
    DEFVAL      { false }
    ::= { tRPAdminPSDefActParamsExtEntry 3 }

tRPAdminPSDefActAdvertiseLabel   OBJECT-TYPE
    SYNTAX      TPolicyAdvertiseLabelMode
    MAX-ACCESS  read-create
    STATUS      current
    DESCRIPTION
        "The value of tRPAdminPSDefActAdvertiseLabel specifies the
         advertisement label mode for the route matching this entry."
    DEFVAL      { none }
    ::= { tRPAdminPSDefActParamsExtEntry 4 }

tRPAdminPSDefActBgpLeaking       OBJECT-TYPE
    SYNTAX      TruthValue
    MAX-ACCESS  read-create
    STATUS      current
    DESCRIPTION
        "The value of tRPAdminPSDefActBgpLeaking specifies whether BGP leaking
         has to be applied to the route.

         When the value of tRPAdminPSDefActBgpLeaking is true, the BGP route is
         leaked into a VPRN according to the user configured policies."
    DEFVAL      { false }
    ::= { tRPAdminPSDefActParamsExtEntry 5 }

tRPAdminPSDefActAigpMetricSource OBJECT-TYPE
    SYNTAX      TPolicyActionSource
    MAX-ACCESS  read-create
    STATUS      current
    DESCRIPTION
        "The value of tRPAdminPSDefActAigpMetricSource specifies the source of
         the accept action AIGP (Accumulated IGP) metric.

         The value 'actionValue(1)' means the AIGP metric value is the value of
         tRPAdminPSDefActnAigpMetricVal; the value of the object
         tRPAdminPSDefActAigpMetricParam is ignored.

         The value 'actionParam(2) means the AIGP metric value is derived from
         the object tRPAdminPSDefActAigpMetricParam; the value of the object
         tRPAdminPSDefActnAigpMetricVal is ignored.

         When the value of tRPAdminPSDefActionAigpMetric is set to 'none(1)' or
         'useIgp(4)', the value of tRPAdminPSDefActAigpMetricSource is ignored."
    DEFVAL      { actionValue }
    ::= { tRPAdminPSDefActParamsExtEntry 6 }

tRPAdminPSDefActAigpMetricParam  OBJECT-TYPE
    SYNTAX      TPolicyVariableNameOrEmpty
    MAX-ACCESS  read-create
    STATUS      current
    DESCRIPTION
        "The value of tRPAdminPSDefActAigpMetricParam specifies the variable
         name that must be resolved to get the value to be added or set for the
         route AIGP(Accumulated IGP) metric.

         The value of this object tRPAdminPSDefActAigpMetricParam is ignored
         when the object tRPAdminPSDefActAigpMetricSource has a value different
         from actionParam(2).

         When the value of tRPAdminPSDefActionAigpMetric is set to 'none(1)' or
         'useIgp(4)', the value of tRPAdminPSDefActAigpMetricParam is ignored."
    DEFVAL      { ''H }
    ::= { tRPAdminPSDefActParamsExtEntry 7 }

tRPAdminPSDefActASPathPendSource OBJECT-TYPE
    SYNTAX      TPolicyActionSource
    MAX-ACCESS  read-create
    STATUS      current
    DESCRIPTION
        "The value of tRPAdminPSDefActASPathPendSource specifies the source of
         the default action AS Path prepend.

         The value 'actionValue(1)' means the AS Path prepend value is the
         value of tRPAdminPSDefaultActionASPathPnd; the value of the object
         tRPAdminPSDefActASPathPendParam is ignored.

         The value 'actionParam(2) means the AS Path prepend value is derived
         from the object tRPAdminPSDefActASPathPendParam; the value of the
         object tRPAdminPSDefaultActionASPathPnd is ignored."
    DEFVAL      { actionValue }
    ::= { tRPAdminPSDefActParamsExtEntry 8 }

tRPAdminPSDefActASPathPendParam  OBJECT-TYPE
    SYNTAX      TPolicyVariableNameOrEmpty
    MAX-ACCESS  read-create
    STATUS      current
    DESCRIPTION
        "The value of tRPAdminPSDefActASPathPendParam specifies the variable
         name that must be resolved to get the AS Number to prepend to the
         AS-Path attribute of the route.

         The value of this object tRPAdminPSDefActASPathPendParam is ignored
         when the object tRPAdminPSDefActASPathPendSource has a value different
         from actionParam(2).

         The AS-Path prepending is disabled when the repeat count is set to
         zero; i.e. when tRPAdminPSDefaultActionASPathPrependCount is zero and
         tRPAdminPSDefActASPPendCountSrc is set to actionValue(1)."
    DEFVAL      { ''H }
    ::= { tRPAdminPSDefActParamsExtEntry 9 }

tRPAdminPSDefActLocalPrefSource  OBJECT-TYPE
    SYNTAX      TPolicyActionSource
    MAX-ACCESS  read-create
    STATUS      current
    DESCRIPTION
        "The value of tRPAdminPSDefActLocalPrefSource specifies the source of
         the default action local preference.

         The value 'actionValue(1)' means the local preference value is the
         value of tRPAdminPSDefaultActionLocalPreference; the value of the
         object tRPAdminPSDefActLocalPrefParam is ignored.

         The value 'actionParam(2) means the local preference value is derived
         from the object tRPAdminPSDefActLocalPrefParam; the value of the
         object tRPAdminPSDefaultActionLocalPreference is ignored."
    DEFVAL      { actionValue }
    ::= { tRPAdminPSDefActParamsExtEntry 10 }

tRPAdminPSDefActLocalPrefParam   OBJECT-TYPE
    SYNTAX      TPolicyVariableNameOrEmpty
    MAX-ACCESS  read-create
    STATUS      current
    DESCRIPTION
        "The value of tRPAdminPSDefActLocalPrefParam specifies the variable
         name that must be resolved to get the local preference for the route.

         The value of this object tRPAdminPSDefActLocalPrefParam is ignored
         when the object tRPAdminPSDefActLocalPrefSource has a value different
         from actionParam(2)."
    DEFVAL      { ''H }
    ::= { tRPAdminPSDefActParamsExtEntry 11 }

tRPAdminPSDefActMetricParam      OBJECT-TYPE
    SYNTAX      TPolicyVariableNameOrEmpty
    MAX-ACCESS  read-create
    STATUS      current
    DESCRIPTION
        "The value of tRPAdminPSDefActMetricParam specifies the variable name
         that must be resolved to get the metric value for the route.

         The value of this object tRPAdminPSDefActMetricParam is ignored when
         the object tRPAdminPSDefActionMetricSource has a value different from
         metricParam(3)."
    DEFVAL      { ''H }
    ::= { tRPAdminPSDefActParamsExtEntry 12 }

tRPAdminPSDefActNextHopSource    OBJECT-TYPE
    SYNTAX      TPolicyActionSource
    MAX-ACCESS  read-create
    STATUS      current
    DESCRIPTION
        "The value of tRPAdminPSDefActNextHopSource specifies the source of the
         default action next-hop.

         The value 'actionValue(1)' means the next-hop address is the value of
         tRPAdminPSDefActInetNextHop and the address type is defined by
         tRPAdminPSDefActInetNextHopType; the value of the object
         tRPAdminPSDefActNextHopParam is ignored.

         The value 'actionParam(2) means the next-hop value is derived from the
         object tRPAdminPSDefActNextHopParam; the value of the object
         tRPAdminPSDefActInetNextHop and tRPAdminPSDefActInetNextHopType are
         ignored."
    DEFVAL      { actionValue }
    ::= { tRPAdminPSDefActParamsExtEntry 13 }

tRPAdminPSDefActNextHopParam     OBJECT-TYPE
    SYNTAX      TPolicyVariableNameOrEmpty
    MAX-ACCESS  read-create
    STATUS      current
    DESCRIPTION
        "The value of tRPAdminPSDefActNextHopParam specifies the variable name
         that must be resolved to get the next-hop IP address in the route.

         The value of this object tRPAdminPSDefActNextHopParam is ignored when
         the object tRPAdminPSDefActNextHopSource has a value different from
         actionParam(2)."
    DEFVAL      { ''H }
    ::= { tRPAdminPSDefActParamsExtEntry 14 }

tRPAdminPSDefActOriginSource     OBJECT-TYPE
    SYNTAX      TPolicyActionSource
    MAX-ACCESS  read-create
    STATUS      current
    DESCRIPTION
        "The value of tRPAdminPSDefActOriginSource specifies the source of the
         route origin default action.

         The value 'actionValue(1)' means the origin is the value of
         tRPAdminPSDefaultActionOrigin; the value of the object
         tRPAdminPSDefActOriginParam is ignored.

         The value 'actionParam(2) means the origin value is derived from the
         object tRPAdminPSDefActOriginParam; the value of the object
         tRPAdminPSDefaultActionOrigin is ignored."
    DEFVAL      { actionValue }
    ::= { tRPAdminPSDefActParamsExtEntry 15 }

tRPAdminPSDefActOriginParam      OBJECT-TYPE
    SYNTAX      TPolicyVariableNameOrEmpty
    MAX-ACCESS  read-create
    STATUS      current
    DESCRIPTION
        "The value of tRPAdminPSDefActOriginParam specifies the variable name
         that must be resolved to get the origin of the route exported into BGP
         if it does not match an entry.

         The value of this object tRPAdminPSDefActOriginParam is ignored when
         the object tRPAdminPSDefActOriginSource has a value different from
         actionParam(2)."
    DEFVAL      { ''H }
    ::= { tRPAdminPSDefActParamsExtEntry 16 }

tRPAdminPSDefActOrigValStateSrc  OBJECT-TYPE
    SYNTAX      TPolicyActionSource
    MAX-ACCESS  read-create
    STATUS      current
    DESCRIPTION
        "The value of tRPAdminPSDefActOrigValStateSrc specifies the source of
         the default origin validation state.

         The value 'actionValue(1)' means the origin validation state is the
         value of tRPAdminPSDefActnOrigValidState; the value of the object
         tRPAdminPSDefActOrigValStatePar is ignored.

         The value 'actionParam(2) means the origin validation state value is
         derived from the object tRPAdminPSDefActOrigValStatePar; the value of
         the object tRPAdminPSDefActnOrigValidState is ignored."
    DEFVAL      { actionValue }
    ::= { tRPAdminPSDefActParamsExtEntry 17 }

tRPAdminPSDefActOrigValStatePar  OBJECT-TYPE
    SYNTAX      TPolicyVariableNameOrEmpty
    MAX-ACCESS  read-create
    STATUS      current
    DESCRIPTION
        "The value of tRPAdminPSDefActOrigValStatePar specifies the variable
         name that must be resolved to get the default origin validation state.

         The value of this object tRPAdminPSDefActOrigValStatePar can only be
         set when the object tRPAdminPSDefActOrigValStateSrc has the value
         actionParam(2)."
    DEFVAL      { ''H }
    ::= { tRPAdminPSDefActParamsExtEntry 18 }

tRPAdminPSDefActPreferenceSource OBJECT-TYPE
    SYNTAX      TPolicyActionSource
    MAX-ACCESS  read-create
    STATUS      current
    DESCRIPTION
        "The value of tRPAdminPSDefActPreferenceSource specifies the source of
         the default action preference.

         The value 'actionValue(1)' means the preference is the value of
         tRPAdminPSDefaultActionPreference; the value of the object
         tRPAdminPSDefActPreferenceParam is ignored.

         The value 'actionParam(2) means the preference value is derived from
         the object tRPAdminPSDefActPreferenceParam; the value of the object
         tRPAdminPSDefaultActionPreference is ignored."
    DEFVAL      { actionValue }
    ::= { tRPAdminPSDefActParamsExtEntry 19 }

tRPAdminPSDefActPreferenceParam  OBJECT-TYPE
    SYNTAX      TPolicyVariableNameOrEmpty
    MAX-ACCESS  read-create
    STATUS      current
    DESCRIPTION
        "The value of tRPAdminPSDefActPreferenceParam specifies the variable
         name that must be resolved to get the preference to apply to the
         route.

         The value of this object tRPAdminPSDefActPreferenceParam is ignored
         when the object tRPAdminPSDefActPreferenceSource has a value different
         from actionParam(2)."
    DEFVAL      { ''H }
    ::= { tRPAdminPSDefActParamsExtEntry 20 }

tRPAdminPSDefActTagSource        OBJECT-TYPE
    SYNTAX      TPolicyActionSource
    MAX-ACCESS  read-create
    STATUS      current
    DESCRIPTION
        "The value of tRPAdminPSDefActTagSource specifies the source of the tag
         default action.

         The value 'actionValue(1)' means the tag is the value of
         tRPAdminPSDefaultActionTag; the value of the object
         tRPAdminPSDefActTagParam is ignored.

         The value 'actionParam(2) means the tag value is derived from the
         object tRPAdminPSDefActTagParam; the value of the object
         tRPAdminPSDefaultActionTag is ignored."
    DEFVAL      { actionValue }
    ::= { tRPAdminPSDefActParamsExtEntry 21 }

tRPAdminPSDefActTagParam         OBJECT-TYPE
    SYNTAX      TPolicyVariableNameOrEmpty
    MAX-ACCESS  read-create
    STATUS      current
    DESCRIPTION
        "The value of tRPAdminPSDefActTagParam specifies the variable name that
         must be resolved to get the tag for the route.

         The value of this object tRPAdminPSDefActTagParam is ignored when the
         object tRPAdminPSDefActTagSource has a value different from
         actionParam(2)."
    DEFVAL      { ''H }
    ::= { tRPAdminPSDefActParamsExtEntry 22 }

tRPAdminPSDefActOspfTypeSource   OBJECT-TYPE
    SYNTAX      TPolicyActionSource
    MAX-ACCESS  read-create
    STATUS      current
    DESCRIPTION
        "The value of tRPAdminPSDefActOspfTypeSource specifies the source of
         the OSPF route type.

         The value 'actionValue(1)' means the OSPF route type is the value of
         tRPAdminPSDefaultActionOspfType; the value of the object
         tRPAdminPSDefActOspfTypeParam is ignored.

         The value 'actionParam(2) means the OSPF route type value is derived
         from the object tRPAdminPSDefActOspfTypeParam; the value of the object
         tRPAdminPSDefaultActionOspfType is ignored."
    DEFVAL      { actionValue }
    ::= { tRPAdminPSDefActParamsExtEntry 23 }

tRPAdminPSDefActOspfTypeParam    OBJECT-TYPE
    SYNTAX      TPolicyVariableNameOrEmpty
    MAX-ACCESS  read-create
    STATUS      current
    DESCRIPTION
        "The value of tRPAdminPSDefActOspfTypeParam specifies the variable name
         that must be resolved to get the OSPF route type for the route.

         The value of this object tRPAdminPSDefActOspfTypeParam is ignored when
         the object tRPAdminPSDefActOspfTypeSource has a value different from
         actionParam(2)."
    DEFVAL      { ''H }
    ::= { tRPAdminPSDefActParamsExtEntry 24 }

tRPAdminPSDefActASPPendCountSrc  OBJECT-TYPE
    SYNTAX      TPolicyActionSource
    MAX-ACCESS  read-create
    STATUS      current
    DESCRIPTION
        "The value of tRPAdminPSDefActASPPendCountSrc specifies the source of
         the default action AS Path prepend repeat count.

         The value 'actionValue(1)' means the AS Path prepend count is the
         value of tRPAdminPSDefaultActionASPathPrependCount; the value of the
         object tRPAdminPSDefActASPPendCountPar is ignored.

         The value 'actionParam(2) means the AS Path prepend count is derived
         from the object tRPAdminPSDefActASPPendCountPar; the value of the
         object tRPAdminPSDefaultActionASPathPrependCount is ignored."
    DEFVAL      { actionValue }
    ::= { tRPAdminPSDefActParamsExtEntry 26 }

tRPAdminPSDefActASPPendCountPar  OBJECT-TYPE
    SYNTAX      TPolicyVariableNameOrEmpty
    MAX-ACCESS  read-create
    STATUS      current
    DESCRIPTION
        "The value of tRPAdminPSDefActASPPendCountPar specifies the variable
         name that must be resolved to get the number of times to prepend the
         AS number to the AS-Path attribute of the route.

         The value of this object is ignored when the object
         tRPAdminPSDefActASPPendCountSrc has a value different from
         actionParam(2)."
    DEFVAL      { ''H }
    ::= { tRPAdminPSDefActParamsExtEntry 27 }

tRPAdminPSDefActASPPndMstRecent  OBJECT-TYPE
    SYNTAX      TruthValue
    MAX-ACCESS  read-create
    STATUS      current
    DESCRIPTION
        "The value of tRPAdminPSDefActASPPndMstRecent specifies whether the
         most recent AS number must be prepended to the AS-Path attribute of
         the route.

         When the value of tRPAdminPSDefActASPPndMstRecent is true the last
         (most recent) ASN in the AS path is used to prepend to the AS-Path;
         tRPAdminPSDefaultActionASPathPnd and tRPAdminPSDefActASPathPendParam
         are ignored."
    DEFVAL      { false }
    ::= { tRPAdminPSDefActParamsExtEntry 28 }

tRPAdminPSDefActCreateUdpTunnel  OBJECT-TYPE
    SYNTAX      TruthValue
    MAX-ACCESS  read-create
    STATUS      current
    DESCRIPTION
        "The value of tRPAdminPSDefActCreateUdpTunnel specifies whether a UDP
         tunnel must be instantiated for the route matching this entry."
    DEFVAL      { false }
    ::= { tRPAdminPSDefActParamsExtEntry 29 }

tRPAdminPSDefActResolveStatic    OBJECT-TYPE
    SYNTAX      TruthValue
    MAX-ACCESS  read-create
    STATUS      current
    DESCRIPTION
        "The value of tRPAdminPSDefActResolveStatic specifies whether the BGP
         next-hop for the route is the resolved next-hop of the static route.

         This object has only effect in BGP export policies and applies only to
         BGP routes created by exporting static routes with indirect next-hops.

         When the value of tRPAdminPSDefActResolveStatic is true, the BGP
         next-hop is the resolved next-hop of the static route. When the value
         is false, the BGP next-hop is copied from the indirect next-hop."
    DEFVAL      { false }
    ::= { tRPAdminPSDefActParamsExtEntry 30 }

tRPAdminPSDefActAdminTagPolicy   OBJECT-TYPE
    SYNTAX      TPolicyAdminTagPolicyOrVarName
    MAX-ACCESS  read-create
    STATUS      current
    DESCRIPTION
        "The value of tRPAdminPSDefActAdminTagPolicy specifies the
         administrative tag policy for the route.

         The tRPAdminPSDefActAdminTagPolicy can be a string containing the
         administrative tag policy or a variable name that needs to be resolved
         to get the administrative tag policy.

         The internal colour value assigned to the tag is associated with the
         route. If one or more tags are specified in the policy in an
         include/exclude, then the internal colours associated with those tags
         are assigned to the include/exclude list.

         Set to empty string to disable."
    DEFVAL      { ''H }
    ::= { tRPAdminPSDefActParamsExtEntry 31 }

tRPAdminPSDefActBgpMedSource     OBJECT-TYPE
    SYNTAX      TPolicyBgpMedSource
    MAX-ACCESS  read-create
    STATUS      current
    DESCRIPTION
        "The value of tRPAdminPSDefActBgpMedSource specifies the source to
         resolve to get the BGP MED value.

         When the value is 'igp', the BGP MED value is set to the  IGP cost of
         the route or tunnel that resolves the BGP next-hop of the received BGP
         route.

         When the value is 'minIgp', the BGP MED value is set to the minimum
         IGP cost; i.e. if the cost of the resolving route or tunnel increases
         the advertised MED is not changed.

         When the value is 'medValue', the BGP MED value is set to the value of
         tRPAdminPSDefActBgpMedValue.

         When the value is 'expression', the BGP MED value is set based on a
         calculation of the provided expression in tRPAdminPSDefActBgpMedExpr."
    DEFVAL      { none }
    ::= { tRPAdminPSDefActParamsExtEntry 32 }

tRPAdminPSDefActBgpMedValue      OBJECT-TYPE
    SYNTAX      TPolicyValueOrVarNameOrEmpty
    MAX-ACCESS  read-create
    STATUS      current
    DESCRIPTION
        "The value of tRPAdminPSDefActBgpMedValue specifies the the BGP MED
         value.

         The value of this object can be a string containing the BGP MED value
         in the range [0..4294967295] or a variable name that needs to be
         resolved to get the BGP MED value.

         The value of this object is ignored when the object
         tRPAdminPSDefActBgpMedSource has a value different from 'medValue'."
    DEFVAL      { "" }
    ::= { tRPAdminPSDefActParamsExtEntry 33 }

tRPAdminPSDefActBgpMedExpr       OBJECT-TYPE
    SYNTAX      TPolicyBgpMedExpression
    MAX-ACCESS  read-create
    STATUS      current
    DESCRIPTION
        "The value of tRPAdminPSDefActBgpMedExpr specifies the expression that
         is used to calculate the BGP MED value.

         The value of this object is ignored when the object
         tRPAdminPSDefActBgpMedSource has a value different from 'expression'."
    DEFVAL      { "" }
    ::= { tRPAdminPSDefActParamsExtEntry 34 }

tRPAdminPSDefActDisableRtInstall OBJECT-TYPE
    SYNTAX      TruthValue
    MAX-ACCESS  read-create
    STATUS      current
    DESCRIPTION
        "The value of tRPAdminPSDefActDisableRtInstall specifies whether to
         disable the installation of a BGP route in the Routing Table and the
         Forwarding Information Base (FIB)."
    DEFVAL      { false }
    ::= { tRPAdminPSDefActParamsExtEntry 35 }

tRPAdminPSDefActSrLabelIndex     OBJECT-TYPE
    SYNTAX      TPolicyValueOrVarNameOrEmpty
    MAX-ACCESS  read-create
    STATUS      current
    DESCRIPTION
        "The value of tRPAdminPSDefActSrLabelIndex specifies the the Segment
         Routing (SR) Label Index value.

         The value of this object can be a string containing the SR label Index
         value in the range [1..1048575] or [0..1048575] (max label value
         depends on the platform) or a variable name that needs to be resolved
         to get the SR Label Index."
    DEFVAL      { "" }
    ::= { tRPAdminPSDefActParamsExtEntry 36 }

tRPAdminPSDefActSrLblIndPrefIgp  OBJECT-TYPE
    SYNTAX      TruthValue
    MAX-ACCESS  read-create
    STATUS      current
    DESCRIPTION
        "The value of tRPAdminPSDefActSrLblIndPrefIgp specifies whether it is
         preferred to use the SR Label Index from the IGP route.

         When the value is 'true', BGP will use the SR Label Index form the IGP
         route when present else it will use the value from
         tRPAdminPSDefActSrLabelIndex. When the value is 'false', BGP will
         always use the  tRPAdminPSDefActSrLabelIndex.

         The value of this object is ignored when the object
         tRPAdminPSDefActSrLabelIndex is empty."
    DEFVAL      { false }
    ::= { tRPAdminPSDefActParamsExtEntry 37 }

tRPAdminPSDefActNextHopPeerAddr  OBJECT-TYPE
    SYNTAX      TruthValue
    MAX-ACCESS  read-create
    STATUS      current
    DESCRIPTION
        "The value of tRPAdminPSDefActNextHopPeerAddr specifies whether the
         next-hop must be set to the peer address.

         This object cannot be set to 'true' at the same time as setting the
         other next-hop objects to a non-default value.

         When this object is set to 'true' then
         tRPAdminPSDefaultActionNextHopSelf, tRPAdminPSDefaultActionNextHop,
         tRPAdminPSDefActInetNextHopType, tRPAdminPSDefActInetNextHop,
         tRPAdminPSDefActNextHopSource and tRPAdminPSDefActNextHopParam objects
         are reset."
    DEFVAL      { false }
    ::= { tRPAdminPSDefActParamsExtEntry 38 }

tRPAdminPSDefActBgpHighPriority  OBJECT-TYPE
    SYNTAX      TruthValue
    MAX-ACCESS  read-create
    STATUS      current
    DESCRIPTION
        "The value of tRPAdminPSDefActBgpHighPriority specifies whether the
         corresponding prefix must be marked in BGP as needing high priority
         treatment."
    DEFVAL      { false }
    ::= { tRPAdminPSDefActParamsExtEntry 39 }

tRPAdminPSDefActFlexAlgo         OBJECT-TYPE
    SYNTAX      TPolicyValueOrVarNameOrEmpty
    MAX-ACCESS  read-create
    STATUS      current
    DESCRIPTION
        "The value of tRPAdminPSDefActFlexAlgo specifies the identifier of the
         Flexible Algorithm.

         The value of this object can be a string containing the Flex Algo Id
         value in the range [128..255] or a variable name that needs to be
         resolved to get the Flex Algo Id."
    DEFVAL      { "" }
    ::= { tRPAdminPSDefActParamsExtEntry 40 }

tRPAdminPSDefActBgpTunnelMetric  OBJECT-TYPE
    SYNTAX      TPolicyValueOrVarNameOrEmpty
    MAX-ACCESS  read-create
    STATUS      current
    DESCRIPTION
        "The value of tRPAdminPSDefActBgpTunnelMetric specifies the the BGP
         Tunnel Metric value.

         The value of this object can be a string containing the BGP Tunnel
         Metric value in the range [0..4294967295] or a  variable name that
         needs to be resolved to get the  BGP Tunnel Metric."
    DEFVAL      { "" }
    ::= { tRPAdminPSDefActParamsExtEntry 41 }

tRPAdminPSDefActBgpTMetPrefAigp  OBJECT-TYPE
    SYNTAX      TruthValue
    MAX-ACCESS  read-create
    STATUS      current
    DESCRIPTION
        "The value of tRPAdminPSDefActBgpTMetPrefAigp specifies whether it is
         preferred to use the value of the received AIGP attribute as BGP
         Tunnel Metric.

         If the value is 'true', the TTM metric is set to the value of the AIGP
         attribute if attached.  If an AIGP metric is not attached or if the
         value is 'false', the TTM metric is based on the attached MED metric
         (if preferred) or set to tRPAdminPSDefActBgpTunnelMetric.

         The value of this object is ignored if the object
         tRPAdminPSDefActBgpTunnelMetric is empty."
    DEFVAL      { false }
    ::= { tRPAdminPSDefActParamsExtEntry 42 }

tRPAdminPSDefActEgressStats      OBJECT-TYPE
    SYNTAX      TruthValue
    MAX-ACCESS  read-create
    STATUS      current
    DESCRIPTION
        "The value of tRPAdminPSDefActEgressStats specifies whether to collect
         egress statistics for BGP Labeled Unicast routes.

         If the value is 'true', the system is instructed to allocate a
         statistical index."
    DEFVAL      { false }
    ::= { tRPAdminPSDefActParamsExtEntry 43 }

tRPAdminPSDefActIngressStats     OBJECT-TYPE
    SYNTAX      TruthValue
    MAX-ACCESS  read-create
    STATUS      current
    DESCRIPTION
        "The value of tRPAdminPSDefActIngressStats specifies whether to collect
         ingress statistics for BGP Labeled Unicast routes.

         If the value is 'true', the system is instructed to allocate a
         statistical index."
    DEFVAL      { false }
    ::= { tRPAdminPSDefActParamsExtEntry 44 }

tRPAdminPSDefActSrMaintPolicy    OBJECT-TYPE
    SYNTAX      TNamedItemOrEmpty
    MAX-ACCESS  read-create
    STATUS      current
    DESCRIPTION
        "The value of tRPAdminPSDefActSrMaintPolicy specifies the named segment
         routing (SR) maintenance policy for SR policy routes.

         The maintenance policy must exist in
         TIMETRA-SR-POLICY-MIB::vRtrSrMainPlcyTable.

         The value of this object can be a string containing the
         maintenance policy or a variable name that needs to be
         resolved to get the maintenance policy. An empty string
         means that is disabled."
    DEFVAL      { ''H }
    ::= { tRPAdminPSDefActParamsExtEntry 45 }

tRPAdminPSDefActNatPolicy        OBJECT-TYPE
    SYNTAX      TNamedItemOrEmpty
    MAX-ACCESS  read-create
    STATUS      current
    DESCRIPTION
        "The value of tRPAdminPSDefActNatPolicy specifies the Network Address
         Translator (NAT) policy for the route matching this entry.

         The NAT policy must exist in TIMETRA-NAT-MIB::tmnxNatPlcyTable.

         The value of this object can be a string containing the
         NAT policy or a variable name that needs to be
         resolved to get the NAT policy. An empty string
         means that it is disabled."
    DEFVAL      { ''H }
    ::= { tRPAdminPSDefActParamsExtEntry 46 }

tRPAdminPSDefActCreateMplsTunl   OBJECT-TYPE
    SYNTAX      TruthValue
    MAX-ACCESS  read-create
    STATUS      current
    DESCRIPTION
        "The value of tRPAdminPSDefActCreateMplsTunl specifies whether a MPLS
         tunnel must be instantiated for the route matching this entry.

         When the value is 'true', BGP sends the next hop and  (optionally if
         configured) admin-tag-policy name to MPLS if the route is accepted."
    DEFVAL      { false }
    ::= { tRPAdminPSDefActParamsExtEntry 47 }

tRPAdminPSDefActBgpTMetPrefMed   OBJECT-TYPE
    SYNTAX      TruthValue
    MAX-ACCESS  read-create
    STATUS      current
    DESCRIPTION
        "The value of tRPAdminPSDefActBgpTMetPrefMed specifies whether it is
         preferred to use the value of the received MED attribute as BGP Tunnel
         Metric.

         If the value is 'true', the attached MED attribute is preferred to use
         as TTM metric above the tRPAdminPSDefActBgpTunnelMetric. If a MED
         metric is not attached or if the value is 'false' or if AIGP metric is
         preferred, the TTM metric is set based on the attached AIGP metric or
         set to tRPAdminPSDefActBgpTunnelMetric.

         The value of this object is ignored if the object
         tRPAdminPSDefActBgpTunnelMetric is empty."
    DEFVAL      { false }
    ::= { tRPAdminPSDefActParamsExtEntry 48 }

tRPAdminPSDefActPrefTransFrr     OBJECT-TYPE
    SYNTAX      TruthValue
    MAX-ACCESS  read-create
    STATUS      current
    DESCRIPTION
        "The value of tRPAdminPSDefActPrefTransFrr specifies whether transport
         fast-re-route should be preferred.

         The value of this object is ignored if the object
         tRPAdminPSFromCriteriaFamily is not srplcyIpv4, srplcyIpv6,
         ipv4MplsLabel or ipv6MplsLabel."
    DEFVAL      { false }
    ::= { tRPAdminPSDefActParamsExtEntry 49 }

tRPAdminPSDefActSrv6Locator      OBJECT-TYPE
    SYNTAX      TLNamedItemOrEmpty
    MAX-ACCESS  read-create
    STATUS      current
    DESCRIPTION
        "The value of tRPAdminPSDefActSrv6Locator specifies the Segment Routing
         over IPv6 (SRv6) locator to advertise for the route matching this
         entry.

         The locator name must exist in  TIMETRA-SRV6:vRtrSrv6LocatorTable.

         The value of this object can be a string containing the
         locator or a variable name TPolicyVariableName that needs
         to be resolved to get the locator. An empty string
         means that it is disabled.

         The objects tRPAdminPSDefActSrv6Locator and
         tRPAdminPSDefActSrv6MSLocator are mutually exclusive."
    DEFVAL      { ''H }
    ::= { tRPAdminPSDefActParamsExtEntry 50 }

tRPAdminPSDActSrv6RPathBfdSidSrc OBJECT-TYPE
    SYNTAX      TPolicyActionSource
    MAX-ACCESS  read-create
    STATUS      current
    DESCRIPTION
        "The value of tRPAdminPSDActSrv6RPathBfdSidSrc specifies the source of
         the SRv6 Return Path BFD SID default action.

         The SID can only be set if tRPAdminPSDefActSrMaintPolicy is set.

         The value 'actionValue(1)' means the Return Path SID is the value of
         tRPAdminPSDActSrv6RPathBfdSid and the address type is defined by
         tRPAdminPSDActSrv6RPathBfdSidTyp; the value of the object
         tRPAdminPSDActSrv6RPathBfdSidPar is ignored.

         The value 'actionParam(2) means the Return Path SID is derived from
         the object tRPAdminPSDActSrv6RPathBfdSidPar; the value of the object
         tRPAdminPSDActSrv6RPathBfdSid and tRPAdminPSDActSrv6RPathBfdSidTyp are
         ignored."
    DEFVAL      { actionValue }
    ::= { tRPAdminPSDefActParamsExtEntry 51 }

tRPAdminPSDActSrv6RPathBfdSidTyp OBJECT-TYPE
    SYNTAX      InetAddressType
    MAX-ACCESS  read-create
    STATUS      current
    DESCRIPTION
        "The value of tRPAdminPSDActSrv6RPathBfdSidTyp specifies the type of
         tRPAdminPSDActSrv6RPathBfdSid."
    DEFVAL      { unknown }
    ::= { tRPAdminPSDefActParamsExtEntry 52 }

tRPAdminPSDActSrv6RPathBfdSid    OBJECT-TYPE
    SYNTAX      InetAddress (SIZE (0|16))
    MAX-ACCESS  read-create
    STATUS      current
    DESCRIPTION
        "The value of tRPAdminPSDActSrv6RPathBfdSid specifies the the SRv6
         Return Path BFD SID.

         The SID can only be set if tRPAdminPSDefActSrMaintPolicy is set."
    DEFVAL      { ''H }
    ::= { tRPAdminPSDefActParamsExtEntry 53 }

tRPAdminPSDActSrv6RPathBfdSidPar OBJECT-TYPE
    SYNTAX      TPolicyVariableNameOrEmpty
    MAX-ACCESS  read-create
    STATUS      current
    DESCRIPTION
        "The value of tRPAdminPSDActSrv6RPathBfdSidPar specifies the variable
         name that must be resolved to get the SRv6 Return Path BFD SID to set
         in route.

         The value of this object tRPAdminPSDActSrv6RPathBfdSidPar is ignored
         when the object tRPAdminPSDActSrv6RPathBfdSidSrc has a value different
         from actionParam(2)."
    DEFVAL      { ''H }
    ::= { tRPAdminPSDefActParamsExtEntry 54 }

tRPAdminPSDActSrReturnPathBfdLbl OBJECT-TYPE
    SYNTAX      TPolicyValueOrVarNameOrEmpty
    MAX-ACCESS  read-create
    STATUS      current
    DESCRIPTION
        "The value of tRPAdminPSDActSrReturnPathBfdLbl specifies the Return
         Path MPLS label for the BFD packet from the route matching this entry.

         The SID can only be set if tRPAdminPSDefActSrMaintPolicy is set.

         The value of this object can be a string containing the label value in
         the range [32..1048575] or a variable name TPolicyVariableName that
         needs to be resolved to get the label. An empty string means that it
         is disabled."
    DEFVAL      { "" }
    ::= { tRPAdminPSDefActParamsExtEntry 55 }

tRPAdminPSDefActSrv6MSLocator    OBJECT-TYPE
    SYNTAX      TLNamedItemOrEmpty
    MAX-ACCESS  read-create
    STATUS      current
    DESCRIPTION
        "The value of tRPAdminPSDefActSrv6MSLocator specifies the Segment
         Routing over IPv6 (SRv6) Micro Segment locator to advertise for the
         route matching this entry.

         The locator name must exist in  TIMETRA-SRV6:vRtrSrv6MSLocatorTable.

         The value of this object can be a string containing the locator or a
         variable name TPolicyVariableName that needs  to be resolved to get
         the locator. An empty string  means that it is disabled.

         The objects tRPAdminPSDefActSrv6Locator and
         tRPAdminPSDefActSrv6MSLocator are mutually exclusive."
    DEFVAL      { ''H }
    ::= { tRPAdminPSDefActParamsExtEntry 56 }

tRPAdminPfxListNameTable         OBJECT-TYPE
    SYNTAX      SEQUENCE OF TRPAdminPfxListNameEntry
    MAX-ACCESS  not-accessible
    STATUS      current
    DESCRIPTION
        "The table of admin prefix list names."
    ::= { tRPAdminValueObjects 25 }

tRPAdminPfxListNameEntry         OBJECT-TYPE
    SYNTAX      TRPAdminPfxListNameEntry
    MAX-ACCESS  not-accessible
    STATUS      current
    DESCRIPTION
        "Each row entry in the tRPAdminPfxListNameEntry represents information
         about a particular prefix list name.

         Entries are created and deleted by the user.

         When a prefix list entry is created in tRPAdminPrefixListTable or
         tRPAdminInetPrefixListTable with a name that doesn't exist in the
         tRPAdminPfxListNameTable, a corresponding entry will be created
         automatically in tRPAdminPfxListNameTable.

         When a prefix list name is deleted from the tRPAdminPfxListNameTable,
         the corresponding entry will be deleted automatically in
         tRPAdminPrefixListTable and tRPAdminInetPrefixListTable."
    INDEX       { tRPAdminPfxListName }
    ::= { tRPAdminPfxListNameTable 1 }

TRPAdminPfxListNameEntry         ::= SEQUENCE
{
    tRPAdminPfxListName              TLPrefixListName,
    tRPAdminPfxListNameRowStatus     RowStatus,
    tRPAdminPfxListNameCrOrigin      TmnxCreateOrigin
}

tRPAdminPfxListName              OBJECT-TYPE
    SYNTAX      TLPrefixListName (SIZE (1..64))
    MAX-ACCESS  not-accessible
    STATUS      current
    DESCRIPTION
        "The value of tRPAdminPfxListName indicates the name of the prefix list
         entry."
    ::= { tRPAdminPfxListNameEntry 1 }

tRPAdminPfxListNameRowStatus     OBJECT-TYPE
    SYNTAX      RowStatus
    MAX-ACCESS  read-create
    STATUS      current
    DESCRIPTION
        "RowStatus for this row.

         To create a row, set this object to createAndGo(4). When
         tRPAdminControlApply is set to commit(3), the row will actually be
         created in the tRPOperPfxListNameTable.

         To destroy a row, set this object to destroy(6). When
         tRPAdminControlApply is set to commit(3) the row will actually be
         removed from the tRPOperPfxListNameTable."
    ::= { tRPAdminPfxListNameEntry 2 }

tRPAdminPfxListNameCrOrigin      OBJECT-TYPE
    SYNTAX      TmnxCreateOrigin
    MAX-ACCESS  read-only
    STATUS      current
    DESCRIPTION
        "The value of the object tRPAdminPfxListNameCrOrigin indicates the
         mechanism used to create this entry."
    ::= { tRPAdminPfxListNameEntry 3 }

tRPAdminPSCondExprTable          OBJECT-TYPE
    SYNTAX      SEQUENCE OF TRPAdminPSCondExprEntry
    MAX-ACCESS  not-accessible
    STATUS      current
    DESCRIPTION
        "A table of conditional expressions for a policy statement."
    ::= { tRPAdminValueObjects 26 }

tRPAdminPSCondExprEntry          OBJECT-TYPE
    SYNTAX      TRPAdminPSCondExprEntry
    MAX-ACCESS  not-accessible
    STATUS      current
    DESCRIPTION
        "Information about a particular conditional expression for a policy
         statement entry.

         The conditional expressions decides whether an entry should be
         evaluated. If the result of the conditional expression is 'TRUE' the
         entry is fully evaluated; if the result is 'FALSE' the entry is
         skipped and evaluations continues to the next entry or the default
         action is applied in case no next entry exists."
    INDEX       {
        tRPAdminPolicyStatementName,
        tRPAdminPSNameEntryIndex
    }
    ::= { tRPAdminPSCondExprTable 1 }

TRPAdminPSCondExprEntry          ::= SEQUENCE
{
    tRPAdminPSCondExprRowStatus      RowStatus,
    tRPAdminPSCondExprRtExistString1 TPrefixListNameExpression
}

tRPAdminPSCondExprRowStatus      OBJECT-TYPE
    SYNTAX      RowStatus
    MAX-ACCESS  read-create
    STATUS      current
    DESCRIPTION
        "The value of tRPAdminPSCondExprRowStatus specifies the RowStatus for
         this row.

         To create a row, set this object to 'createAndGo(4)'. When
         tRPAdminControlApply is set to 'commit(3)', the row will actually be
         created in the tRPOperPSCondExprTable.

         To destroy a row, set this object to 'destroy(6)'. When
         tRPAdminControlApply is set to 'commit(3)', the row will actually be
         removed from the tRPOperPSCondExprTable."
    ::= { tRPAdminPSCondExprEntry 1 }

tRPAdminPSCondExprRtExistString1 OBJECT-TYPE
    SYNTAX      TPrefixListNameExpression
    MAX-ACCESS  read-create
    STATUS      current
    DESCRIPTION
        "The value of object tRPAdminPSCondExprRtExistString1 specifies an
         expression that contains a prefix list name and is used to test the
         route existence.

         The expression tests for the presence or absence of routes in the IP
         routing table that matches any of the entries in the prefix list.

         When tRPAdminPSCondExprRtExistString1 contains an empty string there
         is no route existence test and the expression is automatically
         considered 'TRUE'."
    DEFVAL      { "" }
    ::= { tRPAdminPSCondExprEntry 2 }

tRPAdminASPathGroupNameTable     OBJECT-TYPE
    SYNTAX      SEQUENCE OF TRPAdminASPathGroupNameEntry
    MAX-ACCESS  not-accessible
    STATUS      current
    DESCRIPTION
        "The table of admin AS-Path Group names."
    ::= { tRPAdminValueObjects 27 }

tRPAdminASPathGroupNameEntry     OBJECT-TYPE
    SYNTAX      TRPAdminASPathGroupNameEntry
    MAX-ACCESS  not-accessible
    STATUS      current
    DESCRIPTION
        "Each row entry in the tRPAdminASPathGroupNameEntry represents
         information about a particular AS-Path Group name.

         Entries can be created and deleted by the user.

         When an AS-Path Group entry is created with a name that doesn't exist
         in the tRPAdminASPathGroupNameTable, a corresponding entry will be
         created automatically in tRPAdminASPathGroupNameTable.

         When an AS-Path Group name is deleted from the
         tRPAdminASPathGroupNameTable, the corresponding entry will be deleted
         automatically in tRPAdminASPathGroupTable."
    INDEX       { tRPAdminASPGroupName }
    ::= { tRPAdminASPathGroupNameTable 1 }

TRPAdminASPathGroupNameEntry     ::= SEQUENCE
{
    tRPAdminASPGroupName             TASPathGroupName,
    tRPAdminASPGroupNameRowStatus    RowStatus,
    tRPAdminASPGroupNameCrOrigin     TmnxCreateOrigin
}

tRPAdminASPGroupName             OBJECT-TYPE
    SYNTAX      TASPathGroupName (SIZE (1..32))
    MAX-ACCESS  not-accessible
    STATUS      current
    DESCRIPTION
        "The value of tRPAdminASPGroupName indicates the name of the AS-Path
         Group."
    ::= { tRPAdminASPathGroupNameEntry 1 }

tRPAdminASPGroupNameRowStatus    OBJECT-TYPE
    SYNTAX      RowStatus
    MAX-ACCESS  read-create
    STATUS      current
    DESCRIPTION
        "The value of tRPAdminASPGroupNameRowStatus specifies the RowStatus for
         this row.

         To create a row, set this object to 'createAndGo(4)'. When
         tRPAdminControlApply is set to 'commit(3)', the row will actually be
         created in the tRPOperASPathGroupNameTable.

         To destroy a row, set this object to 'destroy(6)'. When
         tRPAdminControlApply is set to 'commit(3)', the row will actually be
         removed from the tRPOperASPathGroupNameTable."
    ::= { tRPAdminASPathGroupNameEntry 2 }

tRPAdminASPGroupNameCrOrigin     OBJECT-TYPE
    SYNTAX      TmnxCreateOrigin
    MAX-ACCESS  read-only
    STATUS      current
    DESCRIPTION
        "The value of the object tRPAdminASPGroupNameCrOrigin indicates the
         mechanism used to create this entry."
    ::= { tRPAdminASPathGroupNameEntry 3 }

tRPAdminCommunityNameTable       OBJECT-TYPE
    SYNTAX      SEQUENCE OF TRPAdminCommunityNameEntry
    MAX-ACCESS  not-accessible
    STATUS      current
    DESCRIPTION
        "The table of admin community names."
    ::= { tRPAdminValueObjects 28 }

tRPAdminCommunityNameEntry       OBJECT-TYPE
    SYNTAX      TRPAdminCommunityNameEntry
    MAX-ACCESS  not-accessible
    STATUS      current
    DESCRIPTION
        "Each row entry in the tRPAdminCommunityNameEntry represents
         information about a particular community name.

         Entries can be created and deleted by the user.

         When a community entry is created in tRPAdminCommunityTable with a
         name that doesn't exist in the tRPAdminCommunityNameTable, a
         corresponding entry will be created automatically in
         tRPAdminCommunityNameTable.

         When a community name is deleted from the tRPAdminCommunityNameTable,
         the corresponding entry will be deleted automatically in
         tRPAdminCommunityTable."
    INDEX       { tRPAdminCommName }
    ::= { tRPAdminCommunityNameTable 1 }

TRPAdminCommunityNameEntry       ::= SEQUENCE
{
    tRPAdminCommName                 TLCommunityName,
    tRPAdminCommNameRowStatus        RowStatus,
    tRPAdminCommNameCrOrigin         TmnxCreateOrigin
}

tRPAdminCommName                 OBJECT-TYPE
    SYNTAX      TLCommunityName (SIZE (1..64))
    MAX-ACCESS  not-accessible
    STATUS      current
    DESCRIPTION
        "The value of tRPAdminCommName indicates the name of the community."
    ::= { tRPAdminCommunityNameEntry 1 }

tRPAdminCommNameRowStatus        OBJECT-TYPE
    SYNTAX      RowStatus
    MAX-ACCESS  read-create
    STATUS      current
    DESCRIPTION
        "The value of tRPAdminCommNameRowStatus specifies the RowStatus for
         this row.

         To create a row, set this object to 'createAndGo(4)'. When
         tRPAdminControlApply is set to 'commit(3)', the row will actually be
         created in the tRPOperCommunityNameTable.

         To destroy a row, set this object to 'destroy(6)'. When
         tRPAdminControlApply is set to 'commit(3)', the row will actually be
         removed from the tRPOperCommunityNameTable."
    ::= { tRPAdminCommunityNameEntry 2 }

tRPAdminCommNameCrOrigin         OBJECT-TYPE
    SYNTAX      TmnxCreateOrigin
    MAX-ACCESS  read-only
    STATUS      current
    DESCRIPTION
        "The value of the object tRPAdminCommNameCrOrigin indicates the
         mechanism used to create this entry."
    ::= { tRPAdminCommunityNameEntry 3 }

tRPAdminGlobalVariableTable      OBJECT-TYPE
    SYNTAX      SEQUENCE OF TRPAdminGlobalVariableEntry
    MAX-ACCESS  not-accessible
    STATUS      current
    DESCRIPTION
        "Information to resolve global variables used in policy."
    ::= { tRPAdminValueObjects 29 }

tRPAdminGlobalVariableEntry      OBJECT-TYPE
    SYNTAX      TRPAdminGlobalVariableEntry
    MAX-ACCESS  not-accessible
    STATUS      current
    DESCRIPTION
        "This entry maps a global variable to a name which can be used in
         tRPAdminPSFromCriteriaTable, tRPAdminPSAcceptActionParamsTable,
         tRPAdminPSDefaultActionParamsTable, tRPAdminPSAcptActParamsExtTable or
         tRPAdminPSDefActParamsExtTable entries.

         If a local variable with the same name exists in
         tRPAdminPSPolicyVariableTable for the corresponding entry, the local
         variable is used to resolve the name."
    INDEX       { tRPAdminGlobalVarName }
    ::= { tRPAdminGlobalVariableTable 1 }

TRPAdminGlobalVariableEntry      ::= SEQUENCE
{
    tRPAdminGlobalVarName            TPolicyVariableName,
    tRPAdminGlobalVarRowStatus       RowStatus,
    tRPAdminGlobalVarType            TPolicyVariableType,
    tRPAdminGlobalVarString          TNamedItemOrEmpty,
    tRPAdminGlobalVarNumber          Unsigned32,
    tRPAdminGlobalVarAddressType     InetAddressType,
    tRPAdminGlobalVarAddress         InetAddress,
    tRPAdminGlobalVarDecimal         TPolicyDecimal,
    tRPAdminGlobalVarPrefixLength    InetAddressPrefixLength
}

tRPAdminGlobalVarName            OBJECT-TYPE
    SYNTAX      TPolicyVariableName
    MAX-ACCESS  not-accessible
    STATUS      current
    DESCRIPTION
        "The value of tRPAdminGlobalVarName specifies a variable name that can
         be used in the tRPAdminPSFromCriteriaTable,
         tRPAdminPSAcceptActionParamsTable, tRPAdminPSDefaultActionParamsTable,
         tRPAdminPSAcptActParamsExtTable or tRPAdminPSDefActParamsExtTable."
    ::= { tRPAdminGlobalVariableEntry 1 }

tRPAdminGlobalVarRowStatus       OBJECT-TYPE
    SYNTAX      RowStatus
    MAX-ACCESS  read-create
    STATUS      current
    DESCRIPTION
        "The value of tRPAdminGlobalVarRowStatus specifies the RowStatus for
         this row."
    ::= { tRPAdminGlobalVariableEntry 2 }

tRPAdminGlobalVarType            OBJECT-TYPE
    SYNTAX      TPolicyVariableType
    MAX-ACCESS  read-create
    STATUS      current
    DESCRIPTION
        "The value of tRPAdminGlobalVarType specifies how to resolve the
         tRPAdminGlobalVarName.

         string(1)  - indicates that tRPAdminGlobalVarString is to be used
         integer(2) - indicates that tRPAdminGlobalVarNumber is to be used
         address(3) - indicates that tRPAdminGlobalVarAddressType and
                      tRPAdminGlobalVarAddress are to be used
         decimal(4) - indicates that tRPAdminGlobalVarDecimal is to be used
         prefix (5) - indicates that tRPAdminGlobalVarAddressType,
                      tRPAdminGlobalVarAddress and tRPAdminGlobalVarPrefixLength
                      are to be used"
    DEFVAL      { string }
    ::= { tRPAdminGlobalVariableEntry 3 }

tRPAdminGlobalVarString          OBJECT-TYPE
    SYNTAX      TNamedItemOrEmpty
    MAX-ACCESS  read-create
    STATUS      current
    DESCRIPTION
        "The value of tRPAdminGlobalVarString specifies e.g. the actual as-path
         name to which tRPAdminGlobalVarName is resolved.

         This object tRPAdminGlobalVarString is ignored when the object
         tRPAdminGlobalVarType has a value different then string(1)."
    DEFVAL      { ''H }
    ::= { tRPAdminGlobalVariableEntry 4 }

tRPAdminGlobalVarNumber          OBJECT-TYPE
    SYNTAX      Unsigned32
    MAX-ACCESS  read-create
    STATUS      current
    DESCRIPTION
        "The value of tRPAdminGlobalVarNumber specifies e.g. the actual metric
         value to which tRPAdminGlobalVarName is resolved.

         This object tRPAdminGlobalVarNumber is ignored when the object
         tRPAdminGlobalVarType has a value different then integer(2)."
    DEFVAL      { 0 }
    ::= { tRPAdminGlobalVariableEntry 5 }

tRPAdminGlobalVarAddressType     OBJECT-TYPE
    SYNTAX      InetAddressType
    MAX-ACCESS  read-create
    STATUS      current
    DESCRIPTION
        "The value of tRPAdminGlobalVarAddressType specifies the actual IP
         address type of the tRPAdminGlobalVarAddress to which
         tRPAdminGlobalVarName is resolved.

         This object tRPAdminGlobalVarAddressType is ignored when the object
         tRPAdminGlobalVarType has a value different from address(3) or prefix
         (5)."
    DEFVAL      { unknown }
    ::= { tRPAdminGlobalVariableEntry 6 }

tRPAdminGlobalVarAddress         OBJECT-TYPE
    SYNTAX      InetAddress (SIZE (0|4|16|20))
    MAX-ACCESS  read-create
    STATUS      current
    DESCRIPTION
        "The value of tRPAdminGlobalVarAddress specifies e.g. the actual
         next-hop address to which tRPAdminGlobalVarName is resolved.

         This object tRPAdminGlobalVarAddress is ignored when the object
         tRPAdminGlobalVarType has a value different from address(3) or prefix
         (5)."
    DEFVAL      { ''H }
    ::= { tRPAdminGlobalVariableEntry 7 }

tRPAdminGlobalVarDecimal         OBJECT-TYPE
    SYNTAX      TPolicyDecimal
    MAX-ACCESS  read-create
    STATUS      current
    DESCRIPTION
        "The value of tRPAdminGlobalVarDecimal specifies the actual value in
         thousandths to which tRPAdminGlobalVarName is resolved.

         This object tRPAdminGlobalVarDecimal is ignored when the object
         tRPAdminGlobalVarType has a value different then decimal(4)."
    DEFVAL      { "0" }
    ::= { tRPAdminGlobalVariableEntry 8 }

tRPAdminGlobalVarPrefixLength    OBJECT-TYPE
    SYNTAX      InetAddressPrefixLength (0..128)
    MAX-ACCESS  read-create
    STATUS      current
    DESCRIPTION
        "The value of tRPAdminGlobalVarPrefixLength specifies the prefix length
         of the prefix to which tRPAdminGlobalVarName is resolved.

         This object tRPAdminGlobalVarPrefixLength is ignored when the object
         tRPAdminGlobalVarType has a value different from prefix (5)."
    DEFVAL      { 0 }
    ::= { tRPAdminGlobalVariableEntry 9 }

tRPAdminPSToCritPfxListTable     OBJECT-TYPE
    SYNTAX      SEQUENCE OF TRPAdminPSToCritPfxListEntry
    MAX-ACCESS  not-accessible
    STATUS      current
    DESCRIPTION
        "A table of prefix list names to match on as 'to' criteria for each
         policy statement entry."
    ::= { tRPAdminValueObjects 30 }

tRPAdminPSToCritPfxListEntry     OBJECT-TYPE
    SYNTAX      TRPAdminPSToCritPfxListEntry
    MAX-ACCESS  not-accessible
    STATUS      current
    DESCRIPTION
        "Information about policy statement entry to prefix list criteria..

         Entries are created or deleted when an entry in
         tRPAdminPSToCriteriaTable is created or deleted."
    AUGMENTS    { tRPAdminPSToCriteriaEntry }
    ::= { tRPAdminPSToCritPfxListTable 1 }

TRPAdminPSToCritPfxListEntry     ::= SEQUENCE
{
    tRPAdminPSToCritPrefixList1      TLPrefixListName,
    tRPAdminPSToCritPrefixList2      TLPrefixListName,
    tRPAdminPSToCritPrefixList3      TLPrefixListName,
    tRPAdminPSToCritPrefixList4      TLPrefixListName,
    tRPAdminPSToCritPrefixList5      TLPrefixListName,
    tRPAdminPSToCritPrefixList6      TLPrefixListName,
    tRPAdminPSToCritPrefixList7      TLPrefixListName,
    tRPAdminPSToCritPrefixList8      TLPrefixListName,
    tRPAdminPSToCritPrefixList9      TLPrefixListName,
    tRPAdminPSToCritPrefixList10     TLPrefixListName,
    tRPAdminPSToCritPrefixList11     TLPrefixListName,
    tRPAdminPSToCritPrefixList12     TLPrefixListName,
    tRPAdminPSToCritPrefixList13     TLPrefixListName,
    tRPAdminPSToCritPrefixList14     TLPrefixListName,
    tRPAdminPSToCritPrefixList15     TLPrefixListName,
    tRPAdminPSToCritPrefixList16     TLPrefixListName,
    tRPAdminPSToCritPrefixList17     TLPrefixListName,
    tRPAdminPSToCritPrefixList18     TLPrefixListName,
    tRPAdminPSToCritPrefixList19     TLPrefixListName,
    tRPAdminPSToCritPrefixList20     TLPrefixListName,
    tRPAdminPSToCritPrefixList21     TLPrefixListName,
    tRPAdminPSToCritPrefixList22     TLPrefixListName,
    tRPAdminPSToCritPrefixList23     TLPrefixListName,
    tRPAdminPSToCritPrefixList24     TLPrefixListName,
    tRPAdminPSToCritPrefixList25     TLPrefixListName,
    tRPAdminPSToCritPrefixList26     TLPrefixListName,
    tRPAdminPSToCritPrefixList27     TLPrefixListName,
    tRPAdminPSToCritPrefixList28     TLPrefixListName
}

tRPAdminPSToCritPrefixList1      OBJECT-TYPE
    SYNTAX      TLPrefixListName
    MAX-ACCESS  read-create
    STATUS      current
    DESCRIPTION
        "The value of tRPAdminPSToCritPrefixList1 indicates the name of the
         first prefix list to match on. Setting this value to an empty string
         disables this prefix list as a match criteria."
    DEFVAL      { "" }
    ::= { tRPAdminPSToCritPfxListEntry 1 }

tRPAdminPSToCritPrefixList2      OBJECT-TYPE
    SYNTAX      TLPrefixListName
    MAX-ACCESS  read-create
    STATUS      current
    DESCRIPTION
        "The value of tRPAdminPSToCritPrefixList2 indicates the name of the
         second prefix list to match on. Setting this value to an empty string
         disables this prefix list as a match criteria."
    DEFVAL      { "" }
    ::= { tRPAdminPSToCritPfxListEntry 2 }

tRPAdminPSToCritPrefixList3      OBJECT-TYPE
    SYNTAX      TLPrefixListName
    MAX-ACCESS  read-create
    STATUS      current
    DESCRIPTION
        "The value of tRPAdminPSToCritPrefixList3 indicates the name of the
         third prefix list to match on. Setting this value to an empty string
         disables this prefix list as a match criteria."
    DEFVAL      { "" }
    ::= { tRPAdminPSToCritPfxListEntry 3 }

tRPAdminPSToCritPrefixList4      OBJECT-TYPE
    SYNTAX      TLPrefixListName
    MAX-ACCESS  read-create
    STATUS      current
    DESCRIPTION
        "The value of tRPAdminPSToCritPrefixList4 indicates the name of the
         fourth prefix list to match on. Setting this value to an empty string
         disables this prefix list as a match criteria."
    DEFVAL      { "" }
    ::= { tRPAdminPSToCritPfxListEntry 4 }

tRPAdminPSToCritPrefixList5      OBJECT-TYPE
    SYNTAX      TLPrefixListName
    MAX-ACCESS  read-create
    STATUS      current
    DESCRIPTION
        "The value of tRPAdminPSToCritPrefixList5 indicates the name of the
         fifth prefix list to match on. Setting this value to an empty string
         disables this prefix list as a match criteria."
    DEFVAL      { "" }
    ::= { tRPAdminPSToCritPfxListEntry 5 }

tRPAdminPSToCritPrefixList6      OBJECT-TYPE
    SYNTAX      TLPrefixListName
    MAX-ACCESS  read-create
    STATUS      current
    DESCRIPTION
        "The value of tRPAdminPSToCritPrefixList6 indicates the name of the
         sixth prefix list to match on. Setting this value to an empty string
         disables this prefix list as a match criteria."
    DEFVAL      { "" }
    ::= { tRPAdminPSToCritPfxListEntry 6 }

tRPAdminPSToCritPrefixList7      OBJECT-TYPE
    SYNTAX      TLPrefixListName
    MAX-ACCESS  read-create
    STATUS      current
    DESCRIPTION
        "The value of tRPAdminPSToCritPrefixList7 indicates the name of the
         seventh prefix list to match on. Setting this value to an empty string
         disables this prefix list as a match criteria."
    DEFVAL      { "" }
    ::= { tRPAdminPSToCritPfxListEntry 7 }

tRPAdminPSToCritPrefixList8      OBJECT-TYPE
    SYNTAX      TLPrefixListName
    MAX-ACCESS  read-create
    STATUS      current
    DESCRIPTION
        "The value of tRPAdminPSToCritPrefixList8 indicates the name of the
         eight prefix list to match on. Setting this value to an empty string
         disables this prefix list as a match criteria."
    DEFVAL      { "" }
    ::= { tRPAdminPSToCritPfxListEntry 8 }

tRPAdminPSToCritPrefixList9      OBJECT-TYPE
    SYNTAX      TLPrefixListName
    MAX-ACCESS  read-create
    STATUS      current
    DESCRIPTION
        "The value of tRPAdminPSToCritPrefixList9 indicates the name of the
         ninth prefix list to match on. Setting this value to an empty string
         disables this prefix list as a match criteria."
    DEFVAL      { "" }
    ::= { tRPAdminPSToCritPfxListEntry 9 }

tRPAdminPSToCritPrefixList10     OBJECT-TYPE
    SYNTAX      TLPrefixListName
    MAX-ACCESS  read-create
    STATUS      current
    DESCRIPTION
        "The value of tRPAdminPSToCritPrefixList10 indicates the name of the
         10th prefix list to match on. Setting this value to an empty string
         disables this prefix list as a match criteria."
    DEFVAL      { "" }
    ::= { tRPAdminPSToCritPfxListEntry 10 }

tRPAdminPSToCritPrefixList11     OBJECT-TYPE
    SYNTAX      TLPrefixListName
    MAX-ACCESS  read-create
    STATUS      current
    DESCRIPTION
        "The value of tRPAdminPSToCritPrefixList11 indicates the name of the
         11th prefix list to match on. Setting this value to an empty string
         disables this prefix list as a match criteria."
    DEFVAL      { "" }
    ::= { tRPAdminPSToCritPfxListEntry 11 }

tRPAdminPSToCritPrefixList12     OBJECT-TYPE
    SYNTAX      TLPrefixListName
    MAX-ACCESS  read-create
    STATUS      current
    DESCRIPTION
        "The value of tRPAdminPSToCritPrefixList12 indicates the name of the
         12th prefix list to match on. Setting this value to an empty string
         disables this prefix list as a match criteria."
    DEFVAL      { "" }
    ::= { tRPAdminPSToCritPfxListEntry 12 }

tRPAdminPSToCritPrefixList13     OBJECT-TYPE
    SYNTAX      TLPrefixListName
    MAX-ACCESS  read-create
    STATUS      current
    DESCRIPTION
        "The value of tRPAdminPSToCritPrefixList13 indicates the name of the
         13th prefix list to match on. Setting this value to an empty string
         disables this prefix list as a match criteria."
    DEFVAL      { "" }
    ::= { tRPAdminPSToCritPfxListEntry 13 }

tRPAdminPSToCritPrefixList14     OBJECT-TYPE
    SYNTAX      TLPrefixListName
    MAX-ACCESS  read-create
    STATUS      current
    DESCRIPTION
        "The value of tRPAdminPSToCritPrefixList14 indicates the name of the
         14th prefix list to match on. Setting this value to an empty string
         disables this prefix list as a match criteria."
    DEFVAL      { "" }
    ::= { tRPAdminPSToCritPfxListEntry 14 }

tRPAdminPSToCritPrefixList15     OBJECT-TYPE
    SYNTAX      TLPrefixListName
    MAX-ACCESS  read-create
    STATUS      current
    DESCRIPTION
        "The value of tRPAdminPSToCritPrefixList15 indicates the name of the
         15th prefix list to match on. Setting this value to an empty string
         disables this prefix list as a match criteria."
    DEFVAL      { "" }
    ::= { tRPAdminPSToCritPfxListEntry 15 }

tRPAdminPSToCritPrefixList16     OBJECT-TYPE
    SYNTAX      TLPrefixListName
    MAX-ACCESS  read-create
    STATUS      current
    DESCRIPTION
        "The value of tRPAdminPSToCritPrefixList16 indicates the name of the
         16th prefix list to match on. Setting this value to an empty string
         disables this prefix list as a match criteria."
    DEFVAL      { "" }
    ::= { tRPAdminPSToCritPfxListEntry 16 }

tRPAdminPSToCritPrefixList17     OBJECT-TYPE
    SYNTAX      TLPrefixListName
    MAX-ACCESS  read-create
    STATUS      current
    DESCRIPTION
        "The value of tRPAdminPSToCritPrefixList17 indicates the name of the
         17th prefix list to match on. Setting this value to an empty string
         disables this prefix list as a match criteria."
    DEFVAL      { "" }
    ::= { tRPAdminPSToCritPfxListEntry 17 }

tRPAdminPSToCritPrefixList18     OBJECT-TYPE
    SYNTAX      TLPrefixListName
    MAX-ACCESS  read-create
    STATUS      current
    DESCRIPTION
        "The value of tRPAdminPSToCritPrefixList18 indicates the name of the
         18th prefix list to match on. Setting this value to an empty string
         disables this prefix list as a match criteria."
    DEFVAL      { "" }
    ::= { tRPAdminPSToCritPfxListEntry 18 }

tRPAdminPSToCritPrefixList19     OBJECT-TYPE
    SYNTAX      TLPrefixListName
    MAX-ACCESS  read-create
    STATUS      current
    DESCRIPTION
        "The value of tRPAdminPSToCritPrefixList19 indicates the name of the
         19th prefix list to match on. Setting this value to an empty string
         disables this prefix list as a match criteria."
    DEFVAL      { "" }
    ::= { tRPAdminPSToCritPfxListEntry 19 }

tRPAdminPSToCritPrefixList20     OBJECT-TYPE
    SYNTAX      TLPrefixListName
    MAX-ACCESS  read-create
    STATUS      current
    DESCRIPTION
        "The value of tRPAdminPSToCritPrefixList20 indicates the name of the
         20th prefix list to match on. Setting this value to an empty string
         disables this prefix list as a match criteria."
    DEFVAL      { "" }
    ::= { tRPAdminPSToCritPfxListEntry 20 }

tRPAdminPSToCritPrefixList21     OBJECT-TYPE
    SYNTAX      TLPrefixListName
    MAX-ACCESS  read-create
    STATUS      current
    DESCRIPTION
        "The value of tRPAdminPSToCritPrefixList21 indicates the name of the
         21th prefix list to match on. Setting this value to an empty string
         disables this prefix list as a match criteria."
    DEFVAL      { "" }
    ::= { tRPAdminPSToCritPfxListEntry 21 }

tRPAdminPSToCritPrefixList22     OBJECT-TYPE
    SYNTAX      TLPrefixListName
    MAX-ACCESS  read-create
    STATUS      current
    DESCRIPTION
        "The value of tRPAdminPSToCritPrefixList22 indicates the name of the
         22th prefix list to match on. Setting this value to an empty string
         disables this prefix list as a match criteria."
    DEFVAL      { "" }
    ::= { tRPAdminPSToCritPfxListEntry 22 }

tRPAdminPSToCritPrefixList23     OBJECT-TYPE
    SYNTAX      TLPrefixListName
    MAX-ACCESS  read-create
    STATUS      current
    DESCRIPTION
        "The value of tRPAdminPSToCritPrefixList23 indicates the name of the
         23th prefix list to match on. Setting this value to an empty string
         disables this prefix list as a match criteria."
    DEFVAL      { "" }
    ::= { tRPAdminPSToCritPfxListEntry 23 }

tRPAdminPSToCritPrefixList24     OBJECT-TYPE
    SYNTAX      TLPrefixListName
    MAX-ACCESS  read-create
    STATUS      current
    DESCRIPTION
        "The value of tRPAdminPSToCritPrefixList24 indicates the name of the
         24th prefix list to match on. Setting this value to an empty string
         disables this prefix list as a match criteria."
    DEFVAL      { "" }
    ::= { tRPAdminPSToCritPfxListEntry 24 }

tRPAdminPSToCritPrefixList25     OBJECT-TYPE
    SYNTAX      TLPrefixListName
    MAX-ACCESS  read-create
    STATUS      current
    DESCRIPTION
        "The value of tRPAdminPSToCritPrefixList25 indicates the name of the
         25th prefix list to match on. Setting this value to an empty string
         disables this prefix list as a match criteria."
    DEFVAL      { "" }
    ::= { tRPAdminPSToCritPfxListEntry 25 }

tRPAdminPSToCritPrefixList26     OBJECT-TYPE
    SYNTAX      TLPrefixListName
    MAX-ACCESS  read-create
    STATUS      current
    DESCRIPTION
        "The value of tRPAdminPSToCritPrefixList26 indicates the name of the
         26th prefix list to match on. Setting this value to an empty string
         disables this prefix list as a match criteria."
    DEFVAL      { "" }
    ::= { tRPAdminPSToCritPfxListEntry 26 }

tRPAdminPSToCritPrefixList27     OBJECT-TYPE
    SYNTAX      TLPrefixListName
    MAX-ACCESS  read-create
    STATUS      current
    DESCRIPTION
        "The value of tRPAdminPSToCritPrefixList27 indicates the name of the
         27th prefix list to match on. Setting this value to an empty string
         disables this prefix list as a match criteria."
    DEFVAL      { "" }
    ::= { tRPAdminPSToCritPfxListEntry 27 }

tRPAdminPSToCritPrefixList28     OBJECT-TYPE
    SYNTAX      TLPrefixListName
    MAX-ACCESS  read-create
    STATUS      current
    DESCRIPTION
        "The value of tRPAdminPSToCritPrefixList28 indicates the name of the
         28th prefix list to match on. Setting this value to an empty string
         disables this prefix list as a match criteria."
    DEFVAL      { "" }
    ::= { tRPAdminPSToCritPfxListEntry 28 }

tRPAdminPSFromCritPfxListTable   OBJECT-TYPE
    SYNTAX      SEQUENCE OF TRPAdminPSFromCritPfxListEntry
    MAX-ACCESS  not-accessible
    STATUS      current
    DESCRIPTION
        "A table of prefix list names to match on as 'from' criteria for each
         policy statement entry"
    ::= { tRPAdminValueObjects 44 }

tRPAdminPSFromCritPfxListEntry   OBJECT-TYPE
    SYNTAX      TRPAdminPSFromCritPfxListEntry
    MAX-ACCESS  not-accessible
    STATUS      current
    DESCRIPTION
        "Information about policy statement entry from prefix list criteria.

         Entries are created or deleted when an entry in
         tRPAdminPSFromCriteriaTable is created or deleted.

         The prefix list match condition is mutually exclusive with the  prefix
         list override match condition, i.e. no prefix list criteria  can be
         set if a prefix list override is set in
         tRPAdminPSFromCrPfxListOvrTable."
    AUGMENTS    { tRPAdminPSFromCriteriaEntry }
    ::= { tRPAdminPSFromCritPfxListTable 1 }

TRPAdminPSFromCritPfxListEntry   ::= SEQUENCE
{
    tRPAdminPSFromCritPrefixList1    TLPrefixListName,
    tRPAdminPSFromCritPrefixList2    TLPrefixListName,
    tRPAdminPSFromCritPrefixList3    TLPrefixListName,
    tRPAdminPSFromCritPrefixList4    TLPrefixListName,
    tRPAdminPSFromCritPrefixList5    TLPrefixListName,
    tRPAdminPSFromCritPrefixList6    TLPrefixListName,
    tRPAdminPSFromCritPrefixList7    TLPrefixListName,
    tRPAdminPSFromCritPrefixList8    TLPrefixListName,
    tRPAdminPSFromCritPrefixList9    TLPrefixListName,
    tRPAdminPSFromCritPrefixList10   TLPrefixListName,
    tRPAdminPSFromCritPrefixList11   TLPrefixListName,
    tRPAdminPSFromCritPrefixList12   TLPrefixListName,
    tRPAdminPSFromCritPrefixList13   TLPrefixListName,
    tRPAdminPSFromCritPrefixList14   TLPrefixListName,
    tRPAdminPSFromCritPrefixList15   TLPrefixListName,
    tRPAdminPSFromCritPrefixList16   TLPrefixListName,
    tRPAdminPSFromCritPrefixList17   TLPrefixListName,
    tRPAdminPSFromCritPrefixList18   TLPrefixListName,
    tRPAdminPSFromCritPrefixList19   TLPrefixListName,
    tRPAdminPSFromCritPrefixList20   TLPrefixListName,
    tRPAdminPSFromCritPrefixList21   TLPrefixListName,
    tRPAdminPSFromCritPrefixList22   TLPrefixListName,
    tRPAdminPSFromCritPrefixList23   TLPrefixListName,
    tRPAdminPSFromCritPrefixList24   TLPrefixListName,
    tRPAdminPSFromCritPrefixList25   TLPrefixListName,
    tRPAdminPSFromCritPrefixList26   TLPrefixListName,
    tRPAdminPSFromCritPrefixList27   TLPrefixListName,
    tRPAdminPSFromCritPrefixList28   TLPrefixListName
}

tRPAdminPSFromCritPrefixList1    OBJECT-TYPE
    SYNTAX      TLPrefixListName
    MAX-ACCESS  read-create
    STATUS      current
    DESCRIPTION
        "The value of tRPAdminPSFromCritPrefixList1 indicates the name of the
         first prefix list to match on. Setting this value to an empty string
         disables this prefix list as a match criteria."
    DEFVAL      { "" }
    ::= { tRPAdminPSFromCritPfxListEntry 1 }

tRPAdminPSFromCritPrefixList2    OBJECT-TYPE
    SYNTAX      TLPrefixListName
    MAX-ACCESS  read-create
    STATUS      current
    DESCRIPTION
        "The value of tRPAdminPSFromCritPrefixList2 indicates the name of the
         second prefix list to match on. Setting this value to an empty string
         disables this prefix list as a match criteria."
    DEFVAL      { "" }
    ::= { tRPAdminPSFromCritPfxListEntry 2 }

tRPAdminPSFromCritPrefixList3    OBJECT-TYPE
    SYNTAX      TLPrefixListName
    MAX-ACCESS  read-create
    STATUS      current
    DESCRIPTION
        "The value of tRPAdminPSFromCritPrefixList3 indicates the name of the
         third prefix list to match on. Setting this value to an empty string
         disables this prefix list as a match criteria."
    DEFVAL      { "" }
    ::= { tRPAdminPSFromCritPfxListEntry 3 }

tRPAdminPSFromCritPrefixList4    OBJECT-TYPE
    SYNTAX      TLPrefixListName
    MAX-ACCESS  read-create
    STATUS      current
    DESCRIPTION
        "The value of tRPAdminPSFromCritPrefixList4 indicates the name of the
         fourth prefix list to match on. Setting this value to an empty string
         disables this prefix list as a match criteria."
    DEFVAL      { "" }
    ::= { tRPAdminPSFromCritPfxListEntry 4 }

tRPAdminPSFromCritPrefixList5    OBJECT-TYPE
    SYNTAX      TLPrefixListName
    MAX-ACCESS  read-create
    STATUS      current
    DESCRIPTION
        "The value of tRPAdminPSFromCritPrefixList5 indicates the name of the
         fifth prefix list to match on. Setting this value to an empty string
         disables this prefix list as a match criteria."
    DEFVAL      { "" }
    ::= { tRPAdminPSFromCritPfxListEntry 5 }

tRPAdminPSFromCritPrefixList6    OBJECT-TYPE
    SYNTAX      TLPrefixListName
    MAX-ACCESS  read-create
    STATUS      current
    DESCRIPTION
        "The value of tRPAdminPSFromCritPrefixList6 indicates the name of the
         sixth prefix list to match on. Setting this value to an empty string
         disables this prefix list as a match criteria."
    DEFVAL      { "" }
    ::= { tRPAdminPSFromCritPfxListEntry 6 }

tRPAdminPSFromCritPrefixList7    OBJECT-TYPE
    SYNTAX      TLPrefixListName
    MAX-ACCESS  read-create
    STATUS      current
    DESCRIPTION
        "The value of tRPAdminPSFromCritPrefixList7 indicates the name of the
         seventh prefix list to match on. Setting this value to an empty string
         disables this prefix list as a match criteria."
    DEFVAL      { "" }
    ::= { tRPAdminPSFromCritPfxListEntry 7 }

tRPAdminPSFromCritPrefixList8    OBJECT-TYPE
    SYNTAX      TLPrefixListName
    MAX-ACCESS  read-create
    STATUS      current
    DESCRIPTION
        "The value of tRPAdminPSFromCritPrefixList8 indicates the name of the
         eight prefix list to match on. Setting this value to an empty string
         disables this prefix list as a match criteria."
    DEFVAL      { "" }
    ::= { tRPAdminPSFromCritPfxListEntry 8 }

tRPAdminPSFromCritPrefixList9    OBJECT-TYPE
    SYNTAX      TLPrefixListName
    MAX-ACCESS  read-create
    STATUS      current
    DESCRIPTION
        "The value of tRPAdminPSFromCritPrefixList9 indicates the name of the
         ninth prefix list to match on. Setting this value to an empty string
         disables this prefix list as a match criteria."
    DEFVAL      { "" }
    ::= { tRPAdminPSFromCritPfxListEntry 9 }

tRPAdminPSFromCritPrefixList10   OBJECT-TYPE
    SYNTAX      TLPrefixListName
    MAX-ACCESS  read-create
    STATUS      current
    DESCRIPTION
        "The value of tRPAdminPSFromCritPrefixList10 indicates the name of the
         10th prefix list to match on. Setting this value to an empty string
         disables this prefix list as a match criteria."
    DEFVAL      { "" }
    ::= { tRPAdminPSFromCritPfxListEntry 10 }

tRPAdminPSFromCritPrefixList11   OBJECT-TYPE
    SYNTAX      TLPrefixListName
    MAX-ACCESS  read-create
    STATUS      current
    DESCRIPTION
        "The value of tRPAdminPSFromCritPrefixList11 indicates the name of the
         11th prefix list to match on. Setting this value to an empty string
         disables this prefix list as a match criteria."
    DEFVAL      { "" }
    ::= { tRPAdminPSFromCritPfxListEntry 11 }

tRPAdminPSFromCritPrefixList12   OBJECT-TYPE
    SYNTAX      TLPrefixListName
    MAX-ACCESS  read-create
    STATUS      current
    DESCRIPTION
        "The value of tRPAdminPSFromCritPrefixList12 indicates the name of the
         12th prefix list to match on. Setting this value to an empty string
         disables this prefix list as a match criteria."
    DEFVAL      { "" }
    ::= { tRPAdminPSFromCritPfxListEntry 12 }

tRPAdminPSFromCritPrefixList13   OBJECT-TYPE
    SYNTAX      TLPrefixListName
    MAX-ACCESS  read-create
    STATUS      current
    DESCRIPTION
        "The value of tRPAdminPSFromCritPrefixList13 indicates the name of the
         13th prefix list to match on. Setting this value to an empty string
         disables this prefix list as a match criteria."
    DEFVAL      { "" }
    ::= { tRPAdminPSFromCritPfxListEntry 13 }

tRPAdminPSFromCritPrefixList14   OBJECT-TYPE
    SYNTAX      TLPrefixListName
    MAX-ACCESS  read-create
    STATUS      current
    DESCRIPTION
        "The value of tRPAdminPSFromCritPrefixList14 indicates the name of the
         14th prefix list to match on. Setting this value to an empty string
         disables this prefix list as a match criteria."
    DEFVAL      { "" }
    ::= { tRPAdminPSFromCritPfxListEntry 14 }

tRPAdminPSFromCritPrefixList15   OBJECT-TYPE
    SYNTAX      TLPrefixListName
    MAX-ACCESS  read-create
    STATUS      current
    DESCRIPTION
        "The value of tRPAdminPSFromCritPrefixList15 indicates the name of the
         15th prefix list to match on. Setting this value to an empty string
         disables this prefix list as a match criteria."
    DEFVAL      { "" }
    ::= { tRPAdminPSFromCritPfxListEntry 15 }

tRPAdminPSFromCritPrefixList16   OBJECT-TYPE
    SYNTAX      TLPrefixListName
    MAX-ACCESS  read-create
    STATUS      current
    DESCRIPTION
        "The value of tRPAdminPSFromCritPrefixList16 indicates the name of the
         16th prefix list to match on. Setting this value to an empty string
         disables this prefix list as a match criteria."
    DEFVAL      { "" }
    ::= { tRPAdminPSFromCritPfxListEntry 16 }

tRPAdminPSFromCritPrefixList17   OBJECT-TYPE
    SYNTAX      TLPrefixListName
    MAX-ACCESS  read-create
    STATUS      current
    DESCRIPTION
        "The value of tRPAdminPSFromCritPrefixList17 indicates the name of the
         17th prefix list to match on. Setting this value to an empty string
         disables this prefix list as a match criteria."
    DEFVAL      { "" }
    ::= { tRPAdminPSFromCritPfxListEntry 17 }

tRPAdminPSFromCritPrefixList18   OBJECT-TYPE
    SYNTAX      TLPrefixListName
    MAX-ACCESS  read-create
    STATUS      current
    DESCRIPTION
        "The value of tRPAdminPSFromCritPrefixList18 indicates the name of the
         18th prefix list to match on. Setting this value to an empty string
         disables this prefix list as a match criteria."
    DEFVAL      { "" }
    ::= { tRPAdminPSFromCritPfxListEntry 18 }

tRPAdminPSFromCritPrefixList19   OBJECT-TYPE
    SYNTAX      TLPrefixListName
    MAX-ACCESS  read-create
    STATUS      current
    DESCRIPTION
        "The value of tRPAdminPSFromCritPrefixList19 indicates the name of the
         19th prefix list to match on. Setting this value to an empty string
         disables this prefix list as a match criteria."
    DEFVAL      { "" }
    ::= { tRPAdminPSFromCritPfxListEntry 19 }

tRPAdminPSFromCritPrefixList20   OBJECT-TYPE
    SYNTAX      TLPrefixListName
    MAX-ACCESS  read-create
    STATUS      current
    DESCRIPTION
        "The value of tRPAdminPSFromCritPrefixList20 indicates the name of the
         20th prefix list to match on. Setting this value to an empty string
         disables this prefix list as a match criteria."
    DEFVAL      { "" }
    ::= { tRPAdminPSFromCritPfxListEntry 20 }

tRPAdminPSFromCritPrefixList21   OBJECT-TYPE
    SYNTAX      TLPrefixListName
    MAX-ACCESS  read-create
    STATUS      current
    DESCRIPTION
        "The value of tRPAdminPSFromCritPrefixList21 indicates the name of the
         21th prefix list to match on. Setting this value to an empty string
         disables this prefix list as a match criteria."
    DEFVAL      { "" }
    ::= { tRPAdminPSFromCritPfxListEntry 21 }

tRPAdminPSFromCritPrefixList22   OBJECT-TYPE
    SYNTAX      TLPrefixListName
    MAX-ACCESS  read-create
    STATUS      current
    DESCRIPTION
        "The value of tRPAdminPSFromCritPrefixList22 indicates the name of the
         22th prefix list to match on. Setting this value to an empty string
         disables this prefix list as a match criteria."
    DEFVAL      { "" }
    ::= { tRPAdminPSFromCritPfxListEntry 22 }

tRPAdminPSFromCritPrefixList23   OBJECT-TYPE
    SYNTAX      TLPrefixListName
    MAX-ACCESS  read-create
    STATUS      current
    DESCRIPTION
        "The value of tRPAdminPSFromCritPrefixList23 indicates the name of the
         23th prefix list to match on. Setting this value to an empty string
         disables this prefix list as a match criteria."
    DEFVAL      { "" }
    ::= { tRPAdminPSFromCritPfxListEntry 23 }

tRPAdminPSFromCritPrefixList24   OBJECT-TYPE
    SYNTAX      TLPrefixListName
    MAX-ACCESS  read-create
    STATUS      current
    DESCRIPTION
        "The value of tRPAdminPSFromCritPrefixList24 indicates the name of the
         24th prefix list to match on. Setting this value to an empty string
         disables this prefix list as a match criteria."
    DEFVAL      { "" }
    ::= { tRPAdminPSFromCritPfxListEntry 24 }

tRPAdminPSFromCritPrefixList25   OBJECT-TYPE
    SYNTAX      TLPrefixListName
    MAX-ACCESS  read-create
    STATUS      current
    DESCRIPTION
        "The value of tRPAdminPSFromCritPrefixList25 indicates the name of the
         25th prefix list to match on. Setting this value to an empty string
         disables this prefix list as a match criteria."
    DEFVAL      { "" }
    ::= { tRPAdminPSFromCritPfxListEntry 25 }

tRPAdminPSFromCritPrefixList26   OBJECT-TYPE
    SYNTAX      TLPrefixListName
    MAX-ACCESS  read-create
    STATUS      current
    DESCRIPTION
        "The value of tRPAdminPSFromCritPrefixList26 indicates the name of the
         26th prefix list to match on. Setting this value to an empty string
         disables this prefix list as a match criteria."
    DEFVAL      { "" }
    ::= { tRPAdminPSFromCritPfxListEntry 26 }

tRPAdminPSFromCritPrefixList27   OBJECT-TYPE
    SYNTAX      TLPrefixListName
    MAX-ACCESS  read-create
    STATUS      current
    DESCRIPTION
        "The value of tRPAdminPSFromCritPrefixList27 indicates the name of the
         27th prefix list to match on. Setting this value to an empty string
         disables this prefix list as a match criteria."
    DEFVAL      { "" }
    ::= { tRPAdminPSFromCritPfxListEntry 27 }

tRPAdminPSFromCritPrefixList28   OBJECT-TYPE
    SYNTAX      TLPrefixListName
    MAX-ACCESS  read-create
    STATUS      current
    DESCRIPTION
        "The value of tRPAdminPSFromCritPrefixList28 indicates the name of the
         28th prefix list to match on. Setting this value to an empty string
         disables this prefix list as a match criteria."
    DEFVAL      { "" }
    ::= { tRPAdminPSFromCritPfxListEntry 28 }

tRPAdminPfxListToTable           OBJECT-TYPE
    SYNTAX      SEQUENCE OF TRPAdminPfxListToEntry
    MAX-ACCESS  not-accessible
    STATUS      current
    DESCRIPTION
        "The table of IPv4 and IPv6 admin prefix lists specifying a match
         condition from a start prefix/length to an end prefix/length."
    ::= { tRPAdminValueObjects 45 }

tRPAdminPfxListToEntry           OBJECT-TYPE
    SYNTAX      TRPAdminPfxListToEntry
    MAX-ACCESS  not-accessible
    STATUS      current
    DESCRIPTION
        "Each row entry in the tRPAdminPfxListToEntry represents information
         about a particular prefix list to prefix.

         A route's prefix/length is considered a match if all of the
         following are true:
         - the begin prefix-length most-significant bits of the route
           matches the begin prefix
         - the end prefix-length most-significant bits of the route
           matches the end prefix
         - the prefix-length of the route is between begin prefix-length and
           end prefix-length (inclusive).

         Entries are created and deleted by the user."
    INDEX       {
        tRPAdminPfxListName,
        tRPAdminInetPrefixListPrefixType,
        tRPAdminInetPrefixListPrefix,
        tRPAdminInetPrefixListPrefixLen,
        tRPAdminPfxListToEndPrefixType,
        tRPAdminPfxListToEndPrefix,
        tRPAdminPfxListToEndPrefixLen
    }
    ::= { tRPAdminPfxListToTable 1 }

TRPAdminPfxListToEntry           ::= SEQUENCE
{
    tRPAdminPfxListToEndPrefixType   TmnxAddressAndPrefixType,
    tRPAdminPfxListToEndPrefix       TmnxAddressAndPrefixAddress,
    tRPAdminPfxListToEndPrefixLen    TmnxAddressAndPrefixPrefix,
    tRPAdminPfxListToRowStatus       RowStatus,
    tRPAdminPfxListToCrOrigin        TmnxCreateOrigin
}

tRPAdminPfxListToEndPrefixType   OBJECT-TYPE
    SYNTAX      TmnxAddressAndPrefixType
    MAX-ACCESS  not-accessible
    STATUS      current
    DESCRIPTION
        "The value of tRPAdminPfxListToEndPrefixType indicates the address type
         of tRPAdminPfxListToEndPrefix."
    ::= { tRPAdminPfxListToEntry 1 }

tRPAdminPfxListToEndPrefix       OBJECT-TYPE
    SYNTAX      TmnxAddressAndPrefixAddress (SIZE (4|16))
    MAX-ACCESS  not-accessible
    STATUS      current
    DESCRIPTION
        "The value of tRPAdminPfxListToEndPrefix indicates the end IP prefix of
         the prefix list entry."
    ::= { tRPAdminPfxListToEntry 2 }

tRPAdminPfxListToEndPrefixLen    OBJECT-TYPE
    SYNTAX      TmnxAddressAndPrefixPrefix
    MAX-ACCESS  not-accessible
    STATUS      current
    DESCRIPTION
        "The value of tRPAdminPfxListToEndPrefixLen indicates the end IP prefix
         length of the prefix list entry."
    ::= { tRPAdminPfxListToEntry 3 }

tRPAdminPfxListToRowStatus       OBJECT-TYPE
    SYNTAX      RowStatus
    MAX-ACCESS  read-create
    STATUS      current
    DESCRIPTION
        "The value of tRPAdminPfxListToRowStatus specifies the RowStatus for
         this row.

         To create a row, set this object to createAndGo(4). When
         tRPAdminControlApply is set to commit(3), the row will actually be
         created in the tRPOperPfxListToTable.

         To destroy a row, set this object to destroy(6). When
         tRPAdminControlApply is set to commit(3) the row will actually be
         removed from the tRPOperPfxListToTable."
    ::= { tRPAdminPfxListToEntry 4 }

tRPAdminPfxListToCrOrigin        OBJECT-TYPE
    SYNTAX      TmnxCreateOrigin
    MAX-ACCESS  read-only
    STATUS      current
    DESCRIPTION
        "The value of the object tRPAdminPfxListToCrOrigin indicates the
         mechanism used to create this entry."
    ::= { tRPAdminPfxListToEntry 5 }

tRPAdminPfxListAddressMaskTable  OBJECT-TYPE
    SYNTAX      SEQUENCE OF TRPAdminPfxListAddressMaskEntry
    MAX-ACCESS  not-accessible
    STATUS      current
    DESCRIPTION
        "The table of admin prefix lists specifying a match condition that does
         not require contiguous network mask bits."
    ::= { tRPAdminValueObjects 46 }

tRPAdminPfxListAddressMaskEntry  OBJECT-TYPE
    SYNTAX      TRPAdminPfxListAddressMaskEntry
    MAX-ACCESS  not-accessible
    STATUS      current
    DESCRIPTION
        "Each row entry in the tRPAdminPfxListAddressMaskEntry represents
         information about a particular prefix list address mask.

         A route's prefix/length is considered a match if all of the
         following are true:
         - the bitwise logical AND of the prefix-list address and the mask
           equals the bitwise logical AND of the route address and the mask
         - the prefix length of the route matches the prefix length of
           the prefix-list entry

         Entries are created and deleted by the user."
    INDEX       {
        tRPAdminPfxListName,
        tRPAdminInetPrefixListPrefixType,
        tRPAdminInetPrefixListPrefix,
        tRPAdminInetPrefixListPrefixLen,
        tRPAdminPfxListAddressMaskType,
        tRPAdminPfxListAddressMask
    }
    ::= { tRPAdminPfxListAddressMaskTable 1 }

TRPAdminPfxListAddressMaskEntry  ::= SEQUENCE
{
    tRPAdminPfxListAddressMaskType   InetAddressType,
    tRPAdminPfxListAddressMask       InetAddress,
    tRPAdminPfxListAddrMaskRowStatus RowStatus,
    tRPAdminPfxListAddrMaskCrOrigin  TmnxCreateOrigin
}

tRPAdminPfxListAddressMaskType   OBJECT-TYPE
    SYNTAX      InetAddressType
    MAX-ACCESS  not-accessible
    STATUS      current
    DESCRIPTION
        "The value of tRPAdminPfxListAddressMaskType specifies the address type
         of tRPAdminPfxListAddressMask."
    ::= { tRPAdminPfxListAddressMaskEntry 1 }

tRPAdminPfxListAddressMask       OBJECT-TYPE
    SYNTAX      InetAddress (SIZE (4|16))
    MAX-ACCESS  not-accessible
    STATUS      current
    DESCRIPTION
        "The value of tRPAdminPfxListAddressMask specifies the address mask of
         the prefix list entry.

         The address type is specified by tRPAdminInetPrefixListPrefixType."
    ::= { tRPAdminPfxListAddressMaskEntry 2 }

tRPAdminPfxListAddrMaskRowStatus OBJECT-TYPE
    SYNTAX      RowStatus
    MAX-ACCESS  read-create
    STATUS      current
    DESCRIPTION
        "The value of the object tRPAdminPfxListAddrMaskRowStatus  specifies
         the RowStatus for this row.

         To create a row, set this object to createAndGo(4). When
         tRPAdminControlApply is set to commit(3), the row will actually be
         created in the tRPOperPfxListAddressMaskTable.

         To destroy a row, set this object to destroy(6). When
         tRPAdminControlApply is set to commit(3) the row will actually be
         removed from the tRPOperPfxListAddressMaskTable."
    ::= { tRPAdminPfxListAddressMaskEntry 3 }

tRPAdminPfxListAddrMaskCrOrigin  OBJECT-TYPE
    SYNTAX      TmnxCreateOrigin
    MAX-ACCESS  read-only
    STATUS      current
    DESCRIPTION
        "The value of the object tRPAdminPfxListAddrMaskCrOrigin  indicates the
         mechanism used to create this entry."
    ::= { tRPAdminPfxListAddressMaskEntry 4 }

tRPAdminPSFromCritInterfaceTable OBJECT-TYPE
    SYNTAX      SEQUENCE OF TRPAdminPSFromCritInterfaceEntry
    MAX-ACCESS  not-accessible
    STATUS      current
    DESCRIPTION
        "A table of interface subnets to match on as 'from' criteria for each
         policy statement entry"
    ::= { tRPAdminValueObjects 47 }

tRPAdminPSFromCritInterfaceEntry OBJECT-TYPE
    SYNTAX      TRPAdminPSFromCritInterfaceEntry
    MAX-ACCESS  not-accessible
    STATUS      current
    DESCRIPTION
        "Information about policy statement entry from interface subnet
         criteria. Entries are created or deleted when an entry in
         tRPAdminPSFromCriteriaTable is created or deleted."
    AUGMENTS    { tRPAdminPSFromCriteriaEntry }
    ::= { tRPAdminPSFromCritInterfaceTable 1 }

TRPAdminPSFromCritInterfaceEntry ::= SEQUENCE
{
    tRPAdminPSFromCritIntfServiceId  TNamedItemOrEmpty,
    tRPAdminPSFromCritInterface1     TNamedItemOrEmpty,
    tRPAdminPSFromCritInterface2     TNamedItemOrEmpty,
    tRPAdminPSFromCritInterface3     TNamedItemOrEmpty,
    tRPAdminPSFromCritInterface4     TNamedItemOrEmpty,
    tRPAdminPSFromCritInterface5     TNamedItemOrEmpty,
    tRPAdminPSFromCritInterface6     TNamedItemOrEmpty,
    tRPAdminPSFromCritInterface7     TNamedItemOrEmpty,
    tRPAdminPSFromCritInterface8     TNamedItemOrEmpty,
    tRPAdminPSFromCritInterface9     TNamedItemOrEmpty,
    tRPAdminPSFromCritInterface10    TNamedItemOrEmpty
}

tRPAdminPSFromCritIntfServiceId  OBJECT-TYPE
    SYNTAX      TNamedItemOrEmpty
    MAX-ACCESS  read-create
    STATUS      current
    DESCRIPTION
        "The value of tRPAdminPSFromCritIntfServiceId specifies the
         service ID of the interface subnets to match on.

         The value of this object can be a string containing the service ID
         value. An empty string means that no service ID is configured.

         If interface subnets are configured without service ID,
         it is assumed they belong to the BASE routing instance."
    DEFVAL      { ''H }
    ::= { tRPAdminPSFromCritInterfaceEntry 1 }

tRPAdminPSFromCritInterface1     OBJECT-TYPE
    SYNTAX      TNamedItemOrEmpty
    MAX-ACCESS  read-create
    STATUS      current
    DESCRIPTION
        "The value of tRPAdminPSFromCritInterface1 specifies the name of the
         first interface to match on. Setting this value to an empty string
         disables this interface as a match criteria."
    DEFVAL      { ''H }
    ::= { tRPAdminPSFromCritInterfaceEntry 2 }

tRPAdminPSFromCritInterface2     OBJECT-TYPE
    SYNTAX      TNamedItemOrEmpty
    MAX-ACCESS  read-create
    STATUS      current
    DESCRIPTION
        "The value of tRPAdminPSFromCritInterface2 specifies the name of the
         second interface to match on. Setting this value to an empty string
         disables this interface as a match criteria."
    DEFVAL      { ''H }
    ::= { tRPAdminPSFromCritInterfaceEntry 3 }

tRPAdminPSFromCritInterface3     OBJECT-TYPE
    SYNTAX      TNamedItemOrEmpty
    MAX-ACCESS  read-create
    STATUS      current
    DESCRIPTION
        "The value of tRPAdminPSFromCritInterface3 specifies the name of the
         third interface to match on. Setting this value to an empty string
         disables this interface as a match criteria."
    DEFVAL      { ''H }
    ::= { tRPAdminPSFromCritInterfaceEntry 4 }

tRPAdminPSFromCritInterface4     OBJECT-TYPE
    SYNTAX      TNamedItemOrEmpty
    MAX-ACCESS  read-create
    STATUS      current
    DESCRIPTION
        "The value of tRPAdminPSFromCritInterface4 specifies the name of the
         fourth interface to match on. Setting this value to an empty string
         disables this interface as a match criteria."
    DEFVAL      { ''H }
    ::= { tRPAdminPSFromCritInterfaceEntry 5 }

tRPAdminPSFromCritInterface5     OBJECT-TYPE
    SYNTAX      TNamedItemOrEmpty
    MAX-ACCESS  read-create
    STATUS      current
    DESCRIPTION
        "The value of tRPAdminPSFromCritInterface5 specifies the name of the
         fifth interface to match on. Setting this value to an empty string
         disables this interface as a match criteria."
    DEFVAL      { ''H }
    ::= { tRPAdminPSFromCritInterfaceEntry 6 }

tRPAdminPSFromCritInterface6     OBJECT-TYPE
    SYNTAX      TNamedItemOrEmpty
    MAX-ACCESS  read-create
    STATUS      current
    DESCRIPTION
        "The value of tRPAdminPSFromCritInterface6 specifies the name of the
         sixth interface to match on. Setting this value to an empty string
         disables this interface as a match criteria."
    DEFVAL      { ''H }
    ::= { tRPAdminPSFromCritInterfaceEntry 7 }

tRPAdminPSFromCritInterface7     OBJECT-TYPE
    SYNTAX      TNamedItemOrEmpty
    MAX-ACCESS  read-create
    STATUS      current
    DESCRIPTION
        "The value of tRPAdminPSFromCritInterface7 specifies the name of the
         seventh interface to match on. Setting this value to an empty string
         disables this interface as a match criteria."
    DEFVAL      { ''H }
    ::= { tRPAdminPSFromCritInterfaceEntry 8 }

tRPAdminPSFromCritInterface8     OBJECT-TYPE
    SYNTAX      TNamedItemOrEmpty
    MAX-ACCESS  read-create
    STATUS      current
    DESCRIPTION
        "The value of tRPAdminPSFromCritInterface8 specifies the name of the
         eight interface to match on. Setting this value to an empty string
         disables this interface as a match criteria."
    DEFVAL      { ''H }
    ::= { tRPAdminPSFromCritInterfaceEntry 9 }

tRPAdminPSFromCritInterface9     OBJECT-TYPE
    SYNTAX      TNamedItemOrEmpty
    MAX-ACCESS  read-create
    STATUS      current
    DESCRIPTION
        "The value of tRPAdminPSFromCritInterface9 specifies the name of the
         9th interface to match on. Setting this value to an empty string
         disables this interface as a match criteria."
    DEFVAL      { ''H }
    ::= { tRPAdminPSFromCritInterfaceEntry 10 }

tRPAdminPSFromCritInterface10    OBJECT-TYPE
    SYNTAX      TNamedItemOrEmpty
    MAX-ACCESS  read-create
    STATUS      current
    DESCRIPTION
        "The value of tRPAdminPSFromCritInterface10 specifies the name of the
         10th interface to match on. Setting this value to an empty string
         disables this interface as a match criteria."
    DEFVAL      { ''H }
    ::= { tRPAdminPSFromCritInterfaceEntry 11 }

tRPAdminRDListTable              OBJECT-TYPE
    SYNTAX      SEQUENCE OF TRPAdminRDListEntry
    MAX-ACCESS  not-accessible
    STATUS      current
    DESCRIPTION
        "The table contains the admin information pertaining to  a route
         distinguisher (RD) list."
    ::= { tRPAdminValueObjects 48 }

tRPAdminRDListEntry              OBJECT-TYPE
    SYNTAX      TRPAdminRDListEntry
    MAX-ACCESS  not-accessible
    STATUS      current
    DESCRIPTION
        "Each conceptual row represents a particular route distinguisher (RD)
         list.

         Rows in the table are created and destroyed by SNMP Set operations on
         the object tRPAdminRDListRowStatus."
    INDEX       { tRPAdminRDListName }
    ::= { tRPAdminRDListTable 1 }

TRPAdminRDListEntry              ::= SEQUENCE
{
    tRPAdminRDListName               TRouteDistinguisherListName,
    tRPAdminRDListRowStatus          RowStatus,
    tRPAdminRDListCrOrigin           TmnxCreateOrigin
}

tRPAdminRDListName               OBJECT-TYPE
    SYNTAX      TRouteDistinguisherListName (SIZE (1..64))
    MAX-ACCESS  not-accessible
    STATUS      current
    DESCRIPTION
        "The value of tRPAdminRDListName indicates the name of  the route
         distinguisher (RD) list entry."
    ::= { tRPAdminRDListEntry 1 }

tRPAdminRDListRowStatus          OBJECT-TYPE
    SYNTAX      RowStatus
    MAX-ACCESS  read-create
    STATUS      current
    DESCRIPTION
        "RowStatus for this row.

         To create a row, set this object to createAndGo(4). When
         tRPAdminControlApply is set to commit(3), the row will actually be
         created in the tRPOperRDListTable.

         To destroy a row, set this object to destroy(6). When
         tRPAdminControlApply is set to commit(3) the row will actually be
         removed from the tRPOperRDListTable."
    ::= { tRPAdminRDListEntry 2 }

tRPAdminRDListCrOrigin           OBJECT-TYPE
    SYNTAX      TmnxCreateOrigin
    MAX-ACCESS  read-only
    STATUS      current
    DESCRIPTION
        "The value of the object tRPAdminRDListCrOrigin indicates the mechanism
         used to create this entry."
    ::= { tRPAdminRDListEntry 3 }

tRPAdminRouteDistinguisherTable  OBJECT-TYPE
    SYNTAX      SEQUENCE OF TRPAdminRouteDistinguisherEntry
    MAX-ACCESS  not-accessible
    STATUS      current
    DESCRIPTION
        "The table contains the information pertaining to  a route
         distinguisher (RD) in a RD list."
    ::= { tRPAdminValueObjects 49 }

tRPAdminRouteDistinguisherEntry  OBJECT-TYPE
    SYNTAX      TRPAdminRouteDistinguisherEntry
    MAX-ACCESS  not-accessible
    STATUS      current
    DESCRIPTION
        "Each conceptual row represents a particular route distinguisher (RD)
         in the RD list.

         Rows in the table are created and destroyed by SNMP Set operations on
         the object tRPAdminRDRowStatus."
    INDEX       {
        tRPAdminRDListName,
        tRPAdminRouteDistinguisher
    }
    ::= { tRPAdminRouteDistinguisherTable 1 }

TRPAdminRouteDistinguisherEntry  ::= SEQUENCE
{
    tRPAdminRouteDistinguisher       TPolicyRouteDistinguisher,
    tRPAdminRDRowStatus              RowStatus,
    tRPAdminRDCrOrigin               TmnxCreateOrigin
}

tRPAdminRouteDistinguisher       OBJECT-TYPE
    SYNTAX      TPolicyRouteDistinguisher
    MAX-ACCESS  not-accessible
    STATUS      current
    DESCRIPTION
        "The value of tRPAdminRouteDistinguisher indicates the route
         distinguisher of the RD list entry."
    ::= { tRPAdminRouteDistinguisherEntry 1 }

tRPAdminRDRowStatus              OBJECT-TYPE
    SYNTAX      RowStatus
    MAX-ACCESS  read-create
    STATUS      current
    DESCRIPTION
        "RowStatus for this row.

         To create a row, set this object to createAndGo(4). When
         tRPAdminControlApply is set to commit(3), the row will actually be
         created in the tRPOperRouteDistinguisherTable.

         To destroy a row, set this object to destroy(6). When
         tRPAdminControlApply is set to commit(3) the row will actually be
         removed from the tRPOperRouteDistinguisherTable."
    ::= { tRPAdminRouteDistinguisherEntry 2 }

tRPAdminRDCrOrigin               OBJECT-TYPE
    SYNTAX      TmnxCreateOrigin
    MAX-ACCESS  read-only
    STATUS      current
    DESCRIPTION
        "The value of the object tRPAdminRDCrOrigin indicates the mechanism
         used to create this entry."
    ::= { tRPAdminRouteDistinguisherEntry 3 }

tRPAdminPSFromCrPfxListOvrTable  OBJECT-TYPE
    SYNTAX      SEQUENCE OF TRPAdminPSFromCrPfxListOvrEntry
    MAX-ACCESS  not-accessible
    STATUS      current
    DESCRIPTION
        "The table contains the information pertaining to  a prefix-list
         override to match on as 'from' criteria for each policy statement
         entry."
    ::= { tRPAdminValueObjects 50 }

tRPAdminPSFromCrPfxListOvrEntry  OBJECT-TYPE
    SYNTAX      TRPAdminPSFromCrPfxListOvrEntry
    MAX-ACCESS  not-accessible
    STATUS      current
    DESCRIPTION
        "Each conceptual row represents a particular prefix list override match
         criteria.

         Rows in the table are created and destroyed by SNMP Set operations on
         the object tRPAdminPSFromCrPLOvrRowStatus.

         Only 1 prefix-list override is supported per match condition entry."
    INDEX       {
        tRPAdminPolicyStatementName,
        tRPAdminPSFromCriteriaIndex,
        tRPAdminPSFromCrPLOvrPfxListName
    }
    ::= { tRPAdminPSFromCrPfxListOvrTable 1 }

TRPAdminPSFromCrPfxListOvrEntry  ::= SEQUENCE
{
    tRPAdminPSFromCrPLOvrPfxListName TLPrefixListName,
    tRPAdminPSFromCrPLOvrRowStatus   RowStatus,
    tRPAdminPSFromCrPLOvrType        INTEGER,
    tRPAdminPSFromCrPLOvrCrOrigin    TmnxCreateOrigin,
    tRPAdminPSFromCrPLOvrThroughLen  InetAddressPrefixLength,
    tRPAdminPSFromCrPLOvrBeginLen    InetAddressPrefixLength
}

tRPAdminPSFromCrPLOvrPfxListName OBJECT-TYPE
    SYNTAX      TLPrefixListName (SIZE (1..64))
    MAX-ACCESS  not-accessible
    STATUS      current
    DESCRIPTION
        "The value of tRPAdminPSFromCrPLOvrPfxListName specifies the name of
         the prefix-list from which the type must be overridden to match the
         route on.

         The value of this object can be a string containing the name of the
         prefix-list or a variable name that needs to be resolved to get the
         name of the prefix-list. The prefix-list name must exist in
         tRPAdminPfxListNameTable.

         The prefix list override match condition is mutually exclusive with
         the prefix list match condition, i.e. no prefix list can be
         overridden if a prefix list is set in tRPAdminPSFromCritPfxListTable."
    ::= { tRPAdminPSFromCrPfxListOvrEntry 1 }

tRPAdminPSFromCrPLOvrRowStatus   OBJECT-TYPE
    SYNTAX      RowStatus
    MAX-ACCESS  read-create
    STATUS      current
    DESCRIPTION
        "The value of tRPAdminPSFromCrPLOvrRowStatus specifies the RowStatus
         for this row.

         To create a row, set this object to createAndGo(4). When
         tRPAdminControlApply is set to commit(3), the row will actually be
         created in the tRPOperPSFromCrPfxListOvrTable.

         To destroy a row, set this object to destroy(6). When
         tRPAdminControlApply is set to commit(3) the row will actually be
         removed from the tRPOperPSFromCrPfxListOvrTable."
    ::= { tRPAdminPSFromCrPfxListOvrEntry 2 }

tRPAdminPSFromCrPLOvrType        OBJECT-TYPE
    SYNTAX      INTEGER {
        exact   (1),
        longer  (2),
        through (3),
        range   (4)
    }
    MAX-ACCESS  read-create
    STATUS      current
    DESCRIPTION
        "The value of tRPAdminPSFromCrPLOvrType specifies the prefix-list
         override type to match the route on.

         exact (1) - a route's prefix/length must match the prefix list entry
         exactly in order for an entry to be considered a match.

         longer (2) - a route's prefix/length must match the defined prefix AND
         have a length that is an exact match or longer in order for an entry
         to be considered a match.

         through (3) - a route's prefix/length must match the defined prefix
         AND have a length that is an exact match or longer up to and including
         the defined maximum length  tRPAdminPSFromCrPLOvrThroughLen in order
         for an entry to be considered a match.

         range (4) - a route's prefix/length must match the defined prefix AND
         have a length that is greater than or equal to the length defined by
         tRPAdminPSFromCrPLOvrBeginLen and less than or equal to the length
         defined by tRPAdminPSFromCrPLOvrThroughLen in order for an entry to be
         considered a match."
    DEFVAL      { exact }
    ::= { tRPAdminPSFromCrPfxListOvrEntry 3 }

tRPAdminPSFromCrPLOvrCrOrigin    OBJECT-TYPE
    SYNTAX      TmnxCreateOrigin
    MAX-ACCESS  read-only
    STATUS      current
    DESCRIPTION
        "The value of the object tRPAdminPSFromCrPLOvrCrOrigin indicates the
         mechanism used to create this entry."
    ::= { tRPAdminPSFromCrPfxListOvrEntry 4 }

tRPAdminPSFromCrPLOvrThroughLen  OBJECT-TYPE
    SYNTAX      InetAddressPrefixLength
    MAX-ACCESS  read-create
    STATUS      current
    DESCRIPTION
        "The value of tRPAdminPSFromCrPLOvrThroughLen specifies the maximum
         mask length to use when tRPAdminPSFromCrPLOvrType is set to
         'through(3)' or 'range(4)'.

         The mask length must be larger than the corresponding
         tRPAdminPrefixListMask from the prefix-list."
    DEFVAL      { 0 }
    ::= { tRPAdminPSFromCrPfxListOvrEntry 5 }

tRPAdminPSFromCrPLOvrBeginLen    OBJECT-TYPE
    SYNTAX      InetAddressPrefixLength
    MAX-ACCESS  read-create
    STATUS      current
    DESCRIPTION
        "The value of tRPAdminPSFromCrPLOvrBeginLen specifies the mask length
         to use as the lower limit for the mask range when
         tRPAdminPSFromCrPLOvrType is set to 'range(4)'.

         The mask length must be larger than the corresponding
         tRPAdminPrefixListMask and less than tRPAdminPSFromCrPLOvrThroughLen."
    DEFVAL      { 0 }
    ::= { tRPAdminPSFromCrPfxListOvrEntry 6 }

tmnxRoutePolicyConformance       OBJECT IDENTIFIER ::= { tmnxSRConfs 17 }

tmnxRoutePolicyCompliances       OBJECT IDENTIFIER ::= { tmnxRoutePolicyConformance 1 }

tmnxRoutePolicy7450V4v0Compliance MODULE-COMPLIANCE
    STATUS      obsolete
    DESCRIPTION
        "The compliance statement supporting management of Route Policies on
         Nokia 7450 ESS series systems 4.0 release."
    MODULE
        MANDATORY-GROUPS {
            tmnxRPAdminControlObjectsGroup,
            tmnxRPPolicyObjectsV4v0Group,
            tmnxRPPolicyEntryObjectsV4v0Group
        }
    ::= { tmnxRoutePolicyCompliances 3 }

tmnxRoutePolicy7750V4v0Compliance MODULE-COMPLIANCE
    STATUS      obsolete
    DESCRIPTION
        "The compliance statement supporting management of Route Policies on
         Nokia 7750 SR series systems 4.0 release."
    MODULE
        MANDATORY-GROUPS {
            tmnxRPAdminControlObjectsGroup,
            tmnxRPASPathObjectsGroup,
            tmnxRPCommunityObjectsGroup,
            tmnxRPDampingObjectsGroup,
            tmnxRPPrefixListObjectsGroup,
            tmnxRPPolicyObjectsV4v0Group,
            tmnxRPPolicyEntryObjectsV4v0Group,
            tmnxRPInetPrefixListObjectsGroup
        }
    ::= { tmnxRoutePolicyCompliances 4 }

tmnxRoutePolicy7450V5v0Compliance MODULE-COMPLIANCE
    STATUS      obsolete
    DESCRIPTION
        "The compliance statement supporting management of Route Policies on
         Nokia 7450 ESS series systems 5.0 release."
    MODULE
        MANDATORY-GROUPS {
            tmnxRPAdminControlObjectsGroup,
            tmnxRPPolicyObjectsV5v0Group,
            tmnxRPPolicyEntryObjectsV5v0Group,
            tmnxRPPolicyObsoleteV5v0Group
        }
    ::= { tmnxRoutePolicyCompliances 5 }

tmnxRoutePolicy7750V5v0Compliance MODULE-COMPLIANCE
    STATUS      obsolete
    DESCRIPTION
        "The compliance statement supporting management of Route Policies on
         Nokia 7750 SR series systems 5.0 release."
    MODULE
        MANDATORY-GROUPS {
            tmnxRPAdminControlObjectsGroup,
            tmnxRPASPathObjectsV5v0Group,
            tmnxRPCommunityObjectsV5v0Group,
            tmnxRPDampingObjectsV5v0Group,
            tmnxRPPrefixListObjectsV5v0Group,
            tmnxRPPolicyObjectsV5v0Group,
            tmnxRPPolicyEntryObjectsV5v0Group,
            tmnxRPInetPrefixListObjectsV5v0Group,
            tmnxRPPolicyObsoleteV5v0Group
        }
    ::= { tmnxRoutePolicyCompliances 6 }

tmnxRoutePolicy7450V7v0Compliance MODULE-COMPLIANCE
    STATUS      obsolete
    DESCRIPTION
        "The compliance statement supporting management of Route Policies on
         Nokia 7450 ESS series systems 5.0 release."
    MODULE
        MANDATORY-GROUPS {
            tmnxRPAdminControlObjectsGroup,
            tmnxRPPolicyObsoleteV5v0Group,
            tmnxRPPolicyObjectsV7v0Group,
            tmnxRPPolicyEntryObjectsV7v0Group,
            tmnxRPPolicyObsoleteV7v0Group
        }
    ::= { tmnxRoutePolicyCompliances 7 }

tmnxRoutePolicy7750V7v0Compliance MODULE-COMPLIANCE
    STATUS      obsolete
    DESCRIPTION
        "The compliance statement supporting management of Route Policies on
         Nokia 7750 SR series systems 5.0 release."
    MODULE
        MANDATORY-GROUPS {
            tmnxRPAdminControlObjectsGroup,
            tmnxRPASPathObjectsV5v0Group,
            tmnxRPCommunityObjectsV5v0Group,
            tmnxRPDampingObjectsV5v0Group,
            tmnxRPPrefixListObjectsV5v0Group,
            tmnxRPInetPrefixListObjectsV5v0Group,
            tmnxRPPolicyObsoleteV5v0Group,
            tmnxRPPolicyObjectsV7v0Group,
            tmnxRPPolicyEntryObjectsV7v0Group,
            tmnxRPPolicyObsoleteV7v0Group
        }
    ::= { tmnxRoutePolicyCompliances 8 }

tmnxRoutePolicy7450V8v0Compliance MODULE-COMPLIANCE
    STATUS      obsolete
    DESCRIPTION
        "The compliance statement supporting management of Route Policies on
         Nokia 7450 ESS series systems 5.0 release."
    MODULE
        MANDATORY-GROUPS {
            tmnxRPAdminControlObjectsGroup,
            tmnxRPPolicyObsoleteV5v0Group,
            tmnxRPPolicyObjectsV7v0Group,
            tmnxRPPolicyObjectsV8v0Group,
            tmnxRPPolicyEntryObjectsV7v0Group,
            tmnxRPPolicyObsoleteV7v0Group
        }
    ::= { tmnxRoutePolicyCompliances 9 }

tmnxRoutePolicy7750V8v0Compliance MODULE-COMPLIANCE
    STATUS      obsolete
    DESCRIPTION
        "The compliance statement supporting management of Route Policies on
         Nokia 7750 SR series systems 5.0 release."
    MODULE
        MANDATORY-GROUPS {
            tmnxRPAdminControlObjectsGroup,
            tmnxRPASPathObjectsV5v0Group,
            tmnxRPCommunityObjectsV5v0Group,
            tmnxRPDampingObjectsV5v0Group,
            tmnxRPPrefixListObjectsV5v0Group,
            tmnxRPInetPrefixListObjectsV5v0Group,
            tmnxRPPolicyObsoleteV5v0Group,
            tmnxRPPolicyObjectsV7v0Group,
            tmnxRPPolicyObjectsV8v0Group,
            tmnxRPPolicyEntryObjectsV7v0Group,
            tmnxRPPolicyObsoleteV7v0Group
        }
    ::= { tmnxRoutePolicyCompliances 10 }

tmnxRoutePolicy7450V9v0Compliance MODULE-COMPLIANCE
    STATUS      obsolete
    DESCRIPTION
        "The compliance statement supporting management of Route Policies on
         Nokia 7450 ESS series systems 9.0 release."
    MODULE
        MANDATORY-GROUPS {
            tmnxRPAdminControlObjectsGroup,
            tmnxRPPolicyObsoleteV5v0Group,
            tmnxRPPolicyObjectsV7v0Group,
            tmnxRPPolicyObjectsV8v0Group,
            tmnxRPPolicyObjectsV9v0Group,
            tmnxRPPolicyEntryObjectsV9v0Group,
            tmnxRPPolicyObsoleteV7v0Group,
            tmnxRPQPPBV9v0R4Group
        }
    ::= { tmnxRoutePolicyCompliances 11 }

tmnxRoutePolicy7750V9v0Compliance MODULE-COMPLIANCE
    STATUS      obsolete
    DESCRIPTION
        "The compliance statement supporting management of Route Policies on
         Nokia 7750 SR series systems 9.0 release."
    MODULE
        MANDATORY-GROUPS {
            tmnxRPAdminControlObjectsGroup,
            tmnxRPASPathObjectsV5v0Group,
            tmnxRPCommunityObjectsV5v0Group,
            tmnxRPDampingObjectsV5v0Group,
            tmnxRPPrefixListObjectsV5v0Group,
            tmnxRPInetPrefixListObjectsV5v0Group,
            tmnxRPPolicyObsoleteV5v0Group,
            tmnxRPPolicyObjectsV7v0Group,
            tmnxRPPolicyObjectsV8v0Group,
            tmnxRPPolicyObjectsV9v0Group,
            tmnxRPPolicyEntryObjectsV9v0Group,
            tmnxRPPolicyObsoleteV7v0Group,
            tmnxRPQPPBV9v0R4Group
        }
    ::= { tmnxRoutePolicyCompliances 12 }

tmnxRtPolicy7450V10v0Compliance  MODULE-COMPLIANCE
    STATUS      obsolete
    DESCRIPTION
        "The compliance statement supporting management of Route Policies on
         Nokia 7450 ESS series systems 10.0 release."
    MODULE
        MANDATORY-GROUPS {
            tmnxRPAdminControlObjectsGroup,
            tmnxRPPolicyObsoleteV5v0Group,
            tmnxRPPolicyObjectsV7v0Group,
            tmnxRPPolicyObjectsV8v0Group,
            tmnxRPPolicyObjectsV9v0Group,
            tmnxRPPolicyEntryObjectsV9v0Group,
            tmnxRPPolicyObsoleteV7v0Group,
            tmnxRPQPPBV9v0R4Group,
            tmnxRPPolicyObjectsV10v0Group,
            tmnxRPASPathGroupV10v0Group
        }
    ::= { tmnxRoutePolicyCompliances 13 }

tmnxRtPolicy7750V10v0Compliance  MODULE-COMPLIANCE
    STATUS      obsolete
    DESCRIPTION
        "The compliance statement supporting management of Route Policies on
         Nokia 7750 SR series systems 10.0 release."
    MODULE
        MANDATORY-GROUPS {
            tmnxRPAdminControlObjectsGroup,
            tmnxRPASPathObjectsV5v0Group,
            tmnxRPCommunityObjectsV5v0Group,
            tmnxRPDampingObjectsV5v0Group,
            tmnxRPPrefixListObjectsV5v0Group,
            tmnxRPInetPrefixListObjectsV5v0Group,
            tmnxRPPolicyObsoleteV5v0Group,
            tmnxRPPolicyObjectsV7v0Group,
            tmnxRPPolicyObjectsV8v0Group,
            tmnxRPPolicyObjectsV9v0Group,
            tmnxRPPolicyEntryObjectsV9v0Group,
            tmnxRPPolicyObsoleteV7v0Group,
            tmnxRPQPPBV9v0R4Group,
            tmnxRPPolicyObjectsV10v0Group,
            tmnxRPASPathGroupV10v0Group
        }
    ::= { tmnxRoutePolicyCompliances 14 }

tmnxRtPolicyV11v0Compliance      MODULE-COMPLIANCE
    STATUS      obsolete
    DESCRIPTION
        "The compliance statement supporting management of Route Policies on
         Nokia SROS series systems 11.0 release."
    MODULE
        MANDATORY-GROUPS {
            tmnxRPAdminControlObjectsGroup,
            tmnxRPAdminControlObjV11v0Group,
            tmnxRPASPathObjectsV5v0Group,
            tmnxRPCommunityObjectsV5v0Group,
            tmnxRPDampingObjectsV5v0Group,
            tmnxRPPrefixListObjectsV5v0Group,
            tmnxRPInetPrefixListObjectsV5v0Group,
            tmnxRPPolicyObsoleteV5v0Group,
            tmnxRPPolicyObjectsV8v0Group,
            tmnxRPPolicyObjectsV9v0Group,
            tmnxRPPolicyObjectsV11v0Group,
            tmnxRPPolicyEntryObjsV11v0Group,
            tmnxRPPolicyObsoleteV7v0Group,
            tmnxRPQPPBV9v0R4Group,
            tmnxRPPolicyObjectsV10v0Group,
            tmnxRPASPathGroupV10v0Group,
            tmnxRPPolicyEntryObjV11v0Group
        }
    ::= { tmnxRoutePolicyCompliances 15 }

tmnxRtPolicyV12v0Compliance      MODULE-COMPLIANCE
    STATUS      obsolete
    DESCRIPTION
        "The compliance statement supporting management of Route Policies on
         Nokia SROS series systems 12.0 release."
    MODULE
        MANDATORY-GROUPS {
            tmnxRPAdminControlObjectsGroup,
            tmnxRPAdminControlObjV11v0Group,
            tmnxRPASPathObjectsV5v0Group,
            tmnxRPCommunityObjectsV5v0Group,
            tmnxRPDampingObjectsV5v0Group,
            tmnxRPPrefixListObjectsV5v0Group,
            tmnxRPInetPrefixListObjectsV5v0Group,
            tmnxRPPolicyObsoleteV5v0Group,
            tmnxRPPolicyObjectsV8v0Group,
            tmnxRPPolicyObjectsV9v0Group,
            tmnxRPPolicyObjectsV11v0Group,
            tmnxRPPolicyObjectsV12v0Group,
            tmnxRPPolicyVarObjectsGroup,
            tmnxRPPolicyEntryObjsV11v0Group,
            tmnxRPPolicyObsoleteV7v0Group,
            tmnxRPQPPBV9v0R4Group,
            tmnxRPPolicyObjectsV10v0Group,
            tmnxRPASPathGroupV10v0Group,
            tmnxRPPolicyEntryObjV11v0Group,
            tmnxRPOperPSAcceptActionFCGroup,
            tRPAdminPSAcceptOrigValidGroup,
            tmnxRPCreationOriginGroup,
            tmnxRPStickyEcmpGroup,
            tmnxRPBgpLeakingGroup
        }
    ::= { tmnxRoutePolicyCompliances 16 }

tmnxRtPolicyV13v0Compliance      MODULE-COMPLIANCE
    STATUS      obsolete
    DESCRIPTION
        "The compliance statement supporting management of Route Policies on
         Nokia SROS series systems 13.0 release."
    MODULE
        MANDATORY-GROUPS {
            tmnxRPAdminControlObjectsGroup,
            tmnxRPAdminControlObjV11v0Group,
            tmnxRPASPathObjectsV5v0Group,
            tmnxRPCommunityObjectsV5v0Group,
            tmnxRPDampingObjectsV5v0Group,
            tmnxRPPrefixListObjectsV5v0Group,
            tmnxRPInetPrefixListObjectsV5v0Group,
            tmnxRPPolicyObsoleteV5v0Group,
            tmnxRPPolicyObjectsV8v0Group,
            tmnxRPPolicyObjectsV9v0Group,
            tmnxRPPolicyObjectsV11v0Group,
            tmnxRPPolicyObjectsV12v0Group,
            tmnxRPPolicyVarObjectsGroup,
            tmnxRPPolicyEntryObjsV11v0Group,
            tmnxRPPolicyObsoleteV7v0Group,
            tmnxRPQPPBV9v0R4Group,
            tmnxRPPolicyObjectsV10v0Group,
            tmnxRPASPathGroupV10v0Group,
            tmnxRPPolicyEntryObjV11v0Group,
            tmnxRPOperPSAcceptActionFCGroup,
            tRPAdminPSAcceptOrigValidGroup,
            tmnxRPCreationOriginGroup,
            tmnxRPStickyEcmpGroup,
            tmnxRPFlowSpecGroup,
            tmnxRPAddPathsGroup,
            tmnxRPBackupPathGroup,
            tmnxRPPrefixListV13v0Group,
            tmnxRPAdvertiseLabelGroup,
            tmnxRPBgpLeakingGroup,
            tmnxRPPolicyVarExtGroup,
            tmnxRPPSCondRouteGroup
        }
    ::= { tmnxRoutePolicyCompliances 17 }

tmnxRtPolicyV14v0Compliance      MODULE-COMPLIANCE
    STATUS      obsolete
    DESCRIPTION
        "The compliance statement supporting management of Route Policies on
         Nokia SROS series systems 14.0 release."
    MODULE
        MANDATORY-GROUPS {
            tmnxRPAdminControlObjectsGroup,
            tmnxRPAdminControlObjV11v0Group,
            tmnxRPASPathObjectsV5v0Group,
            tmnxRPCommunityObjectsV5v0Group,
            tmnxRPDampingObjectsV5v0Group,
            tmnxRPPrefixListObjectsV5v0Group,
            tmnxRPInetPrefixListObjectsV5v0Group,
            tmnxRPPolicyObsoleteV5v0Group,
            tmnxRPPolicyObjectsV8v0Group,
            tmnxRPPolicyObjectsV9v0Group,
            tmnxRPPolicyObjectsV11v0Group,
            tmnxRPPolicyObjectsV12v0Group,
            tmnxRPPolicyVarObjectsGroup,
            tmnxRPPolicyObsoleteV7v0Group,
            tmnxRPPolicyObsoleteV14v0Group,
            tmnxRPQPPBV9v0R4Group,
            tmnxRPPolicyObjectsV10v0Group,
            tmnxRPASPathGroupV14v0Group,
            tmnxRPPolicyEntryObjV11v0Group,
            tmnxRPOperPSAcceptActionFCGroup,
            tRPAdminPSAcceptOrigValidGroup,
            tmnxRPCreationOriginGroup,
            tmnxRPStickyEcmpGroup,
            tmnxRPFlowSpecGroup,
            tmnxRPAddPathsGroup,
            tmnxRPBackupPathGroup,
            tmnxRPPrefixListV13v0Group,
            tmnxRPAdvertiseLabelGroup,
            tmnxRPBgpLeakingGroup,
            tmnxRPPolicyVarExtGroup,
            tmnxRPPSCondRouteGroup,
            tmnxRPPSCriteriaObjsV14v0Group,
            tmnxRPCreationOriginV14v0Group
        }
    ::= { tmnxRoutePolicyCompliances 18 }

tmnxRtPolicyV15v0Compliance      MODULE-COMPLIANCE
    STATUS      obsolete
    DESCRIPTION
        "The compliance statement supporting management of Route Policies on
         Nokia SROS series systems 15.0 release."
    MODULE
        MANDATORY-GROUPS {
            tmnxRPAdminControlObjectsGroup,
            tmnxRPAdminControlObjV11v0Group,
            tmnxRPASPathObjectsV5v0Group,
            tmnxRPCommunityObjectsV5v0Group,
            tmnxRPDampingObjectsV5v0Group,
            tmnxRPPrefixListObjectsV5v0Group,
            tmnxRPInetPrefixListObjectsV5v0Group,
            tmnxRPPolicyObsoleteV5v0Group,
            tmnxRPPolicyObjectsV8v0Group,
            tmnxRPPolicyObjectsV9v0Group,
            tmnxRPPolicyObjectsV11v0Group,
            tmnxRPPolicyObjectsV12v0Group,
            tmnxRPPolicyVarObjectsGroup,
            tmnxRPPolicyObsoleteV7v0Group,
            tmnxRPPolicyObsoleteV14v0Group,
            tmnxRPQPPBV9v0R4Group,
            tmnxRPPolicyObjectsV10v0Group,
            tmnxRPASPathGroupV14v0Group,
            tmnxRPPolicyEntryObjV11v0Group,
            tmnxRPOperPSAcceptActionFCGroup,
            tRPAdminPSAcceptOrigValidGroup,
            tmnxRPCreationOriginGroup,
            tmnxRPStickyEcmpGroup,
            tmnxRPFlowSpecGroup,
            tmnxRPAddPathsGroup,
            tmnxRPBackupPathGroup,
            tmnxRPPrefixListV13v0Group,
            tmnxRPAdvertiseLabelGroup,
            tmnxRPBgpLeakingGroup,
            tmnxRPPolicyVarExtGroup,
            tmnxRPPSCondRouteGroup,
            tmnxRPPSCriteriaObjsV14v0Group,
            tmnxRPCreationOriginV14v0Group,
            tmnxRPPolicyExtV15v0Group
        }
    ::= { tmnxRoutePolicyCompliances 19 }

tmnxRtPolicyV16v0Compliance      MODULE-COMPLIANCE
    STATUS      current
    DESCRIPTION
        "The compliance statement supporting management of Route Policies on
         Nokia SROS series systems 16.0 release."
    MODULE
        MANDATORY-GROUPS {
            tmnxRPAdminControlObjectsGroup,
            tmnxRPAdminControlObjV11v0Group,
            tmnxRPASPathObjectsV5v0Group,
            tmnxRPCommunityObjectsV5v0Group,
            tmnxRPDampingObjectsV5v0Group,
            tmnxRPPrefixListObjectsV5v0Group,
            tmnxRPInetPrefixListObjectsV5v0Group,
            tmnxRPPolicyObsoleteV5v0Group,
            tmnxRPPolicyObjectsV8v0Group,
            tmnxRPPolicyObjectsV9v0Group,
            tmnxRPPolicyObjectsV11v0Group,
            tmnxRPPolicyObjectsV12v0Group,
            tmnxRPPolicyVarObjectsGroup,
            tmnxRPPolicyObsoleteV7v0Group,
            tmnxRPPolicyObsoleteV14v0Group,
            tmnxRPQPPBV9v0R4Group,
            tmnxRPPolicyObjectsV10v0Group,
            tmnxRPASPathGroupV14v0Group,
            tmnxRPPolicyEntryObjV11v0Group,
            tmnxRPOperPSAcceptActionFCGroup,
            tRPAdminPSAcceptOrigValidGroup,
            tmnxRPCreationOriginGroup,
            tmnxRPStickyEcmpGroup,
            tmnxRPFlowSpecGroup,
            tmnxRPAddPathsGroup,
            tmnxRPBackupPathGroup,
            tmnxRPPrefixListV13v0Group,
            tmnxRPAdvertiseLabelGroup,
            tmnxRPBgpLeakingGroup,
            tmnxRPPolicyVarExtGroup,
            tmnxRPPSCondRouteGroup,
            tmnxRPPSCriteriaObjsV14v0Group,
            tmnxRPCreationOriginV14v0Group,
            tmnxRPPolicyExtV15v0Group,
            tmnxRPPolicyExtV16v0Group,
            tmnxRPPfxListExtV16v0Group
        }
    ::= { tmnxRoutePolicyCompliances 20 }

tmnxRtPolicyV19v0Compliance      MODULE-COMPLIANCE
    STATUS      current
    DESCRIPTION
        "The compliance statement supporting management of Route Policies on
         Nokia SROS series systems 19.0 release."
    MODULE
        MANDATORY-GROUPS {
            tmnxRPPolicyExtV19v0Group
        }
    ::= { tmnxRoutePolicyCompliances 21 }

tmnxRtPolicyV20v0Compliance      MODULE-COMPLIANCE
    STATUS      current
    DESCRIPTION
        "The compliance statement supporting management of Route Policies on
         Nokia SROS series systems 20.0 release."
    MODULE
        MANDATORY-GROUPS {
            tmnxRPPolicyV20v0Group,
            tmnxRPFromCritInterfaceGroup
        }
    ::= { tmnxRoutePolicyCompliances 22 }

tmnxRtPolicyV21v0Compliance      MODULE-COMPLIANCE
    STATUS      current
    DESCRIPTION
        "The compliance statement supporting management of Route Policies on
         Nokia SROS series systems 21.0 release."
    MODULE
        MANDATORY-GROUPS {
            tmnxRPPolicyV21v0Group
        }
    ::= { tmnxRoutePolicyCompliances 23 }

tmnxRtPolicyV22v0Compliance      MODULE-COMPLIANCE
    STATUS      current
    DESCRIPTION
        "The compliance statement supporting management of Route Policies on
         Nokia SROS series systems 22.0 release."
    MODULE
        MANDATORY-GROUPS {
            tmnxRPPolicyV22v0Group
        }
    ::= { tmnxRoutePolicyCompliances 24 }

tmnxRtPolicyV23v0Compliance      MODULE-COMPLIANCE
    STATUS      current
    DESCRIPTION
        "The compliance statement supporting management of Route Policies on
         Nokia SROS series systems 23.0 release."
    MODULE
        MANDATORY-GROUPS {
            tmnxRPPolicyV23v0Group
        }
    ::= { tmnxRoutePolicyCompliances 25 }

tmnxRoutePolicyGroups            OBJECT IDENTIFIER ::= { tmnxRoutePolicyConformance 2 }

tmnxRPAdminControlObjectsGroup   OBJECT-GROUP
    OBJECTS     {
        tRPAdminOwner,
        tRPAdminControlApply,
        tRPAdminLastSetTimer,
        tRPAdminLastSetTimeout
    }
    STATUS      current
    DESCRIPTION
        "The group of objects supporting management of transactions applying
         changed Administrative values to the Operational Route Policy database
         on Nokia SROS series systems."
    ::= { tmnxRoutePolicyGroups 1 }

tmnxRPASPathObjectsGroup         OBJECT-GROUP
    OBJECTS     {
        tRPOperASPathTableLastChanged,
        tRPOperASPathRowStatus,
        tRPOperASPathRegEx,
        tRPOperASPathEntryLastChanged,
        tRPAdminASPathRowStatus,
        tRPAdminASPathRegEx
    }
    STATUS      obsolete
    DESCRIPTION
        "The group of objects supporting management of AS Paths on Nokia SROS
         series systems."
    ::= { tmnxRoutePolicyGroups 2 }

tmnxRPCommunityObjectsGroup      OBJECT-GROUP
    OBJECTS     {
        tRPOperCommunityTableLastChanged,
        tRPOperCommunityRowStatus,
        tRPOperCommunityEntryLastChanged,
        tRPAdminCommunityRowStatus
    }
    STATUS      obsolete
    DESCRIPTION
        "The group of objects supporting management of route policy communities
         on Nokia SROS series systems."
    ::= { tmnxRoutePolicyGroups 3 }

tmnxRPDampingObjectsGroup        OBJECT-GROUP
    OBJECTS     {
        tRPOperDampingTableLastChanged,
        tRPOperDampingRowStatus,
        tRPOperDampingHalfLife,
        tRPOperDampingMaxSuppress,
        tRPOperDampingReuse,
        tRPOperDampingSuppress,
        tRPOperDampingEntryLastChanged,
        tRPAdminDampingRowStatus,
        tRPAdminDampingHalfLife,
        tRPAdminDampingMaxSuppress,
        tRPAdminDampingReuse,
        tRPAdminDampingSuppress
    }
    STATUS      obsolete
    DESCRIPTION
        "The group of objects supporting management route policy damping on
         Nokia SROS series systems."
    ::= { tmnxRoutePolicyGroups 4 }

tmnxRPPrefixListObjectsGroup     OBJECT-GROUP
    OBJECTS     {
        tRPOperPrefixListTableLastChanged,
        tRPOperPrefixListRowStatus,
        tRPOperPrefixListThroughLength,
        tRPOperPrefixListEntryLastChanged,
        tRPOperPrefixListBeginLength,
        tRPAdminPrefixListRowStatus,
        tRPAdminPrefixListThroughLength,
        tRPAdminPrefixListBeginLength
    }
    STATUS      obsolete
    DESCRIPTION
        "The group of objects supporting management of route policy prefix
         lists on Nokia SROS series systems."
    ::= { tmnxRoutePolicyGroups 5 }

tmnxRPPolicyObjectsV4v0Group     OBJECT-GROUP
    OBJECTS     {
        tRPOperPolicyStatementTableLastChanged,
        tRPOperPolicyStatementRowStatus,
        tRPOperPolicyStatementDescription,
        tRPOperPolicyStatementDefaultAction,
        tRPOperPolicyStatementEntryLastChanged,
        tRPOperPSDefaultActionParamsTableLastChanged,
        tRPOperPSDefaultActionASPath,
        tRPOperPSDefaultActionASPathName,
        tRPOperPSDefaultActionASPathPrependAS,
        tRPOperPSDefaultActionASPathPrependCount,
        tRPOperPSDefaultActionCommunity1,
        tRPOperPSDefaultActionCommunityName1,
        tRPOperPSDefaultActionCommunity2,
        tRPOperPSDefaultActionCommunityName2,
        tRPOperPSDefaultActionOrigin,
        tRPOperPSDefaultActionLocalPreferenceSet,
        tRPOperPSDefaultActionLocalPreference,
        tRPOperPSDefaultActionMetric,
        tRPOperPSDefaultActionMetricValue,
        tRPOperPSDefaultActionPreference,
        tRPOperPSDefaultActionDamping,
        tRPOperPSDefaultActionNextHopSelf,
        tRPOperPSDefaultActionNextHop,
        tRPOperPSDefaultActionTag,
        tRPOperPSDefaultActionOspfType,
        tRPOperPSDefaultActionParamsEntryLastChanged,
        tRPOperPSDefActInetNextHopType,
        tRPOperPSDefActInetNextHop,
        tRPAdminPolicyStatementRowStatus,
        tRPAdminPolicyStatementDescription,
        tRPAdminPolicyStatementDefaultAction,
        tRPAdminPSDefaultActionASPath,
        tRPAdminPSDefaultActionASPathName,
        tRPAdminPSDefaultActionASPathPrependAS,
        tRPAdminPSDefaultActionASPathPrependCount,
        tRPAdminPSDefaultActionCommunity1,
        tRPAdminPSDefaultActionCommunityName1,
        tRPAdminPSDefaultActionCommunity2,
        tRPAdminPSDefaultActionCommunityName2,
        tRPAdminPSDefaultActionOrigin,
        tRPAdminPSDefaultActionLocalPreferenceSet,
        tRPAdminPSDefaultActionLocalPreference,
        tRPAdminPSDefaultActionMetric,
        tRPAdminPSDefaultActionMetricValue,
        tRPAdminPSDefaultActionPreference,
        tRPAdminPSDefaultActionDamping,
        tRPAdminPSDefaultActionNextHopSelf,
        tRPAdminPSDefaultActionNextHop,
        tRPAdminPSDefaultActionTag,
        tRPAdminPSDefaultActionOspfType,
        tRPAdminPSDefActInetNextHopType,
        tRPAdminPSDefActInetNextHop
    }
    STATUS      obsolete
    DESCRIPTION
        "The group of objects supporting management of policy statements and
         default action parameters on Nokia SROS series systems."
    ::= { tmnxRoutePolicyGroups 9 }

tmnxRPPolicyEntryObjectsV4v0Group OBJECT-GROUP
    OBJECTS     {
        tRPOperPSParamsTableLastChanged,
        tRPOperPSParamsRowStatus,
        tRPOperPSParamsDescription,
        tRPOperPSParamsAction,
        tRPOperPSParamsEntryLastChanged,
        tRPOperPSAcceptActionParamsTableLastChanged,
        tRPOperPSAcceptActionASPath,
        tRPOperPSAcceptActionASPathName,
        tRPOperPSAcceptActionASPathPrependAS,
        tRPOperPSAcceptActionASPathPrependCount,
        tRPOperPSAcceptActionCommunity1,
        tRPOperPSAcceptActionCommunityName1,
        tRPOperPSAcceptActionCommunity2,
        tRPOperPSAcceptActionCommunityName2,
        tRPOperPSAcceptActionOrigin,
        tRPOperPSAcceptActionLocalPreferenceSet,
        tRPOperPSAcceptActionLocalPreference,
        tRPOperPSAcceptActionMetric,
        tRPOperPSAcceptActionMetricValue,
        tRPOperPSAcceptActionPreference,
        tRPOperPSAcceptActionDamping,
        tRPOperPSAcceptActionNextHopSelf,
        tRPOperPSAcceptActionNextHop,
        tRPOperPSAcceptActionTag,
        tRPOperPSAcceptActionOspfType,
        tRPOperPSAcceptActionParamsEntryLastChanged,
        tRPOperPSAcptActInetNextHopType,
        tRPOperPSAcptActInetNextHop,
        tRPOperPSToCriteriaTableLastChanged,
        tRPOperPSToCriteriaRowStatus,
        tRPOperPSToCriteriaProtocol,
        tRPOperPSToCriteriaNeighborIpAddr,
        tRPOperPSToCriteriaNeighborPrefixList,
        tRPOperPSToCriteriaEntryLastChanged,
        tRPOperPSToCriteriaIsisLevel,
        tRPOperPSToCriteriaPrefixList1,
        tRPOperPSToCriteriaPrefixList2,
        tRPOperPSToCriteriaPrefixList3,
        tRPOperPSToCriteriaPrefixList4,
        tRPOperPSToCriteriaPrefixList5,
        tRPOperPSToCritNbrInetAddrType,
        tRPOperPSToCritNbrInetAddr,
        tRPOperPSFromCriteriaTableLastChanged,
        tRPOperPSFromCriteriaRowStatus,
        tRPOperPSFromCriteriaProtocol,
        tRPOperPSFromCriteriaNeighborIpAddr,
        tRPOperPSFromCriteriaNeighborPrefixList,
        tRPOperPSFromCriteriaPrefixList1,
        tRPOperPSFromCriteriaPrefixList2,
        tRPOperPSFromCriteriaPrefixList3,
        tRPOperPSFromCriteriaPrefixList4,
        tRPOperPSFromCriteriaPrefixList5,
        tRPOperPSFromCriteriaASPath,
        tRPOperPSFromCriteriaCommunity,
        tRPOperPSFromCriteriaOrigin,
        tRPOperPSFromCriteriaOspfRouteType,
        tRPOperPSFromCriteriaEntryLastChanged,
        tRPOperPSFromCriteriaArea,
        tRPOperPSFromCriteriaAreaConfigured,
        tRPOperPSFromCriteriaIsisLevel,
        tRPOperPSFromCriteriaIsisExternal,
        tRPOperPSFromCriteriaIgmpHostPrefixList,
        tRPOperPSFromCriteriaGrpAddrPrefixList,
        tRPOperPSFromCriteriaSrcAddr,
        tRPOperPSFromCriteriaInterface,
        tRPOperPSFromCriteriaTag,
        tRPOperPSFromCritNbrInetAddrType,
        tRPOperPSFromCritNbrInetAddr,
        tRPOperPSFromCritSrcInetAddrType,
        tRPOperPSFromCritSrcInetAddr,
        tRPOperPSFromCriteriaFamily,
        tRPAdminPSParamsRowStatus,
        tRPAdminPSParamsDescription,
        tRPAdminPSParamsAction,
        tRPAdminPSAcceptActionASPath,
        tRPAdminPSAcceptActionASPathName,
        tRPAdminPSAcceptActionASPathPrependAS,
        tRPAdminPSAcceptActionASPathPrependCount,
        tRPAdminPSAcceptActionCommunity1,
        tRPAdminPSAcceptActionCommunityName1,
        tRPAdminPSAcceptActionCommunity2,
        tRPAdminPSAcceptActionCommunityName2,
        tRPAdminPSAcceptActionOrigin,
        tRPAdminPSAcceptActionLocalPreferenceSet,
        tRPAdminPSAcceptActionLocalPreference,
        tRPAdminPSAcceptActionMetric,
        tRPAdminPSAcceptActionMetricValue,
        tRPAdminPSAcceptActionPreference,
        tRPAdminPSAcceptActionDamping,
        tRPAdminPSAcceptActionNextHopSelf,
        tRPAdminPSAcceptActionNextHop,
        tRPAdminPSAcceptActionTag,
        tRPAdminPSAcceptActionOspfType,
        tRPAdminPSAcptActInetNextHopType,
        tRPAdminPSAcptActInetNextHop,
        tRPAdminPSToCriteriaRowStatus,
        tRPAdminPSToCriteriaProtocol,
        tRPAdminPSToCriteriaNeighborIpAddr,
        tRPAdminPSToCriteriaNeighborPrefixList,
        tRPAdminPSToCriteriaIsisLevel,
        tRPAdminPSToCriteriaPrefixList1,
        tRPAdminPSToCriteriaPrefixList2,
        tRPAdminPSToCriteriaPrefixList3,
        tRPAdminPSToCriteriaPrefixList4,
        tRPAdminPSToCriteriaPrefixList5,
        tRPAdminPSToCritNbrInetAddrType,
        tRPAdminPSToCritNbrInetAddr,
        tRPAdminPSFromCriteriaRowStatus,
        tRPAdminPSFromCriteriaProtocol,
        tRPAdminPSFromCriteriaNeighborIpAddr,
        tRPAdminPSFromCriteriaNeighborPrefixList,
        tRPAdminPSFromCriteriaPrefixList1,
        tRPAdminPSFromCriteriaPrefixList2,
        tRPAdminPSFromCriteriaPrefixList3,
        tRPAdminPSFromCriteriaPrefixList4,
        tRPAdminPSFromCriteriaPrefixList5,
        tRPAdminPSFromCriteriaASPath,
        tRPAdminPSFromCriteriaCommunity,
        tRPAdminPSFromCriteriaOrigin,
        tRPAdminPSFromCriteriaOspfRouteType,
        tRPAdminPSFromCriteriaArea,
        tRPAdminPSFromCriteriaAreaConfigured,
        tRPAdminPSFromCriteriaIsisLevel,
        tRPAdminPSFromCriteriaIsisExternal,
        tRPAdminPSFromCriteriaIgmpHostPrefixList,
        tRPAdminPSFromCriteriaGrpAddrPrefixList,
        tRPAdminPSFromCriteriaSrcAddr,
        tRPAdminPSFromCriteriaInterface,
        tRPAdminPSFromCriteriaTag,
        tRPAdminPSFromCritNbrInetAddrType,
        tRPAdminPSFromCritNbrInetAddr,
        tRPAdminPSFromCritSrcInetAddrType,
        tRPAdminPSFromCritSrcInetAddr,
        tRPAdminPSFromCriteriaFamily
    }
    STATUS      obsolete
    DESCRIPTION
        "The group of objects supporting management of route policy statement
         entries, 'to' filter parameters, 'from' filter parameters, and accept
         action parameters on Nokia SROS series systems 4.0 release."
    ::= { tmnxRoutePolicyGroups 10 }

tmnxRPInetPrefixListObjectsGroup OBJECT-GROUP
    OBJECTS     {
        tRPOperInetPrefixListTblLastChg,
        tRPOperInetPrefixListRowStatus,
        tRPOperInetPrefixListThroughLen,
        tRPOperInetPrefixListLastChg,
        tRPOperInetPrefixListBeginLen,
        tRPAdminInetPrefixListRowStatus,
        tRPAdminInetPrefixListThroughLen,
        tRPAdminInetPrefixListBeginLen
    }
    STATUS      obsolete
    DESCRIPTION
        "The group of objects supporting management of route policy prefix
         lists on Nokia SROS series systems."
    ::= { tmnxRoutePolicyGroups 11 }

tmnxRPPolicyEntryObjectsV5v0Group OBJECT-GROUP
    OBJECTS     {
        tRPOperPSParamsRowStatus,
        tRPOperPSParamsDescription,
        tRPOperPSParamsAction,
        tRPOperPSAcceptActionASPath,
        tRPOperPSAcceptActionASPathName,
        tRPOperPSAcceptActionASPathPrependAS,
        tRPOperPSAcceptActionASPathPrependCount,
        tRPOperPSAcceptActionCommunity1,
        tRPOperPSAcceptActionCommunityName1,
        tRPOperPSAcceptActionCommunity2,
        tRPOperPSAcceptActionCommunityName2,
        tRPOperPSAcceptActionOrigin,
        tRPOperPSAcceptActionLocalPreferenceSet,
        tRPOperPSAcceptActionLocalPreference,
        tRPOperPSAcceptActionMetric,
        tRPOperPSAcceptActionMetricValue,
        tRPOperPSAcceptActionPreference,
        tRPOperPSAcceptActionDamping,
        tRPOperPSAcceptActionNextHopSelf,
        tRPOperPSAcceptActionNextHop,
        tRPOperPSAcceptActionTag,
        tRPOperPSAcceptActionOspfType,
        tRPOperPSAcptActInetNextHopType,
        tRPOperPSAcptActInetNextHop,
        tRPOperPSToCriteriaRowStatus,
        tRPOperPSToCriteriaProtocol,
        tRPOperPSToCriteriaNeighborIpAddr,
        tRPOperPSToCriteriaNeighborPrefixList,
        tRPOperPSToCriteriaIsisLevel,
        tRPOperPSToCriteriaPrefixList1,
        tRPOperPSToCriteriaPrefixList2,
        tRPOperPSToCriteriaPrefixList3,
        tRPOperPSToCriteriaPrefixList4,
        tRPOperPSToCriteriaPrefixList5,
        tRPOperPSToCritNbrInetAddrType,
        tRPOperPSToCritNbrInetAddr,
        tRPOperPSToCriteriaInstanceId,
        tRPOperPSFromCriteriaRowStatus,
        tRPOperPSFromCriteriaProtocol,
        tRPOperPSFromCriteriaNeighborIpAddr,
        tRPOperPSFromCriteriaNeighborPrefixList,
        tRPOperPSFromCriteriaPrefixList1,
        tRPOperPSFromCriteriaPrefixList2,
        tRPOperPSFromCriteriaPrefixList3,
        tRPOperPSFromCriteriaPrefixList4,
        tRPOperPSFromCriteriaPrefixList5,
        tRPOperPSFromCriteriaASPath,
        tRPOperPSFromCriteriaCommunity,
        tRPOperPSFromCriteriaOrigin,
        tRPOperPSFromCriteriaOspfRouteType,
        tRPOperPSFromCriteriaArea,
        tRPOperPSFromCriteriaAreaConfigured,
        tRPOperPSFromCriteriaIsisLevel,
        tRPOperPSFromCriteriaIsisExternal,
        tRPOperPSFromCriteriaIgmpHostPrefixList,
        tRPOperPSFromCriteriaGrpAddrPrefixList,
        tRPOperPSFromCriteriaSrcAddr,
        tRPOperPSFromCriteriaInterface,
        tRPOperPSFromCriteriaTag,
        tRPOperPSFromCritNbrInetAddrType,
        tRPOperPSFromCritNbrInetAddr,
        tRPOperPSFromCritSrcInetAddrType,
        tRPOperPSFromCritSrcInetAddr,
        tRPOperPSFromCriteriaFamily,
        tRPOperPSFromCriteriaInstanceId,
        tRPAdminPSParamsRowStatus,
        tRPAdminPSParamsDescription,
        tRPAdminPSParamsAction,
        tRPAdminPSAcceptActionASPath,
        tRPAdminPSAcceptActionASPathName,
        tRPAdminPSAcceptActionASPathPrependAS,
        tRPAdminPSAcceptActionASPathPrependCount,
        tRPAdminPSAcceptActionCommunity1,
        tRPAdminPSAcceptActionCommunityName1,
        tRPAdminPSAcceptActionCommunity2,
        tRPAdminPSAcceptActionCommunityName2,
        tRPAdminPSAcceptActionOrigin,
        tRPAdminPSAcceptActionLocalPreferenceSet,
        tRPAdminPSAcceptActionLocalPreference,
        tRPAdminPSAcceptActionMetric,
        tRPAdminPSAcceptActionMetricValue,
        tRPAdminPSAcceptActionPreference,
        tRPAdminPSAcceptActionDamping,
        tRPAdminPSAcceptActionNextHopSelf,
        tRPAdminPSAcceptActionNextHop,
        tRPAdminPSAcceptActionTag,
        tRPAdminPSAcceptActionOspfType,
        tRPAdminPSAcptActInetNextHopType,
        tRPAdminPSAcptActInetNextHop,
        tRPAdminPSToCriteriaRowStatus,
        tRPAdminPSToCriteriaProtocol,
        tRPAdminPSToCriteriaNeighborIpAddr,
        tRPAdminPSToCriteriaNeighborPrefixList,
        tRPAdminPSToCriteriaIsisLevel,
        tRPAdminPSToCriteriaPrefixList1,
        tRPAdminPSToCriteriaPrefixList2,
        tRPAdminPSToCriteriaPrefixList3,
        tRPAdminPSToCriteriaPrefixList4,
        tRPAdminPSToCriteriaPrefixList5,
        tRPAdminPSToCritNbrInetAddrType,
        tRPAdminPSToCritNbrInetAddr,
        tRPAdminPSToCriteriaInstanceId,
        tRPAdminPSFromCriteriaRowStatus,
        tRPAdminPSFromCriteriaProtocol,
        tRPAdminPSFromCriteriaNeighborIpAddr,
        tRPAdminPSFromCriteriaNeighborPrefixList,
        tRPAdminPSFromCriteriaPrefixList1,
        tRPAdminPSFromCriteriaPrefixList2,
        tRPAdminPSFromCriteriaPrefixList3,
        tRPAdminPSFromCriteriaPrefixList4,
        tRPAdminPSFromCriteriaPrefixList5,
        tRPAdminPSFromCriteriaASPath,
        tRPAdminPSFromCriteriaCommunity,
        tRPAdminPSFromCriteriaOrigin,
        tRPAdminPSFromCriteriaOspfRouteType,
        tRPAdminPSFromCriteriaArea,
        tRPAdminPSFromCriteriaAreaConfigured,
        tRPAdminPSFromCriteriaIsisLevel,
        tRPAdminPSFromCriteriaIsisExternal,
        tRPAdminPSFromCriteriaIgmpHostPrefixList,
        tRPAdminPSFromCriteriaGrpAddrPrefixList,
        tRPAdminPSFromCriteriaSrcAddr,
        tRPAdminPSFromCriteriaInterface,
        tRPAdminPSFromCriteriaTag,
        tRPAdminPSFromCritNbrInetAddrType,
        tRPAdminPSFromCritNbrInetAddr,
        tRPAdminPSFromCritSrcInetAddrType,
        tRPAdminPSFromCritSrcInetAddr,
        tRPAdminPSFromCriteriaFamily,
        tRPAdminPSFromCriteriaInstanceId
    }
    STATUS      obsolete
    DESCRIPTION
        "The group of objects supporting management of route policy statement
         entries, 'to' filter parameters, 'from' filter parameters, and accept
         action parameters on Nokia SROS SR series systems 5.0 release."
    ::= { tmnxRoutePolicyGroups 12 }

tmnxRPPolicyObsoleteV5v0Group    OBJECT-GROUP
    OBJECTS     {
        tRPOperASPathTableLastChanged,
        tRPOperASPathEntryLastChanged,
        tRPOperCommunityTableLastChanged,
        tRPOperCommunityEntryLastChanged,
        tRPOperDampingTableLastChanged,
        tRPOperDampingEntryLastChanged,
        tRPOperPrefixListTableLastChanged,
        tRPOperPrefixListEntryLastChanged,
        tRPOperPolicyStatementTableLastChanged,
        tRPOperPolicyStatementEntryLastChanged,
        tRPOperPSDefaultActionParamsTableLastChanged,
        tRPOperPSDefaultActionParamsEntryLastChanged,
        tRPOperPSParamsTableLastChanged,
        tRPOperPSParamsEntryLastChanged,
        tRPOperPSAcceptActionParamsTableLastChanged,
        tRPOperPSAcceptActionParamsEntryLastChanged,
        tRPOperPSToCriteriaTableLastChanged,
        tRPOperPSToCriteriaEntryLastChanged,
        tRPOperPSFromCriteriaTableLastChanged,
        tRPOperPSFromCriteriaEntryLastChanged,
        tRPOperInetPrefixListTblLastChg,
        tRPOperInetPrefixListLastChg
    }
    STATUS      current
    DESCRIPTION
        "The group of objects in TIMETRA-ROUTE-POLICY-MIB which are obsoleted."
    ::= { tmnxRoutePolicyGroups 13 }

tmnxRPASPathObjectsV5v0Group     OBJECT-GROUP
    OBJECTS     {
        tRPOperASPathRowStatus,
        tRPOperASPathRegEx,
        tRPAdminASPathRowStatus,
        tRPAdminASPathRegEx
    }
    STATUS      current
    DESCRIPTION
        "The group of objects supporting management of AS Paths on Nokia SROS
         series systems."
    ::= { tmnxRoutePolicyGroups 14 }

tmnxRPCommunityObjectsV5v0Group  OBJECT-GROUP
    OBJECTS     {
        tRPOperCommunityRowStatus,
        tRPAdminCommunityRowStatus
    }
    STATUS      current
    DESCRIPTION
        "The group of objects supporting management of route policy communities
         on Nokia SROS series systems."
    ::= { tmnxRoutePolicyGroups 15 }

tmnxRPDampingObjectsV5v0Group    OBJECT-GROUP
    OBJECTS     {
        tRPOperDampingRowStatus,
        tRPOperDampingHalfLife,
        tRPOperDampingMaxSuppress,
        tRPOperDampingReuse,
        tRPOperDampingSuppress,
        tRPAdminDampingRowStatus,
        tRPAdminDampingHalfLife,
        tRPAdminDampingMaxSuppress,
        tRPAdminDampingReuse,
        tRPAdminDampingSuppress
    }
    STATUS      current
    DESCRIPTION
        "The group of objects supporting management route policy damping on
         Nokia SROS series systems."
    ::= { tmnxRoutePolicyGroups 16 }

tmnxRPPrefixListObjectsV5v0Group OBJECT-GROUP
    OBJECTS     {
        tRPOperPrefixListRowStatus,
        tRPOperPrefixListThroughLength,
        tRPOperPrefixListBeginLength,
        tRPAdminPrefixListRowStatus,
        tRPAdminPrefixListThroughLength,
        tRPAdminPrefixListBeginLength
    }
    STATUS      current
    DESCRIPTION
        "The group of objects supporting management of route policy prefix
         lists on Nokia SROS series systems."
    ::= { tmnxRoutePolicyGroups 17 }

tmnxRPPolicyObjectsV5v0Group     OBJECT-GROUP
    OBJECTS     {
        tRPOperPolicyStatementRowStatus,
        tRPOperPolicyStatementDescription,
        tRPOperPolicyStatementDefaultAction,
        tRPOperPSDefaultActionASPath,
        tRPOperPSDefaultActionASPathName,
        tRPOperPSDefaultActionASPathPrependAS,
        tRPOperPSDefaultActionASPathPrependCount,
        tRPOperPSDefaultActionCommunity1,
        tRPOperPSDefaultActionCommunityName1,
        tRPOperPSDefaultActionCommunity2,
        tRPOperPSDefaultActionCommunityName2,
        tRPOperPSDefaultActionOrigin,
        tRPOperPSDefaultActionLocalPreferenceSet,
        tRPOperPSDefaultActionLocalPreference,
        tRPOperPSDefaultActionMetric,
        tRPOperPSDefaultActionMetricValue,
        tRPOperPSDefaultActionPreference,
        tRPOperPSDefaultActionDamping,
        tRPOperPSDefaultActionNextHopSelf,
        tRPOperPSDefaultActionNextHop,
        tRPOperPSDefaultActionTag,
        tRPOperPSDefaultActionOspfType,
        tRPOperPSDefActInetNextHopType,
        tRPOperPSDefActInetNextHop,
        tRPAdminPolicyStatementRowStatus,
        tRPAdminPolicyStatementDescription,
        tRPAdminPolicyStatementDefaultAction,
        tRPAdminPSDefaultActionASPath,
        tRPAdminPSDefaultActionASPathName,
        tRPAdminPSDefaultActionASPathPrependAS,
        tRPAdminPSDefaultActionASPathPrependCount,
        tRPAdminPSDefaultActionCommunity1,
        tRPAdminPSDefaultActionCommunityName1,
        tRPAdminPSDefaultActionCommunity2,
        tRPAdminPSDefaultActionCommunityName2,
        tRPAdminPSDefaultActionOrigin,
        tRPAdminPSDefaultActionLocalPreferenceSet,
        tRPAdminPSDefaultActionLocalPreference,
        tRPAdminPSDefaultActionMetric,
        tRPAdminPSDefaultActionMetricValue,
        tRPAdminPSDefaultActionPreference,
        tRPAdminPSDefaultActionDamping,
        tRPAdminPSDefaultActionNextHopSelf,
        tRPAdminPSDefaultActionNextHop,
        tRPAdminPSDefaultActionTag,
        tRPAdminPSDefaultActionOspfType,
        tRPAdminPSDefActInetNextHopType,
        tRPAdminPSDefActInetNextHop
    }
    STATUS      obsolete
    DESCRIPTION
        "The group of objects supporting management of policy statements and
         default action parameters on Nokia SROS series systems."
    ::= { tmnxRoutePolicyGroups 18 }

tmnxRPInetPrefixListObjectsV5v0Group OBJECT-GROUP
    OBJECTS     {
        tRPOperInetPrefixListRowStatus,
        tRPOperInetPrefixListThroughLen,
        tRPOperInetPrefixListBeginLen,
        tRPAdminInetPrefixListRowStatus,
        tRPAdminInetPrefixListThroughLen,
        tRPAdminInetPrefixListBeginLen
    }
    STATUS      current
    DESCRIPTION
        "The group of objects supporting management of route policy prefix
         lists on Nokia SROS series systems."
    ::= { tmnxRoutePolicyGroups 19 }

tmnxRPPolicyObjectsV7v0Group     OBJECT-GROUP
    OBJECTS     {
        tRPOperPolicyStatementRowStatus,
        tRPOperPolicyStatementDescription,
        tRPOperPolicyStatementDefaultAction,
        tRPOperPSDefaultActionASPath,
        tRPOperPSDefaultActionASPathName,
        tRPOperPSDefaultActionASPathPrependCount,
        tRPOperPSDefaultActionCommunity1,
        tRPOperPSDefaultActionCommunityName1,
        tRPOperPSDefaultActionCommunity2,
        tRPOperPSDefaultActionCommunityName2,
        tRPOperPSDefaultActionOrigin,
        tRPOperPSDefaultActionLocalPreferenceSet,
        tRPOperPSDefaultActionLocalPreference,
        tRPOperPSDefaultActionMetric,
        tRPOperPSDefaultActionMetricValue,
        tRPOperPSDefaultActionPreference,
        tRPOperPSDefaultActionDamping,
        tRPOperPSDefaultActionNextHopSelf,
        tRPOperPSDefaultActionNextHop,
        tRPOperPSDefaultActionTag,
        tRPOperPSDefaultActionOspfType,
        tRPOperPSDefActInetNextHopType,
        tRPOperPSDefActInetNextHop,
        tRPAdminPolicyStatementRowStatus,
        tRPAdminPolicyStatementDescription,
        tRPAdminPolicyStatementDefaultAction,
        tRPAdminPSDefaultActionASPath,
        tRPAdminPSDefaultActionASPathName,
        tRPAdminPSDefaultActionASPathPrependCount,
        tRPAdminPSDefaultActionCommunity1,
        tRPAdminPSDefaultActionCommunityName1,
        tRPAdminPSDefaultActionCommunity2,
        tRPAdminPSDefaultActionCommunityName2,
        tRPAdminPSDefaultActionOrigin,
        tRPAdminPSDefaultActionLocalPreferenceSet,
        tRPAdminPSDefaultActionLocalPreference,
        tRPAdminPSDefaultActionMetric,
        tRPAdminPSDefaultActionMetricValue,
        tRPAdminPSDefaultActionPreference,
        tRPAdminPSDefaultActionDamping,
        tRPAdminPSDefaultActionNextHopSelf,
        tRPAdminPSDefaultActionNextHop,
        tRPAdminPSDefaultActionTag,
        tRPAdminPSDefaultActionOspfType,
        tRPAdminPSDefActInetNextHopType,
        tRPAdminPSDefActInetNextHop,
        tRPAdminPSDefaultActionASPathPnd,
        tRPOperPSDefaultActionASPathPend
    }
    STATUS      obsolete
    DESCRIPTION
        "The group of objects supporting management of policy statements and
         default action parameters on Nokia SROS series systems."
    ::= { tmnxRoutePolicyGroups 20 }

tmnxRPPolicyEntryObjectsV7v0Group OBJECT-GROUP
    OBJECTS     {
        tRPOperPSParamsRowStatus,
        tRPOperPSParamsDescription,
        tRPOperPSParamsAction,
        tRPOperPSAcceptActionASPath,
        tRPOperPSAcceptActionASPathName,
        tRPOperPSAcceptActionASPathPrependCount,
        tRPOperPSAcceptActionCommunity1,
        tRPOperPSAcceptActionCommunityName1,
        tRPOperPSAcceptActionCommunity2,
        tRPOperPSAcceptActionCommunityName2,
        tRPOperPSAcceptActionOrigin,
        tRPOperPSAcceptActionLocalPreferenceSet,
        tRPOperPSAcceptActionLocalPreference,
        tRPOperPSAcceptActionMetric,
        tRPOperPSAcceptActionMetricValue,
        tRPOperPSAcceptActionPreference,
        tRPOperPSAcceptActionDamping,
        tRPOperPSAcceptActionNextHopSelf,
        tRPOperPSAcceptActionNextHop,
        tRPOperPSAcceptActionTag,
        tRPOperPSAcceptActionOspfType,
        tRPOperPSAcptActInetNextHopType,
        tRPOperPSAcptActInetNextHop,
        tRPOperPSToCriteriaRowStatus,
        tRPOperPSToCriteriaProtocol,
        tRPOperPSToCriteriaNeighborIpAddr,
        tRPOperPSToCriteriaNeighborPrefixList,
        tRPOperPSToCriteriaIsisLevel,
        tRPOperPSToCriteriaPrefixList1,
        tRPOperPSToCriteriaPrefixList2,
        tRPOperPSToCriteriaPrefixList3,
        tRPOperPSToCriteriaPrefixList4,
        tRPOperPSToCriteriaPrefixList5,
        tRPOperPSToCritNbrInetAddrType,
        tRPOperPSToCritNbrInetAddr,
        tRPOperPSToCriteriaInstanceId,
        tRPOperPSFromCriteriaRowStatus,
        tRPOperPSFromCriteriaProtocol,
        tRPOperPSFromCriteriaNeighborIpAddr,
        tRPOperPSFromCriteriaNeighborPrefixList,
        tRPOperPSFromCriteriaPrefixList1,
        tRPOperPSFromCriteriaPrefixList2,
        tRPOperPSFromCriteriaPrefixList3,
        tRPOperPSFromCriteriaPrefixList4,
        tRPOperPSFromCriteriaPrefixList5,
        tRPOperPSFromCriteriaASPath,
        tRPOperPSFromCriteriaCommunity,
        tRPOperPSFromCriteriaOrigin,
        tRPOperPSFromCriteriaOspfRouteType,
        tRPOperPSFromCriteriaArea,
        tRPOperPSFromCriteriaAreaConfigured,
        tRPOperPSFromCriteriaIsisLevel,
        tRPOperPSFromCriteriaIsisExternal,
        tRPOperPSFromCriteriaIgmpHostPrefixList,
        tRPOperPSFromCriteriaGrpAddrPrefixList,
        tRPOperPSFromCriteriaSrcAddr,
        tRPOperPSFromCriteriaInterface,
        tRPOperPSFromCriteriaTag,
        tRPOperPSFromCritNbrInetAddrType,
        tRPOperPSFromCritNbrInetAddr,
        tRPOperPSFromCritSrcInetAddrType,
        tRPOperPSFromCritSrcInetAddr,
        tRPOperPSFromCriteriaFamily,
        tRPOperPSFromCriteriaInstanceId,
        tRPAdminPSParamsRowStatus,
        tRPAdminPSParamsDescription,
        tRPAdminPSParamsAction,
        tRPAdminPSAcceptActionASPath,
        tRPAdminPSAcceptActionASPathName,
        tRPAdminPSAcceptActionASPathPrependCount,
        tRPAdminPSAcceptActionCommunity1,
        tRPAdminPSAcceptActionCommunityName1,
        tRPAdminPSAcceptActionCommunity2,
        tRPAdminPSAcceptActionCommunityName2,
        tRPAdminPSAcceptActionOrigin,
        tRPAdminPSAcceptActionLocalPreferenceSet,
        tRPAdminPSAcceptActionLocalPreference,
        tRPAdminPSAcceptActionMetric,
        tRPAdminPSAcceptActionMetricValue,
        tRPAdminPSAcceptActionPreference,
        tRPAdminPSAcceptActionDamping,
        tRPAdminPSAcceptActionNextHopSelf,
        tRPAdminPSAcceptActionNextHop,
        tRPAdminPSAcceptActionTag,
        tRPAdminPSAcceptActionOspfType,
        tRPAdminPSAcptActInetNextHopType,
        tRPAdminPSAcptActInetNextHop,
        tRPAdminPSToCriteriaRowStatus,
        tRPAdminPSToCriteriaProtocol,
        tRPAdminPSToCriteriaNeighborIpAddr,
        tRPAdminPSToCriteriaNeighborPrefixList,
        tRPAdminPSToCriteriaIsisLevel,
        tRPAdminPSToCriteriaPrefixList1,
        tRPAdminPSToCriteriaPrefixList2,
        tRPAdminPSToCriteriaPrefixList3,
        tRPAdminPSToCriteriaPrefixList4,
        tRPAdminPSToCriteriaPrefixList5,
        tRPAdminPSToCritNbrInetAddrType,
        tRPAdminPSToCritNbrInetAddr,
        tRPAdminPSToCriteriaInstanceId,
        tRPAdminPSFromCriteriaRowStatus,
        tRPAdminPSFromCriteriaProtocol,
        tRPAdminPSFromCriteriaNeighborIpAddr,
        tRPAdminPSFromCriteriaNeighborPrefixList,
        tRPAdminPSFromCriteriaPrefixList1,
        tRPAdminPSFromCriteriaPrefixList2,
        tRPAdminPSFromCriteriaPrefixList3,
        tRPAdminPSFromCriteriaPrefixList4,
        tRPAdminPSFromCriteriaPrefixList5,
        tRPAdminPSFromCriteriaASPath,
        tRPAdminPSFromCriteriaCommunity,
        tRPAdminPSFromCriteriaOrigin,
        tRPAdminPSFromCriteriaOspfRouteType,
        tRPAdminPSFromCriteriaArea,
        tRPAdminPSFromCriteriaAreaConfigured,
        tRPAdminPSFromCriteriaIsisLevel,
        tRPAdminPSFromCriteriaIsisExternal,
        tRPAdminPSFromCriteriaIgmpHostPrefixList,
        tRPAdminPSFromCriteriaGrpAddrPrefixList,
        tRPAdminPSFromCriteriaSrcAddr,
        tRPAdminPSFromCriteriaInterface,
        tRPAdminPSFromCriteriaTag,
        tRPAdminPSFromCritNbrInetAddrType,
        tRPAdminPSFromCritNbrInetAddr,
        tRPAdminPSFromCritSrcInetAddrType,
        tRPAdminPSFromCritSrcInetAddr,
        tRPAdminPSFromCriteriaFamily,
        tRPAdminPSFromCriteriaInstanceId,
        tRPAdminPSAcceptActionASPathPend,
        tRPOperPSAcceptActionASPathPend,
        tRPOperPSFromCriteriaMatchTag,
        tRPAdminPSFromCriteriaMatchTag
    }
    STATUS      obsolete
    DESCRIPTION
        "The group of objects supporting management of route policy statement
         entries, 'to' filter parameters, 'from' filter parameters, and accept
         action parameters on Nokia SROS series systems 7.0 release."
    ::= { tmnxRoutePolicyGroups 21 }

tmnxRPPolicyObsoleteV7v0Group    OBJECT-GROUP
    OBJECTS     {
        tRPAdminPSDefaultActionASPathPrependAS,
        tRPAdminPSAcceptActionASPathPrependAS,
        tRPOperPSDefaultActionASPathPrependAS,
        tRPOperPSAcceptActionASPathPrependAS
    }
    STATUS      current
    DESCRIPTION
        "The group of objects in TIMETRA-ROUTE-POLICY-MIB which are obsoleted
         in Nokia SROS series systems 7.0 release."
    ::= { tmnxRoutePolicyGroups 22 }

tmnxRPPolicyObjectsV8v0Group     OBJECT-GROUP
    OBJECTS     {
        tRPAdminPSDefActMcRedirSvcId,
        tRPAdminPSDefActMcRedirIfIndex,
        tRPOperPSDefActMcRedirSvcId,
        tRPOperPSDefActMcRedirIfIndex
    }
    STATUS      current
    DESCRIPTION
        "The group of objects supporting management of policy statements and
         default action parameters on Nokia SROS series systems that were added
         in release 8.0."
    ::= { tmnxRoutePolicyGroups 25 }

tmnxRPQPPBV9v0R4Group            OBJECT-GROUP
    OBJECTS     {
        tRPAdminPSAcceptActionFC,
        tRPAdminPSAcceptActionFCPriority
    }
    STATUS      current
    DESCRIPTION
        "The group of objects supporting QoS policy propagation using BGP in
         release 9.0R4 Nokia SROS series systems."
    ::= { tmnxRoutePolicyGroups 26 }

tmnxRPPolicyEntryObjectsV9v0Group OBJECT-GROUP
    OBJECTS     {
        tRPOperPSParamsRowStatus,
        tRPOperPSParamsDescription,
        tRPOperPSParamsAction,
        tRPOperPSAcceptActionASPath,
        tRPOperPSAcceptActionASPathName,
        tRPOperPSAcceptActionASPathPrependCount,
        tRPOperPSAcceptActionCommunity1,
        tRPOperPSAcceptActionCommunityName1,
        tRPOperPSAcceptActionCommunity2,
        tRPOperPSAcceptActionCommunityName2,
        tRPOperPSAcceptActionOrigin,
        tRPOperPSAcceptActionLocalPreferenceSet,
        tRPOperPSAcceptActionLocalPreference,
        tRPOperPSAcceptActionMetric,
        tRPOperPSAcceptActionMetricValue,
        tRPOperPSAcceptActionPreference,
        tRPOperPSAcceptActionDamping,
        tRPOperPSAcceptActionNextHopSelf,
        tRPOperPSAcceptActionNextHop,
        tRPOperPSAcceptActionTag,
        tRPOperPSAcceptActionOspfType,
        tRPOperPSAcptActInetNextHopType,
        tRPOperPSAcptActInetNextHop,
        tRPOperPSToCriteriaRowStatus,
        tRPOperPSToCriteriaProtocol,
        tRPOperPSToCriteriaNeighborIpAddr,
        tRPOperPSToCriteriaNeighborPrefixList,
        tRPOperPSToCriteriaIsisLevel,
        tRPOperPSToCriteriaPrefixList1,
        tRPOperPSToCriteriaPrefixList2,
        tRPOperPSToCriteriaPrefixList3,
        tRPOperPSToCriteriaPrefixList4,
        tRPOperPSToCriteriaPrefixList5,
        tRPOperPSToCritNbrInetAddrType,
        tRPOperPSToCritNbrInetAddr,
        tRPOperPSToCriteriaInstanceId,
        tRPOperPSFromCriteriaRowStatus,
        tRPOperPSFromCriteriaProtocol,
        tRPOperPSFromCriteriaNeighborIpAddr,
        tRPOperPSFromCriteriaNeighborPrefixList,
        tRPOperPSFromCriteriaPrefixList1,
        tRPOperPSFromCriteriaPrefixList2,
        tRPOperPSFromCriteriaPrefixList3,
        tRPOperPSFromCriteriaPrefixList4,
        tRPOperPSFromCriteriaPrefixList5,
        tRPOperPSFromCriteriaASPath,
        tRPOperPSFromCriteriaCommunity,
        tRPOperPSFromCriteriaOrigin,
        tRPOperPSFromCriteriaOspfRouteType,
        tRPOperPSFromCriteriaArea,
        tRPOperPSFromCriteriaAreaConfigured,
        tRPOperPSFromCriteriaIsisLevel,
        tRPOperPSFromCriteriaIsisExternal,
        tRPOperPSFromCriteriaIgmpHostPrefixList,
        tRPOperPSFromCriteriaGrpAddrPrefixList,
        tRPOperPSFromCriteriaSrcAddr,
        tRPOperPSFromCriteriaInterface,
        tRPOperPSFromCriteriaTag,
        tRPOperPSFromCritNbrInetAddrType,
        tRPOperPSFromCritNbrInetAddr,
        tRPOperPSFromCritSrcInetAddrType,
        tRPOperPSFromCritSrcInetAddr,
        tRPOperPSFromCriteriaFamily,
        tRPOperPSFromCriteriaInstanceId,
        tRPAdminPSParamsRowStatus,
        tRPAdminPSParamsDescription,
        tRPAdminPSParamsAction,
        tRPAdminPSAcceptActionASPath,
        tRPAdminPSAcceptActionASPathName,
        tRPAdminPSAcceptActionASPathPrependCount,
        tRPAdminPSAcceptActionCommunity1,
        tRPAdminPSAcceptActionCommunityName1,
        tRPAdminPSAcceptActionCommunity2,
        tRPAdminPSAcceptActionCommunityName2,
        tRPAdminPSAcceptActionOrigin,
        tRPAdminPSAcceptActionLocalPreferenceSet,
        tRPAdminPSAcceptActionLocalPreference,
        tRPAdminPSAcceptActionMetric,
        tRPAdminPSAcceptActionMetricValue,
        tRPAdminPSAcceptActionPreference,
        tRPAdminPSAcceptActionDamping,
        tRPAdminPSAcceptActionNextHopSelf,
        tRPAdminPSAcceptActionNextHop,
        tRPAdminPSAcceptActionTag,
        tRPAdminPSAcceptActionOspfType,
        tRPAdminPSAcptActInetNextHopType,
        tRPAdminPSAcptActInetNextHop,
        tRPAdminPSToCriteriaRowStatus,
        tRPAdminPSToCriteriaProtocol,
        tRPAdminPSToCriteriaNeighborIpAddr,
        tRPAdminPSToCriteriaNeighborPrefixList,
        tRPAdminPSToCriteriaIsisLevel,
        tRPAdminPSToCriteriaPrefixList1,
        tRPAdminPSToCriteriaPrefixList2,
        tRPAdminPSToCriteriaPrefixList3,
        tRPAdminPSToCriteriaPrefixList4,
        tRPAdminPSToCriteriaPrefixList5,
        tRPAdminPSToCritNbrInetAddrType,
        tRPAdminPSToCritNbrInetAddr,
        tRPAdminPSToCriteriaInstanceId,
        tRPAdminPSFromCriteriaRowStatus,
        tRPAdminPSFromCriteriaProtocol,
        tRPAdminPSFromCriteriaNeighborIpAddr,
        tRPAdminPSFromCriteriaNeighborPrefixList,
        tRPAdminPSFromCriteriaPrefixList1,
        tRPAdminPSFromCriteriaPrefixList2,
        tRPAdminPSFromCriteriaPrefixList3,
        tRPAdminPSFromCriteriaPrefixList4,
        tRPAdminPSFromCriteriaPrefixList5,
        tRPAdminPSFromCriteriaASPath,
        tRPAdminPSFromCriteriaCommunity,
        tRPAdminPSFromCriteriaOrigin,
        tRPAdminPSFromCriteriaOspfRouteType,
        tRPAdminPSFromCriteriaArea,
        tRPAdminPSFromCriteriaAreaConfigured,
        tRPAdminPSFromCriteriaIsisLevel,
        tRPAdminPSFromCriteriaIsisExternal,
        tRPAdminPSFromCriteriaIgmpHostPrefixList,
        tRPAdminPSFromCriteriaGrpAddrPrefixList,
        tRPAdminPSFromCriteriaSrcAddr,
        tRPAdminPSFromCriteriaInterface,
        tRPAdminPSFromCriteriaTag,
        tRPAdminPSFromCritNbrInetAddrType,
        tRPAdminPSFromCritNbrInetAddr,
        tRPAdminPSFromCritSrcInetAddrType,
        tRPAdminPSFromCritSrcInetAddr,
        tRPAdminPSFromCriteriaFamily,
        tRPAdminPSFromCriteriaInstanceId,
        tRPAdminPSAcceptActionASPathPend,
        tRPOperPSAcceptActionASPathPend,
        tRPOperPSFromCriteriaMatchTag,
        tRPAdminPSFromCriteriaMatchTag,
        tRPAdminPSFromCriteriaState,
        tRPOperPSFromCriteriaState
    }
    STATUS      obsolete
    DESCRIPTION
        "The group of objects supporting management of route policy statement
         entries, 'to' filter parameters, 'from' filter parameters, and accept
         action parameters on Nokia SROS SR series systems 9.0 release."
    ::= { tmnxRoutePolicyGroups 27 }

tmnxRPPolicyObjectsV9v0Group     OBJECT-GROUP
    OBJECTS     {
        tRPAdminPSAcptActMcRedirSvcId,
        tRPAdminPSAcptActMcRedirIfIndex,
        tRPOperPSAcptActMcRedirSvcId,
        tRPOperPSAcptActMcRedirIfIndex
    }
    STATUS      current
    DESCRIPTION
        "The group of objects supporting management of policy statements and
         default action parameters on Nokia SROS series systems that were added
         in release 9.0."
    ::= { tmnxRoutePolicyGroups 30 }

tmnxRPPolicyObjectsV10v0Group    OBJECT-GROUP
    OBJECTS     {
        tRPAdminPSAcptActnMetricSource,
        tRPAdminPSDefActionMetricSource,
        tRPOperPSAcptActnMetricSource,
        tRPOperPSDefActionMetricSource,
        tRPAdminPSAcptActionAigpMetric,
        tRPAdminPSAcptActnAigpMetricVal,
        tRPOperPSAcptActionAigpMetric,
        tRPOperPSAcptActnAigpMetricVal,
        tRPOperCommunityExprString1,
        tRPOperCommunityExprString2,
        tRPOperCommunityExprString3,
        tRPOperCommunityExprString4,
        tRPOperCommunityExprRowStatus,
        tRPAdminCommunityExprString1,
        tRPAdminCommunityExprString2,
        tRPAdminCommunityExprString3,
        tRPAdminCommunityExprString4,
        tRPAdminCommunityExprRowStatus,
        tRPAdminPSDefActionAigpMetric,
        tRPAdminPSDefActnAigpMetricVal,
        tRPOperPSDefActionAigpMetric,
        tRPOperPSDefActnAigpMetricVal
    }
    STATUS      current
    DESCRIPTION
        "The group of objects supporting management of policy statements and
         default action parameters on Nokia SROS series systems that were added
         in release 10.0."
    ::= { tmnxRoutePolicyGroups 31 }

tmnxRPASPathGroupV10v0Group      OBJECT-GROUP
    OBJECTS     {
        tRPOperASPathGroupRowStatus,
        tRPOperASPathGroupASPathName,
        tRPOperASPathGroupASPathRegEx,
        tRPAdminASPathGroupRowStatus,
        tRPAdminASPathGroupASPathName,
        tRPAdminASPathGroupASPathRegEx,
        tRPOperPSFromCritASPathGroup,
        tRPAdminPSFromCritASPathGroup
    }
    STATUS      obsolete
    DESCRIPTION
        "The group of objects supporting management of AS-Path Groups on Nokia
         SROS series systems since release 10.0."
    ::= { tmnxRoutePolicyGroups 32 }

tmnxRPPolicyEntryObjV11v0Group   OBJECT-GROUP
    OBJECTS     {
        tRPOperPSFromCriteriaPolicy,
        tRPAdminPSFromCriteriaPolicy,
        tRPOperPSFromCommExprRowStatus,
        tRPOperPSFromCommExprString1,
        tRPOperPSFromCommExprString2,
        tRPOperPSFromCommExprString3,
        tRPOperPSFromCommExprString4,
        tRPAdminPSFromCommExprRowStatus,
        tRPAdminPSFromCommExprString1,
        tRPAdminPSFromCommExprString2,
        tRPAdminPSFromCommExprString3,
        tRPAdminPSFromCommExprString4
    }
    STATUS      current
    DESCRIPTION
        "The group of objects supporting management of route policy statement
         entries, 'to' filter parameters, 'from' filter parameters, and accept
         action parameters on Nokia SROS SR series systems 11.0 release."
    ::= { tmnxRoutePolicyGroups 33 }

tmnxRPAdminControlObjV11v0Group  OBJECT-GROUP
    OBJECTS     {
        tRPAdminControlResetExclusive
    }
    STATUS      current
    DESCRIPTION
        "The group of objects supporting management of transactions applying
         changed Administrative values to the Operational Route Policy database
         on Nokia SROS series systems since 11.0 release."
    ::= { tmnxRoutePolicyGroups 34 }

tmnxRPPolicyObjectsV11v0Group    OBJECT-GROUP
    OBJECTS     {
        tRPOperPolicyStatementRowStatus,
        tRPOperPolicyStatementDescription,
        tRPOperPolicyStatementDefaultAction,
        tRPOperPSDefaultActionASPath,
        tRPOperPSDefaultActionASPathName,
        tRPOperPSDefaultActionASPathPrependCount,
        tRPOperPSDefaultActionOrigin,
        tRPOperPSDefaultActionLocalPreferenceSet,
        tRPOperPSDefaultActionLocalPreference,
        tRPOperPSDefaultActionMetric,
        tRPOperPSDefaultActionMetricValue,
        tRPOperPSDefaultActionPreference,
        tRPOperPSDefaultActionDamping,
        tRPOperPSDefaultActionNextHopSelf,
        tRPOperPSDefaultActionNextHop,
        tRPOperPSDefaultActionTag,
        tRPOperPSDefaultActionOspfType,
        tRPOperPSDefActInetNextHopType,
        tRPOperPSDefActInetNextHop,
        tRPAdminPolicyStatementRowStatus,
        tRPAdminPolicyStatementDescription,
        tRPAdminPolicyStatementDefaultAction,
        tRPAdminPSDefaultActionASPath,
        tRPAdminPSDefaultActionASPathName,
        tRPAdminPSDefaultActionASPathPrependCount,
        tRPAdminPSDefaultActionOrigin,
        tRPAdminPSDefaultActionLocalPreferenceSet,
        tRPAdminPSDefaultActionLocalPreference,
        tRPAdminPSDefaultActionMetric,
        tRPAdminPSDefaultActionMetricValue,
        tRPAdminPSDefaultActionPreference,
        tRPAdminPSDefaultActionDamping,
        tRPAdminPSDefaultActionNextHopSelf,
        tRPAdminPSDefaultActionNextHop,
        tRPAdminPSDefaultActionTag,
        tRPAdminPSDefaultActionOspfType,
        tRPAdminPSDefActInetNextHopType,
        tRPAdminPSDefActInetNextHop,
        tRPAdminPSDefaultActionASPathPnd,
        tRPOperPSDefaultActionASPathPend,
        tRPOperPSParamsRowStatus,
        tRPOperPSParamsDescription,
        tRPOperPSParamsAction,
        tRPAdminPSParamsRowStatus,
        tRPAdminPSParamsDescription,
        tRPAdminPSParamsAction,
        tRPOperPSAcceptActionASPath,
        tRPOperPSAcceptActionASPathName,
        tRPOperPSAcceptActionASPathPrependCount,
        tRPOperPSAcceptActionOrigin,
        tRPOperPSAcceptActionLocalPreferenceSet,
        tRPOperPSAcceptActionLocalPreference,
        tRPOperPSAcceptActionMetric,
        tRPOperPSAcceptActionMetricValue,
        tRPOperPSAcceptActionPreference,
        tRPOperPSAcceptActionDamping,
        tRPOperPSAcceptActionNextHopSelf,
        tRPOperPSAcceptActionNextHop,
        tRPOperPSAcceptActionTag,
        tRPOperPSAcceptActionOspfType,
        tRPOperPSAcptActInetNextHopType,
        tRPOperPSAcptActInetNextHop,
        tRPOperPSAcceptActionASPathPend,
        tRPAdminPSAcceptActionASPath,
        tRPAdminPSAcceptActionASPathName,
        tRPAdminPSAcceptActionASPathPrependCount,
        tRPAdminPSAcceptActionOrigin,
        tRPAdminPSAcceptActionLocalPreferenceSet,
        tRPAdminPSAcceptActionLocalPreference,
        tRPAdminPSAcceptActionMetric,
        tRPAdminPSAcceptActionMetricValue,
        tRPAdminPSAcceptActionPreference,
        tRPAdminPSAcceptActionDamping,
        tRPAdminPSAcceptActionNextHopSelf,
        tRPAdminPSAcceptActionNextHop,
        tRPAdminPSAcceptActionTag,
        tRPAdminPSAcceptActionOspfType,
        tRPAdminPSAcptActInetNextHopType,
        tRPAdminPSAcptActInetNextHop,
        tRPAdminPSAcceptActionASPathPend,
        tRPOperPSDefActionAddComm1,
        tRPOperPSDefActionAddComm2,
        tRPOperPSDefActionAddComm3,
        tRPOperPSDefActionAddComm4,
        tRPOperPSDefActionAddComm5,
        tRPOperPSDefActionAddComm6,
        tRPOperPSDefActionAddComm7,
        tRPOperPSDefActionAddComm8,
        tRPOperPSDefActionAddComm9,
        tRPOperPSDefActionAddComm10,
        tRPOperPSDefActionAddComm11,
        tRPOperPSDefActionAddComm12,
        tRPOperPSDefActionAddComm13,
        tRPOperPSDefActionAddComm14,
        tRPOperPSDefActionAddComm15,
        tRPOperPSDefActionAddComm16,
        tRPOperPSDefActionAddComm17,
        tRPOperPSDefActionAddComm18,
        tRPOperPSDefActionAddComm19,
        tRPOperPSDefActionAddComm20,
        tRPOperPSDefActionAddComm21,
        tRPOperPSDefActionAddComm22,
        tRPOperPSDefActionAddComm23,
        tRPOperPSDefActionAddComm24,
        tRPOperPSDefActionAddComm25,
        tRPOperPSDefActionAddComm26,
        tRPOperPSDefActionAddComm27,
        tRPOperPSDefActionAddComm28,
        tRPOperPSDefActionRemoveComm1,
        tRPOperPSDefActionRemoveComm2,
        tRPOperPSDefActionRemoveComm3,
        tRPOperPSDefActionRemoveComm4,
        tRPOperPSDefActionRemoveComm5,
        tRPOperPSDefActionRemoveComm6,
        tRPOperPSDefActionRemoveComm7,
        tRPOperPSDefActionRemoveComm8,
        tRPOperPSDefActionRemoveComm9,
        tRPOperPSDefActionRemoveComm10,
        tRPOperPSDefActionRemoveComm11,
        tRPOperPSDefActionRemoveComm12,
        tRPOperPSDefActionRemoveComm13,
        tRPOperPSDefActionRemoveComm14,
        tRPOperPSDefActionRemoveComm15,
        tRPOperPSDefActionRemoveComm16,
        tRPOperPSDefActionRemoveComm17,
        tRPOperPSDefActionRemoveComm18,
        tRPOperPSDefActionRemoveComm19,
        tRPOperPSDefActionRemoveComm20,
        tRPOperPSDefActionRemoveComm21,
        tRPOperPSDefActionRemoveComm22,
        tRPOperPSDefActionRemoveComm23,
        tRPOperPSDefActionRemoveComm24,
        tRPOperPSDefActionRemoveComm25,
        tRPOperPSDefActionRemoveComm26,
        tRPOperPSDefActionRemoveComm27,
        tRPOperPSDefActionRemoveComm28,
        tRPOperPSDefActionReplaceComm1,
        tRPOperPSDefActionReplaceComm2,
        tRPOperPSDefActionReplaceComm3,
        tRPOperPSDefActionReplaceComm4,
        tRPOperPSDefActionReplaceComm5,
        tRPOperPSDefActionReplaceComm6,
        tRPOperPSDefActionReplaceComm7,
        tRPOperPSDefActionReplaceComm8,
        tRPOperPSDefActionReplaceComm9,
        tRPOperPSDefActionReplaceComm10,
        tRPOperPSDefActionReplaceComm11,
        tRPOperPSDefActionReplaceComm12,
        tRPOperPSDefActionReplaceComm13,
        tRPOperPSDefActionReplaceComm14,
        tRPOperPSDefActionReplaceComm15,
        tRPOperPSDefActionReplaceComm16,
        tRPOperPSDefActionReplaceComm17,
        tRPOperPSDefActionReplaceComm18,
        tRPOperPSDefActionReplaceComm19,
        tRPOperPSDefActionReplaceComm20,
        tRPOperPSDefActionReplaceComm21,
        tRPOperPSDefActionReplaceComm22,
        tRPOperPSDefActionReplaceComm23,
        tRPOperPSDefActionReplaceComm24,
        tRPOperPSDefActionReplaceComm25,
        tRPOperPSDefActionReplaceComm26,
        tRPOperPSDefActionReplaceComm27,
        tRPOperPSDefActionReplaceComm28,
        tRPAdminPSDefActionAddComm1,
        tRPAdminPSDefActionAddComm2,
        tRPAdminPSDefActionAddComm3,
        tRPAdminPSDefActionAddComm4,
        tRPAdminPSDefActionAddComm5,
        tRPAdminPSDefActionAddComm6,
        tRPAdminPSDefActionAddComm7,
        tRPAdminPSDefActionAddComm8,
        tRPAdminPSDefActionAddComm9,
        tRPAdminPSDefActionAddComm10,
        tRPAdminPSDefActionAddComm11,
        tRPAdminPSDefActionAddComm12,
        tRPAdminPSDefActionAddComm13,
        tRPAdminPSDefActionAddComm14,
        tRPAdminPSDefActionAddComm15,
        tRPAdminPSDefActionAddComm16,
        tRPAdminPSDefActionAddComm17,
        tRPAdminPSDefActionAddComm18,
        tRPAdminPSDefActionAddComm19,
        tRPAdminPSDefActionAddComm20,
        tRPAdminPSDefActionAddComm21,
        tRPAdminPSDefActionAddComm22,
        tRPAdminPSDefActionAddComm23,
        tRPAdminPSDefActionAddComm24,
        tRPAdminPSDefActionAddComm25,
        tRPAdminPSDefActionAddComm26,
        tRPAdminPSDefActionAddComm27,
        tRPAdminPSDefActionAddComm28,
        tRPAdminPSDefActionRemoveComm1,
        tRPAdminPSDefActionRemoveComm2,
        tRPAdminPSDefActionRemoveComm3,
        tRPAdminPSDefActionRemoveComm4,
        tRPAdminPSDefActionRemoveComm5,
        tRPAdminPSDefActionRemoveComm6,
        tRPAdminPSDefActionRemoveComm7,
        tRPAdminPSDefActionRemoveComm8,
        tRPAdminPSDefActionRemoveComm9,
        tRPAdminPSDefActionRemoveComm10,
        tRPAdminPSDefActionRemoveComm11,
        tRPAdminPSDefActionRemoveComm12,
        tRPAdminPSDefActionRemoveComm13,
        tRPAdminPSDefActionRemoveComm14,
        tRPAdminPSDefActionRemoveComm15,
        tRPAdminPSDefActionRemoveComm16,
        tRPAdminPSDefActionRemoveComm17,
        tRPAdminPSDefActionRemoveComm18,
        tRPAdminPSDefActionRemoveComm19,
        tRPAdminPSDefActionRemoveComm20,
        tRPAdminPSDefActionRemoveComm21,
        tRPAdminPSDefActionRemoveComm22,
        tRPAdminPSDefActionRemoveComm23,
        tRPAdminPSDefActionRemoveComm24,
        tRPAdminPSDefActionRemoveComm25,
        tRPAdminPSDefActionRemoveComm26,
        tRPAdminPSDefActionRemoveComm27,
        tRPAdminPSDefActionRemoveComm28,
        tRPAdminPSDefActionReplaceComm1,
        tRPAdminPSDefActionReplaceComm2,
        tRPAdminPSDefActionReplaceComm3,
        tRPAdminPSDefActionReplaceComm4,
        tRPAdminPSDefActionReplaceComm5,
        tRPAdminPSDefActionReplaceComm6,
        tRPAdminPSDefActionReplaceComm7,
        tRPAdminPSDefActionReplaceComm8,
        tRPAdminPSDefActionReplaceComm9,
        tRPAdminPSDefActionReplaceComm10,
        tRPAdminPSDefActionReplaceComm11,
        tRPAdminPSDefActionReplaceComm12,
        tRPAdminPSDefActionReplaceComm13,
        tRPAdminPSDefActionReplaceComm14,
        tRPAdminPSDefActionReplaceComm15,
        tRPAdminPSDefActionReplaceComm16,
        tRPAdminPSDefActionReplaceComm17,
        tRPAdminPSDefActionReplaceComm18,
        tRPAdminPSDefActionReplaceComm19,
        tRPAdminPSDefActionReplaceComm20,
        tRPAdminPSDefActionReplaceComm21,
        tRPAdminPSDefActionReplaceComm22,
        tRPAdminPSDefActionReplaceComm23,
        tRPAdminPSDefActionReplaceComm24,
        tRPAdminPSDefActionReplaceComm25,
        tRPAdminPSDefActionReplaceComm26,
        tRPAdminPSDefActionReplaceComm27,
        tRPAdminPSDefActionReplaceComm28,
        tRPOperPSAccActionAddComm1,
        tRPOperPSAccActionAddComm2,
        tRPOperPSAccActionAddComm3,
        tRPOperPSAccActionAddComm4,
        tRPOperPSAccActionAddComm5,
        tRPOperPSAccActionAddComm6,
        tRPOperPSAccActionAddComm7,
        tRPOperPSAccActionAddComm8,
        tRPOperPSAccActionAddComm9,
        tRPOperPSAccActionAddComm10,
        tRPOperPSAccActionAddComm11,
        tRPOperPSAccActionAddComm12,
        tRPOperPSAccActionAddComm13,
        tRPOperPSAccActionAddComm14,
        tRPOperPSAccActionAddComm15,
        tRPOperPSAccActionAddComm16,
        tRPOperPSAccActionAddComm17,
        tRPOperPSAccActionAddComm18,
        tRPOperPSAccActionAddComm19,
        tRPOperPSAccActionAddComm20,
        tRPOperPSAccActionAddComm21,
        tRPOperPSAccActionAddComm22,
        tRPOperPSAccActionAddComm23,
        tRPOperPSAccActionAddComm24,
        tRPOperPSAccActionAddComm25,
        tRPOperPSAccActionAddComm26,
        tRPOperPSAccActionAddComm27,
        tRPOperPSAccActionAddComm28,
        tRPOperPSAccActionRemoveComm1,
        tRPOperPSAccActionRemoveComm2,
        tRPOperPSAccActionRemoveComm3,
        tRPOperPSAccActionRemoveComm4,
        tRPOperPSAccActionRemoveComm5,
        tRPOperPSAccActionRemoveComm6,
        tRPOperPSAccActionRemoveComm7,
        tRPOperPSAccActionRemoveComm8,
        tRPOperPSAccActionRemoveComm9,
        tRPOperPSAccActionRemoveComm10,
        tRPOperPSAccActionRemoveComm11,
        tRPOperPSAccActionRemoveComm12,
        tRPOperPSAccActionRemoveComm13,
        tRPOperPSAccActionRemoveComm14,
        tRPOperPSAccActionRemoveComm15,
        tRPOperPSAccActionRemoveComm16,
        tRPOperPSAccActionRemoveComm17,
        tRPOperPSAccActionRemoveComm18,
        tRPOperPSAccActionRemoveComm19,
        tRPOperPSAccActionRemoveComm20,
        tRPOperPSAccActionRemoveComm21,
        tRPOperPSAccActionRemoveComm22,
        tRPOperPSAccActionRemoveComm23,
        tRPOperPSAccActionRemoveComm24,
        tRPOperPSAccActionRemoveComm25,
        tRPOperPSAccActionRemoveComm26,
        tRPOperPSAccActionRemoveComm27,
        tRPOperPSAccActionRemoveComm28,
        tRPOperPSAccActionReplaceComm1,
        tRPOperPSAccActionReplaceComm2,
        tRPOperPSAccActionReplaceComm3,
        tRPOperPSAccActionReplaceComm4,
        tRPOperPSAccActionReplaceComm5,
        tRPOperPSAccActionReplaceComm6,
        tRPOperPSAccActionReplaceComm7,
        tRPOperPSAccActionReplaceComm8,
        tRPOperPSAccActionReplaceComm9,
        tRPOperPSAccActionReplaceComm10,
        tRPOperPSAccActionReplaceComm11,
        tRPOperPSAccActionReplaceComm12,
        tRPOperPSAccActionReplaceComm13,
        tRPOperPSAccActionReplaceComm14,
        tRPOperPSAccActionReplaceComm15,
        tRPOperPSAccActionReplaceComm16,
        tRPOperPSAccActionReplaceComm17,
        tRPOperPSAccActionReplaceComm18,
        tRPOperPSAccActionReplaceComm19,
        tRPOperPSAccActionReplaceComm20,
        tRPOperPSAccActionReplaceComm21,
        tRPOperPSAccActionReplaceComm22,
        tRPOperPSAccActionReplaceComm23,
        tRPOperPSAccActionReplaceComm24,
        tRPOperPSAccActionReplaceComm25,
        tRPOperPSAccActionReplaceComm26,
        tRPOperPSAccActionReplaceComm27,
        tRPOperPSAccActionReplaceComm28,
        tRPAdminPSAccActionAddComm1,
        tRPAdminPSAccActionAddComm2,
        tRPAdminPSAccActionAddComm3,
        tRPAdminPSAccActionAddComm4,
        tRPAdminPSAccActionAddComm5,
        tRPAdminPSAccActionAddComm6,
        tRPAdminPSAccActionAddComm7,
        tRPAdminPSAccActionAddComm8,
        tRPAdminPSAccActionAddComm9,
        tRPAdminPSAccActionAddComm10,
        tRPAdminPSAccActionAddComm11,
        tRPAdminPSAccActionAddComm12,
        tRPAdminPSAccActionAddComm13,
        tRPAdminPSAccActionAddComm14,
        tRPAdminPSAccActionAddComm15,
        tRPAdminPSAccActionAddComm16,
        tRPAdminPSAccActionAddComm17,
        tRPAdminPSAccActionAddComm18,
        tRPAdminPSAccActionAddComm19,
        tRPAdminPSAccActionAddComm20,
        tRPAdminPSAccActionAddComm21,
        tRPAdminPSAccActionAddComm22,
        tRPAdminPSAccActionAddComm23,
        tRPAdminPSAccActionAddComm24,
        tRPAdminPSAccActionAddComm25,
        tRPAdminPSAccActionAddComm26,
        tRPAdminPSAccActionAddComm27,
        tRPAdminPSAccActionAddComm28,
        tRPAdminPSAccActionRemoveComm1,
        tRPAdminPSAccActionRemoveComm2,
        tRPAdminPSAccActionRemoveComm3,
        tRPAdminPSAccActionRemoveComm4,
        tRPAdminPSAccActionRemoveComm5,
        tRPAdminPSAccActionRemoveComm6,
        tRPAdminPSAccActionRemoveComm7,
        tRPAdminPSAccActionRemoveComm8,
        tRPAdminPSAccActionRemoveComm9,
        tRPAdminPSAccActionRemoveComm10,
        tRPAdminPSAccActionRemoveComm11,
        tRPAdminPSAccActionRemoveComm12,
        tRPAdminPSAccActionRemoveComm13,
        tRPAdminPSAccActionRemoveComm14,
        tRPAdminPSAccActionRemoveComm15,
        tRPAdminPSAccActionRemoveComm16,
        tRPAdminPSAccActionRemoveComm17,
        tRPAdminPSAccActionRemoveComm18,
        tRPAdminPSAccActionRemoveComm19,
        tRPAdminPSAccActionRemoveComm20,
        tRPAdminPSAccActionRemoveComm21,
        tRPAdminPSAccActionRemoveComm22,
        tRPAdminPSAccActionRemoveComm23,
        tRPAdminPSAccActionRemoveComm24,
        tRPAdminPSAccActionRemoveComm25,
        tRPAdminPSAccActionRemoveComm26,
        tRPAdminPSAccActionRemoveComm27,
        tRPAdminPSAccActionRemoveComm28,
        tRPAdminPSAccActionReplaceComm1,
        tRPAdminPSAccActionReplaceComm2,
        tRPAdminPSAccActionReplaceComm3,
        tRPAdminPSAccActionReplaceComm4,
        tRPAdminPSAccActionReplaceComm5,
        tRPAdminPSAccActionReplaceComm6,
        tRPAdminPSAccActionReplaceComm7,
        tRPAdminPSAccActionReplaceComm8,
        tRPAdminPSAccActionReplaceComm9,
        tRPAdminPSAccActionReplaceComm10,
        tRPAdminPSAccActionReplaceComm11,
        tRPAdminPSAccActionReplaceComm12,
        tRPAdminPSAccActionReplaceComm13,
        tRPAdminPSAccActionReplaceComm14,
        tRPAdminPSAccActionReplaceComm15,
        tRPAdminPSAccActionReplaceComm16,
        tRPAdminPSAccActionReplaceComm17,
        tRPAdminPSAccActionReplaceComm18,
        tRPAdminPSAccActionReplaceComm19,
        tRPAdminPSAccActionReplaceComm20,
        tRPAdminPSAccActionReplaceComm21,
        tRPAdminPSAccActionReplaceComm22,
        tRPAdminPSAccActionReplaceComm23,
        tRPAdminPSAccActionReplaceComm24,
        tRPAdminPSAccActionReplaceComm25,
        tRPAdminPSAccActionReplaceComm26,
        tRPAdminPSAccActionReplaceComm27,
        tRPAdminPSAccActionReplaceComm28
    }
    STATUS      current
    DESCRIPTION
        "The group of objects supporting management of policy statements and
         action parameters on Nokia SROS series systems."
    ::= { tmnxRoutePolicyGroups 35 }

tmnxRPPolicyEntryObjsV11v0Group  OBJECT-GROUP
    OBJECTS     {
        tRPOperPSToCriteriaRowStatus,
        tRPOperPSToCriteriaProtocol,
        tRPOperPSToCriteriaNeighborIpAddr,
        tRPOperPSToCriteriaNeighborPrefixList,
        tRPOperPSToCriteriaIsisLevel,
        tRPOperPSToCriteriaPrefixList1,
        tRPOperPSToCriteriaPrefixList2,
        tRPOperPSToCriteriaPrefixList3,
        tRPOperPSToCriteriaPrefixList4,
        tRPOperPSToCriteriaPrefixList5,
        tRPOperPSToCritNbrInetAddrType,
        tRPOperPSToCritNbrInetAddr,
        tRPOperPSToCriteriaInstanceId,
        tRPOperPSFromCriteriaRowStatus,
        tRPOperPSFromCriteriaProtocol,
        tRPOperPSFromCriteriaNeighborIpAddr,
        tRPOperPSFromCriteriaNeighborPrefixList,
        tRPOperPSFromCriteriaPrefixList1,
        tRPOperPSFromCriteriaPrefixList2,
        tRPOperPSFromCriteriaPrefixList3,
        tRPOperPSFromCriteriaPrefixList4,
        tRPOperPSFromCriteriaPrefixList5,
        tRPOperPSFromCriteriaASPath,
        tRPOperPSFromCriteriaCommunity,
        tRPOperPSFromCriteriaOrigin,
        tRPOperPSFromCriteriaOspfRouteType,
        tRPOperPSFromCriteriaArea,
        tRPOperPSFromCriteriaAreaConfigured,
        tRPOperPSFromCriteriaIsisLevel,
        tRPOperPSFromCriteriaIsisExternal,
        tRPOperPSFromCriteriaIgmpHostPrefixList,
        tRPOperPSFromCriteriaGrpAddrPrefixList,
        tRPOperPSFromCriteriaSrcAddr,
        tRPOperPSFromCriteriaInterface,
        tRPOperPSFromCriteriaTag,
        tRPOperPSFromCritNbrInetAddrType,
        tRPOperPSFromCritNbrInetAddr,
        tRPOperPSFromCritSrcInetAddrType,
        tRPOperPSFromCritSrcInetAddr,
        tRPOperPSFromCriteriaFamily,
        tRPOperPSFromCriteriaInstanceId,
        tRPAdminPSToCriteriaRowStatus,
        tRPAdminPSToCriteriaProtocol,
        tRPAdminPSToCriteriaNeighborIpAddr,
        tRPAdminPSToCriteriaNeighborPrefixList,
        tRPAdminPSToCriteriaIsisLevel,
        tRPAdminPSToCriteriaPrefixList1,
        tRPAdminPSToCriteriaPrefixList2,
        tRPAdminPSToCriteriaPrefixList3,
        tRPAdminPSToCriteriaPrefixList4,
        tRPAdminPSToCriteriaPrefixList5,
        tRPAdminPSToCritNbrInetAddrType,
        tRPAdminPSToCritNbrInetAddr,
        tRPAdminPSToCriteriaInstanceId,
        tRPAdminPSFromCriteriaRowStatus,
        tRPAdminPSFromCriteriaProtocol,
        tRPAdminPSFromCriteriaNeighborIpAddr,
        tRPAdminPSFromCriteriaNeighborPrefixList,
        tRPAdminPSFromCriteriaPrefixList1,
        tRPAdminPSFromCriteriaPrefixList2,
        tRPAdminPSFromCriteriaPrefixList3,
        tRPAdminPSFromCriteriaPrefixList4,
        tRPAdminPSFromCriteriaPrefixList5,
        tRPAdminPSFromCriteriaASPath,
        tRPAdminPSFromCriteriaCommunity,
        tRPAdminPSFromCriteriaOrigin,
        tRPAdminPSFromCriteriaOspfRouteType,
        tRPAdminPSFromCriteriaArea,
        tRPAdminPSFromCriteriaAreaConfigured,
        tRPAdminPSFromCriteriaIsisLevel,
        tRPAdminPSFromCriteriaIsisExternal,
        tRPAdminPSFromCriteriaIgmpHostPrefixList,
        tRPAdminPSFromCriteriaGrpAddrPrefixList,
        tRPAdminPSFromCriteriaSrcAddr,
        tRPAdminPSFromCriteriaInterface,
        tRPAdminPSFromCriteriaTag,
        tRPAdminPSFromCritNbrInetAddrType,
        tRPAdminPSFromCritNbrInetAddr,
        tRPAdminPSFromCritSrcInetAddrType,
        tRPAdminPSFromCritSrcInetAddr,
        tRPAdminPSFromCriteriaFamily,
        tRPAdminPSFromCriteriaInstanceId,
        tRPOperPSFromCriteriaMatchTag,
        tRPAdminPSFromCriteriaMatchTag,
        tRPAdminPSFromCriteriaState,
        tRPOperPSFromCriteriaState
    }
    STATUS      obsolete
    DESCRIPTION
        "The group of objects supporting management of route policy statement
         entries, 'to' filter parameters and 'from' filter parameters on Nokia
         SROS SR series systems 11.0 release."
    ::= { tmnxRoutePolicyGroups 36 }

tmnxRPPolicyObsoleteV11v0Group   OBJECT-GROUP
    OBJECTS     {
        tRPOperPSDefaultActionCommunity1,
        tRPOperPSDefaultActionCommunityName1,
        tRPOperPSDefaultActionCommunity2,
        tRPOperPSDefaultActionCommunityName2,
        tRPAdminPSDefaultActionCommunity1,
        tRPAdminPSDefaultActionCommunityName1,
        tRPAdminPSDefaultActionCommunity2,
        tRPAdminPSDefaultActionCommunityName2,
        tRPOperPSAcceptActionCommunity1,
        tRPOperPSAcceptActionCommunityName1,
        tRPOperPSAcceptActionCommunity2,
        tRPOperPSAcceptActionCommunityName2,
        tRPAdminPSAcceptActionCommunity1,
        tRPAdminPSAcceptActionCommunityName1,
        tRPAdminPSAcceptActionCommunity2,
        tRPAdminPSAcceptActionCommunityName2
    }
    STATUS      current
    DESCRIPTION
        "The group of objects in TIMETRA-ROUTE-POLICY-MIB which are obsoleted
         in Nokia SROS series systems 11.0 release."
    ::= { tmnxRoutePolicyGroups 37 }

tmnxRPPolicyObjectsV12v0Group    OBJECT-GROUP
    OBJECTS     {
        tRPAdminPSAcptActnSrcClassIndex,
        tRPAdminPSAcptActnDstClassIndex,
        tRPAdminPSDefActnSrcClassIndex,
        tRPAdminPSDefActnDstClassIndex,
        tRPOperPSAcptActnSrcClassIndex,
        tRPOperPSAcptActnDstClassIndex,
        tRPOperPSDefActnSrcClassIndex,
        tRPOperPSDefActnDstClassIndex,
        tRPAdminCommunityExprExactMatch,
        tRPOperCommunityExprExactMatch,
        tRPAdminPSFromCritExtMvpnType,
        tRPOperPSFromCritExtMvpnType,
        tRPAdminPSFromCritSrcAddrPfxList,
        tRPOperPSFromCritSrcAddrPfxList
    }
    STATUS      current
    DESCRIPTION
        "The group of objects supporting management of policy statements on
         Nokia SROS series systems 12.0 release."
    ::= { tmnxRoutePolicyGroups 38 }

tmnxRPPolicyVarObjectsGroup      OBJECT-GROUP
    OBJECTS     {
        tRPAdminPSPolicyVarRowStatus,
        tRPAdminPSPolicyVarValue,
        tRPOperPSPolicyVarRowStatus,
        tRPOperPSPolicyVarValue
    }
    STATUS      current
    DESCRIPTION
        "The group of objects supporting management of variables in policy
         statements on Nokia SROS series systems 12.0 release."
    ::= { tmnxRoutePolicyGroups 39 }

tmnxRPOperPSAcceptActionFCGroup  OBJECT-GROUP
    OBJECTS     {
        tRPOperPSAcceptActionFC,
        tRPOperPSAcceptActionFCPriority
    }
    STATUS      current
    DESCRIPTION
        "The group of objects supporting management of acceptance action
         statistics policy statements on Nokia SROS series systems 12.0
         release."
    ::= { tmnxRoutePolicyGroups 40 }

tRPAdminPSAcceptOrigValidGroup   OBJECT-GROUP
    OBJECTS     {
        tRPAdminPSAcptActnOrigValidState,
        tRPOperPSAcptActnOrigValidState,
        tRPAdminPSDefActnOrigValidState,
        tRPOperPSDefActnOrigValidState,
        tRPAdminPSFromCritOrigValidState,
        tRPOperPSFromCritOrigValidState
    }
    STATUS      current
    DESCRIPTION
        "The group of objects supporting management of origin validation state
         for policy statements on Nokia SROS series system 12.0 release."
    ::= { tmnxRoutePolicyGroups 41 }

tmnxRPCreationOriginGroup        OBJECT-GROUP
    OBJECTS     {
        tRPOperCommunityCreationOrigin,
        tRPOperPolicyStatementCrOrigin,
        tRPOperPSParamsCreationOrigin,
        tRPOperPSFromCritCreationOrigin,
        tRPOperPSAccActionAddCommCrOrig,
        tRPAdminCommunityCreationOrigin,
        tRPAdminPolicyStatementCrOrigin,
        tRPAdminPSParamsCreationOrigin,
        tRPAdminPSFromCritCreationOrigin,
        tRPAdminPSAccActionAddCommCrOrig
    }
    STATUS      current
    DESCRIPTION
        "The group of objects supporting management of policy statements
         creation origin objects on Nokia SROS series systems 12.0 release."
    ::= { tmnxRoutePolicyGroups 42 }

tmnxRPStickyEcmpGroup            OBJECT-GROUP
    OBJECTS     {
        tRPOperPSAcptActStickyEcmp,
        tRPOperPSDefActStickyEcmp,
        tRPAdminPSAcptActStickyEcmp,
        tRPAdminPSDefActStickyEcmp
    }
    STATUS      current
    DESCRIPTION
        "The group of objects supporting management of policy statements sticky
         ECMP hash objects on Nokia SROS series systems 12.0 release."
    ::= { tmnxRoutePolicyGroups 43 }

tmnxRPFlowSpecGroup              OBJECT-GROUP
    OBJECTS     {
        tRPOperPSFromCritFlowSrcPfxList,
        tRPOperPSFromCritFlowDstPfxList,
        tRPAdminPSFromCritFlowSrcPfxList,
        tRPAdminPSFromCritFlowDstPfxList
    }
    STATUS      current
    DESCRIPTION
        "The group of objects supporting management of policy statements
         flow-spec objects on Nokia SROS series systems 13.0 release."
    ::= { tmnxRoutePolicyGroups 44 }

tmnxRPAddPathsGroup              OBJECT-GROUP
    OBJECTS     {
        tRPAdminPSAcptActAddPathSndLimit,
        tRPOperPSAcptActAddPathSendLimit,
        tRPAdminPSDefActAddPathSendLimit,
        tRPOperPSDefActAddPathSendLimit
    }
    STATUS      current
    DESCRIPTION
        "The group of objects supporting management of policy statements
         ADD-PATHS objects on Nokia SROS series systems 13.0 release."
    ::= { tmnxRoutePolicyGroups 45 }

tmnxRPBackupPathGroup            OBJECT-GROUP
    OBJECTS     {
        tRPAdminPSAcptActInstBackupPath,
        tRPOperPSAcptActInstBackupPath,
        tRPAdminPSDefActInstBackupPath,
        tRPOperPSDefActInstBackupPath
    }
    STATUS      current
    DESCRIPTION
        "The group of objects supporting management of policy statements backup
         path objects on Nokia SROS series systems 13.0 release."
    ::= { tmnxRoutePolicyGroups 46 }

tmnxRPPrefixListV13v0Group       OBJECT-GROUP
    OBJECTS     {
        tRPAdminPfxListNameRowStatus,
        tRPOperPfxListNameRowStatus
    }
    STATUS      current
    DESCRIPTION
        "The group of objects supporting management of Prefix List objects on
         Nokia SROS series systems 13.0 release."
    ::= { tmnxRoutePolicyGroups 47 }

tmnxRPAdvertiseLabelGroup        OBJECT-GROUP
    OBJECTS     {
        tRPAdminPSAcptActAdvertiseLabel,
        tRPOperPSAcptActAdvertiseLabel,
        tRPAdminPSDefActAdvertiseLabel,
        tRPOperPSDefActAdvertiseLabel
    }
    STATUS      current
    DESCRIPTION
        "The group of objects supporting management of policy statements
         advertise label objects on Nokia SROS series systems 13.0 release."
    ::= { tmnxRoutePolicyGroups 48 }

tmnxRPBgpLeakingGroup            OBJECT-GROUP
    OBJECTS     {
        tRPAdminPSAcptActBgpLeaking,
        tRPOperPSAcptActBgpLeaking,
        tRPAdminPSDefActBgpLeaking,
        tRPOperPSDefActBgpLeaking
    }
    STATUS      current
    DESCRIPTION
        "The group of objects supporting management of policy statements BGP
         leaking objects on Nokia SROS series systems 12.0 release."
    ::= { tmnxRoutePolicyGroups 50 }

tmnxRPPolicyVarExtGroup          OBJECT-GROUP
    OBJECTS     {
        tRPAdminPSPolicyVarNumber,
        tRPAdminPSPolicyVarType,
        tRPAdminPSPolicyVarAddressType,
        tRPAdminPSPolicyVarAddress,
        tRPOperPSPolicyVarNumber,
        tRPOperPSPolicyVarType,
        tRPOperPSPolicyVarAddressType,
        tRPOperPSPolicyVarAddress,
        tRPAdminPSAcptActAigpMetricSrc,
        tRPAdminPSAcptActAigpMetricParam,
        tRPOperPSAcptActAigpMetricSource,
        tRPOperPSAcptActAigpMetricParam,
        tRPAdminPSDefActAigpMetricSource,
        tRPAdminPSDefActAigpMetricParam,
        tRPOperPSDefActAigpMetricSource,
        tRPOperPSDefActAigpMetricParam,
        tRPAdminPSAcptActASPathPendSrc,
        tRPAdminPSAcptActASPathPendParam,
        tRPOperPSAcptActASPathPendSource,
        tRPOperPSAcptActASPathPendParam,
        tRPAdminPSDefActASPathPendSource,
        tRPAdminPSDefActASPathPendParam,
        tRPOperPSDefActASPathPendSource,
        tRPOperPSDefActASPathPendParam,
        tRPOperPSAcptActLocalPrefSource,
        tRPOperPSAcptActLocalPrefParam,
        tRPAdminPSAcptActLocalPrefSource,
        tRPAdminPSAcptActLocalPrefParam,
        tRPOperPSDefActLocalPrefSource,
        tRPOperPSDefActLocalPrefParam,
        tRPAdminPSDefActLocalPrefSource,
        tRPAdminPSDefActLocalPrefParam,
        tRPOperPSAcptActMetricParam,
        tRPAdminPSAcptActMetricParam,
        tRPOperPSDefActMetricParam,
        tRPAdminPSDefActMetricParam,
        tRPOperPSAcptActNextHopSource,
        tRPOperPSAcptActNextHopParam,
        tRPAdminPSAcptActNextHopSource,
        tRPAdminPSAcptActNextHopParam,
        tRPOperPSDefActNextHopSource,
        tRPOperPSDefActNextHopParam,
        tRPAdminPSDefActNextHopSource,
        tRPAdminPSDefActNextHopParam,
        tRPOperPSAcptActOriginSource,
        tRPOperPSAcptActOriginParam,
        tRPAdminPSAcptActOriginSource,
        tRPAdminPSAcptActOriginParam,
        tRPOperPSDefActOriginSource,
        tRPOperPSDefActOriginParam,
        tRPAdminPSDefActOriginSource,
        tRPAdminPSDefActOriginParam,
        tRPOperPSAcptActOrigValStateSrc,
        tRPOperPSAcptActOrigValStatePar,
        tRPAdminPSAcptActOrigValStateSrc,
        tRPAdminPSAcptActOrigValStatePar,
        tRPOperPSDefActOrigValStateSrc,
        tRPOperPSDefActOrigValStatePar,
        tRPAdminPSDefActOrigValStateSrc,
        tRPAdminPSDefActOrigValStatePar,
        tRPOperPSAcptActPreferenceSource,
        tRPOperPSAcptActPreferenceParam,
        tRPAdminPSAcptActPreferenceSrc,
        tRPAdminPSAcptActPreferenceParam,
        tRPOperPSDefActPreferenceSource,
        tRPOperPSDefActPreferenceParam,
        tRPAdminPSDefActPreferenceSource,
        tRPAdminPSDefActPreferenceParam,
        tRPOperPSAcptActTagSource,
        tRPOperPSAcptActTagParam,
        tRPAdminPSAcptActTagSource,
        tRPAdminPSAcptActTagParam,
        tRPOperPSDefActTagSource,
        tRPOperPSDefActTagParam,
        tRPAdminPSDefActTagSource,
        tRPAdminPSDefActTagParam,
        tRPOperPSAcptActOspfTypeSource,
        tRPOperPSAcptActOspfTypeParam,
        tRPAdminPSAcptActOspfTypeSource,
        tRPAdminPSAcptActOspfTypeParam,
        tRPOperPSDefActOspfTypeSource,
        tRPOperPSDefActOspfTypeParam,
        tRPAdminPSDefActOspfTypeSource,
        tRPAdminPSDefActOspfTypeParam
    }
    STATUS      current
    DESCRIPTION
        "The group of objects supporting management of variables extension in
         policy statements on Nokia SROS series systems 13.0 release."
    ::= { tmnxRoutePolicyGroups 51 }

tmnxRPPSCondRouteGroup           OBJECT-GROUP
    OBJECTS     {
        tRPOperPSCondExprRowStatus,
        tRPOperPSCondExprRtExistString1,
        tRPAdminPSCondExprRowStatus,
        tRPAdminPSCondExprRtExistString1
    }
    STATUS      current
    DESCRIPTION
        "The group of objects supporting management of BGP conditional route
         advertisement in policy statements on Nokia SROS series systems 13.0
         release."
    ::= { tmnxRoutePolicyGroups 52 }

tmnxRPASPathGroupV14v0Group      OBJECT-GROUP
    OBJECTS     {
        tRPOperASPathGroupRowStatus,
        tRPOperASPathGroupASPathRegEx,
        tRPAdminASPathGroupRowStatus,
        tRPAdminASPathGroupASPathRegEx,
        tRPOperPSFromCritASPathGroup,
        tRPAdminPSFromCritASPathGroup
    }
    STATUS      current
    DESCRIPTION
        "The group of objects supporting management of AS-Path Groups on Nokia
         SROS series systems since release 14.0."
    ::= { tmnxRoutePolicyGroups 53 }

tmnxRPPolicyObsoleteV14v0Group   OBJECT-GROUP
    OBJECTS     {
        tRPOperASPathGroupASPathName,
        tRPAdminASPathGroupASPathName,
        tRPOperPSToCriteriaProtocol,
        tRPOperPSFromCriteriaProtocol,
        tRPAdminPSToCriteriaProtocol,
        tRPAdminPSFromCriteriaProtocol
    }
    STATUS      current
    DESCRIPTION
        "The group of objects in TIMETRA-ROUTE-POLICY-MIB which are obsoleted
         in Nokia SROS series systems 14.0 release."
    ::= { tmnxRoutePolicyGroups 54 }

tmnxRPPSCriteriaObjsV14v0Group   OBJECT-GROUP
    OBJECTS     {
        tRPOperPSToCriteriaRowStatus,
        tRPOperPSToCriteriaNeighborIpAddr,
        tRPOperPSToCriteriaNeighborPrefixList,
        tRPOperPSToCriteriaIsisLevel,
        tRPOperPSToCriteriaPrefixList1,
        tRPOperPSToCriteriaPrefixList2,
        tRPOperPSToCriteriaPrefixList3,
        tRPOperPSToCriteriaPrefixList4,
        tRPOperPSToCriteriaPrefixList5,
        tRPOperPSToCritNbrInetAddrType,
        tRPOperPSToCritNbrInetAddr,
        tRPOperPSToCriteriaInstanceId,
        tRPOperPSToCritProtocolBits,
        tRPOperPSFromCriteriaRowStatus,
        tRPOperPSFromCriteriaNeighborIpAddr,
        tRPOperPSFromCriteriaNeighborPrefixList,
        tRPOperPSFromCriteriaPrefixList1,
        tRPOperPSFromCriteriaPrefixList2,
        tRPOperPSFromCriteriaPrefixList3,
        tRPOperPSFromCriteriaPrefixList4,
        tRPOperPSFromCriteriaPrefixList5,
        tRPOperPSFromCriteriaASPath,
        tRPOperPSFromCriteriaCommunity,
        tRPOperPSFromCriteriaOrigin,
        tRPOperPSFromCriteriaOspfRouteType,
        tRPOperPSFromCriteriaArea,
        tRPOperPSFromCriteriaAreaConfigured,
        tRPOperPSFromCriteriaIsisLevel,
        tRPOperPSFromCriteriaIsisExternal,
        tRPOperPSFromCriteriaIgmpHostPrefixList,
        tRPOperPSFromCriteriaGrpAddrPrefixList,
        tRPOperPSFromCriteriaSrcAddr,
        tRPOperPSFromCriteriaInterface,
        tRPOperPSFromCriteriaTag,
        tRPOperPSFromCritNbrInetAddrType,
        tRPOperPSFromCritNbrInetAddr,
        tRPOperPSFromCritSrcInetAddrType,
        tRPOperPSFromCritSrcInetAddr,
        tRPOperPSFromCriteriaFamily,
        tRPOperPSFromCriteriaInstanceId,
        tRPOperPSFromCritProtocolBits,
        tRPAdminPSToCriteriaRowStatus,
        tRPAdminPSToCriteriaNeighborIpAddr,
        tRPAdminPSToCriteriaNeighborPrefixList,
        tRPAdminPSToCriteriaIsisLevel,
        tRPAdminPSToCriteriaPrefixList1,
        tRPAdminPSToCriteriaPrefixList2,
        tRPAdminPSToCriteriaPrefixList3,
        tRPAdminPSToCriteriaPrefixList4,
        tRPAdminPSToCriteriaPrefixList5,
        tRPAdminPSToCritNbrInetAddrType,
        tRPAdminPSToCritNbrInetAddr,
        tRPAdminPSToCriteriaInstanceId,
        tRPAdminPSToCritProtocolBits,
        tRPAdminPSFromCriteriaRowStatus,
        tRPAdminPSFromCriteriaNeighborIpAddr,
        tRPAdminPSFromCriteriaNeighborPrefixList,
        tRPAdminPSFromCriteriaPrefixList1,
        tRPAdminPSFromCriteriaPrefixList2,
        tRPAdminPSFromCriteriaPrefixList3,
        tRPAdminPSFromCriteriaPrefixList4,
        tRPAdminPSFromCriteriaPrefixList5,
        tRPAdminPSFromCriteriaASPath,
        tRPAdminPSFromCriteriaCommunity,
        tRPAdminPSFromCriteriaOrigin,
        tRPAdminPSFromCriteriaOspfRouteType,
        tRPAdminPSFromCriteriaArea,
        tRPAdminPSFromCriteriaAreaConfigured,
        tRPAdminPSFromCriteriaIsisLevel,
        tRPAdminPSFromCriteriaIsisExternal,
        tRPAdminPSFromCriteriaIgmpHostPrefixList,
        tRPAdminPSFromCriteriaGrpAddrPrefixList,
        tRPAdminPSFromCriteriaSrcAddr,
        tRPAdminPSFromCriteriaInterface,
        tRPAdminPSFromCriteriaTag,
        tRPAdminPSFromCritNbrInetAddrType,
        tRPAdminPSFromCritNbrInetAddr,
        tRPAdminPSFromCritSrcInetAddrType,
        tRPAdminPSFromCritSrcInetAddr,
        tRPAdminPSFromCriteriaFamily,
        tRPAdminPSFromCriteriaInstanceId,
        tRPOperPSFromCriteriaMatchTag,
        tRPAdminPSFromCriteriaMatchTag,
        tRPAdminPSFromCriteriaState,
        tRPOperPSFromCriteriaState,
        tRPAdminPSFromCritProtocolBits,
        tRPOperPSFromCritPathType,
        tRPAdminPSFromCritPathType
    }
    STATUS      current
    DESCRIPTION
        "The group of objects supporting management of route policy statement
         entries, 'to' filter parameters and 'from' filter parameters on Nokia
         SROS SR series systems 14.0 release."
    ::= { tmnxRoutePolicyGroups 56 }

tmnxRPCreationOriginV14v0Group   OBJECT-GROUP
    OBJECTS     {
        tRPAdminDampingCreationOrigin,
        tRPOperDampingCreationOrigin,
        tRPOperASPathCreationOrigin,
        tRPAdminASPathCreationOrigin,
        tRPOperInetPrefixListCrOrigin,
        tRPAdminInetPrefixListCrOrigin,
        tRPOperASPathGroupCrOrigin,
        tRPAdminASPathGroupCrOrigin,
        tRPOperPfxListNameCrOrigin,
        tRPAdminPfxListNameCrOrigin
    }
    STATUS      current
    DESCRIPTION
        "The group of objects supporting management of creation origin objects
         on Nokia SROS series systems 14.0 release."
    ::= { tmnxRoutePolicyGroups 57 }

tmnxRPPolicyExtV15v0Group        OBJECT-GROUP
    OBJECTS     {
        tRPOperPSFromCritASPathLength,
        tRPOperPSFromCritASPathLenInd,
        tRPOperPSFromCritASPLenUnique,
        tRPOperPSFromCritCommunityCount,
        tRPOperPSFromCritCommCountInd,
        tRPOperPSFromCritCommCountType,
        tRPOperPSFromCritMetric,
        tRPOperPSFromCritMetricInd,
        tRPOperPSFromCritLocalPref,
        tRPOperPSFromCritLocalPrefInd,
        tRPOperPSFromCritClusterAddrTp1,
        tRPOperPSFromCritClusterAddr1,
        tRPOperPSFromCritClusterPfxLen1,
        tRPOperPSFromCritClusterAddrTp2,
        tRPOperPSFromCritClusterAddr2,
        tRPOperPSFromCritClusterPfxLen2,
        tRPOperPSFromCritClusterAddrTp3,
        tRPOperPSFromCritClusterAddr3,
        tRPOperPSFromCritClusterPfxLen3,
        tRPOperPSFromCritClusterAddrTp4,
        tRPOperPSFromCritClusterAddr4,
        tRPOperPSFromCritClusterPfxLen4,
        tRPOperPSFromCritClusterAddrTp5,
        tRPOperPSFromCritClusterAddr5,
        tRPOperPSFromCritClusterPfxLen5,
        tRPOperPSFromCritClusterIdNone,
        tRPOperPSFromCritNextHopAddrTyp,
        tRPOperPSFromCritNextHopAddr,
        tRPOperPSFromCritNextHopPfxList,
        tRPAdminPSFromCritASPathLength,
        tRPAdminPSFromCritASPathLenInd,
        tRPAdminPSFromCritASPLenUnique,
        tRPAdminPSFromCritCommunityCount,
        tRPAdminPSFromCritCommCountInd,
        tRPAdminPSFromCritCommCountType,
        tRPAdminPSFromCritMetric,
        tRPAdminPSFromCritMetricInd,
        tRPAdminPSFromCritLocalPref,
        tRPAdminPSFromCritLocalPrefInd,
        tRPAdminPSFromCritClusterAddrTp1,
        tRPAdminPSFromCritClusterAddr1,
        tRPAdminPSFromCritClusterPfxLen1,
        tRPAdminPSFromCritClusterAddrTp2,
        tRPAdminPSFromCritClusterAddr2,
        tRPAdminPSFromCritClusterPfxLen2,
        tRPAdminPSFromCritClusterAddrTp3,
        tRPAdminPSFromCritClusterAddr3,
        tRPAdminPSFromCritClusterPfxLen3,
        tRPAdminPSFromCritClusterAddrTp4,
        tRPAdminPSFromCritClusterAddr4,
        tRPAdminPSFromCritClusterPfxLen4,
        tRPAdminPSFromCritClusterAddrTp5,
        tRPAdminPSFromCritClusterAddr5,
        tRPAdminPSFromCritClusterPfxLen5,
        tRPAdminPSFromCritClusterIdNone,
        tRPAdminPSFromCritNextHopAddrTyp,
        tRPAdminPSFromCritNextHopAddr,
        tRPAdminPSFromCritNextHopPfxList,
        tRPOperPSAcptActASPPendCountSrc,
        tRPOperPSAcptActASPPendCountPar,
        tRPOperPSAcptActASPPndMstRecent,
        tRPAdminPSAcptActASPPendCountSrc,
        tRPAdminPSAcptActASPPendCountPar,
        tRPAdminPSAcptActASPPndMstRecent,
        tRPOperPSDefActASPPendCountSrc,
        tRPOperPSDefActASPPendCountPar,
        tRPOperPSDefActASPPndMstRecent,
        tRPAdminPSDefActASPPendCountSrc,
        tRPAdminPSDefActASPPendCountPar,
        tRPAdminPSDefActASPPndMstRecent,
        tRPOperPSAcptActCreateUdpTunnel,
        tRPAdminPSAcptActCreateUdpTunnel,
        tRPOperPSDefActCreateUdpTunnel,
        tRPAdminPSDefActCreateUdpTunnel,
        tRPAdminASPGroupNameRowStatus,
        tRPAdminASPGroupNameCrOrigin,
        tRPOperASPGroupNameRowStatus,
        tRPOperASPGroupNameCrOrigin,
        tRPAdminCommNameRowStatus,
        tRPAdminCommNameCrOrigin,
        tRPOperCommNameRowStatus,
        tRPOperCommNameCrOrigin
    }
    STATUS      current
    DESCRIPTION
        "The group of objects supporting management of policy extension objects
         on Nokia SROS series systems 15.0 release."
    ::= { tmnxRoutePolicyGroups 58 }

tmnxRPPolicyExtV16v0Group        OBJECT-GROUP
    OBJECTS     {
        tRPOperGlobalVarRowStatus,
        tRPOperGlobalVarType,
        tRPOperGlobalVarString,
        tRPOperGlobalVarNumber,
        tRPOperGlobalVarAddressType,
        tRPOperGlobalVarAddress,
        tRPAdminGlobalVarRowStatus,
        tRPAdminGlobalVarType,
        tRPAdminGlobalVarString,
        tRPAdminGlobalVarNumber,
        tRPAdminGlobalVarAddressType,
        tRPAdminGlobalVarAddress,
        tRPOperPSAcptActResolveStatic,
        tRPOperPSDefActResolveStatic,
        tRPAdminPSAcptActResolveStatic,
        tRPAdminPSDefActResolveStatic,
        tRPOperPSAcptActAdminTagPolicy,
        tRPOperPSDefActAdminTagPolicy,
        tRPAdminPSAcptActAdminTagPolicy,
        tRPAdminPSDefActAdminTagPolicy,
        tRPOperPSFromCritExtEvpnType,
        tRPAdminPSFromCritExtEvpnType
    }
    STATUS      current
    DESCRIPTION
        "The group of objects supporting management of policy extension objects
         on Nokia SROS series systems 16.0 release."
    ::= { tmnxRoutePolicyGroups 59 }

tmnxRPPfxListExtV16v0Group       OBJECT-GROUP
    OBJECTS     {
        tRPOperPSToCritPrefixList1,
        tRPOperPSToCritPrefixList2,
        tRPOperPSToCritPrefixList3,
        tRPOperPSToCritPrefixList4,
        tRPOperPSToCritPrefixList5,
        tRPOperPSToCritPrefixList6,
        tRPOperPSToCritPrefixList7,
        tRPOperPSToCritPrefixList8,
        tRPOperPSToCritPrefixList9,
        tRPOperPSToCritPrefixList10,
        tRPOperPSToCritPrefixList11,
        tRPOperPSToCritPrefixList12,
        tRPOperPSToCritPrefixList13,
        tRPOperPSToCritPrefixList14,
        tRPOperPSToCritPrefixList15,
        tRPOperPSToCritPrefixList16,
        tRPOperPSToCritPrefixList17,
        tRPOperPSToCritPrefixList18,
        tRPOperPSToCritPrefixList19,
        tRPOperPSToCritPrefixList20,
        tRPOperPSToCritPrefixList21,
        tRPOperPSToCritPrefixList22,
        tRPOperPSToCritPrefixList23,
        tRPOperPSToCritPrefixList24,
        tRPOperPSToCritPrefixList25,
        tRPOperPSToCritPrefixList26,
        tRPOperPSToCritPrefixList27,
        tRPOperPSToCritPrefixList28,
        tRPOperPSFromCritPrefixList1,
        tRPOperPSFromCritPrefixList2,
        tRPOperPSFromCritPrefixList3,
        tRPOperPSFromCritPrefixList4,
        tRPOperPSFromCritPrefixList5,
        tRPOperPSFromCritPrefixList6,
        tRPOperPSFromCritPrefixList7,
        tRPOperPSFromCritPrefixList8,
        tRPOperPSFromCritPrefixList9,
        tRPOperPSFromCritPrefixList10,
        tRPOperPSFromCritPrefixList11,
        tRPOperPSFromCritPrefixList12,
        tRPOperPSFromCritPrefixList13,
        tRPOperPSFromCritPrefixList14,
        tRPOperPSFromCritPrefixList15,
        tRPOperPSFromCritPrefixList16,
        tRPOperPSFromCritPrefixList17,
        tRPOperPSFromCritPrefixList18,
        tRPOperPSFromCritPrefixList19,
        tRPOperPSFromCritPrefixList20,
        tRPOperPSFromCritPrefixList21,
        tRPOperPSFromCritPrefixList22,
        tRPOperPSFromCritPrefixList23,
        tRPOperPSFromCritPrefixList24,
        tRPOperPSFromCritPrefixList25,
        tRPOperPSFromCritPrefixList26,
        tRPOperPSFromCritPrefixList27,
        tRPOperPSFromCritPrefixList28,
        tRPAdminPSToCritPrefixList1,
        tRPAdminPSToCritPrefixList2,
        tRPAdminPSToCritPrefixList3,
        tRPAdminPSToCritPrefixList4,
        tRPAdminPSToCritPrefixList5,
        tRPAdminPSToCritPrefixList6,
        tRPAdminPSToCritPrefixList7,
        tRPAdminPSToCritPrefixList8,
        tRPAdminPSToCritPrefixList9,
        tRPAdminPSToCritPrefixList10,
        tRPAdminPSToCritPrefixList11,
        tRPAdminPSToCritPrefixList12,
        tRPAdminPSToCritPrefixList13,
        tRPAdminPSToCritPrefixList14,
        tRPAdminPSToCritPrefixList15,
        tRPAdminPSToCritPrefixList16,
        tRPAdminPSToCritPrefixList17,
        tRPAdminPSToCritPrefixList18,
        tRPAdminPSToCritPrefixList19,
        tRPAdminPSToCritPrefixList20,
        tRPAdminPSToCritPrefixList21,
        tRPAdminPSToCritPrefixList22,
        tRPAdminPSToCritPrefixList23,
        tRPAdminPSToCritPrefixList24,
        tRPAdminPSToCritPrefixList25,
        tRPAdminPSToCritPrefixList26,
        tRPAdminPSToCritPrefixList27,
        tRPAdminPSToCritPrefixList28,
        tRPAdminPSFromCritPrefixList1,
        tRPAdminPSFromCritPrefixList2,
        tRPAdminPSFromCritPrefixList3,
        tRPAdminPSFromCritPrefixList4,
        tRPAdminPSFromCritPrefixList5,
        tRPAdminPSFromCritPrefixList6,
        tRPAdminPSFromCritPrefixList7,
        tRPAdminPSFromCritPrefixList8,
        tRPAdminPSFromCritPrefixList9,
        tRPAdminPSFromCritPrefixList10,
        tRPAdminPSFromCritPrefixList11,
        tRPAdminPSFromCritPrefixList12,
        tRPAdminPSFromCritPrefixList13,
        tRPAdminPSFromCritPrefixList14,
        tRPAdminPSFromCritPrefixList15,
        tRPAdminPSFromCritPrefixList16,
        tRPAdminPSFromCritPrefixList17,
        tRPAdminPSFromCritPrefixList18,
        tRPAdminPSFromCritPrefixList19,
        tRPAdminPSFromCritPrefixList20,
        tRPAdminPSFromCritPrefixList21,
        tRPAdminPSFromCritPrefixList22,
        tRPAdminPSFromCritPrefixList23,
        tRPAdminPSFromCritPrefixList24,
        tRPAdminPSFromCritPrefixList25,
        tRPAdminPSFromCritPrefixList26,
        tRPAdminPSFromCritPrefixList27,
        tRPAdminPSFromCritPrefixList28
    }
    STATUS      current
    DESCRIPTION
        "The group of objects supporting management of policy prefix-list match
         criteria extension objects on Nokia SROS series systems 16.0 release."
    ::= { tmnxRoutePolicyGroups 60 }

tmnxRPPolicyExtV19v0Group        OBJECT-GROUP
    OBJECTS     {
        tRPOperPSPolicyVarDecimal,
        tRPAdminPSPolicyVarDecimal,
        tRPOperGlobalVarDecimal,
        tRPAdminGlobalVarDecimal,
        tRPOperPSDefActBgpMedSource,
        tRPOperPSDefActBgpMedValue,
        tRPOperPSDefActBgpMedExpr,
        tRPOperPSAcptActBgpMedSource,
        tRPOperPSAcptActBgpMedValue,
        tRPOperPSAcptActBgpMedExpr,
        tRPAdminPSDefActBgpMedSource,
        tRPAdminPSDefActBgpMedValue,
        tRPAdminPSDefActBgpMedExpr,
        tRPAdminPSAcptActBgpMedSource,
        tRPAdminPSAcptActBgpMedValue,
        tRPAdminPSAcptActBgpMedExpr,
        tRPOperPSDefActDisableRtInstall,
        tRPOperPSAcptActDisableRtInstall,
        tRPAdminPSDefActDisableRtInstall,
        tRPAdminPSAcptActDisableRtInst,
        tRPOperPSDefActSrLabelIndex,
        tRPOperPSDefActSrLblIndPrefIgp,
        tRPOperPSAcptActSrLabelIndex,
        tRPOperPSAcptActSrLblIndPrefIgp,
        tRPAdminPSDefActSrLabelIndex,
        tRPAdminPSDefActSrLblIndPrefIgp,
        tRPAdminPSAcptActSrLabelIndex,
        tRPAdminPSAcptActSrLblIndPrefIgp
    }
    STATUS      current
    DESCRIPTION
        "The group of objects supporting management of policy extension objects
         on Nokia SROS series systems 19.0 release."
    ::= { tmnxRoutePolicyGroups 61 }

tmnxRPPolicyV20v0Group           OBJECT-GROUP
    OBJECTS     {
        tRPOperPSDefActNextHopPeerAddr,
        tRPOperPSAcptActNextHopPeerAddr,
        tRPAdminPSDefActNextHopPeerAddr,
        tRPAdminPSAcptActNextHopPeerAddr,
        tRPOperPSDefActBgpHighPriority,
        tRPOperPSAcptActBgpHighPriority,
        tRPAdminPSDefActBgpHighPriority,
        tRPAdminPSAcptActBgpHighPriority,
        tRPOperPSFromCrAggrContributor,
        tRPAdminPSFromCrAggrContributor,
        tRPOperPSDefActFlexAlgo,
        tRPOperPSAcptActFlexAlgo,
        tRPAdminPSDefActFlexAlgo,
        tRPAdminPSAcptActFlexAlgo,
        tRPOperPSDefActBgpTunnelMetric,
        tRPOperPSDefActBgpTMetPrefAigp,
        tRPOperPSAcptActBgpTunnelMetric,
        tRPOperPSAcptActBgpTMetPrefAigp,
        tRPAdminPSDefActBgpTunnelMetric,
        tRPAdminPSDefActBgpTMetPrefAigp,
        tRPAdminPSAcptActBgpTunnelMetric,
        tRPAdminPSAcptActBgpTMetPrefAigp,
        tRPOperPfxListToCrOrigin,
        tRPOperPfxListToRowStatus,
        tRPAdminPfxListToCrOrigin,
        tRPAdminPfxListToRowStatus,
        tRPOperPfxListAddrMaskRowStatus,
        tRPOperPfxListAddrMaskCrOrigin,
        tRPAdminPfxListAddrMaskRowStatus,
        tRPAdminPfxListAddrMaskCrOrigin,
        tRPOperPSDefActEgressStats,
        tRPOperPSDefActIngressStats,
        tRPOperPSAcptActEgressStats,
        tRPOperPSAcptActIngressStats,
        tRPAdminPSDefActEgressStats,
        tRPAdminPSDefActIngressStats,
        tRPAdminPSAcptActEgressStats,
        tRPAdminPSAcptActIngressStats,
        tRPOperPSDefActSrMaintPolicy,
        tRPOperPSAcptActSrMaintPolicy,
        tRPAdminPSDefActSrMaintPolicy,
        tRPAdminPSAcptActSrMaintPolicy,
        tRPOperPSFromCrEndpointAddrTyp,
        tRPOperPSFromCrEndpointAddr,
        tRPOperPSFromCritColor,
        tRPOperPSFromCritDistinguisher,
        tRPAdminPSFromCrEndpointAddrTyp,
        tRPAdminPSFromCrEndpointAddr,
        tRPAdminPSFromCritColor,
        tRPAdminPSFromCritDistinguisher
    }
    STATUS      current
    DESCRIPTION
        "The group of objects supporting management of route policy objects on
         Nokia SROS series systems 20.0 release."
    ::= { tmnxRoutePolicyGroups 62 }

tmnxRPFromCritInterfaceGroup     OBJECT-GROUP
    OBJECTS     {
        tRPOperPSFromCritIntfServiceId,
        tRPOperPSFromCritInterface1,
        tRPOperPSFromCritInterface2,
        tRPOperPSFromCritInterface3,
        tRPOperPSFromCritInterface4,
        tRPOperPSFromCritInterface5,
        tRPOperPSFromCritInterface6,
        tRPOperPSFromCritInterface7,
        tRPOperPSFromCritInterface8,
        tRPOperPSFromCritInterface9,
        tRPOperPSFromCritInterface10,
        tRPAdminPSFromCritIntfServiceId,
        tRPAdminPSFromCritInterface1,
        tRPAdminPSFromCritInterface2,
        tRPAdminPSFromCritInterface3,
        tRPAdminPSFromCritInterface4,
        tRPAdminPSFromCritInterface5,
        tRPAdminPSFromCritInterface6,
        tRPAdminPSFromCritInterface7,
        tRPAdminPSFromCritInterface8,
        tRPAdminPSFromCritInterface9,
        tRPAdminPSFromCritInterface10
    }
    STATUS      current
    DESCRIPTION
        "The group of objects supporting management of matching multiple
         interfaces in policy statements on Nokia SROS series systems 20.0
         release."
    ::= { tmnxRoutePolicyGroups 63 }

tmnxRPPolicyV21v0Group           OBJECT-GROUP
    OBJECTS     {
        tRPOperPSDefActNatPolicy,
        tRPOperPSAcptActNatPolicy,
        tRPAdminPSDefActNatPolicy,
        tRPAdminPSAcptActNatPolicy,
        tRPOperPSDefActCreateMplsTunl,
        tRPOperPSAcptActCreateMplsTunl,
        tRPAdminPSDefActCreateMplsTunl,
        tRPAdminPSAcptActCreateMplsTunl
    }
    STATUS      current
    DESCRIPTION
        "The group of objects supporting management of route policy objects on
         Nokia SROS series systems 21.0 release."
    ::= { tmnxRoutePolicyGroups 64 }

tmnxRPPolicyV22v0Group           OBJECT-GROUP
    OBJECTS     {
        tRPOperPSDefActBgpTMetPrefMed,
        tRPOperPSAcptActBgpTMetPrefMed,
        tRPAdminPSDefActBgpTMetPrefMed,
        tRPAdminPSAcptActBgpTMetPrefMed,
        tRPOperPSDefActPrefTransFrr,
        tRPOperPSAcptActPrefTransFrr,
        tRPAdminPSDefActPrefTransFrr,
        tRPAdminPSAcptActPrefTransFrr
    }
    STATUS      current
    DESCRIPTION
        "The group of objects supporting management of route policy objects on
         Nokia SROS series systems 22.0 release."
    ::= { tmnxRoutePolicyGroups 65 }

tmnxRPPolicyV23v0Group           OBJECT-GROUP
    OBJECTS     {
        tRPOperPSFromCritRDList,
        tRPAdminPSFromCritRDList,
        tRPOperRDListRowStatus,
        tRPOperRDListCrOrigin,
        tRPOperRDRowStatus,
        tRPOperRDCrOrigin,
        tRPAdminRDListRowStatus,
        tRPAdminRDListCrOrigin,
        tRPAdminRDRowStatus,
        tRPAdminRDCrOrigin,
        tRPOperPSDefActSrv6Locator,
        tRPOperPSAcptActSrv6Locator,
        tRPAdminPSDefActSrv6Locator,
        tRPAdminPSAcptActSrv6Locator,
        tRPOperPSDefActSrv6MSLocator,
        tRPOperPSAcptActSrv6MSLocator,
        tRPAdminPSDefActSrv6MSLocator,
        tRPAdminPSAcptActSrv6MSLocator,
        tRPOperPSDActSrv6RPathBfdSidSrc,
        tRPOperPSDActSrv6RPathBfdSidTyp,
        tRPOperPSDActSrv6RPathBfdSid,
        tRPOperPSDActSrv6RPathBfdSidPar,
        tRPOperPSAActSrv6RPathBfdSidSrc,
        tRPOperPSAActSrv6RPathBfdSidTyp,
        tRPOperPSAActSrv6RPathBfdSid,
        tRPOperPSAActSrv6RPathBfdSidPar,
        tRPAdminPSDActSrv6RPathBfdSidSrc,
        tRPAdminPSDActSrv6RPathBfdSidTyp,
        tRPAdminPSDActSrv6RPathBfdSid,
        tRPAdminPSDActSrv6RPathBfdSidPar,
        tRPAdminPSAActSrv6RPathBfdSidSrc,
        tRPAdminPSAActSrv6RPathBfdSidTyp,
        tRPAdminPSAActSrv6RPathBfdSid,
        tRPAdminPSAActSrv6RPathBfdSidPar,
        tRPOperPSFromCritSrv6Tlv,
        tRPOperPSFromCritSrv6SidPfxSrc,
        tRPOperPSFromCritSrv6SidPfxType,
        tRPOperPSFromCritSrv6SidPfxAddr,
        tRPOperPSFromCritSrv6SidPfxLen,
        tRPOperPSFromCritSrv6SidPfxPar,
        tRPAdminPSFromCritSrv6Tlv,
        tRPAdminPSFromCritSrv6SidPfxSrc,
        tRPAdminPSFromCritSrv6SidPfxType,
        tRPAdminPSFromCritSrv6SidPfxAddr,
        tRPAdminPSFromCritSrv6SidPfxLen,
        tRPAdminPSFromCritSrv6SidPfxPar,
        tRPOperGlobalVarPrefixLength,
        tRPAdminGlobalVarPrefixLength,
        tRPOperPSPolicyVarPrefixLength,
        tRPAdminPSPolicyVarPrefixLength,
        tRPOperPSDActSrReturnPathBfdLbl,
        tRPOperPSAActSrReturnPathBfdLbl,
        tRPAdminPSDActSrReturnPathBfdLbl,
        tRPAdminPSAActSrReturnPathBfdLbl,
        tRPOperPSFromCrPLOvrRowStatus,
        tRPOperPSFromCrPLOvrType,
        tRPOperPSFromCrPLOvrCrOrigin,
        tRPOperPSFromCrPLOvrThroughLen,
        tRPOperPSFromCrPLOvrBeginLen,
        tRPAdminPSFromCrPLOvrRowStatus,
        tRPAdminPSFromCrPLOvrType,
        tRPAdminPSFromCrPLOvrCrOrigin,
        tRPAdminPSFromCrPLOvrThroughLen,
        tRPAdminPSFromCrPLOvrBeginLen
    }
    STATUS      current
    DESCRIPTION
        "The group of objects supporting management of route policy objects on
         Nokia SROS series systems 23.0 release."
    ::= { tmnxRoutePolicyGroups 66 }

tmnxRoutePolicyDCCompliances     OBJECT IDENTIFIER ::= { tmnxRoutePolicyConformance 3 }

tmnxRoutePolicyDCGroups          OBJECT IDENTIFIER ::= { tmnxRoutePolicyConformance 4 }

tmnxRoutePolicyMobGwCompliances  OBJECT IDENTIFIER ::= { tmnxRoutePolicyConformance 5 }

tmnxRoutePolicyMobGatewayGroups  OBJECT IDENTIFIER ::= { tmnxRoutePolicyConformance 6 }

tRoutePolicyNotifyPrefix         OBJECT IDENTIFIER ::= { tmnxSRNotifyPrefix 17 }

tRoutePolicyNotifications        OBJECT IDENTIFIER ::= { tRoutePolicyNotifyPrefix 0 }

END
