TIMETRA-ISIS-NG-MIB DEFINITIONS ::= BEGIN

IMPORTS
    InterfaceIndex, InterfaceIndexOrZero
                                                         FROM IF-MIB
    InetAddress, InetAddressIPv6,
    InetAddressPrefixLength,
    InetAddressType,
    InetAutonomousSystemNumber
                                                         FROM INET-ADDRESS-MIB
    SNPAAddress, SystemID, isisCircIndex,
    isisISAdjIndex, isisISAdjState,
    isisManAreaAddrExistState,
    isisSysInstance, isisSysL1State,
    isisSysL2State
                                                         FROM ISIS-MIB
    MODULE-COMPLIANCE, NOTIFICATION-GROUP,
    OBJECT-GROUP
                                                         FROM SNMPv2-CONF
    Counter32, Counter64, Gauge32,
    Integer32, IpAddress, MODULE-IDENTITY,
    NOTIFICATION-TYPE, OBJECT-TYPE,
    TimeTicks, Unsigned32
                                                         FROM SNMPv2-SMI
    DisplayString, MacAddress, RowStatus,
    TEXTUAL-CONVENTION, TimeInterval,
    TimeStamp, TruthValue
                                                         FROM SNMPv2-TC
    timetraSRMIBModules, tmnxSRConfs,
    tmnxSRNotifyPrefix, tmnxSRObjs
                                                         FROM TIMETRA-GLOBAL-MIB
    vRtrSrv6LocatorName,
    vRtrSrv6MSLocatorName
                                                         FROM TIMETRA-SRV6-MIB
    TLNamedItemOrEmpty, TNamedItemOrEmpty,
    TResolveStatus, TSrv6EndpointBehavior,
    TmnxAdjacencySetFamilyType,
    TmnxAdminState, TmnxAlgorithmId,
    TmnxEnabledDisabled, TmnxFlexAlgoId,
    TmnxHigh32, TmnxIgpSCFamilyType,
    TmnxLow32, TmnxOperState,
    TmnxPrefixSidFullRange,
    TmnxReferenceBandwidth
                                                         FROM TIMETRA-TC-MIB
    TmnxInetCidrNextHopOwner,
    TmnxInetCidrNextHopType, vRtrID,
    vRtrIfIndex
                                                         FROM TIMETRA-VRTR-MIB
    ;

timetraIsisNgMIBModule           MODULE-IDENTITY
    LAST-UPDATED "202402010000Z"
    ORGANIZATION "Nokia"
    CONTACT-INFO
        "Nokia SROS Support
         Web: http://www.nokia.com"
    DESCRIPTION
        "This document is the SNMP MIB module to manage and provision the
         extensions to the ISIS routing protocol for the Nokia SROS device.

         Copyright 2013-2024 Nokia. All rights reserved. Reproduction of this
         document is authorized on the condition that the foregoing copyright
         notice is included.

         This SNMP MIB module (Specification) embodies Nokia's
         proprietary intellectual property.  Nokia retains
         all title and ownership in the Specification, including any
         revisions.

         Nokia grants all interested parties a non-exclusive license to use and
         distribute an unmodified copy of this Specification in connection with
         management of Nokia products, and without fee, provided this copyright
         notice and license appear on all copies.

         This Specification is supplied 'as is', and Nokia makes no warranty,
         either express or implied, as to the use, operation, condition, or
         performance of the Specification."

    REVISION    "202402010000Z"
    DESCRIPTION
        "Rev 24.0               01 Feb 2024 00:00
         24.0 release of the TIMETRA-ISIS-NG-MIB."

    REVISION    "202302010000Z"
    DESCRIPTION
        "Rev 23.0               01 Feb 2023 00:00
         23.0 release of the TIMETRA-ISIS-NG-MIB."

    REVISION    "202202010000Z"
    DESCRIPTION
        "Rev 22.0               01 Feb 2022 00:00
         22.0 release of the TIMETRA-ISIS-NG-MIB."

    REVISION    "202102010000Z"
    DESCRIPTION
        "Rev 21.0               01 Feb 2021 00:00
         21.0 release of the TIMETRA-ISIS-NG-MIB."

    REVISION    "202002010000Z"
    DESCRIPTION
        "Rev 20.0               01 Feb 2020 00:00
         20.0 release of the TIMETRA-ISIS-NG-MIB."

    REVISION    "201904010000Z"
    DESCRIPTION
        "Rev 19.0               01 April 2019 00:00
         19.0 release of the TIMETRA-ISIS-NG-MIB."

    REVISION    "201802010000Z"
    DESCRIPTION
        "Rev 16.0               01 Feb 2018 00:00
         16.0 release of the TIMETRA-ISIS-NG-MIB."

    REVISION    "201603010000Z"
    DESCRIPTION
        "Rev 15.0               01 Mar 2016 00:00
         15.0 release of the TIMETRA-ISIS-NG-MIB."

    REVISION    "201503010000Z"
    DESCRIPTION
        "Rev 14.0               01 Mar 2015 00:00
         14.0 release of the TIMETRA-ISIS-NG-MIB."

    REVISION    "201501010000Z"
    DESCRIPTION
        "Rev 13.0               01 Jan 2015 00:00
         13.0 release of the TIMETRA-ISIS-NG-MIB."

    REVISION    "201304080000Z"
    DESCRIPTION
        "Rev 0.1                08 Apr 2013 00:00
         Initial version of the TIMETRA-ISIS-NG-MIB."

    ::= { timetraSRMIBModules 88 }

TmnxIsisLSPBuffSize              ::= TEXTUAL-CONVENTION
    STATUS      current
    DESCRIPTION
        "TmnxIsisLSPBuffSize is the extended integer sub range for LSP size."
    SYNTAX      Integer32 (490..9190)

TmnxIsisLSPBuffExtSize           ::= TEXTUAL-CONVENTION
    STATUS      current
    DESCRIPTION
        "TmnxIsisLSPBuffExtSize is the extended integer sub range for LSP size
         for increased interface mtu in fp4 cards."
    SYNTAX      Integer32 (490..9778)

TmnxIsisRoutingTopology          ::= TEXTUAL-CONVENTION
    STATUS      current
    DESCRIPTION
        "TmnxIsisRoutingTopology specifies the isis routing topology.

         native(1) - Indicates standard topology.

         mt(2) - Indicates multi-topology for IPv4/IPv6 unicast/multicast
         routing."
    SYNTAX      INTEGER {
        none   (0),
        native (1),
        mt     (2)
    }

TmnxIsisPrefixSidFlags           ::= TEXTUAL-CONVENTION
    STATUS      current
    DESCRIPTION
        "TmnxIsisPrefixSidFlags indicates the flags of a Prefix-SID as defined
         by IETF segment routing.

         bitUsed(0)  - If set, SID label or index value for this prefix is valid.
         bitR   (1)  - Re-advertisement flag.  If set, then the prefix to
                       which this Prefix-SID is attached, has been propagated by the
                       router either from another level (i.e.: from level-1 to level-2
                       or the opposite) or from redistribution (e.g.: from another
                       protocol).
         bitN   (2)  - Node-SID flag. The N-Flag is set on Prefix-SIDs
                       attached to a router loopback address.
         bitP   (3)  - no-PHP flag. If set, then the penultimate hop MUST NOT
                       pop the Prefix-SID before delivering the packet to the node
                       that advertised the Prefix-SID.
         bitE   (4)  - Explicit-Null Flag.  If set, any upstream neighbor
                       of the Prefix-SID originator MUST replace the Prefix-SID with
                       a Prefix-SID having an Explicit-NULL value (0 for IPv4 and 2 for
                       IPv6) before forwarding the packet.
         bitV   (5)  - Value flag. If set, then the Prefix-SID carries a
                       value (instead of an index).
         bitL   (6)  - Local Flag.  If set, then the value/index carried by
                       the Prefix-SID has local significance."
    SYNTAX      BITS {
        bitUsed (0),
        bitR    (1),
        bitN    (2),
        bitP    (3),
        bitE    (4),
        bitV    (5),
        bitL    (6)
    }

TmnxIsisSpfTriggerReason         ::= TEXTUAL-CONVENTION
    STATUS      current
    DESCRIPTION
        "TmnxIsisSpfTriggerReason indicates the reasons that triggered the SPF
         run.

         newAdjacency (0)    - a new adjacency was formed.
         newLSP (1)          - a new LSP was received.
         newArea (2)         - a new area was joined.
         reach (3)           - a new prefix can be reached.
         ecmpChanged (4)     - the number of ecmp routes to a destination
                               changed.
         newMetric (5)       - a route has a new metric.
         teChanged (6)       - traffic engineering changed.
         restart (7)         - the IS-IS router was restarted.
         lspExpired (8)      - an LSP expired.
         lspDbChanged (9)    - the IS-IS LSP database was cleared.
         lspChanged (10)     - an LSP changed.
         newPreference (11)  - a route preference changed.
         newNLPID (12)       - a Network Layer Protocol was added to the
                               IS-IS router protocol set.
         manualRun (13)      - Manual request issued.
         adminTagChanged (14)- admin tag has changed.
         tunnelChanged (15)  - list of tunnels has changed.
         throttleEnd (16)    - throttling of SPF ended.
         lfaChanged (17)     - lfa changed."
    SYNTAX      BITS {
        newAdjacency    (0),
        newLSP          (1),
        newArea         (2),
        reach           (3),
        ecmpChanged     (4),
        newMetric       (5),
        teChanged       (6),
        restart         (7),
        lspExpired      (8),
        lspDbChanged    (9),
        lspChanged      (10),
        newPreference   (11),
        newNLPID        (12),
        manualRun       (13),
        adminTagChanged (14),
        tunnelChanged   (15),
        throttleEnd     (16),
        lfaChanged      (17)
    }

tmnxIsisObjs                     OBJECT IDENTIFIER ::= { tmnxSRObjs 88 }

tmnxIsisSystemObjs               OBJECT IDENTIFIER ::= { tmnxIsisObjs 1 }

tmnxIsisTable                    OBJECT-TYPE
    SYNTAX      SEQUENCE OF TmnxIsisEntry
    MAX-ACCESS  not-accessible
    STATUS      current
    DESCRIPTION
        "The tmnxIsisTable provides an extension of the isisSysTable in the
         ISIS-MIB."
    ::= { tmnxIsisSystemObjs 1 }

tmnxIsisEntry                    OBJECT-TYPE
    SYNTAX      TmnxIsisEntry
    MAX-ACCESS  not-accessible
    STATUS      current
    DESCRIPTION
        "Each row entry in the tmnxIsisTable represents additional columns for
         attributes specific to the Nokia SROS series IS-IS protocol instance
         on this router."
    INDEX       {
        vRtrID,
        isisSysInstance
    }
    ::= { tmnxIsisTable 1 }

TmnxIsisEntry                    ::= SEQUENCE
{
    tmnxIsisLastEnabledTime          TimeStamp,
    tmnxIsisAuthKey                  OCTET STRING,
    tmnxIsisAuthType                 INTEGER,
    tmnxIsisAuthCheck                TruthValue,
    tmnxIsisExportPolicy1            TNamedItemOrEmpty,
    tmnxIsisExportPolicy2            TNamedItemOrEmpty,
    tmnxIsisExportPolicy3            TNamedItemOrEmpty,
    tmnxIsisExportPolicy4            TNamedItemOrEmpty,
    tmnxIsisExportPolicy5            TNamedItemOrEmpty,
    tmnxIsisLspLifetime              Unsigned32,
    tmnxIsisOverloadTimeout          Unsigned32,
    tmnxIsisOperState                TmnxOperState,
    tmnxIsisReferenceBw              TmnxReferenceBandwidth,
    tmnxIsisTrafficEng               TruthValue,
    tmnxIsisShortCuts                TruthValue,
    tmnxIsisSpfHoldTime              Integer32,
    tmnxIsisLastSpfRun               TimeStamp,
    tmnxIsisGracefulRestart          TruthValue,
    tmnxIsisOverloadOnBoot           INTEGER,
    tmnxIsisOverloadOnBootTimeout    Unsigned32,
    tmnxIsisSpfWait                  Unsigned32,
    tmnxIsisSpfInitialWait           Unsigned32,
    tmnxIsisSpfSecondWait            Unsigned32,
    tmnxIsisLspMaxWait               Unsigned32,
    tmnxIsisLspInitialWait           Unsigned32,
    tmnxIsisLspSecondWait            Unsigned32,
    tmnxIsisCsnpAuthentication       TruthValue,
    tmnxIsisHelloAuthentication      TruthValue,
    tmnxIsisPsnpAuthentication       TruthValue,
    tmnxIsisGRHelperMode             TruthValue,
    tmnxIsisEnableIPv4               TruthValue,
    tmnxIsisUnicastImport            TruthValue,
    tmnxIsisMulticastImport          TruthValue,
    tmnxIsisStrictAdjacencyCheck     TruthValue,
    tmnxIsisManualSpfTrigger         INTEGER,
    tmnxIsisMultiTopology            TruthValue,
    tmnxIsisMultiTopoIPv6Ucast       TruthValue,
    tmnxIsisIPv6RoutingTopo          INTEGER,
    tmnxIsisSysOrigL1LSPBuffSize     TmnxIsisLSPBuffExtSize,
    tmnxIsisSysOrigL2LSPBuffSize     TmnxIsisLSPBuffExtSize,
    tmnxIsisLdpSyncAdminState        TruthValue,
    tmnxIsisIPv6UnicastImport        TruthValue,
    tmnxIsisIPv6MulticastImport      TruthValue,
    tmnxIsisAdvertisePassiveOnly     TruthValue,
    tmnxIsisDefaultRouteTag          Unsigned32,
    tmnxIsisSuppressDefault          TruthValue,
    tmnxIsisLdpOverRsvp              TmnxEnabledDisabled,
    tmnxIsisExportLimit              Unsigned32,
    tmnxIsisExportLimitLogPercent    Unsigned32,
    tmnxIsisTotalL1ExportedRoutes    Gauge32,
    tmnxIsisTotalL2ExportedRoutes    Gauge32,
    tmnxIsisRsvpShortcut             TruthValue,
    tmnxIsisAdvertiseTunnelLink      TruthValue,
    tmnxIsisIidTlv                   TmnxEnabledDisabled,
    tmnxIsisL1MacAddress             MacAddress,
    tmnxIsisL2MacAddress             MacAddress,
    tmnxIsisSysOperL1LSPBuffSize     Integer32,
    tmnxIsisSysOperL2LSPBuffSize     Integer32,
    tmnxIsisLoopfreeAlternate        TruthValue,
    tmnxIsisIPv4McastRoutingTopo     TmnxIsisRoutingTopology,
    tmnxIsisIPv6McastRoutingTopo     TmnxIsisRoutingTopology,
    tmnxIsisMultiTopoIPv4Mcast       TruthValue,
    tmnxIsisMultiTopoIPv6Mcast       TruthValue,
    tmnxIsisOverloadMaxMetric        TruthValue,
    tmnxIsisOverloadOnBootMaxMetric  TruthValue,
    tmnxIsisRouterId                 Unsigned32,
    tmnxIsisAdvRtrCapability         INTEGER,
    tmnxIsisHelloPadding             INTEGER,
    tmnxIsisLspRefreshInterval       Unsigned32,
    tmnxIsisOperRouterId             Unsigned32,
    tmnxIsisAuthKeyChain             TNamedItemOrEmpty,
    tmnxIsisIgnoreLspErrors          TruthValue,
    tmnxIsisSuppressAttachedBit      TruthValue,
    tmnxIsisRemoteLoopfreeAlternate  TruthValue
}

tmnxIsisLastEnabledTime          OBJECT-TYPE
    SYNTAX      TimeStamp
    MAX-ACCESS  read-only
    STATUS      current
    DESCRIPTION
        "The value of the object tmnxIsisLastEnabledTime indicates the
         sysUpTime value when isisSysAdminState was last set to enabled (1) to
         run the IS-IS protocol in the router."
    ::= { tmnxIsisEntry 1 }

tmnxIsisAuthKey                  OBJECT-TYPE
    SYNTAX      OCTET STRING (SIZE (0..254))
    MAX-ACCESS  read-write
    STATUS      current
    DESCRIPTION
        "The value of the object tmnxIsisAuthKey specifies the authentication
         key string used to verify the authenticity of packets sent by
         neighboring routers on an IS-IS interface.

         For authentication to succeed both the authentication key and the
         authentication type defined by the object tmnxIsisAuthType must match.

         If tmnxIsisAuthType is set to 'password', tmnxIsisAuthKey can include
         any ASCII character.

         Authentication can be configured globally and applied to all ISIS
         levels or it can be configured on a per level basis; the most specific
         value is used.

         When read, tmnxIsisAuthKey always returns an Octet String of length
         zero."
    DEFVAL      { ''H }
    ::= { tmnxIsisEntry 2 }

tmnxIsisAuthType                 OBJECT-TYPE
    SYNTAX      INTEGER {
        none     (1),
        password (2),
        md5      (3)
    }
    MAX-ACCESS  read-write
    STATUS      current
    DESCRIPTION
        "The value of the object tmnxIsisAuthType specifies the method of
         authentication used to verify the authenticity of packets sent by
         neighboring routers on an IS-IS interface.

         For authentication to succeed both the authentication key defined in
         the tmnxIsisAuthKey object and the authentication type must match.

         Authentication can be configured globally and applied to all ISIS
         levels or it can be configured on a per level basis; the most specific
         value is used."
    DEFVAL      { none }
    ::= { tmnxIsisEntry 3 }

tmnxIsisAuthCheck                OBJECT-TYPE
    SYNTAX      TruthValue
    MAX-ACCESS  read-write
    STATUS      current
    DESCRIPTION
        "The value of the object tmnxIsisAuthCheck specifies whether
         authentication check has to be performed on received
             IS-IS protocol packets to determine if they should be rejected.

             When tmnxIsisAuthCheck has a value of 'true', all IS-IS protocol
             packets that have a mismatch on either the authentication type,
             specified by the value of tmnxIsisAuthType, or the authentication
             key, given in tmnxIsisAuthKey are rejected.

             When tmnxIsisAuthCheck has a value of 'false', authentication is
             performed on received IS-IS protocol packets but mismatched
             packets are not rejected."
    DEFVAL      { true }
    ::= { tmnxIsisEntry 4 }

tmnxIsisExportPolicy1            OBJECT-TYPE
    SYNTAX      TNamedItemOrEmpty
    MAX-ACCESS  read-write
    STATUS      current
    DESCRIPTION
        "The value of the object tmnxIsisExportPolicy1 specifies the name of
         the first policy to be used for determining which routes are exported
         from the routing table to IS-IS.

         If no export policy is defined, non IS-IS router will not be exported
         from the routing table manager to IS-IS.

         If multiple policy names are specified, the policies are evaluated in
         the order they are specified and the first policy that matches will be
         applied.

         The export policy name list, tmnxIsisExportPolicy1 through
         tmnxIsisExportPolicy5, is handled by the SNMP agent as a single
         entity.  When an SNMP SET request is received to modify one or
         more of the policy names, all the policy variables are first
         set to the empty string, ''H, and then the new names are set
         into the specified policy variables within a single SNMP SET PDU."
    DEFVAL      { ''H }
    ::= { tmnxIsisEntry 5 }

tmnxIsisExportPolicy2            OBJECT-TYPE
    SYNTAX      TNamedItemOrEmpty
    MAX-ACCESS  read-write
    STATUS      current
    DESCRIPTION
        "The value of the object tmnxIsisExportPolicy2 specifies the name of
         the second policy to be used for determining which routes are exported
         from the routing table to IS-IS.

         If no export policy is defined, non IS-IS router will not be exported
         from the routing table manager to IS-IS.

         If multiple policy names are specified, the policies are evaluated in
         the order they are specified and the first policy that matches will be
         applied.

         The export policy name list, tmnxIsisExportPolicy1 through
         tmnxIsisExportPolicy5, is handled by the SNMP agent as a single
         entity.  When an SNMP SET request is received to modify one or
         more of the policy names, all the policy variables are first
         set to the empty string, ''H, and then the new names are set
         into the specified policy variables within a single SNMP SET PDU."
    DEFVAL      { ''H }
    ::= { tmnxIsisEntry 6 }

tmnxIsisExportPolicy3            OBJECT-TYPE
    SYNTAX      TNamedItemOrEmpty
    MAX-ACCESS  read-write
    STATUS      current
    DESCRIPTION
        "The value of the object tmnxIsisExportPolicy3 specifies the name of
         the third policy to be used for determining which routes are exported
         from the routing table to IS-IS.

         If no export policy is defined, non IS-IS router will not be exported
         from the routing table manager to IS-IS.

         If multiple policy names are specified, the policies are evaluated in
         the order they are specified and the first policy that matches will be
         applied.

         The export policy name list, tmnxIsisExportPolicy1 through
         tmnxIsisExportPolicy5, is handled by the SNMP agent as a single
         entity.  When an SNMP SET request is received to modify one or
         more of the policy names, all the policy variables are first
         set to the empty string, ''H, and then the new names are set
         into the specified policy variables within a single SNMP SET PDU."
    DEFVAL      { ''H }
    ::= { tmnxIsisEntry 7 }

tmnxIsisExportPolicy4            OBJECT-TYPE
    SYNTAX      TNamedItemOrEmpty
    MAX-ACCESS  read-write
    STATUS      current
    DESCRIPTION
        "The value of the object tmnxIsisExportPolicy4 specifies the name of
         the fourth policy to be used for determining which routes are exported
         from the routing table to IS-IS.

         If no export policy is defined, non IS-IS router will not be exported
         from the routing table manager to IS-IS.

         If multiple policy names are specified, the policies are evaluated in
         the order they are specified and the first policy that matches will be
         applied.

         The export policy name list, tmnxIsisExportPolicy1 through
         tmnxIsisExportPolicy5, is handled by the SNMP agent as a single
         entity.  When an SNMP SET request is received to modify one or
         more of the policy names, all the policy variables are first
         set to the empty string, ''H, and then the new names are set
         into the specified policy variables within a single SNMP SET PDU."
    DEFVAL      { ''H }
    ::= { tmnxIsisEntry 8 }

tmnxIsisExportPolicy5            OBJECT-TYPE
    SYNTAX      TNamedItemOrEmpty
    MAX-ACCESS  read-write
    STATUS      current
    DESCRIPTION
        "The value of the object tmnxIsisExportPolicy5 specifies the name of
         the fifth policy to be used for determining which routes are exported
         from the routing table to IS-IS.

         If no export policy is defined, non IS-IS router will not be exported
         from the routing table manager to IS-IS.

         If multiple policy names are specified, the policies are evaluated in
         the order they are specified and the first policy that matches will be
         applied.

         The export policy name list, tmnxIsisExportPolicy1 through
         tmnxIsisExportPolicy5, is handled by the SNMP agent as a single
         entity.  When an SNMP SET request is received to modify one or
         more of the policy names, all the policy variables are first
         set to the empty string, ''H, and then the new names are set
         into the specified policy variables within a single SNMP SET PDU."
    DEFVAL      { ''H }
    ::= { tmnxIsisEntry 9 }

tmnxIsisLspLifetime              OBJECT-TYPE
    SYNTAX      Unsigned32 (350..65535)
    UNITS       "seconds"
    MAX-ACCESS  read-write
    STATUS      current
    DESCRIPTION
        "The value of the object tmnxIsisLspLifetime specifies the amount of
         time, in seconds, a given LSP is considered valid without the
         originating router having refreshed the LSP.

         The actual LSP refresh timer is the value of tmnxIsisLspLifetime minus
         317 seconds."
    DEFVAL      { 1200 }
    ::= { tmnxIsisEntry 10 }

tmnxIsisOverloadTimeout          OBJECT-TYPE
    SYNTAX      Unsigned32 (0 | 60..1800)
    UNITS       "seconds"
    MAX-ACCESS  read-write
    STATUS      current
    DESCRIPTION
        "The value of the object tmnxIsisOverloadTimeout specifies the amount
         of time, in seconds, the router operates in the overload state before
         attempting to reestablish normal operations.

         While in overload state, this IS-IS router will only be used if the
         destination is only reachable via this router; it is not used for
         other transit traffic.

         Operationally placing the router into the overload state is often used
         as a precursor to shutting down the IS-IS protocol operation.

         This variable is an extension to the isisSysWaitTime to accept an
         additional value of 0 to specify that the router is in overload
         infinitely."
    DEFVAL      { 0 }
    ::= { tmnxIsisEntry 11 }

tmnxIsisOperState                OBJECT-TYPE
    SYNTAX      TmnxOperState
    MAX-ACCESS  read-only
    STATUS      current
    DESCRIPTION
        "The value of the object tmnxIsisOperState indicates the current
         operating state of this IS-IS protocol instance on this router."
    ::= { tmnxIsisEntry 12 }

tmnxIsisReferenceBw              OBJECT-TYPE
    SYNTAX      TmnxReferenceBandwidth
    UNITS       "kilobps"
    MAX-ACCESS  read-write
    STATUS      current
    DESCRIPTION
        "The value of the object tmnxIsisReferenceBw specifies the reference
         bandwidth that needs to be used to calculate the cost.

         To configure higher reference bandwidth values, please use the newer
         objects tmnxIsisReferenceBwU64High and tmnxIsisReferenceBwU64Low in
         tmnxIsisExtTable.

         In case a reference bandwidth is configured in tmnxIsisExtTable that
         exceeds the maximum of the tmnxIsisReferenceBw range, this object will
         return the maximum value. The real reference bandwidth can be found in
         tmnxIsisReferenceBwU64High and tmnxIsisReferenceBwU64Low.

         In order to calculate the lowest cost to reach a given destination
         each configured level on each interface must have a cost.

         If the reference-bandwidth is defined then the cost is calculated
         using the following formula:
             Cost = reference-bandwidth / bandwidth.

         If the reference bandwidth is configured as Ten Gig (10,000,000,000) a
         100-Mbps interface has a default metric of 100. In order for metrics
         in excess of 63 to be configured wide metrics must be deployed.

         A value of '0' means that the reference bandwidth is not defined."
    DEFVAL      { 0 }
    ::= { tmnxIsisEntry 13 }

tmnxIsisTrafficEng               OBJECT-TYPE
    SYNTAX      TruthValue
    MAX-ACCESS  read-write
    STATUS      current
    DESCRIPTION
        "The value of the object tmnxIsisTrafficEng specifies whether traffic
         engineering is enabled for the router.

         When the value of tmnxIsisTrafficEng is 'true', traffic engineering is
         enabled for the router.

         When the value of tmnxIsisTrafficEng is 'false', traffic engineering
         is disabled so that te-metrics are not generated and are ignored when
         received by this node.

         Traffic engineering is only supported on a base router  ISIS instance."
    DEFVAL      { false }
    ::= { tmnxIsisEntry 14 }

tmnxIsisShortCuts                OBJECT-TYPE
    SYNTAX      TruthValue
    MAX-ACCESS  read-only
    STATUS      current
    DESCRIPTION
        "The value of the object tmnxIsisShortCuts indicates whether IGP
         shortcuts are required or not.

         When the value of tmnxIsisShortCuts is 'true', MPLS label switched
         paths of LSPs are used as next hops whenever BGP need to resolve the
         next hop within the IS-IS domain.

         When the value of tmnxIsisShortCuts is 'false', IGP shortcuts are not
         required by BGP.

         This doesn't have any meaning if tmnxIsisTrafficEng is set to false."
    ::= { tmnxIsisEntry 15 }

tmnxIsisSpfHoldTime              OBJECT-TYPE
    SYNTAX      Integer32 (0..65535)
    UNITS       "seconds"
    MAX-ACCESS  read-only
    STATUS      current
    DESCRIPTION
        "The value of the object tmnxIsisSpfHoldTime indicates the time
         interval at which SPF is run."
    ::= { tmnxIsisEntry 16 }

tmnxIsisLastSpfRun               OBJECT-TYPE
    SYNTAX      TimeStamp
    MAX-ACCESS  read-only
    STATUS      current
    DESCRIPTION
        "The value of the object tmnxIsisLastSpfRun indicates the sysUpTime
         value when the last SPF run was performed for this instance of the
         IS-IS protocol in the router."
    ::= { tmnxIsisEntry 17 }

tmnxIsisGracefulRestart          OBJECT-TYPE
    SYNTAX      TruthValue
    MAX-ACCESS  read-write
    STATUS      current
    DESCRIPTION
        "The value of the object tmnxIsisGracefulRestart specifies whether the
         graceful restart is enabled or disabled for this instance of IS-IS on
         the router."
    DEFVAL      { false }
    ::= { tmnxIsisEntry 18 }

tmnxIsisOverloadOnBoot           OBJECT-TYPE
    SYNTAX      INTEGER {
        disabled (1),
        enabled  (2)
    }
    MAX-ACCESS  read-write
    STATUS      current
    DESCRIPTION
        "The value of the object tmnxIsisOverloadOnBoot specifies if the router
         should be in overload state right after the boot up process.

         If the tmnxIsisOverloadOnBoot is set to 'enabled' the overload timeout
         is maintained by tmnxIsisOverloadOnBootTimeout."
    DEFVAL      { disabled }
    ::= { tmnxIsisEntry 19 }

tmnxIsisOverloadOnBootTimeout    OBJECT-TYPE
    SYNTAX      Unsigned32 (0 | 60..1800)
    UNITS       "seconds"
    MAX-ACCESS  read-write
    STATUS      current
    DESCRIPTION
        "The value of the object tmnxIsisOverloadOnBootTimeout specifies the
         amount of time, in seconds, for which the router operates in the
         overload state before attempting to reestablish normal operations when
         the system comes up after a fresh boot.

         While in overload state, this IS-IS router will only be used if the
         destination is only reachable via this router; it is not used for
         other transit traffic."
    DEFVAL      { 0 }
    ::= { tmnxIsisEntry 20 }

tmnxIsisSpfWait                  OBJECT-TYPE
    SYNTAX      Unsigned32 (10..120000)
    UNITS       "milliseconds"
    MAX-ACCESS  read-write
    STATUS      current
    DESCRIPTION
        "The value of the object tmnxIsisSpfWait specifies the Maximum interval
         between two consecutive spf calculations in milliseconds."
    DEFVAL      { 10000 }
    ::= { tmnxIsisEntry 21 }

tmnxIsisSpfInitialWait           OBJECT-TYPE
    SYNTAX      Unsigned32 (10..100000)
    UNITS       "milliseconds"
    MAX-ACCESS  read-write
    STATUS      current
    DESCRIPTION
        "The value of the object tmnxIsisSpfInitialWait specifies the initial
         SPF calculation delay (in milliseconds) after a topology change."
    DEFVAL      { 1000 }
    ::= { tmnxIsisEntry 22 }

tmnxIsisSpfSecondWait            OBJECT-TYPE
    SYNTAX      Unsigned32 (10..100000)
    UNITS       "milliseconds"
    MAX-ACCESS  read-write
    STATUS      current
    DESCRIPTION
        "The value of the object tmnxIsisSpfSecondWait specifies the hold time,
         in milliseconds, between the first and second SPF calculation.

         Subsequent SPF runs will occur at exponentially increasing intervals
         of spf-second-wait i.e. if spf-second-wait is 1000, then the next SPF
         will run after 2000 msec, the next one at 4000 msec etc until it is
         capped off at spf-wait value.

         The SPF interval will stay at spf-wait value until there are no more
         SPF runs scheduled in that interval. After a full interval without any
         SPF runs, the SPF interval will drop back to spf-initial-wait."
    DEFVAL      { 1000 }
    ::= { tmnxIsisEntry 23 }

tmnxIsisLspMaxWait               OBJECT-TYPE
    SYNTAX      Unsigned32 (10..120000)
    UNITS       "milliseconds"
    MAX-ACCESS  read-write
    STATUS      current
    DESCRIPTION
        "The value of the object tmnxIsisLspMaxWait specifies the maximum
         interval, in milliseconds, between two consecutive occurrences of an
         LSP being generated."
    DEFVAL      { 5000 }
    ::= { tmnxIsisEntry 24 }

tmnxIsisLspInitialWait           OBJECT-TYPE
    SYNTAX      Unsigned32 (10..100000)
    UNITS       "milliseconds"
    MAX-ACCESS  read-write
    STATUS      current
    DESCRIPTION
        "The value of the object tmnxIsisLspInitialWait specifies the initial
         LSP generation delay in milliseconds."
    DEFVAL      { 10 }
    ::= { tmnxIsisEntry 25 }

tmnxIsisLspSecondWait            OBJECT-TYPE
    SYNTAX      Unsigned32 (10..100000)
    UNITS       "milliseconds"
    MAX-ACCESS  read-write
    STATUS      current
    DESCRIPTION
        "The value of the object tmnxIsisLspSecondWait specifies the hold time,
         in milliseconds, between the first and second LSP generation."
    DEFVAL      { 1000 }
    ::= { tmnxIsisEntry 26 }

tmnxIsisCsnpAuthentication       OBJECT-TYPE
    SYNTAX      TruthValue
    MAX-ACCESS  read-write
    STATUS      current
    DESCRIPTION
        "The value of the object tmnxIsisCsnpAuthentication specifies whether
         authentication of CSNP packets is enabled or not.

         When tmnxIsisCsnpAuthentication has a value of 'true', authentication
         of individual ISIS packets of CSNP type is enabled.

         When tmnxIsisCsnpAuthentication has a value of 'false', authentication
         of CSNP packets is suppressed."
    DEFVAL      { true }
    ::= { tmnxIsisEntry 27 }

tmnxIsisHelloAuthentication      OBJECT-TYPE
    SYNTAX      TruthValue
    MAX-ACCESS  read-write
    STATUS      current
    DESCRIPTION
        "The value of the object tmnxIsisHelloAuthentication specifies whether
         authentication of HELLO packets is enabled or not.

         When tmnxIsisHelloAuthentication has a value of 'true', authentication
         of individual ISIS packets of HELLO type is enabled.

         When tmnxIsisHelloAuthentication has a value of 'false',
         authentication of HELLO packets is suppressed."
    DEFVAL      { true }
    ::= { tmnxIsisEntry 28 }

tmnxIsisPsnpAuthentication       OBJECT-TYPE
    SYNTAX      TruthValue
    MAX-ACCESS  read-write
    STATUS      current
    DESCRIPTION
        "The value of the object tmnxIsisPsnpAuthentication specifies whether
         authentication of PSNP packets is enabled or not.

         When tmnxIsisPsnpAuthentication has a value of 'true', authentication
         of individual ISIS packets of PSNP type is enabled.

         When tmnxIsisPsnpAuthentication has a value of 'false', authentication
         of PSNP packets is suppressed."
    DEFVAL      { true }
    ::= { tmnxIsisEntry 29 }

tmnxIsisGRHelperMode             OBJECT-TYPE
    SYNTAX      TruthValue
    MAX-ACCESS  read-write
    STATUS      current
    DESCRIPTION
        "The value of the object tmnxIsisGRHelperMode specifies whether the
         graceful restart helper mode is enabled or disabled for this instance
         of IS-IS on the router.

         The value of the object tmnxIsisGRHelperMode is only valid if the
         value of object tmnxIsisGracefulRestart is 'true'.

         When tmnxIsisGRHelperMode has a value of 'true' graceful restart
         helper capabilities are enabled.

         When tmnxIsisGRHelperMode has a value of 'false' the graceful restart
         helper capabilities are disabled."
    DEFVAL      { false }
    ::= { tmnxIsisEntry 30 }

tmnxIsisEnableIPv4               OBJECT-TYPE
    SYNTAX      TruthValue
    MAX-ACCESS  read-write
    STATUS      current
    DESCRIPTION
        "The value of the object tmnxIsisEnableIPv4 specifies whether this
         IS-IS instance supports IPv4.

         When tmnxIsisEnableIPv4 has a value of 'true', the IS-IS instance
         supports IPv4, and when it has a value of 'false', it does not."
    DEFVAL      { true }
    ::= { tmnxIsisEntry 31 }

tmnxIsisUnicastImport            OBJECT-TYPE
    SYNTAX      TruthValue
    MAX-ACCESS  read-write
    STATUS      current
    DESCRIPTION
        "The value of the object tmnxIsisUnicastImport specifies whether ISIS
         protocol will submit routes into the unicast Route Table Manage(RTM).

         When tmnxIsisUnicastImport has a value of 'true', the IS-IS instance
         submits routes into the unicast RTM, and when it has a value of
         'false', it does not."
    DEFVAL      { true }
    ::= { tmnxIsisEntry 32 }

tmnxIsisMulticastImport          OBJECT-TYPE
    SYNTAX      TruthValue
    MAX-ACCESS  read-write
    STATUS      current
    DESCRIPTION
        "The value of the object tmnxIsisMulticastImport specifies whether ISIS
         protocol will submit routes into the multicast Reverse Path
         Forwarding(RPF) Route Table Manage(RTM).

         When tmnxIsisMulticastImport has a value of 'true', ISIS protocol
         submits routes into the multicast RPF RTM and when it has a value of
         'false', it does not."
    DEFVAL      { false }
    ::= { tmnxIsisEntry 33 }

tmnxIsisStrictAdjacencyCheck     OBJECT-TYPE
    SYNTAX      TruthValue
    MAX-ACCESS  read-write
    STATUS      current
    DESCRIPTION
        "The value of the object tmnxIsisStrictAdjacencyCheck specifies whether
         an ISIS adjacency can be formed when two routers do not run the same
         IP versions.

         When tmnxIsisStrictAdjacencyCheck is 'true', both routers have to run
         the same IP versions in the ISIS protocol.

         When tmnxIsisStrictAdjacencyCheck is 'false', having one common IP
         version running is enough to form an adjacency."
    DEFVAL      { false }
    ::= { tmnxIsisEntry 34 }

tmnxIsisManualSpfTrigger         OBJECT-TYPE
    SYNTAX      INTEGER {
        noAction    (1),
        runTotalSpf (2)
    }
    MAX-ACCESS  read-write
    STATUS      current
    DESCRIPTION
        "The value of the object tmnxIsisManualSpfTrigger specifies a manual
         Dijkstra SPF calculation trigger.

         When tmnxIsisManualSpfTrigger is set to 'runTotalSpf' a normal
         Dijkstra SPF calculation is performed.

         GETs and GETNEXTs on this variable return 'noAction'."
    DEFVAL      { noAction }
    ::= { tmnxIsisEntry 35 }

tmnxIsisMultiTopology            OBJECT-TYPE
    SYNTAX      TruthValue
    MAX-ACCESS  read-write
    STATUS      current
    DESCRIPTION
        "The value of the object tmnxIsisMultiTopology specifies if the multi
         topology for ISIS is enabled."
    DEFVAL      { false }
    ::= { tmnxIsisEntry 36 }

tmnxIsisMultiTopoIPv6Ucast       OBJECT-TYPE
    SYNTAX      TruthValue
    MAX-ACCESS  read-write
    STATUS      current
    DESCRIPTION
        "The value of the object tmnxIsisMultiTopoIPv6Ucast specifies if IPv6
         unicast is enabled for ISIS multi topology.

         To enable IPv6 unicast on ISIS, tmnxIsisMultiTopology should be set to
         'true'."
    DEFVAL      { false }
    ::= { tmnxIsisEntry 37 }

tmnxIsisIPv6RoutingTopo          OBJECT-TYPE
    SYNTAX      INTEGER {
        none   (0),
        native (1),
        mt     (2)
    }
    MAX-ACCESS  read-write
    STATUS      current
    DESCRIPTION
        "The value of the object tmnxIsisIPv6RoutingTopo specifies the routing
         topology for IPv6.

         If the value of tmnxIsisIPv6RoutingTopo is set to 'mt', multi topology
         for ipv6 routing is in effect only if tmnxIsisMultiTopoIPv6Ucast is
         set to 'true'."
    DEFVAL      { none }
    ::= { tmnxIsisEntry 38 }

tmnxIsisSysOrigL1LSPBuffSize     OBJECT-TYPE
    SYNTAX      TmnxIsisLSPBuffExtSize
    MAX-ACCESS  read-write
    STATUS      current
    DESCRIPTION
        "The value of the object tmnxIsisSysOrigL1LSPBuffSize specifies the
         maximum size of Level 1 LSPs and SNPs originated by this instance.

         This object may only be modified when the ISIS-MIB::isisSysAdminState
         member of the corresponding entry in the ISIS-MIB::isisSysTable table
         has a value of 'outOfService (3)'.

         This object replaces the ISIS-MIB::isisSysOrigL1LSPBuffSize member of
         the ISIS-MIB::isisSysTable table."
    DEFVAL      { 1492 }
    ::= { tmnxIsisEntry 39 }

tmnxIsisSysOrigL2LSPBuffSize     OBJECT-TYPE
    SYNTAX      TmnxIsisLSPBuffExtSize
    MAX-ACCESS  read-write
    STATUS      current
    DESCRIPTION
        "The value of the object tmnxIsisSysOrigL2LSPBuffSize specifies the
         maximum size of Level 2 LSPs and SNPs originated by this system.

         This object may only be modified when the ISIS-MIB::isisSysAdminState
         member of the corresponding entry in the ISIS-MIB::isisSysTable table
         has a value of 'outOfService (3)'.

         This object replaces the ISIS-MIB::isisSysOrigL2LSPBuffSize member of
         the ISIS-MIB::isisSysTable table."
    DEFVAL      { 1492 }
    ::= { tmnxIsisEntry 40 }

tmnxIsisLdpSyncAdminState        OBJECT-TYPE
    SYNTAX      TruthValue
    MAX-ACCESS  read-write
    STATUS      current
    DESCRIPTION
        "The value of the object tmnxIsisLdpSyncAdminState specifies whether
         the IGP-LDP synchronization feature is enabled or disabled on all
         interfaces participating in the ISIS routing protocol.

         When the value is set to 'false', IGP immediately advertises the
         actual value of the link cost for all interfaces which have the
         IGP-LDP synchronization enabled if the currently advertised cost is
         different. It will then disable IGP-LDP synchronization for all
         interfaces."
    DEFVAL      { true }
    ::= { tmnxIsisEntry 41 }

tmnxIsisIPv6UnicastImport        OBJECT-TYPE
    SYNTAX      TruthValue
    MAX-ACCESS  read-write
    STATUS      current
    DESCRIPTION
        "The value of the object tmnxIsisIPv6UnicastImport specifies whether
         ISIS protocol will submit routes into the unicast IPv6 Route Table
         Manage(RTM).

         When tmnxIsisUnicastImport has a value of 'true', the IS-IS instance
         submits routes into the unicast IPv6 RTM, and when it has a value of
         'false', it does not."
    DEFVAL      { true }
    ::= { tmnxIsisEntry 42 }

tmnxIsisIPv6MulticastImport      OBJECT-TYPE
    SYNTAX      TruthValue
    MAX-ACCESS  read-write
    STATUS      current
    DESCRIPTION
        "The value of the object tmnxIsisIPv6MulticastImport specifies whether
         ISIS protocol will submit routes into the multicast IPv6 Reverse Path
         Forwarding(RPF) Route Table Manage(RTM).

         When tmnxIsisMulticastImport has a value of 'true', ISIS protocol
         submits routes into the multicast IPv6 RPF RTM and when it has a value
         of 'false', it does not."
    DEFVAL      { false }
    ::= { tmnxIsisEntry 43 }

tmnxIsisAdvertisePassiveOnly     OBJECT-TYPE
    SYNTAX      TruthValue
    MAX-ACCESS  read-write
    STATUS      current
    DESCRIPTION
        "The value of the object tmnxIsisAdvertisePassiveOnly specifies whether
         ISIS protocol will advertise only prefixes that belong to passive
         interfaces.

         When tmnxIsisAdvertisePassiveOnly is set to 'true', ISIS protocol
         advertises only prefixes that belong to passive interfaces."
    DEFVAL      { false }
    ::= { tmnxIsisEntry 44 }

tmnxIsisDefaultRouteTag          OBJECT-TYPE
    SYNTAX      Unsigned32
    MAX-ACCESS  read-write
    STATUS      current
    DESCRIPTION
        "The value of the object tmnxIsisDefaultRouteTag specifies a 32-bit
         integer tag for the ISIS default route.

         This route tag can be used to apply administrative policy.

         A value of 0 indicates that the tag has not been set."
    DEFVAL      { 0 }
    ::= { tmnxIsisEntry 45 }

tmnxIsisSuppressDefault          OBJECT-TYPE
    SYNTAX      TruthValue
    MAX-ACCESS  read-write
    STATUS      current
    DESCRIPTION
        "The value of the object tmnxIsisSuppressDefault specifies whether ISIS
         protocol will ignore the ATT bit and therefore suppress the
         installation of the default routes on L1 router.

         When tmnxIsisSuppressDefault is set to 'true', ISIS protocol will
         ignore the ATT bit and therefore suppress the installation of the
         default routes."
    DEFVAL      { false }
    ::= { tmnxIsisEntry 46 }

tmnxIsisLdpOverRsvp              OBJECT-TYPE
    SYNTAX      TmnxEnabledDisabled
    MAX-ACCESS  read-write
    STATUS      current
    DESCRIPTION
        "The value of the object tmnxIsisLdpOverRsvp specifies whether
         LDP-over-RSVP feature is enabled or disabled for ISIS.

         When tmnxIsisLdpOverRsvp is enabled, ISIS will select the endpoint
         that is closest to the destination for further selection of
         LDP-over-RSVP tunnels to that endpoint."
    DEFVAL      { disabled }
    ::= { tmnxIsisEntry 47 }

tmnxIsisExportLimit              OBJECT-TYPE
    SYNTAX      Unsigned32
    MAX-ACCESS  read-write
    STATUS      current
    DESCRIPTION
        "The value of the object tmnxIsisExportLimit specifies the maximum
         number of routes or prefixes that can be exported into ISIS from the
         route table.

         A value of 0 indicates that the export limit for routes or prefixes
         has been disabled."
    DEFVAL      { 0 }
    ::= { tmnxIsisEntry 48 }

tmnxIsisExportLimitLogPercent    OBJECT-TYPE
    SYNTAX      Unsigned32 (0..100)
    UNITS       "percent"
    MAX-ACCESS  read-write
    STATUS      current
    DESCRIPTION
        "The value of the object tmnxIsisExportLimitLogPercent specifies the
         percentage of the export-limit at which a warning log message and SNMP
         notification would be sent; this would only be a warning and
         additional routes will be learned up to 100% of tmnxIsisExportLimit.

         A value of 0 indicates that tmnxIsisExportLimitLogPercent is disabled
         and no log message or SNMP notification would be sent."
    DEFVAL      { 0 }
    ::= { tmnxIsisEntry 49 }

tmnxIsisTotalL1ExportedRoutes    OBJECT-TYPE
    SYNTAX      Gauge32
    MAX-ACCESS  read-only
    STATUS      current
    DESCRIPTION
        "The value of the object tmnxIsisTotalL1ExportedRoutes indicates the
         total number of routes exported into ISIS level 1 from the route table
         manager when an export policy is configured.

         If no export policy is configured, tmnxIsisTotalL1ExportedRoutes will
         return 0."
    ::= { tmnxIsisEntry 50 }

tmnxIsisTotalL2ExportedRoutes    OBJECT-TYPE
    SYNTAX      Gauge32
    MAX-ACCESS  read-only
    STATUS      current
    DESCRIPTION
        "The value of the object tmnxIsisTotalL2ExportedRoutes indicates the
         total number of routes exported into ISIS level 2 from the route table
         manager when an export policy is configured.

         If no export policy is configured, tmnxIsisTotalL2ExportedRoutes will
         return 0."
    ::= { tmnxIsisEntry 51 }

tmnxIsisRsvpShortcut             OBJECT-TYPE
    SYNTAX      TruthValue
    MAX-ACCESS  read-write
    STATUS      obsolete
    DESCRIPTION
        "The value of the object tmnxIsisRsvpShortcut specifies whether RSVP-TE
         shortcut for resolving IGP routes has been enabled or disabled for
         IS-IS.

         When the value of tmnxIsisRsvpShortcut is set to true RSVP-TE shortcut
         is enabled and when tmnxIsisRsvpShortcut is set to false RSVP-TE
         shortcut is disabled for IS-IS."
    DEFVAL      { false }
    ::= { tmnxIsisEntry 52 }

tmnxIsisAdvertiseTunnelLink      OBJECT-TYPE
    SYNTAX      TruthValue
    MAX-ACCESS  read-write
    STATUS      current
    DESCRIPTION
        "The value of the object tmnxIsisAdvertiseTunnelLink specifies whether
         advertisement of LSP shortcuts into IGP has been enabled or disabled
         for IS-IS.

         When the value of tmnxIsisAdvertiseTunnelLink is set to true LSP
         shortcut advertisement into IGP is enabled and when
         tmnxIsisAdvertiseTunnelLink is set to false LSP shortcut advertisement
         into IGP is disabled."
    DEFVAL      { false }
    ::= { tmnxIsisEntry 53 }

tmnxIsisIidTlv                   OBJECT-TYPE
    SYNTAX      TmnxEnabledDisabled
    MAX-ACCESS  read-write
    STATUS      current
    DESCRIPTION
        "The value of the object tmnxIsisIidTlv specifies whether Instance
         Identifier (IID) TLV has been enabled or disabled for this ISIS
         instance.

         When the value of tmnxIsisIidTlv is 'enabled', each ISIS instance
         marks its packets with the IID TLV containing its unique 16-bit IID
         for the routing domain."
    DEFVAL      { disabled }
    ::= { tmnxIsisEntry 54 }

tmnxIsisL1MacAddress             OBJECT-TYPE
    SYNTAX      MacAddress
    MAX-ACCESS  read-write
    STATUS      current
    DESCRIPTION
        "The value of the object tmnxIsisL1MacAddress specifies the destination
         MAC address for all L1 ISIS neighbors on the link for this ISIS
         instance."
    DEFVAL      { '0180C2000014'H }
    ::= { tmnxIsisEntry 55 }

tmnxIsisL2MacAddress             OBJECT-TYPE
    SYNTAX      MacAddress
    MAX-ACCESS  read-write
    STATUS      current
    DESCRIPTION
        "The value of the object tmnxIsisL2MacAddress specifies the destination
         MAC address for all L2 ISIS neighbors on the link for this ISIS
         instance."
    DEFVAL      { '0180C2000015'H }
    ::= { tmnxIsisEntry 56 }

tmnxIsisSysOperL1LSPBuffSize     OBJECT-TYPE
    SYNTAX      Integer32
    MAX-ACCESS  read-only
    STATUS      current
    DESCRIPTION
        "The value of the object tmnxIsisSysOperL1LSPBuffSize indicates the
         operational size of Level 1 LSPs and SNPs originated by this instance."
    ::= { tmnxIsisEntry 57 }

tmnxIsisSysOperL2LSPBuffSize     OBJECT-TYPE
    SYNTAX      Integer32
    MAX-ACCESS  read-only
    STATUS      current
    DESCRIPTION
        "The value of the object tmnxIsisSysOperL2LSPBuffSize indicates the
         operational size of Level 2 LSPs and SNPs originated by this instance."
    ::= { tmnxIsisEntry 58 }

tmnxIsisLoopfreeAlternate        OBJECT-TYPE
    SYNTAX      TruthValue
    MAX-ACCESS  read-write
    STATUS      current
    DESCRIPTION
        "The value of the object tmnxIsisLoopfreeAlternate specifies whether IP
         fast reroute capability for ISIS is enabled or disabled.

         When the value of tmnxIsisLoopfreeAlternate is set to 'true' IP fast
         reroute capability for ISIS is enabled and when
         tmnxIsisLoopfreeAlternate is set to 'false' IP fast reroute capability
         for ISIS is disabled."
    DEFVAL      { false }
    ::= { tmnxIsisEntry 59 }

tmnxIsisIPv4McastRoutingTopo     OBJECT-TYPE
    SYNTAX      TmnxIsisRoutingTopology
    MAX-ACCESS  read-write
    STATUS      current
    DESCRIPTION
        "The value of the object tmnxIsisIPv4McastRoutingTopo specifies Whether
         to add native IPv4 routes to the multicast RTM.

         If the value of tmnxIsisIPv4McastRoutingTopo is 'native', it enables
         MT0 IPv4 routes to be added to the multicast RTM.

         If the value of tmnxIsisIPv4McastRoutingTopo is 'none' or 'mt', then
         no MT0 IPv4 routes are added to the multicast RTM.

         The object tmnxIsisMultiTopoIPv4Mcast can be used to control if  MT3
         routes are added to the multicast RTM."
    DEFVAL      { native }
    ::= { tmnxIsisEntry 60 }

tmnxIsisIPv6McastRoutingTopo     OBJECT-TYPE
    SYNTAX      TmnxIsisRoutingTopology
    MAX-ACCESS  read-write
    STATUS      current
    DESCRIPTION
        "The value of the object tmnxIsisIPv6McastRoutingTopo specifies
         Whether to add native IPv6 routes to the multicast RTM.

         If the value of tmnxIsisIPv6McastRoutingTopo is 'native', it enables
         MT0 IPv6 routes to be added to the multicast RTM.

         If the value of tmnxIsisIPv6McastRoutingTopo is 'none' or 'mt', then
         no MT0 IPv6 routes are added to the multicast RTM.

         The object tmnxIsisMultiTopoIPv6Mcast can be used to control if MT4
         routes are added to the multicast RTM."
    DEFVAL      { native }
    ::= { tmnxIsisEntry 61 }

tmnxIsisMultiTopoIPv4Mcast       OBJECT-TYPE
    SYNTAX      TruthValue
    MAX-ACCESS  read-write
    STATUS      current
    DESCRIPTION
        "The value of the object tmnxIsisMultiTopoIPv4Mcast specifies whether
         IPv4 multicast for ISIS multi topology is enabled or not.

         To enable IPv4 multicast on ISIS, tmnxIsisMultiTopology should be set
         to 'true'."
    DEFVAL      { false }
    ::= { tmnxIsisEntry 62 }

tmnxIsisMultiTopoIPv6Mcast       OBJECT-TYPE
    SYNTAX      TruthValue
    MAX-ACCESS  read-write
    STATUS      current
    DESCRIPTION
        "The value of the object tmnxIsisMultiTopoIPv6Mcast specifies whether
         IPv6 multicast for ISIS multi topology is enabled or not.

         To enable IPv6 multicast on ISIS, tmnxIsisMultiTopology should be set
         to 'true'."
    DEFVAL      { false }
    ::= { tmnxIsisEntry 63 }

tmnxIsisOverloadMaxMetric        OBJECT-TYPE
    SYNTAX      TruthValue
    MAX-ACCESS  read-write
    STATUS      current
    DESCRIPTION
        "The value of the object tmnxIsisOverloadMaxMetric specifies whether
         max-metric is enabled or disabled for this instance of IS-IS on the
         router.

         If the value of tmnxIsisOverloadMaxMetric set to 'true', the SR-OS
         router would not set the overload bit but would instead set all
         transit links to the maximum value of '0xFFFFFE'."
    DEFVAL      { false }
    ::= { tmnxIsisEntry 64 }

tmnxIsisOverloadOnBootMaxMetric  OBJECT-TYPE
    SYNTAX      TruthValue
    MAX-ACCESS  read-write
    STATUS      current
    DESCRIPTION
        "The value of the object tmnxIsisOverloadOnBootMaxMetric specifies
         whether max-metric is enabled or disabled for this instance of IS-IS
         on the router.

         If the value of tmnxIsisOverloadOnBootMaxMetric set to 'true', the
         SR-OS router would not set the overload bit but would instead set all
         transit links to the maximum value of '0xFFFFFE'."
    DEFVAL      { false }
    ::= { tmnxIsisEntry 65 }

tmnxIsisRouterId                 OBJECT-TYPE
    SYNTAX      Unsigned32
    MAX-ACCESS  read-write
    STATUS      current
    DESCRIPTION
        "The value of the object tmnxIsisRouterId specifies a 32-bit integer
         uniquely identifying the router in the Autonomous System."
    DEFVAL      { 0 }
    ::= { tmnxIsisEntry 66 }

tmnxIsisAdvRtrCapability         OBJECT-TYPE
    SYNTAX      INTEGER {
        disable (0),
        area    (2),
        as      (3)
    }
    MAX-ACCESS  read-write
    STATUS      current
    DESCRIPTION
        "The value of the object tmnxIsisAdvRtrCapability specifies the ISIS
         advertise router capabilities."
    DEFVAL      { disable }
    ::= { tmnxIsisEntry 67 }

tmnxIsisHelloPadding             OBJECT-TYPE
    SYNTAX      INTEGER {
        disable  (0),
        adaptive (1),
        loose    (2),
        strict   (3),
        none     (4)
    }
    MAX-ACCESS  read-write
    STATUS      current
    DESCRIPTION
        "The value of the object tmnxIsisHelloPadding specifies whether padding
         should be done on the ISIS hello packets.

         If the value of tmnxIsisHelloPadding is set to disable, the padding is
         disabled on all types of interfaces for all adjacency states. However,
         padding may be done if it is configured at one of the higher/parent
         levels.

         If the value of tmnxIsisHelloPadding is set to adaptive, the padding
         is done until the state of the neighbor adjacency is up.

         If the value of tmnxIsisHelloPadding is set to loose, the padding is
         done until the state of the neighbor adjacency is initialized.

         If the value of tmnxIsisHelloPadding is set to strict, the padding is
         done for all adjacency states.

         If the value of tmnxIsisHelloPadding is set to none, the padding is
         disabled on all types of interfaces for all adjacency states. Also,
         padding will not be done even if it is configured at one of the
         higher/parent levels."
    DEFVAL      { disable }
    ::= { tmnxIsisEntry 68 }

tmnxIsisLspRefreshInterval       OBJECT-TYPE
    SYNTAX      Unsigned32 (150..65535)
    UNITS       "seconds"
    MAX-ACCESS  read-write
    STATUS      current
    DESCRIPTION
        "The value of the object tmnxIsisLspRefreshInterval specifies the
         interval, in seconds, at which LSPs are refreshed.

         To be able to refresh LSPs before they time out, the
         tmnxIsisLspRefreshInterval must be set to a value less than the value
         set for tmnxIsisLspLifetime.

         The interval value of this object is ignored when
         tmnxIsisLspRefreshHalfLifetime is true."
    DEFVAL      { 600 }
    ::= { tmnxIsisEntry 69 }

tmnxIsisOperRouterId             OBJECT-TYPE
    SYNTAX      Unsigned32
    MAX-ACCESS  read-only
    STATUS      current
    DESCRIPTION
        "The value of tmnxIsisOperRouterId indicates a 32-bit integer uniquely
         identifying the router in the Autonomous System."
    ::= { tmnxIsisEntry 70 }

tmnxIsisAuthKeyChain             OBJECT-TYPE
    SYNTAX      TNamedItemOrEmpty
    MAX-ACCESS  read-write
    STATUS      current
    DESCRIPTION
        "The value of tmnxIsisAuthKeyChain specifies the keychain to use to
         sign and/or authenticate the IS-IS instance.

         The keychain name is defined by tmnxKeyChainName and is the index for
         TIMETRA-SECURITY-MIB::tmnxKeyChainTable"
    DEFVAL      { ''H }
    ::= { tmnxIsisEntry 71 }

tmnxIsisIgnoreLspErrors          OBJECT-TYPE
    SYNTAX      TruthValue
    MAX-ACCESS  read-write
    STATUS      current
    DESCRIPTION
        "The value of the object tmnxIsisIgnoreLspErrors specifies whether
         checksum errors are ignored or not.

         If the value of tmnxIsisIgnoreLspErrors is set to 'false' lsp packets
         (CSNP/PSNP) with checksum errors will purge the corresponding lsp
         entry in the database; if the value is set to 'true', the packet will
         get discarded."
    DEFVAL      { false }
    ::= { tmnxIsisEntry 72 }

tmnxIsisSuppressAttachedBit      OBJECT-TYPE
    SYNTAX      TruthValue
    MAX-ACCESS  read-write
    STATUS      current
    DESCRIPTION
        "The value of the object tmnxIsisSuppressAttachedBit specifies whether
         ISIS protocol will suppress setting the ATT bit on L1L2 router.

         When tmnxIsisSuppressAttachedBit is set to 'true', ISIS protocol will
         suppress setting the ATT bit and therefore suppress the installation
         of a default route to the L1L2 router by all L1 routers in the area."
    DEFVAL      { false }
    ::= { tmnxIsisEntry 73 }

tmnxIsisRemoteLoopfreeAlternate  OBJECT-TYPE
    SYNTAX      TruthValue
    MAX-ACCESS  read-write
    STATUS      current
    DESCRIPTION
        "The value of the object tmnxIsisRemoteLoopfreeAlternate specifies
         whether remote-lfa is enabled or not.

         The value of tmnxIsisRemoteLoopfreeAlternate is only valid when the
         object tmnxIsisLoopfreeAlternate has the value 'true'. "
    DEFVAL      { false }
    ::= { tmnxIsisEntry 74 }

tmnxIsisLevelTable               OBJECT-TYPE
    SYNTAX      SEQUENCE OF TmnxIsisLevelEntry
    MAX-ACCESS  not-accessible
    STATUS      current
    DESCRIPTION
        "The tmnxIsisLevelTable provides attributes to be applied on a specific
         IS-IS protocol level."
    ::= { tmnxIsisSystemObjs 2 }

tmnxIsisLevelEntry               OBJECT-TYPE
    SYNTAX      TmnxIsisLevelEntry
    MAX-ACCESS  not-accessible
    STATUS      current
    DESCRIPTION
        "Each row entry in the tmnxIsisLevelTable represents IS-IS level
         default global attributes to be used with interfaces belonging to
         a specific IS-IS protocol instance on a specific
         router instance.  The rows in this table cannot be created nor
         destroyed by SNMP SET requests.  There are always two rows in this
         table that are created by the agent with default values upon system
         initialization."
    INDEX       {
        vRtrID,
        isisSysInstance,
        tmnxIsisLevel
    }
    ::= { tmnxIsisLevelTable 1 }

TmnxIsisLevelEntry               ::= SEQUENCE
{
    tmnxIsisLevel                    INTEGER,
    tmnxIsisLevelAuthKey             OCTET STRING,
    tmnxIsisLevelAuthType            INTEGER,
    tmnxIsisLevelExtPreference       Unsigned32,
    tmnxIsisLevelPreference          Unsigned32,
    tmnxIsisLevelWideMetricsOnly     TruthValue,
    tmnxIsisLevelOverloadStatus      INTEGER,
    tmnxIsisLevelOverloadTimeLeft    TimeInterval,
    tmnxIsisLevelNumLSPs             Unsigned32,
    tmnxIsisLevelCsnpAuthentication  TruthValue,
    tmnxIsisLevelHelloAuthentication TruthValue,
    tmnxIsisLevelPsnpAuthentication  TruthValue,
    tmnxIsisLevelDefMetric           Unsigned32,
    tmnxIsisLevelIPv6DefMetric       Unsigned32,
    tmnxIsisLevelLoopfreeAltExclude  TruthValue,
    tmnxIsisLevelSpbBridgePriority   Unsigned32,
    tmnxIsisLevelSpbForwardTreeTopo  Unsigned32,
    tmnxIsisLevelDefIPv4McastMetric  Unsigned32,
    tmnxIsisLevelDefIPv6McastMetric  Unsigned32,
    tmnxIsisLevelAdvRtrCapability    TruthValue,
    tmnxIsisLevelAuthKeyChain        TNamedItemOrEmpty,
    tmnxIsisLevelLSPBuffSize         TmnxIsisLSPBuffExtSize,
    tmnxIsisLevelHelloPadding        INTEGER,
    tmnxIsisLevelDbExportExclude     TruthValue,
    tmnxIsisLevelMaxOperLSPBuffSize  Integer32,
    tmnxIsisLevelBierTemplate        TNamedItemOrEmpty,
    tmnxIsisLevelBierTemplAdminState TmnxAdminState
}

tmnxIsisLevel                    OBJECT-TYPE
    SYNTAX      INTEGER {
        level1 (1),
        level2 (2)
    }
    MAX-ACCESS  not-accessible
    STATUS      current
    DESCRIPTION
        "The value of the object tmnxIsisLevel specifies the IS-IS protocol
         level to which these row attributes are applied."
    ::= { tmnxIsisLevelEntry 1 }

tmnxIsisLevelAuthKey             OBJECT-TYPE
    SYNTAX      OCTET STRING (SIZE (0..254))
    MAX-ACCESS  read-write
    STATUS      current
    DESCRIPTION
        "The value of the object tmnxIsisLevelAuthKey specifies the
         authentication key string used to verify the authenticity of packets
         sent by neighboring routers on an IS-IS interface at this level.

         For authentication to succeed both the authentication key and the
         authentication type defined by the tmnxIsisLevelAuthType variable must
         match.

         If tmnxIsisLevelAuthType is set to 'password', tmnxIsisLevelAuthKey
         can include any ASCII character.

         When read, tmnxIsisLevelAuthKey always returns an Octet String of
         length zero."
    DEFVAL      { ''H }
    ::= { tmnxIsisLevelEntry 2 }

tmnxIsisLevelAuthType            OBJECT-TYPE
    SYNTAX      INTEGER {
        none     (1),
        password (2),
        md5      (3)
    }
    MAX-ACCESS  read-write
    STATUS      current
    DESCRIPTION
        "The value of the object tmnxIsisLevelAuthType specifies the method of
         authentication used to verify the authenticity of packets sent by
         neighboring routers on an IS-IS interface at this level.

         For authentication to succeed both the authentication key defined in
         the tmnxIsisLevelAuthKey variable and the authentication type must
         match."
    DEFVAL      { none }
    ::= { tmnxIsisLevelEntry 3 }

tmnxIsisLevelExtPreference       OBJECT-TYPE
    SYNTAX      Unsigned32 (1..255)
    MAX-ACCESS  read-write
    STATUS      current
    DESCRIPTION
        "The value of the object tmnxIsisLevelExtPreference specifies the
         preference level to be used with external routes at this IS-IS level.

         A route can be learned from different routing protocols supported
         in the system, in which case their costs are not comparable.  In
         this case the preference value is used to decide which route to
         use.

         The initial default external preference value for IS-IS level 1
         is 160.  The initial default external preference value for IS-IS
         level 2 is 165."
    ::= { tmnxIsisLevelEntry 4 }

tmnxIsisLevelPreference          OBJECT-TYPE
    SYNTAX      Unsigned32 (1..255)
    MAX-ACCESS  read-write
    STATUS      current
    DESCRIPTION
        "The value of the object tmnxIsisLevelPreference specifies the
         preference level to be used with internal routes at this IS-IS level.

         A route can be learned from different routing protocols supported
         in the system, in which case their costs are not comparable.  In
         this case the preference value is used to decide which route to
         use.

         The initial default internal preference value for IS-IS level 1
         is 15.  The initial default internal preference value for IS-IS
         level 2 is 18."
    ::= { tmnxIsisLevelEntry 5 }

tmnxIsisLevelWideMetricsOnly     OBJECT-TYPE
    SYNTAX      TruthValue
    MAX-ACCESS  read-write
    STATUS      current
    DESCRIPTION
        "The value of the object tmnxIsisLevelWideMetricsOnly specifies whether
         only the wide metric pair of TLVs is generated.

         IS-IS metrics can have values between 1 and 63, referred to as
         small metrics.  IS-IS generates two TLVs: one for the adjacency
         and one for the IP prefix.  In order to support traffic
         engineering, wider metrics are required; a second pair of TLVs
         are also generated.

         When tmnxIsisLevelWideMetricsOnly has a value of 'false', both the
         small and wide metric pairs of TLVs are generated.

         When tmnxIsisLevelWideMetricsOnly has a value of 'true', only the wide
         metric pair of TLVs is generated."
    DEFVAL      { false }
    ::= { tmnxIsisLevelEntry 6 }

tmnxIsisLevelOverloadStatus      OBJECT-TYPE
    SYNTAX      INTEGER {
        notInOverload (1),
        dynamic       (2),
        manual        (3),
        manualOnBoot  (4),
        singleSfm     (5),
        fibAddFail    (6),
        rtmAddFail    (7),
        prefixLimit   (8)
    }
    MAX-ACCESS  read-only
    STATUS      current
    DESCRIPTION
        "The value of the object tmnxIsisLevelOverloadStatus indicates whether
         or not this level is in overload state.

         When tmnxIsisLevelOverloadStatus has the value 'notInOverload', the
         IS-IS level is normal state.

         When tmnxIsisLevelOverloadStatus has the value 'dynamic', the level is
         in the overload state because of insufficient memory to add additional
         entries to the IS-IS database for this level.

         When tmnxIsisLevelOverloadStatus has the value 'manual', the level has
         been put into the overload state administratively as a result of the
         isisSysSetOverload object in the ISIS-MIB having been set.

         When tmnxIsisLevelOverloadStatus has the value 'singleSfm', this level
         is in overload because there is only a single SFM functioning, while
         the value of the single-SFM-overload state  (referred to as
         TIMETRA-VRTR-MIB::vRtrSingleSfmOverloadAdminState) is equal to
         'inService' for this router instance.

         When tmnxIsisLevelOverloadStatus has the value 'fibAddFail', this
         level is in the overload state because adding routes to the FIB fails.

         When tmnxIsisLevelOverloadStatus has the value 'rtmAddFail', the level
         is in the overload state because adding routes to the RTM fails.

         When tmnxIsisLevelOverloadStatus has the value 'prefixLimit', the
         level is in the overload state because this ISIS instance reaches the
         configured maximum prefix limit."
    ::= { tmnxIsisLevelEntry 7 }

tmnxIsisLevelOverloadTimeLeft    OBJECT-TYPE
    SYNTAX      TimeInterval
    MAX-ACCESS  read-only
    STATUS      current
    DESCRIPTION
        "The value of the object tmnxIsisLevelOverloadTimeLeft indicates the
         remaining time, measured in units of centiseconds, before this level
         will attempt to enter its normal state.

         If tmnxIsisLevelOverloadStatus has a value of 'notInOverload', then a
         read of tmnxIsisLevelOverloadTimeLeft returns zero (0)."
    ::= { tmnxIsisLevelEntry 8 }

tmnxIsisLevelNumLSPs             OBJECT-TYPE
    SYNTAX      Unsigned32
    MAX-ACCESS  read-only
    STATUS      current
    DESCRIPTION
        "The value of the object tmnxIsisLevelNumLSPs indicates the number of
         LSPs existing in the system for the particular level."
    ::= { tmnxIsisLevelEntry 9 }

tmnxIsisLevelCsnpAuthentication  OBJECT-TYPE
    SYNTAX      TruthValue
    MAX-ACCESS  read-write
    STATUS      current
    DESCRIPTION
        "The value of the object tmnxIsisLevelCsnpAuthentication specifies
         whether authentication of CSNP packets at this level is enabled or
         not.

         When tmnxIsisLevelCsnpAuthentication has a value of 'true',
         authentication of individual ISIS packets of CSNP type at this level
         is enabled.

         When tmnxIsisLevelCsnpAuthentication has a value of 'false',
         authentication of CSNP packets at this level is suppressed."
    DEFVAL      { true }
    ::= { tmnxIsisLevelEntry 10 }

tmnxIsisLevelHelloAuthentication OBJECT-TYPE
    SYNTAX      TruthValue
    MAX-ACCESS  read-write
    STATUS      current
    DESCRIPTION
        "The value of the object tmnxIsisLevelHelloAuthentication specifies
         whether authentication of HELLO packets at this level is enabled or
         not.

         When tmnxIsisLevelHelloAuthentication has a value of 'true',
         authentication of individual ISIS packets of HELLO type at this level
         is enabled.

         When tmnxIsisLevelHelloAuthentication has a value of 'false',
         authentication of HELLO packets at this level is suppressed."
    DEFVAL      { true }
    ::= { tmnxIsisLevelEntry 11 }

tmnxIsisLevelPsnpAuthentication  OBJECT-TYPE
    SYNTAX      TruthValue
    MAX-ACCESS  read-write
    STATUS      current
    DESCRIPTION
        "The value of the object tmnxIsisLevelPsnpAuthentication specifies
         whether authentication of PSNP packets at this level is enabled or
         not.

         When tmnxIsisLevelPsnpAuthentication has a value of 'true',
         authentication of individual ISIS packets of PSNP type at this level
         is enabled.

         When tmnxIsisLevelPsnpAuthentication has a value of 'false',
         authentication of PSNP packets at this level is suppressed."
    DEFVAL      { true }
    ::= { tmnxIsisLevelEntry 12 }

tmnxIsisLevelDefMetric           OBJECT-TYPE
    SYNTAX      Unsigned32 (0..16777215)
    MAX-ACCESS  read-write
    STATUS      current
    DESCRIPTION
        "The value of the object tmnxIsisLevelDefMetric specifies the
         configurable default metric used for all IS-IS interfaces on this
         level.

         The value of tmnxIsisLevelDefMetric will not be used if
         tmnxIsisIfLevelAdminMetric is configured for an interface."
    DEFVAL      { 10 }
    ::= { tmnxIsisLevelEntry 13 }

tmnxIsisLevelIPv6DefMetric       OBJECT-TYPE
    SYNTAX      Unsigned32 (0..16777215)
    MAX-ACCESS  read-write
    STATUS      current
    DESCRIPTION
        "The value of the object tmnxIsisLevelIPv6DefMetric specifies the
         configurable default metric used for all IS-IS interfaces on this
         level for IPv6.

         The value of tmnxIsisLevelIPv6DefMetric will not be used if
         tmnxIsisIfLvlIPv6UcastAdmMet is configured for an interface."
    DEFVAL      { 10 }
    ::= { tmnxIsisLevelEntry 14 }

tmnxIsisLevelLoopfreeAltExclude  OBJECT-TYPE
    SYNTAX      TruthValue
    MAX-ACCESS  read-write
    STATUS      current
    DESCRIPTION
        "The value of the object tmnxIsisLevelLoopfreeAltExclude specifies
         whether or not the ISIS level should be excluded during LFA
         calculations.

         If the value is 'true', the ISIS level is excluded from LFA
         calculations; if the value is 'false', the ISIS level is included in
         LFA calculations.

         The value of tmnxIsisLevelLoopfreeAltExclude is only valid when
         tmnxIsisLoopfreeAlternate has a value of 'true'."
    DEFVAL      { false }
    ::= { tmnxIsisLevelEntry 15 }

tmnxIsisLevelSpbBridgePriority   OBJECT-TYPE
    SYNTAX      Unsigned32
    MAX-ACCESS  read-only
    STATUS      current
    DESCRIPTION
        "The value of the object tmnxIsisLevelSpbBridgePriority indicates the
         bridge priority of the SPB instance on this IS-IS level."
    ::= { tmnxIsisLevelEntry 16 }

tmnxIsisLevelSpbForwardTreeTopo  OBJECT-TYPE
    SYNTAX      Unsigned32
    MAX-ACCESS  read-only
    STATUS      current
    DESCRIPTION
        "The value of the object tmnxIsisLevelSpbForwardTreeTopo indicates the
         forwarding tree topology of the SPB instance on this IS-IS level."
    ::= { tmnxIsisLevelEntry 17 }

tmnxIsisLevelDefIPv4McastMetric  OBJECT-TYPE
    SYNTAX      Unsigned32 (0..16777215)
    MAX-ACCESS  read-write
    STATUS      current
    DESCRIPTION
        "The value of the object tmnxIsisLevelDefIPv4McastMetric specifies the
         configurable default IPv4 multicast metric used for all IS-IS
         interfaces on this level."
    DEFVAL      { 10 }
    ::= { tmnxIsisLevelEntry 18 }

tmnxIsisLevelDefIPv6McastMetric  OBJECT-TYPE
    SYNTAX      Unsigned32 (0..16777215)
    MAX-ACCESS  read-write
    STATUS      current
    DESCRIPTION
        "The value of the object tmnxIsisLevelDefIPv6McastMetric specifies the
         configurable default IPv6 multicast metric used for all IS-IS
         interfaces on this level."
    DEFVAL      { 10 }
    ::= { tmnxIsisLevelEntry 19 }

tmnxIsisLevelAdvRtrCapability    OBJECT-TYPE
    SYNTAX      TruthValue
    MAX-ACCESS  read-write
    STATUS      current
    DESCRIPTION
        "The value of the object tmnxIsisLevelAdvRtrCapability specifies
         whether or not advertise-router-capabilities are enabled at IS-IS
         instance L1 or L2 level."
    DEFVAL      { true }
    ::= { tmnxIsisLevelEntry 20 }

tmnxIsisLevelAuthKeyChain        OBJECT-TYPE
    SYNTAX      TNamedItemOrEmpty
    MAX-ACCESS  read-write
    STATUS      current
    DESCRIPTION
        "The value of tmnxIsisLevelAuthKeyChain specifies the keychain to use
         to sign and/or authenticate the IS-IS instance L1 or L2 level.

         The keychain name is defined by tmnxKeyChainName and is the index for
         TIMETRA-SECURITY-MIB::tmnxKeyChainTable"
    DEFVAL      { ''H }
    ::= { tmnxIsisLevelEntry 21 }

tmnxIsisLevelLSPBuffSize         OBJECT-TYPE
    SYNTAX      TmnxIsisLSPBuffExtSize
    MAX-ACCESS  read-write
    STATUS      current
    DESCRIPTION
        "The value of the object tmnxIsisLevelLSPBuffSize specifies the maximum
         size of LSPs and SNPs originated by the IS-IS instance L1 or L2 level.

         This object may only be modified when the ISIS-MIB::isisSysAdminState
         member of the corresponding entry in the ISIS-MIB::isisSysTable table
         has a value of 'outOfService (3)'."
    DEFVAL      { 1492 }
    ::= { tmnxIsisLevelEntry 22 }

tmnxIsisLevelHelloPadding        OBJECT-TYPE
    SYNTAX      INTEGER {
        disable  (0),
        adaptive (1),
        loose    (2),
        strict   (3),
        none     (4)
    }
    MAX-ACCESS  read-write
    STATUS      current
    DESCRIPTION
        "The value of the object tmnxIsisLevelHelloPadding specifies whether
         padding should be done on the ISIS hello packets.

         If the value of tmnxIsisLevelHelloPadding is set to disable, the
         padding is disabled on all types of interfaces for all adjacency
         states. However, padding may be done if it is configured at one of the
         higher/parent levels.

         If the value of tmnxIsisLevelHelloPadding is set to adaptive, the
         padding is done until the state of the neighbor adjacency is up.

         If the value of tmnxIsisLevelHelloPadding is set to loose, the padding
         is done until the state of the neighbor adjacency is initialized.

         If the value of tmnxIsisLevelHelloPadding is set to strict, the
         padding is done for all adjacency states.

         If the value of tmnxIsisLevelHelloPadding is set to none, the padding
         is disabled on all types of interfaces for all adjacency states. Also,
         padding will not be done even if it is configured at one of the
         higher/parent levels."
    DEFVAL      { disable }
    ::= { tmnxIsisLevelEntry 23 }

tmnxIsisLevelDbExportExclude     OBJECT-TYPE
    SYNTAX      TruthValue
    MAX-ACCESS  read-write
    STATUS      current
    DESCRIPTION
        "The value of tmnxIsisLevelDbExportExclude specifies whether database
         export is explicitly disabled or not for this IS-IS level.

         If the value is 'true', database export is disabled for this IS-IS
         level.

         If the value is 'false', this level inherits the configuration from
         the instance level; i.e. if tmnxIsisDatabaseExport is 'enabled' for
         the IS-IS instance, then database export is enabled for this level."
    DEFVAL      { false }
    ::= { tmnxIsisLevelEntry 24 }

tmnxIsisLevelMaxOperLSPBuffSize  OBJECT-TYPE
    SYNTAX      Integer32
    MAX-ACCESS  read-only
    STATUS      current
    DESCRIPTION
        "The value of the object tmnxIsisLevelMaxOperLSPBuffSize indicates the
         maximum size of LSPs and SNPs that can be originated on any circuit by
         this instance for a given area.

         The value of tmnxIsisLevelLSPBuffSize and the value of
         tmnxIsisSysOrigL1LSPBuffSize or tmnxIsisSysOrigL2LSPBuffSize which
         specifies the maximum size of LSPs and SNPs for an instance in this
         area should be less than or equal to tmnxIsisLevelMaxOperLSPBuffSize."
    ::= { tmnxIsisLevelEntry 25 }

tmnxIsisLevelBierTemplate        OBJECT-TYPE
    SYNTAX      TNamedItemOrEmpty
    MAX-ACCESS  read-write
    STATUS      current
    DESCRIPTION
        "The value of the object tmnxIsisLevelBierTemplate specifies the BIER
         template name as defined by vRtrBierTemplateName which is  an index in
         the table TIMETRA-BIER-MIB::vRtrBierTemplateTable for this IS-IS
         level."
    DEFVAL      { ''H }
    ::= { tmnxIsisLevelEntry 26 }

tmnxIsisLevelBierTemplAdminState OBJECT-TYPE
    SYNTAX      TmnxAdminState
    MAX-ACCESS  read-write
    STATUS      current
    DESCRIPTION
        "The value of the object tmnxIsisLevelBierTemplAdminState specifies the
         administrative state of the template specified by the object
         tmnxIsisLevelBierTemplate for this IS-IS level."
    DEFVAL      { outOfService }
    ::= { tmnxIsisLevelEntry 27 }

tmnxIsisStatsTable               OBJECT-TYPE
    SYNTAX      SEQUENCE OF TmnxIsisStatsEntry
    MAX-ACCESS  not-accessible
    STATUS      current
    DESCRIPTION
        "The tmnxIsisStatsTable provides statistics for each instance of IS-IS
         protocol configured. There is a one-to-one dependent relationship
         between the tables tmnxIsisTable and tmnxIsisStatsTable."
    ::= { tmnxIsisSystemObjs 3 }

tmnxIsisStatsEntry               OBJECT-TYPE
    SYNTAX      TmnxIsisStatsEntry
    MAX-ACCESS  not-accessible
    STATUS      current
    DESCRIPTION
        "Each row entry in the tmnxIsisStatsTable stores statistics for an
         instance of IS-IS protocol configured."
    INDEX       {
        vRtrID,
        isisSysInstance
    }
    ::= { tmnxIsisStatsTable 1 }

TmnxIsisStatsEntry               ::= SEQUENCE
{
    tmnxIsisStatsSpfRuns             Counter32,
    tmnxIsisStatsLSPRegenerations    Counter32,
    tmnxIsisStatsInitiatedPurges     Counter32,
    tmnxIsisStatsLSPRecd             Counter32,
    tmnxIsisStatsLSPDrop             Counter32,
    tmnxIsisStatsLSPSent             Counter32,
    tmnxIsisStatsLSPRetrans          Counter32,
    tmnxIsisStatsIIHRecd             Counter32,
    tmnxIsisStatsIIHDrop             Counter32,
    tmnxIsisStatsIIHSent             Counter32,
    tmnxIsisStatsIIHRetrans          Counter32,
    tmnxIsisStatsCSNPRecd            Counter32,
    tmnxIsisStatsCSNPDrop            Counter32,
    tmnxIsisStatsCSNPSent            Counter32,
    tmnxIsisStatsCSNPRetrans         Counter32,
    tmnxIsisStatsPSNPRecd            Counter32,
    tmnxIsisStatsPSNPDrop            Counter32,
    tmnxIsisStatsPSNPSent            Counter32,
    tmnxIsisStatsPSNPRetrans         Counter32,
    tmnxIsisStatsUnknownRecd         Counter32,
    tmnxIsisStatsUnknownDrop         Counter32,
    tmnxIsisStatsUnknownSent         Counter32,
    tmnxIsisStatsUnknownRetrans      Counter32,
    tmnxIsisStatsCSPFRequests        Counter32,
    tmnxIsisStatsCSPFDroppedRequests Counter32,
    tmnxIsisStatsCSPFPathsFound      Counter32,
    tmnxIsisStatsCSPFPathsNotFound   Counter32,
    tmnxIsisStatsLfaRuns             Counter32,
    tmnxIsisStatsPartSpfRuns         Counter32,
    tmnxIsisStatsPartSpfTimeStamp    TimeStamp,
    tmnxIsisStatsPartLfaRuns         Counter32,
    tmnxIsisStatsPartLfaTimeStamp    TimeStamp,
    tmnxIsisStatsLfaTimeStamp        TimeStamp,
    tmnxIsisStatsSpfTimeStamp        TimeStamp,
    tmnxIsisStatsSidLabelRangeErrs   Counter32,
    tmnxIsisStatsSidDupErrs          Counter32,
    tmnxIsisStatsRlfaRuns            Counter32,
    tmnxIsisStatsRlfaTimeStamp       TimeStamp,
    tmnxIsisStatsTiLfaRuns           Counter32,
    tmnxIsisStatsTiLfaTimeStamp      TimeStamp
}

tmnxIsisStatsSpfRuns             OBJECT-TYPE
    SYNTAX      Counter32
    MAX-ACCESS  read-only
    STATUS      current
    DESCRIPTION
        "The value of the object tmnxIsisStatsSpfRuns indicates the number of
         times shortest path first calculations have been made."
    ::= { tmnxIsisStatsEntry 1 }

tmnxIsisStatsLSPRegenerations    OBJECT-TYPE
    SYNTAX      Counter32
    MAX-ACCESS  read-only
    STATUS      current
    DESCRIPTION
        "The value of the object tmnxIsisStatsLSPRegenerations indicates the
         count of LSP regenerations."
    ::= { tmnxIsisStatsEntry 2 }

tmnxIsisStatsInitiatedPurges     OBJECT-TYPE
    SYNTAX      Counter32
    MAX-ACCESS  read-only
    STATUS      current
    DESCRIPTION
        "The value of the object tmnxIsisStatsInitiatedPurges indicates the
         number of times purges have been initiated."
    ::= { tmnxIsisStatsEntry 3 }

tmnxIsisStatsLSPRecd             OBJECT-TYPE
    SYNTAX      Counter32
    MAX-ACCESS  read-only
    STATUS      current
    DESCRIPTION
        "The value of the object tmnxIsisStatsLSPRecd indicates the number of
         link state PDUs received by this instance."
    ::= { tmnxIsisStatsEntry 4 }

tmnxIsisStatsLSPDrop             OBJECT-TYPE
    SYNTAX      Counter32
    MAX-ACCESS  read-only
    STATUS      current
    DESCRIPTION
        "The value of the object tmnxIsisStatsLSPDrop indicates the number of
         link state PDUs dropped by this instance."
    ::= { tmnxIsisStatsEntry 5 }

tmnxIsisStatsLSPSent             OBJECT-TYPE
    SYNTAX      Counter32
    MAX-ACCESS  read-only
    STATUS      current
    DESCRIPTION
        "The value of the object tmnxIsisStatsLSPSent indicates the number of
         link state PDUs sent out by this instance."
    ::= { tmnxIsisStatsEntry 6 }

tmnxIsisStatsLSPRetrans          OBJECT-TYPE
    SYNTAX      Counter32
    MAX-ACCESS  read-only
    STATUS      current
    DESCRIPTION
        "The value of the object tmnxIsisStatsLSPRetrans indicates the number
         of link state PDUs that had to be retransmitted by this instance."
    ::= { tmnxIsisStatsEntry 7 }

tmnxIsisStatsIIHRecd             OBJECT-TYPE
    SYNTAX      Counter32
    MAX-ACCESS  read-only
    STATUS      current
    DESCRIPTION
        "The value of the object tmnxIsisStatsIIHRecd indicates the number of
         IS-IS Hello packets received by this instance."
    ::= { tmnxIsisStatsEntry 8 }

tmnxIsisStatsIIHDrop             OBJECT-TYPE
    SYNTAX      Counter32
    MAX-ACCESS  read-only
    STATUS      current
    DESCRIPTION
        "The value of the object tmnxIsisStatsIIHDrop indicates the number of
         IS-IS Hello packets dropped by this instance."
    ::= { tmnxIsisStatsEntry 9 }

tmnxIsisStatsIIHSent             OBJECT-TYPE
    SYNTAX      Counter32
    MAX-ACCESS  read-only
    STATUS      current
    DESCRIPTION
        "The value of the object tmnxIsisStatsIIHSent indicates the number of
         IS-IS Hello packets sent out by this instance."
    ::= { tmnxIsisStatsEntry 10 }

tmnxIsisStatsIIHRetrans          OBJECT-TYPE
    SYNTAX      Counter32
    MAX-ACCESS  read-only
    STATUS      current
    DESCRIPTION
        "The value of the object tmnxIsisStatsIIHRetrans indicates the number
         of IS-IS Hello packets that had to be retransmitted by this instance."
    ::= { tmnxIsisStatsEntry 11 }

tmnxIsisStatsCSNPRecd            OBJECT-TYPE
    SYNTAX      Counter32
    MAX-ACCESS  read-only
    STATUS      current
    DESCRIPTION
        "The value of the object tmnxIsisStatsCSNPRecd indicates the number of
         Complete Sequence Number PDUs received by this instance."
    ::= { tmnxIsisStatsEntry 12 }

tmnxIsisStatsCSNPDrop            OBJECT-TYPE
    SYNTAX      Counter32
    MAX-ACCESS  read-only
    STATUS      current
    DESCRIPTION
        "The value of the object tmnxIsisStatsCSNPDrop indicates the number of
         Complete Sequence Number PDUs dropped by this instance."
    ::= { tmnxIsisStatsEntry 13 }

tmnxIsisStatsCSNPSent            OBJECT-TYPE
    SYNTAX      Counter32
    MAX-ACCESS  read-only
    STATUS      current
    DESCRIPTION
        "The value of the object tmnxIsisStatsCSNPSent indicates the number of
         Complete Sequence Number PDUs sent out by this instance."
    ::= { tmnxIsisStatsEntry 14 }

tmnxIsisStatsCSNPRetrans         OBJECT-TYPE
    SYNTAX      Counter32
    MAX-ACCESS  read-only
    STATUS      current
    DESCRIPTION
        "The value of the object tmnxIsisStatsCSNPRetrans indicates the number
         of Complete Sequence Number PDUs that had to be retransmitted by this
         instance."
    ::= { tmnxIsisStatsEntry 15 }

tmnxIsisStatsPSNPRecd            OBJECT-TYPE
    SYNTAX      Counter32
    MAX-ACCESS  read-only
    STATUS      current
    DESCRIPTION
        "The value of the object tmnxIsisStatsPSNPRecd indicates the number of
         Partial Sequence Number PDUs received by this instance."
    ::= { tmnxIsisStatsEntry 16 }

tmnxIsisStatsPSNPDrop            OBJECT-TYPE
    SYNTAX      Counter32
    MAX-ACCESS  read-only
    STATUS      current
    DESCRIPTION
        "The value of the object tmnxIsisStatsPSNPDrop indicates the number of
         Partial Sequence Number PDUs dropped by this instance."
    ::= { tmnxIsisStatsEntry 17 }

tmnxIsisStatsPSNPSent            OBJECT-TYPE
    SYNTAX      Counter32
    MAX-ACCESS  read-only
    STATUS      current
    DESCRIPTION
        "The value of the object tmnxIsisStatsPSNPSent indicates the number of
         Partial Sequence Number PDUs sent out by this instance."
    ::= { tmnxIsisStatsEntry 18 }

tmnxIsisStatsPSNPRetrans         OBJECT-TYPE
    SYNTAX      Counter32
    MAX-ACCESS  read-only
    STATUS      current
    DESCRIPTION
        "The value of the object tmnxIsisStatsPSNPRetrans indicates the number
         of Partial Sequence Number PDUs that had to be retransmitted by this
         instance."
    ::= { tmnxIsisStatsEntry 19 }

tmnxIsisStatsUnknownRecd         OBJECT-TYPE
    SYNTAX      Counter32
    MAX-ACCESS  read-only
    STATUS      current
    DESCRIPTION
        "The value of the object tmnxIsisStatsUnknownRecd indicates the number
         of unknown packets received by this instance."
    ::= { tmnxIsisStatsEntry 20 }

tmnxIsisStatsUnknownDrop         OBJECT-TYPE
    SYNTAX      Counter32
    MAX-ACCESS  read-only
    STATUS      current
    DESCRIPTION
        "The value of the object tmnxIsisStatsUnknownDrop indicates the number
         of unknown packets dropped by this instance."
    ::= { tmnxIsisStatsEntry 21 }

tmnxIsisStatsUnknownSent         OBJECT-TYPE
    SYNTAX      Counter32
    MAX-ACCESS  read-only
    STATUS      current
    DESCRIPTION
        "The value of the object tmnxIsisStatsUnknownSent indicates the number
         of unknown packets sent out by this instance."
    ::= { tmnxIsisStatsEntry 22 }

tmnxIsisStatsUnknownRetrans      OBJECT-TYPE
    SYNTAX      Counter32
    MAX-ACCESS  read-only
    STATUS      current
    DESCRIPTION
        "The value of the object tmnxIsisStatsUnknownRetrans indicates the
         number of unknown packets that had to be retransmitted by this
         instance."
    ::= { tmnxIsisStatsEntry 23 }

tmnxIsisStatsCSPFRequests        OBJECT-TYPE
    SYNTAX      Counter32
    MAX-ACCESS  read-only
    STATUS      current
    DESCRIPTION
        "The value of the object tmnxIsisStatsCSPFRequests indicates the number
         of CSPF requests made to the protocol."
    ::= { tmnxIsisStatsEntry 24 }

tmnxIsisStatsCSPFDroppedRequests OBJECT-TYPE
    SYNTAX      Counter32
    MAX-ACCESS  read-only
    STATUS      current
    DESCRIPTION
        "The value of the object tmnxIsisStatsCSPFDroppedRequests indicates the
         number of dropped CSPF requests by the protocol."
    ::= { tmnxIsisStatsEntry 25 }

tmnxIsisStatsCSPFPathsFound      OBJECT-TYPE
    SYNTAX      Counter32
    MAX-ACCESS  read-only
    STATUS      current
    DESCRIPTION
        "The value of the object tmnxIsisStatsCSPFPathsFound indicates the
         number of responses to CSPF requests for which paths satisfying the
         constraints were found."
    ::= { tmnxIsisStatsEntry 26 }

tmnxIsisStatsCSPFPathsNotFound   OBJECT-TYPE
    SYNTAX      Counter32
    MAX-ACCESS  read-only
    STATUS      current
    DESCRIPTION
        "The value of the object tmnxIsisStatsCSPFPathsNotFound indicates the
         number of responses to CSPF requests for which no paths satisfying the
         constraints were found."
    ::= { tmnxIsisStatsEntry 27 }

tmnxIsisStatsLfaRuns             OBJECT-TYPE
    SYNTAX      Counter32
    MAX-ACCESS  read-only
    STATUS      current
    DESCRIPTION
        "The value of the object tmnxIsisStatsLfaRuns indicates the number of
         times loopfree-alternate calculations have been made."
    ::= { tmnxIsisStatsEntry 28 }

tmnxIsisStatsPartSpfRuns         OBJECT-TYPE
    SYNTAX      Counter32
    MAX-ACCESS  read-only
    STATUS      current
    DESCRIPTION
        "The value of the object tmnxIsisStatsPartSpfRuns indicates the number
         of times Partial SPF calculations have been made."
    ::= { tmnxIsisStatsEntry 29 }

tmnxIsisStatsPartSpfTimeStamp    OBJECT-TYPE
    SYNTAX      TimeStamp
    MAX-ACCESS  read-only
    STATUS      current
    DESCRIPTION
        "The value of the object tmnxIsisStatsPartSpfTimeStamp indicates the
         timestamp when the last Partial SPF was scheduled."
    ::= { tmnxIsisStatsEntry 30 }

tmnxIsisStatsPartLfaRuns         OBJECT-TYPE
    SYNTAX      Counter32
    MAX-ACCESS  read-only
    STATUS      current
    DESCRIPTION
        "The value of the object tmnxIsisStatsPartLfaRuns indicates the number
         of times Partial LFA calculations have been made."
    ::= { tmnxIsisStatsEntry 31 }

tmnxIsisStatsPartLfaTimeStamp    OBJECT-TYPE
    SYNTAX      TimeStamp
    MAX-ACCESS  read-only
    STATUS      current
    DESCRIPTION
        "The value of the object tmnxIsisStatsPartLfaTimeStamp indicates the
         timestamp when the last Partial LFA was scheduled."
    ::= { tmnxIsisStatsEntry 32 }

tmnxIsisStatsLfaTimeStamp        OBJECT-TYPE
    SYNTAX      TimeStamp
    MAX-ACCESS  read-only
    STATUS      current
    DESCRIPTION
        "The value of the object tmnxIsisStatsLfaTimeStamp indicates the
         timestamp when the last LFA was scheduled."
    ::= { tmnxIsisStatsEntry 33 }

tmnxIsisStatsSpfTimeStamp        OBJECT-TYPE
    SYNTAX      TimeStamp
    MAX-ACCESS  read-only
    STATUS      current
    DESCRIPTION
        "The value of the object tmnxIsisStatsSpfTimeStamp indicates the
         timestamp when the last SPF was scheduled."
    ::= { tmnxIsisStatsEntry 34 }

tmnxIsisStatsSidLabelRangeErrs   OBJECT-TYPE
    SYNTAX      Counter32
    MAX-ACCESS  read-only
    STATUS      current
    DESCRIPTION
        "The value of tmnxIsisStatsSidLabelRangeErrs gives the total number of
         errors for SIDs that are not within the label-range of the router."
    ::= { tmnxIsisStatsEntry 35 }

tmnxIsisStatsSidDupErrs          OBJECT-TYPE
    SYNTAX      Counter32
    MAX-ACCESS  read-only
    STATUS      current
    DESCRIPTION
        "The value of tmnxIsisStatsSidDupErrs gives the total number of errors
         for SIDs which are already assigned to another prefix."
    ::= { tmnxIsisStatsEntry 36 }

tmnxIsisStatsRlfaRuns            OBJECT-TYPE
    SYNTAX      Counter32
    MAX-ACCESS  read-only
    STATUS      current
    DESCRIPTION
        "The value of the object tmnxIsisStatsRlfaRuns indicates the number of
         times remote-loopfree-alternate calculations have been made."
    ::= { tmnxIsisStatsEntry 37 }

tmnxIsisStatsRlfaTimeStamp       OBJECT-TYPE
    SYNTAX      TimeStamp
    MAX-ACCESS  read-only
    STATUS      current
    DESCRIPTION
        "The value of the object tmnxIsisStatsRlfaTimeStamp indicates the
         timestamp when the last RLFA was scheduled."
    ::= { tmnxIsisStatsEntry 38 }

tmnxIsisStatsTiLfaRuns           OBJECT-TYPE
    SYNTAX      Counter32
    MAX-ACCESS  read-only
    STATUS      current
    DESCRIPTION
        "The value of the object tmnxIsisStatsTiLfaRuns indicates the number of
         times Topology Independent loopfree-alternate calculations have been
         made."
    ::= { tmnxIsisStatsEntry 39 }

tmnxIsisStatsTiLfaTimeStamp      OBJECT-TYPE
    SYNTAX      TimeStamp
    MAX-ACCESS  read-only
    STATUS      current
    DESCRIPTION
        "The value of the object tmnxIsisStatsTiLfaTimeStamp indicates the
         timestamp when the last Topology Independent LFA was scheduled."
    ::= { tmnxIsisStatsEntry 40 }

tmnxIsisHostTable                OBJECT-TYPE
    SYNTAX      SEQUENCE OF TmnxIsisHostEntry
    MAX-ACCESS  not-accessible
    STATUS      current
    DESCRIPTION
        "The tmnxIsisHostTable provides the mapping of a system-id for an IS to
         the hostname as provided by the system. This table may not have
         mapping of all system-id to hostname as it is not mandatory to
         exchange hostnames."
    ::= { tmnxIsisSystemObjs 4 }

tmnxIsisHostEntry                OBJECT-TYPE
    SYNTAX      TmnxIsisHostEntry
    MAX-ACCESS  not-accessible
    STATUS      current
    DESCRIPTION
        "Each row entry in the tmnxIsisHostTable stores the mapping of a
         system-id to a hostname."
    INDEX       {
        vRtrID,
        isisSysInstance,
        tmnxIsisHostSysID
    }
    ::= { tmnxIsisHostTable 1 }

TmnxIsisHostEntry                ::= SEQUENCE
{
    tmnxIsisHostSysID                SystemID,
    tmnxIsisHostName                 DisplayString
}

tmnxIsisHostSysID                OBJECT-TYPE
    SYNTAX      SystemID
    MAX-ACCESS  not-accessible
    STATUS      current
    DESCRIPTION
        "The value of the object tmnxIsisHostSysID specifies the system-id for
         which we map the hostname in the object tmnxIsisHostName."
    ::= { tmnxIsisHostEntry 1 }

tmnxIsisHostName                 OBJECT-TYPE
    SYNTAX      DisplayString
    MAX-ACCESS  read-only
    STATUS      current
    DESCRIPTION
        "The value of the object tmnxIsisHostName indicates the mapping
         hostname for the corresponding system-id."
    ::= { tmnxIsisHostEntry 2 }

tmnxIsisRouteTable               OBJECT-TYPE
    SYNTAX      SEQUENCE OF TmnxIsisRouteEntry
    MAX-ACCESS  not-accessible
    STATUS      obsolete
    DESCRIPTION
        "The tmnxIsisRouteTable maintains the routes learned by an instance of
         IS-IS protocol for a specific multi topology id. This table is
         replaced by tmnxIsisRouteNhTable."
    ::= { tmnxIsisSystemObjs 5 }

tmnxIsisRouteEntry               OBJECT-TYPE
    SYNTAX      TmnxIsisRouteEntry
    MAX-ACCESS  not-accessible
    STATUS      obsolete
    DESCRIPTION
        "Each row entry in the tmnxIsisRouteTable stores a route for a given
         instance of the IS-IS protocol for a specific multi topology id."
    INDEX       {
        vRtrID,
        isisSysInstance,
        tmnxIsisRouteMtId,
        tmnxIsisRouteDestType,
        tmnxIsisRouteDest,
        tmnxIsisRoutePrefixLength,
        tmnxIsisRouteNexthopIPType,
        tmnxIsisRouteNexthopIP
    }
    ::= { tmnxIsisRouteTable 1 }

TmnxIsisRouteEntry               ::= SEQUENCE
{
    tmnxIsisRouteMtId                Unsigned32,
    tmnxIsisRouteDestType            InetAddressType,
    tmnxIsisRouteDest                InetAddress,
    tmnxIsisRoutePrefixLength        InetAddressPrefixLength,
    tmnxIsisRouteNexthopIPType       InetAddressType,
    tmnxIsisRouteNexthopIP           InetAddress,
    tmnxIsisRouteLevel               INTEGER,
    tmnxIsisRouteSpfRunNumber        Counter32,
    tmnxIsisRouteMetric              Unsigned32,
    tmnxIsisRouteType                INTEGER,
    tmnxIsisRouteNHopSysID           SystemID,
    tmnxIsisRouteTag                 Unsigned32,
    tmnxIsisRouteBkupFlags           INTEGER,
    tmnxIsisRouteBkupNextHopTy       INTEGER,
    tmnxIsisRouteBkupNextHopType     InetAddressType,
    tmnxIsisRouteBkupNextHop         InetAddress,
    tmnxIsisRouteBkupMetric          Unsigned32,
    tmnxIsisRouteNextHopType         TmnxInetCidrNextHopType,
    tmnxIsisRouteNextHopOwner        TmnxInetCidrNextHopOwner,
    tmnxIsisRouteNHOwnerAuxInfo      Unsigned32,
    tmnxIsisRouteBkupNHType          TmnxInetCidrNextHopType,
    tmnxIsisRouteBkupNHOwner         TmnxInetCidrNextHopOwner,
    tmnxIsisRouteBkupNHOwnAxInfo     Unsigned32,
    tmnxIsisRouteSidFlags            BITS,
    tmnxIsisRouteSidValue            Unsigned32,
    tmnxIsisRouteStatus              INTEGER
}

tmnxIsisRouteMtId                OBJECT-TYPE
    SYNTAX      Unsigned32
    MAX-ACCESS  not-accessible
    STATUS      current
    DESCRIPTION
        "The value of the object tmnxIsisRouteMtId specifies the multi topology
         id number for this route.

         If multi-topology is not supported for the route then the value of
         tmnxIsisRouteMtId should be 0."
    ::= { tmnxIsisRouteEntry 1 }

tmnxIsisRouteDestType            OBJECT-TYPE
    SYNTAX      InetAddressType
    MAX-ACCESS  not-accessible
    STATUS      current
    DESCRIPTION
        "The value of the object tmnxIsisRouteDestType specifies the IP address
         type for tmnxIsisRouteDest."
    ::= { tmnxIsisRouteEntry 2 }

tmnxIsisRouteDest                OBJECT-TYPE
    SYNTAX      InetAddress (SIZE (4|16|20))
    MAX-ACCESS  not-accessible
    STATUS      current
    DESCRIPTION
        "The value of the object tmnxIsisRouteDest specifies the destination IP
         address of this route.

         The address type of tmnxIsisRouteDest is indicated by
         tmnxIsisRouteDestType."
    ::= { tmnxIsisRouteEntry 3 }

tmnxIsisRoutePrefixLength        OBJECT-TYPE
    SYNTAX      InetAddressPrefixLength
    MAX-ACCESS  not-accessible
    STATUS      current
    DESCRIPTION
        "The value of the object tmnxIsisRoutePrefixLength specifies the prefix
         length to be used with tmnxIsisRouteDest to get the network prefix."
    ::= { tmnxIsisRouteEntry 4 }

tmnxIsisRouteNexthopIPType       OBJECT-TYPE
    SYNTAX      InetAddressType
    MAX-ACCESS  not-accessible
    STATUS      obsolete
    DESCRIPTION
        "The value of the object tmnxIsisRouteNexthopIPType specifies the IP
         address type for tmnxIsisRouteNexthopIP."
    ::= { tmnxIsisRouteEntry 5 }

tmnxIsisRouteNexthopIP           OBJECT-TYPE
    SYNTAX      InetAddress (SIZE (4|16|20))
    MAX-ACCESS  not-accessible
    STATUS      obsolete
    DESCRIPTION
        "The value of the object tmnxIsisRouteNexthopIP specifies the IP
         address of the nexthop for this route.

         The address type of tmnxIsisRouteNexthopIP is indicated by
         tmnxIsisRouteNexthopIPType"
    ::= { tmnxIsisRouteEntry 6 }

tmnxIsisRouteLevel               OBJECT-TYPE
    SYNTAX      INTEGER {
        level1IS (1),
        level2IS (2)
    }
    MAX-ACCESS  read-only
    STATUS      obsolete
    DESCRIPTION
        "The value of the object tmnxIsisRouteLevel indicates the IS-IS Level
         at which the prefix was learned."
    ::= { tmnxIsisRouteEntry 7 }

tmnxIsisRouteSpfRunNumber        OBJECT-TYPE
    SYNTAX      Counter32
    MAX-ACCESS  read-only
    STATUS      obsolete
    DESCRIPTION
        "The value of the object tmnxIsisRouteSpfRunNumber indicates the run of
         spf calculation in which this route was selected."
    ::= { tmnxIsisRouteEntry 8 }

tmnxIsisRouteMetric              OBJECT-TYPE
    SYNTAX      Unsigned32
    MAX-ACCESS  read-only
    STATUS      obsolete
    DESCRIPTION
        "The value of the object tmnxIsisRouteMetric indicates the metric value
         associated with the route.

         This metric is obtained by the SPF calculations and is used by the
         instance of the protocol.

         For a given destination prefix, the route with the lower metric is the
         shorter route."
    ::= { tmnxIsisRouteEntry 9 }

tmnxIsisRouteType                OBJECT-TYPE
    SYNTAX      INTEGER {
        internal (1),
        external (2)
    }
    MAX-ACCESS  read-only
    STATUS      obsolete
    DESCRIPTION
        "The value of the object tmnxIsisRouteType indicates the type of route
         represented by this row entry."
    ::= { tmnxIsisRouteEntry 10 }

tmnxIsisRouteNHopSysID           OBJECT-TYPE
    SYNTAX      SystemID
    MAX-ACCESS  read-only
    STATUS      obsolete
    DESCRIPTION
        "The value of the object tmnxIsisRouteNHopSysID indicates the system-id
         of the nexthop IS through which this route is reachable."
    ::= { tmnxIsisRouteEntry 11 }

tmnxIsisRouteTag                 OBJECT-TYPE
    SYNTAX      Unsigned32
    MAX-ACCESS  read-only
    STATUS      obsolete
    DESCRIPTION
        "The value of the object tmnxIsisRouteTag indicates a 32-bit integer
         route tag for this route.

         A value of 0 indicates that the tag has not been set."
    ::= { tmnxIsisRouteEntry 12 }

tmnxIsisRouteBkupFlags           OBJECT-TYPE
    SYNTAX      INTEGER {
        none   (0),
        hasLfa (1)
    }
    MAX-ACCESS  read-only
    STATUS      obsolete
    DESCRIPTION
        "The value of the object tmnxIsisRouteBkupFlags indicates the presence
         or absence of LFA next-hops.

         The value 'none'  indicates that no next-hop is present;
         the value 'hasLfa' indicates that an LFA next-hop is present in addition
         to the regular next-hop."
    ::= { tmnxIsisRouteEntry 13 }

tmnxIsisRouteBkupNextHopTy       OBJECT-TYPE
    SYNTAX      INTEGER {
        notApplicable  (0),
        nodeProtection (1),
        linkProtection (2)
    }
    MAX-ACCESS  read-only
    STATUS      obsolete
    DESCRIPTION
        "The value of the object tmnxIsisRouteBkupNextHopTy indicates the type
         of protection used by the backup next-hop.

         The value 'notApplicable' indicates that the backup next-hop type is
         not applicable; the value 'nodeProtection' indicates that the backup
         next-hop uses a node-protection mechanism; the value 'linkProtection'
         indicates that the backup next-hop uses link-protection mechanism."
    ::= { tmnxIsisRouteEntry 14 }

tmnxIsisRouteBkupNextHopType     OBJECT-TYPE
    SYNTAX      InetAddressType
    MAX-ACCESS  read-only
    STATUS      obsolete
    DESCRIPTION
        "The value of the object tmnxIsisRouteBkupNextHopType indicates the IP
         address type for tmnxIsisRouteBkupNextHop."
    ::= { tmnxIsisRouteEntry 15 }

tmnxIsisRouteBkupNextHop         OBJECT-TYPE
    SYNTAX      InetAddress (SIZE (0|4|16|20))
    MAX-ACCESS  read-only
    STATUS      obsolete
    DESCRIPTION
        "The value of the object tmnxIsisRouteBkupNextHop indicates the IP
         address of a backup next-hop.

         The value of tmnxIsisRouteBkupNextHop is only valid when
         tmnxIsisRouteBkupFlags has a value of 'hasLfa'.

         The address type of tmnxIsisRouteBkupNextHop is indicated by the value
         of tmnxIsisRouteBkupNextHopType."
    ::= { tmnxIsisRouteEntry 16 }

tmnxIsisRouteBkupMetric          OBJECT-TYPE
    SYNTAX      Unsigned32
    MAX-ACCESS  read-only
    STATUS      obsolete
    DESCRIPTION
        "The value of the object tmnxIsisRouteBkupMetric indicates the routing
         metric for a backup route.

         The semantics of this metric are determined by the routing-protocol
         specified in the route's ipCidrRouteProto value.

         The value of tmnxIsisRouteBkupMetric is only valid when
         tmnxIsisRouteBkupFlags has a value of 'hasLfa'."
    ::= { tmnxIsisRouteEntry 17 }

tmnxIsisRouteNextHopType         OBJECT-TYPE
    SYNTAX      TmnxInetCidrNextHopType
    MAX-ACCESS  read-only
    STATUS      obsolete
    DESCRIPTION
        "The value of the object tmnxIsisRouteNextHopType indicates the type of
         next hop for this route."
    ::= { tmnxIsisRouteEntry 18 }

tmnxIsisRouteNextHopOwner        OBJECT-TYPE
    SYNTAX      TmnxInetCidrNextHopOwner
    MAX-ACCESS  read-only
    STATUS      obsolete
    DESCRIPTION
        "The value of the object tmnxIsisRouteNextHopOwner indicates the owner
         of next hop for this route."
    ::= { tmnxIsisRouteEntry 19 }

tmnxIsisRouteNHOwnerAuxInfo      OBJECT-TYPE
    SYNTAX      Unsigned32
    MAX-ACCESS  read-only
    STATUS      obsolete
    DESCRIPTION
        "The value of the object tmnxIsisRouteNHOwnerAuxInfo indicates the
         auxiliary information for next hop owner as indicated by
         tmnxIsisRouteNextHopOwner.

         The value of tmnxIsisRouteNHOwnerAuxInfo indicates the tunnel id
         existing for this next hop type and owner."
    ::= { tmnxIsisRouteEntry 20 }

tmnxIsisRouteBkupNHType          OBJECT-TYPE
    SYNTAX      TmnxInetCidrNextHopType
    MAX-ACCESS  read-only
    STATUS      obsolete
    DESCRIPTION
        "The value of the object tmnxIsisRouteBkupNHType indicates the type of
         next hop for this backup route."
    ::= { tmnxIsisRouteEntry 21 }

tmnxIsisRouteBkupNHOwner         OBJECT-TYPE
    SYNTAX      TmnxInetCidrNextHopOwner
    MAX-ACCESS  read-only
    STATUS      obsolete
    DESCRIPTION
        "The value of the object tmnxIsisRouteBkupNHOwner indicates the owner
         of next hop for this backup route."
    ::= { tmnxIsisRouteEntry 22 }

tmnxIsisRouteBkupNHOwnAxInfo     OBJECT-TYPE
    SYNTAX      Unsigned32
    MAX-ACCESS  read-only
    STATUS      obsolete
    DESCRIPTION
        "The value of the object tmnxIsisRouteBkupNHOwnAxInfo indicates the
         auxiliary information, for next hop owner as indicated by
         tmnxIsisRouteBkupNHOwner.

         The value of tmnxIsisRouteBkupNHOwnAxInfo indicates the tunnel id
         existing for this backup next hop type and owner."
    ::= { tmnxIsisRouteEntry 23 }

tmnxIsisRouteSidFlags            OBJECT-TYPE
    SYNTAX      BITS {
        bitUsed (0),
        bitR    (1),
        bitN    (2),
        bitP    (3),
        bitE    (4),
        bitV    (5),
        bitL    (6)
    }
    MAX-ACCESS  read-only
    STATUS      obsolete
    DESCRIPTION
        "The value of the object tmnxIsisRouteSidFlags indicates the flags of a
         Prefix-SID as defined by IETF segment routing.

         bitUsed(0)  - If set, tmnxIsisRouteSidValue is valid.
         bitR   (1)  - Re-advertisement flag.  If set, then the prefix to
           which this Prefix-SID is attached, has been propagated by the
           router either from another level (i.e.: from level-1 to level-2
           or the opposite) or from redistribution (e.g.: from another
           protocol).
         bitN   (2)  - Node-SID flag. The N-Flag is set on Prefix-SIDs
           attached to a router loopback address.
         bitP   (3)  - no-PHP flag. If set, then the penultimate hop MUST NOT
           pop the Prefix-SID before delivering the packet to the node
           that advertised the Prefix-SID.
         bitE   (4)  - Explicit-Null Flag.  If set, any upstream neighbor
           of the Prefix-SID originator MUST replace the Prefix-SID with
           a Prefix-SID having an Explicit-NULL value (0 for IPv4 and 2 for
           IPv6) before forwarding the packet.
         bitV   (5)  - Value flag. If set, then the Prefix-SID carries a
           value (instead of an index).
         bitL   (6)  - Local Flag.  If set, then the value/index carried by
           the Prefix-SID has local significance."
    ::= { tmnxIsisRouteEntry 24 }

tmnxIsisRouteSidValue            OBJECT-TYPE
    SYNTAX      Unsigned32
    MAX-ACCESS  read-only
    STATUS      obsolete
    DESCRIPTION
        "The value of the object tmnxIsisRouteSidValue indicates the SID label
         or index for this prefix."
    ::= { tmnxIsisRouteEntry 25 }

tmnxIsisRouteStatus              OBJECT-TYPE
    SYNTAX      INTEGER {
        active       (0),
        rtmAddFailed (1),
        fibAddFailed (2)
    }
    MAX-ACCESS  read-only
    STATUS      obsolete
    DESCRIPTION
        "The value of tmnxIsisRouteStatus indicates the reason why a route is
         not active."
    ::= { tmnxIsisRouteEntry 26 }

tmnxIsisPathTable                OBJECT-TYPE
    SYNTAX      SEQUENCE OF TmnxIsisPathEntry
    MAX-ACCESS  not-accessible
    STATUS      current
    DESCRIPTION
        "The tmnxIsisPathTable maintains information regarding SPF calculation
         for each instance of IS-IS protocol."
    ::= { tmnxIsisSystemObjs 6 }

tmnxIsisPathEntry                OBJECT-TYPE
    SYNTAX      TmnxIsisPathEntry
    MAX-ACCESS  not-accessible
    STATUS      current
    DESCRIPTION
        "Each row entry in the tmnxIsisPathTable represents the ISIS path for
         an instance, level, multi topology id, path identifier and the path
         outgoing interface."
    INDEX       {
        vRtrID,
        isisSysInstance,
        tmnxIsisLevel,
        tmnxIsisPathMtID,
        tmnxIsisPathID,
        tmnxIsisPathIfIndex,
        tmnxIsisPathNHopSysID
    }
    ::= { tmnxIsisPathTable 1 }

TmnxIsisPathEntry                ::= SEQUENCE
{
    tmnxIsisPathMtID                 Unsigned32,
    tmnxIsisPathID                   OCTET STRING,
    tmnxIsisPathIfIndex              InterfaceIndex,
    tmnxIsisPathNHopSysID            SystemID,
    tmnxIsisPathMetric               Unsigned32,
    tmnxIsisPathSNPA                 SNPAAddress,
    tmnxIsisPathLfaIfIndex           InterfaceIndexOrZero,
    tmnxIsisPathLfaNHop              SystemID,
    tmnxIsisPathLfaMetric            Unsigned32,
    tmnxIsisPathLfaType              INTEGER,
    tmnxIsisPathRouteType            INTEGER
}

tmnxIsisPathMtID                 OBJECT-TYPE
    SYNTAX      Unsigned32
    MAX-ACCESS  not-accessible
    STATUS      current
    DESCRIPTION
        "The value of the object tmnxIsisPathMtID specifies the multi-topology
         id number for the path.

         If multi-topology is not supported for the path then the value of
         tmnxIsisPathMtID should be 0."
    ::= { tmnxIsisPathEntry 1 }

tmnxIsisPathID                   OBJECT-TYPE
    SYNTAX      OCTET STRING (SIZE (7))
    MAX-ACCESS  not-accessible
    STATUS      current
    DESCRIPTION
        "The value of the object tmnxIsisPathID specifies the path identifier
         and has first 6 octets as the system-id followed by one octet of the
         Lan-ID."
    ::= { tmnxIsisPathEntry 2 }

tmnxIsisPathIfIndex              OBJECT-TYPE
    SYNTAX      InterfaceIndex
    MAX-ACCESS  not-accessible
    STATUS      current
    DESCRIPTION
        "The value of the object tmnxIsisPathIfIndex specifies the ifIndex of
         the outgoing interface for the path."
    ::= { tmnxIsisPathEntry 3 }

tmnxIsisPathNHopSysID            OBJECT-TYPE
    SYNTAX      SystemID
    MAX-ACCESS  not-accessible
    STATUS      current
    DESCRIPTION
        "The value of the object tmnxIsisPathNHopSysID specifies the system-id
         of the nexthop and is used to reference the nexthop for this route."
    ::= { tmnxIsisPathEntry 4 }

tmnxIsisPathMetric               OBJECT-TYPE
    SYNTAX      Unsigned32
    MAX-ACCESS  read-only
    STATUS      current
    DESCRIPTION
        "The value of the object tmnxIsisPathMetric indicates the metric
         assigned to this path entry after SPF calculations.

         The lower the metric value, the shorter is the path and hence more
         preferred by the protocol."
    ::= { tmnxIsisPathEntry 5 }

tmnxIsisPathSNPA                 OBJECT-TYPE
    SYNTAX      SNPAAddress
    MAX-ACCESS  read-only
    STATUS      current
    DESCRIPTION
        "The value of the object tmnxIsisPathSNPA indicates the subnet point of
         attachment for this path."
    ::= { tmnxIsisPathEntry 6 }

tmnxIsisPathLfaIfIndex           OBJECT-TYPE
    SYNTAX      InterfaceIndexOrZero
    MAX-ACCESS  read-only
    STATUS      current
    DESCRIPTION
        "The value of the object tmnxIsisPathLfaIfIndex indicates the
         loopfree-alternate ifIndex of the outgoing interface for the path."
    ::= { tmnxIsisPathEntry 7 }

tmnxIsisPathLfaNHop              OBJECT-TYPE
    SYNTAX      SystemID
    MAX-ACCESS  read-only
    STATUS      current
    DESCRIPTION
        "The value of the object tmnxIsisPathLfaNHop indicates the
         loopfree-alternate nexthop and is referenced by the system-id."
    ::= { tmnxIsisPathEntry 8 }

tmnxIsisPathLfaMetric            OBJECT-TYPE
    SYNTAX      Unsigned32
    MAX-ACCESS  read-only
    STATUS      current
    DESCRIPTION
        "The value of the object tmnxIsisPathLfaMetric indicates the metric
         assigned to this entry which are a result of loopfree-alternate
         calculations.

         The lower the metric value, the shorter is the path and hence more
         preferred by the protocol."
    ::= { tmnxIsisPathEntry 9 }

tmnxIsisPathLfaType              OBJECT-TYPE
    SYNTAX      INTEGER {
        none     (0),
        nodeLink (1),
        pathLink (2)
    }
    MAX-ACCESS  read-only
    STATUS      current
    DESCRIPTION
        "The value of the object tmnxIsisPathLfaType indicates the type of
         route represented by this row entry."
    ::= { tmnxIsisPathEntry 10 }

tmnxIsisPathRouteType            OBJECT-TYPE
    SYNTAX      INTEGER {
        spf (0),
        lfa (1)
    }
    MAX-ACCESS  read-only
    STATUS      current
    DESCRIPTION
        "The value of the object tmnxIsisPathRouteType indicates whether a
         backup route exists for this row entry."
    ::= { tmnxIsisPathEntry 11 }

tmnxIsisLSPTable                 OBJECT-TYPE
    SYNTAX      SEQUENCE OF TmnxIsisLSPEntry
    MAX-ACCESS  not-accessible
    STATUS      current
    DESCRIPTION
        "The tmnxIsisLSPTable maintain information regarding all the LSPs in
         the LSP database of each instance of IS-IS protocol for a given level."
    ::= { tmnxIsisSystemObjs 7 }

tmnxIsisLSPEntry                 OBJECT-TYPE
    SYNTAX      TmnxIsisLSPEntry
    MAX-ACCESS  not-accessible
    STATUS      current
    DESCRIPTION
        "Each row entry in the tmnxIsisLSPTable represents an LSP in the LSP
         database."
    INDEX       {
        vRtrID,
        isisSysInstance,
        tmnxIsisLevel,
        tmnxIsisLSPId
    }
    ::= { tmnxIsisLSPTable 1 }

TmnxIsisLSPEntry                 ::= SEQUENCE
{
    tmnxIsisLSPId                    OCTET STRING,
    tmnxIsisLSPSeq                   Counter32,
    tmnxIsisLSPChecksum              Integer32,
    tmnxIsisLSPLifetimeRemain        Integer32,
    tmnxIsisLSPVersion               Integer32,
    tmnxIsisLSPPktType               Integer32,
    tmnxIsisLSPPktVersion            Integer32,
    tmnxIsisLSPMaxArea               Integer32,
    tmnxIsisLSPSysIdLen              Integer32,
    tmnxIsisLSPAttributes            Integer32,
    tmnxIsisLSPUsedLen               Integer32,
    tmnxIsisLSPAllocLen              Integer32,
    tmnxIsisLSPBuff                  OCTET STRING,
    tmnxIsisLSPZeroRLT               TruthValue
}

tmnxIsisLSPId                    OBJECT-TYPE
    SYNTAX      OCTET STRING (SIZE (0..8))
    MAX-ACCESS  not-accessible
    STATUS      current
    DESCRIPTION
        "The value of the object tmnxIsisLSPId specifies the LSP Id and is
         given in the format as 6 octets of adjacency system-id followed by 1
         octet Lan-ID and 1 octet LSP Number."
    ::= { tmnxIsisLSPEntry 1 }

tmnxIsisLSPSeq                   OBJECT-TYPE
    SYNTAX      Counter32
    MAX-ACCESS  read-only
    STATUS      current
    DESCRIPTION
        "The value of the object tmnxIsisLSPSeq indicates the sequence number
         of an LSP and is a four byte quantity that represents the version of
         an LSP.

         The higher the sequence number, the more up to date the information.

         The sequence number is always incremented by the system that
         originated the LSP and ensures that there is only one version of that
         LSP in the entire network."
    ::= { tmnxIsisLSPEntry 2 }

tmnxIsisLSPChecksum              OBJECT-TYPE
    SYNTAX      Integer32 (0..65535)
    MAX-ACCESS  read-only
    STATUS      current
    DESCRIPTION
        "The value of the object tmnxIsisLSPChecksum indicates the checksum of
         contents of LSP from the SourceID field in the LSP till the end.

         The checksum is computed using the Fletcher checksum algorithm. "
    ::= { tmnxIsisLSPEntry 3 }

tmnxIsisLSPLifetimeRemain        OBJECT-TYPE
    SYNTAX      Integer32 (0..65535)
    UNITS       "seconds"
    MAX-ACCESS  read-only
    STATUS      current
    DESCRIPTION
        "The value of the object tmnxIsisLSPLifetimeRemain indicates the
         Remaining lifetime of this LSP and is a decrementing counter that
         decrements in seconds starting from the value as received in the LSP
         if not self-originated OR from tmnxIsisLspLifetime for self originated
         LSPs.

         When the remaining lifetime becomes zero, the contents of the LSP
         should not be considered for SPF calculation."
    ::= { tmnxIsisLSPEntry 4 }

tmnxIsisLSPVersion               OBJECT-TYPE
    SYNTAX      Integer32
    MAX-ACCESS  read-only
    STATUS      current
    DESCRIPTION
        "The value of the object tmnxIsisLSPVersion indicates the version of
         the ISIS protocol that has generated the LSP"
    ::= { tmnxIsisLSPEntry 5 }

tmnxIsisLSPPktType               OBJECT-TYPE
    SYNTAX      Integer32
    MAX-ACCESS  read-only
    STATUS      current
    DESCRIPTION
        "The value of the object tmnxIsisLSPPktType indicates the packet type
         for instance Hello PDUs, LSPs, CSNPs OR PSNPs at both IS-IS protocol
         levels i.e. L1 and L2 as maintained in tmnxIsisLSPPktType."
    ::= { tmnxIsisLSPEntry 6 }

tmnxIsisLSPPktVersion            OBJECT-TYPE
    SYNTAX      Integer32
    MAX-ACCESS  read-only
    STATUS      current
    DESCRIPTION
        "The value of the object tmnxIsisLSPPktVersion indicates the version of
         the ISIS protocol that has generated the Packet."
    ::= { tmnxIsisLSPEntry 7 }

tmnxIsisLSPMaxArea               OBJECT-TYPE
    SYNTAX      Integer32
    MAX-ACCESS  read-only
    STATUS      current
    DESCRIPTION
        "The value of the object tmnxIsisLSPMaxArea indicates the maximum
         number of areas supported by the originator of the LSP.

         A value of 0 for tmnxIsisLSPMaxArea indicates a default of 3 areas. "
    ::= { tmnxIsisLSPEntry 8 }

tmnxIsisLSPSysIdLen              OBJECT-TYPE
    SYNTAX      Integer32
    MAX-ACCESS  read-only
    STATUS      current
    DESCRIPTION
        "The value of the object tmnxIsisLSPSysIdLen indicates the length of
         the system-id as used by the originator."
    ::= { tmnxIsisLSPEntry 9 }

tmnxIsisLSPAttributes            OBJECT-TYPE
    SYNTAX      Integer32
    MAX-ACCESS  read-only
    STATUS      current
    DESCRIPTION
        "The value of the object tmnxIsisLSPAttributes indicates the attributes
         associated with the LSP and these include the attached bit, overload
         bit, IS type of the system originating the LSP and the partition
         repair capability.

         The attached bit and the overload bit are of significance only when
         present in the LSP numbered zero and should be ignored on receipt in
         any other LSP."
    ::= { tmnxIsisLSPEntry 10 }

tmnxIsisLSPUsedLen               OBJECT-TYPE
    SYNTAX      Integer32
    MAX-ACCESS  read-only
    STATUS      current
    DESCRIPTION
        "The value of the object tmnxIsisLSPUsedLen indicates the used length
         for the LSP.

         For an LSP that is not self originated, the used length is always
         equal to tmnxIsisLSPAllocLen; for self originated LSPs, the used
         length is less than or equal to tmnxIsisLSPAllocLen."
    ::= { tmnxIsisLSPEntry 11 }

tmnxIsisLSPAllocLen              OBJECT-TYPE
    SYNTAX      Integer32
    MAX-ACCESS  read-only
    STATUS      current
    DESCRIPTION
        "The value of the object tmnxIsisLSPAllocLen indicates the length
         allocated for the LSP to be stored."
    ::= { tmnxIsisLSPEntry 12 }

tmnxIsisLSPBuff                  OBJECT-TYPE
    SYNTAX      OCTET STRING (SIZE (27..9190))
    MAX-ACCESS  read-only
    STATUS      current
    DESCRIPTION
        "The value of the object tmnxIsisLSPBuff indicates the LSP as existing
         in the LSP database."
    ::= { tmnxIsisLSPEntry 13 }

tmnxIsisLSPZeroRLT               OBJECT-TYPE
    SYNTAX      TruthValue
    MAX-ACCESS  read-only
    STATUS      current
    DESCRIPTION
        "The value of the object tmnxIsisLSPZeroRLT indicates the LSP state if
         it has once reached zero remaining lifetime.

         If this object is 'true' then the object tmnxIsisLSPLifetimeRemain
         will maintain the time remaining after which this LSP will be
         discarded."
    ::= { tmnxIsisLSPEntry 14 }

tmnxIsisSpfLogTable              OBJECT-TYPE
    SYNTAX      SEQUENCE OF TmnxIsisSpfLogEntry
    MAX-ACCESS  not-accessible
    STATUS      current
    DESCRIPTION
        "The tmnxIsisSpfLogTable maintains information regarding SPF runs for
         each instance of IS-IS protocol.

         There is a maximum of 20 log entries stored per IS-IS protocol
         instance."
    ::= { tmnxIsisSystemObjs 8 }

tmnxIsisSpfLogEntry              OBJECT-TYPE
    SYNTAX      TmnxIsisSpfLogEntry
    MAX-ACCESS  not-accessible
    STATUS      current
    DESCRIPTION
        "Each entry maintains log information about a specific SPF run made on
         a particular IS-IS protocol instance."
    INDEX       {
        vRtrID,
        isisSysInstance,
        tmnxIsisSpfLogTimeStamp
    }
    ::= { tmnxIsisSpfLogTable 1 }

TmnxIsisSpfLogEntry              ::= SEQUENCE
{
    tmnxIsisSpfLogTimeStamp          TimeStamp,
    tmnxIsisSpfLogRunTime            TimeTicks,
    tmnxIsisSpfLogL1Nodes            Unsigned32,
    tmnxIsisSpfLogL2Nodes            Unsigned32,
    tmnxIsisSpfLogEventCount         Unsigned32,
    tmnxIsisSpfLogLastTriggerLSPId   OCTET STRING,
    tmnxIsisSpfLogTriggerReason      TmnxIsisSpfTriggerReason,
    tmnxIsisSpfLogType               INTEGER
}

tmnxIsisSpfLogTimeStamp          OBJECT-TYPE
    SYNTAX      TimeStamp
    MAX-ACCESS  not-accessible
    STATUS      current
    DESCRIPTION
        "The value of the object tmnxIsisSpfLogTimeStamp specifies the
         timestamp when the SPF run started on the system."
    ::= { tmnxIsisSpfLogEntry 1 }

tmnxIsisSpfLogRunTime            OBJECT-TYPE
    SYNTAX      TimeTicks
    MAX-ACCESS  read-only
    STATUS      current
    DESCRIPTION
        "The value of the object tmnxIsisSpfLogRunTime indicates the time (in
         centiseconds) required to complete the SPF run."
    ::= { tmnxIsisSpfLogEntry 2 }

tmnxIsisSpfLogL1Nodes            OBJECT-TYPE
    SYNTAX      Unsigned32
    MAX-ACCESS  read-only
    STATUS      current
    DESCRIPTION
        "The value of the object tmnxIsisSpfLogL1Nodes indicates the number of
         level 1 nodes involved in the SPF run."
    ::= { tmnxIsisSpfLogEntry 3 }

tmnxIsisSpfLogL2Nodes            OBJECT-TYPE
    SYNTAX      Unsigned32
    MAX-ACCESS  read-only
    STATUS      current
    DESCRIPTION
        "The value of the object tmnxIsisSpfLogL2Nodes indicates the number of
         level 2 nodes involved in the SPF run."
    ::= { tmnxIsisSpfLogEntry 4 }

tmnxIsisSpfLogEventCount         OBJECT-TYPE
    SYNTAX      Unsigned32
    MAX-ACCESS  read-only
    STATUS      current
    DESCRIPTION
        "The value of the object tmnxIsisSpfLogEventCount indicates the number
         of SPF events that triggered the SPF calculation."
    ::= { tmnxIsisSpfLogEntry 5 }

tmnxIsisSpfLogLastTriggerLSPId   OBJECT-TYPE
    SYNTAX      OCTET STRING (SIZE (0..8))
    MAX-ACCESS  read-only
    STATUS      current
    DESCRIPTION
        "The value of the object tmnxIsisSpfLogLastTriggerLSPId indicates the
         LSPId of the last LSP processed before the SPF run."
    ::= { tmnxIsisSpfLogEntry 6 }

tmnxIsisSpfLogTriggerReason      OBJECT-TYPE
    SYNTAX      TmnxIsisSpfTriggerReason
    MAX-ACCESS  read-only
    STATUS      current
    DESCRIPTION
        "The value of the object tmnxIsisSpfLogTriggerReason indicates the
         reasons that triggered this SPF run."
    ::= { tmnxIsisSpfLogEntry 7 }

tmnxIsisSpfLogType               OBJECT-TYPE
    SYNTAX      INTEGER {
        regular    (0),
        lfa        (1),
        partialSpf (2),
        partialLfa (3),
        remoteLfa  (4),
        tiLfa      (5)
    }
    MAX-ACCESS  read-only
    STATUS      current
    DESCRIPTION
        "The value of the object tmnxIsisSpfLogType indicates the type of SPF
         calculation."
    ::= { tmnxIsisSpfLogEntry 8 }

tmnxIsisSummaryTable             OBJECT-TYPE
    SYNTAX      SEQUENCE OF TmnxIsisSummaryEntry
    MAX-ACCESS  not-accessible
    STATUS      current
    DESCRIPTION
        "The tmnxIsisSummaryTable maintains the summary prefixes for a specific
         instance of the IS-IS protocol."
    ::= { tmnxIsisSystemObjs 9 }

tmnxIsisSummaryEntry             OBJECT-TYPE
    SYNTAX      TmnxIsisSummaryEntry
    MAX-ACCESS  not-accessible
    STATUS      current
    DESCRIPTION
        "Each row entry in the tmnxIsisSummaryTable stores a summary prefix for
         a specific instance of the IS-IS protocol."
    INDEX       {
        vRtrID,
        isisSysInstance,
        tmnxIsisSummPrefixType,
        tmnxIsisSummPrefix,
        tmnxIsisSummPrefixLength
    }
    ::= { tmnxIsisSummaryTable 1 }

TmnxIsisSummaryEntry             ::= SEQUENCE
{
    tmnxIsisSummPrefixType           InetAddressType,
    tmnxIsisSummPrefix               InetAddress,
    tmnxIsisSummPrefixLength         InetAddressPrefixLength,
    tmnxIsisSummRowStatus            RowStatus,
    tmnxIsisSummLevel                INTEGER,
    tmnxIsisSummRouteTag             Unsigned32,
    tmnxIsisSummAlgorithm            Integer32,
    tmnxIsisSummAdvertiseUnreachable TruthValue,
    tmnxIsisSummUpaMatchRouteTag     Unsigned32,
    tmnxIsisSummUpaAdvertiseRouteTag Unsigned32
}

tmnxIsisSummPrefixType           OBJECT-TYPE
    SYNTAX      InetAddressType
    MAX-ACCESS  not-accessible
    STATUS      current
    DESCRIPTION
        "The value of the object tmnxIsisSummPrefixType specifies the IP
         address type of tmnxIsisSummPrefix."
    ::= { tmnxIsisSummaryEntry 1 }

tmnxIsisSummPrefix               OBJECT-TYPE
    SYNTAX      InetAddress (SIZE (4|16|20))
    MAX-ACCESS  not-accessible
    STATUS      current
    DESCRIPTION
        "The value of the object tmnxIsisSummPrefix specifies the prefix for
         this summary address entry."
    ::= { tmnxIsisSummaryEntry 2 }

tmnxIsisSummPrefixLength         OBJECT-TYPE
    SYNTAX      InetAddressPrefixLength (0..128)
    MAX-ACCESS  not-accessible
    STATUS      current
    DESCRIPTION
        "The value of the object tmnxIsisSummPrefixLength specifies the prefix
         length to be used with tmnxIsisSummPrefix to get the network prefix."
    ::= { tmnxIsisSummaryEntry 3 }

tmnxIsisSummRowStatus            OBJECT-TYPE
    SYNTAX      RowStatus
    MAX-ACCESS  read-create
    STATUS      current
    DESCRIPTION
        "The value of the object tmnxIsisSummRowStatus specifies the row status
         used to create and delete entries in the tmnxIsisSummaryTable."
    ::= { tmnxIsisSummaryEntry 4 }

tmnxIsisSummLevel                OBJECT-TYPE
    SYNTAX      INTEGER {
        level1   (1),
        level2   (2),
        level1L2 (3)
    }
    MAX-ACCESS  read-create
    STATUS      current
    DESCRIPTION
        "The value of the object tmnxIsisSummLevel specifies the IS-IS Level
         from which the prefix should be summarized."
    DEFVAL      { level1L2 }
    ::= { tmnxIsisSummaryEntry 5 }

tmnxIsisSummRouteTag             OBJECT-TYPE
    SYNTAX      Unsigned32
    MAX-ACCESS  read-create
    STATUS      current
    DESCRIPTION
        "The value of the object tmnxIsisSummRouteTag specifies a 32-bit
         integer tag for the ISIS summary address and can be used to apply
         administrative policy.

         A value of 0 indicates that the tag has not been set."
    DEFVAL      { 0 }
    ::= { tmnxIsisSummaryEntry 6 }

tmnxIsisSummAlgorithm            OBJECT-TYPE
    SYNTAX      Integer32 (-1 | 0 | 128..255)
    MAX-ACCESS  read-create
    STATUS      current
    DESCRIPTION
        "The value of the object tmnxIsisSummAlgorithm specifies the algorithm
         for the summary address for a SRv6 locator TLV.

         If the algorithm is not explicit configured (value '-1'), the  summary
         address is only generated for algorithm 0 as IP reach TLV and
         suppresses all more specific prefixes.

         If the algorithm is configured (value [0, 128-255]), the  summary
         address is generated only for member prefixes belonging to the same
         algorithm. Only member prefixes within the configured algorithm are
         summarized, while member prefixes that belong to a  different
         algorithm will not be suppressed.

         If the algorithm '0' is configured the summary will be inserted in an
         IP reach TLV and SRv6 locator TLV.

         If a flexible algorithm [128-255] is configured the summary will be
         inserted in a SRv6 locator TLV."
    DEFVAL      { -1 }
    ::= { tmnxIsisSummaryEntry 7 }

tmnxIsisSummAdvertiseUnreachable OBJECT-TYPE
    SYNTAX      TruthValue
    MAX-ACCESS  read-create
    STATUS      current
    DESCRIPTION
        "The value of the object tmnxIsisSummAdvertiseUnreachable specifies
         whether Unreachable Prefix Announcement (UPA) is enabled or not for
         summary member routes.

         If the value is 'true', an UPA will be advertised for the summary
         member prefixes when it becomes unreachable."
    DEFVAL      { false }
    ::= { tmnxIsisSummaryEntry 8 }

tmnxIsisSummUpaMatchRouteTag     OBJECT-TYPE
    SYNTAX      Unsigned32
    MAX-ACCESS  read-create
    STATUS      current
    DESCRIPTION
        "The value of the object tmnxIsisSummUpaMatchRouteTag specifies a
         32-bit integer tag to limit the UPAs to the subset of summary member
         prefixes that are advertised with the tag.

         A value of 0 indicates that the tag has not been set.

         The value of tmnxIsisSummUpaMatchRouteTag is only valid when
         tmnxIsisSummAdvertiseUnreachable has the value 'true'."
    DEFVAL      { 0 }
    ::= { tmnxIsisSummaryEntry 9 }

tmnxIsisSummUpaAdvertiseRouteTag OBJECT-TYPE
    SYNTAX      Unsigned32
    MAX-ACCESS  read-create
    STATUS      current
    DESCRIPTION
        "The value of the object tmnxIsisSummUpaAdvertiseRouteTag specifies a
         32-bit integer tag to add to the advertised UPA.

         A value of 0 indicates that the tag has not been set.

         The value of tmnxIsisSummUpaAdvertiseRouteTag is only valid when
         tmnxIsisSummAdvertiseUnreachable has the value 'true'."
    DEFVAL      { 0 }
    ::= { tmnxIsisSummaryEntry 10 }

tmnxIsisLfaTable                 OBJECT-TYPE
    SYNTAX      SEQUENCE OF TmnxIsisLfaEntry
    MAX-ACCESS  not-accessible
    STATUS      current
    DESCRIPTION
        "The tmnxIsisLfaTable maintains information on loopfree-alternate (LFA)
         coverage for each instance of IS-IS protocol."
    ::= { tmnxIsisSystemObjs 10 }

tmnxIsisLfaEntry                 OBJECT-TYPE
    SYNTAX      TmnxIsisLfaEntry
    MAX-ACCESS  not-accessible
    STATUS      current
    DESCRIPTION
        "Each row entry in the tmnxIsisLfaTable represents information on LFA
         coverage for various topologies of the system."
    INDEX       {
        vRtrID,
        isisSysInstance,
        tmnxIsisLevel,
        tmnxIsisLfaFamilyCoverage
    }
    ::= { tmnxIsisLfaTable 1 }

TmnxIsisLfaEntry                 ::= SEQUENCE
{
    tmnxIsisLfaFamilyCoverage        INTEGER,
    tmnxIsisLfaNodesCovered          Unsigned32,
    tmnxIsisLfaTotalNodes            Unsigned32,
    tmnxIsisLfaNodeCoverage          Unsigned32,
    tmnxIsisLfaIPv4NodesCovered      Unsigned32,
    tmnxIsisLfaIPv4TotalNodes        Unsigned32,
    tmnxIsisLfaIPv4Coverage          Unsigned32,
    tmnxIsisLfaIPv6NodesCovered      Unsigned32,
    tmnxIsisLfaIPv6TotalNodes        Unsigned32,
    tmnxIsisLfaIPv6Coverage          Unsigned32
}

tmnxIsisLfaFamilyCoverage        OBJECT-TYPE
    SYNTAX      INTEGER {
        ipv4      (0),
        ipv6      (1),
        ipv4Mcast (2),
        ipv6Mcast (3)
    }
    MAX-ACCESS  not-accessible
    STATUS      current
    DESCRIPTION
        "The value of the object tmnxIsisLfaFamilyCoverage specifies the multi
         topology (MTs) for which LFA coverage has been computed.

         Possible values are:

         ipv4(0)      - indicates MT0 or standard topology
         ipv6(1)      - indicates MT2 or IPv6 routing topology
         ipv4Mcast(2) - indicates MT3 or IPv4 multicast routing topology
         ipv6Mcast(3) - indicates MT4 or IPv6 multicast routing topology."
    ::= { tmnxIsisLfaEntry 1 }

tmnxIsisLfaNodesCovered          OBJECT-TYPE
    SYNTAX      Unsigned32
    MAX-ACCESS  read-only
    STATUS      current
    DESCRIPTION
        "The value of the object tmnxIsisLfaNodesCovered indicates in absolute
         numbers how much LFA coverage is being obtained for the available
         routes."
    ::= { tmnxIsisLfaEntry 2 }

tmnxIsisLfaTotalNodes            OBJECT-TYPE
    SYNTAX      Unsigned32
    MAX-ACCESS  read-only
    STATUS      current
    DESCRIPTION
        "The value of the object tmnxIsisLfaTotalNodes indicates in absolute
         numbers how much LFA coverage can be obtained for the available
         routes."
    ::= { tmnxIsisLfaEntry 3 }

tmnxIsisLfaNodeCoverage          OBJECT-TYPE
    SYNTAX      Unsigned32 (0..100)
    UNITS       "percent"
    MAX-ACCESS  read-only
    STATUS      current
    DESCRIPTION
        "The value of the object tmnxIsisLfaNodeCoverage indicates how much LFA
         coverage is being obtained for the set of available nodes."
    ::= { tmnxIsisLfaEntry 4 }

tmnxIsisLfaIPv4NodesCovered      OBJECT-TYPE
    SYNTAX      Unsigned32
    MAX-ACCESS  read-only
    STATUS      current
    DESCRIPTION
        "The value of the object tmnxIsisLfaIPv4NodesCovered indicates in
         absolute numbers how much LFA coverage is being obtained for the
         available IPv4 routes."
    ::= { tmnxIsisLfaEntry 5 }

tmnxIsisLfaIPv4TotalNodes        OBJECT-TYPE
    SYNTAX      Unsigned32
    MAX-ACCESS  read-only
    STATUS      current
    DESCRIPTION
        "The value of the object tmnxIsisLfaIPv4TotalNodes indicates in
         absolute numbers how much LFA coverage can be obtained for the
         available IPv4 routes."
    ::= { tmnxIsisLfaEntry 6 }

tmnxIsisLfaIPv4Coverage          OBJECT-TYPE
    SYNTAX      Unsigned32 (0..100)
    UNITS       "percent"
    MAX-ACCESS  read-only
    STATUS      current
    DESCRIPTION
        "The value of the object tmnxIsisLfaIPv4Coverage indicates how much LFA
         coverage is being obtained for the available IPv4 routes."
    ::= { tmnxIsisLfaEntry 7 }

tmnxIsisLfaIPv6NodesCovered      OBJECT-TYPE
    SYNTAX      Unsigned32
    MAX-ACCESS  read-only
    STATUS      current
    DESCRIPTION
        "The value of the object tmnxIsisLfaIPv6NodesCovered indicates in
         absolute numbers how much LFA coverage is being obtained for available
         IPv6 routes."
    ::= { tmnxIsisLfaEntry 8 }

tmnxIsisLfaIPv6TotalNodes        OBJECT-TYPE
    SYNTAX      Unsigned32
    MAX-ACCESS  read-only
    STATUS      current
    DESCRIPTION
        "The value of the object tmnxIsisLfaIPv6TotalNodes indicates in
         absolute numbers how much LFA coverage can be obtained for the
         available IPv6 routes."
    ::= { tmnxIsisLfaEntry 9 }

tmnxIsisLfaIPv6Coverage          OBJECT-TYPE
    SYNTAX      Unsigned32 (0..100)
    UNITS       "percent"
    MAX-ACCESS  read-only
    STATUS      current
    DESCRIPTION
        "The value of the object tmnxIsisLfaIPv6Coverage indicates how much LFA
         coverage is being obtained for the available IPv6 routes."
    ::= { tmnxIsisLfaEntry 10 }

tmnxIsisExtTable                 OBJECT-TYPE
    SYNTAX      SEQUENCE OF TmnxIsisExtEntry
    MAX-ACCESS  not-accessible
    STATUS      current
    DESCRIPTION
        "The tmnxIsisExtTable provides an extension of the tmnxIsisTable."
    ::= { tmnxIsisSystemObjs 11 }

tmnxIsisExtEntry                 OBJECT-TYPE
    SYNTAX      TmnxIsisExtEntry
    MAX-ACCESS  not-accessible
    STATUS      current
    DESCRIPTION
        "Each row entry in tmnxIsisExtTable represents additional columns for
         attributes specific to the Nokia SROS series implementation for the
         ISIS configuration table."
    AUGMENTS    { tmnxIsisEntry }
    ::= { tmnxIsisExtTable 1 }

TmnxIsisExtEntry                 ::= SEQUENCE
{
    tmnxIsisExLastChanged            TimeStamp,
    tmnxIsisLFAExcludePolicy1        TNamedItemOrEmpty,
    tmnxIsisLFAExcludePolicy2        TNamedItemOrEmpty,
    tmnxIsisLFAExcludePolicy3        TNamedItemOrEmpty,
    tmnxIsisLFAExcludePolicy4        TNamedItemOrEmpty,
    tmnxIsisLFAExcludePolicy5        TNamedItemOrEmpty,
    tmnxIsisPrefixSidRangeType       INTEGER,
    tmnxIsisPrefixSidRangeStartLabel TmnxPrefixSidFullRange,
    tmnxIsisPrefixSidRangeMaxIdx     TmnxPrefixSidFullRange,
    tmnxIsisSrAdminState             TmnxAdminState,
    tmnxIsisTunnelTablePreference    Unsigned32,
    tmnxIsisRibPriorityListHigh      TNamedItemOrEmpty,
    tmnxIsisRibPriorityListHighTag   Unsigned32,
    tmnxIsisTunnelMtu                Unsigned32,
    tmnxIsisMaxPqCost                Unsigned32,
    tmnxIsisIgnoreNarrowMetric       TruthValue,
    tmnxIsisPoiTlv                   TmnxEnabledDisabled,
    tmnxIsisSystemId                 SystemID,
    tmnxIsisPrefixLimit              Unsigned32,
    tmnxIsisPfxLimitOverloadTimeout  Unsigned32,
    tmnxIsisPrefixLimitThreshold     Unsigned32,
    tmnxIsisPrefixLimitLogOnly       TruthValue,
    tmnxIsisPfxLimitOverloadTimeLeft Unsigned32,
    tmnxIsisImportPolicy1            TNamedItemOrEmpty,
    tmnxIsisImportPolicy2            TNamedItemOrEmpty,
    tmnxIsisImportPolicy3            TNamedItemOrEmpty,
    tmnxIsisImportPolicy4            TNamedItemOrEmpty,
    tmnxIsisImportPolicy5            TNamedItemOrEmpty,
    tmnxIsisSrAdjSidHold             Unsigned32,
    tmnxIsisSrExportTunnelTableProt  INTEGER,
    tmnxIsisDatabaseExport           TmnxEnabledDisabled,
    tmnxIsisDbExportIdentifierSet    TruthValue,
    tmnxIsisDbExportIdentifierLow    Unsigned32,
    tmnxIsisDbExportIdentifierHigh   Unsigned32,
    tmnxIsisBgpLsIdentifierSet       TruthValue,
    tmnxIsisBgpLsIdentifier          Unsigned32,
    tmnxIsisOverloadExportInterlevel TruthValue,
    tmnxIsisOverloadExportExternal   TruthValue,
    tmnxIsisStandardMultiInstance    TruthValue,
    tmnxIsisDbAsn                    InetAutonomousSystemNumber,
    tmnxIsisSrEntropyLabel           INTEGER,
    tmnxIsisTiLfa                    TruthValue,
    tmnxIsisMaxSrFrrLabels           Unsigned32,
    tmnxIsisPrefixAttributesTlv      TmnxEnabledDisabled,
    tmnxIsisLspRefreshHalfLifetime   TruthValue,
    tmnxIsisOverrideTunnelElc        INTEGER,
    tmnxIsisSrlbReservedLblBlockName TLNamedItemOrEmpty,
    tmnxIsisRemoteLfaNodeProtect     TruthValue,
    tmnxIsisRemoteLfaMaxPqNodes      Unsigned32,
    tmnxIsisTiLfaNodeProtect         TruthValue,
    tmnxIsisLspMinRemainingLifetime  Unsigned32,
    tmnxIsisReferenceBwU64High       TmnxHigh32,
    tmnxIsisReferenceBwU64Low        TmnxLow32,
    tmnxIsisEgressStatsNodeSid       TruthValue,
    tmnxIsisEgressStatsAdjSid        TruthValue,
    tmnxIsisEgressStatsAdjSet        TruthValue,
    tmnxIsisIngressStatsNodeSid      TruthValue,
    tmnxIsisIngressStatsAdjSid       TruthValue,
    tmnxIsisIngressStatsAdjSet       TruthValue,
    tmnxIsisTEIpv6                   TruthValue,
    tmnxIsisTEApplicationLinkAttr    TruthValue,
    tmnxIsisTEApplLegacy             TruthValue,
    tmnxIsisOperIpv6TERouterIdType   InetAddressType,
    tmnxIsisOperIpv6TERouterId       InetAddress,
    tmnxIsisSrMicroLoopAvoidance     TruthValue,
    tmnxIsisSrMicroLoopAvdFibDelay   Unsigned32,
    tmnxIsisSrClassForwarding        TruthValue,
    tmnxIsisLoopfreeAltAugmRteTable  TruthValue,
    tmnxIsisMaxSrv6FrrSids           Unsigned32
}

tmnxIsisExLastChanged            OBJECT-TYPE
    SYNTAX      TimeStamp
    MAX-ACCESS  read-only
    STATUS      current
    DESCRIPTION
        "The value of tmnxIsisExLastChanged indicates the sysUpTime when a
         configurable object in this row was last modified."
    ::= { tmnxIsisExtEntry 1 }

tmnxIsisLFAExcludePolicy1        OBJECT-TYPE
    SYNTAX      TNamedItemOrEmpty
    MAX-ACCESS  read-write
    STATUS      current
    DESCRIPTION
        "The value of tmnxIsisLFAExcludePolicy1 is the name of the first policy
         from which prefixes are excluded which match on the ISIS tag. Prefixes
         excluded from LFA (Loopfree Alternative) this way will not be used in
         the LFA calculation, regardless of its priority."
    DEFVAL      { ''H }
    ::= { tmnxIsisExtEntry 2 }

tmnxIsisLFAExcludePolicy2        OBJECT-TYPE
    SYNTAX      TNamedItemOrEmpty
    MAX-ACCESS  read-write
    STATUS      current
    DESCRIPTION
        "The value of tmnxIsisLFAExcludePolicy2 is the name of the second
         policy from which prefixes are excluded which match on the ISIS tag.
         Prefixes excluded from LFA (Loopfree Alternative) this way will not be
         used in the LFA calculation, regardless of its priority."
    DEFVAL      { ''H }
    ::= { tmnxIsisExtEntry 3 }

tmnxIsisLFAExcludePolicy3        OBJECT-TYPE
    SYNTAX      TNamedItemOrEmpty
    MAX-ACCESS  read-write
    STATUS      current
    DESCRIPTION
        "The value of tmnxIsisLFAExcludePolicy3 is the name of the third policy
         from which prefixes are excluded which match on the ISIS tag. Prefixes
         excluded from LFA (Loopfree Alternative) this way will not be used in
         the LFA calculation, regardless of its priority."
    DEFVAL      { ''H }
    ::= { tmnxIsisExtEntry 4 }

tmnxIsisLFAExcludePolicy4        OBJECT-TYPE
    SYNTAX      TNamedItemOrEmpty
    MAX-ACCESS  read-write
    STATUS      current
    DESCRIPTION
        "The value of tmnxIsisLFAExcludePolicy4 is the name of the fourth
         policy from which prefixes are excluded which match on the ISIS tag.
         Prefixes excluded from LFA (Loopfree Alternative) this way will not be
         used in the LFA calculation, regardless of its priority."
    DEFVAL      { ''H }
    ::= { tmnxIsisExtEntry 5 }

tmnxIsisLFAExcludePolicy5        OBJECT-TYPE
    SYNTAX      TNamedItemOrEmpty
    MAX-ACCESS  read-write
    STATUS      current
    DESCRIPTION
        "The value of tmnxIsisLFAExcludePolicy5 is the name of the fifth policy
         from which prefixes are excluded which match on the ISIS tag. Prefixes
         excluded from LFA (Loopfree Alternative) this way will not be used in
         the LFA calculation, regardless of its priority."
    DEFVAL      { ''H }
    ::= { tmnxIsisExtEntry 6 }

tmnxIsisPrefixSidRangeType       OBJECT-TYPE
    SYNTAX      INTEGER {
        none   (0),
        global (1),
        local  (2)
    }
    MAX-ACCESS  read-write
    STATUS      current
    DESCRIPTION
        "The value of tmnxIsisPrefixSidRangeType specifies whether global or
         local operation mode is selected."
    DEFVAL      { none }
    ::= { tmnxIsisExtEntry 7 }

tmnxIsisPrefixSidRangeStartLabel OBJECT-TYPE
    SYNTAX      TmnxPrefixSidFullRange
    MAX-ACCESS  read-write
    STATUS      current
    DESCRIPTION
        "The value of tmnxIsisPrefixSidRangeStartLabel specifies the local
         label starting offset value."
    DEFVAL      { 0 }
    ::= { tmnxIsisExtEntry 8 }

tmnxIsisPrefixSidRangeMaxIdx     OBJECT-TYPE
    SYNTAX      TmnxPrefixSidFullRange
    MAX-ACCESS  read-write
    STATUS      current
    DESCRIPTION
        "The value of tmnxIsisPrefixSidRangeMaxIdx specifies the maximum local
         SID index that can be used."
    DEFVAL      { 1 }
    ::= { tmnxIsisExtEntry 9 }

tmnxIsisSrAdminState             OBJECT-TYPE
    SYNTAX      TmnxAdminState
    MAX-ACCESS  read-write
    STATUS      current
    DESCRIPTION
        "The value of the object tmnxIsisSrAdminState specifies the desired
         administrative state of Segment Routing for this IS-IS instance."
    DEFVAL      { outOfService }
    ::= { tmnxIsisExtEntry 10 }

tmnxIsisTunnelTablePreference    OBJECT-TYPE
    SYNTAX      Unsigned32 (1..255)
    MAX-ACCESS  read-write
    STATUS      current
    DESCRIPTION
        "The value of tmnxIsisTunnelTablePreference specifies the preference
         value for TTM tunnels in this IS-IS instance."
    DEFVAL      { 11 }
    ::= { tmnxIsisExtEntry 11 }

tmnxIsisRibPriorityListHigh      OBJECT-TYPE
    SYNTAX      TNamedItemOrEmpty
    MAX-ACCESS  read-write
    STATUS      current
    DESCRIPTION
        "The value of tmnxIsisRibPriorityListHigh specifies the name of the
         prefix list from which prefixes are prioritised for rib update."
    DEFVAL      { ''H }
    ::= { tmnxIsisExtEntry 12 }

tmnxIsisRibPriorityListHighTag   OBJECT-TYPE
    SYNTAX      Unsigned32
    MAX-ACCESS  read-write
    STATUS      current
    DESCRIPTION
        "The value of tmnxIsisRibPriorityListHighTag specifies a 32-bit integer
         tag for rib update.

         A value of 0 indicates that the tag has not been set."
    DEFVAL      { 0 }
    ::= { tmnxIsisExtEntry 13 }

tmnxIsisTunnelMtu                OBJECT-TYPE
    SYNTAX      Unsigned32 (0 | 512..9786)
    MAX-ACCESS  read-write
    STATUS      current
    DESCRIPTION
        "The value of tmnxIsisTunnelMtu specifies the tunnel MTU size used for
         segment routing.

         A value of 0 results in using the MTU of the nexthop, a value in the
         range of 512..9198 will override this."
    DEFVAL      { 0 }
    ::= { tmnxIsisExtEntry 14 }

tmnxIsisMaxPqCost                OBJECT-TYPE
    SYNTAX      Unsigned32
    MAX-ACCESS  read-write
    STATUS      current
    DESCRIPTION
        "The value of tmnxIsisMaxPqCost specifies the maximum cost of a
         destination node during reverse SPF calculation.

         The value of tmnxIsisMaxPqCost is only valid when the objects
         tmnxIsisLoopfreeAlternate and tmnxIsisRemoteLoopfreeAlternate both
         have the value 'true'."
    DEFVAL      { 4261412864 }
    ::= { tmnxIsisExtEntry 15 }

tmnxIsisIgnoreNarrowMetric       OBJECT-TYPE
    SYNTAX      TruthValue
    MAX-ACCESS  read-write
    STATUS      current
    DESCRIPTION
        "The value of the object tmnxIsisIgnoreNarrowMetric specifies whether
         links with narrow metrics are ignored or not in its SPF calculations
         when wide-metrics is enabled.

         If the value of tmnxIsisIgnoreNarrowMetric is set to 'true' IS-IS is
         forced to ignore links with narrow metrics when wide-metrics support
         has been enabled."
    DEFVAL      { false }
    ::= { tmnxIsisExtEntry 16 }

tmnxIsisPoiTlv                   OBJECT-TYPE
    SYNTAX      TmnxEnabledDisabled
    MAX-ACCESS  read-write
    STATUS      current
    DESCRIPTION
        "The value of the object tmnxIsisPoiTlv specifies whether Purge
         Originator Identification (POI) TLV has been enabled or disabled for
         this ISIS instance.

         When the value of tmnxIsisPoiTlv is 'enabled', each ISIS instance that
         generate a purge should include the POI TLV in the purge with its own
         system ID.

         When the value of tmnxIsisPoiTlv is 'enabled' and the ISIS instance
         receives a purge that doesn't include the POI TLV, then it should add
         the POI TLV with both its own system ID and the system ID of the ISIS
         instance from which it received the purge."
    DEFVAL      { disabled }
    ::= { tmnxIsisExtEntry 17 }

tmnxIsisSystemId                 OBJECT-TYPE
    SYNTAX      SystemID
    MAX-ACCESS  read-write
    STATUS      current
    DESCRIPTION
        "The value of the object tmnxIsisSystemId specifies the ID for this
         instance of the Integrated IS-IS protocol. This value is appended to
         each of the instance's area addresses to form the Network Entity
         Titles valid for this instance. The derivation of a value for this
         object is implementation-specific. Some implementations may assign
         values and not permit write, others may require the value to be set
         manually on Nokia 7xxx series systems 14.0 release."
    ::= { tmnxIsisExtEntry 18 }

tmnxIsisPrefixLimit              OBJECT-TYPE
    SYNTAX      Unsigned32
    MAX-ACCESS  read-write
    STATUS      current
    DESCRIPTION
        "The value of the object tmnxIsisPrefixLimit specifies the maximum
         number of prefixes for this IS-IS instance.

         If the number of prefixes exceeds this limit, IS-IS goes into
         overload.

         A value of 0 indicates no limit."
    DEFVAL      { 0 }
    ::= { tmnxIsisExtEntry 19 }

tmnxIsisPfxLimitOverloadTimeout  OBJECT-TYPE
    SYNTAX      Unsigned32 (0 | 1..1800)
    UNITS       "seconds"
    MAX-ACCESS  read-write
    STATUS      current
    DESCRIPTION
        "The value of the object tmnxIsisPfxLimitOverloadTimeout specifies the
         maximum timeout in seconds we go into overload when
         tmnxIsisPrefixLimit is reached.

         A value of 0 indicates indefinite."
    DEFVAL      { 0 }
    ::= { tmnxIsisExtEntry 20 }

tmnxIsisPrefixLimitThreshold     OBJECT-TYPE
    SYNTAX      Unsigned32 (0..100)
    UNITS       "percent"
    MAX-ACCESS  read-write
    STATUS      current
    DESCRIPTION
        "The value of the object tmnxIsisPrefixLimitThreshold specifies the
         percentage of the tmnxIsisPrefixLimit, at which a warning log message
         and SNMP notification would be sent.

         This would only be a warning and additional prefixes will be learned
         up to 100% of tmnxIsisPrefixLimit.

         A value of 0 indicates that tmnxIsisPrefixLimitThreshold is disabled
         and no log message or SNMP notification will be sent."
    DEFVAL      { 0 }
    ::= { tmnxIsisExtEntry 21 }

tmnxIsisPrefixLimitLogOnly       OBJECT-TYPE
    SYNTAX      TruthValue
    MAX-ACCESS  read-write
    STATUS      current
    DESCRIPTION
        "The value of the object tmnxIsisPrefixLimitLogOnly specifies whether
         IS-IS should go into overload when tmnxIsisPrefixLimit is reached.

         If the value of tmnxIsisPrefixLimitLogOnly is set to 'true', IS-IS
         will only sent a trap and will not go in overload when
         tmnxIsisPrefixLimit is reached; if the value of
         tmnxIsisPrefixLimitLogOnly is set to 'false' IS-IS will go in overload
         when tmnxIsisPrefixLimit is reached."
    DEFVAL      { false }
    ::= { tmnxIsisExtEntry 22 }

tmnxIsisPfxLimitOverloadTimeLeft OBJECT-TYPE
    SYNTAX      Unsigned32 (0 | 1..1800)
    UNITS       "seconds"
    MAX-ACCESS  read-only
    STATUS      current
    DESCRIPTION
        "The value of the object tmnxIsisPfxLimitOverloadTimeLeft indicates the
         remaining time in seconds before IS-IS will attempt to enter its
         normal state to recover from the overload state due to prefix limit
         exceeded.

         The value of 0 implies that the system is either not in overload or
         indefinitely in overload state."
    ::= { tmnxIsisExtEntry 23 }

tmnxIsisImportPolicy1            OBJECT-TYPE
    SYNTAX      TNamedItemOrEmpty
    MAX-ACCESS  read-write
    STATUS      current
    DESCRIPTION
        "The value of the object tmnxIsisImportPolicy1 specifies the name of
         the first policy to be used for determining which routes are imported
         from IS-IS into the routing table .

         If no import policy is defined, all IS-IS routes will be imported into
         the routing table.

         If multiple policy names are specified, the policies are evaluated in
         the order they are specified and the first policy that matches will be
         applied.

         The import policy name list, tmnxIsisImportPolicy1 through
         tmnxIsisImportPolicy5, is handled by the SNMP agent as a single
         entity.  When an SNMP SET request is received to modify one or
         more of the policy names, all the policy variables are first
         set to the empty string, ''H, and then the new names are set
         into the specified policy variables within a single SNMP SET PDU."
    DEFVAL      { ''H }
    ::= { tmnxIsisExtEntry 24 }

tmnxIsisImportPolicy2            OBJECT-TYPE
    SYNTAX      TNamedItemOrEmpty
    MAX-ACCESS  read-write
    STATUS      current
    DESCRIPTION
        "The value of the object tmnxIsisImportPolicy2 specifies the name of
         the second policy to be used for determining which routes are imported
         from IS-IS into the routing table .

         If no import policy is defined, all IS-IS routes will be imported into
         the routing table.

         If multiple policy names are specified, the policies are evaluated in
         the order they are specified and the first policy that matches will be
         applied.

         The import policy name list, tmnxIsisImportPolicy1 through
         tmnxIsisImportPolicy5, is handled by the SNMP agent as a single
         entity.  When an SNMP SET request is received to modify one or
         more of the policy names, all the policy variables are first
         set to the empty string, ''H, and then the new names are set
         into the specified policy variables within a single SNMP SET PDU."
    DEFVAL      { ''H }
    ::= { tmnxIsisExtEntry 25 }

tmnxIsisImportPolicy3            OBJECT-TYPE
    SYNTAX      TNamedItemOrEmpty
    MAX-ACCESS  read-write
    STATUS      current
    DESCRIPTION
        "The value of the object tmnxIsisImportPolicy3 specifies the name of
         the third policy to be used for determining which routes are imported
         from IS-IS into the routing table .

         If no import policy is defined, all IS-IS routes will be imported into
         the routing table.

         If multiple policy names are specified, the policies are evaluated in
         the order they are specified and the first policy that matches will be
         applied.

         The import policy name list, tmnxIsisImportPolicy1 through
         tmnxIsisImportPolicy5, is handled by the SNMP agent as a single
         entity.  When an SNMP SET request is received to modify one or
         more of the policy names, all the policy variables are first
         set to the empty string, ''H, and then the new names are set
         into the specified policy variables within a single SNMP SET PDU."
    DEFVAL      { ''H }
    ::= { tmnxIsisExtEntry 26 }

tmnxIsisImportPolicy4            OBJECT-TYPE
    SYNTAX      TNamedItemOrEmpty
    MAX-ACCESS  read-write
    STATUS      current
    DESCRIPTION
        "The value of the object tmnxIsisImportPolicy4 specifies the name of
         the fourth policy to be used for determining which routes are imported
         from IS-IS into the routing table .

         If no import policy is defined, all IS-IS routes will be imported into
         the routing table.

         If multiple policy names are specified, the policies are evaluated in
         the order they are specified and the first policy that matches will be
         applied.

         The import policy name list, tmnxIsisImportPolicy1 through
         tmnxIsisImportPolicy5, is handled by the SNMP agent as a single
         entity.  When an SNMP SET request is received to modify one or
         more of the policy names, all the policy variables are first
         set to the empty string, ''H, and then the new names are set
         into the specified policy variables within a single SNMP SET PDU."
    DEFVAL      { ''H }
    ::= { tmnxIsisExtEntry 27 }

tmnxIsisImportPolicy5            OBJECT-TYPE
    SYNTAX      TNamedItemOrEmpty
    MAX-ACCESS  read-write
    STATUS      current
    DESCRIPTION
        "The value of the object tmnxIsisImportPolicy5 specifies the name of
         the fifth policy to be used for determining which routes are imported
         from IS-IS into the routing table .

         If no import policy is defined, all IS-IS routes will be imported into
         the routing table.

         If multiple policy names are specified, the policies are evaluated in
         the order they are specified and the first policy that matches will be
         applied.

         The import policy name list, tmnxIsisImportPolicy1 through
         tmnxIsisImportPolicy5, is handled by the SNMP agent as a single
         entity.  When an SNMP SET request is received to modify one or
         more of the policy names, all the policy variables are first
         set to the empty string, ''H, and then the new names are set
         into the specified policy variables within a single SNMP SET PDU."
    DEFVAL      { ''H }
    ::= { tmnxIsisExtEntry 28 }

tmnxIsisSrAdjSidHold             OBJECT-TYPE
    SYNTAX      Unsigned32 (0..1800)
    UNITS       "seconds"
    MAX-ACCESS  read-write
    STATUS      current
    DESCRIPTION
        "The value of the object tmnxIsisSrAdjSidHold specifies the adjacency
         SID hold time in seconds.

         When both tmnxIsisSrAdminState and tmnxIsisSrv6AdminState are enabled,
         the higher of the two timer values (tmnxIsisSrAdjSidHold and
         tmnxIsisSrv6AdjSidHold) is programmed for all SIDs on the adjacency."
    DEFVAL      { 15 }
    ::= { tmnxIsisExtEntry 29 }

tmnxIsisSrExportTunnelTableProt  OBJECT-TYPE
    SYNTAX      INTEGER {
        none (0),
        ldp  (1)
    }
    MAX-ACCESS  read-write
    STATUS      current
    DESCRIPTION
        "The value of the object tmnxIsisSrExportTunnelTableProt specifies the
         protocol Segment Routing is stitched to.

         If the value of tmnxIsisSrExportTunnelTableProt is none (0), ISIS will
         not export tunnels from the Tunnel Table Manager (TTM).

         If the value of tmnxIsisSrExportTunnelTableProt is ldp (1), ISIS will
         export LDP tunnels from TTM to the Segment Routing (SR)."
    DEFVAL      { none }
    ::= { tmnxIsisExtEntry 30 }

tmnxIsisDatabaseExport           OBJECT-TYPE
    SYNTAX      TmnxEnabledDisabled
    MAX-ACCESS  read-write
    STATUS      current
    DESCRIPTION
        "The value of the object tmnxIsisDatabaseExport specifies whether
         database export has been enabled or disabled for this ISIS instance.

         When the value of tmnxIsisDatabaseExport is 'enabled', ISIS will
         redistribute LSDB via segment routing TE-DB into NLRI format."
    DEFVAL      { disabled }
    ::= { tmnxIsisExtEntry 31 }

tmnxIsisDbExportIdentifierSet    OBJECT-TYPE
    SYNTAX      TruthValue
    MAX-ACCESS  read-write
    STATUS      current
    DESCRIPTION
        "The value of the object tmnxIsisDbExportIdentifierSet specifies
         whether to use the values of tmnxIsisDbExportIdentifierLow and
         tmnxIsisDbExportIdentifierHigh or not.

         When set to true(1), the values of tmnxIsisDbExportIdentifierLow and
         tmnxIsisDbExportIdentifierHigh are used to uniquely identify the IGP
         instance in the BGP-LS NLRI.

         When set to false, the identifier in the BGP-LS NLRI defaults to the
         IGP instance number assigned by SROS."
    DEFVAL      { false }
    ::= { tmnxIsisExtEntry 32 }

tmnxIsisDbExportIdentifierLow    OBJECT-TYPE
    SYNTAX      Unsigned32
    MAX-ACCESS  read-write
    STATUS      current
    DESCRIPTION
        "The value of the object tmnxIsisDbExportIdentifierLow specifies the
         lower 32 bits of the unique identifier of the IGP instance in the
         BGP-LS NLRI.

         The value of this object is ignored when the object
         tmnxIsisDbExportIdentifierSet is false."
    DEFVAL      { 0 }
    ::= { tmnxIsisExtEntry 33 }

tmnxIsisDbExportIdentifierHigh   OBJECT-TYPE
    SYNTAX      Unsigned32
    MAX-ACCESS  read-write
    STATUS      current
    DESCRIPTION
        "The value of the object tmnxIsisDbExportIdentifierHigh specifies the
         upper 32 bits of the unique identifier of the IGP instance in the
         BGP-LS NLRI.

         The value of this object is ignored when the object
         tmnxIsisDbExportIdentifierSet is false."
    DEFVAL      { 0 }
    ::= { tmnxIsisExtEntry 34 }

tmnxIsisBgpLsIdentifierSet       OBJECT-TYPE
    SYNTAX      TruthValue
    MAX-ACCESS  read-write
    STATUS      current
    DESCRIPTION
        "The value of the object tmnxIsisBgpLsIdentifierSet specifies whether
         to use the value of tmnxIsisBgpLsIdentifier or not.

         When set to true(1), the value of tmnxIsisBgpLsIdentifier is used to
         identify the BGP-LS in the BGP-LS NLRI.

         When set to false, no BGP-LS identifier is sent in the BGP-LS NLRI."
    DEFVAL      { false }
    ::= { tmnxIsisExtEntry 35 }

tmnxIsisBgpLsIdentifier          OBJECT-TYPE
    SYNTAX      Unsigned32 (0..4294967295)
    MAX-ACCESS  read-write
    STATUS      current
    DESCRIPTION
        "The value of the object tmnxIsisBgpLsIdentifier specifies the BGP-LS
         identifier that is sent in the BGP-LS NLRI.

         The BGP-LS identifier is used along with the ASN to correlate the
         BGP-LS NLRI advertisements of multiple BGP-LS speakers of the same IGP
         domain.

         The value of this object is ignored when the object
         tmnxIsisBgpLsIdentifierSet is false."
    DEFVAL      { 0 }
    ::= { tmnxIsisExtEntry 36 }

tmnxIsisOverloadExportInterlevel OBJECT-TYPE
    SYNTAX      TruthValue
    MAX-ACCESS  read-write
    STATUS      current
    DESCRIPTION
        "The value of tmnxIsisOverloadExportInterlevel would enable the
         advertisement of ISIS interlevel routes when the system goes into
         overload state.

         When the value is set to 'true', the system will advertise the ISIS
         interlevel routes while it is in overload state.

         When the value is set to 'false', the system will suppress the ISIS
         interlevel routes while it is in overload state."
    DEFVAL      { false }
    ::= { tmnxIsisExtEntry 37 }

tmnxIsisOverloadExportExternal   OBJECT-TYPE
    SYNTAX      TruthValue
    MAX-ACCESS  read-write
    STATUS      current
    DESCRIPTION
        "The value of tmnxIsisOverloadExportExternal would enable the
         advertisement of ISIS external routes originated on the same node when
         the system goes into overload state.

         When the value is set to 'true', the system will advertise the ISIS
         external routes originated on the same node while it is in overload
         state.

         When the value is set to 'false', the system will suppress the ISIS
         external routes originated on the same node while it is in overload
         state."
    DEFVAL      { false }
    ::= { tmnxIsisExtEntry 38 }

tmnxIsisStandardMultiInstance    OBJECT-TYPE
    SYNTAX      TruthValue
    MAX-ACCESS  read-write
    STATUS      current
    DESCRIPTION
        "The value of tmnxIsisStandardMultiInstance controls the activation of
         RFC 6822 standards-compliant IS-IS Multi-Instance (single topology)
         behavior by the system.

         If the value is set to 'true', then IS-IS Multi-Instance behavior is
         according to the standard.

         If the value is set to 'false', then IS-IS Multi-Instance behavior is
         proprietary."
    DEFVAL      { false }
    ::= { tmnxIsisExtEntry 39 }

tmnxIsisDbAsn                    OBJECT-TYPE
    SYNTAX      InetAutonomousSystemNumber
    MAX-ACCESS  read-only
    STATUS      current
    DESCRIPTION
        "The value of the object tmnxIsisDbAsn indicates the Autonomous System
         Number the IGP is using during its database export.

         The value from TIMETRA-VRTR-MIB::vRtrAS4Byte at the moment
         tmnxIsisDatabaseExport is enabled is used as AS number.

         The used AS number gets updated when the value from
         ISIS-MIB::isisSysAdminState changes from off(1) to on(2) or when the
         value from tmnxIsisDatabaseExport changes from disabled(2) to
         enabled(1)."
    ::= { tmnxIsisExtEntry 40 }

tmnxIsisSrEntropyLabel           OBJECT-TYPE
    SYNTAX      INTEGER {
        enable       (1),
        forceDisable (2)
    }
    MAX-ACCESS  read-write
    STATUS      current
    DESCRIPTION
        "The value of the object tmnxIsisSrEntropyLabel specifies whether
         processing of received entropy label capability (ELC) advertisements
         is enabled or not for this ISIS instance.

         When the value is set to 'enable', the system will process any
         received ELC in ISIS.

         When the value is set to 'force-disable', the system is forced to
         ignore any received ELC in ISIS. It also prevents a user to configure
         override-tunnel ELC; i.e. the object tmnxIsisOverrideTunnelElc is
         ignored."
    DEFVAL      { enable }
    ::= { tmnxIsisExtEntry 41 }

tmnxIsisTiLfa                    OBJECT-TYPE
    SYNTAX      TruthValue
    MAX-ACCESS  read-write
    STATUS      current
    DESCRIPTION
        "The value of tmnxIsisTiLfa specifies whether Topology Independent LFA
         is enabled or not.

         The value of tmnxIsisTiLfa is only valid when the object
         tmnxIsisLoopfreeAlternate has the value 'true'."
    DEFVAL      { false }
    ::= { tmnxIsisExtEntry 42 }

tmnxIsisMaxSrFrrLabels           OBJECT-TYPE
    SYNTAX      Unsigned32 (0..3)
    MAX-ACCESS  read-write
    STATUS      current
    DESCRIPTION
        "The value of tmnxIsisMaxSrFrrLabels specifies the maximum number of
         Segment Routing Fast-Reroute labels.

         The value of tmnxIsisMaxSrFrrLabels is only valid when the objects
         tmnxIsisLoopfreeAlternate and tmnxIsisTiLfa both have the value
         'true'."
    DEFVAL      { 2 }
    ::= { tmnxIsisExtEntry 43 }

tmnxIsisPrefixAttributesTlv      OBJECT-TYPE
    SYNTAX      TmnxEnabledDisabled
    MAX-ACCESS  read-write
    STATUS      current
    DESCRIPTION
        "The value of the object tmnxIsisPrefixAttributesTlv specifies whether
         Prefix Attributes TLV has been enabled or disabled for this ISIS
         instance.

         When the value of tmnxIsisPrefixAttributesTlv is 'enabled', the ISIS
         instance will advertise the Extended Reachability Attribute Flags as
         defined in RFC7794 and process them as defined in RFC7775."
    REFERENCE
        "RFC7794 IS-IS Prefix Attributes for Extended IPv4 and IPv6 Reachability,
         section 2.1 IPv4/IPv6 Extended Reachability Attribute Flags.

         RFC7775 IS-IS Route Preference for Extended IP and IPv6 Reachability,
         section 3 Types of Routes in IS-IS Supported by Extended Reachability TLVs."
    DEFVAL      { disabled }
    ::= { tmnxIsisExtEntry 44 }

tmnxIsisLspRefreshHalfLifetime   OBJECT-TYPE
    SYNTAX      TruthValue
    MAX-ACCESS  read-write
    STATUS      current
    DESCRIPTION
        "The value of the object tmnxIsisLspRefreshHalfLifetime specifies
         whether the interval at which LSPs are refreshed is the half of the
         value set for tmnxIsisLspLifetime.

         If the value is set to true the LSPs are refreshed at the interval half of the
         LSP lifetime,  the value of tmnxIsisLspRefreshInterval is ignored.
         If the value is set to false the LSPs are refreshed at the interval set for
         tmnxIsisLspRefreshInterval."
    DEFVAL      { true }
    ::= { tmnxIsisExtEntry 45 }

tmnxIsisOverrideTunnelElc        OBJECT-TYPE
    SYNTAX      INTEGER {
        enabled  (1),
        disabled (2)
    }
    MAX-ACCESS  read-write
    STATUS      current
    DESCRIPTION
        "The value of the object tmnxIsisOverrideTunnelElc specifies whether
         received entropy label capability (ELC) advertisement is overridden or
         not for this ISIS instance.

         When the value is set to 'enabled', the system will assume that all
         ISIS nodes are capable of receiving and processing the entropy label
         on segment routed tunnels.

         When the value is set to 'disabled', the override is disabled;  the
         system will only assume entropy label capability for other ISIS nodes
         if capability advertisements are received.

         This override value is only applicable when tmnxIsisSrEntropyLabel is
         enabled."
    DEFVAL      { disabled }
    ::= { tmnxIsisExtEntry 46 }

tmnxIsisSrlbReservedLblBlockName OBJECT-TYPE
    SYNTAX      TLNamedItemOrEmpty
    MAX-ACCESS  read-write
    STATUS      current
    DESCRIPTION
        "The value of the object tmnxIsisSrlbReservedLblBlockName specifies the
         name identifying the reserved label block (SRLB) to be used on this
         ISIS instance.

         The SR Local Block (SRLB) Sub-TLV contains the range of labels the
         node has reserved for local SIDs.

         When no reserved label block name is specified, no static labels can
         be allocated.

         The reserved label block name is defined by vRtrMplsReservedLblBlkName
         and is the index for TIMETRA-MPLS-MIB::vRtrMplsReservedLblBlkTable."
    DEFVAL      { ''H }
    ::= { tmnxIsisExtEntry 47 }

tmnxIsisRemoteLfaNodeProtect     OBJECT-TYPE
    SYNTAX      TruthValue
    MAX-ACCESS  read-write
    STATUS      current
    DESCRIPTION
        "The value of tmnxIsisRemoteLfaNodeProtect specifies whether Node
         protection with Remote LFA is enabled or not.

         The value of tmnxIsisRemoteLfaNodeProtect is only valid when the
         objects tmnxIsisLoopfreeAlternate and tmnxIsisRemoteLoopfreeAlternate
         both have the value 'true'."
    DEFVAL      { false }
    ::= { tmnxIsisExtEntry 48 }

tmnxIsisRemoteLfaMaxPqNodes      OBJECT-TYPE
    SYNTAX      Unsigned32 (1..32)
    MAX-ACCESS  read-write
    STATUS      current
    DESCRIPTION
        "The value of tmnxIsisRemoteLfaMaxPqNodes specifies the maximum number
         of PQ nodes for which we perform the forward SPF check to see if its
         path to the destination does not go via the node which we are
         protecting against.

         The value of tmnxIsisRemoteLfaMaxPqNodes is only valid when the
         objects tmnxIsisLoopfreeAlternate and tmnxIsisRemoteLoopfreeAlternate
         both have the value 'true'."
    DEFVAL      { 16 }
    ::= { tmnxIsisExtEntry 49 }

tmnxIsisTiLfaNodeProtect         OBJECT-TYPE
    SYNTAX      TruthValue
    MAX-ACCESS  read-write
    STATUS      current
    DESCRIPTION
        "The value of tmnxIsisTiLfaNodeProtect specifies whether Node
         protection with Topology Independent LFA is enabled or not.

         The value of tmnxIsisTiLfaNodeProtect is only valid when the objects
         tmnxIsisLoopfreeAlternate and tmnxIsisTiLfa both have the value
         'true'."
    DEFVAL      { false }
    ::= { tmnxIsisExtEntry 50 }

tmnxIsisLspMinRemainingLifetime  OBJECT-TYPE
    SYNTAX      Unsigned32 (0 | 350..65535)
    UNITS       "seconds"
    MAX-ACCESS  read-write
    STATUS      current
    DESCRIPTION
        "The value of the object tmnxIsisLspMinRemainingLifetime specifies the
         minimum value to which the Remaining Lifetime of the LSP can be set.

         To avoid that LSPs are purged prematurely, the
         tmnxIsisLspMinRemainingLifetime must be set to a value greater than or
         equal to the locally configured value of tmnxIsisLspLifetime.

         A value of 0 indicates that there is no minimum configured, i.e. the
         Remaining Lifetime in the incoming LSP will not be changed."
    DEFVAL      { 0 }
    ::= { tmnxIsisExtEntry 51 }

tmnxIsisReferenceBwU64High       OBJECT-TYPE
    SYNTAX      TmnxHigh32
    UNITS       "kilobps"
    MAX-ACCESS  read-write
    STATUS      current
    DESCRIPTION
        "The value of the object tmnxIsisReferenceBwU64High specifies the upper
         32 bit of the reference bandwidth that needs to be used to calculate
         the cost.

         This value should always be set along with tmnxIsisReferenceBwU64Low,
         otherwise an 'inconsistentValue' error is returned.

         In order to calculate the lowest cost to reach a given destination
         each configured level on each interface must have a cost.

         If the reference-bandwidth is defined then the cost is calculated
         using the following formula:
             Cost = reference-bandwidth / bandwidth.

         If the reference bandwidth is configured as Ten Gig (10,000,000,000) a
         100-Mbps interface has a default metric of 100. In order for metrics
         in excess of 63 to be configured wide metrics must be deployed.

         A value of '0' means that the reference bandwidth is not defined."
    DEFVAL      { 0 }
    ::= { tmnxIsisExtEntry 52 }

tmnxIsisReferenceBwU64Low        OBJECT-TYPE
    SYNTAX      TmnxLow32
    UNITS       "kilobps"
    MAX-ACCESS  read-write
    STATUS      current
    DESCRIPTION
        "The value of the object tmnxIsisReferenceBwU64Low specifies the lower
         32 bit of the reference bandwidth that needs to be used to calculate
         the cost.

         This value should always be set along with tmnxIsisReferenceBwU64High,
         otherwise an 'inconsistentValue' error is returned.

         In order to calculate the lowest cost to reach a given destination
         each configured level on each interface must have a cost.

         If the reference-bandwidth is defined then the cost is calculated
         using the following formula:
             Cost = reference-bandwidth / bandwidth.

         If the reference bandwidth is configured as Ten Gig (10,000,000,000) a
         100-Mbps interface has a default metric of 100. In order for metrics
         in excess of 63 to be configured wide metrics must be deployed.

         A value of '0' means that the reference bandwidth is not defined."
    DEFVAL      { 0 }
    ::= { tmnxIsisExtEntry 53 }

tmnxIsisEgressStatsNodeSid       OBJECT-TYPE
    SYNTAX      TruthValue
    MAX-ACCESS  read-write
    STATUS      current
    DESCRIPTION
        "The value of tmnxIsisEgressStatsNodeSid specifies whether egress
         statistic collection on Node SIDs is enabled or not."
    DEFVAL      { false }
    ::= { tmnxIsisExtEntry 54 }

tmnxIsisEgressStatsAdjSid        OBJECT-TYPE
    SYNTAX      TruthValue
    MAX-ACCESS  read-write
    STATUS      current
    DESCRIPTION
        "The value of tmnxIsisEgressStatsAdjSid specifies whether egress
         statistic collection on Adjacency SIDs is enabled or not."
    DEFVAL      { false }
    ::= { tmnxIsisExtEntry 55 }

tmnxIsisEgressStatsAdjSet        OBJECT-TYPE
    SYNTAX      TruthValue
    MAX-ACCESS  read-write
    STATUS      current
    DESCRIPTION
        "The value of tmnxIsisEgressStatsAdjSet specifies whether egress
         statistic collection on Adjacency sets is enabled or not."
    DEFVAL      { false }
    ::= { tmnxIsisExtEntry 56 }

tmnxIsisIngressStatsNodeSid      OBJECT-TYPE
    SYNTAX      TruthValue
    MAX-ACCESS  read-write
    STATUS      current
    DESCRIPTION
        "The value of tmnxIsisIngressStatsNodeSid specifies whether ingress
         statistic collection on Node SIDs is enabled or not."
    DEFVAL      { false }
    ::= { tmnxIsisExtEntry 57 }

tmnxIsisIngressStatsAdjSid       OBJECT-TYPE
    SYNTAX      TruthValue
    MAX-ACCESS  read-write
    STATUS      current
    DESCRIPTION
        "The value of tmnxIsisIngressStatsAdjSid specifies whether ingress
         statistic collection on Adjacency SIDs is enabled or not."
    DEFVAL      { false }
    ::= { tmnxIsisExtEntry 58 }

tmnxIsisIngressStatsAdjSet       OBJECT-TYPE
    SYNTAX      TruthValue
    MAX-ACCESS  read-write
    STATUS      current
    DESCRIPTION
        "The value of tmnxIsisIngressStatsAdjSet specifies whether ingress
         statistic collection on Adjacency sets is enabled or not."
    DEFVAL      { false }
    ::= { tmnxIsisExtEntry 59 }

tmnxIsisTEIpv6                   OBJECT-TYPE
    SYNTAX      TruthValue
    MAX-ACCESS  read-write
    STATUS      current
    DESCRIPTION
        "The value of tmnxIsisTEIpv6 specifies whether traffic engineering (TE)
         behavior for IPv6 SR-TE is enabled or not.

         If the value is 'true', the ISIS instance will advertise the RFC 6119
         TLVs and sub-TLVs: IPv6 TE router ID TLV, IPv6 interface Address
         sub-TLV and Neighbor Address sub-TLV, or Link-Local Interface
         Identifiers sub-TLV if the interface has no global unicast IPv6
         address.

         The value of tmnxIsisTEIpv6 is only valid when the object
         tmnxIsisTrafficEng has the value 'true'.

         This traffic engineering option is only supported on a  base router
         ISIS instance."
    DEFVAL      { false }
    ::= { tmnxIsisExtEntry 60 }

tmnxIsisTEApplicationLinkAttr    OBJECT-TYPE
    SYNTAX      TruthValue
    MAX-ACCESS  read-write
    STATUS      current
    DESCRIPTION
        "The value of tmnxIsisTEApplicationLinkAttr specifies whether the
         traffic engineering (TE) attributes of each link are advertised on a
         per application basis or not.

         If the value is 'true', the ISIS instance will advertise the TE
         attributes for the SR-TE and RSVP-TE application separately in the
         sub-sub-TLVs of the application attribute sub-TLV. The legacy TE
         attributes will also be advertised if the object  tmnxIsisTEApplLegacy
         is 'true'.

         The value of tmnxIsisTEApplicationLinkAttr is only valid when the
         object tmnxIsisTrafficEng has the value 'true'.

         This traffic engineering option is only supported on a  base router
         ISIS instance."
    DEFVAL      { false }
    ::= { tmnxIsisExtEntry 61 }

tmnxIsisTEApplLegacy             OBJECT-TYPE
    SYNTAX      TruthValue
    MAX-ACCESS  read-write
    STATUS      current
    DESCRIPTION
        "The value of tmnxIsisTEApplLegacy specifies whether the legacy mode of
         advertising traffic engineering (TE) attributes is enabled or not.

         If the value is 'true', the ISIS instance will advertise the legacy TE
         attributes for the application.

         The value of tmnxIsisTEApplicationLinkAttr is only valid when the
         objects tmnxIsisTrafficEng and tmnxIsisTEApplicationLinkAttr both have
         the value 'true'.

         This traffic engineering option is only supported on a  base router
         instance."
    DEFVAL      { false }
    ::= { tmnxIsisExtEntry 62 }

tmnxIsisOperIpv6TERouterIdType   OBJECT-TYPE
    SYNTAX      InetAddressType
    MAX-ACCESS  read-only
    STATUS      current
    DESCRIPTION
        "The value of tmnxIsisOperIpv6TERouterIdType indicates the IP address
         type of tmnxIsisOperIpv6TERouterId"
    ::= { tmnxIsisExtEntry 63 }

tmnxIsisOperIpv6TERouterId       OBJECT-TYPE
    SYNTAX      InetAddress (SIZE (0|16))
    MAX-ACCESS  read-only
    STATUS      current
    DESCRIPTION
        "The value of the object tmnxIsisOperIpv6TERouterId indicates the
         Traffic Engineering Router ID."
    ::= { tmnxIsisExtEntry 64 }

tmnxIsisSrMicroLoopAvoidance     OBJECT-TYPE
    SYNTAX      TruthValue
    MAX-ACCESS  read-write
    STATUS      current
    DESCRIPTION
        "The value of tmnxIsisSrMicroLoopAvoidance specifies whether
         micro-loops avoidance during the convergence is enabled or not.

         If the value is 'true', the ISIS instance will use the Loop Free SR
         path for the time specified by the object
         tmnxIsisSrMicroLoopAvdFibDelay."
    DEFVAL      { false }
    ::= { tmnxIsisExtEntry 65 }

tmnxIsisSrMicroLoopAvdFibDelay   OBJECT-TYPE
    SYNTAX      Unsigned32 (1..300)
    UNITS       "deciseconds"
    MAX-ACCESS  read-write
    STATUS      current
    DESCRIPTION
        "The value of the object tmnxIsisSrMicroLoopAvdFibDelay specifies the
         time during which the system would continue to use the loop free
         alternate path when the micro-loops avoidance is enabled."
    DEFVAL      { 15 }
    ::= { tmnxIsisExtEntry 66 }

tmnxIsisSrClassForwarding        OBJECT-TYPE
    SYNTAX      TruthValue
    MAX-ACCESS  read-write
    STATUS      current
    DESCRIPTION
        "The value of tmnxIsisSrClassForwarding specifies whether Class Based
         Forwarding is enabled or not.

         If the value is 'true', Class Based Forwarding with ECMP for SR-ISIS
         over RSVP-TE LSPs as IGP shortcuts is enabled."
    DEFVAL      { false }
    ::= { tmnxIsisExtEntry 67 }

tmnxIsisLoopfreeAltAugmRteTable  OBJECT-TYPE
    SYNTAX      TruthValue
    MAX-ACCESS  read-write
    STATUS      current
    DESCRIPTION
        "The value of the object tmnxIsisLoopfreeAltAugmRteTable specifies
         whether detailed LFA information should be augmented to the route
         table.

         The value of tmnxIsisLoopfreeAltAugmRteTable is only valid when the
         objects tmnxIsisLoopfreeAlternate and tmnxIsisRemoteLoopfreeAlternate
         both have the value 'true'."
    DEFVAL      { false }
    ::= { tmnxIsisExtEntry 68 }

tmnxIsisMaxSrv6FrrSids           OBJECT-TYPE
    SYNTAX      Unsigned32 (0..3)
    MAX-ACCESS  read-write
    STATUS      current
    DESCRIPTION
        "The value of tmnxIsisMaxSrv6FrrSids specifies the maximum number of
         SRv6 Fast-Reroute SIDs.

         The value of tmnxIsisMaxSrv6FrrSids is only valid when the objects
         tmnxIsisLoopfreeAlternate and tmnxIsisTiLfa both have the value
         'true'."
    DEFVAL      { 1 }
    ::= { tmnxIsisExtEntry 69 }

tmnxIsisPrefixSidTable           OBJECT-TYPE
    SYNTAX      SEQUENCE OF TmnxIsisPrefixSidEntry
    MAX-ACCESS  not-accessible
    STATUS      current
    DESCRIPTION
        "The tmnxIsisPrefixSidTable maintains the routes learned by an instance
         of IS-IS protocol for a specific multi topology id."
    ::= { tmnxIsisSystemObjs 12 }

tmnxIsisPrefixSidEntry           OBJECT-TYPE
    SYNTAX      TmnxIsisPrefixSidEntry
    MAX-ACCESS  not-accessible
    STATUS      current
    DESCRIPTION
        "Each row entry in the tmnxIsisPrefixSidTable stores a route for a
         given instance of the IS-IS protocol for a specific multi topology id."
    INDEX       {
        vRtrID,
        isisSysInstance,
        tmnxIsisRouteMtId,
        tmnxIsisRouteDestType,
        tmnxIsisRouteDest,
        tmnxIsisRoutePrefixLength,
        tmnxIsisPrefixSidAdvRtrSysID,
        tmnxIsisPrefixSidLevel,
        tmnxIsisPrefixSidValue
    }
    ::= { tmnxIsisPrefixSidTable 1 }

TmnxIsisPrefixSidEntry           ::= SEQUENCE
{
    tmnxIsisPrefixSidAdvRtrSysID     SystemID,
    tmnxIsisPrefixSidLevel           INTEGER,
    tmnxIsisPrefixSidValue           Unsigned32,
    tmnxIsisPrefixSidType            INTEGER,
    tmnxIsisPrefixSidFlags           BITS,
    tmnxIsisPrefixSidSRMS            TruthValue,
    tmnxIsisPrefixSidSRMSSelected    TruthValue,
    tmnxIsisPrefixSidAlgorithm       TmnxAlgorithmId,
    tmnxIsisPrefixSharedSid          TruthValue
}

tmnxIsisPrefixSidAdvRtrSysID     OBJECT-TYPE
    SYNTAX      SystemID
    MAX-ACCESS  not-accessible
    STATUS      current
    DESCRIPTION
        "The value of the object tmnxIsisPrefixSidAdvRtrSysID specifies the
         system-id of the advertising IS through which this prefix/SID is
         reachable."
    ::= { tmnxIsisPrefixSidEntry 1 }

tmnxIsisPrefixSidLevel           OBJECT-TYPE
    SYNTAX      INTEGER {
        level1IS (1),
        level2IS (2)
    }
    MAX-ACCESS  not-accessible
    STATUS      current
    DESCRIPTION
        "The value of the object tmnxIsisPrefixSidLevel specifies the IS-IS
         Level at which the prefix was learned."
    ::= { tmnxIsisPrefixSidEntry 2 }

tmnxIsisPrefixSidValue           OBJECT-TYPE
    SYNTAX      Unsigned32
    MAX-ACCESS  not-accessible
    STATUS      current
    DESCRIPTION
        "The value of the object tmnxIsisPrefixSidValue specifies the SID label
         or index for this prefix."
    ::= { tmnxIsisPrefixSidEntry 3 }

tmnxIsisPrefixSidType            OBJECT-TYPE
    SYNTAX      INTEGER {
        internal (1),
        external (2)
    }
    MAX-ACCESS  read-only
    STATUS      current
    DESCRIPTION
        "The value of the object tmnxIsisPrefixSidType indicates the type of
         route represented by this row entry."
    ::= { tmnxIsisPrefixSidEntry 4 }

tmnxIsisPrefixSidFlags           OBJECT-TYPE
    SYNTAX      BITS {
        bitR (0),
        bitN (1),
        bitP (2),
        bitE (3),
        bitV (4),
        bitL (5)
    }
    MAX-ACCESS  read-only
    STATUS      current
    DESCRIPTION
        "The value of the object tmnxIsisPrefixSidFlags indicates the flags of
         a Prefix-SID advertised by an IP Reach or Label Binding TLV.

         bitR   (0)  - Re-advertisement flag.  If set, then the prefix to
           which this Prefix-SID is attached, has been propagated by the
           router either from another level (i.e.: from level-1 to level-2
           or the opposite) or from redistribution (e.g.: from another
           protocol).
         bitN   (1)  - Node-SID flag. The N-Flag is set on Prefix-SIDs
           attached to a router loopback address.
         bitP   (2)  - no-PHP flag. If set, then the penultimate hop MUST NOT
           pop the Prefix-SID before delivering the packet to the node
           that advertised the Prefix-SID.
         bitE   (3)  - Explicit-Null Flag.  If set, any upstream neighbor
           of the Prefix-SID originator MUST replace the Prefix-SID with
           a Prefix-SID having an Explicit-NULL value (0 for IPv4 and 2 for
           IPv6) before forwarding the packet.
         bitV   (4)  - Value flag. If set, then the Prefix-SID carries a
           value (instead of an index).
         bitL   (5)  - Local Flag.  If set, then the value/index carried by
           the Prefix-SID has local significance."
    ::= { tmnxIsisPrefixSidEntry 5 }

tmnxIsisPrefixSidSRMS            OBJECT-TYPE
    SYNTAX      TruthValue
    MAX-ACCESS  read-only
    STATUS      current
    DESCRIPTION
        "The value of the object tmnxIsisPrefixSidSRMS indicates whether or not
         the Prefix/SID is advertised by a Segment Routing Mapping Server."
    ::= { tmnxIsisPrefixSidEntry 6 }

tmnxIsisPrefixSidSRMSSelected    OBJECT-TYPE
    SYNTAX      TruthValue
    MAX-ACCESS  read-only
    STATUS      current
    DESCRIPTION
        "The value of the object tmnxIsisPrefixSidSRMSSelected indicates
         whether or not the prefix SID received in the SRMS TLV is selected to
         be programmed.

         When there is however a SID for the same prefix received in a prefix
         TLV, that prefix SID will be programmed and not the SRMS prefix SID.

         The object tmnxIsisPrefixSidSRMSSelected is only applicable for SRMS
         prefix SID; tmnxIsisPrefixSidSRMSSelected will return false in case
         the value of tmnxIsisPrefixSidSRMS is false."
    ::= { tmnxIsisPrefixSidEntry 7 }

tmnxIsisPrefixSidAlgorithm       OBJECT-TYPE
    SYNTAX      TmnxAlgorithmId
    MAX-ACCESS  read-only
    STATUS      current
    DESCRIPTION
        "The value of the object tmnxIsisPrefixSidAlgorithm indicates the
         algorithm related to the prefix SID.

         The value can indicate a defined IGP Algorithm (value 0 is SPF) or a
         Flexible Algorithm (range 128..255)."
    ::= { tmnxIsisPrefixSidEntry 8 }

tmnxIsisPrefixSharedSid          OBJECT-TYPE
    SYNTAX      TruthValue
    MAX-ACCESS  read-only
    STATUS      current
    DESCRIPTION
        "The value of the object tmnxIsisPrefixSharedSid indicates whether or
         not the Prefix/SID is a local shared node SID.

         In case it is a remote prefix SID or if it is not a local shared node
         SID, the returned value will be 'false'."
    ::= { tmnxIsisPrefixSidEntry 9 }

tmnxIsisSRMapServTable           OBJECT-TYPE
    SYNTAX      SEQUENCE OF TmnxIsisSRMapServEntry
    MAX-ACCESS  not-accessible
    STATUS      current
    DESCRIPTION
        "The tmnxIsisSRMapServTable contains objects to configure Segment
         Routing (SR) Mapping Server (MS) data for IS-IS instances.

         The system automatically creates and destroys rows in this table when
         rows in the tmnxIsisTable are created and destroyed."
    ::= { tmnxIsisSystemObjs 13 }

tmnxIsisSRMapServEntry           OBJECT-TYPE
    SYNTAX      TmnxIsisSRMapServEntry
    MAX-ACCESS  not-accessible
    STATUS      current
    DESCRIPTION
        "Each conceptual row in the tmnxIsisSRMapServTable contains Segment
         Routing (SR) Mapping Server (MS) information of an IS-IS instance.

         Entries in this table are created and removed automatically by the
         system."
    INDEX       {
        vRtrID,
        isisSysInstance
    }
    ::= { tmnxIsisSRMapServTable 1 }

TmnxIsisSRMapServEntry           ::= SEQUENCE
{
    tmnxIsisSRMapServLastCh          TimeStamp,
    tmnxIsisSRMapServAdminState      TmnxAdminState
}

tmnxIsisSRMapServLastCh          OBJECT-TYPE
    SYNTAX      TimeStamp
    MAX-ACCESS  read-only
    STATUS      current
    DESCRIPTION
        "The value of the object tmnxIsisSRMapServLastCh indicates the
         sysUpTime when a configurable object in this row was last modified."
    ::= { tmnxIsisSRMapServEntry 1 }

tmnxIsisSRMapServAdminState      OBJECT-TYPE
    SYNTAX      TmnxAdminState
    MAX-ACCESS  read-write
    STATUS      current
    DESCRIPTION
        "The value of the object tmnxIsisSRMapServAdminState specifies the
         administrative state of the Segment Routing Mapping Server for this
         IS-IS instance."
    DEFVAL      { outOfService }
    ::= { tmnxIsisSRMapServEntry 2 }

tmnxIsisSRMSSidMapTable          OBJECT-TYPE
    SYNTAX      SEQUENCE OF TmnxIsisSRMSSidMapEntry
    MAX-ACCESS  not-accessible
    STATUS      current
    DESCRIPTION
        "The tmnxIsisSRMSSidMapTable contains objects to configure Segment
         Routing (SR) Mapping Server (MS) SID data for IS-IS prefixes."
    ::= { tmnxIsisSystemObjs 14 }

tmnxIsisSRMSSidMapEntry          OBJECT-TYPE
    SYNTAX      TmnxIsisSRMSSidMapEntry
    MAX-ACCESS  not-accessible
    STATUS      current
    DESCRIPTION
        "Each conceptual row in the tmnxIsisSRMSSidMapTable contains Segment
         Routing (SR) Mapping Server (MS) SID information of an IS-IS prefix.

         Entries in this table can be created and deleted via SNMP SET
         operations to tmnxIsisSRMSSidMapRowStatus."
    INDEX       {
        vRtrID,
        isisSysInstance,
        tmnxIsisSRMSSidMapNodeSidIndex
    }
    ::= { tmnxIsisSRMSSidMapTable 1 }

TmnxIsisSRMSSidMapEntry          ::= SEQUENCE
{
    tmnxIsisSRMSSidMapNodeSidIndex   Unsigned32,
    tmnxIsisSRMSSidMapRowStatus      RowStatus,
    tmnxIsisSRMSSidMapLastCh         TimeStamp,
    tmnxIsisSRMSSidMapPrefixType     InetAddressType,
    tmnxIsisSRMSSidMapPrefix         InetAddress,
    tmnxIsisSRMSSidMapPrefixLength   InetAddressPrefixLength,
    tmnxIsisSRMSSidMapNodeSidRange   Unsigned32,
    tmnxIsisSRMSSidMapFlags          BITS,
    tmnxIsisSRMSSidMapLevel          INTEGER,
    tmnxIsisSRMSSidMapClearNFlag     TruthValue
}

tmnxIsisSRMSSidMapNodeSidIndex   OBJECT-TYPE
    SYNTAX      Unsigned32
    MAX-ACCESS  not-accessible
    STATUS      current
    DESCRIPTION
        "The value of the object tmnxIsisSRMSSidMapNodeSidIndex specifies the
         the node SID index/label for the IS-IS prefix which will be advertised
         in a SID/Label Binding TLV."
    ::= { tmnxIsisSRMSSidMapEntry 1 }

tmnxIsisSRMSSidMapRowStatus      OBJECT-TYPE
    SYNTAX      RowStatus
    MAX-ACCESS  read-create
    STATUS      current
    DESCRIPTION
        "The value of the object tmnxIsisSRMSSidMapRowStatus specifies the row
         status used to create and delete entries in the
         tmnxIsisSRMSSidMapTable.

         To create a row, set this object to 'createAndGo(4)'. For the row
         creation to succeed the prefix must be set in the same SNMP SET PDU;
         i.e. the value of tmnxIsisSRMSSidMapPrefixType and
         tmnxIsisSRMSSidMapPrefixLength must be set to a non-zero value and
         tmnxIsisSRMSSidMapPrefix must be set to a non-empty string."
    ::= { tmnxIsisSRMSSidMapEntry 2 }

tmnxIsisSRMSSidMapLastCh         OBJECT-TYPE
    SYNTAX      TimeStamp
    MAX-ACCESS  read-only
    STATUS      current
    DESCRIPTION
        "The value of the object tmnxIsisSRMSSidMapLastCh specifies the
         sysUpTime when a configurable object in this row was last modified."
    ::= { tmnxIsisSRMSSidMapEntry 3 }

tmnxIsisSRMSSidMapPrefixType     OBJECT-TYPE
    SYNTAX      InetAddressType
    MAX-ACCESS  read-create
    STATUS      current
    DESCRIPTION
        "The value of the object tmnxIsisSRMSSidMapPrefixType specifies the IP
         address type of tmnxIsisSRMSSidMapPrefix."
    ::= { tmnxIsisSRMSSidMapEntry 4 }

tmnxIsisSRMSSidMapPrefix         OBJECT-TYPE
    SYNTAX      InetAddress (SIZE (4|16))
    MAX-ACCESS  read-create
    STATUS      current
    DESCRIPTION
        "The value of the object tmnxIsisSRMSSidMapPrefix specifies the IP
         address of the IS-IS prefix which will be advertised in a SID/Label
         Binding TLV by the SR Mapping Server."
    ::= { tmnxIsisSRMSSidMapEntry 5 }

tmnxIsisSRMSSidMapPrefixLength   OBJECT-TYPE
    SYNTAX      InetAddressPrefixLength
    MAX-ACCESS  read-create
    STATUS      current
    DESCRIPTION
        "The value of the object tmnxIsisSRMSSidMapPrefixLength specifies the
         prefix length to be used with tmnxIsisSRMSSidMapPrefix to get the SR
         Mapping Server prefix."
    ::= { tmnxIsisSRMSSidMapEntry 6 }

tmnxIsisSRMSSidMapNodeSidRange   OBJECT-TYPE
    SYNTAX      Unsigned32 (0..65535)
    MAX-ACCESS  read-create
    STATUS      current
    DESCRIPTION
        "The value of the object tmnxIsisSRMSSidMapNodeSidRange specifies the
         the node SID range for the IS-IS prefix which will be advertised in a
         SID/Label Binding TLV."
    DEFVAL      { 1 }
    ::= { tmnxIsisSRMSSidMapEntry 7 }

tmnxIsisSRMSSidMapFlags          OBJECT-TYPE
    SYNTAX      BITS {
        bitS (0)
    }
    MAX-ACCESS  read-create
    STATUS      current
    DESCRIPTION
        "The value of the object tmnxIsisSRMSSidMapFlags specifies the flags
         that are set in a SID/Label Binding TLV advertised by the Segment
         Routing Mapping Server.

         bitS  (0)  - If the S flag is set, the SID/Label Binding TLV should
                      be flooded across the entire routing domain;
                      if the S flag is not set, the SID/Label Binding TLV
                      must not be leaked between levels."
    DEFVAL      { {} }
    ::= { tmnxIsisSRMSSidMapEntry 8 }

tmnxIsisSRMSSidMapLevel          OBJECT-TYPE
    SYNTAX      INTEGER {
        level1   (1),
        level2   (2),
        level1L2 (3)
    }
    MAX-ACCESS  read-create
    STATUS      current
    DESCRIPTION
        "The value of the object tmnxIsisSRMSSidMapLevel specifies the IS-IS
         Level in which the SID/Label Binding TLV is flood by the Segment
         Routing Mapping Server.

         When this object is set to level1 but the level capability on the
         IS-IS instance (isisSysType) is set to level2, no MS SID/Label Binding
         TLV is sent.

         When this object is set to level1 and the level capability on the
         IS-IS instance (isisSysType) is set to level1 or level1L2, SID/Label
         Binding TLV will be sent on the interfaces with isisCircLevel set to
         level1 or level1L2.

         When this object is set to level2 and the level capability on the
         IS-IS instance (isisSysType) is set to level2 or level1L2, SID/Label
         Binding TLV will be sent on the interfaces with isisCircLevel set to
         level2 or level1L2.

         When this object is set to level1L2, SID/Label Binding TLV will be
         sent on all interfaces."
    DEFVAL      { level1L2 }
    ::= { tmnxIsisSRMSSidMapEntry 9 }

tmnxIsisSRMSSidMapClearNFlag     OBJECT-TYPE
    SYNTAX      TruthValue
    MAX-ACCESS  read-create
    STATUS      current
    DESCRIPTION
        "The value of tmnxIsisSRMSSidMapClearNFlag specifies whether the
         node-sid flag (N-flag) should be cleared in a SID/Label Binding TLV.

         When the value of tmnxIsisSRMSSidMapClearNFlag is false, the TLV is
         tagged as a node SID meaning that it belongs to this node only.

         When the value of tmnxIsisSRMSSidMapClearNFlag is true, the TLV is
         considered as anycast SID meaning that the same prefix may be
         advertised by multiple nodes."
    DEFVAL      { false }
    ::= { tmnxIsisSRMSSidMapEntry 10 }

tmnxIsisSRLfaStatsTable          OBJECT-TYPE
    SYNTAX      SEQUENCE OF TmnxIsisSRLfaStatsEntry
    MAX-ACCESS  not-accessible
    STATUS      current
    DESCRIPTION
        "The tmnxIsisSRLfaStatsTable maintains information on Segment Routing
         (SR) loopfree-alternate (LFA) coverage for each instance of IS-IS
         protocol for a specific multi topology id."
    ::= { tmnxIsisSystemObjs 15 }

tmnxIsisSRLfaStatsEntry          OBJECT-TYPE
    SYNTAX      TmnxIsisSRLfaStatsEntry
    MAX-ACCESS  not-accessible
    STATUS      current
    DESCRIPTION
        "Each row entry in the tmnxIsisSRLfaStatsTable represents information
         on SR LFA coverage for various topologies of the system."
    INDEX       {
        vRtrID,
        isisSysInstance,
        tmnxIsisSRLfaStatsLevel,
        tmnxIsisSRLfaStatsMtId,
        tmnxIsisSRLfaStatsSidType,
        tmnxIsisSRLfaStatsProtoVersion
    }
    ::= { tmnxIsisSRLfaStatsTable 1 }

TmnxIsisSRLfaStatsEntry          ::= SEQUENCE
{
    tmnxIsisSRLfaStatsLevel          INTEGER,
    tmnxIsisSRLfaStatsMtId           Unsigned32,
    tmnxIsisSRLfaStatsSidType        INTEGER,
    tmnxIsisSRLfaStatsProtoVersion   INTEGER,
    tmnxIsisSRLfaStatsTotalSid       Unsigned32,
    tmnxIsisSRLfaStatsLfaCovered     Unsigned32,
    tmnxIsisSRLfaStatsRLfaCovered    Unsigned32,
    tmnxIsisSRLfaStatsTiLfaCovered   Unsigned32
}

tmnxIsisSRLfaStatsLevel          OBJECT-TYPE
    SYNTAX      INTEGER {
        level1   (1),
        level2   (2),
        level1L2 (3)
    }
    MAX-ACCESS  not-accessible
    STATUS      current
    DESCRIPTION
        "The value of the object tmnxIsisSRLfaStatsLevel specifies the IS-IS
         Level for which SR LFA coverage has been computed."
    ::= { tmnxIsisSRLfaStatsEntry 1 }

tmnxIsisSRLfaStatsMtId           OBJECT-TYPE
    SYNTAX      Unsigned32
    MAX-ACCESS  not-accessible
    STATUS      current
    DESCRIPTION
        "The value of the object tmnxIsisSRLfaStatsMtId specifies the
         multi-topology (MT) id number for which SR LFA coverage has been
         computed."
    ::= { tmnxIsisSRLfaStatsEntry 2 }

tmnxIsisSRLfaStatsSidType        OBJECT-TYPE
    SYNTAX      INTEGER {
        nodeSid    (0),
        adjSid     (1),
        globAdjSid (2)
    }
    MAX-ACCESS  not-accessible
    STATUS      current
    DESCRIPTION
        "The value of the object tmnxIsisSRLfaStatsSidType specifies the SID
         type for which SR LFA coverage has been computed."
    ::= { tmnxIsisSRLfaStatsEntry 3 }

tmnxIsisSRLfaStatsProtoVersion   OBJECT-TYPE
    SYNTAX      INTEGER {
        ipv4 (0),
        ipv6 (1)
    }
    MAX-ACCESS  not-accessible
    STATUS      current
    DESCRIPTION
        "The value of the object tmnxIsisSRLfaStatsProtoVersion specifies the
         protocol version for which SR LFA coverage has been computed."
    ::= { tmnxIsisSRLfaStatsEntry 4 }

tmnxIsisSRLfaStatsTotalSid       OBJECT-TYPE
    SYNTAX      Unsigned32
    MAX-ACCESS  read-only
    STATUS      current
    DESCRIPTION
        "The value of the object tmnxIsisSRLfaStatsTotalSid indicates the
         number of SIDs eligible for SR LFA calculation"
    ::= { tmnxIsisSRLfaStatsEntry 5 }

tmnxIsisSRLfaStatsLfaCovered     OBJECT-TYPE
    SYNTAX      Unsigned32
    MAX-ACCESS  read-only
    STATUS      current
    DESCRIPTION
        "The value of the object tmnxIsisSRLfaStatsLfaCovered indicates the
         number of SIDs for which an LFA is found."
    ::= { tmnxIsisSRLfaStatsEntry 6 }

tmnxIsisSRLfaStatsRLfaCovered    OBJECT-TYPE
    SYNTAX      Unsigned32
    MAX-ACCESS  read-only
    STATUS      current
    DESCRIPTION
        "The value of the object tmnxIsisSRLfaStatsRLfaCovered indicates the
         number of SIDs for which an Remote LFA is found."
    ::= { tmnxIsisSRLfaStatsEntry 7 }

tmnxIsisSRLfaStatsTiLfaCovered   OBJECT-TYPE
    SYNTAX      Unsigned32
    MAX-ACCESS  read-only
    STATUS      current
    DESCRIPTION
        "The value of the object tmnxIsisSRLfaStatsTiLfaCovered indicates the
         number of SIDs for which an Topology Independent LFA is found."
    ::= { tmnxIsisSRLfaStatsEntry 8 }

tmnxIsisIgpSCTable               OBJECT-TYPE
    SYNTAX      SEQUENCE OF TmnxIsisIgpSCEntry
    MAX-ACCESS  not-accessible
    STATUS      current
    DESCRIPTION
        "The tmnxIsisIgpSCTable maintains information on IGP Shortcut for each
         instance of IS-IS protocol."
    ::= { tmnxIsisSystemObjs 16 }

tmnxIsisIgpSCEntry               OBJECT-TYPE
    SYNTAX      TmnxIsisIgpSCEntry
    MAX-ACCESS  not-accessible
    STATUS      current
    DESCRIPTION
        "Each row entry in the tmnxIsisIgpSCTable represents information on IGP
         shortcut parameters configured for an ISIS instance."
    INDEX       {
        vRtrID,
        isisSysInstance
    }
    ::= { tmnxIsisIgpSCTable 1 }

TmnxIsisIgpSCEntry               ::= SEQUENCE
{
    tmnxIsisIgpSCAdminState          TmnxAdminState,
    tmnxIsisIgpSCAllowSrOverSrTe     TruthValue
}

tmnxIsisIgpSCAdminState          OBJECT-TYPE
    SYNTAX      TmnxAdminState
    MAX-ACCESS  read-create
    STATUS      current
    DESCRIPTION
        "The value of the object tmnxIsisIgpSCAdminState specifies the desired
         administrative state for IGP shortcuts on this ISIS instance."
    DEFVAL      { outOfService }
    ::= { tmnxIsisIgpSCEntry 2 }

tmnxIsisIgpSCAllowSrOverSrTe     OBJECT-TYPE
    SYNTAX      TruthValue
    MAX-ACCESS  read-create
    STATUS      current
    DESCRIPTION
        "The value of the object tmnxIsisIgpSCAllowSrOverSrTe specifies to
         allow SR over SRTE, for that prefer strict SR-TE tunnels."
    DEFVAL      { false }
    ::= { tmnxIsisIgpSCEntry 3 }

tmnxIsisIgpSCTunnNextHopTable    OBJECT-TYPE
    SYNTAX      SEQUENCE OF TmnxIsisIgpSCTunnNextHopEntry
    MAX-ACCESS  not-accessible
    STATUS      current
    DESCRIPTION
        "The tmnxIsisIgpSCTunnNextHopTable maintains information on IGP
         Shortcut for each instance of IS-IS protocol."
    ::= { tmnxIsisSystemObjs 17 }

tmnxIsisIgpSCTunnNextHopEntry    OBJECT-TYPE
    SYNTAX      TmnxIsisIgpSCTunnNextHopEntry
    MAX-ACCESS  not-accessible
    STATUS      current
    DESCRIPTION
        "Each row entry in the tmnxIsisIgpSCTunnNextHopTable represents
         information on IGP shortcut tunnel next hop parameters configured on
         the system."
    INDEX       {
        vRtrID,
        isisSysInstance,
        tmnxIsisIgpSCTunnNextHopFamily
    }
    ::= { tmnxIsisIgpSCTunnNextHopTable 1 }

TmnxIsisIgpSCTunnNextHopEntry    ::= SEQUENCE
{
    tmnxIsisIgpSCTunnNextHopFamily   TmnxIgpSCFamilyType,
    tmnxIsisIgpSCTunnNextHopLstCh    TimeStamp,
    tmnxIsisIgpSCTNHResolution       TResolveStatus,
    tmnxIsisIgpSCTNHResFilterRsvp    TruthValue,
    tmnxIsisIgpSCTNHResFilterSrTe    TruthValue
}

tmnxIsisIgpSCTunnNextHopFamily   OBJECT-TYPE
    SYNTAX      TmnxIgpSCFamilyType
    MAX-ACCESS  not-accessible
    STATUS      current
    DESCRIPTION
        "The value of tmnxIsisIgpSCTunnNextHopFamily specifies the address
         family for which the tunnel selection applies."
    ::= { tmnxIsisIgpSCTunnNextHopEntry 1 }

tmnxIsisIgpSCTunnNextHopLstCh    OBJECT-TYPE
    SYNTAX      TimeStamp
    MAX-ACCESS  read-only
    STATUS      current
    DESCRIPTION
        "The value of the object tmnxIsisIgpSCTunnNextHopLstCh indicates the
         sysUpTime when this row was last modified."
    ::= { tmnxIsisIgpSCTunnNextHopEntry 2 }

tmnxIsisIgpSCTNHResolution       OBJECT-TYPE
    SYNTAX      TResolveStatus
    MAX-ACCESS  read-create
    STATUS      current
    DESCRIPTION
        "The value of tmnxIsisIgpSCTNHResolution specifies the resolution
         status used for resolving IGP shortcut tunnel next hops belonging to a
         specific family type.

         When the value is 'filter', only selected tunnel types are used to
         resolve routes following TTM preference.

         When the value is 'any', any of the supported tunnel types are
         selected to resolve routes following TTM preference.

         When the value is 'match-family-ip', SR family uses the tunnel types
         selected to resolve corresponding IP family routes except SR-TE
         tunnels.

         When the value is 'disabled' none of the tunnel types are selected."
    DEFVAL      { disabled }
    ::= { tmnxIsisIgpSCTunnNextHopEntry 3 }

tmnxIsisIgpSCTNHResFilterRsvp    OBJECT-TYPE
    SYNTAX      TruthValue
    MAX-ACCESS  read-create
    STATUS      current
    DESCRIPTION
        "The value of tmnxIsisIgpSCTNHResFilterRsvp specifies whether RSVP-TE
         LSPs are allowed to be used for resolving IGP shortcut tunnels
         belonging to a specific family type."
    DEFVAL      { false }
    ::= { tmnxIsisIgpSCTunnNextHopEntry 4 }

tmnxIsisIgpSCTNHResFilterSrTe    OBJECT-TYPE
    SYNTAX      TruthValue
    MAX-ACCESS  read-create
    STATUS      current
    DESCRIPTION
        "The value of tmnxIsisIgpSCTNHResFilterSrTe specifies whether SR-TE
         Ipv4 LSPs are allowed to be used for resolving IGP shortcut tunnels
         belonging to a specific family type."
    DEFVAL      { false }
    ::= { tmnxIsisIgpSCTunnNextHopEntry 5 }

tmnxIsisAdjSetTable              OBJECT-TYPE
    SYNTAX      SEQUENCE OF TmnxIsisAdjSetEntry
    MAX-ACCESS  not-accessible
    STATUS      current
    DESCRIPTION
        "The tmnxIsisAdjSetTable maintains information on Adjacency Sets for
         each instance of IS-IS protocol."
    ::= { tmnxIsisSystemObjs 18 }

tmnxIsisAdjSetEntry              OBJECT-TYPE
    SYNTAX      TmnxIsisAdjSetEntry
    MAX-ACCESS  not-accessible
    STATUS      current
    DESCRIPTION
        "Each row entry in the tmnxIsisAdjSetTable represents information on an
         Adjacency Set configured on the system."
    INDEX       {
        vRtrID,
        isisSysInstance,
        tmnxIsisAdjSetId
    }
    ::= { tmnxIsisAdjSetTable 1 }

TmnxIsisAdjSetEntry              ::= SEQUENCE
{
    tmnxIsisAdjSetId                 Unsigned32,
    tmnxIsisAdjSetRowStatus          RowStatus,
    tmnxIsisAdjSetIdLstCh            TimeStamp,
    tmnxIsisAdjSetFamilyType         TmnxAdjacencySetFamilyType,
    tmnxIsisAdjSetSidType            INTEGER,
    tmnxIsisAdjSetSidValue           Unsigned32,
    tmnxIsisAdjSetParallel           TruthValue,
    tmnxIsisAdjSetAdvertise          TruthValue,
    tmnxIsisAdjSetDynSidValue        Unsigned32,
    tmnxIsisAdjSetTunlDestType       InetAddressType,
    tmnxIsisAdjSetTunlDestIp         InetAddress,
    tmnxIsisAdjSetNeighborSysID      SystemID,
    tmnxIsisAdjSetMembersCount       Unsigned32,
    tmnxIsisAdjSetActiveMembers      Unsigned32,
    tmnxIsisAdjSetUpTime             Integer32,
    tmnxIsisAdjSetStatus             INTEGER,
    tmnxIsisAdjSetMtu                Unsigned32
}

tmnxIsisAdjSetId                 OBJECT-TYPE
    SYNTAX      Unsigned32 (1..4294967295)
    MAX-ACCESS  not-accessible
    STATUS      current
    DESCRIPTION
        "The value of tmnxIsisAdjSetId specifies an identifier for given
         adjacency set."
    ::= { tmnxIsisAdjSetEntry 1 }

tmnxIsisAdjSetRowStatus          OBJECT-TYPE
    SYNTAX      RowStatus
    MAX-ACCESS  read-create
    STATUS      current
    DESCRIPTION
        "The value of the object tmnxIsisAdjSetRowStatus specifies the row
         status used for creation, deletion, or control of tmnxIsisAdjSetTable
         entries."
    ::= { tmnxIsisAdjSetEntry 2 }

tmnxIsisAdjSetIdLstCh            OBJECT-TYPE
    SYNTAX      TimeStamp
    MAX-ACCESS  read-only
    STATUS      current
    DESCRIPTION
        "The value of the object tmnxIsisAdjSetIdLstCh indicates the sysUpTime
         when this row was last modified."
    ::= { tmnxIsisAdjSetEntry 3 }

tmnxIsisAdjSetFamilyType         OBJECT-TYPE
    SYNTAX      TmnxAdjacencySetFamilyType
    MAX-ACCESS  read-create
    STATUS      current
    DESCRIPTION
        "The value of tmnxIsisAdjSetFamilyType specifies the address family for
         the adjacency set."
    DEFVAL      { ipv4 }
    ::= { tmnxIsisAdjSetEntry 4 }

tmnxIsisAdjSetSidType            OBJECT-TYPE
    SYNTAX      INTEGER {
        none  (0),
        label (2)
    }
    MAX-ACCESS  read-create
    STATUS      current
    DESCRIPTION
        "The value of the object tmnxIsisAdjSetSidType specifies whether the
         object tmnxIsisAdjSetSidValue is not valid, an index value or an
         absolute label value."
    DEFVAL      { none }
    ::= { tmnxIsisAdjSetEntry 5 }

tmnxIsisAdjSetSidValue           OBJECT-TYPE
    SYNTAX      Unsigned32
    MAX-ACCESS  read-create
    STATUS      current
    DESCRIPTION
        "The value of the object tmnxIsisAdjSetSidValue together with
         tmnxIsisAdjSetSidType specifies the static adjacency SID value  or
         index to be used for this adjacency-set. "
    DEFVAL      { 0 }
    ::= { tmnxIsisAdjSetEntry 6 }

tmnxIsisAdjSetParallel           OBJECT-TYPE
    SYNTAX      TruthValue
    MAX-ACCESS  read-create
    STATUS      current
    DESCRIPTION
        "The value of tmnxIsisAdjSetParallel specifies whether all links must
         go to the same neighbor."
    DEFVAL      { true }
    ::= { tmnxIsisAdjSetEntry 8 }

tmnxIsisAdjSetAdvertise          OBJECT-TYPE
    SYNTAX      TruthValue
    MAX-ACCESS  read-create
    STATUS      current
    DESCRIPTION
        "The value of tmnxIsisAdjSetAdvertise specifies whether this adjacency
         set should be advertised. Can only be set to true when all links go to
         the same neighbor (parallel=true)."
    DEFVAL      { true }
    ::= { tmnxIsisAdjSetEntry 9 }

tmnxIsisAdjSetDynSidValue        OBJECT-TYPE
    SYNTAX      Unsigned32
    MAX-ACCESS  read-only
    STATUS      current
    DESCRIPTION
        "The value of the object tmnxIsisAdjSetDynSidValue indicates the
         dynamic SID value used for this adjacency-set. In case a static sid is
         configured, the dynamic sid will be 0."
    ::= { tmnxIsisAdjSetEntry 10 }

tmnxIsisAdjSetTunlDestType       OBJECT-TYPE
    SYNTAX      InetAddressType
    MAX-ACCESS  read-only
    STATUS      current
    DESCRIPTION
        "The value of the object tmnxIsisAdjSetTunlDestType indicates the IP
         address type for tmnxIsisAdjSetTunlDestIp."
    ::= { tmnxIsisAdjSetEntry 11 }

tmnxIsisAdjSetTunlDestIp         OBJECT-TYPE
    SYNTAX      InetAddress (SIZE (0|4|16|20))
    MAX-ACCESS  read-only
    STATUS      current
    DESCRIPTION
        "The value of the object tmnxIsisAdjSetTunlDestIp indicates the IP
         address of the adjacency-set tunnel destination.  An adjacency-set
         with links to different neighbors will have  dest@ set to 0.0.0.0."
    ::= { tmnxIsisAdjSetEntry 12 }

tmnxIsisAdjSetNeighborSysID      OBJECT-TYPE
    SYNTAX      SystemID
    MAX-ACCESS  read-only
    STATUS      current
    DESCRIPTION
        "The value of the object tmnxIsisAdjSetNeighborSysID indicates the
         system-id of the node where all links are terminated in case the
         adjacency-set is of type parallel."
    ::= { tmnxIsisAdjSetEntry 13 }

tmnxIsisAdjSetMembersCount       OBJECT-TYPE
    SYNTAX      Unsigned32
    MAX-ACCESS  read-only
    STATUS      current
    DESCRIPTION
        "The value of the object tmnxIsisAdjSetMembersCount indicates the
         number of interfaces that are a member of the adjacency-set."
    ::= { tmnxIsisAdjSetEntry 14 }

tmnxIsisAdjSetActiveMembers      OBJECT-TYPE
    SYNTAX      Unsigned32
    MAX-ACCESS  read-only
    STATUS      current
    DESCRIPTION
        "The value of the object tmnxIsisAdjSetActiveMembers indicates the
         number of active adjacencies that are a member of the adjacency-set."
    ::= { tmnxIsisAdjSetEntry 15 }

tmnxIsisAdjSetUpTime             OBJECT-TYPE
    SYNTAX      Integer32
    MAX-ACCESS  read-only
    STATUS      current
    DESCRIPTION
        "The value of the object tmnxIsisAdjSetUpTime indicates the amount of
         time in seconds since this adjacency-set was last programmed."
    ::= { tmnxIsisAdjSetEntry 16 }

tmnxIsisAdjSetStatus             OBJECT-TYPE
    SYNTAX      INTEGER {
        notActive        (0),
        active           (1),
        activeIncomplete (2),
        fibAddFailed     (3)
    }
    MAX-ACCESS  read-only
    STATUS      current
    DESCRIPTION
        "The value of tmnxIsisAdjSetStatus indicates the reason why an adj-set
         is not active."
    ::= { tmnxIsisAdjSetEntry 17 }

tmnxIsisAdjSetMtu                OBJECT-TYPE
    SYNTAX      Unsigned32
    MAX-ACCESS  read-only
    STATUS      current
    DESCRIPTION
        "The value of tmnxIsisAdjSetMtu indicates the MTU of the adjacency-set
         tunnel. This value takes into account the lowest value of active
         links, the label overhead and the segment routing tunnel-mtu"
    ::= { tmnxIsisAdjSetEntry 18 }

tmnxIsisAdjSetNhopTable          OBJECT-TYPE
    SYNTAX      SEQUENCE OF TmnxIsisAdjSetNhopEntry
    MAX-ACCESS  not-accessible
    STATUS      current
    DESCRIPTION
        "The tmnxIsisAdjSetNhopTable maintains information on Adjacency-Set
         nhop for each instance of IS-IS protocol."
    ::= { tmnxIsisSystemObjs 19 }

tmnxIsisAdjSetNhopEntry          OBJECT-TYPE
    SYNTAX      TmnxIsisAdjSetNhopEntry
    MAX-ACCESS  not-accessible
    STATUS      current
    DESCRIPTION
        "Each row entry in the tmnxIsisAdjSetNhopTable represents information
         on an Adjacency Set configured on the system."
    INDEX       {
        vRtrID,
        isisSysInstance,
        tmnxIsisAdjSetNhopId,
        tmnxIsisAdjSetNhopSysID,
        tmnxIsisAdjSetNhopIfIndex
    }
    ::= { tmnxIsisAdjSetNhopTable 1 }

TmnxIsisAdjSetNhopEntry          ::= SEQUENCE
{
    tmnxIsisAdjSetNhopId             Unsigned32,
    tmnxIsisAdjSetNhopSysID          SystemID,
    tmnxIsisAdjSetNhopIfIndex        InterfaceIndex,
    tmnxIsisAdjSetNhopType           InetAddressType,
    tmnxIsisAdjSetNhop               InetAddress,
    tmnxIsisAdjSetNhopUsage          INTEGER,
    tmnxIsisAdjSetNhopLevel          INTEGER
}

tmnxIsisAdjSetNhopId             OBJECT-TYPE
    SYNTAX      Unsigned32
    MAX-ACCESS  not-accessible
    STATUS      current
    DESCRIPTION
        "The value of tmnxIsisAdjSetNhopId specifies an identifier for given
         adjacency set."
    ::= { tmnxIsisAdjSetNhopEntry 1 }

tmnxIsisAdjSetNhopSysID          OBJECT-TYPE
    SYNTAX      SystemID
    MAX-ACCESS  not-accessible
    STATUS      current
    DESCRIPTION
        "The value of the object tmnxIsisAdjSetNhopSysID specifies the
         system-id of the nexthop and is used to reference the nexthop for this
         adjacency-set link."
    ::= { tmnxIsisAdjSetNhopEntry 2 }

tmnxIsisAdjSetNhopIfIndex        OBJECT-TYPE
    SYNTAX      InterfaceIndex
    MAX-ACCESS  not-accessible
    STATUS      current
    DESCRIPTION
        "The value of the object tmnxIsisAdjSetNhopIfIndex specifies the
         ifIndex of the outgoing interface for the path."
    ::= { tmnxIsisAdjSetNhopEntry 3 }

tmnxIsisAdjSetNhopType           OBJECT-TYPE
    SYNTAX      InetAddressType
    MAX-ACCESS  read-only
    STATUS      current
    DESCRIPTION
        "The value of the object tmnxIsisAdjSetNhopType indicates the IP
         address type for tmnxIsisAdjSetNhop."
    ::= { tmnxIsisAdjSetNhopEntry 4 }

tmnxIsisAdjSetNhop               OBJECT-TYPE
    SYNTAX      InetAddress (SIZE (0|4|16|20))
    MAX-ACCESS  read-only
    STATUS      current
    DESCRIPTION
        "The value of the object tmnxIsisAdjSetNhop indicates the IP address of
         the next hop for this adjacency-set link."
    ::= { tmnxIsisAdjSetNhopEntry 5 }

tmnxIsisAdjSetNhopUsage          OBJECT-TYPE
    SYNTAX      INTEGER {
        undefined  (1),
        level1     (2),
        level2     (3),
        level1and2 (4)
    }
    MAX-ACCESS  read-only
    STATUS      current
    DESCRIPTION
        "The value of the object tmnxIsisAdjSetNhopUsage indicates the
         adjacency-set link type. An adjacency-set link of type level1 is used
         for level 1 traffic  only. An adjacency-set link of type level2 is
         used for level 2  traffic only. An adjacency-set link of type
         level1and2 is used  for both level 1 and level 2 traffic."
    ::= { tmnxIsisAdjSetNhopEntry 6 }

tmnxIsisAdjSetNhopLevel          OBJECT-TYPE
    SYNTAX      INTEGER {
        level1   (1),
        level2   (2),
        level1L2 (3),
        unknown  (4)
    }
    MAX-ACCESS  read-only
    STATUS      current
    DESCRIPTION
        "The value of the object tmnxIsisAdjSetNhopLevel indicates the circuit
         type of the adjacency-set link."
    ::= { tmnxIsisAdjSetNhopEntry 7 }

tmnxIsisRouteNhTable             OBJECT-TYPE
    SYNTAX      SEQUENCE OF TmnxIsisRouteNhEntry
    MAX-ACCESS  not-accessible
    STATUS      current
    DESCRIPTION
        "The tmnxIsisRouteNhTable maintains the routes and nexthops  learned by
         an instance of IS-IS protocol for a specific  multi topology id. This
         table replaces tmnxIsisRouteTable."
    ::= { tmnxIsisSystemObjs 20 }

tmnxIsisRouteNhEntry             OBJECT-TYPE
    SYNTAX      TmnxIsisRouteNhEntry
    MAX-ACCESS  not-accessible
    STATUS      current
    DESCRIPTION
        "Each row entry in the tmnxIsisRouteNhTable stores a route and nexthop
         for a given instance of the IS-IS protocol for a specific multi
         topology id."
    INDEX       {
        vRtrID,
        isisSysInstance,
        tmnxIsisRouteNhMtId,
        tmnxIsisRouteNhDestType,
        tmnxIsisRouteNhDest,
        tmnxIsisRouteNhPrefixLength,
        tmnxIsisRouteNhEcmpIndex
    }
    ::= { tmnxIsisRouteNhTable 1 }

TmnxIsisRouteNhEntry             ::= SEQUENCE
{
    tmnxIsisRouteNhMtId              Unsigned32,
    tmnxIsisRouteNhDestType          InetAddressType,
    tmnxIsisRouteNhDest              InetAddress,
    tmnxIsisRouteNhPrefixLength      InetAddressPrefixLength,
    tmnxIsisRouteNhEcmpIndex         Unsigned32,
    tmnxIsisRouteNhIPType            InetAddressType,
    tmnxIsisRouteNhIP                InetAddress,
    tmnxIsisRouteNhLevel             INTEGER,
    tmnxIsisRouteNhSpfRunNumber      Counter32,
    tmnxIsisRouteNhMetric            Unsigned32,
    tmnxIsisRouteNhType              INTEGER,
    tmnxIsisRouteNhSysID             SystemID,
    tmnxIsisRouteNhTag               Unsigned32,
    tmnxIsisRouteNhBkupFlags         INTEGER,
    tmnxIsisRouteNhBkupType          INTEGER,
    tmnxIsisRouteNhBkupIpType        InetAddressType,
    tmnxIsisRouteNhBkupIP            InetAddress,
    tmnxIsisRouteNhBkupMetric        Unsigned32,
    tmnxIsisRouteNhCidrType          TmnxInetCidrNextHopType,
    tmnxIsisRouteNhOwner             TmnxInetCidrNextHopOwner,
    tmnxIsisRouteNhOwnerAuxInfo      Unsigned32,
    tmnxIsisRouteNhBkupCidrType      TmnxInetCidrNextHopType,
    tmnxIsisRouteNhBkupOwner         TmnxInetCidrNextHopOwner,
    tmnxIsisRouteNhBkupOwnerAuxInfo  Unsigned32,
    tmnxIsisRouteNhSidFlags          TmnxIsisPrefixSidFlags,
    tmnxIsisRouteNhSidValue          Unsigned32,
    tmnxIsisRouteNhRouteStatus       INTEGER,
    tmnxIsisRouteNhNhopStatus        INTEGER,
    tmnxIsisRouteNhAlgorithm         TmnxAlgorithmId
}

tmnxIsisRouteNhMtId              OBJECT-TYPE
    SYNTAX      Unsigned32
    MAX-ACCESS  not-accessible
    STATUS      current
    DESCRIPTION
        "The value of the object tmnxIsisRouteNhMtId specifies the multi
         topology id number for this route.

         If multi-topology is not supported for the route then the value of
         tmnxIsisRouteNhMtId should be 0."
    ::= { tmnxIsisRouteNhEntry 1 }

tmnxIsisRouteNhDestType          OBJECT-TYPE
    SYNTAX      InetAddressType
    MAX-ACCESS  not-accessible
    STATUS      current
    DESCRIPTION
        "The value of the object tmnxIsisRouteNhDestType specifies the IP
         address type for tmnxIsisRouteNhDest."
    ::= { tmnxIsisRouteNhEntry 2 }

tmnxIsisRouteNhDest              OBJECT-TYPE
    SYNTAX      InetAddress (SIZE (4|16|20))
    MAX-ACCESS  not-accessible
    STATUS      current
    DESCRIPTION
        "The value of the object tmnxIsisRouteNhDest specifies the destination
         IP address of this route.

         The address type of tmnxIsisRouteNhDest is indicated by
         tmnxIsisRouteNhDestType."
    ::= { tmnxIsisRouteNhEntry 3 }

tmnxIsisRouteNhPrefixLength      OBJECT-TYPE
    SYNTAX      InetAddressPrefixLength
    MAX-ACCESS  not-accessible
    STATUS      current
    DESCRIPTION
        "The value of the object tmnxIsisRouteNhPrefixLength specifies the
         prefix length to be used with tmnxIsisRouteNhDest to get the network
         prefix."
    ::= { tmnxIsisRouteNhEntry 4 }

tmnxIsisRouteNhEcmpIndex         OBJECT-TYPE
    SYNTAX      Unsigned32
    MAX-ACCESS  not-accessible
    STATUS      current
    DESCRIPTION
        "The value of the object tmnxIsisRouteNhEcmpIndex specifies the ecmp
         index of this nexthop entry."
    ::= { tmnxIsisRouteNhEntry 5 }

tmnxIsisRouteNhIPType            OBJECT-TYPE
    SYNTAX      InetAddressType
    MAX-ACCESS  read-only
    STATUS      current
    DESCRIPTION
        "The value of the object tmnxIsisRouteNhIPType indicates the IP address
         type for tmnxIsisRouteNhIP."
    ::= { tmnxIsisRouteNhEntry 6 }

tmnxIsisRouteNhIP                OBJECT-TYPE
    SYNTAX      InetAddress (SIZE (4|16|20))
    MAX-ACCESS  read-only
    STATUS      current
    DESCRIPTION
        "The value of the object tmnxIsisRouteNhIP indicates the IP address of
         the nexthop for this route.

         The address type of tmnxIsisRouteNhIP is indicated by
         tmnxIsisRouteNhIPType"
    ::= { tmnxIsisRouteNhEntry 7 }

tmnxIsisRouteNhLevel             OBJECT-TYPE
    SYNTAX      INTEGER {
        level1IS (1),
        level2IS (2)
    }
    MAX-ACCESS  read-only
    STATUS      current
    DESCRIPTION
        "The value of the object tmnxIsisRouteNhLevel indicates the IS-IS Level
         at which the prefix was learned."
    ::= { tmnxIsisRouteNhEntry 8 }

tmnxIsisRouteNhSpfRunNumber      OBJECT-TYPE
    SYNTAX      Counter32
    MAX-ACCESS  read-only
    STATUS      current
    DESCRIPTION
        "The value of the object tmnxIsisRouteNhSpfRunNumber indicates the run
         of spf calculation in which this route was selected."
    ::= { tmnxIsisRouteNhEntry 9 }

tmnxIsisRouteNhMetric            OBJECT-TYPE
    SYNTAX      Unsigned32
    MAX-ACCESS  read-only
    STATUS      current
    DESCRIPTION
        "The value of the object tmnxIsisRouteNhMetric indicates the metric
         value associated with the route.

         This metric is obtained by the SPF calculations and is used by the
         instance of the protocol.

         For a given destination prefix, the route with the lower metric is the
         shorter route.

         A metric value in the range from 4261412865 to 4294967294 (0xFE000001
         to 0xFFFFFFFE) indicates an unreachable route."
    ::= { tmnxIsisRouteNhEntry 10 }

tmnxIsisRouteNhType              OBJECT-TYPE
    SYNTAX      INTEGER {
        internal (1),
        external (2)
    }
    MAX-ACCESS  read-only
    STATUS      current
    DESCRIPTION
        "The value of the object tmnxIsisRouteNhType indicates the type of
         route represented by this row entry."
    ::= { tmnxIsisRouteNhEntry 11 }

tmnxIsisRouteNhSysID             OBJECT-TYPE
    SYNTAX      SystemID
    MAX-ACCESS  read-only
    STATUS      current
    DESCRIPTION
        "The value of the object tmnxIsisRouteNhSysID indicates the system-id
         of the nexthop IS through which this route is reachable."
    ::= { tmnxIsisRouteNhEntry 12 }

tmnxIsisRouteNhTag               OBJECT-TYPE
    SYNTAX      Unsigned32
    MAX-ACCESS  read-only
    STATUS      current
    DESCRIPTION
        "The value of the object tmnxIsisRouteNhTag indicates a 32-bit integer
         route tag for this route.

         A value of 0 indicates that the tag has not been set."
    ::= { tmnxIsisRouteNhEntry 13 }

tmnxIsisRouteNhBkupFlags         OBJECT-TYPE
    SYNTAX      INTEGER {
        none   (0),
        hasLfa (1)
    }
    MAX-ACCESS  read-only
    STATUS      current
    DESCRIPTION
        "The value of the object tmnxIsisRouteNhBkupFlags indicates the
         presence or absence of LFA next-hops.

         The value 'none'  indicates that no next-hop is present;
         the value 'hasLfa' indicates that an LFA next-hop is present in addition
         to the regular next-hop."
    ::= { tmnxIsisRouteNhEntry 14 }

tmnxIsisRouteNhBkupType          OBJECT-TYPE
    SYNTAX      INTEGER {
        notApplicable  (0),
        nodeProtection (1),
        linkProtection (2)
    }
    MAX-ACCESS  read-only
    STATUS      current
    DESCRIPTION
        "The value of the object tmnxIsisRouteNhBkupType indicates the type of
         protection used by the backup next-hop.

         The value 'notApplicable' indicates that the backup next-hop type is
         not applicable; the value 'nodeProtection' indicates that the backup
         next-hop uses a node-protection mechanism; the value 'linkProtection'
         indicates that the backup next-hop uses link-protection mechanism."
    ::= { tmnxIsisRouteNhEntry 15 }

tmnxIsisRouteNhBkupIpType        OBJECT-TYPE
    SYNTAX      InetAddressType
    MAX-ACCESS  read-only
    STATUS      current
    DESCRIPTION
        "The value of the object tmnxIsisRouteNhBkupIpType indicates the IP
         address type for tmnxIsisRouteNhBkupIP."
    ::= { tmnxIsisRouteNhEntry 16 }

tmnxIsisRouteNhBkupIP            OBJECT-TYPE
    SYNTAX      InetAddress (SIZE (0|4|16|20))
    MAX-ACCESS  read-only
    STATUS      current
    DESCRIPTION
        "The value of the object tmnxIsisRouteNhBkupIP indicates the IP address
         of a backup next-hop.

         The value of tmnxIsisRouteNhBkupIP is only valid when
         tmnxIsisRouteNhBkupFlags has a value of 'hasLfa'.

         The address type of tmnxIsisRouteNhBkupIP is indicated by the value of
         tmnxIsisRouteNhBkupIpType."
    ::= { tmnxIsisRouteNhEntry 17 }

tmnxIsisRouteNhBkupMetric        OBJECT-TYPE
    SYNTAX      Unsigned32
    MAX-ACCESS  read-only
    STATUS      current
    DESCRIPTION
        "The value of the object tmnxIsisRouteNhBkupMetric indicates the
         routing metric for a backup route.

         The semantics of this metric are determined by the routing-protocol
         specified in the route's ipCidrRouteProto value.

         The value of tmnxIsisRouteNhBkupMetric is only valid when
         tmnxIsisRouteNhBkupFlags has a value of 'hasLfa'."
    ::= { tmnxIsisRouteNhEntry 18 }

tmnxIsisRouteNhCidrType          OBJECT-TYPE
    SYNTAX      TmnxInetCidrNextHopType
    MAX-ACCESS  read-only
    STATUS      current
    DESCRIPTION
        "The value of the object tmnxIsisRouteNhCidrType indicates the type of
         next hop for this route."
    ::= { tmnxIsisRouteNhEntry 19 }

tmnxIsisRouteNhOwner             OBJECT-TYPE
    SYNTAX      TmnxInetCidrNextHopOwner
    MAX-ACCESS  read-only
    STATUS      current
    DESCRIPTION
        "The value of the object tmnxIsisRouteNhOwner indicates the owner of
         next hop for this route."
    ::= { tmnxIsisRouteNhEntry 20 }

tmnxIsisRouteNhOwnerAuxInfo      OBJECT-TYPE
    SYNTAX      Unsigned32
    MAX-ACCESS  read-only
    STATUS      current
    DESCRIPTION
        "The value of the object tmnxIsisRouteNhOwnerAuxInfo indicates the
         auxiliary information for next hop owner as indicated by
         tmnxIsisRouteNhOwner.

         The value of tmnxIsisRouteNhOwnerAuxInfo indicates the tunnel id
         existing for this next hop type and owner."
    ::= { tmnxIsisRouteNhEntry 21 }

tmnxIsisRouteNhBkupCidrType      OBJECT-TYPE
    SYNTAX      TmnxInetCidrNextHopType
    MAX-ACCESS  read-only
    STATUS      current
    DESCRIPTION
        "The value of the object tmnxIsisRouteNhBkupCidrType indicates the type
         of next hop for this backup route."
    ::= { tmnxIsisRouteNhEntry 22 }

tmnxIsisRouteNhBkupOwner         OBJECT-TYPE
    SYNTAX      TmnxInetCidrNextHopOwner
    MAX-ACCESS  read-only
    STATUS      current
    DESCRIPTION
        "The value of the object tmnxIsisRouteNhBkupOwner indicates the owner
         of next hop for this backup route."
    ::= { tmnxIsisRouteNhEntry 23 }

tmnxIsisRouteNhBkupOwnerAuxInfo  OBJECT-TYPE
    SYNTAX      Unsigned32
    MAX-ACCESS  read-only
    STATUS      current
    DESCRIPTION
        "The value of the object tmnxIsisRouteNhBkupOwnerAuxInfo indicates the
         auxiliary information, for next hop owner as indicated by
         tmnxIsisRouteNhBkupOwner.

         The value of tmnxIsisRouteNhBkupOwnerAuxInfo indicates the tunnel id
         existing for this backup next hop type and owner."
    ::= { tmnxIsisRouteNhEntry 24 }

tmnxIsisRouteNhSidFlags          OBJECT-TYPE
    SYNTAX      TmnxIsisPrefixSidFlags
    MAX-ACCESS  read-only
    STATUS      current
    DESCRIPTION
        "The value of the object tmnxIsisRouteNhSidFlags indicates the flags of
         a Prefix-SID as defined by IETF segment routing.

         If bitUsed(0) is set, tmnxIsisRouteNhSidValue is valid."
    ::= { tmnxIsisRouteNhEntry 25 }

tmnxIsisRouteNhSidValue          OBJECT-TYPE
    SYNTAX      Unsigned32
    MAX-ACCESS  read-only
    STATUS      current
    DESCRIPTION
        "The value of the object tmnxIsisRouteNhSidValue indicates the SID
         label or index for this prefix."
    ::= { tmnxIsisRouteNhEntry 26 }

tmnxIsisRouteNhRouteStatus       OBJECT-TYPE
    SYNTAX      INTEGER {
        active       (0),
        rtmAddFailed (1),
        fibAddFailed (2),
        unreachable  (3)
    }
    MAX-ACCESS  read-only
    STATUS      current
    DESCRIPTION
        "The value of tmnxIsisRouteNhRouteStatus indicates the reason why a
         route is not active."
    ::= { tmnxIsisRouteNhEntry 27 }

tmnxIsisRouteNhNhopStatus        OBJECT-TYPE
    SYNTAX      INTEGER {
        success   (0),
        discarded (1)
    }
    MAX-ACCESS  read-only
    STATUS      current
    DESCRIPTION
        "Indicates the next hop status in RTM"
    ::= { tmnxIsisRouteNhEntry 28 }

tmnxIsisRouteNhAlgorithm         OBJECT-TYPE
    SYNTAX      TmnxAlgorithmId
    MAX-ACCESS  read-only
    STATUS      current
    DESCRIPTION
        "The value of the object tmnxIsisRouteNhAlgorithm indicates the
         algorithm.

         The value can indicate a defined IGP Algorithm (value 0 is SPF) or a
         Flexible Algorithm (range 128..255)."
    ::= { tmnxIsisRouteNhEntry 29 }

tmnxIsisSidStatsTable            OBJECT-TYPE
    SYNTAX      SEQUENCE OF TmnxIsisSidStatsEntry
    MAX-ACCESS  not-accessible
    STATUS      current
    DESCRIPTION
        "The tmnxIsisSidStatsTable provides statistics for each IS-IS  Segment
         Identifier (SID) on ingress and egress and per SID type."
    ::= { tmnxIsisSystemObjs 21 }

tmnxIsisSidStatsEntry            OBJECT-TYPE
    SYNTAX      TmnxIsisSidStatsEntry
    MAX-ACCESS  not-accessible
    STATUS      current
    DESCRIPTION
        "Each row entry in the tmnxIsisSidStatsEntry stores statistics for an
         IS-IS SID."
    INDEX       {
        vRtrID,
        isisSysInstance,
        tmnxIsisSidStatsSid
    }
    ::= { tmnxIsisSidStatsTable 1 }

TmnxIsisSidStatsEntry            ::= SEQUENCE
{
    tmnxIsisSidStatsSid              Unsigned32,
    tmnxIsisSidStatsSidType          INTEGER,
    tmnxIsisSidStatsPrefixType       InetAddressType,
    tmnxIsisSidStatsPrefix           InetAddress,
    tmnxIsisSidStatsPrefixLength     InetAddressPrefixLength,
    tmnxIsisSidStatsIfIndex          InterfaceIndexOrZero,
    tmnxIsisSidStatsAdjSet           Unsigned32,
    tmnxIsisSidStatsIngressOperState INTEGER,
    tmnxIsisSidStatsIngressOctets    Counter64,
    tmnxIsisSidStatsIngressPackets   Counter64,
    tmnxIsisSidStatsEgressOperState  INTEGER,
    tmnxIsisSidStatsEgressOctets     Counter64,
    tmnxIsisSidStatsEgressPackets    Counter64,
    tmnxIsisSidStatsAlgorithm        TmnxAlgorithmId
}

tmnxIsisSidStatsSid              OBJECT-TYPE
    SYNTAX      Unsigned32
    MAX-ACCESS  not-accessible
    STATUS      current
    DESCRIPTION
        "The value of the object tmnxIsisSidStatsSid specifies the SID for
         which statistics are collected."
    ::= { tmnxIsisSidStatsEntry 1 }

tmnxIsisSidStatsSidType          OBJECT-TYPE
    SYNTAX      INTEGER {
        node         (0),
        adjacency    (1),
        adjacencySet (2)
    }
    MAX-ACCESS  read-only
    STATUS      current
    DESCRIPTION
        "The value of the object tmnxIsisSidStatsSidType indicates the type of
         SID for which statistics are collected."
    ::= { tmnxIsisSidStatsEntry 2 }

tmnxIsisSidStatsPrefixType       OBJECT-TYPE
    SYNTAX      InetAddressType
    MAX-ACCESS  read-only
    STATUS      current
    DESCRIPTION
        "The value of the object tmnxIsisSidStatsPrefixType indicates the IP
         address type of tmnxIsisSidStatsPrefix."
    ::= { tmnxIsisSidStatsEntry 3 }

tmnxIsisSidStatsPrefix           OBJECT-TYPE
    SYNTAX      InetAddress (SIZE (0|4|16))
    MAX-ACCESS  read-only
    STATUS      current
    DESCRIPTION
        "The value of the object tmnxIsisSidStatsPrefix indicates the IP
         address of the prefix for which SID statistics are collected."
    ::= { tmnxIsisSidStatsEntry 4 }

tmnxIsisSidStatsPrefixLength     OBJECT-TYPE
    SYNTAX      InetAddressPrefixLength
    MAX-ACCESS  read-only
    STATUS      current
    DESCRIPTION
        "The value of the object tmnxIsisSidStatsPrefixLength indicates the
         prefix length to be used with tmnxIsisSidStatsPrefix to get the SID
         prefix."
    ::= { tmnxIsisSidStatsEntry 5 }

tmnxIsisSidStatsIfIndex          OBJECT-TYPE
    SYNTAX      InterfaceIndexOrZero
    MAX-ACCESS  read-only
    STATUS      current
    DESCRIPTION
        "The value of the object tmnxIsisSidStatsIfIndex specifies the
         Interface Index on which the adjacency that uses this SID is
         established in case the object tmnxIsisSidStatsSidType is 'adjacency'.
         The value of this object contains '0' in case the object
         tmnxIsisSidStatsSidType is different from 'adjacency'."
    ::= { tmnxIsisSidStatsEntry 6 }

tmnxIsisSidStatsAdjSet           OBJECT-TYPE
    SYNTAX      Unsigned32 (0..4294967295)
    MAX-ACCESS  read-only
    STATUS      current
    DESCRIPTION
        "The value of the object tmnxIsisSidStatsAdjSet specifies the Adjacency
         Set Identifier in case the object tmnxIsisSidStatsSidType is
         'adjacencySet'.

         The value of this object contains '0' in case the object
         tmnxIsisSidStatsSidType is different from 'adjacencySet'."
    ::= { tmnxIsisSidStatsEntry 7 }

tmnxIsisSidStatsIngressOperState OBJECT-TYPE
    SYNTAX      INTEGER {
        enabled    (1),
        disabled   (2),
        noResource (3)
    }
    MAX-ACCESS  read-only
    STATUS      current
    DESCRIPTION
        "The value of the object tmnxIsisSidStatsIngressOperState indicates the
         operating state of this SID on ingress direction."
    ::= { tmnxIsisSidStatsEntry 8 }

tmnxIsisSidStatsIngressOctets    OBJECT-TYPE
    SYNTAX      Counter64
    MAX-ACCESS  read-only
    STATUS      current
    DESCRIPTION
        "The value of the object tmnxIsisSidStatsIngressOctets indicates the
         number of ingress octets."
    ::= { tmnxIsisSidStatsEntry 9 }

tmnxIsisSidStatsIngressPackets   OBJECT-TYPE
    SYNTAX      Counter64
    MAX-ACCESS  read-only
    STATUS      current
    DESCRIPTION
        "The value of the object tmnxIsisSidStatsIngressPackets indicates the
         number of ingress packets."
    ::= { tmnxIsisSidStatsEntry 10 }

tmnxIsisSidStatsEgressOperState  OBJECT-TYPE
    SYNTAX      INTEGER {
        enabled    (1),
        disabled   (2),
        noResource (3)
    }
    MAX-ACCESS  read-only
    STATUS      current
    DESCRIPTION
        "The value of the object tmnxIsisSidStatsEgressOperState indicates the
         operating state of this SID on egress direction."
    ::= { tmnxIsisSidStatsEntry 11 }

tmnxIsisSidStatsEgressOctets     OBJECT-TYPE
    SYNTAX      Counter64
    MAX-ACCESS  read-only
    STATUS      current
    DESCRIPTION
        "The value of the object tmnxIsisSidStatsEgressOctets indicates the
         number of ingress octets."
    ::= { tmnxIsisSidStatsEntry 12 }

tmnxIsisSidStatsEgressPackets    OBJECT-TYPE
    SYNTAX      Counter64
    MAX-ACCESS  read-only
    STATUS      current
    DESCRIPTION
        "The value of the object tmnxIsisSidStatsEgressPackets indicates the
         number of ingress packets."
    ::= { tmnxIsisSidStatsEntry 13 }

tmnxIsisSidStatsAlgorithm        OBJECT-TYPE
    SYNTAX      TmnxAlgorithmId
    MAX-ACCESS  read-only
    STATUS      current
    DESCRIPTION
        "The value of the object tmnxIsisSidStatsAlgorithm indicates the
         algorithm related to the prefix SID.

         The value can indicate a defined IGP Algorithm (value 0 is SPF) or a
         Flexible Algorithm (range 128..255)."
    ::= { tmnxIsisSidStatsEntry 14 }

tmnxIsisSegmentRoutingTable      OBJECT-TYPE
    SYNTAX      SEQUENCE OF TmnxIsisSegmentRoutingEntry
    MAX-ACCESS  not-accessible
    STATUS      current
    DESCRIPTION
        "The tmnxIsisSegmentRoutingTable provides an extension of the
         tmnxIsisTable for Segment Routing."
    ::= { tmnxIsisSystemObjs 22 }

tmnxIsisSegmentRoutingEntry      OBJECT-TYPE
    SYNTAX      TmnxIsisSegmentRoutingEntry
    MAX-ACCESS  not-accessible
    STATUS      current
    DESCRIPTION
        "Each row entry in tmnxIsisSegmentRoutingTable represents additional
         columns for an ISIS instance."
    AUGMENTS    { tmnxIsisEntry }
    ::= { tmnxIsisSegmentRoutingTable 1 }

TmnxIsisSegmentRoutingEntry      ::= SEQUENCE
{
    tmnxIsisSrLastChanged            TimeStamp,
    tmnxIsisSrMsdOverrideBmi         Integer32,
    tmnxIsisSrMsdOverrideErld        Integer32,
    tmnxIsisSrAdjSidAllocDualSids    TruthValue,
    tmnxIsisSrMultiTopologyMt2       TruthValue
}

tmnxIsisSrLastChanged            OBJECT-TYPE
    SYNTAX      TimeStamp
    MAX-ACCESS  read-only
    STATUS      current
    DESCRIPTION
        "The value of tmnxIsisSrLastChanged indicates the sysUpTime when a
         configurable object in this row was last modified."
    ::= { tmnxIsisSegmentRoutingEntry 1 }

tmnxIsisSrMsdOverrideBmi         OBJECT-TYPE
    SYNTAX      Integer32 (-1 | 0..12)
    MAX-ACCESS  read-write
    STATUS      current
    DESCRIPTION
        "The value of tmnxIsisSrMsdOverrideBmi specifies the override Base MPLS
         Imposition (BMI) Maximum Sid Depth (MSD) value that will be announced
         when Segment Routing is enabled.

         The value '-1' indicates that the default MSD value will be used. The
         default MSD value announced is the maximum value the platform supports
         under ideal conditions.

         The supported override range depends on the platform."
    DEFVAL      { -1 }
    ::= { tmnxIsisSegmentRoutingEntry 2 }

tmnxIsisSrMsdOverrideErld        OBJECT-TYPE
    SYNTAX      Integer32 (-1 | 0..15)
    MAX-ACCESS  read-write
    STATUS      current
    DESCRIPTION
        "The value of tmnxIsisSrMsdOverrideErld specifies the override Entropy
         Readable Label Depth (ERLD) Maximum Sid Depth (MSD) value  that will
         be announced when Segment Routing is enabled.

         The value '-1' indicates that the default MSD value will be used. The
         default MSD value announced is the maximum value the platform supports
         under ideal conditions.

         The supported override range depends on the platform."
    DEFVAL      { -1 }
    ::= { tmnxIsisSegmentRoutingEntry 3 }

tmnxIsisSrAdjSidAllocDualSids    OBJECT-TYPE
    SYNTAX      TruthValue
    MAX-ACCESS  read-write
    STATUS      current
    DESCRIPTION
        "The value of tmnxIsisSrAdjSidAllocDualSids specifies whether
         instantiating and advertising dual adjacency SIDs per interface is
         enabled or not.

         If the value is 'true', SR-ISIS will support two adjacency SIDs per
         interface, a protected and unprotected adjacency SID. SR-ISIS will
         instantiate an additional adjacency SID to complement the original
         interface adjacency SID.

         If the value of object tmnxIsisIfSidProtection is disabled on an
         interface, no additional adjacency SID will be instantiated for that
         interface."
    DEFVAL      { false }
    ::= { tmnxIsisSegmentRoutingEntry 4 }

tmnxIsisSrMultiTopologyMt2       OBJECT-TYPE
    SYNTAX      TruthValue
    MAX-ACCESS  read-write
    STATUS      current
    DESCRIPTION
        "The value of tmnxIsisSrMultiTopologyMt2 specifies whether Segment
         Routing is enabled for IPv6 routing topology (mt2).

         If the value is 'false', no MT2 Segment Routing is enabled and ISIS
         will not program sr-mpls tunnels for MT2 ipv6 routes.

         If the value is 'true', ISIS will program sr-mpls tunnels for MT2 ipv6
         routes.

         ISIS can only program MT2 sr-mpls tunnels when MT2 ipv6 routes are
         available, i.e. if tmnxIsisMultiTopology and
         tmnxIsisMultiTopoIPv6Ucast are configured."
    DEFVAL      { false }
    ::= { tmnxIsisSegmentRoutingEntry 5 }

tmnxIsisGeneralTable             OBJECT-TYPE
    SYNTAX      SEQUENCE OF TmnxIsisGeneralEntry
    MAX-ACCESS  not-accessible
    STATUS      current
    DESCRIPTION
        "The tmnxIsisGeneralTable provides an extension of the tmnxIsisTable."
    ::= { tmnxIsisSystemObjs 23 }

tmnxIsisGeneralEntry             OBJECT-TYPE
    SYNTAX      TmnxIsisGeneralEntry
    MAX-ACCESS  not-accessible
    STATUS      current
    DESCRIPTION
        "Each row entry in tmnxIsisGeneralTable represents additional columns
         for an ISIS instance.

         The system automatically creates and destroys rows in this table when
         rows in the tmnxIsisTable are created and destroyed."
    AUGMENTS    { tmnxIsisEntry }
    ::= { tmnxIsisGeneralTable 1 }

TmnxIsisGeneralEntry             ::= SEQUENCE
{
    tmnxIsisGeneralLastChanged       TimeStamp,
    tmnxIsisFlexAlgosAdminState      TmnxAdminState,
    tmnxIsisMruMismatchDetection     TruthValue,
    tmnxIsisTeAdvertiseDelay         TruthValue,
    tmnxIsisMultiHomedPrefixLfa      TruthValue,
    tmnxIsisMhpLfaPreference         INTEGER,
    tmnxIsisFaAdvertiseAdminGroup    INTEGER,
    tmnxIsisCsnpOnP2p                TruthValue,
    tmnxIsisOverloadFibErrNotifyOnly TruthValue,
    tmnxIsisOverloadIncludeLocators  TruthValue,
    tmnxIsisOverloadFibErrRetryTime  Unsigned32,
    tmnxIsisUpaLifetime              Unsigned32,
    tmnxIsisUpaMetric                Unsigned32,
    tmnxIsisMaximumNumberUpas        Unsigned32,
    tmnxIsisProcessReceivedUpa       TruthValue,
    tmnxIsisDbExportReachableLsOnly  TruthValue
}

tmnxIsisGeneralLastChanged       OBJECT-TYPE
    SYNTAX      TimeStamp
    MAX-ACCESS  read-only
    STATUS      current
    DESCRIPTION
        "The value of tmnxIsisGeneralLastChanged indicates the sysUpTime when a
         configurable object in this row was last modified."
    ::= { tmnxIsisGeneralEntry 1 }

tmnxIsisFlexAlgosAdminState      OBJECT-TYPE
    SYNTAX      TmnxAdminState
    MAX-ACCESS  read-write
    STATUS      current
    DESCRIPTION
        "The value of tmnxIsisFlexAlgosAdminState specifies the
         administrative state of all Flexible Algorithm processing
         for this ISIS instance."
    DEFVAL      { outOfService }
    ::= { tmnxIsisGeneralEntry 2 }

tmnxIsisMruMismatchDetection     OBJECT-TYPE
    SYNTAX      TruthValue
    MAX-ACCESS  read-write
    STATUS      current
    DESCRIPTION
        "The value of the object tmnxIsisMruMismatchDetection specifies whether
         Maximum Receive Unit (MRU) mismatch must be detected.

         When the value is 'true', the router drops IIH Hello-packets exceeding
         interface MRU size."
    DEFVAL      { false }
    ::= { tmnxIsisGeneralEntry 3 }

tmnxIsisTeAdvertiseDelay         OBJECT-TYPE
    SYNTAX      TruthValue
    MAX-ACCESS  read-write
    STATUS      current
    DESCRIPTION
        "The value of tmnxIsisTeAdvertiseDelay specifies whether advertising
         the interface delay is enabled or not.

         If the value is 'true', the ISIS instance will advertise the interface
         delay in legacy attributes, or in  Application Specific Link
         Attributes (ASLA) when enabled for SR-TE and/or RSVP-TE application.

         The value of tmnxIsisTeAdvertiseDelay is only valid when the object
         tmnxIsisTrafficEng has the value 'true'."
    DEFVAL      { false }
    ::= { tmnxIsisGeneralEntry 4 }

tmnxIsisMultiHomedPrefixLfa      OBJECT-TYPE
    SYNTAX      TruthValue
    MAX-ACCESS  read-write
    STATUS      current
    DESCRIPTION
        "The value of the object tmnxIsisMultiHomedPrefixLfa specifies whether
         multi-homed prefix (MHP) loopfree-alternate (LFA) is enabled or not.

         The value of tmnxIsisMultiHomedPrefixLfa is only valid when the
         object tmnxIsisLoopfreeAlternate has the value 'true'."
    DEFVAL      { false }
    ::= { tmnxIsisGeneralEntry 5 }

tmnxIsisMhpLfaPreference         OBJECT-TYPE
    SYNTAX      INTEGER {
        none (0),
        all  (1)
    }
    MAX-ACCESS  read-write
    STATUS      current
    DESCRIPTION
        "The value of the object tmnxIsisMhpLfaPreference specifies the backup
         preference of a multi-homed prefix (MHP).

         If the value is 'none(0)', a LFA/TI-LFA backup path is preferred over
         a backup via an alternate router that is advertising the same mhp.

         The value of tmnxIsisMhpLfaPreference is only valid when the objects
         tmnxIsisLoopfreeAlternate and tmnxIsisMultiHomedPrefixLfa both have
         the value 'true'."
    DEFVAL      { none }
    ::= { tmnxIsisGeneralEntry 6 }

tmnxIsisFaAdvertiseAdminGroup    OBJECT-TYPE
    SYNTAX      INTEGER {
        preferAg (1),
        eagOnly  (2),
        agEag    (3)
    }
    MAX-ACCESS  read-write
    STATUS      current
    DESCRIPTION
        "The value of the object tmnxIsisFaAdvertiseAdminGroup specifies
         whether Admin Group (AG) TLV, Extended Admin Group (EAG) TLV or both
         must be advertised.

         If the value is 'preferAg', an AG tlv will be advertised representing
         all  admin-group affinity bits set in range [0..31]. If an admin-group
         from the extended range [32..255] is used then a second EAG TLV will
         be advertised representing all admin-group affinity bits set in range
         [0..255].

         If the value is 'eagOnly', only an EAG TLV will be advertised.

         If the value is 'agEag', both AG and EAG TLV's will be advertised even
         if there is no affinity bit set in the extended EAG range."
    DEFVAL      { preferAg }
    ::= { tmnxIsisGeneralEntry 7 }

tmnxIsisCsnpOnP2p                OBJECT-TYPE
    SYNTAX      TruthValue
    MAX-ACCESS  read-write
    STATUS      current
    DESCRIPTION
        "The value of the object tmnxIsisCsnpOnP2p specifies whether sending
         periodic CSNP packets on ISIS P2P interfaces is enabled or not."
    DEFVAL      { true }
    ::= { tmnxIsisGeneralEntry 8 }

tmnxIsisOverloadFibErrNotifyOnly OBJECT-TYPE
    SYNTAX      TruthValue
    MAX-ACCESS  read-write
    STATUS      current
    DESCRIPTION
        "The value of the object tmnxIsisOverloadFibErrNotifyOnly specifies
         whether to originate only a notification when an overload condition
         occurs when programming the FIB, instead of advertising its overload
         condition in the ISIS LSP."
    DEFVAL      { false }
    ::= { tmnxIsisGeneralEntry 9 }

tmnxIsisOverloadIncludeLocators  OBJECT-TYPE
    SYNTAX      TruthValue
    MAX-ACCESS  read-write
    STATUS      current
    DESCRIPTION
        "The value of tmnxIsisOverloadIncludeLocators specifies  whether to
         advertise SRv6 Locators with max-metric when the system goes into
         overload state."
    DEFVAL      { false }
    ::= { tmnxIsisGeneralEntry 10 }

tmnxIsisOverloadFibErrRetryTime  OBJECT-TYPE
    SYNTAX      Unsigned32 (10..1800)
    UNITS       "seconds"
    MAX-ACCESS  read-write
    STATUS      current
    DESCRIPTION
        "The value of the object tmnxIsisOverloadFibErrRetryTime specifies  the
         time, in seconds, that this router must use to retry programming the
         failed entries in the FIB, when tmnxIsisOverloadFibErrNotifyOnly is
         set to 'true'.

         This tmnxIsisOverloadFibErrRetryTime value, is only used if
         tmnxIsisOverloadFibErrNotifyOnly is 'true'. If
         tmnxIsisOverloadFibErrNotifyOnly is 'false', we will immediately try
         to program the failed entries in the FIB, by triggering an immediate
         SPF."
    DEFVAL      { 10 }
    ::= { tmnxIsisGeneralEntry 11 }

tmnxIsisUpaLifetime              OBJECT-TYPE
    SYNTAX      Unsigned32 (30..1800)
    UNITS       "seconds"
    MAX-ACCESS  read-write
    STATUS      current
    DESCRIPTION
        "The value of the object tmnxIsisUpaLifetime specifies  the amount of
         time in seconds during which an UPA is  advertised after the prefix
         becomes unreachable."
    DEFVAL      { 180 }
    ::= { tmnxIsisGeneralEntry 12 }

tmnxIsisUpaMetric                OBJECT-TYPE
    SYNTAX      Unsigned32 (4261412865..4294967294)
    MAX-ACCESS  read-write
    STATUS      current
    DESCRIPTION
        "The value of the object tmnxIsisUpaMetric specifies  the metric used
         when advertising an UPA.

         The metric value ranges from 4261412865 to 4294967294 (0xFE000001 to
         0xFFFFFFFE)."
    DEFVAL      { 4261412865 }
    ::= { tmnxIsisGeneralEntry 13 }

tmnxIsisMaximumNumberUpas        OBJECT-TYPE
    SYNTAX      Unsigned32 (1..8192)
    MAX-ACCESS  read-write
    STATUS      current
    DESCRIPTION
        "The value of the object tmnxIsisMaximumNumberUpas specifies  the
         maximum number of UPAs the router is allowed to advertise."
    DEFVAL      { 32 }
    ::= { tmnxIsisGeneralEntry 14 }

tmnxIsisProcessReceivedUpa       OBJECT-TYPE
    SYNTAX      TruthValue
    MAX-ACCESS  read-write
    STATUS      current
    DESCRIPTION
        "The value of tmnxIsisProcessReceivedUpa specifies  whether processing
         is enabled of received UPAs from other routers.

         If the value is 'false', received UPAs are ignored by the router.

         If the value is 'true', received UPAs are inserted to the Unreachable
         Prefix Table."
    DEFVAL      { false }
    ::= { tmnxIsisGeneralEntry 15 }

tmnxIsisDbExportReachableLsOnly  OBJECT-TYPE
    SYNTAX      TruthValue
    MAX-ACCESS  read-write
    STATUS      current
    DESCRIPTION
        "The value of the object tmnxIsisDbExportReachableLsOnly specifies
         whether only Link State information from reachable nodes should be
         advertised by BGP-LS.

         If the value is 'false', Link State information from unreachable nodes
         may still be advertised by BGP-LS."
    DEFVAL      { false }
    ::= { tmnxIsisGeneralEntry 16 }

tmnxIsisFlexAlgoTable            OBJECT-TYPE
    SYNTAX      SEQUENCE OF TmnxIsisFlexAlgoEntry
    MAX-ACCESS  not-accessible
    STATUS      current
    DESCRIPTION
        "The table tmnxIsisFlexAlgoTable contains the information pertaining to
         IS-IS Flexible Algorithms."
    ::= { tmnxIsisSystemObjs 24 }

tmnxIsisFlexAlgoEntry            OBJECT-TYPE
    SYNTAX      TmnxIsisFlexAlgoEntry
    MAX-ACCESS  not-accessible
    STATUS      current
    DESCRIPTION
        "Each row entry in tmnxIsisFlexAlgoTable represents the configuration
         for a Flexible Algorithm on an ISIS instance.

         Rows in this table can be created and destroyed by SNMP Set operations
         on the object tmnxIsisFlexAlgoRowStatus"
    INDEX       {
        vRtrID,
        isisSysInstance,
        tmnxIsisFlexAlgoId
    }
    ::= { tmnxIsisFlexAlgoTable 1 }

TmnxIsisFlexAlgoEntry            ::= SEQUENCE
{
    tmnxIsisFlexAlgoId               TmnxFlexAlgoId,
    tmnxIsisFlexAlgoLastChanged      TimeStamp,
    tmnxIsisFlexAlgoRowStatus        RowStatus,
    tmnxIsisFlexAlgoParticipate      TruthValue,
    tmnxIsisFlexAlgoAdvertise        TNamedItemOrEmpty,
    tmnxIsisFlexAlgoMicroLoopAvd     TruthValue,
    tmnxIsisFlexAlgoLfa              TruthValue
}

tmnxIsisFlexAlgoId               OBJECT-TYPE
    SYNTAX      TmnxFlexAlgoId
    MAX-ACCESS  not-accessible
    STATUS      current
    DESCRIPTION
        "The value of tmnxIsisFlexAlgoId specifies the identifier of the
         Flexible Algorithm."
    ::= { tmnxIsisFlexAlgoEntry 1 }

tmnxIsisFlexAlgoLastChanged      OBJECT-TYPE
    SYNTAX      TimeStamp
    MAX-ACCESS  read-only
    STATUS      current
    DESCRIPTION
        "The value of tmnxIsisFlexAlgoLastChanged indicates the sysUpTime when
         a configurable object in this row was last modified."
    ::= { tmnxIsisFlexAlgoEntry 2 }

tmnxIsisFlexAlgoRowStatus        OBJECT-TYPE
    SYNTAX      RowStatus
    MAX-ACCESS  read-create
    STATUS      current
    DESCRIPTION
        "The value of tmnxIsisFlexAlgoRowStatus specifies the row status used
         for creation, deletion, or control of tmnxIsisFlexAlgoTable entries."
    ::= { tmnxIsisFlexAlgoEntry 3 }

tmnxIsisFlexAlgoParticipate      OBJECT-TYPE
    SYNTAX      TruthValue
    MAX-ACCESS  read-create
    STATUS      current
    DESCRIPTION
        "The value of the object tmnxIsisFlexAlgoParticipate specifies whether
         the router must participate in the Flexible Algorithm.

         When the value is 'true', the router is participating in the Flexible
         Algorithm and will advertise the flex-algo SIDs."
    DEFVAL      { false }
    ::= { tmnxIsisFlexAlgoEntry 4 }

tmnxIsisFlexAlgoAdvertise        OBJECT-TYPE
    SYNTAX      TNamedItemOrEmpty
    MAX-ACCESS  read-create
    STATUS      current
    DESCRIPTION
        "The value of the object tmnxIsisFlexAlgoAdvertise specifies the
         Flexible Algorithm Definition to advertise.

         The Flexible Algorithm Definition is defined by tmnxFlexAlgoName and
         is the index for TIMETRA-VRTR-MIB::tmnxFlexAlgoDefinitionTable.

         If a flex-algo name is set, the router will encode and flood the
         locally configured flex-algo definition in the TLV or sub-TLV.

         If an empty string is set, the router will not advertise the locally
         configured flex-algo definitions."
    DEFVAL      { ''H }
    ::= { tmnxIsisFlexAlgoEntry 5 }

tmnxIsisFlexAlgoMicroLoopAvd     OBJECT-TYPE
    SYNTAX      TruthValue
    MAX-ACCESS  read-create
    STATUS      current
    DESCRIPTION
        "The value of tmnxIsisFlexAlgoMicroLoopAvd specifies whether
         micro-loops avoidance during the convergence is enabled for the
         Flexible Algorithm."
    DEFVAL      { false }
    ::= { tmnxIsisFlexAlgoEntry 6 }

tmnxIsisFlexAlgoLfa              OBJECT-TYPE
    SYNTAX      TruthValue
    MAX-ACCESS  read-create
    STATUS      current
    DESCRIPTION
        "The value of tmnxIsisFlexAlgoLfa specifies whether
         loopfree alternate (LFA) is enabled for the
         Flexible Algorithm."
    DEFVAL      { false }
    ::= { tmnxIsisFlexAlgoEntry 7 }

tmnxIsisFlexAlgoRouteNhTable     OBJECT-TYPE
    SYNTAX      SEQUENCE OF TmnxIsisFlexAlgoRouteNhEntry
    MAX-ACCESS  not-accessible
    STATUS      current
    DESCRIPTION
        "The tmnxIsisFlexAlgoRouteNhTable maintains the routes and nexthops
         learned by an instance of IS-IS protocol for a specific  Flexible
         Algorithm and multi topology id."
    ::= { tmnxIsisSystemObjs 25 }

tmnxIsisFlexAlgoRouteNhEntry     OBJECT-TYPE
    SYNTAX      TmnxIsisFlexAlgoRouteNhEntry
    MAX-ACCESS  not-accessible
    STATUS      current
    DESCRIPTION
        "Each row entry in the tmnxIsisRouteNhTable stores a route and nexthop
         for a given instance of the IS-IS protocol for a specific multi
         topology id."
    INDEX       {
        vRtrID,
        isisSysInstance,
        tmnxIsisFlexAlgoId,
        tmnxIsisFaRouteNhMtId,
        tmnxIsisFaRouteNhDestType,
        tmnxIsisFaRouteNhDest,
        tmnxIsisFaRouteNhPrefixLength,
        tmnxIsisFaRouteNhEcmpIndex
    }
    ::= { tmnxIsisFlexAlgoRouteNhTable 1 }

TmnxIsisFlexAlgoRouteNhEntry     ::= SEQUENCE
{
    tmnxIsisFaRouteNhMtId            Unsigned32,
    tmnxIsisFaRouteNhDestType        InetAddressType,
    tmnxIsisFaRouteNhDest            InetAddress,
    tmnxIsisFaRouteNhPrefixLength    InetAddressPrefixLength,
    tmnxIsisFaRouteNhEcmpIndex       Unsigned32,
    tmnxIsisFaRouteNhIPType          InetAddressType,
    tmnxIsisFaRouteNhIP              InetAddress,
    tmnxIsisFaRouteNhLevel           INTEGER,
    tmnxIsisFaRouteNhSpfRunNumber    Counter32,
    tmnxIsisFaRouteNhMetric          Unsigned32,
    tmnxIsisFaRouteNhType            INTEGER,
    tmnxIsisFaRouteNhSysID           SystemID,
    tmnxIsisFaRouteNhTag             Unsigned32,
    tmnxIsisFaRouteNhCidrType        TmnxInetCidrNextHopType,
    tmnxIsisFaRouteNhOwner           TmnxInetCidrNextHopOwner,
    tmnxIsisFaRouteNhOwnerAuxInfo    Unsigned32,
    tmnxIsisFaRouteNhSidFlags        TmnxIsisPrefixSidFlags,
    tmnxIsisFaRouteNhSidValue        Unsigned32,
    tmnxIsisFaRouteNhRouteStatus     INTEGER,
    tmnxIsisFaRouteNhNhopStatus      INTEGER
}

tmnxIsisFaRouteNhMtId            OBJECT-TYPE
    SYNTAX      Unsigned32
    MAX-ACCESS  not-accessible
    STATUS      current
    DESCRIPTION
        "The value of the object tmnxIsisFaRouteNhMtId specifies the multi
         topology id number for this route.

         If multi-topology is not supported for the route then the value of
         tmnxIsisFaRouteNhMtId should be 0."
    ::= { tmnxIsisFlexAlgoRouteNhEntry 1 }

tmnxIsisFaRouteNhDestType        OBJECT-TYPE
    SYNTAX      InetAddressType
    MAX-ACCESS  not-accessible
    STATUS      current
    DESCRIPTION
        "The value of the object tmnxIsisFaRouteNhDestType specifies the IP
         address type for tmnxIsisFaRouteNhDest."
    ::= { tmnxIsisFlexAlgoRouteNhEntry 2 }

tmnxIsisFaRouteNhDest            OBJECT-TYPE
    SYNTAX      InetAddress (SIZE (4|16|20))
    MAX-ACCESS  not-accessible
    STATUS      current
    DESCRIPTION
        "The value of the object tmnxIsisFaRouteNhDest specifies the
         destination IP address of this route.

         The address type of tmnxIsisFaRouteNhDest is indicated by
         tmnxIsisFaRouteNhDestType."
    ::= { tmnxIsisFlexAlgoRouteNhEntry 3 }

tmnxIsisFaRouteNhPrefixLength    OBJECT-TYPE
    SYNTAX      InetAddressPrefixLength
    MAX-ACCESS  not-accessible
    STATUS      current
    DESCRIPTION
        "The value of the object tmnxIsisFaRouteNhPrefixLength specifies the
         prefix length to be used with tmnxIsisFaRouteNhDest to get the network
         prefix."
    ::= { tmnxIsisFlexAlgoRouteNhEntry 4 }

tmnxIsisFaRouteNhEcmpIndex       OBJECT-TYPE
    SYNTAX      Unsigned32
    MAX-ACCESS  not-accessible
    STATUS      current
    DESCRIPTION
        "The value of the object tmnxIsisFaRouteNhEcmpIndex specifies the ecmp
         index of this nexthop entry."
    ::= { tmnxIsisFlexAlgoRouteNhEntry 5 }

tmnxIsisFaRouteNhIPType          OBJECT-TYPE
    SYNTAX      InetAddressType
    MAX-ACCESS  read-only
    STATUS      current
    DESCRIPTION
        "The value of the object tmnxIsisFaRouteNhIPType indicates the IP
         address type for tmnxIsisFaRouteNhIP."
    ::= { tmnxIsisFlexAlgoRouteNhEntry 6 }

tmnxIsisFaRouteNhIP              OBJECT-TYPE
    SYNTAX      InetAddress (SIZE (4|16|20))
    MAX-ACCESS  read-only
    STATUS      current
    DESCRIPTION
        "The value of the object tmnxIsisFaRouteNhIP indicates the IP address
         of the nexthop for this route.

         The address type of tmnxIsisFaRouteNhIP is indicated by
         tmnxIsisFaRouteNhIPType"
    ::= { tmnxIsisFlexAlgoRouteNhEntry 7 }

tmnxIsisFaRouteNhLevel           OBJECT-TYPE
    SYNTAX      INTEGER {
        level1IS (1),
        level2IS (2)
    }
    MAX-ACCESS  read-only
    STATUS      current
    DESCRIPTION
        "The value of the object tmnxIsisFaRouteNhLevel indicates the IS-IS
         Level at which the prefix was learned."
    ::= { tmnxIsisFlexAlgoRouteNhEntry 8 }

tmnxIsisFaRouteNhSpfRunNumber    OBJECT-TYPE
    SYNTAX      Counter32
    MAX-ACCESS  read-only
    STATUS      current
    DESCRIPTION
        "The value of the object tmnxIsisFaRouteNhSpfRunNumber indicates the
         run of spf calculation in which this route was selected."
    ::= { tmnxIsisFlexAlgoRouteNhEntry 9 }

tmnxIsisFaRouteNhMetric          OBJECT-TYPE
    SYNTAX      Unsigned32
    MAX-ACCESS  read-only
    STATUS      current
    DESCRIPTION
        "The value of the object tmnxIsisFaRouteNhMetric indicates the metric
         value associated with the route.

         This metric is obtained by the SPF calculations and is used by the
         instance of the protocol.

         For a given destination prefix, the route with the lower metric is the
         shorter route.

         A metric value in the range from 4261412865 to 4294967294 (0xFE000001
         to 0xFFFFFFFE) indicates an unreachable route."
    ::= { tmnxIsisFlexAlgoRouteNhEntry 10 }

tmnxIsisFaRouteNhType            OBJECT-TYPE
    SYNTAX      INTEGER {
        internal (1),
        external (2)
    }
    MAX-ACCESS  read-only
    STATUS      current
    DESCRIPTION
        "The value of the object tmnxIsisFaRouteNhType indicates the type of
         route represented by this row entry."
    ::= { tmnxIsisFlexAlgoRouteNhEntry 11 }

tmnxIsisFaRouteNhSysID           OBJECT-TYPE
    SYNTAX      SystemID
    MAX-ACCESS  read-only
    STATUS      current
    DESCRIPTION
        "The value of the object tmnxIsisFaRouteNhSysID indicates the system-id
         of the nexthop IS through which this route is reachable."
    ::= { tmnxIsisFlexAlgoRouteNhEntry 12 }

tmnxIsisFaRouteNhTag             OBJECT-TYPE
    SYNTAX      Unsigned32
    MAX-ACCESS  read-only
    STATUS      current
    DESCRIPTION
        "The value of the object tmnxIsisFaRouteNhTag indicates a 32-bit
         integer route tag for this route.

         A value of 0 indicates that the tag has not been set."
    ::= { tmnxIsisFlexAlgoRouteNhEntry 13 }

tmnxIsisFaRouteNhCidrType        OBJECT-TYPE
    SYNTAX      TmnxInetCidrNextHopType
    MAX-ACCESS  read-only
    STATUS      current
    DESCRIPTION
        "The value of the object tmnxIsisFaRouteNhCidrType indicates the type
         of next hop for this route."
    ::= { tmnxIsisFlexAlgoRouteNhEntry 19 }

tmnxIsisFaRouteNhOwner           OBJECT-TYPE
    SYNTAX      TmnxInetCidrNextHopOwner
    MAX-ACCESS  read-only
    STATUS      current
    DESCRIPTION
        "The value of the object tmnxIsisFaRouteNhOwner indicates the owner of
         next hop for this route."
    ::= { tmnxIsisFlexAlgoRouteNhEntry 20 }

tmnxIsisFaRouteNhOwnerAuxInfo    OBJECT-TYPE
    SYNTAX      Unsigned32
    MAX-ACCESS  read-only
    STATUS      current
    DESCRIPTION
        "The value of the object tmnxIsisFaRouteNhOwnerAuxInfo indicates the
         auxiliary information for next hop owner as indicated by
         tmnxIsisFaRouteNhOwner.

         The value of tmnxIsisFaRouteNhOwnerAuxInfo indicates the tunnel id
         existing for this next hop type and owner."
    ::= { tmnxIsisFlexAlgoRouteNhEntry 21 }

tmnxIsisFaRouteNhSidFlags        OBJECT-TYPE
    SYNTAX      TmnxIsisPrefixSidFlags
    MAX-ACCESS  read-only
    STATUS      current
    DESCRIPTION
        "The value of the object tmnxIsisFaRouteNhSidFlags indicates the flags
         of a Prefix-SID as defined by IETF segment routing.


         If bitUsed(0) is set, tmnxIsisFaRouteNhSidValue is valid."
    ::= { tmnxIsisFlexAlgoRouteNhEntry 25 }

tmnxIsisFaRouteNhSidValue        OBJECT-TYPE
    SYNTAX      Unsigned32
    MAX-ACCESS  read-only
    STATUS      current
    DESCRIPTION
        "The value of the object tmnxIsisFaRouteNhSidValue indicates the SID
         label or index for this prefix."
    ::= { tmnxIsisFlexAlgoRouteNhEntry 26 }

tmnxIsisFaRouteNhRouteStatus     OBJECT-TYPE
    SYNTAX      INTEGER {
        active       (0),
        rtmAddFailed (1),
        fibAddFailed (2),
        unreachable  (3)
    }
    MAX-ACCESS  read-only
    STATUS      current
    DESCRIPTION
        "The value of tmnxIsisFaRouteNhRouteStatus indicates the reason why a
         route is not active."
    ::= { tmnxIsisFlexAlgoRouteNhEntry 27 }

tmnxIsisFaRouteNhNhopStatus      OBJECT-TYPE
    SYNTAX      INTEGER {
        success   (0),
        discarded (1)
    }
    MAX-ACCESS  read-only
    STATUS      current
    DESCRIPTION
        "The value of tmnxIsisFaRouteNhNhopStatus indicates the next hop status
         in RTM."
    ::= { tmnxIsisFlexAlgoRouteNhEntry 28 }

tmnxIsisFlexAlgoPathTable        OBJECT-TYPE
    SYNTAX      SEQUENCE OF TmnxIsisFlexAlgoPathEntry
    MAX-ACCESS  not-accessible
    STATUS      current
    DESCRIPTION
        "The tmnxIsisFlexAlgoPathTable maintains information regarding SPF
         calculation for each instance of IS-IS protocol for a Flexible
         Algorithm."
    ::= { tmnxIsisSystemObjs 26 }

tmnxIsisFlexAlgoPathEntry        OBJECT-TYPE
    SYNTAX      TmnxIsisFlexAlgoPathEntry
    MAX-ACCESS  not-accessible
    STATUS      current
    DESCRIPTION
        "Each row entry in the tmnxIsisFlexAlgoPathTable represents the ISIS
         path for an instance, Flexible Algorithm, level, multi topology id,
         path identifier and the path outgoing interface."
    INDEX       {
        vRtrID,
        isisSysInstance,
        tmnxIsisFlexAlgoId,
        tmnxIsisLevel,
        tmnxIsisFaPathMtID,
        tmnxIsisFaPathID,
        tmnxIsisFaPathIfIndex,
        tmnxIsisFaPathNHopSysID
    }
    ::= { tmnxIsisFlexAlgoPathTable 1 }

TmnxIsisFlexAlgoPathEntry        ::= SEQUENCE
{
    tmnxIsisFaPathMtID               Unsigned32,
    tmnxIsisFaPathID                 OCTET STRING,
    tmnxIsisFaPathIfIndex            InterfaceIndex,
    tmnxIsisFaPathNHopSysID          SystemID,
    tmnxIsisFaPathMetric             Unsigned32,
    tmnxIsisFaPathSNPA               SNPAAddress,
    tmnxIsisFaPathLfaIfIndex         InterfaceIndexOrZero,
    tmnxIsisFaPathLfaNHop            SystemID,
    tmnxIsisFaPathLfaMetric          Unsigned32,
    tmnxIsisFaPathLfaType            INTEGER,
    tmnxIsisFaPathRouteType          INTEGER
}

tmnxIsisFaPathMtID               OBJECT-TYPE
    SYNTAX      Unsigned32
    MAX-ACCESS  not-accessible
    STATUS      current
    DESCRIPTION
        "The value of the object tmnxIsisFaPathMtID specifies the
         multi-topology id number for the path.

         If multi-topology is not supported for the path then the value of
         tmnxIsisFaPathMtID should be 0."
    ::= { tmnxIsisFlexAlgoPathEntry 1 }

tmnxIsisFaPathID                 OBJECT-TYPE
    SYNTAX      OCTET STRING (SIZE (7))
    MAX-ACCESS  not-accessible
    STATUS      current
    DESCRIPTION
        "The value of the object tmnxIsisFaPathID specifies the path identifier
         and has first 6 octets as the system-id followed by one octet of the
         Lan-ID."
    ::= { tmnxIsisFlexAlgoPathEntry 2 }

tmnxIsisFaPathIfIndex            OBJECT-TYPE
    SYNTAX      InterfaceIndex
    MAX-ACCESS  not-accessible
    STATUS      current
    DESCRIPTION
        "The value of the object tmnxIsisFaPathIfIndex specifies the ifIndex of
         the outgoing interface for the path."
    ::= { tmnxIsisFlexAlgoPathEntry 3 }

tmnxIsisFaPathNHopSysID          OBJECT-TYPE
    SYNTAX      SystemID
    MAX-ACCESS  not-accessible
    STATUS      current
    DESCRIPTION
        "The value of the object tmnxIsisFaPathNHopSysID specifies the
         system-id of the nexthop and is used to reference the nexthop for this
         route."
    ::= { tmnxIsisFlexAlgoPathEntry 4 }

tmnxIsisFaPathMetric             OBJECT-TYPE
    SYNTAX      Unsigned32
    MAX-ACCESS  read-only
    STATUS      current
    DESCRIPTION
        "The value of the object tmnxIsisFaPathMetric indicates the metric
         assigned to this path entry after SPF calculations.

         The lower the metric value, the shorter is the path and hence more
         preferred by the protocol."
    ::= { tmnxIsisFlexAlgoPathEntry 5 }

tmnxIsisFaPathSNPA               OBJECT-TYPE
    SYNTAX      SNPAAddress
    MAX-ACCESS  read-only
    STATUS      current
    DESCRIPTION
        "The value of the object tmnxIsisFaPathSNPA indicates the subnet point
         of attachment for this path."
    ::= { tmnxIsisFlexAlgoPathEntry 6 }

tmnxIsisFaPathLfaIfIndex         OBJECT-TYPE
    SYNTAX      InterfaceIndexOrZero
    MAX-ACCESS  read-only
    STATUS      current
    DESCRIPTION
        "The value of the object tmnxIsisFaPathLfaIfIndex indicates the
         loopfree-alternate ifIndex of the outgoing interface for the path."
    ::= { tmnxIsisFlexAlgoPathEntry 7 }

tmnxIsisFaPathLfaNHop            OBJECT-TYPE
    SYNTAX      SystemID
    MAX-ACCESS  read-only
    STATUS      current
    DESCRIPTION
        "The value of the object tmnxIsisFaPathLfaNHop indicates the
         loopfree-alternate nexthop and is referenced by the system-id."
    ::= { tmnxIsisFlexAlgoPathEntry 8 }

tmnxIsisFaPathLfaMetric          OBJECT-TYPE
    SYNTAX      Unsigned32
    MAX-ACCESS  read-only
    STATUS      current
    DESCRIPTION
        "The value of the object tmnxIsisFaPathLfaMetric indicates the metric
         assigned to this entry which are a result of loopfree-alternate
         calculations.

         The lower the metric value, the shorter is the path and hence more
         preferred by the protocol."
    ::= { tmnxIsisFlexAlgoPathEntry 9 }

tmnxIsisFaPathLfaType            OBJECT-TYPE
    SYNTAX      INTEGER {
        none     (0),
        nodeLink (1),
        pathLink (2)
    }
    MAX-ACCESS  read-only
    STATUS      current
    DESCRIPTION
        "The value of the object tmnxIsisFaPathLfaType indicates the type of
         route represented by this row entry."
    ::= { tmnxIsisFlexAlgoPathEntry 10 }

tmnxIsisFaPathRouteType          OBJECT-TYPE
    SYNTAX      INTEGER {
        spf (0),
        lfa (1)
    }
    MAX-ACCESS  read-only
    STATUS      current
    DESCRIPTION
        "The value of the object tmnxIsisFaPathRouteType indicates whether a
         backup route exists for this row entry."
    ::= { tmnxIsisFlexAlgoPathEntry 11 }

tmnxIsisFlexAlgoSRLfaStatsTable  OBJECT-TYPE
    SYNTAX      SEQUENCE OF TmnxIsisFlexAlgoSRLfaStatsEntry
    MAX-ACCESS  not-accessible
    STATUS      current
    DESCRIPTION
        "The tmnxIsisFlexAlgoSRLfaStatsTable maintains information on Segment
         Routing (SR) loopfree-alternate (LFA) coverage for each instance of
         IS-IS protocol for a specific Flexible Algorithm and multi topology
         id."
    ::= { tmnxIsisSystemObjs 27 }

tmnxIsisFlexAlgoSRLfaStatsEntry  OBJECT-TYPE
    SYNTAX      TmnxIsisFlexAlgoSRLfaStatsEntry
    MAX-ACCESS  not-accessible
    STATUS      current
    DESCRIPTION
        "Each row entry in the tmnxIsisFlexAlgoSRLfaStatsTable represents
         information on SR LFA coverage for a Flexible Algorithm and various
         topologies of the system."
    INDEX       {
        vRtrID,
        isisSysInstance,
        tmnxIsisFlexAlgoId,
        tmnxIsisFaSRLfaStatsLevel,
        tmnxIsisFaSRLfaStatsMtId,
        tmnxIsisFaSRLfaStatsSidType,
        tmnxIsisFaSRLfaStatsProtoVersion
    }
    ::= { tmnxIsisFlexAlgoSRLfaStatsTable 1 }

TmnxIsisFlexAlgoSRLfaStatsEntry  ::= SEQUENCE
{
    tmnxIsisFaSRLfaStatsLevel        INTEGER,
    tmnxIsisFaSRLfaStatsMtId         Unsigned32,
    tmnxIsisFaSRLfaStatsSidType      INTEGER,
    tmnxIsisFaSRLfaStatsProtoVersion INTEGER,
    tmnxIsisFaSRLfaStatsTotalSid     Unsigned32,
    tmnxIsisFaSRLfaStatsLfaCovered   Unsigned32,
    tmnxIsisFaSRLfaStatsRLfaCovered  Unsigned32,
    tmnxIsisFaSRLfaStatsTiLfaCovered Unsigned32
}

tmnxIsisFaSRLfaStatsLevel        OBJECT-TYPE
    SYNTAX      INTEGER {
        level1   (1),
        level2   (2),
        level1L2 (3)
    }
    MAX-ACCESS  not-accessible
    STATUS      current
    DESCRIPTION
        "The value of the object tmnxIsisFaSRLfaStatsLevel specifies the IS-IS
         Level for which SR LFA coverage has been computed."
    ::= { tmnxIsisFlexAlgoSRLfaStatsEntry 1 }

tmnxIsisFaSRLfaStatsMtId         OBJECT-TYPE
    SYNTAX      Unsigned32
    MAX-ACCESS  not-accessible
    STATUS      current
    DESCRIPTION
        "The value of the object tmnxIsisFaSRLfaStatsMtId specifies the
         multi-topology (MT) id number for which SR LFA coverage has been
         computed."
    ::= { tmnxIsisFlexAlgoSRLfaStatsEntry 2 }

tmnxIsisFaSRLfaStatsSidType      OBJECT-TYPE
    SYNTAX      INTEGER {
        nodeSid    (0),
        adjSid     (1),
        globAdjSid (2)
    }
    MAX-ACCESS  not-accessible
    STATUS      current
    DESCRIPTION
        "The value of the object tmnxIsisFaSRLfaStatsSidType specifies the SID
         type for which SR LFA coverage has been computed."
    ::= { tmnxIsisFlexAlgoSRLfaStatsEntry 3 }

tmnxIsisFaSRLfaStatsProtoVersion OBJECT-TYPE
    SYNTAX      INTEGER {
        ipv4 (0),
        ipv6 (1)
    }
    MAX-ACCESS  not-accessible
    STATUS      current
    DESCRIPTION
        "The value of the object tmnxIsisFaSRLfaStatsProtoVersion specifies the
         protocol version for which SR LFA coverage has been computed."
    ::= { tmnxIsisFlexAlgoSRLfaStatsEntry 4 }

tmnxIsisFaSRLfaStatsTotalSid     OBJECT-TYPE
    SYNTAX      Unsigned32
    MAX-ACCESS  read-only
    STATUS      current
    DESCRIPTION
        "The value of the object tmnxIsisFaSRLfaStatsTotalSid indicates the
         number of SIDs eligible for SR LFA calculation"
    ::= { tmnxIsisFlexAlgoSRLfaStatsEntry 5 }

tmnxIsisFaSRLfaStatsLfaCovered   OBJECT-TYPE
    SYNTAX      Unsigned32
    MAX-ACCESS  read-only
    STATUS      current
    DESCRIPTION
        "The value of the object tmnxIsisFaSRLfaStatsLfaCovered indicates the
         number of SIDs for which an LFA is found."
    ::= { tmnxIsisFlexAlgoSRLfaStatsEntry 6 }

tmnxIsisFaSRLfaStatsRLfaCovered  OBJECT-TYPE
    SYNTAX      Unsigned32
    MAX-ACCESS  read-only
    STATUS      current
    DESCRIPTION
        "The value of the object tmnxIsisFaSRLfaStatsRLfaCovered indicates the
         number of SIDs for which an Remote LFA is found."
    ::= { tmnxIsisFlexAlgoSRLfaStatsEntry 7 }

tmnxIsisFaSRLfaStatsTiLfaCovered OBJECT-TYPE
    SYNTAX      Unsigned32
    MAX-ACCESS  read-only
    STATUS      current
    DESCRIPTION
        "The value of the object tmnxIsisFaSRLfaStatsTiLfaCovered indicates the
         number of SIDs for which an Topology Independent LFA is found."
    ::= { tmnxIsisFlexAlgoSRLfaStatsEntry 8 }

tmnxIsisFlexAlgoStateTable       OBJECT-TYPE
    SYNTAX      SEQUENCE OF TmnxIsisFlexAlgoStateEntry
    MAX-ACCESS  not-accessible
    STATUS      current
    DESCRIPTION
        "The table tmnxIsisFlexAlgoStateTable contains the  state information
         for a Flexible Algorithm."
    ::= { tmnxIsisSystemObjs 29 }

tmnxIsisFlexAlgoStateEntry       OBJECT-TYPE
    SYNTAX      TmnxIsisFlexAlgoStateEntry
    MAX-ACCESS  not-accessible
    STATUS      current
    DESCRIPTION
        "Each row entry in tmnxIsisFlexAlgoStateTable represents  the
         information for a Flex Algo in a specific ISIS level."
    INDEX       {
        vRtrID,
        isisSysInstance,
        tmnxIsisFlexAlgoId,
        tmnxIsisLevel
    }
    ::= { tmnxIsisFlexAlgoStateTable 1 }

TmnxIsisFlexAlgoStateEntry       ::= SEQUENCE
{
    tmnxIsisFaStatOperState          TmnxEnabledDisabled,
    tmnxIsisFaStatFadCount           Counter32,
    tmnxIsisFaStatSelectedFadOwner   SystemID
}

tmnxIsisFaStatOperState          OBJECT-TYPE
    SYNTAX      TmnxEnabledDisabled
    MAX-ACCESS  read-only
    STATUS      current
    DESCRIPTION
        "The value of the object tmnxIsisFaStatOperState indicates the current
         operating state of the Flexible Algorithm participation  in this ISIS
         level."
    ::= { tmnxIsisFlexAlgoStateEntry 1 }

tmnxIsisFaStatFadCount           OBJECT-TYPE
    SYNTAX      Counter32
    MAX-ACCESS  read-only
    STATUS      current
    DESCRIPTION
        "The value of the object tmnxIsisFaStatFadCount indicates the number of
         Flexible Algorithm Definitions (FAD) for the Flex Algo in the ISIS
         level."
    ::= { tmnxIsisFlexAlgoStateEntry 2 }

tmnxIsisFaStatSelectedFadOwner   OBJECT-TYPE
    SYNTAX      SystemID
    MAX-ACCESS  read-only
    STATUS      current
    DESCRIPTION
        "The value of the object tmnxIsisFaStatSelectedFadOwner indicates the
         system-id of the owner of the selected Flexible Algorithm Definition
         (FAD).

         A corresponding entry for the FAD owner exists in
         tmnxIsisFlexAlgoFadTable."
    ::= { tmnxIsisFlexAlgoStateEntry 3 }

tmnxIsisFlexAlgoFadTable         OBJECT-TYPE
    SYNTAX      SEQUENCE OF TmnxIsisFlexAlgoFadEntry
    MAX-ACCESS  not-accessible
    STATUS      current
    DESCRIPTION
        "The table tmnxIsisFlexAlgoFadTable contains the  Flexible Algorithms
         Definition (FAD) information for a Flexible Algorithm."
    ::= { tmnxIsisSystemObjs 30 }

tmnxIsisFlexAlgoFadEntry         OBJECT-TYPE
    SYNTAX      TmnxIsisFlexAlgoFadEntry
    MAX-ACCESS  not-accessible
    STATUS      current
    DESCRIPTION
        "Each row entry in tmnxIsisFlexAlgoFadTable represents  the information
         of a Flexible Algorithms Definition (FAD) for a Flex Algo in a
         specific ISIS level."
    INDEX       {
        vRtrID,
        isisSysInstance,
        tmnxIsisFlexAlgoId,
        tmnxIsisLevel,
        tmnxIsisFadOwnerLSPId
    }
    ::= { tmnxIsisFlexAlgoFadTable 1 }

TmnxIsisFlexAlgoFadEntry         ::= SEQUENCE
{
    tmnxIsisFadOwnerLSPId            OCTET STRING,
    tmnxIsisFadPriority              Integer32,
    tmnxIsisFadSupported             TruthValue,
    tmnxIsisFadUnsupportedReason     INTEGER,
    tmnxIsisFadMetricType            Unsigned32,
    tmnxIsisFadCalculationType       Unsigned32,
    tmnxIsisFadExclude               Unsigned32,
    tmnxIsisFadIncludeAny            Unsigned32,
    tmnxIsisFadIncludeAll            Unsigned32,
    tmnxIsisFadFlags                 BITS,
    tmnxIsisFadExcludeEAG            OCTET STRING,
    tmnxIsisFadIncludeAnyEAG         OCTET STRING,
    tmnxIsisFadIncludeAllEAG         OCTET STRING
}

tmnxIsisFadOwnerLSPId            OBJECT-TYPE
    SYNTAX      OCTET STRING (SIZE (0..8))
    MAX-ACCESS  not-accessible
    STATUS      current
    DESCRIPTION
        "The value of the object tmnxIsisFadOwnerLSPId specifies the LSP Id of the
         of the Fad owner and is given in the format as 6 octets of
         Fad owner system-id followed by 1 octet Lan-ID and 1 octet LSP Number."
    ::= { tmnxIsisFlexAlgoFadEntry 1 }

tmnxIsisFadPriority              OBJECT-TYPE
    SYNTAX      Integer32 (0..255)
    MAX-ACCESS  read-only
    STATUS      current
    DESCRIPTION
        "The value of the object tmnxIsisFadPriority indicates the priority of
         the FAD."
    ::= { tmnxIsisFlexAlgoFadEntry 2 }

tmnxIsisFadSupported             OBJECT-TYPE
    SYNTAX      TruthValue
    MAX-ACCESS  read-only
    STATUS      current
    DESCRIPTION
        "The value of the object tmnxIsisFadSupported indicates whether the FAD
         is supported."
    ::= { tmnxIsisFlexAlgoFadEntry 3 }

tmnxIsisFadUnsupportedReason     OBJECT-TYPE
    SYNTAX      INTEGER {
        none            (0),
        metricType      (1),
        calculationType (2),
        constraint      (3),
        flag            (4),
        subtlv          (5)
    }
    MAX-ACCESS  read-only
    STATUS      current
    DESCRIPTION
        "The value of the object tmnxIsisFadUnsupportedReason indicates the
         reason why the FAD is not supported.

         This object is only applicable if the object  tmnxIsisFadSupported has
         the value 'false'."
    ::= { tmnxIsisFlexAlgoFadEntry 4 }

tmnxIsisFadMetricType            OBJECT-TYPE
    SYNTAX      Unsigned32
    MAX-ACCESS  read-only
    STATUS      current
    DESCRIPTION
        "The value of the object tmnxIsisFadMetricType indicates the metric
         type of the FAD.

         The supported metric types are igp (0), delay (1) and  teMetric (2).

         If the metric type has another value then tmnxIsisFadSupported will be
         'false' and tmnxIsisFadUnsupportedReason will be  metricType (1)."
    ::= { tmnxIsisFlexAlgoFadEntry 5 }

tmnxIsisFadCalculationType       OBJECT-TYPE
    SYNTAX      Unsigned32
    MAX-ACCESS  read-only
    STATUS      current
    DESCRIPTION
        "The value of the object tmnxIsisFadCalculationType indicates the
         calculation type of the FAD.

         A value '0' indicates calculation type SPF."
    ::= { tmnxIsisFlexAlgoFadEntry 6 }

tmnxIsisFadExclude               OBJECT-TYPE
    SYNTAX      Unsigned32
    MAX-ACCESS  read-only
    STATUS      current
    DESCRIPTION
        "The value of the object tmnxIsisFadExclude indicates the exclude rule
         that is used during the Flex-Algorithm path calculation.

         This object is deprecated, please use the extended object
         tmnxIsisFadExcludeEAG instead."
    ::= { tmnxIsisFlexAlgoFadEntry 7 }

tmnxIsisFadIncludeAny            OBJECT-TYPE
    SYNTAX      Unsigned32
    MAX-ACCESS  read-only
    STATUS      current
    DESCRIPTION
        "The value of the object tmnxIsisFadIncludeAny indicates the
         include-any rule that is used during the Flex-Algorithm path
         calculation.

         This object is deprecated, please use the extended object
         tmnxIsisFadIncludeAnyEAG instead."
    ::= { tmnxIsisFlexAlgoFadEntry 8 }

tmnxIsisFadIncludeAll            OBJECT-TYPE
    SYNTAX      Unsigned32
    MAX-ACCESS  read-only
    STATUS      current
    DESCRIPTION
        "The value of the object tmnxIsisFadIncludeAll indicates the
         include-all rule that is used during the Flex-Algorithm path
         calculation.

         This object is deprecated, please use the extended object
         tmnxIsisFadIncludeAllEAG instead."
    ::= { tmnxIsisFlexAlgoFadEntry 9 }

tmnxIsisFadFlags                 OBJECT-TYPE
    SYNTAX      BITS {
        bitM (0)
    }
    MAX-ACCESS  read-only
    STATUS      current
    DESCRIPTION
        "The value of the object tmnxIsisFadFlags indicates the Flexible
         Algorithm Definition flags.

         bitM   (0)  - M flag. If set, then Flex-Algorithm specific
                       prefix metric MUST be used, if advertised with
                       the prefix."
    ::= { tmnxIsisFlexAlgoFadEntry 10 }

tmnxIsisFadExcludeEAG            OBJECT-TYPE
    SYNTAX      OCTET STRING (SIZE (0..128))
    MAX-ACCESS  read-only
    STATUS      current
    DESCRIPTION
        "The value of the object tmnxIsisFadExcludeEAG indicates the exclude
         rule that is used during the Flex-Algorithm path calculation.

         The value represents the bitmap of Extended Admin Groups (EAG)."
    ::= { tmnxIsisFlexAlgoFadEntry 11 }

tmnxIsisFadIncludeAnyEAG         OBJECT-TYPE
    SYNTAX      OCTET STRING (SIZE (0..128))
    MAX-ACCESS  read-only
    STATUS      current
    DESCRIPTION
        "The value of the object tmnxIsisFadIncludeAnyEAG indicates the
         include-any rule that is used during the Flex-Algorithm path
         calculation.

         The value represents the bitmap of Extended Admin Groups (EAG)."
    ::= { tmnxIsisFlexAlgoFadEntry 12 }

tmnxIsisFadIncludeAllEAG         OBJECT-TYPE
    SYNTAX      OCTET STRING (SIZE (0..128))
    MAX-ACCESS  read-only
    STATUS      current
    DESCRIPTION
        "The value of the object tmnxIsisFadIncludeAllEAG indicates the
         include-all rule that is used during the Flex-Algorithm path
         calculation.

         The value represents the bitmap of Extended Admin Groups (EAG)."
    ::= { tmnxIsisFlexAlgoFadEntry 13 }

tmnxIsisSrv6Table                OBJECT-TYPE
    SYNTAX      SEQUENCE OF TmnxIsisSrv6Entry
    MAX-ACCESS  not-accessible
    STATUS      current
    DESCRIPTION
        "The tmnxIsisSrv6Table provides an extension of the tmnxIsisTable for
         Segment Routing over IPv6 (SRv6)."
    ::= { tmnxIsisSystemObjs 31 }

tmnxIsisSrv6Entry                OBJECT-TYPE
    SYNTAX      TmnxIsisSrv6Entry
    MAX-ACCESS  not-accessible
    STATUS      current
    DESCRIPTION
        "Each row entry in tmnxIsisSrv6Table represents additional columns for
         an ISIS instance for Segment Routing over IPv6.

         The system automatically creates and destroys rows in this table when
         rows in the tmnxIsisTable are created and destroyed."
    AUGMENTS    { tmnxIsisEntry }
    ::= { tmnxIsisSrv6Table 1 }

TmnxIsisSrv6Entry                ::= SEQUENCE
{
    tmnxIsisSrv6LastChanged          TimeStamp,
    tmnxIsisSrv6AdminState           TmnxAdminState,
    tmnxIsisSrv6AdjSidHold           Unsigned32
}

tmnxIsisSrv6LastChanged          OBJECT-TYPE
    SYNTAX      TimeStamp
    MAX-ACCESS  read-only
    STATUS      current
    DESCRIPTION
        "The value of tmnxIsisSrv6LastChanged indicates the sysUpTime when a
         configurable object in this row was last modified."
    ::= { tmnxIsisSrv6Entry 1 }

tmnxIsisSrv6AdminState           OBJECT-TYPE
    SYNTAX      TmnxAdminState
    MAX-ACCESS  read-write
    STATUS      current
    DESCRIPTION
        "The value of tmnxIsisSrv6AdminState specifies the
         administrative state of Segment Routing over IPv6
         for this ISIS instance."
    DEFVAL      { outOfService }
    ::= { tmnxIsisSrv6Entry 2 }

tmnxIsisSrv6AdjSidHold           OBJECT-TYPE
    SYNTAX      Unsigned32 (0..1800)
    UNITS       "seconds"
    MAX-ACCESS  read-write
    STATUS      current
    DESCRIPTION
        "The value of the object tmnxIsisSrv6AdjSidHold specifies the adjacency
         SID hold time in seconds for SRv6.

         When both tmnxIsisSrAdminState and tmnxIsisSrv6AdminState are enabled,
         the higher of the two timer values (tmnxIsisSrAdjSidHold and
         tmnxIsisSrv6AdjSidHold) is programmed for all SIDs on the adjacency."
    DEFVAL      { 15 }
    ::= { tmnxIsisSrv6Entry 3 }

tmnxIsisSrv6LocatorTable         OBJECT-TYPE
    SYNTAX      SEQUENCE OF TmnxIsisSrv6LocatorEntry
    MAX-ACCESS  not-accessible
    STATUS      current
    DESCRIPTION
        "The table tmnxIsisSrv6LocatorTable contains the information pertaining
         to a SRv6 Locator on an ISIS instance."
    ::= { tmnxIsisSystemObjs 32 }

tmnxIsisSrv6LocatorEntry         OBJECT-TYPE
    SYNTAX      TmnxIsisSrv6LocatorEntry
    MAX-ACCESS  not-accessible
    STATUS      current
    DESCRIPTION
        "Each row entry in tmnxIsisSrv6LocatorTable represents the
         configuration for a SRv6 Locator on an ISIS instance.

         Rows in this table can be created and destroyed by SNMP Set operations
         on the object tmnxIsisSrv6LocatorRowStatus"
    INDEX       {
        vRtrID,
        isisSysInstance,
        vRtrSrv6LocatorName
    }
    ::= { tmnxIsisSrv6LocatorTable 1 }

TmnxIsisSrv6LocatorEntry         ::= SEQUENCE
{
    tmnxIsisSrv6LocatorLastChanged   TimeStamp,
    tmnxIsisSrv6LocatorRowStatus     RowStatus,
    tmnxIsisSrv6LocatorLevelCap      INTEGER,
    tmnxIsisSrv6LocatorTag           Unsigned32,
    tmnxIsisSrv6LocatorMultiTopology BITS
}

tmnxIsisSrv6LocatorLastChanged   OBJECT-TYPE
    SYNTAX      TimeStamp
    MAX-ACCESS  read-only
    STATUS      current
    DESCRIPTION
        "The value of tmnxIsisSrv6LocatorLastChanged indicates the sysUpTime
         when a configurable object in this row was last modified."
    ::= { tmnxIsisSrv6LocatorEntry 1 }

tmnxIsisSrv6LocatorRowStatus     OBJECT-TYPE
    SYNTAX      RowStatus
    MAX-ACCESS  read-create
    STATUS      current
    DESCRIPTION
        "The value of tmnxIsisSrv6LocatorRowStatus specifies the row status
         used for creation, deletion, or control of tmnxIsisSrv6LocatorTable
         entries."
    ::= { tmnxIsisSrv6LocatorEntry 2 }

tmnxIsisSrv6LocatorLevelCap      OBJECT-TYPE
    SYNTAX      INTEGER {
        level1   (1),
        level2   (2),
        level1L2 (3)
    }
    MAX-ACCESS  read-create
    STATUS      current
    DESCRIPTION
        "The value of tmnxIsisSrv6LocatorLevelCap specifies the level in which
         the SRv6 locator will be advertised."
    DEFVAL      { level1L2 }
    ::= { tmnxIsisSrv6LocatorEntry 3 }

tmnxIsisSrv6LocatorTag           OBJECT-TYPE
    SYNTAX      Unsigned32
    MAX-ACCESS  read-create
    STATUS      current
    DESCRIPTION
        "The value of tmnxIsisSrv6LocatorTag specifies the route tag to
         advertise in the SRv6 locator TLV.

         A value of 0 indicates that the tag has not been set."
    DEFVAL      { 0 }
    ::= { tmnxIsisSrv6LocatorEntry 4 }

tmnxIsisSrv6LocatorMultiTopology OBJECT-TYPE
    SYNTAX      BITS {
        mt0 (0),
        mt2 (1)
    }
    MAX-ACCESS  read-create
    STATUS      current
    DESCRIPTION
        "The value of tmnxIsisSrv6LocatorMultiTopology specifies the  multi
         topology in which the SRv6 locator is enabled.

         The locator can be assigned to standard topology (mt0), or IPv6
         routing topology (mt2)."
    DEFVAL      { {mt0} }
    ::= { tmnxIsisSrv6LocatorEntry 5 }

tmnxIsisSrv6LocLevelTable        OBJECT-TYPE
    SYNTAX      SEQUENCE OF TmnxIsisSrv6LocLevelEntry
    MAX-ACCESS  not-accessible
    STATUS      current
    DESCRIPTION
        "The table tmnxIsisSrv6LocLevelTable contains the information
         pertaining to a SRv6 Locator on an ISIS Level."
    ::= { tmnxIsisSystemObjs 33 }

tmnxIsisSrv6LocLevelEntry        OBJECT-TYPE
    SYNTAX      TmnxIsisSrv6LocLevelEntry
    MAX-ACCESS  not-accessible
    STATUS      current
    DESCRIPTION
        "Each row entry in tmnxIsisSrv6LocLevelTable represents the
         configuration for a SRv6 Locator on an ISIS level. Rows for Level 1
         and 2 are created as an action of creating a row in the
         tmnxIsisSrv6LocatorTable."
    INDEX       {
        vRtrID,
        isisSysInstance,
        vRtrSrv6LocatorName,
        tmnxIsisSrv6LocLevel
    }
    ::= { tmnxIsisSrv6LocLevelTable 1 }

TmnxIsisSrv6LocLevelEntry        ::= SEQUENCE
{
    tmnxIsisSrv6LocLevel             INTEGER,
    tmnxIsisSrv6LocLevelLastChanged  TimeStamp,
    tmnxIsisSrv6LocLevelMetric       Unsigned32
}

tmnxIsisSrv6LocLevel             OBJECT-TYPE
    SYNTAX      INTEGER {
        level1 (1),
        level2 (2)
    }
    MAX-ACCESS  not-accessible
    STATUS      current
    DESCRIPTION
        "The value of the object tmnxIsisSrv6LocLevel specifies the IS-IS
         protocol level that this row entry describes."
    ::= { tmnxIsisSrv6LocLevelEntry 1 }

tmnxIsisSrv6LocLevelLastChanged  OBJECT-TYPE
    SYNTAX      TimeStamp
    MAX-ACCESS  read-only
    STATUS      current
    DESCRIPTION
        "The value of tmnxIsisSrv6LocLevelLastChanged indicates the sysUpTime
         when a configurable object in this row was last modified."
    ::= { tmnxIsisSrv6LocLevelEntry 2 }

tmnxIsisSrv6LocLevelMetric       OBJECT-TYPE
    SYNTAX      Unsigned32 (0..16777215)
    MAX-ACCESS  read-create
    STATUS      current
    DESCRIPTION
        "The value of the object tmnxIsisSrv6LocLevelMetric specifies the
         metric value to advertise in this locator for this level.

         A value of 0 means that the metric is not configured; in such a case
         tmnxIsisLevelDefMetric is used for regular interfaces. System and
         loopback interface levels will always have a metric value of 0."
    DEFVAL      { 0 }
    ::= { tmnxIsisSrv6LocLevelEntry 3 }

tmnxIsisSrv6SidTable             OBJECT-TYPE
    SYNTAX      SEQUENCE OF TmnxIsisSrv6SidEntry
    MAX-ACCESS  not-accessible
    STATUS      current
    DESCRIPTION
        "The tmnxIsisSrv6SidTable maintains the SRv6 locators and end-sid's
         learned by an instance of IS-IS protocol for a specific multi topology
         id."
    ::= { tmnxIsisSystemObjs 34 }

tmnxIsisSrv6SidEntry             OBJECT-TYPE
    SYNTAX      TmnxIsisSrv6SidEntry
    MAX-ACCESS  not-accessible
    STATUS      current
    DESCRIPTION
        "Each row entry in the tmnxIsisSrv6SidTable stores a SRV6 locator or
         end-sid for a given instance of the IS-IS protocol for a specific
         multi topology id."
    INDEX       {
        vRtrID,
        isisSysInstance,
        tmnxIsisRouteMtId,
        tmnxIsisRouteDestType,
        tmnxIsisRouteDest,
        tmnxIsisRoutePrefixLength,
        tmnxIsisSrv6SidAdvRtrSysID,
        tmnxIsisSrv6SidLevel,
        tmnxIsisSrv6SidValue
    }
    ::= { tmnxIsisSrv6SidTable 1 }

TmnxIsisSrv6SidEntry             ::= SEQUENCE
{
    tmnxIsisSrv6SidAdvRtrSysID       SystemID,
    tmnxIsisSrv6SidLevel             INTEGER,
    tmnxIsisSrv6SidValue             InetAddressIPv6,
    tmnxIsisSrv6SidType              INTEGER,
    tmnxIsisSrv6SidLocatorFlags      BITS,
    tmnxIsisSrv6SidAlgorithm         TmnxAlgorithmId,
    tmnxIsisSrv6SidAdminTag          Unsigned32,
    tmnxIsisSrv6SidPrefixAttribFlags BITS,
    tmnxIsisSrv6SidEndpointBehavior  TSrv6EndpointBehavior
}

tmnxIsisSrv6SidAdvRtrSysID       OBJECT-TYPE
    SYNTAX      SystemID
    MAX-ACCESS  not-accessible
    STATUS      current
    DESCRIPTION
        "The value of the object tmnxIsisSrv6SidAdvRtrSysID specifies the
         system-id of the advertising IS through which this SID is reachable."
    ::= { tmnxIsisSrv6SidEntry 1 }

tmnxIsisSrv6SidLevel             OBJECT-TYPE
    SYNTAX      INTEGER {
        level1IS (1),
        level2IS (2)
    }
    MAX-ACCESS  not-accessible
    STATUS      current
    DESCRIPTION
        "The value of the object tmnxIsisSrv6SidLevel specifies the IS-IS Level
         at which the SID was learned."
    ::= { tmnxIsisSrv6SidEntry 2 }

tmnxIsisSrv6SidValue             OBJECT-TYPE
    SYNTAX      InetAddressIPv6
    MAX-ACCESS  not-accessible
    STATUS      current
    DESCRIPTION
        "The value of the object tmnxIsisSrv6SidValue specifies the IPv6
         address of the SID."
    ::= { tmnxIsisSrv6SidEntry 3 }

tmnxIsisSrv6SidType              OBJECT-TYPE
    SYNTAX      INTEGER {
        internal (1),
        external (2)
    }
    MAX-ACCESS  read-only
    STATUS      current
    DESCRIPTION
        "The value of the object tmnxIsisSrv6SidType indicates the type of
         route represented by this row entry."
    ::= { tmnxIsisSrv6SidEntry 4 }

tmnxIsisSrv6SidLocatorFlags      OBJECT-TYPE
    SYNTAX      BITS {
        bitD (0)
    }
    MAX-ACCESS  read-only
    STATUS      current
    DESCRIPTION
        "The value of the object tmnxIsisSrv6SidLocatorFlags indicates the
         flags advertised in the SRv6 Locator TLV.

         bitD   (0)  - Down flag.  If set, then the Locator has been leaked
           from Level-2 to Level-1 (only downwards, not upwards to prevent
           looping)."
    ::= { tmnxIsisSrv6SidEntry 5 }

tmnxIsisSrv6SidAlgorithm         OBJECT-TYPE
    SYNTAX      TmnxAlgorithmId
    MAX-ACCESS  read-only
    STATUS      current
    DESCRIPTION
        "The value of the object tmnxIsisSrv6SidAlgorithm indicates the
         algorithm related to the SID.

         The value can indicate a defined IGP Algorithm (value 0 is SPF) or a
         Flexible Algorithm (range 128..255)."
    ::= { tmnxIsisSrv6SidEntry 6 }

tmnxIsisSrv6SidAdminTag          OBJECT-TYPE
    SYNTAX      Unsigned32
    MAX-ACCESS  read-only
    STATUS      current
    DESCRIPTION
        "The value of tmnxIsisSrv6SidAdminTag indicates the  administrative tag
         advertised in the sub-TLV."
    ::= { tmnxIsisSrv6SidEntry 7 }

tmnxIsisSrv6SidPrefixAttribFlags OBJECT-TYPE
    SYNTAX      BITS {
        bitX (0),
        bitR (1),
        bitN (2),
        bitE (3),
        bitA (4)
    }
    MAX-ACCESS  read-only
    STATUS      current
    DESCRIPTION
        "The value of the object tmnxIsisSrv6SidPrefixAttribFlags indicates the
         Prefix Attribute Flags advertised in the sub-TLV.

         bitX   (0)  - External Prefix flag. If set, then the prefix
           has been redistributed from another protocol.
         bitR   (1)  - Re-advertisement flag.  If set, then the prefix
           has been leaked from one level to another (upwards or downwards).
         bitN   (2)  - Node flag. If set, then the prefix identifies the
           advertising router. The advertising router may choose to not set
           this flag.
         bitE   (3)  - ELC flag. If set, then the local host prefix supports
           Entropy Label Capability (ELC) on all interfaces.
         bitA   (4)  - Anycast flag. If set, then the prefix/SRv6 locator
           is configured as anycast."
    ::= { tmnxIsisSrv6SidEntry 8 }

tmnxIsisSrv6SidEndpointBehavior  OBJECT-TYPE
    SYNTAX      TSrv6EndpointBehavior
    MAX-ACCESS  read-only
    STATUS      current
    DESCRIPTION
        "The value of the object tmnxIsisSrv6SidEndpointBehavior indicates the
         SRv6 endpoint behavior advertised in the SID sub-TLV.

         Only the End (PSP, USP, USD) and End.X (PSP, USP, USD) behaviors are
         supported to be advertised by the system;  the other behaviors
         (End.DX6, End.DX4, End.DT6, End.DT4, End.Dt46) may be received by
         ISIS.

         The endpoint behavior may only be advertised by ISIS if  it is
         supported for the SID; i.e. End SIDs may only advertise End behaviors."
    ::= { tmnxIsisSrv6SidEntry 9 }

tmnxIsisSrv6MSLocatorTable       OBJECT-TYPE
    SYNTAX      SEQUENCE OF TmnxIsisSrv6MSLocatorEntry
    MAX-ACCESS  not-accessible
    STATUS      current
    DESCRIPTION
        "The table tmnxIsisSrv6MSLocatorTable contains the information
         pertaining to a SRv6 Micro Segment Locator on an ISIS instance."
    ::= { tmnxIsisSystemObjs 36 }

tmnxIsisSrv6MSLocatorEntry       OBJECT-TYPE
    SYNTAX      TmnxIsisSrv6MSLocatorEntry
    MAX-ACCESS  not-accessible
    STATUS      current
    DESCRIPTION
        "Each row entry in tmnxIsisSrv6MSLocatorTable represents the
         configuration for a SRv6 Micro Segment Locator on an ISIS instance.

         Rows in this table can be created and destroyed by SNMP Set operations
         on the object tmnxIsisSrv6MSLocatorRowStatus"
    INDEX       {
        vRtrID,
        isisSysInstance,
        vRtrSrv6MSLocatorName
    }
    ::= { tmnxIsisSrv6MSLocatorTable 1 }

TmnxIsisSrv6MSLocatorEntry       ::= SEQUENCE
{
    tmnxIsisSrv6MSLocatorLastChanged TimeStamp,
    tmnxIsisSrv6MSLocatorRowStatus   RowStatus,
    tmnxIsisSrv6MSLocatorLevelCap    INTEGER,
    tmnxIsisSrv6MSLocatorTag         Unsigned32,
    tmnxIsisSrv6MSLocatorMultiTopo   BITS
}

tmnxIsisSrv6MSLocatorLastChanged OBJECT-TYPE
    SYNTAX      TimeStamp
    MAX-ACCESS  read-only
    STATUS      current
    DESCRIPTION
        "The value of tmnxIsisSrv6MSLocatorLastChanged indicates the sysUpTime
         when a configurable object in this row was last modified."
    ::= { tmnxIsisSrv6MSLocatorEntry 1 }

tmnxIsisSrv6MSLocatorRowStatus   OBJECT-TYPE
    SYNTAX      RowStatus
    MAX-ACCESS  read-create
    STATUS      current
    DESCRIPTION
        "The value of tmnxIsisSrv6MSLocatorRowStatus specifies the row status
         used for creation, deletion, or control of tmnxIsisSrv6MSLocatorTable
         entries."
    ::= { tmnxIsisSrv6MSLocatorEntry 2 }

tmnxIsisSrv6MSLocatorLevelCap    OBJECT-TYPE
    SYNTAX      INTEGER {
        level1   (1),
        level2   (2),
        level1L2 (3)
    }
    MAX-ACCESS  read-create
    STATUS      current
    DESCRIPTION
        "The value of tmnxIsisSrv6MSLocatorLevelCap specifies the level in
         which the SRv6 micro segment locator will be advertised."
    DEFVAL      { level1L2 }
    ::= { tmnxIsisSrv6MSLocatorEntry 3 }

tmnxIsisSrv6MSLocatorTag         OBJECT-TYPE
    SYNTAX      Unsigned32
    MAX-ACCESS  read-create
    STATUS      current
    DESCRIPTION
        "The value of tmnxIsisSrv6MSLocatorTag specifies the route tag to
         advertise in the SRv6 micro segment locator TLV.

         A value of 0 indicates that the tag has not been set."
    DEFVAL      { 0 }
    ::= { tmnxIsisSrv6MSLocatorEntry 4 }

tmnxIsisSrv6MSLocatorMultiTopo   OBJECT-TYPE
    SYNTAX      BITS {
        mt0 (0),
        mt2 (1)
    }
    MAX-ACCESS  read-create
    STATUS      current
    DESCRIPTION
        "The value of tmnxIsisSrv6MSLocatorMultiTopo specifies the  multi
         topology in which the SRv6 micro segment locator is enabled.

         The locator can be assigned to standard topology (mt0), or IPv6
         routing topology (mt2)."
    DEFVAL      { {mt0} }
    ::= { tmnxIsisSrv6MSLocatorEntry 5 }

tmnxIsisSrv6MSLocLevelTable      OBJECT-TYPE
    SYNTAX      SEQUENCE OF TmnxIsisSrv6MSLocLevelEntry
    MAX-ACCESS  not-accessible
    STATUS      current
    DESCRIPTION
        "The table tmnxIsisSrv6MSLocLevelTable contains the information
         pertaining to a SRv6 Micro Segment Locator on an ISIS Level."
    ::= { tmnxIsisSystemObjs 37 }

tmnxIsisSrv6MSLocLevelEntry      OBJECT-TYPE
    SYNTAX      TmnxIsisSrv6MSLocLevelEntry
    MAX-ACCESS  not-accessible
    STATUS      current
    DESCRIPTION
        "Each row entry in tmnxIsisSrv6MSLocLevelTable represents the
         configuration for a SRv6 Micro Segment Locator on an ISIS level. Rows
         for Level 1 and 2 are created as an action of creating a row in the
         tmnxIsisSrv6MSLocatorTable."
    INDEX       {
        vRtrID,
        isisSysInstance,
        vRtrSrv6MSLocatorName,
        tmnxIsisSrv6MSLocLevel
    }
    ::= { tmnxIsisSrv6MSLocLevelTable 1 }

TmnxIsisSrv6MSLocLevelEntry      ::= SEQUENCE
{
    tmnxIsisSrv6MSLocLevel           INTEGER,
    tmnxIsisSrv6MSLocLevelLastCh     TimeStamp,
    tmnxIsisSrv6MSLocLevelMetric     Unsigned32
}

tmnxIsisSrv6MSLocLevel           OBJECT-TYPE
    SYNTAX      INTEGER {
        level1 (1),
        level2 (2)
    }
    MAX-ACCESS  not-accessible
    STATUS      current
    DESCRIPTION
        "The value of the object tmnxIsisSrv6MSLocLevel specifies the IS-IS
         protocol level that this row entry describes."
    ::= { tmnxIsisSrv6MSLocLevelEntry 1 }

tmnxIsisSrv6MSLocLevelLastCh     OBJECT-TYPE
    SYNTAX      TimeStamp
    MAX-ACCESS  read-only
    STATUS      current
    DESCRIPTION
        "The value of tmnxIsisSrv6MSLocLevelLastCh indicates the sysUpTime when
         a configurable object in this row was last modified."
    ::= { tmnxIsisSrv6MSLocLevelEntry 2 }

tmnxIsisSrv6MSLocLevelMetric     OBJECT-TYPE
    SYNTAX      Unsigned32 (0..16777215)
    MAX-ACCESS  read-create
    STATUS      current
    DESCRIPTION
        "The value of the object tmnxIsisSrv6MSLocLevelMetric specifies the
         metric value to advertise in this locator for this level.

         A value of 0 means that the metric is not configured; in such a case
         tmnxIsisLevelDefMetric is used for regular interfaces. System and
         loopback interface levels will always have a metric value of 0."
    DEFVAL      { 0 }
    ::= { tmnxIsisSrv6MSLocLevelEntry 3 }

tmnxIsisSrv6USidTable            OBJECT-TYPE
    SYNTAX      SEQUENCE OF TmnxIsisSrv6USidEntry
    MAX-ACCESS  not-accessible
    STATUS      current
    DESCRIPTION
        "The tmnxIsisSrv6USidTable maintains the SRv6 micro segment locators
         and USID end-sid's learned by an instance of IS-IS protocol for a
         specific multi topology id."
    ::= { tmnxIsisSystemObjs 38 }

tmnxIsisSrv6USidEntry            OBJECT-TYPE
    SYNTAX      TmnxIsisSrv6USidEntry
    MAX-ACCESS  not-accessible
    STATUS      current
    DESCRIPTION
        "Each row entry in the tmnxIsisSrv6USidTable stores a  SRV6 micro
         segment locator or USID end-sid for a given instance of the IS-IS
         protocol for a specific multi topology id."
    INDEX       {
        vRtrID,
        isisSysInstance,
        tmnxIsisRouteMtId,
        tmnxIsisRouteDestType,
        tmnxIsisRouteDest,
        tmnxIsisRoutePrefixLength,
        tmnxIsisSrv6USidAdvRtrSysID,
        tmnxIsisSrv6USidLevel,
        tmnxIsisSrv6USidValue
    }
    ::= { tmnxIsisSrv6USidTable 1 }

TmnxIsisSrv6USidEntry            ::= SEQUENCE
{
    tmnxIsisSrv6USidAdvRtrSysID      SystemID,
    tmnxIsisSrv6USidLevel            INTEGER,
    tmnxIsisSrv6USidValue            InetAddressIPv6,
    tmnxIsisSrv6USidType             INTEGER,
    tmnxIsisSrv6USidLocatorFlags     BITS,
    tmnxIsisSrv6USidAlgorithm        TmnxAlgorithmId,
    tmnxIsisSrv6USidAdminTag         Unsigned32,
    tmnxIsisSrv6USidPfxAttribFlags   BITS,
    tmnxIsisSrv6USidEndpointBehavior TSrv6EndpointBehavior
}

tmnxIsisSrv6USidAdvRtrSysID      OBJECT-TYPE
    SYNTAX      SystemID
    MAX-ACCESS  not-accessible
    STATUS      current
    DESCRIPTION
        "The value of the object tmnxIsisSrv6USidAdvRtrSysID specifies the
         system-id of the advertising IS through which this USID is reachable."
    ::= { tmnxIsisSrv6USidEntry 1 }

tmnxIsisSrv6USidLevel            OBJECT-TYPE
    SYNTAX      INTEGER {
        level1IS (1),
        level2IS (2)
    }
    MAX-ACCESS  not-accessible
    STATUS      current
    DESCRIPTION
        "The value of the object tmnxIsisSrv6USidLevel specifies the IS-IS
         Level at which the USID was learned."
    ::= { tmnxIsisSrv6USidEntry 2 }

tmnxIsisSrv6USidValue            OBJECT-TYPE
    SYNTAX      InetAddressIPv6
    MAX-ACCESS  not-accessible
    STATUS      current
    DESCRIPTION
        "The value of the object tmnxIsisSrv6USidValue specifies the IPv6
         address of the USID."
    ::= { tmnxIsisSrv6USidEntry 3 }

tmnxIsisSrv6USidType             OBJECT-TYPE
    SYNTAX      INTEGER {
        internal (1),
        external (2)
    }
    MAX-ACCESS  read-only
    STATUS      current
    DESCRIPTION
        "The value of the object tmnxIsisSrv6USidType indicates the type of
         route represented by this row entry."
    ::= { tmnxIsisSrv6USidEntry 4 }

tmnxIsisSrv6USidLocatorFlags     OBJECT-TYPE
    SYNTAX      BITS {
        bitD (0)
    }
    MAX-ACCESS  read-only
    STATUS      current
    DESCRIPTION
        "The value of the object tmnxIsisSrv6USidLocatorFlags indicates the
         flags advertised in the SRv6 micro segment locator TLV.

         bitD   (0)  - Down flag.  If set, then the locator has been leaked
           from Level-2 to Level-1 (only downwards, not upwards to prevent
           looping)."
    ::= { tmnxIsisSrv6USidEntry 5 }

tmnxIsisSrv6USidAlgorithm        OBJECT-TYPE
    SYNTAX      TmnxAlgorithmId
    MAX-ACCESS  read-only
    STATUS      current
    DESCRIPTION
        "The value of the object tmnxIsisSrv6USidAlgorithm indicates the
         algorithm related to the USID.

         The value can indicate a defined IGP Algorithm (value 0 is SPF) or a
         Flexible Algorithm (range 128..255)."
    ::= { tmnxIsisSrv6USidEntry 6 }

tmnxIsisSrv6USidAdminTag         OBJECT-TYPE
    SYNTAX      Unsigned32
    MAX-ACCESS  read-only
    STATUS      current
    DESCRIPTION
        "The value of tmnxIsisSrv6USidAdminTag indicates the  administrative
         tag advertised in the sub-TLV."
    ::= { tmnxIsisSrv6USidEntry 7 }

tmnxIsisSrv6USidPfxAttribFlags   OBJECT-TYPE
    SYNTAX      BITS {
        bitX (0),
        bitR (1),
        bitN (2),
        bitE (3),
        bitA (4)
    }
    MAX-ACCESS  read-only
    STATUS      current
    DESCRIPTION
        "The value of the object tmnxIsisSrv6USidPfxAttribFlags indicates the
         Prefix Attribute Flags advertised in the sub-TLV.

         bitX   (0)  - External Prefix flag. If set, then the prefix
           has been redistributed from another protocol.
         bitR   (1)  - Re-advertisement flag.  If set, then the prefix
           has been leaked from one level to another (upwards or downwards).
         bitN   (2)  - Node flag. If set, then the prefix identifies the
           advertising router. The advertising router may choose to not set
           this flag.
         bitE   (3)  - ELC flag. If set, then the local host prefix supports
           Entropy Label Capability (ELC) on all interfaces.
         bitA   (4)  - Anycast flag. If set, then the prefix/SRv6 locator
           is configured as anycast."
    ::= { tmnxIsisSrv6USidEntry 8 }

tmnxIsisSrv6USidEndpointBehavior OBJECT-TYPE
    SYNTAX      TSrv6EndpointBehavior
    MAX-ACCESS  read-only
    STATUS      current
    DESCRIPTION
        "The value of the object tmnxIsisSrv6USidEndpointBehavior indicates the
         SRv6 endpoint behavior advertised in the USID sub-TLV.

         Only the End (PSP, USP, USD) and End.X (PSP, USP, USD) behaviors are
         supported to be advertised by the system;  the other behaviors
         (End.DX6, End.DX4, End.DT6, End.DT4, End.Dt46) may be received by
         ISIS.

         The endpoint behavior may only be advertised by ISIS if  it is
         supported for the SID; i.e. End SID's may only advertise End
         behaviors."
    ::= { tmnxIsisSrv6USidEntry 9 }

tmnxIsisSrSidRouteTable          OBJECT-TYPE
    SYNTAX      SEQUENCE OF TmnxIsisSrSidRouteEntry
    MAX-ACCESS  not-accessible
    STATUS      current
    DESCRIPTION
        "The tmnxIsisSrSidRouteTable contains backup path information  for a
         particular ISIS segment-routing sid prefix."
    ::= { tmnxIsisSystemObjs 39 }

tmnxIsisSrSidRouteEntry          OBJECT-TYPE
    SYNTAX      TmnxIsisSrSidRouteEntry
    MAX-ACCESS  not-accessible
    STATUS      current
    DESCRIPTION
        "Each row entry in the tmnxIsisSrSidRouteTable stores backup path
         information for a particular ISIS segment-routing sid prefix."
    INDEX       {
        vRtrID,
        isisSysInstance,
        tmnxIsisSrSidRouteAlgorithm,
        tmnxIsisSrSidRouteMtId,
        tmnxIsisSrSidRouteDestType,
        tmnxIsisSrSidRouteDest,
        tmnxIsisSrSidRoutePrefixLength
    }
    ::= { tmnxIsisSrSidRouteTable 1 }

TmnxIsisSrSidRouteEntry          ::= SEQUENCE
{
    tmnxIsisSrSidRouteAlgorithm      TmnxAlgorithmId,
    tmnxIsisSrSidRouteMtId           Unsigned32,
    tmnxIsisSrSidRouteDestType       InetAddressType,
    tmnxIsisSrSidRouteDest           InetAddress,
    tmnxIsisSrSidRoutePrefixLength   InetAddressPrefixLength,
    tmnxIsisSrSidRoutePrimPathIpType InetAddressType,
    tmnxIsisSrSidRoutePrimPathIp     InetAddress,
    tmnxIsisSrSidRouteBkupPathType   INTEGER,
    tmnxIsisSrSidRouteBkupProtection INTEGER,
    tmnxIsisSrSidRouteBkupPathIpType InetAddressType,
    tmnxIsisSrSidRouteBkupPathIp     InetAddress,
    tmnxIsisSrSidRouteBkupNodesCount Unsigned32
}

tmnxIsisSrSidRouteAlgorithm      OBJECT-TYPE
    SYNTAX      TmnxAlgorithmId
    MAX-ACCESS  not-accessible
    STATUS      current
    DESCRIPTION
        "The value of the object tmnxIsisSrSidRouteAlgorithm specifies the
         algorithm related to the SR route.

         The value can indicate a defined IGP Algorithm (value 0 is SPF) or a
         Flexible Algorithm (range 128..255)."
    ::= { tmnxIsisSrSidRouteEntry 1 }

tmnxIsisSrSidRouteMtId           OBJECT-TYPE
    SYNTAX      Unsigned32
    MAX-ACCESS  not-accessible
    STATUS      current
    DESCRIPTION
        "The value of the object tmnxIsisSrSidRouteMtId specifies the multi
         topology id number for this SR route.

         If multi-topology is not supported for the route then the value of
         tmnxIsisSrSidRouteMtId should be 0."
    ::= { tmnxIsisSrSidRouteEntry 2 }

tmnxIsisSrSidRouteDestType       OBJECT-TYPE
    SYNTAX      InetAddressType
    MAX-ACCESS  not-accessible
    STATUS      current
    DESCRIPTION
        "The value of the object tmnxIsisSrSidRouteDestType specifies the IP
         address type for tmnxIsisSrSidRouteDest."
    ::= { tmnxIsisSrSidRouteEntry 3 }

tmnxIsisSrSidRouteDest           OBJECT-TYPE
    SYNTAX      InetAddress (SIZE (4|16|20))
    MAX-ACCESS  not-accessible
    STATUS      current
    DESCRIPTION
        "The value of the object tmnxIsisSrSidRouteDest specifies the
         destination IP address of this route.

         The address type of tmnxIsisSrSidRouteDest is indicated by
         tmnxIsisSrSidRouteDestType."
    ::= { tmnxIsisSrSidRouteEntry 4 }

tmnxIsisSrSidRoutePrefixLength   OBJECT-TYPE
    SYNTAX      InetAddressPrefixLength
    MAX-ACCESS  not-accessible
    STATUS      current
    DESCRIPTION
        "The value of the object tmnxIsisSrSidRoutePrefixLength specifies the
         prefix length to be used with tmnxIsisSrSidRouteDest to get the
         network prefix."
    ::= { tmnxIsisSrSidRouteEntry 5 }

tmnxIsisSrSidRoutePrimPathIpType OBJECT-TYPE
    SYNTAX      InetAddressType
    MAX-ACCESS  read-only
    STATUS      current
    DESCRIPTION
        "The value of the object tmnxIsisSrSidRoutePrimPathIpType indicates the
         IP address type for tmnxIsisSrSidRoutePrimPathIp."
    ::= { tmnxIsisSrSidRouteEntry 6 }

tmnxIsisSrSidRoutePrimPathIp     OBJECT-TYPE
    SYNTAX      InetAddress (SIZE (4|16|20))
    MAX-ACCESS  read-only
    STATUS      current
    DESCRIPTION
        "The value of the object tmnxIsisSrSidRoutePrimPathIp indicates the IP
         address of the nexthop for this route.

         The address type of tmnxIsisSrSidRoutePrimPathIp is indicated by
         tmnxIsisSrSidRoutePrimPathIpType"
    ::= { tmnxIsisSrSidRouteEntry 7 }

tmnxIsisSrSidRouteBkupPathType   OBJECT-TYPE
    SYNTAX      INTEGER {
        lfa   (0),
        tiLfa (1),
        rLfa  (2)
    }
    MAX-ACCESS  read-only
    STATUS      current
    DESCRIPTION
        "The value of the object tmnxIsisSrSidRouteBkupPathType indicates the
         type of LFA used by the backup path."
    ::= { tmnxIsisSrSidRouteEntry 8 }

tmnxIsisSrSidRouteBkupProtection OBJECT-TYPE
    SYNTAX      INTEGER {
        notApplicable  (0),
        nodeProtection (1),
        linkProtection (2)
    }
    MAX-ACCESS  read-only
    STATUS      current
    DESCRIPTION
        "The value of the object tmnxIsisSrSidRouteBkupProtection  indicates
         the type of protection used by the backup next-hop.

         The value 'notApplicable' indicates that the backup next-hop type is
         not applicable; the value 'nodeProtection' indicates that the backup
         next-hop uses a node-protection mechanism; the value 'linkProtection'
         indicates that the backup next-hop uses link-protection mechanism."
    ::= { tmnxIsisSrSidRouteEntry 9 }

tmnxIsisSrSidRouteBkupPathIpType OBJECT-TYPE
    SYNTAX      InetAddressType
    MAX-ACCESS  read-only
    STATUS      current
    DESCRIPTION
        "The value of the object tmnxIsisSrSidRouteBkupPathIpType indicates the
         IP address type for tmnxIsisSrSidRouteBkupPathIp."
    ::= { tmnxIsisSrSidRouteEntry 10 }

tmnxIsisSrSidRouteBkupPathIp     OBJECT-TYPE
    SYNTAX      InetAddress (SIZE (0|4|16|20))
    MAX-ACCESS  read-only
    STATUS      current
    DESCRIPTION
        "The value of the object tmnxIsisSrSidRouteBkupPathIp indicates the IP
         address of a backup path.

         The address type of tmnxIsisSrSidRouteBkupPathIp is indicated by the
         value of tmnxIsisSrSidRouteBkupPathIpType."
    ::= { tmnxIsisSrSidRouteEntry 11 }

tmnxIsisSrSidRouteBkupNodesCount OBJECT-TYPE
    SYNTAX      Unsigned32
    MAX-ACCESS  read-only
    STATUS      current
    DESCRIPTION
        "The value of the object tmnxIsisSrSidRouteBkupNodesCount indicates the
         number of backup nodes, needed for the LFA backup."
    ::= { tmnxIsisSrSidRouteEntry 12 }

tmnxIsisSrSidBackupNodeTable     OBJECT-TYPE
    SYNTAX      SEQUENCE OF TmnxIsisSrSidBackupNodeEntry
    MAX-ACCESS  not-accessible
    STATUS      current
    DESCRIPTION
        "The tmnxIsisSrSidBackupNodeTable contains the information of the PQ
         nodes used in the backup path for a particular sid prefix."
    ::= { tmnxIsisSystemObjs 40 }

tmnxIsisSrSidBackupNodeEntry     OBJECT-TYPE
    SYNTAX      TmnxIsisSrSidBackupNodeEntry
    MAX-ACCESS  not-accessible
    STATUS      current
    DESCRIPTION
        "Each row entry in the tmnxIsisSrSidBackupNodeTable stores the
         information of a PQ node used in the backup path for a particular sid
         prefix."
    INDEX       {
        vRtrID,
        isisSysInstance,
        tmnxIsisSrSidRouteAlgorithm,
        tmnxIsisSrSidRouteMtId,
        tmnxIsisSrSidRouteDestType,
        tmnxIsisSrSidRouteDest,
        tmnxIsisSrSidRoutePrefixLength,
        tmnxIsisSrSidBkUpNodeSysID,
        tmnxIsisSrSidBkUpNodeSidValue
    }
    ::= { tmnxIsisSrSidBackupNodeTable 1 }

TmnxIsisSrSidBackupNodeEntry     ::= SEQUENCE
{
    tmnxIsisSrSidBkUpNodeSysID       SystemID,
    tmnxIsisSrSidBkUpNodeType        INTEGER,
    tmnxIsisSrSidBkUpNodeSidValue    Unsigned32,
    tmnxIsisSrSidBkUpNodeSidLblType  INTEGER
}

tmnxIsisSrSidBkUpNodeSysID       OBJECT-TYPE
    SYNTAX      SystemID
    MAX-ACCESS  not-accessible
    STATUS      current
    DESCRIPTION
        "The value of the object tmnxIsisSrSidBkUpNodeSysID specifies the
         system-id of the node."
    ::= { tmnxIsisSrSidBackupNodeEntry 1 }

tmnxIsisSrSidBkUpNodeType        OBJECT-TYPE
    SYNTAX      INTEGER {
        pNode  (1),
        pqNode (2),
        trNode (3),
        qNode  (4)
    }
    MAX-ACCESS  read-only
    STATUS      current
    DESCRIPTION
        "The value of the object tmnxIsisSrSidBkUpNodeType indicates the node
         type."
    ::= { tmnxIsisSrSidBackupNodeEntry 2 }

tmnxIsisSrSidBkUpNodeSidValue    OBJECT-TYPE
    SYNTAX      Unsigned32
    MAX-ACCESS  read-only
    STATUS      current
    DESCRIPTION
        "The value of the object tmnxIsisSrSidBkUpNodeSidValue indicates the
         SID label or index for this node."
    ::= { tmnxIsisSrSidBackupNodeEntry 3 }

tmnxIsisSrSidBkUpNodeSidLblType  OBJECT-TYPE
    SYNTAX      INTEGER {
        adjacencylbl (1),
        prefixlbl    (2)
    }
    MAX-ACCESS  read-only
    STATUS      current
    DESCRIPTION
        "The value of the object tmnxIsisSrSidBkUpNodeSidLblType indicates the
         label is node-prefix or adjacency label."
    ::= { tmnxIsisSrSidBackupNodeEntry 4 }

tmnxIsisSr6SidRouteTable         OBJECT-TYPE
    SYNTAX      SEQUENCE OF TmnxIsisSr6SidRouteEntry
    MAX-ACCESS  not-accessible
    STATUS      current
    DESCRIPTION
        "The tmnxIsisSr6SidRouteTable contains backup path information  for a
         particular ISIS segment-routing sid prefix."
    ::= { tmnxIsisSystemObjs 41 }

tmnxIsisSr6SidRouteEntry         OBJECT-TYPE
    SYNTAX      TmnxIsisSr6SidRouteEntry
    MAX-ACCESS  not-accessible
    STATUS      current
    DESCRIPTION
        "Each row entry in the tmnxIsisSr6SidRouteTable stores backup path
         information for a particular ISIS segment-routing sid prefix."
    INDEX       {
        vRtrID,
        isisSysInstance,
        tmnxIsisSr6SidRouteAlgorithm,
        tmnxIsisSr6SidRouteMtId,
        tmnxIsisSr6SidRouteDestType,
        tmnxIsisSr6SidRouteDest,
        tmnxIsisSr6SidRoutePrefixLength
    }
    ::= { tmnxIsisSr6SidRouteTable 1 }

TmnxIsisSr6SidRouteEntry         ::= SEQUENCE
{
    tmnxIsisSr6SidRouteAlgorithm     TmnxAlgorithmId,
    tmnxIsisSr6SidRouteMtId          Unsigned32,
    tmnxIsisSr6SidRouteDestType      InetAddressType,
    tmnxIsisSr6SidRouteDest          InetAddress,
    tmnxIsisSr6SidRoutePrefixLength  InetAddressPrefixLength,
    tmnxIsisSr6SidRoutePriPathIpType InetAddressType,
    tmnxIsisSr6SidRoutePrimPathIp    InetAddress,
    tmnxIsisSr6SidRouteBkPathType    INTEGER,
    tmnxIsisSr6SidRouteBkProtection  INTEGER,
    tmnxIsisSr6SidRouteBkPathIpType  InetAddressType,
    tmnxIsisSr6SidRouteBkPathIp      InetAddress,
    tmnxIsisSr6SidBkComprAddrTyp     InetAddressType,
    tmnxIsisSr6SidBkComprAddr        InetAddress,
    tmnxIsisSr6SidRouteBkNodesCount  Unsigned32
}

tmnxIsisSr6SidRouteAlgorithm     OBJECT-TYPE
    SYNTAX      TmnxAlgorithmId
    MAX-ACCESS  not-accessible
    STATUS      current
    DESCRIPTION
        "The value of the object tmnxIsisSr6SidRouteAlgorithm specifies the
         algorithm related to the SR route.

         The value can indicate a defined IGP Algorithm (value 0 is SPF) or a
         Flexible Algorithm (range 128..255)."
    ::= { tmnxIsisSr6SidRouteEntry 1 }

tmnxIsisSr6SidRouteMtId          OBJECT-TYPE
    SYNTAX      Unsigned32
    MAX-ACCESS  not-accessible
    STATUS      current
    DESCRIPTION
        "The value of the object tmnxIsisSr6SidRouteMtId specifies the multi
         topology id number for this SR route.

         If multi-topology is not supported for the route then the value of
         tmnxIsisSr6SidRouteMtId should be 0."
    ::= { tmnxIsisSr6SidRouteEntry 2 }

tmnxIsisSr6SidRouteDestType      OBJECT-TYPE
    SYNTAX      InetAddressType
    MAX-ACCESS  not-accessible
    STATUS      current
    DESCRIPTION
        "The value of the object tmnxIsisSr6SidRouteDestType specifies the IP
         address type for tmnxIsisSr6SidRouteDest."
    ::= { tmnxIsisSr6SidRouteEntry 3 }

tmnxIsisSr6SidRouteDest          OBJECT-TYPE
    SYNTAX      InetAddress (SIZE (4|16|20))
    MAX-ACCESS  not-accessible
    STATUS      current
    DESCRIPTION
        "The value of the object tmnxIsisSr6SidRouteDest specifies the
         destination IP address of this route.

         The address type of tmnxIsisSr6SidRouteDest is indicated by
         tmnxIsisSr6SidRouteDestType."
    ::= { tmnxIsisSr6SidRouteEntry 4 }

tmnxIsisSr6SidRoutePrefixLength  OBJECT-TYPE
    SYNTAX      InetAddressPrefixLength
    MAX-ACCESS  not-accessible
    STATUS      current
    DESCRIPTION
        "The value of the object tmnxIsisSr6SidRoutePrefixLength specifies the
         prefix length to be used with tmnxIsisSr6SidRouteDest to get the
         network prefix."
    ::= { tmnxIsisSr6SidRouteEntry 5 }

tmnxIsisSr6SidRoutePriPathIpType OBJECT-TYPE
    SYNTAX      InetAddressType
    MAX-ACCESS  read-only
    STATUS      current
    DESCRIPTION
        "The value of the object tmnxIsisSr6SidRoutePriPathIpType indicates the
         IP address type for tmnxIsisSr6SidRoutePrimPathIp."
    ::= { tmnxIsisSr6SidRouteEntry 6 }

tmnxIsisSr6SidRoutePrimPathIp    OBJECT-TYPE
    SYNTAX      InetAddress (SIZE (4|16|20))
    MAX-ACCESS  read-only
    STATUS      current
    DESCRIPTION
        "The value of the object tmnxIsisSr6SidRoutePrimPathIp indicates the IP
         address of the nexthop for this route.

         The address type of tmnxIsisSr6SidRoutePrimPathIp is indicated by
         tmnxIsisSr6SidRoutePriPathIpType"
    ::= { tmnxIsisSr6SidRouteEntry 7 }

tmnxIsisSr6SidRouteBkPathType    OBJECT-TYPE
    SYNTAX      INTEGER {
        lfa   (0),
        tiLfa (1),
        rLfa  (2)
    }
    MAX-ACCESS  read-only
    STATUS      current
    DESCRIPTION
        "The value of the object tmnxIsisSr6SidRouteBkPathType indicates the
         type of LFA used by the backup path."
    ::= { tmnxIsisSr6SidRouteEntry 8 }

tmnxIsisSr6SidRouteBkProtection  OBJECT-TYPE
    SYNTAX      INTEGER {
        notApplicable  (0),
        nodeProtection (1),
        linkProtection (2)
    }
    MAX-ACCESS  read-only
    STATUS      current
    DESCRIPTION
        "The value of the object tmnxIsisSr6SidRouteBkProtection  indicates the
         type of protection used by the backup next-hop.

         The value 'notApplicable' indicates that the backup next-hop type is
         not applicable; the value 'nodeProtection' indicates that the backup
         next-hop uses a node-protection mechanism; the value 'linkProtection'
         indicates that the backup next-hop uses link-protection mechanism."
    ::= { tmnxIsisSr6SidRouteEntry 9 }

tmnxIsisSr6SidRouteBkPathIpType  OBJECT-TYPE
    SYNTAX      InetAddressType
    MAX-ACCESS  read-only
    STATUS      current
    DESCRIPTION
        "The value of the object tmnxIsisSr6SidRouteBkPathIpType indicates the
         IP address type for tmnxIsisSr6SidRouteBkPathIp."
    ::= { tmnxIsisSr6SidRouteEntry 10 }

tmnxIsisSr6SidRouteBkPathIp      OBJECT-TYPE
    SYNTAX      InetAddress (SIZE (0|4|16|20))
    MAX-ACCESS  read-only
    STATUS      current
    DESCRIPTION
        "The value of the object tmnxIsisSr6SidRouteBkPathIp indicates the IP
         address of a backup path.

         The address type of tmnxIsisSr6SidRouteBkPathIp is indicated by the
         value of tmnxIsisSr6SidRouteBkPathIpType."
    ::= { tmnxIsisSr6SidRouteEntry 11 }

tmnxIsisSr6SidBkComprAddrTyp     OBJECT-TYPE
    SYNTAX      InetAddressType
    MAX-ACCESS  read-only
    STATUS      current
    DESCRIPTION
        "The value of the object tmnxIsisSr6SidBkComprAddrTyp indicates the IP
         address type of tmnxIsisSr6SidBkComprAddr."
    ::= { tmnxIsisSr6SidRouteEntry 12 }

tmnxIsisSr6SidBkComprAddr        OBJECT-TYPE
    SYNTAX      InetAddress (SIZE (0|16))
    MAX-ACCESS  read-only
    STATUS      current
    DESCRIPTION
        "The value of the object tmnxIsisSr6SidBkComprAddr indicates the IPv6
         address of the compressed SID."
    ::= { tmnxIsisSr6SidRouteEntry 13 }

tmnxIsisSr6SidRouteBkNodesCount  OBJECT-TYPE
    SYNTAX      Unsigned32
    MAX-ACCESS  read-only
    STATUS      current
    DESCRIPTION
        "The value of the object tmnxIsisSr6SidRouteBkNodesCount indicates the
         number of backup nodes, needed for the LFA backup."
    ::= { tmnxIsisSr6SidRouteEntry 14 }

tmnxIsisSr6SidBackupNodeTable    OBJECT-TYPE
    SYNTAX      SEQUENCE OF TmnxIsisSr6SidBackupNodeEntry
    MAX-ACCESS  not-accessible
    STATUS      current
    DESCRIPTION
        "The tmnxIsisSr6SidBackupNodeTable contains the information of the PQ
         nodes used in the backup path for a particular sid prefix."
    ::= { tmnxIsisSystemObjs 42 }

tmnxIsisSr6SidBackupNodeEntry    OBJECT-TYPE
    SYNTAX      TmnxIsisSr6SidBackupNodeEntry
    MAX-ACCESS  not-accessible
    STATUS      current
    DESCRIPTION
        "Each row entry in the tmnxIsisSr6SidBackupNodeTable stores the
         information of a PQ node used in the backup path for a particular sid
         prefix."
    INDEX       {
        vRtrID,
        isisSysInstance,
        tmnxIsisSr6SidRouteAlgorithm,
        tmnxIsisSr6SidRouteMtId,
        tmnxIsisSr6SidRouteDestType,
        tmnxIsisSr6SidRouteDest,
        tmnxIsisSr6SidRoutePrefixLength,
        tmnxIsisSr6SidBkNodeSysID
    }
    ::= { tmnxIsisSr6SidBackupNodeTable 1 }

TmnxIsisSr6SidBackupNodeEntry    ::= SEQUENCE
{
    tmnxIsisSr6SidBkNodeSysID        SystemID,
    tmnxIsisSr6SidBkNodeType         INTEGER,
    tmnxIsisSr6SidBkNodeSidAddrType  InetAddressType,
    tmnxIsisSr6SidBkNodeSidAddr      InetAddress,
    tmnxIsisSr6SidBkNodeEndPointBeh  TSrv6EndpointBehavior,
    tmnxIsisSr6SidBkNodeSidType      INTEGER,
    tmnxIsisSr6SidBkNodeSrhMode      INTEGER,
    tmnxIsisSr6SidBkNodePrtMode      INTEGER
}

tmnxIsisSr6SidBkNodeSysID        OBJECT-TYPE
    SYNTAX      SystemID
    MAX-ACCESS  not-accessible
    STATUS      current
    DESCRIPTION
        "The value of the object tmnxIsisSr6SidBkNodeSysID specifies the
         system-id of the node."
    ::= { tmnxIsisSr6SidBackupNodeEntry 1 }

tmnxIsisSr6SidBkNodeType         OBJECT-TYPE
    SYNTAX      INTEGER {
        pNode  (1),
        pqNode (2),
        trNode (3),
        qNode  (4)
    }
    MAX-ACCESS  read-only
    STATUS      current
    DESCRIPTION
        "The value of the object tmnxIsisSr6SidBkNodeType indicates the node
         type."
    ::= { tmnxIsisSr6SidBackupNodeEntry 2 }

tmnxIsisSr6SidBkNodeSidAddrType  OBJECT-TYPE
    SYNTAX      InetAddressType
    MAX-ACCESS  read-only
    STATUS      current
    DESCRIPTION
        "The value of the object tmnxIsisSr6SidBkNodeSidAddrType indicates the
         IP address type of tmnxIsisSr6SidBkNodeSidAddr."
    ::= { tmnxIsisSr6SidBackupNodeEntry 3 }

tmnxIsisSr6SidBkNodeSidAddr      OBJECT-TYPE
    SYNTAX      InetAddress (SIZE (0|16))
    MAX-ACCESS  read-only
    STATUS      current
    DESCRIPTION
        "The value of the object tmnxIsisSr6SidBkNodeSidAddr indicates the IPv6
         address of the SID."
    ::= { tmnxIsisSr6SidBackupNodeEntry 4 }

tmnxIsisSr6SidBkNodeEndPointBeh  OBJECT-TYPE
    SYNTAX      TSrv6EndpointBehavior
    MAX-ACCESS  read-only
    STATUS      current
    DESCRIPTION
        "The value of the object tmnxIsisSr6SidBkNodeEndPointBeh indicates the
         SRv6 endpoint behavior advertised in the SID sub-TLV."
    ::= { tmnxIsisSr6SidBackupNodeEntry 5 }

tmnxIsisSr6SidBkNodeSidType      OBJECT-TYPE
    SYNTAX      INTEGER {
        end  (1),
        endX (2),
        uN   (3),
        uA   (4)
    }
    MAX-ACCESS  read-only
    STATUS      current
    DESCRIPTION
        "The value of the object tmnxIsisSr6SidBkNodeSidType indicates the type
         of backup node SRv6 sid."
    ::= { tmnxIsisSr6SidBackupNodeEntry 6 }

tmnxIsisSr6SidBkNodeSrhMode      OBJECT-TYPE
    SYNTAX      INTEGER {
        srhModePsp       (0),
        srhModeUsp       (1),
        srhModePspUsd    (2),
        srhModeUspUsd    (3),
        srhModePspUspUsd (4)
    }
    MAX-ACCESS  read-only
    STATUS      current
    DESCRIPTION
        "The value of the object tmnxIsisSr6SidBkNodeSrhMode  indicates the SRH
         (Segment-Routing Header) mode for a particular backup node end-point."
    ::= { tmnxIsisSr6SidBackupNodeEntry 7 }

tmnxIsisSr6SidBkNodePrtMode      OBJECT-TYPE
    SYNTAX      INTEGER {
        unprotected (1),
        protected   (2)
    }
    MAX-ACCESS  read-only
    STATUS      current
    DESCRIPTION
        "The value of the object tmnxIsisSr6SidBkNodePrtMode indicates whether
         the endx.Sid to the backup node is protected or not."
    ::= { tmnxIsisSr6SidBackupNodeEntry 8 }

tmnxIsisUnreachableRteSentTable  OBJECT-TYPE
    SYNTAX      SEQUENCE OF TmnxIsisUnreachableRteSentEntry
    MAX-ACCESS  not-accessible
    STATUS      current
    DESCRIPTION
        "The tmnxIsisUnreachableRteSentTable maintains the unreachable routes
         from the originated Unreachable Prefix Announcements (UPA)."
    ::= { tmnxIsisSystemObjs 43 }

tmnxIsisUnreachableRteSentEntry  OBJECT-TYPE
    SYNTAX      TmnxIsisUnreachableRteSentEntry
    MAX-ACCESS  not-accessible
    STATUS      current
    DESCRIPTION
        "Each row entry in the tmnxIsisUnreachableRteSentTable stores an
         unreachable route for a given instance of the IS-IS protocol
         for a specific multi topology id that is being sent in an UPA."
    INDEX       {
        vRtrID,
        isisSysInstance,
        tmnxIsisUpaSentAlgorithm,
        tmnxIsisUpaSentLevel,
        tmnxIsisUpaSentMtId,
        tmnxIsisUpaSentDestType,
        tmnxIsisUpaSentDest,
        tmnxIsisUpaSentPrefixLength
    }
    ::= { tmnxIsisUnreachableRteSentTable 1 }

TmnxIsisUnreachableRteSentEntry  ::= SEQUENCE
{
    tmnxIsisUpaSentAlgorithm         TmnxAlgorithmId,
    tmnxIsisUpaSentLevel             INTEGER,
    tmnxIsisUpaSentMtId              Unsigned32,
    tmnxIsisUpaSentDestType          InetAddressType,
    tmnxIsisUpaSentDest              InetAddress,
    tmnxIsisUpaSentPrefixLength      InetAddressPrefixLength,
    tmnxIsisUpaSentSpfRunNumber      Counter32,
    tmnxIsisUpaSentMetric            Unsigned32,
    tmnxIsisUpaSentType              INTEGER,
    tmnxIsisUpaSentSysID             SystemID,
    tmnxIsisUpaSentTag               Unsigned32,
    tmnxIsisUpaSentLifetimeRemain    Unsigned32
}

tmnxIsisUpaSentAlgorithm         OBJECT-TYPE
    SYNTAX      TmnxAlgorithmId
    MAX-ACCESS  not-accessible
    STATUS      current
    DESCRIPTION
        "The value of the object tmnxIsisUpaSentAlgorithm specifies the
         algorithm.

         The value can indicate a defined IGP Algorithm (value 0 is SPF) or a
         Flexible Algorithm (range 128..255)."
    ::= { tmnxIsisUnreachableRteSentEntry 1 }

tmnxIsisUpaSentLevel             OBJECT-TYPE
    SYNTAX      INTEGER {
        level1IS (1),
        level2IS (2)
    }
    MAX-ACCESS  not-accessible
    STATUS      current
    DESCRIPTION
        "The value of the object tmnxIsisUpaSentLevel specifies the IS-IS
         Level."
    ::= { tmnxIsisUnreachableRteSentEntry 2 }

tmnxIsisUpaSentMtId              OBJECT-TYPE
    SYNTAX      Unsigned32
    MAX-ACCESS  not-accessible
    STATUS      current
    DESCRIPTION
        "The value of the object tmnxIsisUpaSentMtId specifies the multi
         topology id number for this originated unreachable route.

         If multi-topology is not supported for the route then the value of
         tmnxIsisUpaSentMtId will be 0."
    ::= { tmnxIsisUnreachableRteSentEntry 3 }

tmnxIsisUpaSentDestType          OBJECT-TYPE
    SYNTAX      InetAddressType
    MAX-ACCESS  not-accessible
    STATUS      current
    DESCRIPTION
        "The value of the object tmnxIsisUpaSentDestType specifies the IP
         address type for tmnxIsisUpaSentDest."
    ::= { tmnxIsisUnreachableRteSentEntry 4 }

tmnxIsisUpaSentDest              OBJECT-TYPE
    SYNTAX      InetAddress (SIZE (4|16|20))
    MAX-ACCESS  not-accessible
    STATUS      current
    DESCRIPTION
        "The value of the object tmnxIsisUpaSentDest specifies the destination
         IP address of this originated unreachable route.

         The address type of tmnxIsisUpaSentDest is indicated by
         tmnxIsisUpaSentDestType."
    ::= { tmnxIsisUnreachableRteSentEntry 5 }

tmnxIsisUpaSentPrefixLength      OBJECT-TYPE
    SYNTAX      InetAddressPrefixLength
    MAX-ACCESS  not-accessible
    STATUS      current
    DESCRIPTION
        "The value of the object tmnxIsisUpaSentPrefixLength specifies the
         prefix length to be used with tmnxIsisUpaSentDest to get the network
         prefix."
    ::= { tmnxIsisUnreachableRteSentEntry 6 }

tmnxIsisUpaSentSpfRunNumber      OBJECT-TYPE
    SYNTAX      Counter32
    MAX-ACCESS  read-only
    STATUS      current
    DESCRIPTION
        "The value of the object tmnxIsisUpaSentSpfRunNumber indicates the run
         of spf calculation in which this route was selected."
    ::= { tmnxIsisUnreachableRteSentEntry 7 }

tmnxIsisUpaSentMetric            OBJECT-TYPE
    SYNTAX      Unsigned32
    MAX-ACCESS  read-only
    STATUS      current
    DESCRIPTION
        "The value of the object tmnxIsisUpaSentMetric indicates the metric
         value that is advertised in the UPA that is being sent."
    ::= { tmnxIsisUnreachableRteSentEntry 8 }

tmnxIsisUpaSentType              OBJECT-TYPE
    SYNTAX      INTEGER {
        internal (1),
        external (2)
    }
    MAX-ACCESS  read-only
    STATUS      current
    DESCRIPTION
        "The value of the object tmnxIsisUpaSentType indicates the type of
         route represented by this row entry."
    ::= { tmnxIsisUnreachableRteSentEntry 9 }

tmnxIsisUpaSentSysID             OBJECT-TYPE
    SYNTAX      SystemID
    MAX-ACCESS  read-only
    STATUS      current
    DESCRIPTION
        "The value of the object tmnxIsisUpaSentSysID indicates the system-id
         of this route."
    ::= { tmnxIsisUnreachableRteSentEntry 10 }

tmnxIsisUpaSentTag               OBJECT-TYPE
    SYNTAX      Unsigned32
    MAX-ACCESS  read-only
    STATUS      current
    DESCRIPTION
        "The value of the object tmnxIsisUpaSentTag indicates a route tag that
         is advertised in the UPA that is being sent.

         A value of 0 indicates that the tag has not been set."
    ::= { tmnxIsisUnreachableRteSentEntry 11 }

tmnxIsisUpaSentLifetimeRemain    OBJECT-TYPE
    SYNTAX      Unsigned32 (0..1800)
    UNITS       "seconds"
    MAX-ACCESS  read-only
    STATUS      current
    DESCRIPTION
        "The value of the object tmnxIsisUpaSentLifetimeRemain indicates  the
         remaining lifetime of the UPA that is being sent."
    ::= { tmnxIsisUnreachableRteSentEntry 12 }

tmnxIsisIfObjs                   OBJECT IDENTIFIER ::= { tmnxIsisObjs 2 }

tmnxIsisIfTable                  OBJECT-TYPE
    SYNTAX      SEQUENCE OF TmnxIsisIfEntry
    MAX-ACCESS  not-accessible
    STATUS      current
    DESCRIPTION
        "The tmnxIsisIfTable has an entry for each router interface configured
         for the IS-IS protocol."
    ::= { tmnxIsisIfObjs 1 }

tmnxIsisIfEntry                  OBJECT-TYPE
    SYNTAX      TmnxIsisIfEntry
    MAX-ACCESS  not-accessible
    STATUS      current
    DESCRIPTION
        "Each row entry in the tmnxIsisIfTable represents an interface on
         this router that participates in the IS-IS protocol.  An entry in
         this table can be created or destroyed by an SNMP SET request to
         tmnxIsisIfRowStatus.  An attempt to destroy a row will fail if
         tmnxIsisIfAdminState has not first been set to 'outOfService'."
    INDEX       {
        vRtrID,
        isisSysInstance,
        vRtrIfIndex
    }
    ::= { tmnxIsisIfTable 1 }

TmnxIsisIfEntry                  ::= SEQUENCE
{
    tmnxIsisIfRowStatus              RowStatus,
    tmnxIsisIfLastChanged            TimeStamp,
    tmnxIsisIfAdminState             TmnxAdminState,
    tmnxIsisIfOperState              TmnxOperState,
    tmnxIsisIfCsnpInterval           Unsigned32,
    tmnxIsisIfHelloAuthKey           OCTET STRING,
    tmnxIsisIfHelloAuthType          INTEGER,
    tmnxIsisIfLspPacingInterval      Unsigned32,
    tmnxIsisIfCircIndex              Integer32,
    tmnxIsisIfRetransmitInterval     Unsigned32,
    tmnxIsisIfTypeDefault            TruthValue,
    tmnxIsisIfEnableBfd              TruthValue,
    tmnxIsisIfIPv6Unicast            TruthValue,
    tmnxIsisIfTeMetric               Unsigned32,
    tmnxIsisIfTeState                TmnxOperState,
    tmnxIsisIfAdminGroup             Unsigned32,
    tmnxIsisIfLdpSyncState           TmnxOperState,
    tmnxIsisIfLdpSyncMaxMetric       TruthValue,
    tmnxIsisIfLdpSyncTimerState      INTEGER,
    tmnxIsisIfLdpSyncTimeLeft        Unsigned32,
    tmnxIsisIfRouteTag               Unsigned32,
    tmnxIsisIfIPv6EnableBfd          TruthValue,
    tmnxIsisIfHelloAuth              TruthValue,
    tmnxIsisIfLoopfreeAltExclude     TruthValue,
    tmnxIsisIfOperType               INTEGER,
    tmnxIsisIfIPv4Mcast              TruthValue,
    tmnxIsisIfIPv6Mcast              TruthValue,
    tmnxIsisIfBerState               INTEGER,
    tmnxIsisIfIPv4IncludeBfdTlv      TruthValue,
    tmnxIsisIfIPv6IncludeBfdTlv      TruthValue,
    tmnxIsisIfHelloAuthKeyChain      TNamedItemOrEmpty,
    tmnxIsisIfRouteNHTemplate        TNamedItemOrEmpty,
    tmnxIsisIfIpv4SidType            INTEGER,
    tmnxIsisIfIpv4SidValue           Unsigned32,
    tmnxIsisIfIpv6SidType            INTEGER,
    tmnxIsisIfIpv6SidValue           Unsigned32,
    tmnxIsisIfDefaultInstance        TruthValue,
    tmnxIsisIfLBAdminWeight          Unsigned32,
    tmnxIsisIfHelloPadding           INTEGER,
    tmnxIsisIfSidProtection          INTEGER,
    tmnxIsisIfIpv4SidClearNFlag      TruthValue,
    tmnxIsisIfIpv6SidClearNFlag      TruthValue,
    tmnxIsisIfIpv4AdjSidType         INTEGER,
    tmnxIsisIfIpv4AdjSidValue        Unsigned32,
    tmnxIsisIfIpv6AdjSidType         INTEGER,
    tmnxIsisIfIpv6AdjSidValue        Unsigned32,
    tmnxIsisIfIpv4SharedSidType      INTEGER,
    tmnxIsisIfIpv4SharedSidValue     Unsigned32,
    tmnxIsisIfIpv6SharedSidType      INTEGER,
    tmnxIsisIfIpv6SharedSidValue     Unsigned32,
    tmnxIsisIfDelayNormalization     TruthValue,
    tmnxIsisIfMinimumDelay           Unsigned32,
    tmnxIsisIfDelayToleranceInterval Unsigned32,
    tmnxIsisIfMeasuredDelay          Unsigned32,
    tmnxIsisIfNormalizedDelay        Unsigned32
}

tmnxIsisIfRowStatus              OBJECT-TYPE
    SYNTAX      RowStatus
    MAX-ACCESS  read-create
    STATUS      current
    DESCRIPTION
        "The value of the object tmnxIsisIfRowStatus specifies the row status
         used for creation, deletion, or control of tmnxIsisIfTable entries.

         Before this row can be destroyed, tmnxIsisIfAdminState must have been
         set to 'outOfService'."
    ::= { tmnxIsisIfEntry 1 }

tmnxIsisIfLastChanged            OBJECT-TYPE
    SYNTAX      TimeStamp
    MAX-ACCESS  read-only
    STATUS      current
    DESCRIPTION
        "The value of the object tmnxIsisIfLastChanged indicates the sysUpTime
         when this row was last modified."
    ::= { tmnxIsisIfEntry 2 }

tmnxIsisIfAdminState             OBJECT-TYPE
    SYNTAX      TmnxAdminState
    MAX-ACCESS  read-create
    STATUS      current
    DESCRIPTION
        "The value of the object tmnxIsisIfAdminState specifies the desired
         administrative state for IS-IS protocol on this interface."
    DEFVAL      { inService }
    ::= { tmnxIsisIfEntry 3 }

tmnxIsisIfOperState              OBJECT-TYPE
    SYNTAX      TmnxOperState
    MAX-ACCESS  read-only
    STATUS      current
    DESCRIPTION
        "The value of the object tmnxIsisIfOperState indicates the current
         operational state of IS-IS protocol on this interface."
    ::= { tmnxIsisIfEntry 4 }

tmnxIsisIfCsnpInterval           OBJECT-TYPE
    SYNTAX      Unsigned32 (1..65535)
    UNITS       "seconds"
    MAX-ACCESS  read-create
    STATUS      current
    DESCRIPTION
        "The value of the object tmnxIsisIfCsnpInterval specifies the interval
         of time, in seconds, between transmission of Complete Sequence Number
         PDUs (CSNP)."
    DEFVAL      { 10 }
    ::= { tmnxIsisIfEntry 5 }

tmnxIsisIfHelloAuthKey           OBJECT-TYPE
    SYNTAX      OCTET STRING (SIZE (0..254))
    MAX-ACCESS  read-create
    STATUS      current
    DESCRIPTION
        "The value of the object tmnxIsisIfHelloAuthKey specifies the
         authentication key string used to verify the authenticity of packets
         sent by neighboring routers on this IS-IS interface.

         For authentication to succeed both the authentication key and the
         authentication type defined by the tmnxIsisIfHelloAuthType variable
         must match.

         If tmnxIsisIfHelloAuthType is set to 'password',
         tmnxIsisIfHelloAuthKey can include any ASCII character.

         Authentication can be configured globally and applied to all
         ISIS levels running on this interface or it can be configured
         on a per level basis.  The most specific value is used.

         When read, tmnxIsisIfHelloAuthKey always returns an Octet String of
         length zero."
    DEFVAL      { ''H }
    ::= { tmnxIsisIfEntry 6 }

tmnxIsisIfHelloAuthType          OBJECT-TYPE
    SYNTAX      INTEGER {
        none     (1),
        password (2),
        md5      (3)
    }
    MAX-ACCESS  read-create
    STATUS      current
    DESCRIPTION
        "The value of the object tmnxIsisIfHelloAuthType specifies the method
         of authentication used to verify the authenticity of packets sent by
         neighboring routers on this IS-IS interface.

         For authentication to succeed both the authentication key defined in
         the tmnxIsisIfHelloAuthKey variable and the authentication type must
         match.

         Authentication can be configured globally and applied to all
         ISIS levels running on this interface or it can be configured on
         a per level basis.  The most specific value is used."
    DEFVAL      { none }
    ::= { tmnxIsisIfEntry 7 }

tmnxIsisIfLspPacingInterval      OBJECT-TYPE
    SYNTAX      Unsigned32 (0..65535)
    UNITS       "milliseconds"
    MAX-ACCESS  read-create
    STATUS      current
    DESCRIPTION
        "The value of the object tmnxIsisIfLspPacingInterval specifies the
         interval of time, in milliseconds, for transmission of Link State PDUs
         (LSPs) for all ISIS levels running on this interface.

         If the value of tmnxIsisIfLspPacingInterval is zero (0), no LSPs will
         be sent on this interface."
    DEFVAL      { 100 }
    ::= { tmnxIsisIfEntry 8 }

tmnxIsisIfCircIndex              OBJECT-TYPE
    SYNTAX      Integer32 (1..2000000000)
    MAX-ACCESS  read-only
    STATUS      current
    DESCRIPTION
        "The value of the object tmnxIsisIfCircIndex indicates a cross
         reference index to the isisCircTable."
    ::= { tmnxIsisIfEntry 9 }

tmnxIsisIfRetransmitInterval     OBJECT-TYPE
    SYNTAX      Unsigned32 (1..65535)
    UNITS       "seconds"
    MAX-ACCESS  read-create
    STATUS      current
    DESCRIPTION
        "The value of the object tmnxIsisIfRetransmitInterval specifies the
         minimal interval of time, in seconds between retransmission of an LSP
         on point-to-point interfaces."
    DEFVAL      { 5 }
    ::= { tmnxIsisIfEntry 10 }

tmnxIsisIfTypeDefault            OBJECT-TYPE
    SYNTAX      TruthValue
    MAX-ACCESS  read-create
    STATUS      current
    DESCRIPTION
        "The value of the object tmnxIsisIfTypeDefault specifies if the circuit
         type is default or has been modified.

         Setting tmnxIsisIfTypeDefault to 'true' resets isisCircType to the
         default for that interface.

         Similarly any modification to the object isisCircType triggers this
         object to become 'false'.

         There is no effect of setting this object to 'false'."
    DEFVAL      { true }
    ::= { tmnxIsisIfEntry 11 }

tmnxIsisIfEnableBfd              OBJECT-TYPE
    SYNTAX      TruthValue
    MAX-ACCESS  read-create
    STATUS      current
    DESCRIPTION
        "The value of the object tmnxIsisIfEnableBfd specifies whether
         Bi-directional Forwarding Detection is enabled for IPv4 on this IS-IS
         interface.

         When the value is 'true', this IS-IS interface can establish BFD
         sessions and use BFD as a signaling mechanism for forming adjacencies.

         When tmnxIsisIfEnableBfd is 'false', BFD cannot be for IPv4."
    DEFVAL      { false }
    ::= { tmnxIsisIfEntry 12 }

tmnxIsisIfIPv6Unicast            OBJECT-TYPE
    SYNTAX      TruthValue
    MAX-ACCESS  read-create
    STATUS      current
    DESCRIPTION
        "The value of the object tmnxIsisIfIPv6Unicast specifies whether IPv6
         unicast routing is enabled for the interface.

         By default IPv6 unicast on all interfaces is set to true. However,
         IPv6 unicast routing on ISIS is in effect when the object
         'tmnxIsisMultiTopoIPv6Ucast' is set to 'true'."
    DEFVAL      { true }
    ::= { tmnxIsisIfEntry 13 }

tmnxIsisIfTeMetric               OBJECT-TYPE
    SYNTAX      Unsigned32 (0..16777215)
    MAX-ACCESS  read-only
    STATUS      current
    DESCRIPTION
        "The value of the object tmnxIsisIfTeMetric indicates the MPLS TE
         metric configured for this interface; this metric is flooded out in
         the TE metric sub-tlv in the ISIS LSPs.

         Depending on the configuration, either the TE metric value or the
         native ISIS metric values are used in CSPF computations."
    ::= { tmnxIsisIfEntry 14 }

tmnxIsisIfTeState                OBJECT-TYPE
    SYNTAX      TmnxOperState
    MAX-ACCESS  read-only
    STATUS      current
    DESCRIPTION
        "The value of the object tmnxIsisIfTeState indicates the MPLS interface
         TE status from the ISIS standpoint."
    ::= { tmnxIsisIfEntry 15 }

tmnxIsisIfAdminGroup             OBJECT-TYPE
    SYNTAX      Unsigned32
    MAX-ACCESS  read-only
    STATUS      current
    DESCRIPTION
        "The value of the object tmnxIsisIfAdminGroup indicates the bit-map
         inherited from MPLS interface that identifies the admin groups to
         which the interface belongs.

         If bit 'n' is set, then the interface belongs to the admin group with
         value 'n'."
    ::= { tmnxIsisIfEntry 16 }

tmnxIsisIfLdpSyncState           OBJECT-TYPE
    SYNTAX      TmnxOperState
    MAX-ACCESS  read-only
    STATUS      current
    DESCRIPTION
        "The value of the object tmnxIsisIfLdpSyncState indicates if IGP-LDP
         synchronization is enabled on this interface.

         tmnxIsisIfLdpSyncState is derived from tmnxIsisLdpSyncAdminState and
         also whether it was enabled at the IP layer from ISIS standpoint."
    ::= { tmnxIsisIfEntry 17 }

tmnxIsisIfLdpSyncMaxMetric       OBJECT-TYPE
    SYNTAX      TruthValue
    MAX-ACCESS  read-only
    STATUS      current
    DESCRIPTION
        "The value of the object tmnxIsisIfLdpSyncMaxMetric indicates if ISIS
         advertised maximum metric value for the interface, depending on
         whether tmnxIsisIfLdpSyncState is enabled on this interface."
    ::= { tmnxIsisIfEntry 18 }

tmnxIsisIfLdpSyncTimerState      OBJECT-TYPE
    SYNTAX      INTEGER {
        waitForLdpAdj (1),
        timerActive   (2),
        ldpExchgDone  (3),
        timerExpired  (4),
        manualExit    (5),
        disabled      (6)
    }
    MAX-ACCESS  read-only
    STATUS      current
    DESCRIPTION
        "The value of the object tmnxIsisIfLdpSyncTimerState indicates the
         state of the tmnxIsisIfLdpSyncTimeLeft on this ISIS interface."
    ::= { tmnxIsisIfEntry 19 }

tmnxIsisIfLdpSyncTimeLeft        OBJECT-TYPE
    SYNTAX      Unsigned32 (0 | 1..1800)
    UNITS       "seconds"
    MAX-ACCESS  read-only
    STATUS      current
    DESCRIPTION
        "The value of the object tmnxIsisIfLdpSyncTimeLeft indicates the time
         left before ISIS reverts back to advertising normal metric for this
         interface.

         This is applicable only when tmnxIsisIfLdpSyncMaxMetric is 'true'."
    ::= { tmnxIsisIfEntry 20 }

tmnxIsisIfRouteTag               OBJECT-TYPE
    SYNTAX      Unsigned32
    MAX-ACCESS  read-create
    STATUS      current
    DESCRIPTION
        "The value of the object tmnxIsisIfRouteTag specifies a 32-bit integer
         tag for the IP addresses of an interface.

         This route tag can be used to apply administrative policy.

         A value of 0 indicates that the tag has not been set."
    DEFVAL      { 0 }
    ::= { tmnxIsisIfEntry 21 }

tmnxIsisIfIPv6EnableBfd          OBJECT-TYPE
    SYNTAX      TruthValue
    MAX-ACCESS  read-create
    STATUS      current
    DESCRIPTION
        "The value of the object tmnxIsisIfIPv6EnableBfd specifies whether
         Bi-directional Forwarding Detection is enabled for IPv6 on this IS-IS
         interface.

         When the value is 'true', this IS-IS interface can establish BFD
         sessions and use BFD as a signaling mechanism for forming adjacencies.
         When it is 'false', it cannot use BFD for IPv6."
    DEFVAL      { false }
    ::= { tmnxIsisIfEntry 22 }

tmnxIsisIfHelloAuth              OBJECT-TYPE
    SYNTAX      TruthValue
    MAX-ACCESS  read-create
    STATUS      current
    DESCRIPTION
        "The value of the object tmnxIsisIfHelloAuth specifies whether ISIS
         hello-authentication is enabled or disabled on this IS-IS interface.

         When tmnxIsisIfHelloAuth is set to 'true', hello-authentication is
         enabled on this IS-IS interface.

         When tmnxIsisIfHelloAuth is set to 'false',
         hello-authentication is disabled on this IS-IS interface and
         the values of the following MIB objects are no longer applicable:
         - tmnxIsisIfHelloAuthKey and tmnxIsisIfHelloAuthType at a global
           interface level
         - tmnxIsisIfLevelHelloAuthKey and tmnxIsisIfLevelHelloAuthType
           at the specific L1/L2 interface level
         - tmnxIsisAuthKey and tmnxIsisAuthType at the ISIS level."
    DEFVAL      { true }
    ::= { tmnxIsisIfEntry 23 }

tmnxIsisIfLoopfreeAltExclude     OBJECT-TYPE
    SYNTAX      TruthValue
    MAX-ACCESS  read-create
    STATUS      current
    DESCRIPTION
        "The value of the object tmnxIsisIfLoopfreeAltExclude specifies whether
         or not the ISIS interface should be excluded during LFA calculations.

         If the value is 'true', the ISIS interface is excluded from LFA
         calculations. If the value is 'false', the ISIS interface is included
         in LFA calculations.

         The value of tmnxIsisIfLoopfreeAltExclude for an interface is only
         valid when both conditions are met - tmnxIsisLoopfreeAlternate has a
         value of 'true' and tmnxIsisLevelLoopfreeAltExclude has a value of
         'false'."
    DEFVAL      { false }
    ::= { tmnxIsisIfEntry 24 }

tmnxIsisIfOperType               OBJECT-TYPE
    SYNTAX      INTEGER {
        broadcast (1),
        ptToPt    (2)
    }
    MAX-ACCESS  read-only
    STATUS      current
    DESCRIPTION
        "The value of the object tmnxIsisIfOperType indicates the operational
         type on this ISIS interface."
    ::= { tmnxIsisIfEntry 25 }

tmnxIsisIfIPv4Mcast              OBJECT-TYPE
    SYNTAX      TruthValue
    MAX-ACCESS  read-create
    STATUS      current
    DESCRIPTION
        "The value of the object tmnxIsisIfIPv4Mcast specifies if IPv4
         multicast routing is enabled for the interface."
    DEFVAL      { true }
    ::= { tmnxIsisIfEntry 26 }

tmnxIsisIfIPv6Mcast              OBJECT-TYPE
    SYNTAX      TruthValue
    MAX-ACCESS  read-create
    STATUS      current
    DESCRIPTION
        "The value of the object tmnxIsisIfIPv6Mcast specifies if IPv6
         multicast routing is enabled for the interface."
    DEFVAL      { true }
    ::= { tmnxIsisIfEntry 27 }

tmnxIsisIfBerState               OBJECT-TYPE
    SYNTAX      INTEGER {
        none (0),
        sd   (1),
        sf   (2)
    }
    MAX-ACCESS  read-only
    STATUS      current
    DESCRIPTION
        "The value of the object tmnxIsisIfBerState indicates the BER (Bit
         Error Rate) state of this interface."
    ::= { tmnxIsisIfEntry 28 }

tmnxIsisIfIPv4IncludeBfdTlv      OBJECT-TYPE
    SYNTAX      TruthValue
    MAX-ACCESS  read-create
    STATUS      current
    DESCRIPTION
        "The value of the object tmnxIsisIfIPv4IncludeBfdTlv specifies whether
         a BFD-enabled type-length-value (TLV) is included for IPv4 on this
         IS-IS interface.

         When the value of tmnxIsisIfEnableBfd is false, the value of
         tmnxIsisIfIPv4IncludeBfdTlv is ignored.

         When both tmnxIsisIfEnableBfd and tmnxIsisIfIPv4IncludeBfdTlv have the
         value set to true, then the BFD-enabled TLV is included for IPv4."
    DEFVAL      { false }
    ::= { tmnxIsisIfEntry 29 }

tmnxIsisIfIPv6IncludeBfdTlv      OBJECT-TYPE
    SYNTAX      TruthValue
    MAX-ACCESS  read-create
    STATUS      current
    DESCRIPTION
        "The value of the object tmnxIsisIfIPv6IncludeBfdTlv specifies whether
         a BFD-enabled type-length-value (TLV) is included for IPv6 on this
         IS-IS interface.

         When the value of tmnxIsisIfIPv6EnableBfd is false, the value of
         tmnxIsisIfIPv6IncludeBfdTlv is ignored.

         When both tmnxIsisIfIPv6EnableBfd and tmnxIsisIfIPv6IncludeBfdTlv have
         the value set to true, then the BFD-enabled TLV is included for IPv6."
    DEFVAL      { false }
    ::= { tmnxIsisIfEntry 30 }

tmnxIsisIfHelloAuthKeyChain      OBJECT-TYPE
    SYNTAX      TNamedItemOrEmpty
    MAX-ACCESS  read-create
    STATUS      current
    DESCRIPTION
        "The value of tmnxIsisIfHelloAuthKeyChain specifies the keychain to use
         to sign and/or authenticate the IS-IS instance.

         The keychain name is defined by tmnxKeyChainName and is the index for
         TIMETRA-SECURITY-MIB::tmnxKeyChainTable"
    DEFVAL      { ''H }
    ::= { tmnxIsisIfEntry 31 }

tmnxIsisIfRouteNHTemplate        OBJECT-TYPE
    SYNTAX      TNamedItemOrEmpty
    MAX-ACCESS  read-create
    STATUS      current
    DESCRIPTION
        "The value of tmnxIsisIfRouteNHTemplate specifies the next-hop template
         that must be applied to the prefixes which primary next-hop uses this
         interface name.

         The next-hop template name is defined by tmnxRouteNHTemplateName and
         is the index for
         TIMETRA-ROUTE-NEXT-HOP-TEMPLATE-MIB::tmnxRouteNHTemplateTable."
    DEFVAL      { ''H }
    ::= { tmnxIsisIfEntry 32 }

tmnxIsisIfIpv4SidType            OBJECT-TYPE
    SYNTAX      INTEGER {
        none  (0),
        index (1),
        label (2)
    }
    MAX-ACCESS  read-create
    STATUS      current
    DESCRIPTION
        "The value of tmnxIsisIfIpv4SidType specifies how the value of
         tmnxIsisIfIpv4SidValue shall be interpreted."
    DEFVAL      { none }
    ::= { tmnxIsisIfEntry 33 }

tmnxIsisIfIpv4SidValue           OBJECT-TYPE
    SYNTAX      Unsigned32
    MAX-ACCESS  read-create
    STATUS      current
    DESCRIPTION
        "The value of the object tmnxIsisIfIpv4SidValue specifies the IPv4 node
         SID label or index for this interface."
    DEFVAL      { 0 }
    ::= { tmnxIsisIfEntry 34 }

tmnxIsisIfIpv6SidType            OBJECT-TYPE
    SYNTAX      INTEGER {
        none  (0),
        index (1),
        label (2)
    }
    MAX-ACCESS  read-create
    STATUS      current
    DESCRIPTION
        "The value of tmnxIsisIfIpv6SidType specifies how the value of
         tmnxIsisIfIpv6SidValue shall be interpreted."
    DEFVAL      { none }
    ::= { tmnxIsisIfEntry 35 }

tmnxIsisIfIpv6SidValue           OBJECT-TYPE
    SYNTAX      Unsigned32
    MAX-ACCESS  read-create
    STATUS      current
    DESCRIPTION
        "The value of the object tmnxIsisIfIpv6SidValue specifies the IPv6 node
         SID label or index for this interface."
    DEFVAL      { 0 }
    ::= { tmnxIsisIfEntry 36 }

tmnxIsisIfDefaultInstance        OBJECT-TYPE
    SYNTAX      TruthValue
    MAX-ACCESS  read-create
    STATUS      current
    DESCRIPTION
        "The value of the object tmnxIsisIfDefaultInstance specifies whether a
         non-MI capable router can establish an adjacency and operate with an
         SR OS router in a non zero IS-IS instance.

         When the value of tmnxIsisIfDefaultInstance is true and the router
         doesn't receive IID-TLVs it will establish an adjacency in the
         non-zero isisSysInstance; the router will then operate in the non-zero
         isisSysInstance so that it appears to be in the default IS-IS instance
         0 to its neighbor."
    DEFVAL      { false }
    ::= { tmnxIsisIfEntry 37 }

tmnxIsisIfLBAdminWeight          OBJECT-TYPE
    SYNTAX      Unsigned32
    MAX-ACCESS  read-create
    STATUS      current
    DESCRIPTION
        "The value of the object tmnxIsisIfLBAdminWeight specifies an explicit
         load-balancing-weight for this interface."
    DEFVAL      { 0 }
    ::= { tmnxIsisIfEntry 38 }

tmnxIsisIfHelloPadding           OBJECT-TYPE
    SYNTAX      INTEGER {
        disable  (0),
        adaptive (1),
        loose    (2),
        strict   (3),
        none     (4)
    }
    MAX-ACCESS  read-create
    STATUS      current
    DESCRIPTION
        "The value of the object tmnxIsisIfHelloPadding specifies whether
         padding should be done on the ISIS hello packets.

         If the value of tmnxIsisIfHelloPadding is set to disable, the padding
         is disabled on all types of interfaces for all adjacency states.
         However, padding may be done if it is configured at one of the
         higher/parent levels.

         If the value of tmnxIsisIfHelloPadding is set to adaptive, the padding
         is done until the state of the neighbor adjacency is up.

         If the value of tmnxIsisIfHelloPadding is set to loose, the padding is
         done until the state of the neighbor adjacency is initialized.

         If the value of tmnxIsisIfHelloPadding is set to strict, the padding
         is done for all adjacency states.

         If the value of tmnxIsisIfHelloPadding is set to none, the padding is
         disabled on all types of interfaces for all adjacency states. Also,
         padding will not be done even if it is configured at one of the
         higher/parent levels."
    DEFVAL      { disable }
    ::= { tmnxIsisIfEntry 39 }

tmnxIsisIfSidProtection          OBJECT-TYPE
    SYNTAX      INTEGER {
        enabled  (1),
        disabled (2)
    }
    MAX-ACCESS  read-create
    STATUS      current
    DESCRIPTION
        "The value of the object tmnxIsisIfSidProtection specifies whether the
         SID needs to be advertised with protection enabled or disabled.

         If the value of tmnxIsisIfSidProtection is set to disabled, no
         protection is calculated and a single SID with B-flag cleared is sent
         in adjacency SID sub-TLV.

         If the value of tmnxIsisIfSidProtection is set to enabled, SID
         protection is provided and a single SID with B-flag set is sent in
         adjacency SID sub-TLV."
    DEFVAL      { enabled }
    ::= { tmnxIsisIfEntry 40 }

tmnxIsisIfIpv4SidClearNFlag      OBJECT-TYPE
    SYNTAX      TruthValue
    MAX-ACCESS  read-create
    STATUS      current
    DESCRIPTION
        "The value of tmnxIsisIfIpv4SidClearNFlag specifies whether the
         node-sid flag (N-flag) should be cleared in an IPv4 prefix SID
         sub-TLV.

         When the value of tmnxIsisIfIpv4SidClearNFlag is false, the prefix SID
         sub-TLV for the IPv4 prefix of a loopback interface is tagged as a
         node SID meaning that it belongs to this node only.

         When the value of tmnxIsisIfIpv4SidClearNFlag is true, the same prefix
         SID sub-TLV may be advertised by multiple nodes."
    DEFVAL      { false }
    ::= { tmnxIsisIfEntry 41 }

tmnxIsisIfIpv6SidClearNFlag      OBJECT-TYPE
    SYNTAX      TruthValue
    MAX-ACCESS  read-create
    STATUS      current
    DESCRIPTION
        "The value of tmnxIsisIfIpv6SidClearNFlag specifies whether the
         node-sid flag (N-flag) should be cleared in an IPv6 prefix SID
         sub-TLV.

         When the value of tmnxIsisIfIpv6SidClearNFlag is false, the prefix SID
         sub-TLV for the IPv6 prefix of a loopback interface is tagged as a
         node SID meaning that it belongs to this node only.

         When the value of tmnxIsisIfIpv6SidClearNFlag is true, the same prefix
         SID sub-TLV may be advertised by multiple nodes."
    DEFVAL      { false }
    ::= { tmnxIsisIfEntry 42 }

tmnxIsisIfIpv4AdjSidType         OBJECT-TYPE
    SYNTAX      INTEGER {
        none  (0),
        label (2)
    }
    MAX-ACCESS  read-create
    STATUS      current
    DESCRIPTION
        "The value of the object tmnxIsisIfIpv4AdjSidType specifies whether the
         object tmnxIsisIfIpv4AdjSidValue is not valid, an index value or an
         absolute label value."
    DEFVAL      { none }
    ::= { tmnxIsisIfEntry 43 }

tmnxIsisIfIpv4AdjSidValue        OBJECT-TYPE
    SYNTAX      Unsigned32
    MAX-ACCESS  read-create
    STATUS      current
    DESCRIPTION
        "The value of the object tmnxIsisIfIpv4AdjSidValue together with
         tmnxIsisIfIpv4AdjSidType specifies the static adjacency SID value  or
         index to be used for this adjacency. "
    DEFVAL      { 0 }
    ::= { tmnxIsisIfEntry 44 }

tmnxIsisIfIpv6AdjSidType         OBJECT-TYPE
    SYNTAX      INTEGER {
        none  (0),
        label (2)
    }
    MAX-ACCESS  read-create
    STATUS      current
    DESCRIPTION
        "The value of the object tmnxIsisIfIpv6AdjSidType specifies whether the
         object tmnxIsisIfIpv6AdjSidValue is not valid, an index value or an
         absolute label value."
    DEFVAL      { none }
    ::= { tmnxIsisIfEntry 46 }

tmnxIsisIfIpv6AdjSidValue        OBJECT-TYPE
    SYNTAX      Unsigned32
    MAX-ACCESS  read-create
    STATUS      current
    DESCRIPTION
        "The value of the object tmnxIsisIfIpv6AdjSidValue together with
         tmnxIsisIfIpv6AdjSidType specifies the static adjacency SID value  or
         index to be used for this adjacency. "
    DEFVAL      { 0 }
    ::= { tmnxIsisIfEntry 47 }

tmnxIsisIfIpv4SharedSidType      OBJECT-TYPE
    SYNTAX      INTEGER {
        none  (0),
        index (1),
        label (2)
    }
    MAX-ACCESS  read-only
    STATUS      current
    DESCRIPTION
        "The value of the object tmnxIsisIfIpv4SharedSidType indicates how  the
         value of tmnxIsisIfIpv4SharedSidValue shall be interpreted."
    ::= { tmnxIsisIfEntry 49 }

tmnxIsisIfIpv4SharedSidValue     OBJECT-TYPE
    SYNTAX      Unsigned32
    MAX-ACCESS  read-only
    STATUS      current
    DESCRIPTION
        "The value of the object tmnxIsisIfIpv4SharedSidValue together  with
         tmnxIsisIfIpv4SharedSidType indicates the IPv4 shared SID label or
         index for this interface that will be advertised."
    ::= { tmnxIsisIfEntry 50 }

tmnxIsisIfIpv6SharedSidType      OBJECT-TYPE
    SYNTAX      INTEGER {
        none  (0),
        index (1),
        label (2)
    }
    MAX-ACCESS  read-only
    STATUS      current
    DESCRIPTION
        "The value of the object tmnxIsisIfIpv6SharedSidType indicates how  the
         value of tmnxIsisIfIpv6SharedSidValue shall be interpreted."
    ::= { tmnxIsisIfEntry 51 }

tmnxIsisIfIpv6SharedSidValue     OBJECT-TYPE
    SYNTAX      Unsigned32
    MAX-ACCESS  read-only
    STATUS      current
    DESCRIPTION
        "The value of the object tmnxIsisIfIpv6SharedSidValue together  with
         tmnxIsisIfIpv6SharedSidType indicates the IPv6 shared SID label or
         index for this interface that will be advertised."
    ::= { tmnxIsisIfEntry 52 }

tmnxIsisIfDelayNormalization     OBJECT-TYPE
    SYNTAX      TruthValue
    MAX-ACCESS  read-create
    STATUS      current
    DESCRIPTION
        "The value of the object tmnxIsisIfDelayNormalization specifies whether
         the interface supports delay normalization.

         If the value is 'true', a normalized delay value is computed and used.
         The normalized delay is based on the measured delay, the
         tmnxIsisIfMinimumDelay and tmnxIsisIfDelayToleranceInterval.

         If the value is 'false', the measured delay is used."
    DEFVAL      { false }
    ::= { tmnxIsisIfEntry 53 }

tmnxIsisIfMinimumDelay           OBJECT-TYPE
    SYNTAX      Unsigned32 (1..10000000)
    UNITS       "microseconds"
    MAX-ACCESS  read-create
    STATUS      current
    DESCRIPTION
        "The value of the object tmnxIsisIfMinimumDelay specifies  the minimum
         delay in microseconds on the interface.

         The value of tmnxIsisIfMinimumDelay is only valid when
         tmnxIsisIfDelayNormalization has a value of 'true'."
    DEFVAL      { 1 }
    ::= { tmnxIsisIfEntry 54 }

tmnxIsisIfDelayToleranceInterval OBJECT-TYPE
    SYNTAX      Unsigned32 (1..10000000)
    UNITS       "microseconds"
    MAX-ACCESS  read-create
    STATUS      current
    DESCRIPTION
        "The value of the object tmnxIsisIfDelayToleranceInterval specifies
         the interval between two delay values on the interface.

         The value of tmnxIsisIfDelayToleranceInterval is only valid when
         tmnxIsisIfDelayNormalization has a value of 'true'."
    DEFVAL      { 10 }
    ::= { tmnxIsisIfEntry 55 }

tmnxIsisIfMeasuredDelay          OBJECT-TYPE
    SYNTAX      Unsigned32
    UNITS       "microseconds"
    MAX-ACCESS  read-only
    STATUS      current
    DESCRIPTION
        "The value of the object tmnxIsisIfMeasuredDelay indicates  the
         measured delay in microseconds on the interface."
    ::= { tmnxIsisIfEntry 56 }

tmnxIsisIfNormalizedDelay        OBJECT-TYPE
    SYNTAX      Unsigned32
    UNITS       "microseconds"
    MAX-ACCESS  read-only
    STATUS      current
    DESCRIPTION
        "The value of the object tmnxIsisIfNormalizedDelay indicates  the
         normalized delay in microseconds on the interface.

         When tmnxIsisIfDelayNormalization is 'false', the value of
         tmnxIsisIfNormalizedDelay will be the same as
         tmnxIsisIfMeasuredDelay."
    ::= { tmnxIsisIfEntry 57 }

tmnxIsisIfLevelTable             OBJECT-TYPE
    SYNTAX      SEQUENCE OF TmnxIsisIfLevelEntry
    MAX-ACCESS  not-accessible
    STATUS      current
    DESCRIPTION
        "The tmnxIsisIfLevelTable provides attributes to be applied on a
         specific IS-IS interface operating at a specific IS-IS protocol level."
    ::= { tmnxIsisIfObjs 2 }

tmnxIsisIfLevelEntry             OBJECT-TYPE
    SYNTAX      TmnxIsisIfLevelEntry
    MAX-ACCESS  not-accessible
    STATUS      current
    DESCRIPTION
        "Each row entry in the tmnxIsisIfLevelTable represents IS-IS level
         attributes to be used with an interface belonging to a specific IS-IS
         protocol instance on a specific router instance. Rows for Level 1 and
         2 are created as an action of creating a row in the tmnxIsisIfTable."
    INDEX       {
        vRtrID,
        isisSysInstance,
        vRtrIfIndex,
        tmnxIsisIfLevel
    }
    ::= { tmnxIsisIfLevelTable 1 }

TmnxIsisIfLevelEntry             ::= SEQUENCE
{
    tmnxIsisIfLevel                  INTEGER,
    tmnxIsisIfLevelLastChangeTime    TimeStamp,
    tmnxIsisIfLevelHelloAuthKey      OCTET STRING,
    tmnxIsisIfLevelHelloAuthType     INTEGER,
    tmnxIsisIfLevelPassive           TruthValue,
    tmnxIsisIfLevelNumAdjacencies    Unsigned32,
    tmnxIsisIfLevelISPriority        Unsigned32,
    tmnxIsisIfLevelHelloTimer        Unsigned32,
    tmnxIsisIfLevelAdminMetric       Unsigned32,
    tmnxIsisIfLevelOperMetric        Unsigned32,
    tmnxIsisIfLvlIPv6UcastAdmMet     Unsigned32,
    tmnxIsisIfLvlIPv6UcastOperMet    Unsigned32,
    tmnxIsisIfLvlIPv4McastAdmMetric  Unsigned32,
    tmnxIsisIfLvlIPv6McastAdmMetric  Unsigned32,
    tmnxIsisIfLevelLinkGroupName     TNamedItemOrEmpty,
    tmnxIsisIfLevelSdOffset          Unsigned32,
    tmnxIsisIfLevelSfOffset          Unsigned32,
    tmnxIsisIfLvlIPv4McastOperMetric Unsigned32,
    tmnxIsisIfLvlIPv6McastOperMetric Unsigned32,
    tmnxIsisIfLevelHelloAuthKeyChain TNamedItemOrEmpty,
    tmnxIsisIfLevelLspTxQCount       Unsigned32,
    tmnxIsisIfLevelHelloPadding      INTEGER
}

tmnxIsisIfLevel                  OBJECT-TYPE
    SYNTAX      INTEGER {
        level1 (1),
        level2 (2)
    }
    MAX-ACCESS  not-accessible
    STATUS      current
    DESCRIPTION
        "The value of the object tmnxIsisIfLevel specifies the IS-IS protocol
         level that this row entry describes."
    ::= { tmnxIsisIfLevelEntry 1 }

tmnxIsisIfLevelLastChangeTime    OBJECT-TYPE
    SYNTAX      TimeStamp
    MAX-ACCESS  read-only
    STATUS      current
    DESCRIPTION
        "The value of the object tmnxIsisIfLevelLastChangeTime indicates the
         sysUpTime when this row was last modified."
    ::= { tmnxIsisIfLevelEntry 2 }

tmnxIsisIfLevelHelloAuthKey      OBJECT-TYPE
    SYNTAX      OCTET STRING (SIZE (0..254))
    MAX-ACCESS  read-create
    STATUS      current
    DESCRIPTION
        "The value of the object tmnxIsisIfLevelHelloAuthKey specifies the
         authentication key string used to verify the authenticity of packets
         sent by neighboring routers on this IS-IS interface at this level.

         For authentication to succeed both the authentication key and the
         authentication type defined by the tmnxIsisIfLevelHelloAuthType
         variable must match.

         If tmnxIsisIfLevelHelloAuthType is set to 'password',
         tmnxIsisIfLevelHelloAuthKey can include any ASCII character.

         Authentication can be configured globally and applied to all ISIS
         levels or it can be configured on a per level basis; the most specific
         value is used.

         If the value of tmnxIsisIfLevelHelloAuthType is 'useGlobal', then the
         global values, if any, defined in tmnxIsisIfHelloAuthKey and
         tmnxIsisIfHelloAuthType are used instead.

         When read, tmnxIsisIfLevelHelloAuthKey always returns an Octet String
         of length zero."
    DEFVAL      { ''H }
    ::= { tmnxIsisIfLevelEntry 3 }

tmnxIsisIfLevelHelloAuthType     OBJECT-TYPE
    SYNTAX      INTEGER {
        useGlobal (0),
        none      (1),
        password  (2),
        md5       (3)
    }
    MAX-ACCESS  read-create
    STATUS      current
    DESCRIPTION
        "The value of the object tmnxIsisIfLevelHelloAuthType specifies the
         method of authentication used to verify the authenticity of packets
         sent by neighboring routers on this IS-IS interface at this level.

         For authentication to succeed both the authentication key defined in
         the tmnxIsisIfLevelHelloAuthKey variable and the authentication type
         must match.

         Authentication can be configured globally and applied to all ISIS
         levels running on this interface or it can be configured on a per
         level basis; the most specific value is used.

         When tmnxIsisIfLevelHelloAuthType has a value of 'useGlobal', the
         values of tmnxIsisIfLevelHelloAuthKey and tmnxIsisIfLevelHelloAuthType
         are applied to the interfaces for this level."
    DEFVAL      { useGlobal }
    ::= { tmnxIsisIfLevelEntry 4 }

tmnxIsisIfLevelPassive           OBJECT-TYPE
    SYNTAX      TruthValue
    MAX-ACCESS  read-create
    STATUS      current
    DESCRIPTION
        "The value of the object tmnxIsisIfLevelPassive specifies whether the
         interface level should run in passive mode.

         If the configured value is 'false', the running state of the passive
         mode is inherited from the interface.

         If ISIS-MIB::isisCircPassiveCircuit is true, the interface is running
         in passive mode for both L1 and L2. If
         ISIS-MIB::isisCircPassiveCircuit is false and tmnxIsisIfLevelPassive
         is true then only the corresponding level is running in passive mode.

         When running in passive mode, this interface address is  advertised
         for this level without running the IS-IS protocol on this interface
         level; while in passive mode, the interface level ignores ingress
         IS-IS protocol packets and does not transmit any IS-IS protocol
         packets.

         When not running in passive mode, this interface address is advertised
         at this IS-IS level only if it is configured as with the IS-IS
         protocol as enabled."
    DEFVAL      { false }
    ::= { tmnxIsisIfLevelEntry 5 }

tmnxIsisIfLevelNumAdjacencies    OBJECT-TYPE
    SYNTAX      Unsigned32
    MAX-ACCESS  read-only
    STATUS      current
    DESCRIPTION
        "The value of the object tmnxIsisIfLevelNumAdjacencies indicates the
         number of adjacencies on this particular level of the interface."
    ::= { tmnxIsisIfLevelEntry 6 }

tmnxIsisIfLevelISPriority        OBJECT-TYPE
    SYNTAX      Unsigned32 (0..127)
    MAX-ACCESS  read-create
    STATUS      current
    DESCRIPTION
        "The value of the object tmnxIsisIfLevelISPriority specifies the
         priority for becoming LAN Designated Intermediate System at this
         level.

         The value of tmnxIsisIfLevelISPriority shadows the value of object
         isisCircLevelISPriority to have an additional accepted value of 0."
    ::= { tmnxIsisIfLevelEntry 7 }

tmnxIsisIfLevelHelloTimer        OBJECT-TYPE
    SYNTAX      Unsigned32 (1..20000)
    MAX-ACCESS  read-create
    STATUS      current
    DESCRIPTION
        "The value of the object tmnxIsisIfLevelHelloTimer specifies the
         maximum period, in seconds, between IIH PDUs on multiaccess networks
         at this level for LANs.

         The value of tmnxIsisIfLevelHelloTimer shadows isisCircLevelHelloTimer
         to store the values of hello timer in seconds."
    ::= { tmnxIsisIfLevelEntry 8 }

tmnxIsisIfLevelAdminMetric       OBJECT-TYPE
    SYNTAX      Unsigned32 (0..16777215)
    MAX-ACCESS  read-create
    STATUS      current
    DESCRIPTION
        "The value of the object tmnxIsisIfLevelAdminMetric specifies the
         default metric value of this circuit for this level.

         A value of 0 means that the metric is not configured; in such a case
         if the tmnxIsisReferenceBw is configured, the value of the metric
         should be calculated using the formula :

            Metric = reference-bandwidth / bandwidth.

         If the tmnxIsisReferenceBw is configured as Ten Gig (10,000,000,000) a
         100-Mbps interface has a default metric of 100.

         In order for metrics in excess of 63 to be configured wide metrics
         must be deployed.

         If the reference bandwidth is not configured then all levels will have
         a default metric of 10.

         System and loopback interface levels will always have a metric value
         of 0.

         The operational value of the metric is maintained in the object
         tmnxIsisIfLevelOperMetric."
    DEFVAL      { 0 }
    ::= { tmnxIsisIfLevelEntry 9 }

tmnxIsisIfLevelOperMetric        OBJECT-TYPE
    SYNTAX      Unsigned32 (0..16777215)
    MAX-ACCESS  read-only
    STATUS      current
    DESCRIPTION
        "The value of the object tmnxIsisIfLevelOperMetric indicates the
         operational value of the metric being used in this circuit for this
         level.

         System and loop back interface levels will have metric value of 0."
    ::= { tmnxIsisIfLevelEntry 10 }

tmnxIsisIfLvlIPv6UcastAdmMet     OBJECT-TYPE
    SYNTAX      Unsigned32 (0..16777215)
    MAX-ACCESS  read-create
    STATUS      current
    DESCRIPTION
        "The value of the object tmnxIsisIfLvlIPv6UcastAdmMet specifies the
         interface level metric for IPv6 unicast."
    DEFVAL      { 0 }
    ::= { tmnxIsisIfLevelEntry 11 }

tmnxIsisIfLvlIPv6UcastOperMet    OBJECT-TYPE
    SYNTAX      Unsigned32 (0..16777215)
    MAX-ACCESS  read-only
    STATUS      current
    DESCRIPTION
        "The value of the object tmnxIsisIfLvlIPv6UcastOperMet indicates the
         operational value of the IPv6 unicast metric being used with this
         interface level."
    ::= { tmnxIsisIfLevelEntry 12 }

tmnxIsisIfLvlIPv4McastAdmMetric  OBJECT-TYPE
    SYNTAX      Unsigned32 (0..16777215)
    MAX-ACCESS  read-create
    STATUS      current
    DESCRIPTION
        "The value of the object tmnxIsisIfLvlIPv4McastAdmMetric specifies the
         interface level metric for IPv4 multicast."
    DEFVAL      { 0 }
    ::= { tmnxIsisIfLevelEntry 13 }

tmnxIsisIfLvlIPv6McastAdmMetric  OBJECT-TYPE
    SYNTAX      Unsigned32 (0..16777215)
    MAX-ACCESS  read-create
    STATUS      current
    DESCRIPTION
        "The value of the object tmnxIsisIfLvlIPv6McastAdmMetric specifies the
         interface level metric for IPv6 multicast."
    DEFVAL      { 0 }
    ::= { tmnxIsisIfLevelEntry 14 }

tmnxIsisIfLevelLinkGroupName     OBJECT-TYPE
    SYNTAX      TNamedItemOrEmpty
    MAX-ACCESS  read-create
    STATUS      current
    DESCRIPTION
        "The value of the object tmnxIsisIfLevelLinkGroupName specifies the
         ISIS link group associated with this particular level of the
         interface."
    DEFVAL      { ''H }
    ::= { tmnxIsisIfLevelEntry 15 }

tmnxIsisIfLevelSdOffset          OBJECT-TYPE
    SYNTAX      Unsigned32 (0..16777215)
    MAX-ACCESS  read-create
    STATUS      current
    DESCRIPTION
        "The value of the object tmnxIsisIfLevelSdOffset specifies the offset
         by which the IS-IS interface metric should be increased upon receiving
         the signal degrade threshold event."
    DEFVAL      { 0 }
    ::= { tmnxIsisIfLevelEntry 16 }

tmnxIsisIfLevelSfOffset          OBJECT-TYPE
    SYNTAX      Unsigned32 (0..16777215)
    MAX-ACCESS  read-create
    STATUS      current
    DESCRIPTION
        "The value of the object tmnxIsisIfLevelSfOffset specifies the offset
         by which the IS-IS interface metric should be further increased in
         addition to the offset specified by tmnxIsisIfLevelSdOffset upon
         receiving the signal fail threshold event."
    DEFVAL      { 0 }
    ::= { tmnxIsisIfLevelEntry 17 }

tmnxIsisIfLvlIPv4McastOperMetric OBJECT-TYPE
    SYNTAX      Unsigned32 (0..16777215)
    MAX-ACCESS  read-only
    STATUS      current
    DESCRIPTION
        "The value of the object tmnxIsisIfLvlIPv4McastOperMetric indicates the
         operational value of the interface level metric for IPv4 multicast."
    ::= { tmnxIsisIfLevelEntry 18 }

tmnxIsisIfLvlIPv6McastOperMetric OBJECT-TYPE
    SYNTAX      Unsigned32 (0..16777215)
    MAX-ACCESS  read-only
    STATUS      current
    DESCRIPTION
        "The value of the object tmnxIsisIfLvlIPv6McastOperMetric indicates the
         operational value of the interface level metric for IPv6 multicast."
    ::= { tmnxIsisIfLevelEntry 19 }

tmnxIsisIfLevelHelloAuthKeyChain OBJECT-TYPE
    SYNTAX      TNamedItemOrEmpty
    MAX-ACCESS  read-create
    STATUS      current
    DESCRIPTION
        "The value of tmnxIsisIfLevelHelloAuthKeyChain specifies the keychain
         to use to sign and/or authenticate the IS-IS instance.

         The keychain name is defined by tmnxKeyChainName and is the index for
         TIMETRA-SECURITY-MIB::tmnxKeyChainTable"
    DEFVAL      { ''H }
    ::= { tmnxIsisIfLevelEntry 20 }

tmnxIsisIfLevelLspTxQCount       OBJECT-TYPE
    SYNTAX      Unsigned32
    MAX-ACCESS  read-only
    STATUS      current
    DESCRIPTION
        "The value of the object tmnxIsisIfLevelLspTxQCount indicates how many
         LSPs are in the transmit queue of this interface for this ISIS level."
    ::= { tmnxIsisIfLevelEntry 21 }

tmnxIsisIfLevelHelloPadding      OBJECT-TYPE
    SYNTAX      INTEGER {
        disable  (0),
        adaptive (1),
        loose    (2),
        strict   (3),
        none     (4)
    }
    MAX-ACCESS  read-create
    STATUS      current
    DESCRIPTION
        "The value of the object tmnxIsisIfLevelHelloPadding specifies whether
         padding should be done on the ISIS hello packets.

         If the value of tmnxIsisIfLevelHelloPadding is set to disable, the
         padding is disabled on all types of interfaces for all adjacency
         states. However, padding may be done if it is configured at one of the
         higher/parent levels.

         If the value of tmnxIsisIfLevelHelloPadding is set to adaptive, the
         padding is done until the state of the neighbor adjacency is up.

         If the value of tmnxIsisIfLevelHelloPadding is set to loose, the
         padding is done until the state of the neighbor adjacency is
         initialized.

         If the value of tmnxIsisIfLevelHelloPadding is set to strict, the
         padding is done for all adjacency states.

         If the value of tmnxIsisIfLevelHelloPadding is set to none, the
         padding is disabled on all types of interfaces for all adjacency
         states. Also, padding will not be done even if it is configured at one
         of the higher/parent levels."
    DEFVAL      { disable }
    ::= { tmnxIsisIfLevelEntry 22 }

tmnxIsisIfAdjSetTable            OBJECT-TYPE
    SYNTAX      SEQUENCE OF TmnxIsisIfAdjSetEntry
    MAX-ACCESS  not-accessible
    STATUS      current
    DESCRIPTION
        "The tmnxIsisIfAdjSetTable maintains list of Adjacency Sets assigned to
         an interface."
    ::= { tmnxIsisIfObjs 3 }

tmnxIsisIfAdjSetEntry            OBJECT-TYPE
    SYNTAX      TmnxIsisIfAdjSetEntry
    MAX-ACCESS  not-accessible
    STATUS      current
    DESCRIPTION
        "Each row entry in the tmnxIsisIfAdjSetTable indicates that the
         interface is assigned to an adjacency set (tmnxIsisAdjSetEntry).  The
         adjacency-set must exist under segment routing before it can be
         assigned to an interface"
    INDEX       {
        vRtrID,
        isisSysInstance,
        vRtrIfIndex,
        tmnxIsisIfAdjSetId
    }
    ::= { tmnxIsisIfAdjSetTable 1 }

TmnxIsisIfAdjSetEntry            ::= SEQUENCE
{
    tmnxIsisIfAdjSetId               Unsigned32,
    tmnxIsisIfAdjSetRowStatus        RowStatus,
    tmnxIsisIfAdjSetIdLstCh          TimeStamp
}

tmnxIsisIfAdjSetId               OBJECT-TYPE
    SYNTAX      Unsigned32 (1..4294967295)
    MAX-ACCESS  not-accessible
    STATUS      current
    DESCRIPTION
        "The value of tmnxIsisIfAdjSetId specifies an identifier for given
         adjacency set."
    ::= { tmnxIsisIfAdjSetEntry 1 }

tmnxIsisIfAdjSetRowStatus        OBJECT-TYPE
    SYNTAX      RowStatus
    MAX-ACCESS  read-create
    STATUS      current
    DESCRIPTION
        "The value of the object tmnxIsisIfAdjSetRowStatus specifies the row
         status used for creation, deletion, or control of
         tmnxIsisIfAdjSetTable entries."
    ::= { tmnxIsisIfAdjSetEntry 2 }

tmnxIsisIfAdjSetIdLstCh          OBJECT-TYPE
    SYNTAX      TimeStamp
    MAX-ACCESS  read-only
    STATUS      current
    DESCRIPTION
        "The value of the object tmnxIsisIfAdjSetIdLstCh indicates the
         sysUpTime when this row was last modified."
    ::= { tmnxIsisIfAdjSetEntry 3 }

tmnxIsisIfFlexAlgoTable          OBJECT-TYPE
    SYNTAX      SEQUENCE OF TmnxIsisIfFlexAlgoEntry
    MAX-ACCESS  not-accessible
    STATUS      current
    DESCRIPTION
        "The table tmnxIsisIfFlexAlgoTable contains the information pertaining
         to a Flexible Algorithm on an ISIS interface."
    ::= { tmnxIsisIfObjs 4 }

tmnxIsisIfFlexAlgoEntry          OBJECT-TYPE
    SYNTAX      TmnxIsisIfFlexAlgoEntry
    MAX-ACCESS  not-accessible
    STATUS      current
    DESCRIPTION
        "Each row entry in tmnxIsisIfFlexAlgoTable represents a Flexible
         Algorithm on an ISIS interface.

         Rows in this table can be created and destroyed by SNMP Set operations
         on the object tmnxIsisIfFlexAlgoRowStatus"
    INDEX       {
        vRtrID,
        isisSysInstance,
        vRtrIfIndex,
        tmnxIsisIfFlexAlgoId
    }
    ::= { tmnxIsisIfFlexAlgoTable 1 }

TmnxIsisIfFlexAlgoEntry          ::= SEQUENCE
{
    tmnxIsisIfFlexAlgoId             TmnxFlexAlgoId,
    tmnxIsisIfFlexAlgoLastChanged    TimeStamp,
    tmnxIsisIfFlexAlgoRowStatus      RowStatus,
    tmnxIsisIfFlexAlgoIpv4SidType    INTEGER,
    tmnxIsisIfFlexAlgoIpv4SidValue   Unsigned32,
    tmnxIsisIfFlexAlgoIpv6SidType    INTEGER,
    tmnxIsisIfFlexAlgoIpv6SidValue   Unsigned32
}

tmnxIsisIfFlexAlgoId             OBJECT-TYPE
    SYNTAX      TmnxFlexAlgoId
    MAX-ACCESS  not-accessible
    STATUS      current
    DESCRIPTION
        "The value of the object tmnxIsisIfFlexAlgoId specifies the identifier
         of the Flexible Algorithm."
    ::= { tmnxIsisIfFlexAlgoEntry 1 }

tmnxIsisIfFlexAlgoLastChanged    OBJECT-TYPE
    SYNTAX      TimeStamp
    MAX-ACCESS  read-only
    STATUS      current
    DESCRIPTION
        "The value of the object tmnxIsisIfFlexAlgoLastChanged indicates the
         sysUpTime when this row was last modified."
    ::= { tmnxIsisIfFlexAlgoEntry 2 }

tmnxIsisIfFlexAlgoRowStatus      OBJECT-TYPE
    SYNTAX      RowStatus
    MAX-ACCESS  read-create
    STATUS      current
    DESCRIPTION
        "The value of the object tmnxIsisIfFlexAlgoRowStatus specifies the row
         status used for creation, deletion, or control of
         tmnxIsisIfFlexAlgoTable entries."
    ::= { tmnxIsisIfFlexAlgoEntry 3 }

tmnxIsisIfFlexAlgoIpv4SidType    OBJECT-TYPE
    SYNTAX      INTEGER {
        none  (0),
        index (1),
        label (2)
    }
    MAX-ACCESS  read-create
    STATUS      current
    DESCRIPTION
        "The value of tmnxIsisIfFlexAlgoIpv4SidType specifies how the value of
         tmnxIsisIfFlexAlgoIpv4SidValue shall be interpreted."
    DEFVAL      { none }
    ::= { tmnxIsisIfFlexAlgoEntry 4 }

tmnxIsisIfFlexAlgoIpv4SidValue   OBJECT-TYPE
    SYNTAX      Unsigned32
    MAX-ACCESS  read-create
    STATUS      current
    DESCRIPTION
        "The value of the object tmnxIsisIfFlexAlgoIpv4SidValue specifies the
         IPv4 node SID label or index for this flex-algo on the interface."
    DEFVAL      { 0 }
    ::= { tmnxIsisIfFlexAlgoEntry 5 }

tmnxIsisIfFlexAlgoIpv6SidType    OBJECT-TYPE
    SYNTAX      INTEGER {
        none  (0),
        index (1),
        label (2)
    }
    MAX-ACCESS  read-create
    STATUS      current
    DESCRIPTION
        "The value of tmnxIsisIfFlexAlgoIpv6SidType specifies how the value of
         tmnxIsisIfFlexAlgoIpv6SidValue shall be interpreted."
    DEFVAL      { none }
    ::= { tmnxIsisIfFlexAlgoEntry 6 }

tmnxIsisIfFlexAlgoIpv6SidValue   OBJECT-TYPE
    SYNTAX      Unsigned32
    MAX-ACCESS  read-create
    STATUS      current
    DESCRIPTION
        "The value of the object tmnxIsisIfFlexAlgoIpv6SidValue specifies the
         IPv6 node SID label or index for this flex-algo on the interface."
    DEFVAL      { 0 }
    ::= { tmnxIsisIfFlexAlgoEntry 7 }

tmnxIsisAdjObjs                  OBJECT IDENTIFIER ::= { tmnxIsisObjs 3 }

tmnxIsisISAdjTable               OBJECT-TYPE
    SYNTAX      SEQUENCE OF TmnxIsisISAdjEntry
    MAX-ACCESS  not-accessible
    STATUS      current
    DESCRIPTION
        "The tmnxIsisISAdjTable is the table of adjacencies to Intermediate
         Systems and their operational status information."
    ::= { tmnxIsisAdjObjs 1 }

tmnxIsisISAdjEntry               OBJECT-TYPE
    SYNTAX      TmnxIsisISAdjEntry
    MAX-ACCESS  not-accessible
    STATUS      current
    DESCRIPTION
        "Each row entry in the tmnxIsisISAdjTable represents an adjacency to an
         Intermediate System on this system."
    INDEX       {
        vRtrID,
        isisSysInstance,
        isisCircIndex,
        isisISAdjIndex
    }
    ::= { tmnxIsisISAdjTable 1 }

TmnxIsisISAdjEntry               ::= SEQUENCE
{
    tmnxIsisISAdjExpiresIn           Integer32,
    tmnxIsisISAdjCircLevel           INTEGER,
    tmnxIsisISAdjNeighborIP          IpAddress,
    tmnxIsisISAdjRestartSupport      TruthValue,
    tmnxIsisISAdjRestartStatus       INTEGER,
    tmnxIsisISAdjRestartSupressed    TruthValue,
    tmnxIsisISAdjNumRestarts         Unsigned32,
    tmnxIsisISAdjLastRestartTime     TimeStamp,
    tmnxIsisISAdjNeighborIPv6Type    InetAddressType,
    tmnxIsisISAdjNeighborIPv6        InetAddress,
    tmnxIsisISAdjMtEnabled           TruthValue,
    tmnxIsisISAdjMtId0               TruthValue,
    tmnxIsisISAdjMtId2               TruthValue,
    tmnxIsisISAdjMtId3               TruthValue,
    tmnxIsisISAdjMtId4               TruthValue,
    tmnxIsisISAdjIpv4SidType         INTEGER,
    tmnxIsisISAdjIpv4SidValue        Unsigned32,
    tmnxIsisISAdjIpv6SidType         INTEGER,
    tmnxIsisISAdjIpv6SidValue        Unsigned32,
    tmnxIsisISAdjMtId0BfdRequired    TruthValue,
    tmnxIsisISAdjMtId2BfdRequired    TruthValue,
    tmnxIsisISAdjMtId3BfdRequired    TruthValue,
    tmnxIsisISAdjMtId4BfdRequired    TruthValue,
    tmnxIsisISAdjMtId0BfdUsable      TruthValue,
    tmnxIsisISAdjMtId2BfdUsable      TruthValue,
    tmnxIsisISAdjMtId3BfdUsable      TruthValue,
    tmnxIsisISAdjMtId4BfdUsable      TruthValue,
    tmnxIsisISAdjSecondIpv4SidType   INTEGER,
    tmnxIsisISAdjSecondIpv4SidValue  Unsigned32,
    tmnxIsisISAdjSecondIpv6SidType   INTEGER,
    tmnxIsisISAdjSecondIpv6SidValue  Unsigned32,
    tmnxIsisISAdjIpv4SidBackup       TruthValue,
    tmnxIsisISAdjIpv6SidBackup       TruthValue,
    tmnxIsisISAdjSecondIpv4SidBackup TruthValue,
    tmnxIsisISAdjSecondIpv6SidBackup TruthValue
}

tmnxIsisISAdjExpiresIn           OBJECT-TYPE
    SYNTAX      Integer32 (0..65535)
    UNITS       "seconds"
    MAX-ACCESS  read-only
    STATUS      current
    DESCRIPTION
        "The value of the object tmnxIsisISAdjExpiresIn indicates the time in
         which the adjacency will expire if no hello packets are received."
    ::= { tmnxIsisISAdjEntry 1 }

tmnxIsisISAdjCircLevel           OBJECT-TYPE
    SYNTAX      INTEGER {
        level1   (1),
        level2   (2),
        level1L2 (3),
        unknown  (4)
    }
    MAX-ACCESS  read-only
    STATUS      current
    DESCRIPTION
        "The value of the object tmnxIsisISAdjCircLevel indicates the circuit
         type of the adjacency as advertised."
    ::= { tmnxIsisISAdjEntry 2 }

tmnxIsisISAdjNeighborIP          OBJECT-TYPE
    SYNTAX      IpAddress
    MAX-ACCESS  read-only
    STATUS      current
    DESCRIPTION
        "The value of the object tmnxIsisISAdjNeighborIP indicates the IP
         address of the neighbor with which adjacency is formed."
    ::= { tmnxIsisISAdjEntry 3 }

tmnxIsisISAdjRestartSupport      OBJECT-TYPE
    SYNTAX      TruthValue
    MAX-ACCESS  read-only
    STATUS      current
    DESCRIPTION
        "The value of the object tmnxIsisISAdjRestartSupport indicates whether
         adjacency supports ISIS graceful restart.

         If tmnxIsisISAdjRestartSupport has a value of 'true' the adjacency
         supports graceful restart."
    ::= { tmnxIsisISAdjEntry 4 }

tmnxIsisISAdjRestartStatus       OBJECT-TYPE
    SYNTAX      INTEGER {
        notHelping      (1),
        restarting      (2),
        restartComplete (3),
        helping         (4),
        aborted         (5)
    }
    MAX-ACCESS  read-only
    STATUS      current
    DESCRIPTION
        "The value of the object tmnxIsisISAdjRestartStatus indicates the
         graceful restart status of the adjacency."
    ::= { tmnxIsisISAdjEntry 5 }

tmnxIsisISAdjRestartSupressed    OBJECT-TYPE
    SYNTAX      TruthValue
    MAX-ACCESS  read-only
    STATUS      current
    DESCRIPTION
        "The value of the object tmnxIsisISAdjRestartSupressed indicates if the
         adjacency has requested this router to suppress advertisement of the
         adjacency in this router's LSPs.

         If tmnxIsisISAdjRestartSupressed has a value of 'true' the adjacency
         has requested to suppress advertisement of the LSPs."
    ::= { tmnxIsisISAdjEntry 6 }

tmnxIsisISAdjNumRestarts         OBJECT-TYPE
    SYNTAX      Unsigned32
    MAX-ACCESS  read-only
    STATUS      current
    DESCRIPTION
        "The value of the object tmnxIsisISAdjNumRestarts indicates the number
         of times the adjacency has attempted restart."
    ::= { tmnxIsisISAdjEntry 7 }

tmnxIsisISAdjLastRestartTime     OBJECT-TYPE
    SYNTAX      TimeStamp
    MAX-ACCESS  read-only
    STATUS      current
    DESCRIPTION
        "The value of the object tmnxIsisISAdjLastRestartTime indicates the
         last time the adjacency attempted restart."
    ::= { tmnxIsisISAdjEntry 8 }

tmnxIsisISAdjNeighborIPv6Type    OBJECT-TYPE
    SYNTAX      InetAddressType
    MAX-ACCESS  read-only
    STATUS      current
    DESCRIPTION
        "The value of the object tmnxIsisISAdjNeighborIPv6Type indicates the IP
         address type of tmnxIsisISAdjNeighborIPv6; it will be 'ipv6', 'ipv6z'
         or 'unknown'."
    ::= { tmnxIsisISAdjEntry 9 }

tmnxIsisISAdjNeighborIPv6        OBJECT-TYPE
    SYNTAX      InetAddress (SIZE (0|16|20))
    MAX-ACCESS  read-only
    STATUS      current
    DESCRIPTION
        "The value of the object tmnxIsisISAdjNeighborIPv6 indicates the IP
         address of the neighbor with which an IPv6-adjacency is formed; this
         will always be an IPv6 address."
    ::= { tmnxIsisISAdjEntry 10 }

tmnxIsisISAdjMtEnabled           OBJECT-TYPE
    SYNTAX      TruthValue
    MAX-ACCESS  read-only
    STATUS      current
    DESCRIPTION
        "The value of the object tmnxIsisISAdjMtEnabled indicates if the ISIS
         multi-topology protocol is supported on the neighbor.

         If the value of tmnxIsisISAdjMtEnabled is 'true', ISIS multi-topology
         protocol is enabled on the neighbor."
    ::= { tmnxIsisISAdjEntry 11 }

tmnxIsisISAdjMtId0               OBJECT-TYPE
    SYNTAX      TruthValue
    MAX-ACCESS  read-only
    STATUS      current
    DESCRIPTION
        "The value of the object tmnxIsisISAdjMtId0 indicates if the native
         topology is supported on the neighbor.

         If the value of tmnxIsisISAdjMtId0 is 'true', native topology is
         supported on the neighbor."
    ::= { tmnxIsisISAdjEntry 12 }

tmnxIsisISAdjMtId2               OBJECT-TYPE
    SYNTAX      TruthValue
    MAX-ACCESS  read-only
    STATUS      current
    DESCRIPTION
        "The value of the object tmnxIsisISAdjMtId2 indicates if the
         multi-topology for IPv6 is supported on the neighbor.

         If the value of tmnxIsisISAdjMtId2 is 'true', multi-topology for IPv6
         is supported on the neighbor."
    ::= { tmnxIsisISAdjEntry 13 }

tmnxIsisISAdjMtId3               OBJECT-TYPE
    SYNTAX      TruthValue
    MAX-ACCESS  read-only
    STATUS      current
    DESCRIPTION
        "The value of the object tmnxIsisISAdjMtId3 indicates if the MT 3 IPv4
         topology is supported on the neighbor.

         If the value of tmnxIsisISAdjMtId3 is 'true', MT 3 IPv4 topology is
         supported on the neighbor."
    ::= { tmnxIsisISAdjEntry 14 }

tmnxIsisISAdjMtId4               OBJECT-TYPE
    SYNTAX      TruthValue
    MAX-ACCESS  read-only
    STATUS      current
    DESCRIPTION
        "The value of the object tmnxIsisISAdjMtId4 indicates if the MT 4 IPv6
         topology is supported on the neighbor.

         If the value of tmnxIsisISAdjMtId4 is 'true', MT 4 IPv6 topology is
         supported on the neighbor."
    ::= { tmnxIsisISAdjEntry 15 }

tmnxIsisISAdjIpv4SidType         OBJECT-TYPE
    SYNTAX      INTEGER {
        none      (0),
        index     (1),
        mplsLabel (2)
    }
    MAX-ACCESS  read-only
    STATUS      current
    DESCRIPTION
        "The value of tmnxIsisISAdjIpv4SidType indicates how the value of
         tmnxIsisISAdjIpv4SidValue shall be interpreted."
    ::= { tmnxIsisISAdjEntry 16 }

tmnxIsisISAdjIpv4SidValue        OBJECT-TYPE
    SYNTAX      Unsigned32
    MAX-ACCESS  read-only
    STATUS      current
    DESCRIPTION
        "The value of the object tmnxIsisISAdjIpv4SidValue indicates the IPv4
         SID label or index for this adjacency."
    ::= { tmnxIsisISAdjEntry 17 }

tmnxIsisISAdjIpv6SidType         OBJECT-TYPE
    SYNTAX      INTEGER {
        none      (0),
        index     (1),
        mplsLabel (2),
        ipv6Label (3)
    }
    MAX-ACCESS  read-only
    STATUS      current
    DESCRIPTION
        "The value of tmnxIsisISAdjIpv6SidType indicates how the value of
         tmnxIsisISAdjIpv6SidValue shall be interpreted."
    ::= { tmnxIsisISAdjEntry 18 }

tmnxIsisISAdjIpv6SidValue        OBJECT-TYPE
    SYNTAX      Unsigned32
    MAX-ACCESS  read-only
    STATUS      current
    DESCRIPTION
        "The value of the object tmnxIsisISAdjIpv6SidValue indicates the IPv6
         SID label or index for this adjacency."
    ::= { tmnxIsisISAdjEntry 19 }

tmnxIsisISAdjMtId0BfdRequired    OBJECT-TYPE
    SYNTAX      TruthValue
    MAX-ACCESS  read-only
    STATUS      current
    DESCRIPTION
        "The value of the object tmnxIsisISAdjMtId0BfdRequired indicates if BFD
         session is required for this Multi Topology before bringing the
         adjacency to FULL state, as described in RFC6213."
    ::= { tmnxIsisISAdjEntry 20 }

tmnxIsisISAdjMtId2BfdRequired    OBJECT-TYPE
    SYNTAX      TruthValue
    MAX-ACCESS  read-only
    STATUS      current
    DESCRIPTION
        "The value of the object tmnxIsisISAdjMtId2BfdRequired indicates if BFD
         session is required for this Multi Topology before bringing the
         adjacency to FULL state, as described in RFC6213."
    ::= { tmnxIsisISAdjEntry 21 }

tmnxIsisISAdjMtId3BfdRequired    OBJECT-TYPE
    SYNTAX      TruthValue
    MAX-ACCESS  read-only
    STATUS      current
    DESCRIPTION
        "The value of the object tmnxIsisISAdjMtId3BfdRequired indicates if BFD
         session is required for this Multi Topology before bringing the
         adjacency to FULL state, as described in RFC6213."
    ::= { tmnxIsisISAdjEntry 22 }

tmnxIsisISAdjMtId4BfdRequired    OBJECT-TYPE
    SYNTAX      TruthValue
    MAX-ACCESS  read-only
    STATUS      current
    DESCRIPTION
        "The value of the object tmnxIsisISAdjMtId4BfdRequired indicates if BFD
         session is required for this Multi Topology before bringing the
         adjacency to FULL state, as described in RFC6213."
    ::= { tmnxIsisISAdjEntry 23 }

tmnxIsisISAdjMtId0BfdUsable      OBJECT-TYPE
    SYNTAX      TruthValue
    MAX-ACCESS  read-only
    STATUS      current
    DESCRIPTION
        "The value of the object tmnxIsisISAdjMtId0BfdUsable indicates if BFD
         session for this Multi Topology is usable, that is either not required
         or in state UP, as described in RFC6213."
    ::= { tmnxIsisISAdjEntry 24 }

tmnxIsisISAdjMtId2BfdUsable      OBJECT-TYPE
    SYNTAX      TruthValue
    MAX-ACCESS  read-only
    STATUS      current
    DESCRIPTION
        "The value of the object tmnxIsisISAdjMtId2BfdUsable indicates if BFD
         session for this Multi Topology is usable, that is either not required
         or in state UP, as described in RFC6213."
    ::= { tmnxIsisISAdjEntry 25 }

tmnxIsisISAdjMtId3BfdUsable      OBJECT-TYPE
    SYNTAX      TruthValue
    MAX-ACCESS  read-only
    STATUS      current
    DESCRIPTION
        "The value of the object tmnxIsisISAdjMtId3BfdUsable indicates if BFD
         session for this Multi Topology is usable, that is either not required
         or in state UP, as described in RFC6213."
    ::= { tmnxIsisISAdjEntry 26 }

tmnxIsisISAdjMtId4BfdUsable      OBJECT-TYPE
    SYNTAX      TruthValue
    MAX-ACCESS  read-only
    STATUS      current
    DESCRIPTION
        "The value of the object tmnxIsisISAdjMtId4BfdUsable indicates if BFD
         session for this Multi Topology is usable, that is either not required
         or in state UP, as described in RFC6213."
    ::= { tmnxIsisISAdjEntry 27 }

tmnxIsisISAdjSecondIpv4SidType   OBJECT-TYPE
    SYNTAX      INTEGER {
        none      (0),
        index     (1),
        mplsLabel (2)
    }
    MAX-ACCESS  read-only
    STATUS      current
    DESCRIPTION
        "The value of tmnxIsisISAdjSecondIpv4SidType indicates how the value of
         tmnxIsisISAdjSecondIpv4SidValue shall be interpreted."
    ::= { tmnxIsisISAdjEntry 28 }

tmnxIsisISAdjSecondIpv4SidValue  OBJECT-TYPE
    SYNTAX      Unsigned32
    MAX-ACCESS  read-only
    STATUS      current
    DESCRIPTION
        "The value of the object tmnxIsisISAdjSecondIpv4SidValue indicates the
         secondary IPv4 SID label or index for this adjacency."
    ::= { tmnxIsisISAdjEntry 29 }

tmnxIsisISAdjSecondIpv6SidType   OBJECT-TYPE
    SYNTAX      INTEGER {
        none      (0),
        index     (1),
        mplsLabel (2),
        ipv6Label (3)
    }
    MAX-ACCESS  read-only
    STATUS      current
    DESCRIPTION
        "The value of tmnxIsisISAdjSecondIpv6SidType indicates how the value of
         tmnxIsisISAdjSecondIpv6SidValue shall be interpreted."
    ::= { tmnxIsisISAdjEntry 30 }

tmnxIsisISAdjSecondIpv6SidValue  OBJECT-TYPE
    SYNTAX      Unsigned32
    MAX-ACCESS  read-only
    STATUS      current
    DESCRIPTION
        "The value of the object tmnxIsisISAdjSecondIpv6SidValue indicates the
         secondary IPv6 SID label or index for this adjacency."
    ::= { tmnxIsisISAdjEntry 31 }

tmnxIsisISAdjIpv4SidBackup       OBJECT-TYPE
    SYNTAX      TruthValue
    MAX-ACCESS  read-only
    STATUS      current
    DESCRIPTION
        "The value of tmnxIsisISAdjIpv4SidBackup indicates whether the SID for
         the IPv4 adjacency is eligible for protection or not."
    ::= { tmnxIsisISAdjEntry 32 }

tmnxIsisISAdjIpv6SidBackup       OBJECT-TYPE
    SYNTAX      TruthValue
    MAX-ACCESS  read-only
    STATUS      current
    DESCRIPTION
        "The value of tmnxIsisISAdjIpv6SidBackup indicates whether the SID for
         the IPv6 adjacency is eligible for protection or not."
    ::= { tmnxIsisISAdjEntry 33 }

tmnxIsisISAdjSecondIpv4SidBackup OBJECT-TYPE
    SYNTAX      TruthValue
    MAX-ACCESS  read-only
    STATUS      current
    DESCRIPTION
        "The value of tmnxIsisISAdjSecondIpv4SidBackup indicates whether the
         secondary SID for the IPv4 adjacency is eligible for protection or
         not."
    ::= { tmnxIsisISAdjEntry 34 }

tmnxIsisISAdjSecondIpv6SidBackup OBJECT-TYPE
    SYNTAX      TruthValue
    MAX-ACCESS  read-only
    STATUS      current
    DESCRIPTION
        "The value of tmnxIsisISAdjSecondIpv6SidBackup indicates whether the
         secondary SID for the IPv6 adjacency is eligible for protection or
         not."
    ::= { tmnxIsisISAdjEntry 35 }

tmnxIsisNotificationObjs         OBJECT IDENTIFIER ::= { tmnxIsisObjs 4 }

tmnxIsisNotificationTable        OBJECT-TYPE
    SYNTAX      SEQUENCE OF TmnxIsisNotificationEntry
    MAX-ACCESS  not-accessible
    STATUS      current
    DESCRIPTION
        "Objects seen in the most recent notification this instance of the
         IS-IS protocol."
    ::= { tmnxIsisNotificationObjs 1 }

tmnxIsisNotificationEntry        OBJECT-TYPE
    SYNTAX      TmnxIsisNotificationEntry
    MAX-ACCESS  not-accessible
    STATUS      current
    DESCRIPTION
        "Each entry defines variables relevant to notifications for one
         instance of the IS-IS protocol."
    INDEX       {
        vRtrID,
        isisSysInstance
    }
    ::= { tmnxIsisNotificationTable 1 }

TmnxIsisNotificationEntry        ::= SEQUENCE
{
    tmnxIsisNotifTrapLSPID           OCTET STRING,
    tmnxIsisNotifSystemLevel         INTEGER,
    tmnxIsisNotifPDUFragment         OCTET STRING,
    tmnxIsisNotifFieldLen            Integer32,
    tmnxIsisNotifMaxAreaAddress      Integer32,
    tmnxIsisNotifProtocolVersion     Integer32,
    tmnxIsisNotifLSPSize             Integer32,
    tmnxIsisNotifOriginatingBuffSize Integer32,
    tmnxIsisNotifProtocolsSupported  OCTET STRING,
    tmnxIsisNotifNbrSysId            OCTET STRING,
    tmnxIsisNotifPurgeOriginator     SystemID,
    tmnxIsisNotifPurgeSource         SystemID,
    tmnxIsisNotifAdditionalInfo      DisplayString,
    tmnxIsisNotifCircMtuSize         Integer32,
    tmnxIsisNotifCircMinReqMtuSize   Integer32,
    tmnxIsisNotifyIfIndex            InterfaceIndex
}

tmnxIsisNotifTrapLSPID           OBJECT-TYPE
    SYNTAX      OCTET STRING (SIZE (0|8))
    MAX-ACCESS  read-only
    STATUS      current
    DESCRIPTION
        "The object tmnxIsisNotifTrapLSPID is an Octet String that uniquely
         identifies a Link State PDU."
    ::= { tmnxIsisNotificationEntry 1 }

tmnxIsisNotifSystemLevel         OBJECT-TYPE
    SYNTAX      INTEGER {
        l1   (1),
        l2   (2),
        l1l2 (3)
    }
    MAX-ACCESS  read-only
    STATUS      current
    DESCRIPTION
        "The object tmnxIsisNotifSystemLevel identifies the level the
         notification applies to."
    ::= { tmnxIsisNotificationEntry 2 }

tmnxIsisNotifPDUFragment         OBJECT-TYPE
    SYNTAX      OCTET STRING (SIZE (0..64))
    MAX-ACCESS  read-only
    STATUS      current
    DESCRIPTION
        "The object tmnxIsisNotifPDUFragment holds up to the first 64 bytes of
         a PDU that triggered the notification."
    ::= { tmnxIsisNotificationEntry 3 }

tmnxIsisNotifFieldLen            OBJECT-TYPE
    SYNTAX      Integer32 (0..255)
    MAX-ACCESS  read-only
    STATUS      current
    DESCRIPTION
        "The object tmnxIsisNotifFieldLen holds the System ID length reported
         in a PDU we received."
    ::= { tmnxIsisNotificationEntry 4 }

tmnxIsisNotifMaxAreaAddress      OBJECT-TYPE
    SYNTAX      Integer32 (0..255)
    MAX-ACCESS  read-only
    STATUS      current
    DESCRIPTION
        "The object tmnxIsisNotifMaxAreaAddress holds the Max Area Addresses
         reported in a PDU we received."
    ::= { tmnxIsisNotificationEntry 5 }

tmnxIsisNotifProtocolVersion     OBJECT-TYPE
    SYNTAX      Integer32 (0..255)
    MAX-ACCESS  read-only
    STATUS      current
    DESCRIPTION
        "The object tmnxIsisNotifProtocolVersion holds the Protocol version
         reported in a PDU we received."
    ::= { tmnxIsisNotificationEntry 6 }

tmnxIsisNotifLSPSize             OBJECT-TYPE
    SYNTAX      Integer32 (0..2147483647)
    MAX-ACCESS  read-only
    STATUS      current
    DESCRIPTION
        "The object tmnxIsisNotifLSPSize holds the size of LSP we received that
         is too big to forward."
    ::= { tmnxIsisNotificationEntry 7 }

tmnxIsisNotifOriginatingBuffSize OBJECT-TYPE
    SYNTAX      Integer32 (0..2147483647)
    MAX-ACCESS  read-only
    STATUS      current
    DESCRIPTION
        "The object tmnxIsisNotifOriginatingBuffSize holds the size of
         tmnxIsisSysOrigL1LSPBuffSize or tmnxIsisSysOrigL2LSPBuffSize
         advertised by peer in TLV."
    ::= { tmnxIsisNotificationEntry 8 }

tmnxIsisNotifProtocolsSupported  OBJECT-TYPE
    SYNTAX      OCTET STRING (SIZE (0..255))
    MAX-ACCESS  read-only
    STATUS      current
    DESCRIPTION
        "The object tmnxIsisNotifProtocolsSupported contains the list of
         protocols supported by an adjacent system and may be empty."
    ::= { tmnxIsisNotificationEntry 9 }

tmnxIsisNotifNbrSysId            OBJECT-TYPE
    SYNTAX      OCTET STRING (SIZE (0..6))
    MAX-ACCESS  accessible-for-notify
    STATUS      current
    DESCRIPTION
        "The value of the object tmnxIsisNotifNbrSysId indicates the system-id
         of the neighbor associated with the notification."
    ::= { tmnxIsisNotificationEntry 10 }

tmnxIsisNotifPurgeOriginator     OBJECT-TYPE
    SYNTAX      SystemID
    MAX-ACCESS  accessible-for-notify
    STATUS      current
    DESCRIPTION
        "The value of the object tmnxIsisNotifPurgeOriginator indicates the
         system-id of the IS that inserted the Purge Originator Identification
         (POI) TLV in the purge."
    ::= { tmnxIsisNotificationEntry 11 }

tmnxIsisNotifPurgeSource         OBJECT-TYPE
    SYNTAX      SystemID
    MAX-ACCESS  accessible-for-notify
    STATUS      current
    DESCRIPTION
        "The value of the object tmnxIsisNotifPurgeSource indicates the
         system-id of the IS from which the purge was received."
    ::= { tmnxIsisNotificationEntry 12 }

tmnxIsisNotifAdditionalInfo      OBJECT-TYPE
    SYNTAX      DisplayString
    MAX-ACCESS  accessible-for-notify
    STATUS      current
    DESCRIPTION
        "The value of the object tmnxIsisNotifAdditionalInfo is a printable
         character string which contains information about the reason why the
         notification was generated."
    ::= { tmnxIsisNotificationEntry 13 }

tmnxIsisNotifCircMtuSize         OBJECT-TYPE
    SYNTAX      Integer32 (0..2147483647)
    MAX-ACCESS  accessible-for-notify
    STATUS      current
    DESCRIPTION
        "The value of the object tmnxIsisNotifCircMtuSize indicates the size of
         the circuit MTU that is too low to propagate an LSP or SNP."
    ::= { tmnxIsisNotificationEntry 14 }

tmnxIsisNotifCircMinReqMtuSize   OBJECT-TYPE
    SYNTAX      Integer32 (0..2147483647)
    MAX-ACCESS  accessible-for-notify
    STATUS      current
    DESCRIPTION
        "The value of the object tmnxIsisNotifCircMinReqMtuSize indicates the
         minimum required size of the circuit MTU to propagate an LSP or SNP."
    ::= { tmnxIsisNotificationEntry 15 }

tmnxIsisNotifyIfIndex            OBJECT-TYPE
    SYNTAX      InterfaceIndex
    MAX-ACCESS  accessible-for-notify
    STATUS      current
    DESCRIPTION
        "The value of the object tmnxIsisNotifyIfIndex indicates the ISIS
         Interface Index."
    ::= { tmnxIsisNotificationEntry 16 }

tmnxIsisFailureReasonCode        OBJECT-TYPE
    SYNTAX      INTEGER {
        outOfResources (1)
    }
    MAX-ACCESS  accessible-for-notify
    STATUS      current
    DESCRIPTION
        "The value of tmnxIsisFailureReasonCode indicates the reason for the
         last ISIS failure which resulted in it being marked operationally
         down.This object is used by the tmnxIsisFailureDisabled notification."
    ::= { tmnxIsisNotificationObjs 4 }

tmnxIsisNotifPfxSidRangeStartLbl OBJECT-TYPE
    SYNTAX      Unsigned32
    MAX-ACCESS  accessible-for-notify
    STATUS      current
    DESCRIPTION
        "The value of tmnxIsisNotifPfxSidRangeStartLbl indicates the start
         label of the first segment of a Segment Routing Global Block."
    ::= { tmnxIsisNotificationObjs 5 }

tmnxIsisNotifPfxSidRangeMaxIdx   OBJECT-TYPE
    SYNTAX      Unsigned32
    MAX-ACCESS  accessible-for-notify
    STATUS      current
    DESCRIPTION
        "The value of tmnxIsisNotifPfxSidRangeMaxIdx indicates the maximum SID
         index of the first segment of a Segment Routing Global Block."
    ::= { tmnxIsisNotificationObjs 6 }

tmnxIsisNotifPfxSidSysID         OBJECT-TYPE
    SYNTAX      SystemID
    MAX-ACCESS  accessible-for-notify
    STATUS      current
    DESCRIPTION
        "The value of the object tmnxIsisNotifPfxSidSysID indicates the
         system-id of the IS through which this prefix-sid is reachable."
    ::= { tmnxIsisNotificationObjs 7 }

tmnxIsisNotifyDescription        OBJECT-TYPE
    SYNTAX      DisplayString
    MAX-ACCESS  accessible-for-notify
    STATUS      current
    DESCRIPTION
        "The object tmnxIsisNotifyDescription is a printable character string."
    ::= { tmnxIsisNotificationObjs 8 }

tmnxIsisBfdSessSetupFailReason   OBJECT-TYPE
    SYNTAX      INTEGER {
        bfdSessNoError                 (0),
        bfdSessFailMaxSessionLimit     (1),
        bfdSessFailCfgNotProper        (2),
        bfdSessFailSanityCheck         (3),
        bfdSessFailGeneral             (4),
        bfdSessFailInternalProgramming (5),
        bfdSessFailCvDiscrNotFound     (6),
        bfdSessFailMaxPacketRate       (7),
        bfdSessFailHandleReplaced      (8),
        bfdSessFailBfdDisabledOnIntf   (9),
        bfdSessFailConflict            (10),
        bfdSessFailRemDiscrInvalid     (11)
    }
    MAX-ACCESS  accessible-for-notify
    STATUS      current
    DESCRIPTION
        "The value of tmnxIsisBfdSessSetupFailReason indicates the reason for
         the BFD setup failure. This object is used by the
         tmnxIsisAdjBfdSessionSetupFail notification."
    ::= { tmnxIsisNotificationObjs 9 }

tmnxIsisNotifSrgbRangeStartLbl   OBJECT-TYPE
    SYNTAX      Unsigned32
    MAX-ACCESS  accessible-for-notify
    STATUS      current
    DESCRIPTION
        "The value of the object tmnxIsisNotifSrgbRangeStartLbl indicates the
         label at which the SRGB label range starts."
    ::= { tmnxIsisNotificationObjs 10 }

tmnxIsisNotifSrgbRangeMaxIdx     OBJECT-TYPE
    SYNTAX      Unsigned32
    MAX-ACCESS  accessible-for-notify
    STATUS      current
    DESCRIPTION
        "The value of the object tmnxIsisNotifSrgbRangeMaxIdx indicates the
         maximum index for the SRGB label range."
    ::= { tmnxIsisNotificationObjs 11 }

tmnxIsisNotifSrgbAdvRtrSysID     OBJECT-TYPE
    SYNTAX      SystemID
    MAX-ACCESS  accessible-for-notify
    STATUS      current
    DESCRIPTION
        "The value of the object tmnxIsisNotifSrgbAdvRtrSysID indicates the
         system-id of the SRGB advertising router."
    ::= { tmnxIsisNotificationObjs 12 }

tmnxIsisNotifSrgbLevel           OBJECT-TYPE
    SYNTAX      INTEGER {
        level1IS (1),
        level2IS (2)
    }
    MAX-ACCESS  accessible-for-notify
    STATUS      current
    DESCRIPTION
        "The value of the object tmnxIsisNotifSrgbLevel indicates the IS-IS
         Level at which the SRGB was learned."
    ::= { tmnxIsisNotificationObjs 13 }

tmnxIsisNotifSrgbMtId            OBJECT-TYPE
    SYNTAX      Unsigned32
    MAX-ACCESS  accessible-for-notify
    STATUS      current
    DESCRIPTION
        "The value of the object tmnxIsisNotifSrgbMtId indicates the multi
         topology id number for this SRGB."
    ::= { tmnxIsisNotificationObjs 14 }

tmnxIsisNotifStatsIndexStatus    OBJECT-TYPE
    SYNTAX      INTEGER {
        statsIndexAllocNoError    (0),
        statsIndexAllocNoResource (1)
    }
    MAX-ACCESS  accessible-for-notify
    STATUS      current
    DESCRIPTION
        "The value of tmnxIsisNotifStatsIndexStatus indicates the statistic
         index allocation status. This object is used by the
         tmnxIsisSidStatsIndexAlloc notification."
    ::= { tmnxIsisNotificationObjs 15 }

tmnxIsisConformance              OBJECT IDENTIFIER ::= { tmnxSRConfs 88 }

tmnxIsisCompliances              OBJECT IDENTIFIER ::= { tmnxIsisConformance 1 }

tmnxIsisCompliance               MODULE-COMPLIANCE
    STATUS      obsolete
    DESCRIPTION
        "The compliance statement for management of ISIS routing protocol on
         Nokia 7xxx series systems."
    MODULE
        MANDATORY-GROUPS {
            tmnxIsisGroup,
            tmnxIsisIfGroup,
            tmnxIsisAdjGroup,
            tmnxIsisLFAV12v0Group
        }
    ::= { tmnxIsisCompliances 1 }

tmnxIsisNotifyCompliance         MODULE-COMPLIANCE
    STATUS      obsolete
    DESCRIPTION
        "The compliance statement for ISIS notifications on Nokia SROS series
         systems."
    MODULE
        MANDATORY-GROUPS {
            tmnxIsisNotifyGroup
        }
    ::= { tmnxIsisCompliances 2 }

tmnxIsisV13v0Compliance          MODULE-COMPLIANCE
    STATUS      obsolete
    DESCRIPTION
        "The compliance statement for management of ISIS routing protocol on
         Nokia 7xxx series systems 13.0 release."
    MODULE
        MANDATORY-GROUPS {
            tmnxIsisGroup,
            tmnxIsisIfGroup,
            tmnxIsisAdjGroup,
            tmnxIsisLFAV12v0Group,
            tmnxIsisV13v0Group
        }
    ::= { tmnxIsisCompliances 3 }

tmnxIsisNotifyV13v0Compliance    MODULE-COMPLIANCE
    STATUS      obsolete
    DESCRIPTION
        "The compliance statement for ISIS notifications on Nokia 7xxx series
         systems 13.0 release."
    MODULE
        MANDATORY-GROUPS {
            tmnxIsisNotifyGroup,
            tmnxIsisNotifyV13v0Group
        }
    ::= { tmnxIsisCompliances 4 }

tmnxIsisV14v0Compliance          MODULE-COMPLIANCE
    STATUS      obsolete
    DESCRIPTION
        "The compliance statement for management of ISIS routing protocol on
         Nokia 7xxx series systems 14.0 release."
    MODULE
        MANDATORY-GROUPS {
            tmnxIsisGroup,
            tmnxIsisIfGroup,
            tmnxIsisAdjGroup,
            tmnxIsisLFAV12v0Group,
            tmnxIsisV13v0Group,
            tmnxIsisV14v0Group
        }
    ::= { tmnxIsisCompliances 5 }

tmnxIsisNotifyV14v0Compliance    MODULE-COMPLIANCE
    STATUS      obsolete
    DESCRIPTION
        "The compliance statement for ISIS notifications on Nokia 7xxx series
         systems 14.0 release."
    MODULE
        MANDATORY-GROUPS {
            tmnxIsisNotifyGroup,
            tmnxIsisNotifyV13v0Group,
            tmnxIsisNotifyV14v0Group
        }
    ::= { tmnxIsisCompliances 6 }

tmnxIsisV15v0Compliance          MODULE-COMPLIANCE
    STATUS      obsolete
    DESCRIPTION
        "The compliance statement for management of ISIS routing protocol on
         Nokia 7xxx series systems 15.0 release."
    MODULE
        MANDATORY-GROUPS {
            tmnxIsisGroup,
            tmnxIsisIfGroup,
            tmnxIsisAdjGroup,
            tmnxIsisLFAV12v0Group,
            tmnxIsisV13v0Group,
            tmnxIsisV14v0Group,
            tmnxIsisV15v0Group,
            tmnxIsisIgpSC15v0Group,
            tmnxIsisObsolete15v0Group
        }
    ::= { tmnxIsisCompliances 7 }

tmnxIsisNotifyV15v0Compliance    MODULE-COMPLIANCE
    STATUS      current
    DESCRIPTION
        "The compliance statement for ISIS notifications on Nokia 7xxx series
         systems 15.0 release."
    MODULE
        MANDATORY-GROUPS {
            tmnxIsisNotifyGroup,
            tmnxIsisNotifyV13v0Group,
            tmnxIsisNotifyV14v0Group,
            tmnxIsisNotifyV15v0Group
        }
    ::= { tmnxIsisCompliances 8 }

tmnxIsisV16v0Compliance          MODULE-COMPLIANCE
    STATUS      obsolete
    DESCRIPTION
        "The compliance statement for management of ISIS routing protocol on
         Nokia 7xxx series systems 16.0 release."
    MODULE
        MANDATORY-GROUPS {
            tmnxIsisGroup,
            tmnxIsisIfGroup,
            tmnxIsisAdjGroup,
            tmnxIsisLFAV12v0Group,
            tmnxIsisV13v0Group,
            tmnxIsisV14v0Group,
            tmnxIsisV15v0Group,
            tmnxIsisIgpSC15v0Group,
            tmnxIsisV16v0Group,
            tmnxIsisBier16v0Group
        }
    ::= { tmnxIsisCompliances 9 }

tmnxIsisNotifyV16v0Compliance    MODULE-COMPLIANCE
    STATUS      current
    DESCRIPTION
        "The compliance statement for ISIS notifications on Nokia 7xxx series
         systems 16.0 release."
    MODULE
        MANDATORY-GROUPS {
            tmnxIsisNotifyV16v0Group
        }
    ::= { tmnxIsisCompliances 10 }

tmnxIsisV19v0Compliance          MODULE-COMPLIANCE
    STATUS      current
    DESCRIPTION
        "The compliance statement for management of ISIS routing protocol on
         Nokia 7xxx series systems 19.0 release."
    MODULE
        MANDATORY-GROUPS {
            tmnxIsisGroup,
            tmnxIsisIfGroup,
            tmnxIsisAdjGroup,
            tmnxIsisLFAV12v0Group,
            tmnxIsisV13v0Group,
            tmnxIsisV14v0Group,
            tmnxIsisV15v0Group,
            tmnxIsisIgpSC15v0Group,
            tmnxIsisV16v0Group,
            tmnxIsisBier16v0Group,
            tmnxIsisV19v0Group,
            tmnxIsisV19v0ObsoleteGroup
        }
    ::= { tmnxIsisCompliances 11 }

tmnxIsisNotifyV19v0Compliance    MODULE-COMPLIANCE
    STATUS      current
    DESCRIPTION
        "The compliance statement for ISIS notifications on Nokia 7xxx series
         systems 19.0 release."
    MODULE
        MANDATORY-GROUPS {
            tmnxIsisNotifyV19v0Group
        }
    ::= { tmnxIsisCompliances 12 }

tmnxIsisV20v0Compliance          MODULE-COMPLIANCE
    STATUS      current
    DESCRIPTION
        "The compliance statement for management of ISIS routing protocol on
         Nokia 7xxx series systems 20.0 release."
    MODULE
        MANDATORY-GROUPS {
            tmnxIsisV20v0Group
        }
    ::= { tmnxIsisCompliances 13 }

tmnxIsisNotifyV20v0Compliance    MODULE-COMPLIANCE
    STATUS      current
    DESCRIPTION
        "The compliance statement for ISIS notifications on Nokia 7xxx series
         systems 20.0 release."
    MODULE
        MANDATORY-GROUPS {
            tmnxIsisNotifyV20v0Group
        }
    ::= { tmnxIsisCompliances 14 }

tmnxIsisV21v0Compliance          MODULE-COMPLIANCE
    STATUS      current
    DESCRIPTION
        "The compliance statement for management of ISIS routing protocol on
         Nokia 7xxx series systems 21.0 release."
    MODULE
        MANDATORY-GROUPS {
            tmnxIsisSrv6Group,
            tmnxIsisV21v0Group,
            tmnxIsisNotifyV21v0Group
        }
    ::= { tmnxIsisCompliances 15 }

tmnxIsisV22v0Compliance          MODULE-COMPLIANCE
    STATUS      current
    DESCRIPTION
        "The compliance statement for management of ISIS routing protocol on
         Nokia 7xxx series systems 22.0 release."
    MODULE
        MANDATORY-GROUPS {
            tmnxIsisV22v0Group
        }
    ::= { tmnxIsisCompliances 16 }

tmnxIsisV23v0Compliance          MODULE-COMPLIANCE
    STATUS      current
    DESCRIPTION
        "The compliance statement for management of ISIS routing protocol on
         Nokia 7xxx series systems 23.0 release."
    MODULE
        MANDATORY-GROUPS {
            tmnxIsisV23v0Group,
            tmnxIsisNotifyV23v0Group
        }
    ::= { tmnxIsisCompliances 17 }

tmnxIsisV24v0Compliance          MODULE-COMPLIANCE
    STATUS      current
    DESCRIPTION
        "The compliance statement for management of ISIS routing protocol on
         Nokia 7xxx series systems 24.0 release."
    MODULE
        MANDATORY-GROUPS {
            tmnxIsisV24v0Group
        }
    ::= { tmnxIsisCompliances 18 }

tmnxIsisGroups                   OBJECT IDENTIFIER ::= { tmnxIsisConformance 2 }

tmnxIsisGroup                    OBJECT-GROUP
    OBJECTS     {
        tmnxIsisLastEnabledTime,
        tmnxIsisAuthKey,
        tmnxIsisAuthType,
        tmnxIsisAuthCheck,
        tmnxIsisExportPolicy1,
        tmnxIsisExportPolicy2,
        tmnxIsisExportPolicy3,
        tmnxIsisExportPolicy4,
        tmnxIsisExportPolicy5,
        tmnxIsisLspLifetime,
        tmnxIsisOverloadTimeout,
        tmnxIsisOperState,
        tmnxIsisReferenceBw,
        tmnxIsisTrafficEng,
        tmnxIsisShortCuts,
        tmnxIsisSpfHoldTime,
        tmnxIsisLastSpfRun,
        tmnxIsisGracefulRestart,
        tmnxIsisOverloadOnBoot,
        tmnxIsisOverloadOnBootTimeout,
        tmnxIsisSpfWait,
        tmnxIsisSpfInitialWait,
        tmnxIsisSpfSecondWait,
        tmnxIsisLspMaxWait,
        tmnxIsisLspInitialWait,
        tmnxIsisLspSecondWait,
        tmnxIsisCsnpAuthentication,
        tmnxIsisHelloAuthentication,
        tmnxIsisPsnpAuthentication,
        tmnxIsisGRHelperMode,
        tmnxIsisEnableIPv4,
        tmnxIsisUnicastImport,
        tmnxIsisMulticastImport,
        tmnxIsisStrictAdjacencyCheck,
        tmnxIsisManualSpfTrigger,
        tmnxIsisMultiTopology,
        tmnxIsisMultiTopoIPv6Ucast,
        tmnxIsisIPv6RoutingTopo,
        tmnxIsisSysOrigL1LSPBuffSize,
        tmnxIsisSysOrigL2LSPBuffSize,
        tmnxIsisLdpSyncAdminState,
        tmnxIsisIPv6UnicastImport,
        tmnxIsisIPv6MulticastImport,
        tmnxIsisAdvertisePassiveOnly,
        tmnxIsisDefaultRouteTag,
        tmnxIsisSuppressDefault,
        tmnxIsisLdpOverRsvp,
        tmnxIsisExportLimit,
        tmnxIsisExportLimitLogPercent,
        tmnxIsisTotalL1ExportedRoutes,
        tmnxIsisTotalL2ExportedRoutes,
        tmnxIsisRsvpShortcut,
        tmnxIsisAdvertiseTunnelLink,
        tmnxIsisIidTlv,
        tmnxIsisL1MacAddress,
        tmnxIsisL2MacAddress,
        tmnxIsisSysOperL1LSPBuffSize,
        tmnxIsisSysOperL2LSPBuffSize,
        tmnxIsisLoopfreeAlternate,
        tmnxIsisIPv4McastRoutingTopo,
        tmnxIsisIPv6McastRoutingTopo,
        tmnxIsisMultiTopoIPv4Mcast,
        tmnxIsisMultiTopoIPv6Mcast,
        tmnxIsisOverloadMaxMetric,
        tmnxIsisOverloadOnBootMaxMetric,
        tmnxIsisRouterId,
        tmnxIsisAdvRtrCapability,
        tmnxIsisHelloPadding,
        tmnxIsisLspRefreshInterval,
        tmnxIsisIgnoreLspErrors,
        tmnxIsisLevelAuthKey,
        tmnxIsisLevelAuthType,
        tmnxIsisLevelExtPreference,
        tmnxIsisLevelPreference,
        tmnxIsisLevelWideMetricsOnly,
        tmnxIsisLevelOverloadStatus,
        tmnxIsisLevelOverloadTimeLeft,
        tmnxIsisLevelNumLSPs,
        tmnxIsisLevelCsnpAuthentication,
        tmnxIsisLevelHelloAuthentication,
        tmnxIsisLevelPsnpAuthentication,
        tmnxIsisLevelDefMetric,
        tmnxIsisLevelIPv6DefMetric,
        tmnxIsisLevelLoopfreeAltExclude,
        tmnxIsisLevelSpbBridgePriority,
        tmnxIsisLevelSpbForwardTreeTopo,
        tmnxIsisLevelDefIPv4McastMetric,
        tmnxIsisLevelDefIPv6McastMetric,
        tmnxIsisLevelAdvRtrCapability,
        tmnxIsisLevelAuthKeyChain,
        tmnxIsisStatsSpfRuns,
        tmnxIsisStatsLSPRegenerations,
        tmnxIsisStatsInitiatedPurges,
        tmnxIsisStatsLSPRecd,
        tmnxIsisStatsLSPDrop,
        tmnxIsisStatsLSPSent,
        tmnxIsisStatsLSPRetrans,
        tmnxIsisStatsIIHRecd,
        tmnxIsisStatsIIHDrop,
        tmnxIsisStatsIIHSent,
        tmnxIsisStatsIIHRetrans,
        tmnxIsisStatsCSNPRecd,
        tmnxIsisStatsCSNPDrop,
        tmnxIsisStatsCSNPSent,
        tmnxIsisStatsCSNPRetrans,
        tmnxIsisStatsPSNPRecd,
        tmnxIsisStatsPSNPDrop,
        tmnxIsisStatsPSNPSent,
        tmnxIsisStatsPSNPRetrans,
        tmnxIsisStatsUnknownRecd,
        tmnxIsisStatsUnknownDrop,
        tmnxIsisStatsUnknownSent,
        tmnxIsisStatsUnknownRetrans,
        tmnxIsisStatsCSPFRequests,
        tmnxIsisStatsCSPFDroppedRequests,
        tmnxIsisStatsCSPFPathsFound,
        tmnxIsisStatsCSPFPathsNotFound,
        tmnxIsisStatsLfaRuns,
        tmnxIsisHostName,
        tmnxIsisPathMetric,
        tmnxIsisPathSNPA,
        tmnxIsisPathLfaIfIndex,
        tmnxIsisPathLfaNHop,
        tmnxIsisPathLfaMetric,
        tmnxIsisPathLfaType,
        tmnxIsisPathRouteType,
        tmnxIsisLSPSeq,
        tmnxIsisLSPChecksum,
        tmnxIsisLSPLifetimeRemain,
        tmnxIsisLSPVersion,
        tmnxIsisLSPPktType,
        tmnxIsisLSPPktVersion,
        tmnxIsisLSPMaxArea,
        tmnxIsisLSPSysIdLen,
        tmnxIsisLSPAttributes,
        tmnxIsisLSPUsedLen,
        tmnxIsisLSPAllocLen,
        tmnxIsisLSPBuff,
        tmnxIsisLSPZeroRLT,
        tmnxIsisSpfLogRunTime,
        tmnxIsisSpfLogL1Nodes,
        tmnxIsisSpfLogL2Nodes,
        tmnxIsisSpfLogEventCount,
        tmnxIsisSpfLogLastTriggerLSPId,
        tmnxIsisSpfLogTriggerReason,
        tmnxIsisSpfLogType,
        tmnxIsisSummRowStatus,
        tmnxIsisSummLevel,
        tmnxIsisSummRouteTag,
        tmnxIsisLfaNodesCovered,
        tmnxIsisLfaTotalNodes,
        tmnxIsisLfaNodeCoverage,
        tmnxIsisLfaIPv4NodesCovered,
        tmnxIsisLfaIPv4TotalNodes,
        tmnxIsisLfaIPv4Coverage,
        tmnxIsisLfaIPv6NodesCovered,
        tmnxIsisLfaIPv6TotalNodes,
        tmnxIsisLfaIPv6Coverage,
        tmnxIsisOperRouterId,
        tmnxIsisPrefixSidType,
        tmnxIsisPrefixSidFlags,
        tmnxIsisPrefixSidSRMS,
        tmnxIsisAuthKeyChain,
        tmnxIsisStatsPartSpfRuns,
        tmnxIsisStatsPartSpfTimeStamp,
        tmnxIsisStatsPartLfaRuns,
        tmnxIsisStatsPartLfaTimeStamp,
        tmnxIsisStatsLfaTimeStamp,
        tmnxIsisStatsSpfTimeStamp,
        tmnxIsisNotifTrapLSPID,
        tmnxIsisNotifSystemLevel,
        tmnxIsisNotifPDUFragment,
        tmnxIsisNotifFieldLen,
        tmnxIsisNotifMaxAreaAddress,
        tmnxIsisNotifProtocolVersion,
        tmnxIsisNotifLSPSize,
        tmnxIsisNotifOriginatingBuffSize,
        tmnxIsisNotifProtocolsSupported,
        tmnxIsisStatsRlfaRuns,
        tmnxIsisStatsRlfaTimeStamp
    }
    STATUS      current
    DESCRIPTION
        "The group of objects supporting management of ISIS system objects on
         release 12.0 Nokia SROS series systems."
    ::= { tmnxIsisGroups 1 }

tmnxIsisIfGroup                  OBJECT-GROUP
    OBJECTS     {
        tmnxIsisIfRowStatus,
        tmnxIsisIfLastChanged,
        tmnxIsisIfAdminState,
        tmnxIsisIfOperState,
        tmnxIsisIfCsnpInterval,
        tmnxIsisIfHelloAuthKey,
        tmnxIsisIfHelloAuthType,
        tmnxIsisIfLspPacingInterval,
        tmnxIsisIfCircIndex,
        tmnxIsisIfRetransmitInterval,
        tmnxIsisIfTypeDefault,
        tmnxIsisIfEnableBfd,
        tmnxIsisIfIPv6Unicast,
        tmnxIsisIfTeMetric,
        tmnxIsisIfTeState,
        tmnxIsisIfAdminGroup,
        tmnxIsisIfLdpSyncState,
        tmnxIsisIfLdpSyncMaxMetric,
        tmnxIsisIfLdpSyncTimerState,
        tmnxIsisIfLdpSyncTimeLeft,
        tmnxIsisIfRouteTag,
        tmnxIsisIfIPv6EnableBfd,
        tmnxIsisIfHelloAuth,
        tmnxIsisIfLoopfreeAltExclude,
        tmnxIsisIfOperType,
        tmnxIsisIfIPv4Mcast,
        tmnxIsisIfIPv6Mcast,
        tmnxIsisIfBerState,
        tmnxIsisIfIPv4IncludeBfdTlv,
        tmnxIsisIfIPv6IncludeBfdTlv,
        tmnxIsisIfHelloAuthKeyChain,
        tmnxIsisIfLevelLastChangeTime,
        tmnxIsisIfLevelHelloAuthKey,
        tmnxIsisIfLevelHelloAuthType,
        tmnxIsisIfLevelPassive,
        tmnxIsisIfLevelNumAdjacencies,
        tmnxIsisIfLevelISPriority,
        tmnxIsisIfLevelHelloTimer,
        tmnxIsisIfLevelAdminMetric,
        tmnxIsisIfLevelOperMetric,
        tmnxIsisIfLvlIPv6UcastAdmMet,
        tmnxIsisIfLvlIPv6UcastOperMet,
        tmnxIsisIfLvlIPv4McastAdmMetric,
        tmnxIsisIfLvlIPv6McastAdmMetric,
        tmnxIsisIfLevelLinkGroupName,
        tmnxIsisIfLevelSdOffset,
        tmnxIsisIfLevelSfOffset,
        tmnxIsisIfLvlIPv4McastOperMetric,
        tmnxIsisIfLvlIPv6McastOperMetric,
        tmnxIsisIfLevelHelloAuthKeyChain
    }
    STATUS      current
    DESCRIPTION
        "The group of objects supporting management of ISIS interface objects
         on Nokia SROS series systems."
    ::= { tmnxIsisGroups 2 }

tmnxIsisAdjGroup                 OBJECT-GROUP
    OBJECTS     {
        tmnxIsisISAdjExpiresIn,
        tmnxIsisISAdjCircLevel,
        tmnxIsisISAdjNeighborIP,
        tmnxIsisISAdjRestartSupport,
        tmnxIsisISAdjRestartStatus,
        tmnxIsisISAdjRestartSupressed,
        tmnxIsisISAdjNumRestarts,
        tmnxIsisISAdjLastRestartTime,
        tmnxIsisISAdjNeighborIPv6Type,
        tmnxIsisISAdjNeighborIPv6,
        tmnxIsisISAdjMtEnabled,
        tmnxIsisISAdjMtId0,
        tmnxIsisISAdjMtId2,
        tmnxIsisISAdjMtId3,
        tmnxIsisISAdjMtId4,
        tmnxIsisISAdjIpv4SidType,
        tmnxIsisISAdjIpv4SidValue,
        tmnxIsisISAdjIpv6SidType,
        tmnxIsisISAdjIpv6SidValue,
        tmnxIsisISAdjMtId0BfdRequired,
        tmnxIsisISAdjMtId2BfdRequired,
        tmnxIsisISAdjMtId3BfdRequired,
        tmnxIsisISAdjMtId4BfdRequired,
        tmnxIsisISAdjMtId0BfdUsable,
        tmnxIsisISAdjMtId2BfdUsable,
        tmnxIsisISAdjMtId3BfdUsable,
        tmnxIsisISAdjMtId4BfdUsable
    }
    STATUS      current
    DESCRIPTION
        "The group of objects supporting management of ISIS adjacencies objects
         on Nokia SROS series systems."
    ::= { tmnxIsisGroups 3 }

tmnxIsisLFAV12v0Group            OBJECT-GROUP
    OBJECTS     {
        tmnxIsisExLastChanged,
        tmnxIsisLFAExcludePolicy1,
        tmnxIsisLFAExcludePolicy2,
        tmnxIsisLFAExcludePolicy3,
        tmnxIsisLFAExcludePolicy4,
        tmnxIsisLFAExcludePolicy5,
        tmnxIsisIfRouteNHTemplate
    }
    STATUS      current
    DESCRIPTION
        "The group of objects supporting management of ISIS system objects on
         Nokia 12.0 release of SROS series systems."
    ::= { tmnxIsisGroups 4 }

tmnxIsisV13v0Group               OBJECT-GROUP
    OBJECTS     {
        tmnxIsisSuppressAttachedBit,
        tmnxIsisPrefixSidRangeType,
        tmnxIsisPrefixSidRangeStartLabel,
        tmnxIsisPrefixSidRangeMaxIdx,
        tmnxIsisSrAdminState,
        tmnxIsisTunnelTablePreference,
        tmnxIsisRemoteLoopfreeAlternate,
        tmnxIsisIfIpv4SidType,
        tmnxIsisIfIpv4SidValue,
        tmnxIsisIfIpv6SidType,
        tmnxIsisIfIpv6SidValue,
        tmnxIsisStatsSidLabelRangeErrs,
        tmnxIsisStatsSidDupErrs,
        tmnxIsisRibPriorityListHigh,
        tmnxIsisRibPriorityListHighTag,
        tmnxIsisIfDefaultInstance,
        tmnxIsisTunnelMtu,
        tmnxIsisMaxPqCost,
        tmnxIsisIgnoreNarrowMetric,
        tmnxIsisPoiTlv,
        tmnxIsisIfLevelLspTxQCount
    }
    STATUS      current
    DESCRIPTION
        "The group of objects supporting management of ISIS system objects on
         release 13.0 Nokia SROS series systems."
    ::= { tmnxIsisGroups 5 }

tmnxIsisV14v0Group               OBJECT-GROUP
    OBJECTS     {
        tmnxIsisSystemId,
        tmnxIsisPrefixLimit,
        tmnxIsisPfxLimitOverloadTimeout,
        tmnxIsisPrefixLimitThreshold,
        tmnxIsisPrefixLimitLogOnly,
        tmnxIsisPfxLimitOverloadTimeLeft,
        tmnxIsisImportPolicy1,
        tmnxIsisImportPolicy2,
        tmnxIsisImportPolicy3,
        tmnxIsisImportPolicy4,
        tmnxIsisImportPolicy5,
        tmnxIsisIfLBAdminWeight,
        tmnxIsisLevelLSPBuffSize,
        tmnxIsisLevelHelloPadding,
        tmnxIsisIfHelloPadding,
        tmnxIsisIfLevelHelloPadding,
        tmnxIsisSrAdjSidHold,
        tmnxIsisDatabaseExport,
        tmnxIsisDbExportIdentifierSet,
        tmnxIsisDbExportIdentifierLow,
        tmnxIsisDbExportIdentifierHigh,
        tmnxIsisBgpLsIdentifierSet,
        tmnxIsisBgpLsIdentifier,
        tmnxIsisLevelDbExportExclude,
        tmnxIsisIfSidProtection,
        tmnxIsisSrExportTunnelTableProt,
        tmnxIsisSRMapServLastCh,
        tmnxIsisSRMapServAdminState,
        tmnxIsisSRMSSidMapRowStatus,
        tmnxIsisSRMSSidMapLastCh,
        tmnxIsisSRMSSidMapPrefixType,
        tmnxIsisSRMSSidMapPrefix,
        tmnxIsisSRMSSidMapPrefixLength,
        tmnxIsisSRMSSidMapNodeSidRange,
        tmnxIsisSRMSSidMapFlags,
        tmnxIsisSRMSSidMapLevel,
        tmnxIsisOverloadExportInterlevel,
        tmnxIsisOverloadExportExternal,
        tmnxIsisPrefixSidSRMSSelected,
        tmnxIsisStandardMultiInstance,
        tmnxIsisDbAsn
    }
    STATUS      current
    DESCRIPTION
        "The group of objects supporting management of ISIS system objects on
         release 14.0 Nokia SROS series systems."
    ::= { tmnxIsisGroups 6 }

tmnxIsisV15v0Group               OBJECT-GROUP
    OBJECTS     {
        tmnxIsisTiLfa,
        tmnxIsisMaxSrFrrLabels,
        tmnxIsisPrefixAttributesTlv,
        tmnxIsisStatsTiLfaRuns,
        tmnxIsisStatsTiLfaTimeStamp,
        tmnxIsisSRLfaStatsTotalSid,
        tmnxIsisSRLfaStatsLfaCovered,
        tmnxIsisSRLfaStatsRLfaCovered,
        tmnxIsisSRLfaStatsTiLfaCovered,
        tmnxIsisLevelMaxOperLSPBuffSize,
        tmnxIsisIfIpv4SidClearNFlag,
        tmnxIsisIfIpv6SidClearNFlag,
        tmnxIsisSRMSSidMapClearNFlag,
        tmnxIsisLspRefreshHalfLifetime,
        tmnxIsisSrEntropyLabel,
        tmnxIsisOverrideTunnelElc
    }
    STATUS      current
    DESCRIPTION
        "The group of objects supporting management of ISIS system objects on
         release 15.0 Nokia SROS series systems."
    ::= { tmnxIsisGroups 7 }

tmnxIsisIgpSC15v0Group           OBJECT-GROUP
    OBJECTS     {
        tmnxIsisIgpSCAdminState,
        tmnxIsisIgpSCTunnNextHopLstCh,
        tmnxIsisIgpSCTNHResolution,
        tmnxIsisIgpSCTNHResFilterRsvp,
        tmnxIsisIgpSCTNHResFilterSrTe
    }
    STATUS      current
    DESCRIPTION
        "The group of objects supporting management of ISIS IGP shortcut
         objects on release 15.0 Nokia SROS series systems."
    ::= { tmnxIsisGroups 8 }

tmnxIsisObsolete15v0Group        OBJECT-GROUP
    OBJECTS     {
        tmnxIsisRsvpShortcut
    }
    STATUS      current
    DESCRIPTION
        "The group of objects in TIMETRA-ISIS-MIB which are obsoleted."
    ::= { tmnxIsisGroups 9 }

tmnxIsisBier16v0Group            OBJECT-GROUP
    OBJECTS     {
        tmnxIsisLevelBierTemplate,
        tmnxIsisLevelBierTemplAdminState
    }
    STATUS      current
    DESCRIPTION
        "The group of objects supporting management of BIER ISIS
         objects on release 16.0  Nokia SROS series systems."
    ::= { tmnxIsisGroups 10 }

tmnxIsisNotifyObjsGroup          OBJECT-GROUP
    OBJECTS     {
        tmnxIsisNotifNbrSysId,
        tmnxIsisFailureReasonCode,
        tmnxIsisBfdSessSetupFailReason
    }
    STATUS      current
    DESCRIPTION
        "The group of notification objects supporting management of ISIS
         notification objects on Nokia SROS series systems."
    ::= { tmnxIsisGroups 100 }

tmnxIsisNotifyGroup              NOTIFICATION-GROUP
    NOTIFICATIONS {
        tmnxIsisDatabaseOverload,
        tmnxIsisManualAddressDrops,
        tmnxIsisCorruptedLSPDetected,
        tmnxIsisMaxSeqExceedAttempt,
        tmnxIsisIDLenMismatch,
        tmnxIsisMaxAreaAddrsMismatch,
        tmnxIsisOwnLSPPurge,
        tmnxIsisSequenceNumberSkip,
        tmnxIsisAutTypeFail,
        tmnxIsisAuthFail,
        tmnxIsisVersionSkew,
        tmnxIsisAreaMismatch,
        tmnxIsisRejectedAdjacency,
        tmnxIsisLSPTooLargeToPropagate,
        tmnxIsisOrigLSPBufSizeMismatch,
        tmnxIsisProtoSuppMismatch,
        tmnxIsisAdjacencyChange,
        tmnxIsisCircIdExhausted,
        tmnxIsisAdjRestartStatusChange,
        tmnxIsisLdpSyncTimerStarted,
        tmnxIsisLdpSyncExit,
        tmnxIsisExportLimitReached,
        tmnxIsisExportLimitWarning,
        tmnxIsisRoutesExpLmtDropped,
        tmnxIsisSidError,
        tmnxIsisSidNotInLabelRange,
        tmnxIsisRejectedAdjacencySid,
        tmnxIsisFailureDisabled,
        tmnxIsisAdjBfdSessionSetupFail
    }
    STATUS      current
    DESCRIPTION
        "The group of notifications supporting management of ISIS notifications
         on Nokia SROS series systems."
    ::= { tmnxIsisGroups 101 }

tmnxIsisNotifyObjsV13v0Group     OBJECT-GROUP
    OBJECTS     {
        tmnxIsisNotifPfxSidRangeStartLbl,
        tmnxIsisNotifPfxSidRangeMaxIdx,
        tmnxIsisNotifPfxSidSysID,
        tmnxIsisNotifyDescription,
        tmnxIsisNotifPurgeOriginator,
        tmnxIsisNotifPurgeSource,
        tmnxIsisNotifAdditionalInfo,
        tmnxIsisNotifSrgbRangeStartLbl,
        tmnxIsisNotifSrgbRangeMaxIdx,
        tmnxIsisNotifSrgbAdvRtrSysID,
        tmnxIsisNotifSrgbLevel,
        tmnxIsisNotifSrgbMtId
    }
    STATUS      current
    DESCRIPTION
        "The group of notification objects supporting management of ISIS
         notification objects on Nokia 7xxx systems 13.0 release."
    ::= { tmnxIsisGroups 102 }

tmnxIsisNotifyV13v0Group         NOTIFICATION-GROUP
    NOTIFICATIONS {
        tmnxIsisSidError,
        tmnxIsisSidNotInLabelRange,
        tmnxIsisLSPPurge,
        tmnxIsisSrgbBadLabelRange
    }
    STATUS      current
    DESCRIPTION
        "The group of notifications supporting management of ISIS notifications
         on Nokia 7xxx series systems 13.0 release."
    ::= { tmnxIsisGroups 103 }

tmnxIsisNotifyV14v0Group         NOTIFICATION-GROUP
    NOTIFICATIONS {
        tmnxIsisPfxLimitOverloadWarning
    }
    STATUS      current
    DESCRIPTION
        "The group of notifications supporting management of ISIS that were
         added in release 14.0 on Nokia 7xxx series systems."
    ::= { tmnxIsisGroups 104 }

tmnxIsisNotifyObjsV15v0Group     OBJECT-GROUP
    OBJECTS     {
        tmnxIsisNotifCircMtuSize,
        tmnxIsisNotifCircMinReqMtuSize
    }
    STATUS      current
    DESCRIPTION
        "The group of notification objects supporting management of ISIS
         notification objects on Nokia 7xxx systems 15.0 release."
    ::= { tmnxIsisGroups 105 }

tmnxIsisNotifyV15v0Group         NOTIFICATION-GROUP
    NOTIFICATIONS {
        tmnxIsisCircMtuTooLow
    }
    STATUS      current
    DESCRIPTION
        "The group of notifications supporting management of ISIS that were
         added in release 15.0 on Nokia 7xxx series systems."
    ::= { tmnxIsisGroups 106 }

tmnxIsisV16v0Group               OBJECT-GROUP
    OBJECTS     {
        tmnxIsisIfIpv4AdjSidType,
        tmnxIsisIfIpv4AdjSidValue,
        tmnxIsisIfIpv6AdjSidType,
        tmnxIsisIfIpv6AdjSidValue,
        tmnxIsisAdjSetFamilyType,
        tmnxIsisAdjSetIdLstCh,
        tmnxIsisAdjSetParallel,
        tmnxIsisAdjSetAdvertise,
        tmnxIsisAdjSetSidType,
        tmnxIsisAdjSetSidValue,
        tmnxIsisAdjSetRowStatus,
        tmnxIsisAdjSetDynSidValue,
        tmnxIsisAdjSetTunlDestType,
        tmnxIsisAdjSetTunlDestIp,
        tmnxIsisAdjSetNeighborSysID,
        tmnxIsisAdjSetMembersCount,
        tmnxIsisAdjSetActiveMembers,
        tmnxIsisAdjSetUpTime,
        tmnxIsisAdjSetStatus,
        tmnxIsisIfAdjSetIdLstCh,
        tmnxIsisIfAdjSetRowStatus,
        tmnxIsisAdjSetNhop,
        tmnxIsisAdjSetNhopType,
        tmnxIsisAdjSetNhopUsage,
        tmnxIsisAdjSetNhopLevel,
        tmnxIsisAdjSetMtu,
        tmnxIsisSrlbReservedLblBlockName,
        tmnxIsisRemoteLfaNodeProtect,
        tmnxIsisRemoteLfaMaxPqNodes,
        tmnxIsisTiLfaNodeProtect,
        tmnxIsisSrMicroLoopAvoidance,
        tmnxIsisSrMicroLoopAvdFibDelay
    }
    STATUS      current
    DESCRIPTION
        "The group of objects supporting management of ISIS system objects on
         release 16.0 Nokia SROS series systems."
    ::= { tmnxIsisGroups 107 }

tmnxIsisNotifyObjsV16v0Group     OBJECT-GROUP
    OBJECTS     {
        tmnxIsisNotifyIfIndex
    }
    STATUS      current
    DESCRIPTION
        "The group of notification objects supporting management of ISIS
         notification objects on Nokia 7xxx systems 16.0 release."
    ::= { tmnxIsisGroups 108 }

tmnxIsisNotifyV16v0Group         NOTIFICATION-GROUP
    NOTIFICATIONS {
        tmnxIsisRejectedAdjacencySet
    }
    STATUS      current
    DESCRIPTION
        "The group of notifications supporting management of ISIS that were
         added in release 16.0 on Nokia 7xxx series systems."
    ::= { tmnxIsisGroups 109 }

tmnxIsisV19v0Group               OBJECT-GROUP
    OBJECTS     {
        tmnxIsisLspMinRemainingLifetime,
        tmnxIsisReferenceBwU64High,
        tmnxIsisReferenceBwU64Low,
        tmnxIsisRouteNhIPType,
        tmnxIsisRouteNhIP,
        tmnxIsisRouteNhLevel,
        tmnxIsisRouteNhSpfRunNumber,
        tmnxIsisRouteNhMetric,
        tmnxIsisRouteNhType,
        tmnxIsisRouteNhSysID,
        tmnxIsisRouteNhTag,
        tmnxIsisRouteNhBkupFlags,
        tmnxIsisRouteNhBkupCidrType,
        tmnxIsisRouteNhBkupIpType,
        tmnxIsisRouteNhBkupIP,
        tmnxIsisRouteNhBkupMetric,
        tmnxIsisRouteNhCidrType,
        tmnxIsisRouteNhOwner,
        tmnxIsisRouteNhOwnerAuxInfo,
        tmnxIsisRouteNhBkupType,
        tmnxIsisRouteNhBkupOwner,
        tmnxIsisRouteNhBkupOwnerAuxInfo,
        tmnxIsisRouteNhSidFlags,
        tmnxIsisRouteNhSidValue,
        tmnxIsisRouteNhRouteStatus,
        tmnxIsisRouteNhNhopStatus,
        tmnxIsisEgressStatsNodeSid,
        tmnxIsisEgressStatsAdjSid,
        tmnxIsisEgressStatsAdjSet,
        tmnxIsisIngressStatsNodeSid,
        tmnxIsisIngressStatsAdjSid,
        tmnxIsisIngressStatsAdjSet,
        tmnxIsisSidStatsSidType,
        tmnxIsisSidStatsPrefixType,
        tmnxIsisSidStatsPrefix,
        tmnxIsisSidStatsPrefixLength,
        tmnxIsisSidStatsIfIndex,
        tmnxIsisSidStatsAdjSet,
        tmnxIsisSidStatsIngressOperState,
        tmnxIsisSidStatsIngressOctets,
        tmnxIsisSidStatsIngressPackets,
        tmnxIsisSidStatsEgressOperState,
        tmnxIsisSidStatsEgressOctets,
        tmnxIsisSidStatsEgressPackets,
        tmnxIsisTEIpv6,
        tmnxIsisTEApplicationLinkAttr,
        tmnxIsisTEApplLegacy,
        tmnxIsisOperIpv6TERouterIdType,
        tmnxIsisOperIpv6TERouterId,
        tmnxIsisSrClassForwarding,
        tmnxIsisLoopfreeAltAugmRteTable
    }
    STATUS      current
    DESCRIPTION
        "The group of objects supporting management of ISIS system objects on
         release 19.0 Nokia SROS series systems."
    ::= { tmnxIsisGroups 110 }

tmnxIsisNotifyV19v0Group         NOTIFICATION-GROUP
    NOTIFICATIONS {
        tmnxIsisCorruptRemainingLifetime,
        tmnxIsisSidStatsIndexAlloc
    }
    STATUS      current
    DESCRIPTION
        "The group of notifications supporting management of ISIS that were
         added in release 19.0 on Nokia 7xxx series systems."
    ::= { tmnxIsisGroups 111 }

tmnxIsisNotifyObjsV19v0Group     OBJECT-GROUP
    OBJECTS     {
        tmnxIsisNotifStatsIndexStatus
    }
    STATUS      current
    DESCRIPTION
        "The group of objects supporting ISIS notifications, added in the 19.0
         release of Nokia SROS series systems."
    ::= { tmnxIsisGroups 112 }

tmnxIsisV19v0ObsoleteGroup       OBJECT-GROUP
    OBJECTS     {
        tmnxIsisRouteLevel,
        tmnxIsisRouteSpfRunNumber,
        tmnxIsisRouteMetric,
        tmnxIsisRouteType,
        tmnxIsisRouteNHopSysID,
        tmnxIsisRouteTag,
        tmnxIsisRouteBkupFlags,
        tmnxIsisRouteBkupNextHopTy,
        tmnxIsisRouteBkupNextHopType,
        tmnxIsisRouteBkupNextHop,
        tmnxIsisRouteBkupMetric,
        tmnxIsisRouteNextHopType,
        tmnxIsisRouteNextHopOwner,
        tmnxIsisRouteNHOwnerAuxInfo,
        tmnxIsisRouteBkupNHType,
        tmnxIsisRouteBkupNHOwner,
        tmnxIsisRouteBkupNHOwnAxInfo,
        tmnxIsisRouteSidFlags,
        tmnxIsisRouteSidValue,
        tmnxIsisRouteStatus
    }
    STATUS      current
    DESCRIPTION
        "The group of objects supporting management of ISIS system objects that
         are obsoleted in release 19.0 Nokia SROS series systems."
    ::= { tmnxIsisGroups 113 }

tmnxIsisV20v0Group               OBJECT-GROUP
    OBJECTS     {
        tmnxIsisSrLastChanged,
        tmnxIsisSrMsdOverrideBmi,
        tmnxIsisSrMsdOverrideErld,
        tmnxIsisPrefixSidAlgorithm,
        tmnxIsisSidStatsAlgorithm,
        tmnxIsisGeneralLastChanged,
        tmnxIsisFlexAlgosAdminState,
        tmnxIsisFlexAlgoLastChanged,
        tmnxIsisFlexAlgoRowStatus,
        tmnxIsisFlexAlgoParticipate,
        tmnxIsisFlexAlgoAdvertise,
        tmnxIsisFlexAlgoMicroLoopAvd,
        tmnxIsisFlexAlgoLfa,
        tmnxIsisIfFlexAlgoLastChanged,
        tmnxIsisIfFlexAlgoRowStatus,
        tmnxIsisIfFlexAlgoIpv4SidType,
        tmnxIsisIfFlexAlgoIpv4SidValue,
        tmnxIsisIfFlexAlgoIpv6SidType,
        tmnxIsisIfFlexAlgoIpv6SidValue,
        tmnxIsisFaRouteNhIPType,
        tmnxIsisFaRouteNhIP,
        tmnxIsisFaRouteNhLevel,
        tmnxIsisFaRouteNhSpfRunNumber,
        tmnxIsisFaRouteNhMetric,
        tmnxIsisFaRouteNhType,
        tmnxIsisFaRouteNhSysID,
        tmnxIsisFaRouteNhTag,
        tmnxIsisFaRouteNhCidrType,
        tmnxIsisFaRouteNhOwner,
        tmnxIsisFaRouteNhOwnerAuxInfo,
        tmnxIsisFaRouteNhSidFlags,
        tmnxIsisFaRouteNhSidValue,
        tmnxIsisFaRouteNhRouteStatus,
        tmnxIsisFaRouteNhNhopStatus,
        tmnxIsisFaSRLfaStatsTotalSid,
        tmnxIsisFaSRLfaStatsLfaCovered,
        tmnxIsisFaSRLfaStatsRLfaCovered,
        tmnxIsisFaSRLfaStatsTiLfaCovered,
        tmnxIsisFaPathMetric,
        tmnxIsisFaPathSNPA,
        tmnxIsisFaPathLfaIfIndex,
        tmnxIsisFaPathLfaNHop,
        tmnxIsisFaPathLfaMetric,
        tmnxIsisFaPathLfaType,
        tmnxIsisFaPathRouteType,
        tmnxIsisFaStatOperState,
        tmnxIsisFaStatFadCount,
        tmnxIsisFaStatSelectedFadOwner,
        tmnxIsisFadPriority,
        tmnxIsisFadSupported,
        tmnxIsisFadUnsupportedReason,
        tmnxIsisFadMetricType,
        tmnxIsisFadCalculationType,
        tmnxIsisFadExclude,
        tmnxIsisFadIncludeAny,
        tmnxIsisFadIncludeAll,
        tmnxIsisFadFlags
    }
    STATUS      current
    DESCRIPTION
        "The group of objects supporting management of ISIS system objects on
         release 20.0 Nokia SROS series systems."
    ::= { tmnxIsisGroups 114 }

tmnxIsisNotifyV20v0Group         NOTIFICATION-GROUP
    NOTIFICATIONS {
        tmnxIsisFaOperParticipationDown
    }
    STATUS      current
    DESCRIPTION
        "The group of notifications supporting management of ISIS that were
         added in release 20.0 on Nokia 7xxx series systems."
    ::= { tmnxIsisGroups 115 }

tmnxIsisSrv6Group                OBJECT-GROUP
    OBJECTS     {
        tmnxIsisSrv6LastChanged,
        tmnxIsisSrv6AdminState,
        tmnxIsisSrv6LocatorLastChanged,
        tmnxIsisSrv6LocatorRowStatus,
        tmnxIsisSrv6LocatorLevelCap,
        tmnxIsisSrv6LocatorTag,
        tmnxIsisSrv6LocLevelLastChanged,
        tmnxIsisSrv6LocLevelMetric,
        tmnxIsisSrv6SidType,
        tmnxIsisSrv6SidLocatorFlags,
        tmnxIsisSrv6SidAlgorithm,
        tmnxIsisSrv6SidAdminTag,
        tmnxIsisSrv6SidPrefixAttribFlags,
        tmnxIsisSrv6SidEndpointBehavior,
        tmnxIsisSrv6AdjSidHold
    }
    STATUS      current
    DESCRIPTION
        "The group of objects supporting management of ISIS Segment Routing
         over IPv6 on Nokia SROS series systems."
    ::= { tmnxIsisGroups 118 }

tmnxIsisV21v0Group               OBJECT-GROUP
    OBJECTS     {
        tmnxIsisMruMismatchDetection,
        tmnxIsisSummAlgorithm,
        tmnxIsisTeAdvertiseDelay,
        tmnxIsisPrefixSharedSid,
        tmnxIsisIfIpv4SharedSidType,
        tmnxIsisIfIpv4SharedSidValue,
        tmnxIsisIfIpv6SharedSidType,
        tmnxIsisIfIpv6SharedSidValue
    }
    STATUS      current
    DESCRIPTION
        "The group of objects supporting management of ISIS system objects on
         release 21.0 Nokia SROS series systems."
    ::= { tmnxIsisGroups 119 }

tmnxIsisNotifyV21v0Group         NOTIFICATION-GROUP
    NOTIFICATIONS {
        tmnxIsisRejectedEndXSid,
        tmnxIsisRejectedPgId,
        tmnxIsisSrv6LocError
    }
    STATUS      current
    DESCRIPTION
        "The group of notifications supporting management of ISIS that were
         added in release 21.0 on Nokia 7xxx series systems."
    ::= { tmnxIsisGroups 120 }

tmnxIsisV22v0Group               OBJECT-GROUP
    OBJECTS     {
        tmnxIsisMultiHomedPrefixLfa,
        tmnxIsisMhpLfaPreference,
        tmnxIsisSrAdjSidAllocDualSids,
        tmnxIsisISAdjSecondIpv4SidType,
        tmnxIsisISAdjSecondIpv4SidValue,
        tmnxIsisISAdjSecondIpv6SidType,
        tmnxIsisISAdjSecondIpv6SidValue,
        tmnxIsisSrv6LocatorMultiTopology,
        tmnxIsisFaAdvertiseAdminGroup,
        tmnxIsisFadExcludeEAG,
        tmnxIsisFadIncludeAnyEAG,
        tmnxIsisFadIncludeAllEAG,
        tmnxIsisMaxSrv6FrrSids,
        tmnxIsisSrv6MSLocatorLastChanged,
        tmnxIsisSrv6MSLocatorRowStatus,
        tmnxIsisSrv6MSLocatorLevelCap,
        tmnxIsisSrv6MSLocatorTag,
        tmnxIsisSrv6MSLocatorMultiTopo,
        tmnxIsisSrv6MSLocLevelLastCh,
        tmnxIsisSrv6MSLocLevelMetric,
        tmnxIsisSrv6USidType,
        tmnxIsisSrv6USidLocatorFlags,
        tmnxIsisSrv6USidAlgorithm,
        tmnxIsisSrv6USidAdminTag,
        tmnxIsisSrv6USidPfxAttribFlags,
        tmnxIsisSrv6USidEndpointBehavior,
        tmnxIsisISAdjIpv4SidBackup,
        tmnxIsisISAdjIpv6SidBackup,
        tmnxIsisISAdjSecondIpv4SidBackup,
        tmnxIsisISAdjSecondIpv6SidBackup
    }
    STATUS      current
    DESCRIPTION
        "The group of objects supporting management of ISIS system objects on
         release 22.0 Nokia SROS series systems."
    ::= { tmnxIsisGroups 121 }

tmnxIsisV23v0Group               OBJECT-GROUP
    OBJECTS     {
        tmnxIsisIgpSCAllowSrOverSrTe,
        tmnxIsisCsnpOnP2p,
        tmnxIsisOverloadFibErrNotifyOnly,
        tmnxIsisOverloadIncludeLocators,
        tmnxIsisOverloadFibErrRetryTime,
        tmnxIsisRouteNhAlgorithm,
        tmnxIsisSrMultiTopologyMt2,
        tmnxIsisSrSidRoutePrimPathIpType,
        tmnxIsisSrSidRoutePrimPathIp,
        tmnxIsisSrSidRouteBkupPathType,
        tmnxIsisSrSidRouteBkupProtection,
        tmnxIsisSrSidRouteBkupPathIpType,
        tmnxIsisSrSidRouteBkupPathIp,
        tmnxIsisSrSidRouteBkupNodesCount,
        tmnxIsisSrSidBkUpNodeType,
        tmnxIsisSrSidBkUpNodeSidValue,
        tmnxIsisSrSidBkUpNodeSidLblType,
        tmnxIsisSr6SidRoutePriPathIpType,
        tmnxIsisSr6SidRoutePrimPathIp,
        tmnxIsisSr6SidRouteBkPathType,
        tmnxIsisSr6SidRouteBkProtection,
        tmnxIsisSr6SidRouteBkPathIpType,
        tmnxIsisSr6SidRouteBkPathIp,
        tmnxIsisSr6SidBkComprAddrTyp,
        tmnxIsisSr6SidBkComprAddr,
        tmnxIsisSr6SidRouteBkNodesCount,
        tmnxIsisSr6SidBkNodeType,
        tmnxIsisSr6SidBkNodeSidAddrType,
        tmnxIsisSr6SidBkNodeSidAddr,
        tmnxIsisSr6SidBkNodeEndPointBeh,
        tmnxIsisSr6SidBkNodeSidType,
        tmnxIsisSr6SidBkNodeSrhMode,
        tmnxIsisSr6SidBkNodePrtMode
    }
    STATUS      current
    DESCRIPTION
        "The group of objects supporting management of ISIS system objects on
         release 23.0 Nokia SROS series systems."
    ::= { tmnxIsisGroups 122 }

tmnxIsisNotifyV23v0Group         NOTIFICATION-GROUP
    NOTIFICATIONS {
        tmnxIsisSrv6StaticSidIfTypeError
    }
    STATUS      current
    DESCRIPTION
        "The group of notifications supporting management of ISIS that were
         added in release 23.0 on Nokia 7xxx series systems."
    ::= { tmnxIsisGroups 123 }

tmnxIsisV24v0Group               OBJECT-GROUP
    OBJECTS     {
        tmnxIsisSummAdvertiseUnreachable,
        tmnxIsisSummUpaMatchRouteTag,
        tmnxIsisSummUpaAdvertiseRouteTag,
        tmnxIsisUpaLifetime,
        tmnxIsisUpaMetric,
        tmnxIsisMaximumNumberUpas,
        tmnxIsisProcessReceivedUpa,
        tmnxIsisUpaSentSpfRunNumber,
        tmnxIsisUpaSentMetric,
        tmnxIsisUpaSentType,
        tmnxIsisUpaSentSysID,
        tmnxIsisUpaSentTag,
        tmnxIsisUpaSentLifetimeRemain,
        tmnxIsisIfDelayNormalization,
        tmnxIsisIfMinimumDelay,
        tmnxIsisIfDelayToleranceInterval,
        tmnxIsisIfMeasuredDelay,
        tmnxIsisIfNormalizedDelay,
        tmnxIsisDbExportReachableLsOnly
    }
    STATUS      current
    DESCRIPTION
        "The group of objects supporting management of ISIS system objects on
         release 24.0 Nokia SROS series systems."
    ::= { tmnxIsisGroups 124 }

tmnxIsisNotifyPrefix             OBJECT IDENTIFIER ::= { tmnxSRNotifyPrefix 88 }

tmnxIsisNotifications            OBJECT IDENTIFIER ::= { tmnxIsisNotifyPrefix 0 }

tmnxIsisDatabaseOverload         NOTIFICATION-TYPE
    OBJECTS     {
        tmnxIsisNotifSystemLevel,
        isisSysL1State,
        isisSysL2State,
        tmnxIsisNotifyDescription,
        tmnxIsisLevelOverloadStatus
    }
    STATUS      current
    DESCRIPTION
        "[CAUSE] The tmnxIsisDatabaseOverload notification is generated when
         the system enters or leaves the Overload state.

         [EFFECT] Database is overloaded.

         [RECOVERY] No recovery is necessary unless tmnxIsisNotifyDescription
         indicates it."
    ::= { tmnxIsisNotifications 1 }

tmnxIsisManualAddressDrops       NOTIFICATION-TYPE
    OBJECTS     {
        isisManAreaAddrExistState
    }
    STATUS      current
    DESCRIPTION
        "[CAUSE] This notification is generated when one of the manual area
         addresses assigned to this system is ignored when computing routes.
         The object isisManAreaAddrExistState describes the area that has been
         dropped.

         This notification is edge triggered, and should not be regenerated
         until an address that was used in the previous computation has been
         dropped.

         [EFFECT] Assigned manual area address is ignored for computing routes.

         [RECOVERY] No recovery is necessary."
    ::= { tmnxIsisNotifications 2 }

tmnxIsisCorruptedLSPDetected     NOTIFICATION-TYPE
    OBJECTS     {
        vRtrIfIndex,
        tmnxIsisNotifSystemLevel,
        tmnxIsisNotifTrapLSPID
    }
    STATUS      current
    DESCRIPTION
        "[CAUSE] The tmnxIsisCorruptedLSPDetected notification is generated
         when we find that and LSP that was stored in memory has become
         corrupted.

         We forward an LSP ID. We may have independent knowledge of the ID, but
         in some implementations there is a chance that the ID itself will be
         corrupted.

         [EFFECT] LSP is dropped.

         [RECOVERY] No recovery is necessary."
    ::= { tmnxIsisNotifications 3 }

tmnxIsisMaxSeqExceedAttempt      NOTIFICATION-TYPE
    OBJECTS     {
        tmnxIsisNotifSystemLevel,
        tmnxIsisNotifTrapLSPID
    }
    STATUS      current
    DESCRIPTION
        "[CAUSE] The tmnxIsisMaxSeqExceedAttempt notification is generated when
         the sequence number on an LSP wraps the 32 bit sequence counter, we
         purge and wait to re-announce this information. Since these should not
         be generated rapidly, we generate an event each time this happens.

         A possible cause could be that the same system-id is configured on
         multiple nodes; when 2 nodes have the same system-id they both keep
         incrementing its LSP sequence number causing the sequence counter to
         rollover.

         While the first 6 bytes of the LSPID are ours, the other two contain
         useful information.

         [EFFECT] No effect.

         [RECOVERY] No recovery is necessary."
    ::= { tmnxIsisNotifications 4 }

tmnxIsisIDLenMismatch            NOTIFICATION-TYPE
    OBJECTS     {
        tmnxIsisNotifFieldLen,
        vRtrIfIndex,
        tmnxIsisNotifPDUFragment
    }
    STATUS      current
    DESCRIPTION
        "[CAUSE] The tmnxIsisIDLenMismatch notification is sent when we receive
         a PDU with a different value of the System ID Length.

         This notification includes the index to identify the circuit where we
         saw the PDU and the header of the PDU which may help a network manager
         identify the source of the confusion.

         This should be an edge-triggered notification. We should not send a
         second notification about PDUs received from what seem to be the same
         source. This decision is up to the agent to make, and may be based on
         the circuit or on some MAC level information.

         [EFFECT] No effect.

         [RECOVERY] No recovery is necessary."
    ::= { tmnxIsisNotifications 5 }

tmnxIsisMaxAreaAddrsMismatch     NOTIFICATION-TYPE
    OBJECTS     {
        tmnxIsisNotifMaxAreaAddress,
        vRtrIfIndex,
        tmnxIsisNotifPDUFragment
    }
    STATUS      current
    DESCRIPTION
        "[CAUSE] The tmnxIsisMaxAreaAddrsMismatch notification is sent when we
         receive a PDU with a different value of the Maximum Area Addresses.

         This notification includes the header of the packet, which may help a
         network manager identify the source of the confusion.

         This should be an edge-triggered notification. We should not send a
         second notification about PDUs received from what seem to be the same
         source.

         [EFFECT] No effect.

         [RECOVERY] No recovery is necessary."
    ::= { tmnxIsisNotifications 6 }

tmnxIsisOwnLSPPurge              NOTIFICATION-TYPE
    OBJECTS     {
        vRtrIfIndex,
        tmnxIsisNotifTrapLSPID,
        tmnxIsisNotifSystemLevel
    }
    STATUS      current
    DESCRIPTION
        "[CAUSE] The tmnxIsisOwnLSPPurge notification is sent when we receive a
         PDU with our SystemID and zero age.

         This notification includes the circuit Index if available, which may
         help a network manager identify the source of the confusion.

         [EFFECT] No effect.

         [RECOVERY] No recovery is necessary."
    ::= { tmnxIsisNotifications 7 }

tmnxIsisSequenceNumberSkip       NOTIFICATION-TYPE
    OBJECTS     {
        tmnxIsisNotifTrapLSPID,
        vRtrIfIndex,
        tmnxIsisNotifSystemLevel
    }
    STATUS      current
    DESCRIPTION
        "[CAUSE] The tmnxIsisSequenceNumberSkip notification is sent when we
         need to increase the sequence number by more than one.

         When we receive an LSP with out System ID and different contents, we
         may need to reissue the LSP with a higher sequence number.

         If two Intermediate Systems are configured with the same System ID,
         this notification will fire.

         [EFFECT] No effect.

         [RECOVERY] No recovery is necessary."
    ::= { tmnxIsisNotifications 8 }

tmnxIsisAutTypeFail              NOTIFICATION-TYPE
    OBJECTS     {
        tmnxIsisNotifSystemLevel,
        tmnxIsisNotifPDUFragment,
        vRtrIfIndex
    }
    STATUS      current
    DESCRIPTION
        "[CAUSE] The tmnxIsisAutTypeFail notification is sent when we receive a
         PDU with the wrong authentication type field.

         This notification includes the header of the packet, which may help a
         network manager identify the source of the confusion.

         This should be an edge-triggered notification. We should not send a
         second notification about PDUs received from what seem to be the same
         source.

         [EFFECT] No effect.

         [RECOVERY] No recovery is necessary."
    ::= { tmnxIsisNotifications 9 }

tmnxIsisAuthFail                 NOTIFICATION-TYPE
    OBJECTS     {
        tmnxIsisNotifSystemLevel,
        tmnxIsisNotifPDUFragment,
        vRtrIfIndex
    }
    STATUS      current
    DESCRIPTION
        "[CAUSE] The tmnxIsisAuthFail notification is sent when we receive a
         PDU with incorrect authentication information field.

         This notification includes the header of the packet, which may help a
         network manager identify the source of the confusion.

         This should be an edge-triggered notification. We should not send a
         second notification about PDUs received from what seem to be the same
         source.

         [EFFECT] No effect.

         [RECOVERY] No recovery is necessary."
    ::= { tmnxIsisNotifications 10 }

tmnxIsisVersionSkew              NOTIFICATION-TYPE
    OBJECTS     {
        tmnxIsisNotifProtocolVersion,
        tmnxIsisNotifSystemLevel,
        tmnxIsisNotifPDUFragment,
        vRtrIfIndex
    }
    STATUS      current
    DESCRIPTION
        "[CAUSE] The tmnxIsisVersionSkew notification is sent when we receive a
         Hello PDU from an IS running a different version of the protocol.

         This notification includes the header of the packet, which may help a
         network manager identify the source of the confusion.

         This should be an edge-triggered notification. We should not send a
         second notification about PDUs received from what seem to be the same
         source. This decision is up to the agent to make, and may be based on
         the circuit or on some MAC level information.

         [EFFECT] No effect.

         [RECOVERY] No recovery is necessary."
    ::= { tmnxIsisNotifications 11 }

tmnxIsisAreaMismatch             NOTIFICATION-TYPE
    OBJECTS     {
        tmnxIsisNotifLSPSize,
        tmnxIsisNotifSystemLevel,
        vRtrIfIndex,
        tmnxIsisNotifPDUFragment
    }
    STATUS      current
    DESCRIPTION
        "[CAUSE] The tmnxIsisAreaMismatch notification is sent when we receive
         a Hello PDU from an IS which does not share any area address.

         This notification includes the header of the packet, which may
         help a network manager identify the source of the  confusion.

         This should be an edge-triggered notification. We should not send a
         second notification about PDUs received from what seem to be the same
         source. This decision is up to the agent to make, and may be based on
         the circuit or on some MAC level information.

         [EFFECT] No effect.

         [RECOVERY] No recovery is necessary."
    ::= { tmnxIsisNotifications 12 }

tmnxIsisRejectedAdjacency        NOTIFICATION-TYPE
    OBJECTS     {
        tmnxIsisNotifSystemLevel,
        vRtrIfIndex
    }
    STATUS      current
    DESCRIPTION
        "[CAUSE] The tmnxIsisRejectedAdjacency notification is sent when we
         receive a Hello PDU from an IS, but do not establish an adjacency due
         to a lack of resources.

         This should be an edge-triggered notification. We should not send a
         second notification about PDUs received from the same source.

         [EFFECT] No effect.

         [RECOVERY] No recovery is necessary."
    ::= { tmnxIsisNotifications 13 }

tmnxIsisLSPTooLargeToPropagate   NOTIFICATION-TYPE
    OBJECTS     {
        tmnxIsisNotifLSPSize,
        tmnxIsisNotifSystemLevel,
        tmnxIsisNotifTrapLSPID,
        vRtrIfIndex
    }
    STATUS      current
    DESCRIPTION
        "[CAUSE] The tmnxIsisLSPTooLargeToPropagate notification is sent when
         we attempt to propagate an LSP which is larger than the
         dataLinkBlockSize for a circuit.

         This should be an edge-triggered notification. We should not send a
         second notification about PDUs received from the same source.

         [EFFECT] No effect.

         [RECOVERY] No recovery is necessary."
    ::= { tmnxIsisNotifications 14 }

tmnxIsisOrigLSPBufSizeMismatch   NOTIFICATION-TYPE
    OBJECTS     {
        tmnxIsisNotifOriginatingBuffSize,
        tmnxIsisNotifSystemLevel,
        tmnxIsisNotifTrapLSPID,
        vRtrIfIndex
    }
    STATUS      current
    DESCRIPTION
        "[CAUSE] The tmnxIsisOrigLSPBufSizeMismatch notification is sent when
         a Level 1 LSP or Level 2 LSP is received which is larger than
         the local value for tmnxIsisLevelLSPBuffSize or
         tmnxIsisSysOrigL1LSPBuffSize or tmnxIsisSysOrigL2LSPBuffSize
         respectively, or when a Level 1 LSP or Level2 LSP is received
         containing the originatingLSPBufferSize option and the value in
         the PDU option field does not match the local value
         for tmnxIsisLevelLSPBuffSize or tmnxIsisSysOrigL1LSPBuffSize or
         tmnxIsisSysOrigL2LSPBuffSize respectively.  We pass up the size from
         the option field or the size of the LSP that exceeds our
         configuration.

         This should be an edge-triggered notification. We should not send a
         second notification about PDUs received from the same source.

         [EFFECT] No effect.

         [RECOVERY] No recovery is necessary."
    ::= { tmnxIsisNotifications 15 }

tmnxIsisProtoSuppMismatch        NOTIFICATION-TYPE
    OBJECTS     {
        tmnxIsisNotifProtocolsSupported,
        tmnxIsisNotifSystemLevel,
        tmnxIsisNotifTrapLSPID,
        vRtrIfIndex
    }
    STATUS      current
    DESCRIPTION
        "[CAUSE] The tmnxIsisProtoSuppMismatch notification is sent when a
         non-pseudonode segment 0 LSP is received that has no matching
         protocols supported.

         This may be because the system does not generate the field, or because
         there are no common elements.

         The list of protocols supported should be included in the
         notification: it may be empty if the TLV is not supported, or if the
         TLV is empty.

         This should be an edge-triggered notification. We should not send a
         second notification about PDUs received from the same source.

         [EFFECT] No effect.

         [RECOVERY] No recovery is necessary."
    ::= { tmnxIsisNotifications 16 }

tmnxIsisAdjacencyChange          NOTIFICATION-TYPE
    OBJECTS     {
        tmnxIsisNotifSystemLevel,
        vRtrIfIndex,
        tmnxIsisNotifTrapLSPID,
        isisISAdjState
    }
    STATUS      current
    DESCRIPTION
        "[CAUSE] The tmnxIsisAdjacencyChange notification is sent when an
         adjacency changes state, entering or leaving state up.

         The first 6 bytes of the tmnxIsisNotifTrapLSPID are the SystemID of
         the adjacent IS.

         The isisISAdjState is the new state of the adjacency.

         [EFFECT] No effect.

         [RECOVERY] No recovery is necessary."
    ::= { tmnxIsisNotifications 17 }

tmnxIsisCircIdExhausted          NOTIFICATION-TYPE
    OBJECTS     {
        vRtrIfIndex,
        tmnxIsisNotifSystemLevel
    }
    STATUS      current
    DESCRIPTION
        "[CAUSE] The tmnxIsisCircIdExhausted notification is sent when the
         specific ISIS level cannot be started on a LAN interface as a unique
         circid could not be assigned due to the exhaustion of the circid
         space.

         This could happen only on the broadcast interfaces.

         [EFFECT] In such a case the interface is marked operationally down.

         [RECOVERY] When an operationally up interface is deleted, the circid
         can be reused by any interface which is waiting to receive a unique
         circid."
    ::= { tmnxIsisNotifications 18 }

tmnxIsisAdjRestartStatusChange   NOTIFICATION-TYPE
    OBJECTS     {
        tmnxIsisNotifSystemLevel,
        vRtrIfIndex,
        tmnxIsisISAdjRestartStatus
    }
    STATUS      current
    DESCRIPTION
        "[CAUSE] The tmnxIsisAdjRestartStatusChange notification is sent when
         an adjacency's graceful restart status changes.

         The tmnxIsisISAdjRestartStatus is the new graceful restart state of
         the adjacency.

         [EFFECT] No effect.

         [RECOVERY] No recovery is necessary."
    ::= { tmnxIsisNotifications 19 }

tmnxIsisLdpSyncTimerStarted      NOTIFICATION-TYPE
    OBJECTS     {
        vRtrIfIndex,
        tmnxIsisIfLdpSyncTimerState
    }
    STATUS      current
    DESCRIPTION
        "[CAUSE] The tmnxIsisLdpSyncTimerStarted notification is sent when the
         vRtrIfLdpSyncTimer is started.

         The timer is started from the time the LDP session to the neighbor is
         up over the interface.

         [EFFECT] This allows for the label FEC bindings to be exchanged.

         [RECOVERY] No recovery is necessary."
    ::= { tmnxIsisNotifications 20 }

tmnxIsisLdpSyncExit              NOTIFICATION-TYPE
    OBJECTS     {
        vRtrIfIndex,
        tmnxIsisIfLdpSyncTimerState
    }
    STATUS      current
    DESCRIPTION
        "[CAUSE] The tmnxIsisLdpSyncExit notification is sent when IGP-LDP
         synchronization has stopped.

         The cause of this event is indicated by tmnxIsisIfLdpSyncTimerState,
         one of them being expiry of vRtrIfLdpSyncTimer.

         [EFFECT] The IGP link metric is restored to normal levels.

         [RECOVERY] No recovery is necessary."
    ::= { tmnxIsisNotifications 21 }

tmnxIsisExportLimitReached       NOTIFICATION-TYPE
    OBJECTS     {
        tmnxIsisNotifSystemLevel,
        tmnxIsisExportLimit
    }
    STATUS      current
    DESCRIPTION
        "[CAUSE] The tmnxIsisExportLimitReached notification is sent when the
         total number of exported routes for the level is equal to the
         configured limit for exported routes, tmnxIsisExportLimit.

         [EFFECT] Additional routes would not be exported into this ISIS level
         from the route table.

         [RECOVERY] Change ISIS export policy."
    ::= { tmnxIsisNotifications 22 }

tmnxIsisExportLimitWarning       NOTIFICATION-TYPE
    OBJECTS     {
        tmnxIsisNotifSystemLevel,
        tmnxIsisExportLimit,
        tmnxIsisExportLimitLogPercent
    }
    STATUS      current
    DESCRIPTION
        "[CAUSE] The tmnxIsisExportLimitWarning notification is sent when the
         total number of exported routes or the level is equal to the
         configured percent, tmnxIsisExportLimitLogPercent of the export limit,
         tmnxIsisExportLimit.

         Additional routes will continue to be exported into this ISIS level
         from the route table till the export limit is reached.

         [EFFECT] No effect.

         [RECOVERY] No recovery is necessary."
    ::= { tmnxIsisNotifications 23 }

tmnxIsisRoutesExpLmtDropped      NOTIFICATION-TYPE
    OBJECTS     {
        tmnxIsisNotifSystemLevel,
        tmnxIsisExportLimit
    }
    STATUS      current
    DESCRIPTION
        "[CAUSE] The tmnxIsisRoutesExpLmtDropped notification is sent when the
         total number of exported routes from the route table to this ISIS
         level drops below the configured export limit, tmnxIsisExportLimit.

         [EFFECT] No effect.

         [RECOVERY] No recovery is necessary."
    ::= { tmnxIsisNotifications 24 }

tmnxIsisFailureDisabled          NOTIFICATION-TYPE
    OBJECTS     {
        tmnxIsisFailureReasonCode
    }
    STATUS      current
    DESCRIPTION
        "[CAUSE] A tmnxIsisFailureDisabled notification is generated when ISIS
         is operationally brought down. Reason for the failure is indicated by
         tmnxIsisFailureReasonCode.

         [EFFECT] ISIS is now operationally down.

         [RECOVERY] ISIS will auto restart."
    ::= { tmnxIsisNotifications 28 }

tmnxIsisSidError                 NOTIFICATION-TYPE
    OBJECTS     {
        tmnxIsisPrefixSidType,
        tmnxIsisPrefixSidFlags,
        tmnxIsisNotifyDescription,
        tmnxIsisPrefixSidAlgorithm
    }
    STATUS      current
    DESCRIPTION
        "[CAUSE] This notification is generated when ISIS receives an IOM or
         CPM failure (system exhausted ILM, NHLFE, duplicate SID) while
         resolving and programming a received prefix SID.

         [EFFECT] The Segment Routing tunnel corresponding to this SID will not
         be programmed.

         [RECOVERY] In case of system exhaustion, the IGP instance goes into
         overload. The operator must manually clear the IGP overload condition
         after freeing resources. IGP will attempt to program at the next SPF
         all tunnels which previously failed the programming operation"
    ::= { tmnxIsisNotifications 29 }

tmnxIsisSidNotInLabelRange       NOTIFICATION-TYPE
    OBJECTS     {
        tmnxIsisPrefixSidType,
        tmnxIsisPrefixSidFlags,
        tmnxIsisNotifPfxSidRangeStartLbl,
        tmnxIsisNotifPfxSidRangeMaxIdx,
        tmnxIsisNotifPfxSidSysID,
        tmnxIsisPrefixSidAlgorithm
    }
    STATUS      current
    DESCRIPTION
        "[CAUSE] This notification is generated when ISIS receives a SID which
         is not within the label range of the nhop router.

         [EFFECT] The Segment Routing tunnel corresponding to this SID will not
         be programmed.

         [RECOVERY] Increase the label range or change the SID index to be
         within the current label range."
    ::= { tmnxIsisNotifications 30 }

tmnxIsisRejectedAdjacencySid     NOTIFICATION-TYPE
    OBJECTS     {
        tmnxIsisNotifSystemLevel,
        vRtrIfIndex,
        tmnxIsisNotifyDescription
    }
    STATUS      current
    DESCRIPTION
        "[CAUSE] The tmnxIsisRejectedAdjacencySid notification is sent when we
         do not establish an adjacency SID or adjacency PGID due to a lack of
         resources.

         This should be an edge-triggered notification. We should not send a
         second notification about adjacency SID allocation failure for the
         same adjacency. We should not send a second notification about
         adjacency PGID allocation failure for the same adjacency.

         [EFFECT] No effect.

         [RECOVERY] Whenever an ADJ-SID is released, the released ADJ-SID can
         be reused by any other adjacency which is waiting to receive an
         ADJ-SID. Whenever a PGID is released, the released PGID can be reused
         by any other adjacency which is waiting to receive a PGID."
    ::= { tmnxIsisNotifications 31 }

tmnxIsisLSPPurge                 NOTIFICATION-TYPE
    OBJECTS     {
        vRtrIfIndex,
        tmnxIsisNotifTrapLSPID,
        tmnxIsisNotifSystemLevel,
        tmnxIsisNotifPurgeOriginator,
        tmnxIsisNotifPurgeSource,
        tmnxIsisNotifAdditionalInfo
    }
    STATUS      current
    DESCRIPTION
        "[CAUSE] The tmnxIsisLSPPurge notification is sent when a LSP is
         purged.

         This notification includes the system ID of the originator, or the
         upstream source of the purge, which may help a network manager to
         locate the origin of the purge and thus the cause of the purge.

         [EFFECT] No effect.

         [RECOVERY] No recovery is necessary."
    ::= { tmnxIsisNotifications 32 }

tmnxIsisPfxLimitOverloadWarning  NOTIFICATION-TYPE
    OBJECTS     {
        tmnxIsisNotifAdditionalInfo
    }
    STATUS      current
    DESCRIPTION
        "[CAUSE] The tmnxIsisPfxLimitOverloadWarning notification is sent when
         the number of prefixes in the system reaches the
         tmnxIsisPrefixLimitThreshold or the tmnxIsisPrefixLimit.

         [EFFECT] When tmnxIsisPrefixLimit is not yet reached, but the
         tmnxIsisPrefixLimitThreshold is reached there is no direct effect; but
         when the number of prefixes grows the system might go into overload.
         When the tmnxIsisPrefixLimit is reached and the object
         tmnxIsisPrefixLimitLogOnly is false, IS-IS will be in overload. There
         is no direct effect when the object tmnxIsisPrefixLimitLogOnly is
         true.

         [RECOVERY] Increase the IS-IS prefix limit."
    ::= { tmnxIsisNotifications 33 }

tmnxIsisAdjBfdSessionSetupFail   NOTIFICATION-TYPE
    OBJECTS     {
        vRtrIfIndex,
        tmnxIsisNotifSystemLevel,
        tmnxIsisNotifTrapLSPID,
        tmnxIsisBfdSessSetupFailReason
    }
    STATUS      current
    DESCRIPTION
        "[CAUSE] The tmnxIsisAdjBfdSessionSetupFail notification is sent when
         BFD session setup fails.

         The first 6 bytes of the tmnxIsisNotifTrapLSPID are the SystemID of
         the adjacent IS.

         [EFFECT] The system can not setup the BFD session.

         [RECOVERY] Depending on the tmnxIsisBfdSessSetupFailReason, recovery
         can be possible. Check the BFD configuration to recover."
    ::= { tmnxIsisNotifications 34 }

tmnxIsisSrgbBadLabelRange        NOTIFICATION-TYPE
    OBJECTS     {
        tmnxIsisNotifAdditionalInfo,
        tmnxIsisNotifSrgbRangeStartLbl,
        tmnxIsisNotifSrgbRangeMaxIdx,
        tmnxIsisNotifSrgbAdvRtrSysID,
        tmnxIsisNotifSrgbLevel,
        tmnxIsisNotifSrgbMtId
    }
    STATUS      current
    DESCRIPTION
        "[CAUSE] The tmnxIsisSrgbBadLabelRange notification is sent when ISIS
         receives a bad SRGB label range from a router (for example,
         overlapping with another label range).

         [EFFECT] The configured Segment Routing tunnels will be wrong.

         [RECOVERY] Change the label range to recover."
    ::= { tmnxIsisNotifications 35 }

tmnxIsisCircMtuTooLow            NOTIFICATION-TYPE
    OBJECTS     {
        vRtrIfIndex,
        tmnxIsisNotifSystemLevel,
        tmnxIsisNotifCircMinReqMtuSize,
        tmnxIsisNotifCircMtuSize
    }
    STATUS      current
    DESCRIPTION
        "[CAUSE] The tmnxIsisCircMtuTooLow notification is sent when we attempt
         to a) configure a circuit which cannot propagate an LSP or SNP with
         max size tmnxIsisLevelLSPBuffSize. b) configure
         tmnxIsisLevelLSPBuffSize which is bigger than
         tmnxIsisLevelMaxOperLSPBuffSize. c) configure
         tmnxIsisSysOrigL1LSPBuffSize or tmnxIsisSysOrigL2LSPBuffSize which is
         bigger than tmnxIsisLevelMaxOperLSPBuffSize.

         [EFFECT] No effect.

         [RECOVERY] Increase port-mtu or decrease lsp-mtu."
    ::= { tmnxIsisNotifications 36 }

tmnxIsisRejectedAdjacencySet     NOTIFICATION-TYPE
    OBJECTS     {
        tmnxIsisAdjSetNeighborSysID,
        tmnxIsisNotifyIfIndex,
        tmnxIsisNotifSystemLevel,
        tmnxIsisNotifNbrSysId,
        tmnxIsisNotifyDescription
    }
    STATUS      current
    DESCRIPTION
        "[CAUSE] The tmnxIsisRejectedAdjacencySet notification is sent when an
         adjacency can not be assigned to an adjacency-set because it does not
         terminate on the same neighbor node as the other adjacencies.

         This notification each time the adjacency-set is programmed.

         [EFFECT] Adjacency-set nhops will not include this adjacency.

         [RECOVERY] Remove the interface from the adjacency-set or change the
         adjacency-set type to non parallel."
    ::= { tmnxIsisNotifications 37 }

tmnxIsisCorruptRemainingLifetime NOTIFICATION-TYPE
    OBJECTS     {
        tmnxIsisLSPLifetimeRemain
    }
    STATUS      current
    DESCRIPTION
        "[CAUSE] The tmnxIsisCorruptRemainingLifetime notification is sent when
         an LSP is received with a possible corrupt Remaining Lifetime field.

         The Remaining Lifetime of a received LSP is considered as possible
         corrupt based on following algorithm:

         - The LSP has passed all acceptance tests.
         - The LSP is newer than the copy in the local LSPDB or no copy present.
         - The Remaining Lifetime in the received LSP is less than Zero Age Lifetime.
         - The adjacency to the neighbor from which the LSP is received has been up
           for a minimum of Zero Age Lifetime.

         [EFFECT] It is possible that an LSP is purged prematurely.

         [RECOVERY] The ISIS system will try to recover by setting the
         Remaining Lifetime to the tmnxIsisLspMinRemainingLifetime value."
    ::= { tmnxIsisNotifications 38 }

tmnxIsisSidStatsIndexAlloc       NOTIFICATION-TYPE
    OBJECTS     {
        tmnxIsisSidStatsSidType,
        tmnxIsisSidStatsPrefixType,
        tmnxIsisSidStatsPrefix,
        tmnxIsisSidStatsPrefixLength,
        tmnxIsisSidStatsIfIndex,
        tmnxIsisSidStatsAdjSet,
        tmnxIsisNotifStatsIndexStatus
    }
    STATUS      current
    DESCRIPTION
        "[CAUSE] The tmnxIsisSidStatsIndexAlloc notification is sent when the
         system is not able to allocate a statistic index to at least one SID.
         This indication is sent once, i.e. if the system retries to allocate a
         stat index but fails no new notification is sent. Conversely, in case
         the system resolves the situation and allocates stat indices to all
         needed SIDs a notification is sent to indicate that stat allocation is
         in nominal state.

         [EFFECT] No effect.

         [RECOVERY] No recovery is necessary."
    ::= { tmnxIsisNotifications 39 }

tmnxIsisFaOperParticipationDown  NOTIFICATION-TYPE
    OBJECTS     {
        tmnxIsisFlexAlgoLastChanged,
        tmnxIsisNotifSystemLevel,
        tmnxIsisNotifyDescription
    }
    STATUS      current
    DESCRIPTION
        "[CAUSE] The tmnxIsisFaOperParticipationDown notification is
         sent when the Flexible Algorithm Participation is operationally down.
         This notification occurs each time when:
         a) there are no Flexible Algorithm Definitions(FADs) present for
            the Flexible Algorithm.
         b) the FAD chosen for Flex-Algo calculation has unsupported
            parameters like unsupported:
            1. Metric-Type
            2. Calculation-Type
            3. Constraint
            4. Fad-Flags
            5. Sub-Tlv

         [EFFECT] The node will cease to participate in that Flexible
         Algorithm,  and won't advertise its participation in SR-algo sub-TLV.

         [RECOVERY] The operator may make sure if at least one FAD is present
         for that Flexible Algorithm, and in case of unsupported FAD, correct
         the FAD parameters to send supported values from remote side."
    ::= { tmnxIsisNotifications 40 }

tmnxIsisRejectedEndXSid          NOTIFICATION-TYPE
    OBJECTS     {
        tmnxIsisNotifSystemLevel,
        vRtrIfIndex,
        tmnxIsisNotifyDescription
    }
    STATUS      current
    DESCRIPTION
        "[CAUSE] The tmnxIsisRejectedEndXSid notification is sent when we do
         not establish a SRv6 End-X SID due to a lack of resources.

         This should be an edge-triggered notification. We should not send a
         second notification about end-x SID allocation failure for the same
         adjacency.

         [EFFECT] No effect.

         [RECOVERY] Whenever an end-x SID is released, the released end-x SID
         can be reused by any other adjacency which is waiting to receive an
         end-x SID."
    ::= { tmnxIsisNotifications 41 }

tmnxIsisRejectedPgId             NOTIFICATION-TYPE
    OBJECTS     {
        tmnxIsisNotifSystemLevel,
        vRtrIfIndex,
        tmnxIsisNotifyDescription
    }
    STATUS      current
    DESCRIPTION
        "[CAUSE] The tmnxIsisRejectedPgId notification is sent when we do not
         establish a SRv6 adjacency PGID due to a lack of resources.

         This should be an edge-triggered notification. We should not send a
         second notification about adjacency PGID allocation failure for the
         same adjacency.

         [EFFECT] No effect.

         [RECOVERY] Whenever a PGID is released, the released PGID can be
         reused by any other adjacency which is waiting to receive a PGID."
    ::= { tmnxIsisNotifications 42 }

tmnxIsisSrv6LocError             NOTIFICATION-TYPE
    OBJECTS     {
        tmnxIsisNotifSystemLevel,
        tmnxIsisSrv6SidAlgorithm,
        tmnxIsisNotifyDescription
    }
    STATUS      current
    DESCRIPTION
        "[CAUSE] This notification is generated when ISIS receives an IOM or
         CPM failure (system exhausted ILM, NHLFE, duplicate SID) while
         resolving and programming a received SRv6 locator.

         [EFFECT] The Segment Routing tunnel corresponding to this locator will
         not be programmed.

         [RECOVERY] In case of system exhaustion, the IGP instance goes into
         overload. The operator must manually clear the IGP overload condition
         after freeing resources. IGP will attempt to program at the next SPF
         all SRv6 tunnels which previously failed the programming operation"
    ::= { tmnxIsisNotifications 43 }

tmnxIsisSrv6StaticSidIfTypeError NOTIFICATION-TYPE
    OBJECTS     {
        tmnxIsisSrv6SidEndpointBehavior,
        tmnxIsisSrv6USidEndpointBehavior,
        tmnxIsisIfOperType,
        tmnxIsisNotifyDescription
    }
    STATUS      current
    DESCRIPTION
        "[CAUSE] This notification is generated when ISIS receives an
         end.x/uA-sid from the locator module  for an existing interface which
         is up and type bcast; or when a new ISIS bcast interface is enabled
         for which an end.x/uA-sid exists in the locator module.

         [EFFECT] The static SID will not be programmed in the RTM.

         [RECOVERY] No recovery is necessary."
    ::= { tmnxIsisNotifications 44 }

END
