TIMETRA-RADIUS-MIB DEFINITIONS ::= BEGIN

IMPORTS
    InetAddress, InetAddressPrefixLength,
    InetAddressType, InetPortNumber
                                                         FROM INET-ADDRESS-MIB
    MODULE-COMPLIANCE, NOTIFICATION-GROUP,
    OBJECT-GROUP
                                                         FROM SNMPv2-CONF
    Counter32, Gauge32, MODULE-IDENTITY,
    NOTIFICATION-TYPE, OBJECT-TYPE,
    Unsigned32
                                                         FROM SNMPv2-SMI
    DisplayString, RowStatus,
    TEXTUAL-CONVENTION, TimeInterval,
    TimeStamp, TruthValue
                                                         FROM SNMPv2-TC
    timetraSRMIBModules, tmnxSRConfs,
    tmnxSRNotifyPrefix, tmnxSRObjs
                                                         FROM TIMETRA-GLOBAL-MIB
    TItemDescription, TNamedItem,
    TNamedItemOrEmpty, TmnxAdminState,
    TmnxAuthPassword, TmnxDisplayStringURL,
    TmnxEnabledDisabled, TmnxOperState,
    TmnxRadiusPendingReqLimit,
    TmnxRadiusServerOperState,
    TmnxSubRadIsaServAlgorithm,
    TmnxSubRadServAlgorithm,
    TmnxSubRadiusAttrType,
    TmnxSubRadiusVendorId, TmnxVRtrIDOrZero,
    TmnxWlanGwIsaGrpIdOrZero
                                                         FROM TIMETRA-TC-MIB
    vRtrID, vRtrIfIndex
                                                         FROM TIMETRA-VRTR-MIB
    ;

timetraRadiusMIBModule           MODULE-IDENTITY
    LAST-UPDATED "201601010000Z"
    ORGANIZATION "Nokia"
    CONTACT-INFO
        "Nokia 7xxx Support
         Web: http://www.nokia.com"
    DESCRIPTION
        "This document is the SNMP MIB module to manage and provision RADIUS
         for the Nokia 7xxx device.

         Copyright 2011-2018 Nokia. All rights reserved. Reproduction of this
         document is authorized on the condition that the foregoing copyright
         notice is included.

         This SNMP MIB module (Specification) embodies Nokia's proprietary
         intellectual property. Nokia retains all title and ownership in the
         Specification, including any revisions.

         Nokia grants all interested parties a non-exclusive license to use and
         distribute an unmodified copy of this Specification in connection with
         management of Nokia products, and without fee, provided this copyright
         notice and license appear on all copies.

         This Specification is supplied 'as is', and Nokia makes no warranty,
         either express or implied, as to the use, operation, condition, or
         performance of the Specification."

    REVISION    "201601010000Z"
    DESCRIPTION
        "Rev 14.0                1 Jan 2016 00:00
         14.0 release of the TIMETRA-RADIUS-MIB."

    REVISION    "201501010000Z"
    DESCRIPTION
        "Rev 13.0                1 Jan 2015 00:00
         13.0 release of the TIMETRA-RADIUS-MIB."

    REVISION    "201401010000Z"
    DESCRIPTION
        "Rev 12.0                1 Jan 2014 00:00
         12.0 release of the TIMETRA-RADIUS-MIB."

    REVISION    "201208010000Z"
    DESCRIPTION
        "Rev 11.0                1 Aug 2012 00:00
         11.0 release of the TIMETRA-RADIUS-MIB."

    REVISION    "201202280000Z"
    DESCRIPTION
        "Rev 10.0                28 February 2012 12:00
         10.0 release of the TIMETRA-RADIUS-MIB."

    ::= { timetraSRMIBModules 79 }

TmnxAuthSecret                   ::= TEXTUAL-CONVENTION
    STATUS      current
    DESCRIPTION
        "The TmnxAuthSecret data type contains a shared secret used for message
         authentication."
    SYNTAX      DisplayString (SIZE (0..64))

TmnxAuthSecretShort              ::= TEXTUAL-CONVENTION
    STATUS      current
    DESCRIPTION
        "The TmnxAuthSecretShort data type contains a shared secret used for
         message authentication."
    SYNTAX      DisplayString (SIZE (0..20))

TmnxRadMatchString               ::= TEXTUAL-CONVENTION
    STATUS      current
    DESCRIPTION
        "The data type TmnxRadMatchString specifies a string to be matched.

         The format is as follows:

         <match-specification> ::= [<match-prefix-spec>][%%<match-suffix-spec>]

         <match-prefix-spec> ::= <char-specification>+
         <match-suffix-spec> ::= <char-specification>+

         <char-specification>  ::= <ascii-char>

         <ascii-char> refers to a printable ASCII character; two consecutive
         percent signs are not allowed.

         Examples and usage are supplied with the object definitions."
    SYNTAX      DisplayString (SIZE (0..128))

TmnxRadiusAcctStatusType         ::= TEXTUAL-CONVENTION
    STATUS      current
    DESCRIPTION
        "The data type TmnxRadiusAcctStatusType specifies a set of values from
         the RADIUS Acct-Status-Type message."
    SYNTAX      BITS {
        start         (0),
        stop          (1),
        interimUpdate (2),
        accountingOn  (3),
        accountingOff (4)
    }

tmnxRadius                       OBJECT IDENTIFIER ::= { tmnxSRObjs 79 }

tmnxRadiusObjs                   OBJECT IDENTIFIER ::= { tmnxRadius 1 }

tmnxRadProxSrvObjs               OBJECT IDENTIFIER ::= { tmnxRadiusObjs 1 }

tmnxRadProxSrvTable              OBJECT-TYPE
    SYNTAX      SEQUENCE OF TmnxRadProxSrvEntry
    MAX-ACCESS  not-accessible
    STATUS      current
    DESCRIPTION
        "The tmnxRadProxSrvTable contains objects to configure the RADIUS Proxy
         Servers of this system."
    ::= { tmnxRadProxSrvObjs 1 }

tmnxRadProxSrvEntry              OBJECT-TYPE
    SYNTAX      TmnxRadProxSrvEntry
    MAX-ACCESS  not-accessible
    STATUS      current
    DESCRIPTION
        "Each conceptual row represents information about a particular RADIUS
         Proxy Server.

         Entries in this table can be created or deleted via SNMP operations."
    INDEX       {
        vRtrID,
        IMPLIED tmnxRadProxSrvName
    }
    ::= { tmnxRadProxSrvTable 1 }

TmnxRadProxSrvEntry              ::= SEQUENCE
{
    tmnxRadProxSrvName               TNamedItem,
    tmnxRadProxSrvLastCh             TimeStamp,
    tmnxRadProxSrvRowStatus          RowStatus,
    tmnxRadProxSrvPurpose            BITS,
    tmnxRadProxSrvAdminState         TmnxAdminState,
    tmnxRadProxSrvDescription        TItemDescription,
    tmnxRadProxSrvSecret             TmnxAuthSecret,
    tmnxRadProxSrvDefAuthSrvPlcy     TNamedItemOrEmpty,
    tmnxRadProxSrvDefAccSrvPlcy      TNamedItemOrEmpty,
    tmnxRadProxSrvCaching            TmnxEnabledDisabled,
    tmnxRadProxSrvCacheKeyPktType    INTEGER,
    tmnxRadProxSrvCacheKeyAttrType   TmnxSubRadiusAttrType,
    tmnxRadProxSrvCacheKeyVendorId   TmnxSubRadiusVendorId,
    tmnxRadProxSrvCacheTimeout       Unsigned32,
    tmnxRadProxSrvCacheTrackAcct     TmnxRadiusAcctStatusType,
    tmnxRadProxSrvSendAcctResponse   TruthValue,
    tmnxRadProxSrvLoadBalanceKey     INTEGER,
    tmnxRadProxSrvLoadBAttr1         TmnxSubRadiusAttrType,
    tmnxRadProxSrvLoadBVendorId1     TmnxSubRadiusVendorId,
    tmnxRadProxSrvLoadBAttr2         TmnxSubRadiusAttrType,
    tmnxRadProxSrvLoadBVendorId2     TmnxSubRadiusVendorId,
    tmnxRadProxSrvLoadBAttr3         TmnxSubRadiusAttrType,
    tmnxRadProxSrvLoadBVendorId3     TmnxSubRadiusVendorId,
    tmnxRadProxSrvLoadBAttr4         TmnxSubRadiusAttrType,
    tmnxRadProxSrvLoadBVendorId4     TmnxSubRadiusVendorId,
    tmnxRadProxSrvLoadBAttr5         TmnxSubRadiusAttrType,
    tmnxRadProxSrvLoadBVendorId5     TmnxSubRadiusVendorId,
    tmnxRadProxSrvCacheTrackAuth     BITS,
    tmnxRadProxSrvWlanGwGroup        TmnxWlanGwIsaGrpIdOrZero,
    tmnxRadProxSrvPythonPolicy       TNamedItemOrEmpty,
    tmnxRadProxSrvCacheTrkDelHoldT   Unsigned32,
    tmnxRadProxSrvAttrMatAttrType    TmnxSubRadiusAttrType,
    tmnxRadProxSrvAttrMatVendorId    TmnxSubRadiusVendorId
}

tmnxRadProxSrvName               OBJECT-TYPE
    SYNTAX      TNamedItem
    MAX-ACCESS  not-accessible
    STATUS      current
    DESCRIPTION
        "The value of tmnxRadProxSrvName specifies the name of this RADIUS
         Proxy server."
    ::= { tmnxRadProxSrvEntry 1 }

tmnxRadProxSrvLastCh             OBJECT-TYPE
    SYNTAX      TimeStamp
    MAX-ACCESS  read-only
    STATUS      current
    DESCRIPTION
        "The value of tmnxRadProxSrvLastCh indicates the sysUpTime at the time
         of the most recent management-initiated change to this table row."
    ::= { tmnxRadProxSrvEntry 2 }

tmnxRadProxSrvRowStatus          OBJECT-TYPE
    SYNTAX      RowStatus
    MAX-ACCESS  read-create
    STATUS      current
    DESCRIPTION
        "The value of tmnxRadProxSrvRowStatus specifies the row status of this
         row."
    ::= { tmnxRadProxSrvEntry 3 }

tmnxRadProxSrvPurpose            OBJECT-TYPE
    SYNTAX      BITS {
        accounting     (0),
        authentication (1)
    }
    MAX-ACCESS  read-create
    STATUS      current
    DESCRIPTION
        "The value of tmnxRadProxSrvPurpose specifies the purpose of this
         RADIUS Proxy server.

         A value for this object must be specified when a conceptual row is
         created, and it cannot be modified afterwards."
    ::= { tmnxRadProxSrvEntry 4 }

tmnxRadProxSrvAdminState         OBJECT-TYPE
    SYNTAX      TmnxAdminState
    MAX-ACCESS  read-create
    STATUS      current
    DESCRIPTION
        "The value of tmnxRadProxSrvAdminState specifies the administrative
         state of this RADIUS Proxy server."
    DEFVAL      { outOfService }
    ::= { tmnxRadProxSrvEntry 5 }

tmnxRadProxSrvDescription        OBJECT-TYPE
    SYNTAX      TItemDescription
    MAX-ACCESS  read-create
    STATUS      current
    DESCRIPTION
        "The value of tmnxRadProxSrvDescription specifies the description of
         this RADIUS Proxy server."
    DEFVAL      { "" }
    ::= { tmnxRadProxSrvEntry 6 }

tmnxRadProxSrvSecret             OBJECT-TYPE
    SYNTAX      TmnxAuthSecret
    MAX-ACCESS  read-create
    STATUS      current
    DESCRIPTION
        "The value of tmnxRadProxSrvSecret specifies the secret key associated
         with the RADIUS server.

         A non-empty value for this object must be provided while the value of
         the object tmnxRadProxSrvAdminState is equal to 'inService'.

         Any GET request on this object returns an empty string."
    DEFVAL      { "" }
    ::= { tmnxRadProxSrvEntry 7 }

tmnxRadProxSrvDefAuthSrvPlcy     OBJECT-TYPE
    SYNTAX      TNamedItemOrEmpty
    MAX-ACCESS  read-create
    STATUS      current
    DESCRIPTION
        "The value of tmnxRadProxSrvDefAuthSrvPlcy specifies the name of the
         default RADIUS Server Policy associated with this RADIUS Proxy server
         for authentication purposes.

         This default policy is used if no policy can be derived from the user
         name.

         The value of tmnxRadProxSrvDefAuthSrvPlcy refers to a row in the
         tmnxRadSrvPlcyTable if the value of tmnxRadProxSrvWlanGwGroup is zero,
         or to a row in the tmnxRadIsaPlcyTable if the value of
         tmnxRadProxSrvWlanGwGroup is not zero."
    DEFVAL      { "" }
    ::= { tmnxRadProxSrvEntry 8 }

tmnxRadProxSrvDefAccSrvPlcy      OBJECT-TYPE
    SYNTAX      TNamedItemOrEmpty
    MAX-ACCESS  read-create
    STATUS      current
    DESCRIPTION
        "The value of tmnxRadProxSrvDefAccSrvPlcy specifies the name of the
         default RADIUS Server Policy associated with this RADIUS Proxy server
         for accounting purposes.

         This default policy is used if no policy can be derived from the user
         name.

         The value of tmnxRadProxSrvDefAccSrvPlcy refers to a row in the
         tmnxRadSrvPlcyTable if the value of tmnxRadProxSrvWlanGwGroup is zero,
         or to a row in the tmnxRadIsaPlcyTable if the value of
         tmnxRadProxSrvWlanGwGroup is not zero."
    DEFVAL      { "" }
    ::= { tmnxRadProxSrvEntry 9 }

tmnxRadProxSrvCaching            OBJECT-TYPE
    SYNTAX      TmnxEnabledDisabled
    MAX-ACCESS  read-create
    STATUS      current
    DESCRIPTION
        "The value of tmnxRadProxSrvCaching specifies if caching is enabled for
         this RADIUS Proxy server.

         While caching is enabled, the attributes of the RADIUS Access-Accept
         messages are cached."
    REFERENCE
        "RFC 2865 RADIUS section 4.2 Access-Accept."
    DEFVAL      { disabled }
    ::= { tmnxRadProxSrvEntry 10 }

tmnxRadProxSrvCacheKeyPktType    OBJECT-TYPE
    SYNTAX      INTEGER {
        none          (0),
        accessRequest (1),
        accessAccept  (2)
    }
    MAX-ACCESS  read-create
    STATUS      current
    DESCRIPTION
        "The value of tmnxRadProxSrvCacheKeyPktType specifies the packet type
         of the RADIUS messages to use to generate the key for the cache of
         this RADIUS Proxy server.

         In order to generate the key associated with a RADIUS Access-Accept
         message, the system uses the attribute of the type specified by the
         value of tmnxRadProxSrvCacheKeyAttrType, within the associated RADIUS
         message of the type specified by the value of
         tmnxRadProxSrvCacheKeyPktType."
    REFERENCE
        "RFC 2865 RADIUS section 4 Packet Types."
    DEFVAL      { none }
    ::= { tmnxRadProxSrvEntry 11 }

tmnxRadProxSrvCacheKeyAttrType   OBJECT-TYPE
    SYNTAX      TmnxSubRadiusAttrType
    MAX-ACCESS  read-create
    STATUS      current
    DESCRIPTION
        "The value of tmnxRadProxSrvCacheKeyAttrType specifies the RADIUS
         attribute type to cache for this RADIUS Proxy server.

         In order to generate the key associated with a RADIUS Access-Accept or
         Accept-Request message, the system uses the attribute of the type
         specified by the value of tmnxRadProxSrvCacheKeyAttrType, within the
         associated RADIUS message of the type specified by the value of
         tmnxRadProxSrvCacheKeyPktType.

         The value zero means that no RADIUS attribute type is specified."
    REFERENCE
        "RFC 2865 RADIUS section 5 Attributes."
    DEFVAL      { 0 }
    ::= { tmnxRadProxSrvEntry 12 }

tmnxRadProxSrvCacheKeyVendorId   OBJECT-TYPE
    SYNTAX      TmnxSubRadiusVendorId
    MAX-ACCESS  read-create
    STATUS      current
    DESCRIPTION
        "The value of tmnxRadProxSrvCacheKeyVendorId specifies the RADIUS
         Vendor-Id.

         If the value of tmnxRadProxSrvCacheKeyVendorId is equal to zero, the
         attribute type specified by tmnxRadProxSrvCacheKeyAttrType must be
         used if it appears outside of a Vendor-Specific attribute.

         If the value of tmnxRadProxSrvCacheKeyVendorId is not equal to zero,
         the attribute type specified by tmnxRadProxSrvCacheKeyAttrType must be
         used if it appears as a sub-attribute within a Vendor-Specific
         attribute with Vendor-Id equal to the value of
         tmnxRadProxSrvCacheKeyVendorId."
    REFERENCE
        "RFC 2865 RADIUS section 5.25 Vendor-Specific."
    DEFVAL      { 0 }
    ::= { tmnxRadProxSrvEntry 13 }

tmnxRadProxSrvCacheTimeout       OBJECT-TYPE
    SYNTAX      Unsigned32 (60..3600)
    UNITS       "seconds"
    MAX-ACCESS  read-create
    STATUS      current
    DESCRIPTION
        "The value of tmnxRadProxSrvCacheTimeout specifies, in seconds, the
         timeout after which an entry in the cache will expire."
    DEFVAL      { 300 }
    ::= { tmnxRadProxSrvEntry 14 }

tmnxRadProxSrvCacheTrackAcct     OBJECT-TYPE
    SYNTAX      TmnxRadiusAcctStatusType
    MAX-ACCESS  read-create
    STATUS      current
    DESCRIPTION
        "The value of tmnxRadProxSrvCacheTrackAcct specifies what RADIUS
         accounting packets have impact on the cache of this RADIUS Proxy
         server."
    REFERENCE
        "RFC 2139 RADIUS Accounting
         section 5.1.  Acct-Status-Type."
    DEFVAL      { {} }
    ::= { tmnxRadProxSrvEntry 15 }

tmnxRadProxSrvSendAcctResponse   OBJECT-TYPE
    SYNTAX      TruthValue
    MAX-ACCESS  read-create
    STATUS      current
    DESCRIPTION
        "The value of tmnxRadProxSrvSendAcctResponse specifies if this RADIUS
         Proxy server itself responds with an Accounting-Response message to
         each received Accounting-Request instead of proxying them to a
         configured RADIUS server."
    DEFVAL      { false }
    ::= { tmnxRadProxSrvEntry 16 }

tmnxRadProxSrvLoadBalanceKey     OBJECT-TYPE
    SYNTAX      INTEGER {
        none        (0),
        sourceIpUdp (1),
        attributes  (2)
    }
    MAX-ACCESS  read-create
    STATUS      current
    DESCRIPTION
        "The value of tmnxRadProxSrvLoadBalanceKey specifies how to construct
         the key for load-balancing RADIUS messages between RADIUS servers.

         The value 'none' specifies that there be no load-balancing.

         The value 'sourceIpUdp' specifies that the key consists of the source
         IP address and source UDP port of the RADIUS message.

         The value 'attributes' specifies that the key is constructed with the
         attributes in the RADIUS message listed in the objects
         tmnxRadProxSrvLoadBAttr1 to tmnxRadProxSrvLoadBAttr5."
    DEFVAL      { none }
    ::= { tmnxRadProxSrvEntry 17 }

tmnxRadProxSrvLoadBAttr1         OBJECT-TYPE
    SYNTAX      TmnxSubRadiusAttrType
    MAX-ACCESS  read-create
    STATUS      current
    DESCRIPTION
        "The value of tmnxRadProxSrvLoadBAttr1 specifies a RADIUS attribute
         that must be used to construct the key for load-balancing RADIUS
         messages between RADIUS servers while the value of the object
         tmnxRadProxSrvLoadBalanceKey is equal to 'attributes'.

         While the value of tmnxRadProxSrvLoadBalanceKey is different from
         'attributes', the value of tmnxRadProxSrvLoadBAttr1 must be equal to
         zero."
    DEFVAL      { 0 }
    ::= { tmnxRadProxSrvEntry 18 }

tmnxRadProxSrvLoadBVendorId1     OBJECT-TYPE
    SYNTAX      TmnxSubRadiusVendorId
    MAX-ACCESS  read-create
    STATUS      current
    DESCRIPTION
        "The value of tmnxRadProxSrvLoadBVendorId1 specifies the RADIUS
         Vendor-Id associated with tmnxRadProxSrvLoadBAttr1.

         If the value of tmnxRadProxSrvLoadBVendorId1 is equal to zero, the
         attribute type specified by tmnxRadProxSrvLoadBAttr1 must be used if
         it appears outside of a Vendor-Specific attribute.

         If the value of tmnxRadProxSrvLoadBVendorId1 is not equal to zero, the
         attribute type specified by tmnxRadProxSrvLoadBAttr1 must be used if
         it appears as a sub-attribute within a Vendor-Specific attribute with
         Vendor-Id equal to the value of tmnxRadProxSrvLoadBVendorId1."
    REFERENCE
        "RFC 2865 RADIUS section 5.25 Vendor-Specific."
    DEFVAL      { 0 }
    ::= { tmnxRadProxSrvEntry 19 }

tmnxRadProxSrvLoadBAttr2         OBJECT-TYPE
    SYNTAX      TmnxSubRadiusAttrType
    MAX-ACCESS  read-create
    STATUS      current
    DESCRIPTION
        "The value of tmnxRadProxSrvLoadBAttr2 specifies a RADIUS attribute
         that must be used to construct the key for load-balancing RADIUS
         messages between RADIUS servers while the value of the object
         tmnxRadProxSrvLoadBalanceKey is equal to 'attributes'.

         While the value of tmnxRadProxSrvLoadBalanceKey is different from
         'attributes', the value of tmnxRadProxSrvLoadBAttr2 must be equal to
         zero."
    DEFVAL      { 0 }
    ::= { tmnxRadProxSrvEntry 20 }

tmnxRadProxSrvLoadBVendorId2     OBJECT-TYPE
    SYNTAX      TmnxSubRadiusVendorId
    MAX-ACCESS  read-create
    STATUS      current
    DESCRIPTION
        "The value of tmnxRadProxSrvLoadBVendorId2 specifies the RADIUS
         Vendor-Id associated with tmnxRadProxSrvLoadBAttr2.

         If the value of tmnxRadProxSrvLoadBVendorId2 is equal to zero, the
         attribute type specified by tmnxRadProxSrvLoadBAttr2 must be used if
         it appears outside of a Vendor-Specific attribute.

         If the value of tmnxRadProxSrvLoadBVendorId2 is not equal to zero, the
         attribute type specified by tmnxRadProxSrvLoadBAttr2 must be used if
         it appears as a sub-attribute within a Vendor-Specific attribute with
         Vendor-Id equal to the value of tmnxRadProxSrvLoadBVendorId2."
    REFERENCE
        "RFC 2865 RADIUS section 5.25 Vendor-Specific."
    DEFVAL      { 0 }
    ::= { tmnxRadProxSrvEntry 21 }

tmnxRadProxSrvLoadBAttr3         OBJECT-TYPE
    SYNTAX      TmnxSubRadiusAttrType
    MAX-ACCESS  read-create
    STATUS      current
    DESCRIPTION
        "The value of tmnxRadProxSrvLoadBAttr3 specifies a RADIUS attribute
         that must be used to construct the key for load-balancing RADIUS
         messages between RADIUS servers while the value of the object
         tmnxRadProxSrvLoadBalanceKey is equal to 'attributes'.

         While the value of tmnxRadProxSrvLoadBalanceKey is different from
         'attributes', the value of tmnxRadProxSrvLoadBAttr3 must be equal to
         zero."
    DEFVAL      { 0 }
    ::= { tmnxRadProxSrvEntry 22 }

tmnxRadProxSrvLoadBVendorId3     OBJECT-TYPE
    SYNTAX      TmnxSubRadiusVendorId
    MAX-ACCESS  read-create
    STATUS      current
    DESCRIPTION
        "The value of tmnxRadProxSrvLoadBVendorId3 specifies the RADIUS
         Vendor-Id associated with tmnxRadProxSrvLoadBAttr3.

         If the value of tmnxRadProxSrvLoadBVendorId3 is equal to zero, the
         attribute type specified by tmnxRadProxSrvLoadBAttr3 must be used if
         it appears outside of a Vendor-Specific attribute.

         If the value of tmnxRadProxSrvLoadBVendorId3 is not equal to zero, the
         attribute type specified by tmnxRadProxSrvLoadBAttr3 must be used if
         it appears as a sub-attribute within a Vendor-Specific attribute with
         Vendor-Id equal to the value of tmnxRadProxSrvLoadBVendorId3."
    REFERENCE
        "RFC 2865 RADIUS section 5.25 Vendor-Specific."
    DEFVAL      { 0 }
    ::= { tmnxRadProxSrvEntry 23 }

tmnxRadProxSrvLoadBAttr4         OBJECT-TYPE
    SYNTAX      TmnxSubRadiusAttrType
    MAX-ACCESS  read-create
    STATUS      current
    DESCRIPTION
        "The value of tmnxRadProxSrvLoadBAttr4 specifies a RADIUS attribute
         that must be used to construct the key for load-balancing RADIUS
         messages between RADIUS servers while the value of the object
         tmnxRadProxSrvLoadBalanceKey is equal to 'attributes'.

         While the value of tmnxRadProxSrvLoadBalanceKey is different from
         'attributes', the value of tmnxRadProxSrvLoadBAttr4 must be equal to
         zero."
    DEFVAL      { 0 }
    ::= { tmnxRadProxSrvEntry 24 }

tmnxRadProxSrvLoadBVendorId4     OBJECT-TYPE
    SYNTAX      TmnxSubRadiusVendorId
    MAX-ACCESS  read-create
    STATUS      current
    DESCRIPTION
        "The value of tmnxRadProxSrvLoadBVendorId4 specifies the RADIUS
         Vendor-Id associated with tmnxRadProxSrvLoadBAttr4.

         If the value of tmnxRadProxSrvLoadBVendorId4 is equal to zero, the
         attribute type specified by tmnxRadProxSrvLoadBAttr4 must be used if
         it appears outside of a Vendor-Specific attribute.

         If the value of tmnxRadProxSrvLoadBVendorId4 is not equal to zero, the
         attribute type specified by tmnxRadProxSrvLoadBAttr4 must be used if
         it appears as a sub-attribute within a Vendor-Specific attribute with
         Vendor-Id equal to the value of tmnxRadProxSrvLoadBVendorId4."
    REFERENCE
        "RFC 2865 RADIUS section 5.25 Vendor-Specific."
    DEFVAL      { 0 }
    ::= { tmnxRadProxSrvEntry 25 }

tmnxRadProxSrvLoadBAttr5         OBJECT-TYPE
    SYNTAX      TmnxSubRadiusAttrType
    MAX-ACCESS  read-create
    STATUS      current
    DESCRIPTION
        "The value of tmnxRadProxSrvLoadBAttr5 specifies a RADIUS attribute
         that must be used to construct the key for load-balancing RADIUS
         messages between RADIUS servers while the value of the object
         tmnxRadProxSrvLoadBalanceKey is equal to 'attributes'.

         While the value of tmnxRadProxSrvLoadBalanceKey is different from
         'attributes', the value of tmnxRadProxSrvLoadBAttr5 must be equal to
         zero."
    DEFVAL      { 0 }
    ::= { tmnxRadProxSrvEntry 26 }

tmnxRadProxSrvLoadBVendorId5     OBJECT-TYPE
    SYNTAX      TmnxSubRadiusVendorId
    MAX-ACCESS  read-create
    STATUS      current
    DESCRIPTION
        "The value of tmnxRadProxSrvLoadBVendorId5 specifies the RADIUS
         Vendor-Id associated with tmnxRadProxSrvLoadBAttr5.

         If the value of tmnxRadProxSrvLoadBVendorId5 is equal to zero, the
         attribute type specified by tmnxRadProxSrvLoadBAttr5 must be used if
         it appears outside of a Vendor-Specific attribute.

         If the value of tmnxRadProxSrvLoadBVendorId5 is not equal to zero, the
         attribute type specified by tmnxRadProxSrvLoadBAttr5 must be used if
         it appears as a sub-attribute within a Vendor-Specific attribute with
         Vendor-Id equal to the value of tmnxRadProxSrvLoadBVendorId5."
    REFERENCE
        "RFC 2865 RADIUS section 5.25 Vendor-Specific."
    DEFVAL      { 0 }
    ::= { tmnxRadProxSrvEntry 27 }

tmnxRadProxSrvCacheTrackAuth     OBJECT-TYPE
    SYNTAX      BITS {
        accept (0)
    }
    MAX-ACCESS  read-create
    STATUS      current
    DESCRIPTION
        "The value of tmnxRadProxSrvCacheTrackAuth specifies what RADIUS
         authentication packets have impact on the cache of this RADIUS Proxy
         server."
    DEFVAL      { {accept} }
    ::= { tmnxRadProxSrvEntry 28 }

tmnxRadProxSrvWlanGwGroup        OBJECT-TYPE
    SYNTAX      TmnxWlanGwIsaGrpIdOrZero
    MAX-ACCESS  read-create
    STATUS      current
    DESCRIPTION
        "The value of tmnxRadProxSrvWlanGwGroup specifies the Wireless Local
         Access Network Gateway Integrated Service Adaptor group of this RADIUS
         Proxy server.

         While a nonzero value for this object is specified, this RADIUS Proxy
         server runs on the ISA cards associated with the WLAN Gateway group.

         The value zero means that no WLAN Gateway group is specified.

         A nonzero value for this object can only be set while this row is
         created; a nonzero value must correspond to a row in the
         TIMETRA-WLAN-GW-MIB::tmnxWlanGwGrpTable.

         The value of this object cannot be modified while this row is active."
    DEFVAL      { 0 }
    ::= { tmnxRadProxSrvEntry 35 }

tmnxRadProxSrvPythonPolicy       OBJECT-TYPE
    SYNTAX      TNamedItemOrEmpty
    MAX-ACCESS  read-create
    STATUS      current
    DESCRIPTION
        "The value of tmnxRadProxSrvPythonPolicy specifies the Python policy
         used for modifying the RADIUS messages of this RADIUS Proxy server.

         This object supersedes the tmnxRadProxSrvDefAuthSrvPlcy, and
         tmnxRadProxSrvDefAccSrvPlcy objects.

         A nonzero value must correspond to a row in the
         TIMETRA-PYTHON-MIB::tmnxPythonPolicyTable."
    DEFVAL      { "" }
    ::= { tmnxRadProxSrvEntry 36 }

tmnxRadProxSrvCacheTrkDelHoldT   OBJECT-TYPE
    SYNTAX      Unsigned32 (0..600)
    UNITS       "seconds"
    MAX-ACCESS  read-create
    STATUS      current
    DESCRIPTION
        "The value of tmnxRadProxSrvCacheTrkDelHoldT specifies the delete
         hold-time in case the DHCP host gets a trigger to delete from the
         matched RADIUS Proxy server."
    DEFVAL      { 0 }
    ::= { tmnxRadProxSrvEntry 37 }

tmnxRadProxSrvAttrMatAttrType    OBJECT-TYPE
    SYNTAX      TmnxSubRadiusAttrType (1..255)
    MAX-ACCESS  read-create
    STATUS      current
    DESCRIPTION
        "The value of tmnxRadProxSrvAttrMatAttrType specifies the RADIUS
         attribute type used to match the attribute-matching entry to a server
         policy."
    DEFVAL      { 1 }
    ::= { tmnxRadProxSrvEntry 38 }

tmnxRadProxSrvAttrMatVendorId    OBJECT-TYPE
    SYNTAX      TmnxSubRadiusVendorId
    MAX-ACCESS  read-create
    STATUS      current
    DESCRIPTION
        "The value of tmnxRadProxSrvAttrMatVendorId specifies the RADIUS
         Vendor-Id specific attribute type used to match the attribute-matching
         entry to a server policy.

         If the value of tmnxRadProxSrvAttrMatVendorId is equal to zero, the
         attribute type specified by tmnxRadProxSrvAttrMatAttrType must be used
         if it appears outside of a Vendor-Specific attribute.

         If the value of tmnxRadProxSrvAttrMatVendorId is not equal to zero,
         the attribute type specified by tmnxRadProxSrvAttrMatAttrType must be
         used if it appears as a sub-attribute within a Vendor-Specific
         attribute with Vendor-Id equal to the value of
         tmnxRadProxSrvAttrMatVendorId."
    REFERENCE
        "
         RFC 2865 RADIUS section 5.25 Vendor-Specific."
    DEFVAL      { 0 }
    ::= { tmnxRadProxSrvEntry 39 }

tmnxRadPSStatusTable             OBJECT-TYPE
    SYNTAX      SEQUENCE OF TmnxRadPSStatusEntry
    MAX-ACCESS  not-accessible
    STATUS      current
    DESCRIPTION
        "The tmnxRadPSStatusTable contains statistics about the RADIUS Proxy
         Servers of this system."
    ::= { tmnxRadProxSrvObjs 2 }

tmnxRadPSStatusEntry             OBJECT-TYPE
    SYNTAX      TmnxRadPSStatusEntry
    MAX-ACCESS  not-accessible
    STATUS      current
    DESCRIPTION
        "Each conceptual row represents statistics about a particular RADIUS
         Proxy Server.

         Rows are created and destroyed automatically by the system."
    AUGMENTS    { tmnxRadProxSrvEntry }
    ::= { tmnxRadPSStatusTable 1 }

TmnxRadPSStatusEntry             ::= SEQUENCE
{
    tmnxRadPSStatusCacheEntries      Gauge32,
    tmnxRadPSStatusCacheEntriesReg   Gauge32
}

tmnxRadPSStatusCacheEntries      OBJECT-TYPE
    SYNTAX      Gauge32
    MAX-ACCESS  read-only
    STATUS      current
    DESCRIPTION
        "The value of tmnxRadPSStatusCacheEntries indicates the number of
         entries in the cache of this RADIUS Proxy Server."
    ::= { tmnxRadPSStatusEntry 1 }

tmnxRadPSStatusCacheEntriesReg   OBJECT-TYPE
    SYNTAX      Gauge32
    MAX-ACCESS  read-only
    STATUS      current
    DESCRIPTION
        "The value of tmnxRadPSStatusCacheEntriesReg indicates the number of
         entries in the cache of this RADIUS Proxy Server.

         Pending entries have a registered application.

         An example of an application that could register to a cache entry is
         Subscriber Management of DHCP clients."
    ::= { tmnxRadPSStatusEntry 2 }

tmnxRadPSStatsTable              OBJECT-TYPE
    SYNTAX      SEQUENCE OF TmnxRadPSStatsEntry
    MAX-ACCESS  not-accessible
    STATUS      current
    DESCRIPTION
        "The tmnxRadPSStatsTable contains statistics about the RADIUS Proxy
         Servers of this system."
    ::= { tmnxRadProxSrvObjs 3 }

tmnxRadPSStatsEntry              OBJECT-TYPE
    SYNTAX      TmnxRadPSStatsEntry
    MAX-ACCESS  not-accessible
    STATUS      current
    DESCRIPTION
        "Each conceptual row represents statistics about a particular RADIUS
         Proxy Server.

         Rows are created and destroyed automatically by the system."
    AUGMENTS    { tmnxRadProxSrvEntry }
    ::= { tmnxRadPSStatsTable 1 }

TmnxRadPSStatsEntry              ::= SEQUENCE
{
    tmnxRadPSStatsRxPacket           Counter32,
    tmnxRadPSStatsRxAuthRequest      Counter32,
    tmnxRadPSStatsRxAcctRequest      Counter32,
    tmnxRadPSStatsRxDropped          Counter32,
    tmnxRadPSStatsRxRetransmit       Counter32,
    tmnxRadPSStatsRxAdminDown        Counter32,
    tmnxRadPSStatsRxNoAaaPol         Counter32,
    tmnxRadPSStatsRxNoLoadBKey       Counter32,
    tmnxRadPSStatsRxInvLen           Counter32,
    tmnxRadPSStatsRxInvCode          Counter32,
    tmnxRadPSStatsRxInvAttr          Counter32,
    tmnxRadPSStatsRxInvUserName      Counter32,
    tmnxRadPSStatsRxInvPassword      Counter32,
    tmnxRadPSStatsRxInvAcctStatusTyp Counter32,
    tmnxRadPSStatsRxNoAcctStatusTyp  Counter32,
    tmnxRadPSStatsRxInvAcctAuth      Counter32,
    tmnxRadPSStatsRxInvMsgAuth       Counter32,
    tmnxRadPSStatsRxNoMemory         Counter32,
    tmnxRadPSStatsRxUserOverload     Counter32,
    tmnxRadPSStatsTxAuthAck          Counter32,
    tmnxRadPSStatsTxAuthReject       Counter32,
    tmnxRadPSStatsTxAuthChallenge    Counter32,
    tmnxRadPSStatsTxAcctResponse     Counter32,
    tmnxRadPSStatsTxDropped          Counter32,
    tmnxRadPSStatsTxCacheNoKey       Counter32,
    tmnxRadPSStatsTxCacheKeyTooLong  Counter32,
    tmnxRadPSStatsTxCacheAttrTooLong Counter32,
    tmnxRadPSStatsTxCacheMaxEntries  Counter32,
    tmnxRadPSStatsTxNoMemory         Counter32,
    tmnxRadPSStatsTxServerTimeout    Counter32,
    tmnxRadPSStatsTxServerAuthFail   Counter32,
    tmnxRadPSStatsTxServerInvCode    Counter32,
    tmnxRadPSStatsTxServerInvAttr    Counter32,
    tmnxRadPSStatsTxUserOverload     Counter32,
    tmnxRadPSStatsTxNoRadiusServer   Counter32,
    tmnxRadPSStatsTxSendFailure      Counter32,
    tmnxRadPSStatsRxDroppedByPython  Counter32,
    tmnxRadPSStatsTxDroppedByPython  Counter32,
    tmnxRadPSStatsTxDroppedByAuthC   Counter32
}

tmnxRadPSStatsRxPacket           OBJECT-TYPE
    SYNTAX      Counter32
    MAX-ACCESS  read-only
    STATUS      current
    DESCRIPTION
        "The value of tmnxRadPSStatsRxPacket indicates the number of packets
         received by this RADIUS Proxy Server."
    ::= { tmnxRadPSStatsEntry 1 }

tmnxRadPSStatsRxAuthRequest      OBJECT-TYPE
    SYNTAX      Counter32
    MAX-ACCESS  read-only
    STATUS      current
    DESCRIPTION
        "The value of tmnxRadPSStatsRxAuthRequest indicates the number of
         Access-Request packets received by this RADIUS Proxy Server."
    ::= { tmnxRadPSStatsEntry 2 }

tmnxRadPSStatsRxAcctRequest      OBJECT-TYPE
    SYNTAX      Counter32
    MAX-ACCESS  read-only
    STATUS      current
    DESCRIPTION
        "The value of tmnxRadPSStatsRxAcctRequest indicates the number of
         Accounting-Request packets received by this RADIUS Proxy Server."
    ::= { tmnxRadPSStatsEntry 3 }

tmnxRadPSStatsRxDropped          OBJECT-TYPE
    SYNTAX      Counter32
    MAX-ACCESS  read-only
    STATUS      current
    DESCRIPTION
        "The value of tmnxRadPSStatsRxDropped indicates the number of packets
         received by this RADIUS Proxy Server but dropped."
    ::= { tmnxRadPSStatsEntry 4 }

tmnxRadPSStatsRxRetransmit       OBJECT-TYPE
    SYNTAX      Counter32
    MAX-ACCESS  read-only
    STATUS      current
    DESCRIPTION
        "The value of tmnxRadPSStatsRxRetransmit indicates the number of
         packets received by this RADIUS Proxy Server that were rejected
         because they are retransmitted."
    ::= { tmnxRadPSStatsEntry 5 }

tmnxRadPSStatsRxAdminDown        OBJECT-TYPE
    SYNTAX      Counter32
    MAX-ACCESS  read-only
    STATUS      current
    DESCRIPTION
        "The value of tmnxRadPSStatsRxAdminDown indicates the number of packets
         received by this RADIUS Proxy Server that were rejected because it is
         administratively shut down."
    ::= { tmnxRadPSStatsEntry 6 }

tmnxRadPSStatsRxNoAaaPol         OBJECT-TYPE
    SYNTAX      Counter32
    MAX-ACCESS  read-only
    STATUS      current
    DESCRIPTION
        "The value of tmnxRadPSStatsRxNoAaaPol indicates the number of packets
         received by this RADIUS Proxy Server that were rejected because it has
         no RADIUS server policy configured for that type of packet."
    ::= { tmnxRadPSStatsEntry 7 }

tmnxRadPSStatsRxNoLoadBKey       OBJECT-TYPE
    SYNTAX      Counter32
    MAX-ACCESS  read-only
    STATUS      current
    DESCRIPTION
        "The value of tmnxRadPSStatsRxNoLoadBKey indicates the number of
         packets received by this RADIUS Proxy Server that were rejected
         because the selected RADIUS server policy's algorithm
         (tmnxRadSrvPlcyAlgorithm) is set to 'hashBased' and no load balance
         key (tmnxRadProxSrvLoadBalanceKey) is configured."
    ::= { tmnxRadPSStatsEntry 8 }

tmnxRadPSStatsRxInvLen           OBJECT-TYPE
    SYNTAX      Counter32
    MAX-ACCESS  read-only
    STATUS      current
    DESCRIPTION
        "The value of tmnxRadPSStatsRxInvLen indicates the number of packets
         received by this RADIUS Proxy Server that were rejected because their
         length was invalid."
    ::= { tmnxRadPSStatsEntry 9 }

tmnxRadPSStatsRxInvCode          OBJECT-TYPE
    SYNTAX      Counter32
    MAX-ACCESS  read-only
    STATUS      current
    DESCRIPTION
        "The value of tmnxRadPSStatsRxInvCode indicates the number of packets
         received by this RADIUS Proxy Server that were rejected because they
         had an invalid Code field."
    REFERENCE
        "RFC 2865 Remote Authentication Dial In User Service (RADIUS)
         section 3 Packet format."
    ::= { tmnxRadPSStatsEntry 10 }

tmnxRadPSStatsRxInvAttr          OBJECT-TYPE
    SYNTAX      Counter32
    MAX-ACCESS  read-only
    STATUS      current
    DESCRIPTION
        "The value of tmnxRadPSStatsRxInvAttr indicates the number of packets
         received by this RADIUS Proxy Server that were rejected because one of
         the attributes was incorrectly encoded."
    REFERENCE
        "RFC 2865 Remote Authentication Dial In User Service (RADIUS)
         section 5 Attributes."
    ::= { tmnxRadPSStatsEntry 11 }

tmnxRadPSStatsRxInvUserName      OBJECT-TYPE
    SYNTAX      Counter32
    MAX-ACCESS  read-only
    STATUS      current
    DESCRIPTION
        "The value of tmnxRadPSStatsRxInvUserName indicates the number of
         packets received by this RADIUS Proxy Server that were rejected
         because they contained an invalid User-Name attribute."
    REFERENCE
        "RFC 2865 Remote Authentication Dial In User Service (RADIUS)
         section 5.1 User-Name."
    ::= { tmnxRadPSStatsEntry 12 }

tmnxRadPSStatsRxInvPassword      OBJECT-TYPE
    SYNTAX      Counter32
    MAX-ACCESS  read-only
    STATUS      current
    DESCRIPTION
        "The value of tmnxRadPSStatsRxInvPassword indicates the number of
         packets received by this RADIUS Proxy Server that were rejected
         because the User-Password attribute could not be decoded."
    REFERENCE
        "RFC 2865 Remote Authentication Dial In User Service (RADIUS)
         section 5.2 User-Password."
    ::= { tmnxRadPSStatsEntry 13 }

tmnxRadPSStatsRxInvAcctStatusTyp OBJECT-TYPE
    SYNTAX      Counter32
    MAX-ACCESS  read-only
    STATUS      current
    DESCRIPTION
        "The value of tmnxRadPSStatsRxInvAcctStatusTyp indicates the number of
         accounting packets received by this RADIUS Proxy Server that were
         rejected because they contained an invalid Acct-Status-Type attribute."
    REFERENCE
        "RFC 2866 RADIUS Accounting
         section 5.1 Acct-Status-Type."
    ::= { tmnxRadPSStatsEntry 14 }

tmnxRadPSStatsRxNoAcctStatusTyp  OBJECT-TYPE
    SYNTAX      Counter32
    MAX-ACCESS  read-only
    STATUS      current
    DESCRIPTION
        "The value of tmnxRadPSStatsRxNoAcctStatusTyp indicates the number of
         accounting packets received by this RADIUS Proxy Server that were
         rejected because they contained no Acct-Status-Type attribute."
    REFERENCE
        "RFC 2866 RADIUS Accounting
         section 5.1 Acct-Status-Type."
    ::= { tmnxRadPSStatsEntry 15 }

tmnxRadPSStatsRxInvAcctAuth      OBJECT-TYPE
    SYNTAX      Counter32
    MAX-ACCESS  read-only
    STATUS      current
    DESCRIPTION
        "The value of tmnxRadPSStatsRxInvAcctAuth indicates the number of
         accounting packets received by this RADIUS Proxy Server that were
         rejected because they contained an invalid Authenticator field."
    REFERENCE
        "RFC 2139 RADIUS Accounting
         section 3 Request Authenticator."
    ::= { tmnxRadPSStatsEntry 16 }

tmnxRadPSStatsRxInvMsgAuth       OBJECT-TYPE
    SYNTAX      Counter32
    MAX-ACCESS  read-only
    STATUS      current
    DESCRIPTION
        "The value of tmnxRadPSStatsRxInvMsgAuth indicates the number of
         packets received by this RADIUS Proxy Server that were rejected
         because they contained an invalid Message-Authenticator attribute."
    REFERENCE
        "RFC 2869 RADIUS Extensions
         section 5.14 Message-Authenticator."
    ::= { tmnxRadPSStatsEntry 17 }

tmnxRadPSStatsRxNoMemory         OBJECT-TYPE
    SYNTAX      Counter32
    MAX-ACCESS  read-only
    STATUS      current
    DESCRIPTION
        "The value of tmnxRadPSStatsRxNoMemory indicates the number of packets
         that were rejected by this RADIUS server because there was not enough
         memory to store them."
    ::= { tmnxRadPSStatsEntry 18 }

tmnxRadPSStatsRxUserOverload     OBJECT-TYPE
    SYNTAX      Counter32
    MAX-ACCESS  read-only
    STATUS      current
    DESCRIPTION
        "The value of tmnxRadPSStatsRxUserOverload indicates the number of
         packets that were rejected by this RADIUS server because the
         registered user indicated to be in overload."
    ::= { tmnxRadPSStatsEntry 19 }

tmnxRadPSStatsTxAuthAck          OBJECT-TYPE
    SYNTAX      Counter32
    MAX-ACCESS  read-only
    STATUS      current
    DESCRIPTION
        "The value of tmnxRadPSStatsTxAuthAck indicates the number of
         Access-Accept packets transmitted by this RADIUS Proxy Server."
    REFERENCE
        "RFC 2865 Remote Authentication Dial In User Service (RADIUS)
         section 4.2 Access-Accept."
    ::= { tmnxRadPSStatsEntry 20 }

tmnxRadPSStatsTxAuthReject       OBJECT-TYPE
    SYNTAX      Counter32
    MAX-ACCESS  read-only
    STATUS      current
    DESCRIPTION
        "The value of tmnxRadPSStatsTxAuthReject indicates the number of
         Access-Reject packets transmitted by this RADIUS Proxy Server."
    REFERENCE
        "RFC 2865 Remote Authentication Dial In User Service (RADIUS)
         section 4.3 Access-Reject."
    ::= { tmnxRadPSStatsEntry 21 }

tmnxRadPSStatsTxAuthChallenge    OBJECT-TYPE
    SYNTAX      Counter32
    MAX-ACCESS  read-only
    STATUS      current
    DESCRIPTION
        "The value of tmnxRadPSStatsTxAuthChallenge indicates the number of
         Access-Challenge packets transmitted by this RADIUS Proxy Server."
    REFERENCE
        "RFC 2865 Remote Authentication Dial In User Service (RADIUS)
         section 4.4 Access-Challenge."
    ::= { tmnxRadPSStatsEntry 22 }

tmnxRadPSStatsTxAcctResponse     OBJECT-TYPE
    SYNTAX      Counter32
    MAX-ACCESS  read-only
    STATUS      current
    DESCRIPTION
        "The value of tmnxRadPSStatsTxAcctResponse indicates the number of
         Accounting-Response packets transmitted by this RADIUS Proxy Server."
    REFERENCE
        "RFC 2866 RADIUS Accounting
         section 4.2 Accounting-Response."
    ::= { tmnxRadPSStatsEntry 23 }

tmnxRadPSStatsTxDropped          OBJECT-TYPE
    SYNTAX      Counter32
    MAX-ACCESS  read-only
    STATUS      current
    DESCRIPTION
        "The value of tmnxRadPSStatsTxDropped indicates the number of packets
         dropped by this RADIUS Proxy Server before transmission."
    ::= { tmnxRadPSStatsEntry 24 }

tmnxRadPSStatsTxCacheNoKey       OBJECT-TYPE
    SYNTAX      Counter32
    MAX-ACCESS  read-only
    STATUS      current
    DESCRIPTION
        "The value of tmnxRadPSStatsTxCacheNoKey indicates the number of
         packets that could not be cached by this RADIUS Proxy Server because
         the key information was not present in the packet."
    ::= { tmnxRadPSStatsEntry 25 }

tmnxRadPSStatsTxCacheKeyTooLong  OBJECT-TYPE
    SYNTAX      Counter32
    MAX-ACCESS  read-only
    STATUS      current
    DESCRIPTION
        "The value of tmnxRadPSStatsTxCacheKeyTooLong indicates the number of
         packets that could not be cached by this RADIUS Proxy Server because
         the key information present in the packet was too long."
    ::= { tmnxRadPSStatsEntry 26 }

tmnxRadPSStatsTxCacheAttrTooLong OBJECT-TYPE
    SYNTAX      Counter32
    MAX-ACCESS  read-only
    STATUS      current
    DESCRIPTION
        "The value of tmnxRadPSStatsTxCacheAttrTooLong indicates the number of
         packets that could not be cached by this RADIUS Proxy Server because
         the total length of the attributes is too long."
    ::= { tmnxRadPSStatsEntry 27 }

tmnxRadPSStatsTxCacheMaxEntries  OBJECT-TYPE
    SYNTAX      Counter32
    MAX-ACCESS  read-only
    STATUS      current
    DESCRIPTION
        "The value of tmnxRadPSStatsTxCacheMaxEntries indicates the number of
         packets that could not be cached by this RADIUS Proxy Server because
         the limit has been reached."
    ::= { tmnxRadPSStatsEntry 28 }

tmnxRadPSStatsTxNoMemory         OBJECT-TYPE
    SYNTAX      Counter32
    MAX-ACCESS  read-only
    STATUS      current
    DESCRIPTION
        "The value of tmnxRadPSStatsTxNoMemory indicates the number of packets
         that could not be transmitted by this RADIUS Proxy Server because
         there was not enough memory."
    ::= { tmnxRadPSStatsEntry 29 }

tmnxRadPSStatsTxServerTimeout    OBJECT-TYPE
    SYNTAX      Counter32
    MAX-ACCESS  read-only
    STATUS      current
    DESCRIPTION
        "The value of tmnxRadPSStatsTxServerTimeout indicates the number of
         packets that were dropped because the RADIUS servers have timed out."
    ::= { tmnxRadPSStatsEntry 30 }

tmnxRadPSStatsTxServerAuthFail   OBJECT-TYPE
    SYNTAX      Counter32
    MAX-ACCESS  read-only
    STATUS      current
    DESCRIPTION
        "The value of tmnxRadPSStatsTxServerAuthFail indicates the number of
         packets that were dropped because the RADIUS server replied with a
         packet which failed authentication (invalid response Authenticator or
         Message-Authenticator attribute)."
    ::= { tmnxRadPSStatsEntry 31 }

tmnxRadPSStatsTxServerInvCode    OBJECT-TYPE
    SYNTAX      Counter32
    MAX-ACCESS  read-only
    STATUS      current
    DESCRIPTION
        "The value of tmnxRadPSStatsTxServerInvCode indicates the number of
         packets that were dropped because the RADIUS server replied with a
         packet with an invalid Code field."
    ::= { tmnxRadPSStatsEntry 32 }

tmnxRadPSStatsTxServerInvAttr    OBJECT-TYPE
    SYNTAX      Counter32
    MAX-ACCESS  read-only
    STATUS      current
    DESCRIPTION
        "The value of tmnxRadPSStatsTxServerInvAttr indicates the number of
         packets that were dropped because the RADIUS server replied with a
         packet with an invalid attribute."
    REFERENCE
        "RFC 2865 Remote Authentication Dial In User Service (RADIUS)
         section 5 Attributes."
    ::= { tmnxRadPSStatsEntry 33 }

tmnxRadPSStatsTxUserOverload     OBJECT-TYPE
    SYNTAX      Counter32
    MAX-ACCESS  read-only
    STATUS      current
    DESCRIPTION
        "The value of tmnxRadPSStatsTxUserOverload indicates the number of
         packets that were dropped because the registered user indicated to be
         in overload."
    ::= { tmnxRadPSStatsEntry 34 }

tmnxRadPSStatsTxNoRadiusServer   OBJECT-TYPE
    SYNTAX      Counter32
    MAX-ACCESS  read-only
    STATUS      current
    DESCRIPTION
        "The value of tmnxRadPSStatsTxNoRadiusServer indicates the number of
         packets that were dropped by this RADIUS server because the RADIUS
         server policy has no servers configured."
    ::= { tmnxRadPSStatsEntry 35 }

tmnxRadPSStatsTxSendFailure      OBJECT-TYPE
    SYNTAX      Counter32
    MAX-ACCESS  read-only
    STATUS      current
    DESCRIPTION
        "The value of tmnxRadPSStatsTxSendFailure indicates the number of
         packets that were dropped by this RADIUS server because the packet
         could not get transmitted to one of the servers in the RADIUS server
         policy."
    ::= { tmnxRadPSStatsEntry 36 }

tmnxRadPSStatsRxDroppedByPython  OBJECT-TYPE
    SYNTAX      Counter32
    MAX-ACCESS  read-only
    STATUS      current
    DESCRIPTION
        "The value of tmnxRadPSStatsRxDroppedByPython indicates the number of
         packets received by this RADIUS Proxy Server but dropped by Python."
    ::= { tmnxRadPSStatsEntry 37 }

tmnxRadPSStatsTxDroppedByPython  OBJECT-TYPE
    SYNTAX      Counter32
    MAX-ACCESS  read-only
    STATUS      current
    DESCRIPTION
        "The value of tmnxRadPSStatsTxDroppedByPython indicates the number of
         packets that were dropped by this RADIUS server because the packet was
         dropped by the Python script."
    ::= { tmnxRadPSStatsEntry 38 }

tmnxRadPSStatsTxDroppedByAuthC   OBJECT-TYPE
    SYNTAX      Counter32
    MAX-ACCESS  read-only
    STATUS      current
    DESCRIPTION
        "The value of tmnxRadPSStatsTxDroppedByAuthC indicates the number of
         packets that were dropped by a client registered for authentication
         packets."
    ::= { tmnxRadPSStatsEntry 39 }

tmnxRadProxSrvIfTable            OBJECT-TYPE
    SYNTAX      SEQUENCE OF TmnxRadProxSrvIfEntry
    MAX-ACCESS  not-accessible
    STATUS      current
    DESCRIPTION
        "The tmnxRadProxSrvIfTable contains the interfaces associated with the
         RADIUS Proxy servers."
    ::= { tmnxRadProxSrvObjs 4 }

tmnxRadProxSrvIfEntry            OBJECT-TYPE
    SYNTAX      TmnxRadProxSrvIfEntry
    MAX-ACCESS  not-accessible
    STATUS      current
    DESCRIPTION
        "Each conceptual row represents an interface associated with a
         particular RADIUS Proxy server.

         Entries in this table can be created or deleted via SNMP operations.

         An row in this table can only be created if the value of the object
         vRtrIfType in the conceptual row in the TIMETRA-VRTR-MIB::vRtrIfTable
         corresponding with the same vRtrID and vRtrIfIndex, is equal to either
         'network' or 'serviceIes in the Base router, or 'serviceVprn' in a
         VPRN router instance."
    INDEX       {
        vRtrID,
        tmnxRadProxSrvName,
        vRtrIfIndex
    }
    ::= { tmnxRadProxSrvIfTable 1 }

TmnxRadProxSrvIfEntry            ::= SEQUENCE
{
    tmnxRadProxSrvIfRowStatus        RowStatus,
    tmnxRadProxSrvIfLastCh           TimeStamp
}

tmnxRadProxSrvIfRowStatus        OBJECT-TYPE
    SYNTAX      RowStatus
    MAX-ACCESS  read-create
    STATUS      current
    DESCRIPTION
        "The value of tmnxRadProxSrvIfRowStatus specifies the row status of
         this row."
    ::= { tmnxRadProxSrvIfEntry 1 }

tmnxRadProxSrvIfLastCh           OBJECT-TYPE
    SYNTAX      TimeStamp
    MAX-ACCESS  read-only
    STATUS      current
    DESCRIPTION
        "The value of tmnxRadProxSrvIfLastCh indicates the sysUpTime at the
         time of the most recent management-initiated change to this table row."
    ::= { tmnxRadProxSrvIfEntry 2 }

tmnxRadProxUsrToRspTable         OBJECT-TYPE
    SYNTAX      SEQUENCE OF TmnxRadProxUsrToRspEntry
    MAX-ACCESS  not-accessible
    STATUS      current
    DESCRIPTION
        "The tmnxRadProxUsrToRspTable associates RADIUS Proxy users with RADIUS
         Server policies, by specifying match criteria for the RADIUS
         User-Name.

         The order of evaluation is determined by the numeric index: within the
         scope of a RADIUS Proxy server, the row with the lowest value of the
         object tmnxRadProxUsrToRspIndex is evaluated first."
    ::= { tmnxRadProxSrvObjs 5 }

tmnxRadProxUsrToRspEntry         OBJECT-TYPE
    SYNTAX      TmnxRadProxUsrToRspEntry
    MAX-ACCESS  not-accessible
    STATUS      current
    DESCRIPTION
        "Each conceptual row represents a RADIUS User-Name match rule that
         associates a RADIUS Proxy user with a RADIUS server policy.

         Entries in this table can be created or deleted via SNMP operations."
    INDEX       {
        vRtrID,
        tmnxRadProxSrvName,
        tmnxRadProxUsrToRspIndex
    }
    ::= { tmnxRadProxUsrToRspTable 1 }

TmnxRadProxUsrToRspEntry         ::= SEQUENCE
{
    tmnxRadProxUsrToRspIndex         Unsigned32,
    tmnxRadProxUsrToRspRowStatus     RowStatus,
    tmnxRadProxUsrToRspLastCh        TimeStamp,
    tmnxRadProxUsrToRspMatchString   TmnxRadMatchString,
    tmnxRadProxUsrToRspAuthSrvPlcy   TNamedItemOrEmpty,
    tmnxRadProxUsrToRspAccSrvPlcy    TNamedItemOrEmpty
}

tmnxRadProxUsrToRspIndex         OBJECT-TYPE
    SYNTAX      Unsigned32 (1..32)
    MAX-ACCESS  not-accessible
    STATUS      current
    DESCRIPTION
        "The value of tmnxRadProxUsrToRspIndex specifies the index of this row."
    ::= { tmnxRadProxUsrToRspEntry 1 }

tmnxRadProxUsrToRspRowStatus     OBJECT-TYPE
    SYNTAX      RowStatus
    MAX-ACCESS  read-create
    STATUS      current
    DESCRIPTION
        "The value of tmnxRadProxUsrToRspRowStatus specifies the row status of
         this row."
    ::= { tmnxRadProxUsrToRspEntry 2 }

tmnxRadProxUsrToRspLastCh        OBJECT-TYPE
    SYNTAX      TimeStamp
    MAX-ACCESS  read-only
    STATUS      current
    DESCRIPTION
        "The value of tmnxRadProxUsrToRspLastCh indicates the sysUpTime at the
         time of the most recent management-initiated change to this table row."
    ::= { tmnxRadProxUsrToRspEntry 3 }

tmnxRadProxUsrToRspMatchString   OBJECT-TYPE
    SYNTAX      TmnxRadMatchString (SIZE (1..128))
    MAX-ACCESS  read-create
    STATUS      current
    DESCRIPTION
        "The value of tmnxRadProxUsrToRspMatchString specifies the characters
         to match with the first and (optionally) the last characters in the
         RADIUS User-Name attribute.

         For example, a value of '20620' matches a RADIUS User-Name
         '206200487175230' and '206200486514245', but not '206010476405285' or
         '206010476420620'.

         Another example: a value of '%%@myprovider.com' matches
         'john.doe@myprovider.com' and 'mary.lynn@myprovider.com', but not
         'john.smith@anotherprovider.com'.

         A value of 'john%%@myprovider.com' matches 'john.doe@myprovider.com'
         and 'john.smith@myprovider.com' but not 'mary.lynn@myprovider.com'.

         A value for this object must be specified when the row is created."
    ::= { tmnxRadProxUsrToRspEntry 4 }

tmnxRadProxUsrToRspAuthSrvPlcy   OBJECT-TYPE
    SYNTAX      TNamedItemOrEmpty
    MAX-ACCESS  read-create
    STATUS      current
    DESCRIPTION
        "The value of tmnxRadProxUsrToRspAuthSrvPlcy specifies the name of the
         RADIUS Server Policy to be used within this RADIUS Proxy server for
         the authentication of users that match the value of the object
         tmnxRadProxUsrToRspMatchString.

         The value of tmnxRadProxUsrToRspAuthSrvPlcy refers to a row in the
         tmnxRadSrvPlcyTable if the value of tmnxRadProxSrvWlanGwGroup for the
         associated RADIUS Proxy server is zero, or to a row in the
         tmnxRadIsaPlcyTable if the value of tmnxRadProxSrvWlanGwGroup for the
         associated RADIUS Proxy server is not zero. A value for the object
         tmnxRadProxUsrToRspAuthSrvPlcy or for the object
         tmnxRadProxUsrToRspAccSrvPlcy, or both, must be specified when the row
         is created."
    ::= { tmnxRadProxUsrToRspEntry 5 }

tmnxRadProxUsrToRspAccSrvPlcy    OBJECT-TYPE
    SYNTAX      TNamedItemOrEmpty
    MAX-ACCESS  read-create
    STATUS      current
    DESCRIPTION
        "The value of tmnxRadProxUsrToRspAccSrvPlcy specifies the name of the
         RADIUS Server Policy to be used within this RADIUS Proxy server for
         the accounting of users that match the value of the object
         tmnxRadProxUsrToRspMatchString.

         The value of tmnxRadProxUsrToRspAccSrvPlcy refers to a row in the
         tmnxRadSrvPlcyTable if the value of tmnxRadProxSrvWlanGwGroup for the
         associated RADIUS Proxy server is zero, or to a row in the
         tmnxRadIsaPlcyTable if the value of tmnxRadProxSrvWlanGwGroup for the
         associated RADIUS Proxy server is not zero.

         A value for the object tmnxRadProxUsrToRspAuthSrvPlcy or for the
         object tmnxRadProxUsrToRspAccSrvPlcy, or both, must be specified when
         the row is created."
    ::= { tmnxRadProxUsrToRspEntry 6 }

tmnxRadProxSrvCacheTable         OBJECT-TYPE
    SYNTAX      SEQUENCE OF TmnxRadProxSrvCacheEntry
    MAX-ACCESS  not-accessible
    STATUS      current
    DESCRIPTION
        "The tmnxRadProxSrvCacheTable contains a summary of the cache of the
         RADIUS Proxy servers.

         The RADIUS Proxy servers can cache the RADIUS Access-Request and
         Access-Accept messages and order them, according to
         the values of the objects
             - tmnxRadProxSrvCaching,
             - tmnxRadProxSrvCacheKeyPktType,
             - tmnxRadProxSrvCacheKeyAttrType,
             - tmnxRadProxSrvCacheKeyVendorId ,
             - tmnxRadProxSrvCacheTimeout,
             - tmnxRadProxSrvCacheTrackAcct."
    ::= { tmnxRadProxSrvObjs 6 }

tmnxRadProxSrvCacheEntry         OBJECT-TYPE
    SYNTAX      TmnxRadProxSrvCacheEntry
    MAX-ACCESS  not-accessible
    STATUS      current
    DESCRIPTION
        "Each conceptual row represents a summary of a specific cache entry of
         a particular RADIUS Proxy server.

         Entries in this table are created and destroyed automatically by the
         system."
    INDEX       {
        vRtrID,
        tmnxRadProxSrvName,
        tmnxRadProxSrvCacheKey
    }
    ::= { tmnxRadProxSrvCacheTable 1 }

TmnxRadProxSrvCacheEntry         ::= SEQUENCE
{
    tmnxRadProxSrvCacheKey           OCTET STRING,
    tmnxRadProxSrvCacheAge           TimeInterval,
    tmnxRadProxSrvCacheTimeLeft      TimeInterval,
    tmnxRadProxSrvCacheRequestLength Unsigned32,
    tmnxRadProxSrvCacheAcceptLength  Unsigned32,
    tmnxRadProxSrvCacheRegistered    TruthValue,
    tmnxRadProxSrvCacheNasIpAddrTyp  InetAddressType,
    tmnxRadProxSrvCacheNasIpAddr     InetAddress,
    tmnxRadProxSrvCacheNasIp6AddrTyp InetAddressType,
    tmnxRadProxSrvCacheNasIp6Addr    InetAddress,
    tmnxRadProxSrvCacheCalldStation  OCTET STRING
}

tmnxRadProxSrvCacheKey           OBJECT-TYPE
    SYNTAX      OCTET STRING (SIZE (1..64))
    MAX-ACCESS  not-accessible
    STATUS      current
    DESCRIPTION
        "The value of tmnxRadProxSrvCacheKey indicates the key of this cache
         entry."
    ::= { tmnxRadProxSrvCacheEntry 1 }

tmnxRadProxSrvCacheAge           OBJECT-TYPE
    SYNTAX      TimeInterval
    MAX-ACCESS  read-only
    STATUS      current
    DESCRIPTION
        "The value of tmnxRadProxSrvCacheAge indicates the age of this cache
         entry."
    ::= { tmnxRadProxSrvCacheEntry 2 }

tmnxRadProxSrvCacheTimeLeft      OBJECT-TYPE
    SYNTAX      TimeInterval
    MAX-ACCESS  read-only
    STATUS      current
    DESCRIPTION
        "The value of tmnxRadProxSrvCacheTimeLeft indicates the period of time
         left for this cache entry.

         A value of zero indicates that this cache entry is not scheduled to
         expire.

         An unregistered cache entry is destroyed when its timer expires, while
         a registered cache entry is reset when its timer expires."
    ::= { tmnxRadProxSrvCacheEntry 3 }

tmnxRadProxSrvCacheRequestLength OBJECT-TYPE
    SYNTAX      Unsigned32
    MAX-ACCESS  read-only
    STATUS      current
    DESCRIPTION
        "The value of tmnxRadProxSrvCacheRequestLength indicates the length of
         the RADIUS Access-Request packet attribute(s) in the cache."
    ::= { tmnxRadProxSrvCacheEntry 4 }

tmnxRadProxSrvCacheAcceptLength  OBJECT-TYPE
    SYNTAX      Unsigned32
    MAX-ACCESS  read-only
    STATUS      current
    DESCRIPTION
        "The value of tmnxRadProxSrvCacheAcceptLength indicates the length of
         the RADIUS Access-Accept packet attribute(s) in the cache."
    ::= { tmnxRadProxSrvCacheEntry 5 }

tmnxRadProxSrvCacheRegistered    OBJECT-TYPE
    SYNTAX      TruthValue
    MAX-ACCESS  read-only
    STATUS      current
    DESCRIPTION
        "The value of tmnxRadProxSrvCacheRegistered indicates if this cache
         entry is used by a client of this RADIUS Proxy server."
    ::= { tmnxRadProxSrvCacheEntry 6 }

tmnxRadProxSrvCacheNasIpAddrTyp  OBJECT-TYPE
    SYNTAX      InetAddressType
    MAX-ACCESS  read-only
    STATUS      current
    DESCRIPTION
        "The value of tmnxRadProxSrvCacheNasIpAddrTyp indicates the address
         type of tmnxRadProxSrvCacheNasIpAddr."
    ::= { tmnxRadProxSrvCacheEntry 7 }

tmnxRadProxSrvCacheNasIpAddr     OBJECT-TYPE
    SYNTAX      InetAddress (SIZE (0|4))
    MAX-ACCESS  read-only
    STATUS      current
    DESCRIPTION
        "The value of tmnxRadProxSrvCacheNasIpAddr indicates the NAS-IP-Address
         in the RADIUS message cache."
    REFERENCE
        "RFC 2865 Remote Authentication Dial In User Service (RADIUS)
         section 5.4.  NAS-IP-Address."
    ::= { tmnxRadProxSrvCacheEntry 8 }

tmnxRadProxSrvCacheNasIp6AddrTyp OBJECT-TYPE
    SYNTAX      InetAddressType
    MAX-ACCESS  read-only
    STATUS      current
    DESCRIPTION
        "The value of tmnxRadProxSrvCacheNasIp6AddrTyp indicates the address
         type of tmnxRadProxSrvCacheNasIp6Addr."
    ::= { tmnxRadProxSrvCacheEntry 9 }

tmnxRadProxSrvCacheNasIp6Addr    OBJECT-TYPE
    SYNTAX      InetAddress (SIZE (0|16))
    MAX-ACCESS  read-only
    STATUS      current
    DESCRIPTION
        "The value of tmnxRadProxSrvCacheNasIp6Addr indicates the
         NAS-IPv6-Address in the RADIUS message cache."
    REFERENCE
        "RFC 3162 RADIUS and IPv6
         section 2.1. NAS-IPv6-Address."
    ::= { tmnxRadProxSrvCacheEntry 10 }

tmnxRadProxSrvCacheCalldStation  OBJECT-TYPE
    SYNTAX      OCTET STRING (SIZE (0..64))
    MAX-ACCESS  read-only
    STATUS      current
    DESCRIPTION
        "The value of tmnxRadProxSrvCacheCalldStation indicates the
         Called-Station-Id in the RADIUS message cache."
    REFERENCE
        "RFC 2865 Remote Authentication Dial In User Service (RADIUS)
         section 5.30. Called-Station-Id."
    ::= { tmnxRadProxSrvCacheEntry 11 }

tmnxRadPSWlanGwTable             OBJECT-TYPE
    SYNTAX      SEQUENCE OF TmnxRadPSWlanGwEntry
    MAX-ACCESS  not-accessible
    STATUS      current
    DESCRIPTION
        "The tmnxRadPSWlanGwTable contains objects to configure Wireless Local
         Access Network Gateway functionality for the RADIUS Proxy Servers of
         this system."
    ::= { tmnxRadProxSrvObjs 8 }

tmnxRadPSWlanGwEntry             OBJECT-TYPE
    SYNTAX      TmnxRadPSWlanGwEntry
    MAX-ACCESS  not-accessible
    STATUS      current
    DESCRIPTION
        "Each conceptual row represents configuration for a particular RADIUS
         Proxy Server associated with a WLAN Gateway group.

         Rows are created and destroyed automatically by the system, for each
         corresponding row in the tmnxRadProxSrvTable where the value of
         tmnxRadProxSrvWlanGwGroup is not zero."
    INDEX       {
        vRtrID,
        IMPLIED tmnxRadProxSrvName
    }
    ::= { tmnxRadPSWlanGwTable 1 }

TmnxRadPSWlanGwEntry             ::= SEQUENCE
{
    tmnxRadPSWlanGwLastCh            TimeStamp,
    tmnxRadPSWlanGwIpv4AddrType      InetAddressType,
    tmnxRadPSWlanGwIpv4Addr          InetAddress,
    tmnxRadPSWlanGwIpv6AddrType      InetAddressType,
    tmnxRadPSWlanGwIpv6Addr          InetAddress
}

tmnxRadPSWlanGwLastCh            OBJECT-TYPE
    SYNTAX      TimeStamp
    MAX-ACCESS  read-create
    STATUS      current
    DESCRIPTION
        "The value of tmnxRadPSWlanGwLastCh indicates the sysUpTime at the time
         of the most recent management-initiated change to this table row."
    ::= { tmnxRadPSWlanGwEntry 1 }

tmnxRadPSWlanGwIpv4AddrType      OBJECT-TYPE
    SYNTAX      InetAddressType
    MAX-ACCESS  read-create
    STATUS      current
    DESCRIPTION
        "The value of tmnxRadPSWlanGwIpv4AddrType specifies the type of address
         stored in tmnxRadPSWlanGwIpv4Addr.

         The value 'unknown' means that no value is configured for
         tmnxRadPSWlanGwIpv4Addr."
    DEFVAL      { unknown }
    ::= { tmnxRadPSWlanGwEntry 2 }

tmnxRadPSWlanGwIpv4Addr          OBJECT-TYPE
    SYNTAX      InetAddress (SIZE (0|4))
    MAX-ACCESS  read-create
    STATUS      current
    DESCRIPTION
        "The value of tmnxRadPSWlanGwIpv4Addr specifies the IP address of this
         RADIUS Proxy server.

         A non-empty value must be a valid unicast IP address."
    DEFVAL      { ''H }
    ::= { tmnxRadPSWlanGwEntry 3 }

tmnxRadPSWlanGwIpv6AddrType      OBJECT-TYPE
    SYNTAX      InetAddressType
    MAX-ACCESS  read-create
    STATUS      current
    DESCRIPTION
        "The value of tmnxRadPSWlanGwIpv6AddrType specifies the type of address
         stored in tmnxRadPSWlanGwIpv6Addr.

         The value 'unknown' means that no value is configured for
         tmnxRadPSWlanGwIpv6Addr."
    DEFVAL      { unknown }
    ::= { tmnxRadPSWlanGwEntry 4 }

tmnxRadPSWlanGwIpv6Addr          OBJECT-TYPE
    SYNTAX      InetAddress (SIZE (0|16))
    MAX-ACCESS  read-create
    STATUS      current
    DESCRIPTION
        "The value of tmnxRadPSWlanGwIpv6Addr specifies the IPv6 address of
         this RADIUS Proxy server.

         A non-empty value must be a valid unicast IPv6 address."
    DEFVAL      { ''H }
    ::= { tmnxRadPSWlanGwEntry 5 }

tmnxRadSrvObjs                   OBJECT IDENTIFIER ::= { tmnxRadiusObjs 2 }

tmnxRadServTable                 OBJECT-TYPE
    SYNTAX      SEQUENCE OF TmnxRadServEntry
    MAX-ACCESS  not-accessible
    STATUS      current
    DESCRIPTION
        "The tmnxRadServTable contains objects to configure how to access the
         RADIUS Servers used by the RADIUS Proxy function of this system."
    ::= { tmnxRadSrvObjs 1 }

tmnxRadServEntry                 OBJECT-TYPE
    SYNTAX      TmnxRadServEntry
    MAX-ACCESS  not-accessible
    STATUS      current
    DESCRIPTION
        "Each conceptual row represents information about a particular RADIUS
         Server.

         Entries in this table can be created or deleted via SNMP operations."
    INDEX       {
        vRtrID,
        IMPLIED tmnxRadServName
    }
    ::= { tmnxRadServTable 1 }

TmnxRadServEntry                 ::= SEQUENCE
{
    tmnxRadServName                  TNamedItem,
    tmnxRadServLastCh                TimeStamp,
    tmnxRadServRowStatus             RowStatus,
    tmnxRadServAddrType              InetAddressType,
    tmnxRadServAddr                  InetAddress,
    tmnxRadServPort                  Unsigned32,
    tmnxRadServSecret                TmnxAuthSecret,
    tmnxRadServDescription           TItemDescription,
    tmnxRadServAcceptCoa             TruthValue,
    tmnxRadServCoaScriptPlcy         TNamedItemOrEmpty,
    tmnxRadServPndRqLimit            TmnxRadiusPendingReqLimit,
    tmnxRadServAuthPort              Unsigned32,
    tmnxRadServAcctPort              Unsigned32,
    tmnxRadServPythonPolicy          TNamedItemOrEmpty
}

tmnxRadServName                  OBJECT-TYPE
    SYNTAX      TNamedItem
    MAX-ACCESS  not-accessible
    STATUS      current
    DESCRIPTION
        "The value of tmnxRadServName specifies the name of this RADIUS server."
    ::= { tmnxRadServEntry 1 }

tmnxRadServLastCh                OBJECT-TYPE
    SYNTAX      TimeStamp
    MAX-ACCESS  read-only
    STATUS      current
    DESCRIPTION
        "The value of tmnxRadServLastCh indicates the sysUpTime at the time of
         the most recent management-initiated change to this table row."
    ::= { tmnxRadServEntry 2 }

tmnxRadServRowStatus             OBJECT-TYPE
    SYNTAX      RowStatus
    MAX-ACCESS  read-create
    STATUS      current
    DESCRIPTION
        "The value of tmnxRadServRowStatus specifies the row status of this
         row."
    ::= { tmnxRadServEntry 3 }

tmnxRadServAddrType              OBJECT-TYPE
    SYNTAX      InetAddressType
    MAX-ACCESS  read-create
    STATUS      current
    DESCRIPTION
        "The value of tmnxRadServAddrType specifies the type of address stored
         in tmnxRadServAddr."
    ::= { tmnxRadServEntry 4 }

tmnxRadServAddr                  OBJECT-TYPE
    SYNTAX      InetAddress (SIZE (4|16))
    MAX-ACCESS  read-create
    STATUS      current
    DESCRIPTION
        "The value of tmnxRadServAddr specifies the IP address of the RADIUS
         server.

         A valid unicast IP address must be specified at row creation time."
    ::= { tmnxRadServEntry 5 }

tmnxRadServPort                  OBJECT-TYPE
    SYNTAX      Unsigned32 (1..65535)
    MAX-ACCESS  read-create
    STATUS      obsolete
    DESCRIPTION
        "The value of tmnxRadServPort specifies the UDP port number on which to
         contact the RADIUS server.

         A value for this object must be specified when the row is created.

         This object has been obsoleted. It is replaced by 2 new objects
         (tmnxRadServAuthPort and tmnxRadServAcctPort), allowing a different
         port to be used when accessing the RADIUS server for accounting or for
         authentication purposes."
    ::= { tmnxRadServEntry 6 }

tmnxRadServSecret                OBJECT-TYPE
    SYNTAX      TmnxAuthSecret
    MAX-ACCESS  read-create
    STATUS      current
    DESCRIPTION
        "The value of tmnxRadServSecret specifies the secret key associated
         with the RADIUS server.

         A non-empty value for this object must be provided when a conceptual
         row is created'.

         Any GET request on this object returns an empty string."
    ::= { tmnxRadServEntry 7 }

tmnxRadServDescription           OBJECT-TYPE
    SYNTAX      TItemDescription
    MAX-ACCESS  read-create
    STATUS      current
    DESCRIPTION
        "The value of tmnxRadServDescription specifies the description of this
         RADIUS server."
    DEFVAL      { "" }
    ::= { tmnxRadServEntry 8 }

tmnxRadServAcceptCoa             OBJECT-TYPE
    SYNTAX      TruthValue
    MAX-ACCESS  read-create
    STATUS      current
    DESCRIPTION
        "The value of tmnxRadServAcceptCoa specifies if this RADIUS server is
         allowed to process Change of Authorization messages."
    REFERENCE
        "RFC 3576 Dynamic Authorization Extensions to RADIUS
         section 2.2 Change-of-Authorization Messages (CoA)."
    DEFVAL      { false }
    ::= { tmnxRadServEntry 9 }

tmnxRadServCoaScriptPlcy         OBJECT-TYPE
    SYNTAX      TNamedItemOrEmpty
    MAX-ACCESS  read-create
    STATUS      current
    DESCRIPTION
        "The value of tmnxRadServCoaScriptPlcy specifies the RADIUS script
         policy used to change the RADIUS attributes of the
         Change-of-Authorization messages.

         If both tmnxRadServPythonPolicy and tmnxRadServCoaScriptPlcy are
         configured, the script mentioned in tmnxRadServCoaScriptPlcy will be
         ignored."
    REFERENCE
        "RFC 3576 Dynamic Authorization Extensions to RADIUS
         section 2.2 Change-of-Authorization Messages (CoA)."
    DEFVAL      { "" }
    ::= { tmnxRadServEntry 10 }

tmnxRadServPndRqLimit            OBJECT-TYPE
    SYNTAX      TmnxRadiusPendingReqLimit
    MAX-ACCESS  read-create
    STATUS      current
    DESCRIPTION
        "The value of tmnxRadServPndRqLimit specifies the limit of the number
         of pending RADIUS authentication requests."
    DEFVAL      { 4096 }
    ::= { tmnxRadServEntry 11 }

tmnxRadServAuthPort              OBJECT-TYPE
    SYNTAX      Unsigned32 (1..65535)
    MAX-ACCESS  read-create
    STATUS      current
    DESCRIPTION
        "The value of tmnxRadServAuthPort specifies the UDP port number on
         which to contact the RADIUS server for authentication purposes."
    DEFVAL      { 1812 }
    ::= { tmnxRadServEntry 12 }

tmnxRadServAcctPort              OBJECT-TYPE
    SYNTAX      Unsigned32 (1..65535)
    MAX-ACCESS  read-create
    STATUS      current
    DESCRIPTION
        "The value of tmnxRadServAcctPort specifies the UDP port number on
         which to contact the RADIUS server for accounting purposes."
    DEFVAL      { 1813 }
    ::= { tmnxRadServEntry 13 }

tmnxRadServPythonPolicy          OBJECT-TYPE
    SYNTAX      TNamedItemOrEmpty
    MAX-ACCESS  read-create
    STATUS      current
    DESCRIPTION
        "The value of tmnxRadServPythonPolicy specifies the Python script
         policy used to change the RADIUS attributes of the
         Change-of-Authorization messages.

         If both tmnxRadServPythonPolicy and tmnxRadServCoaScriptPlcy are
         configured, the script mentioned in tmnxRadServCoaScriptPlcy will be
         ignored."
    REFERENCE
        "RFC 3576 Dynamic Authorization Extensions to RADIUS
         section 2.2 Change-of-Authorization Messages (CoA)."
    DEFVAL      { "" }
    ::= { tmnxRadServEntry 14 }

tmnxRadSrvPlcyTable              OBJECT-TYPE
    SYNTAX      SEQUENCE OF TmnxRadSrvPlcyEntry
    MAX-ACCESS  not-accessible
    STATUS      current
    DESCRIPTION
        "The tmnxRadSrvPlcyTable allows configuration of how to access a group
         of RADIUS servers."
    ::= { tmnxRadSrvObjs 2 }

tmnxRadSrvPlcyEntry              OBJECT-TYPE
    SYNTAX      TmnxRadSrvPlcyEntry
    MAX-ACCESS  not-accessible
    STATUS      current
    DESCRIPTION
        "Each entry represents the configuration for a specific RADIUS servers
         policy.

         Entries in this table can be created and deleted via SNMP SET
         operations to tmnxRadSrvPlcyRowStatus."
    INDEX       { IMPLIED tmnxRadSrvPlcyName }
    ::= { tmnxRadSrvPlcyTable 1 }

TmnxRadSrvPlcyEntry              ::= SEQUENCE
{
    tmnxRadSrvPlcyName               TNamedItem,
    tmnxRadSrvPlcyRowStatus          RowStatus,
    tmnxRadSrvPlcyLastCh             TimeStamp,
    tmnxRadSrvPlcyDescription        TItemDescription,
    tmnxRadSrvPlcyTimeout            Unsigned32,
    tmnxRadSrvPlcyRetry              Unsigned32,
    tmnxRadSrvPlcyDownTime           Unsigned32,
    tmnxRadSrvPlcyRouter             TmnxVRtrIDOrZero,
    tmnxRadSrvPlcySrcAddrType        InetAddressType,
    tmnxRadSrvPlcySrcAddr            InetAddress,
    tmnxRadSrvPlcyAlgorithm          TmnxSubRadServAlgorithm,
    tmnxRadSrvPlcyRequestScriptPlcy  TNamedItemOrEmpty,
    tmnxRadSrvPlcyAcceptScriptPlcy   TNamedItemOrEmpty,
    tmnxRadSrvPlcyBlockedState       INTEGER,
    tmnxRadSrvPlcyAcctReqScriptPlcy  TNamedItemOrEmpty,
    tmnxRadSrvPlcyAuthReqScriptPlcy  TNamedItemOrEmpty,
    tmnxRadSrvPlcyAcctInterimMinItvl Unsigned32,
    tmnxRadSrvPlcyAcctInterimMaxItvl Unsigned32,
    tmnxRadSrvPlcyAcctInterimlifetim Unsigned32,
    tmnxRadSrvPlcyAcctStopMinItvl    Unsigned32,
    tmnxRadSrvPlcyAcctStopMaxItvl    Unsigned32,
    tmnxRadSrvPlcyAcctStoplifetim    Unsigned32,
    tmnxRadSrvPlcyPythonPolicy       TNamedItemOrEmpty,
    tmnxRadSrvPlcyIpv6SrcAddrType    InetAddressType,
    tmnxRadSrvPlcyIpv6SrcAddr        InetAddress,
    tmnxRadSrvPlcyServerDownTimeout  Unsigned32,
    tmnxRadSrvPlcyTestAccntChecking  TmnxEnabledDisabled,
    tmnxRadSrvPlcyTestAccntIvl       Unsigned32,
    tmnxRadSrvPlcyTestAccntUserName  DisplayString,
    tmnxRadSrvPlcyTestAccntPassword  TmnxAuthPassword,
    tmnxRadSrvPlcyDisableStickiness  TruthValue,
    tmnxRadSrvPlcyAcctStartMinItvl   Unsigned32,
    tmnxRadSrvPlcyAcctStartMaxItvl   Unsigned32,
    tmnxRadSrvPlcyAcctStartlifetim   Unsigned32
}

tmnxRadSrvPlcyName               OBJECT-TYPE
    SYNTAX      TNamedItem
    MAX-ACCESS  accessible-for-notify
    STATUS      current
    DESCRIPTION
        "The value of tmnxRadSrvPlcyName specifies a specific RADIUS servers
         policy."
    ::= { tmnxRadSrvPlcyEntry 1 }

tmnxRadSrvPlcyRowStatus          OBJECT-TYPE
    SYNTAX      RowStatus
    MAX-ACCESS  read-create
    STATUS      current
    DESCRIPTION
        "The value of tmnxRadSrvPlcyRowStatus controls the creation and
         deletion of rows in the table. An attempt to delete a row that is
         referred to will fail with an inconsistentValue error."
    ::= { tmnxRadSrvPlcyEntry 2 }

tmnxRadSrvPlcyLastCh             OBJECT-TYPE
    SYNTAX      TimeStamp
    MAX-ACCESS  read-only
    STATUS      current
    DESCRIPTION
        "The value of tmnxRadSrvPlcyLastCh indicates the sysUpTime at the time
         of the most recent management-initiated change to this policy."
    ::= { tmnxRadSrvPlcyEntry 3 }

tmnxRadSrvPlcyDescription        OBJECT-TYPE
    SYNTAX      TItemDescription
    MAX-ACCESS  read-create
    STATUS      current
    DESCRIPTION
        "The value of tmnxRadSrvPlcyDescription specifies the user provided
         description of this subscriber RADIUS based accounting policy."
    DEFVAL      { "" }
    ::= { tmnxRadSrvPlcyEntry 4 }

tmnxRadSrvPlcyTimeout            OBJECT-TYPE
    SYNTAX      Unsigned32 (1..340)
    UNITS       "seconds"
    MAX-ACCESS  read-create
    STATUS      current
    DESCRIPTION
        "The value of tmnxRadSrvPlcyTimeout specifies, in seconds, the timeout
         between retries towards the same RADIUS server."
    DEFVAL      { 5 }
    ::= { tmnxRadSrvPlcyEntry 100 }

tmnxRadSrvPlcyRetry              OBJECT-TYPE
    SYNTAX      Unsigned32 (1..256)
    MAX-ACCESS  read-create
    STATUS      current
    DESCRIPTION
        "The value of tmnxRadSrvPlcyRetry specifies the number of RADIUS
         requests towards the same RADIUS server."
    DEFVAL      { 3 }
    ::= { tmnxRadSrvPlcyEntry 101 }

tmnxRadSrvPlcyDownTime           OBJECT-TYPE
    SYNTAX      Unsigned32 (30..86400)
    UNITS       "seconds"
    MAX-ACCESS  read-create
    STATUS      current
    DESCRIPTION
        "The value of tmnxRadSrvPlcyDownTime specifies the hold down time.

         If a RADIUS authentication server that was detected to be
         'outOfService', the system waits for this amount of time before it
         starts to address that server again."
    DEFVAL      { 30 }
    ::= { tmnxRadSrvPlcyEntry 102 }

tmnxRadSrvPlcyRouter             OBJECT-TYPE
    SYNTAX      TmnxVRtrIDOrZero
    MAX-ACCESS  read-create
    STATUS      current
    DESCRIPTION
        "The value of tmnxRadSrvPlcyRouter specifies the virtual router
         instance applicable for the set of configured RADIUS servers
         tmnxRadServTable."
    DEFVAL      { 0 }
    ::= { tmnxRadSrvPlcyEntry 103 }

tmnxRadSrvPlcySrcAddrType        OBJECT-TYPE
    SYNTAX      InetAddressType
    MAX-ACCESS  read-create
    STATUS      current
    DESCRIPTION
        "The value of tmnxRadSrvPlcySrcAddrType specifies the type of address
         stored in tmnxRadSrvPlcySrcAddr."
    DEFVAL      { unknown }
    ::= { tmnxRadSrvPlcyEntry 104 }

tmnxRadSrvPlcySrcAddr            OBJECT-TYPE
    SYNTAX      InetAddress (SIZE (0|4|16))
    MAX-ACCESS  read-create
    STATUS      current
    DESCRIPTION
        "The value of tmnxRadSrvPlcySrcAddr specifies the source addresses
         while transmitting RADIUS protocol messages to one of the RADIUS
         servers; it must be a valid unicast address."
    DEFVAL      { ''H }
    ::= { tmnxRadSrvPlcyEntry 105 }

tmnxRadSrvPlcyAlgorithm          OBJECT-TYPE
    SYNTAX      TmnxSubRadServAlgorithm
    MAX-ACCESS  read-create
    STATUS      current
    DESCRIPTION
        "The value of tmnxRadSrvPlcyAlgorithm specifies the algorithm used to
         select a RADIUS server from the list of configured servers
         tmnxRadServTable."
    DEFVAL      { direct }
    ::= { tmnxRadSrvPlcyEntry 106 }

tmnxRadSrvPlcyRequestScriptPlcy  OBJECT-TYPE
    SYNTAX      TNamedItemOrEmpty
    MAX-ACCESS  read-create
    STATUS      obsolete
    DESCRIPTION
        "The value of tmnxRadSrvPlcyRequestScriptPlcy specifies the RADIUS
         script policy used to change the RADIUS attributes of the outgoing
         Access-Request or Accounting-Request messages.

         This object is made obsolete. It is replaced by 2 new objects
         (tmnxRadSrvPlcyAcctReqScriptPlcy and tmnxRadSrvPlcyAuthReqScriptPlcy)
         to allow a different RADIUS script policy to be configured for
         accounting or for authentication purposes."
    DEFVAL      { "" }
    ::= { tmnxRadSrvPlcyEntry 107 }

tmnxRadSrvPlcyAcceptScriptPlcy   OBJECT-TYPE
    SYNTAX      TNamedItemOrEmpty
    MAX-ACCESS  read-create
    STATUS      current
    DESCRIPTION
        "The value of tmnxRadSrvPlcyAcceptScriptPlcy specifies the RADIUS
         script policy used to change the RADIUS attributes of the outgoing
         Access-Accept messages."
    DEFVAL      { "" }
    ::= { tmnxRadSrvPlcyEntry 108 }

tmnxRadSrvPlcyBlockedState       OBJECT-TYPE
    SYNTAX      INTEGER {
        notBlocked (0),
        blocked    (1)
    }
    MAX-ACCESS  read-only
    STATUS      current
    DESCRIPTION
        "The value of tmnxRadSrvPlcyBlockedState indicates whether or not the
         RADIUS server policy is blocked by the acct-on-off function as
         controlled by the object tmnxRadSrvPlcyAcctOnOffAdminSt. In the state
         'blocked' only the RADIUS messages Acct-on and Acct-off can be
         exchanged."
    ::= { tmnxRadSrvPlcyEntry 109 }

tmnxRadSrvPlcyAcctReqScriptPlcy  OBJECT-TYPE
    SYNTAX      TNamedItemOrEmpty
    MAX-ACCESS  read-create
    STATUS      current
    DESCRIPTION
        "The value of tmnxRadSrvPlcyAcctReqScriptPlcy specifies the RADIUS
         script policy used to change the RADIUS attributes of the
         Accounting-Request messages."
    DEFVAL      { "" }
    ::= { tmnxRadSrvPlcyEntry 110 }

tmnxRadSrvPlcyAuthReqScriptPlcy  OBJECT-TYPE
    SYNTAX      TNamedItemOrEmpty
    MAX-ACCESS  read-create
    STATUS      current
    DESCRIPTION
        "The value of tmnxRadSrvPlcyAuthReqScriptPlcy specifies the RADIUS
         script policy used to change the RADIUS attributes of the outgoing
         Access-Request messages."
    DEFVAL      { "" }
    ::= { tmnxRadSrvPlcyEntry 111 }

tmnxRadSrvPlcyAcctInterimMinItvl OBJECT-TYPE
    SYNTAX      Unsigned32 (0..3600)
    UNITS       "seconds"
    MAX-ACCESS  read-create
    STATUS      current
    DESCRIPTION
        "The value of tmnxRadSrvPlcyAcctInterimMinItvl specifies the minimum
         interval (in seconds) between retries to send the RADIUS accounting
         interim update message.

         The value '0' specifies that no retries are performed.

         The value specified must be less then or equal to the value specified
         for the object tmnxRadSrvPlcyAcctInterimMaxItvl.

         If a value '0' is specified for any of the objects
         tmnxRadSrvPlcyAcctInterimMinItvl, tmnxRadSrvPlcyAcctInterimMaxItvl, or
         tmnxRadSrvPlcyAcctInterimlifetim, then all 3 objects will be set to
         '0' by the system."
    DEFVAL      { 0 }
    ::= { tmnxRadSrvPlcyEntry 112 }

tmnxRadSrvPlcyAcctInterimMaxItvl OBJECT-TYPE
    SYNTAX      Unsigned32 (0..3600)
    UNITS       "seconds"
    MAX-ACCESS  read-create
    STATUS      current
    DESCRIPTION
        "The value of tmnxRadSrvPlcyAcctInterimMaxItvl specifies the maximum
         interval (in seconds) between retries to send the RADIUS accounting
         interim update message.

         The value '0' specifies that no retries are performed.

         The value specified must be bigger then or equal to the value
         specified for the object tmnxRadSrvPlcyAcctInterimMinItvl.

         If a value '0' is specified for any of the objects
         tmnxRadSrvPlcyAcctInterimMinItvl, tmnxRadSrvPlcyAcctInterimMaxItvl, or
         tmnxRadSrvPlcyAcctInterimlifetim, then all 3 objects will be set to
         '0' by the system."
    DEFVAL      { 0 }
    ::= { tmnxRadSrvPlcyEntry 113 }

tmnxRadSrvPlcyAcctInterimlifetim OBJECT-TYPE
    SYNTAX      Unsigned32 (0..25)
    UNITS       "hours"
    MAX-ACCESS  read-create
    STATUS      current
    DESCRIPTION
        "The value of tmnxRadSrvPlcyAcctInterimlifetim specifies the time (in
         hours) an accounting message can be in the retransmission buffer.

         The value '0' specifies that no retries are performed, and hence that
         no data is buffered.

         If a value '0' is specified for any of the objects
         tmnxRadSrvPlcyAcctInterimMinItvl, tmnxRadSrvPlcyAcctInterimMaxItvl, or
         tmnxRadSrvPlcyAcctInterimlifetim, then all 3 objects will be set to
         '0' by the system."
    DEFVAL      { 0 }
    ::= { tmnxRadSrvPlcyEntry 114 }

tmnxRadSrvPlcyAcctStopMinItvl    OBJECT-TYPE
    SYNTAX      Unsigned32 (0..3600)
    UNITS       "seconds"
    MAX-ACCESS  read-create
    STATUS      current
    DESCRIPTION
        "The value of tmnxRadSrvPlcyAcctStopMinItvl specifies the minimum
         interval (in seconds) between retries to send the RADIUS accounting
         stop message.

         The value '0' specifies that no retries are performed.

         The value specified must be less then or equal to the value specified
         for the object tmnxRadSrvPlcyAcctStopMaxItvl.

         If a value '0' is specified for any of the objects
         tmnxRadSrvPlcyAcctStopMinItvl, tmnxRadSrvPlcyAcctStopMaxItvl, or
         tmnxRadSrvPlcyAcctStoplifetim, then all 3 objects will be set to '0'
         by the system."
    DEFVAL      { 0 }
    ::= { tmnxRadSrvPlcyEntry 115 }

tmnxRadSrvPlcyAcctStopMaxItvl    OBJECT-TYPE
    SYNTAX      Unsigned32 (0..3600)
    UNITS       "seconds"
    MAX-ACCESS  read-create
    STATUS      current
    DESCRIPTION
        "The value of tmnxRadSrvPlcyAcctStopMaxItvl specifies the maximum
         interval (in seconds) between retries to send the RADIUS accounting
         stop message.

         The value '0' specifies that no retries are performed.

         The value specified must be bigger then or equal to the value
         specified for the object tmnxRadSrvPlcyAcctStopMinItvl.

         If a value '0' is specified for any of the objects
         tmnxRadSrvPlcyAcctStopMinItvl, tmnxRadSrvPlcyAcctStopMaxItvl, or
         tmnxRadSrvPlcyAcctStoplifetim, then all 3 objects will be set to '0'
         by the system."
    DEFVAL      { 0 }
    ::= { tmnxRadSrvPlcyEntry 116 }

tmnxRadSrvPlcyAcctStoplifetim    OBJECT-TYPE
    SYNTAX      Unsigned32 (0..25)
    UNITS       "hours"
    MAX-ACCESS  read-create
    STATUS      current
    DESCRIPTION
        "The value of tmnxRadSrvPlcyAcctStoplifetim specifies the time (in
         hours) an accounting message can be in the retransmission buffer.

         The value '0' specifies that no retries are performed, and hence that
         no data is buffered.

         If a value '0' is specified for any of the objects
         tmnxRadSrvPlcyAcctStopMinItvl, tmnxRadSrvPlcyAcctStopMaxItvl, or
         tmnxRadSrvPlcyAcctInterimlifetim, then all 3 objects will be set to
         '0' by the system."
    DEFVAL      { 0 }
    ::= { tmnxRadSrvPlcyEntry 117 }

tmnxRadSrvPlcyPythonPolicy       OBJECT-TYPE
    SYNTAX      TNamedItemOrEmpty
    MAX-ACCESS  read-create
    STATUS      current
    DESCRIPTION
        "The value of tmnxRadSrvPlcyPythonPolicy specifies the Python policy
         used to change the RADIUS attributes of the different RADIUS messages.

         This object replaces the tmnxRadSrvPlcyRequestScriptPlcy,
         tmnxRadSrvPlcyAcceptScriptPlcy, tmnxRadSrvPlcyAcctReqScriptPlcy and
         tmnxRadSrvPlcyAuthReqScriptPlcy objects.

         A nonzero value must correspond to a row in the
         TIMETRA-PYTHON-MIB::tmnxPythonPolicyTable."
    DEFVAL      { "" }
    ::= { tmnxRadSrvPlcyEntry 118 }

tmnxRadSrvPlcyIpv6SrcAddrType    OBJECT-TYPE
    SYNTAX      InetAddressType
    MAX-ACCESS  read-create
    STATUS      current
    DESCRIPTION
        "The value of tmnxRadSrvPlcyIpv6SrcAddrType specifies the type of
         address stored in tmnxRadSrvPlcyIpv6SrcAddr."
    DEFVAL      { unknown }
    ::= { tmnxRadSrvPlcyEntry 119 }

tmnxRadSrvPlcyIpv6SrcAddr        OBJECT-TYPE
    SYNTAX      InetAddress (SIZE (0|16))
    MAX-ACCESS  read-create
    STATUS      current
    DESCRIPTION
        "The value of tmnxRadSrvPlcyIpv6SrcAddr specifies the IPv6 source
         addresses while transmitting RADIUS protocol messages to one of the
         RADIUS servers; it must be a valid unicast address."
    DEFVAL      { ''H }
    ::= { tmnxRadSrvPlcyEntry 120 }

tmnxRadSrvPlcyServerDownTimeout  OBJECT-TYPE
    SYNTAX      Unsigned32 (0 | 1..340)
    UNITS       "seconds"
    MAX-ACCESS  read-create
    STATUS      current
    DESCRIPTION
        "The value of tmnxRadSrvPlcyServerDownTimeout specifies, in seconds,
         the timeout after a which an unresponsive RADIUS server is declared
         'outOfService'.

         A value of '0' indicates that the system will generate a timeout value
         itself."
    DEFVAL      { 0 }
    ::= { tmnxRadSrvPlcyEntry 121 }

tmnxRadSrvPlcyTestAccntChecking  OBJECT-TYPE
    SYNTAX      TmnxEnabledDisabled
    MAX-ACCESS  read-create
    STATUS      current
    DESCRIPTION
        "The value of tmnxRadSrvPlcyTestAccntChecking specifies if periodic
         checking for the operational state of the RADIUS servers configured in
         tmnxRadSrvPlcySrvTable will be done.

         Checking will be done via the generation of a dummy RADIUS
         Access-Request including a User-Name and Password attribute set with
         respectively tmnxRadSrvPlcyTestAccntUserName and
         tmnxRadSrvPlcyTestAccntPassword. If not set, the system will generate
         the content for the User-Name and/or Password attribute itself. The
         interval at which these requests will be sent is defined with
         tmnxRadSrvPlcyTestAccntIvl."
    DEFVAL      { disabled }
    ::= { tmnxRadSrvPlcyEntry 122 }

tmnxRadSrvPlcyTestAccntIvl       OBJECT-TYPE
    SYNTAX      Unsigned32 (1..60)
    UNITS       "seconds"
    MAX-ACCESS  read-create
    STATUS      current
    DESCRIPTION
        "The value of tmnxRadSrvPlcyTestAccntIvl specifies the interval used to
         periodically check the operational state of the RADIUS servers
         configured in tmnxRadSrvPlcySrvTable."
    DEFVAL      { 3 }
    ::= { tmnxRadSrvPlcyEntry 123 }

tmnxRadSrvPlcyTestAccntUserName  OBJECT-TYPE
    SYNTAX      DisplayString (SIZE (0..64))
    MAX-ACCESS  read-create
    STATUS      current
    DESCRIPTION
        "The value of tmnxRadSrvPlcyTestAccntUserName specifies the content of
         the User-Name attribute when periodically performing health-checking
         of the RADIUS servers.

         If tmnxRadSrvPlcyTestAccntUserName is set to the empty string, the
         system will generate a user-name itself."
    DEFVAL      { ''H }
    ::= { tmnxRadSrvPlcyEntry 124 }

tmnxRadSrvPlcyTestAccntPassword  OBJECT-TYPE
    SYNTAX      TmnxAuthPassword
    MAX-ACCESS  read-create
    STATUS      current
    DESCRIPTION
        "The value of tmnxRadSrvPlcyTestAccntPassword specifies the content of
         the Password attribute when periodically performing health-checking of
         the RADIUS servers.

         If tmnxRadSrvPlcyTestAccntPassword is set to the empty string, the
         system will generate a password itself."
    DEFVAL      { ''H }
    ::= { tmnxRadSrvPlcyEntry 125 }

tmnxRadSrvPlcyDisableStickiness  OBJECT-TYPE
    SYNTAX      TruthValue
    MAX-ACCESS  read-create
    STATUS      current
    DESCRIPTION
        "In a multi-server application, the value of
         tmnxRadSrvPlcyDisableStickiness specifies the subsequent packets to be
         sent to the same host as the first packet was sent to. In case
         tmnxRadSrvPlcyDisableStickiness is true, this behavior is disabled."
    DEFVAL      { false }
    ::= { tmnxRadSrvPlcyEntry 126 }

tmnxRadSrvPlcyAcctStartMinItvl   OBJECT-TYPE
    SYNTAX      Unsigned32 (0..3600)
    UNITS       "seconds"
    MAX-ACCESS  read-create
    STATUS      current
    DESCRIPTION
        "The value of tmnxRadSrvPlcyAcctStartMinItvl specifies the minimum
         interval (in seconds) between retries to send the RADIUS accounting
         start message.

         The value '0' specifies that no retries are performed.

         The value specified must be less then or equal to the value specified
         for the object tmnxRadSrvPlcyAcctStartMaxItvl.

         If a value '0' is specified for any of the objects
         tmnxRadSrvPlcyAcctStartMinItvl, tmnxRadSrvPlcyAcctStartMaxItvl, or
         tmnxRadSrvPlcyAcctStartlifetim, then all 3 objects will be set to '0'
         by the system."
    DEFVAL      { 0 }
    ::= { tmnxRadSrvPlcyEntry 127 }

tmnxRadSrvPlcyAcctStartMaxItvl   OBJECT-TYPE
    SYNTAX      Unsigned32 (0..3600)
    UNITS       "seconds"
    MAX-ACCESS  read-create
    STATUS      current
    DESCRIPTION
        "The value of tmnxRadSrvPlcyAcctStartMaxItvl specifies the maximum
         interval (in seconds) between retries to send the RADIUS accounting
         start message.

         The value '0' specifies that no retries are performed.

         The value specified must be bigger then or equal to the value
         specified for the object tmnxRadSrvPlcyAcctStartMinItvl.

         If a value '0' is specified for any of the objects
         tmnxRadSrvPlcyAcctStartMinItvl, tmnxRadSrvPlcyAcctStartMaxItvl, or
         tmnxRadSrvPlcyAcctStartlifetim, then all 3 objects will be set to '0'
         by the system."
    DEFVAL      { 0 }
    ::= { tmnxRadSrvPlcyEntry 128 }

tmnxRadSrvPlcyAcctStartlifetim   OBJECT-TYPE
    SYNTAX      Unsigned32 (0..25)
    UNITS       "hours"
    MAX-ACCESS  read-create
    STATUS      current
    DESCRIPTION
        "The value of tmnxRadSrvPlcyAcctStartlifetim specifies the time (in
         hours) an accounting message can be in the retransmission buffer.

         The value '0' specifies that no retries are performed, and hence that
         no data is buffered.

         If a value '0' is specified for any of the objects
         tmnxRadSrvPlcyAcctStartMinItvl, tmnxRadSrvPlcyAcctStartMaxItvl, or
         tmnxRadSrvPlcyAcctInterimlifetim, then all 3 objects will be set to
         '0' by the system."
    DEFVAL      { 0 }
    ::= { tmnxRadSrvPlcyEntry 129 }

tmnxRadSrvPlcyStatsTable         OBJECT-TYPE
    SYNTAX      SEQUENCE OF TmnxRadSrvPlcyStatsEntry
    MAX-ACCESS  not-accessible
    STATUS      current
    DESCRIPTION
        "The tmnxRadSrvPlcyStatsTable presents statistics of RADIUS server
         policies."
    ::= { tmnxRadSrvObjs 3 }

tmnxRadSrvPlcyStatsEntry         OBJECT-TYPE
    SYNTAX      TmnxRadSrvPlcyStatsEntry
    MAX-ACCESS  not-accessible
    STATUS      current
    DESCRIPTION
        "Each row represents statistics about a specific RADIUS server policy.

         Rows in this table are created automatically by the system."
    AUGMENTS    { tmnxRadSrvPlcyEntry }
    ::= { tmnxRadSrvPlcyStatsTable 1 }

TmnxRadSrvPlcyStatsEntry         ::= SEQUENCE
{
    tmnxRadSrvPlcyStatsTxRequests    Counter32,
    tmnxRadSrvPlcyStatsRxResponses   Counter32,
    tmnxRadSrvPlcyStatsReqTimeout    Counter32,
    tmnxRadSrvPlcyStatsReqSendFail   Counter32,
    tmnxRadSrvPlcyStatsReqSendRetry  Counter32,
    tmnxRadSrvPlcyStatsReqRejected   Counter32,
    tmnxRadSrvPlcyStatsAuthFailed    Counter32,
    tmnxRadSrvPlcyStatsRejectRatio   Unsigned32,
    tmnxRadSrvPlcyStatsAcctFailed    Counter32,
    tmnxRadSrvPlcyStatsSuccessRatio  Unsigned32,
    tmnxRadSrvPlcyStatsFailureRatio  Unsigned32
}

tmnxRadSrvPlcyStatsTxRequests    OBJECT-TYPE
    SYNTAX      Counter32
    MAX-ACCESS  read-only
    STATUS      current
    DESCRIPTION
        "The value of tmnxRadSrvPlcyStatsTxRequests indicates the number of
         RADIUS transaction requests transmitted."
    ::= { tmnxRadSrvPlcyStatsEntry 1 }

tmnxRadSrvPlcyStatsRxResponses   OBJECT-TYPE
    SYNTAX      Counter32
    MAX-ACCESS  read-only
    STATUS      current
    DESCRIPTION
        "The value of tmnxRadSrvPlcyStatsRxResponses indicates the number of
         RADIUS transaction responses received."
    ::= { tmnxRadSrvPlcyStatsEntry 2 }

tmnxRadSrvPlcyStatsReqTimeout    OBJECT-TYPE
    SYNTAX      Counter32
    MAX-ACCESS  read-only
    STATUS      current
    DESCRIPTION
        "The value of tmnxRadSrvPlcyStatsReqTimeout indicates the number of
         RADIUS transaction requests that have timed out."
    ::= { tmnxRadSrvPlcyStatsEntry 3 }

tmnxRadSrvPlcyStatsReqSendFail   OBJECT-TYPE
    SYNTAX      Counter32
    MAX-ACCESS  read-only
    STATUS      current
    DESCRIPTION
        "The value of tmnxRadSrvPlcyStatsReqSendFail indicates the number of
         RADIUS transaction requests that could not be transmitted."
    ::= { tmnxRadSrvPlcyStatsEntry 4 }

tmnxRadSrvPlcyStatsReqSendRetry  OBJECT-TYPE
    SYNTAX      Counter32
    MAX-ACCESS  read-only
    STATUS      current
    DESCRIPTION
        "The value of tmnxRadSrvPlcyStatsReqSendRetry indicates the number of
         times a RADIUS request packet was retransmitted to a server."
    ::= { tmnxRadSrvPlcyStatsEntry 5 }

tmnxRadSrvPlcyStatsReqRejected   OBJECT-TYPE
    SYNTAX      Counter32
    MAX-ACCESS  read-only
    STATUS      current
    DESCRIPTION
        "The value of tmnxRadSrvPlcyStatsReqRejected indicates the number of
         RADIUS transaction requests that were not transmitted due to
         unacceptable configuration."
    ::= { tmnxRadSrvPlcyStatsEntry 6 }

tmnxRadSrvPlcyStatsAuthFailed    OBJECT-TYPE
    SYNTAX      Counter32
    MAX-ACCESS  read-only
    STATUS      current
    DESCRIPTION
        "The value of tmnxRadSrvPlcyStatsAuthFailed indicates the number of
         authentication failures for this policy."
    ::= { tmnxRadSrvPlcyStatsEntry 7 }

tmnxRadSrvPlcyStatsRejectRatio   OBJECT-TYPE
    SYNTAX      Unsigned32 (0..100)
    MAX-ACCESS  read-only
    STATUS      current
    DESCRIPTION
        "The value of tmnxRadSrvPlcyStatsRejectRatio indicates the ratio of
         access-rejects in the auth responses for this policy."
    ::= { tmnxRadSrvPlcyStatsEntry 8 }

tmnxRadSrvPlcyStatsAcctFailed    OBJECT-TYPE
    SYNTAX      Counter32
    MAX-ACCESS  read-only
    STATUS      current
    DESCRIPTION
        "The value of tmnxRadSrvPlcyStatsAcctFailed indicates the number of
         accounting failures for this policy."
    ::= { tmnxRadSrvPlcyStatsEntry 9 }

tmnxRadSrvPlcyStatsSuccessRatio  OBJECT-TYPE
    SYNTAX      Unsigned32 (0..100)
    MAX-ACCESS  read-only
    STATUS      current
    DESCRIPTION
        "The value of tmnxRadSrvPlcyStatsSuccessRatio indicates the transaction
         success ratio for this policy."
    ::= { tmnxRadSrvPlcyStatsEntry 10 }

tmnxRadSrvPlcyStatsFailureRatio  OBJECT-TYPE
    SYNTAX      Unsigned32 (0..100)
    MAX-ACCESS  read-only
    STATUS      current
    DESCRIPTION
        "The value of tmnxRadSrvPlcyStatsFailureRatio indicates the transaction
         failure ratio for this policy."
    ::= { tmnxRadSrvPlcyStatsEntry 11 }

tmnxRadSrvPlcySrvTable           OBJECT-TYPE
    SYNTAX      SEQUENCE OF TmnxRadSrvPlcySrvEntry
    MAX-ACCESS  not-accessible
    STATUS      current
    DESCRIPTION
        "The tmnxRadSrvPlcySrvTable allows the configuration of the association
         between the RADIUS servers policies and the RADIUS servers."
    ::= { tmnxRadSrvObjs 4 }

tmnxRadSrvPlcySrvEntry           OBJECT-TYPE
    SYNTAX      TmnxRadSrvPlcySrvEntry
    MAX-ACCESS  not-accessible
    STATUS      current
    DESCRIPTION
        "Each entry represents the association between an RADIUS servers policy
         and a RADIUS server in tmnxRadServTable.

         Rows in this table can be created and deleted via SNMP SET operations
         to tmnxRadSrvPlcySrvRowStatus."
    INDEX       {
        tmnxRadSrvPlcyName,
        tmnxRadSrvPlcySrvIndex
    }
    ::= { tmnxRadSrvPlcySrvTable 1 }

TmnxRadSrvPlcySrvEntry           ::= SEQUENCE
{
    tmnxRadSrvPlcySrvIndex           Unsigned32,
    tmnxRadSrvPlcySrvRowStatus       RowStatus,
    tmnxRadSrvPlcySrvLastCh          TimeStamp,
    tmnxRadSrvPlcySrvName            TNamedItem,
    tmnxRadSrvPlcySrvOperState       TmnxRadiusServerOperState,
    tmnxRadSrvPlcySrvOutTime         Counter32,
    tmnxRadSrvPlcySrvOvrldTime       Counter32
}

tmnxRadSrvPlcySrvIndex           OBJECT-TYPE
    SYNTAX      Unsigned32 (1..16)
    MAX-ACCESS  not-accessible
    STATUS      current
    DESCRIPTION
        "The value of tmnxRadSrvPlcySrvIndex specifies the rank order of the
         RADIUS server associated with this row."
    ::= { tmnxRadSrvPlcySrvEntry 1 }

tmnxRadSrvPlcySrvRowStatus       OBJECT-TYPE
    SYNTAX      RowStatus
    MAX-ACCESS  read-create
    STATUS      current
    DESCRIPTION
        "The value of tmnxRadSrvPlcySrvRowStatus controls the creation and
         deletion of rows in the table."
    ::= { tmnxRadSrvPlcySrvEntry 2 }

tmnxRadSrvPlcySrvLastCh          OBJECT-TYPE
    SYNTAX      TimeStamp
    MAX-ACCESS  read-only
    STATUS      current
    DESCRIPTION
        "The value tmnxRadSrvPlcySrvLastCh indicates the sysUpTime at the time
         of the most recent management-initiated change to this policy server."
    ::= { tmnxRadSrvPlcySrvEntry 3 }

tmnxRadSrvPlcySrvName            OBJECT-TYPE
    SYNTAX      TNamedItem
    MAX-ACCESS  read-create
    STATUS      current
    DESCRIPTION
        "The value of tmnxRadSrvPlcySrvName specifies the name of the RADIUS
         server in the tmnxRadServTable associated with this RADIUS Server
         policy.

         The virtual router instance of that RADIUS server is the value of the
         object tmnxRadSrvPlcyRouter.

         A row in this table can only be created if a conceptual row with this
         name and this virtual router instance exists in the tmnxRadServTable.

         A value for this object must be specified when the row is created."
    ::= { tmnxRadSrvPlcySrvEntry 4 }

tmnxRadSrvPlcySrvOperState       OBJECT-TYPE
    SYNTAX      TmnxRadiusServerOperState
    MAX-ACCESS  read-only
    STATUS      current
    DESCRIPTION
        "The value of tmnxRadSrvPlcySrvOperState indicates the operational
         state of this policy server."
    ::= { tmnxRadSrvPlcySrvEntry 5 }

tmnxRadSrvPlcySrvOutTime         OBJECT-TYPE
    SYNTAX      Counter32
    UNITS       "seconds"
    MAX-ACCESS  read-only
    STATUS      current
    DESCRIPTION
        "The value of tmnxRadSrvPlcySrvOutTime indicates the accumulated time
         that the value of the object tmnxRadSrvPlcySrvOperState has been equal
         to 'outOfService' since this row was created."
    ::= { tmnxRadSrvPlcySrvEntry 6 }

tmnxRadSrvPlcySrvOvrldTime       OBJECT-TYPE
    SYNTAX      Counter32
    UNITS       "seconds"
    MAX-ACCESS  read-only
    STATUS      current
    DESCRIPTION
        "The value of tmnxRadSrvPlcySrvOvrldTime indicates the accumulated time
         that the value of the object tmnxRadSrvPlcySrvOperState has been equal
         to 'overloaded' since this row was created."
    ::= { tmnxRadSrvPlcySrvEntry 7 }

tmnxRadSrvStatsTable             OBJECT-TYPE
    SYNTAX      SEQUENCE OF TmnxRadSrvStatsEntry
    MAX-ACCESS  not-accessible
    STATUS      current
    DESCRIPTION
        "The tmnxRadSrvStatsTable presents statistics of
         RADIUS-server-policies' RADIUS servers."
    ::= { tmnxRadSrvObjs 5 }

tmnxRadSrvStatsEntry             OBJECT-TYPE
    SYNTAX      TmnxRadSrvStatsEntry
    MAX-ACCESS  not-accessible
    STATUS      current
    DESCRIPTION
        "Each row represents statistics about a specific server of a specific
         RADIUS server policy.

         Rows in this table are created automatically by the system."
    AUGMENTS    { tmnxRadSrvPlcySrvEntry }
    ::= { tmnxRadSrvStatsTable 1 }

TmnxRadSrvStatsEntry             ::= SEQUENCE
{
    tmnxRadSrvStatsTxRequests        Counter32,
    tmnxRadSrvStatsRxResponses       Counter32,
    tmnxRadSrvStatsReqTimeout        Counter32,
    tmnxRadSrvStatsReqSendFailure    Counter32,
    tmnxRadSrvStatsReqOvrldSendFail  Counter32,
    tmnxRadSrvStatsReqPending        Counter32,
    tmnxRadSrvStatsRespInvAuth       Counter32,
    tmnxRadSrvStatsRespInvMsgAuth    Counter32,
    tmnxRadSrvStatsAuthFailed        Counter32,
    tmnxRadSrvStatsAcctFailed        Counter32,
    tmnxRadSrvStatsAuthAvgDelay10    Gauge32,
    tmnxRadSrvStatsAuthAvgDelay100   Gauge32,
    tmnxRadSrvStatsAuthAvgDelay1000  Gauge32,
    tmnxRadSrvStatsAuthAvgDelay10000 Gauge32,
    tmnxRadSrvStatsAcctAvgDelay10    Gauge32,
    tmnxRadSrvStatsAcctAvgDelay100   Gauge32,
    tmnxRadSrvStatsAcctAvgDelay1000  Gauge32,
    tmnxRadSrvStatsAcctAvgDelay10000 Gauge32
}

tmnxRadSrvStatsTxRequests        OBJECT-TYPE
    SYNTAX      Counter32
    MAX-ACCESS  read-only
    STATUS      current
    DESCRIPTION
        "The value of tmnxRadSrvStatsTxRequests indicates the number of RADIUS
         request packets transmitted for this server."
    ::= { tmnxRadSrvStatsEntry 1 }

tmnxRadSrvStatsRxResponses       OBJECT-TYPE
    SYNTAX      Counter32
    MAX-ACCESS  read-only
    STATUS      current
    DESCRIPTION
        "The value of tmnxRadSrvStatsRxResponses indicates the number of RADIUS
         response packets received from this server."
    ::= { tmnxRadSrvStatsEntry 2 }

tmnxRadSrvStatsReqTimeout        OBJECT-TYPE
    SYNTAX      Counter32
    MAX-ACCESS  read-only
    STATUS      current
    DESCRIPTION
        "The value of tmnxRadSrvStatsReqTimeout indicates the number of RADIUS
         request packets that have timed out for this server."
    ::= { tmnxRadSrvStatsEntry 3 }

tmnxRadSrvStatsReqSendFailure    OBJECT-TYPE
    SYNTAX      Counter32
    MAX-ACCESS  read-only
    STATUS      current
    DESCRIPTION
        "The value of tmnxRadSrvStatsReqSendFailure indicates the number of
         RADIUS request packets that could not be transmitted for this server."
    ::= { tmnxRadSrvStatsEntry 4 }

tmnxRadSrvStatsReqOvrldSendFail  OBJECT-TYPE
    SYNTAX      Counter32
    MAX-ACCESS  read-only
    STATUS      current
    DESCRIPTION
        "The value of tmnxRadSrvStatsReqOvrldSendFail indicates the number of
         RADIUS request packets that could not be transmitted while the RADIUS
         server was in overload."
    ::= { tmnxRadSrvStatsEntry 5 }

tmnxRadSrvStatsReqPending        OBJECT-TYPE
    SYNTAX      Counter32
    MAX-ACCESS  read-only
    STATUS      current
    DESCRIPTION
        "The value of tmnxRadSrvStatsReqPending indicates the number of RADIUS
         request packets that are currently waiting for reply from this server."
    ::= { tmnxRadSrvStatsEntry 6 }

tmnxRadSrvStatsRespInvAuth       OBJECT-TYPE
    SYNTAX      Counter32
    MAX-ACCESS  read-only
    STATUS      current
    DESCRIPTION
        "The value of tmnxRadSrvStatsRespInvAuth indicates the number of RADIUS
         response packets with an invalid Authenticator received from this
         server."
    ::= { tmnxRadSrvStatsEntry 7 }

tmnxRadSrvStatsRespInvMsgAuth    OBJECT-TYPE
    SYNTAX      Counter32
    MAX-ACCESS  read-only
    STATUS      current
    DESCRIPTION
        "The value of tmnxRadSrvStatsRespInvMsgAuth indicates the number of
         RADIUS response packets with an invalid Message-Authenticator
         attribute received from this server."
    REFERENCE
        "RFC 2869 RADIUS Extensions
         section 5.14 Message-Authenticator."
    ::= { tmnxRadSrvStatsEntry 8 }

tmnxRadSrvStatsAuthFailed        OBJECT-TYPE
    SYNTAX      Counter32
    MAX-ACCESS  read-only
    STATUS      current
    DESCRIPTION
        "The value of tmnxRadSrvStatsAuthFailed indicates the number of
         authentication failures for this server."
    ::= { tmnxRadSrvStatsEntry 9 }

tmnxRadSrvStatsAcctFailed        OBJECT-TYPE
    SYNTAX      Counter32
    MAX-ACCESS  read-only
    STATUS      current
    DESCRIPTION
        "The value of tmnxRadSrvStatsAcctFailed indicates the number of
         accounting failures for this server."
    ::= { tmnxRadSrvStatsEntry 10 }

tmnxRadSrvStatsAuthAvgDelay10    OBJECT-TYPE
    SYNTAX      Gauge32
    MAX-ACCESS  read-only
    STATUS      current
    DESCRIPTION
        "The value of tmnxRadSrvStatsAuthAvgDelay10 indicates in microseconds,
         the average response delay for the last 10 authentication packets."
    ::= { tmnxRadSrvStatsEntry 11 }

tmnxRadSrvStatsAuthAvgDelay100   OBJECT-TYPE
    SYNTAX      Gauge32
    MAX-ACCESS  read-only
    STATUS      current
    DESCRIPTION
        "The value of tmnxRadSrvStatsAuthAvgDelay100 indicates in microseconds,
         the average response delay for the last 100 authentication packets."
    ::= { tmnxRadSrvStatsEntry 12 }

tmnxRadSrvStatsAuthAvgDelay1000  OBJECT-TYPE
    SYNTAX      Gauge32
    MAX-ACCESS  read-only
    STATUS      current
    DESCRIPTION
        "The value of tmnxRadSrvStatsAuthAvgDelay1000 indicates in
         microseconds, the average response delay for the last 1000
         authentication packets."
    ::= { tmnxRadSrvStatsEntry 13 }

tmnxRadSrvStatsAuthAvgDelay10000 OBJECT-TYPE
    SYNTAX      Gauge32
    MAX-ACCESS  read-only
    STATUS      current
    DESCRIPTION
        "The value of tmnxRadSrvStatsAuthAvgDelay10000 indicates in
         microseconds, the average response delay for the last 10000
         authentication packets."
    ::= { tmnxRadSrvStatsEntry 14 }

tmnxRadSrvStatsAcctAvgDelay10    OBJECT-TYPE
    SYNTAX      Gauge32
    MAX-ACCESS  read-only
    STATUS      current
    DESCRIPTION
        "The value of tmnxRadSrvStatsAcctAvgDelay10 indicates in microseconds,
         the average response delay for the last 10 accounting packets."
    ::= { tmnxRadSrvStatsEntry 15 }

tmnxRadSrvStatsAcctAvgDelay100   OBJECT-TYPE
    SYNTAX      Gauge32
    MAX-ACCESS  read-only
    STATUS      current
    DESCRIPTION
        "The value of tmnxRadSrvStatsAcctAvgDelay100 indicates in microseconds,
         the average response delay for the last 100 accounting packets."
    ::= { tmnxRadSrvStatsEntry 16 }

tmnxRadSrvStatsAcctAvgDelay1000  OBJECT-TYPE
    SYNTAX      Gauge32
    MAX-ACCESS  read-only
    STATUS      current
    DESCRIPTION
        "The value of tmnxRadSrvStatsAcctAvgDelay1000 indicates in
         microseconds, the average response delay for the last 1000 accounting
         packets."
    ::= { tmnxRadSrvStatsEntry 17 }

tmnxRadSrvStatsAcctAvgDelay10000 OBJECT-TYPE
    SYNTAX      Gauge32
    MAX-ACCESS  read-only
    STATUS      current
    DESCRIPTION
        "The value of tmnxRadSrvStatsAcctAvgDelay10000 indicates in
         microseconds, the average response delay for the last 10000 accounting
         packets."
    ::= { tmnxRadSrvStatsEntry 18 }

tmnxRadSrvPlcyAcctOnOffTable     OBJECT-TYPE
    SYNTAX      SEQUENCE OF TmnxRadSrvPlcyAcctOnOffEntry
    MAX-ACCESS  not-accessible
    STATUS      current
    DESCRIPTION
        "The tmnxRadSrvPlcyAcctOnOffTable contains the data needed to control
         the sending of the Accounting-On and Accounting-Off RADIUS messages of
         any RADIUS server policy."
    ::= { tmnxRadSrvObjs 6 }

tmnxRadSrvPlcyAcctOnOffEntry     OBJECT-TYPE
    SYNTAX      TmnxRadSrvPlcyAcctOnOffEntry
    MAX-ACCESS  not-accessible
    STATUS      current
    DESCRIPTION
        "Each row contains the data needed to control the sending of the
         Accounting-On and Accounting-Off RADIUS messages for a particular
         RADIUS server policy."
    AUGMENTS    { tmnxRadSrvPlcyEntry }
    ::= { tmnxRadSrvPlcyAcctOnOffTable 1 }

TmnxRadSrvPlcyAcctOnOffEntry     ::= SEQUENCE
{
    tmnxRadSrvPlcyAcctLastChange     TimeStamp,
    tmnxRadSrvPlcyAcctOnOffAdminSt   INTEGER,
    tmnxRadSrvPlcyAcctOnOffOperState INTEGER,
    tmnxRadSrvPlcyAcctOnOffSessionId DisplayString,
    tmnxRadSrvPlcyAcctOnOffStateChng TimeStamp,
    tmnxRadSrvPlcyAcctPerformAction  INTEGER,
    tmnxRadSrvPlcyAcctmAcctOffCause  Unsigned32,
    tmnxRadSrvPlcyAcctOnOffTrigger   INTEGER,
    tmnxRadSrvPlcyAcctOnOffSrvName   TNamedItemOrEmpty,
    tmnxRadSrvPlcyAcctOnOffGroup     TNamedItemOrEmpty,
    tmnxRadSrvPlcyAcctOnOffRetryCnt  Unsigned32
}

tmnxRadSrvPlcyAcctLastChange     OBJECT-TYPE
    SYNTAX      TimeStamp
    MAX-ACCESS  read-only
    STATUS      current
    DESCRIPTION
        "The value of tmnxRadSrvPlcyAcctLastChange indicates the sysUpTime at
         the time of the most recent management-initiated change to this table
         row."
    ::= { tmnxRadSrvPlcyAcctOnOffEntry 1 }

tmnxRadSrvPlcyAcctOnOffAdminSt   OBJECT-TYPE
    SYNTAX      INTEGER {
        disabled           (0),
        enabled            (1),
        enabledStateChange (2),
        enabledMonitoring  (3)
    }
    MAX-ACCESS  read-write
    STATUS      current
    DESCRIPTION
        "The value of tmnxRadSrvPlcyAcctOnOffAdminSt specifies the admin state
         of the acct-on-off feature.
         disabled:
            The sending of the RADIUS Accounting-On and Accounting-Off messages
            is not active for this RADIUS server policy.

         enabled:
            The sending of the RADIUS Accounting-On and Accounting-Off messages
            is active for this RADIUS server policy.

         enabledStateChange:
            The sending of the RADIUS Accounting-On and Accounting-Off messages
            is active for this RADIUS server policy. In addition, all RADIUS
            messages will be discarded until the reply on the  Accounting-On is
            received whereafter RADIUS messages for this Radius Server Policy and
            for the Radius Server Policies belonging to the Radius Server Policy
            Group as specified in tmnxRadSrvPlcyAcctOnOffGroup are allowed to
            pass.

         enabledMonitoring:
            The sending of the RADIUS Accounting-On and Accounting-Off messages
            is active. In addition, all RADIUS messages will be discarded until
            the reply on the Accounting-On is received for the group
            as specified in tmnxRadSrvPlcyAcctOnOffGroup."
    DEFVAL      { disabled }
    ::= { tmnxRadSrvPlcyAcctOnOffEntry 2 }

tmnxRadSrvPlcyAcctOnOffOperState OBJECT-TYPE
    SYNTAX      INTEGER {
        notApplicable  (0),
        off            (1),
        offNoResponse  (2),
        on             (3),
        sendingAcctOn  (4),
        sendingAcctOff (5)
    }
    MAX-ACCESS  read-only
    STATUS      current
    DESCRIPTION
        "The value of tmnxRadSrvPlcyAcctOnOffOperState indicates the
         operational state related to the sending of RADIUS Accounting-On and
         Accounting-Off messages for this RADIUS server policy."
    ::= { tmnxRadSrvPlcyAcctOnOffEntry 3 }

tmnxRadSrvPlcyAcctOnOffSessionId OBJECT-TYPE
    SYNTAX      DisplayString
    MAX-ACCESS  read-only
    STATUS      current
    DESCRIPTION
        "The value of tmnxRadSrvPlcyAcctOnOffSessionId indicates the accounting
         session id used in the RADIUS Accounting-On and Accounting-Off
         messages sent for this RADIUS server policy."
    ::= { tmnxRadSrvPlcyAcctOnOffEntry 4 }

tmnxRadSrvPlcyAcctOnOffStateChng OBJECT-TYPE
    SYNTAX      TimeStamp
    MAX-ACCESS  read-only
    STATUS      current
    DESCRIPTION
        "The value of tmnxRadSrvPlcyAcctOnOffStateChng indicates the sysUpTime
         time of the last state change."
    ::= { tmnxRadSrvPlcyAcctOnOffEntry 5 }

tmnxRadSrvPlcyAcctPerformAction  OBJECT-TYPE
    SYNTAX      INTEGER {
        none         (0),
        acctOn       (1),
        acctOnForce  (2),
        acctOff      (3),
        acctOffForce (4)
    }
    MAX-ACCESS  read-write
    STATUS      current
    DESCRIPTION
        "The value of tmnxRadSrvPlcyAcctPerformAction is used to specify an
         action to be performed towards RADIUS for this RADIUS server policy.

         The object will return the value none '0' on any GET request.

         Setting the value to a non zero value will be rejected if the value of
         the object tmnxRadSrvPlcyAcctOnOffAdminSt is set to disabled, or
         whenever a transaction is in progress.

         - acctOn       '1' : the system will send a RADIUS Accounting-On
                              message,
                              unless the last successful event sent was an
                              Accounting-On message.
         - acctOnForce  '2  : the system will send a RADIUS Accounting-On message,
                              regardless of which event was last sent.
         - acctOff      '3  : the system will send a RADIUS Accounting-Off message,
                              unless the last successful event sent was an
                              Accounting-Off message.
         - acctOffForce '4' : the system will send a RADIUS Accounting-Off
                              message,
                              regardless of which event was last sent.
         When sending an RADIUS Accounting-Off message the Acct-Terminate-Cause
         used is taken from tmnxRadSrvPlcyAcctmAcctOffCause."
    DEFVAL      { none }
    ::= { tmnxRadSrvPlcyAcctOnOffEntry 6 }

tmnxRadSrvPlcyAcctmAcctOffCause  OBJECT-TYPE
    SYNTAX      Unsigned32 (1..4294967295)
    MAX-ACCESS  read-write
    STATUS      current
    DESCRIPTION
        "The value of tmnxRadSrvPlcyAcctmAcctOffCause specifies the
         Acct-Terminate-Cause that will be used in the RADIUS Accounting-Off
         message sent after manipulating the object
         tmnxRadSrvPlcyAcctPerformAction.

         The default cause assumed by the system is User-Request '1' (according
         to RFC 2866).

         A value different from '1' can be provided only if the admin state
         tmnxRadSrvPlcyAcctOnOffAdminSt is not set to 'disabled'. If not the
         value will be set to '1' by the system, and any attempt to change it
         will be ignored."
    DEFVAL      { 1 }
    ::= { tmnxRadSrvPlcyAcctOnOffEntry 7 }

tmnxRadSrvPlcyAcctOnOffTrigger   OBJECT-TYPE
    SYNTAX      INTEGER {
        notApplicable (0),
        startUp       (1),
        tools         (2),
        toolsForced   (3),
        reboot        (4),
        group         (5)
    }
    MAX-ACCESS  read-only
    STATUS      current
    DESCRIPTION
        "The value of tmnxRadSrvPlcyAcctOnOffTrigger indicates the event that
         caused the most recent operational state change as defined in
         tmnxRadSrvPlcyAcctOnOffOperState."
    ::= { tmnxRadSrvPlcyAcctOnOffEntry 8 }

tmnxRadSrvPlcyAcctOnOffSrvName   OBJECT-TYPE
    SYNTAX      TNamedItemOrEmpty
    MAX-ACCESS  read-only
    STATUS      current
    DESCRIPTION
        "The value of tmnxRadSrvPlcyAcctOnOffSrvName indicates the name of the
         RADIUS server from which the most recent RADIUS response has been
         received."
    ::= { tmnxRadSrvPlcyAcctOnOffEntry 9 }

tmnxRadSrvPlcyAcctOnOffGroup     OBJECT-TYPE
    SYNTAX      TNamedItemOrEmpty
    MAX-ACCESS  read-write
    STATUS      current
    DESCRIPTION
        "The value of tmnxRadSrvPlcyAcctOnOffGroup specifies the name of a
         RADIUS server policy Accounting-On-Off-Group.

         A non zero value is only allowed in case the object
         tmnxRadSrvPlcyAcctOnOffOperState is set to 'enabledStateChange' (in
         which case a non-zero value is optional), or 'enabledMonitoring' (in
         which case a non-zero value is mandatory)."
    DEFVAL      { "" }
    ::= { tmnxRadSrvPlcyAcctOnOffEntry 10 }

tmnxRadSrvPlcyAcctOnOffRetryCnt  OBJECT-TYPE
    SYNTAX      Unsigned32
    MAX-ACCESS  read-only
    STATUS      current
    DESCRIPTION
        "The value of tmnxRadSrvPlcyAcctOnOffRetryCnt indicates the number of
         times the acct-on client has already sent a new RADIUS Accounting-On
         message after no accounting response was received in time.

         The value of this object is meaningful only if the value of the object
         tmnxRadSrvPlcyAcctOnOffOperState is set to 'sendingAcctOn'."
    ::= { tmnxRadSrvPlcyAcctOnOffEntry 11 }

tmnxRadSrvPlcyAcctOnOffGrpTable  OBJECT-TYPE
    SYNTAX      SEQUENCE OF TmnxRadSrvPlcyAcctOnOffGrpEntry
    MAX-ACCESS  not-accessible
    STATUS      current
    DESCRIPTION
        "The tmnxRadSrvPlcyAcctOnOffGrpTable contains the data needed to create
         RADIUS Accounting-On-Off Groups.

         A RADIUS Accounting-On-Off-Group is referred to from the object
         tmnxRadSrvPlcyAcctOnOffGroup. In this way it groups together a number
         of RADIUS server policies for the handling of the Accounting-On-Off
         feature.

         A row in this table can only be referred to once from withing a RADIUS
         server policy with tmnxRadSrvPlcyAcctOnOffOperState is set to
         'enabledStateChange'. It can in addition be referred to several times
         from within a RADIUS server policy with
         tmnxRadSrvPlcyAcctOnOffOperState is set to 'enabledMonitoring'."
    ::= { tmnxRadSrvObjs 7 }

tmnxRadSrvPlcyAcctOnOffGrpEntry  OBJECT-TYPE
    SYNTAX      TmnxRadSrvPlcyAcctOnOffGrpEntry
    MAX-ACCESS  not-accessible
    STATUS      current
    DESCRIPTION
        "Each row contains the data needed to configure a RADIUS Acct-On-Off
         group."
    INDEX       { tmnxRadSrvPlcyAcctOnOffGrpName }
    ::= { tmnxRadSrvPlcyAcctOnOffGrpTable 1 }

TmnxRadSrvPlcyAcctOnOffGrpEntry  ::= SEQUENCE
{
    tmnxRadSrvPlcyAcctOnOffGrpName   TNamedItem,
    tmnxRadSrvPlcyAcctOnOffGrpRowSt  RowStatus,
    tmnxRadSrvPlcyAcctOnOffGrpLastCh TimeStamp,
    tmnxRadSrvPlcyAcctOnOffGrpDescr  TItemDescription
}

tmnxRadSrvPlcyAcctOnOffGrpName   OBJECT-TYPE
    SYNTAX      TNamedItem
    MAX-ACCESS  not-accessible
    STATUS      current
    DESCRIPTION
        "The value of tmnxRadSrvPlcyAcctOnOffGrpName specifies the name of this
         RADIUS Acct-On-Off group."
    ::= { tmnxRadSrvPlcyAcctOnOffGrpEntry 1 }

tmnxRadSrvPlcyAcctOnOffGrpRowSt  OBJECT-TYPE
    SYNTAX      RowStatus
    MAX-ACCESS  read-create
    STATUS      current
    DESCRIPTION
        "The value of tmnxRadSrvPlcyAcctOnOffGrpRowSt controls the creation and
         deletion of rows in the table."
    ::= { tmnxRadSrvPlcyAcctOnOffGrpEntry 2 }

tmnxRadSrvPlcyAcctOnOffGrpLastCh OBJECT-TYPE
    SYNTAX      TimeStamp
    MAX-ACCESS  read-only
    STATUS      current
    DESCRIPTION
        "The value tmnxRadSrvPlcyAcctOnOffGrpLastCh indicates the sysUpTime at
         the time of the most recent management-initiated change to this row"
    ::= { tmnxRadSrvPlcyAcctOnOffGrpEntry 3 }

tmnxRadSrvPlcyAcctOnOffGrpDescr  OBJECT-TYPE
    SYNTAX      TItemDescription
    MAX-ACCESS  read-create
    STATUS      current
    DESCRIPTION
        "The value of tmnxRadSrvPlcyAcctOnOffGrpDescr specifies the description
         of this RADIUS Acct-On-Off group."
    DEFVAL      { "" }
    ::= { tmnxRadSrvPlcyAcctOnOffGrpEntry 4 }

tmnxRadSrvPlcyMsgBufStatsTable   OBJECT-TYPE
    SYNTAX      SEQUENCE OF TmnxRadSrvPlcyMsgBufStatsEntry
    MAX-ACCESS  not-accessible
    STATUS      current
    DESCRIPTION
        "The tmnxRadSrvPlcyMsgBufStatsTable presents statistics related to the
         RADIUS messages that are buffered for each given Radius Server Policy."
    ::= { tmnxRadSrvObjs 8 }

tmnxRadSrvPlcyMsgBufStatsEntry   OBJECT-TYPE
    SYNTAX      TmnxRadSrvPlcyMsgBufStatsEntry
    MAX-ACCESS  not-accessible
    STATUS      current
    DESCRIPTION
        "Each row represents statistics related to the RADIUS messages that are
         buffered for a given Radius Server Policy.

         Rows in this table are created and removed automatically by the
         system."
    AUGMENTS    { tmnxRadSrvPlcyEntry }
    ::= { tmnxRadSrvPlcyMsgBufStatsTable 1 }

TmnxRadSrvPlcyMsgBufStatsEntry   ::= SEQUENCE
{
    tmnxRadSrvPlcyNbrAcctStopBuf     Counter32,
    tmnxRadSrvPlcyNbrAcctInterimBuf  Counter32,
    tmnxRadSrvPlcyNbrAcctStopDrop    Counter32,
    tmnxRadSrvPlcyNbrAcctInterimDrop Counter32,
    tmnxRadSrvPlcyLastBufClean       TimeStamp,
    tmnxRadSrvPlcyLastBufStatsClean  TimeStamp,
    tmnxRadSrvPlcyNbrAcctStartBuf    Counter32,
    tmnxRadSrvPlcyNbrAcctStartDrop   Counter32
}

tmnxRadSrvPlcyNbrAcctStopBuf     OBJECT-TYPE
    SYNTAX      Counter32
    MAX-ACCESS  read-only
    STATUS      current
    DESCRIPTION
        "The value of tmnxRadSrvPlcyNbrAcctStopBuf indicates the number of
         RADIUS accounting stop messages that are currently buffered for this
         radius server policy."
    ::= { tmnxRadSrvPlcyMsgBufStatsEntry 1 }

tmnxRadSrvPlcyNbrAcctInterimBuf  OBJECT-TYPE
    SYNTAX      Counter32
    MAX-ACCESS  read-only
    STATUS      current
    DESCRIPTION
        "The value of tmnxRadSrvPlcyNbrAcctInterimBuf indicates the number of
         RADIUS accounting interim update messages that are currently buffered
         for this radius server policy."
    ::= { tmnxRadSrvPlcyMsgBufStatsEntry 2 }

tmnxRadSrvPlcyNbrAcctStopDrop    OBJECT-TYPE
    SYNTAX      Counter32
    MAX-ACCESS  read-only
    STATUS      current
    DESCRIPTION
        "The value of tmnxRadSrvPlcyNbrAcctStopDrop indicates the number of
         RADIUS accounting stop messages that were dropped from the buffer
         because their lifetime expired."
    ::= { tmnxRadSrvPlcyMsgBufStatsEntry 3 }

tmnxRadSrvPlcyNbrAcctInterimDrop OBJECT-TYPE
    SYNTAX      Counter32
    MAX-ACCESS  read-only
    STATUS      current
    DESCRIPTION
        "The value of tmnxRadSrvPlcyNbrAcctInterimDrop indicates the number of
         RADIUS accounting interim update messages that were dropped from the
         buffer because their lifetime expired."
    ::= { tmnxRadSrvPlcyMsgBufStatsEntry 4 }

tmnxRadSrvPlcyLastBufClean       OBJECT-TYPE
    SYNTAX      TimeStamp
    MAX-ACCESS  read-only
    STATUS      current
    DESCRIPTION
        "The value of tmnxRadSrvPlcyLastBufClean indicates the sysUpTime at the
         time of the most recent reset (empty) of the message buffer."
    ::= { tmnxRadSrvPlcyMsgBufStatsEntry 5 }

tmnxRadSrvPlcyLastBufStatsClean  OBJECT-TYPE
    SYNTAX      TimeStamp
    MAX-ACCESS  read-only
    STATUS      current
    DESCRIPTION
        "The value of tmnxRadSrvPlcyLastBufStatsClean indicates the sysUpTime
         at the time of the most recent reset of the message buffer statistics."
    ::= { tmnxRadSrvPlcyMsgBufStatsEntry 6 }

tmnxRadSrvPlcyNbrAcctStartBuf    OBJECT-TYPE
    SYNTAX      Counter32
    MAX-ACCESS  read-only
    STATUS      current
    DESCRIPTION
        "The value of tmnxRadSrvPlcyNbrAcctStartBuf indicates the number of
         RADIUS accounting start messages that are currently buffered for this
         radius server policy."
    ::= { tmnxRadSrvPlcyMsgBufStatsEntry 7 }

tmnxRadSrvPlcyNbrAcctStartDrop   OBJECT-TYPE
    SYNTAX      Counter32
    MAX-ACCESS  read-only
    STATUS      current
    DESCRIPTION
        "The value of tmnxRadSrvPlcyNbrAcctStartDrop indicates the number of
         RADIUS accounting start messages that were dropped from the buffer
         because their lifetime expired."
    ::= { tmnxRadSrvPlcyMsgBufStatsEntry 8 }

tmnxRadScriptPlcyObjs            OBJECT IDENTIFIER ::= { tmnxRadiusObjs 3 }

tmnxRadScriptPlcyTable           OBJECT-TYPE
    SYNTAX      SEQUENCE OF TmnxRadScriptPlcyEntry
    MAX-ACCESS  not-accessible
    STATUS      current
    DESCRIPTION
        "The tmnxRadScriptPlcyTable allows the configuration of RADIUS Python
         script policies used to change RADIUS messages."
    ::= { tmnxRadScriptPlcyObjs 1 }

tmnxRadScriptPlcyEntry           OBJECT-TYPE
    SYNTAX      TmnxRadScriptPlcyEntry
    MAX-ACCESS  not-accessible
    STATUS      current
    DESCRIPTION
        "Each entry represents a set of Python scripts used to change RADIUS
         messages.

         Rows in this table can be created and deleted via SNMP SET operations
         to tmnxRadScriptPlcyRowStatus."
    INDEX       { tmnxRadScriptPlcyName }
    ::= { tmnxRadScriptPlcyTable 1 }

TmnxRadScriptPlcyEntry           ::= SEQUENCE
{
    tmnxRadScriptPlcyName            TNamedItem,
    tmnxRadScriptPlcyRowStatus       RowStatus,
    tmnxRadScriptPlcyLastCh          TimeStamp,
    tmnxRadScriptPlcyDescription     TItemDescription,
    tmnxRadScriptPlcyOnFail          INTEGER,
    tmnxRadScriptPlcyPriURL          TmnxDisplayStringURL,
    tmnxRadScriptPlcyPriAdminState   TmnxAdminState,
    tmnxRadScriptPlcyPriOperState    TmnxOperState,
    tmnxRadScriptPlcySecURL          TmnxDisplayStringURL,
    tmnxRadScriptPlcySecAdminState   TmnxAdminState,
    tmnxRadScriptPlcySecOperState    TmnxOperState
}

tmnxRadScriptPlcyName            OBJECT-TYPE
    SYNTAX      TNamedItem
    MAX-ACCESS  not-accessible
    STATUS      current
    DESCRIPTION
        "The value of tmnxRadScriptPlcyName specifies the name of this RADIUS
         script policy."
    ::= { tmnxRadScriptPlcyEntry 1 }

tmnxRadScriptPlcyRowStatus       OBJECT-TYPE
    SYNTAX      RowStatus
    MAX-ACCESS  read-create
    STATUS      current
    DESCRIPTION
        "The value of tmnxRadScriptPlcyRowStatus controls the creation and
         deletion of rows in the table."
    ::= { tmnxRadScriptPlcyEntry 2 }

tmnxRadScriptPlcyLastCh          OBJECT-TYPE
    SYNTAX      TimeStamp
    MAX-ACCESS  read-only
    STATUS      current
    DESCRIPTION
        "The value tmnxRadScriptPlcyLastCh indicates the sysUpTime at the time
         of the most recent management-initiated change to this RADIUS script
         policy."
    ::= { tmnxRadScriptPlcyEntry 3 }

tmnxRadScriptPlcyDescription     OBJECT-TYPE
    SYNTAX      TItemDescription
    MAX-ACCESS  read-create
    STATUS      current
    DESCRIPTION
        "The value of tmnxRadScriptPlcyDescription specifies the description of
         this RADIUS script policy."
    DEFVAL      { "" }
    ::= { tmnxRadScriptPlcyEntry 4 }

tmnxRadScriptPlcyOnFail          OBJECT-TYPE
    SYNTAX      INTEGER {
        passthrough (1),
        drop        (2)
    }
    MAX-ACCESS  read-create
    STATUS      current
    DESCRIPTION
        "The value of tmnxRadScriptPlcyOnFail specifies the action taken when
         Python fails to modify the RADIUS message.

         When the value is 'passthrough' the packet will be sent out without
         any modifications.

         When the value is 'drop' the packet will be dropped."
    DEFVAL      { drop }
    ::= { tmnxRadScriptPlcyEntry 5 }

tmnxRadScriptPlcyPriURL          OBJECT-TYPE
    SYNTAX      TmnxDisplayStringURL
    MAX-ACCESS  read-create
    STATUS      current
    DESCRIPTION
        "The value of tmnxRadScriptPlcyPriURL specifies the URL of the primary
         script to change RADIUS attributes of the RADIUS message."
    DEFVAL      { ''H }
    ::= { tmnxRadScriptPlcyEntry 6 }

tmnxRadScriptPlcyPriAdminState   OBJECT-TYPE
    SYNTAX      TmnxAdminState
    MAX-ACCESS  read-create
    STATUS      current
    DESCRIPTION
        "The value of tmnxRadScriptPlcyPriAdminState specifies the
         administrative state of the primary script to change RADIUS attributes
         of the RADIUS message."
    DEFVAL      { outOfService }
    ::= { tmnxRadScriptPlcyEntry 7 }

tmnxRadScriptPlcyPriOperState    OBJECT-TYPE
    SYNTAX      TmnxOperState
    MAX-ACCESS  read-only
    STATUS      current
    DESCRIPTION
        "The value of tmnxRadScriptPlcyPriOperState indicates the operational
         state of the primary script to change RADIUS attributes of the RADIUS
         message."
    ::= { tmnxRadScriptPlcyEntry 8 }

tmnxRadScriptPlcySecURL          OBJECT-TYPE
    SYNTAX      TmnxDisplayStringURL
    MAX-ACCESS  read-create
    STATUS      current
    DESCRIPTION
        "The value of tmnxRadScriptPlcySecURL specifies the URL of the
         secondary script to change RADIUS attributes of the RADIUS message."
    DEFVAL      { ''H }
    ::= { tmnxRadScriptPlcyEntry 9 }

tmnxRadScriptPlcySecAdminState   OBJECT-TYPE
    SYNTAX      TmnxAdminState
    MAX-ACCESS  read-create
    STATUS      current
    DESCRIPTION
        "The value of tmnxRadScriptPlcySecAdminState specifies the
         administrative state of the secondary script to change RADIUS
         attributes of the RADIUS message."
    DEFVAL      { outOfService }
    ::= { tmnxRadScriptPlcyEntry 10 }

tmnxRadScriptPlcySecOperState    OBJECT-TYPE
    SYNTAX      TmnxOperState
    MAX-ACCESS  read-only
    STATUS      current
    DESCRIPTION
        "The value of tmnxRadScriptPlcySecOperState indicates the operational
         state of the secondary script to change RADIUS attributes of the
         RADIUS message."
    ::= { tmnxRadScriptPlcyEntry 11 }

tmnxRadRouteDownlObjs            OBJECT IDENTIFIER ::= { tmnxRadiusObjs 4 }

tmnxRadRouteDownlTable           OBJECT-TYPE
    SYNTAX      SEQUENCE OF TmnxRadRouteDownlEntry
    MAX-ACCESS  not-accessible
    STATUS      current
    DESCRIPTION
        "The tmnxRadRouteDownlTable allows the configuration of RADIUS route
         downloaders to download a given set of routes from the RADIUS AAA
         server by periodically sending RADIUS access requests."
    ::= { tmnxRadRouteDownlObjs 1 }

tmnxRadRouteDownlEntry           OBJECT-TYPE
    SYNTAX      TmnxRadRouteDownlEntry
    MAX-ACCESS  not-accessible
    STATUS      current
    DESCRIPTION
        "Each entry represents a RADIUS route downloader instance.

         Rows in this table can be created and deleted via SNMP SET operations
         to tmnxRadRouteDownlRowStatus."
    INDEX       { tmnxRadRouteDownlName }
    ::= { tmnxRadRouteDownlTable 1 }

TmnxRadRouteDownlEntry           ::= SEQUENCE
{
    tmnxRadRouteDownlName            TNamedItem,
    tmnxRadRouteDownlRowStatus       RowStatus,
    tmnxRadRouteDownlLastCh          TimeStamp,
    tmnxRadRouteDownlDescription     TItemDescription,
    tmnxRadRouteDownlAdminState      TmnxAdminState,
    tmnxRadRouteDownlRadServPlcy     TNamedItemOrEmpty,
    tmnxRadRouteDownlDownloadIntvl   Unsigned32,
    tmnxRadRouteDownlMinRetryIntvl   Unsigned32,
    tmnxRadRouteDownlMaxRetryIntvl   Unsigned32,
    tmnxRadRouteDownlDefaultMetric   Unsigned32,
    tmnxRadRouteDownlDefaultTag      Unsigned32,
    tmnxRadRouteDownlMaxRoutes       Unsigned32,
    tmnxRadRouteDownlBaseUserName    TNamedItemOrEmpty,
    tmnxRadRouteDownlPassword        DisplayString
}

tmnxRadRouteDownlName            OBJECT-TYPE
    SYNTAX      TNamedItem
    MAX-ACCESS  not-accessible
    STATUS      current
    DESCRIPTION
        "The value of tmnxRadRouteDownlName specifies the name of this RADIUS
         route downloader."
    ::= { tmnxRadRouteDownlEntry 1 }

tmnxRadRouteDownlRowStatus       OBJECT-TYPE
    SYNTAX      RowStatus
    MAX-ACCESS  read-create
    STATUS      current
    DESCRIPTION
        "The value of tmnxRadRouteDownlRowStatus controls the creation and
         deletion of rows in this table."
    ::= { tmnxRadRouteDownlEntry 2 }

tmnxRadRouteDownlLastCh          OBJECT-TYPE
    SYNTAX      TimeStamp
    MAX-ACCESS  read-only
    STATUS      current
    DESCRIPTION
        "The value tmnxRadRouteDownlLastCh indicates the sysUpTime at the time
         of the most recent management-initiated change to this table entry."
    ::= { tmnxRadRouteDownlEntry 3 }

tmnxRadRouteDownlDescription     OBJECT-TYPE
    SYNTAX      TItemDescription
    MAX-ACCESS  read-create
    STATUS      current
    DESCRIPTION
        "The value of tmnxRadRouteDownlDescription specifies the description of
         this RADIUS route downloader entry."
    DEFVAL      { "" }
    ::= { tmnxRadRouteDownlEntry 4 }

tmnxRadRouteDownlAdminState      OBJECT-TYPE
    SYNTAX      TmnxAdminState
    MAX-ACCESS  read-create
    STATUS      current
    DESCRIPTION
        "The value of tmnxRadRouteDownlAdminState specifies the administrative
         state of this route downloader entry."
    DEFVAL      { outOfService }
    ::= { tmnxRadRouteDownlEntry 5 }

tmnxRadRouteDownlRadServPlcy     OBJECT-TYPE
    SYNTAX      TNamedItemOrEmpty
    MAX-ACCESS  read-create
    STATUS      current
    DESCRIPTION
        "The value of tmnxRadRouteDownlRadServPlcy specifies the RADIUS server
         policy defined in tmnxRadSrvPlcyTable."
    DEFVAL      { "" }
    ::= { tmnxRadRouteDownlEntry 6 }

tmnxRadRouteDownlDownloadIntvl   OBJECT-TYPE
    SYNTAX      Unsigned32 (1..1440)
    UNITS       "minutes"
    MAX-ACCESS  read-create
    STATUS      current
    DESCRIPTION
        "The value of tmnxRadRouteDownlDownloadIntvl specifies the time
         interval, in minutes, between the start of the last route downloader
         run and the start of the next route downloader run."
    DEFVAL      { 720 }
    ::= { tmnxRadRouteDownlEntry 7 }

tmnxRadRouteDownlMinRetryIntvl   OBJECT-TYPE
    SYNTAX      Unsigned32 (1..1440)
    UNITS       "minutes"
    MAX-ACCESS  read-create
    STATUS      current
    DESCRIPTION
        "The value of tmnxRadRouteDownlMinRetryIntvl specifies the duration, in
         minutes, of the retry interval. This duration grows exponentially
         after each sequential failure. The maximum duration is configured in
         tmnxRadRouteDownlMaxRetryIntvl."
    DEFVAL      { 10 }
    ::= { tmnxRadRouteDownlEntry 8 }

tmnxRadRouteDownlMaxRetryIntvl   OBJECT-TYPE
    SYNTAX      Unsigned32 (1..1440)
    UNITS       "minutes"
    MAX-ACCESS  read-create
    STATUS      current
    DESCRIPTION
        "The value of tmnxRadRouteDownlMaxRetryIntvl specifies the maximum
         duration, in minutes, of the retry interval. The start value of the
         retry interval is configured in tmnxRadRouteDownlMinRetryIntvl and
         this duration grows exponentially after each sequential failure. The
         value of tmnxRadRouteDownlMaxRetryIntvl specifies the maximum value of
         this duration."
    DEFVAL      { 20 }
    ::= { tmnxRadRouteDownlEntry 9 }

tmnxRadRouteDownlDefaultMetric   OBJECT-TYPE
    SYNTAX      Unsigned32 (0..254)
    MAX-ACCESS  read-create
    STATUS      current
    DESCRIPTION
        "The value of tmnxRadRouteDownlDefaultMetric specifies the default
         metric of the routes imported."
    DEFVAL      { 2 }
    ::= { tmnxRadRouteDownlEntry 10 }

tmnxRadRouteDownlDefaultTag      OBJECT-TYPE
    SYNTAX      Unsigned32 (0..4294967295)
    MAX-ACCESS  read-create
    STATUS      current
    DESCRIPTION
        "The value of tmnxRadRouteDownlDefaultTag specifies the default tag of
         the routes imported."
    DEFVAL      { 0 }
    ::= { tmnxRadRouteDownlEntry 11 }

tmnxRadRouteDownlMaxRoutes       OBJECT-TYPE
    SYNTAX      Unsigned32 (1..200000)
    MAX-ACCESS  read-create
    STATUS      current
    DESCRIPTION
        "The value of tmnxRadRouteDownlMaxRoutes specifies the maximum number
         of the routes imported."
    DEFVAL      { 200000 }
    ::= { tmnxRadRouteDownlEntry 12 }

tmnxRadRouteDownlBaseUserName    OBJECT-TYPE
    SYNTAX      TNamedItemOrEmpty
    MAX-ACCESS  read-create
    STATUS      current
    DESCRIPTION
        "The value of tmnxRadRouteDownlBaseUserName specifies the prefix of the
         username that is used in the RADIUS access requests. The username used
         in the RADIUS access requests is a concatenation of this string, the
         dash character and an increasing integer.

         If the value of this object is the default value then the string
         configured in tmnxChassisName is used."
    DEFVAL      { "" }
    ::= { tmnxRadRouteDownlEntry 13 }

tmnxRadRouteDownlPassword        OBJECT-TYPE
    SYNTAX      DisplayString (SIZE (0..32))
    MAX-ACCESS  read-create
    STATUS      current
    DESCRIPTION
        "The value of tmnxRadRouteDownlPassword specifies the password that is
         used in the RADIUS access requests.

         The value of this object must be set to a non-empty string when
         tmnxRadRouteDownlAdminState is set to 'inService (2)'."
    DEFVAL      { "" }
    ::= { tmnxRadRouteDownlEntry 14 }

tmnxRadRDStatsTable              OBJECT-TYPE
    SYNTAX      SEQUENCE OF TmnxRadRDStatsEntry
    MAX-ACCESS  not-accessible
    STATUS      current
    DESCRIPTION
        "The tmnxRadRDStatsTable contains statistics about the RADIUS Route
         Downloaders of this system."
    ::= { tmnxRadRouteDownlObjs 2 }

tmnxRadRDStatsEntry              OBJECT-TYPE
    SYNTAX      TmnxRadRDStatsEntry
    MAX-ACCESS  not-accessible
    STATUS      current
    DESCRIPTION
        "Each conceptual row represents statistics about a particular Route
         Downloader.

         Rows are created and destroyed automatically by the system."
    AUGMENTS    { tmnxRadRouteDownlEntry }
    ::= { tmnxRadRDStatsTable 1 }

TmnxRadRDStatsEntry              ::= SEQUENCE
{
    tmnxRadRDStatsRxLastAccessReject TimeStamp,
    tmnxRadRDStatsRxLastAccessAccept TimeStamp,
    tmnxRadRDStatsTxLastAccessReq    TimeStamp,
    tmnxRadRDStatsTxLastAccReqRetry  TimeStamp,
    tmnxRadRDStatsRemainingDownlTime TimeInterval,
    tmnxRadRDStatsRemainingRetryTime TimeInterval,
    tmnxRadRDStatsRoutesReceived     Counter32,
    tmnxRadRDStatsRxAccessReject     Counter32,
    tmnxRadRDStatsRxAccessAccept     Counter32,
    tmnxRadRDStatsRxAccessAcceptDrop Counter32,
    tmnxRadRDStatsTxAccessRequest    Counter32,
    tmnxRadRDStatsTxAccessReqRetry   Counter32,
    tmnxRadRDStatsDownloads          Counter32,
    tmnxRadRDStatsRtmFailures        Counter32
}

tmnxRadRDStatsRxLastAccessReject OBJECT-TYPE
    SYNTAX      TimeStamp
    MAX-ACCESS  read-only
    STATUS      current
    DESCRIPTION
        "The value of tmnxRadRDStatsRxLastAccessReject indicates when this
         Route Downloader last received an Access-Reject packet."
    ::= { tmnxRadRDStatsEntry 1 }

tmnxRadRDStatsRxLastAccessAccept OBJECT-TYPE
    SYNTAX      TimeStamp
    MAX-ACCESS  read-only
    STATUS      current
    DESCRIPTION
        "The value of tmnxRadRDStatsRxLastAccessAccept indicates when this
         Route Downloader last received an Access-Accept packet."
    ::= { tmnxRadRDStatsEntry 2 }

tmnxRadRDStatsTxLastAccessReq    OBJECT-TYPE
    SYNTAX      TimeStamp
    MAX-ACCESS  read-only
    STATUS      current
    DESCRIPTION
        "The value of tmnxRadRDStatsTxLastAccessReq indicates when this Route
         Downloader last sent an Access-Request packet."
    ::= { tmnxRadRDStatsEntry 3 }

tmnxRadRDStatsTxLastAccReqRetry  OBJECT-TYPE
    SYNTAX      TimeStamp
    MAX-ACCESS  read-only
    STATUS      current
    DESCRIPTION
        "The value of tmnxRadRDStatsTxLastAccReqRetry indicates the time of the
         last Access-Request retry."
    ::= { tmnxRadRDStatsEntry 4 }

tmnxRadRDStatsRemainingDownlTime OBJECT-TYPE
    SYNTAX      TimeInterval
    MAX-ACCESS  read-only
    STATUS      current
    DESCRIPTION
        "The value of tmnxRadRDStatsRemainingDownlTime indicates the remaining
         time before the next download attempt."
    ::= { tmnxRadRDStatsEntry 5 }

tmnxRadRDStatsRemainingRetryTime OBJECT-TYPE
    SYNTAX      TimeInterval
    MAX-ACCESS  read-only
    STATUS      current
    DESCRIPTION
        "The value of tmnxRadRDStatsRemainingRetryTime indicates the remaining
         time before the next download retry."
    ::= { tmnxRadRDStatsEntry 6 }

tmnxRadRDStatsRoutesReceived     OBJECT-TYPE
    SYNTAX      Counter32
    MAX-ACCESS  read-only
    STATUS      current
    DESCRIPTION
        "The value of tmnxRadRDStatsRoutesReceived indicates the number of
         routes received in the last completed route download process."
    ::= { tmnxRadRDStatsEntry 7 }

tmnxRadRDStatsRxAccessReject     OBJECT-TYPE
    SYNTAX      Counter32
    MAX-ACCESS  read-only
    STATUS      current
    DESCRIPTION
        "The value of tmnxRadRDStatsRxAccessReject indicates the number of
         Access-Reject packets received by this Route Downloader."
    ::= { tmnxRadRDStatsEntry 8 }

tmnxRadRDStatsRxAccessAccept     OBJECT-TYPE
    SYNTAX      Counter32
    MAX-ACCESS  read-only
    STATUS      current
    DESCRIPTION
        "The value of tmnxRadRDStatsRxAccessAccept indicates the number of
         Access-Accept packets received by this Route Downloader."
    ::= { tmnxRadRDStatsEntry 9 }

tmnxRadRDStatsRxAccessAcceptDrop OBJECT-TYPE
    SYNTAX      Counter32
    MAX-ACCESS  read-only
    STATUS      current
    DESCRIPTION
        "The value of tmnxRadRDStatsRxAccessAcceptDrop indicates the number of
         Access-Accept packets received but dropped by this Route Downloader."
    ::= { tmnxRadRDStatsEntry 10 }

tmnxRadRDStatsTxAccessRequest    OBJECT-TYPE
    SYNTAX      Counter32
    MAX-ACCESS  read-only
    STATUS      current
    DESCRIPTION
        "The value of tmnxRadRDStatsTxAccessRequest indicates the number of
         Access-Requests sent by this Route Downloader."
    ::= { tmnxRadRDStatsEntry 11 }

tmnxRadRDStatsTxAccessReqRetry   OBJECT-TYPE
    SYNTAX      Counter32
    MAX-ACCESS  read-only
    STATUS      current
    DESCRIPTION
        "The value of tmnxRadRDStatsTxAccessReqRetry indicates the number of
         Access-Requests retries for this Route Downloader."
    ::= { tmnxRadRDStatsEntry 12 }

tmnxRadRDStatsDownloads          OBJECT-TYPE
    SYNTAX      Counter32
    MAX-ACCESS  read-only
    STATUS      current
    DESCRIPTION
        "The value of tmnxRadRDStatsDownloads indicates the number of downloads
         started by this Route Downloader."
    ::= { tmnxRadRDStatsEntry 13 }

tmnxRadRDStatsRtmFailures        OBJECT-TYPE
    SYNTAX      Counter32
    MAX-ACCESS  read-only
    STATUS      current
    DESCRIPTION
        "The value of tmnxRadRDStatsRtmFailures indicates the number of times
         installing received routes failed for this Route Downloader."
    ::= { tmnxRadRDStatsEntry 14 }

tmnxRadSysCfgObjs                OBJECT IDENTIFIER ::= { tmnxRadiusObjs 5 }

tmnxRadSysCfgCoAPort             OBJECT-TYPE
    SYNTAX      InetPortNumber (1647 | 1700 | 1812 | 3799)
    MAX-ACCESS  read-write
    STATUS      current
    DESCRIPTION
        "The value of the object tmnxRadSysCfgCoAPort specifies the UDP port
         number on which RADIUS is listening for CoA and Disconnect messages."
    DEFVAL      { 3799 }
    ::= { tmnxRadSysCfgObjs 1 }

tmnxRadIsaObjs                   OBJECT IDENTIFIER ::= { tmnxRadiusObjs 6 }

tmnxRadIsaPlcyTable              OBJECT-TYPE
    SYNTAX      SEQUENCE OF TmnxRadIsaPlcyEntry
    MAX-ACCESS  not-accessible
    STATUS      current
    DESCRIPTION
        "The tmnxRadIsaPlcyTable allows configuration of authentication and
         accounting processes distributed on ISA cards."
    ::= { tmnxRadIsaObjs 1 }

tmnxRadIsaPlcyEntry              OBJECT-TYPE
    SYNTAX      TmnxRadIsaPlcyEntry
    MAX-ACCESS  not-accessible
    STATUS      current
    DESCRIPTION
        "Each conceptual row represents the configuration for a specific ISA
         RADIUS policy.

         Rows in this table can be created and deleted via SNMP SET operations
         to tmnxRadIsaPlcyRowStatus."
    INDEX       { IMPLIED tmnxRadIsaPlcyName }
    ::= { tmnxRadIsaPlcyTable 1 }

TmnxRadIsaPlcyEntry              ::= SEQUENCE
{
    tmnxRadIsaPlcyName               TNamedItem,
    tmnxRadIsaPlcyRowStatus          RowStatus,
    tmnxRadIsaPlcyLastCh             TimeStamp,
    tmnxRadIsaPlcyDescription        TItemDescription,
    tmnxRadIsaPlcyPassword           TmnxAuthPassword,
    tmnxRadIsaPlcyAuthInclAttr       BITS,
    tmnxRadIsaPlcyAcctInclAttr       BITS,
    tmnxRadIsaPlcyUserNameFormat     INTEGER,
    tmnxRadIsaPlcyUserNameMacFormat  INTEGER,
    tmnxRadIsaPlcyNasIpAddressOrigin INTEGER,
    tmnxRadIsaPlcySrvTimeout         Unsigned32,
    tmnxRadIsaPlcySrvRetry           Unsigned32,
    tmnxRadIsaPlcySrvVRtrID          TmnxVRtrIDOrZero,
    tmnxRadIsaPlcySrvSrcAddrType     InetAddressType,
    tmnxRadIsaPlcySrvSrcAddrStart    InetAddress,
    tmnxRadIsaPlcySrvSrcAddrEnd      InetAddress,
    tmnxRadIsaPlcySrvAlgorithm       TmnxSubRadIsaServAlgorithm,
    tmnxRadIsaPlcyAcctUpdateTriggers BITS,
    tmnxRadIsaPlcyPythonPolicy       TNamedItemOrEmpty,
    tmnxRadIsaPlcyInterval           Unsigned32,
    tmnxRadIsaPlcyRateLimit          Unsigned32,
    tmnxRadIsaPlcySrvIp6SrcAddrType  InetAddressType,
    tmnxRadIsaPlcySrvIp6SrcAddr      InetAddress,
    tmnxRadIsaPlcySrvIp6SrcPrefixLen InetAddressPrefixLength,
    tmnxRadIsaPlcySrvIp6Mtu          Unsigned32
}

tmnxRadIsaPlcyName               OBJECT-TYPE
    SYNTAX      TNamedItem
    MAX-ACCESS  not-accessible
    STATUS      current
    DESCRIPTION
        "The value of tmnxRadIsaPlcyName specifies the identifier of this ISA
         RADIUS policy."
    ::= { tmnxRadIsaPlcyEntry 1 }

tmnxRadIsaPlcyRowStatus          OBJECT-TYPE
    SYNTAX      RowStatus
    MAX-ACCESS  read-create
    STATUS      current
    DESCRIPTION
        "The value of tmnxRadIsaPlcyRowStatus controls the creation and
         deletion of rows in the table."
    ::= { tmnxRadIsaPlcyEntry 2 }

tmnxRadIsaPlcyLastCh             OBJECT-TYPE
    SYNTAX      TimeStamp
    MAX-ACCESS  read-only
    STATUS      current
    DESCRIPTION
        "The value of tmnxRadIsaPlcyLastCh indicates the sysUpTime at the time
         of the most recent management-initiated change to this policy."
    ::= { tmnxRadIsaPlcyEntry 3 }

tmnxRadIsaPlcyDescription        OBJECT-TYPE
    SYNTAX      TItemDescription
    MAX-ACCESS  read-create
    STATUS      current
    DESCRIPTION
        "The value of tmnxRadIsaPlcyDescription specifies the user provided
         description of this subscriber ISA RADIUS policy."
    DEFVAL      { "" }
    ::= { tmnxRadIsaPlcyEntry 4 }

tmnxRadIsaPlcyPassword           OBJECT-TYPE
    SYNTAX      TmnxAuthPassword (SIZE (0..10))
    MAX-ACCESS  read-create
    STATUS      current
    DESCRIPTION
        "The value of tmnxRadIsaPlcyPassword specifies the string to use in the
         User-Password RADIUS attribute.

         A get request on this object always returns an empty string."
    DEFVAL      { "" }
    ::= { tmnxRadIsaPlcyEntry 5 }

tmnxRadIsaPlcyAuthInclAttr       OBJECT-TYPE
    SYNTAX      BITS {
        circuitId                 (0),
        remoteId                  (1),
        nasPortId                 (2),
        nasIdentifier             (3),
        dhcpVendorClassId         (4),
        macAddress                (5),
        callingStationId          (6),
        calledStationId           (7),
        dhcpOptions               (8),
        nasPortType               (9),
        wifiSsidVlan              (10),
        framedIpAddr              (11),
        nasIpAddress              (12),
        nasPort                   (13),
        ipv6Address               (14),
        dhcp6Options              (15),
        reserved16                (16),
        reserved17                (17),
        xconnectTunnelHomeAddress (18),
        nasIpv6Address            (19)
    }
    MAX-ACCESS  read-create
    STATUS      current
    DESCRIPTION
        "The value of tmnxRadIsaPlcyAuthInclAttr specifies what RADIUS
         attributes the system should include into RADIUS Access-Request
         messages."
    DEFVAL      { {nasIpAddress, nasIpv6Address} }
    ::= { tmnxRadIsaPlcyEntry 6 }

tmnxRadIsaPlcyAcctInclAttr       OBJECT-TYPE
    SYNTAX      BITS {
        framedIpAddr                    (0),
        nasIdentifier                   (1),
        natSubscriberString             (2),
        userName                        (3),
        insideServiceId                 (4),
        outsideServiceId                (5),
        outsideIp                       (6),
        portRangeBlock                  (7),
        hardwareTimestamp               (8),
        releaseReason                   (9),
        multiSessionId                  (10),
        frameCounters                   (11),
        octetCounters                   (12),
        sessionTime                     (13),
        calledStationId                 (14),
        subscriberData                  (15),
        framedIpNetmask                 (16),
        circuitId                       (17),
        remoteId                        (18),
        dhcpOptions                     (19),
        dhcpVendorClassId               (20),
        macAddress                      (21),
        nasPortId                       (22),
        nasPortType                     (23),
        callingStationId                (24),
        subscriberId                    (25),
        acctTriggerReason               (26),
        ueCreationType                  (27),
        wifiRssi                        (28),
        acctDelayTime                   (29),
        wifiSsidVlan                    (30),
        nasIpAddress                    (31),
        nasPort                         (32),
        class                           (33),
        ipv6Address                     (34),
        framedIpv6Prefix                (35),
        dhcp6Options                    (36),
        xconnectTunnelService           (37),
        xconnectTunnelRemoteIpv6Address (38),
        xconnectTunnelLocalIpv6Address  (39),
        xconnectTunnelType              (40),
        xconnectTunnelHomeAddress       (41),
        millisecondEventTimestamp       (42),
        creditControlQuota              (43),
        nasIpv6Address                  (44),
        wlanCustomUserGroup             (45),
        portForwardLogging              (46),
        portTime                        (47)
    }
    MAX-ACCESS  read-create
    STATUS      current
    DESCRIPTION
        "The value of tmnxRadIsaPlcyAcctInclAttr specifies what RADIUS
         attributes the system should include into RADIUS accounting messages."
    DEFVAL      { {} }
    ::= { tmnxRadIsaPlcyEntry 7 }

tmnxRadIsaPlcyUserNameFormat     OBJECT-TYPE
    SYNTAX      INTEGER {
        mac        (1),
        macIp      (2),
        dhcpVendor (3),
        circuitId  (4)
    }
    MAX-ACCESS  read-create
    STATUS      current
    DESCRIPTION
        "The value of tmnxRadIsaPlcyUserNameFormat specifies the format used to
         identify the user towards the RADIUS server."
    DEFVAL      { mac }
    ::= { tmnxRadIsaPlcyEntry 8 }

tmnxRadIsaPlcyUserNameMacFormat  OBJECT-TYPE
    SYNTAX      INTEGER {
        alu  (1),
        ieee (2)
    }
    MAX-ACCESS  read-create
    STATUS      current
    DESCRIPTION
        "The value of tmnxRadIsaPlcyUserNameMacFormat specifies how to format a
         MAC address.

         The value 'alu' specifies the Nokia SROS style, like
         00:0c:f1:99:85:b8.

         The value 'ieee' specifies IEEE canonical style, like
         00-0C-F1-99-85-B8.

         The value of this object is only relevant while the value of
         tmnxRadIsaPlcyUserNameFormat is equal to 'mac' or 'macIp'."
    DEFVAL      { alu }
    ::= { tmnxRadIsaPlcyEntry 9 }

tmnxRadIsaPlcyNasIpAddressOrigin OBJECT-TYPE
    SYNTAX      INTEGER {
        systemIp (0),
        isaIp    (1)
    }
    MAX-ACCESS  read-create
    STATUS      current
    DESCRIPTION
        "The value of tmnxRadIsaPlcyNasIpAddressOrigin specifies the content of
         the NAS-IP-Address attribute.

         If the value is 'systemIp', the value of the object
         TIMETRA-VRTR-MIB::vRiaIpAddress.1.1.1 is used; if the value is
         'isaIp', a value in the range specified by
         tmnxRadIsaPlcySrvSrcAddrStart and tmnxRadIsaPlcySrvSrcAddrEnd is used
         that corresponds to the ISA card that transmits the Access-Request
         packet or the Accounting-Request packet."
    REFERENCE
        "RFC 2865 Remote Authentication Dial In User Service (RADIUS)
         section 5.4.  NAS-IP-Address.

         RFC 2866 RADIUS Accounting
         section 4.1.  Accounting-Request."
    DEFVAL      { systemIp }
    ::= { tmnxRadIsaPlcyEntry 10 }

tmnxRadIsaPlcySrvTimeout         OBJECT-TYPE
    SYNTAX      Unsigned32 (1..90)
    UNITS       "seconds"
    MAX-ACCESS  read-create
    STATUS      current
    DESCRIPTION
        "The value of tmnxRadIsaPlcySrvTimeout specifies, in seconds, the
         timeout between retries towards the same RADIUS server."
    DEFVAL      { 5 }
    ::= { tmnxRadIsaPlcyEntry 100 }

tmnxRadIsaPlcySrvRetry           OBJECT-TYPE
    SYNTAX      Unsigned32 (1..10)
    MAX-ACCESS  read-create
    STATUS      current
    DESCRIPTION
        "The value of tmnxRadIsaPlcySrvRetry specifies the number of RADIUS
         requests towards the same RADIUS server."
    DEFVAL      { 3 }
    ::= { tmnxRadIsaPlcyEntry 101 }

tmnxRadIsaPlcySrvVRtrID          OBJECT-TYPE
    SYNTAX      TmnxVRtrIDOrZero
    MAX-ACCESS  read-create
    STATUS      current
    DESCRIPTION
        "The value of tmnxRadIsaPlcySrvVRtrID specifies the virtual router
         instance applicable for the set of configured RADIUS servers
         (tmnxNatAccServTable).

         The value of this object cannot be changed once a RADIUS server is
         configured for this policy.

         When the value is '0', both base and management router instances are
         available."
    DEFVAL      { 0 }
    ::= { tmnxRadIsaPlcyEntry 102 }

tmnxRadIsaPlcySrvSrcAddrType     OBJECT-TYPE
    SYNTAX      InetAddressType
    MAX-ACCESS  read-create
    STATUS      current
    DESCRIPTION
        "The value of tmnxRadIsaPlcySrvSrcAddrType specifies the type of
         address stored in tmnxRadIsaPlcySrvSrcAddrStart and
         tmnxRadIsaPlcySrvSrcAddrEnd."
    DEFVAL      { unknown }
    ::= { tmnxRadIsaPlcyEntry 103 }

tmnxRadIsaPlcySrvSrcAddrStart    OBJECT-TYPE
    SYNTAX      InetAddress (SIZE (0|4|16))
    MAX-ACCESS  read-create
    STATUS      current
    DESCRIPTION
        "The value of tmnxRadIsaPlcySrvSrcAddrStart specifies the start of the
         the range of source addresses; it must be a valid unicast address.

         Each ISA MDA of the NAT ISA group associated with this policy, uses an
         address of this range."
    DEFVAL      { ''H }
    ::= { tmnxRadIsaPlcyEntry 104 }

tmnxRadIsaPlcySrvSrcAddrEnd      OBJECT-TYPE
    SYNTAX      InetAddress (SIZE (0|4|16))
    MAX-ACCESS  read-only
    STATUS      current
    DESCRIPTION
        "The value of tmnxRadIsaPlcySrvSrcAddrEnd indicates the end of the the
         range of source addresses.

         Each ISA MDA of the NAT ISA group associated with this policy, uses an
         address of this range."
    ::= { tmnxRadIsaPlcyEntry 105 }

tmnxRadIsaPlcySrvAlgorithm       OBJECT-TYPE
    SYNTAX      TmnxSubRadIsaServAlgorithm
    MAX-ACCESS  read-create
    STATUS      current
    DESCRIPTION
        "The value of tmnxRadIsaPlcySrvAlgorithm specifies the algorithm used
         to select a RADIUS server from the list of configured servers
         (tmnxRadIsaPlcyRadServTable)."
    DEFVAL      { direct }
    ::= { tmnxRadIsaPlcyEntry 106 }

tmnxRadIsaPlcyAcctUpdateTriggers OBJECT-TYPE
    SYNTAX      BITS {
        addressState       (0),
        softQuotaExhausted (1)
    }
    MAX-ACCESS  read-create
    STATUS      current
    DESCRIPTION
        "The value of tmnxRadIsaPlcyAcctUpdateTriggers specifies a bitmap to
         enable/disable triggered RADIUS Interim Account updates."
    DEFVAL      { {} }
    ::= { tmnxRadIsaPlcyEntry 110 }

tmnxRadIsaPlcyPythonPolicy       OBJECT-TYPE
    SYNTAX      TNamedItemOrEmpty
    MAX-ACCESS  read-create
    STATUS      current
    DESCRIPTION
        "The value of tmnxRadIsaPlcyPythonPolicy specifies the Python policy
         used for modifying Radius messages.

         A non-empty value for tmnxRadIsaPlcyPythonPolicy must correspond to a
         row in the TIMETRA-PYTHON-MIB::tmnxPythonPolicyTable."
    DEFVAL      { "" }
    ::= { tmnxRadIsaPlcyEntry 111 }

tmnxRadIsaPlcyInterval           OBJECT-TYPE
    SYNTAX      Unsigned32 (0..72)
    UNITS       "hours"
    MAX-ACCESS  read-create
    STATUS      current
    DESCRIPTION
        "The value of tmnxRadIsaPlcyInterval specifies the interval at which
         the Radius logging refreshes are generated. The generation of logging
         refreshes may be delayed past the configured interval value in case
         that message pacing (rate-limit) is enabled. Another scenario in which
         the generation of refreshes might be delayed is when the number of
         unacknowledged (pending) messages in SR OS has reached its upper
         limit. An increasing number of pending Interim-Update messages in SR
         OS is due to lack of adequate responsiveness of the Radius server.

         When tmnxRadIsaPlcyInterval is set to 0, no Interim-Update messages
         are sent."
    DEFVAL      { 0 }
    ::= { tmnxRadIsaPlcyEntry 112 }

tmnxRadIsaPlcyRateLimit          OBJECT-TYPE
    SYNTAX      Unsigned32 (0..100000)
    UNITS       "messages per second"
    MAX-ACCESS  read-create
    STATUS      current
    DESCRIPTION
        "The value of tmnxRadIsaPlcyRateLimit specifies the pacing of the
         Interim-Update messages related to the refreshment of the currently
         allocated port blocks. By default, when this command is disabled, the
         messages are sent at a high rate determined by the processing
         capability of the SR OS. Such high message rate can exceed the
         processing power of the logging server which can result in loss of
         logging information. To overcome this, the Interim-Update messages can
         be generated in a staggered fashion at a configured interval that is
         more accommodating towards the processing capabilities of the logging
         server.

         When tmnxRadIsaPlcyRateLimit is set to 0, Interim-Update messages are
         sent without any delay."
    DEFVAL      { 0 }
    ::= { tmnxRadIsaPlcyEntry 113 }

tmnxRadIsaPlcySrvIp6SrcAddrType  OBJECT-TYPE
    SYNTAX      InetAddressType
    MAX-ACCESS  read-create
    STATUS      current
    DESCRIPTION
        "The value of tmnxRadIsaPlcySrvIp6SrcAddrType specifies the type of
         address stored in tmnxRadIsaPlcySrvIp6SrcAddr.

         The value 'unknown' means that no value is configured for
         tmnxRadIsaPlcySrvIp6SrcAddr."
    DEFVAL      { unknown }
    ::= { tmnxRadIsaPlcyEntry 114 }

tmnxRadIsaPlcySrvIp6SrcAddr      OBJECT-TYPE
    SYNTAX      InetAddress (SIZE (0|16))
    MAX-ACCESS  read-create
    STATUS      current
    DESCRIPTION
        "The value of tmnxRadIsaPlcySrvIp6SrcAddr specifies the IPv6 prefix of
         source addresses.

         Each ISA MDA of the NAT ISA group associated with this policy, uses an
         individual /128 address of this prefix."
    DEFVAL      { ''H }
    ::= { tmnxRadIsaPlcyEntry 115 }

tmnxRadIsaPlcySrvIp6SrcPrefixLen OBJECT-TYPE
    SYNTAX      InetAddressPrefixLength (0 | 64)
    MAX-ACCESS  read-create
    STATUS      current
    DESCRIPTION
        "The value of tmnxRadIsaPlcySrvIp6SrcPrefixLen specifies the IPv6
         prefix length of source addresses."
    DEFVAL      { 0 }
    ::= { tmnxRadIsaPlcyEntry 116 }

tmnxRadIsaPlcySrvIp6Mtu          OBJECT-TYPE
    SYNTAX      Unsigned32 (1280..9000)
    MAX-ACCESS  read-create
    STATUS      current
    DESCRIPTION
        "The value of tmnxRadIsaPlcySrvIp6Mtu specifies the MTU (Maximum
         Transmission Unit) for outgoing IPv6 RADIUS traffic.

         The system fragments IP datagrams exceeding the MTU."
    DEFVAL      { 9000 }
    ::= { tmnxRadIsaPlcyEntry 117 }

tmnxRadIsaSrvTable               OBJECT-TYPE
    SYNTAX      SEQUENCE OF TmnxRadIsaSrvEntry
    MAX-ACCESS  not-accessible
    STATUS      current
    DESCRIPTION
        "The tmnxRadIsaSrvTable allows the configuration of the ISA RADIUS
         servers associated with ISA RADIUS Policies."
    ::= { tmnxRadIsaObjs 2 }

tmnxRadIsaSrvEntry               OBJECT-TYPE
    SYNTAX      TmnxRadIsaSrvEntry
    MAX-ACCESS  not-accessible
    STATUS      current
    DESCRIPTION
        "Each row represents the configuration for a particular RADIUS server
         of an ISA RADIUS policy.

         Rows in this table can be created and deleted via SNMP SET operations
         to tmnxRadIsaSrvRowStatus."
    INDEX       {
        tmnxRadIsaPlcyName,
        tmnxRadIsaSrvIndex
    }
    ::= { tmnxRadIsaSrvTable 1 }

TmnxRadIsaSrvEntry               ::= SEQUENCE
{
    tmnxRadIsaSrvIndex               Unsigned32,
    tmnxRadIsaSrvRowStatus           RowStatus,
    tmnxRadIsaSrvLastMgmtChange      TimeStamp,
    tmnxRadIsaSrvAdminState          TmnxEnabledDisabled,
    tmnxRadIsaSrvAddrType            InetAddressType,
    tmnxRadIsaSrvAddr                InetAddress,
    tmnxRadIsaSrvSecret              TmnxAuthSecret,
    tmnxRadIsaSrvPurpose             BITS,
    tmnxRadIsaSrvAcctPort            Unsigned32,
    tmnxRadIsaSrvAuthPort            Unsigned32,
    tmnxRadIsaSrvCoaPort             Unsigned32
}

tmnxRadIsaSrvIndex               OBJECT-TYPE
    SYNTAX      Unsigned32 (1..10)
    MAX-ACCESS  not-accessible
    STATUS      current
    DESCRIPTION
        "The value of tmnxRadIsaSrvIndex specifies the index of this RADIUS
         server in the set of servers associated with this ISA RADIUS policy.

         The value of tmnxRadIsaSrvIndex is particularly important if the value
         of the object tmnxRadIsaPlcySrvAlgorithm in its ISA RADIUS policy is
         equal to 'direct'."
    ::= { tmnxRadIsaSrvEntry 1 }

tmnxRadIsaSrvRowStatus           OBJECT-TYPE
    SYNTAX      RowStatus
    MAX-ACCESS  read-create
    STATUS      current
    DESCRIPTION
        "The value of tmnxRadIsaSrvRowStatus controls the creation and deletion
         of rows in the table."
    ::= { tmnxRadIsaSrvEntry 2 }

tmnxRadIsaSrvLastMgmtChange      OBJECT-TYPE
    SYNTAX      TimeStamp
    MAX-ACCESS  read-only
    STATUS      current
    DESCRIPTION
        "The value tmnxRadIsaSrvLastMgmtChange indicates the sysUpTime at the
         time of the most recent management-initiated change to this conceptual
         row."
    ::= { tmnxRadIsaSrvEntry 3 }

tmnxRadIsaSrvAdminState          OBJECT-TYPE
    SYNTAX      TmnxEnabledDisabled
    MAX-ACCESS  read-create
    STATUS      current
    DESCRIPTION
        "The value of tmnxRadIsaSrvAdminState specifies the administrative
         state of the ISA RADIUS server."
    DEFVAL      { disabled }
    ::= { tmnxRadIsaSrvEntry 4 }

tmnxRadIsaSrvAddrType            OBJECT-TYPE
    SYNTAX      InetAddressType
    MAX-ACCESS  read-create
    STATUS      current
    DESCRIPTION
        "The value of tmnxRadIsaSrvAddrType specifies the type of address
         stored in tmnxRadIsaSrvAddr."
    DEFVAL      { unknown }
    ::= { tmnxRadIsaSrvEntry 5 }

tmnxRadIsaSrvAddr                OBJECT-TYPE
    SYNTAX      InetAddress (SIZE (0|4|16))
    MAX-ACCESS  read-create
    STATUS      current
    DESCRIPTION
        "The value of tmnxRadIsaSrvAddr specifies the IP address of the ISA
         RADIUS server."
    DEFVAL      { ''H }
    ::= { tmnxRadIsaSrvEntry 6 }

tmnxRadIsaSrvSecret              OBJECT-TYPE
    SYNTAX      TmnxAuthSecret
    MAX-ACCESS  read-create
    STATUS      current
    DESCRIPTION
        "The value of tmnxRadIsaSrvSecret specifies the secret key associated
         with the ISA RADIUS server.

         An SNMP get request on this object always returns an empty string."
    ::= { tmnxRadIsaSrvEntry 7 }

tmnxRadIsaSrvPurpose             OBJECT-TYPE
    SYNTAX      BITS {
        accounting     (0),
        authentication (1),
        coa            (2)
    }
    MAX-ACCESS  read-create
    STATUS      current
    DESCRIPTION
        "The value of tmnxRadIsaSrvPurpose specifies the purpose of this ISA
         RADIUS server.

         The value of tmnxRadProxSrvPurpose is associated with the values of
         tmnxRadIsaSrvAcctPort, tmnxRadIsaSrvAuthPort and tmnxRadIsaSrvCoaPort."
    DEFVAL      { {} }
    ::= { tmnxRadIsaSrvEntry 8 }

tmnxRadIsaSrvAcctPort            OBJECT-TYPE
    SYNTAX      Unsigned32 (0 | 1..65535)
    MAX-ACCESS  read-create
    STATUS      current
    DESCRIPTION
        "The value of tmnxRadIsaSrvAcctPort specifies the UDP port number on
         which to contact the RADIUS server for accounting.

         The value of tmnxRadIsaSrvAcctPort is associated with the value of
         tmnxRadIsaSrvPurpose. While the 'accounting' bit is off, the value is
         zero; when the 'accounting' bit is switched on without specifying a
         value, the system sets it to 1813 by default."
    DEFVAL      { 0 }
    ::= { tmnxRadIsaSrvEntry 9 }

tmnxRadIsaSrvAuthPort            OBJECT-TYPE
    SYNTAX      Unsigned32 (0 | 1..65535)
    MAX-ACCESS  read-create
    STATUS      current
    DESCRIPTION
        "The value of tmnxRadIsaSrvAuthPort specifies the UDP port number on
         which to contact the RADIUS server for authentication.

         The value of tmnxRadIsaSrvAuthPort is associated with the value of
         tmnxRadIsaSrvPurpose. While the 'authentication' bit is off, the value
         is zero; when the 'authentication' bit is switched on without
         specifying a value, the system sets it to 1812 by default."
    DEFVAL      { 0 }
    ::= { tmnxRadIsaSrvEntry 10 }

tmnxRadIsaSrvCoaPort             OBJECT-TYPE
    SYNTAX      Unsigned32 (0 | 1..65535)
    MAX-ACCESS  read-create
    STATUS      current
    DESCRIPTION
        "The value of tmnxRadIsaSrvCoaPort specifies the UDP port number
         acceptable for Change-of-Authorization messages.

         The value of tmnxRadIsaSrvCoaPort is associated with the value of
         tmnxRadIsaSrvPurpose. While the 'coa' bit is off, the value is zero;
         when the 'coa' bit is switched on without specifying a value, the
         system sets it to 3799 by default."
    DEFVAL      { 0 }
    ::= { tmnxRadIsaSrvEntry 11 }

tmnxRadIsaSrvStatTable           OBJECT-TYPE
    SYNTAX      SEQUENCE OF TmnxRadIsaSrvStatEntry
    MAX-ACCESS  not-accessible
    STATUS      current
    DESCRIPTION
        "The tmnxRadIsaSrvStatTable contains basic status information about the
         connections with ISA RADIUS servers."
    ::= { tmnxRadIsaObjs 3 }

tmnxRadIsaSrvStatEntry           OBJECT-TYPE
    SYNTAX      TmnxRadIsaSrvStatEntry
    MAX-ACCESS  not-accessible
    STATUS      current
    DESCRIPTION
        "Each entry represents the status of a connection with a particular
         RADIUS server.

         Rows in this table are automatically created and destroyed by the
         system.

         Each connection originates in a particular ISA group member, using an
         IP source address of the range configured for a particular ISA RADIUS
         policy, and connects with a RADIUS server associated with that policy."
    INDEX       {
        tmnxRadIsaPlcyName,
        tmnxRadIsaSrvIndex,
        tmnxRadIsaSrvStatGrpId,
        tmnxRadIsaSrvStatMemberId
    }
    ::= { tmnxRadIsaSrvStatTable 1 }

TmnxRadIsaSrvStatEntry           ::= SEQUENCE
{
    tmnxRadIsaSrvStatGrpId           Unsigned32,
    tmnxRadIsaSrvStatMemberId        Unsigned32,
    tmnxRadIsaSrvStatSrcAddrType     InetAddressType,
    tmnxRadIsaSrvStatSrcAddr         InetAddress,
    tmnxRadIsaSrvStatPurposeUp       BITS,
    tmnxRadIsaSrvStatPurposeHoldDown BITS
}

tmnxRadIsaSrvStatGrpId           OBJECT-TYPE
    SYNTAX      Unsigned32
    MAX-ACCESS  not-accessible
    STATUS      current
    DESCRIPTION
        "The value of the object tmnxRadIsaSrvStatGrpId specifies the
         identifier of the Integrated Service Adaptor group."
    ::= { tmnxRadIsaSrvStatEntry 1 }

tmnxRadIsaSrvStatMemberId        OBJECT-TYPE
    SYNTAX      Unsigned32
    MAX-ACCESS  not-accessible
    STATUS      current
    DESCRIPTION
        "The value of the object tmnxRadIsaSrvStatMemberId indicates the
         identifier of this ISA Group member."
    ::= { tmnxRadIsaSrvStatEntry 2 }

tmnxRadIsaSrvStatSrcAddrType     OBJECT-TYPE
    SYNTAX      InetAddressType
    MAX-ACCESS  read-only
    STATUS      current
    DESCRIPTION
        "The value of tmnxRadIsaSrvStatSrcAddrType indicates the address type
         of tmnxRadIsaSrvStatSrcAddr."
    ::= { tmnxRadIsaSrvStatEntry 3 }

tmnxRadIsaSrvStatSrcAddr         OBJECT-TYPE
    SYNTAX      InetAddress (SIZE (0|4|16))
    MAX-ACCESS  read-only
    STATUS      current
    DESCRIPTION
        "The value of tmnxRadIsaSrvStatSrcAddr indicates the source IP address
         used by this system for this connection with this RADIUS server."
    ::= { tmnxRadIsaSrvStatEntry 4 }

tmnxRadIsaSrvStatPurposeUp       OBJECT-TYPE
    SYNTAX      BITS {
        accounting     (0),
        authentication (1),
        coa            (2)
    }
    MAX-ACCESS  read-only
    STATUS      current
    DESCRIPTION
        "The value of tmnxRadIsaSrvStatPurposeUp indicates for each purpose if
         this connection is operational 'up'.

         If a named bit is set, it indicates that the connection is operational
         for that purpose.

         If a named bit is cleared, it indicates that the connection is not
         operational for that purpose."
    ::= { tmnxRadIsaSrvStatEntry 9 }

tmnxRadIsaSrvStatPurposeHoldDown OBJECT-TYPE
    SYNTAX      BITS {
        accounting     (0),
        authentication (1),
        coa            (2)
    }
    MAX-ACCESS  read-only
    STATUS      current
    DESCRIPTION
        "The value of tmnxRadIsaSrvStatPurposeHoldDown indicates for each
         purpose if this connection is in hold down.

         If a named bit is set, it indicates that the connection is in hold
         down for that purpose.

         If a named bit is cleared, it indicates that the connection is not in
         hold down for that purpose."
    ::= { tmnxRadIsaSrvStatEntry 10 }

tmnxRadIsaSrvStatsTable          OBJECT-TYPE
    SYNTAX      SEQUENCE OF TmnxRadIsaSrvStatsEntry
    MAX-ACCESS  not-accessible
    STATUS      current
    DESCRIPTION
        "The tmnxRadIsaSrvStatsTable contains statistics information about the
         connections with ISA RADIUS servers."
    ::= { tmnxRadIsaObjs 4 }

tmnxRadIsaSrvStatsEntry          OBJECT-TYPE
    SYNTAX      TmnxRadIsaSrvStatsEntry
    MAX-ACCESS  not-accessible
    STATUS      current
    DESCRIPTION
        "Each conceptual row represents a type of statistics of a connection
         with a particular RADIUS server.

         Rows in this table are automatically created and destroyed by the
         system."
    INDEX       {
        tmnxRadIsaPlcyName,
        tmnxRadIsaSrvIndex,
        tmnxRadIsaSrvStatGrpId,
        tmnxRadIsaSrvStatMemberId,
        tmnxRadIsaSrvStatsType
    }
    ::= { tmnxRadIsaSrvStatsTable 1 }

TmnxRadIsaSrvStatsEntry          ::= SEQUENCE
{
    tmnxRadIsaSrvStatsType           Unsigned32,
    tmnxRadIsaSrvStatsName           DisplayString,
    tmnxRadIsaSrvStatsValue          Counter32
}

tmnxRadIsaSrvStatsType           OBJECT-TYPE
    SYNTAX      Unsigned32 (0..11)
    MAX-ACCESS  not-accessible
    STATUS      current
    DESCRIPTION
        "The value of tmnxRadIsaSrvStatsType indicates the type of ISA RADIUS
         server statistics contained in this conceptual row."
    ::= { tmnxRadIsaSrvStatsEntry 1 }

tmnxRadIsaSrvStatsName           OBJECT-TYPE
    SYNTAX      DisplayString (SIZE (1..64))
    MAX-ACCESS  read-only
    STATUS      current
    DESCRIPTION
        "The value of the object tmnxRadIsaSrvStatsName indicates the
         human-readable identifier of the statistics contained in this
         conceptual row."
    ::= { tmnxRadIsaSrvStatsEntry 2 }

tmnxRadIsaSrvStatsValue          OBJECT-TYPE
    SYNTAX      Counter32
    MAX-ACCESS  read-only
    STATUS      current
    DESCRIPTION
        "The value of the object tmnxRadIsaSrvStatsValue indicates the value of
         the statistics contained in this conceptual row."
    ::= { tmnxRadIsaSrvStatsEntry 3 }

tmnxRadIsaPSStatsTable           OBJECT-TYPE
    SYNTAX      SEQUENCE OF TmnxRadIsaPSStatsEntry
    MAX-ACCESS  not-accessible
    STATUS      current
    DESCRIPTION
        "The tmnxRadIsaPSStatsTable contains statistics information about the
         connections with RADIUS Proxy servers running on ISA cards associated
         with WLAN Gateway groups."
    ::= { tmnxRadIsaObjs 5 }

tmnxRadIsaPSStatsEntry           OBJECT-TYPE
    SYNTAX      TmnxRadIsaPSStatsEntry
    MAX-ACCESS  not-accessible
    STATUS      current
    DESCRIPTION
        "Each conceptual row represents statistics of connections with a
         particular RADIUS Proxy server on a member of a WLAN Gateway group.

         Rows in this table are automatically created and destroyed by the
         system."
    INDEX       {
        vRtrID,
        tmnxRadProxSrvName,
        tmnxRadIsaSrvStatGrpId,
        tmnxRadIsaSrvStatMemberId
    }
    ::= { tmnxRadIsaPSStatsTable 1 }

TmnxRadIsaPSStatsEntry           ::= SEQUENCE
{
    tmnxRadIsaPSStatsRxPacket        Counter32,
    tmnxRadIsaPSStatsRxAuthRequest   Counter32,
    tmnxRadIsaPSStatsRxAcctRequest   Counter32,
    tmnxRadIsaPSStatsRxDropped       Counter32,
    tmnxRadIsaPSStatsRxRetransmit    Counter32,
    tmnxRadIsaPSStatsRxWrongPurpose  Counter32,
    tmnxRadIsaPSStatsRxCacheNoUeMac  Counter32,
    tmnxRadIsaPSStatsRxClientCtxtLim Counter32,
    tmnxRadIsaPSStatsRxNoAaaPol      Counter32,
    tmnxRadIsaPSStatsRxInvAttr       Counter32,
    tmnxRadIsaPSStatsRxInvPassword   Counter32,
    tmnxRadIsaPSStatsRxInvAcctStatus Counter32,
    tmnxRadIsaPSStatsRxNoAcctStatus  Counter32,
    tmnxRadIsaPSStatsRxInvAcctAuth   Counter32,
    tmnxRadIsaPSStatsRxInvMsgAuth    Counter32,
    tmnxRadIsaPSStatsRxMgmtOverload  Counter32,
    tmnxRadIsaPSStatsTxAuthAck       Counter32,
    tmnxRadIsaPSStatsTxAuthReject    Counter32,
    tmnxRadIsaPSStatsTxAuthChallenge Counter32,
    tmnxRadIsaPSStatsTxAcctResponse  Counter32,
    tmnxRadIsaPSStatsTxDropped       Counter32,
    tmnxRadIsaPSStatsTxSrvTimeout    Counter32,
    tmnxRadIsaPSStatsTxSrvInvAuth    Counter32,
    tmnxRadIsaPSStatsTxSrvInvMsgAuth Counter32,
    tmnxRadIsaPSStatsTxSrvInvAttr    Counter32,
    tmnxRadIsaPSStatsTxSendFailure   Counter32
}

tmnxRadIsaPSStatsRxPacket        OBJECT-TYPE
    SYNTAX      Counter32
    MAX-ACCESS  read-only
    STATUS      current
    DESCRIPTION
        "The value of tmnxRadIsaPSStatsRxPacket indicates the number of packets
         received by this RADIUS Proxy Server."
    ::= { tmnxRadIsaPSStatsEntry 1 }

tmnxRadIsaPSStatsRxAuthRequest   OBJECT-TYPE
    SYNTAX      Counter32
    MAX-ACCESS  read-only
    STATUS      current
    DESCRIPTION
        "The value of tmnxRadIsaPSStatsRxAuthRequest indicates the number of
         Access-Request packets received by this RADIUS Proxy Server."
    ::= { tmnxRadIsaPSStatsEntry 2 }

tmnxRadIsaPSStatsRxAcctRequest   OBJECT-TYPE
    SYNTAX      Counter32
    MAX-ACCESS  read-only
    STATUS      current
    DESCRIPTION
        "The value of tmnxRadIsaPSStatsRxAcctRequest indicates the number of
         Accounting-Request packets received by this RADIUS Proxy Server."
    ::= { tmnxRadIsaPSStatsEntry 3 }

tmnxRadIsaPSStatsRxDropped       OBJECT-TYPE
    SYNTAX      Counter32
    MAX-ACCESS  read-only
    STATUS      current
    DESCRIPTION
        "The value of tmnxRadIsaPSStatsRxDropped indicates the number of
         packets received by this RADIUS Proxy Server but dropped."
    ::= { tmnxRadIsaPSStatsEntry 4 }

tmnxRadIsaPSStatsRxRetransmit    OBJECT-TYPE
    SYNTAX      Counter32
    MAX-ACCESS  read-only
    STATUS      current
    DESCRIPTION
        "The value of tmnxRadIsaPSStatsRxRetransmit indicates the number of
         packets received by this RADIUS Proxy Server that were rejected
         because they are retransmitted."
    ::= { tmnxRadIsaPSStatsEntry 5 }

tmnxRadIsaPSStatsRxWrongPurpose  OBJECT-TYPE
    SYNTAX      Counter32
    MAX-ACCESS  read-only
    STATUS      current
    DESCRIPTION
        "The value of tmnxRadIsaPSStatsRxWrongPurpose indicates the number of
         packets received by this RADIUS Proxy Server that were rejected
         because the value of tmnxRadProxSrvPurpose is set to a value not
         matching the type of packet."
    ::= { tmnxRadIsaPSStatsEntry 6 }

tmnxRadIsaPSStatsRxCacheNoUeMac  OBJECT-TYPE
    SYNTAX      Counter32
    MAX-ACCESS  read-only
    STATUS      current
    DESCRIPTION
        "The value of tmnxRadIsaPSStatsRxCacheNoUeMac indicates the number of
         packets received by this RADIUS Proxy Server that were rejected
         because the UE MAC address was not present in the packet."
    ::= { tmnxRadIsaPSStatsEntry 7 }

tmnxRadIsaPSStatsRxClientCtxtLim OBJECT-TYPE
    SYNTAX      Counter32
    MAX-ACCESS  read-only
    STATUS      current
    DESCRIPTION
        "The value of tmnxRadIsaPSStatsRxClientCtxtLim indicates the number of
         packets received by this RADIUS Proxy Server that were rejected
         because the limit of client contexts was reached. For each RADIUS
         transaction a client context is created, and will be deleted once the
         transaction is finished."
    ::= { tmnxRadIsaPSStatsEntry 8 }

tmnxRadIsaPSStatsRxNoAaaPol      OBJECT-TYPE
    SYNTAX      Counter32
    MAX-ACCESS  read-only
    STATUS      current
    DESCRIPTION
        "The value of tmnxRadIsaPSStatsRxNoAaaPol indicates the number of
         packets received by this RADIUS Proxy Server that were rejected
         because it has no ISA RADIUS server policy configured for that type of
         packet."
    ::= { tmnxRadIsaPSStatsEntry 9 }

tmnxRadIsaPSStatsRxInvAttr       OBJECT-TYPE
    SYNTAX      Counter32
    MAX-ACCESS  read-only
    STATUS      current
    DESCRIPTION
        "The value of tmnxRadIsaPSStatsRxInvAttr indicates the number of
         packets received by this RADIUS Proxy Server that were rejected
         because one of the attributes was incorrectly encoded."
    REFERENCE
        "RFC 2865 Remote Authentication Dial In User Service (RADIUS)
         section 5 Attributes."
    ::= { tmnxRadIsaPSStatsEntry 10 }

tmnxRadIsaPSStatsRxInvPassword   OBJECT-TYPE
    SYNTAX      Counter32
    MAX-ACCESS  read-only
    STATUS      current
    DESCRIPTION
        "The value of tmnxRadIsaPSStatsRxInvPassword indicates the number of
         packets received by this RADIUS Proxy Server that were rejected
         because the User-Password attribute could not be decoded."
    REFERENCE
        "RFC 2865 Remote Authentication Dial In User Service (RADIUS)
         section 5.2 User-Password."
    ::= { tmnxRadIsaPSStatsEntry 11 }

tmnxRadIsaPSStatsRxInvAcctStatus OBJECT-TYPE
    SYNTAX      Counter32
    MAX-ACCESS  read-only
    STATUS      current
    DESCRIPTION
        "The value of tmnxRadIsaPSStatsRxInvAcctStatus indicates the number of
         accounting packets received by this RADIUS Proxy Server that were
         rejected because they contained an invalid Acct-Status-Type attribute."
    REFERENCE
        "RFC 2866 RADIUS Accounting
         section 5.1 Acct-Status-Type."
    ::= { tmnxRadIsaPSStatsEntry 12 }

tmnxRadIsaPSStatsRxNoAcctStatus  OBJECT-TYPE
    SYNTAX      Counter32
    MAX-ACCESS  read-only
    STATUS      current
    DESCRIPTION
        "The value of tmnxRadIsaPSStatsRxNoAcctStatus indicates the number of
         accounting packets received by this RADIUS Proxy Server that were
         rejected because they contained no Acct-Status-Type attribute."
    REFERENCE
        "RFC 2866 RADIUS Accounting
         section 5.1 Acct-Status-Type."
    ::= { tmnxRadIsaPSStatsEntry 13 }

tmnxRadIsaPSStatsRxInvAcctAuth   OBJECT-TYPE
    SYNTAX      Counter32
    MAX-ACCESS  read-only
    STATUS      current
    DESCRIPTION
        "The value of tmnxRadIsaPSStatsRxInvAcctAuth indicates the number of
         accounting packets received by this RADIUS Proxy Server that were
         rejected because they contained an invalid Authenticator field."
    REFERENCE
        "RFC 2139 RADIUS Accounting
         section 3 Request Authenticator."
    ::= { tmnxRadIsaPSStatsEntry 14 }

tmnxRadIsaPSStatsRxInvMsgAuth    OBJECT-TYPE
    SYNTAX      Counter32
    MAX-ACCESS  read-only
    STATUS      current
    DESCRIPTION
        "The value of tmnxRadIsaPSStatsRxInvMsgAuth indicates the number of
         packets received by this RADIUS Proxy Server that were rejected
         because they contained an invalid Message-Authenticator attribute."
    REFERENCE
        "RFC 2869 RADIUS Extensions
         section 5.14 Message-Authenticator."
    ::= { tmnxRadIsaPSStatsEntry 15 }

tmnxRadIsaPSStatsRxMgmtOverload  OBJECT-TYPE
    SYNTAX      Counter32
    MAX-ACCESS  read-only
    STATUS      current
    DESCRIPTION
        "The value of tmnxRadIsaPSStatsRxMgmtOverload indicates the number of
         packets that were rejected by this RADIUS server because the ISA
         management core is not able to process any new RADIUS requests because
         of overload."
    ::= { tmnxRadIsaPSStatsEntry 16 }

tmnxRadIsaPSStatsTxAuthAck       OBJECT-TYPE
    SYNTAX      Counter32
    MAX-ACCESS  read-only
    STATUS      current
    DESCRIPTION
        "The value of tmnxRadIsaPSStatsTxAuthAck indicates the number of
         Access-Accept packets transmitted by this RADIUS Proxy Server."
    REFERENCE
        "RFC 2865 Remote Authentication Dial In User Service (RADIUS)
         section 4.2 Access-Accept."
    ::= { tmnxRadIsaPSStatsEntry 17 }

tmnxRadIsaPSStatsTxAuthReject    OBJECT-TYPE
    SYNTAX      Counter32
    MAX-ACCESS  read-only
    STATUS      current
    DESCRIPTION
        "The value of tmnxRadIsaPSStatsTxAuthReject indicates the number of
         Access-Reject packets transmitted by this RADIUS Proxy Server."
    REFERENCE
        "RFC 2865 Remote Authentication Dial In User Service (RADIUS)
         section 4.3 Access-Reject."
    ::= { tmnxRadIsaPSStatsEntry 18 }

tmnxRadIsaPSStatsTxAuthChallenge OBJECT-TYPE
    SYNTAX      Counter32
    MAX-ACCESS  read-only
    STATUS      current
    DESCRIPTION
        "The value of tmnxRadIsaPSStatsTxAuthChallenge indicates the number of
         Access-Challenge packets transmitted by this RADIUS Proxy Server."
    REFERENCE
        "RFC 2865 Remote Authentication Dial In User Service (RADIUS)
         section 4.4 Access-Challenge."
    ::= { tmnxRadIsaPSStatsEntry 19 }

tmnxRadIsaPSStatsTxAcctResponse  OBJECT-TYPE
    SYNTAX      Counter32
    MAX-ACCESS  read-only
    STATUS      current
    DESCRIPTION
        "The value of tmnxRadIsaPSStatsTxAcctResponse indicates the number of
         Accounting-Response packets transmitted by this RADIUS Proxy Server."
    REFERENCE
        "RFC 2866 RADIUS Accounting
         section 4.2 Accounting-Response."
    ::= { tmnxRadIsaPSStatsEntry 20 }

tmnxRadIsaPSStatsTxDropped       OBJECT-TYPE
    SYNTAX      Counter32
    MAX-ACCESS  read-only
    STATUS      current
    DESCRIPTION
        "The value of tmnxRadIsaPSStatsTxDropped indicates the number of
         packets dropped by this RADIUS Proxy Server before transmission."
    ::= { tmnxRadIsaPSStatsEntry 21 }

tmnxRadIsaPSStatsTxSrvTimeout    OBJECT-TYPE
    SYNTAX      Counter32
    MAX-ACCESS  read-only
    STATUS      current
    DESCRIPTION
        "The value of tmnxRadIsaPSStatsTxSrvTimeout indicates the number of
         packets that were dropped because the RADIUS servers have timed out."
    ::= { tmnxRadIsaPSStatsEntry 22 }

tmnxRadIsaPSStatsTxSrvInvAuth    OBJECT-TYPE
    SYNTAX      Counter32
    MAX-ACCESS  read-only
    STATUS      current
    DESCRIPTION
        "The value of tmnxRadIsaPSStatsTxSrvInvAuth indicates the number of
         packets that were dropped because the RADIUS server replied with a
         packet with an invalid response Authenticator."
    ::= { tmnxRadIsaPSStatsEntry 23 }

tmnxRadIsaPSStatsTxSrvInvMsgAuth OBJECT-TYPE
    SYNTAX      Counter32
    MAX-ACCESS  read-only
    STATUS      current
    DESCRIPTION
        "The value of tmnxRadIsaPSStatsTxSrvInvMsgAuth indicates the number of
         packets that were dropped because the RADIUS server replied with a
         packet with an invalid Message-Authenticator attribute."
    REFERENCE
        "RFC 2869 RADIUS Extensions
         section 5.14 Message-Authenticator."
    ::= { tmnxRadIsaPSStatsEntry 24 }

tmnxRadIsaPSStatsTxSrvInvAttr    OBJECT-TYPE
    SYNTAX      Counter32
    MAX-ACCESS  read-only
    STATUS      current
    DESCRIPTION
        "The value of tmnxRadIsaPSStatsTxSrvInvAttr indicates the number of
         packets that were dropped because the RADIUS server replied with a
         packet with an invalid attribute."
    REFERENCE
        "RFC 2865 Remote Authentication Dial In User Service (RADIUS)
         section 5 Attributes."
    ::= { tmnxRadIsaPSStatsEntry 25 }

tmnxRadIsaPSStatsTxSendFailure   OBJECT-TYPE
    SYNTAX      Counter32
    MAX-ACCESS  read-only
    STATUS      current
    DESCRIPTION
        "The value of tmnxRadIsaPSStatsTxSendFailure indicates the number of
         packets that were dropped by this RADIUS server because the packet
         could not get transmitted to one of the servers in the ISA RADIUS
         server policy."
    ::= { tmnxRadIsaPSStatsEntry 26 }

tmnxRadProxSrvTableCh            OBJECT-TYPE
    SYNTAX      TimeStamp
    MAX-ACCESS  read-only
    STATUS      current
    DESCRIPTION
        "The value of the object tmnxRadProxSrvTableCh indicates the value of
         sysUpTime at the time of the last modification of an entry in the
         tmnxRadProxSrvTable."
    ::= { tmnxRadiusObjs 100 }

tmnxRadProxSrvIfTableCh          OBJECT-TYPE
    SYNTAX      TimeStamp
    MAX-ACCESS  read-only
    STATUS      current
    DESCRIPTION
        "The value of the object tmnxRadProxSrvIfTableCh indicates the value of
         sysUpTime at the time of the last modification of an entry in the
         tmnxRadProxSrvIfTable."
    ::= { tmnxRadiusObjs 101 }

tmnxRadProxUsrToRspTableCh       OBJECT-TYPE
    SYNTAX      TimeStamp
    MAX-ACCESS  read-only
    STATUS      current
    DESCRIPTION
        "The value of the object tmnxRadProxUsrToRspTableCh indicates the value
         of sysUpTime at the time of the last modification of an entry in the
         tmnxRadProxUsrToRspTableCh."
    ::= { tmnxRadiusObjs 102 }

tmnxRadServTableCh               OBJECT-TYPE
    SYNTAX      TimeStamp
    MAX-ACCESS  read-only
    STATUS      current
    DESCRIPTION
        "The value of the object tmnxRadServTableCh indicates the value of
         sysUpTime at the time of the last modification of an entry in the
         tmnxRadServTable."
    ::= { tmnxRadiusObjs 120 }

tmnxRadSrvPlcyTableCh            OBJECT-TYPE
    SYNTAX      TimeStamp
    MAX-ACCESS  read-only
    STATUS      current
    DESCRIPTION
        "The value of the object tmnxRadSrvPlcyTableCh indicates the value of
         sysUpTime at the time of the last modification of an entry in the
         tmnxRadSrvPlcyTable."
    ::= { tmnxRadiusObjs 121 }

tmnxRadSrvPlcySrvTableCh         OBJECT-TYPE
    SYNTAX      TimeStamp
    MAX-ACCESS  read-only
    STATUS      current
    DESCRIPTION
        "The value of the object tmnxRadSrvPlcySrvTableCh indicates the value
         of sysUpTime at the time of the last modification of an entry in the
         tmnxRadSrvPlcySrvTable."
    ::= { tmnxRadiusObjs 122 }

tmnxRadScriptPlcyTableCh         OBJECT-TYPE
    SYNTAX      TimeStamp
    MAX-ACCESS  read-only
    STATUS      current
    DESCRIPTION
        "The value of the object tmnxRadScriptPlcyTableCh indicates the value
         of sysUpTime at the time of the last modification of an entry in the
         tmnxRadScriptPlcyTable."
    ::= { tmnxRadiusObjs 123 }

tmnxRadRouteDownlTableCh         OBJECT-TYPE
    SYNTAX      TimeStamp
    MAX-ACCESS  read-only
    STATUS      current
    DESCRIPTION
        "The value of the object tmnxRadRouteDownlTableCh indicates the value
         of sysUpTime at the time of the last modification of an entry in the
         tmnxRadRouteDownlTable."
    ::= { tmnxRadiusObjs 124 }

tmnxRadSysCfgObjsCh              OBJECT-TYPE
    SYNTAX      TimeStamp
    MAX-ACCESS  read-only
    STATUS      current
    DESCRIPTION
        "The value of the object tmnxRadSysCfgObjsCh indicates the value of
         sysUpTime at the time of the last modification of an object from
         tmnxRadSysCfgObjs."
    ::= { tmnxRadiusObjs 125 }

tmnxRadIsaPlcyTableCh            OBJECT-TYPE
    SYNTAX      TimeStamp
    MAX-ACCESS  read-only
    STATUS      current
    DESCRIPTION
        "The value of the object tmnxRadIsaPlcyTableCh indicates the value of
         sysUpTime at the time of the last modification of an entry in the
         tmnxRadIsaPlcyTable."
    ::= { tmnxRadiusObjs 126 }

tmnxRadIsaSrvTableCh             OBJECT-TYPE
    SYNTAX      TimeStamp
    MAX-ACCESS  read-only
    STATUS      current
    DESCRIPTION
        "The value of the object tmnxRadIsaSrvTableCh indicates the value of
         sysUpTime at the time of the last modification of an entry in the
         tmnxRadIsaSrvTable."
    ::= { tmnxRadiusObjs 127 }

tmnxRadSrvPlcyAcctOnOffTableCh   OBJECT-TYPE
    SYNTAX      TimeStamp
    MAX-ACCESS  read-only
    STATUS      current
    DESCRIPTION
        "The value of the object tmnxRadSrvPlcyAcctOnOffTableCh indicates the
         value of sysUpTime at the time of the last modification of an entry in
         the tmnxRadSrvPlcyAcctOnOffTable."
    ::= { tmnxRadiusObjs 128 }

tmnxRadSrvPlcyAcctOnOffGrpTbleCh OBJECT-TYPE
    SYNTAX      TimeStamp
    MAX-ACCESS  read-only
    STATUS      current
    DESCRIPTION
        "The value of the object tmnxRadSrvPlcyAcctOnOffGrpTbleCh indicates the
         value of sysUpTime at the time of the last modification of an entry in
         the tmnxRadSrvPlcyAcctOnOffGrpTable."
    ::= { tmnxRadiusObjs 129 }

tmnxRadiusNotificationObjects    OBJECT IDENTIFIER ::= { tmnxRadius 2 }

tmnxRadiusNotifyAddrType         OBJECT-TYPE
    SYNTAX      InetAddressType
    MAX-ACCESS  accessible-for-notify
    STATUS      current
    DESCRIPTION
        "The object tmnxRadiusNotifyAddrType is value that represents a type of
         Internet address."
    ::= { tmnxRadiusNotificationObjects 1 }

tmnxRadiusNotifyAddr             OBJECT-TYPE
    SYNTAX      InetAddress (SIZE (4|16))
    MAX-ACCESS  accessible-for-notify
    STATUS      current
    DESCRIPTION
        "The object tmnxRadiusNotifyAddr is a generic Internet address."
    ::= { tmnxRadiusNotificationObjects 2 }

tmnxRadiusAdditionalInfo         OBJECT-TYPE
    SYNTAX      DisplayString
    MAX-ACCESS  accessible-for-notify
    STATUS      current
    DESCRIPTION
        "The value of tmnxRadiusAdditionalInfo is a printable character string
         which contains information about the reason why the notification was
         generated."
    ::= { tmnxRadiusNotificationObjects 3 }

tmnxRadRouteDownlFailedReason    OBJECT-TYPE
    SYNTAX      INTEGER {
        parsing-radius-attr-failed (1),
        max-routes-reached         (2),
        rtm-update-failed          (3)
    }
    MAX-ACCESS  accessible-for-notify
    STATUS      current
    DESCRIPTION
        "The value of tmnxRadRouteDownlFailedReason indicates the reason why a
         route download process failed."
    ::= { tmnxRadiusNotificationObjects 4 }

tmnxRadProxConformance           OBJECT IDENTIFIER ::= { tmnxSRConfs 79 }

tmnxRadProxCompliances           OBJECT IDENTIFIER ::= { tmnxRadProxConformance 1 }

tmnxRadProxCompliance            MODULE-COMPLIANCE
    STATUS      obsolete
    DESCRIPTION
        "The compliance statement for management of RADIUS on Nokia 7xxx series
         systems."
    MODULE
        MANDATORY-GROUPS {
            tmnxRadProxSrvGroup,
            tmnxRadServGroup,
            tmnxRadScriptPlcyGroup,
            tmnxRadRouteDownlGroup
        }
    ::= { tmnxRadProxCompliances 1 }

tmnxRadiusNotifyCompliance       MODULE-COMPLIANCE
    STATUS      obsolete
    DESCRIPTION
        "The compliance statement for RADIUS notifications on Nokia SROS series
         systems."
    MODULE
        MANDATORY-GROUPS {
            tmnxRadiusNotifyGroup
        }
    ::= { tmnxRadProxCompliances 2 }

tmnxRadProxV11v0Compliance       MODULE-COMPLIANCE
    STATUS      obsolete
    DESCRIPTION
        "The compliance statement for management of RADIUS on Nokia 7xxx series
         systems release 11.0."
    MODULE
        MANDATORY-GROUPS {
            tmnxRadProxSrvV11v0Group,
            tmnxRadServGroup,
            tmnxRadServV11v0Group,
            tmnxRadScriptPlcyGroup,
            tmnxRadRouteDownlGroup,
            tmnxRadIsaAuthGroup,
            tmnxRadSrvPlcyAcctOnOffV11v0Grp
        }
    ::= { tmnxRadProxCompliances 3 }

tmnxRadiusV11v0NotifyCompliance  MODULE-COMPLIANCE
    STATUS      current
    DESCRIPTION
        "The compliance statement for RADIUS notifications on Nokia SROS series
         systems."
    MODULE
        MANDATORY-GROUPS {
            tmnxRadiusV11v0NotifyGroup
        }
    ::= { tmnxRadProxCompliances 4 }

tmnxRadProxV12v0Compliance       MODULE-COMPLIANCE
    STATUS      obsolete
    DESCRIPTION
        "The compliance statement for management of RADIUS on Nokia 7xxx series
         systems release 12.0."
    MODULE
        MANDATORY-GROUPS {
            tmnxRadProxSrvV11v0Group,
            tmnxRadProxSrvV12v0Group,
            tmnxRadServGroup,
            tmnxRadServV11v0Group,
            tmnxRadScriptPlcyGroup,
            tmnxRadRouteDownlGroup,
            tmnxRadIsaAuthGroup,
            tmnxRadSrvPlcyAcctOnOffV11v0Grp,
            tmnxRadServIpv6Group
        }
    ::= { tmnxRadProxCompliances 5 }

tmnxRadProxV13v0Compliance       MODULE-COMPLIANCE
    STATUS      obsolete
    DESCRIPTION
        "The compliance statement for management of RADIUS on Nokia 7xxx series
         systems release 13.0."
    MODULE
        MANDATORY-GROUPS {
            tmnxRadProxSrvV11v0Group,
            tmnxRadProxSrvV12v0Group,
            tmnxRadServGroup,
            tmnxRadServV11v0Group,
            tmnxRadScriptPlcyGroup,
            tmnxRadRouteDownlGroup,
            tmnxRadIsaAuthGroup,
            tmnxRadSrvPlcyAcctOnOffV11v0Grp,
            tmnxRadServIpv6Group,
            tmnxRadServHealthCheckGroup
        }
    ::= { tmnxRadProxCompliances 6 }

tmnxRadProxV14v0Compliance       MODULE-COMPLIANCE
    STATUS      obsolete
    DESCRIPTION
        "The compliance statement for management of RADIUS on Nokia 7xxx series
         systems release 14.0."
    MODULE
        MANDATORY-GROUPS {
            tmnxRadProxSrvV11v0Group,
            tmnxRadProxSrvV12v0Group,
            tmnxRadProxSrvV14v0Group,
            tmnxRadServGroup,
            tmnxRadServV11v0Group,
            tmnxRadScriptPlcyGroup,
            tmnxRadRouteDownlGroup,
            tmnxRadIsaAuthGroup,
            tmnxRadSrvPlcyAcctOnOffV11v0Grp,
            tmnxRadServIpv6Group,
            tmnxRadServHealthCheckGroup,
            tmnxRadSrvPlcyV14v0Group,
            tmnxRadIsaAuthV14v0Group
        }
    ::= { tmnxRadProxCompliances 7 }

tmnxRadProxV20v0Compliance       MODULE-COMPLIANCE
    STATUS      current
    DESCRIPTION
        "The compliance statement for management of RADIUS on Nokia 7xxx series
         systems release 20.0."
    MODULE
        MANDATORY-GROUPS {
            tmnxRadProxSrvV11v0Group,
            tmnxRadProxSrvV12v0Group,
            tmnxRadProxSrvV14v0Group,
            tmnxRadServGroup,
            tmnxRadServV11v0Group,
            tmnxRadScriptPlcyGroup,
            tmnxRadRouteDownlGroup,
            tmnxRadIsaAuthGroup,
            tmnxRadSrvPlcyAcctOnOffV11v0Grp,
            tmnxRadServIpv6Group,
            tmnxRadServHealthCheckGroup,
            tmnxRadSrvPlcyV14v0Group,
            tmnxRadIsaAuthV14v0Group,
            tmnxRadSrvPlcyV20v0Group,
            tmnxRadIsaAuthV22v0Group
        }
    ::= { tmnxRadProxCompliances 8 }

tmnxRadProxGroups                OBJECT IDENTIFIER ::= { tmnxRadProxConformance 2 }

tmnxRadProxSrvGroup              OBJECT-GROUP
    OBJECTS     {
        tmnxRadProxSrvTableCh,
        tmnxRadProxSrvLastCh,
        tmnxRadProxSrvRowStatus,
        tmnxRadProxSrvPurpose,
        tmnxRadProxSrvAdminState,
        tmnxRadProxSrvDescription,
        tmnxRadProxSrvSecret,
        tmnxRadProxSrvDefAuthSrvPlcy,
        tmnxRadProxSrvDefAccSrvPlcy,
        tmnxRadProxSrvCaching,
        tmnxRadProxSrvCacheKeyPktType,
        tmnxRadProxSrvCacheKeyAttrType,
        tmnxRadProxSrvCacheKeyVendorId,
        tmnxRadProxSrvCacheTimeout,
        tmnxRadProxSrvCacheTrackAcct,
        tmnxRadProxSrvSendAcctResponse,
        tmnxRadProxSrvLoadBalanceKey,
        tmnxRadProxSrvLoadBAttr1,
        tmnxRadProxSrvLoadBVendorId1,
        tmnxRadProxSrvLoadBAttr2,
        tmnxRadProxSrvLoadBVendorId2,
        tmnxRadProxSrvLoadBAttr3,
        tmnxRadProxSrvLoadBVendorId3,
        tmnxRadProxSrvLoadBAttr4,
        tmnxRadProxSrvLoadBVendorId4,
        tmnxRadProxSrvLoadBAttr5,
        tmnxRadProxSrvLoadBVendorId5,
        tmnxRadPSStatusCacheEntries,
        tmnxRadPSStatusCacheEntriesReg,
        tmnxRadPSStatsRxPacket,
        tmnxRadPSStatsRxAuthRequest,
        tmnxRadPSStatsRxAcctRequest,
        tmnxRadPSStatsRxDropped,
        tmnxRadPSStatsRxRetransmit,
        tmnxRadPSStatsRxAdminDown,
        tmnxRadPSStatsRxNoAaaPol,
        tmnxRadPSStatsRxNoLoadBKey,
        tmnxRadPSStatsRxInvLen,
        tmnxRadPSStatsRxInvCode,
        tmnxRadPSStatsRxInvAttr,
        tmnxRadPSStatsRxInvUserName,
        tmnxRadPSStatsRxInvPassword,
        tmnxRadPSStatsRxInvAcctStatusTyp,
        tmnxRadPSStatsRxNoAcctStatusTyp,
        tmnxRadPSStatsRxInvAcctAuth,
        tmnxRadPSStatsRxInvMsgAuth,
        tmnxRadPSStatsRxNoMemory,
        tmnxRadPSStatsRxUserOverload,
        tmnxRadPSStatsTxAuthAck,
        tmnxRadPSStatsTxAuthReject,
        tmnxRadPSStatsTxAuthChallenge,
        tmnxRadPSStatsTxAcctResponse,
        tmnxRadPSStatsTxDropped,
        tmnxRadPSStatsTxCacheNoKey,
        tmnxRadPSStatsTxCacheKeyTooLong,
        tmnxRadPSStatsTxCacheAttrTooLong,
        tmnxRadPSStatsTxCacheMaxEntries,
        tmnxRadPSStatsTxNoMemory,
        tmnxRadPSStatsTxServerTimeout,
        tmnxRadPSStatsTxServerAuthFail,
        tmnxRadPSStatsTxServerInvCode,
        tmnxRadPSStatsTxServerInvAttr,
        tmnxRadPSStatsTxUserOverload,
        tmnxRadPSStatsTxNoRadiusServer,
        tmnxRadPSStatsTxSendFailure,
        tmnxRadProxSrvIfTableCh,
        tmnxRadProxSrvIfRowStatus,
        tmnxRadProxSrvIfLastCh,
        tmnxRadProxUsrToRspTableCh,
        tmnxRadProxUsrToRspRowStatus,
        tmnxRadProxUsrToRspLastCh,
        tmnxRadProxUsrToRspMatchString,
        tmnxRadProxUsrToRspAuthSrvPlcy,
        tmnxRadProxUsrToRspAccSrvPlcy,
        tmnxRadProxSrvCacheAge,
        tmnxRadProxSrvCacheTimeLeft,
        tmnxRadProxSrvCacheRequestLength,
        tmnxRadProxSrvCacheAcceptLength,
        tmnxRadProxSrvCacheRegistered,
        tmnxRadServTableCh,
        tmnxRadServLastCh,
        tmnxRadServRowStatus,
        tmnxRadServAddrType,
        tmnxRadServAddr,
        tmnxRadServPort,
        tmnxRadServSecret,
        tmnxRadServDescription,
        tmnxRadServAcceptCoa,
        tmnxRadServCoaScriptPlcy,
        tmnxRadServPndRqLimit
    }
    STATUS      obsolete
    DESCRIPTION
        "The group of objects providing configuration of RADIUS Proxy servers
         on Nokia SROS series systems."
    ::= { tmnxRadProxGroups 1 }

tmnxRadServGroup                 OBJECT-GROUP
    OBJECTS     {
        tmnxRadSrvPlcyRowStatus,
        tmnxRadSrvPlcyLastCh,
        tmnxRadSrvPlcyDescription,
        tmnxRadSrvPlcyTimeout,
        tmnxRadSrvPlcyRetry,
        tmnxRadSrvPlcyDownTime,
        tmnxRadSrvPlcyRouter,
        tmnxRadSrvPlcySrcAddrType,
        tmnxRadSrvPlcySrcAddr,
        tmnxRadSrvPlcyAlgorithm,
        tmnxRadSrvPlcyStatsTxRequests,
        tmnxRadSrvPlcyStatsRxResponses,
        tmnxRadSrvPlcyStatsReqTimeout,
        tmnxRadSrvPlcyStatsReqSendFail,
        tmnxRadSrvPlcyStatsReqSendRetry,
        tmnxRadSrvPlcyStatsReqRejected,
        tmnxRadSrvPlcySrvRowStatus,
        tmnxRadSrvPlcySrvLastCh,
        tmnxRadSrvPlcySrvName,
        tmnxRadSrvPlcySrvOperState,
        tmnxRadSrvPlcySrvOutTime,
        tmnxRadSrvPlcySrvOvrldTime,
        tmnxRadSrvStatsTxRequests,
        tmnxRadSrvStatsRxResponses,
        tmnxRadSrvStatsReqTimeout,
        tmnxRadSrvStatsReqSendFailure,
        tmnxRadSrvStatsReqOvrldSendFail,
        tmnxRadSrvStatsReqPending,
        tmnxRadSrvStatsRespInvAuth,
        tmnxRadSrvStatsRespInvMsgAuth,
        tmnxRadSrvPlcyTableCh,
        tmnxRadSrvPlcySrvTableCh,
        tmnxRadSrvPlcyRequestScriptPlcy,
        tmnxRadSrvPlcyAcceptScriptPlcy,
        tmnxRadSysCfgCoAPort,
        tmnxRadSysCfgObjsCh
    }
    STATUS      current
    DESCRIPTION
        "The group of objects for the management of the RADIUS servers access
         on Nokia SROS series systems."
    ::= { tmnxRadProxGroups 2 }

tmnxRadScriptPlcyGroup           OBJECT-GROUP
    OBJECTS     {
        tmnxRadScriptPlcyTableCh,
        tmnxRadScriptPlcyRowStatus,
        tmnxRadScriptPlcyLastCh,
        tmnxRadScriptPlcyDescription,
        tmnxRadScriptPlcyOnFail,
        tmnxRadScriptPlcyPriURL,
        tmnxRadScriptPlcyPriAdminState,
        tmnxRadScriptPlcyPriOperState,
        tmnxRadScriptPlcySecURL,
        tmnxRadScriptPlcySecAdminState,
        tmnxRadScriptPlcySecOperState
    }
    STATUS      current
    DESCRIPTION
        "The group of objects for the management of the RADIUS script policies
         on Nokia SROS series systems."
    ::= { tmnxRadProxGroups 3 }

tmnxRadRouteDownlGroup           OBJECT-GROUP
    OBJECTS     {
        tmnxRadRouteDownlTableCh,
        tmnxRadRouteDownlRowStatus,
        tmnxRadRouteDownlLastCh,
        tmnxRadRouteDownlDescription,
        tmnxRadRouteDownlAdminState,
        tmnxRadRouteDownlRadServPlcy,
        tmnxRadRouteDownlDownloadIntvl,
        tmnxRadRouteDownlMinRetryIntvl,
        tmnxRadRouteDownlMaxRetryIntvl,
        tmnxRadRouteDownlDefaultMetric,
        tmnxRadRouteDownlDefaultTag,
        tmnxRadRouteDownlMaxRoutes,
        tmnxRadRouteDownlBaseUserName,
        tmnxRadRouteDownlPassword,
        tmnxRadRDStatsRxLastAccessReject,
        tmnxRadRDStatsRxLastAccessAccept,
        tmnxRadRDStatsTxLastAccessReq,
        tmnxRadRDStatsTxLastAccReqRetry,
        tmnxRadRDStatsRemainingDownlTime,
        tmnxRadRDStatsRemainingRetryTime,
        tmnxRadRDStatsRoutesReceived,
        tmnxRadRDStatsRxAccessReject,
        tmnxRadRDStatsRxAccessAccept,
        tmnxRadRDStatsRxAccessAcceptDrop,
        tmnxRadRDStatsTxAccessRequest,
        tmnxRadRDStatsTxAccessReqRetry,
        tmnxRadRDStatsDownloads,
        tmnxRadRDStatsRtmFailures
    }
    STATUS      current
    DESCRIPTION
        "The group of objects for the management of the RADIUS route
         downloaders on Nokia SROS series systems."
    ::= { tmnxRadProxGroups 4 }

tmnxRadIsaAuthGroup              OBJECT-GROUP
    OBJECTS     {
        tmnxRadIsaPlcyTableCh,
        tmnxRadIsaPlcyRowStatus,
        tmnxRadIsaPlcyLastCh,
        tmnxRadIsaPlcyDescription,
        tmnxRadIsaPlcyPassword,
        tmnxRadIsaPlcyAuthInclAttr,
        tmnxRadIsaPlcyAcctInclAttr,
        tmnxRadIsaPlcyUserNameFormat,
        tmnxRadIsaPlcyUserNameMacFormat,
        tmnxRadIsaPlcyNasIpAddressOrigin,
        tmnxRadIsaPlcySrvTimeout,
        tmnxRadIsaPlcySrvRetry,
        tmnxRadIsaPlcySrvVRtrID,
        tmnxRadIsaPlcySrvSrcAddrType,
        tmnxRadIsaPlcySrvSrcAddrStart,
        tmnxRadIsaPlcySrvSrcAddrEnd,
        tmnxRadIsaPlcySrvAlgorithm,
        tmnxRadIsaPlcyAcctUpdateTriggers,
        tmnxRadIsaSrvTableCh,
        tmnxRadIsaSrvRowStatus,
        tmnxRadIsaSrvLastMgmtChange,
        tmnxRadIsaSrvAdminState,
        tmnxRadIsaSrvAddrType,
        tmnxRadIsaSrvAddr,
        tmnxRadIsaSrvSecret,
        tmnxRadIsaSrvPurpose,
        tmnxRadIsaSrvAcctPort,
        tmnxRadIsaSrvAuthPort,
        tmnxRadIsaSrvCoaPort,
        tmnxRadIsaSrvStatSrcAddrType,
        tmnxRadIsaSrvStatSrcAddr,
        tmnxRadIsaSrvStatPurposeUp,
        tmnxRadIsaSrvStatsName,
        tmnxRadIsaSrvStatsValue,
        tmnxRadIsaSrvStatPurposeHoldDown
    }
    STATUS      current
    DESCRIPTION
        "The group of objects for the management of the RADIUS distributed on
         ISA cards on Nokia SROS series systems."
    ::= { tmnxRadProxGroups 5 }

tmnxRadSrvPlcyAcctOnOffV11v0Grp  OBJECT-GROUP
    OBJECTS     {
        tmnxRadSrvPlcyAcctLastChange,
        tmnxRadSrvPlcyAcctOnOffAdminSt,
        tmnxRadSrvPlcyAcctOnOffOperState,
        tmnxRadSrvPlcyAcctOnOffSessionId,
        tmnxRadSrvPlcyAcctOnOffStateChng,
        tmnxRadSrvPlcyBlockedState,
        tmnxRadSrvPlcyAcctPerformAction,
        tmnxRadSrvPlcyAcctmAcctOffCause,
        tmnxRadSrvPlcyAcctOnOffTrigger,
        tmnxRadSrvPlcyAcctOnOffSrvName,
        tmnxRadSrvPlcyAcctOnOffGroup,
        tmnxRadSrvPlcyAcctOnOffRetryCnt,
        tmnxRadSrvPlcyAcctReqScriptPlcy,
        tmnxRadSrvPlcyAuthReqScriptPlcy,
        tmnxRadSrvPlcyAcctOnOffGrpRowSt,
        tmnxRadSrvPlcyAcctOnOffGrpLastCh,
        tmnxRadSrvPlcyAcctOnOffGrpDescr,
        tmnxRadSrvPlcyAcctOnOffTableCh,
        tmnxRadSrvPlcyAcctOnOffGrpTbleCh,
        tmnxRadSrvPlcyAcctInterimMinItvl,
        tmnxRadSrvPlcyAcctInterimMaxItvl,
        tmnxRadSrvPlcyAcctInterimlifetim,
        tmnxRadSrvPlcyAcctStopMinItvl,
        tmnxRadSrvPlcyAcctStopMaxItvl,
        tmnxRadSrvPlcyAcctStoplifetim,
        tmnxRadSrvPlcyNbrAcctStopBuf,
        tmnxRadSrvPlcyNbrAcctInterimBuf,
        tmnxRadSrvPlcyNbrAcctStopDrop,
        tmnxRadSrvPlcyNbrAcctInterimDrop,
        tmnxRadSrvPlcyLastBufClean,
        tmnxRadSrvPlcyLastBufStatsClean
    }
    STATUS      current
    DESCRIPTION
        "The group of objects for the management of the RADIUS Acct On Off
         feature on Nokia SROS series systems."
    ::= { tmnxRadProxGroups 6 }

tmnxRadiusObsoletedV11v0Group    OBJECT-GROUP
    OBJECTS     {
        tmnxRadServPort,
        tmnxRadSrvPlcyRequestScriptPlcy
    }
    STATUS      current
    DESCRIPTION
        "The group services feature objects obsoleted in release 11.0 of Nokia
         SROS SR series systems."
    ::= { tmnxRadProxGroups 7 }

tmnxRadProxSrvV11v0Group         OBJECT-GROUP
    OBJECTS     {
        tmnxRadProxSrvTableCh,
        tmnxRadProxSrvLastCh,
        tmnxRadProxSrvRowStatus,
        tmnxRadProxSrvPurpose,
        tmnxRadProxSrvAdminState,
        tmnxRadProxSrvDescription,
        tmnxRadProxSrvSecret,
        tmnxRadProxSrvDefAuthSrvPlcy,
        tmnxRadProxSrvDefAccSrvPlcy,
        tmnxRadProxSrvCaching,
        tmnxRadProxSrvCacheKeyPktType,
        tmnxRadProxSrvCacheKeyAttrType,
        tmnxRadProxSrvCacheKeyVendorId,
        tmnxRadProxSrvCacheTimeout,
        tmnxRadProxSrvCacheTrackAcct,
        tmnxRadProxSrvSendAcctResponse,
        tmnxRadProxSrvLoadBalanceKey,
        tmnxRadProxSrvLoadBAttr1,
        tmnxRadProxSrvLoadBVendorId1,
        tmnxRadProxSrvLoadBAttr2,
        tmnxRadProxSrvLoadBVendorId2,
        tmnxRadProxSrvLoadBAttr3,
        tmnxRadProxSrvLoadBVendorId3,
        tmnxRadProxSrvLoadBAttr4,
        tmnxRadProxSrvLoadBVendorId4,
        tmnxRadProxSrvLoadBAttr5,
        tmnxRadProxSrvLoadBVendorId5,
        tmnxRadPSStatusCacheEntries,
        tmnxRadPSStatusCacheEntriesReg,
        tmnxRadPSStatsRxPacket,
        tmnxRadPSStatsRxAuthRequest,
        tmnxRadPSStatsRxAcctRequest,
        tmnxRadPSStatsRxDropped,
        tmnxRadPSStatsRxRetransmit,
        tmnxRadPSStatsRxAdminDown,
        tmnxRadPSStatsRxNoAaaPol,
        tmnxRadPSStatsRxNoLoadBKey,
        tmnxRadPSStatsRxInvLen,
        tmnxRadPSStatsRxInvCode,
        tmnxRadPSStatsRxInvAttr,
        tmnxRadPSStatsRxInvUserName,
        tmnxRadPSStatsRxInvPassword,
        tmnxRadPSStatsRxInvAcctStatusTyp,
        tmnxRadPSStatsRxNoAcctStatusTyp,
        tmnxRadPSStatsRxInvAcctAuth,
        tmnxRadPSStatsRxInvMsgAuth,
        tmnxRadPSStatsRxNoMemory,
        tmnxRadPSStatsRxUserOverload,
        tmnxRadPSStatsTxAuthAck,
        tmnxRadPSStatsTxAuthReject,
        tmnxRadPSStatsTxAuthChallenge,
        tmnxRadPSStatsTxAcctResponse,
        tmnxRadPSStatsTxDropped,
        tmnxRadPSStatsTxCacheNoKey,
        tmnxRadPSStatsTxCacheKeyTooLong,
        tmnxRadPSStatsTxCacheAttrTooLong,
        tmnxRadPSStatsTxCacheMaxEntries,
        tmnxRadPSStatsTxNoMemory,
        tmnxRadPSStatsTxServerTimeout,
        tmnxRadPSStatsTxServerAuthFail,
        tmnxRadPSStatsTxServerInvCode,
        tmnxRadPSStatsTxServerInvAttr,
        tmnxRadPSStatsTxUserOverload,
        tmnxRadPSStatsTxNoRadiusServer,
        tmnxRadPSStatsTxSendFailure,
        tmnxRadProxSrvIfTableCh,
        tmnxRadProxSrvIfRowStatus,
        tmnxRadProxSrvIfLastCh,
        tmnxRadProxUsrToRspTableCh,
        tmnxRadProxUsrToRspRowStatus,
        tmnxRadProxUsrToRspLastCh,
        tmnxRadProxUsrToRspMatchString,
        tmnxRadProxUsrToRspAuthSrvPlcy,
        tmnxRadProxUsrToRspAccSrvPlcy,
        tmnxRadProxSrvCacheAge,
        tmnxRadProxSrvCacheTimeLeft,
        tmnxRadProxSrvCacheRequestLength,
        tmnxRadProxSrvCacheAcceptLength,
        tmnxRadProxSrvCacheRegistered,
        tmnxRadServTableCh,
        tmnxRadServLastCh,
        tmnxRadServRowStatus,
        tmnxRadServAddrType,
        tmnxRadServAddr,
        tmnxRadServSecret,
        tmnxRadServDescription,
        tmnxRadServAcceptCoa,
        tmnxRadServCoaScriptPlcy,
        tmnxRadServPndRqLimit,
        tmnxRadServAuthPort,
        tmnxRadServAcctPort
    }
    STATUS      current
    DESCRIPTION
        "The group of objects providing configuration of RADIUS Proxy servers
         on Nokia SROS series systems."
    ::= { tmnxRadProxGroups 8 }

tmnxRadServV11v0Group            OBJECT-GROUP
    OBJECTS     {
        tmnxRadSrvPlcyStatsAuthFailed,
        tmnxRadSrvPlcyStatsRejectRatio,
        tmnxRadSrvPlcyStatsAcctFailed,
        tmnxRadSrvPlcyStatsSuccessRatio,
        tmnxRadSrvPlcyStatsFailureRatio,
        tmnxRadSrvStatsAuthFailed,
        tmnxRadSrvStatsAcctFailed,
        tmnxRadSrvStatsAuthAvgDelay10,
        tmnxRadSrvStatsAuthAvgDelay100,
        tmnxRadSrvStatsAuthAvgDelay1000,
        tmnxRadSrvStatsAuthAvgDelay10000,
        tmnxRadSrvStatsAcctAvgDelay10,
        tmnxRadSrvStatsAcctAvgDelay100,
        tmnxRadSrvStatsAcctAvgDelay1000,
        tmnxRadSrvStatsAcctAvgDelay10000
    }
    STATUS      current
    DESCRIPTION
        "The group of objects for the management of the RADIUS servers access
         on Nokia SROS release 11.0 series systems."
    ::= { tmnxRadProxGroups 9 }

tmnxRadProxSrvV12v0Group         OBJECT-GROUP
    OBJECTS     {
        tmnxRadProxSrvCacheTrackAuth,
        tmnxRadProxSrvCacheTrkDelHoldT,
        tmnxRadProxSrvCacheNasIpAddrTyp,
        tmnxRadProxSrvCacheNasIpAddr,
        tmnxRadProxSrvCacheNasIp6AddrTyp,
        tmnxRadProxSrvCacheNasIp6Addr,
        tmnxRadProxSrvCacheCalldStation,
        tmnxRadProxSrvAttrMatAttrType,
        tmnxRadProxSrvAttrMatVendorId,
        tmnxRadProxSrvWlanGwGroup,
        tmnxRadPSWlanGwLastCh,
        tmnxRadPSWlanGwIpv4AddrType,
        tmnxRadPSWlanGwIpv4Addr,
        tmnxRadPSWlanGwIpv6AddrType,
        tmnxRadPSWlanGwIpv6Addr,
        tmnxRadIsaPSStatsRxPacket,
        tmnxRadIsaPSStatsRxAuthRequest,
        tmnxRadIsaPSStatsRxAcctRequest,
        tmnxRadIsaPSStatsRxDropped,
        tmnxRadIsaPSStatsRxRetransmit,
        tmnxRadIsaPSStatsRxWrongPurpose,
        tmnxRadIsaPSStatsRxCacheNoUeMac,
        tmnxRadIsaPSStatsRxClientCtxtLim,
        tmnxRadIsaPSStatsRxNoAaaPol,
        tmnxRadIsaPSStatsRxInvAttr,
        tmnxRadIsaPSStatsRxInvPassword,
        tmnxRadIsaPSStatsRxInvAcctStatus,
        tmnxRadIsaPSStatsRxNoAcctStatus,
        tmnxRadIsaPSStatsRxInvAcctAuth,
        tmnxRadIsaPSStatsRxInvMsgAuth,
        tmnxRadIsaPSStatsRxMgmtOverload,
        tmnxRadIsaPSStatsTxAuthAck,
        tmnxRadIsaPSStatsTxAuthReject,
        tmnxRadIsaPSStatsTxAuthChallenge,
        tmnxRadIsaPSStatsTxAcctResponse,
        tmnxRadIsaPSStatsTxDropped,
        tmnxRadIsaPSStatsTxSrvTimeout,
        tmnxRadIsaPSStatsTxSrvInvAuth,
        tmnxRadIsaPSStatsTxSrvInvMsgAuth,
        tmnxRadIsaPSStatsTxSrvInvAttr,
        tmnxRadIsaPSStatsTxSendFailure,
        tmnxRadSrvPlcyPythonPolicy,
        tmnxRadProxSrvPythonPolicy,
        tmnxRadPSStatsRxDroppedByPython,
        tmnxRadPSStatsTxDroppedByPython,
        tmnxRadServPythonPolicy
    }
    STATUS      current
    DESCRIPTION
        "The group of objects providing configuration of RADIUS Proxy servers
         on Nokia SROS series systems added in release 12.0."
    ::= { tmnxRadProxGroups 10 }

tmnxRadServIpv6Group             OBJECT-GROUP
    OBJECTS     {
        tmnxRadSrvPlcyIpv6SrcAddrType,
        tmnxRadSrvPlcyIpv6SrcAddr
    }
    STATUS      current
    DESCRIPTION
        "The group of objects for the management of the RADIUS servers
         communication with IPv6 on Nokia SROS series systems."
    ::= { tmnxRadProxGroups 11 }

tmnxRadServHealthCheckGroup      OBJECT-GROUP
    OBJECTS     {
        tmnxRadSrvPlcyServerDownTimeout,
        tmnxRadSrvPlcyTestAccntChecking,
        tmnxRadSrvPlcyTestAccntIvl,
        tmnxRadSrvPlcyTestAccntUserName,
        tmnxRadSrvPlcyTestAccntPassword
    }
    STATUS      current
    DESCRIPTION
        "The group of objects for the management of the health status of the
         RADIUS servers on Nokia SROS series systems."
    ::= { tmnxRadProxGroups 12 }

tmnxRadSrvPlcyV14v0Group         OBJECT-GROUP
    OBJECTS     {
        tmnxRadSrvPlcyDisableStickiness
    }
    STATUS      current
    DESCRIPTION
        "The group of objects for the management of the release 14.0 features
         of the RADIUS servers on Nokia SROS series systems."
    ::= { tmnxRadProxGroups 13 }

tmnxRadIsaAuthV14v0Group         OBJECT-GROUP
    OBJECTS     {
        tmnxRadIsaPlcyPythonPolicy,
        tmnxRadIsaPlcyInterval,
        tmnxRadIsaPlcyRateLimit
    }
    STATUS      current
    DESCRIPTION
        "The group of objects for the management of the RADIUS distributed on
         ISA cards added in release 14.0 of Nokia SROS series systems."
    ::= { tmnxRadProxGroups 14 }

tmnxRadProxSrvV14v0Group         OBJECT-GROUP
    OBJECTS     {
        tmnxRadPSStatsTxDroppedByAuthC
    }
    STATUS      current
    DESCRIPTION
        "The group of objects providing configuration of RADIUS Proxy servers
         on Nokia SROS series systems added in release 14.0."
    ::= { tmnxRadProxGroups 15 }

tmnxRadSrvPlcyV20v0Group         OBJECT-GROUP
    OBJECTS     {
        tmnxRadSrvPlcyAcctStartMinItvl,
        tmnxRadSrvPlcyAcctStartMaxItvl,
        tmnxRadSrvPlcyAcctStartlifetim,
        tmnxRadSrvPlcyNbrAcctStartBuf,
        tmnxRadSrvPlcyNbrAcctStartDrop
    }
    STATUS      current
    DESCRIPTION
        "The group of objects for the management of the release 20.0 features
         of the RADIUS servers on Nokia SROS series systems."
    ::= { tmnxRadProxGroups 16 }

tmnxRadIsaAuthV22v0Group         OBJECT-GROUP
    OBJECTS     {
        tmnxRadIsaPlcySrvIp6SrcAddrType,
        tmnxRadIsaPlcySrvIp6SrcAddr,
        tmnxRadIsaPlcySrvIp6SrcPrefixLen,
        tmnxRadIsaPlcySrvIp6Mtu
    }
    STATUS      current
    DESCRIPTION
        "The group of objects for the management of the RADIUS distributed on
         ISA cards added in release 22.0 of Nokia SROS series systems."
    ::= { tmnxRadProxGroups 17 }

tmnxRadiusNotifyObjsGroup        OBJECT-GROUP
    OBJECTS     {
        tmnxRadiusNotifyAddrType,
        tmnxRadiusNotifyAddr,
        tmnxRadRouteDownlFailedReason,
        tmnxRadiusAdditionalInfo
    }
    STATUS      obsolete
    DESCRIPTION
        "The group of notification objects supporting RADIUS notifications on
         Nokia SROS series systems."
    ::= { tmnxRadProxGroups 99 }

tmnxRadiusNotifyGroup            NOTIFICATION-GROUP
    NOTIFICATIONS {
        tmnxRadSrvPlcySrvOperStateCh,
        tmnxRadRouteDownloadFailed
    }
    STATUS      obsolete
    DESCRIPTION
        "The group of notifications supporting RADIUS on Nokia SROS series
         systems."
    ::= { tmnxRadProxGroups 100 }

tmnxRadiusV11v0NotifyGroup       NOTIFICATION-GROUP
    NOTIFICATIONS {
        tmnxRadSrvPlcySrvOperStateCh,
        tmnxRadRouteDownloadFailed,
        tmnxRadAcctOnOngoing
    }
    STATUS      current
    DESCRIPTION
        "The group of notifications supporting RADIUS on Nokia SROS series
         systems."
    ::= { tmnxRadProxGroups 101 }

tmnxRadiusV11v0NotifyObjsGroup   OBJECT-GROUP
    OBJECTS     {
        tmnxRadiusNotifyAddrType,
        tmnxRadiusNotifyAddr,
        tmnxRadRouteDownlFailedReason,
        tmnxRadiusAdditionalInfo,
        tmnxRadSrvPlcyName
    }
    STATUS      current
    DESCRIPTION
        "The group of notification objects supporting RADIUS notifications on
         Nokia SROS series systems."
    ::= { tmnxRadProxGroups 102 }

tmnxRadProxNotifyPrefix          OBJECT IDENTIFIER ::= { tmnxSRNotifyPrefix 79 }

tmnxRadProxNotifications         OBJECT IDENTIFIER ::= { tmnxRadProxNotifyPrefix 0 }

tmnxRadSrvPlcySrvOperStateCh     NOTIFICATION-TYPE
    OBJECTS     {
        tmnxRadiusNotifyAddrType,
        tmnxRadiusNotifyAddr,
        tmnxRadSrvPlcySrvOperState
    }
    STATUS      current
    DESCRIPTION
        "[CAUSE] The tmnxRadSrvPlcySrvOperStateCh notification is sent when the
         value of the object tmnxRadSrvPlcySrvOperState changes.

         A RADIUS server is reported as 'outOfService' when the system does not
         receive timely responses from that server, according to the values of
         the objects tmnxRadSrvPlcyTimeout and tmnxRadSrvPlcyRetry.

         It is reported as 'overloaded' when the system crosses the
         pending-requests-limit for that server.

         [EFFECT] While the value of the object tmnxRadSrvPlcySrvOperState is equal
         to 'outOfService' or 'overloaded',
         - the corresponding RADIUS server is out of use;
         - traffic is sent to other RADIUS server(s) associated with the same
           policy, depending on the value of the object tmnxRadSrvPlcyAlgorithm.
         - after the time specified in the object tmnxRadSrvPlcyDownTime has elapsed,
           the state changes to 'unknown'.

         While the value of the object tmnxRadSrvPlcySrvOperState is equal to
         'unknown', the system sends traffic to the RADIUS server; if it
         replies timely, the operational state will change to 'inService',
         otherwise to 'outOfService'. [RECOVERY] The communication with the
         RADIUS server should recover after some time. Otherwise, or if it
         becomes out of use too frequently, the capacity of the RADIUS
         server(s) may have to be increased, or the values of the objects
         mentioned above may have to be adapted."
    ::= { tmnxRadProxNotifications 1 }

tmnxRadRouteDownloadFailed       NOTIFICATION-TYPE
    OBJECTS     {
        tmnxRadRouteDownlDownloadIntvl,
        tmnxRadRouteDownlFailedReason,
        tmnxRadiusAdditionalInfo
    }
    STATUS      current
    DESCRIPTION
        "[CAUSE] The tmnxRadRouteDownloadFailed notification is sent when a
         RADIUS route-download process failed.

         [EFFECT] The route-download process is delayed.

         [RECOVERY] The route-download process restarts after the time defined
         in tmnxRadRouteDownlDownloadIntvl."
    ::= { tmnxRadProxNotifications 2 }

tmnxRadAcctOnOngoing             NOTIFICATION-TYPE
    OBJECTS     {
        tmnxRadSrvPlcyName,
        tmnxRadSrvPlcyAcctOnOffRetryCnt,
        tmnxRadiusAdditionalInfo
    }
    STATUS      current
    DESCRIPTION
        "[CAUSE] The tmnxRadAcctOnOngoing notification is sent each time the
         acct-on client has sent 10 RADIUS Accounting-On messages without
         receiving any Ack.

         [EFFECT] RADIUS is unaware that the system is online.

         [RECOVERY] The system will keep on retrying indefinitely."
    ::= { tmnxRadProxNotifications 3 }

END
