TIMETRA-BSX-NG-MIB DEFINITIONS ::= BEGIN

IMPORTS
    VlanId, VlanIdOrNone
                                                         FROM IEEE8021-CFM-MIB
    InetAddress, InetAddressPrefixLength,
    InetAddressType
                                                         FROM INET-ADDRESS-MIB
    SnmpAdminString
                                                         FROM SNMP-FRAMEWORK-MIB
    MODULE-COMPLIANCE, NOTIFICATION-GROUP,
    OBJECT-GROUP
                                                         FROM SNMPv2-CONF
    Counter32, Counter64, Gauge32,
    Integer32, MODULE-IDENTITY,
    NOTIFICATION-TYPE, OBJECT-TYPE,
    Unsigned32
                                                         FROM SNMPv2-SMI
    DateAndTime, DisplayString, MacAddress,
    RowStatus, StorageType,
    TEXTUAL-CONVENTION, TimeStamp,
    TruthValue
                                                         FROM SNMPv2-TC
    TmnxHwIndexOrZero, TmnxSlotNumOrZero,
    tmnxChassisIndex
                                                         FROM TIMETRA-CHASSIS-MIB
    timetraSRMIBModules, tmnxSRConfs,
    tmnxSRNotifyPrefix, tmnxSRObjs
                                                         FROM TIMETRA-GLOBAL-MIB
    tmnxLogFileIdLogId,
    tmnxLogNotifyApInterval
                                                         FROM TIMETRA-LOG-MIB
    TmnxPortEncapType
                                                         FROM TIMETRA-PORT-MIB
    tFCName
                                                         FROM TIMETRA-QOS-MIB
    ServType
                                                         FROM TIMETRA-SERV-MIB
    TmnxMobApnOrZero, TmnxMobImei,
    TmnxMobImsiStr, TmnxMobMsisdn
                                                         FROM TIMETRA-TC-MG-MIB
    SdpBindId, ServiceAdminStatus,
    ServiceOperStatus, TAdaptationRule,
    TCIRRate, TDSCPNameOrEmpty, TEntryId,
    TFCNameOrEmpty, TIpProtocol,
    TItemDescription, TLNamedItemOrEmpty,
    TNamedItem, TNamedItemOrEmpty,
    TPIRRateOrZero, TPriorityOrDefault,
    TQueueId, TTcpUdpPort, TXLNamedItem,
    TXLNamedItemOrEmpty, TmnxActionType,
    TmnxAdminState, TmnxBsxAarpId,
    TmnxBsxAarpIdOrZero,
    TmnxBsxTransPrefPolicyId,
    TmnxBsxTransPrefPolicyIdOrZero,
    TmnxBsxTransitIpPolicyId,
    TmnxBsxTransitIpPolicyIdOrZero,
    TmnxDayOfWeek, TmnxDayOfWeekList,
    TmnxDisplayStringURL,
    TmnxEnabledDisabled, TmnxEncapVal,
    TmnxOperState, TmnxPortID, TmnxServId,
    TmnxSubRadServAlgorithm,
    TmnxSyslogFacility, TmnxSyslogSeverity,
    TmnxUdpPort, TmnxVRtrIDOrZero,
    TmnxWlanGwIsaGrpIdOrZero
                                                         FROM TIMETRA-TC-MIB
    ;

tmnxBsxNgMIBModule               MODULE-IDENTITY
    LAST-UPDATED "201701010000Z"
    ORGANIZATION "Nokia"
    CONTACT-INFO
        "Nokia SROS Support
         Web: http://www.nokia.com"
    DESCRIPTION
        "This document is the SNMP MIB module to manage and provision the
         Application Assurance capability of the Nokia SROS device.

         Copyright (c) 2010-2018 Nokia.  All rights reserved.
         Reproduction of this document is authorized on the condition that
         the foregoing copyright notice is included.

         This SNMP MIB module (Specification) embodies Nokia's
         proprietary intellectual property.  Nokia retains
         all title and ownership in the Specification, including any
         revisions.

         Nokia grants all interested parties a non-exclusive license to use and
         distribute an unmodified copy of this Specification in connection with
         management of Nokia products, and without fee, provided this copyright
         notice and license appear on all copies.

         This Specification is supplied 'as is', and Nokia makes no warranty,
         either express or implied, as to the use, operation, condition, or
         performance of the Specification."

    REVISION    "201701010000Z"
    DESCRIPTION
        "Rev 15.0               01 Jan 2017 00:00
         15.0 release of the TIMETRA-BSX-NG-MIB."

    REVISION    "201601010000Z"
    DESCRIPTION
        "Rev 14.0               01 Jan 2016 00:00
         14.0 release of the TIMETRA-BSX-NG-MIB."

    REVISION    "201501010000Z"
    DESCRIPTION
        "Rev 13.0               01 Jan 2015 00:00
         13.0 release of the TIMETRA-BSX-NG-MIB."

    REVISION    "201401010000Z"
    DESCRIPTION
        "Rev 12.0               01 Jan 2014 00:00
         12.0 release of the TIMETRA-BSX-NG-MIB."

    REVISION    "201102010000Z"
    DESCRIPTION
        "Rev 9.0                01 Feb 2011 00:00
         9.0 release of the TIMETRA-BSX-NG-MIB."

    REVISION    "200812030000Z"
    DESCRIPTION
        "Rev 7.0                03 Dec 2008 00:00
         7.0 release of the TIMETRA-BSX-NG-MIB."

    ::= { timetraSRMIBModules 63 }

TmnxBsxIsaAaGroupIndex           ::= TEXTUAL-CONVENTION
    STATUS      current
    DESCRIPTION
        "TmnxBsxIsaAaGroupIndex is an index of a group of BSX MDAs."
    SYNTAX      Unsigned32 (1..255)

TmnxBsxAaGrpPartIndex            ::= TEXTUAL-CONVENTION
    STATUS      current
    DESCRIPTION
        "TmnxBsxAaGrpPartIndex is an index of an Application Assurance
         partition within an Application Assurance group, and is a unique
         32-bit number encoded as follows.

            | 32   25 | 24    9 | 8      1 |
            +---------+---------+----------+
            |    0    | partidx |  groupidx|  Partition Index
            +---------+---------+----------+

            - groupidx represents a group of ISA MDAs and has
              a valid range from 1..255. The corresponding
              TmnxBsxIsaAaGroupIndex must already exist in the
              tmnxBsxIsaAaGrpTable.

            - partidx represents a partition within a group and
              has a valid range from 0..65535. A partition index
              of '0' represents group wide information."
    SYNTAX      Unsigned32 (1..16777215)

TmnxBsxAnlSourceLevel            ::= TEXTUAL-CONVENTION
    STATUS      current
    DESCRIPTION
        "TmnxBsxAnlSourceLevel specifies ANL Source level.

         Values:
           cell                   - ANL source level is a cell site in a
                                    Universal Mobile Telecommunications System.
           transport-network-link - ANL source level is one of the
                                    transport network links defined in a UMTS
                                    (Universal Mobile Telecommunications System).
           mac-vlan               - ANL source level is a virtual network as
                                    identified by MAC and VLAN identifiers."
    SYNTAX      INTEGER {
        cell                   (1),
        transport-network-link (2),
        mac-vlan               (3)
    }

TmnxBsxAnlSource                 ::= TEXTUAL-CONVENTION
    STATUS      current
    DESCRIPTION
        "The value of TmnxBsxAnlSource specifies the ANL source.

         Values:
           mobile-3g    - ANL source is 3G mobile network.
           access-point - ANL source is an access-point.
           uli-3gpp     - ANL source is a 3GPP user location."
    SYNTAX      INTEGER {
        mobile-3g    (0),
        access-point (1),
        uli-3gpp     (2)
    }

TmnxBsxCflowdExpOvdMode          ::= TEXTUAL-CONVENTION
    STATUS      current
    DESCRIPTION
        "The value of TmnxBsxCflowdExpOvdMode specifies the cflowd export override mode.
         Values:
             none   - no override
             mobile - mobile export format
             ifname-obfuscate - cflowd record interfaceName is obfuscated"
    SYNTAX      INTEGER {
        none             (0),
        mobile           (1),
        ifname-obfuscate (2)
    }

TmnxBsxFailToMode                ::= TEXTUAL-CONVENTION
    STATUS      current
    DESCRIPTION
        "TmnxBsxFailToMode specifies how traffic is handled when there are no
         available ISA-AA cards to handle the traffic."
    SYNTAX      INTEGER {
        failToWire (0),
        failToOpen (1)
    }

TmnxBsxPolicyVersion             ::= TEXTUAL-CONVENTION
    STATUS      current
    DESCRIPTION
        "TmnxBsxPolicyVersion specifies either the administrative or the
         operational version of the policy.  Configuration changes can
         only be made to the administrative version of the policy.  The
         operational copy is updated when a 'commit' operation is done."
    SYNTAX      INTEGER {
        admin (0),
        oper  (1)
    }

TmnxBsxDirection                 ::= TEXTUAL-CONVENTION
    STATUS      current
    DESCRIPTION
        "TmnxBsxDirection specifies either the subscriber to network 'sub2net'
         or the network to subscriber direction 'net2sub' or that the policy is
         to apply to 'both'."
    SYNTAX      INTEGER {
        sub2net (0),
        net2sub (1),
        both    (2)
    }

TmnxBsxPolicerType               ::= TEXTUAL-CONVENTION
    STATUS      current
    DESCRIPTION
        "TmnxBsxPolicerType specifies whether the policer is a bandwidth, flow
         rate, or a flow count policer in addition to the number of buckets
         used by the policer."
    SYNTAX      INTEGER {
        none                  (0),
        singleBucketBandwidth (1),
        dualBucketBandwidth   (2),
        flowRateLimit         (3),
        flowCountLimit        (4)
    }

TmnxBsxGranularity               ::= TEXTUAL-CONVENTION
    STATUS      current
    DESCRIPTION
        "TmnxBsxGranularity specifies the granularity of the policer.
         Values:
         'none'                    - No granularity has been configured.
         'system'                  - Create one policer instance per system.
         'subscriber'              - Create one policer instance per subscriber.
         'accessNetworkLocation'   - Create one policer instance per
                                     ANL (Access Network Location).
         'flow'                    - Create one policer instance per flow."
    SYNTAX      INTEGER {
        none                  (0),
        system                (1),
        subscriber            (2),
        accessNetworkLocation (3),
        flow                  (4)
    }

TmnxBsxPolicerAction             ::= TEXTUAL-CONVENTION
    STATUS      current
    DESCRIPTION
        "TmnxBsxPolicerAction specifies either 'permitDeny' to permit or deny
         packets or 'priorityMark' to mark to in or out of profile based on the
         outcome of the policer. Additional options of 'monitor' and
         'peakMeasure' are supported for the flow granularity bandwidth
         policer."
    SYNTAX      INTEGER {
        permitDeny   (0),
        priorityMark (1),
        monitor      (2),
        reserved3    (3)
    }

TmnxBsxBurstSize                 ::= TEXTUAL-CONVENTION
    STATUS      current
    DESCRIPTION
        "The amount of burst capacity (in kbytes) assigned to a policer."
    SYNTAX      Integer32 (0..131071)

TmnxBsxOperator                  ::= TEXTUAL-CONVENTION
    STATUS      current
    DESCRIPTION
        "TmnxBsxOperator specifies the type of comparison operator to perform
         on another associated member of the row of the table."
    SYNTAX      INTEGER {
        none  (0),
        eq    (1),
        neq   (2),
        lt    (3),
        gt    (4),
        range (5),
        gte   (6)
    }

TmnxBsxMdaRole                   ::= TEXTUAL-CONVENTION
    STATUS      current
    DESCRIPTION
        "TmnxBsxMdaRole specifies the configured role of an ISA-AA MDA.
         An MDA may take on the role of:
                primary (0) - configured within an ISA-AA group as a primary
                backup  (1) - configured within an ISA-AA group as a backup

                Multiple primary ISA-AA MDAs can be configured in an ISA-AA
                group, but only one backup."
    SYNTAX      INTEGER {
        primary (0),
        backup  (1)
    }

TmnxBsxMdaActivityState          ::= TEXTUAL-CONVENTION
    STATUS      current
    DESCRIPTION
        "TmnxBsxMdaActivityState specifies the working state of an ISA-AA MDA
         in a group. The Activity state may be one of:
               unavailable (0) - is not available to provide service
               active      (1) - is online and providing service
               standby     (2) - is online, but not providing service"
    SYNTAX      INTEGER {
        unavailable (0),
        active      (1),
        standby     (2)
    }

TmnxBsxAaSubscriberType          ::= TEXTUAL-CONVENTION
    STATUS      current
    DESCRIPTION
        "A value that represents a type (and thereby the format)
         of a TmnxBsxAaSubscriber.  The value can be one of
         the following:

         unknown     (0) - An unknown subscriber type is specified.

         esm         (1) - Enhanced Subscriber Management identity is
                           specified. This indicates that the format
                           of the TmnxBsxAaSubscriber is the Enhanced
                           Subscriber Management Subscriber as specified
                           in the TIMETRA-SUBSCRIBER-MGMT-MIB in
                           tmnxSubInfoSubIdent in the
                           tmnxSubscriberInfoTable.

                           The value of the TmnxBsxAaSubscriber is
                           a NON IMPLIED String of type TNamedItem.

         sap         (2) - A Service Access Point (SAP) is specified.
                           This indicates that the format of the
                           TmnxBsxAaSubscriber is an OCTET string
                           containing the Service Access Point (SAP)
                           subscriber as specified in the TIMETRA-SAP-MIB
                           including the sapPortId and sapEncapValue.

                           Octets   Contents
                           1-4       sapPortId (unsigned integer),
                           5-8       sapEncapValue (unsigned integer)

         spokeSdp    (3) - A spoke SDP binding is specified.
                           This indicates that the format of the
                           TmnxBsxAaSubscriber is an OCTET string
                           containing the spoke SDP Binding Id as
                           specified in the TIMETRA-SDP-MIB in
                           sdpBindId in the sdpBindTable.

         transit     (4) - A Transit subscriber is specified.
                           This indicates that the format of the
                           TmnxBsxAaSubscriber is an OCTET string
                           containing the transit subscriber name.

         mobile      (5) - A mobile subscriber is specified.
                           This indicates that the format of the
                           TmnxBsxAaSubscriber is an OCTET string
                           containing the mobile subscriber name.

         dsm         (6) - A Distributed Subscriber Management identity
                           is specified.
                           This indicates that the format of the
                           TmnxBsxAaSubscriber is an OCTET string
                           containing the distributed subscriber name.

                           The value of the TmnxBsxAaSubscriber is
                           a NON IMPLIED String of type TNamedItem.

         esmMac      (7) - Enhanced Subscriber Management MAC host identity is
                           specified. This indicates that the format
                           of the TmnxBsxAaSubscriber is an OCTET string
                           containing the esm-mac name."
    SYNTAX      INTEGER {
        unknown  (0),
        esm      (1),
        sap      (2),
        spokeSdp (3),
        transit  (4),
        mobile   (5),
        dsm      (6),
        esmMac   (7)
    }

TmnxBsxAaSubscriber              ::= TEXTUAL-CONVENTION
    STATUS      current
    DESCRIPTION
        "Denotes a generic Application Assurance Subscriber.

         An TmnxBsxAaSubscriber value is always interpreted within
         the context of an TmnxBsxAaSubscriberType value.  Every usage
         of the TmnxBsxAaSubscriber textual convention is required to
         specify the TmnxBsxAaSubscriberType object that provides the
         context.

         The value of an TmnxBsxAaSubscriber object must always be
         consistent with the value of the associated
         TmnxBsxAaSubscriberType object.  Attempts to set an
         TmnxBsxAaSubscriber object to a value inconsistent with the
         associated TmnxBsxAaSubscriberType will fail with an
         inconsistentValue error."
    SYNTAX      OCTET STRING (SIZE (0..32))

TmnxBsxStatAaAcctCfgType         ::= TEXTUAL-CONVENTION
    STATUS      current
    DESCRIPTION
        "Represents all of the possible statistics accounting types
         that can be configured within an Application Assurance
         group and partition. The various types are:
             unknown     - unknown statistics type
             protocol    - system wide protocol stats
             application - system wide application stats
             app-group   - system wide app-group stats
             aa-sub      - subscriber specific stats
             aa-sub-study-protocol    - special study protocol
                                        subscriber stats
             aa-sub-study-application - special study app subscriber
                                        stats"
    SYNTAX      INTEGER {
        unknown                  (0),
        protocol                 (1),
        application              (2),
        app-group                (3),
        aa-sub                   (4),
        aa-sub-study-protocol    (5),
        aa-sub-study-application (6)
    }

TmnxBsxAaStatType                ::= TEXTUAL-CONVENTION
    STATUS      current
    DESCRIPTION
        "Represents the various kinds of statistics
         objects used in Application Assurance.
         The various types are:
             unknown        - unknown
             protocol       - protocol based statistics
             application    - application based statistics
             app-group      - application group based statistics
             chargingGroup  - charging group based statistics"
    SYNTAX      INTEGER {
        unknown       (0),
        protocol      (1),
        application   (2),
        app-group     (3),
        chargingGroup (4)
    }

TmnxBsxAaStatExportMethod        ::= TEXTUAL-CONVENTION
    STATUS      current
    DESCRIPTION
        "Represents the method to use to export statistics
         in Application Assurance.  If no method is selected, stats are not exported.
         The various methods are:
             accountingPolicy       - use the accounting policy
             radiusAccountingPolicy - use the RADIUS accounting policy"
    SYNTAX      BITS {
        accountingPolicy       (0),
        radiusAccountingPolicy (1)
    }

TmnxBsxExprSubStringIndex        ::= TEXTUAL-CONVENTION
    STATUS      current
    DESCRIPTION
        "TmnxBsxExprSubStringIndex is an index of a list of expression
         substrings."
    SYNTAX      Integer32 (1..255)

TmnxBsxExprSubStringType         ::= TEXTUAL-CONVENTION
    STATUS      current
    DESCRIPTION
        "A value that represents a type (and thereby the
         expression substring) of a TmnxBsxExprSubString.
         The various types are:
             none               - no substring
             httpHost           - HTTP host substring
             httpUri            - HTTP URI (Uniform Resource Identifier)
                                  substring
             httpReferrer       - HTTP referrer substring
             sipUa              - SIP UA (User Agent) substring
             sipUri             - SIP URI (Uniform Resource Identifier)
                                  substring
             sipMt              - SIP RTP Media Type substring
             citrixApp          - Citrix application substring
             httpUserAgent      - HTTP User Agent substring
             h323ProductId      - H323 Product Id substring
             tlsCsOrgName       - TLS Certificate Subject Organization
                                  Name substring
             tlsCsCommonName    - TLS Certificate Subject Common
                                  Name substring
             rtspHost           - RTSP (Real Time Streaming Protocol) host
                                  substring
             rtspUri            - RTSP URI substring
             rtspUa             - RTSP UA substring
             rtmpPageHost       - RTMP (Real Time Messaging Protocol) page
                                  host substring
             rtmpPageUri        - RTMP page URI substring
             rtmpSwfHost        - RTMP SWF (Shock Wave Flash) host substring
             rtmpSwfUri         - RTMP SWF URI substring
             rtmpTcHost         - RTMP TC (Target Content) host substring
             rtmpTcUri          - RTMP TC URI substring
             dnsDomainName      - DNS domain name substring"
    SYNTAX      INTEGER {
        none            (0),
        httpHost        (1),
        httpUri         (2),
        httpReferrer    (3),
        sipUa           (4),
        sipUri          (5),
        sipMt           (6),
        citrixApp       (7),
        httpUserAgent   (8),
        h323ProductId   (9),
        tlsCsOrgName    (10),
        tlsCsCommonName (11),
        rtspHost        (12),
        rtspUri         (13),
        rtspUa          (14),
        rtmpPageHost    (15),
        rtmpPageUri     (16),
        rtmpSwfHost     (17),
        rtmpSwfUri      (18),
        rtmpTcHost      (19),
        rtmpTcUri       (20),
        dnsDomainName   (21)
    }

TmnxBsxExprSubString             ::= TEXTUAL-CONVENTION
    STATUS      current
    DESCRIPTION
        "Denotes a printable ASCII substring used as input to an application
         assurance filter match criteria object. The following syntax is
         permitted within the substring to define the pattern match criteria:

         ^<substring>* - matches when <substring> is at the beginning
                         of the object.
         *<substring>* - matches when <substring> is at any place
                         within the object.
         *<substring>$ - matches when <substring> is at the end
                         of the object.
         ^<substring>$ - matches when <substring> is the entire object.

         Rules for <substring> characters:
         ---------------------------------
         - <substring> must contain printable ASCII characters.
         - <substring> must not contain the 'double quote' character
         - <substring> match is case insensitive by default.
         - <substring> may contain the following meta-characters:
         *             - matches zero or more of any character
                         (limit of 1 per substring)
         \*            - matches the asterisk character
         \.            - matches any single character
         \d            - matches any single decimal digit [0-9]
         \xYY          - matches a single byte with hex value 0xYY
         \I            - forces case sensitivity (by default,
                         the expression match are case insensitive),
                         the \I can be specified anywhere between
                         the leading [^*] and trailing [$*]"
    SYNTAX      DisplayString (SIZE (0..255))

TmnxBsxFirstPacketPolicy         ::= TEXTUAL-CONVENTION
    STATUS      current
    DESCRIPTION
        "TmnxBsxFirstPacketPolicy specifies the policy to apply to
         the first packet within a flow. The First Packet Policy
         may be one of:
           none (0)                   - there is no policy to apply
           first-packet-trusted   (1) - the first packet is trusted
           first-packet-validate  (2) - the first packet is validated"
    SYNTAX      INTEGER {
        none                  (0),
        first-packet-trusted  (1),
        first-packet-validate (2)
    }

TmnxBsxActionStatus              ::= TEXTUAL-CONVENTION
    STATUS      current
    DESCRIPTION
        "TmnxBsxActionStatus specifies the status of
         an ISA-AA action. The status may be one of:
            none       (0)    - no action
            start      (1)    - action has started
            stop       (2)    - action has stopped"
    SYNTAX      INTEGER {
        none  (0),
        start (1),
        stop  (2)
    }

TmnxBsxAdminCtrl                 ::= TEXTUAL-CONVENTION
    STATUS      current
    DESCRIPTION
        "TmnxBsxAdminCtrl specifies the copying and
         editing of tmnxBsxPolicyObjs tables from one instance
         of a policy version to another. The admin
         control may be one of:
               none       (1) - no policies being edited
               initialize (2) - policies being edited
               commit     (3) - policies committed"
    SYNTAX      INTEGER {
        none       (1),
        initialize (2),
        commit     (3)
    }

TmnxBsxCustProtExprSubString     ::= TEXTUAL-CONVENTION
    STATUS      current
    DESCRIPTION
        "Denotes a printable ASCII substring used as input to an application
         assurance custom protocol match criteria object.

         Rules for <substring> characters:
         ---------------------------------

         - <substring> must contain printable ASCII characters.
         - <substring> must not contain the 'double quote' character
                       or the ' ' (space) character on its own.
         - <substring> match is case sensitive.
         - <substring> must not include any Regular Expression
                       meta-characters.

         - The '\' character is used as an ESCAPE sequence.
         - the following ESCAPE sequences are permitted within
           the <substring>:

         character to match     <substring> input
         ------------------    ------------------
         \                        \
         Hexadecimal Octet YY     \xYY

         Note: A <substring> that uses the '\' (backslash) ESCAPE character
         which is not followed by a '\' or '\x' and a 2-digit hex octet is not
         valid."
    SYNTAX      DisplayString (SIZE (0..255))

TmnxBsxProtocolDirection         ::= TEXTUAL-CONVENTION
    STATUS      current
    DESCRIPTION
        "TmnxBsxProtocolDirection specifies the direction
         to match for a protocol. The protocol direction
         may be one of:
             none          (0) - no direction specified
             client2server (1) - client to server direction
             server2client (2) - server to client direction
             any           (3) - any direction"
    SYNTAX      INTEGER {
        none          (0),
        client2server (1),
        server2client (2),
        any           (3)
    }

TmnxBsxLoadBalanceStatus         ::= TEXTUAL-CONVENTION
    STATUS      current
    DESCRIPTION
        "TmnxBsxLoadBalanceStatus specifies the status of
         a load-balance operation in an ISA-AA group.
         The status may be one of:
            balancing   (0)   - load-balance in progress
            complete    (1)   - load-balance completed"
    SYNTAX      INTEGER {
        balancing (0),
        complete  (1)
    }

TmnxBsxCflowdExpType             ::= TEXTUAL-CONVENTION
    STATUS      current
    DESCRIPTION
        "Represents the various kinds of statistics
         which can be exported using Cflowd in Application
         Assurance.
         The various types are:
             none           - no statistics exported
             volume         - volume statistics
             tcpPerformance - TCP performance statistics
             comprehensive  - comprehensive statistics"
    SYNTAX      INTEGER {
        none           (0),
        volume         (1),
        tcpPerformance (2),
        comprehensive  (4)
    }

TmnxBsxCflowdPerfMeasType        ::= TEXTUAL-CONVENTION
    STATUS      current
    DESCRIPTION
        "Represents the various kinds of performance measurement or statistics
         types which can be exported using Cflowd in Application Assurance.
         The various types are:
             none          - no measurement type specified
             tcp           - TCP performance measurements
             comprehensive - comprehensive statistics"
    SYNTAX      INTEGER {
        none          (0),
        tcp           (1),
        comprehensive (3)
    }

TmnxBsxCflowdRecTemplate         ::= TEXTUAL-CONVENTION
    STATUS      current
    DESCRIPTION
        "Represents the various kinds of templates that can be exported using
         Cflowd in Application Assurance.
         The various types are:
             volume        - volume fields
             tcp           - TCP performance fields
             comprehensive - comprehensive fields"
    SYNTAX      INTEGER {
        volume        (1),
        tcp           (2),
        comprehensive (6)
    }

TmnxBsxCflowdFieldSelType        ::= TEXTUAL-CONVENTION
    STATUS      current
    DESCRIPTION
        "Represents the kind of cflowd template field configuration.
         The various kinds are:
             legacy         - cflowd template fields are chosen by the ISA.
             dynamic        - cflowd template fields are configurable by the operator.
                              With this mode some fields are not configurable yet are sent
                              in addition to the ones chosen by the user."
    SYNTAX      INTEGER {
        legacy  (0),
        dynamic (1)
    }

TmnxBsxWebServiceCategoryId      ::= TEXTUAL-CONVENTION
    STATUS      current
    DESCRIPTION
        "TmnxBsxWebServiceCategoryId is a identifier associated with a URL
         category. Categories are defined by various URL classification
         products."
    SYNTAX      Unsigned32 (0..65535)

TmnxBsxWebServiceCategoryIdKey   ::= TEXTUAL-CONVENTION
    STATUS      current
    DESCRIPTION
        "TmnxBsxWebServiceCategoryId is a identifier associated with a URL
         category. Categories are defined by various URL classification
         products."
    SYNTAX      Unsigned32 (1..65535)

TmnxBsxWebServClassifierId       ::= TEXTUAL-CONVENTION
    STATUS      current
    DESCRIPTION
        "Represents the various category set Identifiers that represents web service classification products.
         The various category sets are:
             none            - no web-service defined
             web-service-1   - web-service provided by Webtitan, API version 1"
    SYNTAX      INTEGER {
        none          (0),
        web-service-1 (1)
    }

TmnxBsxWebServClassifierIdKey    ::= TEXTUAL-CONVENTION
    STATUS      current
    DESCRIPTION
        "Represents the various category sets provided by web service classification products.
         The various category sets are:
             web-service-1   - web-service provided by Webtitan, API version 1"
    SYNTAX      INTEGER {
        web-service-1 (1)
    }

TmnxBsxWebServCategorySetIdKey   ::= TEXTUAL-CONVENTION
    STATUS      current
    DESCRIPTION
        "Represents the various category set Ids supported by one or more
         supported web service classification products."
    SYNTAX      Unsigned32 (1..65535)

TmnxBsxWebServCategorySetId      ::= TEXTUAL-CONVENTION
    STATUS      current
    DESCRIPTION
        "Represents the various category set Ids supported by one or more
         supported web service classification products."
    SYNTAX      Unsigned32 (0..65535)

TmnxBsxFullyQualDomainName       ::= TEXTUAL-CONVENTION
    STATUS      current
    DESCRIPTION
        "A Fully Qualified Domain Name."
    SYNTAX      DisplayString (SIZE (0..255))

TmnxBsxAaSubStatsInterval        ::= TEXTUAL-CONVENTION
    STATUS      current
    DESCRIPTION
        "Represents the various types of statistics intervals for Application
         Assurance subscribers.

         The various types are:
             unknown   - specifies an unknown statistics interval
             realtime  - specifies that the statistics retrieved include the
                         sum of the statistics from the previous collection
                         windows, the statistics for any closed flows since the
                         last collection window, and the statistics accumulated
                         from any currently open flows.
             snapshot  - specifies that the statistics retrieved include the
                         sum of the statistics from the previous collection
                         windows, and the statistics for any closed flows since
                         the last collection window."
    SYNTAX      INTEGER {
        unknown  (0),
        realtime (1),
        snapshot (2)
    }

TmnxBsxUrlFilterDefaultAction    ::= TEXTUAL-CONVENTION
    STATUS      current
    DESCRIPTION
        "TmnxBsxUrlFilterDefaultAction specifies the default action to take
         when the associated URL filter type (deny-list, icap, or web service)
         is out of service.

         The default actions are:
         'allow'               - allow all requests.
         'blockRedirectHttp'   - block and redirect requests.
         'blockAll'            - block all requests."
    SYNTAX      INTEGER {
        allow             (0),
        blockHttpRedirect (1),
        blockAll          (2)
    }

TmnxBsxAaSubAcctLossReason       ::= TEXTUAL-CONVENTION
    STATUS      current
    DESCRIPTION
        "Represents the reason for a loss of Application Assurance
         subscriber accounting statistics.
         The various reasons are:
             noLoss         - no accounting statistics have been lost.
             acctInvlExpiry - accounting interval has expired"
    SYNTAX      INTEGER {
        noLoss         (0),
        acctInvlExpiry (1)
    }

TmnxBsxAaSubAsoValDerivedFrom    ::= TEXTUAL-CONVENTION
    STATUS      current
    DESCRIPTION
        "TmnxBsxAaSubAsoValDerivedFrom specifies from where the characteristic
         value is being derived from for the Application Assurance subscriber.
         The characteristic value can be derived from Application Service
         Option (ASO) defaults, application profiles, or policy-overrides."
    SYNTAX      INTEGER {
        none            (0),
        asoDefault      (1),
        appProfile      (2),
        override        (3),
        dynamicOverride (4)
    }

TmnxBsxAaSubPolicerResStatus     ::= TEXTUAL-CONVENTION
    STATUS      current
    DESCRIPTION
        "TmnxBsxAaSubPolicerResStatus specifies the status
         of policer resources being applied to an
         Application Assurance subscriber.
         The status may be one of:
            none      (0)
            okay      (1)   - policer resources are not exceeded
            unknown   (2)   - policer resources are unknown
            exceeded  (3)   - policer resources are exceeded"
    SYNTAX      INTEGER {
        none     (0),
        okay     (1),
        unknown  (2),
        exceeded (3)
    }

TmnxBsxStatIsaAaCfgType          ::= TEXTUAL-CONVENTION
    STATUS      current
    DESCRIPTION
        "Represents all of the possible statistics accounting types
         that can be configured at the ISA-AA group level.
         The various types are:
           unknown       - unknown statistics type
           aaPerformance - AA performance statistics"
    SYNTAX      INTEGER {
        unknown       (0),
        aaPerformance (1)
    }

TmnxBsxTetherTtlMonitorLevel     ::= TEXTUAL-CONVENTION
    STATUS      current
    DESCRIPTION
        "Represents the set of TCP or UDP protocols in which AA uses the TTL to
         help determine the tethering state of a flow or subscriber."
    SYNTAX      INTEGER {
        standard (0),
        all      (1)
    }

TmnxBsxTransitSubOrigin          ::= TEXTUAL-CONVENTION
    STATUS      current
    DESCRIPTION
        "Represents the possible ways in which the transit AA subscriber was
         created. The various origins of a transit subscriber are:

           static       - statically provisioned
           dhcp         - dynamically learned via DHCP
           radius       - dynamically learned via RADIUS
           autoSeenIp   - automatically created via Seen IP
           diameter     - dynamically learned via Diameter

         A transit subscriber may have more than one origin. The absence of any
         bits indicates a subscriber of unknown origin."
    SYNTAX      BITS {
        static     (0),
        dhcp       (1),
        radius     (2),
        autoSeenIp (3),
        diameter   (4)
    }

TmnxBsxTListAttribType           ::= TEXTUAL-CONVENTION
    STATUS      current
    DESCRIPTION
        "Represents the different types of value a tagged list attribute can
         possess. The various types of values are:

            none(0)        - no value
            uint(1)        - an unsigned integer
            string(2)      - a displayable string
            truthValue(3)  - a truth value"
    SYNTAX      INTEGER {
        none       (0),
        uint       (1),
        string     (2),
        truthValue (3)
    }

TmnxBsxTListAttribValue          ::= TEXTUAL-CONVENTION
    STATUS      current
    DESCRIPTION
        "Represents the different values of a tagged list attribute.

         A TmnxBsxTListAttribValue is always interpreted within the context of
         a TmnxBsxTListAttribType. Every usage of TmnxBsxTListAttribValue is
         required to specify the TmnxBsxTListAttribType that provides that
         context.

         If the TmnxBsxTListAttribType is 'uint(1)' then the numerical value is
         stored in the first 4 bytes of the octet string as a 32-bit value.

         If the TmnxBsxTListAttribType is a 'string(2)' then string is packed
         into TmnxBsxTListAttribValue.

         If the TmnxBsxTListAttribType is a 'truthValue(3)' then the numerical
         value, 1 for true or 2 for false, is stored in the first byte of the
         octet string."
    SYNTAX      OCTET STRING (SIZE (0..80))

TmnxBsxAqpHttpRedirFlowType      ::= TEXTUAL-CONVENTION
    STATUS      current
    DESCRIPTION
        "Represents the different types of flows that can be redirected. The
         different types of flows are:

            none(0)             - no flows
            droppedFlows(1)     - dropped flows
            admittedFlows(2)    - admitted flows"
    SYNTAX      INTEGER {
        none          (0),
        droppedFlows  (1),
        admittedFlows (2)
    }

TmnxBsxCflowdExpFieldExport      ::= TEXTUAL-CONVENTION
    STATUS      current
    DESCRIPTION
        "Represents the cflowd field export template types. The different
         template types are:

            volume         - volume template
            tcpPerformance - TCP performance template
            comprehensive  - comprehensive  template
            pgwEdr         - PGW EDR template"
    SYNTAX      BITS {
        volume         (0),
        tcpPerformance (1),
        reserved2      (2),
        reserved3      (3),
        reserved4      (4),
        comprehensive  (5),
        pgwEdr         (6)
    }

TmnxBsxCflowdSubscaleType        ::= TEXTUAL-CONVENTION
    STATUS      current
    DESCRIPTION
        "Represents the aa group subscale types the field can be used. The
         different subscale types are:

            mobile      - mobile include all mobile related subscale
            residential - residential include all residential related subscales
            vpn         - vpn include all vpn related subscales
            lightWeight - lightWeight include light-weight related subscales"
    SYNTAX      BITS {
        mobile      (0),
        residential (1),
        vpn         (2),
        lightWeight (3)
    }

TmnxBsxCflowdEncryption          ::= TEXTUAL-CONVENTION
    STATUS      current
    DESCRIPTION
        "Represents the encryption type to use on cflowd record field. The
         different encryption types are:

            none(0)   - no encryption is done the field
            sha1(1)   - use SHA-1 to encrypt the field
            sha256(2) - use SHA-256 to encrypt the field field
            aes128(3) - use AES-128 to encrypt the field
            aes256(4) - use AES-256 to encrypt the field"
    SYNTAX      INTEGER {
        none   (0),
        sha1   (1),
        sha256 (2),
        aes128 (3),
        aes256 (4)
    }

TmnxBsxCflowdEncrGrpType         ::= TEXTUAL-CONVENTION
    STATUS      current
    DESCRIPTION
        "Represents the cflowd field encryption group type associated with the
         encrypted field. The different Id types are:

            none - none
            msisdn - MSISDN
            imsi   - IMSI
            imei   - IMEI"
    SYNTAX      INTEGER {
        none   (0),
        msisdn (1),
        imsi   (2),
        imei   (3)
    }

TmnxBsxAarpInstState             ::= TEXTUAL-CONVENTION
    STATUS      current
    DESCRIPTION
        "Represents the different states of an Application Assurance Redundancy
         Protocol (AARP) instance performing asymmetry removal. Asymmetry
         refers to a situation where the two directions of traffic for a
         specific flow take different paths through the network. Asymmetry
         removal ensures that packets for each flow and all flows for each
         subscriber are processed by the same ISA-AA.

         The states are:

            standAlone(0)       - AARP instance is handling AA independently
                                  from the peer. Traffic asymmetry is not
                                  removed. Caused by a configuration problem
                                  or failure in asymmetry removal resources.
            remote(1)           - AARP instance is sending all AA traffic to
                                  the remote peer. Traffic asymmetry is removed.
                                  Locally unable to perform AA and act as a
                                  backup due to failure of a local AA-ISA.
            master(2)           - AARP instance is handling AA locally for local
                                  traffic and remote traffic from the peer.
                                  Traffic asymmetry is removed.
            backup(3)           - AARP instance is sending all AA traffic to the
                                  remote peer. Traffic asymmetry is removed.
                                  Locally ready to take over."
    SYNTAX      INTEGER {
        standAlone (0),
        remote     (1),
        master     (2),
        backup     (3)
    }

TmnxBsxAarpInstOperFlags         ::= TEXTUAL-CONVENTION
    STATUS      current
    DESCRIPTION
        "TmnxBsxAarpInstOperFlags represents the different conditions that
         affect the operating status of an AARP instance.

         The bit values are:
            adminDown(0)                - AARP instance is administratively
                                          down.
            noSubConfigd(1)             - no 'dualHomed(2)' subscriber reference
                                          configured against the AARP instance.
            peerDown(2)                 - no communication with peer AARP
                                          instance.
            peerAarpDown(3)             - MC-CTL link is up, but AARP layer
                                          protocol interaction with peer AARP
                                          instance is not established.
            subTypeMismatch(4)          - mismatch detected in the subscriber
                                          types between peer AARP instances.
            subDown(5)                  - 'dualHomed(2)' subscriber reference
                                          is operationally down.
            shuntsDown(6)               - one of the shunts referenced by the
                                          AARP instance is down.
            divertCapDown(7)            - divert to AA not possible - divert
                                          capability is down.
            appProfNoDivert(8)          - app-profile used by the 'dualHomed(2)'
                                          subscriber reference has 'no divert'
                                          set.
            subSidePipeMismatch(9)      - mismatch detected in the
                                          subscriber-side pipe between AARP
                                          instances.
            subSideIfMismatch(10)       - mismatch detected in the
                                          subscriber-side interface between
                                          peer AARP instances.
            netSidePipeMistmatch(11)    - mismatch detected in the network-side
                                          pipe between AARP instances.
            netSideIfMismatch(12)       - mismatch detected in in the network-
                                          side interface between peer AARP
                                          instances.
            unsupportedIoms(13)         - IOMs which do not support AARP have
                                          been detected.
            configMismatch(14)          - indicates that AARP is down because
                                          of a configuration mismatch between
                                          peer AARP instances.
            noSecondaryEps(15)          - indicates that single-node AARP is
                                          down because no secondary endpoints
                                          exist for that AARP instance."
    SYNTAX      BITS {
        adminDown           (0),
        noSubConfigd        (1),
        peerDown            (2),
        peerAarpDown        (3),
        subTypeMismatch     (4),
        subDown             (5),
        shuntsDown          (6),
        divertCapDown       (7),
        appProfNoDivert     (8),
        subSidePipeMismatch (9),
        subSideIfMismatch   (10),
        netSidePipeMismatch (11),
        netSideIfMismatch   (12),
        unsupportedIoms     (13),
        configMismatch      (14),
        noSecondaryEps      (15)
    }

TmnxBsxAarpCommand               ::= TEXTUAL-CONVENTION
    STATUS      current
    DESCRIPTION
        "TmnxBsxAarpCommand represents the different commands that can be
         performed on an AARP instance.

         The command values are:

            noCmd           (0) - 'noCmd(0)' is returned by a read request
                                  when no control command has been written
                                  to the object since initialization. 'noCmd(0)'
                                  should not be used as a value for a write
                                  operation - the write operation will
                                  fail.
            forceEvaluate   (1) - the command triggers a re-evaluation of the
                                  preferred AARP instance."
    SYNTAX      INTEGER {
        noCmd         (0),
        forceEvaluate (1)
    }

TmnxBsxAarpServPointRole         ::= TEXTUAL-CONVENTION
    STATUS      current
    DESCRIPTION
        "TmnxBsxAarpServPointRole represents the different roles that an AARP
         instance service point can assume.

         The roles of service points are:
                none               (0) - no role.
                dualHomed          (1) - a service point into the dual homed
                                         network being protected by AARP.
                pipeShuntSub       (2) - subscriber side pipe shunt.
                pipeShuntNet       (3) - network side pipe shunt.
                interfaceShuntSub  (4) - subscriber side interface shunt.
                interfaceShuntNet  (5) - network side interface shunt.
                dualHomedSecondary (6) - a secondary service point into the
                                         dual homed network being protected by
                                         AARP."
    SYNTAX      INTEGER {
        none               (0),
        dualHomed          (1),
        pipeShuntSub       (2),
        pipeShuntNet       (3),
        interfaceShuntSub  (4),
        interfaceShuntNet  (5),
        dualHomedSecondary (6)
    }

TmnxBsxAarpServPointType         ::= TEXTUAL-CONVENTION
    STATUS      current
    DESCRIPTION
        "TmnxBsxAarpServPointType represents the different types (and thereby
         the different formats) of TmnxBsxAarpServPoint (an AARP instance
         service point).


         The types of service points are:
                unknown     (0) - unknown.
                sap         (1) - A Service Access Point (SAP) is specified.
                                  This indicates that the format of the
                                  TmnxBsxAarpServPoint is an OCTET STRING
                                  containing the Service Access Point (SAP)
                                  as specified in the TIMETRA-SAP-MIB
                                  including the sapPortId and sapEncapValue.

                                  Octets   Contents
                                  1-4       sapPortId (unsigned integer),
                                  5-8       sapEncapValue (unsigned integer)

                spokeSdp    (2) - A spoke SDP binding is specified.
                                  This indicates that the format of the
                                  TmnxBsxAarpServPoint is an OCTET STRING
                                  containing the spoke SDP Binding Id as
                                  specified in the TIMETRA-SDP-MIB in
                                  sdpBindId in the sdpBindTable."
    SYNTAX      INTEGER {
        unknown  (0),
        sap      (1),
        spokeSdp (2)
    }

TmnxBsxAarpServPoint             ::= TEXTUAL-CONVENTION
    STATUS      current
    DESCRIPTION
        "TmnxBsxAarpServPoint represents a generic AARP instance service point.

         An TmnxBsxAarpServPoint value is always interpreted within
         the context of an TmnxBsxAarpServPointType value.  Every usage
         of the TmnxBsxAarpServPoint textual convention is required to
         specify the TmnxBsxAarpServPointType object that provides the
         context.

         The value of an TmnxBsxAarpServPoint object must always be
         consistent with the value of the associated
         TmnxBsxAarpServPointType object.  Attempts to set an
         TmnxBsxAarpServPoint object to a value inconsistent with the
         associated TmnxBsxAarpServPointType will fail with an
         inconsistentValue error."
    SYNTAX      OCTET STRING (SIZE (0..32))

TmnxBsxFltrAction                ::= TEXTUAL-CONVENTION
    STATUS      current
    DESCRIPTION
        "TmnxBsxFltrAction represents the action to take when applying the
         filter.  Valid values are:
            deny  (1)  - packets matching the criteria are denied
            permit (2) - packets matching the criteria are permitted"
    SYNTAX      INTEGER {
        deny   (1),
        permit (2)
    }

TmnxBsxAqpAction                 ::= TEXTUAL-CONVENTION
    STATUS      current
    DESCRIPTION
        "TmnxBsxAqpAction represents the action to take when applying the
         policy.  Valid values are:
            drop  (1) - packets matching the criteria are dropped
            allow (2) - packets matching the criteria are allowed"
    SYNTAX      INTEGER {
        drop  (1),
        allow (2)
    }

TmnxBsxUmOperStatus              ::= TEXTUAL-CONVENTION
    STATUS      current
    DESCRIPTION
        "TmnxBsxUmOperStatus specifies the status of a usage monitor.
         Valid values are:
            adminDisabled (0)   - rule has been shutdown on the policy server
            inactive (1)        - rule received and either no credits granted
                                  from the policy server or credits have been
                                  exceeded
            active (2)          - rule and credits received from the policy
                                  server and credits have not been exceeded"
    SYNTAX      INTEGER {
        inactiveAdminDisabled (0),
        inactive              (1),
        active                (2)
    }

TmnxBsxEventLogAction            ::= TEXTUAL-CONVENTION
    STATUS      current
    DESCRIPTION
        "TmnxBsxEventLogAction specifies the gtp firewall action on which it
         triggers an event log.
         Valid values are:
            deny   (0)      - event log is raised when the gtp firewall
                              action is deny
            permit (1)      - event log is raised when the gtp firewall
                              action is permit
            all    (2)      - event log is always raised"
    SYNTAX      INTEGER {
        deny   (0),
        permit (1),
        all    (2)
    }

TmnxBsxUmGrantStatus             ::= TEXTUAL-CONVENTION
    STATUS      current
    DESCRIPTION
        "TmnxBsxUmGrantStatus specifies the status of a grant within a
         usage monitor. Valid values are:
            invalid (0)     - the grant is inactive as no credits have been
                              received from policy server
            valid (1)       - usage monitoring is in use and there are credits
                              remaining
            exceeded (2)    - the granted credits have been exceeded, and a
                              report is sent back to the policy server "
    SYNTAX      INTEGER {
        invalid  (0),
        valid    (1),
        exceeded (2)
    }

TmnxBsxAaSubTetherState          ::= TEXTUAL-CONVENTION
    STATUS      current
    DESCRIPTION
        "The value of TmnxBsxAaSubTetherState specifies the tethering
         state of an Application Assurance Subscriber. Valid values are:
               notApplicable (0)    - indicates tethering state is not
                                      applicable
               detected (1)         - indicates that tethering has been
                                      detected
               notDetected (2)      - indicates that tethering has not been
                                      detected "
    SYNTAX      INTEGER {
        notApplicable (0),
        detected      (1),
        notDetected   (2)
    }

TmnxBsxUrlListFlags              ::= TEXTUAL-CONVENTION
    STATUS      current
    DESCRIPTION
        "TmnxBsxUrlListFlags represents the conditions that affect the status
         of a URL list.

         The bit values are:
            adminDown(0)              - URL list is administratively down
            fileDoesNotExist(1)       - file at configured URL does not exist
            invalidFileFormat(2)      - invalid format in file at configured URL
            tooManyUrls(3)            - number of URLs in file exceeds limit
            switchOverError(4)        - CPM activity switch has occurred during
                                        a URL list upgrade
            tooManyChars(5)           - number of characters in file exceeds
                                        limit
            tooManyHostExprUrls(6)      - number of host expression URLs in
                                          the file exceed the limit"
    SYNTAX      BITS {
        adminDown           (0),
        fileDoesNotExist    (1),
        invalidFileFormat   (2),
        tooManyUrls         (3),
        switchOverError     (4),
        tooManyChars        (5),
        tooManyHostExprUrls (6)
    }

TmnxBsxSessionFilterAction       ::= TEXTUAL-CONVENTION
    STATUS      current
    DESCRIPTION
        "TmnxBsxSessionFilterAction represents the action to take when applying
         the session filter.

         Valid values are:
            deny         (1)   - sessions matching the criteria are denied
            permit       (2)   - sessions matching the criteria are permitted
            httpRedirect (3)   - sessions matching the criteria are handled by a
                                 http-redirect
            tcpOptimizer (4)   - sessions matching the criteria are handled by a
                                 TCP optimizer
            application  (5)   - sessions matching the criteria are assigned
                                 an application immediately
            tcpStrictOrder (6) - Out-of-sequence TCP packets of sessions matching
                                 the criteria are dropped
            l3l4Redirect (7)   - sessions matching the criteria are redirected to
                                 specified destination ip addres and/or destination port
            bypassMptcp  (8)   - sessions matching the criteria bypass the
                                 mp-tcp-proxy (if applicable)
            httpProxy    (9)   - sessions matching the criteria are handled by an
                                 HTTP proxy."
    SYNTAX      INTEGER {
        deny         (1),
        permit       (2),
        httpRedirect (3),
        tcpOptimizer (4),
        l3l4Redirect (7),
        reserved9    (9)
    }

TmnxBsxTcaState                  ::= TEXTUAL-CONVENTION
    STATUS      current
    DESCRIPTION
        "The value of TmnxBsxTcaState specifies the Threshold Crossing Alert
         (TCA) state. Valid values are:
               cleared (1) - the state at TCA creation or when the utilization
                             is less than the low watermark and for every
                             subsequent utilization that is less than the high
                             watermark
               raised  (2) - the state when the utilization is greater than the
                             high watermark and for every subsequent utilization
                             that is greater than the low watermark "
    SYNTAX      INTEGER {
        cleared (1),
        raised  (2)
    }

TmnxBsxTcaTriggerType            ::= TEXTUAL-CONVENTION
    STATUS      current
    DESCRIPTION
        "The value of TmnxBsxTcaTriggerType specifies the type of traffic
         used in triggering the Threshold Crossing Alert (TCA) utilization.
         Valid values are:
             deniedTraffic   (1) - the utilization is triggered based on the
                                    amount of denied traffic
             admittedTraffic (2) - the utilization is triggered based on the
                                    amount of admitted traffic"
    SYNTAX      INTEGER {
        deniedTraffic   (1),
        admittedTraffic (2)
    }

TmnxBsxHundredthsOfPercent       ::= TEXTUAL-CONVENTION
    STATUS      current
    DESCRIPTION
        "The value of TmnxBsxHundredthsOfPercent is a percentage defined to two
         decimal places."
    SYNTAX      Unsigned32 (0..10000)

TmnxBsxAaSubCircuitId            ::= TEXTUAL-CONVENTION
    STATUS      current
    DESCRIPTION
        "The value of TmnxBsxAaSubCircuitId specifies the ID of a subscriber
         circuit."
    SYNTAX      DisplayString (SIZE (0..64))

TmnxBsxAaSubRemoteId             ::= TEXTUAL-CONVENTION
    STATUS      current
    DESCRIPTION
        "The value of TmnxBsxAaSubRemoteId specifies the remote ID of a
         subscriber."
    SYNTAX      DisplayString (SIZE (0..64))

TmnxBsxRATType                   ::= TEXTUAL-CONVENTION
    STATUS      current
    DESCRIPTION
        "TmnxBsxRATType represents a type of Radio Access Technology."
    SYNTAX      INTEGER {
        none           (0),
        utran          (1),
        geran          (2),
        wlan           (3),
        gan            (4),
        hspa-evol      (5),
        eutran         (6),
        virtual        (7),
        eutran-nb      (8),
        ehrpd          (9),
        hrpd           (10),
        cdma-1x        (11),
        umb            (12),
        wifi           (13),
        nr             (14),
        lte-m          (15),
        wireline       (16),
        wireline-cable (17),
        wireline-bbf   (18),
        nr-u           (19),
        eutra-u        (20),
        trusted-n3ga   (21),
        trusted-wlan   (22)
    }

TmnxBsxHttpEnrichRATType         ::= TEXTUAL-CONVENTION
    STATUS      current
    DESCRIPTION
        "TmnxBsxHttpEnrichRATType represents a specific RAT type for use on an
         http-enrich field."
    SYNTAX      INTEGER {
        utran     (1),
        geran     (2),
        wlan      (3),
        gan       (4),
        hspa-evol (5),
        eutran    (6),
        virtual   (7),
        eutran-nb (8),
        ehrpd     (9),
        hrpd      (10),
        cdma-1x   (11),
        umb       (12),
        wifi      (13),
        nr        (14),
        lte-m     (15)
    }

TmnxBsxMDevDetectDeviceType      ::= TEXTUAL-CONVENTION
    STATUS      current
    DESCRIPTION
        "TmnxBsxMDevDetectDeviceType represents a specific device for use with
         multi-device detection."
    SYNTAX      INTEGER {
        none    (0),
        host    (1),
        tracked (2),
        excess  (3)
    }

TmnxBsxDnsEnrichOption           ::= TEXTUAL-CONVENTION
    STATUS      current
    DESCRIPTION
        "TmnxBsxDnsEnrichOption specifies whether the dns option is a device id
         or other type that might be available in the future"
    SYNTAX      INTEGER {
        device-id (1)
    }

tmnxBsxObjs                      OBJECT IDENTIFIER ::= { tmnxSRObjs 63 }

tmnxBsxMdaObjs                   OBJECT IDENTIFIER ::= { tmnxBsxObjs 1 }

tmnxBsxMdaScalars                OBJECT IDENTIFIER ::= { tmnxBsxMdaObjs 1 }

tmnxBsxIsaAaGrpLastChangeTime    OBJECT-TYPE
    SYNTAX      TimeStamp
    MAX-ACCESS  read-only
    STATUS      current
    DESCRIPTION
        "The value of tmnxBsxIsaAaGrpLastChangeTime indicates the last time a
         successful set was performed on the tmnxBsxIsaAaGrpTable."
    ::= { tmnxBsxMdaScalars 1 }

tmnxBsxIsaAaGrpFcLastChangeTime  OBJECT-TYPE
    SYNTAX      TimeStamp
    MAX-ACCESS  read-only
    STATUS      current
    DESCRIPTION
        "The value of tmnxBsxIsaAaGrpFcLastChangeTime indicates the last time a
         successful set was performed on the tmnxBsxIsaAaGrpFcTable."
    ::= { tmnxBsxMdaScalars 2 }

tmnxBsxIsaAaGrpMdaLastChangeTime OBJECT-TYPE
    SYNTAX      TimeStamp
    MAX-ACCESS  read-only
    STATUS      current
    DESCRIPTION
        "The value of tmnxBsxIsaAaGrpMdaLastChangeTime indicates the last time
         a successful set was performed on the tmnxBsxGrpMdaTable."
    ::= { tmnxBsxMdaScalars 3 }

tmnxBsxAaGrpPartLastChangeTime   OBJECT-TYPE
    SYNTAX      TimeStamp
    MAX-ACCESS  read-only
    STATUS      current
    DESCRIPTION
        "The value of tmnxBsxAaGrpPartLastChangeTime indicates the last time a
         successful set was performed on the tmnxBsxAaGrpPartTable."
    ::= { tmnxBsxMdaScalars 4 }

tmnxBsxAaWap1xLastChangeTime     OBJECT-TYPE
    SYNTAX      TimeStamp
    MAX-ACCESS  read-only
    STATUS      current
    DESCRIPTION
        "The value of tmnxBsxAaWap1xLastChangeTime indicates the last time a
         successful set was performed on the tmnxBsxAaWap1xTable."
    ::= { tmnxBsxMdaScalars 5 }

tmnxBsxTetherLastChangeTime      OBJECT-TYPE
    SYNTAX      TimeStamp
    MAX-ACCESS  read-only
    STATUS      current
    DESCRIPTION
        "The value of tmnxBsxTetherLastChangeTime indicates the last time a
         successful set was performed on the tmnxBsxTetherTable."
    ::= { tmnxBsxMdaScalars 6 }

tmnxBsxIsaAaGrpTable             OBJECT-TYPE
    SYNTAX      SEQUENCE OF TmnxBsxIsaAaGrpEntry
    MAX-ACCESS  not-accessible
    STATUS      current
    DESCRIPTION
        "The tmnxBsxIsaAaGrpTable contains an entry for each BSX MDA Group in
         the system."
    ::= { tmnxBsxMdaObjs 2 }

tmnxBsxIsaAaGrpEntry             OBJECT-TYPE
    SYNTAX      TmnxBsxIsaAaGrpEntry
    MAX-ACCESS  not-accessible
    STATUS      current
    DESCRIPTION
        "Each tmnxBsxIsaAaGrpEntry indicates a BSX MDA group in the system."
    INDEX       { tmnxBsxIsaAaGroupIndex }
    ::= { tmnxBsxIsaAaGrpTable 1 }

TmnxBsxIsaAaGrpEntry             ::= SEQUENCE
{
    tmnxBsxIsaAaGroupIndex           TmnxBsxIsaAaGroupIndex,
    tmnxBsxIsaAaGrpRowStatus         RowStatus,
    tmnxBsxIsaAaGrpRowLastChange     TimeStamp,
    tmnxBsxIsaAaGrpDescription       TItemDescription,
    tmnxBsxIsaAaGrpAdminState        TmnxAdminState,
    tmnxBsxIsaAaGrpOperState         TmnxOperState,
    tmnxBsxIsaAaGrpFailToMode        TmnxBsxFailToMode,
    tmnxBsxIsaAaGrpFromSubPool       TNamedItem,
    tmnxBsxIsaAaGrpFromSubResvCbs    Integer32,
    tmnxBsxIsaAaGrpFromSubSlpPolicy  TNamedItem,
    tmnxBsxIsaAaGrpFromSubQuePolicy  TNamedItem,
    tmnxBsxIsaAaGrpFromSubSchPolicy  TNamedItemOrEmpty,
    tmnxBsxIsaAaGrpToSubPool         TNamedItem,
    tmnxBsxIsaAaGrpToSubResvCbs      Integer32,
    tmnxBsxIsaAaGrpToSubSlpPolicy    TNamedItem,
    tmnxBsxIsaAaGrpToSubQuePolicy    TNamedItem,
    tmnxBsxIsaAaGrpToSubSchPolicy    TNamedItemOrEmpty,
    tmnxBsxIsaAaGrpIngressPool       TNamedItem,
    tmnxBsxIsaAaGrpIngressResvCbs    Integer32,
    tmnxBsxIsaAaGrpIngressSlpPolicy  TNamedItem,
    tmnxBsxIsaAaGrpIngressQuePolicy  TNamedItem,
    tmnxBsxIsaAaGrpActivityChange    TimeStamp,
    tmnxBsxIsaAaGrpPartitions        TmnxEnabledDisabled,
    tmnxBsxIsaAaGrpCapCostLowThres   Unsigned32,
    tmnxBsxIsaAaGrpCapCostHighThres  Unsigned32,
    tmnxBsxIsaAaGrpLoadBalanceStatus TmnxBsxLoadBalanceStatus,
    tmnxBsxIsaAaGrpUnassignedEsmSubs Gauge32,
    tmnxBsxIsaAaGrpUnassignedSapSubs Gauge32,
    tmnxBsxIsaAaGrpUnassignedSpkSubs Gauge32,
    tmnxBsxIsaAaGrpUnassignedTIpSubs Gauge32,
    tmnxBsxIsaAaGrpAaSubScale        INTEGER,
    tmnxBsxIsaAaGrpOverloadCutThru   TmnxEnabledDisabled,
    tmnxBsxIsaAaGrpFromSubWaSBfHiWmk Integer32,
    tmnxBsxIsaAaGrpFromSubWaSBfLoWmk Integer32,
    tmnxBsxIsaAaGrpToSubWaSBfHiWmk   Integer32,
    tmnxBsxIsaAaGrpToSubWaSBfLoWmk   Integer32,
    tmnxBsxIsaAaGrpTransPrefV4NmEntr Unsigned32,
    tmnxBsxIsaAaGrpTransPrefV6NmEntr Unsigned32,
    tmnxBsxIsaAaGrpTransPrefV6RmEntr Unsigned32,
    tmnxBsxIsaAaGrpHttpEnrichMaxPkt  Unsigned32,
    tmnxBsxIsaAaGrpMinIsaGeneration  Unsigned32,
    tmnxBsxIsaAaGrpWlanGwGrpId       TmnxWlanGwIsaGrpIdOrZero,
    tmnxBsxIsaAaGrpTransPrefV4RmEntr Unsigned32,
    tmnxBsxIsaAaGrpUnassEsmMacSubs   Gauge32,
    tmnxBsxIsaAaGrpSRTcpAdvFnSize    Unsigned32,
    tmnxBsxIsaAaGrpOvrldSubQuarAdmin TmnxAdminState,
    tmnxBsxIsaAaGrpFlowAttributes    TmnxEnabledDisabled,
    tmnxBsxIsaAaGrpVmTrafficDistByIp TmnxEnabledDisabled,
    tmnxBsxIsaAaGrpSRWebServCachSize Unsigned32,
    tmnxBsxIsaAaGrpGtpTunnelDb       Unsigned32,
    tmnxBsxIsaAaGrpVmTrafficDistTeid TmnxEnabledDisabled,
    tmnxBsxIsaAaGrpDistributeByIp    TmnxEnabledDisabled
}

tmnxBsxIsaAaGroupIndex           OBJECT-TYPE
    SYNTAX      TmnxBsxIsaAaGroupIndex
    MAX-ACCESS  not-accessible
    STATUS      current
    DESCRIPTION
        "The value of tmnxBsxIsaAaGroupIndex indicates the group number of this
         group of BSX MDAs."
    ::= { tmnxBsxIsaAaGrpEntry 1 }

tmnxBsxIsaAaGrpRowStatus         OBJECT-TYPE
    SYNTAX      RowStatus
    MAX-ACCESS  read-create
    STATUS      current
    DESCRIPTION
        "The value of tmnxBsxIsaAaGrpRowStatus specifies
         the row status.  It allows entries to be created
         and deleted in the tmnxBsxIsaAaGrpTable.  To
         delete an entry, all references to this ISA-AA
         group in all policy and transit policy tables
         must be deleted."
    ::= { tmnxBsxIsaAaGrpEntry 2 }

tmnxBsxIsaAaGrpRowLastChange     OBJECT-TYPE
    SYNTAX      TimeStamp
    MAX-ACCESS  read-only
    STATUS      current
    DESCRIPTION
        "The value of tmnxBsxIsaAaGrpRowLastChange indicates the last time a
         successful set was performed on this row of the tmnxBsxIsaAaGrpTable."
    ::= { tmnxBsxIsaAaGrpEntry 3 }

tmnxBsxIsaAaGrpDescription       OBJECT-TYPE
    SYNTAX      TItemDescription
    MAX-ACCESS  read-create
    STATUS      current
    DESCRIPTION
        "The value of tmnxBsxIsaAaGrpDescription specifies the description of
         the ISA-AA group."
    DEFVAL      { "" }
    ::= { tmnxBsxIsaAaGrpEntry 4 }

tmnxBsxIsaAaGrpAdminState        OBJECT-TYPE
    SYNTAX      TmnxAdminState
    MAX-ACCESS  read-create
    STATUS      current
    DESCRIPTION
        "The value of tmnxBsxIsaAaGrpAdminState specifies the
         administrative state for the ISA-AA group.  When
         'outOfService', traffic destined to this ISA-AA group
         will apply its' tmnxBsxIsaAaGrpFailToMode behaviour."
    DEFVAL      { outOfService }
    ::= { tmnxBsxIsaAaGrpEntry 5 }

tmnxBsxIsaAaGrpOperState         OBJECT-TYPE
    SYNTAX      TmnxOperState
    MAX-ACCESS  read-only
    STATUS      current
    DESCRIPTION
        "The value of tmnxBsxIsaAaGrpOperState indicates the
         operational state for the ISA-AA group.  When
         'outOfService', traffic destined to this ISA-AA group
         will apply its' tmnxBsxIsaAaGrpFailToMode behaviour."
    DEFVAL      { outOfService }
    ::= { tmnxBsxIsaAaGrpEntry 6 }

tmnxBsxIsaAaGrpFailToMode        OBJECT-TYPE
    SYNTAX      TmnxBsxFailToMode
    MAX-ACCESS  read-create
    STATUS      current
    DESCRIPTION
        "The value of tmnxBsxIsaAaGrpFailToMode specifies the operation upon
         failure of the group: is traffic to be permitted by setting to
         'failToWire' or is it to be denied by setting to 'failToOpen'"
    DEFVAL      { failToWire }
    ::= { tmnxBsxIsaAaGrpEntry 7 }

tmnxBsxIsaAaGrpFromSubPool       OBJECT-TYPE
    SYNTAX      TNamedItem
    MAX-ACCESS  read-create
    STATUS      current
    DESCRIPTION
        "The value of tmnxBsxIsaAaGrpFromSubPool specifies the buffer pool as
         defined in TIMETRA-PORT-MIB::tmnxObjectAppPool for subscriber to
         network traffic egressing towards the ISA-AA MDA."
    DEFVAL      { "default" }
    ::= { tmnxBsxIsaAaGrpEntry 8 }

tmnxBsxIsaAaGrpFromSubResvCbs    OBJECT-TYPE
    SYNTAX      Integer32 (-1..100)
    MAX-ACCESS  read-create
    STATUS      current
    DESCRIPTION
        "The value of tmnxBsxIsaAaGrpFromSubResvCbs specifies the percentage of
         the buffer pool reserved for high priority traffic for subscriber to
         network traffic egressing towards the ISA-AA MDA.

         The value '-1' implies that the reserved CBS should be computed as the
         sum of the CBS requested by the entities using this pool."
    DEFVAL      { -1 }
    ::= { tmnxBsxIsaAaGrpEntry 9 }

tmnxBsxIsaAaGrpFromSubSlpPolicy  OBJECT-TYPE
    SYNTAX      TNamedItem
    MAX-ACCESS  read-create
    STATUS      current
    DESCRIPTION
        "The value of tmnxBsxIsaAaGrpFromSubSlpPolicy specifies the policy as
         defined in TIMETRA-QOS-MIB::tSlopePolicyTable for subscriber to
         network traffic egressing towards the ISA-AA MDA."
    DEFVAL      { "default" }
    ::= { tmnxBsxIsaAaGrpEntry 10 }

tmnxBsxIsaAaGrpFromSubQuePolicy  OBJECT-TYPE
    SYNTAX      TNamedItem
    MAX-ACCESS  read-create
    STATUS      current
    DESCRIPTION
        "The value of tmnxBsxIsaAaGrpFromSubQuePolicy specifies the policy as
         defined in TIMETRA-QOS-MIB::tNetworkQueueTable for subscriber to
         network traffic egressing towards the ISA-AA MDA."
    DEFVAL      { "default" }
    ::= { tmnxBsxIsaAaGrpEntry 11 }

tmnxBsxIsaAaGrpFromSubSchPolicy  OBJECT-TYPE
    SYNTAX      TNamedItemOrEmpty
    MAX-ACCESS  read-create
    STATUS      current
    DESCRIPTION
        "The value of tmnxBsxIsaAaGrpFromSubSchPolicy specifies the policy as
         defined in TIMETRA-QOS-MIB::tSchedulerPolicyTable for subscriber to
         network traffic egressing towards the ISA-AA MDA."
    DEFVAL      { "" }
    ::= { tmnxBsxIsaAaGrpEntry 12 }

tmnxBsxIsaAaGrpToSubPool         OBJECT-TYPE
    SYNTAX      TNamedItem
    MAX-ACCESS  read-create
    STATUS      current
    DESCRIPTION
        "The value of tmnxBsxIsaAaGrpToSubPool specifies the buffer pool as
         defined in TIMETRA-PORT-MIB::tmnxObjectAppPool for network to
         subscriber traffic egressing towards the ISA-AA MDA."
    DEFVAL      { "default" }
    ::= { tmnxBsxIsaAaGrpEntry 13 }

tmnxBsxIsaAaGrpToSubResvCbs      OBJECT-TYPE
    SYNTAX      Integer32 (-1..100)
    MAX-ACCESS  read-create
    STATUS      current
    DESCRIPTION
        "The value of tmnxBsxIsaAaGrpToSubResvCbs specifies the percentage of
         the buffer pool reserved for high priority traffic for network to
         subscriber traffic egressing towards the ISA-AA MDA.

         The value '-1' implies that the reserved CBS should be computed as the
         sum of the CBS requested by the entities using this pool."
    DEFVAL      { -1 }
    ::= { tmnxBsxIsaAaGrpEntry 14 }

tmnxBsxIsaAaGrpToSubSlpPolicy    OBJECT-TYPE
    SYNTAX      TNamedItem
    MAX-ACCESS  read-create
    STATUS      current
    DESCRIPTION
        "The value of tmnxBsxIsaAaGrpToSubSlpPolicy specifies the policy as
         defined in TIMETRA-QOS-MIB::tSlopePolicyTable for network to
         subscriber traffic egressing towards the ISA-AA MDA."
    DEFVAL      { "default" }
    ::= { tmnxBsxIsaAaGrpEntry 15 }

tmnxBsxIsaAaGrpToSubQuePolicy    OBJECT-TYPE
    SYNTAX      TNamedItem
    MAX-ACCESS  read-create
    STATUS      current
    DESCRIPTION
        "The value of tmnxBsxIsaAaGrpToSubQuePolicy specifies the policy as
         defined in TIMETRA-QOS-MIB::tNetworkQueueTable for network to
         subscriber traffic egressing towards the ISA-AA MDA."
    DEFVAL      { "default" }
    ::= { tmnxBsxIsaAaGrpEntry 16 }

tmnxBsxIsaAaGrpToSubSchPolicy    OBJECT-TYPE
    SYNTAX      TNamedItemOrEmpty
    MAX-ACCESS  read-create
    STATUS      current
    DESCRIPTION
        "The value of tmnxBsxIsaAaGrpToSubSchPolicy specifies the policy as
         defined in TIMETRA-QOS-MIB::tSchedulerPolicyTable for network to
         subscriber traffic egressing towards the ISA-AA MDA."
    DEFVAL      { "" }
    ::= { tmnxBsxIsaAaGrpEntry 17 }

tmnxBsxIsaAaGrpIngressPool       OBJECT-TYPE
    SYNTAX      TNamedItem
    MAX-ACCESS  read-create
    STATUS      obsolete
    DESCRIPTION
        "The value of tmnxBsxIsaAaGrpIngressPool specifies the buffer pool as
         defined in TIMETRA-PORT-MIB::tmnxObjectAppPool for all traffic
         ingressing from the ISA-AA MDA.

         This object was obsoleted in release 7.0 and replaced with the
         TIMETRA-PORT-MIB::tmnxObjectAppPool object in the
         TIMETRA-PORT-MIB::tmnxQosPoolAppTable."
    DEFVAL      { "default" }
    ::= { tmnxBsxIsaAaGrpEntry 18 }

tmnxBsxIsaAaGrpIngressResvCbs    OBJECT-TYPE
    SYNTAX      Integer32 (-1..100)
    MAX-ACCESS  read-create
    STATUS      obsolete
    DESCRIPTION
        "The value of tmnxBsxIsaAaGrpIngressResvCbs specifies the percentage of
         the buffer pool reserved for high priority traffic for all traffic
         ingressing from the ISA-AA MDA.

         The value '-1' implies that the reserved CBS should be computed as the
         sum of the CBS requested by the entities using this pool.

         This object was obsoleted in release 7.0 and replaced with the
         TIMETRA-PORT-MIB::tmnxObjectAppResvCbs object in the
         TIMETRA-PORT-MIB::tmnxQosPoolAppTable."
    DEFVAL      { -1 }
    ::= { tmnxBsxIsaAaGrpEntry 19 }

tmnxBsxIsaAaGrpIngressSlpPolicy  OBJECT-TYPE
    SYNTAX      TNamedItem
    MAX-ACCESS  read-create
    STATUS      obsolete
    DESCRIPTION
        "The value of tmnxBsxIsaAaGrpIngressSlpPolicy specifies the policy as
         defined in TIMETRA-QOS-MIB::tSlopePolicyTable for all traffic
         ingressing from the ISA-AA MDA.

         This object was obsoleted in release 7.0 and replaced with the
         TIMETRA-PORT-MIB::tmnxObjectAppSlopePolicy in the
         TIMETRA-PORT-MIB::tmnxQosPoolAppTable."
    DEFVAL      { "default" }
    ::= { tmnxBsxIsaAaGrpEntry 20 }

tmnxBsxIsaAaGrpIngressQuePolicy  OBJECT-TYPE
    SYNTAX      TNamedItem
    MAX-ACCESS  read-create
    STATUS      obsolete
    DESCRIPTION
        "The value of tmnxBsxIsaAaGrpIngressQuePolicy specifies the policy as
         defined in TIMETRA-QOS-MIB::tNetworkQueueTable for all traffic
         ingressing from the ISA-AA MDA.

         This object was obsoleted in release 7.0 and replaced with the
         TIMETRA-CHASSIS-MIB::tmnxMDANetworkIngQueues in the
         TIMETRA-CHASSIS-MIB::tmnxMDATable."
    DEFVAL      { "default" }
    ::= { tmnxBsxIsaAaGrpEntry 21 }

tmnxBsxIsaAaGrpActivityChange    OBJECT-TYPE
    SYNTAX      TimeStamp
    MAX-ACCESS  read-only
    STATUS      current
    DESCRIPTION
        "The value of tmnxBsxIsaAaGrpActivityChange indicates the last time the
         value of tmnxBsxGrpMdaActivityState changed to or from 'active (1)'
         state for an ISA-AA MDA within the group."
    ::= { tmnxBsxIsaAaGrpEntry 22 }

tmnxBsxIsaAaGrpPartitions        OBJECT-TYPE
    SYNTAX      TmnxEnabledDisabled
    MAX-ACCESS  read-create
    STATUS      obsolete
    DESCRIPTION
        "The value of tmnxBsxIsaAaGrpPartitions specifies whether partitions
         are enabled or not within an ISA-AA group. When the value of this
         object is set to 'enabled', partitions can be created in the
         tmnxBsxAaGrpPartTable."
    DEFVAL      { disabled }
    ::= { tmnxBsxIsaAaGrpEntry 23 }

tmnxBsxIsaAaGrpCapCostLowThres   OBJECT-TYPE
    SYNTAX      Unsigned32
    MAX-ACCESS  read-create
    STATUS      current
    DESCRIPTION
        "The value of tmnxBsxIsaAaGrpCapCostLowThres specifies the capacity
         cost low threshold for the ISA-AA group."
    DEFVAL      { 0 }
    ::= { tmnxBsxIsaAaGrpEntry 24 }

tmnxBsxIsaAaGrpCapCostHighThres  OBJECT-TYPE
    SYNTAX      Unsigned32
    MAX-ACCESS  read-create
    STATUS      current
    DESCRIPTION
        "The value of tmnxBsxIsaAaGrpCapCostHighThres specifies the capacity
         cost high threshold for the ISA-AA group."
    DEFVAL      { 'FFFFFFFF'H }
    ::= { tmnxBsxIsaAaGrpEntry 25 }

tmnxBsxIsaAaGrpLoadBalanceStatus OBJECT-TYPE
    SYNTAX      TmnxBsxLoadBalanceStatus
    MAX-ACCESS  read-only
    STATUS      current
    DESCRIPTION
        "The value of tmnxBsxIsaAaGrpLoadBalanceStatus indicates the status of
         the load-balance operation for the ISA-AA group."
    ::= { tmnxBsxIsaAaGrpEntry 26 }

tmnxBsxIsaAaGrpUnassignedEsmSubs OBJECT-TYPE
    SYNTAX      Gauge32
    UNITS       "subscribers"
    MAX-ACCESS  read-only
    STATUS      current
    DESCRIPTION
        "The value of tmnxBsxIsaAaGrpUnassignedEsmSubs indicates the number of
         Enhanced Subscriber Management (ESM) subscribers that have not been
         assigned to an ISA-AA MDA within a group."
    ::= { tmnxBsxIsaAaGrpEntry 27 }

tmnxBsxIsaAaGrpUnassignedSapSubs OBJECT-TYPE
    SYNTAX      Gauge32
    UNITS       "subscribers"
    MAX-ACCESS  read-only
    STATUS      current
    DESCRIPTION
        "The value of tmnxBsxIsaAaGrpUnassignedSapSubs indicates the number of
         Service Access Point (SAP) subscribers that have not been assigned to
         an ISA-AA MDA within a group."
    ::= { tmnxBsxIsaAaGrpEntry 28 }

tmnxBsxIsaAaGrpUnassignedSpkSubs OBJECT-TYPE
    SYNTAX      Gauge32
    UNITS       "subscribers"
    MAX-ACCESS  read-only
    STATUS      current
    DESCRIPTION
        "The value of tmnxBsxIsaAaGrpUnassignedSpkSubs indicates the number of
         Spoke SDP subscribers that have not been assigned to an ISA-AA MDA
         within a group."
    ::= { tmnxBsxIsaAaGrpEntry 29 }

tmnxBsxIsaAaGrpUnassignedTIpSubs OBJECT-TYPE
    SYNTAX      Gauge32
    UNITS       "subscribers"
    MAX-ACCESS  read-only
    STATUS      obsolete
    DESCRIPTION
        "The value of tmnxBsxIsaAaGrpUnassignedTIpSubs indicates the number of
         Transit IP subscribers that have not been assigned to an ISA-AA MDA
         within a group.

         This object was obsoleted in release 9.0 and replaced with
         tmnxBsxIsaLoadBalUnSubTransit."
    ::= { tmnxBsxIsaAaGrpEntry 30 }

tmnxBsxIsaAaGrpAaSubScale        OBJECT-TYPE
    SYNTAX      INTEGER {
        residential             (0),
        vpn                     (1),
        mobileGateway           (2),
        lightweightInternet     (3),
        residential8k           (4),
        residential16k          (5),
        residential32k          (6),
        residential64k          (7),
        vpn1k                   (8),
        vpn2k                   (9),
        vpn4k                   (10),
        vpn8k                   (11),
        mobileGateway1M         (12),
        mobileGateway2M         (13),
        lightweightInternet512k (14),
        firewall32              (15)
    }
    MAX-ACCESS  read-create
    STATUS      current
    DESCRIPTION
        "The value of tmnxBsxIsaAaGrpAaSubScale specifies the set of
         scaling limits that are supported with regards to the
         maximum number of AA subscribers per ISA and the corresponding
         policies that can be specified.
         The scaling limits may be one of:
            residential         (0) - scaling limits for residential operation
            vpn                 (1) - scaling limits for VPNs
            mobileGateway       (2) - scaling limits for operation as a mobile
                                      gateway
            lightweightInternet (3) - scaling limits for lightweight internet
                                      management
            residential8k       (4) - scaling limits for residential operation
                                      with 8192 subscribers
            residential16k      (5) - scaling limits for residential operation
                                      with 16384 subscribers
            residential32k      (6) - scaling limits for residential operation
                                      with 32768 subscribers
            residential64k      (7) - scaling limits for residential operation
                                      with 65536 subscribers
            vpn1k               (8) - scaling limits for VPNs with 1024
                                      subscribers
            vpn2k               (9) - scaling limits for VPNs with 2048
                                      subscribers
            vpn4k              (10) - scaling limits for VPNs with 4096
                                      subscribers
            vpn8k              (11) - scaling limits for VPNs with 8192
                                      subscribers
            mobileGateway1M    (12) - scaling limits for mobile gateway
                                      with 1000000 subscribers
            mobileGateway2M    (13) - scaling limits for mobile gateway
                                      with 2000000 subscribers
            lightweightInternet512k (14) - scaling limits for lightweight internet
                                      with 524288 subscribers
            firewall32         (15) - scaling limits for firewall with
                                      32 subscribers
         Values larger than 'lightweightInternet (3)' can only be set on a
         Virtual Service Router (VSR) or for use with ESA.
         tmnxBsxIsaAaGrpAaSubScale can only be set during row creation."
    DEFVAL      { residential }
    ::= { tmnxBsxIsaAaGrpEntry 31 }

tmnxBsxIsaAaGrpOverloadCutThru   OBJECT-TYPE
    SYNTAX      TmnxEnabledDisabled
    MAX-ACCESS  read-create
    STATUS      current
    DESCRIPTION
        "The value of tmnxBsxIsaAaGrpOverloadCutThru specifies whether or not
         overload cut-through is enabled. If enabled and an ISA overloads, all
         traffic is cut-through with no application identification or
         application specific policies applied until the ISA is no longer
         overloaded. Statistics are counter per subscriber against the
         cut-through protocol. If disabled and an ISA overloads, no action is
         taken."
    DEFVAL      { disabled }
    ::= { tmnxBsxIsaAaGrpEntry 32 }

tmnxBsxIsaAaGrpFromSubWaSBfHiWmk OBJECT-TYPE
    SYNTAX      Integer32 (-1 | 1..100)
    UNITS       "percent"
    MAX-ACCESS  read-create
    STATUS      current
    DESCRIPTION
        "The value of tmnxBsxIsaAaGrpFromSubWaSBfHiWmk specifies the high
         watermark for the weighted average utilization of the shared buffer
         space in the 'FromSub' buffer pool for each ISA. When a buffer pool is
         not in the overload state and the wa-shared buffer utilization for an
         ISA is greater than or equal to tmnxBsxIsaAaGrpFromSubWaSBfHiWmk the
         ISA 'FromSub' buffer pool enters an overload state and an overload
         notification tmnxBsxIsaAaGrpFmSbWaSBufOvld is raised.

         The value must be greater than tmnxBsxIsaAaGrpFromSubWaSBfLoWmk. The
         value of -1 represents the maximum wa-shared buffer utilization
         indicating this high watermark will not be met."
    DEFVAL      { -1 }
    ::= { tmnxBsxIsaAaGrpEntry 33 }

tmnxBsxIsaAaGrpFromSubWaSBfLoWmk OBJECT-TYPE
    SYNTAX      Integer32 (0..99)
    UNITS       "percent"
    MAX-ACCESS  read-create
    STATUS      current
    DESCRIPTION
        "The value of tmnxBsxIsaAaGrpFromSubWaSBfLoWmk specifies the low
         watermark for the weighted average utilization of the shared buffer
         space in the 'FromSub' buffer pool. When a buffer pool is in an
         overloaded state and the wa-shared buffer utilization for an ISA is
         less than or equal to tmnxBsxIsaAaGrpFromSubWaSBfLoWmk the ISA
         'FromSub' buffer pool leaves the overload state and a notification
         tmnxBsxIsaAaGrpFmSbWaSBufOvldClr is sent to indicate the overload
         state has cleared.

         The value of tmnxBsxIsaAaGrpFromSubWaSBfLoWmk must be less than
         tmnxBsxIsaAaGrpFromSubWaSBfHiWmk."
    DEFVAL      { 0 }
    ::= { tmnxBsxIsaAaGrpEntry 34 }

tmnxBsxIsaAaGrpToSubWaSBfHiWmk   OBJECT-TYPE
    SYNTAX      Integer32 (-1 | 1..100)
    UNITS       "percent"
    MAX-ACCESS  read-create
    STATUS      current
    DESCRIPTION
        "The value of tmnxBsxIsaAaGrpToSubWaSBfHiWmk specifies the high
         watermark for the weighed average utilization of the shared buffer
         space in the 'ToSub' buffer pool for each ISA. When a buffer pool is
         not in the overload state and the wa-shared buffer utilization for an
         ISA is greater than or equal to tmnxBsxIsaAaGrpToSubWaSBfHiWmk the ISA
         'ToSub' buffer pool enters an overload state and an overload
         notification tmnxBsxIsaAaGrpToSbWaSBufOvld is raised.

         The value must be greater than tmnxBsxIsaAaGrpToSubWaSBfLoWmk. The
         value of -1 represents the maximum wa-shared buffer utilization
         indicating this high watermark will not be met."
    DEFVAL      { -1 }
    ::= { tmnxBsxIsaAaGrpEntry 35 }

tmnxBsxIsaAaGrpToSubWaSBfLoWmk   OBJECT-TYPE
    SYNTAX      Integer32 (0..99)
    UNITS       "percent"
    MAX-ACCESS  read-create
    STATUS      current
    DESCRIPTION
        "The value of tmnxBsxIsaAaGrpToSubWaSBfLoWmk specifies the low
         watermark for the weighted average utilization of the shared buffer
         space in the 'ToSub' buffer pool. When a buffer pool is in an
         overloaded state and the wa-shared buffer utilization for an ISA is
         less than or equal to tmnxBsxIsaAaGrpToSubWaSBfLoWmk the ISA 'ToSub'
         buffer pool leaves the overload state and a notification
         tmnxBsxIsaAaGrpToSbWaSBufOvldClr is sent to indicate the overload
         state has cleared.

         The value of tmnxBsxIsaAaGrpToSubWaSBfLoWmk must be less than
         tmnxBsxIsaAaGrpToSubWaSBfHiWmk."
    DEFVAL      { 0 }
    ::= { tmnxBsxIsaAaGrpEntry 36 }

tmnxBsxIsaAaGrpTransPrefV4NmEntr OBJECT-TYPE
    SYNTAX      Unsigned32
    MAX-ACCESS  read-create
    STATUS      current
    DESCRIPTION
        "The value of tmnxBsxIsaAaGrpTransPrefV4NmEntr specifies the number of
         transit prefix IPv4 entries to be supported on the ISA."
    DEFVAL      { 0 }
    ::= { tmnxBsxIsaAaGrpEntry 37 }

tmnxBsxIsaAaGrpTransPrefV6NmEntr OBJECT-TYPE
    SYNTAX      Unsigned32
    MAX-ACCESS  read-create
    STATUS      current
    DESCRIPTION
        "The value of tmnxBsxIsaAaGrpTransPrefV6NmEntr specifies the number of
         transit prefix IPv6 entries to be supported on the ISA."
    DEFVAL      { 0 }
    ::= { tmnxBsxIsaAaGrpEntry 38 }

tmnxBsxIsaAaGrpTransPrefV6RmEntr OBJECT-TYPE
    SYNTAX      Unsigned32
    MAX-ACCESS  read-create
    STATUS      current
    DESCRIPTION
        "The value of tmnxBsxIsaAaGrpTransPrefV6RmEntr specifies the number of
         remote transit prefix IPv6 entries to be supported on the ISA."
    DEFVAL      { 0 }
    ::= { tmnxBsxIsaAaGrpEntry 39 }

tmnxBsxIsaAaGrpHttpEnrichMaxPkt  OBJECT-TYPE
    SYNTAX      Unsigned32 (576..9212)
    UNITS       "octets"
    MAX-ACCESS  read-create
    STATUS      current
    DESCRIPTION
        "The value of tmnxBsxIsaAaGrpHttpEnrichMaxPkt specifies the maximum
         HTTP enriched packet size in octets."
    DEFVAL      { 1500 }
    ::= { tmnxBsxIsaAaGrpEntry 40 }

tmnxBsxIsaAaGrpMinIsaGeneration  OBJECT-TYPE
    SYNTAX      Unsigned32 (1..2)
    MAX-ACCESS  read-create
    STATUS      current
    DESCRIPTION
        "The value of tmnxBsxIsaAaGrpMinIsaGeneration specifies the minimum ISA
         Generation allowed in this group.

         On any HSR platform, the minimum ISA Generation has a value of 2."
    ::= { tmnxBsxIsaAaGrpEntry 41 }

tmnxBsxIsaAaGrpWlanGwGrpId       OBJECT-TYPE
    SYNTAX      TmnxWlanGwIsaGrpIdOrZero
    MAX-ACCESS  read-only
    STATUS      current
    DESCRIPTION
        "The value of tmnxBsxIsaAaGrpWlanGwGrpId indicates the identifier of
         the WLAN Gateway Integrated Service Adaptor group associated with this
         ISA-AA group. A value of 0 indicates there is no ISA group associated."
    ::= { tmnxBsxIsaAaGrpEntry 42 }

tmnxBsxIsaAaGrpTransPrefV4RmEntr OBJECT-TYPE
    SYNTAX      Unsigned32 (0..2047)
    MAX-ACCESS  read-create
    STATUS      current
    DESCRIPTION
        "The value of tmnxBsxIsaAaGrpTransPrefV4RmEntr specifies the number of
         remote transit prefix IPv4 entries to be supported on the ISA."
    DEFVAL      { 0 }
    ::= { tmnxBsxIsaAaGrpEntry 43 }

tmnxBsxIsaAaGrpUnassEsmMacSubs   OBJECT-TYPE
    SYNTAX      Gauge32
    UNITS       "subscribers"
    MAX-ACCESS  read-only
    STATUS      current
    DESCRIPTION
        "The value of tmnxBsxIsaAaGrpUnassEsmMacSubs indicates the number of
         Enhanced Subscriber Management (ESM) MAC host subscribers that have
         not been assigned to an ISA-AA MDA within a group."
    ::= { tmnxBsxIsaAaGrpEntry 44 }

tmnxBsxIsaAaGrpSRTcpAdvFnSize    OBJECT-TYPE
    SYNTAX      Unsigned32 (0..100)
    UNITS       "percent"
    MAX-ACCESS  read-create
    STATUS      current
    DESCRIPTION
        "The value of tmnxBsxIsaAaGrpSRTcpAdvFnSize specifies the percentage of
         the maximum scale supported for TCP advanced functions.

         A change to this object will cause the AA ISA to automatically reboot
         in order to take effect. The corresponding group must be shutdown in
         order to change value of this object."
    DEFVAL      { 0 }
    ::= { tmnxBsxIsaAaGrpEntry 45 }

tmnxBsxIsaAaGrpOvrldSubQuarAdmin OBJECT-TYPE
    SYNTAX      TmnxAdminState
    MAX-ACCESS  read-create
    STATUS      current
    DESCRIPTION
        "The value of tmnxBsxIsaAaGrpOvrldSubQuarAdmin specifies the
         operational state of Overload Sub Quarantine on this ISA group."
    DEFVAL      { outOfService }
    ::= { tmnxBsxIsaAaGrpEntry 46 }

tmnxBsxIsaAaGrpFlowAttributes    OBJECT-TYPE
    SYNTAX      TmnxEnabledDisabled
    MAX-ACCESS  read-create
    STATUS      obsolete
    DESCRIPTION
        "The value of tmnxBsxIsaAaGrpFlowAttributes specifies whether flow
         attribute AQP matches are enabled or not within this ISA group.

         This object was obsoleted in release 19.0 and replaced with entries in
         the tmnxBsxIsaAaGrpFlowAttrTable."
    DEFVAL      { disabled }
    ::= { tmnxBsxIsaAaGrpEntry 47 }

tmnxBsxIsaAaGrpVmTrafficDistByIp OBJECT-TYPE
    SYNTAX      TmnxEnabledDisabled
    MAX-ACCESS  read-create
    STATUS      current
    DESCRIPTION
        "The value of tmnxBsxIsaAaGrpVmTrafficDistByIp specifies whether the
         packets IP addresses will be included in the traffic distribution
         mechanism."
    DEFVAL      { disabled }
    ::= { tmnxBsxIsaAaGrpEntry 48 }

tmnxBsxIsaAaGrpSRWebServCachSize OBJECT-TYPE
    SYNTAX      Unsigned32 (0..100)
    UNITS       "percent"
    MAX-ACCESS  read-create
    STATUS      current
    DESCRIPTION
        "The value of tmnxBsxIsaAaGrpSRWebServCachSize specifies the percentage
         of the maximum scale supported for Web Service caching functions.

         A change to this object will cause the AA ISA to automatically reboot
         in order to take effect. The corresponding group must be shutdown in
         order to change value of this object."
    DEFVAL      { 0 }
    ::= { tmnxBsxIsaAaGrpEntry 49 }

tmnxBsxIsaAaGrpGtpTunnelDb       OBJECT-TYPE
    SYNTAX      Unsigned32 (0..100)
    UNITS       "percent"
    MAX-ACCESS  read-create
    STATUS      current
    DESCRIPTION
        "The value of tmnxBsxIsaAaGrpGtpTunnelDb specifies the percentage of
         the maximum scale supported for GTP stateful firewall functions.

         A change to this object will cause the AA ISA to automatically reboot
         in order to take effect. The corresponding group must be shutdown in
         order to change value of this object."
    DEFVAL      { 0 }
    ::= { tmnxBsxIsaAaGrpEntry 50 }

tmnxBsxIsaAaGrpVmTrafficDistTeid OBJECT-TYPE
    SYNTAX      TmnxEnabledDisabled
    MAX-ACCESS  read-create
    STATUS      current
    DESCRIPTION
        "The value of tmnxBsxIsaAaGrpVmTrafficDistTeid specifies whether GTP
         packets TEID will be included in the traffic distribution mechanism."
    DEFVAL      { disabled }
    ::= { tmnxBsxIsaAaGrpEntry 51 }

tmnxBsxIsaAaGrpDistributeByIp    OBJECT-TYPE
    SYNTAX      TmnxEnabledDisabled
    MAX-ACCESS  read-create
    STATUS      current
    DESCRIPTION
        "The value of tmnxBsxIsaAaGrpDistributeByIp..."
    DEFVAL      { disabled }
    ::= { tmnxBsxIsaAaGrpEntry 55 }

tmnxBsxIsaAaGrpFcTable           OBJECT-TYPE
    SYNTAX      SEQUENCE OF TmnxBsxIsaAaGrpFcEntry
    MAX-ACCESS  not-accessible
    STATUS      current
    DESCRIPTION
        "The tmnxBsxIsaAaGrpFcTable contains an entry for each divertable
         forwarding class for each BSX MDA Group in the system."
    ::= { tmnxBsxMdaObjs 3 }

tmnxBsxIsaAaGrpFcEntry           OBJECT-TYPE
    SYNTAX      TmnxBsxIsaAaGrpFcEntry
    MAX-ACCESS  not-accessible
    STATUS      current
    DESCRIPTION
        "Each tmnxBsxIsaAaGrpFcEntry indicates a divertable forwarding class
         for each BSX MDA Group in the system."
    INDEX       {
        tmnxBsxIsaAaGroupIndex,
        tFCName
    }
    ::= { tmnxBsxIsaAaGrpFcTable 1 }

TmnxBsxIsaAaGrpFcEntry           ::= SEQUENCE
{
    tmnxBsxIsaAaGrpFcRowStatus       RowStatus,
    tmnxBsxIsaAaGrpFcRowLastChange   TimeStamp
}

tmnxBsxIsaAaGrpFcRowStatus       OBJECT-TYPE
    SYNTAX      RowStatus
    MAX-ACCESS  read-create
    STATUS      current
    DESCRIPTION
        "The value of tmnxBsxIsaAaGrpFcRowStatus specifies
         the row status.  It allows entries to be created
         and deleted in the tmnxBsxIsaAaGrpFcTable."
    ::= { tmnxBsxIsaAaGrpFcEntry 1 }

tmnxBsxIsaAaGrpFcRowLastChange   OBJECT-TYPE
    SYNTAX      TimeStamp
    MAX-ACCESS  read-only
    STATUS      current
    DESCRIPTION
        "The value of tmnxBsxIsaAaGrpFcRowLastChange indicates the last time a
         successful set was performed on this row of the
         tmnxBsxIsaAaGrpFcTable."
    ::= { tmnxBsxIsaAaGrpFcEntry 2 }

tmnxBsxGrpMdaTable               OBJECT-TYPE
    SYNTAX      SEQUENCE OF TmnxBsxGrpMdaEntry
    MAX-ACCESS  not-accessible
    STATUS      current
    DESCRIPTION
        "The tmnxBsxGrpMdaTable contains an entry for each ISA-AA MDA
         configured within a group. This table is populated when an MDA is
         configured with an MDA type of ISA-AA, and associated with an ISA-AA
         group."
    ::= { tmnxBsxMdaObjs 4 }

tmnxBsxGrpMdaEntry               OBJECT-TYPE
    SYNTAX      TmnxBsxGrpMdaEntry
    MAX-ACCESS  not-accessible
    STATUS      current
    DESCRIPTION
        "Each tmnxBsxGrpMdaEntry indicates a ISA-AA MDA is associated to a
         tmnxBsxIsaAaGrpEntry."
    INDEX       {
        tmnxBsxIsaAaGroupIndex,
        tmnxChassisIndex,
        tmnxBsxCardSlotEsaId,
        tmnxBsxMdaSlotEsaVmId
    }
    ::= { tmnxBsxGrpMdaTable 1 }

TmnxBsxGrpMdaEntry               ::= SEQUENCE
{
    tmnxBsxCardSlotEsaId             Integer32,
    tmnxBsxGrpMdaRowStatus           RowStatus,
    tmnxBsxGrpMdaRowLastChange       TimeStamp,
    tmnxBsxGrpMdaRole                TmnxBsxMdaRole,
    tmnxBsxGrpMdaActivityState       TmnxBsxMdaActivityState,
    tmnxBsxGrpMdaActivityChange      TimeStamp,
    tmnxBsxGrpMdaEsmSubscribers      Gauge32,
    tmnxBsxGrpMdaSapSubscribers      Gauge32,
    tmnxBsxGrpMdaSpokeSdpSubscribers Gauge32,
    tmnxBsxGrpMdaCapacityCost        Gauge32,
    tmnxBsxGrpMdaStatsResourceCount  Gauge32,
    tmnxBsxGrpMdaTransitIpSubs       Gauge32,
    tmnxBsxGrpMdaTransitIpAddrs      Gauge32,
    tmnxBsxGrpMdaTransitSubs         Gauge32,
    tmnxBsxGrpMdaTransPrefEntries    Gauge32,
    tmnxBsxGrpMdaTransPrefV4Entr     Gauge32,
    tmnxBsxGrpMdaTransPrefV6Entr     Gauge32,
    tmnxBsxGrpMdaTransPrefV6RemEntr  Gauge32,
    tmnxBsxGrpMdaTransPrefV4RemEntr  Gauge32,
    tmnxBsxGrpMdaEsmMacSubscribers   Gauge32,
    tmnxBsxMdaSlotEsaVmId            Unsigned32,
    tmnxBsxGrpMdaCflowdColl          Unsigned32,
    tmnxBsxGrpMdaMgCardGroupId       Unsigned32
}

tmnxBsxCardSlotEsaId             OBJECT-TYPE
    SYNTAX      Integer32
    MAX-ACCESS  not-accessible
    STATUS      current
    DESCRIPTION
        "The value of tmnxBsxCardSlotEsaId indicates the slot number of this
         ISA-AA card or the ESA ID."
    ::= { tmnxBsxGrpMdaEntry 1 }

tmnxBsxGrpMdaRowStatus           OBJECT-TYPE
    SYNTAX      RowStatus
    MAX-ACCESS  read-create
    STATUS      current
    DESCRIPTION
        "The value of tmnxBsxGrpMdaRowStatus specifies
         the row status.  It allows entries to be created
         and deleted in the tmnxBsxGrpMdaTable.

         Rows are created by specifying the value of 'createAndGo (4)', and
         deleted by specifying the value of 'destroy (6)'."
    ::= { tmnxBsxGrpMdaEntry 2 }

tmnxBsxGrpMdaRowLastChange       OBJECT-TYPE
    SYNTAX      TimeStamp
    MAX-ACCESS  read-only
    STATUS      current
    DESCRIPTION
        "The value of tmnxBsxGrpMdaRowLastChange indicates
         the last time a successful set was performed on this
         row of the  tmnxBsxGrpMdaTable."
    ::= { tmnxBsxGrpMdaEntry 3 }

tmnxBsxGrpMdaRole                OBJECT-TYPE
    SYNTAX      TmnxBsxMdaRole
    MAX-ACCESS  read-create
    STATUS      current
    DESCRIPTION
        "The value of tmnxBsxGrpMdaRole specifies the role of the MDA in the
         tmnxBsxIsaAaGrpEntry. The role can only be set at row creation, and
         cannot be modified."
    DEFVAL      { primary }
    ::= { tmnxBsxGrpMdaEntry 4 }

tmnxBsxGrpMdaActivityState       OBJECT-TYPE
    SYNTAX      TmnxBsxMdaActivityState
    MAX-ACCESS  read-only
    STATUS      current
    DESCRIPTION
        "The value of tmnxBsxGrpMdaActivityState indicates the current activity
         status of the MDA in the group."
    DEFVAL      { unavailable }
    ::= { tmnxBsxGrpMdaEntry 5 }

tmnxBsxGrpMdaActivityChange      OBJECT-TYPE
    SYNTAX      TimeStamp
    MAX-ACCESS  read-only
    STATUS      current
    DESCRIPTION
        "The value of tmnxBsxGrpMdaActivityChange indicates the last time the
         value of tmnxBsxGrpMdaActivityState changed to or from 'active (1)' or
         'standby (2)' state for an ISA-AA MDA in the group."
    ::= { tmnxBsxGrpMdaEntry 6 }

tmnxBsxGrpMdaEsmSubscribers      OBJECT-TYPE
    SYNTAX      Gauge32
    UNITS       "subscribers"
    MAX-ACCESS  read-only
    STATUS      current
    DESCRIPTION
        "The value of tmnxBsxGrpMdaEsmSubscribers indicates the current number
         of Enhanced Subscriber Management (ESM) subscribers active on the
         ISA-AA MDA in the group."
    ::= { tmnxBsxGrpMdaEntry 7 }

tmnxBsxGrpMdaSapSubscribers      OBJECT-TYPE
    SYNTAX      Gauge32
    UNITS       "subscribers"
    MAX-ACCESS  read-only
    STATUS      current
    DESCRIPTION
        "The value of tmnxBsxGrpMdaSapSubscribers indicates the current number
         of Service Access Point (SAP) subscribers active on the ISA-AA MDA in
         the group."
    ::= { tmnxBsxGrpMdaEntry 8 }

tmnxBsxGrpMdaSpokeSdpSubscribers OBJECT-TYPE
    SYNTAX      Gauge32
    UNITS       "subscribers"
    MAX-ACCESS  read-only
    STATUS      current
    DESCRIPTION
        "The value of tmnxBsxGrpMdaSpokeSdpSubscribers indicates the current
         number of Spoke SDP subscribers active on the ISA-AA MDA in the group."
    ::= { tmnxBsxGrpMdaEntry 9 }

tmnxBsxGrpMdaCapacityCost        OBJECT-TYPE
    SYNTAX      Gauge32
    UNITS       "cost"
    MAX-ACCESS  read-only
    STATUS      current
    DESCRIPTION
        "The value of tmnxBsxGrpMdaCapacityCost indicates the current capacity
         cost assigned to the ISA-AA MDA in the group."
    ::= { tmnxBsxGrpMdaEntry 10 }

tmnxBsxGrpMdaStatsResourceCount  OBJECT-TYPE
    SYNTAX      Gauge32
    UNITS       "resources"
    MAX-ACCESS  read-only
    STATUS      current
    DESCRIPTION
        "The value of tmnxBsxGrpMdaStatsResourceCount indicates the current
         number of Application Assurance subscriber statistics resources in use
         on the ISA-AA MDA in the group."
    ::= { tmnxBsxGrpMdaEntry 11 }

tmnxBsxGrpMdaTransitIpSubs       OBJECT-TYPE
    SYNTAX      Gauge32
    UNITS       "subscribers"
    MAX-ACCESS  read-only
    STATUS      current
    DESCRIPTION
        "The value of tmnxBsxGrpMdaTransitIpSubs indicates the current number
         of Transit IP subscribers active on the ISA-AA MDA in the group.

         This object will be obsolete in a future release in favour of
         tmnxBsxGrpMdaTransitSubs."
    ::= { tmnxBsxGrpMdaEntry 12 }

tmnxBsxGrpMdaTransitIpAddrs      OBJECT-TYPE
    SYNTAX      Gauge32
    MAX-ACCESS  read-only
    STATUS      current
    DESCRIPTION
        "The value of tmnxBsxGrpMdaTransitIpAddrs indicates the current number
         of Transit IP subscriber addresses associated with the ISA-AA MDA in
         the group."
    ::= { tmnxBsxGrpMdaEntry 13 }

tmnxBsxGrpMdaTransitSubs         OBJECT-TYPE
    SYNTAX      Gauge32
    UNITS       "subscribers"
    MAX-ACCESS  read-only
    STATUS      current
    DESCRIPTION
        "The value of tmnxBsxGrpMdaTransitSubs indicates the current number of
         transit subscribers active on the ISA-AA MDA in the group."
    ::= { tmnxBsxGrpMdaEntry 14 }

tmnxBsxGrpMdaTransPrefEntries    OBJECT-TYPE
    SYNTAX      Gauge32
    MAX-ACCESS  read-only
    STATUS      obsolete
    DESCRIPTION
        "The value of tmnxBsxGrpMdaTransPrefEntries indicates the current
         number of transit prefix entries active on the ISA-AA MDA in the
         group.

         This object was obsoleted in release 10.0 and replaced with
         tmnxBsxGrpMdaTransPrefV4Entr for IPv4 entries along with
         tmnxBsxGrpMdaTransPrefV6Entr for IPv6 entries."
    ::= { tmnxBsxGrpMdaEntry 15 }

tmnxBsxGrpMdaTransPrefV4Entr     OBJECT-TYPE
    SYNTAX      Gauge32
    MAX-ACCESS  read-only
    STATUS      current
    DESCRIPTION
        "The value of tmnxBsxGrpMdaTransPrefV4Entr indicates the current number
         of transit prefix IPv4 entries active on the ISA-AA MDA in the group."
    ::= { tmnxBsxGrpMdaEntry 16 }

tmnxBsxGrpMdaTransPrefV6Entr     OBJECT-TYPE
    SYNTAX      Gauge32
    MAX-ACCESS  read-only
    STATUS      current
    DESCRIPTION
        "The value of tmnxBsxGrpMdaTransPrefV6Entr indicates the current number
         of transit prefix IPv6 entries active on the ISA-AA MDA in the group."
    ::= { tmnxBsxGrpMdaEntry 17 }

tmnxBsxGrpMdaTransPrefV6RemEntr  OBJECT-TYPE
    SYNTAX      Gauge32
    MAX-ACCESS  read-only
    STATUS      current
    DESCRIPTION
        "The value of tmnxBsxGrpMdaTransPrefV6RemEntr indicates the current
         number of transit prefix IPv6 remote entries active on the ISA-AA MDA
         in the group."
    ::= { tmnxBsxGrpMdaEntry 18 }

tmnxBsxGrpMdaTransPrefV4RemEntr  OBJECT-TYPE
    SYNTAX      Gauge32
    MAX-ACCESS  read-only
    STATUS      current
    DESCRIPTION
        "The value of tmnxBsxGrpMdaTransPrefV4RemEntr indicates the current
         number of transit prefix IPv4 remote entries active on the ISA-AA MDA
         in the group."
    ::= { tmnxBsxGrpMdaEntry 19 }

tmnxBsxGrpMdaEsmMacSubscribers   OBJECT-TYPE
    SYNTAX      Gauge32
    UNITS       "subscribers"
    MAX-ACCESS  read-only
    STATUS      current
    DESCRIPTION
        "The value of tmnxBsxGrpMdaEsmMacSubscribers indicates the current
         number of Enhanced Subscriber Management (ESM) MAC host subscribers
         active on the ISA-AA MDA in the group."
    ::= { tmnxBsxGrpMdaEntry 20 }

tmnxBsxMdaSlotEsaVmId            OBJECT-TYPE
    SYNTAX      Unsigned32
    MAX-ACCESS  not-accessible
    STATUS      current
    DESCRIPTION
        "The value of tmnxBsxMdaSlotEsaVmId indicates the MDA slot number of
         this ISA-AA MDA or the ESA VM ID."
    ::= { tmnxBsxGrpMdaEntry 21 }

tmnxBsxGrpMdaCflowdColl          OBJECT-TYPE
    SYNTAX      Unsigned32
    MAX-ACCESS  read-only
    STATUS      current
    DESCRIPTION
        "The value of tmnxBsxGrpMdaCflowdColl indicates the configured cflowd
         direct export collector that is used for sending the cflowd records."
    ::= { tmnxBsxGrpMdaEntry 22 }

tmnxBsxGrpMdaMgCardGroupId       OBJECT-TYPE
    SYNTAX      Unsigned32
    MAX-ACCESS  read-only
    STATUS      current
    DESCRIPTION
        "The value of tmnxBsxGrpMdaMgCardGroupId indicates the configured
         mobile gateway card group Id that this MDA is a part of. This object
         is applicable only on AA groups with MG based subscale, otherwise the
         returned value is 0."
    ::= { tmnxBsxGrpMdaEntry 23 }

tmnxBsxGrpStatusTable            OBJECT-TYPE
    SYNTAX      SEQUENCE OF TmnxBsxGrpStatusEntry
    MAX-ACCESS  not-accessible
    STATUS      current
    DESCRIPTION
        "The tmnxBsxGrpStatusTable contains an entry for each ISA-AA MDA and
         Group in the system. Each row contains the performance-oriented status
         information per group for an ISA-AA MDA uniquely identified by the
         tmnxChassisIndex, tmnxBsxCardSlotEsaId, and the tmnxBsxMdaSlotEsaVmId."
    ::= { tmnxBsxMdaObjs 5 }

tmnxBsxGrpStatusEntry            OBJECT-TYPE
    SYNTAX      TmnxBsxGrpStatusEntry
    MAX-ACCESS  not-accessible
    STATUS      current
    DESCRIPTION
        "Each tmnxBsxGrpStatusEntry contains the performance-oriented status
         information for a particular group and ISA-AA MDA.

         An index with a valid tmnxBsxIsaAaGroupIndex, tmnxChassisIndex set to
         one, and a zero value for each of the
         tmnxBsxCardSlotEsaId/tmnxBsxMdaSlotEsaVmId indices will return the
         summarized per group status.

         Rows in this table are created by the agent at initialization and
         cannot be created or destroyed by SNMP Set requests."
    INDEX       {
        tmnxBsxIsaAaGroupIndex,
        tmnxChassisIndex,
        tmnxBsxCardSlotEsaId,
        tmnxBsxMdaSlotEsaVmId
    }
    ::= { tmnxBsxGrpStatusTable 1 }

TmnxBsxGrpStatusEntry            ::= SEQUENCE
{
    tmnxBsxGrpStatusDiscontTime      TimeStamp,
    tmnxBsxGrpStatusOctsIn           Counter32,
    tmnxBsxGrpStatusPktsIn           Counter32,
    tmnxBsxGrpStatusPktsInPChipErs   Counter32,
    tmnxBsxGrpStatusOctsDiscCongIn   Counter32,
    tmnxBsxGrpStatusPktsDiscCongIn   Counter32,
    tmnxBsxGrpStatusOctsToMda        Counter32,
    tmnxBsxGrpStatusPktsToMda        Counter32,
    tmnxBsxGrpStatusOctsDisCongMda   Counter32,
    tmnxBsxGrpStatusPktsDisCongMda   Counter32,
    tmnxBsxGrpStatusOctsDiscErrors   Counter32,
    tmnxBsxGrpStatusPktsDiscErrors   Counter32,
    tmnxBsxGrpStatusOctsPolicyByps   Counter32,
    tmnxBsxGrpStatusPktsPolicyByps   Counter32,
    tmnxBsxGrpStatusOctsInspected    Counter32,
    tmnxBsxGrpStatusPktsInspected    Counter32,
    tmnxBsxGrpStatusOctsDiscPolicy   Counter32,
    tmnxBsxGrpStatusPktsDiscPolicy   Counter32,
    tmnxBsxGrpStatusOctsInMda        Counter32,
    tmnxBsxGrpStatusPktsInMda        Counter32,
    tmnxBsxGrpStatusOctsFromMda      Counter32,
    tmnxBsxGrpStatusPktsFromMda      Counter32,
    tmnxBsxGrpStatusPktsOutPChipEr   Counter32,
    tmnxBsxGrpStatusOctsDisCongOut   Counter32,
    tmnxBsxGrpStatusPktsDisCongOut   Counter32,
    tmnxBsxGrpStatusOctsOut          Counter32,
    tmnxBsxGrpStatusPktsOut          Counter32,
    tmnxBsxGrpStatusFlows            Counter32,
    tmnxBsxGrpStatusFlowsCurrent     Gauge32,
    tmnxBsxGrpStatusFlowSetupRate    Gauge32,
    tmnxBsxGrpStatusSubsDiverted     Gauge32,
    tmnxBsxGrpStatusSubsCurrent      Gauge32,
    tmnxBsxGrpStatusTrafficRate      Gauge32,
    tmnxBsxGrpStatusHCOctsIn         Counter64,
    tmnxBsxGrpStatusHCPktsIn         Counter64,
    tmnxBsxGrpStatusHCPktsInPChipErs Counter64,
    tmnxBsxGrpStatusHCOctsDiscCongIn Counter64,
    tmnxBsxGrpStatusHCPktsDiscCongIn Counter64,
    tmnxBsxGrpStatusHCOctsToMda      Counter64,
    tmnxBsxGrpStatusHCPktsToMda      Counter64,
    tmnxBsxGrpStatusHCOctsDisCongMda Counter64,
    tmnxBsxGrpStatusHCPktsDisCongMda Counter64,
    tmnxBsxGrpStatusHCOctsDiscErrors Counter64,
    tmnxBsxGrpStatusHCPktsDiscErrors Counter64,
    tmnxBsxGrpStatusHCOctsPolicyByps Counter64,
    tmnxBsxGrpStatusHCPktsPolicyByps Counter64,
    tmnxBsxGrpStatusHCOctsInspected  Counter64,
    tmnxBsxGrpStatusHCPktsInspected  Counter64,
    tmnxBsxGrpStatusHCOctsDiscPolicy Counter64,
    tmnxBsxGrpStatusHCPktsDiscPolicy Counter64,
    tmnxBsxGrpStatusHCOctsInMda      Counter64,
    tmnxBsxGrpStatusHCPktsInMda      Counter64,
    tmnxBsxGrpStatusHCOctsFromMda    Counter64,
    tmnxBsxGrpStatusHCPktsFromMda    Counter64,
    tmnxBsxGrpStatusHCPktsOutPChipEr Counter64,
    tmnxBsxGrpStatusHCOctsDisCongOut Counter64,
    tmnxBsxGrpStatusHCPktsDisCongOut Counter64,
    tmnxBsxGrpStatusHCOctsOut        Counter64,
    tmnxBsxGrpStatusHCPktsOut        Counter64,
    tmnxBsxGrpStatusHCFlows          Counter64,
    tmnxBsxGrpStatusFlowsAverage     Gauge32,
    tmnxBsxGrpStatusFlowsPeak        Gauge32,
    tmnxBsxGrpStatusFlowSetupRateAvg Gauge32,
    tmnxBsxGrpStatusFlowSetupRatePk  Gauge32,
    tmnxBsxGrpStatusSubsDivertedAvg  Gauge32,
    tmnxBsxGrpStatusSubsDivertedPk   Gauge32,
    tmnxBsxGrpStatusSubsAverage      Gauge32,
    tmnxBsxGrpStatusSubsPeak         Gauge32,
    tmnxBsxGrpStatusTrafficRateAvg   Gauge32,
    tmnxBsxGrpStatusTrafficRatePeak  Gauge32,
    tmnxBsxGrpStatusPacketRate       Gauge32,
    tmnxBsxGrpStatusPacketRateAvg    Gauge32,
    tmnxBsxGrpStatusPacketRatePeak   Gauge32,
    tmnxBsxGrpStatusFlowResInUse     Gauge32,
    tmnxBsxGrpStatusHCPktSzIncPk     Counter64,
    tmnxBsxGrpStatusPktSzIncPkLo     Counter32,
    tmnxBsxGrpStatusPktSzIncPkHi     Counter32,
    tmnxBsxGrpStatusHCPktSzDecPk     Counter64,
    tmnxBsxGrpStatusPktSzDecPkLo     Counter32,
    tmnxBsxGrpStatusPktSzDecPkHi     Counter32,
    tmnxBsxGrpStatusHCPktSzIncOc     Counter64,
    tmnxBsxGrpStatusPktSzIncOcLo     Counter32,
    tmnxBsxGrpStatusPktSzIncOcHi     Counter32,
    tmnxBsxGrpStatusHCPktSzDecOc     Counter64,
    tmnxBsxGrpStatusPktSzDecOcLo     Counter32,
    tmnxBsxGrpStatusPktSzDecOcHi     Counter32,
    tmnxBsxGrpStatusHCSeenIpReqSent  Counter64,
    tmnxBsxGrpStatusSeenIpReqSentLo  Counter32,
    tmnxBsxGrpStatusSeenIpReqSentHi  Counter32,
    tmnxBsxGrpStatusHCSeenIpReqDrop  Counter64,
    tmnxBsxGrpStatusSeenIpReqDropLo  Counter32,
    tmnxBsxGrpStatusSeenIpReqDropHi  Counter32,
    tmnxBsxGrpStatusHCSubsCreated    Counter64,
    tmnxBsxGrpStatusSubsCreatedLo    Counter32,
    tmnxBsxGrpStatusSubsCreatedHi    Counter32,
    tmnxBsxGrpStatusHCSubsDeleted    Counter64,
    tmnxBsxGrpStatusSubsDeletedLo    Counter32,
    tmnxBsxGrpStatusSubsDeletedHi    Counter32,
    tmnxBsxGrpStatusHCSubsModified   Counter64,
    tmnxBsxGrpStatusSubsModifiedLo   Counter32,
    tmnxBsxGrpStatusSubsModifiedHi   Counter32,
    tmnxBsxGrpStatusPktsDiscTcpOpt   Counter64,
    tmnxBsxGrpStatusOctsDiscTcpOpt   Counter64,
    tmnxBsxGrpStatusPktsGenTcpOpt    Counter64,
    tmnxBsxGrpStatusOctsGenTcpOpt    Counter64,
    tmnxBsxGrpStatusFlowResMax       Gauge32,
    tmnxBsxGrpStatusFlowResAvg       Gauge32,
    tmnxBsxGrpStatusFlowResPeak      Gauge32,
    tmnxBsxGrpStatusFlowResState     TmnxBsxTcaState,
    tmnxBsxGrpStatusFlowResRsdCount  Counter64,
    tmnxBsxGrpStatusFlowResRaisdTime Counter64,
    tmnxBsxGrpStatusFlowSetupState   TmnxBsxTcaState,
    tmnxBsxGrpStatusFlowSetupRsdCnt  Counter64,
    tmnxBsxGrpStatusFlowSetupRsdTime Counter64,
    tmnxBsxGrpStatusBitRateState     TmnxBsxTcaState,
    tmnxBsxGrpStatusBitRateRsdCount  Counter64,
    tmnxBsxGrpStatusBitRateRsdTime   Counter64,
    tmnxBsxGrpStatusPktRateState     TmnxBsxTcaState,
    tmnxBsxGrpStatusPktRateRsdCount  Counter64,
    tmnxBsxGrpStatusPktRateRaisdTime Counter64,
    tmnxBsxGrpStatusDatapathCpu      TmnxBsxHundredthsOfPercent,
    tmnxBsxGrpStatusDatapathCpuAvg   TmnxBsxHundredthsOfPercent,
    tmnxBsxGrpStatusDatapathCpuPeak  TmnxBsxHundredthsOfPercent,
    tmnxBsxGrpStatusDatapathCpuState TmnxBsxTcaState,
    tmnxBsxGrpStatusDatapathCpuRsdCt Counter64,
    tmnxBsxGrpStatusDatapathCpuRsdTm Counter64,
    tmnxBsxGrpStatusMgmtCpu          TmnxBsxHundredthsOfPercent,
    tmnxBsxGrpStatusMgmtCpuAvg       TmnxBsxHundredthsOfPercent,
    tmnxBsxGrpStatusMgmtCpuPeak      TmnxBsxHundredthsOfPercent,
    tmnxBsxGrpStatusWaSBfFmSub       TmnxBsxHundredthsOfPercent,
    tmnxBsxGrpStatusWaSBfFmSubState  TmnxBsxTcaState,
    tmnxBsxGrpStatusWaSBfFmSubRsdCnt Counter64,
    tmnxBsxGrpStatusWaSBfFmSubRsdTm  Counter64,
    tmnxBsxGrpStatusWaSBfToSub       TmnxBsxHundredthsOfPercent,
    tmnxBsxGrpStatusWaSBfToSubState  TmnxBsxTcaState,
    tmnxBsxGrpStatusWaSBfToSubRsdCnt Counter64,
    tmnxBsxGrpStatusWaSBfToSubRsdTm  Counter64,
    tmnxBsxGrpStatusFlwResCtThruOcts Counter64,
    tmnxBsxGrpStatusFlwResCtThruPkts Counter64,
    tmnxBsxGrpStatusOvrldCtThruOcts  Counter64,
    tmnxBsxGrpStatusOvrldCtThruPkts  Counter64,
    tmnxBsxGrpStatusOvrldCtThruState TmnxBsxTcaState,
    tmnxBsxGrpStatusOvrldCtThruRsdCt Counter64,
    tmnxBsxGrpStatusOvrldCtThruRsdTm Counter64,
    tmnxBsxGrpStatusOctsGenHttpRedir Counter64,
    tmnxBsxGrpStatusPktsGenHttpRedir Counter64,
    tmnxBsxGrpStatusPktsInToSub      Counter64,
    tmnxBsxGrpStatusPktsInFrSub      Counter64,
    tmnxBsxGrpStatusOctsInToSub      Counter64,
    tmnxBsxGrpStatusOctsInFrSub      Counter64,
    tmnxBsxGrpStatusPktDisCngInToSub Counter64,
    tmnxBsxGrpStatusPktDisCngInFrSub Counter64,
    tmnxBsxGrpStatusOctDisCngInToSub Counter64,
    tmnxBsxGrpStatusOctDisCngInFrSub Counter64,
    tmnxBsxGrpStatusPktInPChpErToSub Counter64,
    tmnxBsxGrpStatusPktInPChpErFrSub Counter64,
    tmnxBsxGrpStatusPktsToMdaToSub   Counter64,
    tmnxBsxGrpStatusPktsToMdaFrSub   Counter64,
    tmnxBsxGrpStatusPktsInMdaToSub   Counter64,
    tmnxBsxGrpStatusPktsInMdaFrSub   Counter64,
    tmnxBsxGrpStatusPkDisCngMdaToSub Counter64,
    tmnxBsxGrpStatusPkDisCngMdaFrSub Counter64,
    tmnxBsxGrpStatusPktDiscErrToSub  Counter64,
    tmnxBsxGrpStatusPktDiscErrFrSub  Counter64,
    tmnxBsxGrpStatusPktDiscPlcyToSub Counter64,
    tmnxBsxGrpStatusPktDiscPlcyFrSub Counter64,
    tmnxBsxGrpStatusPktDisTcOptToSub Counter64,
    tmnxBsxGrpStatusPktDisTcOptFrSub Counter64,
    tmnxBsxGrpStatusOcDisCngMdaToSub Counter64,
    tmnxBsxGrpStatusOcDisCngMdaFrSub Counter64,
    tmnxBsxGrpStatusOctDiscErrToSub  Counter64,
    tmnxBsxGrpStatusOctDiscErrFrSub  Counter64,
    tmnxBsxGrpStatusOctDiscPlcyToSub Counter64,
    tmnxBsxGrpStatusOctDiscPlcyFrSub Counter64,
    tmnxBsxGrpStatusOctDisTcOptToSub Counter64,
    tmnxBsxGrpStatusOctDisTcOptFrSub Counter64,
    tmnxBsxGrpStatusPktSzIncPkToSub  Counter64,
    tmnxBsxGrpStatusPktSzIncPkFrSub  Counter64,
    tmnxBsxGrpStatusPktSzDecPkToSub  Counter64,
    tmnxBsxGrpStatusPktSzDecPkFrSub  Counter64,
    tmnxBsxGrpStatusPktSzIncOcToSub  Counter64,
    tmnxBsxGrpStatusPktSzIncOcFrSub  Counter64,
    tmnxBsxGrpStatusPktSzDecOcToSub  Counter64,
    tmnxBsxGrpStatusPktSzDecOcFrSub  Counter64,
    tmnxBsxGrpStatusPktPlcyBypsToSub Counter64,
    tmnxBsxGrpStatusPktPlcyBypsFrSub Counter64,
    tmnxBsxGrpStatusOctPlcyBypsToSub Counter64,
    tmnxBsxGrpStatusOctPlcyBypsFrSub Counter64,
    tmnxBsxGrpStatusPktGenTcOptToSub Counter64,
    tmnxBsxGrpStatusPktGenTcOptFrSub Counter64,
    tmnxBsxGrpStatusOctGenTcOptToSub Counter64,
    tmnxBsxGrpStatusOctGenTcOptFrSub Counter64,
    tmnxBsxGrpStatusPkGenHttpRdToSub Counter64,
    tmnxBsxGrpStatusPkGenHttpRdFrSub Counter64,
    tmnxBsxGrpStatusOcGenHttpRdToSub Counter64,
    tmnxBsxGrpStatusOcGenHttpRdFrSub Counter64,
    tmnxBsxGrpStatusPktsFromMdaToSub Counter64,
    tmnxBsxGrpStatusPktsFromMdaFrSub Counter64,
    tmnxBsxGrpStatusOctsFromMdaToSub Counter64,
    tmnxBsxGrpStatusOctsFromMdaFrSub Counter64,
    tmnxBsxGrpStatusPkDisConOutToSub Counter64,
    tmnxBsxGrpStatusPkDisConOutFrSub Counter64,
    tmnxBsxGrpStatusOcDisConOutToSub Counter64,
    tmnxBsxGrpStatusOcDisConOutFrSub Counter64,
    tmnxBsxGrpStatusPktOutPChErToSub Counter64,
    tmnxBsxGrpStatusPktOutPChErFrSub Counter64,
    tmnxBsxGrpStatusPktsOutToSub     Counter64,
    tmnxBsxGrpStatusPktsOutFrSub     Counter64,
    tmnxBsxGrpStatusOctsOutToSub     Counter64,
    tmnxBsxGrpStatusOctsOutFrSub     Counter64,
    tmnxBsxGrpStatusPktCutThrough    Counter64,
    tmnxBsxGrpStatusPktCutThrouToSub Counter64,
    tmnxBsxGrpStatusPktCutThrouFrSub Counter64,
    tmnxBsxGrpStatusOctCutThrough    Counter64,
    tmnxBsxGrpStatusOctCutThrouToSub Counter64,
    tmnxBsxGrpStatusOctCutThrouFrSub Counter64,
    tmnxBsxGrpStatusOctsToMdaToSub   Counter64,
    tmnxBsxGrpStatusOctsToMdaFrSub   Counter64,
    tmnxBsxGrpStatusOctsInMdaToSub   Counter64,
    tmnxBsxGrpStatusOctsInMdaFrSub   Counter64,
    tmnxBsxGrpStatusSubsQuarantined  Counter64
}

tmnxBsxGrpStatusDiscontTime      OBJECT-TYPE
    SYNTAX      TimeStamp
    MAX-ACCESS  read-only
    STATUS      current
    DESCRIPTION
        "The value of tmnxBsxGrpStatusDiscontTime indicates the
         SNMPv2-MIB::sysUpTime (centiseconds) when the ISA-AA MDA within the
         group has last changed status."
    ::= { tmnxBsxGrpStatusEntry 1 }

tmnxBsxGrpStatusOctsIn           OBJECT-TYPE
    SYNTAX      Counter32
    UNITS       "bytes"
    MAX-ACCESS  read-only
    STATUS      current
    DESCRIPTION
        "The value of tmnxBsxGrpStatusOctsIn indicates the number of bytes
         diverted from ingress IOMs towards the ISA-AA MDA(s)."
    ::= { tmnxBsxGrpStatusEntry 2 }

tmnxBsxGrpStatusPktsIn           OBJECT-TYPE
    SYNTAX      Counter32
    UNITS       "packets"
    MAX-ACCESS  read-only
    STATUS      current
    DESCRIPTION
        "The value of tmnxBsxGrpStatusPktsIn indicates the number of packets
         diverted from ingress IOMs towards the ISA-AA MDA(s)."
    ::= { tmnxBsxGrpStatusEntry 3 }

tmnxBsxGrpStatusPktsInPChipErs   OBJECT-TYPE
    SYNTAX      Counter32
    UNITS       "packets"
    MAX-ACCESS  read-only
    STATUS      current
    DESCRIPTION
        "The value of tmnxBsxGrpStatusPktsInPChipErs indicates the number of
         packets discarded by the egress P-chip due to errors in the packets."
    ::= { tmnxBsxGrpStatusEntry 4 }

tmnxBsxGrpStatusOctsDiscCongIn   OBJECT-TYPE
    SYNTAX      Counter32
    UNITS       "bytes"
    MAX-ACCESS  read-only
    STATUS      current
    DESCRIPTION
        "The value of tmnxBsxGrpStatusOctsDiscCongIn indicates the number of
         bytes discarded by the IOMs prior to the ISA-AA MDA(s) due to egress
         IOM congestion."
    ::= { tmnxBsxGrpStatusEntry 5 }

tmnxBsxGrpStatusPktsDiscCongIn   OBJECT-TYPE
    SYNTAX      Counter32
    UNITS       "packets"
    MAX-ACCESS  read-only
    STATUS      current
    DESCRIPTION
        "The value of tmnxBsxGrpStatusPktsDiscCongIn indicates the number of
         packets discarded by the IOMs prior to the ISA-AA MDA(s) due to egress
         IOM congestion."
    ::= { tmnxBsxGrpStatusEntry 6 }

tmnxBsxGrpStatusOctsToMda        OBJECT-TYPE
    SYNTAX      Counter32
    UNITS       "bytes"
    MAX-ACCESS  read-only
    STATUS      current
    DESCRIPTION
        "The value of tmnxBsxGrpStatusOctsToMda indicates the number of bytes
         sent from an IOM which enter the ISA-AA MDA(s)."
    ::= { tmnxBsxGrpStatusEntry 7 }

tmnxBsxGrpStatusPktsToMda        OBJECT-TYPE
    SYNTAX      Counter32
    UNITS       "packets"
    MAX-ACCESS  read-only
    STATUS      current
    DESCRIPTION
        "The value of tmnxBsxGrpStatusPktsToMda indicates the number of packets
         sent from an IOM which enter the ISA-AA MDA(s)."
    ::= { tmnxBsxGrpStatusEntry 8 }

tmnxBsxGrpStatusOctsDisCongMda   OBJECT-TYPE
    SYNTAX      Counter32
    UNITS       "bytes"
    MAX-ACCESS  read-only
    STATUS      current
    DESCRIPTION
        "The value of tmnxBsxGrpStatusOctsDisCongMda indicates the number of
         bytes discarded by the ISA-AA MDA(s) due to congestion."
    ::= { tmnxBsxGrpStatusEntry 9 }

tmnxBsxGrpStatusPktsDisCongMda   OBJECT-TYPE
    SYNTAX      Counter32
    UNITS       "packets"
    MAX-ACCESS  read-only
    STATUS      current
    DESCRIPTION
        "The value of tmnxBsxGrpStatusPktsDisCongMda indicates the number of
         packets discarded by the ISA-AA MDA(s) due to congestion."
    ::= { tmnxBsxGrpStatusEntry 10 }

tmnxBsxGrpStatusOctsDiscErrors   OBJECT-TYPE
    SYNTAX      Counter32
    UNITS       "bytes"
    MAX-ACCESS  read-only
    STATUS      current
    DESCRIPTION
        "The value of tmnxBsxGrpStatusOctsDiscErrors indicates the number of
         bytes discarded due to unrecoverable errors."
    ::= { tmnxBsxGrpStatusEntry 11 }

tmnxBsxGrpStatusPktsDiscErrors   OBJECT-TYPE
    SYNTAX      Counter32
    UNITS       "packets"
    MAX-ACCESS  read-only
    STATUS      current
    DESCRIPTION
        "The value of tmnxBsxGrpStatusPktsDiscErrors indicates the number of
         packets discarded due to unrecoverable errors."
    ::= { tmnxBsxGrpStatusEntry 12 }

tmnxBsxGrpStatusOctsPolicyByps   OBJECT-TYPE
    SYNTAX      Counter32
    UNITS       "bytes"
    MAX-ACCESS  read-only
    STATUS      current
    DESCRIPTION
        "The value of tmnxBsxGrpStatusOctsPolicyByps indicates the number of
         bytes which pass untouched that did not have statistics or policy
         applied. These bytes are counted as policy bypass errors."
    ::= { tmnxBsxGrpStatusEntry 13 }

tmnxBsxGrpStatusPktsPolicyByps   OBJECT-TYPE
    SYNTAX      Counter32
    UNITS       "packets"
    MAX-ACCESS  read-only
    STATUS      current
    DESCRIPTION
        "The value of tmnxBsxGrpStatusPktsPolicyByps indicates the number of
         packets which passed untouched that did not have statistics or policy
         applied. These packets are counted as policy bypass errors."
    ::= { tmnxBsxGrpStatusEntry 14 }

tmnxBsxGrpStatusOctsInspected    OBJECT-TYPE
    SYNTAX      Counter32
    UNITS       "bytes"
    MAX-ACCESS  read-only
    STATUS      current
    DESCRIPTION
        "The value of tmnxBsxGrpStatusOctsInspected indicates the number of
         bytes sent for protocol determination by the ISA-AA MDA(s)."
    ::= { tmnxBsxGrpStatusEntry 15 }

tmnxBsxGrpStatusPktsInspected    OBJECT-TYPE
    SYNTAX      Counter32
    UNITS       "packets"
    MAX-ACCESS  read-only
    STATUS      current
    DESCRIPTION
        "The value of tmnxBsxGrpStatusPktsInspected indicates the number of
         packets sent for protocol determination by the ISA-AA MDA(s)."
    ::= { tmnxBsxGrpStatusEntry 16 }

tmnxBsxGrpStatusOctsDiscPolicy   OBJECT-TYPE
    SYNTAX      Counter32
    UNITS       "bytes"
    MAX-ACCESS  read-only
    STATUS      current
    DESCRIPTION
        "The value of tmnxBsxGrpStatusOctsDiscPolicy indicates the number of
         bytes discarded by the ISA-AA MDA(s) due to policy."
    ::= { tmnxBsxGrpStatusEntry 17 }

tmnxBsxGrpStatusPktsDiscPolicy   OBJECT-TYPE
    SYNTAX      Counter32
    UNITS       "packets"
    MAX-ACCESS  read-only
    STATUS      current
    DESCRIPTION
        "The value of tmnxBsxGrpStatusPktsDiscPolicy indicates the number of
         packets discarded by the ISA-AA MDA(s) due to policy."
    ::= { tmnxBsxGrpStatusEntry 18 }

tmnxBsxGrpStatusOctsInMda        OBJECT-TYPE
    SYNTAX      Counter32
    UNITS       "bytes"
    MAX-ACCESS  read-only
    STATUS      current
    DESCRIPTION
        "The value of tmnxBsxGrpStatusOctsInMda indicates the number of bytes
         buffered by the ISA-AA MDA(s)."
    ::= { tmnxBsxGrpStatusEntry 19 }

tmnxBsxGrpStatusPktsInMda        OBJECT-TYPE
    SYNTAX      Counter32
    UNITS       "packets"
    MAX-ACCESS  read-only
    STATUS      current
    DESCRIPTION
        "The value of tmnxBsxGrpStatusPktsInMda indicates the number of packets
         buffered by the ISA-AA MDA(s)."
    ::= { tmnxBsxGrpStatusEntry 20 }

tmnxBsxGrpStatusOctsFromMda      OBJECT-TYPE
    SYNTAX      Counter32
    UNITS       "bytes"
    MAX-ACCESS  read-only
    STATUS      current
    DESCRIPTION
        "The value of tmnxBsxGrpStatusOctsFromMda indicates the number of bytes
         which exit the ISA-AA MDA(s) and are sent to the local IOM."
    ::= { tmnxBsxGrpStatusEntry 21 }

tmnxBsxGrpStatusPktsFromMda      OBJECT-TYPE
    SYNTAX      Counter32
    UNITS       "packets"
    MAX-ACCESS  read-only
    STATUS      current
    DESCRIPTION
        "The value of tmnxBsxGrpStatusPktsFromMda indicates the number of
         packets which exit the ISA-AA MDA(s) and are sent to the local IOM."
    ::= { tmnxBsxGrpStatusEntry 22 }

tmnxBsxGrpStatusPktsOutPChipEr   OBJECT-TYPE
    SYNTAX      Counter32
    UNITS       "packets"
    MAX-ACCESS  read-only
    STATUS      current
    DESCRIPTION
        "The value of tmnxBsxGrpStatusPktsOutPChipEr indicates the number of
         packets discarded due to an error detected by the P-chip while
         attempting to return the packet to the normal forwarding path."
    ::= { tmnxBsxGrpStatusEntry 23 }

tmnxBsxGrpStatusOctsDisCongOut   OBJECT-TYPE
    SYNTAX      Counter32
    UNITS       "bytes"
    MAX-ACCESS  read-only
    STATUS      current
    DESCRIPTION
        "The value of tmnxBsxGrpStatusOctsDisCongOut indicates the number of
         bytes discarded by the IOMs after the ISA-AA MDA(s) due to ingress IOM
         congestion."
    ::= { tmnxBsxGrpStatusEntry 24 }

tmnxBsxGrpStatusPktsDisCongOut   OBJECT-TYPE
    SYNTAX      Counter32
    UNITS       "packets"
    MAX-ACCESS  read-only
    STATUS      current
    DESCRIPTION
        "The value of tmnxBsxGrpStatusPktsDisCongOut indicates the number of
         packets discarded by the IOMs after the ISA-AA MDA(s) due to ingress
         IOM congestion."
    ::= { tmnxBsxGrpStatusEntry 25 }

tmnxBsxGrpStatusOctsOut          OBJECT-TYPE
    SYNTAX      Counter32
    UNITS       "bytes"
    MAX-ACCESS  read-only
    STATUS      current
    DESCRIPTION
        "The value of tmnxBsxGrpStatusOctsOut indicates the number of bytes
         returned to the normal forwarding path that are sent to egress IOMs
         from the ISA-AA MDA(s)."
    ::= { tmnxBsxGrpStatusEntry 26 }

tmnxBsxGrpStatusPktsOut          OBJECT-TYPE
    SYNTAX      Counter32
    UNITS       "packets"
    MAX-ACCESS  read-only
    STATUS      current
    DESCRIPTION
        "The value of tmnxBsxGrpStatusPktsOut indicates the number of packets
         returned to the normal forwarding path that are sent to egress IOMs
         from the ISA-AA MDA(s)."
    ::= { tmnxBsxGrpStatusEntry 27 }

tmnxBsxGrpStatusFlows            OBJECT-TYPE
    SYNTAX      Counter32
    UNITS       "flows"
    MAX-ACCESS  read-only
    STATUS      current
    DESCRIPTION
        "The value of tmnxBsxGrpStatusFlows indicates the total number of flows
         created on the ISA-AA MDA(s)."
    ::= { tmnxBsxGrpStatusEntry 28 }

tmnxBsxGrpStatusFlowsCurrent     OBJECT-TYPE
    SYNTAX      Gauge32
    UNITS       "flows"
    MAX-ACCESS  read-only
    STATUS      current
    DESCRIPTION
        "The value of tmnxBsxGrpStatusFlowsCurrent indicates the number of
         active flows currently being tracked by the ISA-AA MDA(s)."
    ::= { tmnxBsxGrpStatusEntry 29 }

tmnxBsxGrpStatusFlowSetupRate    OBJECT-TYPE
    SYNTAX      Gauge32
    UNITS       "flows per second"
    MAX-ACCESS  read-only
    STATUS      current
    DESCRIPTION
        "The value of tmnxBsxGrpStatusFlowSetupRate indicates the number of
         flow setups per second over the most recent 10 second period."
    ::= { tmnxBsxGrpStatusEntry 30 }

tmnxBsxGrpStatusSubsDiverted     OBJECT-TYPE
    SYNTAX      Gauge32
    UNITS       "subscribers"
    MAX-ACCESS  read-only
    STATUS      current
    DESCRIPTION
        "The value of tmnxBsxGrpStatusSubsDiverted indicates the number of
         subscribers defined in
         TIMETRA-SUBSCRIBER-MGMT-MIB::tmnxSubInfoAppProfile in the
         tmnxSubscriberInfoTable with tmnxBsxAppProfDivert set to 'true'."
    ::= { tmnxBsxGrpStatusEntry 31 }

tmnxBsxGrpStatusSubsCurrent      OBJECT-TYPE
    SYNTAX      Gauge32
    UNITS       "subscribers"
    MAX-ACCESS  read-only
    STATUS      current
    DESCRIPTION
        "The value of tmnxBsxGrpStatusSubsCurrent indicates the number of
         subscribers currently with flow records in the ISA-AA MDA(s)."
    ::= { tmnxBsxGrpStatusEntry 32 }

tmnxBsxGrpStatusTrafficRate      OBJECT-TYPE
    SYNTAX      Gauge32
    UNITS       "kilobps"
    MAX-ACCESS  read-only
    STATUS      current
    DESCRIPTION
        "The value of tmnxBsxGrpStatusTrafficRate indicates the traffic rate in
         kilobits(s) per second (kbps) incoming to the ISA-AA MDA(s)."
    ::= { tmnxBsxGrpStatusEntry 33 }

tmnxBsxGrpStatusHCOctsIn         OBJECT-TYPE
    SYNTAX      Counter64
    UNITS       "bytes"
    MAX-ACCESS  read-only
    STATUS      current
    DESCRIPTION
        "The value of tmnxBsxGrpStatusHCOctsIn indicates the number of bytes
         diverted from ingress IOMs towards the ISA-AA MDA(s)."
    ::= { tmnxBsxGrpStatusEntry 34 }

tmnxBsxGrpStatusHCPktsIn         OBJECT-TYPE
    SYNTAX      Counter64
    UNITS       "packets"
    MAX-ACCESS  read-only
    STATUS      current
    DESCRIPTION
        "The value of tmnxBsxGrpStatusHCPktsIn indicates the number of packets
         diverted from ingress IOMs towards the ISA-AA MDA(s)."
    ::= { tmnxBsxGrpStatusEntry 35 }

tmnxBsxGrpStatusHCPktsInPChipErs OBJECT-TYPE
    SYNTAX      Counter64
    UNITS       "packets"
    MAX-ACCESS  read-only
    STATUS      current
    DESCRIPTION
        "The value of tmnxBsxGrpStatusHCPktsInPChipErs indicates the number of
         packets discarded by the egress P-chip due to errors in the packets."
    ::= { tmnxBsxGrpStatusEntry 36 }

tmnxBsxGrpStatusHCOctsDiscCongIn OBJECT-TYPE
    SYNTAX      Counter64
    UNITS       "bytes"
    MAX-ACCESS  read-only
    STATUS      current
    DESCRIPTION
        "The value of tmnxBsxGrpStatusHCOctsDiscCongIn indicates the number of
         bytes discarded by the IOMs prior to the ISA-AA MDA(s) due to egress
         IOM congestion."
    ::= { tmnxBsxGrpStatusEntry 37 }

tmnxBsxGrpStatusHCPktsDiscCongIn OBJECT-TYPE
    SYNTAX      Counter64
    UNITS       "packets"
    MAX-ACCESS  read-only
    STATUS      current
    DESCRIPTION
        "The value of tmnxBsxGrpStatusHCPktsDiscCongIn indicates the number of
         packets discarded by the IOMs prior to the ISA-AA MDA(s) due to egress
         IOM congestion."
    ::= { tmnxBsxGrpStatusEntry 38 }

tmnxBsxGrpStatusHCOctsToMda      OBJECT-TYPE
    SYNTAX      Counter64
    UNITS       "bytes"
    MAX-ACCESS  read-only
    STATUS      current
    DESCRIPTION
        "The value of tmnxBsxGrpStatusHCOctsToMda indicates the number of bytes
         sent from an IOM which enter the ISA-AA MDA(s)."
    ::= { tmnxBsxGrpStatusEntry 39 }

tmnxBsxGrpStatusHCPktsToMda      OBJECT-TYPE
    SYNTAX      Counter64
    UNITS       "packets"
    MAX-ACCESS  read-only
    STATUS      current
    DESCRIPTION
        "The value of tmnxBsxGrpStatusHCPktsToMda indicates the number of
         packets sent from an IOM which enter the ISA-AA MDA(s)."
    ::= { tmnxBsxGrpStatusEntry 40 }

tmnxBsxGrpStatusHCOctsDisCongMda OBJECT-TYPE
    SYNTAX      Counter64
    UNITS       "bytes"
    MAX-ACCESS  read-only
    STATUS      current
    DESCRIPTION
        "The value of tmnxBsxGrpStatusHCOctsDisCongMda indicates the number of
         bytes discarded by the ISA-AA MDA(s) due to congestion."
    ::= { tmnxBsxGrpStatusEntry 41 }

tmnxBsxGrpStatusHCPktsDisCongMda OBJECT-TYPE
    SYNTAX      Counter64
    UNITS       "packets"
    MAX-ACCESS  read-only
    STATUS      current
    DESCRIPTION
        "The value of tmnxBsxGrpStatusHCPktsDisCongMda indicates the number of
         packets discarded by the ISA-AA MDA(s) due to congestion."
    ::= { tmnxBsxGrpStatusEntry 42 }

tmnxBsxGrpStatusHCOctsDiscErrors OBJECT-TYPE
    SYNTAX      Counter64
    UNITS       "bytes"
    MAX-ACCESS  read-only
    STATUS      current
    DESCRIPTION
        "The value of tmnxBsxGrpStatusHCOctsDiscErrors indicates the number of
         bytes discarded due to unrecoverable errors."
    ::= { tmnxBsxGrpStatusEntry 43 }

tmnxBsxGrpStatusHCPktsDiscErrors OBJECT-TYPE
    SYNTAX      Counter64
    UNITS       "packets"
    MAX-ACCESS  read-only
    STATUS      current
    DESCRIPTION
        "The value of tmnxBsxGrpStatusHCPktsDiscErrors indicates the number of
         packets discarded due to unrecoverable errors."
    ::= { tmnxBsxGrpStatusEntry 44 }

tmnxBsxGrpStatusHCOctsPolicyByps OBJECT-TYPE
    SYNTAX      Counter64
    UNITS       "bytes"
    MAX-ACCESS  read-only
    STATUS      current
    DESCRIPTION
        "The value of tmnxBsxGrpStatusHCOctsPolicyByps indicates the number of
         bytes which passed untouched that did not have statistics or policy
         applied. These bytes are counted as policy bypass errors."
    ::= { tmnxBsxGrpStatusEntry 45 }

tmnxBsxGrpStatusHCPktsPolicyByps OBJECT-TYPE
    SYNTAX      Counter64
    UNITS       "packets"
    MAX-ACCESS  read-only
    STATUS      current
    DESCRIPTION
        "The value of tmnxBsxGrpStatusHCPktsPolicyByps indicates the number of
         packets which passed untouched that did not have statistics or policy
         applied. These packets are counted as policy bypass errors."
    ::= { tmnxBsxGrpStatusEntry 46 }

tmnxBsxGrpStatusHCOctsInspected  OBJECT-TYPE
    SYNTAX      Counter64
    UNITS       "bytes"
    MAX-ACCESS  read-only
    STATUS      current
    DESCRIPTION
        "The value of tmnxBsxGrpStatusHCOctsInspected indicates the number of
         bytes sent for protocol determination by the ISA-AA MDA(s)."
    ::= { tmnxBsxGrpStatusEntry 47 }

tmnxBsxGrpStatusHCPktsInspected  OBJECT-TYPE
    SYNTAX      Counter64
    UNITS       "packets"
    MAX-ACCESS  read-only
    STATUS      current
    DESCRIPTION
        "The value of tmnxBsxGrpStatusHCPktsInspected indicates the number of
         packets sent for protocol determination by the ISA-AA MDA(s)."
    ::= { tmnxBsxGrpStatusEntry 48 }

tmnxBsxGrpStatusHCOctsDiscPolicy OBJECT-TYPE
    SYNTAX      Counter64
    UNITS       "bytes"
    MAX-ACCESS  read-only
    STATUS      current
    DESCRIPTION
        "The value of tmnxBsxGrpStatusHCOctsDiscPolicy indicates the number of
         bytes discarded by the ISA-AA MDA(s) due to policy policers or discard
         actions."
    ::= { tmnxBsxGrpStatusEntry 49 }

tmnxBsxGrpStatusHCPktsDiscPolicy OBJECT-TYPE
    SYNTAX      Counter64
    UNITS       "packets"
    MAX-ACCESS  read-only
    STATUS      current
    DESCRIPTION
        "The value of tmnxBsxGrpStatusHCPktsDiscPolicy indicates the number of
         packets discarded by the ISA-AA MDA(s) due to policy policers or
         discard actions."
    ::= { tmnxBsxGrpStatusEntry 50 }

tmnxBsxGrpStatusHCOctsInMda      OBJECT-TYPE
    SYNTAX      Counter64
    UNITS       "bytes"
    MAX-ACCESS  read-only
    STATUS      current
    DESCRIPTION
        "The value of tmnxBsxGrpStatusHCOctsInMda indicates the number of bytes
         buffered by the ISA-AA MDA(s)."
    ::= { tmnxBsxGrpStatusEntry 51 }

tmnxBsxGrpStatusHCPktsInMda      OBJECT-TYPE
    SYNTAX      Counter64
    UNITS       "packets"
    MAX-ACCESS  read-only
    STATUS      current
    DESCRIPTION
        "The value of tmnxBsxGrpStatusHCPktsInMda indicates the number of
         packets buffered by the ISA-AA MDA(s)."
    ::= { tmnxBsxGrpStatusEntry 52 }

tmnxBsxGrpStatusHCOctsFromMda    OBJECT-TYPE
    SYNTAX      Counter64
    UNITS       "bytes"
    MAX-ACCESS  read-only
    STATUS      current
    DESCRIPTION
        "The value of tmnxBsxGrpStatusHCOctsFromMda indicates the number of
         bytes which exit the ISA-AA MDA(s) and are sent to the local IOM."
    ::= { tmnxBsxGrpStatusEntry 53 }

tmnxBsxGrpStatusHCPktsFromMda    OBJECT-TYPE
    SYNTAX      Counter64
    UNITS       "packets"
    MAX-ACCESS  read-only
    STATUS      current
    DESCRIPTION
        "The value of tmnxBsxGrpStatusHCPktsFromMda indicates the number of
         packets which exit the ISA-AA MDA(s) and are sent to the local IOM."
    ::= { tmnxBsxGrpStatusEntry 54 }

tmnxBsxGrpStatusHCPktsOutPChipEr OBJECT-TYPE
    SYNTAX      Counter64
    UNITS       "packets"
    MAX-ACCESS  read-only
    STATUS      current
    DESCRIPTION
        "The value of tmnxBsxGrpStatusHCPktsOutPChipEr indicates the number of
         packets discarded by the ingress P-chip due to errors in the packets
         which return to the normal forwarding path."
    ::= { tmnxBsxGrpStatusEntry 55 }

tmnxBsxGrpStatusHCOctsDisCongOut OBJECT-TYPE
    SYNTAX      Counter64
    UNITS       "bytes"
    MAX-ACCESS  read-only
    STATUS      current
    DESCRIPTION
        "The value of tmnxBsxGrpStatusHCOctsDisCongOut indicates the number of
         bytes discarded by the IOMs after the ISA-AA MDA(s) due to ingress IOM
         congestion."
    ::= { tmnxBsxGrpStatusEntry 56 }

tmnxBsxGrpStatusHCPktsDisCongOut OBJECT-TYPE
    SYNTAX      Counter64
    UNITS       "packets"
    MAX-ACCESS  read-only
    STATUS      current
    DESCRIPTION
        "The value of tmnxBsxGrpStatusHCPktsDisCongOut indicates the number of
         packets discarded by the IOMs after the ISA-AA MDA(s) due to ingress
         IOM congestion."
    ::= { tmnxBsxGrpStatusEntry 57 }

tmnxBsxGrpStatusHCOctsOut        OBJECT-TYPE
    SYNTAX      Counter64
    UNITS       "bytes"
    MAX-ACCESS  read-only
    STATUS      current
    DESCRIPTION
        "The value of tmnxBsxGrpStatusHCOctsOut indicates the number of bytes
         returned to the normal forwarding path that are sent to egress IOMs
         from the ISA-AA MDA(s)."
    ::= { tmnxBsxGrpStatusEntry 58 }

tmnxBsxGrpStatusHCPktsOut        OBJECT-TYPE
    SYNTAX      Counter64
    UNITS       "packets"
    MAX-ACCESS  read-only
    STATUS      current
    DESCRIPTION
        "The value of tmnxBsxGrpStatusHCPktsOut indicates the number of packets
         returned to the normal forwarding path that are sent to egress IOMs
         from the ISA-AA MDA(s)."
    ::= { tmnxBsxGrpStatusEntry 59 }

tmnxBsxGrpStatusHCFlows          OBJECT-TYPE
    SYNTAX      Counter64
    UNITS       "flows"
    MAX-ACCESS  read-only
    STATUS      current
    DESCRIPTION
        "The value of tmnxBsxGrpStatusHCFlows indicates the number of active
         flows seen by the ISA-AA MDA(s). Note that if the same 5-tuple is seen
         for a different flow within the flow timeout, it will still be
         considered one flow."
    ::= { tmnxBsxGrpStatusEntry 60 }

tmnxBsxGrpStatusFlowsAverage     OBJECT-TYPE
    SYNTAX      Gauge32
    UNITS       "flows"
    MAX-ACCESS  read-only
    STATUS      current
    DESCRIPTION
        "The value of tmnxBsxGrpStatusFlowsAverage indicates the average number
         of active flows being tracked by the ISA-AA MDA(s) within the last 60
         minutes."
    ::= { tmnxBsxGrpStatusEntry 61 }

tmnxBsxGrpStatusFlowsPeak        OBJECT-TYPE
    SYNTAX      Gauge32
    UNITS       "flows"
    MAX-ACCESS  read-only
    STATUS      current
    DESCRIPTION
        "The value of tmnxBsxGrpStatusFlowsPeak indicates the peak number of
         active flows being tracked by the ISA-AA MDA(s) since system startup."
    ::= { tmnxBsxGrpStatusEntry 62 }

tmnxBsxGrpStatusFlowSetupRateAvg OBJECT-TYPE
    SYNTAX      Gauge32
    UNITS       "flows per second"
    MAX-ACCESS  read-only
    STATUS      current
    DESCRIPTION
        "The value of tmnxBsxGrpStatusFlowSetupRateAvg indicates the average
         number of flow setups per second being tracked by the ISA-AA MDA(s)
         within the last 60 minutes."
    ::= { tmnxBsxGrpStatusEntry 63 }

tmnxBsxGrpStatusFlowSetupRatePk  OBJECT-TYPE
    SYNTAX      Gauge32
    UNITS       "flows per second"
    MAX-ACCESS  read-only
    STATUS      current
    DESCRIPTION
        "The value of tmnxBsxGrpStatusFlowSetupRatePk indicates the peak number
         of flow setups per second being tracked by the ISA-AA MDA(s) since
         system startup."
    ::= { tmnxBsxGrpStatusEntry 64 }

tmnxBsxGrpStatusSubsDivertedAvg  OBJECT-TYPE
    SYNTAX      Gauge32
    UNITS       "subscribers"
    MAX-ACCESS  read-only
    STATUS      current
    DESCRIPTION
        "The value of tmnxBsxGrpStatusSubsDivertedAvg indicates the average
         number of subscribers defined in
         TIMETRA-SUBSCRIBER-MGMT-MIB::tmnxSubInfoAppProfile in the
         tmnxSubscriberInfoTable with tmnxBsxAppProfDivert set to 'true' within
         the last 60 minutes."
    ::= { tmnxBsxGrpStatusEntry 65 }

tmnxBsxGrpStatusSubsDivertedPk   OBJECT-TYPE
    SYNTAX      Gauge32
    UNITS       "subscribers"
    MAX-ACCESS  read-only
    STATUS      current
    DESCRIPTION
        "The value of tmnxBsxGrpStatusSubsDivertedPk indicates the peak number
         of subscribers defined in
         TIMETRA-SUBSCRIBER-MGMT-MIB::tmnxSubInfoAppProfile in the
         tmnxSubscriberInfoTable with tmnxBsxAppProfDivert set to 'true' since
         system startup."
    ::= { tmnxBsxGrpStatusEntry 66 }

tmnxBsxGrpStatusSubsAverage      OBJECT-TYPE
    SYNTAX      Gauge32
    UNITS       "subscribers"
    MAX-ACCESS  read-only
    STATUS      current
    DESCRIPTION
        "The value of tmnxBsxGrpStatusSubsAverage indicates the average number
         of subscribers with flow records in the ISA-AA MDA(s) within the last
         60 minutes."
    ::= { tmnxBsxGrpStatusEntry 67 }

tmnxBsxGrpStatusSubsPeak         OBJECT-TYPE
    SYNTAX      Gauge32
    UNITS       "subscribers"
    MAX-ACCESS  read-only
    STATUS      current
    DESCRIPTION
        "The value of tmnxBsxGrpStatusSubsPeak indicates the peak number of
         subscribers with flow records in the ISA-AA MDA(s) since system
         startup."
    ::= { tmnxBsxGrpStatusEntry 68 }

tmnxBsxGrpStatusTrafficRateAvg   OBJECT-TYPE
    SYNTAX      Gauge32
    UNITS       "kilobps"
    MAX-ACCESS  read-only
    STATUS      current
    DESCRIPTION
        "The value of tmnxBsxGrpStatusTrafficRateAvg indicates the average
         traffic rate in kilobits(s) per second (kbps) incoming to the ISA-AA
         MDA(s) within the last 60 minutes."
    ::= { tmnxBsxGrpStatusEntry 69 }

tmnxBsxGrpStatusTrafficRatePeak  OBJECT-TYPE
    SYNTAX      Gauge32
    UNITS       "kilobps"
    MAX-ACCESS  read-only
    STATUS      current
    DESCRIPTION
        "The value of tmnxBsxGrpStatusTrafficRatePeak indicates the peak
         traffic rate in kilobits(s) per second (kbps) incoming to the ISA-AA
         MDA(s) since system startup."
    ::= { tmnxBsxGrpStatusEntry 70 }

tmnxBsxGrpStatusPacketRate       OBJECT-TYPE
    SYNTAX      Gauge32
    UNITS       "packets per second"
    MAX-ACCESS  read-only
    STATUS      current
    DESCRIPTION
        "The value of tmnxBsxGrpStatusPacketRate indicates the current number
         of packets per second incoming to the ISA-AA MDA(s)."
    ::= { tmnxBsxGrpStatusEntry 71 }

tmnxBsxGrpStatusPacketRateAvg    OBJECT-TYPE
    SYNTAX      Gauge32
    UNITS       "packets per second"
    MAX-ACCESS  read-only
    STATUS      current
    DESCRIPTION
        "The value of tmnxBsxGrpStatusPacketRateAvg indicates the average
         number of packets per second incoming to the ISA-AA MDA(s) within the
         last 60 minutes."
    ::= { tmnxBsxGrpStatusEntry 72 }

tmnxBsxGrpStatusPacketRatePeak   OBJECT-TYPE
    SYNTAX      Gauge32
    UNITS       "packets per second"
    MAX-ACCESS  read-only
    STATUS      current
    DESCRIPTION
        "The value of tmnxBsxGrpStatusPacketRatePeak indicates the peak number
         of packets per second incoming to the ISA-AA MDA(s) since system
         startup."
    ::= { tmnxBsxGrpStatusEntry 73 }

tmnxBsxGrpStatusFlowResInUse     OBJECT-TYPE
    SYNTAX      Gauge32
    UNITS       "flow resources"
    MAX-ACCESS  read-only
    STATUS      current
    DESCRIPTION
        "The value of tmnxBsxGrpStatusFlowResInUse indicates the number of flow
         resources currently in-use on the ISA-AA MDA."
    ::= { tmnxBsxGrpStatusEntry 74 }

tmnxBsxGrpStatusHCPktSzIncPk     OBJECT-TYPE
    SYNTAX      Counter64
    UNITS       "packets"
    MAX-ACCESS  read-only
    STATUS      current
    DESCRIPTION
        "The value of tmnxBsxGrpStatusHCPktSzIncPk indicates the number of
         packets that the ISA-AA MDA has increased in size."
    ::= { tmnxBsxGrpStatusEntry 75 }

tmnxBsxGrpStatusPktSzIncPkLo     OBJECT-TYPE
    SYNTAX      Counter32
    UNITS       "packets"
    MAX-ACCESS  read-only
    STATUS      current
    DESCRIPTION
        "The value of tmnxBsxGrpStatusPktSzIncPkLo indicates the lower 32-bits
         of tmnxBsxGrpStatusHCPktSzIncPk."
    ::= { tmnxBsxGrpStatusEntry 76 }

tmnxBsxGrpStatusPktSzIncPkHi     OBJECT-TYPE
    SYNTAX      Counter32
    UNITS       "packets"
    MAX-ACCESS  read-only
    STATUS      current
    DESCRIPTION
        "The value of tmnxBsxGrpStatusPktSzIncPkHi indicates the upper 32-bits
         of tmnxBsxGrpStatusHCPktSzIncPk."
    ::= { tmnxBsxGrpStatusEntry 77 }

tmnxBsxGrpStatusHCPktSzDecPk     OBJECT-TYPE
    SYNTAX      Counter64
    UNITS       "packets"
    MAX-ACCESS  read-only
    STATUS      current
    DESCRIPTION
        "The value of tmnxBsxGrpStatusHCPktSzDecPk indicates the number of
         packets that the ISA-AA MDA has decreased in size."
    ::= { tmnxBsxGrpStatusEntry 78 }

tmnxBsxGrpStatusPktSzDecPkLo     OBJECT-TYPE
    SYNTAX      Counter32
    UNITS       "packets"
    MAX-ACCESS  read-only
    STATUS      current
    DESCRIPTION
        "The value of tmnxBsxGrpStatusPktSzDecPkLo indicates the lower 32-bits
         of tmnxBsxGrpStatusHCPktSzDecPk."
    ::= { tmnxBsxGrpStatusEntry 79 }

tmnxBsxGrpStatusPktSzDecPkHi     OBJECT-TYPE
    SYNTAX      Counter32
    UNITS       "packets"
    MAX-ACCESS  read-only
    STATUS      current
    DESCRIPTION
        "The value of tmnxBsxGrpStatusPktSzDecPkHi indicates the upper 32-bits
         of tmnxBsxGrpStatusHCPktSzDecPk."
    ::= { tmnxBsxGrpStatusEntry 80 }

tmnxBsxGrpStatusHCPktSzIncOc     OBJECT-TYPE
    SYNTAX      Counter64
    UNITS       "octets"
    MAX-ACCESS  read-only
    STATUS      current
    DESCRIPTION
        "The value of tmnxBsxGrpStatusHCPktSzIncOc indicates the total number
         of additional octets the ISA-AA MDA injected into the packets."
    ::= { tmnxBsxGrpStatusEntry 81 }

tmnxBsxGrpStatusPktSzIncOcLo     OBJECT-TYPE
    SYNTAX      Counter32
    UNITS       "octets"
    MAX-ACCESS  read-only
    STATUS      current
    DESCRIPTION
        "The value of tmnxBsxGrpStatusPktSzIncOcLo indicates the lower 32-bits
         of tmnxBsxGrpStatusPktSzIncOcLo."
    ::= { tmnxBsxGrpStatusEntry 82 }

tmnxBsxGrpStatusPktSzIncOcHi     OBJECT-TYPE
    SYNTAX      Counter32
    UNITS       "octets"
    MAX-ACCESS  read-only
    STATUS      current
    DESCRIPTION
        "The value of tmnxBsxGrpStatusPktSzIncOcHi indicates the upper 32-bits
         of tmnxBsxGrpStatusHCPktSzIncOc."
    ::= { tmnxBsxGrpStatusEntry 83 }

tmnxBsxGrpStatusHCPktSzDecOc     OBJECT-TYPE
    SYNTAX      Counter64
    UNITS       "octets"
    MAX-ACCESS  read-only
    STATUS      current
    DESCRIPTION
        "The value of tmnxBsxGrpStatusHCPktSzDecOc indicates the total number
         of octets the ISA-AA MDA has removed from packets."
    ::= { tmnxBsxGrpStatusEntry 84 }

tmnxBsxGrpStatusPktSzDecOcLo     OBJECT-TYPE
    SYNTAX      Counter32
    UNITS       "octets"
    MAX-ACCESS  read-only
    STATUS      current
    DESCRIPTION
        "The value of tmnxBsxGrpStatusPktSzDecOcLo indicates the lower 32-bits
         of tmnxBsxGrpStatusHCPktSzDecOc."
    ::= { tmnxBsxGrpStatusEntry 85 }

tmnxBsxGrpStatusPktSzDecOcHi     OBJECT-TYPE
    SYNTAX      Counter32
    UNITS       "octets"
    MAX-ACCESS  read-only
    STATUS      current
    DESCRIPTION
        "The value of tmnxBsxGrpStatusPktSzDecOcHi indicates the upper 32-bits
         of tmnxBsxGrpStatusHCPktSzDecOc."
    ::= { tmnxBsxGrpStatusEntry 86 }

tmnxBsxGrpStatusHCSeenIpReqSent  OBJECT-TYPE
    SYNTAX      Counter64
    MAX-ACCESS  read-only
    STATUS      current
    DESCRIPTION
        "The value of tmnxBsxGrpStatusHCSeenIpReqSent indicates the total
         number of requests sent from the ISA-AA MDA to initiate dynamic
         transit subscriber creation when traffic is detected on a parent SAP
         or Spoke SDP."
    ::= { tmnxBsxGrpStatusEntry 87 }

tmnxBsxGrpStatusSeenIpReqSentLo  OBJECT-TYPE
    SYNTAX      Counter32
    MAX-ACCESS  read-only
    STATUS      current
    DESCRIPTION
        "The value of tmnxBsxGrpStatusSeenIpReqSentLo indicates the lower
         32-bits of tmnxBsxGrpStatusHCSeenIpReqSent."
    ::= { tmnxBsxGrpStatusEntry 88 }

tmnxBsxGrpStatusSeenIpReqSentHi  OBJECT-TYPE
    SYNTAX      Counter32
    MAX-ACCESS  read-only
    STATUS      current
    DESCRIPTION
        "The value of tmnxBsxGrpStatusSeenIpReqSentHi indicates the upper
         32-bits of tmnxBsxGrpStatusHCSeenIpReqSent."
    ::= { tmnxBsxGrpStatusEntry 89 }

tmnxBsxGrpStatusHCSeenIpReqDrop  OBJECT-TYPE
    SYNTAX      Counter64
    MAX-ACCESS  read-only
    STATUS      current
    DESCRIPTION
        "The value of tmnxBsxGrpStatusHCSeenIpReqDrop indicates the total
         number of Seen IP requests dropped by the ISA-AA MDA due to congestion
         control mechanisms."
    ::= { tmnxBsxGrpStatusEntry 90 }

tmnxBsxGrpStatusSeenIpReqDropLo  OBJECT-TYPE
    SYNTAX      Counter32
    MAX-ACCESS  read-only
    STATUS      current
    DESCRIPTION
        "The value of tmnxBsxGrpStatusSeenIpReqDropLo indicates the lower
         32-bits of tmnxBsxGrpStatusHCSeenIpReqDrop."
    ::= { tmnxBsxGrpStatusEntry 91 }

tmnxBsxGrpStatusSeenIpReqDropHi  OBJECT-TYPE
    SYNTAX      Counter32
    MAX-ACCESS  read-only
    STATUS      current
    DESCRIPTION
        "The value of tmnxBsxGrpStatusSeenIpReqDropHi indicates the upper
         32-bits of tmnxBsxGrpStatusHCSeenIpReqDrop."
    ::= { tmnxBsxGrpStatusEntry 92 }

tmnxBsxGrpStatusHCSubsCreated    OBJECT-TYPE
    SYNTAX      Counter64
    UNITS       "subscribers"
    MAX-ACCESS  read-only
    STATUS      current
    DESCRIPTION
        "The value of tmnxBsxGrpStatusHCSubsCreated indicates the total number
         of subscribers created."
    ::= { tmnxBsxGrpStatusEntry 93 }

tmnxBsxGrpStatusSubsCreatedLo    OBJECT-TYPE
    SYNTAX      Counter32
    UNITS       "subscribers"
    MAX-ACCESS  read-only
    STATUS      current
    DESCRIPTION
        "The value of tmnxBsxGrpStatusSubsCreatedLo indicates the lower 32-bits
         of tmnxBsxGrpStatusHCSubsCreated."
    ::= { tmnxBsxGrpStatusEntry 94 }

tmnxBsxGrpStatusSubsCreatedHi    OBJECT-TYPE
    SYNTAX      Counter32
    UNITS       "subscribers"
    MAX-ACCESS  read-only
    STATUS      current
    DESCRIPTION
        "The value of tmnxBsxGrpStatusSubsCreatedHi indicates the upper 32-bits
         of tmnxBsxGrpStatusHCSubsCreated."
    ::= { tmnxBsxGrpStatusEntry 95 }

tmnxBsxGrpStatusHCSubsDeleted    OBJECT-TYPE
    SYNTAX      Counter64
    UNITS       "subscribers"
    MAX-ACCESS  read-only
    STATUS      current
    DESCRIPTION
        "The value of tmnxBsxGrpStatusHCSubsDeleted indicates the total number
         of subscribers deleted."
    ::= { tmnxBsxGrpStatusEntry 96 }

tmnxBsxGrpStatusSubsDeletedLo    OBJECT-TYPE
    SYNTAX      Counter32
    UNITS       "subscribers"
    MAX-ACCESS  read-only
    STATUS      current
    DESCRIPTION
        "The value of tmnxBsxGrpStatusSubsDeletedLo indicates the lower 32-bits
         of tmnxBsxGrpStatusHCSubsDeleted."
    ::= { tmnxBsxGrpStatusEntry 97 }

tmnxBsxGrpStatusSubsDeletedHi    OBJECT-TYPE
    SYNTAX      Counter32
    UNITS       "subscribers"
    MAX-ACCESS  read-only
    STATUS      current
    DESCRIPTION
        "The value of tmnxBsxGrpStatusSubsDeletedHi indicates the upper 32-bits
         of tmnxBsxGrpStatusHCSubsDeleted."
    ::= { tmnxBsxGrpStatusEntry 98 }

tmnxBsxGrpStatusHCSubsModified   OBJECT-TYPE
    SYNTAX      Counter64
    UNITS       "subscribers"
    MAX-ACCESS  read-only
    STATUS      current
    DESCRIPTION
        "The value of tmnxBsxGrpStatusHCSubsModified indicates the total number
         of subscribers modified."
    ::= { tmnxBsxGrpStatusEntry 99 }

tmnxBsxGrpStatusSubsModifiedLo   OBJECT-TYPE
    SYNTAX      Counter32
    UNITS       "subscribers"
    MAX-ACCESS  read-only
    STATUS      current
    DESCRIPTION
        "The value of tmnxBsxGrpStatusSubsModifiedLo indicates the lower
         32-bits of tmnxBsxGrpStatusHCSubsModified."
    ::= { tmnxBsxGrpStatusEntry 100 }

tmnxBsxGrpStatusSubsModifiedHi   OBJECT-TYPE
    SYNTAX      Counter32
    UNITS       "subscribers"
    MAX-ACCESS  read-only
    STATUS      current
    DESCRIPTION
        "The value of tmnxBsxGrpStatusSubsModifiedHi indicates the upper
         32-bits of tmnxBsxGrpStatusHCSubsModified."
    ::= { tmnxBsxGrpStatusEntry 101 }

tmnxBsxGrpStatusPktsDiscTcpOpt   OBJECT-TYPE
    SYNTAX      Counter64
    UNITS       "packets"
    MAX-ACCESS  read-only
    STATUS      current
    DESCRIPTION
        "The value of tmnxBsxGrpStatusPktsDiscTcpOpt indicates the number of
         packets that the ISA-AA MDA has discarded due to the TCP optimization
         configuration in tmnxBsxTcpOptTable."
    ::= { tmnxBsxGrpStatusEntry 102 }

tmnxBsxGrpStatusOctsDiscTcpOpt   OBJECT-TYPE
    SYNTAX      Counter64
    UNITS       "octets"
    MAX-ACCESS  read-only
    STATUS      current
    DESCRIPTION
        "The value of tmnxBsxGrpStatusOctsDiscTcpOpt indicates the number of
         octets that the ISA-AA MDA has discarded due to the TCP optimization
         configuration in tmnxBsxTcpOptTable."
    ::= { tmnxBsxGrpStatusEntry 103 }

tmnxBsxGrpStatusPktsGenTcpOpt    OBJECT-TYPE
    SYNTAX      Counter64
    UNITS       "packets"
    MAX-ACCESS  read-only
    STATUS      current
    DESCRIPTION
        "The value of tmnxBsxGrpStatusPktsGenTcpOpt indicates the number of
         packets that the ISA-AA MDA has created due to the TCP optimization
         configuration in tmnxBsxTcpOptTable."
    ::= { tmnxBsxGrpStatusEntry 104 }

tmnxBsxGrpStatusOctsGenTcpOpt    OBJECT-TYPE
    SYNTAX      Counter64
    UNITS       "octets"
    MAX-ACCESS  read-only
    STATUS      current
    DESCRIPTION
        "The value of tmnxBsxGrpStatusOctsGenTcpOpt indicates the number of
         octets that the ISA-AA MDA has created due to the TCP optimization
         configuration in tmnxBsxTcpOptTable."
    ::= { tmnxBsxGrpStatusEntry 105 }

tmnxBsxGrpStatusFlowResMax       OBJECT-TYPE
    SYNTAX      Gauge32
    UNITS       "flow resources"
    MAX-ACCESS  read-only
    STATUS      current
    DESCRIPTION
        "The value of tmnxBsxGrpStatusFlowResMax indicates the maximum number
         of flow resources available on the ISA-AA MDA(s)."
    ::= { tmnxBsxGrpStatusEntry 106 }

tmnxBsxGrpStatusFlowResAvg       OBJECT-TYPE
    SYNTAX      Gauge32
    UNITS       "flow resources"
    MAX-ACCESS  read-only
    STATUS      current
    DESCRIPTION
        "The value of tmnxBsxGrpStatusFlowResAvg indicates the average number
         of flow resources in-use on the ISA-AA MDA(s) within the last 60
         minutes."
    ::= { tmnxBsxGrpStatusEntry 107 }

tmnxBsxGrpStatusFlowResPeak      OBJECT-TYPE
    SYNTAX      Gauge32
    UNITS       "flow resources"
    MAX-ACCESS  read-only
    STATUS      current
    DESCRIPTION
        "The value of tmnxBsxGrpStatusFlowResPeak indicates the peak number of
         flow resources in-use on the ISA-AA MDA(s) since system startup."
    ::= { tmnxBsxGrpStatusEntry 108 }

tmnxBsxGrpStatusFlowResState     OBJECT-TYPE
    SYNTAX      TmnxBsxTcaState
    MAX-ACCESS  read-only
    STATUS      current
    DESCRIPTION
        "The value of tmnxBsxGrpStatusFlowResState indicates the state of the
         flow resource TCA (tmnxBsxIsaAaGrpFlowFull)."
    ::= { tmnxBsxGrpStatusEntry 109 }

tmnxBsxGrpStatusFlowResRsdCount  OBJECT-TYPE
    SYNTAX      Counter64
    MAX-ACCESS  read-only
    STATUS      current
    DESCRIPTION
        "The value of tmnxBsxGrpStatusFlowResRsdCount indicates the number of
         times the flow resource TCA (tmnxBsxIsaAaGrpFlowFull) was raised since
         system startup."
    ::= { tmnxBsxGrpStatusEntry 110 }

tmnxBsxGrpStatusFlowResRaisdTime OBJECT-TYPE
    SYNTAX      Counter64
    UNITS       "seconds"
    MAX-ACCESS  read-only
    STATUS      current
    DESCRIPTION
        "The value of tmnxBsxGrpStatusFlowResRaisdTime indicates the amount of
         time the flow resource TCA (tmnxBsxIsaAaGrpFlowFull) was in the raised
         state since system startup."
    ::= { tmnxBsxGrpStatusEntry 111 }

tmnxBsxGrpStatusFlowSetupState   OBJECT-TYPE
    SYNTAX      TmnxBsxTcaState
    MAX-ACCESS  read-only
    STATUS      current
    DESCRIPTION
        "The value of tmnxBsxGrpStatusFlowSetupState indicates the state of the
         flow setup rate TCA (tmnxBsxIsaAaGrpFlowSetup)."
    ::= { tmnxBsxGrpStatusEntry 112 }

tmnxBsxGrpStatusFlowSetupRsdCnt  OBJECT-TYPE
    SYNTAX      Counter64
    MAX-ACCESS  read-only
    STATUS      current
    DESCRIPTION
        "The value of tmnxBsxGrpStatusFlowSetupRsdCnt indicates the number of
         times the flow setup rate TCA (tmnxBsxIsaAaGrpFlowSetup) was raised
         since system startup."
    ::= { tmnxBsxGrpStatusEntry 113 }

tmnxBsxGrpStatusFlowSetupRsdTime OBJECT-TYPE
    SYNTAX      Counter64
    UNITS       "seconds"
    MAX-ACCESS  read-only
    STATUS      current
    DESCRIPTION
        "The value of tmnxBsxGrpStatusFlowSetupRsdTime indicates the amount of
         time the flow setup rate TCA (tmnxBsxIsaAaGrpFlowSetup) was in the
         raised state since system startup."
    ::= { tmnxBsxGrpStatusEntry 114 }

tmnxBsxGrpStatusBitRateState     OBJECT-TYPE
    SYNTAX      TmnxBsxTcaState
    MAX-ACCESS  read-only
    STATUS      current
    DESCRIPTION
        "The value of tmnxBsxGrpStatusBitRateState indicates the state of the
         bit rate TCA (tmnxBsxIsaAaGrpBitRate)."
    ::= { tmnxBsxGrpStatusEntry 115 }

tmnxBsxGrpStatusBitRateRsdCount  OBJECT-TYPE
    SYNTAX      Counter64
    MAX-ACCESS  read-only
    STATUS      current
    DESCRIPTION
        "The value of tmnxBsxGrpStatusBitRateRsdCount indicates the number of
         times the bit rate TCA (tmnxBsxIsaAaGrpBitRate) was raised since
         system startup."
    ::= { tmnxBsxGrpStatusEntry 116 }

tmnxBsxGrpStatusBitRateRsdTime   OBJECT-TYPE
    SYNTAX      Counter64
    UNITS       "seconds"
    MAX-ACCESS  read-only
    STATUS      current
    DESCRIPTION
        "The value of tmnxBsxGrpStatusBitRateRsdTime indicates the amount of
         time the bit rate TCA (tmnxBsxIsaAaGrpBitRate) was in the raised state
         since system startup."
    ::= { tmnxBsxGrpStatusEntry 117 }

tmnxBsxGrpStatusPktRateState     OBJECT-TYPE
    SYNTAX      TmnxBsxTcaState
    MAX-ACCESS  read-only
    STATUS      current
    DESCRIPTION
        "The value of tmnxBsxGrpStatusPktRateState indicates the state of the
         packet rate TCA (tmnxBsxIsaAaGrpPacketRate)."
    ::= { tmnxBsxGrpStatusEntry 118 }

tmnxBsxGrpStatusPktRateRsdCount  OBJECT-TYPE
    SYNTAX      Counter64
    MAX-ACCESS  read-only
    STATUS      current
    DESCRIPTION
        "The value of tmnxBsxGrpStatusPktRateRsdCount indicates the number of
         times the packet rate TCA (tmnxBsxIsaAaGrpPacketRate) was raised since
         system startup."
    ::= { tmnxBsxGrpStatusEntry 119 }

tmnxBsxGrpStatusPktRateRaisdTime OBJECT-TYPE
    SYNTAX      Counter64
    UNITS       "seconds"
    MAX-ACCESS  read-only
    STATUS      current
    DESCRIPTION
        "The value of tmnxBsxGrpStatusPktRateRaisdTime indicates the amount of
         time the packet rate TCA (tmnxBsxIsaAaGrpPacketRate) was in the raised
         state since system startup."
    ::= { tmnxBsxGrpStatusEntry 120 }

tmnxBsxGrpStatusDatapathCpu      OBJECT-TYPE
    SYNTAX      TmnxBsxHundredthsOfPercent
    MAX-ACCESS  read-only
    STATUS      current
    DESCRIPTION
        "The value of tmnxBsxGrpStatusDatapathCpu indicates the percent
         utilization of the datapath CPU on the ISA-AA MDA(s)."
    ::= { tmnxBsxGrpStatusEntry 121 }

tmnxBsxGrpStatusDatapathCpuAvg   OBJECT-TYPE
    SYNTAX      TmnxBsxHundredthsOfPercent
    MAX-ACCESS  read-only
    STATUS      current
    DESCRIPTION
        "The value of tmnxBsxGrpStatusDatapathCpuAvg indicates the average
         percent utilization of the datapath CPU on the ISA-AA MDA(s) within
         the last 60 minutes."
    ::= { tmnxBsxGrpStatusEntry 122 }

tmnxBsxGrpStatusDatapathCpuPeak  OBJECT-TYPE
    SYNTAX      TmnxBsxHundredthsOfPercent
    MAX-ACCESS  read-only
    STATUS      current
    DESCRIPTION
        "The value of tmnxBsxGrpStatusDatapathCpuPeak indicates the peak
         percent utilization of the datapath CPU on the ISA-AA MDA(s) since
         system startup."
    ::= { tmnxBsxGrpStatusEntry 123 }

tmnxBsxGrpStatusDatapathCpuState OBJECT-TYPE
    SYNTAX      TmnxBsxTcaState
    MAX-ACCESS  read-only
    STATUS      current
    DESCRIPTION
        "The value of tmnxBsxGrpStatusDatapathCpuState indicates the state of
         the datapath CPU TCA (tmnxBsxDatapathCpuUsage)."
    ::= { tmnxBsxGrpStatusEntry 124 }

tmnxBsxGrpStatusDatapathCpuRsdCt OBJECT-TYPE
    SYNTAX      Counter64
    MAX-ACCESS  read-only
    STATUS      current
    DESCRIPTION
        "The value of tmnxBsxGrpStatusDatapathCpuRsdCt indicates the number of
         times the datapath CPU TCA (tmnxBsxDatapathCpuUsage) was raised since
         system startup."
    ::= { tmnxBsxGrpStatusEntry 125 }

tmnxBsxGrpStatusDatapathCpuRsdTm OBJECT-TYPE
    SYNTAX      Counter64
    UNITS       "seconds"
    MAX-ACCESS  read-only
    STATUS      current
    DESCRIPTION
        "The value of tmnxBsxGrpStatusDatapathCpuRsdTm indicates the amount of
         time the datapath CPU TCA (tmnxBsxDatapathCpuUsage) was in the raised
         state since system startup."
    ::= { tmnxBsxGrpStatusEntry 126 }

tmnxBsxGrpStatusMgmtCpu          OBJECT-TYPE
    SYNTAX      TmnxBsxHundredthsOfPercent
    MAX-ACCESS  read-only
    STATUS      current
    DESCRIPTION
        "The value of tmnxBsxGrpStatusMgmtCpu indicates the percent utilization
         of the management CPU on the ISA-AA MDA(s)."
    ::= { tmnxBsxGrpStatusEntry 127 }

tmnxBsxGrpStatusMgmtCpuAvg       OBJECT-TYPE
    SYNTAX      TmnxBsxHundredthsOfPercent
    MAX-ACCESS  read-only
    STATUS      current
    DESCRIPTION
        "The value of tmnxBsxGrpStatusMgmtCpuAvg indicates the average percent
         utilization of the management CPU on the ISA-AA MDA(s) within the last
         60 minutes."
    ::= { tmnxBsxGrpStatusEntry 128 }

tmnxBsxGrpStatusMgmtCpuPeak      OBJECT-TYPE
    SYNTAX      TmnxBsxHundredthsOfPercent
    MAX-ACCESS  read-only
    STATUS      current
    DESCRIPTION
        "The value of tmnxBsxGrpStatusMgmtCpuPeak indicates the peak percent
         utilization of the management CPU on the ISA-AA MDA(s) since system
         startup."
    ::= { tmnxBsxGrpStatusEntry 129 }

tmnxBsxGrpStatusWaSBfFmSub       OBJECT-TYPE
    SYNTAX      TmnxBsxHundredthsOfPercent
    MAX-ACCESS  read-only
    STATUS      current
    DESCRIPTION
        "The value of tmnxBsxGrpStatusWaSBfFmSub indicates the percent
         utilization of the subscriber to network weighted average shared
         buffer on the ISA-AA MDA(s)."
    ::= { tmnxBsxGrpStatusEntry 130 }

tmnxBsxGrpStatusWaSBfFmSubState  OBJECT-TYPE
    SYNTAX      TmnxBsxTcaState
    MAX-ACCESS  read-only
    STATUS      current
    DESCRIPTION
        "The value of tmnxBsxGrpStatusWaSBfFmSubState indicates the state of
         the subscriber to network weighted average shared buffer TCA
         (tmnxBsxIsaAaGrpFmSbWaSBufOvld)."
    ::= { tmnxBsxGrpStatusEntry 131 }

tmnxBsxGrpStatusWaSBfFmSubRsdCnt OBJECT-TYPE
    SYNTAX      Counter64
    MAX-ACCESS  read-only
    STATUS      current
    DESCRIPTION
        "The value of tmnxBsxGrpStatusWaSBfFmSubRsdCnt indicates the number of
         times the subscriber to network weighted average shared buffer TCA
         (tmnxBsxIsaAaGrpFmSbWaSBufOvld) was raised since system startup."
    ::= { tmnxBsxGrpStatusEntry 132 }

tmnxBsxGrpStatusWaSBfFmSubRsdTm  OBJECT-TYPE
    SYNTAX      Counter64
    UNITS       "seconds"
    MAX-ACCESS  read-only
    STATUS      current
    DESCRIPTION
        "The value of tmnxBsxGrpStatusWaSBfFmSubRsdTm indicates the amount of
         time the subscriber to network weighted average shared buffer TCA
         (tmnxBsxIsaAaGrpFmSbWaSBufOvld) was in the raised state since system
         startup."
    ::= { tmnxBsxGrpStatusEntry 133 }

tmnxBsxGrpStatusWaSBfToSub       OBJECT-TYPE
    SYNTAX      TmnxBsxHundredthsOfPercent
    MAX-ACCESS  read-only
    STATUS      current
    DESCRIPTION
        "The value of tmnxBsxGrpStatusWaSBfToSub indicates the percent
         utilization of the network to subscriber weighted average shared
         buffer on the ISA-AA MDA(s)."
    ::= { tmnxBsxGrpStatusEntry 134 }

tmnxBsxGrpStatusWaSBfToSubState  OBJECT-TYPE
    SYNTAX      TmnxBsxTcaState
    MAX-ACCESS  read-only
    STATUS      current
    DESCRIPTION
        "The value of tmnxBsxGrpStatusWaSBfToSubState indicates the state of
         the network to subscriber weighted average shared buffer TCA
         (tmnxBsxIsaAaGrpToSbWaSBufOvld)."
    ::= { tmnxBsxGrpStatusEntry 135 }

tmnxBsxGrpStatusWaSBfToSubRsdCnt OBJECT-TYPE
    SYNTAX      Counter64
    MAX-ACCESS  read-only
    STATUS      current
    DESCRIPTION
        "The value of tmnxBsxGrpStatusWaSBfToSubRsdCnt indicates the number of
         times the network to subscriber weighted average shared buffer TCA
         (tmnxBsxIsaAaGrpToSbWaSBufOvld) was raised since system startup."
    ::= { tmnxBsxGrpStatusEntry 136 }

tmnxBsxGrpStatusWaSBfToSubRsdTm  OBJECT-TYPE
    SYNTAX      Counter64
    UNITS       "seconds"
    MAX-ACCESS  read-only
    STATUS      current
    DESCRIPTION
        "The value of tmnxBsxGrpStatusWaSBfToSubRsdTm indicates the amount of
         time the network to subscriber weighted average shared buffer TCA
         (tmnxBsxIsaAaGrpToSbWaSBufOvld) was in the raised state since system
         startup."
    ::= { tmnxBsxGrpStatusEntry 137 }

tmnxBsxGrpStatusFlwResCtThruOcts OBJECT-TYPE
    SYNTAX      Counter64
    UNITS       "octets"
    MAX-ACCESS  read-only
    STATUS      current
    DESCRIPTION
        "The value of tmnxBsxGrpStatusFlwResCtThruOcts indicates the number of
         octets that the ISA-AA MDA(s) have cut-through due to flow resource
         exhaustion."
    ::= { tmnxBsxGrpStatusEntry 138 }

tmnxBsxGrpStatusFlwResCtThruPkts OBJECT-TYPE
    SYNTAX      Counter64
    UNITS       "packets"
    MAX-ACCESS  read-only
    STATUS      current
    DESCRIPTION
        "The value of tmnxBsxGrpStatusFlwResCtThruPkts indicates the number of
         packets that the ISA-AA MDA(s) have cut-through due to flow resource
         exhaustion."
    ::= { tmnxBsxGrpStatusEntry 139 }

tmnxBsxGrpStatusOvrldCtThruOcts  OBJECT-TYPE
    SYNTAX      Counter64
    UNITS       "octets"
    MAX-ACCESS  read-only
    STATUS      current
    DESCRIPTION
        "The value of tmnxBsxGrpStatusOvrldCtThruOcts indicates the number of
         octets that the ISA-AA MDA has cut-through due to the overload
         cut-through configuration as indicated by the object
         tmnxBsxIsaAaGrpOverloadCutThru."
    ::= { tmnxBsxGrpStatusEntry 140 }

tmnxBsxGrpStatusOvrldCtThruPkts  OBJECT-TYPE
    SYNTAX      Counter64
    UNITS       "packets"
    MAX-ACCESS  read-only
    STATUS      current
    DESCRIPTION
        "The value of tmnxBsxGrpStatusOvrldCtThruPkts indicates the number of
         octets that the ISA-AA MDA has cut-through due to the overload
         cut-through configuration as indicated by the object
         tmnxBsxIsaAaGrpOverloadCutThru."
    ::= { tmnxBsxGrpStatusEntry 141 }

tmnxBsxGrpStatusOvrldCtThruState OBJECT-TYPE
    SYNTAX      TmnxBsxTcaState
    MAX-ACCESS  read-only
    STATUS      current
    DESCRIPTION
        "The value of tmnxBsxGrpStatusOvrldCtThruState indicates the state of
         the overload cut-through TCA (tmnxBsxIsaAaGrpOvrldCutthru)."
    ::= { tmnxBsxGrpStatusEntry 142 }

tmnxBsxGrpStatusOvrldCtThruRsdCt OBJECT-TYPE
    SYNTAX      Counter64
    MAX-ACCESS  read-only
    STATUS      current
    DESCRIPTION
        "The value of tmnxBsxGrpStatusOvrldCtThruRsdCt indicates the number of
         times the overload cut-through TCA (tmnxBsxIsaAaGrpOvrldCutthru) was
         raised since system startup."
    ::= { tmnxBsxGrpStatusEntry 143 }

tmnxBsxGrpStatusOvrldCtThruRsdTm OBJECT-TYPE
    SYNTAX      Counter64
    UNITS       "seconds"
    MAX-ACCESS  read-only
    STATUS      current
    DESCRIPTION
        "The value of tmnxBsxGrpStatusOvrldCtThruRsdTm indicates the amount of
         time the overload cut-through TCA (tmnxBsxIsaAaGrpOvrldCutthru) was in
         the raised state since system startup."
    ::= { tmnxBsxGrpStatusEntry 144 }

tmnxBsxGrpStatusOctsGenHttpRedir OBJECT-TYPE
    SYNTAX      Counter64
    MAX-ACCESS  read-only
    STATUS      current
    DESCRIPTION
        "The value of tmnxBsxGrpStatusOctsGenHttpRedir indicates the number of
         octets that the ISA-AA MDA has created to redirect HTTP and HTTPS."
    ::= { tmnxBsxGrpStatusEntry 149 }

tmnxBsxGrpStatusPktsGenHttpRedir OBJECT-TYPE
    SYNTAX      Counter64
    MAX-ACCESS  read-only
    STATUS      current
    DESCRIPTION
        "The value of tmnxBsxGrpStatusPktsGenHttpRedir indicates the number of
         packets that the ISA-AA MDA has created to redirect HTTP and HTTPS."
    ::= { tmnxBsxGrpStatusEntry 150 }

tmnxBsxGrpStatusPktsInToSub      OBJECT-TYPE
    SYNTAX      Counter64
    UNITS       "packets"
    MAX-ACCESS  read-only
    STATUS      current
    DESCRIPTION
        "The value of tmnxBsxGrpStatusPktsInToSub indicates the number of
         packets diverted from ingress IOMs towards the ISA-AA MDA(s) in the
         network-to-subscriber direction."
    ::= { tmnxBsxGrpStatusEntry 151 }

tmnxBsxGrpStatusPktsInFrSub      OBJECT-TYPE
    SYNTAX      Counter64
    UNITS       "packets"
    MAX-ACCESS  read-only
    STATUS      current
    DESCRIPTION
        "The value of tmnxBsxGrpStatusPktsInFrSub indicates the number of
         packets diverted from ingress IOMs towards the ISA-AA MDA(s) in the
         subscriber-to-network direction."
    ::= { tmnxBsxGrpStatusEntry 152 }

tmnxBsxGrpStatusOctsInToSub      OBJECT-TYPE
    SYNTAX      Counter64
    UNITS       "bytes"
    MAX-ACCESS  read-only
    STATUS      current
    DESCRIPTION
        "The value of tmnxBsxGrpStatusOctsInToSub indicates the number of bytes
         diverted from ingress IOMs towards the ISA-AA MDA(s) in the
         network-to-subscriber direction."
    ::= { tmnxBsxGrpStatusEntry 153 }

tmnxBsxGrpStatusOctsInFrSub      OBJECT-TYPE
    SYNTAX      Counter64
    UNITS       "bytes"
    MAX-ACCESS  read-only
    STATUS      current
    DESCRIPTION
        "The value of tmnxBsxGrpStatusOctsInFrSub indicates the number of bytes
         diverted from ingress IOMs towards the ISA-AA MDA(s) in the
         subscriber-to-network direction."
    ::= { tmnxBsxGrpStatusEntry 154 }

tmnxBsxGrpStatusPktDisCngInToSub OBJECT-TYPE
    SYNTAX      Counter64
    UNITS       "packets"
    MAX-ACCESS  read-only
    STATUS      current
    DESCRIPTION
        "The value of tmnxBsxGrpStatusPktDisCngInToSub indicates the number of
         packets discarded by the IOMs prior to the ISA-AA MDA(s) due to egress
         IOM congestion in the network-to-subscriber direction."
    ::= { tmnxBsxGrpStatusEntry 155 }

tmnxBsxGrpStatusPktDisCngInFrSub OBJECT-TYPE
    SYNTAX      Counter64
    UNITS       "packets"
    MAX-ACCESS  read-only
    STATUS      current
    DESCRIPTION
        "The value of tmnxBsxGrpStatusPktDisCngInFrSub indicates the number of
         packets discarded by the IOMs prior to the ISA-AA MDA(s) due to egress
         IOM congestion in the subscriber-to-network direction."
    ::= { tmnxBsxGrpStatusEntry 156 }

tmnxBsxGrpStatusOctDisCngInToSub OBJECT-TYPE
    SYNTAX      Counter64
    UNITS       "bytes"
    MAX-ACCESS  read-only
    STATUS      current
    DESCRIPTION
        "The value of tmnxBsxGrpStatusOctDisCngInToSub indicates the number of
         bytes discarded by the IOMs prior to the ISA-AA MDA(s) due to egress
         IOM congestion in the network-to-subscriber direction."
    ::= { tmnxBsxGrpStatusEntry 157 }

tmnxBsxGrpStatusOctDisCngInFrSub OBJECT-TYPE
    SYNTAX      Counter64
    UNITS       "bytes"
    MAX-ACCESS  read-only
    STATUS      current
    DESCRIPTION
        "The value of tmnxBsxGrpStatusOctDisCngInFrSub indicates the number of
         bytes discarded by the IOMs prior to the ISA-AA MDA(s) due to egress
         IOM congestion in the subscriber-to-network direction."
    ::= { tmnxBsxGrpStatusEntry 158 }

tmnxBsxGrpStatusPktInPChpErToSub OBJECT-TYPE
    SYNTAX      Counter64
    UNITS       "packets"
    MAX-ACCESS  read-only
    STATUS      current
    DESCRIPTION
        "The value of tmnxBsxGrpStatusPktInPChpErToSub indicates the number of
         packets discarded by the egress P-chip due to errors in the packets in
         the network-to-subscriber direction."
    ::= { tmnxBsxGrpStatusEntry 159 }

tmnxBsxGrpStatusPktInPChpErFrSub OBJECT-TYPE
    SYNTAX      Counter64
    UNITS       "packets"
    MAX-ACCESS  read-only
    STATUS      current
    DESCRIPTION
        "The value of tmnxBsxGrpStatusPktInPChpErFrSub indicates the number of
         packets discarded by the egress P-chip due to errors in the packets in
         the subscriber-to-network direction."
    ::= { tmnxBsxGrpStatusEntry 160 }

tmnxBsxGrpStatusPktsToMdaToSub   OBJECT-TYPE
    SYNTAX      Counter64
    UNITS       "packets"
    MAX-ACCESS  read-only
    STATUS      current
    DESCRIPTION
        "The value of tmnxBsxGrpStatusPktsToMdaToSub indicates the number of
         packets sent from an IOM which enter the ISA-AA MDA(s) in the
         network-to-subscriber direction."
    ::= { tmnxBsxGrpStatusEntry 161 }

tmnxBsxGrpStatusPktsToMdaFrSub   OBJECT-TYPE
    SYNTAX      Counter64
    UNITS       "packets"
    MAX-ACCESS  read-only
    STATUS      current
    DESCRIPTION
        "The value of tmnxBsxGrpStatusPktsToMdaFrSub indicates the number of
         packets sent from an IOM which enter the ISA-AA MDA(s) in the
         subscriber-to-network direction."
    ::= { tmnxBsxGrpStatusEntry 162 }

tmnxBsxGrpStatusPktsInMdaToSub   OBJECT-TYPE
    SYNTAX      Counter64
    UNITS       "packets"
    MAX-ACCESS  read-only
    STATUS      current
    DESCRIPTION
        "The value of tmnxBsxGrpStatusPktsInMdaToSub indicates the number of
         packets buffered by the ISA-AA MDA(s) in the network-to-subscriber
         direction."
    ::= { tmnxBsxGrpStatusEntry 163 }

tmnxBsxGrpStatusPktsInMdaFrSub   OBJECT-TYPE
    SYNTAX      Counter64
    UNITS       "packets"
    MAX-ACCESS  read-only
    STATUS      current
    DESCRIPTION
        "The value of tmnxBsxGrpStatusPktsInMdaFrSub indicates the number of
         packets buffered by the ISA-AA MDA(s) in the subscriber-to-network
         direction."
    ::= { tmnxBsxGrpStatusEntry 164 }

tmnxBsxGrpStatusPkDisCngMdaToSub OBJECT-TYPE
    SYNTAX      Counter64
    UNITS       "packets"
    MAX-ACCESS  read-only
    STATUS      current
    DESCRIPTION
        "The value of tmnxBsxGrpStatusPkDisCngMdaToSub indicates the number of
         packets discarded by the ISA-AA MDA(s) due to congestion in the
         network-to-subscriber direction."
    ::= { tmnxBsxGrpStatusEntry 165 }

tmnxBsxGrpStatusPkDisCngMdaFrSub OBJECT-TYPE
    SYNTAX      Counter64
    UNITS       "packets"
    MAX-ACCESS  read-only
    STATUS      current
    DESCRIPTION
        "The value of tmnxBsxGrpStatusPkDisCngMdaFrSub indicates the number of
         packets discarded by the ISA-AA MDA(s) due to congestion in the
         subscriber-to-network direction."
    ::= { tmnxBsxGrpStatusEntry 166 }

tmnxBsxGrpStatusPktDiscErrToSub  OBJECT-TYPE
    SYNTAX      Counter64
    UNITS       "packets"
    MAX-ACCESS  read-only
    STATUS      current
    DESCRIPTION
        "The value of tmnxBsxGrpStatusPktDiscErrToSub indicates the number of
         packets discarded due to unrecoverable errors in the
         network-to-subscriber direction."
    ::= { tmnxBsxGrpStatusEntry 167 }

tmnxBsxGrpStatusPktDiscErrFrSub  OBJECT-TYPE
    SYNTAX      Counter64
    UNITS       "packets"
    MAX-ACCESS  read-only
    STATUS      current
    DESCRIPTION
        "The value of tmnxBsxGrpStatusPktDiscErrFrSub indicates the number of
         packets discarded due to unrecoverable errors in the
         subscriber-to-network direction."
    ::= { tmnxBsxGrpStatusEntry 168 }

tmnxBsxGrpStatusPktDiscPlcyToSub OBJECT-TYPE
    SYNTAX      Counter64
    UNITS       "packets"
    MAX-ACCESS  read-only
    STATUS      current
    DESCRIPTION
        "The value of tmnxBsxGrpStatusPktDiscPlcyToSub indicates the number of
         packets discarded by the ISA-AA MDA(s) due to policy in the
         network-to-subscriber direction."
    ::= { tmnxBsxGrpStatusEntry 169 }

tmnxBsxGrpStatusPktDiscPlcyFrSub OBJECT-TYPE
    SYNTAX      Counter64
    UNITS       "packets"
    MAX-ACCESS  read-only
    STATUS      current
    DESCRIPTION
        "The value of tmnxBsxGrpStatusPktDiscPlcyFrSub indicates the number of
         packets discarded by the ISA-AA MDA(s) due to policy in the
         subscriber-to-network direction."
    ::= { tmnxBsxGrpStatusEntry 170 }

tmnxBsxGrpStatusPktDisTcOptToSub OBJECT-TYPE
    SYNTAX      Counter64
    UNITS       "packets"
    MAX-ACCESS  read-only
    STATUS      current
    DESCRIPTION
        "The value of tmnxBsxGrpStatusPktDisTcOptToSub indicates the number of
         packets that the ISA-AA MDA has discarded due to the TCP optimization
         configuration in tmnxBsxTcpOptTable in the network-to-subscriber
         direction."
    ::= { tmnxBsxGrpStatusEntry 171 }

tmnxBsxGrpStatusPktDisTcOptFrSub OBJECT-TYPE
    SYNTAX      Counter64
    UNITS       "packets"
    MAX-ACCESS  read-only
    STATUS      current
    DESCRIPTION
        "The value of tmnxBsxGrpStatusPktDisTcOptFrSub indicates the number of
         packets that the ISA-AA MDA has discarded due to the TCP optimization
         configuration in tmnxBsxTcpOptTable in the subscriber-to-network
         direction."
    ::= { tmnxBsxGrpStatusEntry 172 }

tmnxBsxGrpStatusOcDisCngMdaToSub OBJECT-TYPE
    SYNTAX      Counter64
    UNITS       "bytes"
    MAX-ACCESS  read-only
    STATUS      current
    DESCRIPTION
        "The value of tmnxBsxGrpStatusOcDisCngMdaToSub indicates the number of
         bytes discarded by the ISA-AA MDA(s) due to congestion in the
         network-to-subscriber direction."
    ::= { tmnxBsxGrpStatusEntry 175 }

tmnxBsxGrpStatusOcDisCngMdaFrSub OBJECT-TYPE
    SYNTAX      Counter64
    UNITS       "bytes"
    MAX-ACCESS  read-only
    STATUS      current
    DESCRIPTION
        "The value of tmnxBsxGrpStatusOcDisCngMdaFrSub indicates the number of
         bytes discarded by the ISA-AA MDA(s) due to congestion in the
         subscriber-to-network direction."
    ::= { tmnxBsxGrpStatusEntry 176 }

tmnxBsxGrpStatusOctDiscErrToSub  OBJECT-TYPE
    SYNTAX      Counter64
    UNITS       "bytes"
    MAX-ACCESS  read-only
    STATUS      current
    DESCRIPTION
        "The value of tmnxBsxGrpStatusOctDiscErrToSub indicates the number of
         bytes discarded due to unrecoverable errors in the
         network-to-subscriber direction."
    ::= { tmnxBsxGrpStatusEntry 177 }

tmnxBsxGrpStatusOctDiscErrFrSub  OBJECT-TYPE
    SYNTAX      Counter64
    UNITS       "bytes"
    MAX-ACCESS  read-only
    STATUS      current
    DESCRIPTION
        "The value of tmnxBsxGrpStatusOctDiscErrFrSub indicates the number of
         bytes discarded due to unrecoverable errors in the
         subscriber-to-network direction."
    ::= { tmnxBsxGrpStatusEntry 178 }

tmnxBsxGrpStatusOctDiscPlcyToSub OBJECT-TYPE
    SYNTAX      Counter64
    UNITS       "bytes"
    MAX-ACCESS  read-only
    STATUS      current
    DESCRIPTION
        "The value of tmnxBsxGrpStatusOctDiscPlcyToSub indicates the number of
         bytes discarded by the ISA-AA MDA(s) due to policy in the
         network-to-subscriber direction."
    ::= { tmnxBsxGrpStatusEntry 179 }

tmnxBsxGrpStatusOctDiscPlcyFrSub OBJECT-TYPE
    SYNTAX      Counter64
    UNITS       "bytes"
    MAX-ACCESS  read-only
    STATUS      current
    DESCRIPTION
        "The value of tmnxBsxGrpStatusOctDiscPlcyFrSub indicates the number of
         bytes discarded by the ISA-AA MDA(s) due to policy in the
         subscriber-to-network direction."
    ::= { tmnxBsxGrpStatusEntry 180 }

tmnxBsxGrpStatusOctDisTcOptToSub OBJECT-TYPE
    SYNTAX      Counter64
    UNITS       "octets"
    MAX-ACCESS  read-only
    STATUS      current
    DESCRIPTION
        "The value of tmnxBsxGrpStatusOctDisTcOptToSub indicates the number of
         octets that the ISA-AA MDA has discarded due to the TCP optimization
         configuration in tmnxBsxTcpOptTable in the network-to-subscriber
         direction."
    ::= { tmnxBsxGrpStatusEntry 181 }

tmnxBsxGrpStatusOctDisTcOptFrSub OBJECT-TYPE
    SYNTAX      Counter64
    UNITS       "octets"
    MAX-ACCESS  read-only
    STATUS      current
    DESCRIPTION
        "The value of tmnxBsxGrpStatusOctDisTcOptFrSub indicates the number of
         octets that the ISA-AA MDA has discarded due to the TCP optimization
         configuration in tmnxBsxTcpOptTable in the subscriber-to-network
         direction."
    ::= { tmnxBsxGrpStatusEntry 182 }

tmnxBsxGrpStatusPktSzIncPkToSub  OBJECT-TYPE
    SYNTAX      Counter64
    UNITS       "packets"
    MAX-ACCESS  read-only
    STATUS      current
    DESCRIPTION
        "The value of tmnxBsxGrpStatusPktSzIncPkToSub indicates the number of
         packets that the ISA-AA MDA has increased in size in the
         network-to-subscriber direction."
    ::= { tmnxBsxGrpStatusEntry 185 }

tmnxBsxGrpStatusPktSzIncPkFrSub  OBJECT-TYPE
    SYNTAX      Counter64
    UNITS       "packets"
    MAX-ACCESS  read-only
    STATUS      current
    DESCRIPTION
        "The value of tmnxBsxGrpStatusPktSzIncPkFrSub indicates the number of
         packets that the ISA-AA MDA has increased in size in the
         subscriber-to-network direction."
    ::= { tmnxBsxGrpStatusEntry 186 }

tmnxBsxGrpStatusPktSzDecPkToSub  OBJECT-TYPE
    SYNTAX      Counter64
    UNITS       "packets"
    MAX-ACCESS  read-only
    STATUS      current
    DESCRIPTION
        "The value of tmnxBsxGrpStatusPktSzDecPkToSub indicates the number of
         packets that the ISA-AA MDA has decreased in size in the
         network-to-subscriber direction."
    ::= { tmnxBsxGrpStatusEntry 187 }

tmnxBsxGrpStatusPktSzDecPkFrSub  OBJECT-TYPE
    SYNTAX      Counter64
    UNITS       "packets"
    MAX-ACCESS  read-only
    STATUS      current
    DESCRIPTION
        "The value of tmnxBsxGrpStatusPktSzDecPkFrSub indicates the number of
         packets that the ISA-AA MDA has decreased in size in the
         subscriber-to-network direction."
    ::= { tmnxBsxGrpStatusEntry 188 }

tmnxBsxGrpStatusPktSzIncOcToSub  OBJECT-TYPE
    SYNTAX      Counter64
    UNITS       "octets"
    MAX-ACCESS  read-only
    STATUS      current
    DESCRIPTION
        "The value of tmnxBsxGrpStatusPktSzIncOcToSub indicates the total
         number of additional octets the ISA-AA MDA injected into the packets
         in the network-to-subscriber direction."
    ::= { tmnxBsxGrpStatusEntry 189 }

tmnxBsxGrpStatusPktSzIncOcFrSub  OBJECT-TYPE
    SYNTAX      Counter64
    UNITS       "octets"
    MAX-ACCESS  read-only
    STATUS      current
    DESCRIPTION
        "The value of tmnxBsxGrpStatusPktSzIncOcFrSub indicates the total
         number of additional octets the ISA-AA MDA injected into the packets
         in the subscriber-to-network direction."
    ::= { tmnxBsxGrpStatusEntry 190 }

tmnxBsxGrpStatusPktSzDecOcToSub  OBJECT-TYPE
    SYNTAX      Counter64
    UNITS       "octets"
    MAX-ACCESS  read-only
    STATUS      current
    DESCRIPTION
        "The value of tmnxBsxGrpStatusPktSzDecOcToSub indicates the total
         number of octets the ISA-AA MDA has removed from packets in the
         network-to-subscriber direction."
    ::= { tmnxBsxGrpStatusEntry 191 }

tmnxBsxGrpStatusPktSzDecOcFrSub  OBJECT-TYPE
    SYNTAX      Counter64
    UNITS       "octets"
    MAX-ACCESS  read-only
    STATUS      current
    DESCRIPTION
        "The value of tmnxBsxGrpStatusPktSzDecOcFrSub indicates the total
         number of octets the ISA-AA MDA has removed from packets in the
         subscriber-to-network direction."
    ::= { tmnxBsxGrpStatusEntry 192 }

tmnxBsxGrpStatusPktPlcyBypsToSub OBJECT-TYPE
    SYNTAX      Counter64
    UNITS       "packets"
    MAX-ACCESS  read-only
    STATUS      current
    DESCRIPTION
        "The value of tmnxBsxGrpStatusPktPlcyBypsToSub indicates the number of
         packets which passed untouched that did not have statistics or policy
         applied. These packets are counted as policy bypass errors in the
         network-to-subscriber direction."
    ::= { tmnxBsxGrpStatusEntry 193 }

tmnxBsxGrpStatusPktPlcyBypsFrSub OBJECT-TYPE
    SYNTAX      Counter64
    UNITS       "packets"
    MAX-ACCESS  read-only
    STATUS      current
    DESCRIPTION
        "The value of tmnxBsxGrpStatusPktPlcyBypsFrSub indicates the number of
         packets which passed untouched that did not have statistics or policy
         applied. These packets are counted as policy bypass errors in the
         subscriber-to-network direction."
    ::= { tmnxBsxGrpStatusEntry 194 }

tmnxBsxGrpStatusOctPlcyBypsToSub OBJECT-TYPE
    SYNTAX      Counter64
    UNITS       "bytes"
    MAX-ACCESS  read-only
    STATUS      current
    DESCRIPTION
        "The value of tmnxBsxGrpStatusOctPlcyBypsToSub indicates the number of
         bytes which pass untouched that did not have statistics or policy
         applied. These bytes are counted as policy bypass errors in the
         network-to-subscriber direction."
    ::= { tmnxBsxGrpStatusEntry 195 }

tmnxBsxGrpStatusOctPlcyBypsFrSub OBJECT-TYPE
    SYNTAX      Counter64
    UNITS       "bytes"
    MAX-ACCESS  read-only
    STATUS      current
    DESCRIPTION
        "The value of tmnxBsxGrpStatusOctPlcyBypsFrSub indicates the number of
         bytes which pass untouched that did not have statistics or policy
         applied. These bytes are counted as policy bypass errors in the
         subscriber-to-network direction."
    ::= { tmnxBsxGrpStatusEntry 196 }

tmnxBsxGrpStatusPktGenTcOptToSub OBJECT-TYPE
    SYNTAX      Counter64
    UNITS       "packets"
    MAX-ACCESS  read-only
    STATUS      current
    DESCRIPTION
        "The value of tmnxBsxGrpStatusPktGenTcOptToSub indicates the number of
         packets that the ISA-AA MDA has created due to the TCP optimization
         configuration in tmnxBsxTcpOptTable in the network-to-subscriber
         direction."
    ::= { tmnxBsxGrpStatusEntry 197 }

tmnxBsxGrpStatusPktGenTcOptFrSub OBJECT-TYPE
    SYNTAX      Counter64
    UNITS       "packets"
    MAX-ACCESS  read-only
    STATUS      current
    DESCRIPTION
        "The value of tmnxBsxGrpStatusPktGenTcOptFrSub indicates the number of
         packets that the ISA-AA MDA has created due to the TCP optimization
         configuration in tmnxBsxTcpOptTable in the subscriber-to-network
         direction."
    ::= { tmnxBsxGrpStatusEntry 198 }

tmnxBsxGrpStatusOctGenTcOptToSub OBJECT-TYPE
    SYNTAX      Counter64
    UNITS       "octets"
    MAX-ACCESS  read-only
    STATUS      current
    DESCRIPTION
        "The value of tmnxBsxGrpStatusOctGenTcOptToSub indicates the number of
         octets that the ISA-AA MDA has created due to the TCP optimization
         configuration in tmnxBsxTcpOptTable in the network-to-subscriber
         direction."
    ::= { tmnxBsxGrpStatusEntry 199 }

tmnxBsxGrpStatusOctGenTcOptFrSub OBJECT-TYPE
    SYNTAX      Counter64
    UNITS       "octets"
    MAX-ACCESS  read-only
    STATUS      current
    DESCRIPTION
        "The value of tmnxBsxGrpStatusOctGenTcOptFrSub indicates the number of
         octets that the ISA-AA MDA has created due to the TCP optimization
         configuration in tmnxBsxTcpOptTable in the subscriber-to-network
         direction."
    ::= { tmnxBsxGrpStatusEntry 200 }

tmnxBsxGrpStatusPkGenHttpRdToSub OBJECT-TYPE
    SYNTAX      Counter64
    MAX-ACCESS  read-only
    STATUS      current
    DESCRIPTION
        "The value of tmnxBsxGrpStatusPkGenHttpRdToSub indicates the number of
         packets that the ISA-AA MDA has created to redirect HTTP and HTTPS in
         the network-to-subscriber direction."
    ::= { tmnxBsxGrpStatusEntry 205 }

tmnxBsxGrpStatusPkGenHttpRdFrSub OBJECT-TYPE
    SYNTAX      Counter64
    MAX-ACCESS  read-only
    STATUS      current
    DESCRIPTION
        "The value of tmnxBsxGrpStatusPkGenHttpRdFrSub indicates the number of
         packets that the ISA-AA MDA has created to redirect HTTP and HTTPS in
         the subscriber-to-network direction."
    ::= { tmnxBsxGrpStatusEntry 206 }

tmnxBsxGrpStatusOcGenHttpRdToSub OBJECT-TYPE
    SYNTAX      Counter64
    MAX-ACCESS  read-only
    STATUS      current
    DESCRIPTION
        "The value of tmnxBsxGrpStatusOcGenHttpRdToSub indicates the number of
         octets that the ISA-AA MDA has created to redirect HTTP and HTTPS in
         the network-to-subscriber direction."
    ::= { tmnxBsxGrpStatusEntry 207 }

tmnxBsxGrpStatusOcGenHttpRdFrSub OBJECT-TYPE
    SYNTAX      Counter64
    MAX-ACCESS  read-only
    STATUS      current
    DESCRIPTION
        "The value of tmnxBsxGrpStatusOcGenHttpRdFrSub indicates the number of
         octets that the ISA-AA MDA has created to redirect HTTP and HTTPS in
         the subscriber-to-network direction."
    ::= { tmnxBsxGrpStatusEntry 208 }

tmnxBsxGrpStatusPktsFromMdaToSub OBJECT-TYPE
    SYNTAX      Counter64
    UNITS       "packets"
    MAX-ACCESS  read-only
    STATUS      current
    DESCRIPTION
        "The value of tmnxBsxGrpStatusPktsFromMdaToSub indicates the number of
         packets which exit the ISA-AA MDA(s) and are sent to the local IOM in
         the network-to-subscriber direction."
    ::= { tmnxBsxGrpStatusEntry 209 }

tmnxBsxGrpStatusPktsFromMdaFrSub OBJECT-TYPE
    SYNTAX      Counter64
    UNITS       "packets"
    MAX-ACCESS  read-only
    STATUS      current
    DESCRIPTION
        "The value of tmnxBsxGrpStatusPktsFromMdaFrSub indicates the number of
         packets which exit the ISA-AA MDA(s) and are sent to the local IOM in
         the subscriber-to-network direction."
    ::= { tmnxBsxGrpStatusEntry 210 }

tmnxBsxGrpStatusOctsFromMdaToSub OBJECT-TYPE
    SYNTAX      Counter64
    UNITS       "bytes"
    MAX-ACCESS  read-only
    STATUS      current
    DESCRIPTION
        "The value of tmnxBsxGrpStatusOctsFromMdaToSub indicates the number of
         bytes which exit the ISA-AA MDA(s) and are sent to the local IOM in
         the network-to-subscriber direction."
    ::= { tmnxBsxGrpStatusEntry 211 }

tmnxBsxGrpStatusOctsFromMdaFrSub OBJECT-TYPE
    SYNTAX      Counter64
    UNITS       "bytes"
    MAX-ACCESS  read-only
    STATUS      current
    DESCRIPTION
        "The value of tmnxBsxGrpStatusOctsFromMdaFrSub indicates the number of
         bytes which exit the ISA-AA MDA(s) and are sent to the local IOM in
         the subscriber-to-network direction."
    ::= { tmnxBsxGrpStatusEntry 212 }

tmnxBsxGrpStatusPkDisConOutToSub OBJECT-TYPE
    SYNTAX      Counter64
    UNITS       "packets"
    MAX-ACCESS  read-only
    STATUS      current
    DESCRIPTION
        "The value of tmnxBsxGrpStatusPkDisConOutToSub indicates the number of
         packets discarded by the IOMs after the ISA-AA MDA(s) due to ingress
         IOM congestion in the network-to-subscriber direction."
    ::= { tmnxBsxGrpStatusEntry 213 }

tmnxBsxGrpStatusPkDisConOutFrSub OBJECT-TYPE
    SYNTAX      Counter64
    UNITS       "packets"
    MAX-ACCESS  read-only
    STATUS      current
    DESCRIPTION
        "The value of tmnxBsxGrpStatusPkDisConOutFrSub indicates the number of
         packets discarded by the IOMs after the ISA-AA MDA(s) due to ingress
         IOM congestion in the subscriber-to-network direction."
    ::= { tmnxBsxGrpStatusEntry 214 }

tmnxBsxGrpStatusOcDisConOutToSub OBJECT-TYPE
    SYNTAX      Counter64
    UNITS       "bytes"
    MAX-ACCESS  read-only
    STATUS      current
    DESCRIPTION
        "The value of tmnxBsxGrpStatusOcDisConOutToSub indicates the number of
         bytes discarded by the IOMs after the ISA-AA MDA(s) due to ingress IOM
         congestion in the network-to-subscriber direction."
    ::= { tmnxBsxGrpStatusEntry 215 }

tmnxBsxGrpStatusOcDisConOutFrSub OBJECT-TYPE
    SYNTAX      Counter64
    UNITS       "bytes"
    MAX-ACCESS  read-only
    STATUS      current
    DESCRIPTION
        "The value of tmnxBsxGrpStatusOcDisConOutFrSub indicates the number of
         bytes discarded by the IOMs after the ISA-AA MDA(s) due to ingress IOM
         congestion in the subscriber-to-network direction."
    ::= { tmnxBsxGrpStatusEntry 216 }

tmnxBsxGrpStatusPktOutPChErToSub OBJECT-TYPE
    SYNTAX      Counter64
    UNITS       "packets"
    MAX-ACCESS  read-only
    STATUS      current
    DESCRIPTION
        "The value of tmnxBsxGrpStatusPktOutPChErToSub indicates the number of
         packets discarded due to an error detected by the P-chip while
         attempting to return the packet to the normal forwarding path in the
         network-to-subscriber direction."
    ::= { tmnxBsxGrpStatusEntry 217 }

tmnxBsxGrpStatusPktOutPChErFrSub OBJECT-TYPE
    SYNTAX      Counter64
    UNITS       "packets"
    MAX-ACCESS  read-only
    STATUS      current
    DESCRIPTION
        "The value of tmnxBsxGrpStatusPktOutPChErFrSub indicates the number of
         packets discarded due to an error detected by the P-chip while
         attempting to return the packet to the normal forwarding path in the
         subscriber-to-network direction."
    ::= { tmnxBsxGrpStatusEntry 218 }

tmnxBsxGrpStatusPktsOutToSub     OBJECT-TYPE
    SYNTAX      Counter64
    UNITS       "packets"
    MAX-ACCESS  read-only
    STATUS      current
    DESCRIPTION
        "The value of tmnxBsxGrpStatusPktsOutToSub indicates the number of
         packets returned to the normal forwarding path that are sent to egress
         IOMs from the ISA-AA MDA(s) in the network-to-subscriber direction."
    ::= { tmnxBsxGrpStatusEntry 219 }

tmnxBsxGrpStatusPktsOutFrSub     OBJECT-TYPE
    SYNTAX      Counter64
    UNITS       "packets"
    MAX-ACCESS  read-only
    STATUS      current
    DESCRIPTION
        "The value of tmnxBsxGrpStatusPktsOutFrSub indicates the number of
         packets returned to the normal forwarding path that are sent to egress
         IOMs from the ISA-AA MDA(s) in the subscriber-to-network direction."
    ::= { tmnxBsxGrpStatusEntry 220 }

tmnxBsxGrpStatusOctsOutToSub     OBJECT-TYPE
    SYNTAX      Counter64
    UNITS       "bytes"
    MAX-ACCESS  read-only
    STATUS      current
    DESCRIPTION
        "The value of tmnxBsxGrpStatusOctsOutToSub indicates the number of
         bytes returned to the normal forwarding path that are sent to egress
         IOMs from the ISA-AA MDA(s) in the network-to-subscriber direction."
    ::= { tmnxBsxGrpStatusEntry 221 }

tmnxBsxGrpStatusOctsOutFrSub     OBJECT-TYPE
    SYNTAX      Counter64
    UNITS       "bytes"
    MAX-ACCESS  read-only
    STATUS      current
    DESCRIPTION
        "The value of tmnxBsxGrpStatusOctsOutFrSub indicates the number of
         bytes returned to the normal forwarding path that are sent to egress
         IOMs from the ISA-AA MDA(s) in the subscriber-to-network direction."
    ::= { tmnxBsxGrpStatusEntry 222 }

tmnxBsxGrpStatusPktCutThrough    OBJECT-TYPE
    SYNTAX      Counter64
    UNITS       "packets"
    MAX-ACCESS  read-only
    STATUS      current
    DESCRIPTION
        "The value of tmnxBsxGrpStatusPktCutThrough indicates the number of
         packets which passed untouched, but have policy applied. These packets
         are counted as cut-through errors."
    ::= { tmnxBsxGrpStatusEntry 223 }

tmnxBsxGrpStatusPktCutThrouToSub OBJECT-TYPE
    SYNTAX      Counter64
    UNITS       "packets"
    MAX-ACCESS  read-only
    STATUS      current
    DESCRIPTION
        "The value of tmnxBsxGrpStatusPktCutThrouToSub indicates the number of
         packets which passed untouched, but have policy applied in the
         network-to-subscriber direction. These packets are counted as
         cut-through errors."
    ::= { tmnxBsxGrpStatusEntry 224 }

tmnxBsxGrpStatusPktCutThrouFrSub OBJECT-TYPE
    SYNTAX      Counter64
    UNITS       "packets"
    MAX-ACCESS  read-only
    STATUS      current
    DESCRIPTION
        "The value of tmnxBsxGrpStatusPktCutThrouFrSub indicates the number of
         packets which passed untouched, but have policy applied in the
         subscriber-to-network direction. These packets are counted as
         cut-through errors."
    ::= { tmnxBsxGrpStatusEntry 225 }

tmnxBsxGrpStatusOctCutThrough    OBJECT-TYPE
    SYNTAX      Counter64
    UNITS       "bytes"
    MAX-ACCESS  read-only
    STATUS      current
    DESCRIPTION
        "The value of tmnxBsxGrpStatusOctCutThrough indicates the number of
         octets which passed untouched, but have policy applied. These octets
         are counted as cut-through errors."
    ::= { tmnxBsxGrpStatusEntry 226 }

tmnxBsxGrpStatusOctCutThrouToSub OBJECT-TYPE
    SYNTAX      Counter64
    UNITS       "bytes"
    MAX-ACCESS  read-only
    STATUS      current
    DESCRIPTION
        "The value of tmnxBsxGrpStatusOctCutThrouToSub indicates the number of
         octets which passed untouched, but have policy applied in the
         network-to-subscriber direction. These octets are counted as
         cut-through errors."
    ::= { tmnxBsxGrpStatusEntry 227 }

tmnxBsxGrpStatusOctCutThrouFrSub OBJECT-TYPE
    SYNTAX      Counter64
    UNITS       "bytes"
    MAX-ACCESS  read-only
    STATUS      current
    DESCRIPTION
        "The value of tmnxBsxGrpStatusOctCutThrouFrSub indicates the number of
         octets which passed untouched, but have policy applied in the
         subscriber-to-network direction. These octets are counted as
         cut-through errors."
    ::= { tmnxBsxGrpStatusEntry 228 }

tmnxBsxGrpStatusOctsToMdaToSub   OBJECT-TYPE
    SYNTAX      Counter64
    UNITS       "bytes"
    MAX-ACCESS  read-only
    STATUS      current
    DESCRIPTION
        "The value of tmnxBsxGrpStatusOctsToMdaToSub indicates the number of
         bytes sent from an IOM which enter the ISA-AA MDA(s) in the
         network-to-subscriber direction."
    ::= { tmnxBsxGrpStatusEntry 229 }

tmnxBsxGrpStatusOctsToMdaFrSub   OBJECT-TYPE
    SYNTAX      Counter64
    UNITS       "bytes"
    MAX-ACCESS  read-only
    STATUS      current
    DESCRIPTION
        "The value of tmnxBsxGrpStatusOctsToMdaFrSub indicates the number of
         bytes sent from an IOM which enter the ISA-AA MDA(s) in the
         subscriber-to-network direction."
    ::= { tmnxBsxGrpStatusEntry 230 }

tmnxBsxGrpStatusOctsInMdaToSub   OBJECT-TYPE
    SYNTAX      Counter64
    UNITS       "bytes"
    MAX-ACCESS  read-only
    STATUS      current
    DESCRIPTION
        "The value of tmnxBsxGrpStatusOctsInMdaToSub indicates the number of
         bytes buffered by the ISA-AA MDA(s) in the network-to-subscriber
         direction."
    ::= { tmnxBsxGrpStatusEntry 231 }

tmnxBsxGrpStatusOctsInMdaFrSub   OBJECT-TYPE
    SYNTAX      Counter64
    UNITS       "bytes"
    MAX-ACCESS  read-only
    STATUS      current
    DESCRIPTION
        "The value of tmnxBsxGrpStatusOctsInMdaFrSub indicates the number of
         bytes buffered by the ISA-AA MDA(s) in the subscriber-to-network
         direction."
    ::= { tmnxBsxGrpStatusEntry 232 }

tmnxBsxGrpStatusSubsQuarantined  OBJECT-TYPE
    SYNTAX      Counter64
    UNITS       "subscribers"
    MAX-ACCESS  read-only
    STATUS      current
    DESCRIPTION
        "The value of tmnxBsxGrpStatusSubsQuarantined indicates the total
         number of subscribers quarantined."
    ::= { tmnxBsxGrpStatusEntry 233 }

tmnxBsxGrpStatusIngQTable        OBJECT-TYPE
    SYNTAX      SEQUENCE OF TmnxBsxGrpStatusIngQEntry
    MAX-ACCESS  not-accessible
    STATUS      current
    DESCRIPTION
        "The tmnxBsxGrpStatusIngQTable contains an entry for each ISA-AA MDA
         and Group in the system. Each row contains the Qos status information
         for traffic exiting an ISA-AA MDA given the
         tmnxBsxGrpStatusInQDirection and tmnxBsxGrpStatusInQIndex. An ISA-AA
         MDA is uniquely identified by the tmnxChassisIndex,
         tmnxBsxCardSlotEsaId, and the tmnxBsxMdaSlotEsaVmId."
    ::= { tmnxBsxMdaObjs 6 }

tmnxBsxGrpStatusIngQEntry        OBJECT-TYPE
    SYNTAX      TmnxBsxGrpStatusIngQEntry
    MAX-ACCESS  not-accessible
    STATUS      current
    DESCRIPTION
        "Each tmnxBsxGrpStatusIngQEntry contains the Qos status information for
         traffic exiting a particular ISA-AA MDA within a group, given a
         tmnxBsxGrpStatusInQDirection and tmnxBsxGrpStatusInQIndex."
    INDEX       {
        tmnxBsxIsaAaGroupIndex,
        tmnxChassisIndex,
        tmnxBsxCardSlotEsaId,
        tmnxBsxMdaSlotEsaVmId,
        tmnxBsxGrpStatusInQDirection,
        tmnxBsxGrpStatusInQIndex
    }
    ::= { tmnxBsxGrpStatusIngQTable 1 }

TmnxBsxGrpStatusIngQEntry        ::= SEQUENCE
{
    tmnxBsxGrpStatusInQDirection     TmnxBsxDirection,
    tmnxBsxGrpStatusInQIndex         TQueueId,
    tmnxBsxGrpStatusIngQDiscontTime  TimeStamp,
    tmnxBsxGrpStatusIngQFwdInPPkts   Counter32,
    tmnxBsxGrpStatusIngQFwdOutPPkts  Counter32,
    tmnxBsxGrpStatusIngQFwdInPOcts   Counter32,
    tmnxBsxGrpStatusIngQFwdOutPOcts  Counter32,
    tmnxBsxGrpStatusIngQDroInPPkts   Counter32,
    tmnxBsxGrpStatusIngQDroOutPPkts  Counter32,
    tmnxBsxGrpStatusIngQDroInPOcts   Counter32,
    tmnxBsxGrpStatusIngQDroOutPOcts  Counter32,
    tmnxBsxGrpStatusIngQHCFwdInPPkts Counter64,
    tmnxBsxGrpStatusIngQHCFwdOutPPkts Counter64,
    tmnxBsxGrpStatusIngQHCFwdInPOcts Counter64,
    tmnxBsxGrpStatusIngQHCFwdOutPOcts Counter64,
    tmnxBsxGrpStatusIngQHCDroInPPkts Counter64,
    tmnxBsxGrpStatusIngQHCDroOutPPkts Counter64,
    tmnxBsxGrpStatusIngQHCDroInPOcts Counter64,
    tmnxBsxGrpStatusIngQHCDroOutPOcts Counter64
}

tmnxBsxGrpStatusInQDirection     OBJECT-TYPE
    SYNTAX      TmnxBsxDirection
    MAX-ACCESS  not-accessible
    STATUS      current
    DESCRIPTION
        "The value of tmnxBsxGrpStatusInQDirection specifies
         either the subscriber to network 'sub2net' or network
         to subscriber 'net2sub' direction of traffic.  The
         value 'both' is not a valid index."
    ::= { tmnxBsxGrpStatusIngQEntry 1 }

tmnxBsxGrpStatusInQIndex         OBJECT-TYPE
    SYNTAX      TQueueId
    MAX-ACCESS  not-accessible
    STATUS      current
    DESCRIPTION
        "The value of tmnxBsxGrpStatusInQIndex specifies the number of the
         ingress queue as configured within the tmnxBsxIsaAaGrpIngressQuePolicy
         configured against this tmnxBsxIsaAaGroupIndex."
    ::= { tmnxBsxGrpStatusIngQEntry 2 }

tmnxBsxGrpStatusIngQDiscontTime  OBJECT-TYPE
    SYNTAX      TimeStamp
    MAX-ACCESS  read-only
    STATUS      current
    DESCRIPTION
        "The value of tmnxBsxGrpStatusIngQDiscontTime indicates the
         SNMPv2-MIB::sysUpTime (centiseconds) when the ISA-AA MDA within this
         group has last changed status."
    ::= { tmnxBsxGrpStatusIngQEntry 3 }

tmnxBsxGrpStatusIngQFwdInPPkts   OBJECT-TYPE
    SYNTAX      Counter32
    UNITS       "packets"
    MAX-ACCESS  read-only
    STATUS      current
    DESCRIPTION
        "The value of tmnxBsxGrpStatusIngQFwdInPPkts indicates the number of in
         profile packets diverted towards egress IOMs from the ISA-AA MDA
         within this group for the particular queue."
    ::= { tmnxBsxGrpStatusIngQEntry 4 }

tmnxBsxGrpStatusIngQFwdOutPPkts  OBJECT-TYPE
    SYNTAX      Counter32
    UNITS       "packets"
    MAX-ACCESS  read-only
    STATUS      current
    DESCRIPTION
        "The value of tmnxBsxGrpStatusIngQFwdOutPPkts indicates the number of
         out of profile packets diverted towards egress IOMs from the ISA-AA
         MDA within this group for the particular queue."
    ::= { tmnxBsxGrpStatusIngQEntry 5 }

tmnxBsxGrpStatusIngQFwdInPOcts   OBJECT-TYPE
    SYNTAX      Counter32
    UNITS       "bytes"
    MAX-ACCESS  read-only
    STATUS      current
    DESCRIPTION
        "The value of tmnxBsxGrpStatusIngQFwdInPOcts indicates the number of in
         profile bytes diverted towards egress IOMs from the ISA-AA MDA within
         this group for the particular queue."
    ::= { tmnxBsxGrpStatusIngQEntry 6 }

tmnxBsxGrpStatusIngQFwdOutPOcts  OBJECT-TYPE
    SYNTAX      Counter32
    UNITS       "bytes"
    MAX-ACCESS  read-only
    STATUS      current
    DESCRIPTION
        "The value of tmnxBsxGrpStatusIngQFwdOutPOcts indicates the number of
         out of profile bytes diverted towards egress IOMs from the ISA-AA MDA
         within this group for the particular queue."
    ::= { tmnxBsxGrpStatusIngQEntry 7 }

tmnxBsxGrpStatusIngQDroInPPkts   OBJECT-TYPE
    SYNTAX      Counter32
    UNITS       "packets"
    MAX-ACCESS  read-only
    STATUS      current
    DESCRIPTION
        "The value of tmnxBsxGrpStatusIngQDroInPPkts indicates the number of in
         profile packets discarded towards egress IOMs from the ISA-AA MDA
         within this group for the particular queue."
    ::= { tmnxBsxGrpStatusIngQEntry 8 }

tmnxBsxGrpStatusIngQDroOutPPkts  OBJECT-TYPE
    SYNTAX      Counter32
    UNITS       "packets"
    MAX-ACCESS  read-only
    STATUS      current
    DESCRIPTION
        "The value of tmnxBsxGrpStatusIngQDroOutPPkts indicates the number of
         out of profile packets discarded towards egress IOMs from the ISA-AA
         MDA within this group for the particular queue."
    ::= { tmnxBsxGrpStatusIngQEntry 9 }

tmnxBsxGrpStatusIngQDroInPOcts   OBJECT-TYPE
    SYNTAX      Counter32
    UNITS       "bytes"
    MAX-ACCESS  read-only
    STATUS      current
    DESCRIPTION
        "The value of tmnxBsxGrpStatusIngQDroInPOcts indicates the number of in
         profile bytes discarded towards egress IOMs from the ISA-AA MDA within
         this group for the particular queue."
    ::= { tmnxBsxGrpStatusIngQEntry 10 }

tmnxBsxGrpStatusIngQDroOutPOcts  OBJECT-TYPE
    SYNTAX      Counter32
    UNITS       "bytes"
    MAX-ACCESS  read-only
    STATUS      current
    DESCRIPTION
        "The value of tmnxBsxGrpStatusIngQDroOutPOcts indicates the number of
         out of profile bytes discarded towards egress IOMs from the ISA-AA MDA
         within this group for the particular queue."
    ::= { tmnxBsxGrpStatusIngQEntry 11 }

tmnxBsxGrpStatusIngQHCFwdInPPkts OBJECT-TYPE
    SYNTAX      Counter64
    UNITS       "packets"
    MAX-ACCESS  read-only
    STATUS      current
    DESCRIPTION
        "The value of tmnxBsxGrpStatusIngQHCFwdInPPkts indicates the number of
         in profile packets diverted towards egress IOMs from the ISA-AA MDA
         within this group for the particular queue."
    ::= { tmnxBsxGrpStatusIngQEntry 12 }

tmnxBsxGrpStatusIngQHCFwdOutPPkts OBJECT-TYPE
    SYNTAX      Counter64
    UNITS       "packets"
    MAX-ACCESS  read-only
    STATUS      current
    DESCRIPTION
        "The value of tmnxBsxGrpStatusIngQHCFwdOutPPkts indicates the number of
         out of profile packets diverted towards egress IOMs from the ISA-AA
         MDA within this group for the particular queue."
    ::= { tmnxBsxGrpStatusIngQEntry 13 }

tmnxBsxGrpStatusIngQHCFwdInPOcts OBJECT-TYPE
    SYNTAX      Counter64
    UNITS       "bytes"
    MAX-ACCESS  read-only
    STATUS      current
    DESCRIPTION
        "The value of tmnxBsxGrpStatusIngQHCFwdInPOcts indicates the number of
         in profile bytes diverted towards egress IOMs from the ISA-AA MDA
         within this group for the particular queue."
    ::= { tmnxBsxGrpStatusIngQEntry 14 }

tmnxBsxGrpStatusIngQHCFwdOutPOcts OBJECT-TYPE
    SYNTAX      Counter64
    UNITS       "bytes"
    MAX-ACCESS  read-only
    STATUS      current
    DESCRIPTION
        "The value of tmnxBsxGrpStatusIngQHCFwdOutPOcts indicates the number of
         out of profile bytes diverted towards egress IOMs from the ISA-AA MDA
         within this group for the particular queue."
    ::= { tmnxBsxGrpStatusIngQEntry 15 }

tmnxBsxGrpStatusIngQHCDroInPPkts OBJECT-TYPE
    SYNTAX      Counter64
    UNITS       "packets"
    MAX-ACCESS  read-only
    STATUS      current
    DESCRIPTION
        "The value of tmnxBsxGrpStatusIngQHCDroInPPkts indicates the number of
         in profile packets discarded towards egress IOMs from the ISA-AA MDA
         within this group for the particular queue."
    ::= { tmnxBsxGrpStatusIngQEntry 16 }

tmnxBsxGrpStatusIngQHCDroOutPPkts OBJECT-TYPE
    SYNTAX      Counter64
    UNITS       "packets"
    MAX-ACCESS  read-only
    STATUS      current
    DESCRIPTION
        "The value of tmnxBsxGrpStatusIngQHCDroOutPPkts indicates the number of
         out of profile packets discarded towards egress IOMs from the ISA-AA
         MDA within this group for the particular queue."
    ::= { tmnxBsxGrpStatusIngQEntry 17 }

tmnxBsxGrpStatusIngQHCDroInPOcts OBJECT-TYPE
    SYNTAX      Counter64
    UNITS       "bytes"
    MAX-ACCESS  read-only
    STATUS      current
    DESCRIPTION
        "The value of tmnxBsxGrpStatusIngQHCDroInPOcts indicates the number of
         in profile bytes discarded towards egress IOMs from the ISA-AA MDA
         within this group for the particular queue."
    ::= { tmnxBsxGrpStatusIngQEntry 18 }

tmnxBsxGrpStatusIngQHCDroOutPOcts OBJECT-TYPE
    SYNTAX      Counter64
    UNITS       "bytes"
    MAX-ACCESS  read-only
    STATUS      current
    DESCRIPTION
        "The value of tmnxBsxGrpStatusIngQHCDroOutPOcts indicates the number of
         out of profile bytes discarded towards egress IOMs from the ISA-AA MDA
         within this group for the particular queue."
    ::= { tmnxBsxGrpStatusIngQEntry 19 }

tmnxBsxGrpStatusEgrQTable        OBJECT-TYPE
    SYNTAX      SEQUENCE OF TmnxBsxGrpStatusEgrQEntry
    MAX-ACCESS  not-accessible
    STATUS      current
    DESCRIPTION
        "The tmnxBsxGrpStatusEgrQTable contains an entry for each
         ISA-AA MDA and Group in the system.  Each row contains the
         Qos status information for traffic entering an ISA-AA MDA
         given the tmnxBsxGrpStatusEgrQDirection and
         tmnxBsxGrpStatusEgrQIndex. An ISA-AA MDA is uniquely
         identified by the tmnxChassisIndex, tmnxBsxCardSlotEsaId, and
         the tmnxBsxMdaSlotEsaVmId."
    ::= { tmnxBsxMdaObjs 7 }

tmnxBsxGrpStatusEgrQEntry        OBJECT-TYPE
    SYNTAX      TmnxBsxGrpStatusEgrQEntry
    MAX-ACCESS  not-accessible
    STATUS      current
    DESCRIPTION
        "Each tmnxBsxGrpStatusEgrQEntry contains the Qos status information for
         traffic incoming to a particular ISA-AA MDA within a group, given a
         tmnxBsxGrpStatusEgrQDirection and tmnxBsxGrpStatusEgrQIndex."
    INDEX       {
        tmnxBsxIsaAaGroupIndex,
        tmnxChassisIndex,
        tmnxBsxCardSlotEsaId,
        tmnxBsxMdaSlotEsaVmId,
        tmnxBsxGrpStatusEgrQDirection,
        tmnxBsxGrpStatusEgrQIndex
    }
    ::= { tmnxBsxGrpStatusEgrQTable 1 }

TmnxBsxGrpStatusEgrQEntry        ::= SEQUENCE
{
    tmnxBsxGrpStatusEgrQDirection    TmnxBsxDirection,
    tmnxBsxGrpStatusEgrQIndex        TQueueId,
    tmnxBsxGrpStatusEgrQDiscontTime  TimeStamp,
    tmnxBsxGrpStatusEgrQFwdInPPkts   Counter32,
    tmnxBsxGrpStatusEgrQFwdOutPPkts  Counter32,
    tmnxBsxGrpStatusEgrQFwdInPOcts   Counter32,
    tmnxBsxGrpStatusEgrQFwdOutPOcts  Counter32,
    tmnxBsxGrpStatusEgrQDroInPPkts   Counter32,
    tmnxBsxGrpStatusEgrQDroOutPPkts  Counter32,
    tmnxBsxGrpStatusEgrQDroInPOcts   Counter32,
    tmnxBsxGrpStatusEgrQDroOutPOcts  Counter32,
    tmnxBsxGrpStatusEgrQHCFwdInPPkts Counter64,
    tmnxBsxGrpStatusEgrQHCFwdOutPPkts Counter64,
    tmnxBsxGrpStatusEgrQHCFwdInPOcts Counter64,
    tmnxBsxGrpStatusEgrQHCFwdOutPOcts Counter64,
    tmnxBsxGrpStatusEgrQHCDroInPPkts Counter64,
    tmnxBsxGrpStatusEgrQHCDroOutPPkts Counter64,
    tmnxBsxGrpStatusEgrQHCDroInPOcts Counter64,
    tmnxBsxGrpStatusEgrQHCDroOutPOcts Counter64
}

tmnxBsxGrpStatusEgrQDirection    OBJECT-TYPE
    SYNTAX      TmnxBsxDirection
    MAX-ACCESS  not-accessible
    STATUS      current
    DESCRIPTION
        "The value of tmnxBsxGrpStatusEgrQDirection specifies
         either the subscriber to network 'sub2net' or network
         to subscriber 'net2sub' direction of traffic.  The
         value 'both' is not a valid index."
    ::= { tmnxBsxGrpStatusEgrQEntry 1 }

tmnxBsxGrpStatusEgrQIndex        OBJECT-TYPE
    SYNTAX      TQueueId
    MAX-ACCESS  not-accessible
    STATUS      current
    DESCRIPTION
        "The value of tmnxBsxGrpStatusEgrQIndex specifies the number of the
         egress queue as configured within the tmnxBsxIsaAaGrpToSubQuePolicy or
         tmnxBsxIsaAaGrpFromSubQuePolicy configured against this
         tmnxBsxIsaAaGroupIndex."
    ::= { tmnxBsxGrpStatusEgrQEntry 2 }

tmnxBsxGrpStatusEgrQDiscontTime  OBJECT-TYPE
    SYNTAX      TimeStamp
    MAX-ACCESS  read-only
    STATUS      current
    DESCRIPTION
        "The value of tmnxBsxGrpStatusEgrQDiscontTime indicates the
         SNMPv2-MIB::sysUpTime (centiseconds) when the ISA-AA MDA within the
         group has last changed status."
    ::= { tmnxBsxGrpStatusEgrQEntry 3 }

tmnxBsxGrpStatusEgrQFwdInPPkts   OBJECT-TYPE
    SYNTAX      Counter32
    UNITS       "packets"
    MAX-ACCESS  read-only
    STATUS      current
    DESCRIPTION
        "The value of tmnxBsxGrpStatusEgrQFwdInPPkts indicates the number of in
         profile packets diverted from ingress IOMs towards the ISA-AA MDA
         within this group for the particular queue."
    ::= { tmnxBsxGrpStatusEgrQEntry 4 }

tmnxBsxGrpStatusEgrQFwdOutPPkts  OBJECT-TYPE
    SYNTAX      Counter32
    UNITS       "packets"
    MAX-ACCESS  read-only
    STATUS      current
    DESCRIPTION
        "The value of tmnxBsxGrpStatusEgrQFwdOutPPkts indicates the number of
         out of profile packets diverted from ingress IOMs towards the ISA-AA
         MDA within this group for the particular queue."
    ::= { tmnxBsxGrpStatusEgrQEntry 5 }

tmnxBsxGrpStatusEgrQFwdInPOcts   OBJECT-TYPE
    SYNTAX      Counter32
    UNITS       "bytes"
    MAX-ACCESS  read-only
    STATUS      current
    DESCRIPTION
        "The value of tmnxBsxGrpStatusEgrQFwdInPOcts indicates the number of in
         profile bytes diverted from ingress IOMs towards the ISA-AA MDA within
         this group for the particular queue."
    ::= { tmnxBsxGrpStatusEgrQEntry 6 }

tmnxBsxGrpStatusEgrQFwdOutPOcts  OBJECT-TYPE
    SYNTAX      Counter32
    UNITS       "bytes"
    MAX-ACCESS  read-only
    STATUS      current
    DESCRIPTION
        "The value of tmnxBsxGrpStatusEgrQFwdOutPOcts indicates the number of
         out of profile bytes diverted from ingress IOMs towards the ISA-AA MDA
         within this group for the particular queue."
    ::= { tmnxBsxGrpStatusEgrQEntry 7 }

tmnxBsxGrpStatusEgrQDroInPPkts   OBJECT-TYPE
    SYNTAX      Counter32
    UNITS       "packets"
    MAX-ACCESS  read-only
    STATUS      current
    DESCRIPTION
        "The value of tmnxBsxGrpStatusEgrQDroInPPkts indicates the number of in
         profile packets discarded from ingress IOMs towards the ISA-AA MDA
         within this group for the particular queue."
    ::= { tmnxBsxGrpStatusEgrQEntry 8 }

tmnxBsxGrpStatusEgrQDroOutPPkts  OBJECT-TYPE
    SYNTAX      Counter32
    UNITS       "packets"
    MAX-ACCESS  read-only
    STATUS      current
    DESCRIPTION
        "The value of tmnxBsxGrpStatusEgrQDroOutPPkts indicates the number of
         out of profile packets discarded from ingress IOMs towards the ISA-AA
         MDA within this group for the particular queue."
    ::= { tmnxBsxGrpStatusEgrQEntry 9 }

tmnxBsxGrpStatusEgrQDroInPOcts   OBJECT-TYPE
    SYNTAX      Counter32
    UNITS       "bytes"
    MAX-ACCESS  read-only
    STATUS      current
    DESCRIPTION
        "The value of tmnxBsxGrpStatusEgrQDroInPOcts indicates the number of in
         profile bytes discarded from ingress IOMs towards the ISA-AA MDA
         within this group for the particular queue."
    ::= { tmnxBsxGrpStatusEgrQEntry 10 }

tmnxBsxGrpStatusEgrQDroOutPOcts  OBJECT-TYPE
    SYNTAX      Counter32
    UNITS       "bytes"
    MAX-ACCESS  read-only
    STATUS      current
    DESCRIPTION
        "The value of tmnxBsxGrpStatusEgrQDroOutPOcts indicates the number of
         out of profile bytes discarded from ingress IOMs towards the ISA-AA
         MDA within this group for the particular queue."
    ::= { tmnxBsxGrpStatusEgrQEntry 11 }

tmnxBsxGrpStatusEgrQHCFwdInPPkts OBJECT-TYPE
    SYNTAX      Counter64
    UNITS       "packets"
    MAX-ACCESS  read-only
    STATUS      current
    DESCRIPTION
        "The value of tmnxBsxGrpStatusEgrQHCFwdInPPkts indicates the number of
         in profile packets diverted from ingress IOMs towards the ISA-AA MDA
         within this group for the particular queue."
    ::= { tmnxBsxGrpStatusEgrQEntry 12 }

tmnxBsxGrpStatusEgrQHCFwdOutPPkts OBJECT-TYPE
    SYNTAX      Counter64
    UNITS       "packets"
    MAX-ACCESS  read-only
    STATUS      current
    DESCRIPTION
        "The value of tmnxBsxGrpStatusEgrQHCFwdOutPPkts indicates the number of
         out of profile packets diverted from ingress IOMs towards the ISA-AA
         MDA within this group for the particular queue."
    ::= { tmnxBsxGrpStatusEgrQEntry 13 }

tmnxBsxGrpStatusEgrQHCFwdInPOcts OBJECT-TYPE
    SYNTAX      Counter64
    UNITS       "bytes"
    MAX-ACCESS  read-only
    STATUS      current
    DESCRIPTION
        "The value of tmnxBsxGrpStatusEgrQHCFwdInPOcts indicates the number of
         in profile bytes diverted from ingress IOMs towards the ISA-AA MDA
         within this group for the particular queue."
    ::= { tmnxBsxGrpStatusEgrQEntry 14 }

tmnxBsxGrpStatusEgrQHCFwdOutPOcts OBJECT-TYPE
    SYNTAX      Counter64
    UNITS       "bytes"
    MAX-ACCESS  read-only
    STATUS      current
    DESCRIPTION
        "The value of tmnxBsxGrpStatusEgrQHCFwdOutPOcts indicates the number of
         out of profile bytes diverted from ingress IOMs towards the ISA-AA MDA
         within this group for the particular queue."
    ::= { tmnxBsxGrpStatusEgrQEntry 15 }

tmnxBsxGrpStatusEgrQHCDroInPPkts OBJECT-TYPE
    SYNTAX      Counter64
    UNITS       "packets"
    MAX-ACCESS  read-only
    STATUS      current
    DESCRIPTION
        "The value of tmnxBsxGrpStatusEgrQHCDroInPPkts indicates the number of
         in profile packets discarded from ingress IOMs towards the ISA-AA MDA
         within this group for the particular queue."
    ::= { tmnxBsxGrpStatusEgrQEntry 16 }

tmnxBsxGrpStatusEgrQHCDroOutPPkts OBJECT-TYPE
    SYNTAX      Counter64
    UNITS       "packets"
    MAX-ACCESS  read-only
    STATUS      current
    DESCRIPTION
        "The value of tmnxBsxGrpStatusEgrQHCDroOutPPkts indicates the number of
         out of profile packets discarded from ingress IOMs towards the ISA-AA
         MDA within this group for the particular queue."
    ::= { tmnxBsxGrpStatusEgrQEntry 17 }

tmnxBsxGrpStatusEgrQHCDroInPOcts OBJECT-TYPE
    SYNTAX      Counter64
    UNITS       "bytes"
    MAX-ACCESS  read-only
    STATUS      current
    DESCRIPTION
        "The value of tmnxBsxGrpStatusEgrQHCDroInPOcts indicates the number of
         in profile bytes discarded from ingress IOMs towards the ISA-AA MDA
         within this group for the particular queue."
    ::= { tmnxBsxGrpStatusEgrQEntry 18 }

tmnxBsxGrpStatusEgrQHCDroOutPOcts OBJECT-TYPE
    SYNTAX      Counter64
    UNITS       "bytes"
    MAX-ACCESS  read-only
    STATUS      current
    DESCRIPTION
        "The value of tmnxBsxGrpStatusEgrQHCDroOutPOcts indicates the number of
         out of profile bytes discarded from ingress IOMs towards the ISA-AA
         MDA within this group for the particular queue."
    ::= { tmnxBsxGrpStatusEgrQEntry 19 }

tmnxBsxAaSubSumTable             OBJECT-TYPE
    SYNTAX      SEQUENCE OF TmnxBsxAaSubSumEntry
    MAX-ACCESS  not-accessible
    STATUS      current
    DESCRIPTION
        "The tmnxBsxAaSubSumTable contains an entry for each ISA-AA subscriber
         in the system. Each row contains the subscriber summary information
         for a given ISA-AA group, partition and statistics interval."
    ::= { tmnxBsxMdaObjs 8 }

tmnxBsxAaSubSumEntry             OBJECT-TYPE
    SYNTAX      TmnxBsxAaSubSumEntry
    MAX-ACCESS  not-accessible
    STATUS      current
    DESCRIPTION
        "Each tmnxBsxAaSubSumEntry contains the ISA-AA subscriber summary
         information within a group partition and statistics interval."
    INDEX       {
        tmnxBsxAaGrpPartIndex,
        tmnxBsxAaSubStatsInterval,
        tmnxBsxAaSubscriberType,
        tmnxBsxAaSubscriber
    }
    ::= { tmnxBsxAaSubSumTable 1 }

TmnxBsxAaSubSumEntry             ::= SEQUENCE
{
    tmnxBsxAaSubStatsInterval        TmnxBsxAaSubStatsInterval,
    tmnxBsxAaSubSumMdaSlotNum        TmnxSlotNumOrZero,
    tmnxBsxAaSubSumMdaMdaNum         Unsigned32,
    tmnxBsxAaSubSumAppProfName       TNamedItem,
    tmnxBsxAaSubSumDiscontTime       TimeStamp,
    tmnxBsxAaSubSumOctsAdmFmSb       Counter32,
    tmnxBsxAaSubSumPktsAdmFmSb       Counter32,
    tmnxBsxAaSubSumFlwsAdmFmSb       Counter32,
    tmnxBsxAaSubSumOctsDnyFmSb       Counter32,
    tmnxBsxAaSubSumPktsDnyFmSb       Counter32,
    tmnxBsxAaSubSumFlwsDnyFmSb       Counter32,
    tmnxBsxAaSubSumOctsAdmToSb       Counter32,
    tmnxBsxAaSubSumPktsAdmToSb       Counter32,
    tmnxBsxAaSubSumFlwsAdmToSb       Counter32,
    tmnxBsxAaSubSumOctsDnyToSb       Counter32,
    tmnxBsxAaSubSumPktsDnyToSb       Counter32,
    tmnxBsxAaSubSumFlwsDnyToSb       Counter32,
    tmnxBsxAaSubSumTermFlwDur        Counter32,
    tmnxBsxAaSubSumTermFlws          Counter32,
    tmnxBsxAaSubSumShrtDurFlws       Counter32,
    tmnxBsxAaSubSumMedDurFlws        Counter32,
    tmnxBsxAaSubSumLngDurFlws        Counter32,
    tmnxBsxAaSubSumActFlwsFmSb       Gauge32,
    tmnxBsxAaSubSumActFlwsToSb       Gauge32,
    tmnxBsxAaSubSumHCOctsAdmFmSb     Counter64,
    tmnxBsxAaSubSumHCPktsAdmFmSb     Counter64,
    tmnxBsxAaSubSumHCFlwsAdmFmSb     Counter64,
    tmnxBsxAaSubSumHCOctsDnyFmSb     Counter64,
    tmnxBsxAaSubSumHCPktsDnyFmSb     Counter64,
    tmnxBsxAaSubSumHCFlwsDnyFmSb     Counter64,
    tmnxBsxAaSubSumHCOctsAdmToSb     Counter64,
    tmnxBsxAaSubSumHCPktsAdmToSb     Counter64,
    tmnxBsxAaSubSumHCFlwsAdmToSb     Counter64,
    tmnxBsxAaSubSumHCOctsDnyToSb     Counter64,
    tmnxBsxAaSubSumHCPktsDnyToSb     Counter64,
    tmnxBsxAaSubSumHCFlwsDnyToSb     Counter64,
    tmnxBsxAaSubSumHCTermFlwDur      Counter64,
    tmnxBsxAaSubSumHCTermFlws        Counter64,
    tmnxBsxAaSubSumHCShrtDurFlws     Counter64,
    tmnxBsxAaSubSumHCMedDurFlws      Counter64,
    tmnxBsxAaSubSumHCLngDurFlws      Counter64,
    tmnxBsxAaSubSumTetherState       TmnxBsxAaSubTetherState
}

tmnxBsxAaSubStatsInterval        OBJECT-TYPE
    SYNTAX      TmnxBsxAaSubStatsInterval
    MAX-ACCESS  not-accessible
    STATUS      current
    DESCRIPTION
        "The tmnxBsxAaSubStatsInterval specifies the interval for the retrieval
         of application assurance subscriber statistics."
    ::= { tmnxBsxAaSubSumEntry 1 }

tmnxBsxAaSubSumMdaSlotNum        OBJECT-TYPE
    SYNTAX      TmnxSlotNumOrZero
    MAX-ACCESS  read-only
    STATUS      current
    DESCRIPTION
        "The value of tmnxBsxAaSubSumMdaSlotNum indicates the slot number of
         the ISA-AA MDA servicing the subscriber."
    ::= { tmnxBsxAaSubSumEntry 2 }

tmnxBsxAaSubSumMdaMdaNum         OBJECT-TYPE
    SYNTAX      Unsigned32 (0..16)
    MAX-ACCESS  read-only
    STATUS      current
    DESCRIPTION
        "The value of tmnxBsxAaSubSumMdaMdaNum indicates the MDA number of the
         ISA-AA MDA servicing the subscriber."
    ::= { tmnxBsxAaSubSumEntry 3 }

tmnxBsxAaSubSumAppProfName       OBJECT-TYPE
    SYNTAX      TNamedItem
    MAX-ACCESS  read-only
    STATUS      current
    DESCRIPTION
        "The value of tmnxBsxAaSubSumAppProfName indicates the name of the
         ISA-AA application profile associated with the subscriber."
    ::= { tmnxBsxAaSubSumEntry 4 }

tmnxBsxAaSubSumDiscontTime       OBJECT-TYPE
    SYNTAX      TimeStamp
    MAX-ACCESS  read-only
    STATUS      current
    DESCRIPTION
        "The value of tmnxBsxAaSubSumDiscontTime indicates the
         SNMPv2-MIB::sysUpTime (centiseconds) when the summary information for
         the subscriber has last changed status."
    ::= { tmnxBsxAaSubSumEntry 5 }

tmnxBsxAaSubSumOctsAdmFmSb       OBJECT-TYPE
    SYNTAX      Counter32
    UNITS       "bytes"
    MAX-ACCESS  read-only
    STATUS      current
    DESCRIPTION
        "The value of tmnxBsxAaSubSumOctsAdmFmSb indicates the total number of
         bytes permitted for the subscriber to network direction."
    ::= { tmnxBsxAaSubSumEntry 6 }

tmnxBsxAaSubSumPktsAdmFmSb       OBJECT-TYPE
    SYNTAX      Counter32
    UNITS       "packets"
    MAX-ACCESS  read-only
    STATUS      current
    DESCRIPTION
        "The value of tmnxBsxAaSubSumPktsAdmFmSb indicates the total number of
         packets permitted for the subscriber to network direction."
    ::= { tmnxBsxAaSubSumEntry 7 }

tmnxBsxAaSubSumFlwsAdmFmSb       OBJECT-TYPE
    SYNTAX      Counter32
    UNITS       "flows"
    MAX-ACCESS  read-only
    STATUS      current
    DESCRIPTION
        "The value of tmnxBsxAaSubSumFlwsAdmFmSb indicates the total number of
         flows permitted for the subscriber to network direction."
    ::= { tmnxBsxAaSubSumEntry 8 }

tmnxBsxAaSubSumOctsDnyFmSb       OBJECT-TYPE
    SYNTAX      Counter32
    UNITS       "bytes"
    MAX-ACCESS  read-only
    STATUS      current
    DESCRIPTION
        "The value of tmnxBsxAaSubSumOctsDnyFmSb indicates the total number of
         bytes dropped for the subscriber to network direction."
    ::= { tmnxBsxAaSubSumEntry 9 }

tmnxBsxAaSubSumPktsDnyFmSb       OBJECT-TYPE
    SYNTAX      Counter32
    UNITS       "packets"
    MAX-ACCESS  read-only
    STATUS      current
    DESCRIPTION
        "The value of tmnxBsxAaSubSumPktsDnyFmSb indicates the total number of
         packets dropped for the subscriber to network direction."
    ::= { tmnxBsxAaSubSumEntry 10 }

tmnxBsxAaSubSumFlwsDnyFmSb       OBJECT-TYPE
    SYNTAX      Counter32
    UNITS       "flows"
    MAX-ACCESS  read-only
    STATUS      current
    DESCRIPTION
        "The value of tmnxBsxAaSubSumFlwsDnyFmSb indicates the total number of
         flows that dropped subsequent packets in the subscriber to network
         direction."
    ::= { tmnxBsxAaSubSumEntry 11 }

tmnxBsxAaSubSumOctsAdmToSb       OBJECT-TYPE
    SYNTAX      Counter32
    UNITS       "bytes"
    MAX-ACCESS  read-only
    STATUS      current
    DESCRIPTION
        "The value of tmnxBsxAaSubSumOctsAdmToSb indicates the total number of
         bytes permitted for the network to subscriber direction."
    ::= { tmnxBsxAaSubSumEntry 12 }

tmnxBsxAaSubSumPktsAdmToSb       OBJECT-TYPE
    SYNTAX      Counter32
    UNITS       "packets"
    MAX-ACCESS  read-only
    STATUS      current
    DESCRIPTION
        "The value of tmnxBsxAaSubSumPktsAdmToSb indicates the total number of
         packets permitted for the network to subscriber direction."
    ::= { tmnxBsxAaSubSumEntry 13 }

tmnxBsxAaSubSumFlwsAdmToSb       OBJECT-TYPE
    SYNTAX      Counter32
    UNITS       "flows"
    MAX-ACCESS  read-only
    STATUS      current
    DESCRIPTION
        "The value of tmnxBsxAaSubSumFlwsAdmToSb indicates the total number of
         flows permitted for the network to subscriber direction."
    ::= { tmnxBsxAaSubSumEntry 14 }

tmnxBsxAaSubSumOctsDnyToSb       OBJECT-TYPE
    SYNTAX      Counter32
    UNITS       "bytes"
    MAX-ACCESS  read-only
    STATUS      current
    DESCRIPTION
        "The value of tmnxBsxAaSubSumOctsDnyToSb indicates the total number of
         bytes dropped for the network to subscriber direction."
    ::= { tmnxBsxAaSubSumEntry 15 }

tmnxBsxAaSubSumPktsDnyToSb       OBJECT-TYPE
    SYNTAX      Counter32
    UNITS       "packets"
    MAX-ACCESS  read-only
    STATUS      current
    DESCRIPTION
        "The value of tmnxBsxAaSubSumPktsDnyToSb indicates the total number of
         packets dropped for the network to subscriber direction."
    ::= { tmnxBsxAaSubSumEntry 16 }

tmnxBsxAaSubSumFlwsDnyToSb       OBJECT-TYPE
    SYNTAX      Counter32
    UNITS       "flows"
    MAX-ACCESS  read-only
    STATUS      current
    DESCRIPTION
        "The value of tmnxBsxAaSubSumFlwsDnyToSb indicates the total number of
         flows that dropped subsequent packets in the network to subscriber
         direction."
    ::= { tmnxBsxAaSubSumEntry 17 }

tmnxBsxAaSubSumTermFlwDur        OBJECT-TYPE
    SYNTAX      Counter32
    UNITS       "seconds"
    MAX-ACCESS  read-only
    STATUS      current
    DESCRIPTION
        "The value of tmnxBsxAaSubSumTermFlwDur indicates the sum of all flow
         durations from first packet seen to last packet seen for flows that
         have terminated."
    ::= { tmnxBsxAaSubSumEntry 18 }

tmnxBsxAaSubSumTermFlws          OBJECT-TYPE
    SYNTAX      Counter32
    UNITS       "flows"
    MAX-ACCESS  read-only
    STATUS      current
    DESCRIPTION
        "The value of tmnxBsxAaSubSumTermFlws indicates the total number of
         allowed flows that have terminated."
    ::= { tmnxBsxAaSubSumEntry 19 }

tmnxBsxAaSubSumShrtDurFlws       OBJECT-TYPE
    SYNTAX      Counter32
    UNITS       "flows"
    MAX-ACCESS  read-only
    STATUS      current
    DESCRIPTION
        "The value of tmnxBsxAaSubSumShrtDurFlws indicates the total number of
         flows with a duration less than or equal to 30 seconds, that have
         completed."
    ::= { tmnxBsxAaSubSumEntry 20 }

tmnxBsxAaSubSumMedDurFlws        OBJECT-TYPE
    SYNTAX      Counter32
    UNITS       "flows"
    MAX-ACCESS  read-only
    STATUS      current
    DESCRIPTION
        "The value of tmnxBsxAaSubSumMedDurFlws indicates the total number of
         flows with a duration less than or equal to 180 seconds, but greater
         than 30 seconds, that have completed."
    ::= { tmnxBsxAaSubSumEntry 21 }

tmnxBsxAaSubSumLngDurFlws        OBJECT-TYPE
    SYNTAX      Counter32
    UNITS       "flows"
    MAX-ACCESS  read-only
    STATUS      current
    DESCRIPTION
        "The value of tmnxBsxAaSubSumLngDurFlws indicates the total number of
         flows with a duration greater than 180 seconds, that have completed."
    ::= { tmnxBsxAaSubSumEntry 22 }

tmnxBsxAaSubSumActFlwsFmSb       OBJECT-TYPE
    SYNTAX      Gauge32
    UNITS       "flows"
    MAX-ACCESS  read-only
    STATUS      current
    DESCRIPTION
        "The value of tmnxBsxAaSubSumActFlwsFmSb indicates the number of
         allowed flows in the subscriber to network direction that are active."
    ::= { tmnxBsxAaSubSumEntry 23 }

tmnxBsxAaSubSumActFlwsToSb       OBJECT-TYPE
    SYNTAX      Gauge32
    UNITS       "flows"
    MAX-ACCESS  read-only
    STATUS      current
    DESCRIPTION
        "The value of tmnxBsxAaSubSumActFlwsToSb indicates the number of
         allowed flows in the network to subscriber direction that are active."
    ::= { tmnxBsxAaSubSumEntry 24 }

tmnxBsxAaSubSumHCOctsAdmFmSb     OBJECT-TYPE
    SYNTAX      Counter64
    UNITS       "bytes"
    MAX-ACCESS  read-only
    STATUS      current
    DESCRIPTION
        "The value of tmnxBsxAaSubSumHCOctsAdmFmSb indicates the total number
         of bytes permitted for the subscriber to network direction. This
         object is a 64-bit version of tmnxBsxAaSubSumOctsAdmFmSb."
    ::= { tmnxBsxAaSubSumEntry 25 }

tmnxBsxAaSubSumHCPktsAdmFmSb     OBJECT-TYPE
    SYNTAX      Counter64
    UNITS       "packets"
    MAX-ACCESS  read-only
    STATUS      current
    DESCRIPTION
        "The value of tmnxBsxAaSubSumHCPktsAdmFmSb indicates the total number
         of packets permitted for the subscriber to network direction. This
         object is a 64-bit version of tmnxBsxAaSubSumPktsAdmFmSb."
    ::= { tmnxBsxAaSubSumEntry 26 }

tmnxBsxAaSubSumHCFlwsAdmFmSb     OBJECT-TYPE
    SYNTAX      Counter64
    UNITS       "flows"
    MAX-ACCESS  read-only
    STATUS      current
    DESCRIPTION
        "The value of tmnxBsxAaSubSumHCFlwsAdmFmSb indicates the total number
         of flows permitted for the subscriber to network direction. This
         object is a 64-bit version of tmnxBsxAaSubSumFlwsAdmFmSb."
    ::= { tmnxBsxAaSubSumEntry 27 }

tmnxBsxAaSubSumHCOctsDnyFmSb     OBJECT-TYPE
    SYNTAX      Counter64
    UNITS       "bytes"
    MAX-ACCESS  read-only
    STATUS      current
    DESCRIPTION
        "The value of tmnxBsxAaSubSumHCOctsDnyFmSb indicates the total number
         of bytes dropped for the subscriber to network direction. This object
         is a 64-bit version of tmnxBsxAaSubSumOctsDnyFmSb."
    ::= { tmnxBsxAaSubSumEntry 28 }

tmnxBsxAaSubSumHCPktsDnyFmSb     OBJECT-TYPE
    SYNTAX      Counter64
    UNITS       "packets"
    MAX-ACCESS  read-only
    STATUS      current
    DESCRIPTION
        "The value of tmnxBsxAaSubSumHCPktsDnyFmSb indicates the total number
         of packets dropped for the subscriber to network direction. This
         object is a 64-bit version of tmnxBsxAaSubSumPktsDnyFmSb."
    ::= { tmnxBsxAaSubSumEntry 29 }

tmnxBsxAaSubSumHCFlwsDnyFmSb     OBJECT-TYPE
    SYNTAX      Counter64
    UNITS       "flows"
    MAX-ACCESS  read-only
    STATUS      current
    DESCRIPTION
        "The value of tmnxBsxAaSubSumHCFlwsDnyFmSb indicates the total number
         of flows that dropped subsequent packets in the subscriber to network
         direction. This object is a 64-bit version of
         tmnxBsxAaSubSumFlwsDnyFmSb."
    ::= { tmnxBsxAaSubSumEntry 30 }

tmnxBsxAaSubSumHCOctsAdmToSb     OBJECT-TYPE
    SYNTAX      Counter64
    UNITS       "bytes"
    MAX-ACCESS  read-only
    STATUS      current
    DESCRIPTION
        "The value of tmnxBsxAaSubSumHCOctsAdmToSb indicates the total number
         of bytes permitted for the network to subscriber direction. This
         object is a 64-bit version of tmnxBsxAaSubSumOctsAdmToSb."
    ::= { tmnxBsxAaSubSumEntry 31 }

tmnxBsxAaSubSumHCPktsAdmToSb     OBJECT-TYPE
    SYNTAX      Counter64
    UNITS       "packets"
    MAX-ACCESS  read-only
    STATUS      current
    DESCRIPTION
        "The value of tmnxBsxAaSubSumHCPktsAdmToSb indicates the total number
         of packets permitted for the network to subscriber direction. This
         object is a 64-bit version of tmnxBsxAaSubSumPktsAdmToSb."
    ::= { tmnxBsxAaSubSumEntry 32 }

tmnxBsxAaSubSumHCFlwsAdmToSb     OBJECT-TYPE
    SYNTAX      Counter64
    UNITS       "flows"
    MAX-ACCESS  read-only
    STATUS      current
    DESCRIPTION
        "The value of tmnxBsxAaSubSumHCFlwsAdmToSb indicates the total number
         of flows permitted for the network to subscriber direction. This
         object is a 64-bit version of tmnxBsxAaSubSumFlwsAdmToSb."
    ::= { tmnxBsxAaSubSumEntry 33 }

tmnxBsxAaSubSumHCOctsDnyToSb     OBJECT-TYPE
    SYNTAX      Counter64
    UNITS       "bytes"
    MAX-ACCESS  read-only
    STATUS      current
    DESCRIPTION
        "The value of tmnxBsxAaSubSumHCOctsDnyToSb indicates the total number
         of bytes dropped for the network to subscriber direction. This object
         is a 64-bit version of tmnxBsxAaSubSumOctsDnyToSb."
    ::= { tmnxBsxAaSubSumEntry 34 }

tmnxBsxAaSubSumHCPktsDnyToSb     OBJECT-TYPE
    SYNTAX      Counter64
    UNITS       "packets"
    MAX-ACCESS  read-only
    STATUS      current
    DESCRIPTION
        "The value of tmnxBsxAaSubSumHCPktsDnyToSb indicates the total number
         of packets dropped for the network to subscriber direction. This
         object is a 64-bit version of tmnxBsxAaSubSumPktsDnyToSb."
    ::= { tmnxBsxAaSubSumEntry 35 }

tmnxBsxAaSubSumHCFlwsDnyToSb     OBJECT-TYPE
    SYNTAX      Counter64
    UNITS       "flows"
    MAX-ACCESS  read-only
    STATUS      current
    DESCRIPTION
        "The value of tmnxBsxAaSubSumHCFlwsDnyToSb indicates the total number
         of flows that dropped subsequent packets in the network to subscriber
         direction. This object is the 64-bit version of
         tmnxBsxAaSubSumFlwsDnyToSb."
    ::= { tmnxBsxAaSubSumEntry 36 }

tmnxBsxAaSubSumHCTermFlwDur      OBJECT-TYPE
    SYNTAX      Counter64
    UNITS       "seconds"
    MAX-ACCESS  read-only
    STATUS      current
    DESCRIPTION
        "The value of tmnxBsxAaSubSumHCTermFlwDur indicates the sum of all flow
         durations from first packet seen to last packet seen for flows that
         have terminated. This object is a 64-bit version of
         tmnxBsxAaSubSumTermFlwDur."
    ::= { tmnxBsxAaSubSumEntry 37 }

tmnxBsxAaSubSumHCTermFlws        OBJECT-TYPE
    SYNTAX      Counter64
    UNITS       "flows"
    MAX-ACCESS  read-only
    STATUS      current
    DESCRIPTION
        "The value of tmnxBsxAaSubSumHCTermFlws indicates the total number of
         allowed flows that have terminated. This object is a 64-bit version of
         tmnxBsxAaSubSumTermFlws."
    ::= { tmnxBsxAaSubSumEntry 38 }

tmnxBsxAaSubSumHCShrtDurFlws     OBJECT-TYPE
    SYNTAX      Counter64
    UNITS       "flows"
    MAX-ACCESS  read-only
    STATUS      current
    DESCRIPTION
        "The value of tmnxBsxAaSubSumHCShrtDurFlws indicates the total number
         of flows with a duration less than or equal to 30 seconds, that have
         completed. This object is a 64-bit version of
         tmnxBsxAaSubSumShrtDurFlws."
    ::= { tmnxBsxAaSubSumEntry 39 }

tmnxBsxAaSubSumHCMedDurFlws      OBJECT-TYPE
    SYNTAX      Counter64
    UNITS       "flows"
    MAX-ACCESS  read-only
    STATUS      current
    DESCRIPTION
        "The value of tmnxBsxAaSubSumHCMedDurFlws indicates the total number of
         flows with a duration less than or equal to 180 seconds, but greater
         than 30 seconds, that have completed. This object is a 64-bit version
         of tmnxBsxAaSubSumMedDurFlws."
    ::= { tmnxBsxAaSubSumEntry 40 }

tmnxBsxAaSubSumHCLngDurFlws      OBJECT-TYPE
    SYNTAX      Counter64
    UNITS       "flows"
    MAX-ACCESS  read-only
    STATUS      current
    DESCRIPTION
        "The value of tmnxBsxAaSubSumHCLngDurFlws indicates the total number of
         flows with a duration greater than 180 seconds, that have completed.
         This object is a 64-bit version of tmnxBsxAaSubSumLngDurFlws."
    ::= { tmnxBsxAaSubSumEntry 41 }

tmnxBsxAaSubSumTetherState       OBJECT-TYPE
    SYNTAX      TmnxBsxAaSubTetherState
    MAX-ACCESS  read-only
    STATUS      current
    DESCRIPTION
        "The value of tmnxBsxAaSubSumTetherState indicates the tethering state
         of an Application Assurance Subscriber."
    DEFVAL      { notApplicable }
    ::= { tmnxBsxAaSubSumEntry 42 }

tmnxBsxAaGrpPartTable            OBJECT-TYPE
    SYNTAX      SEQUENCE OF TmnxBsxAaGrpPartEntry
    MAX-ACCESS  not-accessible
    STATUS      current
    DESCRIPTION
        "The tmnxBsxAaGrpPartTable contains the Application Assurance partition
         configuration within an Application Assurance group."
    ::= { tmnxBsxMdaObjs 9 }

tmnxBsxAaGrpPartEntry            OBJECT-TYPE
    SYNTAX      TmnxBsxAaGrpPartEntry
    MAX-ACCESS  not-accessible
    STATUS      current
    DESCRIPTION
        "Each tmnxBsxAaGrpPartEntry specifies an Application Assurance
         partition within an Application Assurance group. "
    INDEX       { tmnxBsxAaGrpPartIndex }
    ::= { tmnxBsxAaGrpPartTable 1 }

TmnxBsxAaGrpPartEntry            ::= SEQUENCE
{
    tmnxBsxAaGrpPartIndex            TmnxBsxAaGrpPartIndex,
    tmnxBsxAaGrpPartRowStatus        RowStatus,
    tmnxBsxAaGrpPartRowLastChange    TimeStamp,
    tmnxBsxAaGrpPartDescription      TItemDescription,
    tmnxBsxAaGrpPartXOnlineHost      TmnxEnabledDisabled,
    tmnxBsxAaGrpPartHttpMatchAllReq  TmnxEnabledDisabled,
    tmnxBsxAaGrpPartAaSubRemote      TmnxEnabledDisabled,
    tmnxBsxAaGrpPartAqpInitialLookup TmnxEnabledDisabled,
    tmnxBsxAaGrpPartShallowInspect   TmnxEnabledDisabled,
    tmnxBsxAaGrpPartIpIdentContrib   TmnxEnabledDisabled
}

tmnxBsxAaGrpPartIndex            OBJECT-TYPE
    SYNTAX      TmnxBsxAaGrpPartIndex
    MAX-ACCESS  not-accessible
    STATUS      current
    DESCRIPTION
        "The value of tmnxBsxAaGrpPartIndex specifies the partition index
         within an AA group.

         The corresponding row for the AA group must have already been created
         in the tmnxBsxIsaAaGrpTable.

         Partition index '0' indicates group wide AA policy information, and is
         automatically created when the AA group is created in the
         tmnxBsxIsaAaGrpTable."
    ::= { tmnxBsxAaGrpPartEntry 1 }

tmnxBsxAaGrpPartRowStatus        OBJECT-TYPE
    SYNTAX      RowStatus
    MAX-ACCESS  read-create
    STATUS      current
    DESCRIPTION
        "The value of tmnxBsxAaGrpPartRowStatus specifies the row status. Rows
         in the tmnxBsxAaGrpPartTable are created by specifying the value of
         'createAndGo (4)', and deleted by specifying the value of 'destroy
         (6)'.

         Row entries with partition index '0' are created by creating an ISA
         group in the tmnxBsxIsaAaGrpTable and cannot be deleted directly from
         this table. Instead the corresponding group should be deleted from the
         tmnxBsxIsaAaGrpTable."
    ::= { tmnxBsxAaGrpPartEntry 2 }

tmnxBsxAaGrpPartRowLastChange    OBJECT-TYPE
    SYNTAX      TimeStamp
    MAX-ACCESS  read-only
    STATUS      current
    DESCRIPTION
        "The value of tmnxBsxAaGrpPartRowLastChange indicates the last time a
         successful set was performed on this row of the tmnxBsxAaGrpPartTable."
    ::= { tmnxBsxAaGrpPartEntry 3 }

tmnxBsxAaGrpPartDescription      OBJECT-TYPE
    SYNTAX      TItemDescription
    MAX-ACCESS  read-create
    STATUS      current
    DESCRIPTION
        "The value of tmnxBsxAaGrpPartDescription specifies the description of
         the group or the partition within an AA group."
    DEFVAL      { "" }
    ::= { tmnxBsxAaGrpPartEntry 4 }

tmnxBsxAaGrpPartXOnlineHost      OBJECT-TYPE
    SYNTAX      TmnxEnabledDisabled
    MAX-ACCESS  read-create
    STATUS      current
    DESCRIPTION
        "The value of tmnxBsxAaGrpPartXOnlineHost specifies whether
         X-Online-Host header field is used as a replacement for the HTTP Host
         header field."
    DEFVAL      { disabled }
    ::= { tmnxBsxAaGrpPartEntry 5 }

tmnxBsxAaGrpPartHttpMatchAllReq  OBJECT-TYPE
    SYNTAX      TmnxEnabledDisabled
    MAX-ACCESS  read-create
    STATUS      current
    DESCRIPTION
        "The value of tmnxBsxAaGrpPartHttpMatchAllReq specifies whether or not
         constant monitoring is performed for HTTP request strings for
         application changes in regular HTTP flows."
    DEFVAL      { disabled }
    ::= { tmnxBsxAaGrpPartEntry 6 }

tmnxBsxAaGrpPartAaSubRemote      OBJECT-TYPE
    SYNTAX      TmnxEnabledDisabled
    MAX-ACCESS  read-create
    STATUS      current
    DESCRIPTION
        "The value of tmnxBsxAaGrpPartAaSubRemote specifies whether or not the
         from subscriber and to subscriber traffic direction is reversed for
         this group-partition."
    DEFVAL      { disabled }
    ::= { tmnxBsxAaGrpPartEntry 7 }

tmnxBsxAaGrpPartAqpInitialLookup OBJECT-TYPE
    SYNTAX      TmnxEnabledDisabled
    MAX-ACCESS  read-create
    STATUS      current
    DESCRIPTION
        "The value of tmnxBsxAaGrpPartAqpInitialLookup specifies the
         application QoS policy (AQP) initial lookup which is in use, as
         defined in tmnxBsxAqpBaseTable (and augmenting tables). When 'enabled
         (1)', flows are first subject to an AQP lookup. When 'disabled (2)',
         flows are first subject to the subscriber default policy. When
         identification is completed, a full application-aware AQP lookup is
         performed in either case."
    DEFVAL      { disabled }
    ::= { tmnxBsxAaGrpPartEntry 8 }

tmnxBsxAaGrpPartShallowInspect   OBJECT-TYPE
    SYNTAX      TmnxEnabledDisabled
    MAX-ACCESS  read-create
    STATUS      current
    DESCRIPTION
        "The value of tmnxBsxAaGrpPartShallowInspect specifies whether shallow
         inspection is enabled or not on this partition."
    DEFVAL      { disabled }
    ::= { tmnxBsxAaGrpPartEntry 12 }

tmnxBsxAaGrpPartIpIdentContrib   OBJECT-TYPE
    SYNTAX      TmnxEnabledDisabled
    MAX-ACCESS  read-create
    STATUS      current
    DESCRIPTION
        "The value of tmnxBsxAaGrpPartIpIdentContrib specifies whether the
         partition contributes to the IP-to-Application mappings in IP
         Identification Assist."
    DEFVAL      { enabled }
    ::= { tmnxBsxAaGrpPartEntry 14 }

tmnxBsxIsaLoadBalUnSubTable      OBJECT-TYPE
    SYNTAX      SEQUENCE OF TmnxBsxIsaLoadBalUnSubEntry
    MAX-ACCESS  not-accessible
    STATUS      current
    DESCRIPTION
        "The tmnxBsxIsaLoadBalUnSubTable contains an entry for each ISA-AA
         subscriber that could not be assigned to an ISA-AA MDA after a load
         balancing operation. Each row contains an unassigned ISA-AA subscriber
         within an ISA-AA group."
    ::= { tmnxBsxMdaObjs 10 }

tmnxBsxIsaLoadBalUnSubEntry      OBJECT-TYPE
    SYNTAX      TmnxBsxIsaLoadBalUnSubEntry
    MAX-ACCESS  not-accessible
    STATUS      current
    DESCRIPTION
        "Each tmnxBsxIsaLoadBalUnSubEntry contains an ISA-AA subscriber which
         could not be assigned to an ISA-AA MDA within the ISA-AA group."
    INDEX       {
        tmnxBsxIsaAaGroupIndex,
        tmnxBsxAaSubscriberType,
        tmnxBsxIsaLoadBalUnSub
    }
    ::= { tmnxBsxIsaLoadBalUnSubTable 1 }

TmnxBsxIsaLoadBalUnSubEntry      ::= SEQUENCE
{
    tmnxBsxIsaLoadBalUnSub           TmnxBsxAaSubscriber,
    tmnxBsxIsaLoadBalUnSubTransit    Gauge32
}

tmnxBsxIsaLoadBalUnSub           OBJECT-TYPE
    SYNTAX      TmnxBsxAaSubscriber
    MAX-ACCESS  read-only
    STATUS      current
    DESCRIPTION
        "The value of tmnxBsxIsaLoadBalUnSub indicates the ISA-AA subscriber
         which is not assigned to an ISA-AA MDA. The format of this object is
         determined by the value of the tmnxBsxAaSubscriberType."
    ::= { tmnxBsxIsaLoadBalUnSubEntry 1 }

tmnxBsxIsaLoadBalUnSubTransit    OBJECT-TYPE
    SYNTAX      Gauge32
    UNITS       "subscribers"
    MAX-ACCESS  read-only
    STATUS      current
    DESCRIPTION
        "The value of tmnxBsxIsaLoadBalUnSubTransit indicates the number of
         transit subscribers under the parent subscriber tmnxBsxIsaLoadBalUnSub
         which have not been assigned to an ISA-AA MDA."
    ::= { tmnxBsxIsaLoadBalUnSubEntry 2 }

tmnxBsxAaSubTable                OBJECT-TYPE
    SYNTAX      SEQUENCE OF TmnxBsxAaSubEntry
    MAX-ACCESS  not-accessible
    STATUS      current
    DESCRIPTION
        "The tmnxBsxAaSubTable contains an entry for each ISA-AA subscriber in
         the system. Each row contains information relevant to an Application
         Assurance subscriber."
    ::= { tmnxBsxMdaObjs 11 }

tmnxBsxAaSubEntry                OBJECT-TYPE
    SYNTAX      TmnxBsxAaSubEntry
    MAX-ACCESS  not-accessible
    STATUS      current
    DESCRIPTION
        "Each tmnxBsxAaSubEntry contains information relevant to an Application
         Assurance subscriber including the servicing ISA-AA MDA, application
         profile, and if policy overrides are present."
    INDEX       {
        tmnxBsxAaGrpPartIndex,
        tmnxBsxAaSubscriberType,
        tmnxBsxAaSubscriber
    }
    ::= { tmnxBsxAaSubTable 1 }

TmnxBsxAaSubEntry                ::= SEQUENCE
{
    tmnxBsxAaSubMdaSlotNum           TmnxSlotNumOrZero,
    tmnxBsxAaSubMdaMdaNum            Unsigned32,
    tmnxBsxAaSubAppProfName          TNamedItem,
    tmnxBsxAaSubHasOverrides         TruthValue,
    tmnxBsxAaSubTransitIpPolicyId    TmnxBsxTransitIpPolicyIdOrZero,
    tmnxBsxAaSubTransPrefPolicyId    TmnxBsxTransPrefPolicyIdOrZero,
    tmnxBsxAaSubAarpId               TmnxBsxAarpIdOrZero,
    tmnxBsxAaSubHttpNotifLastTime    DateAndTime,
    tmnxBsxAaSubHttpUrlParam         SnmpAdminString,
    tmnxBsxAaSubCircuitId            TmnxBsxAaSubCircuitId,
    tmnxBsxAaSubRemoteId             TmnxBsxAaSubRemoteId,
    tmnxBsxAaSubMacAddr              MacAddress,
    tmnxBsxAaSubSapPortId            TmnxPortID,
    tmnxBsxAaSubSapEncapVal          TmnxEncapVal,
    tmnxBsxAaSubQuarantined          TruthValue,
    tmnxBsxAaSubImsi                 TmnxMobImsiStr,
    tmnxBsxAaSubImei                 TmnxMobImei,
    tmnxBsxAaSubMsisdn               TmnxMobMsisdn,
    tmnxBsxAaSubApn                  TmnxMobApnOrZero,
    tmnxBsxAaSubUserLocation         DisplayString,
    tmnxBsxAaSubRatType              TmnxBsxHttpEnrichRATType,
    tmnxBsxAaSubChargingId           Unsigned32,
    tmnxBsxAaSubBillingType          Unsigned32,
    tmnxBsxAaSubPlmnId               Unsigned32,
    tmnxBsxAaSubPdnGatewayAddr       InetAddress,
    tmnxBsxAaSubPdnGatewayAddrType   InetAddressType,
    tmnxBsxAaSubTrafficDistByIp      TruthValue,
    tmnxBsxAaSubQci                  Unsigned32,
    tmnxBsxAaSubSliceId              Unsigned32,
    tmnxBsxAaSubMmeAmfAddr           InetAddress,
    tmnxBsxAaSubMmeAmfAddrType       InetAddressType,
    tmnxBsxAaSubPolicyRuleName       TLNamedItemOrEmpty
}

tmnxBsxAaSubMdaSlotNum           OBJECT-TYPE
    SYNTAX      TmnxSlotNumOrZero
    MAX-ACCESS  read-only
    STATUS      current
    DESCRIPTION
        "The value of tmnxBsxAaSubMdaSlotNum indicates the slot number of the
         ISA-AA MDA assigned to the subscriber."
    ::= { tmnxBsxAaSubEntry 1 }

tmnxBsxAaSubMdaMdaNum            OBJECT-TYPE
    SYNTAX      Unsigned32 (0..16)
    MAX-ACCESS  read-only
    STATUS      current
    DESCRIPTION
        "The value of tmnxBsxAaSubMdaMdaNum indicates the MDA number of the
         ISA-AA MDA assigned to the subscriber."
    ::= { tmnxBsxAaSubEntry 2 }

tmnxBsxAaSubAppProfName          OBJECT-TYPE
    SYNTAX      TNamedItem
    MAX-ACCESS  read-only
    STATUS      current
    DESCRIPTION
        "The value of tmnxBsxAaSubAppProfName indicates the name of the ISA-AA
         application profile associated with the subscriber."
    ::= { tmnxBsxAaSubEntry 3 }

tmnxBsxAaSubHasOverrides         OBJECT-TYPE
    SYNTAX      TruthValue
    MAX-ACCESS  read-only
    STATUS      current
    DESCRIPTION
        "The value of tmnxBsxAaSubHasOverrides indicates if the subscriber has
         policy overrides."
    ::= { tmnxBsxAaSubEntry 4 }

tmnxBsxAaSubTransitIpPolicyId    OBJECT-TYPE
    SYNTAX      TmnxBsxTransitIpPolicyIdOrZero
    MAX-ACCESS  read-only
    STATUS      current
    DESCRIPTION
        "The value of tmnxBsxAaSubTransitIpPolicyId indicates the Transit IP
         Policy to which this subscriber belongs.

         The value of '0' indicates that no transit IP policy is associated
         with this subscriber."
    ::= { tmnxBsxAaSubEntry 5 }

tmnxBsxAaSubTransPrefPolicyId    OBJECT-TYPE
    SYNTAX      TmnxBsxTransPrefPolicyIdOrZero
    MAX-ACCESS  read-only
    STATUS      current
    DESCRIPTION
        "The value of tmnxBsxAaSubTransPrefPolicyId indicates the transit
         prefix policy to which this subscriber belongs.

         The value of '0' indicates that no transit prefix policy is associated
         with this subscriber."
    ::= { tmnxBsxAaSubEntry 6 }

tmnxBsxAaSubAarpId               OBJECT-TYPE
    SYNTAX      TmnxBsxAarpIdOrZero
    MAX-ACCESS  read-only
    STATUS      current
    DESCRIPTION
        "The value of tmnxBsxAaSubAarpId indicates the AARP instance id to
         which this subscriber belongs.

         The value of '0' indicates that no AARP instance is associated with
         this subscriber."
    ::= { tmnxBsxAaSubEntry 7 }

tmnxBsxAaSubHttpNotifLastTime    OBJECT-TYPE
    SYNTAX      DateAndTime (SIZE (11))
    MAX-ACCESS  read-only
    STATUS      current
    DESCRIPTION
        "The value of tmnxBsxAaSubHttpNotifLastTime indicates when the last
         HTTP Notification occurred for this subscriber.

         DateAndTime.year = 0 is returned if no HTTP notification has occurred
         for this subscriber since system start up."
    ::= { tmnxBsxAaSubEntry 8 }

tmnxBsxAaSubHttpUrlParam         OBJECT-TYPE
    SYNTAX      SnmpAdminString (SIZE (0..32))
    MAX-ACCESS  read-only
    STATUS      current
    DESCRIPTION
        "The value of tmnxBsxAaSubHttpUrlParam indicates the HTTP URL
         Parameters associated with this subscriber."
    ::= { tmnxBsxAaSubEntry 9 }

tmnxBsxAaSubCircuitId            OBJECT-TYPE
    SYNTAX      TmnxBsxAaSubCircuitId
    MAX-ACCESS  read-only
    STATUS      current
    DESCRIPTION
        "The value of tmnxBsxAaSubCircuitId specifies the ID of a subscriber
         circuit."
    ::= { tmnxBsxAaSubEntry 10 }

tmnxBsxAaSubRemoteId             OBJECT-TYPE
    SYNTAX      TmnxBsxAaSubRemoteId
    MAX-ACCESS  read-only
    STATUS      current
    DESCRIPTION
        "The value of tmnxBsxAaSubRemoteId specifies the remote ID of a
         subscriber."
    ::= { tmnxBsxAaSubEntry 11 }

tmnxBsxAaSubMacAddr              OBJECT-TYPE
    SYNTAX      MacAddress
    MAX-ACCESS  read-only
    STATUS      current
    DESCRIPTION
        "The value of tmnxBsxAaSubMacAddr indicates the MAC address of the
         subscriber."
    ::= { tmnxBsxAaSubEntry 12 }

tmnxBsxAaSubSapPortId            OBJECT-TYPE
    SYNTAX      TmnxPortID
    MAX-ACCESS  read-only
    STATUS      current
    DESCRIPTION
        "The value of tmnxBsxAaSubSapPortId indicates the SAP port identifier
         of the subscriber."
    ::= { tmnxBsxAaSubEntry 13 }

tmnxBsxAaSubSapEncapVal          OBJECT-TYPE
    SYNTAX      TmnxEncapVal
    MAX-ACCESS  read-only
    STATUS      current
    DESCRIPTION
        "The value of tmnxBsxAaSubSapEncapVal indicates the SAP encapsulation
         value of the subscriber."
    ::= { tmnxBsxAaSubEntry 14 }

tmnxBsxAaSubQuarantined          OBJECT-TYPE
    SYNTAX      TruthValue
    MAX-ACCESS  read-only
    STATUS      current
    DESCRIPTION
        "The value of tmnxBsxAaSubQuarantined indicates if the subscriber is
         currently quarantined."
    ::= { tmnxBsxAaSubEntry 15 }

tmnxBsxAaSubImsi                 OBJECT-TYPE
    SYNTAX      TmnxMobImsiStr
    MAX-ACCESS  read-only
    STATUS      current
    DESCRIPTION
        "The value of tmnxBsxAaSubImsi indicates the International Mobile
         Subscriber Identity (IMSI) of the AA subscriber."
    ::= { tmnxBsxAaSubEntry 16 }

tmnxBsxAaSubImei                 OBJECT-TYPE
    SYNTAX      TmnxMobImei
    MAX-ACCESS  read-only
    STATUS      current
    DESCRIPTION
        "The value of tmnxBsxAaSubImei indicates the International Mobile
         Equipment Identity (IMEI) of the AA subscriber."
    ::= { tmnxBsxAaSubEntry 17 }

tmnxBsxAaSubMsisdn               OBJECT-TYPE
    SYNTAX      TmnxMobMsisdn
    MAX-ACCESS  read-only
    STATUS      current
    DESCRIPTION
        "The value of tmnxBsxAaSubMsisdn indicates the Mobile Subscriber
         Integrated Services Digital Network (MSISDN) number of the AA
         subscriber."
    ::= { tmnxBsxAaSubEntry 18 }

tmnxBsxAaSubApn                  OBJECT-TYPE
    SYNTAX      TmnxMobApnOrZero
    MAX-ACCESS  read-only
    STATUS      current
    DESCRIPTION
        "The value of tmnxBsxAaSubApn indicates the Access Point Name (APN) of
         the AA subscriber."
    ::= { tmnxBsxAaSubEntry 19 }

tmnxBsxAaSubUserLocation         OBJECT-TYPE
    SYNTAX      DisplayString
    MAX-ACCESS  read-only
    STATUS      current
    DESCRIPTION
        "The value of tmnxBsxAaSubUserLocation indicates the mobile User
         Location Information (ULI) of the AA subscriber."
    ::= { tmnxBsxAaSubEntry 20 }

tmnxBsxAaSubRatType              OBJECT-TYPE
    SYNTAX      TmnxBsxHttpEnrichRATType
    MAX-ACCESS  read-only
    STATUS      current
    DESCRIPTION
        "The value of tmnxBsxAaSubRatType indicates the Radio Access Technology
         (RAT) type of the AA subscriber."
    ::= { tmnxBsxAaSubEntry 21 }

tmnxBsxAaSubChargingId           OBJECT-TYPE
    SYNTAX      Unsigned32
    MAX-ACCESS  read-only
    STATUS      current
    DESCRIPTION
        "The value of tmnxBsxAaSubChargingId indicates the mobile charging ID
         of the AA subscriber."
    ::= { tmnxBsxAaSubEntry 22 }

tmnxBsxAaSubBillingType          OBJECT-TYPE
    SYNTAX      Unsigned32
    MAX-ACCESS  read-only
    STATUS      current
    DESCRIPTION
        "The value of tmnxBsxAaSubBillingType indicates the mobile billing type
         of the AA subscriber."
    ::= { tmnxBsxAaSubEntry 23 }

tmnxBsxAaSubPlmnId               OBJECT-TYPE
    SYNTAX      Unsigned32
    MAX-ACCESS  read-only
    STATUS      current
    DESCRIPTION
        "The value of tmnxBsxAaSubPlmnId indicates the Public Land Mobile
         Network (PLMN) of the AA subscriber."
    ::= { tmnxBsxAaSubEntry 24 }

tmnxBsxAaSubPdnGatewayAddr       OBJECT-TYPE
    SYNTAX      InetAddress (SIZE (0|4|16))
    MAX-ACCESS  read-only
    STATUS      current
    DESCRIPTION
        "The value of tmnxBsxAaSubPdnGatewayAddr indicates the address of the
         connected PDN gateway interface of the AA subscriber."
    ::= { tmnxBsxAaSubEntry 25 }

tmnxBsxAaSubPdnGatewayAddrType   OBJECT-TYPE
    SYNTAX      InetAddressType
    MAX-ACCESS  read-only
    STATUS      current
    DESCRIPTION
        "The value of tmnxBsxAaSubPdnGatewayAddrType indicates the type of
         tmnxBsxAaSubPdnGatewayAddr."
    ::= { tmnxBsxAaSubEntry 26 }

tmnxBsxAaSubTrafficDistByIp      OBJECT-TYPE
    SYNTAX      TruthValue
    MAX-ACCESS  read-only
    STATUS      current
    DESCRIPTION
        "The value of tmnxBsxAaSubTrafficDistByIp indicates if the subscriber
         traffic is distributed by Ip over all the active ISA/ESA-AA in the
         group, and hence all of  them are assigned to the subscriber."
    ::= { tmnxBsxAaSubEntry 29 }

tmnxBsxAaSubQci                  OBJECT-TYPE
    SYNTAX      Unsigned32
    MAX-ACCESS  read-only
    STATUS      current
    DESCRIPTION
        "The value of tmnxBsxAaSubQci indicates the QoS Class Identifier of the
         AA subscriber PDN session."
    ::= { tmnxBsxAaSubEntry 30 }

tmnxBsxAaSubSliceId              OBJECT-TYPE
    SYNTAX      Unsigned32
    MAX-ACCESS  read-only
    STATUS      current
    DESCRIPTION
        "The value of tmnxBsxAaSubSliceId indicates the mobile network Slice
         Identifier of the AA subscriber PDN session."
    ::= { tmnxBsxAaSubEntry 31 }

tmnxBsxAaSubMmeAmfAddr           OBJECT-TYPE
    SYNTAX      InetAddress (SIZE (0|4|16))
    MAX-ACCESS  read-only
    STATUS      current
    DESCRIPTION
        "The value of tmnxBsxAaSubMmeAmfAddr indicates the address of the MME
         (4G) or AMF (5G) for the AA subscriber PDN session."
    ::= { tmnxBsxAaSubEntry 32 }

tmnxBsxAaSubMmeAmfAddrType       OBJECT-TYPE
    SYNTAX      InetAddressType
    MAX-ACCESS  read-only
    STATUS      current
    DESCRIPTION
        "The value of tmnxBsxAaSubMmeAmfAddrType indicates the type of
         tmnxBsxAaSubMmeAmfAddr."
    ::= { tmnxBsxAaSubEntry 33 }

tmnxBsxAaSubPolicyRuleName       OBJECT-TYPE
    SYNTAX      TLNamedItemOrEmpty
    MAX-ACCESS  read-only
    STATUS      current
    DESCRIPTION
        "The value of tmnxBsxAaSubPolicyRuleName indicates the policy rule name
         associated with the subscriber."
    ::= { tmnxBsxAaSubEntry 34 }

tmnxBsxAaWap1xTable              OBJECT-TYPE
    SYNTAX      SEQUENCE OF TmnxBsxAaWap1xEntry
    MAX-ACCESS  not-accessible
    STATUS      current
    DESCRIPTION
        "The tmnxBsxAaWap1xTable contains configuration information for
         Application Assurance support of the Wireless Application Protocol
         (WAP) 1.X on a group-partition basis. The tmnxBsxAaWap1xTable augments
         the tmnxBsxAaGrpPartTable."
    ::= { tmnxBsxMdaObjs 12 }

tmnxBsxAaWap1xEntry              OBJECT-TYPE
    SYNTAX      TmnxBsxAaWap1xEntry
    MAX-ACCESS  not-accessible
    STATUS      current
    DESCRIPTION
        "An entry in the tmnxBsxAaWap1xTable containing the Wireless
         Application Protocol (WAP) 1.X configuration for a specific AA
         group-partition."
    AUGMENTS    { tmnxBsxAaGrpPartEntry }
    ::= { tmnxBsxAaWap1xTable 1 }

TmnxBsxAaWap1xEntry              ::= SEQUENCE
{
    tmnxBsxAaWap1xRowLastChange      TimeStamp,
    tmnxBsxAaWap1xAdminState         TmnxAdminState
}

tmnxBsxAaWap1xRowLastChange      OBJECT-TYPE
    SYNTAX      TimeStamp
    MAX-ACCESS  read-only
    STATUS      current
    DESCRIPTION
        "The value of tmnxBsxAaWap1xRowLastChange indicates the last time a
         successful set was performed on this row of the tmnxBsxAaWap1xTable."
    ::= { tmnxBsxAaWap1xEntry 1 }

tmnxBsxAaWap1xAdminState         OBJECT-TYPE
    SYNTAX      TmnxAdminState
    MAX-ACCESS  read-create
    STATUS      current
    DESCRIPTION
        "The value of tmnxBsxAaWap1xAdminState specifies the administrative
         state of Wireless Application Protocol (WAP) 1.X support for a
         group-partition. When the value is 'outOfService(3)' AA support for
         WAP 1.X is disabled. "
    DEFVAL      { outOfService }
    ::= { tmnxBsxAaWap1xEntry 2 }

tmnxBsxTetherTable               OBJECT-TYPE
    SYNTAX      SEQUENCE OF TmnxBsxTetherEntry
    MAX-ACCESS  not-accessible
    STATUS      current
    DESCRIPTION
        "The tmnxBsxTetherTable contains configuration information for
         Application Assurance support for Tethering Detection of mobile
         devices on a group-partition basis. The tmnxBsxTetherTable extends the
         tmnxBsxAaGrpPartTable when the tmnxBsxIsaAaGrpAaSubScale is set to
         'mobileGateway (2)'."
    ::= { tmnxBsxMdaObjs 13 }

tmnxBsxTetherEntry               OBJECT-TYPE
    SYNTAX      TmnxBsxTetherEntry
    MAX-ACCESS  not-accessible
    STATUS      current
    DESCRIPTION
        "An entry in the tmnxBsxTetherTable containing the Tethering Detection
         configuration for a specific AA group-partition."
    INDEX       { tmnxBsxAaGrpPartIndex }
    ::= { tmnxBsxTetherTable 1 }

TmnxBsxTetherEntry               ::= SEQUENCE
{
    tmnxBsxTetherRowLastChange       TimeStamp,
    tmnxBsxTetherAdminState          TmnxAdminState,
    tmnxBsxTetherTtlMonitorTcp       TmnxBsxTetherTtlMonitorLevel,
    tmnxBsxTetherTtlMonitorUdp       TmnxBsxTetherTtlMonitorLevel,
    tmnxBsxTetherTtlInvertMatch      TruthValue
}

tmnxBsxTetherRowLastChange       OBJECT-TYPE
    SYNTAX      TimeStamp
    MAX-ACCESS  read-only
    STATUS      current
    DESCRIPTION
        "The value of tmnxBsxTetherRowLastChange indicates the last time a
         successful set was performed on this row of the tmnxBsxTetherTable."
    ::= { tmnxBsxTetherEntry 1 }

tmnxBsxTetherAdminState          OBJECT-TYPE
    SYNTAX      TmnxAdminState
    MAX-ACCESS  read-create
    STATUS      current
    DESCRIPTION
        "The value of tmnxBsxTetherAdminState specifies the administrative
         state of Tethering Detection support for a group-partition. When the
         value is 'outOfService(3)' AA support for Tethering Detection is
         disabled."
    DEFVAL      { outOfService }
    ::= { tmnxBsxTetherEntry 2 }

tmnxBsxTetherTtlMonitorTcp       OBJECT-TYPE
    SYNTAX      TmnxBsxTetherTtlMonitorLevel
    MAX-ACCESS  read-create
    STATUS      current
    DESCRIPTION
        "The value of tmnxBsxTetherTtlMonitorTcp specifies the set of TCP
         protocols in which AA uses the TTL to help determine the tethering
         state of a flow or subscriber."
    DEFVAL      { standard }
    ::= { tmnxBsxTetherEntry 3 }

tmnxBsxTetherTtlMonitorUdp       OBJECT-TYPE
    SYNTAX      TmnxBsxTetherTtlMonitorLevel
    MAX-ACCESS  read-create
    STATUS      current
    DESCRIPTION
        "The value of tmnxBsxTetherTtlMonitorUdp specifies the set of UDP
         protocols in which AA uses the TTL to help determine the tethering
         state of a flow or subscriber. A value of 'standard' is strongly
         recommended."
    DEFVAL      { standard }
    ::= { tmnxBsxTetherEntry 4 }

tmnxBsxTetherTtlInvertMatch      OBJECT-TYPE
    SYNTAX      TruthValue
    MAX-ACCESS  read-create
    STATUS      current
    DESCRIPTION
        "The value of tmnxBsxTetherTtlInvertMatch specifies whether the TTL
         values configured in tmnxBsxTetherSingleDeviceExpTTL refer to
         the expected TTLs of NON-tethered subscribers or flows.  When true,
         AA will consider all subscribers and flows in the group-partition
         tethered except the ones with the expected TTL."
    DEFVAL      { false }
    ::= { tmnxBsxTetherEntry 5 }

tmnxBsxTetherSingleDeviceTable   OBJECT-TYPE
    SYNTAX      SEQUENCE OF TmnxBsxTetherSingleDeviceEntry
    MAX-ACCESS  not-accessible
    STATUS      current
    DESCRIPTION
        "The tmnxBsxTetherSingleDeviceTable contains configuration
         information for Application Assurance support for Tethering Detection
         of mobile devices on a group-partition basis.  The tmnxBsxTetherSingleDeviceTable
         extends the tmnxBsxAaGrpPartTable when the tmnxBsxIsaAaGrpAaSubScale is
         set to 'mobileGateway (2)'."
    ::= { tmnxBsxMdaObjs 14 }

tmnxBsxTetherSingleDeviceEntry   OBJECT-TYPE
    SYNTAX      TmnxBsxTetherSingleDeviceEntry
    MAX-ACCESS  not-accessible
    STATUS      current
    DESCRIPTION
        "An entry in the tmnxBsxTetherSingleDeviceEntry containing the
         Tethering Detection TTL configuration for a specific AA
         group-partition."
    INDEX       {
        tmnxBsxAaGrpPartIndex,
        tmnxBsxTetherSingleDeviceExpTTL
    }
    ::= { tmnxBsxTetherSingleDeviceTable 1 }

TmnxBsxTetherSingleDeviceEntry   ::= SEQUENCE
{
    tmnxBsxTetherSingleDeviceExpTTL  Unsigned32,
    tmnxBsxTetherSingleDevRowStatus  RowStatus
}

tmnxBsxTetherSingleDeviceExpTTL  OBJECT-TYPE
    SYNTAX      Unsigned32 (1..255)
    MAX-ACCESS  read-create
    STATUS      current
    DESCRIPTION
        "The value of tmnxBsxTetherSingleDeviceExpTTL specifies a value of
         expected TTL for TCP traffic from native devices.

         A maximum of 16 TTLs will be allowed to be configured for each
         group-partition."
    ::= { tmnxBsxTetherSingleDeviceEntry 1 }

tmnxBsxTetherSingleDevRowStatus  OBJECT-TYPE
    SYNTAX      RowStatus
    MAX-ACCESS  read-create
    STATUS      current
    DESCRIPTION
        "The value of tmnxBsxTetherSingleDevRowStatus indicates the row status.
         It allows entries to be created and deleted in the
         tmnxBsxTetherSingleDeviceTable."
    ::= { tmnxBsxTetherSingleDeviceEntry 2 }

tmnxBsxGrpMdaSharedResTable      OBJECT-TYPE
    SYNTAX      SEQUENCE OF TmnxBsxGrpMdaSharedResEntry
    MAX-ACCESS  not-accessible
    STATUS      current
    DESCRIPTION
        "The tmnxBsxGrpMdaSharedResTable contains shared resource used by each
         ISA-AA MDA configured within a group.

         Rows in this table are created and deleted by the system."
    ::= { tmnxBsxMdaObjs 15 }

tmnxBsxGrpMdaSharedResEntry      OBJECT-TYPE
    SYNTAX      TmnxBsxGrpMdaSharedResEntry
    MAX-ACCESS  not-accessible
    STATUS      current
    DESCRIPTION
        "Each tmnxBsxGrpMdaSharedResEntry indicates the shared resources usage
         on an ISA-AA MDA associated to a tmnxBsxIsaAaGrpEntry."
    AUGMENTS    { tmnxBsxGrpMdaEntry }
    ::= { tmnxBsxGrpMdaSharedResTable 1 }

TmnxBsxGrpMdaSharedResEntry      ::= SEQUENCE
{
    tmnxBsxGrpMdaAdFnMxConcSesTcpo   Counter32,
    tmnxBsxGrpMdaSRTcpAdvFnBufMem    Counter64,
    tmnxBsxGrpMdaSRTcpAdvFnBufUtil   Gauge32,
    tmnxBsxGrpMdaSRTcpAdvFnSessUtil  Gauge32,
    tmnxBsxGrpMdaSRGtpTunDbSize      Counter64,
    tmnxBsxGrpMdaSRGtpTunDbUtil      Gauge32,
    tmnxBsxGrpMdaSRWebServCacheUtil  Gauge32
}

tmnxBsxGrpMdaAdFnMxConcSesTcpo   OBJECT-TYPE
    SYNTAX      Counter32
    MAX-ACCESS  read-only
    STATUS      current
    DESCRIPTION
        "The value of tmnxBsxGrpMdaAdFnMxConcSesTcpo indicates the maximum
         number of concurrent sessions the TCP advanced functions can handle at
         any point in time for TCP Optimizer."
    ::= { tmnxBsxGrpMdaSharedResEntry 1 }

tmnxBsxGrpMdaSRTcpAdvFnBufMem    OBJECT-TYPE
    SYNTAX      Counter64
    UNITS       "megabytes"
    MAX-ACCESS  read-only
    STATUS      current
    DESCRIPTION
        "The value of tmnxBsxGrpMdaSRTcpAdvFnBufMem indicates the TCP buffer
         memory size of TCP advanced functions."
    ::= { tmnxBsxGrpMdaSharedResEntry 3 }

tmnxBsxGrpMdaSRTcpAdvFnBufUtil   OBJECT-TYPE
    SYNTAX      Gauge32 (0..100)
    UNITS       "percent"
    MAX-ACCESS  read-only
    STATUS      current
    DESCRIPTION
        "The value of tmnxBsxGrpMdaSRTcpAdvFnBufUtil indicates the TCP buffer
         utilization of TCP advanced functions."
    ::= { tmnxBsxGrpMdaSharedResEntry 4 }

tmnxBsxGrpMdaSRTcpAdvFnSessUtil  OBJECT-TYPE
    SYNTAX      Gauge32 (0..100)
    UNITS       "percent"
    MAX-ACCESS  read-only
    STATUS      current
    DESCRIPTION
        "The value of tmnxBsxGrpMdaSRTcpAdvFnSessUtil indicates the TCP session
         utilization of TCP advanced functions."
    ::= { tmnxBsxGrpMdaSharedResEntry 5 }

tmnxBsxGrpMdaSRGtpTunDbSize      OBJECT-TYPE
    SYNTAX      Counter64
    MAX-ACCESS  read-only
    STATUS      current
    DESCRIPTION
        "The value of tmnxBsxGrpMdaSRGtpTunDbSize indicates the number of
         entries in the shared resources GTP Tunnel Database."
    ::= { tmnxBsxGrpMdaSharedResEntry 6 }

tmnxBsxGrpMdaSRGtpTunDbUtil      OBJECT-TYPE
    SYNTAX      Gauge32 (0..100)
    UNITS       "percent"
    MAX-ACCESS  read-only
    STATUS      current
    DESCRIPTION
        "The value of tmnxBsxGrpMdaSRGtpTunDbUtil indicates the utilization
         level of the GTP Tunnel Database."
    ::= { tmnxBsxGrpMdaSharedResEntry 7 }

tmnxBsxGrpMdaSRWebServCacheUtil  OBJECT-TYPE
    SYNTAX      Gauge32 (0..100)
    UNITS       "percent"
    MAX-ACCESS  read-only
    STATUS      current
    DESCRIPTION
        "The value of tmnxBsxGrpMdaSRWebServCacheUtil indicates the utilization
         level of the Web Services cache."
    ::= { tmnxBsxGrpMdaSharedResEntry 9 }

tmnxBsxIsaAaGrpFlowAttrTable     OBJECT-TYPE
    SYNTAX      SEQUENCE OF TmnxBsxIsaAaGrpFlowAttrEntry
    MAX-ACCESS  not-accessible
    STATUS      current
    DESCRIPTION
        "The tmnxBsxIsaAaGrpFlowAttrTable contains an entry for each enabled
         flow attribute for each BSX Group in the system."
    ::= { tmnxBsxMdaObjs 16 }

tmnxBsxIsaAaGrpFlowAttrEntry     OBJECT-TYPE
    SYNTAX      TmnxBsxIsaAaGrpFlowAttrEntry
    MAX-ACCESS  not-accessible
    STATUS      current
    DESCRIPTION
        "Each tmnxBsxIsaAaGrpEntry indicates an enabled flow attribute for each
         BSX Group in the system."
    INDEX       {
        tmnxBsxIsaAaGroupIndex,
        IMPLIED tmnxBsxAqpFlowAttr
    }
    ::= { tmnxBsxIsaAaGrpFlowAttrTable 1 }

TmnxBsxIsaAaGrpFlowAttrEntry     ::= SEQUENCE
{
    tmnxBsxIsaAaGrpFlowAttrRowStatus RowStatus,
    tmnxBsxIsaAaGrpFlowAttrRowLastCh TimeStamp
}

tmnxBsxIsaAaGrpFlowAttrRowStatus OBJECT-TYPE
    SYNTAX      RowStatus
    MAX-ACCESS  read-create
    STATUS      current
    DESCRIPTION
        "The value of tmnxBsxIsaAaGrpFlowAttrRowStatus specifies
         the row status.  It allows entries to be created
         and deleted in the tmnxBsxIsaAaGrpFlowAttrTable.

         Rows are created by specifying the value of 'createAndGo (4)', and
         deleted by specifying the value of 'destroy (6)'."
    ::= { tmnxBsxIsaAaGrpFlowAttrEntry 1 }

tmnxBsxIsaAaGrpFlowAttrRowLastCh OBJECT-TYPE
    SYNTAX      TimeStamp
    MAX-ACCESS  read-only
    STATUS      current
    DESCRIPTION
        "The value of tmnxBsxIsaAaGrpFlowAttrRowLastCh indicates the last time,
         since system startup, a successful set was performed on this row of
         the tmnxBsxIsaAaGrpFlowAttrTable."
    ::= { tmnxBsxIsaAaGrpFlowAttrEntry 2 }

tmnxBsxFlowAttrTable             OBJECT-TYPE
    SYNTAX      SEQUENCE OF TmnxBsxFlowAttrEntry
    MAX-ACCESS  not-accessible
    STATUS      current
    DESCRIPTION
        "The tmnxBsxFlowAttrTable contains an entry for each flow attribute
         pre-configured by the agent. Rows in this table are created by the
         agent at initialization and cannot be created or destroyed by SNMP Get
         or Set requests."
    ::= { tmnxBsxMdaObjs 17 }

tmnxBsxFlowAttrEntry             OBJECT-TYPE
    SYNTAX      TmnxBsxFlowAttrEntry
    MAX-ACCESS  not-accessible
    STATUS      current
    DESCRIPTION
        "Each tmnxBsxFlowAttrEntry indicates a flow-attribute pre-configured by
         the agent."
    INDEX       { IMPLIED tmnxBsxFlowAttrName }
    ::= { tmnxBsxFlowAttrTable 1 }

TmnxBsxFlowAttrEntry             ::= SEQUENCE
{
    tmnxBsxFlowAttrName              TNamedItem,
    tmnxBsxFlowAttrId                Unsigned32,
    tmnxBsxFlowAttrDescr             TItemDescription,
    tmnxBsxFlowAttrComment           TNamedItemOrEmpty,
    tmnxBsxFlowAttrLastChange        TimeStamp
}

tmnxBsxFlowAttrName              OBJECT-TYPE
    SYNTAX      TNamedItem
    MAX-ACCESS  not-accessible
    STATUS      current
    DESCRIPTION
        "The value of tmnxBsxFlowAttrName indicates the name defined for the
         flow attribute."
    ::= { tmnxBsxFlowAttrEntry 1 }

tmnxBsxFlowAttrId                OBJECT-TYPE
    SYNTAX      Unsigned32
    MAX-ACCESS  read-only
    STATUS      current
    DESCRIPTION
        "The value of tmnxBsxFlowAttrId indicates the unique id of the flow
         attribute."
    ::= { tmnxBsxFlowAttrEntry 2 }

tmnxBsxFlowAttrDescr             OBJECT-TYPE
    SYNTAX      TItemDescription
    MAX-ACCESS  read-only
    STATUS      current
    DESCRIPTION
        "The value of tmnxBsxFlowAttrDescr indicates the description of the
         flow attribute."
    ::= { tmnxBsxFlowAttrEntry 3 }

tmnxBsxFlowAttrComment           OBJECT-TYPE
    SYNTAX      TNamedItemOrEmpty
    MAX-ACCESS  read-create
    STATUS      current
    DESCRIPTION
        "The value of tmnxBsxFlowAttrComment indicates a comment that is
         meaningful to the user."
    DEFVAL      { "" }
    ::= { tmnxBsxFlowAttrEntry 4 }

tmnxBsxFlowAttrLastChange        OBJECT-TYPE
    SYNTAX      TimeStamp
    MAX-ACCESS  read-only
    STATUS      current
    DESCRIPTION
        "The value of tmnxBsxFlowAttrLastChange indicates the last time, since
         system startup, a successful set was performed on this row."
    ::= { tmnxBsxFlowAttrEntry 5 }

tmnxBsxHttpEnrFieldTable         OBJECT-TYPE
    SYNTAX      SEQUENCE OF TmnxBsxHttpEnrFieldEntry
    MAX-ACCESS  not-accessible
    STATUS      current
    DESCRIPTION
        "The tmnxBsxHttpEnrFieldTable contains an entry for each HTTP enriched
         field pre-configured by the agent. Rows in this table are created by
         the agent at initialization and cannot be created or destroyed by SNMP
         Get or Set requests."
    ::= { tmnxBsxMdaObjs 18 }

tmnxBsxHttpEnrFieldEntry         OBJECT-TYPE
    SYNTAX      TmnxBsxHttpEnrFieldEntry
    MAX-ACCESS  not-accessible
    STATUS      current
    DESCRIPTION
        "Each tmnxBsxHttpEnrFieldEntry indicates an HTTP enriched field
         pre-configured by the agent."
    INDEX       { IMPLIED tmnxBsxHttpEnrFieldName }
    ::= { tmnxBsxHttpEnrFieldTable 1 }

TmnxBsxHttpEnrFieldEntry         ::= SEQUENCE
{
    tmnxBsxHttpEnrFieldName          TNamedItem,
    tmnxBsxHttpEnrFieldId            Unsigned32,
    tmnxBsxHttpEnrFieldAntiSpoof     TruthValue,
    tmnxBsxHttpEnrFieldAntiSpoofXCli TruthValue,
    tmnxBsxHttpEnrFieldTls           TruthValue,
    tmnxBsxHttpEnrFieldSubscale      TmnxBsxCflowdSubscaleType,
    tmnxBsxHttpEnrFieldDescr         TItemDescription,
    tmnxBsxHttpEnrFieldComment       TNamedItemOrEmpty,
    tmnxBsxHttpEnrFieldLastChange    TimeStamp
}

tmnxBsxHttpEnrFieldName          OBJECT-TYPE
    SYNTAX      TNamedItem
    MAX-ACCESS  not-accessible
    STATUS      current
    DESCRIPTION
        "The value of tmnxBsxHttpEnrFieldName indicates the name defined for
         the HTTP enriched field."
    ::= { tmnxBsxHttpEnrFieldEntry 1 }

tmnxBsxHttpEnrFieldId            OBJECT-TYPE
    SYNTAX      Unsigned32
    MAX-ACCESS  read-only
    STATUS      current
    DESCRIPTION
        "The value of tmnxBsxHttpEnrFieldId indicates the unique id of the HTTP
         enriched field."
    ::= { tmnxBsxHttpEnrFieldEntry 2 }

tmnxBsxHttpEnrFieldAntiSpoof     OBJECT-TYPE
    SYNTAX      TruthValue
    MAX-ACCESS  read-only
    STATUS      current
    DESCRIPTION
        "The value of tmnxBsxHttpEnrFieldAntiSpoof indicates whether the
         http-enrich field supports antispoof."
    ::= { tmnxBsxHttpEnrFieldEntry 3 }

tmnxBsxHttpEnrFieldAntiSpoofXCli OBJECT-TYPE
    SYNTAX      TruthValue
    MAX-ACCESS  read-only
    STATUS      current
    DESCRIPTION
        "The value of tmnxBsxHttpEnrFieldAntiSpoofXCli indicates whether the
         http-enrich field supports antispoof of x-calling-line-id string."
    ::= { tmnxBsxHttpEnrFieldEntry 4 }

tmnxBsxHttpEnrFieldTls           OBJECT-TYPE
    SYNTAX      TruthValue
    MAX-ACCESS  read-only
    STATUS      current
    DESCRIPTION
        "The value of tmnxBsxHttpEnrFieldTls indicates whether the http-enrich
         field has a tls-extension for enrichment of HTTPS."
    ::= { tmnxBsxHttpEnrFieldEntry 5 }

tmnxBsxHttpEnrFieldSubscale      OBJECT-TYPE
    SYNTAX      TmnxBsxCflowdSubscaleType
    MAX-ACCESS  read-only
    STATUS      current
    DESCRIPTION
        "The value of tmnxBsxHttpEnrFieldSubscale indicates the aa group
         subscale in which this field is applicable."
    ::= { tmnxBsxHttpEnrFieldEntry 6 }

tmnxBsxHttpEnrFieldDescr         OBJECT-TYPE
    SYNTAX      TItemDescription
    MAX-ACCESS  read-only
    STATUS      current
    DESCRIPTION
        "The value of tmnxBsxHttpEnrFieldDescr indicates the description of the
         HTTP enriched field."
    ::= { tmnxBsxHttpEnrFieldEntry 7 }

tmnxBsxHttpEnrFieldComment       OBJECT-TYPE
    SYNTAX      TNamedItemOrEmpty
    MAX-ACCESS  read-create
    STATUS      current
    DESCRIPTION
        "The value of tmnxBsxHttpEnrFieldComment indicates a comment that is
         meaningful to the user."
    DEFVAL      { "" }
    ::= { tmnxBsxHttpEnrFieldEntry 8 }

tmnxBsxHttpEnrFieldLastChange    OBJECT-TYPE
    SYNTAX      TimeStamp
    MAX-ACCESS  read-only
    STATUS      current
    DESCRIPTION
        "The value of tmnxBsxHttpEnrFieldLastChange indicates the last time,
         since system startup, a successful set was performed on this row."
    ::= { tmnxBsxHttpEnrFieldEntry 9 }

tmnxBsxHttpRedirErrorCodeTable   OBJECT-TYPE
    SYNTAX      SEQUENCE OF TmnxBsxHttpRedirErrorCodeEntry
    MAX-ACCESS  not-accessible
    STATUS      current
    DESCRIPTION
        "The tmnxBsxHttpRedirErrorCodeTable contains an entry for each http
         error redirect code pre-configured by the agent. Rows in this table
         are created by the agent at initialization and cannot be created or
         destroyed by SNMP Get or Set requests."
    ::= { tmnxBsxMdaObjs 19 }

tmnxBsxHttpRedirErrorCodeEntry   OBJECT-TYPE
    SYNTAX      TmnxBsxHttpRedirErrorCodeEntry
    MAX-ACCESS  not-accessible
    STATUS      current
    DESCRIPTION
        "Each tmnxBsxHttpRedirErrorCodeEntry indicates an HTTP error redirect
         code pre-configured by the agent."
    INDEX       { tmnxBsxHttpRedirErrorCode }
    ::= { tmnxBsxHttpRedirErrorCodeTable 1 }

TmnxBsxHttpRedirErrorCodeEntry   ::= SEQUENCE
{
    tmnxBsxHttpRedirErrorCode        Unsigned32,
    tmnxBsxHttpRedirErrCodeDescr     TItemDescription,
    tmnxBsxHttpRedirErrCodeMsgSize   Unsigned32,
    tmnxBsxHttpRedirErrCodeComment   TNamedItemOrEmpty,
    tmnxBsxHttpRedirErrCodeLastChg   TimeStamp
}

tmnxBsxHttpRedirErrorCode        OBJECT-TYPE
    SYNTAX      Unsigned32 (400..999)
    MAX-ACCESS  not-accessible
    STATUS      current
    DESCRIPTION
        "The value of tmnxBsxHttpRedirErrorCode indicates the HTTP error
         redirect code."
    ::= { tmnxBsxHttpRedirErrorCodeEntry 1 }

tmnxBsxHttpRedirErrCodeDescr     OBJECT-TYPE
    SYNTAX      TItemDescription
    MAX-ACCESS  read-only
    STATUS      current
    DESCRIPTION
        "The value of tmnxBsxHttpRedirErrCodeDescr indicates the description of
         the HTTP error redirect code."
    ::= { tmnxBsxHttpRedirErrorCodeEntry 2 }

tmnxBsxHttpRedirErrCodeMsgSize   OBJECT-TYPE
    SYNTAX      Unsigned32
    MAX-ACCESS  read-only
    STATUS      current
    DESCRIPTION
        "The value of tmnxBsxHttpRedirErrCodeMsgSize indicates the
         http-error-redirect default maximum message size for this error-code."
    ::= { tmnxBsxHttpRedirErrorCodeEntry 3 }

tmnxBsxHttpRedirErrCodeComment   OBJECT-TYPE
    SYNTAX      TNamedItemOrEmpty
    MAX-ACCESS  read-create
    STATUS      current
    DESCRIPTION
        "The value of tmnxBsxHttpRedirErrCodeComment indicates a comment that
         is meaningful to the user."
    DEFVAL      { "" }
    ::= { tmnxBsxHttpRedirErrorCodeEntry 4 }

tmnxBsxHttpRedirErrCodeLastChg   OBJECT-TYPE
    SYNTAX      TimeStamp
    MAX-ACCESS  read-only
    STATUS      current
    DESCRIPTION
        "The value of tmnxBsxHttpRedirErrCodeLastChg indicates the last time,
         since system startup, a successful set was performed on this row."
    ::= { tmnxBsxHttpRedirErrorCodeEntry 5 }

tmnxBsxHttpErrRedirTmplTable     OBJECT-TYPE
    SYNTAX      SEQUENCE OF TmnxBsxHttpErrRedirTmplEntry
    MAX-ACCESS  not-accessible
    STATUS      current
    DESCRIPTION
        "The tmnxBsxHttpErrRedirTmplTable contains an entry for each http error
         redirect template pre-configured by the agent. Rows in this table are
         created by the agent at initialization and cannot be created or
         destroyed by SNMP Get or Set requests."
    ::= { tmnxBsxMdaObjs 20 }

tmnxBsxHttpErrRedirTmplEntry     OBJECT-TYPE
    SYNTAX      TmnxBsxHttpErrRedirTmplEntry
    MAX-ACCESS  not-accessible
    STATUS      current
    DESCRIPTION
        "Each tmnxBsxHttpErrRedirTmplEntry indicates an HTTP error redirect
         template pre-configured by the agent."
    INDEX       { tmnxBsxHttpErrRedirTmplNum }
    ::= { tmnxBsxHttpErrRedirTmplTable 1 }

TmnxBsxHttpErrRedirTmplEntry     ::= SEQUENCE
{
    tmnxBsxHttpErrRedirTmplNum       Unsigned32,
    tmnxBsxHttpErrRedirTmplDescr     TItemDescription,
    tmnxBsxHttpErrRedirTmplComment   TNamedItemOrEmpty,
    tmnxBsxHttpErrRedirTmplLastChg   TimeStamp
}

tmnxBsxHttpErrRedirTmplNum       OBJECT-TYPE
    SYNTAX      Unsigned32
    MAX-ACCESS  not-accessible
    STATUS      current
    DESCRIPTION
        "The value of tmnxBsxHttpErrRedirTmplNum indicates the HTTP error
         redirect template number."
    ::= { tmnxBsxHttpErrRedirTmplEntry 1 }

tmnxBsxHttpErrRedirTmplDescr     OBJECT-TYPE
    SYNTAX      TItemDescription
    MAX-ACCESS  read-only
    STATUS      current
    DESCRIPTION
        "The value of tmnxBsxHttpErrRedirTmplDescr indicates the description of
         the HTTP error redirect template."
    ::= { tmnxBsxHttpErrRedirTmplEntry 2 }

tmnxBsxHttpErrRedirTmplComment   OBJECT-TYPE
    SYNTAX      TNamedItemOrEmpty
    MAX-ACCESS  read-create
    STATUS      current
    DESCRIPTION
        "The value of tmnxBsxHttpErrRedirTmplComment indicates a comment that
         is meaningful to the user."
    DEFVAL      { "" }
    ::= { tmnxBsxHttpErrRedirTmplEntry 3 }

tmnxBsxHttpErrRedirTmplLastChg   OBJECT-TYPE
    SYNTAX      TimeStamp
    MAX-ACCESS  read-only
    STATUS      current
    DESCRIPTION
        "The value of tmnxBsxHttpErrRedirTmplLastChg indicates the last time,
         since system startup, a successful set was performed on this row."
    ::= { tmnxBsxHttpErrRedirTmplEntry 4 }

tmnxBsxHttpRedirTmplTable        OBJECT-TYPE
    SYNTAX      SEQUENCE OF TmnxBsxHttpRedirTmplEntry
    MAX-ACCESS  not-accessible
    STATUS      current
    DESCRIPTION
        "The tmnxBsxHttpRedirTmplTable contains an entry for each http redirect
         template pre-configured by the agent. Rows in this table are created
         by the agent at initialization and cannot be created or destroyed by
         SNMP Get or Set requests."
    ::= { tmnxBsxMdaObjs 21 }

tmnxBsxHttpRedirTmplEntry        OBJECT-TYPE
    SYNTAX      TmnxBsxHttpRedirTmplEntry
    MAX-ACCESS  not-accessible
    STATUS      current
    DESCRIPTION
        "Each tmnxBsxHttpRedirTmplEntry indicates an HTTP redirect template
         pre-configured by the agent."
    INDEX       { tmnxBsxHttpRedirTmplNum }
    ::= { tmnxBsxHttpRedirTmplTable 1 }

TmnxBsxHttpRedirTmplEntry        ::= SEQUENCE
{
    tmnxBsxHttpRedirTmplNum          Unsigned32,
    tmnxBsxHttpRedirTmplDescr        TItemDescription,
    tmnxBsxHttpRedirTmplMacro        TruthValue,
    tmnxBsxHttpRedirTmplComment      TNamedItemOrEmpty,
    tmnxBsxHttpRedirTmplLastChg      TimeStamp
}

tmnxBsxHttpRedirTmplNum          OBJECT-TYPE
    SYNTAX      Unsigned32
    MAX-ACCESS  not-accessible
    STATUS      current
    DESCRIPTION
        "The value of tmnxBsxHttpRedirTmplNum indicates the HTTP redirect
         template number."
    ::= { tmnxBsxHttpRedirTmplEntry 1 }

tmnxBsxHttpRedirTmplDescr        OBJECT-TYPE
    SYNTAX      TItemDescription
    MAX-ACCESS  read-only
    STATUS      current
    DESCRIPTION
        "The value of tmnxBsxHttpRedirTmplDescr indicates the description of
         the HTTP redirect template."
    ::= { tmnxBsxHttpRedirTmplEntry 2 }

tmnxBsxHttpRedirTmplMacro        OBJECT-TYPE
    SYNTAX      TruthValue
    MAX-ACCESS  read-only
    STATUS      current
    DESCRIPTION
        "The value of tmnxBsxHttpRedirTmplMacro indicates whether the
         http-redirect template supports macro substitution."
    ::= { tmnxBsxHttpRedirTmplEntry 3 }

tmnxBsxHttpRedirTmplComment      OBJECT-TYPE
    SYNTAX      TNamedItemOrEmpty
    MAX-ACCESS  read-create
    STATUS      current
    DESCRIPTION
        "The value of tmnxBsxHttpRedirTmplComment indicates a comment that is
         meaningful to the user."
    DEFVAL      { "" }
    ::= { tmnxBsxHttpRedirTmplEntry 4 }

tmnxBsxHttpRedirTmplLastChg      OBJECT-TYPE
    SYNTAX      TimeStamp
    MAX-ACCESS  read-only
    STATUS      current
    DESCRIPTION
        "The value of tmnxBsxHttpRedirTmplLastChg indicates the last time,
         since system startup, a successful set was performed on this row."
    ::= { tmnxBsxHttpRedirTmplEntry 5 }

tmnxBsxHttpNotifyTmplTable       OBJECT-TYPE
    SYNTAX      SEQUENCE OF TmnxBsxHttpNotifyTmplEntry
    MAX-ACCESS  not-accessible
    STATUS      current
    DESCRIPTION
        "The tmnxBsxHttpNotifyTmplTable contains an entry for each http
         notification template pre-configured by the agent. Rows in this table
         are created by the agent at initialization and cannot be created or
         destroyed by SNMP Get or Set requests."
    ::= { tmnxBsxMdaObjs 22 }

tmnxBsxHttpNotifyTmplEntry       OBJECT-TYPE
    SYNTAX      TmnxBsxHttpNotifyTmplEntry
    MAX-ACCESS  not-accessible
    STATUS      current
    DESCRIPTION
        "Each tmnxBsxHttpNotifyTmplEntry indicates an HTTP notification
         template pre-configured by the agent."
    INDEX       { tmnxBsxHttpNotifyTmplNum }
    ::= { tmnxBsxHttpNotifyTmplTable 1 }

TmnxBsxHttpNotifyTmplEntry       ::= SEQUENCE
{
    tmnxBsxHttpNotifyTmplNum         Unsigned32,
    tmnxBsxHttpNotifyTmplDescr       TItemDescription,
    tmnxBsxHttpNotifyTmplComment     TNamedItemOrEmpty,
    tmnxBsxHttpNotifyTmplLastChg     TimeStamp
}

tmnxBsxHttpNotifyTmplNum         OBJECT-TYPE
    SYNTAX      Unsigned32
    MAX-ACCESS  not-accessible
    STATUS      current
    DESCRIPTION
        "The value of tmnxBsxHttpNotifyTmplNum indicates the HTTP notification
         template number."
    ::= { tmnxBsxHttpNotifyTmplEntry 1 }

tmnxBsxHttpNotifyTmplDescr       OBJECT-TYPE
    SYNTAX      TItemDescription
    MAX-ACCESS  read-only
    STATUS      current
    DESCRIPTION
        "The value of tmnxBsxHttpNotifyTmplDescr indicates the description of
         the HTTP notification template."
    ::= { tmnxBsxHttpNotifyTmplEntry 2 }

tmnxBsxHttpNotifyTmplComment     OBJECT-TYPE
    SYNTAX      TNamedItemOrEmpty
    MAX-ACCESS  read-create
    STATUS      current
    DESCRIPTION
        "The value of tmnxBsxHttpNotifyTmplComment indicates a comment that is
         meaningful to the user."
    DEFVAL      { "" }
    ::= { tmnxBsxHttpNotifyTmplEntry 3 }

tmnxBsxHttpNotifyTmplLastChg     OBJECT-TYPE
    SYNTAX      TimeStamp
    MAX-ACCESS  read-only
    STATUS      current
    DESCRIPTION
        "The value of tmnxBsxHttpNotifyTmplLastChg indicates the last time,
         since system startup, a successful set was performed on this row."
    ::= { tmnxBsxHttpNotifyTmplEntry 4 }

tmnxBsxCflowdRecordFieldTable    OBJECT-TYPE
    SYNTAX      SEQUENCE OF TmnxBsxCflowdRecordFieldEntry
    MAX-ACCESS  not-accessible
    STATUS      current
    DESCRIPTION
        "The tmnxBsxCflowdRecordFieldTable contains an entry for each cflowd
         record field pre-configured by the agent. Rows in this table are
         created by the agent at initialization and cannot be created or
         destroyed by SNMP Get or Set requests."
    ::= { tmnxBsxMdaObjs 23 }

tmnxBsxCflowdRecordFieldEntry    OBJECT-TYPE
    SYNTAX      TmnxBsxCflowdRecordFieldEntry
    MAX-ACCESS  not-accessible
    STATUS      current
    DESCRIPTION
        "Each tmnxBsxCflowdRecordFieldEntry indicates a cflowd record field
         pre-configured by the agent."
    INDEX       { IMPLIED tmnxBsxCflowdRecordFieldName }
    ::= { tmnxBsxCflowdRecordFieldTable 1 }

TmnxBsxCflowdRecordFieldEntry    ::= SEQUENCE
{
    tmnxBsxCflowdRecordFieldName     TNamedItem,
    tmnxBsxCflowdRecordFieldId       Unsigned32,
    tmnxBsxCflowdRecordFieldSize     Unsigned32,
    tmnxBsxCflowdRecFieldSubscale    TmnxBsxCflowdSubscaleType,
    tmnxBsxCflowdRecFieldEncryption  TmnxBsxCflowdEncryption,
    tmnxBsxCflowdRecFieldEncryptGrp  TmnxBsxCflowdEncrGrpType,
    tmnxBsxCflowdRecFieldExportOpt   TmnxBsxCflowdExpFieldExport,
    tmnxBsxCflowdRecFieldExportMand  TmnxBsxCflowdExpFieldExport,
    tmnxBsxCflowdRecordFieldDescr    TItemDescription,
    tmnxBsxCflowdRecFieldComment     TNamedItemOrEmpty,
    tmnxBsxCflowdRecFieldLastChg     TimeStamp
}

tmnxBsxCflowdRecordFieldName     OBJECT-TYPE
    SYNTAX      TNamedItem
    MAX-ACCESS  not-accessible
    STATUS      current
    DESCRIPTION
        "The value of tmnxBsxCflowdRecordFieldName indicates the cflowd record
         field name."
    ::= { tmnxBsxCflowdRecordFieldEntry 1 }

tmnxBsxCflowdRecordFieldId       OBJECT-TYPE
    SYNTAX      Unsigned32
    MAX-ACCESS  read-only
    STATUS      current
    DESCRIPTION
        "The value of tmnxBsxCflowdRecordFieldId indicates the unique id of the
         cflowd record field."
    ::= { tmnxBsxCflowdRecordFieldEntry 2 }

tmnxBsxCflowdRecordFieldSize     OBJECT-TYPE
    SYNTAX      Unsigned32
    MAX-ACCESS  read-only
    STATUS      current
    DESCRIPTION
        "The value of tmnxBsxCflowdRecordFieldSize indicates the size (in
         bytes) of the cflowd record field."
    ::= { tmnxBsxCflowdRecordFieldEntry 3 }

tmnxBsxCflowdRecFieldSubscale    OBJECT-TYPE
    SYNTAX      TmnxBsxCflowdSubscaleType
    MAX-ACCESS  read-only
    STATUS      current
    DESCRIPTION
        "The value of tmnxBsxCflowdRecFieldSubscale indicates the subscales in
         which this field is applicable."
    ::= { tmnxBsxCflowdRecordFieldEntry 4 }

tmnxBsxCflowdRecFieldEncryption  OBJECT-TYPE
    SYNTAX      TmnxBsxCflowdEncryption
    MAX-ACCESS  read-only
    STATUS      current
    DESCRIPTION
        "The value of tmnxBsxCflowdRecFieldEncryption indicates the encryption
         types on which this cflowd record field can be applied."
    ::= { tmnxBsxCflowdRecordFieldEntry 5 }

tmnxBsxCflowdRecFieldEncryptGrp  OBJECT-TYPE
    SYNTAX      TmnxBsxCflowdEncrGrpType
    MAX-ACCESS  read-only
    STATUS      current
    DESCRIPTION
        "The value of tmnxBsxCflowdRecFieldEncryptGrp indicates the cflowd
         record field encryption group."
    ::= { tmnxBsxCflowdRecordFieldEntry 6 }

tmnxBsxCflowdRecFieldExportOpt   OBJECT-TYPE
    SYNTAX      TmnxBsxCflowdExpFieldExport
    MAX-ACCESS  read-only
    STATUS      current
    DESCRIPTION
        "The value of tmnxBsxCflowdRecFieldExportOpt indicates the the template
         types in which this field is optional."
    ::= { tmnxBsxCflowdRecordFieldEntry 7 }

tmnxBsxCflowdRecFieldExportMand  OBJECT-TYPE
    SYNTAX      TmnxBsxCflowdExpFieldExport
    MAX-ACCESS  read-only
    STATUS      current
    DESCRIPTION
        "The value of tmnxBsxCflowdRecFieldExportMand indicates the template
         types in which this cflowd record field is mandatory."
    ::= { tmnxBsxCflowdRecordFieldEntry 8 }

tmnxBsxCflowdRecordFieldDescr    OBJECT-TYPE
    SYNTAX      TItemDescription
    MAX-ACCESS  read-only
    STATUS      current
    DESCRIPTION
        "The value of tmnxBsxCflowdRecordFieldDescr indicates the description
         of the cflowd record field."
    ::= { tmnxBsxCflowdRecordFieldEntry 9 }

tmnxBsxCflowdRecFieldComment     OBJECT-TYPE
    SYNTAX      TNamedItemOrEmpty
    MAX-ACCESS  read-create
    STATUS      current
    DESCRIPTION
        "The value of tmnxBsxCflowdRecFieldComment indicates a comment that is
         meaningful to the user."
    DEFVAL      { "" }
    ::= { tmnxBsxCflowdRecordFieldEntry 10 }

tmnxBsxCflowdRecFieldLastChg     OBJECT-TYPE
    SYNTAX      TimeStamp
    MAX-ACCESS  read-only
    STATUS      current
    DESCRIPTION
        "The value of tmnxBsxCflowdRecFieldLastChg indicates the last time,
         since system startup, a successful set was performed on this row."
    ::= { tmnxBsxCflowdRecordFieldEntry 11 }

tmnxBsxGrpTrafficStatsTable      OBJECT-TYPE
    SYNTAX      SEQUENCE OF TmnxBsxGrpTrafficStatsEntry
    MAX-ACCESS  not-accessible
    STATUS      current
    DESCRIPTION
        "The tmnxBsxGrpTrafficStatsTable contains an entry for each ISA-AA MDA
         and Group in the system. Each row contains traffic statistics per
         group for an ISA-AA MDA uniquely identified by the tmnxChassisIndex,
         tmnxBsxCardSlotEsaId, and the tmnxBsxMdaSlotEsaVmId."
    ::= { tmnxBsxMdaObjs 25 }

tmnxBsxGrpTrafficStatsEntry      OBJECT-TYPE
    SYNTAX      TmnxBsxGrpTrafficStatsEntry
    MAX-ACCESS  not-accessible
    STATUS      current
    DESCRIPTION
        "Each tmnxBsxGrpTrafficStatsEntry contains traffic statistics for a
         particular group and ISA-AA MDA.

         An index with a valid tmnxBsxIsaAaGroupIndex, tmnxChassisIndex set to
         one, and a zero value for each of the
         tmnxBsxCardSlotEsaId/tmnxBsxMdaSlotEsaVmId indices will return the
         summarized per group traffic statistics.

         Rows in this table are created by the agent at initialization and
         cannot be created or destroyed by SNMP Set requests."
    INDEX       {
        tmnxBsxIsaAaGroupIndex,
        tmnxChassisIndex,
        tmnxBsxCardSlotEsaId,
        tmnxBsxMdaSlotEsaVmId
    }
    ::= { tmnxBsxGrpTrafficStatsTable 1 }

TmnxBsxGrpTrafficStatsEntry      ::= SEQUENCE
{
    tmnxBsxGrpStsTcpPktFrSub         Counter64,
    tmnxBsxGrpStsTcpOctFrSub         Counter64,
    tmnxBsxGrpStsTcpRetPktFrSub      Counter64,
    tmnxBsxGrpStsTcpRetOctFrSub      Counter64,
    tmnxBsxGrpStsTcpPktToSub         Counter64,
    tmnxBsxGrpStsTcpOctToSub         Counter64,
    tmnxBsxGrpStsTcpRetPktToSub      Counter64,
    tmnxBsxGrpStsTcpRetOctToSub      Counter64
}

tmnxBsxGrpStsTcpPktFrSub         OBJECT-TYPE
    SYNTAX      Counter64
    UNITS       "packets"
    MAX-ACCESS  read-only
    STATUS      current
    DESCRIPTION
        "The value of tmnxBsxGrpStsTcpPktFrSub indicates the number of received
         TCP packets in the subscriber-to-network direction and is only
         collected when TCP retransmissions are being monitored."
    ::= { tmnxBsxGrpTrafficStatsEntry 1 }

tmnxBsxGrpStsTcpOctFrSub         OBJECT-TYPE
    SYNTAX      Counter64
    UNITS       "octets"
    MAX-ACCESS  read-only
    STATUS      current
    DESCRIPTION
        "The value of tmnxBsxGrpStsTcpOctFrSub indicates the number of received
         TCP octets in the subscriber-to-network direction and is only
         collected when TCP retransmissions are being monitored."
    ::= { tmnxBsxGrpTrafficStatsEntry 2 }

tmnxBsxGrpStsTcpRetPktFrSub      OBJECT-TYPE
    SYNTAX      Counter64
    UNITS       "packets"
    MAX-ACCESS  read-only
    STATUS      current
    DESCRIPTION
        "The value of tmnxBsxGrpStsTcpRetPktFrSub indicates the number of
         received TCP retransmitted packets in the subscriber-to-network
         direction and is only collected when TCP retransmissions are being
         monitored."
    ::= { tmnxBsxGrpTrafficStatsEntry 3 }

tmnxBsxGrpStsTcpRetOctFrSub      OBJECT-TYPE
    SYNTAX      Counter64
    UNITS       "octets"
    MAX-ACCESS  read-only
    STATUS      current
    DESCRIPTION
        "The value of tmnxBsxGrpStsTcpRetOctFrSub indicates the number of
         received TCP retransmitted octets in the subscriber-to-network
         direction and is only collected when TCP retransmissions are being
         monitored."
    ::= { tmnxBsxGrpTrafficStatsEntry 4 }

tmnxBsxGrpStsTcpPktToSub         OBJECT-TYPE
    SYNTAX      Counter64
    UNITS       "packets"
    MAX-ACCESS  read-only
    STATUS      current
    DESCRIPTION
        "The value of tmnxBsxGrpStsTcpPktToSub indicates the number of received
         TCP packets in the network-to-subscriber direction and is only
         collected when TCP retransmissions are being monitored."
    ::= { tmnxBsxGrpTrafficStatsEntry 5 }

tmnxBsxGrpStsTcpOctToSub         OBJECT-TYPE
    SYNTAX      Counter64
    UNITS       "octets"
    MAX-ACCESS  read-only
    STATUS      current
    DESCRIPTION
        "The value of tmnxBsxGrpStsTcpOctToSub indicates the number of received
         TCP octets in the network-to-subscriber direction and is only
         collected when TCP retransmissions are being monitored."
    ::= { tmnxBsxGrpTrafficStatsEntry 6 }

tmnxBsxGrpStsTcpRetPktToSub      OBJECT-TYPE
    SYNTAX      Counter64
    UNITS       "packets"
    MAX-ACCESS  read-only
    STATUS      current
    DESCRIPTION
        "The value of tmnxBsxGrpStsTcpRetPktToSub indicates the number of
         received TCP retransmitted packets in the network-to-subscriber
         direction and is only collected when TCP retransmissions are being
         monitored."
    ::= { tmnxBsxGrpTrafficStatsEntry 7 }

tmnxBsxGrpStsTcpRetOctToSub      OBJECT-TYPE
    SYNTAX      Counter64
    UNITS       "octets"
    MAX-ACCESS  read-only
    STATUS      current
    DESCRIPTION
        "The value of tmnxBsxGrpStsTcpRetOctToSub indicates the number of
         received TCP retransmitted octets in the network-to-subscriber
         direction and is only collected when TCP retransmissions are being
         monitored."
    ::= { tmnxBsxGrpTrafficStatsEntry 8 }

tmnxBsxPolicyObjs                OBJECT IDENTIFIER ::= { tmnxBsxObjs 2 }

tmnxBsxProtTable                 OBJECT-TYPE
    SYNTAX      SEQUENCE OF TmnxBsxProtEntry
    MAX-ACCESS  not-accessible
    STATUS      current
    DESCRIPTION
        "The tmnxBsxProtTable contains an entry for each protocol signature
         pre-configured by the agent. Rows in this table are created by the
         agent at initialization and cannot be created or destroyed by SNMP Get
         or Set requests."
    ::= { tmnxBsxPolicyObjs 1 }

tmnxBsxProtEntry                 OBJECT-TYPE
    SYNTAX      TmnxBsxProtEntry
    MAX-ACCESS  not-accessible
    STATUS      current
    DESCRIPTION
        "Each tmnxBsxProtEntry indicates an protocol pre-configured by the
         agent."
    INDEX       { IMPLIED tmnxBsxProtName }
    ::= { tmnxBsxProtTable 1 }

TmnxBsxProtEntry                 ::= SEQUENCE
{
    tmnxBsxProtName                  TNamedItem,
    tmnxBsxProtDescription           TItemDescription,
    tmnxBsxProtParentName            TNamedItemOrEmpty,
    tmnxBsxProtAdminState            TmnxAdminState,
    tmnxBsxProtObsolete              TruthValue,
    tmnxBsxProtRowLastChange         TimeStamp
}

tmnxBsxProtName                  OBJECT-TYPE
    SYNTAX      TNamedItem
    MAX-ACCESS  not-accessible
    STATUS      current
    DESCRIPTION
        "The value of tmnxBsxProtName indicates the name defined for the
         protocol."
    ::= { tmnxBsxProtEntry 1 }

tmnxBsxProtDescription           OBJECT-TYPE
    SYNTAX      TItemDescription
    MAX-ACCESS  read-only
    STATUS      current
    DESCRIPTION
        "The value of tmnxBsxProtDescription indicates the description of the
         protocol."
    ::= { tmnxBsxProtEntry 2 }

tmnxBsxProtParentName            OBJECT-TYPE
    SYNTAX      TNamedItemOrEmpty
    MAX-ACCESS  read-only
    STATUS      current
    DESCRIPTION
        "The value of tmnxBsxProtParentName indicates the parent name of the
         protocol."
    DEFVAL      { "" }
    ::= { tmnxBsxProtEntry 3 }

tmnxBsxProtAdminState            OBJECT-TYPE
    SYNTAX      TmnxAdminState
    MAX-ACCESS  read-create
    STATUS      current
    DESCRIPTION
        "The value of tmnxBsxProtAdminState specifies the administrative state
         of the protocol. When the admin state is set to 'outOfService', the
         protocol will default to its parent protocol as indicated by
         tmnxBsxProtParentName."
    DEFVAL      { outOfService }
    ::= { tmnxBsxProtEntry 4 }

tmnxBsxProtObsolete              OBJECT-TYPE
    SYNTAX      TruthValue
    MAX-ACCESS  read-only
    STATUS      current
    DESCRIPTION
        "The value of tmnxBsxProtObsolete indicates whether or not the protocol
         is obsolete. Obsolete protocols are no longer supported."
    ::= { tmnxBsxProtEntry 5 }

tmnxBsxProtRowLastChange         OBJECT-TYPE
    SYNTAX      TimeStamp
    MAX-ACCESS  read-only
    STATUS      current
    DESCRIPTION
        "The value of tmnxBsxProtRowLastChange indicates the last time, since
         system startup, a successful set was performed on this row."
    ::= { tmnxBsxProtEntry 6 }

tmnxBsxAppGrpCfgTable            OBJECT-TYPE
    SYNTAX      SEQUENCE OF TmnxBsxAppGrpCfgEntry
    MAX-ACCESS  not-accessible
    STATUS      current
    DESCRIPTION
        "The tmnxBsxAppGrpCfgTable contains an entry for each BSX application
         group."
    ::= { tmnxBsxPolicyObjs 2 }

tmnxBsxAppGrpCfgEntry            OBJECT-TYPE
    SYNTAX      TmnxBsxAppGrpCfgEntry
    MAX-ACCESS  not-accessible
    STATUS      current
    DESCRIPTION
        "Each tmnxBsxAppGrpCfgEntry indicates an application group configured
         by the operator."
    INDEX       {
        tmnxBsxAppGrpPolicyVersion,
        tmnxBsxAaGrpPartIndex,
        IMPLIED tmnxBsxAppGrpName
    }
    ::= { tmnxBsxAppGrpCfgTable 1 }

TmnxBsxAppGrpCfgEntry            ::= SEQUENCE
{
    tmnxBsxAppGrpPolicyVersion       TmnxBsxPolicyVersion,
    tmnxBsxAppGrpName                TNamedItem,
    tmnxBsxAppGrpRowStatus           RowStatus,
    tmnxBsxAppGrpStorageType         StorageType,
    tmnxBsxAppGrpDescription         TItemDescription,
    tmnxBsxAppGrpAdminState          TmnxAdminState,
    tmnxBsxAppGrpChargeGrp           TNamedItemOrEmpty,
    tmnxBsxAppGrpRowLastCh           TimeStamp,
    tmnxBsxAppGrpExportId            Unsigned32
}

tmnxBsxAppGrpPolicyVersion       OBJECT-TYPE
    SYNTAX      TmnxBsxPolicyVersion
    MAX-ACCESS  not-accessible
    STATUS      current
    DESCRIPTION
        "The value of tmnxBsxAppGrpPolicyVersion specifies the
         version of the table being accessed.  The table
         is read-create only for the 'admin' version of
         the table.  The 'oper' version is read-only."
    ::= { tmnxBsxAppGrpCfgEntry 1 }

tmnxBsxAppGrpName                OBJECT-TYPE
    SYNTAX      TNamedItem
    MAX-ACCESS  not-accessible
    STATUS      current
    DESCRIPTION
        "The value of tmnxBsxAppGrpName specifies the name defined for the
         application group."
    ::= { tmnxBsxAppGrpCfgEntry 2 }

tmnxBsxAppGrpRowStatus           OBJECT-TYPE
    SYNTAX      RowStatus
    MAX-ACCESS  read-create
    STATUS      current
    DESCRIPTION
        "The value of tmnxBsxAppGrpRowStatus specifies the
         row status.  It allows entries to be created
         and deleted in the tmnxBsxAppGrpCfgTable.  To
         delete an entry, all references to this application
         group in tmnxBsxAqpMatchAppGroup in tmnxBsxAqpMatchTable
         must be deleted."
    ::= { tmnxBsxAppGrpCfgEntry 3 }

tmnxBsxAppGrpStorageType         OBJECT-TYPE
    SYNTAX      StorageType
    MAX-ACCESS  read-create
    STATUS      current
    DESCRIPTION
        "The value of tmnxBsxAppGrpStorageType specifies how the row is stored.

         Entries with a StorageType of 'permanent(4)' are pre-configured by
         the agent and cannot be destroyed.  All of the objects in a permanent
         row (with the exception of tmnxBsxAppGrpChargeGrp and
         tmnxBsxAppGrpExportId) have read-only access.

         All other entries must be created with a StorageType of
         'nonVolatile(3)'."
    DEFVAL      { nonVolatile }
    ::= { tmnxBsxAppGrpCfgEntry 4 }

tmnxBsxAppGrpDescription         OBJECT-TYPE
    SYNTAX      TItemDescription
    MAX-ACCESS  read-create
    STATUS      current
    DESCRIPTION
        "The value of tmnxBsxAppGrpDescription specifies the description of the
         application group."
    DEFVAL      { "" }
    ::= { tmnxBsxAppGrpCfgEntry 5 }

tmnxBsxAppGrpAdminState          OBJECT-TYPE
    SYNTAX      TmnxAdminState
    MAX-ACCESS  read-create
    STATUS      obsolete
    DESCRIPTION
        "The value of tmnxBsxAppGrpAdminState specifies the
         administrative state for the application group.  When
         'outOfService', any match entries referring to this
         application group is skipped.

         This object was obsoleted in release 10.0."
    DEFVAL      { outOfService }
    ::= { tmnxBsxAppGrpCfgEntry 6 }

tmnxBsxAppGrpChargeGrp           OBJECT-TYPE
    SYNTAX      TNamedItemOrEmpty
    MAX-ACCESS  read-create
    STATUS      current
    DESCRIPTION
        "The value of tmnxBsxAppGrpChargeGrp specifies the name of the charging
         group to be associated with this application group's traffic."
    DEFVAL      { "" }
    ::= { tmnxBsxAppGrpCfgEntry 7 }

tmnxBsxAppGrpRowLastCh           OBJECT-TYPE
    SYNTAX      TimeStamp
    MAX-ACCESS  read-only
    STATUS      current
    DESCRIPTION
        "The value of tmnxBsxAppGrpRowLastCh indicates the last time, since
         system startup, a successful set was performed on this row."
    ::= { tmnxBsxAppGrpCfgEntry 8 }

tmnxBsxAppGrpExportId            OBJECT-TYPE
    SYNTAX      Unsigned32 (0 | 1..255)
    MAX-ACCESS  read-create
    STATUS      current
    DESCRIPTION
        "The value of tmnxBsxAppGrpExportId specifies the identifier used to
         represent the application group in the accounting records.  This
         identifier must be unique within the policy.

         When tmnxBsxAppGrpExportId has a value of 0, RADIUS accounting records
         will not be exported for this application group."
    DEFVAL      { 0 }
    ::= { tmnxBsxAppGrpCfgEntry 9 }

tmnxBsxAppCfgTable               OBJECT-TYPE
    SYNTAX      SEQUENCE OF TmnxBsxAppCfgEntry
    MAX-ACCESS  not-accessible
    STATUS      current
    DESCRIPTION
        "The tmnxBsxAppCfgTable contains an entry for each BSX application."
    ::= { tmnxBsxPolicyObjs 3 }

tmnxBsxAppCfgEntry               OBJECT-TYPE
    SYNTAX      TmnxBsxAppCfgEntry
    MAX-ACCESS  not-accessible
    STATUS      current
    DESCRIPTION
        "Each tmnxBsxAppCfgEntry indicates an application configured by the
         operator."
    INDEX       {
        tmnxBsxAppPolicyVersion,
        tmnxBsxAaGrpPartIndex,
        IMPLIED tmnxBsxAppName
    }
    ::= { tmnxBsxAppCfgTable 1 }

TmnxBsxAppCfgEntry               ::= SEQUENCE
{
    tmnxBsxAppPolicyVersion          TmnxBsxPolicyVersion,
    tmnxBsxAppName                   TNamedItem,
    tmnxBsxAppRowStatus              RowStatus,
    tmnxBsxAppStorageType            StorageType,
    tmnxBsxAppDescription            TItemDescription,
    tmnxBsxAppAppGroup               TNamedItem,
    tmnxBsxAppChargeGrp              TNamedItemOrEmpty,
    tmnxBsxAppRowLastCh              TimeStamp,
    tmnxBsxAppExportId               Unsigned32
}

tmnxBsxAppPolicyVersion          OBJECT-TYPE
    SYNTAX      TmnxBsxPolicyVersion
    MAX-ACCESS  not-accessible
    STATUS      current
    DESCRIPTION
        "The value of tmnxBsxAppPolicyVersion specifies the
         version of the table being accessed.  The table
         is read-create only for the 'admin' version of
         the table.  The 'oper' version is read-only."
    ::= { tmnxBsxAppCfgEntry 1 }

tmnxBsxAppName                   OBJECT-TYPE
    SYNTAX      TNamedItem
    MAX-ACCESS  not-accessible
    STATUS      current
    DESCRIPTION
        "The value of tmnxBsxAppName specifies the name defined for the
         application."
    ::= { tmnxBsxAppCfgEntry 2 }

tmnxBsxAppRowStatus              OBJECT-TYPE
    SYNTAX      RowStatus
    MAX-ACCESS  read-create
    STATUS      current
    DESCRIPTION
        "The value of tmnxBsxAppRowStatus specifies the
         row status.  It allows entries to be created
         and deleted in the tmnxBsxAppCfgTable.  To
         delete an entry, all references to this
         application in tmnxBsxAppFilterApplication in
         the tmnxBsxAppFilterTable and
         tmnxBsxAqpMatchApplication in the tmnxBsxAqpMatchTable
         must be deleted."
    ::= { tmnxBsxAppCfgEntry 3 }

tmnxBsxAppStorageType            OBJECT-TYPE
    SYNTAX      StorageType
    MAX-ACCESS  read-create
    STATUS      current
    DESCRIPTION
        "The value of tmnxBsxAppStorageType specifies how the row is stored.

         Entries with a StorageType of 'permanent(4)' are pre-configured by
         the agent and cannot be destroyed.  All of the objects in a permanent
         row (with the exception of tmnxBsxAppChargeGrp and tmnxBsxAppExportId)
         have read-only access.

         All other entries must be created with a StorageType of
         'nonVolatile(3)'."
    DEFVAL      { nonVolatile }
    ::= { tmnxBsxAppCfgEntry 4 }

tmnxBsxAppDescription            OBJECT-TYPE
    SYNTAX      TItemDescription
    MAX-ACCESS  read-create
    STATUS      current
    DESCRIPTION
        "The value of tmnxBsxAppDescription specifies the description of the
         application."
    DEFVAL      { "" }
    ::= { tmnxBsxAppCfgEntry 5 }

tmnxBsxAppAppGroup               OBJECT-TYPE
    SYNTAX      TNamedItem
    MAX-ACCESS  read-create
    STATUS      current
    DESCRIPTION
        "The value of tmnxBsxAppAppGroup specifies the application group to
         which this application belongs.

         If an attempt is made to set this object to a string that does not
         match a tmnxBsxAppGrpName value from the tmnxBsxAppGrpCfgTable, an
         'inconsistentValue' error is returned."
    DEFVAL      { "Unknown" }
    ::= { tmnxBsxAppCfgEntry 6 }

tmnxBsxAppChargeGrp              OBJECT-TYPE
    SYNTAX      TNamedItemOrEmpty
    MAX-ACCESS  read-create
    STATUS      current
    DESCRIPTION
        "The value of tmnxBsxAppChargeGrp specifies the name of the charging
         group to be associated with this application's traffic."
    DEFVAL      { "" }
    ::= { tmnxBsxAppCfgEntry 7 }

tmnxBsxAppRowLastCh              OBJECT-TYPE
    SYNTAX      TimeStamp
    MAX-ACCESS  read-only
    STATUS      current
    DESCRIPTION
        "The value of tmnxBsxAppRowLastCh indicates the last time, since system
         startup, a successful set was performed on this row."
    ::= { tmnxBsxAppCfgEntry 8 }

tmnxBsxAppExportId               OBJECT-TYPE
    SYNTAX      Unsigned32 (0 | 1..255)
    MAX-ACCESS  read-create
    STATUS      current
    DESCRIPTION
        "The value of tmnxBsxAppExportId specifies the identifier used to
         represent the application group in the accounting records.  This
         identifier must be unique within the policy.

         When tmnxBsxAppExportId has a value of 0, RADIUS accounting records
         will not be exported for this application."
    DEFVAL      { 0 }
    ::= { tmnxBsxAppCfgEntry 9 }

tmnxBsxAppFilterTable            OBJECT-TYPE
    SYNTAX      SEQUENCE OF TmnxBsxAppFilterEntry
    MAX-ACCESS  not-accessible
    STATUS      current
    DESCRIPTION
        "The tmnxBsxAppFilterTable contains an entry for each set of match
         criteria defining an application."
    ::= { tmnxBsxPolicyObjs 4 }

tmnxBsxAppFilterEntry            OBJECT-TYPE
    SYNTAX      TmnxBsxAppFilterEntry
    MAX-ACCESS  not-accessible
    STATUS      current
    DESCRIPTION
        "Each tmnxBsxAppFilterEntry indicates a set of match criteria defining
         an application."
    INDEX       {
        tmnxBsxAppFilterPolicyVersion,
        tmnxBsxAaGrpPartIndex,
        tmnxBsxAppFilterEntryId
    }
    ::= { tmnxBsxAppFilterTable 1 }

TmnxBsxAppFilterEntry            ::= SEQUENCE
{
    tmnxBsxAppFilterPolicyVersion    TmnxBsxPolicyVersion,
    tmnxBsxAppFilterEntryId          TEntryId,
    tmnxBsxAppFilterRowStatus        RowStatus,
    tmnxBsxAppFilterDescription      TItemDescription,
    tmnxBsxAppFilterAdminState       TmnxAdminState,
    tmnxBsxAppFilterProtocol         TNamedItemOrEmpty,
    tmnxBsxAppFilterProtocolOp       TmnxBsxOperator,
    tmnxBsxAppFilterFlowSetupDir     TmnxBsxDirection,
    tmnxBsxAppFilterIpProtocolNum    TIpProtocol,
    tmnxBsxAppFilterIpProtocolNumOp  TmnxBsxOperator,
    tmnxBsxAppFilterServerAddrType   InetAddressType,
    tmnxBsxAppFilterServerAddr       InetAddress,
    tmnxBsxAppFilterServerAddrLen    InetAddressPrefixLength,
    tmnxBsxAppFilterServerAddrOp     TmnxBsxOperator,
    tmnxBsxAppFilterServerPort       TTcpUdpPort,
    tmnxBsxAppFilterServerPortOp     TmnxBsxOperator,
    tmnxBsxAppFilterServerPortFpp    TmnxBsxFirstPacketPolicy,
    tmnxBsxAppFilterServerPortLow    TTcpUdpPort,
    tmnxBsxAppFilterServerPortHigh   TTcpUdpPort,
    tmnxBsxAppFilterServerPfxList    TNamedItemOrEmpty,
    tmnxBsxAppFilterServerDnsIpCache TNamedItemOrEmpty,
    tmnxBsxAppFilterNetworkAddrType  InetAddressType,
    tmnxBsxAppFilterNetworkAddr      InetAddress,
    tmnxBsxAppFilterNetworkAddrLen   InetAddressPrefixLength,
    tmnxBsxAppFilterNetworkAddrOp    TmnxBsxOperator,
    tmnxBsxAppFilterNetworkPfxList   TNamedItemOrEmpty,
    tmnxBsxAppFilterHttpPort         TTcpUdpPort,
    tmnxBsxAppFilterHttpPortOp       TmnxBsxOperator,
    tmnxBsxAppFilterServerPortList   TNamedItemOrEmpty,
    tmnxBsxAppFilterHttpPortList     TNamedItemOrEmpty,
    tmnxBsxAppFilterSrvAddrMaskedIp  InetAddress,
    tmnxBsxAppFilterSrvAddrMask      InetAddress,
    tmnxBsxAppFilterSrvAddrMaskType  InetAddressType,
    tmnxBsxAppFilterApplication      TNamedItem,
    tmnxBsxAppFilterRowLastChange    TimeStamp,
    tmnxBsxAppFilterHttpMatchAllReq  TmnxEnabledDisabled,
    tmnxBsxAppFilterIpIdentAssist    TmnxEnabledDisabled
}

tmnxBsxAppFilterPolicyVersion    OBJECT-TYPE
    SYNTAX      TmnxBsxPolicyVersion
    MAX-ACCESS  not-accessible
    STATUS      current
    DESCRIPTION
        "The value of tmnxBsxAppFilterPolicyVersion specifies the
         version of the table being accessed.  The table
         is read-create only for the 'admin' version of
         the table.  The 'oper' version is read-only."
    ::= { tmnxBsxAppFilterEntry 1 }

tmnxBsxAppFilterEntryId          OBJECT-TYPE
    SYNTAX      TEntryId
    MAX-ACCESS  not-accessible
    STATUS      current
    DESCRIPTION
        "The value of tmnxBsxAppFilterEntryId specifies the index into the
         filter list that resolve applications."
    ::= { tmnxBsxAppFilterEntry 2 }

tmnxBsxAppFilterRowStatus        OBJECT-TYPE
    SYNTAX      RowStatus
    MAX-ACCESS  read-create
    STATUS      current
    DESCRIPTION
        "The value of tmnxBsxAppFilterRowStatus specifies
         the row status.  It allows entries to be created
         and deleted in the tmnxBsxAppFilterTable."
    ::= { tmnxBsxAppFilterEntry 3 }

tmnxBsxAppFilterDescription      OBJECT-TYPE
    SYNTAX      TItemDescription
    MAX-ACCESS  read-create
    STATUS      current
    DESCRIPTION
        "The value of tmnxBsxAppFilterDescription specifies the description of
         the application."
    DEFVAL      { "" }
    ::= { tmnxBsxAppFilterEntry 4 }

tmnxBsxAppFilterAdminState       OBJECT-TYPE
    SYNTAX      TmnxAdminState
    MAX-ACCESS  read-create
    STATUS      current
    DESCRIPTION
        "The value of tmnxBsxAppFilterAdminState specifies the
         administrative state for the application.  When
         'outOfService', any match entries referring to this
         application are skipped."
    DEFVAL      { outOfService }
    ::= { tmnxBsxAppFilterEntry 5 }

tmnxBsxAppFilterProtocol         OBJECT-TYPE
    SYNTAX      TNamedItemOrEmpty
    MAX-ACCESS  read-create
    STATUS      current
    DESCRIPTION
        "The value of tmnxBsxAppFilterProtocol specifies
         the particular protocol signature to match against
         to resolve to tmnxBsxAppFilterApplication.  If set
         to an empty string, no match on protocol is done.

         If an attempt is made to set this object to a string that does not
         match a tmnxBsxProtName value from the tmnxBsxProtTable, an
         'inconsistentValue' error is returned."
    DEFVAL      { "" }
    ::= { tmnxBsxAppFilterEntry 6 }

tmnxBsxAppFilterProtocolOp       OBJECT-TYPE
    SYNTAX      TmnxBsxOperator
    MAX-ACCESS  read-create
    STATUS      current
    DESCRIPTION
        "The value of tmnxBsxAppFilterProtocolOp specifies the operator to
         apply in relation to tmnxBsxAppFilterProtocol to match against to
         resolve to tmnxBsxAppFilterApplication."
    DEFVAL      { none }
    ::= { tmnxBsxAppFilterEntry 7 }

tmnxBsxAppFilterFlowSetupDir     OBJECT-TYPE
    SYNTAX      TmnxBsxDirection
    MAX-ACCESS  read-create
    STATUS      current
    DESCRIPTION
        "The value of tmnxBsxAppFilterFlowSetupDir specifies the
         flow setup directions to match against to
         resolve to tmnxBsxAppFilterApplication.  This allows
         separation of client and server applications."
    DEFVAL      { both }
    ::= { tmnxBsxAppFilterEntry 8 }

tmnxBsxAppFilterIpProtocolNum    OBJECT-TYPE
    SYNTAX      TIpProtocol
    MAX-ACCESS  read-create
    STATUS      current
    DESCRIPTION
        "The value of tmnxBsxAppFilterIpProtocolNum specifies the
         IP protocol number to match to resolve to an application.
         A value of '-1' specifies that no matching is to be done to
         resolve an application.  A value of '-2' specifies that a
         match will occur if the protocol is TCP or UDP."
    DEFVAL      { -1 }
    ::= { tmnxBsxAppFilterEntry 9 }

tmnxBsxAppFilterIpProtocolNumOp  OBJECT-TYPE
    SYNTAX      TmnxBsxOperator
    MAX-ACCESS  read-create
    STATUS      current
    DESCRIPTION
        "The value of tmnxBsxAppFilterIpProtocolNumOp specifies the operator to
         apply in relation to tmnxBsxAppFilterIpProtocolNum to match against to
         resolve to tmnxBsxAppFilterApplication."
    DEFVAL      { none }
    ::= { tmnxBsxAppFilterEntry 10 }

tmnxBsxAppFilterServerAddrType   OBJECT-TYPE
    SYNTAX      InetAddressType
    MAX-ACCESS  read-create
    STATUS      current
    DESCRIPTION
        "The value of tmnxBsxAppFilterServerAddrType specifies the type of
         address contained in tmnxBsxAppFilterServerAddr.

         A value of 'unknown' specifies that no matching is to be done to
         resolve to an application."
    DEFVAL      { unknown }
    ::= { tmnxBsxAppFilterEntry 11 }

tmnxBsxAppFilterServerAddr       OBJECT-TYPE
    SYNTAX      InetAddress (SIZE (0|4|16))
    MAX-ACCESS  read-create
    STATUS      current
    DESCRIPTION
        "The value of tmnxBsxAppFilterServerAddr specifies the server address
         to match to resolve to an application.

         The specification of the server address may be done only when
         tmnxBsxAppFilterServerDnsIpCache, tmnxBsxAppFilterNetworkAddr,
         tmnxBsxAppFilterNetworkAddrType, and tmnxBsxAppFilterNetworkAddrLen
         are set to their default value.

         Furthermore, the specification of the server address list must be done
         with the specification of a non-default tmnxBsxAppFilterServerAddrOp."
    DEFVAL      { ''H }
    ::= { tmnxBsxAppFilterEntry 12 }

tmnxBsxAppFilterServerAddrLen    OBJECT-TYPE
    SYNTAX      InetAddressPrefixLength (0..128)
    MAX-ACCESS  read-create
    STATUS      current
    DESCRIPTION
        "The value of tmnxBsxAppFilterServerAddrLen specifies the number of
         relevant bits of the tmnxBsxAppFilterServerAddr."
    DEFVAL      { 0 }
    ::= { tmnxBsxAppFilterEntry 13 }

tmnxBsxAppFilterServerAddrOp     OBJECT-TYPE
    SYNTAX      TmnxBsxOperator
    MAX-ACCESS  read-create
    STATUS      current
    DESCRIPTION
        "The value of tmnxBsxAppFilterServerAddrOp specifies the operator to
         apply in relation to tmnxBsxAppFilterServerAddrType,
         tmnxBsxAppFilterServerAddr, and tmnxBsxAppFilterServerAddrLen to match
         against to resolve to an application."
    DEFVAL      { none }
    ::= { tmnxBsxAppFilterEntry 14 }

tmnxBsxAppFilterServerPort       OBJECT-TYPE
    SYNTAX      TTcpUdpPort
    MAX-ACCESS  read-create
    STATUS      obsolete
    DESCRIPTION
        "The value of tmnxBsxAppFilterServerPort specifies the
         server TCP or UDP port number to match to resolve to an
         application.  This only applies if the
         tmnxBsxAppFilterIpProtocolNum is set to TCP, UDP
         or '-2' (implying either).

         This object was obsoleted in release 8.0 and replaced with the
         tmnxBsxAppFilterServerPortLow and tmnxBsxAppFilterServerPortHigh
         objects."
    DEFVAL      { 0 }
    ::= { tmnxBsxAppFilterEntry 15 }

tmnxBsxAppFilterServerPortOp     OBJECT-TYPE
    SYNTAX      TmnxBsxOperator
    MAX-ACCESS  read-create
    STATUS      current
    DESCRIPTION
        "The value of tmnxBsxAppFilterServerPortOp specifies the operator to
         apply in relation to tmnxBsxAppFilterServerPort to match against to
         resolve to an application.

         In release 15.0, when tmnxBsxAppFilterServerPortOp is used in the
         context of tmnxBsxAppFilterServerPortLow or
         tmnxBsxAppFilterServerPortHigh then all the three objects
         (tmnxBsxAppFilterServerPortLow, tmnxBsxAppFilterServerPortHigh and
         tmnxBsxAppFilterServerPortOp) must be set in the same SNMP PDU."
    DEFVAL      { none }
    ::= { tmnxBsxAppFilterEntry 16 }

tmnxBsxAppFilterServerPortFpp    OBJECT-TYPE
    SYNTAX      TmnxBsxFirstPacketPolicy
    MAX-ACCESS  read-create
    STATUS      current
    DESCRIPTION
        "The value of tmnxBsxAppFilterServerPortFpp specifies the packet policy
         to apply for flows that match the tmnxBsxAppFilterServerPort and
         tmnxBsxAppFilterServerPortOp.

         A value of none(0) specifies that no packet policy is applied.

         A value of first-packet-trusted(1) specifies that flows resolve to an
         application when the first packet for the flow is received. ISA-AA
         analysis is not performed on the flow.

         A value of first-packet-validate(2) specifies that flows resolve to an
         application when the first packet for the flow is received. ISA-AA
         analysis is performed on the flow and the application re-determined
         once the protocol has been identified."
    DEFVAL      { none }
    ::= { tmnxBsxAppFilterEntry 17 }

tmnxBsxAppFilterServerPortLow    OBJECT-TYPE
    SYNTAX      TTcpUdpPort
    MAX-ACCESS  read-create
    STATUS      current
    DESCRIPTION
        "The value of tmnxBsxAppFilterServerPortLow specifies the low server
         TCP or UDP port number to match to resolve to an application.
         tmnxBsxAppFilterServerPortLow must be less than or equal to
         tmnxBsxAppFilterServerPortHigh, and is used when the
         tmnxBsxAppFilterServerPortOp is not 'none (0)'.

         In release 15.0, tmnxBsxAppFilterServerPortLow,
         tmnxBsxAppFilterServerPortHigh and tmnxBsxAppFilterServerPortOp must
         be set in the same SNMP PDU."
    DEFVAL      { 0 }
    ::= { tmnxBsxAppFilterEntry 18 }

tmnxBsxAppFilterServerPortHigh   OBJECT-TYPE
    SYNTAX      TTcpUdpPort
    MAX-ACCESS  read-create
    STATUS      current
    DESCRIPTION
        "The value of tmnxBsxAppFilterServerPortHigh specifies the high server
         TCP or UDP port number to match to resolve to an application.
         tmnxBsxAppFilterServerPortHigh must be greater than or equal to
         tmnxBsxAppFilterServerPortLow, and is used when the
         tmnxBsxAppFilterServerPortOp is not 'none (0)'.

         In release 15.0, tmnxBsxAppFilterServerPortLow,
         tmnxBsxAppFilterServerPortHigh and tmnxBsxAppFilterServerPortOp must
         be set in the same SNMP PDU."
    DEFVAL      { 0 }
    ::= { tmnxBsxAppFilterEntry 19 }

tmnxBsxAppFilterServerPfxList    OBJECT-TYPE
    SYNTAX      TNamedItemOrEmpty
    MAX-ACCESS  read-create
    STATUS      current
    DESCRIPTION
        "The value of tmnxBsxAppFilterServerPfxList specifies the prefix list
         to use when matching the server address to resolve to an application.

         The specification of the server IP prefix list may be done only when
         tmnxBsxAppFilterServerDnsIpCache, tmnxBsxAppFilterServerAddr,
         tmnxBsxAppFilterServerAddrType, tmnxBsxAppFilterServerAddrLen, and the
         equivalent network objects are set to their default value.

         Furthermore, the specification of the server IP prefix list must be
         done with the specification of a non-default
         tmnxBsxAppFilterServerAddrOp."
    DEFVAL      { "" }
    ::= { tmnxBsxAppFilterEntry 20 }

tmnxBsxAppFilterServerDnsIpCache OBJECT-TYPE
    SYNTAX      TNamedItemOrEmpty
    MAX-ACCESS  read-create
    STATUS      current
    DESCRIPTION
        "The value of tmnxBsxAppFilterServerDnsIpCache specifies the DNS IP
         cache to use when matching the server IP address to resolve to an
         application, as defined in the tmnxBsxDnsIpCacheTable.

         The specification of the DNS IP cache may be done only when
         tmnxBsxAppFilterServerPfxList, tmnxBsxAppFilterServerAddr,
         tmnxBsxAppFilterServerAddrType, tmnxBsxAppFilterServerAddrLen, and the
         equivalent network objects are set to their default value."
    DEFVAL      { "" }
    ::= { tmnxBsxAppFilterEntry 21 }

tmnxBsxAppFilterNetworkAddrType  OBJECT-TYPE
    SYNTAX      InetAddressType
    MAX-ACCESS  read-create
    STATUS      current
    DESCRIPTION
        "The value of tmnxBsxAppFilterNetworkAddrType specifies the type of
         address contained in tmnxBsxAppFilterNetworkAddr.

         A value of 'unknown' specifies that no matching is to be done to
         resolve to an application."
    DEFVAL      { unknown }
    ::= { tmnxBsxAppFilterEntry 22 }

tmnxBsxAppFilterNetworkAddr      OBJECT-TYPE
    SYNTAX      InetAddress (SIZE (0|4|16))
    MAX-ACCESS  read-create
    STATUS      current
    DESCRIPTION
        "The value of tmnxBsxAppFilterNetworkAddr specifies the network address
         to match to resolve to an application.

         The specification of the network address may be done only when
         tmnxBsxAppFilterServerAddr, tmnxBsxAppFilterServerAddrType,  and
         tmnxBsxAppFilterServerAddrLen are set to their default value.

         Furthermore, the specification of a network address must be done with
         the specification of a non-default tmnxBsxAppFilterNetworkAddrOp."
    DEFVAL      { ''H }
    ::= { tmnxBsxAppFilterEntry 23 }

tmnxBsxAppFilterNetworkAddrLen   OBJECT-TYPE
    SYNTAX      InetAddressPrefixLength (0..128)
    MAX-ACCESS  read-create
    STATUS      current
    DESCRIPTION
        "The value of tmnxBsxAppFilterNetworkAddrLen specifies the number of
         relevant bits of the tmnxBsxAppFilterNetworkAddr."
    DEFVAL      { 0 }
    ::= { tmnxBsxAppFilterEntry 24 }

tmnxBsxAppFilterNetworkAddrOp    OBJECT-TYPE
    SYNTAX      TmnxBsxOperator
    MAX-ACCESS  read-create
    STATUS      current
    DESCRIPTION
        "The value of tmnxBsxAppFilterNetworkAddrOp specifies the operator to
         apply in relation to tmnxBsxAppFilterNetworkAddrType,
         tmnxBsxAppFilterNetworkAddr, and tmnxBsxAppFilterNetworkAddrLen to
         match against to resolve to an application."
    DEFVAL      { none }
    ::= { tmnxBsxAppFilterEntry 25 }

tmnxBsxAppFilterNetworkPfxList   OBJECT-TYPE
    SYNTAX      TNamedItemOrEmpty
    MAX-ACCESS  read-create
    STATUS      current
    DESCRIPTION
        "The value of tmnxBsxAppFilterNetworkPfxList specifies the prefix list
         to use when matching the network address to resolve to an application.

         The specification of the network IP prefix list may be done only when
         tmnxBsxAppFilterServerDnsIpCache, tmnxBsxAppFilterNetworkAddr,
         tmnxBsxAppFilterNetworkAddrType, tmnxBsxAppFilterNetworkAddrLen, and
         the equivalent server objects are set to their default value.

         Furthermore, the specification of the network IP prefix list must be
         done with the specification of a non-default
         tmnxBsxAppFilterNetworkAddrOp."
    DEFVAL      { "" }
    ::= { tmnxBsxAppFilterEntry 26 }

tmnxBsxAppFilterHttpPort         OBJECT-TYPE
    SYNTAX      TTcpUdpPort
    MAX-ACCESS  read-create
    STATUS      current
    DESCRIPTION
        "The value of tmnxBsxAppFilterHttpPort specifies the HTTP port number
         to match to resolve to an application. This only applies if the
         tmnxBsxAppFilterProtocol is set to 'http'."
    DEFVAL      { 0 }
    ::= { tmnxBsxAppFilterEntry 27 }

tmnxBsxAppFilterHttpPortOp       OBJECT-TYPE
    SYNTAX      TmnxBsxOperator
    MAX-ACCESS  read-create
    STATUS      current
    DESCRIPTION
        "The value of tmnxBsxAppFilterHttpPortOp specifies the operator to
         apply in relation to tmnxBsxAppFilterHttpPort to match against to
         resolve to an application. This only applies if the
         tmnxBsxAppFilterProtocol is set to 'http'."
    DEFVAL      { none }
    ::= { tmnxBsxAppFilterEntry 28 }

tmnxBsxAppFilterServerPortList   OBJECT-TYPE
    SYNTAX      TNamedItemOrEmpty
    MAX-ACCESS  read-create
    STATUS      current
    DESCRIPTION
        "The value of tmnxBsxAppFilterServerPortList specifies the name of the
         server port list (tmnxBsxPortListName) the filter entry uses."
    DEFVAL      { "" }
    ::= { tmnxBsxAppFilterEntry 29 }

tmnxBsxAppFilterHttpPortList     OBJECT-TYPE
    SYNTAX      TNamedItemOrEmpty
    MAX-ACCESS  read-create
    STATUS      current
    DESCRIPTION
        "The value of tmnxBsxAppFilterHttpPortList specifies the name of the
         name of the HTTP port list (tmnxBsxPortListName) the filter entry
         uses."
    DEFVAL      { "" }
    ::= { tmnxBsxAppFilterEntry 30 }

tmnxBsxAppFilterSrvAddrMaskedIp  OBJECT-TYPE
    SYNTAX      InetAddress (SIZE (0|4|16))
    MAX-ACCESS  read-create
    STATUS      current
    DESCRIPTION
        "The value of tmnxBsxAppFilterSrvAddrMaskedIp masked with
         tmnxBsxAppFilterSrvAddrMask specifies the server address to match to
         resolve to an application.

         The specification of tmnxBsxAppFilterSrvAddrMaskedIp may be done only
         when tmnxBsxAppFilterServerDnsIpCache, tmnxBsxAppFilterServerPfxList,
         tmnxBsxAppFilterNetworkAddr, tmnxBsxAppFilterNetworkAddrType, and
         tmnxBsxAppFilterNetworkAddrLen are set to their default value.

         Furthermore, the specification of tmnxBsxAppFilterSrvAddrMaskedIp must
         be done with the specification of a non-default
         tmnxBsxAppFilterSrvAddrMask, tmnxBsxAppFilterServerAddrOp and
         tmnxBsxAppFilterSrvAddrMaskType."
    DEFVAL      { ''H }
    ::= { tmnxBsxAppFilterEntry 31 }

tmnxBsxAppFilterSrvAddrMask      OBJECT-TYPE
    SYNTAX      InetAddress (SIZE (0|4|16))
    MAX-ACCESS  read-create
    STATUS      current
    DESCRIPTION
        "The value of tmnxBsxAppFilterSrvAddrMask specifies the mask (or
         relevant bits) to match tmnxBsxAppFilterSrvAddrMaskedIp.

         The specification of tmnxBsxAppFilterSrvAddrMask may be done only when
         tmnxBsxAppFilterSrvAddrMaskedIp, tmnxBsxAppFilterSrvAddrMaskType, and
         tmnxBsxAppFilterServerAddrOp are set to valid non-default values.

         The specification of tmnxBsxAppFilterSrvAddrMask may be done only when
         tmnxBsxAppFilterServerDnsIpCache, tmnxBsxAppFilterNetworkPfxList,
         tmnxBsxAppFilterNetworkAddr, tmnxBsxAppFilterNetworkAddrType, and
         tmnxBsxAppFilterNetworkAddrLen are set to their default values."
    DEFVAL      { ''H }
    ::= { tmnxBsxAppFilterEntry 32 }

tmnxBsxAppFilterSrvAddrMaskType  OBJECT-TYPE
    SYNTAX      InetAddressType
    MAX-ACCESS  read-create
    STATUS      current
    DESCRIPTION
        "The value of tmnxBsxAppFilterSrvAddrMaskType specifies the type of
         address contained in tmnxBsxAppFilterSrvAddrMaskedIp and
         tmnxBsxAppFilterSrvAddrMask."
    DEFVAL      { unknown }
    ::= { tmnxBsxAppFilterEntry 33 }

tmnxBsxAppFilterApplication      OBJECT-TYPE
    SYNTAX      TNamedItem
    MAX-ACCESS  read-create
    STATUS      current
    DESCRIPTION
        "The value of tmnxBsxAppFilterApplication specifies the result of
         filtering on all other rows of this table.

         If an attempt is made to set this object to a string that does not
         match a tmnxBsxAppName value from the tmnxBsxAppCfgTable, an
         'inconsistentValue' error is returned."
    DEFVAL      { "Unknown" }
    ::= { tmnxBsxAppFilterEntry 99 }

tmnxBsxAppFilterRowLastChange    OBJECT-TYPE
    SYNTAX      TimeStamp
    MAX-ACCESS  read-only
    STATUS      current
    DESCRIPTION
        "The value of tmnxBsxAppFilterRowLastChange indicates the last time,
         since system startup, a successful set was performed on this row."
    ::= { tmnxBsxAppFilterEntry 100 }

tmnxBsxAppFilterHttpMatchAllReq  OBJECT-TYPE
    SYNTAX      TmnxEnabledDisabled
    MAX-ACCESS  read-create
    STATUS      current
    DESCRIPTION
        "The value of tmnxBsxAppFilterHttpMatchAllReq specifies whether or not
         constant monitoring is performed for HTTP request strings for
         application changes classified by the application filter entry."
    DEFVAL      { disabled }
    ::= { tmnxBsxAppFilterEntry 101 }

tmnxBsxAppFilterIpIdentAssist    OBJECT-TYPE
    SYNTAX      TmnxEnabledDisabled
    MAX-ACCESS  read-create
    STATUS      current
    DESCRIPTION
        "The value of tmnxBsxAppFilterIpIdentAssist specifies whether or not
         ip-identification-assist is used for traffic matching this application
         filter entry."
    DEFVAL      { disabled }
    ::= { tmnxBsxAppFilterEntry 102 }

tmnxBsxAsoTable                  OBJECT-TYPE
    SYNTAX      SEQUENCE OF TmnxBsxAsoEntry
    MAX-ACCESS  not-accessible
    STATUS      current
    DESCRIPTION
        "The tmnxBsxAsoTable contains an entry for each subscriber selectable
         characteristic / option used to differentiate services between
         subscribers."
    ::= { tmnxBsxPolicyObjs 5 }

tmnxBsxAsoEntry                  OBJECT-TYPE
    SYNTAX      TmnxBsxAsoEntry
    MAX-ACCESS  not-accessible
    STATUS      current
    DESCRIPTION
        "Each tmnxBsxAsoEntry specifies a subscriber selectable option."
    INDEX       {
        tmnxBsxAsoPolicyVersion,
        tmnxBsxAaGrpPartIndex,
        tmnxBsxAsoCharName
    }
    ::= { tmnxBsxAsoTable 1 }

TmnxBsxAsoEntry                  ::= SEQUENCE
{
    tmnxBsxAsoPolicyVersion          TmnxBsxPolicyVersion,
    tmnxBsxAsoCharName               TNamedItem,
    tmnxBsxAsoRowStatus              RowStatus,
    tmnxBsxAsoDefValName             TNamedItemOrEmpty,
    tmnxBsxAsoRowLastChange          TimeStamp,
    tmnxBsxAsoPersistId              Unsigned32
}

tmnxBsxAsoPolicyVersion          OBJECT-TYPE
    SYNTAX      TmnxBsxPolicyVersion
    MAX-ACCESS  not-accessible
    STATUS      current
    DESCRIPTION
        "The value of tmnxBsxAsoPolicyVersion specifies the
         version of the table being accessed.  The table
         is read-create only for the 'admin' version of
         the table.  The 'oper' version is read-only."
    ::= { tmnxBsxAsoEntry 1 }

tmnxBsxAsoCharName               OBJECT-TYPE
    SYNTAX      TNamedItem
    MAX-ACCESS  not-accessible
    STATUS      current
    DESCRIPTION
        "The value of tmnxBsxAsoCharName specifies the name of a characteristic
         that is selectable by a subscriber."
    ::= { tmnxBsxAsoEntry 2 }

tmnxBsxAsoRowStatus              OBJECT-TYPE
    SYNTAX      RowStatus
    MAX-ACCESS  read-create
    STATUS      current
    DESCRIPTION
        "The value of tmnxBsxAsoRowStatus specifies the
         row status.  It allows entries to be created
         and deleted in the tmnxBsxAsoTable.  To
         delete an entry, all references to this
         characteristic in tmnxBsxAppProfCharCharName in
         the tmnxBsxAppProfTable and the tmnxBsxAqpCharTable
         must be deleted."
    ::= { tmnxBsxAsoEntry 3 }

tmnxBsxAsoDefValName             OBJECT-TYPE
    SYNTAX      TNamedItemOrEmpty
    MAX-ACCESS  read-create
    STATUS      current
    DESCRIPTION
        "The value of tmnxBsxAsoDefValName specifies the default value for a
         characteristic that is not specified in the tmnxBsxAppProfCharTable.

         This value must not exist within the tmnxBsxAsoValTable for
         corresponding entries of tmnxBsxAsoValCharName equal to
         tmnxBsxAsoCharName."
    DEFVAL      { "" }
    ::= { tmnxBsxAsoEntry 4 }

tmnxBsxAsoRowLastChange          OBJECT-TYPE
    SYNTAX      TimeStamp
    MAX-ACCESS  read-only
    STATUS      current
    DESCRIPTION
        "The value of tmnxBsxAsoRowLastChange indicates the last time, since
         system startup, a successful set was performed on this row."
    ::= { tmnxBsxAsoEntry 5 }

tmnxBsxAsoPersistId              OBJECT-TYPE
    SYNTAX      Unsigned32
    MAX-ACCESS  read-create
    STATUS      current
    DESCRIPTION
        "The value of tmnxBsxAsoPersistId specifies the system generated
         persistent ID of an ASO characteristic.

         This value is set by the system and can not be set via SNMP."
    DEFVAL      { 0 }
    ::= { tmnxBsxAsoEntry 6 }

tmnxBsxAsoValTable               OBJECT-TYPE
    SYNTAX      SEQUENCE OF TmnxBsxAsoValEntry
    MAX-ACCESS  not-accessible
    STATUS      current
    DESCRIPTION
        "The tmnxBsxAsoValTable contains an entry for each value of each
         subscriber selectable characteristic used to differentiate services
         between subscribers."
    ::= { tmnxBsxPolicyObjs 6 }

tmnxBsxAsoValEntry               OBJECT-TYPE
    SYNTAX      TmnxBsxAsoValEntry
    MAX-ACCESS  not-accessible
    STATUS      current
    DESCRIPTION
        "Each tmnxBsxAsoValEntry specifies a value for a subscriber selectable
         option."
    INDEX       {
        tmnxBsxAsoValPolicyVersion,
        tmnxBsxAaGrpPartIndex,
        tmnxBsxAsoValCharName,
        IMPLIED tmnxBsxAsoValValName
    }
    ::= { tmnxBsxAsoValTable 1 }

TmnxBsxAsoValEntry               ::= SEQUENCE
{
    tmnxBsxAsoValPolicyVersion       TmnxBsxPolicyVersion,
    tmnxBsxAsoValCharName            TNamedItem,
    tmnxBsxAsoValValName             TNamedItem,
    tmnxBsxAsoValRowStatus           RowStatus,
    tmnxBsxAsoValRowLastChange       TimeStamp,
    tmnxBsxAsoValPersistId           Unsigned32
}

tmnxBsxAsoValPolicyVersion       OBJECT-TYPE
    SYNTAX      TmnxBsxPolicyVersion
    MAX-ACCESS  not-accessible
    STATUS      current
    DESCRIPTION
        "The value of tmnxBsxAsoValPolicyVersion specifies
         the version of the table being accessed.  The table
         is read-create only for the 'admin' version of
         the table.  The 'oper' version is read-only."
    ::= { tmnxBsxAsoValEntry 1 }

tmnxBsxAsoValCharName            OBJECT-TYPE
    SYNTAX      TNamedItem
    MAX-ACCESS  not-accessible
    STATUS      current
    DESCRIPTION
        "The value of tmnxBsxAsoValCharName specifies the name of a
         characteristic that is selectable by a subscriber."
    ::= { tmnxBsxAsoValEntry 2 }

tmnxBsxAsoValValName             OBJECT-TYPE
    SYNTAX      TNamedItem
    MAX-ACCESS  not-accessible
    STATUS      current
    DESCRIPTION
        "The value of tmnxBsxAsoValValName specifies a particular value for a
         characteristic that is selectable by a subscriber.

         This value must not exist within the tmnxBsxAsoDefValName for
         corresponding entries of tmnxBsxAsoCharName equal to
         tmnxBsxAsoValCharName."
    ::= { tmnxBsxAsoValEntry 3 }

tmnxBsxAsoValRowStatus           OBJECT-TYPE
    SYNTAX      RowStatus
    MAX-ACCESS  read-create
    STATUS      current
    DESCRIPTION
        "The value of tmnxBsxAsoValRowStatus specifies the
         row status.  It allows entries to be created
         and deleted in the tmnxBsxAsoValTable.  To
         delete an entry, all references to this
         value in tmnxBsxAppProfCharValName in the
         tmnxBsxAppProfCharTable and the tmnxBsxAqpCharTable
         must be deleted."
    ::= { tmnxBsxAsoValEntry 4 }

tmnxBsxAsoValRowLastChange       OBJECT-TYPE
    SYNTAX      TimeStamp
    MAX-ACCESS  read-only
    STATUS      current
    DESCRIPTION
        "The value of tmnxBsxAsoValRowLastChange indicates the last time, since
         system startup, a successful set was performed on this row."
    ::= { tmnxBsxAsoValEntry 5 }

tmnxBsxAsoValPersistId           OBJECT-TYPE
    SYNTAX      Unsigned32
    MAX-ACCESS  read-create
    STATUS      current
    DESCRIPTION
        "The value of tmnxBsxAsoValPersistId specifies the system generated
         persistent ID of an ASO value characteristic.

         This value is set by the system and can not be set via SNMP."
    DEFVAL      { 0 }
    ::= { tmnxBsxAsoValEntry 6 }

tmnxBsxAppProfTable              OBJECT-TYPE
    SYNTAX      SEQUENCE OF TmnxBsxAppProfEntry
    MAX-ACCESS  not-accessible
    STATUS      current
    DESCRIPTION
        "The tmnxBsxAppProfTable contains an entry for each
         application profile.  App profiles are assigned to
         subscribers and contain characteristics used to
         select subscriber specific policy."
    ::= { tmnxBsxPolicyObjs 7 }

tmnxBsxAppProfEntry              OBJECT-TYPE
    SYNTAX      TmnxBsxAppProfEntry
    MAX-ACCESS  not-accessible
    STATUS      current
    DESCRIPTION
        "Each tmnxBsxAppProfEntry specifies an application profile configured
         by the operator."
    INDEX       {
        tmnxBsxAppPolicyVersion,
        tmnxBsxAaGrpPartIndex,
        tmnxBsxAppProfName
    }
    ::= { tmnxBsxAppProfTable 1 }

TmnxBsxAppProfEntry              ::= SEQUENCE
{
    tmnxBsxAppProfName               TNamedItem,
    tmnxBsxAppProfRowStatus          RowStatus,
    tmnxBsxAppProfDescription        TItemDescription,
    tmnxBsxAppProfDivert             TruthValue,
    tmnxBsxAppProfCapacityCost       Unsigned32,
    tmnxBsxAppProfRowLastChange      TimeStamp,
    tmnxBsxAppProfSubSuppressible    TmnxEnabledDisabled,
    tmnxBsxAppProfDistributeByIp     TmnxEnabledDisabled
}

tmnxBsxAppProfName               OBJECT-TYPE
    SYNTAX      TNamedItem
    MAX-ACCESS  not-accessible
    STATUS      current
    DESCRIPTION
        "The value of tmnxBsxAppProfName specifies the name defined for the
         application profile."
    ::= { tmnxBsxAppProfEntry 1 }

tmnxBsxAppProfRowStatus          OBJECT-TYPE
    SYNTAX      RowStatus
    MAX-ACCESS  read-create
    STATUS      current
    DESCRIPTION
        "The value of tmnxBsxAppProfRowStatus specifies the
         row status.  It allows entries to be created and
         deleted in the tmnxBsxAppProfTable.  To delete an
         entry, all references to this profile by
         TIMETRA-SUBSCRIBER-MGMT-MIB::tmnxSubExplicitMapAppProfile
         in the TIMETRA-SUBSCRIBER-MGMT-MIB::tmnxSubExplicitMapTable
         or by TIMETRA-SUBSCRIBER-MGMT-MIB::tmnxSubHostInfoV2AppProfile
         in the TIMETRA-SUBSCRIBER-MGMT-MIB::tmnxSubHostInfoV2Table
         or by TIMETRA-SAP-MIB::sapIsaAaApplicationProfile
         in the TIMETRA-SAP-MIB::sapBaseInfoTable
         or by TIMETRA-SDP-MIB::sdpBindIsaAaApplicationProfile
         in the TIMETRA-SDP-MIB::sdpBindTable
         or by TIMETRA-BSX-NG-MIB::tmnxBsxTransitIpPolicyDefAppProf
         in the TIMETRA-BSX-NG-MIB::tmnxBsxTransitIpPolicyTable
         or by TIMETRA-BSX-NG-MIB::tmnxBsxTransIpPlcySubAppProfNm
         in the TIMETRA-BSX-NG-MIB::tmnxBsxTransitIpPolicySubTable
         or by  TIMETRA-BSX-NG-MIB::tmnxBsxTransPrefSubAppProfNm
         in the TIMETRA-BSX-NG-MIB::tmnxBsxTransPrefSubTable
         must be deleted.  Note that dynamic subscribers may still
         reference application profiles which have been deleted or
         were never created.  These subscribers will remain
         operationally down when in this state."
    ::= { tmnxBsxAppProfEntry 2 }

tmnxBsxAppProfDescription        OBJECT-TYPE
    SYNTAX      TItemDescription
    MAX-ACCESS  read-create
    STATUS      current
    DESCRIPTION
        "The value of tmnxBsxAppProfDescription specifies the description of
         the application profile."
    DEFVAL      { "" }
    ::= { tmnxBsxAppProfEntry 3 }

tmnxBsxAppProfDivert             OBJECT-TYPE
    SYNTAX      TruthValue
    MAX-ACCESS  read-create
    STATUS      current
    DESCRIPTION
        "The value of tmnxBsxAppProfDivert specifies whether to divert traffic
         to the AEM for subscribers using this application profile."
    DEFVAL      { false }
    ::= { tmnxBsxAppProfEntry 4 }

tmnxBsxAppProfCapacityCost       OBJECT-TYPE
    SYNTAX      Unsigned32 (1..65535)
    MAX-ACCESS  read-create
    STATUS      current
    DESCRIPTION
        "The value of tmnxBsxAppProfCapacityCost specifies the capacity cost
         for this application profile."
    DEFVAL      { 1 }
    ::= { tmnxBsxAppProfEntry 5 }

tmnxBsxAppProfRowLastChange      OBJECT-TYPE
    SYNTAX      TimeStamp
    MAX-ACCESS  read-only
    STATUS      current
    DESCRIPTION
        "The value of tmnxBsxAppProfRowLastChange indicates the last time,
         since system startup, a successful set was performed on this row."
    ::= { tmnxBsxAppProfEntry 6 }

tmnxBsxAppProfSubSuppressible    OBJECT-TYPE
    SYNTAX      TmnxEnabledDisabled
    MAX-ACCESS  read-create
    STATUS      current
    DESCRIPTION
        "The value of tmnxBsxAppProfSubSuppressible specifies whether or not to
         allow suppressing Application-Assurance for Enhanced Subscriber
         Management (ESM) subscribers using this application profile. When set
         to 'enabled (1)', Application-Assurance is suppressed if the
         subscriber is on a group-interface whose corresponding
         TIMETRA-SERV-MIB::iesIfEntry has iesIfSuppressAaSub set to 'enabled
         (1)'."
    DEFVAL      { disabled }
    ::= { tmnxBsxAppProfEntry 7 }

tmnxBsxAppProfDistributeByIp     OBJECT-TYPE
    SYNTAX      TmnxEnabledDisabled
    MAX-ACCESS  read-create
    STATUS      current
    DESCRIPTION
        "The value of tmnxBsxAppProfDistributeByIp..."
    DEFVAL      { disabled }
    ::= { tmnxBsxAppProfEntry 8 }

tmnxBsxAppProfCharTable          OBJECT-TYPE
    SYNTAX      SEQUENCE OF TmnxBsxAppProfCharEntry
    MAX-ACCESS  not-accessible
    STATUS      current
    DESCRIPTION
        "The tmnxBsxAppProfCharTable contains an entry for each
         application profile characteristic.  App profile
         characteristics are referenced by application qos
         policy to define specific policies for subscribers
         using this application profile."
    ::= { tmnxBsxPolicyObjs 8 }

tmnxBsxAppProfCharEntry          OBJECT-TYPE
    SYNTAX      TmnxBsxAppProfCharEntry
    MAX-ACCESS  not-accessible
    STATUS      current
    DESCRIPTION
        "Each tmnxBsxAppProfCharEntry specifies an application profile
         characteristic configured by the operator."
    INDEX       {
        tmnxBsxAppProfCharPolicyVersion,
        tmnxBsxAaGrpPartIndex,
        tmnxBsxAppProfCharProfName,
        tmnxBsxAppProfCharCharName
    }
    ::= { tmnxBsxAppProfCharTable 1 }

TmnxBsxAppProfCharEntry          ::= SEQUENCE
{
    tmnxBsxAppProfCharPolicyVersion  TmnxBsxPolicyVersion,
    tmnxBsxAppProfCharProfName       TNamedItem,
    tmnxBsxAppProfCharCharName       TNamedItem,
    tmnxBsxAppProfCharRowStatus      RowStatus,
    tmnxBsxAppProfCharValName        TNamedItem,
    tmnxBsxAppProfCharRowLastChange  TimeStamp
}

tmnxBsxAppProfCharPolicyVersion  OBJECT-TYPE
    SYNTAX      TmnxBsxPolicyVersion
    MAX-ACCESS  not-accessible
    STATUS      current
    DESCRIPTION
        "The value of tmnxBsxAppProfCharPolicyVersion specifies
         the version of the table being accessed.  The table
         is read-create only for the 'admin' version of the
         table.  The 'oper' version is read-only."
    ::= { tmnxBsxAppProfCharEntry 1 }

tmnxBsxAppProfCharProfName       OBJECT-TYPE
    SYNTAX      TNamedItem
    MAX-ACCESS  not-accessible
    STATUS      current
    DESCRIPTION
        "The value of tmnxBsxAppProfCharProfName specifies the name defined for
         the application profile."
    ::= { tmnxBsxAppProfCharEntry 2 }

tmnxBsxAppProfCharCharName       OBJECT-TYPE
    SYNTAX      TNamedItem
    MAX-ACCESS  not-accessible
    STATUS      current
    DESCRIPTION
        "The value of tmnxBsxAppProfCharCharName specifies the name defined for
         the application profile characteristic."
    ::= { tmnxBsxAppProfCharEntry 3 }

tmnxBsxAppProfCharRowStatus      OBJECT-TYPE
    SYNTAX      RowStatus
    MAX-ACCESS  read-create
    STATUS      current
    DESCRIPTION
        "The value of tmnxBsxAppProfCharRowStatus specifies the
         row status.  It allows entries to be created and
         deleted in the tmnxBsxAppProfCharTable.  There are no
         restrictions on deleting entries in this table."
    ::= { tmnxBsxAppProfCharEntry 4 }

tmnxBsxAppProfCharValName        OBJECT-TYPE
    SYNTAX      TNamedItem
    MAX-ACCESS  read-create
    STATUS      current
    DESCRIPTION
        "The value of tmnxBsxAppProfCharValName specifies the name defined for
         the application profile characteristic."
    ::= { tmnxBsxAppProfCharEntry 5 }

tmnxBsxAppProfCharRowLastChange  OBJECT-TYPE
    SYNTAX      TimeStamp
    MAX-ACCESS  read-only
    STATUS      current
    DESCRIPTION
        "The value of tmnxBsxAppProfCharRowLastChange indicates the last time,
         since system startup, a successful set was performed on this row."
    ::= { tmnxBsxAppProfCharEntry 6 }

tmnxBsxAqpTable                  OBJECT-TYPE
    SYNTAX      SEQUENCE OF TmnxBsxAqpEntry
    MAX-ACCESS  not-accessible
    STATUS      obsolete
    DESCRIPTION
        "The tmnxBsxAqpTable contains the application qos policy which is a set
         of entries containing match criteria defining actions to be taken
         within the AEM MDA."
    ::= { tmnxBsxPolicyObjs 9 }

tmnxBsxAqpEntry                  OBJECT-TYPE
    SYNTAX      TmnxBsxAqpEntry
    MAX-ACCESS  not-accessible
    STATUS      obsolete
    DESCRIPTION
        "Each tmnxBsxAqpEntry indicates a set of match criteria and
         corresponding actions to take."
    INDEX       {
        tmnxBsxAqpPolicyVersion,
        tmnxBsxAaGrpPartIndex,
        tmnxBsxAqpEntryId
    }
    ::= { tmnxBsxAqpTable 1 }

TmnxBsxAqpEntry                  ::= SEQUENCE
{
    tmnxBsxAqpPolicyVersion          TmnxBsxPolicyVersion,
    tmnxBsxAqpEntryId                TEntryId,
    tmnxBsxAqpRowStatus              RowStatus,
    tmnxBsxAqpDescription            TItemDescription,
    tmnxBsxAqpAdminState             TmnxAdminState,
    tmnxBsxAqpApplication            TNamedItemOrEmpty,
    tmnxBsxAqpApplicationOp          TmnxBsxOperator,
    tmnxBsxAqpAppGroup               TNamedItemOrEmpty,
    tmnxBsxAqpAppGroupOp             TmnxBsxOperator,
    tmnxBsxAqpTrafficDir             TmnxBsxDirection,
    tmnxBsxAqpSubscriber             TNamedItemOrEmpty,
    tmnxBsxAqpSubscriberOp           TmnxBsxOperator,
    tmnxBsxAqpDscp                   TDSCPNameOrEmpty,
    tmnxBsxAqpDscpOp                 TmnxBsxOperator,
    tmnxBsxAqpSapSubscrPortId        TmnxPortID,
    tmnxBsxAqpSapSubscrEncapValue    TmnxEncapVal,
    tmnxBsxAqpSapSubscrOp            TmnxBsxOperator,
    tmnxBsxAqpSrcAddressType         InetAddressType,
    tmnxBsxAqpSrcAddress             InetAddress,
    tmnxBsxAqpSrcAddressLength       InetAddressPrefixLength,
    tmnxBsxAqpSrcAddressOp           TmnxBsxOperator,
    tmnxBsxAqpSrcPortOp              TmnxBsxOperator,
    tmnxBsxAqpSrcPortLowValue        TTcpUdpPort,
    tmnxBsxAqpSrcPortHighValue       TTcpUdpPort,
    tmnxBsxAqpDstAddressType         InetAddressType,
    tmnxBsxAqpDstAddress             InetAddress,
    tmnxBsxAqpDstAddressLength       InetAddressPrefixLength,
    tmnxBsxAqpDstAddressOp           TmnxBsxOperator,
    tmnxBsxAqpDstPortOp              TmnxBsxOperator,
    tmnxBsxAqpDstPortLowValue        TTcpUdpPort,
    tmnxBsxAqpDstPortHighValue       TTcpUdpPort,
    tmnxBsxAqpSpokeSdpSubscr         SdpBindId,
    tmnxBsxAqpSpokeSdpSubscrOp       TmnxBsxOperator,
    tmnxBsxAqpAaSubscriberType       TmnxBsxAaSubscriberType,
    tmnxBsxAqpAaSubscriber           TmnxBsxAaSubscriber,
    tmnxBsxAqpAaSubscriberOp         TmnxBsxOperator,
    tmnxBsxAqpChargeGrp              TNamedItemOrEmpty,
    tmnxBsxAqpChargeGrpOp            TmnxBsxOperator,
    tmnxBsxAqpIpProtocolNum          TIpProtocol,
    tmnxBsxAqpIpProtocolNumOp        TmnxBsxOperator,
    tmnxBsxAqpDrop                   TruthValue,
    tmnxBsxAqpBwLimitPolicer         TNamedItemOrEmpty,
    tmnxBsxAqpFlowRatePolicer        TNamedItemOrEmpty,
    tmnxBsxAqpFlowCountPolicer       TNamedItemOrEmpty,
    tmnxBsxAqpRemarkFc               TFCNameOrEmpty,
    tmnxBsxAqpRemarkPriority         TPriorityOrDefault,
    tmnxBsxAqpRemarkDscpInProfile    TDSCPNameOrEmpty,
    tmnxBsxAqpRemarkDscpOutProfile   TDSCPNameOrEmpty,
    tmnxBsxAqpMirrorSource           TmnxServId,
    tmnxBsxAqpMirrorSourceAllIncl    TruthValue,
    tmnxBsxAqpHttpErrRedirName       TNamedItemOrEmpty,
    tmnxBsxAqpHttpRedirName          TNamedItemOrEmpty,
    tmnxBsxAqpHttpRedirFlowType      TmnxBsxAqpHttpRedirFlowType,
    tmnxBsxAqpHttpEnrichName         TNamedItemOrEmpty,
    tmnxBsxAqpRowLastChange          TimeStamp,
    tmnxBsxAqpSessionFilter          TNamedItemOrEmpty,
    tmnxBsxAqpAaSubErrors            TmnxBsxAqpAction,
    tmnxBsxAqpOutOfOrderFrags        TmnxBsxAqpAction,
    tmnxBsxAqpAaSubCutThru           TmnxBsxAqpAction,
    tmnxBsxAqpUrlFilter              TNamedItemOrEmpty,
    tmnxBsxAqpHttpNotif              TNamedItemOrEmpty
}

tmnxBsxAqpPolicyVersion          OBJECT-TYPE
    SYNTAX      TmnxBsxPolicyVersion
    MAX-ACCESS  not-accessible
    STATUS      obsolete
    DESCRIPTION
        "The value of tmnxBsxAqpPolicyVersion specifies the
         version of the table being accessed.  The table
         is read-create only for the 'admin' version of
         the table.  The 'oper' version is read-only."
    ::= { tmnxBsxAqpEntry 1 }

tmnxBsxAqpEntryId                OBJECT-TYPE
    SYNTAX      TEntryId
    MAX-ACCESS  not-accessible
    STATUS      obsolete
    DESCRIPTION
        "The value of tmnxBsxAqpEntryId specifies the index into the filter
         list that resolve applications."
    ::= { tmnxBsxAqpEntry 2 }

tmnxBsxAqpRowStatus              OBJECT-TYPE
    SYNTAX      RowStatus
    MAX-ACCESS  read-create
    STATUS      obsolete
    DESCRIPTION
        "The value of tmnxBsxAqpRowStatus specifies
         the row status.  It allows entries to be created
         and deleted in the tmnxBsxAqpTable."
    ::= { tmnxBsxAqpEntry 3 }

tmnxBsxAqpDescription            OBJECT-TYPE
    SYNTAX      TItemDescription
    MAX-ACCESS  read-create
    STATUS      obsolete
    DESCRIPTION
        "The value of tmnxBsxAqpDescription specifies the description of the
         application."
    DEFVAL      { "" }
    ::= { tmnxBsxAqpEntry 4 }

tmnxBsxAqpAdminState             OBJECT-TYPE
    SYNTAX      TmnxAdminState
    MAX-ACCESS  read-create
    STATUS      obsolete
    DESCRIPTION
        "The value of tmnxBsxAqpAdminState specifies the
         administrative state for the application.  When
         'outOfService', any match entries referring to this
         application are skipped."
    DEFVAL      { outOfService }
    ::= { tmnxBsxAqpEntry 5 }

tmnxBsxAqpApplication            OBJECT-TYPE
    SYNTAX      TNamedItemOrEmpty
    MAX-ACCESS  read-create
    STATUS      obsolete
    DESCRIPTION
        "The value of tmnxBsxAqpApplication specifies
         the particular application to match against
         to resolve to an AQP action.  If set to an empty
         string, no match on application is done.

         If an attempt is made to set this object to a string that does not
         match a tmnxBsxAppName value from the tmnxBsxAppCfgTable, an
         'inconsistentValue' error is returned."
    DEFVAL      { "" }
    ::= { tmnxBsxAqpEntry 6 }

tmnxBsxAqpApplicationOp          OBJECT-TYPE
    SYNTAX      TmnxBsxOperator
    MAX-ACCESS  read-create
    STATUS      obsolete
    DESCRIPTION
        "The value of tmnxBsxAqpApplicationOp specifies the operator to apply
         in relation to tmnxBsxAqpApplication to match against to resolve an
         AQP action."
    DEFVAL      { none }
    ::= { tmnxBsxAqpEntry 7 }

tmnxBsxAqpAppGroup               OBJECT-TYPE
    SYNTAX      TNamedItemOrEmpty
    MAX-ACCESS  read-create
    STATUS      obsolete
    DESCRIPTION
        "The value of tmnxBsxAqpAppGroup specifies the
         particular application group to match against to
         resolve to an AQP action.  If set to an empty string,
         no match on application group is done.

         If an attempt is made to set this object to a string that does not
         match a tmnxBsxAppGrpName value from the tmnxBsxAppGrpCfgTable, an
         'inconsistentValue' error is returned."
    DEFVAL      { "" }
    ::= { tmnxBsxAqpEntry 8 }

tmnxBsxAqpAppGroupOp             OBJECT-TYPE
    SYNTAX      TmnxBsxOperator
    MAX-ACCESS  read-create
    STATUS      obsolete
    DESCRIPTION
        "The value of tmnxBsxAqpAppGroupOp specifies the operator to apply in
         relation to tmnxBsxAqpAppGroup to match against to resolve an AQP
         action."
    DEFVAL      { none }
    ::= { tmnxBsxAqpEntry 9 }

tmnxBsxAqpTrafficDir             OBJECT-TYPE
    SYNTAX      TmnxBsxDirection
    MAX-ACCESS  read-create
    STATUS      obsolete
    DESCRIPTION
        "The value of tmnxBsxAqpTrafficDir specifies the
         traffic directions to match against to resolve to
         an AQP action.  This allows different policer
         bandwidths to apply in each direction."
    DEFVAL      { both }
    ::= { tmnxBsxAqpEntry 10 }

tmnxBsxAqpSubscriber             OBJECT-TYPE
    SYNTAX      TNamedItemOrEmpty
    MAX-ACCESS  read-create
    STATUS      obsolete
    DESCRIPTION
        "The value of tmnxBsxAqpSubscriber specifies the
         particular subscriber to match against to resolve
         to an AQP action.  If the value does not exist in
         TIMETRA-SUBSCRIBER-MGMT-MIB::tmnxSubInfoSubIdent
         in the tmnxSubscriberInfoTable, no error is
         returned.  Instead, no match will be done on the
         subscriber until the entry is populated.  If set
         to an empty string, no match on subscriber is
         done.

         This object was obsoleted in R9.0 and replaced with the
         tmnxBsxAqpAaSubscriber object."
    DEFVAL      { "" }
    ::= { tmnxBsxAqpEntry 11 }

tmnxBsxAqpSubscriberOp           OBJECT-TYPE
    SYNTAX      TmnxBsxOperator
    MAX-ACCESS  read-create
    STATUS      obsolete
    DESCRIPTION
        "The value of tmnxBsxAqpSubscriberOp specifies the operator to apply in
         relation to tmnxBsxAqpSubscriber to match against to resolve an AQP
         action.

         This object was obsoleted in R9.0 and replaced with the
         tmnxBsxAqpAaSubscriberOp object."
    DEFVAL      { none }
    ::= { tmnxBsxAqpEntry 12 }

tmnxBsxAqpDscp                   OBJECT-TYPE
    SYNTAX      TDSCPNameOrEmpty
    MAX-ACCESS  read-create
    STATUS      obsolete
    DESCRIPTION
        "The value of tmnxBsxAqpDscp specifies the DSCP name to match to
         resolve to an AQP action. An empty string will allow all DHCP values
         to match."
    DEFVAL      { "" }
    ::= { tmnxBsxAqpEntry 13 }

tmnxBsxAqpDscpOp                 OBJECT-TYPE
    SYNTAX      TmnxBsxOperator
    MAX-ACCESS  read-create
    STATUS      obsolete
    DESCRIPTION
        "The value of tmnxBsxAqpDscpOp specifies the operator to apply in
         relation to tmnxBsxAqpDscp to match against to resolve an AQP action."
    DEFVAL      { none }
    ::= { tmnxBsxAqpEntry 14 }

tmnxBsxAqpSapSubscrPortId        OBJECT-TYPE
    SYNTAX      TmnxPortID
    MAX-ACCESS  read-create
    STATUS      obsolete
    DESCRIPTION
        "The value of tmnxBsxAqpSapSubscrPortId along with
         tmnxBsxAqpSapSubscrEncapValue specifies a Service Access Point (SAP)
         subscriber. A SAP subscriber matching this criteria is used to resolve
         to an AQP action.

         This object was obsoleted in R9.0 and replaced with the
         tmnxBsxAqpAaSubscriber object."
    DEFVAL      { 0 }
    ::= { tmnxBsxAqpEntry 15 }

tmnxBsxAqpSapSubscrEncapValue    OBJECT-TYPE
    SYNTAX      TmnxEncapVal
    MAX-ACCESS  read-create
    STATUS      obsolete
    DESCRIPTION
        "The value of tmnxBsxAqpSapSubscrPortId along with
         tmnxBsxAqpSapSubscrEncapValue specifies a Service Access Point (SAP)
         subscriber. A SAP subscriber matching this criteria is used to resolve
         to an AQP action.

         This object was obsoleted in R9.0 and replaced with the
         tmnxBsxAqpAaSubscriber object."
    DEFVAL      { 0 }
    ::= { tmnxBsxAqpEntry 16 }

tmnxBsxAqpSapSubscrOp            OBJECT-TYPE
    SYNTAX      TmnxBsxOperator
    MAX-ACCESS  read-create
    STATUS      obsolete
    DESCRIPTION
        "The value of tmnxBsxAqpSapSubscrOp specifies, along with the Service
         Access Point (SAP) indicated by tmnxBsxAqpSapSubscrPortId and
         tmnxBsxAqpSapSubscrEncapValue, the operator to match against to
         resolve to an AQP action.

         This object was obsoleted in R9.0 and replaced with the
         tmnxBsxAqpAaSubscriberOp object."
    DEFVAL      { none }
    ::= { tmnxBsxAqpEntry 17 }

tmnxBsxAqpSrcAddressType         OBJECT-TYPE
    SYNTAX      InetAddressType
    MAX-ACCESS  read-create
    STATUS      obsolete
    DESCRIPTION
        "The value of tmnxBsxAqpSrcAddressType specifies the type of address
         contained in tmnxBsxAqpSrcAddress.

         A value of 'unknown (0)' specifies that no matching is to be done to
         resolve to an AQP action."
    DEFVAL      { unknown }
    ::= { tmnxBsxAqpEntry 18 }

tmnxBsxAqpSrcAddress             OBJECT-TYPE
    SYNTAX      InetAddress (SIZE (0|4|16))
    MAX-ACCESS  read-create
    STATUS      obsolete
    DESCRIPTION
        "The value of tmnxBsxAqpSrcAddress specifies the source address to
         match to resolve to an AQP action."
    DEFVAL      { ''H }
    ::= { tmnxBsxAqpEntry 19 }

tmnxBsxAqpSrcAddressLength       OBJECT-TYPE
    SYNTAX      InetAddressPrefixLength (0..128)
    MAX-ACCESS  read-create
    STATUS      obsolete
    DESCRIPTION
        "The value of tmnxBsxAqpSrcAddressLength specifies the number of
         relevant bits of the tmnxBsxAqpSrcAddress."
    DEFVAL      { 0 }
    ::= { tmnxBsxAqpEntry 20 }

tmnxBsxAqpSrcAddressOp           OBJECT-TYPE
    SYNTAX      TmnxBsxOperator
    MAX-ACCESS  read-create
    STATUS      obsolete
    DESCRIPTION
        "The value of tmnxBsxAqpSrcAddressOp specifies the operator to apply in
         relation to tmnxBsxAqpSrcAddressType, tmnxBsxAqpSrcAddress, and
         tmnxBsxAqpSrcAddressLength to match against to resolve to an AQP
         action."
    DEFVAL      { none }
    ::= { tmnxBsxAqpEntry 21 }

tmnxBsxAqpSrcPortOp              OBJECT-TYPE
    SYNTAX      TmnxBsxOperator
    MAX-ACCESS  read-create
    STATUS      obsolete
    DESCRIPTION
        "The value of tmnxBsxAqpSrcPortOp specifies the operator to apply in
         relation to the tmnxBsxAqpSrcPortLowValue and
         tmnxBsxAqpSrcPortHighValue objects.

         A value of 'none (0)' indicates that no match is done on the
         tmnxBsxAqpSrcPortLowValue and tmnxBsxAqpSrcPortHighValue objects."
    DEFVAL      { none }
    ::= { tmnxBsxAqpEntry 22 }

tmnxBsxAqpSrcPortLowValue        OBJECT-TYPE
    SYNTAX      TTcpUdpPort
    MAX-ACCESS  read-create
    STATUS      obsolete
    DESCRIPTION
        "The value of tmnxBsxAqpSrcPortLowValue specifies the low source TCP or
         UDP port number to match to resolve to an AQP action.
         tmnxBsxAqpSrcPortLowValue must be less than or equal to
         tmnxBsxAqpSrcPortHighValue, and is used when the tmnxBsxAqpSrcPortOp
         is not 'none (0)'."
    DEFVAL      { 0 }
    ::= { tmnxBsxAqpEntry 23 }

tmnxBsxAqpSrcPortHighValue       OBJECT-TYPE
    SYNTAX      TTcpUdpPort
    MAX-ACCESS  read-create
    STATUS      obsolete
    DESCRIPTION
        "The value of tmnxBsxAqpSrcPortHighValue specifies the high source TCP
         or UDP port number to match to resolve to an AQP action.
         tmnxBsxAqpSrcPortHighValue must be greater than or equal to
         tmnxBsxAqpSrcPortLowValue, and is used when the tmnxBsxAqpSrcPortOp is
         not 'none (0)'."
    DEFVAL      { 0 }
    ::= { tmnxBsxAqpEntry 24 }

tmnxBsxAqpDstAddressType         OBJECT-TYPE
    SYNTAX      InetAddressType
    MAX-ACCESS  read-create
    STATUS      obsolete
    DESCRIPTION
        "The value of tmnxBsxAqpDstAddressType specifies the type of address
         contained in tmnxBsxAqpDstAddress.

         A value of 'unknown (0)' specifies that no matching is to be done to
         resolve to an AQP action."
    DEFVAL      { unknown }
    ::= { tmnxBsxAqpEntry 25 }

tmnxBsxAqpDstAddress             OBJECT-TYPE
    SYNTAX      InetAddress (SIZE (0|4|16))
    MAX-ACCESS  read-create
    STATUS      obsolete
    DESCRIPTION
        "The value of tmnxBsxAqpDstAddress specifies the destination address to
         match to resolve to an AQP action."
    DEFVAL      { ''H }
    ::= { tmnxBsxAqpEntry 26 }

tmnxBsxAqpDstAddressLength       OBJECT-TYPE
    SYNTAX      InetAddressPrefixLength (0..128)
    MAX-ACCESS  read-create
    STATUS      obsolete
    DESCRIPTION
        "The value of tmnxBsxAqpDstAddressLength specifies the number of
         relevant bits of the tmnxBsxAqpDstAddress."
    DEFVAL      { 0 }
    ::= { tmnxBsxAqpEntry 27 }

tmnxBsxAqpDstAddressOp           OBJECT-TYPE
    SYNTAX      TmnxBsxOperator
    MAX-ACCESS  read-create
    STATUS      obsolete
    DESCRIPTION
        "The value of tmnxBsxAqpDstAddressOp specifies the operator to apply in
         relation to tmnxBsxAqpDstAddressType, tmnxBsxAqpDstAddress, and
         tmnxBsxAqpDstAddressLength to match against to resolve to an AQP
         action."
    DEFVAL      { none }
    ::= { tmnxBsxAqpEntry 28 }

tmnxBsxAqpDstPortOp              OBJECT-TYPE
    SYNTAX      TmnxBsxOperator
    MAX-ACCESS  read-create
    STATUS      obsolete
    DESCRIPTION
        "The value of tmnxBsxAqpDstPortOp specifies the operator to apply in
         relation to the tmnxBsxAqpDstPortLowValue and
         tmnxBsxAqpDstPortHighValue objects.

         A value of 'none (0)' indicates that no match is done on the
         tmnxBsxAqpDstPortLowValue and tmnxBsxAqpDstPortHighValue objects."
    DEFVAL      { none }
    ::= { tmnxBsxAqpEntry 29 }

tmnxBsxAqpDstPortLowValue        OBJECT-TYPE
    SYNTAX      TTcpUdpPort
    MAX-ACCESS  read-create
    STATUS      obsolete
    DESCRIPTION
        "The value of tmnxBsxAqpDstPortLowValue specifies the low destination
         TCP or UDP port number to match to resolve to an AQP action.
         tmnxBsxAqpDstPortLowValue must be less than or equal to
         tmnxBsxAqpDstPortHighValue, and is used when the tmnxBsxAqpDstPortOp
         is not 'none (0)'."
    DEFVAL      { 0 }
    ::= { tmnxBsxAqpEntry 30 }

tmnxBsxAqpDstPortHighValue       OBJECT-TYPE
    SYNTAX      TTcpUdpPort
    MAX-ACCESS  read-create
    STATUS      obsolete
    DESCRIPTION
        "The value of tmnxBsxAqpDstPortHighValue specifies the high destination
         TCP or UDP port number to match to resolve to an AQP action.
         tmnxBsxAqpDstPortHighValue must be greater than or equal to
         tmnxBsxAqpDstPortLowValue, and is used when the tmnxBsxAqpDstPortOp is
         not 'none (0)'."
    DEFVAL      { 0 }
    ::= { tmnxBsxAqpEntry 31 }

tmnxBsxAqpSpokeSdpSubscr         OBJECT-TYPE
    SYNTAX      SdpBindId
    MAX-ACCESS  read-create
    STATUS      obsolete
    DESCRIPTION
        "The value of tmnxBsxAqpSpokeSdpSubscr specifies a Spoke SDP subscriber
         to match against to resolve to an AQP action.

         This object was obsoleted in R9.0 and replaced with the
         tmnxBsxAqpAaSubscriber object."
    DEFVAL      { '0000000000000000'H }
    ::= { tmnxBsxAqpEntry 32 }

tmnxBsxAqpSpokeSdpSubscrOp       OBJECT-TYPE
    SYNTAX      TmnxBsxOperator
    MAX-ACCESS  read-create
    STATUS      obsolete
    DESCRIPTION
        "The value of tmnxBsxAqpSpokeSdpSubscrOp specifies the operator to
         apply in relation to tmnxBsxAqpSpokeSdpSubscr to match against to
         resolve an AQP action.

         This object was obsoleted in R9.0 and replaced with the
         tmnxBsxAqpAaSubscriberOp object."
    DEFVAL      { none }
    ::= { tmnxBsxAqpEntry 33 }

tmnxBsxAqpAaSubscriberType       OBJECT-TYPE
    SYNTAX      TmnxBsxAaSubscriberType
    MAX-ACCESS  read-create
    STATUS      obsolete
    DESCRIPTION
        "The value of tmnxBsxAqpAaSubscriberType specifies the type of
         subscriber identified by tmnxBsxAqpAaSubscriber. The values of
         tmnxBsxAqpAaSubscriberType and tmnxBsxAqpAaSubscriber must be set
         together in a single SNMP multi-variable SetRequest-PDU.

         If set to 'unknown(0)', no match on a subscriber is done."
    DEFVAL      { unknown }
    ::= { tmnxBsxAqpEntry 34 }

tmnxBsxAqpAaSubscriber           OBJECT-TYPE
    SYNTAX      TmnxBsxAaSubscriber
    MAX-ACCESS  read-create
    STATUS      obsolete
    DESCRIPTION
        "The value of tmnxBsxAqpAaSubscriber specifies the subscriber of type
         tmnxBsxAqpAaSubscriberType to match against to resolve to an AQP
         action. The values of tmnxBsxAqpAaSubscriberType and
         tmnxBsxAqpAaSubscriber must be set together in a single SNMP
         multi-variable SetRequest-PDU.

         If set to an empty string, no match on a subscriber is done."
    DEFVAL      { "" }
    ::= { tmnxBsxAqpEntry 35 }

tmnxBsxAqpAaSubscriberOp         OBJECT-TYPE
    SYNTAX      TmnxBsxOperator
    MAX-ACCESS  read-create
    STATUS      obsolete
    DESCRIPTION
        "The value of tmnxBsxAqpAaSubscriberOp specifies the operator to apply
         in relation to tmnxBsxAqpAaSubscriber to match against to resolve an
         AQP action.

         If set to 'none(0)', no match on a subscriber is done."
    DEFVAL      { none }
    ::= { tmnxBsxAqpEntry 36 }

tmnxBsxAqpChargeGrp              OBJECT-TYPE
    SYNTAX      TNamedItemOrEmpty
    MAX-ACCESS  read-create
    STATUS      obsolete
    DESCRIPTION
        "The value of tmnxBsxAqpChargeGrp along with tmnxBsxAqpChargeGrpOp
         specifies the charging group and operation to match against to resolve
         to an AQP action.

         If set to an empty string or the operation is none, no match on the
         charging group is done.

         If an attempt is made to set this object to a non-empty string that
         does not match a tmnxBsxChargeGrpName value from the
         tmnxBsxChargeGrpCfgTable, an 'inconsistentValue' error is returned."
    DEFVAL      { "" }
    ::= { tmnxBsxAqpEntry 37 }

tmnxBsxAqpChargeGrpOp            OBJECT-TYPE
    SYNTAX      TmnxBsxOperator
    MAX-ACCESS  read-create
    STATUS      obsolete
    DESCRIPTION
        "The value of tmnxBsxAqpChargeGrpOp specifies the operator to apply in
         relation to tmnxBsxAqpChargeGrp to match against to resolve an AQP
         action."
    DEFVAL      { none }
    ::= { tmnxBsxAqpEntry 38 }

tmnxBsxAqpIpProtocolNum          OBJECT-TYPE
    SYNTAX      TIpProtocol
    MAX-ACCESS  read-create
    STATUS      obsolete
    DESCRIPTION
        "The value of tmnxBsxAqpIpProtocolNum along with
         tmnxBsxAqpIpProtocolNumOp specifies the IP protocol number to match to
         resolve to an AQP action.

         A value of '-1' specifies that no matching is to be done. A value of
         '-2' along with an operation not equal to none specifies that a match
         will occur if the protocol is TCP or UDP."
    DEFVAL      { -1 }
    ::= { tmnxBsxAqpEntry 39 }

tmnxBsxAqpIpProtocolNumOp        OBJECT-TYPE
    SYNTAX      TmnxBsxOperator
    MAX-ACCESS  read-create
    STATUS      obsolete
    DESCRIPTION
        "The value of tmnxBsxAqpIpProtocolNumOp specifies the operator to apply
         in relation to tmnxBsxAqpIpProtocolNum to match against to resolve an
         AQP action."
    DEFVAL      { none }
    ::= { tmnxBsxAqpEntry 40 }

tmnxBsxAqpDrop                   OBJECT-TYPE
    SYNTAX      TruthValue
    MAX-ACCESS  read-create
    STATUS      obsolete
    DESCRIPTION
        "The value of tmnxBsxAqpDrop specifies that flows matching this policy
         are to be dropped."
    DEFVAL      { false }
    ::= { tmnxBsxAqpEntry 50 }

tmnxBsxAqpBwLimitPolicer         OBJECT-TYPE
    SYNTAX      TNamedItemOrEmpty
    MAX-ACCESS  read-create
    STATUS      obsolete
    DESCRIPTION
        "The value of tmnxBsxAqpBwLimitPolicer specifies flows matching this
         policy are to be policed using the template defined in
         tmnxBsxPolicerTable.

         If more than one AQP entry refers to the same policer, the same
         policer instances will be used.

         If an attempt is made to set this object to a string that does not
         match a tmnxBsxPolicerName value from the tmnxBsxPolicerTable, an
         'inconsistentValue' error is returned."
    DEFVAL      { "" }
    ::= { tmnxBsxAqpEntry 51 }

tmnxBsxAqpFlowRatePolicer        OBJECT-TYPE
    SYNTAX      TNamedItemOrEmpty
    MAX-ACCESS  read-create
    STATUS      obsolete
    DESCRIPTION
        "The value of tmnxBsxAqpFlowRatePolicer specifies flows matching this
         policy are to be policed using the template defined in
         tmnxBsxPolicerTable.

         If more than one AQP entry refers to the same policer, the same
         policer instances will be used.

         If an attempt is made to set this object to a string that does not
         match a tmnxBsxPolicerName value from the tmnxBsxPolicerTable, an
         'inconsistentValue' error is returned."
    DEFVAL      { "" }
    ::= { tmnxBsxAqpEntry 52 }

tmnxBsxAqpFlowCountPolicer       OBJECT-TYPE
    SYNTAX      TNamedItemOrEmpty
    MAX-ACCESS  read-create
    STATUS      obsolete
    DESCRIPTION
        "The value of tmnxBsxAqpFlowCountPolicer specifies flows matching this
         policy are to be limited using the template defined in
         tmnxBsxPolicerTable.

         If more than one AQP entry refers to the same policer, the same
         policer instances will be used.

         If an attempt is made to set this object to a string that does not
         match a tmnxBsxPolicerName value from the tmnxBsxPolicerTable, an
         'inconsistentValue' error is returned."
    DEFVAL      { "" }
    ::= { tmnxBsxAqpEntry 53 }

tmnxBsxAqpRemarkFc               OBJECT-TYPE
    SYNTAX      TFCNameOrEmpty
    MAX-ACCESS  read-create
    STATUS      obsolete
    DESCRIPTION
        "The value of tmnxBsxAqpRemarkFc specifies the name of the forwarding
         class to use to remark flows that match this policy. An empty string
         value, ''H, specifies no modification to the forwarding class."
    DEFVAL      { ''H }
    ::= { tmnxBsxAqpEntry 54 }

tmnxBsxAqpRemarkPriority         OBJECT-TYPE
    SYNTAX      TPriorityOrDefault
    MAX-ACCESS  read-create
    STATUS      obsolete
    DESCRIPTION
        "The value of tmnxBsxAqpRemarkPriority specifies the priority to use to
         remark flows that match this policy. A value of 'default' specifies no
         modification to the priority."
    DEFVAL      { default }
    ::= { tmnxBsxAqpEntry 55 }

tmnxBsxAqpRemarkDscpInProfile    OBJECT-TYPE
    SYNTAX      TDSCPNameOrEmpty
    MAX-ACCESS  read-create
    STATUS      obsolete
    DESCRIPTION
        "The value of tmnxBsxAqpRemarkDscpInProfile specifies the DSCP name to
         use to remark in-profile flows that match this policy. An empty string
         value, ''H, specifies no modification to the DSCP value."
    DEFVAL      { ''H }
    ::= { tmnxBsxAqpEntry 56 }

tmnxBsxAqpRemarkDscpOutProfile   OBJECT-TYPE
    SYNTAX      TDSCPNameOrEmpty
    MAX-ACCESS  read-create
    STATUS      obsolete
    DESCRIPTION
        "The value of tmnxBsxAqpRemarkDscpOutProfile specifies the DSCP name to
         use to remark out-of-profile flows that match this policy. An empty
         string value, ''H, specifies no modification to the DSCP value."
    DEFVAL      { ''H }
    ::= { tmnxBsxAqpEntry 57 }

tmnxBsxAqpMirrorSource           OBJECT-TYPE
    SYNTAX      TmnxServId
    MAX-ACCESS  read-create
    STATUS      obsolete
    DESCRIPTION
        "The value of tmnxBsxAqpMirrorSource specifies the mirror source
         service id, as defined in the TIMETRA-MIRROR-MIB, to use for flows
         that match this policy. A value of 0 specifies no mirror is set."
    DEFVAL      { 0 }
    ::= { tmnxBsxAqpEntry 58 }

tmnxBsxAqpMirrorSourceAllIncl    OBJECT-TYPE
    SYNTAX      TruthValue
    MAX-ACCESS  read-create
    STATUS      obsolete
    DESCRIPTION
        "The value of tmnxBsxAqpMirrorSourceAllIncl specifies that all flows
         matching the subscriber default policy will be mirrored until the
         protocol is identified. The tmnxBsxAqpMirrorSource must be set to a
         valid mirror."
    DEFVAL      { false }
    ::= { tmnxBsxAqpEntry 59 }

tmnxBsxAqpHttpErrRedirName       OBJECT-TYPE
    SYNTAX      TNamedItemOrEmpty
    MAX-ACCESS  read-create
    STATUS      obsolete
    DESCRIPTION
        "The value of tmnxBsxAqpHttpErrRedirName specifies the HTTP error
         redirect that will be applied as defined in the
         tmnxBsxHttpRedirErrTable. An empty value specifies no HTTP error
         redirect."
    DEFVAL      { "" }
    ::= { tmnxBsxAqpEntry 60 }

tmnxBsxAqpHttpRedirName          OBJECT-TYPE
    SYNTAX      TNamedItemOrEmpty
    MAX-ACCESS  read-create
    STATUS      obsolete
    DESCRIPTION
        "The value of tmnxBsxAqpHttpRedirName specifies the HTTP redirect that
         will be applied as defined in the tmnxBsxHttpRedirTable. An empty
         value specifies no HTTP redirect.

         A tmnxBsxAqpHttpRedirFlowType must have a value other than 'none(0)'
         if tmnxBsxAqpHttpRedirName is not an empty string."
    DEFVAL      { "" }
    ::= { tmnxBsxAqpEntry 61 }

tmnxBsxAqpHttpRedirFlowType      OBJECT-TYPE
    SYNTAX      TmnxBsxAqpHttpRedirFlowType
    MAX-ACCESS  read-create
    STATUS      obsolete
    DESCRIPTION
        "The value of tmnxBsxAqpHttpRedirFlowType specifies the type of flow
         that will be redirected.

         A tmnxBsxAqpHttpRedirName must be specified if
         tmnxBsxAqpHttpRedirFlowType has a value other than 'none(0)'."
    DEFVAL      { none }
    ::= { tmnxBsxAqpEntry 62 }

tmnxBsxAqpHttpEnrichName         OBJECT-TYPE
    SYNTAX      TNamedItemOrEmpty
    MAX-ACCESS  read-create
    STATUS      obsolete
    DESCRIPTION
        "The value of tmnxBsxAqpHttpEnrichName specifies the HTTP header
         enrichment template that will be applied as defined in the
         tmnxBsxHttpEnrichTable. An empty value specifies no HTTP header
         enrichment template."
    DEFVAL      { "" }
    ::= { tmnxBsxAqpEntry 63 }

tmnxBsxAqpRowLastChange          OBJECT-TYPE
    SYNTAX      TimeStamp
    MAX-ACCESS  read-only
    STATUS      obsolete
    DESCRIPTION
        "The value of tmnxBsxAqpRowLastChange indicates the last time, since
         system startup, a successful set was performed on this row."
    ::= { tmnxBsxAqpEntry 64 }

tmnxBsxAqpSessionFilter          OBJECT-TYPE
    SYNTAX      TNamedItemOrEmpty
    MAX-ACCESS  read-create
    STATUS      obsolete
    DESCRIPTION
        "The value of tmnxBsxAqpSessionFilter specifies the
         Application-Assurance session filter that will be evaluated. An empty
         value specifies no session filters will be evaluated."
    DEFVAL      { "" }
    ::= { tmnxBsxAqpEntry 65 }

tmnxBsxAqpAaSubErrors            OBJECT-TYPE
    SYNTAX      TmnxBsxAqpAction
    MAX-ACCESS  read-create
    STATUS      obsolete
    DESCRIPTION
        "The value of tmnxBsxAqpAaSubErrors specifies the action that will be
         applied to errored frames in one or both directions of traffic flow
         based on the match criteria."
    DEFVAL      { allow }
    ::= { tmnxBsxAqpEntry 66 }

tmnxBsxAqpOutOfOrderFrags        OBJECT-TYPE
    SYNTAX      TmnxBsxAqpAction
    MAX-ACCESS  read-create
    STATUS      obsolete
    DESCRIPTION
        "The value of tmnxBsxAqpOutOfOrderFrags specifies the action that will
         be applied to fragments received out of sequence in one or both
         directions of traffic flow based on the match criteria."
    DEFVAL      { allow }
    ::= { tmnxBsxAqpEntry 67 }

tmnxBsxAqpAaSubCutThru           OBJECT-TYPE
    SYNTAX      TmnxBsxAqpAction
    MAX-ACCESS  read-create
    STATUS      obsolete
    DESCRIPTION
        "The value of tmnxBsxAqpAaSubCutThru specifies the action that will be
         applied to traffic which is cut-through in one or both directions of
         traffic flow based on the match criteria."
    DEFVAL      { allow }
    ::= { tmnxBsxAqpEntry 68 }

tmnxBsxAqpUrlFilter              OBJECT-TYPE
    SYNTAX      TNamedItemOrEmpty
    MAX-ACCESS  read-create
    STATUS      obsolete
    DESCRIPTION
        "The value of tmnxBsxAqpUrlFilter specifies the Application-Assurance
         URL filter that will be evaluated. An empty value specifies no URL
         filters will be evaluated."
    DEFVAL      { "" }
    ::= { tmnxBsxAqpEntry 69 }

tmnxBsxAqpHttpNotif              OBJECT-TYPE
    SYNTAX      TNamedItemOrEmpty
    MAX-ACCESS  read-create
    STATUS      obsolete
    DESCRIPTION
        "The value of tmnxBsxAqpHttpNotif specifies the Application-Assurance
         Http Notification that will be applied as defined in the
         tmnxBsxHttpNotifTable. An empty value specifies no HTTP notification
         will occur."
    DEFVAL      { "" }
    ::= { tmnxBsxAqpEntry 70 }

tmnxBsxAdminControl              OBJECT IDENTIFIER ::= { tmnxBsxPolicyObjs 10 }

tmnxBsxAdminOwner                OBJECT-TYPE
    SYNTAX      TNamedItemOrEmpty
    MAX-ACCESS  read-write
    STATUS      obsolete
    DESCRIPTION
        "The value of tmnxBsxAdminOwner specifies who has last initialized the
         configuration tables, who is making all the changes, and who is
         expected to either commit or re-initialize (abort) the transaction.

         tmnxBsxAdminOwner is advisory only.  Before
         beginning a transaction, read tmnxBsxAdminOwner.
         If it is empty then proceed with the
         configuration.  Set tmnxBsxAdminOwner after
         setting tmnxBsxAdminControlApply so that other
         users will be advised to not make changes to the
         tables.

         The agent automatically sets tmnxBsxAdminOwner to an empty string
         after tmnxBsxAdminControlApply is set, either by the user
         re-initializing or committing, or by the agent timing out the
         uncommitted transaction.

         This object was obsoleted in release 8.0 and replaced with the
         tmnxBsxAdminCtrlConfigOwner in the tmnxBsxAdminCtrlTable."
    DEFVAL      { "" }
    ::= { tmnxBsxAdminControl 1 }

tmnxBsxAdminControlApply         OBJECT-TYPE
    SYNTAX      INTEGER {
        none       (1),
        initialize (2),
        commit     (3)
    }
    MAX-ACCESS  read-write
    STATUS      obsolete
    DESCRIPTION
        "The value of tmnxBsxAdminControlApply specifies
         the copying of tmnxBsxPolicyObjs tables from
         one instance of policy version to another.  This
         object reads as none(1) when not editing policy
         and initialize(2) when editing policy.

         When set to initialize(2), the objects in
         tmnxBsxPolicyObjs with the policy version
         index set to 'admin' are set to the values
         with the index set to 'oper' in the same
         tables.  Any uncommitted changes are lost,
         so setting this value corresponds to both
         BEGIN-TRANSACTION and ABORT-TRANSACTION.

         When set to commit(3) (END-TRANSACTION), all
         of the objects from tables with the index
         set to 'admin' are copied to the same items
         with the index set to 'oper'.  Then, the BSX
         policy is evaluated for correctness and
         applied to all BSX MDAs.

         In this way, the (expensive) policy application can be performed at
         one time, with a coherent BSX policy configuration.

         This object was obsoleted in release 8.0 and replaced with the
         tmnxBsxAdminCtrlApply in the tmnxBsxAdminCtrlTable."
    ::= { tmnxBsxAdminControl 2 }

tmnxBsxAdminLastChangeTime       OBJECT-TYPE
    SYNTAX      TimeStamp
    MAX-ACCESS  read-only
    STATUS      obsolete
    DESCRIPTION
        "The value of tmnxBsxAdminLastChangeTime indicates the last time a
         successful set was performed of tmnxBsxAdminControlApply to 'commit'.

         This object was obsoleted in release 8.0 and replaced with the
         tmnxBsxAdminCtrlLastChTime in the tmnxBsxAdminCtrlTable."
    ::= { tmnxBsxAdminControl 3 }

tmnxBsxAdminCtrlTable            OBJECT-TYPE
    SYNTAX      SEQUENCE OF TmnxBsxAdminCtrlEntry
    MAX-ACCESS  not-accessible
    STATUS      current
    DESCRIPTION
        "The tmnxBsxAdminCtrlTable contains the admin control handling for the
         BSX policy configuration for each Application Assurance group and
         partition."
    ::= { tmnxBsxAdminControl 4 }

tmnxBsxAdminCtrlEntry            OBJECT-TYPE
    SYNTAX      TmnxBsxAdminCtrlEntry
    MAX-ACCESS  not-accessible
    STATUS      current
    DESCRIPTION
        "Each tmnxBsxAdminCtrlEntry specifies the admin controls configured by
         the operator within an application assurance group and partition."
    INDEX       { tmnxBsxAaGrpPartIndex }
    ::= { tmnxBsxAdminCtrlTable 1 }

TmnxBsxAdminCtrlEntry            ::= SEQUENCE
{
    tmnxBsxAdminCtrlLastChTime       TimeStamp,
    tmnxBsxAdminCtrlConfigOwner      TNamedItemOrEmpty,
    tmnxBsxAdminCtrlApply            TmnxBsxAdminCtrl
}

tmnxBsxAdminCtrlLastChTime       OBJECT-TYPE
    SYNTAX      TimeStamp
    MAX-ACCESS  read-only
    STATUS      current
    DESCRIPTION
        "The value of tmnxBsxAdminCtrlLastChTime indicates the last time a
         successful set was performed of tmnxBsxAdminCtrlApply to 'commit'."
    ::= { tmnxBsxAdminCtrlEntry 1 }

tmnxBsxAdminCtrlConfigOwner      OBJECT-TYPE
    SYNTAX      TNamedItemOrEmpty
    MAX-ACCESS  read-write
    STATUS      current
    DESCRIPTION
        "The value of tmnxBsxAdminCtrlConfigOwner specifies who has last
         initialized the configuration table, who is making all the changes,
         and who is expected to either commit or re-initialize (abort) the
         transaction.

         tmnxBsxAdminCtrlConfigOwner is advisory only.  Before
         beginning a transaction, read tmnxBsxAdminCtrlConfigOwner.
         If it is empty then proceed with the
         configuration.  Set tmnxBsxAdminCtrlConfigOwner after
         setting tmnxBsxAdminCtrlApply so that other
         users will be advised to not make changes to the
         tables.

         The agent automatically sets tmnxBsxAdminCtrlConfigOwner to an empty
         string after tmnxBsxAdminCtrlApply is set, either by the user
         re-initializing or committing, or by the agent timing out the
         uncommitted transaction."
    DEFVAL      { "" }
    ::= { tmnxBsxAdminCtrlEntry 2 }

tmnxBsxAdminCtrlApply            OBJECT-TYPE
    SYNTAX      TmnxBsxAdminCtrl
    MAX-ACCESS  read-write
    STATUS      current
    DESCRIPTION
        "The value of tmnxBsxAdminCtrlApply specifies
         the copying of tmnxBsxPolicyObjs tables from
         one instance of policy version to another.  This
         object reads as none(1) when not editing policy
         and initialize(2) when editing policy.

         When set to initialize(2), the objects in
         tmnxBsxPolicyObjs with the policy version
         index set to 'admin' are copied to the values
         with the index set to 'oper' in the same
         tables.  Any uncommitted changes are lost,
         so setting this value corresponds to both
         BEGIN-TRANSACTION and ABORT-TRANSACTION.

         When set to commit(3) (END-TRANSACTION), all of the objects from
         tables with the index set to 'admin' are first evaluated for
         correctness, and then copied to the same items with the index set to
         'oper'.

         In this way, the (expensive) policy application can be performed at
         one time, with a coherent BSX policy configuration."
    ::= { tmnxBsxAdminCtrlEntry 3 }

tmnxBsxPolicerTable              OBJECT-TYPE
    SYNTAX      SEQUENCE OF TmnxBsxPolicerEntry
    MAX-ACCESS  not-accessible
    STATUS      current
    DESCRIPTION
        "The tmnxBsxPolicerTable contains the policer templates as referenced
         from tmnxBsxAqpActionTable for rate limiting bandwidth and flows and
         limiting the number of flows depending on the type of policer defined
         by tmnxBsxPolicerType."
    ::= { tmnxBsxPolicyObjs 11 }

tmnxBsxPolicerEntry              OBJECT-TYPE
    SYNTAX      TmnxBsxPolicerEntry
    MAX-ACCESS  not-accessible
    STATUS      current
    DESCRIPTION
        "Each tmnxBsxPolicerEntry indicates a policer template."
    INDEX       {
        tmnxBsxIsaAaGroupIndex,
        IMPLIED tmnxBsxPolicerName
    }
    ::= { tmnxBsxPolicerTable 1 }

TmnxBsxPolicerEntry              ::= SEQUENCE
{
    tmnxBsxPolicerName               TNamedItem,
    tmnxBsxPolicerRowStatus          RowStatus,
    tmnxBsxPolicerDescription        TItemDescription,
    tmnxBsxPolicerType               TmnxBsxPolicerType,
    tmnxBsxPolicerGranularity        TmnxBsxGranularity,
    tmnxBsxPolicerAction             TmnxBsxPolicerAction,
    tmnxBsxPolicerAdminPIR           TPIRRateOrZero,
    tmnxBsxPolicerAdminCIR           TCIRRate,
    tmnxBsxPolicerMBS                TmnxBsxBurstSize,
    tmnxBsxPolicerCBS                TmnxBsxBurstSize,
    tmnxBsxPolicerPIRAdaptation      TAdaptationRule,
    tmnxBsxPolicerCIRAdaptation      TAdaptationRule,
    tmnxBsxPolicerRowLastChange      TimeStamp,
    tmnxBsxPolicerOperTodOverride    Integer32,
    tmnxBsxPolicerGtpFlowCountLmt    TmnxEnabledDisabled,
    tmnxBsxPolicerRatePercentage     Integer32,
    tmnxBsxPolicerCongestedAnlPIR    TPIRRateOrZero,
    tmnxBsxPolicerCongestedAnlCIR    TCIRRate,
    tmnxBsxPolicerCongestedAnlMBS    TmnxBsxBurstSize,
    tmnxBsxPolicerCongestedAnlCBS    TmnxBsxBurstSize,
    tmnxBsxPolicerCongestedPIR       TPIRRateOrZero,
    tmnxBsxPolicerCongestedCIR       TCIRRate,
    tmnxBsxPolicerCongestedMBS       TmnxBsxBurstSize,
    tmnxBsxPolicerCongestedCBS       TmnxBsxBurstSize,
    tmnxBsxPolicerCongestedStage2PIR TPIRRateOrZero,
    tmnxBsxPolicerCongestedStage2CIR TCIRRate,
    tmnxBsxPolicerCongestedStage2MBS TmnxBsxBurstSize,
    tmnxBsxPolicerCongestedStage2CBS TmnxBsxBurstSize,
    tmnxBsxPolicerRatePercentageStg2 Integer32
}

tmnxBsxPolicerName               OBJECT-TYPE
    SYNTAX      TNamedItem
    MAX-ACCESS  not-accessible
    STATUS      current
    DESCRIPTION
        "The value of tmnxBsxPolicerName specifies the name defined for the
         policer action."
    ::= { tmnxBsxPolicerEntry 1 }

tmnxBsxPolicerRowStatus          OBJECT-TYPE
    SYNTAX      RowStatus
    MAX-ACCESS  read-create
    STATUS      current
    DESCRIPTION
        "The value of tmnxBsxPolicerRowStatus specifies the
         row status.  It allows entries to be created
         and deleted in the tmnxBsxPolicerTable.  To
         delete an entry, all references to this
         policer in tmnxBsxAqpActBwLimitPolicer,
         tmnxBsxAqpActFlowRatePolicer, and
         tmnxBsxAqpActFlowCountPolicer in the tmnxBsxAqpActionTable
         must be deleted in both the admin and oper versions
         of the application QoS policy."
    ::= { tmnxBsxPolicerEntry 2 }

tmnxBsxPolicerDescription        OBJECT-TYPE
    SYNTAX      TItemDescription
    MAX-ACCESS  read-create
    STATUS      current
    DESCRIPTION
        "The value of tmnxBsxPolicerDescription specifies the description of
         the policer."
    DEFVAL      { "" }
    ::= { tmnxBsxPolicerEntry 3 }

tmnxBsxPolicerType               OBJECT-TYPE
    SYNTAX      TmnxBsxPolicerType
    MAX-ACCESS  read-create
    STATUS      current
    DESCRIPTION
        "The value of tmnxBsxPolicerType specifies whether the policer is a
         bandwidth, flow rate, or a flow count policer in addition to the
         number of buckets used by the policer.

         Note that this item may be configured away from the value 'none' but
         may not be changed after this."
    DEFVAL      { none }
    ::= { tmnxBsxPolicerEntry 4 }

tmnxBsxPolicerGranularity        OBJECT-TYPE
    SYNTAX      TmnxBsxGranularity
    MAX-ACCESS  read-create
    STATUS      current
    DESCRIPTION
        "The value of tmnxBsxPolicerGranularity specifies the scope of traffic
         over which the policer applies.

         Note that this item may be configured away from the value 'none' but
         may not be changed after this."
    DEFVAL      { none }
    ::= { tmnxBsxPolicerEntry 5 }

tmnxBsxPolicerAction             OBJECT-TYPE
    SYNTAX      TmnxBsxPolicerAction
    MAX-ACCESS  read-create
    STATUS      current
    DESCRIPTION
        "The value of tmnxBsxPolicerAction specifies whether the action taken
         by the policer is to permit or drop the packet or flow or is to mark
         the packet(s) as in profile or out of profile."
    DEFVAL      { permitDeny }
    ::= { tmnxBsxPolicerEntry 6 }

tmnxBsxPolicerAdminPIR           OBJECT-TYPE
    SYNTAX      TPIRRateOrZero
    UNITS       "kbps or flows"
    MAX-ACCESS  read-create
    STATUS      current
    DESCRIPTION
        "The value of tmnxBsxPolicerAdminPIR specifies the administrative PIR
         (Peak Information Rate).

         A value of 0, meaning block flows, is only applicable for rows where
         tmnxBsxPolicerType has a value of 'flowCountLimit (4)'."
    DEFVAL      { -1 }
    ::= { tmnxBsxPolicerEntry 7 }

tmnxBsxPolicerAdminCIR           OBJECT-TYPE
    SYNTAX      TCIRRate
    UNITS       "kbps or flows"
    MAX-ACCESS  read-create
    STATUS      current
    DESCRIPTION
        "The value of tmnxBsxPolicerAdminCIR specifies the administrative CIR
         (Committed Information Rate) specified by the user."
    DEFVAL      { 0 }
    ::= { tmnxBsxPolicerEntry 8 }

tmnxBsxPolicerMBS                OBJECT-TYPE
    SYNTAX      TmnxBsxBurstSize
    UNITS       "KB or flows"
    MAX-ACCESS  read-create
    STATUS      current
    DESCRIPTION
        "The value of tmnxBsxPolicerMBS specifies the maximum burst size
         specified by the user to be used in conjunction with the PIR."
    DEFVAL      { 0 }
    ::= { tmnxBsxPolicerEntry 9 }

tmnxBsxPolicerCBS                OBJECT-TYPE
    SYNTAX      TmnxBsxBurstSize
    UNITS       "KB or flows"
    MAX-ACCESS  read-create
    STATUS      current
    DESCRIPTION
        "The value of tmnxBsxPolicerCBS specifies the committed burst size
         specified by the user to be used in conjunction with the CIR."
    DEFVAL      { 0 }
    ::= { tmnxBsxPolicerEntry 10 }

tmnxBsxPolicerPIRAdaptation      OBJECT-TYPE
    SYNTAX      TAdaptationRule
    MAX-ACCESS  read-create
    STATUS      current
    DESCRIPTION
        "The value of tmnxBsxPolicerPIRAdaptation specifies the adaptation rule
         to be used while computing the operational PIR value. The adaptation
         rule specifies the rules to compute the operational values while
         maintaining minimum offset."
    DEFVAL      { closest }
    ::= { tmnxBsxPolicerEntry 11 }

tmnxBsxPolicerCIRAdaptation      OBJECT-TYPE
    SYNTAX      TAdaptationRule
    MAX-ACCESS  read-create
    STATUS      current
    DESCRIPTION
        "The value of tmnxBsxPolicerCIRAdaptation specifies the adaptation rule
         to be used while computing the operational CIR value. The adaptation
         rule specifies the rules to compute the operational values while
         maintaining minimum offset."
    DEFVAL      { closest }
    ::= { tmnxBsxPolicerEntry 12 }

tmnxBsxPolicerRowLastChange      OBJECT-TYPE
    SYNTAX      TimeStamp
    MAX-ACCESS  read-only
    STATUS      current
    DESCRIPTION
        "The value of tmnxBsxPolicerRowLastChange indicates the last time,
         since system startup, a successful set was performed on this row."
    ::= { tmnxBsxPolicerEntry 13 }

tmnxBsxPolicerOperTodOverride    OBJECT-TYPE
    SYNTAX      Integer32
    MAX-ACCESS  read-only
    STATUS      current
    DESCRIPTION
        "The value of tmnxBsxPolicerOperTodOverride indicates the
         tmnxBsxPolicerOvrdIndex which is currently active.

         A value of 0 indicates that there are no overrides currently active,
         while a value of -1 indicates that there are no overrides associated
         with this policer."
    ::= { tmnxBsxPolicerEntry 14 }

tmnxBsxPolicerGtpFlowCountLmt    OBJECT-TYPE
    SYNTAX      TmnxEnabledDisabled
    MAX-ACCESS  read-create
    STATUS      current
    DESCRIPTION
        "The value of tmnxBsxPolicerGtpFlowCountLmt specifies whether or not
         GPRS Tunneling Protocol (GTP) flow-count limiting is enabled. When
         'enabled (1)', and tmnxBsxPolicerType for this row has a value of
         'flowCountLimit (4)', and the corresponding tmnxBsxGtpAdminState in
         tmnxBsxGtpEntry is 'inService (2)', only GTP flows are subject to the
         tmnxBsxPolicerAdminPIR (if non-default). When 'disabled (2)', GTP
         flows are treated the same as other flows."
    DEFVAL      { disabled }
    ::= { tmnxBsxPolicerEntry 15 }

tmnxBsxPolicerRatePercentage     OBJECT-TYPE
    SYNTAX      Integer32 (-1 | 0..200)
    UNITS       "percent"
    MAX-ACCESS  read-create
    STATUS      current
    DESCRIPTION
        "The value of tmnxBsxPolicerRatePercentage specifies the percentage of
         the non-congested access network location rate used to police ANL.

         tmnxBsxPolicerRatePercentage is meaningful only when the value of
         policer type is set to 'singleBucketBandwidth (1)' and the value of
         policer granularity is set to 'accessNetworkLocation (3)'."
    DEFVAL      { -1 }
    ::= { tmnxBsxPolicerEntry 16 }

tmnxBsxPolicerCongestedAnlPIR    OBJECT-TYPE
    SYNTAX      TPIRRateOrZero
    UNITS       "kbps or flows"
    MAX-ACCESS  read-create
    STATUS      obsolete
    DESCRIPTION
        "The value of tmnxBsxPolicerCongestedAnlPIR specifies the
         administrative PIR of the policer when the access-network-level, which
         the subscriber belongs, to is in a congested state.

         tmnxBsxPolicerCongestedAnlPIR is meaningful only in when
         the value of policer type is set to 'singleBucketBandwidth (1)'
         or  'dualBucketBandwidth (2)' and the value of policer
         granularity is set to 'subscriber (2)'.

         This object was obsoleted in release 16.0 and replaced with the
         tmnxBsxPolicerCongestedAnlPIR."
    DEFVAL      { -1 }
    ::= { tmnxBsxPolicerEntry 17 }

tmnxBsxPolicerCongestedAnlCIR    OBJECT-TYPE
    SYNTAX      TCIRRate
    UNITS       "kbps or flows"
    MAX-ACCESS  read-create
    STATUS      obsolete
    DESCRIPTION
        "The value of tmnxBsxPolicerCongestedAnlCIR specifies the
         administrative CIR of the policer when the access-network-level, which
         the subscriber belongs to, is in a congested state.

         tmnxBsxPolicerCongestedAnlCIR is meaningful only in when the value of
         policer type is set to 'dualBucketBandwidth (2)' and the value of
         policer granularity is set to 'subscriber (2)'.

         This object was obsoleted in release 16.0 and replaced with the
         tmnxBsxPolicerCongestedAnlCIR."
    DEFVAL      { 0 }
    ::= { tmnxBsxPolicerEntry 18 }

tmnxBsxPolicerCongestedAnlMBS    OBJECT-TYPE
    SYNTAX      TmnxBsxBurstSize
    UNITS       "KB or flows"
    MAX-ACCESS  read-create
    STATUS      obsolete
    DESCRIPTION
        "The value of tmnxBsxPolicerCongestedAnlMBS specifies the maximum burst
         size when the access-network-level, which the subscriber belongs to,
         is in a congested state.

         tmnxBsxPolicerCongestedAnlMBS is meaningful only in when
         the value of policer type is set to 'singleBucketBandwidth (1)'
         or  'dualBucketBandwidth (2)' and the value of policer
         granularity is set to 'subscriber (2)'.

         This object was obsoleted in release 16.0 and replaced with the
         tmnxBsxPolicerCongestedAnlMBS."
    DEFVAL      { 0 }
    ::= { tmnxBsxPolicerEntry 19 }

tmnxBsxPolicerCongestedAnlCBS    OBJECT-TYPE
    SYNTAX      TmnxBsxBurstSize
    UNITS       "KB or flows"
    MAX-ACCESS  read-create
    STATUS      obsolete
    DESCRIPTION
        "The value of tmnxBsxPolicerCongestedAnlCBS specifies the committed
         burst size when the access-network-level, which the subscriber belongs
         to, is in a congested state.

         tmnxBsxPolicerCongestedAnlCBS is meaningful only in when the value of
         policer type is set to 'dualBucketBandwidth (2)' and the value of
         policer granularity is set to 'subscriber (2)'.

         This object was obsoleted in release 16.0 and replaced with the
         tmnxBsxPolicerCongestedAnlCBS."
    DEFVAL      { 0 }
    ::= { tmnxBsxPolicerEntry 20 }

tmnxBsxPolicerCongestedPIR       OBJECT-TYPE
    SYNTAX      TPIRRateOrZero
    UNITS       "kbps or flows"
    MAX-ACCESS  read-create
    STATUS      current
    DESCRIPTION
        "The value of tmnxBsxPolicerCongestedPIR specifies the administrative
         PIR of the policer when the access-network-level, which the subscriber
         belongs, to is in a congested state.

         tmnxBsxPolicerCongestedPIR is meaningful only in when
         the value of policer type is set to 'singleBucketBandwidth (1)'
         or  'dualBucketBandwidth (2)' and the value of policer
         granularity is set to 'subscriber (2)'."
    DEFVAL      { -1 }
    ::= { tmnxBsxPolicerEntry 21 }

tmnxBsxPolicerCongestedCIR       OBJECT-TYPE
    SYNTAX      TCIRRate
    UNITS       "kbps or flows"
    MAX-ACCESS  read-create
    STATUS      current
    DESCRIPTION
        "The value of tmnxBsxPolicerCongestedCIR specifies the administrative
         CIR of the policer when the access-network-level, which the subscriber
         belongs to, is in a congested state.

         tmnxBsxPolicerCongestedCIR is meaningful only in when the value of
         policer type is set to 'dualBucketBandwidth (2)' and the value of
         policer granularity is set to 'subscriber (2)'."
    DEFVAL      { 0 }
    ::= { tmnxBsxPolicerEntry 22 }

tmnxBsxPolicerCongestedMBS       OBJECT-TYPE
    SYNTAX      TmnxBsxBurstSize
    UNITS       "KB or flows"
    MAX-ACCESS  read-create
    STATUS      current
    DESCRIPTION
        "The value of tmnxBsxPolicerCongestedMBS specifies the maximum burst
         size when the access-network-level, which the subscriber belongs to,
         is in a congested state.

         tmnxBsxPolicerCongestedMBS is meaningful only in when
         the value of policer type is set to 'singleBucketBandwidth (1)'
         or  'dualBucketBandwidth (2)' and the value of policer
         granularity is set to 'subscriber (2)'."
    DEFVAL      { 0 }
    ::= { tmnxBsxPolicerEntry 23 }

tmnxBsxPolicerCongestedCBS       OBJECT-TYPE
    SYNTAX      TmnxBsxBurstSize
    UNITS       "KB or flows"
    MAX-ACCESS  read-create
    STATUS      current
    DESCRIPTION
        "The value of tmnxBsxPolicerCongestedCBS specifies the committed burst
         size when the access-network-level, which the subscriber belongs to,
         is in a congested state.

         tmnxBsxPolicerCongestedCBS is meaningful only in when the value of
         policer type is set to 'dualBucketBandwidth (2)' and the value of
         policer granularity is set to 'subscriber (2)'."
    DEFVAL      { 0 }
    ::= { tmnxBsxPolicerEntry 24 }

tmnxBsxPolicerCongestedStage2PIR OBJECT-TYPE
    SYNTAX      TPIRRateOrZero
    UNITS       "kbps"
    MAX-ACCESS  read-create
    STATUS      current
    DESCRIPTION
        "The value of tmnxBsxPolicerCongestedStage2PIR specifies the
         administrative PIR of the policer when the subscriber is in the stage
         2 congested state.

         tmnxBsxPolicerCongestedStage2PIR is meaningful only in when
         the value of policer type is set to 'singleBucketBandwidth (1)'
         or  'dualBucketBandwidth (2)' and the value of policer
         granularity is set to 'subscriber (2)'."
    DEFVAL      { -1 }
    ::= { tmnxBsxPolicerEntry 25 }

tmnxBsxPolicerCongestedStage2CIR OBJECT-TYPE
    SYNTAX      TCIRRate
    UNITS       "kbps"
    MAX-ACCESS  read-create
    STATUS      current
    DESCRIPTION
        "The value of tmnxBsxPolicerCongestedStage2CIR specifies the
         administrative CIR of the policer when the subscriber is in the stage
         2 congested state.

         tmnxBsxPolicerCongestedStage2CIR is meaningful only in when the value
         of policer type is set to 'dualBucketBandwidth (2)' and the value of
         policer granularity is set to 'subscriber (2)'."
    DEFVAL      { 0 }
    ::= { tmnxBsxPolicerEntry 26 }

tmnxBsxPolicerCongestedStage2MBS OBJECT-TYPE
    SYNTAX      TmnxBsxBurstSize
    UNITS       "KB"
    MAX-ACCESS  read-create
    STATUS      current
    DESCRIPTION
        "The value of tmnxBsxPolicerCongestedStage2MBS specifies the maximum
         burst size of the policer when the subscriber is in the stage 2
         congested state.

         tmnxBsxPolicerCongestedStage2MBS is meaningful only in when
         the value of policer type is set to 'singleBucketBandwidth (1)'
         or  'dualBucketBandwidth (2)' and the value of policer
         granularity is set to 'subscriber (2)'."
    DEFVAL      { 0 }
    ::= { tmnxBsxPolicerEntry 27 }

tmnxBsxPolicerCongestedStage2CBS OBJECT-TYPE
    SYNTAX      TmnxBsxBurstSize
    UNITS       "KB"
    MAX-ACCESS  read-create
    STATUS      current
    DESCRIPTION
        "The value of tmnxBsxPolicerCongestedStage2CBS specifies the committed
         burst size of the policer when the subscriber is in the stage 2
         congested state.

         tmnxBsxPolicerCongestedStage2CBS is meaningful only in when the value
         of policer type is set to 'dualBucketBandwidth (2)' and the value of
         policer granularity is set to 'subscriber (2)'."
    DEFVAL      { 0 }
    ::= { tmnxBsxPolicerEntry 28 }

tmnxBsxPolicerRatePercentageStg2 OBJECT-TYPE
    SYNTAX      Integer32 (-1 | 0..200)
    UNITS       "percent"
    MAX-ACCESS  read-create
    STATUS      current
    DESCRIPTION
        "The value of tmnxBsxPolicerRatePercentageStg2 specifies the stage 2
         congestion percentage of the non-congested access network location
         rate used to police ANL.

         tmnxBsxPolicerRatePercentageStg2 is meaningful only when the value of
         policer type is set to 'singleBucketBandwidth (1)' and the value of
         policer granularity is set to 'accessNetworkLocation (3)'."
    DEFVAL      { -1 }
    ::= { tmnxBsxPolicerEntry 29 }

tmnxBsxIsaAaTim                  OBJECT IDENTIFIER ::= { tmnxBsxPolicyObjs 12 }

tmnxBsxUpgrade                   OBJECT-TYPE
    SYNTAX      TmnxActionType
    MAX-ACCESS  read-write
    STATUS      current
    DESCRIPTION
        "The value of tmnxBsxUpgrade specifies that when set to 'doAction' that
         a new ISA-AA.tim file is loaded.

         This causes the tmnxBsxProtTable to be populated with new entries.

         The operator is expected to reset each of the
         ISA-AA MDAs within a short period of time after
         this operation.  The ISA-AA will continue to
         collect inconsistent statistics for protocols
         until the reset occurs."
    ::= { tmnxBsxIsaAaTim 1 }

tmnxBsxVersion                   OBJECT-TYPE
    SYNTAX      DisplayString
    MAX-ACCESS  read-only
    STATUS      current
    DESCRIPTION
        "The value of tmnxBsxVersion indicates the version of the ISA-AA.tim
         file currently in use by the system.

         If no ISA-AA.tim file currently exists, this object will contain a
         zero length string."
    ::= { tmnxBsxIsaAaTim 2 }

tmnxBsxAqpStatsTable             OBJECT-TYPE
    SYNTAX      SEQUENCE OF TmnxBsxAqpStatsEntry
    MAX-ACCESS  not-accessible
    STATUS      current
    DESCRIPTION
        "The tmnxBsxAqpStatsTable contains the application qos policy
         statistics."
    ::= { tmnxBsxPolicyObjs 13 }

tmnxBsxAqpStatsEntry             OBJECT-TYPE
    SYNTAX      TmnxBsxAqpStatsEntry
    MAX-ACCESS  not-accessible
    STATUS      current
    DESCRIPTION
        "Each tmnxBsxAqpStatsEntry indicates statistics available to collect
         for each application QoS policy entry."
    INDEX       {
        tmnxBsxAaGrpPartIndex,
        tmnxBsxAqpBaseEntryId
    }
    ::= { tmnxBsxAqpStatsTable 1 }

TmnxBsxAqpStatsEntry             ::= SEQUENCE
{
    tmnxBsxAqpStatsFlows             Counter32,
    tmnxBsxAqpStatsConflicts         Counter32,
    tmnxBsxAqpStatsHCFlows           Counter64,
    tmnxBsxAqpStatsFlowsLo           Counter32,
    tmnxBsxAqpStatsFlowsHi           Counter32,
    tmnxBsxAqpStatsHCConflicts       Counter64,
    tmnxBsxAqpStatsConflictsLo       Counter32,
    tmnxBsxAqpStatsConflictsHi       Counter32
}

tmnxBsxAqpStatsFlows             OBJECT-TYPE
    SYNTAX      Counter32
    MAX-ACCESS  read-only
    STATUS      obsolete
    DESCRIPTION
        "The value of tmnxBsxAqpStatsFlows indicates the number of flows that
         have hit this entry.

         In certain cases, a flow may change its
         attributes thus undergoing a second policy
         evaluation.  In these cases, the flow may
         be counted against two different AQP entries.

         This object was obsoleted in release 9.0 and replaced with the
         tmnxBsxAqpStatsHCFlows and its 32-bit associated objects."
    ::= { tmnxBsxAqpStatsEntry 1 }

tmnxBsxAqpStatsConflicts         OBJECT-TYPE
    SYNTAX      Counter32
    MAX-ACCESS  read-only
    STATUS      obsolete
    DESCRIPTION
        "The value of tmnxBsxAqpStatsConflicts indicates the number of flows
         that have hit this AQP entry, but resulted in a conflict with the
         match criteria.

         This object was obsoleted in release 9.0 and replaced with the
         tmnxBsxAqpStatsHCConflicts and its 32-bit associated objects."
    ::= { tmnxBsxAqpStatsEntry 2 }

tmnxBsxAqpStatsHCFlows           OBJECT-TYPE
    SYNTAX      Counter64
    MAX-ACCESS  read-only
    STATUS      current
    DESCRIPTION
        "The value of tmnxBsxAqpStatsHCFlows indicates the number of flows that
         have hit this entry.

         In certain cases, a flow may change its
         attributes thus undergoing a second policy
         evaluation.  In these cases, the flow may
         be counted against two different AQP entries."
    ::= { tmnxBsxAqpStatsEntry 3 }

tmnxBsxAqpStatsFlowsLo           OBJECT-TYPE
    SYNTAX      Counter32
    MAX-ACCESS  read-only
    STATUS      current
    DESCRIPTION
        "The value of tmnxBsxAqpStatsFlowsLo indicates the lower 32-bits of
         tmnxBsxAqpStatsHCFlows."
    ::= { tmnxBsxAqpStatsEntry 4 }

tmnxBsxAqpStatsFlowsHi           OBJECT-TYPE
    SYNTAX      Counter32
    MAX-ACCESS  read-only
    STATUS      current
    DESCRIPTION
        "The value of tmnxBsxAqpStatsFlowsHi indicates the upper 32-bits of
         tmnxBsxAqpStatsHCFlows."
    ::= { tmnxBsxAqpStatsEntry 5 }

tmnxBsxAqpStatsHCConflicts       OBJECT-TYPE
    SYNTAX      Counter64
    MAX-ACCESS  read-only
    STATUS      current
    DESCRIPTION
        "The value of tmnxBsxAqpStatsHCConflicts indicates the number of flows
         that have hit this AQP entry, but resulted in a conflict with the
         match criteria."
    ::= { tmnxBsxAqpStatsEntry 6 }

tmnxBsxAqpStatsConflictsLo       OBJECT-TYPE
    SYNTAX      Counter32
    MAX-ACCESS  read-only
    STATUS      current
    DESCRIPTION
        "The value of tmnxBsxAqpStatsConflictsLo indicates the lower 32-bits of
         tmnxBsxAqpStatsHCConflicts."
    ::= { tmnxBsxAqpStatsEntry 7 }

tmnxBsxAqpStatsConflictsHi       OBJECT-TYPE
    SYNTAX      Counter32
    MAX-ACCESS  read-only
    STATUS      current
    DESCRIPTION
        "The value of tmnxBsxAqpStatsConflictsHi indicates the upper 32-bits of
         tmnxBsxAqpStatsHCConflicts."
    ::= { tmnxBsxAqpStatsEntry 8 }

tmnxBsxInfo                      OBJECT IDENTIFIER ::= { tmnxBsxPolicyObjs 14 }

tmnxBsxFlowFullHighWatermark     OBJECT-TYPE
    SYNTAX      Integer32 (0..100)
    MAX-ACCESS  read-write
    STATUS      current
    DESCRIPTION
        "The value of tmnxBsxFlowFullHighWatermark specifies the utilization of
         the flow records on the ISA-AA Group when a full trap will be raised
         by the agent. The value must be greater than or equal to
         tmnxBsxFlowFullLowWatermark."
    DEFVAL      { 95 }
    ::= { tmnxBsxInfo 1 }

tmnxBsxFlowFullLowWatermark      OBJECT-TYPE
    SYNTAX      Integer32 (0..100)
    MAX-ACCESS  read-write
    STATUS      current
    DESCRIPTION
        "The value of tmnxBsxFlowFullLowWatermark specifies the utilization of
         the flow records on the ISA-AA Group when the full trap will be
         cleared by the agent. The value must be less than or equal to
         tmnxBsxFlowFullHighWatermark."
    DEFVAL      { 90 }
    ::= { tmnxBsxInfo 2 }

tmnxBsxFlowSetupHighWatermark    OBJECT-TYPE
    SYNTAX      Integer32 (-1 | 1..2000000)
    UNITS       "flows per second"
    MAX-ACCESS  read-write
    STATUS      current
    DESCRIPTION
        "The value of tmnxBsxFlowSetupHighWatermark specifies the flow setup
         rate on the ISA-AA when a Flow Setup trap will be raised by the agent.
         The value must be greater than tmnxBsxFlowSetupLowWatermark.

         The value of -1 represents maximum flow setup rate indicating that
         this high watermark will not be exceeded."
    DEFVAL      { -1 }
    ::= { tmnxBsxInfo 3 }

tmnxBsxFlowSetupLowWatermark     OBJECT-TYPE
    SYNTAX      Integer32 (0..1999999)
    UNITS       "flows per second"
    MAX-ACCESS  read-write
    STATUS      current
    DESCRIPTION
        "The value of tmnxBsxFlowSetupLowWatermark specifies the flow setup
         rate on the ISA-AA when a Flow Setup trap will be cleared by the
         agent. The value must be less than tmnxBsxFlowSetupHighWatermark if
         the value of tmnxBsxFlowSetupHighWatermark is not -1."
    DEFVAL      { 0 }
    ::= { tmnxBsxInfo 4 }

tmnxBsxPacketRateHighWatermark   OBJECT-TYPE
    SYNTAX      Integer32 (-1 | 1..148809524)
    UNITS       "packets per second"
    MAX-ACCESS  read-write
    STATUS      current
    DESCRIPTION
        "The value of tmnxBsxPacketRateHighWatermark specifies the packet rate
         on the ISA-AA when a Packet Rate trap will be raised by the agent. The
         value must be greater than tmnxBsxPacketRateLowWatermark.

         The value of -1 represents maximum packet rate indicating that this
         high watermark will never be exceeded."
    DEFVAL      { -1 }
    ::= { tmnxBsxInfo 5 }

tmnxBsxPacketRateLowWatermark    OBJECT-TYPE
    SYNTAX      Integer32 (0..148809523)
    UNITS       "packets per second"
    MAX-ACCESS  read-write
    STATUS      current
    DESCRIPTION
        "The value of tmnxBsxPacketRateLowWatermark specifies the packet rate
         on the ISA-AA when a Packet Rate trap will be cleared by the agent.
         The value must be less than tmnxBsxPacketRateHighWatermark if the
         value of tmnxBsxPacketRateHighWatermark is not -1."
    DEFVAL      { 0 }
    ::= { tmnxBsxInfo 6 }

tmnxBsxBitRateHighWatermark      OBJECT-TYPE
    SYNTAX      Integer32 (-1 | 1..100000)
    UNITS       "megabps"
    MAX-ACCESS  read-write
    STATUS      current
    DESCRIPTION
        "The value of tmnxBsxBitRateHighWatermark specifies the bit rate on the
         ISA-AA when a Bit Rate trap will be raised by the agent. The value
         must be greater than tmnxBsxBitRateLowWatermark.

         The value of -1 represents maximum bit rate indicating that this high
         watermark will not be exceeded."
    DEFVAL      { -1 }
    ::= { tmnxBsxInfo 7 }

tmnxBsxBitRateLowWatermark       OBJECT-TYPE
    SYNTAX      Integer32 (0..99999)
    UNITS       "megabps"
    MAX-ACCESS  read-write
    STATUS      current
    DESCRIPTION
        "The value of tmnxBsxBitRateLowWatermark specifies the bit rate on the
         ISA-AA when a Bit Rate trap will be cleared by the agent. The value
         must be less than tmnxBsxBitRateHighWatermark if the value of
         tmnxBsxBitRateHighWatermark is not -1."
    DEFVAL      { 0 }
    ::= { tmnxBsxInfo 8 }

tmnxBsxDatapathCpuHighWatermark  OBJECT-TYPE
    SYNTAX      Integer32 (-1 | 0..100)
    UNITS       "percent"
    MAX-ACCESS  read-write
    STATUS      current
    DESCRIPTION
        "The value of tmnxBsxDatapathCpuHighWatermark specifies the utilization
         of the datapath CPU on any Application Assurance group ISA-AA at which
         a datapath CPU trap will be raised by the agent
         (tmnxBsxDatapathCpuUsage). The value must be greater than or equal to
         tmnxBsxDatapathCpuLowWatermark if not -1.

         The value of -1 represents a maximum datapath cpu indicating that this
         high watermark will not be exceeded.

         On a VSR, the value is not applicable and cannot be changed from its
         default."
    DEFVAL      { 95 }
    ::= { tmnxBsxInfo 9 }

tmnxBsxDatapathCpuLowWatermark   OBJECT-TYPE
    SYNTAX      Integer32 (0..100)
    UNITS       "percent"
    MAX-ACCESS  read-write
    STATUS      current
    DESCRIPTION
        "The value of tmnxBsxDatapathCpuLowWatermark specifies the utilization
         of the datapath CPU on any Application Assurance group ISA-AA at which
         a datapath CPU trap will be cleared by the agent
         (tmnxBsxDatapathCpuUsageClear). The value must be less than or equal
         to tmnxBsxDatapathCpuHighWatermark if the value of
         tmnxBsxDatapathCpuHighWatermark is not -1.

         On a VSR, the value is not applicable and cannot be changed from its
         default."
    DEFVAL      { 90 }
    ::= { tmnxBsxInfo 10 }

tmnxBsxAqpCharTable              OBJECT-TYPE
    SYNTAX      SEQUENCE OF TmnxBsxAqpCharEntry
    MAX-ACCESS  not-accessible
    STATUS      obsolete
    DESCRIPTION
        "The tmnxBsxAqpCharTable contains the characteristic matches for the
         application qos policy table."
    ::= { tmnxBsxPolicyObjs 15 }

tmnxBsxAqpCharEntry              OBJECT-TYPE
    SYNTAX      TmnxBsxAqpCharEntry
    MAX-ACCESS  not-accessible
    STATUS      current
    DESCRIPTION
        "Each tmnxBsxAqpCharEntry specifies a match criterion and corresponding
         action for the application qos policy specified by the second and
         third indices tmnxBsxAaGrpPartIndex, and tmnxBsxAqpBaseEntryId. The
         tmnxBsxAsoCharName and tmnxBsxAsoValValName indices uniquely specify
         the characteristic in the tmnxBsxAsoTable and characteristic value in
         the tmnxBsxAsoValTable.

         Rows can only be created and destroyed by specifying the
         tmnxBsxAqpCharRowStatus if the first index,
         tmnxBsxAqpBasePolicyVersion, is set to 'admin'."
    INDEX       {
        tmnxBsxAqpBasePolicyVersion,
        tmnxBsxAaGrpPartIndex,
        tmnxBsxAqpBaseEntryId,
        tmnxBsxAsoCharName,
        IMPLIED tmnxBsxAsoValValName
    }
    ::= { tmnxBsxAqpCharTable 1 }

TmnxBsxAqpCharEntry              ::= SEQUENCE
{
    tmnxBsxAqpCharRowStatus          RowStatus,
    tmnxBsxAqpCharOperator           TmnxBsxOperator,
    tmnxBsxAqpCharRowLastChange      TimeStamp
}

tmnxBsxAqpCharRowStatus          OBJECT-TYPE
    SYNTAX      RowStatus
    MAX-ACCESS  read-create
    STATUS      obsolete
    DESCRIPTION
        "The value of tmnxBsxAqpCharRowStatus specifies
         the row status.  It allows entries to be created
         and deleted in the tmnxBsxAqpCharTable.

         Rows are created by specifying the value of 'createAndGo (4)', and
         deleted by specifying the value of 'destroy (6)'."
    ::= { tmnxBsxAqpCharEntry 1 }

tmnxBsxAqpCharOperator           OBJECT-TYPE
    SYNTAX      TmnxBsxOperator
    MAX-ACCESS  read-create
    STATUS      obsolete
    DESCRIPTION
        "The value of tmnxBsxAqpCharOperator specifies the comparison operator
         applied to the corresponding row in the tmnxBsxAsoValTable."
    DEFVAL      { none }
    ::= { tmnxBsxAqpCharEntry 2 }

tmnxBsxAqpCharRowLastChange      OBJECT-TYPE
    SYNTAX      TimeStamp
    MAX-ACCESS  read-only
    STATUS      obsolete
    DESCRIPTION
        "The value of tmnxBsxAqpCharRowLastChange indicates the last time,
         since system startup, a successful set was performed on this row."
    ::= { tmnxBsxAqpCharEntry 3 }

tmnxBsxAppFilterExprTable        OBJECT-TYPE
    SYNTAX      SEQUENCE OF TmnxBsxAppFilterExprEntry
    MAX-ACCESS  not-accessible
    STATUS      current
    DESCRIPTION
        "The tmnxBsxAppFilterExprTable contains the expression substring match
         criteria for the application filter table."
    ::= { tmnxBsxPolicyObjs 16 }

tmnxBsxAppFilterExprEntry        OBJECT-TYPE
    SYNTAX      TmnxBsxAppFilterExprEntry
    MAX-ACCESS  not-accessible
    STATUS      current
    DESCRIPTION
        "Each tmnxBsxAppFilterExprEntry specifies an expression substring match
         criterion and corresponding action for the application filter
         specified by the second and third indices tmnxBsxAaGrpPartIndex, and
         tmnxBsxAppFilterEntryId. The tmnxBsxAppFilterExprIndex index uniquely
         specifies the expression substring.

         Rows can only be created and destroyed by specifying the
         tmnxBsxAppFilterExprRowStatus if the first index,
         tmnxBsxAppFilterPolicyVersion, is set to 'admin'."
    INDEX       {
        tmnxBsxAppFilterPolicyVersion,
        tmnxBsxAaGrpPartIndex,
        tmnxBsxAppFilterEntryId,
        tmnxBsxAppFilterExprIndex
    }
    ::= { tmnxBsxAppFilterExprTable 1 }

TmnxBsxAppFilterExprEntry        ::= SEQUENCE
{
    tmnxBsxAppFilterExprIndex        TmnxBsxExprSubStringIndex,
    tmnxBsxAppFilterExprRowStatus    RowStatus,
    tmnxBsxAppFilterExprType         TmnxBsxExprSubStringType,
    tmnxBsxAppFilterExprOperator     TmnxBsxOperator,
    tmnxBsxAppFilterExprStr          TmnxBsxExprSubString,
    tmnxBsxAppFilterExprRowLastCh    TimeStamp
}

tmnxBsxAppFilterExprIndex        OBJECT-TYPE
    SYNTAX      TmnxBsxExprSubStringIndex
    MAX-ACCESS  not-accessible
    STATUS      current
    DESCRIPTION
        "The value of tmnxBsxAppFilterExprIndex specifies the expression
         substring index."
    ::= { tmnxBsxAppFilterExprEntry 1 }

tmnxBsxAppFilterExprRowStatus    OBJECT-TYPE
    SYNTAX      RowStatus
    MAX-ACCESS  read-create
    STATUS      current
    DESCRIPTION
        "The value of tmnxBsxAppFilterExprRowStatus specifies
         the row status.  It allows entries to be created
         and deleted in the tmnxBsxAppFilterExprTable.

         Rows are created by specifying the value of 'createAndGo (4)', and
         deleted by specifying the value of 'destroy (6)'."
    ::= { tmnxBsxAppFilterExprEntry 2 }

tmnxBsxAppFilterExprType         OBJECT-TYPE
    SYNTAX      TmnxBsxExprSubStringType
    MAX-ACCESS  read-create
    STATUS      current
    DESCRIPTION
        "The value of tmnxBsxAppFilterExprType specifies the type of
         tmnxBsxAppFilterExprStr."
    DEFVAL      { none }
    ::= { tmnxBsxAppFilterExprEntry 3 }

tmnxBsxAppFilterExprOperator     OBJECT-TYPE
    SYNTAX      TmnxBsxOperator
    MAX-ACCESS  read-create
    STATUS      current
    DESCRIPTION
        "The value of tmnxBsxAppFilterExprOperator specifies the comparison
         operator applied to the tmnxBsxAppFilterExprStr."
    DEFVAL      { none }
    ::= { tmnxBsxAppFilterExprEntry 4 }

tmnxBsxAppFilterExprStr          OBJECT-TYPE
    SYNTAX      TmnxBsxExprSubString
    MAX-ACCESS  read-create
    STATUS      current
    DESCRIPTION
        "The value of tmnxBsxAppFilterExprStr specifies a substring expression,
         of the type specified by tmnxBsxAppFilterExprType, to match against
         that resolves to a tmnxBsxAppFilterApplication. If set to an empty
         string, no match on the substring expression is done."
    DEFVAL      { "" }
    ::= { tmnxBsxAppFilterExprEntry 5 }

tmnxBsxAppFilterExprRowLastCh    OBJECT-TYPE
    SYNTAX      TimeStamp
    MAX-ACCESS  read-only
    STATUS      current
    DESCRIPTION
        "The value of tmnxBsxAppFilterExprRowLastCh indicates the last time,
         since system startup, a successful set was performed on this row."
    ::= { tmnxBsxAppFilterExprEntry 6 }

tmnxBsxCustProtTable             OBJECT-TYPE
    SYNTAX      SEQUENCE OF TmnxBsxCustProtEntry
    MAX-ACCESS  not-accessible
    STATUS      current
    DESCRIPTION
        "The tmnxBsxCustProtTable contains the definitions of custom protocols
         for an Application Assurance group and partition."
    ::= { tmnxBsxPolicyObjs 17 }

tmnxBsxCustProtEntry             OBJECT-TYPE
    SYNTAX      TmnxBsxCustProtEntry
    MAX-ACCESS  not-accessible
    STATUS      current
    DESCRIPTION
        "Each tmnxBsxCustProtEntry specifies a set of match criteria to define
         a custom protocol within an Application Assurance group and partition.

         Rows can only be created and destroyed by specifying the
         tmnxBsxCustProtRowStatus if the first index,
         tmnxBsxCustProtPolicyVersion, is set to 'admin'."
    INDEX       {
        tmnxBsxCustProtPolicyVersion,
        tmnxBsxAaGrpPartIndex,
        tmnxBsxCustProtEntryId
    }
    ::= { tmnxBsxCustProtTable 1 }

TmnxBsxCustProtEntry             ::= SEQUENCE
{
    tmnxBsxCustProtPolicyVersion     TmnxBsxPolicyVersion,
    tmnxBsxCustProtEntryId           TEntryId,
    tmnxBsxCustProtRowStatus         RowStatus,
    tmnxBsxCustProtRowLastChange     TimeStamp,
    tmnxBsxCustProtIpProtocolNum     TIpProtocol,
    tmnxBsxCustProtDescription       TItemDescription,
    tmnxBsxCustProtAdminState        TmnxAdminState
}

tmnxBsxCustProtPolicyVersion     OBJECT-TYPE
    SYNTAX      TmnxBsxPolicyVersion
    MAX-ACCESS  not-accessible
    STATUS      current
    DESCRIPTION
        "The value of tmnxBsxCustProtPolicyVersion specifies the
         version of the table being accessed.  The table
         is read-create only for the 'admin' version of
         the table.  The 'oper' version is read-only."
    ::= { tmnxBsxCustProtEntry 1 }

tmnxBsxCustProtEntryId           OBJECT-TYPE
    SYNTAX      TEntryId
    MAX-ACCESS  not-accessible
    STATUS      current
    DESCRIPTION
        "The value of tmnxBsxCustProtEntryId specifies the index into the
         protocol list that defines a custom protocol for application
         assurance."
    ::= { tmnxBsxCustProtEntry 2 }

tmnxBsxCustProtRowStatus         OBJECT-TYPE
    SYNTAX      RowStatus
    MAX-ACCESS  read-create
    STATUS      current
    DESCRIPTION
        "The value of tmnxBsxCustProtRowStatus specifies the row status. Rows
         in the tmnxBsxCustProtTable are created by specifying the value of
         'createAndGo (4)', and deleted by specifying the value of 'destroy
         (6)'."
    ::= { tmnxBsxCustProtEntry 3 }

tmnxBsxCustProtRowLastChange     OBJECT-TYPE
    SYNTAX      TimeStamp
    MAX-ACCESS  read-only
    STATUS      current
    DESCRIPTION
        "The value of tmnxBsxCustProtRowLastChange indicates the last time a
         successful set was performed on this row of the tmnxBsxCustProtTable."
    ::= { tmnxBsxCustProtEntry 4 }

tmnxBsxCustProtIpProtocolNum     OBJECT-TYPE
    SYNTAX      TIpProtocol
    MAX-ACCESS  read-create
    STATUS      current
    DESCRIPTION
        "The value of tmnxBsxCustProtIpProtocolNum specifies the IP protocol
         number to match against for the custom protocol.

         A value of '-1' specifies that no matching is to be done to resolve to
         a custom protocol."
    DEFVAL      { -1 }
    ::= { tmnxBsxCustProtEntry 5 }

tmnxBsxCustProtDescription       OBJECT-TYPE
    SYNTAX      TItemDescription
    MAX-ACCESS  read-create
    STATUS      current
    DESCRIPTION
        "The value of tmnxBsxCustProtDescription specifies the description of
         the custom protocol."
    DEFVAL      { "" }
    ::= { tmnxBsxCustProtEntry 6 }

tmnxBsxCustProtAdminState        OBJECT-TYPE
    SYNTAX      TmnxAdminState
    MAX-ACCESS  read-create
    STATUS      current
    DESCRIPTION
        "The value of tmnxBsxCustProtAdminState specifies the
         administrative state for the custom protocol.  When
         'outOfService', any match entries referring to this
         custom protocol are skipped."
    DEFVAL      { outOfService }
    ::= { tmnxBsxCustProtEntry 7 }

tmnxBsxCustProtExprTable         OBJECT-TYPE
    SYNTAX      SEQUENCE OF TmnxBsxCustProtExprEntry
    MAX-ACCESS  not-accessible
    STATUS      current
    DESCRIPTION
        "The tmnxBsxCustProtExprTable contains the expression substring match
         criteria for the tmnxBsxCustProtTable."
    ::= { tmnxBsxPolicyObjs 18 }

tmnxBsxCustProtExprEntry         OBJECT-TYPE
    SYNTAX      TmnxBsxCustProtExprEntry
    MAX-ACCESS  not-accessible
    STATUS      current
    DESCRIPTION
        "Each tmnxBsxCustProtExprEntry specifies an expression substring match
         criterion for the custom protocol specified by the second and third
         indices tmnxBsxAaGrpPartIndex, and tmnxBsxCustProtEntryId. The
         tmnxBsxCustProtExprIndex index uniquely specifies the expression
         substring.

         Rows can only be created and destroyed by specifying the
         tmnxBsxCustProtExprRowStatus if the first index,
         tmnxBsxCustProtPolicyVersion, is set to 'admin'."
    INDEX       {
        tmnxBsxCustProtPolicyVersion,
        tmnxBsxAaGrpPartIndex,
        tmnxBsxCustProtEntryId,
        tmnxBsxCustProtExprIndex
    }
    ::= { tmnxBsxCustProtExprTable 1 }

TmnxBsxCustProtExprEntry         ::= SEQUENCE
{
    tmnxBsxCustProtExprIndex         TmnxBsxExprSubStringIndex,
    tmnxBsxCustProtExprRowStatus     RowStatus,
    tmnxBsxCustProtExprRowLastChange TimeStamp,
    tmnxBsxCustProtExprOffset        Unsigned32,
    tmnxBsxCustProtExprDirection     TmnxBsxProtocolDirection,
    tmnxBsxCustProtExprOperator      TmnxBsxOperator,
    tmnxBsxCustProtExprStr           TmnxBsxCustProtExprSubString
}

tmnxBsxCustProtExprIndex         OBJECT-TYPE
    SYNTAX      TmnxBsxExprSubStringIndex
    MAX-ACCESS  not-accessible
    STATUS      current
    DESCRIPTION
        "The value of tmnxBsxCustProtExprIndex specifies the expression
         substring index."
    ::= { tmnxBsxCustProtExprEntry 1 }

tmnxBsxCustProtExprRowStatus     OBJECT-TYPE
    SYNTAX      RowStatus
    MAX-ACCESS  read-create
    STATUS      current
    DESCRIPTION
        "The value of tmnxBsxCustProtExprRowStatus specifies the row status.
         Rows in the tmnxBsxCustProtExprTable are created by specifying the
         value of 'createAndGo (4)', and deleted by specifying the value of
         'destroy (6)'."
    ::= { tmnxBsxCustProtExprEntry 2 }

tmnxBsxCustProtExprRowLastChange OBJECT-TYPE
    SYNTAX      TimeStamp
    MAX-ACCESS  read-only
    STATUS      current
    DESCRIPTION
        "The value of tmnxBsxCustProtExprRowLastChange indicates the last time
         a successful set was performed on this row of the
         tmnxBsxCustProtExprTable."
    ::= { tmnxBsxCustProtExprEntry 3 }

tmnxBsxCustProtExprOffset        OBJECT-TYPE
    SYNTAX      Unsigned32 (0..127)
    MAX-ACCESS  read-create
    STATUS      current
    DESCRIPTION
        "The value of tmnxBsxCustProtExprOffset specifies the offset (in
         octets) into the protocol payload, where the substring expression
         match criteria will start."
    DEFVAL      { 0 }
    ::= { tmnxBsxCustProtExprEntry 4 }

tmnxBsxCustProtExprDirection     OBJECT-TYPE
    SYNTAX      TmnxBsxProtocolDirection
    MAX-ACCESS  read-create
    STATUS      current
    DESCRIPTION
        "The value of tmnxBsxCustProtExprDirection specifies the protocol
         direction to match against to resolve to a custom protocol.

         The value can be either client-to-server 'client2server',
         server-to-client 'server2client', or 'any'."
    DEFVAL      { none }
    ::= { tmnxBsxCustProtExprEntry 5 }

tmnxBsxCustProtExprOperator      OBJECT-TYPE
    SYNTAX      TmnxBsxOperator
    MAX-ACCESS  read-create
    STATUS      current
    DESCRIPTION
        "The value of tmnxBsxCustProtExprOperator specifies the comparison
         operator applied to the tmnxBsxCustProtExprStr."
    DEFVAL      { none }
    ::= { tmnxBsxCustProtExprEntry 6 }

tmnxBsxCustProtExprStr           OBJECT-TYPE
    SYNTAX      TmnxBsxCustProtExprSubString
    MAX-ACCESS  read-create
    STATUS      current
    DESCRIPTION
        "The value of tmnxBsxCustProtExprStr specifies a substring expression
         to match against that resolves to a custom protocol. If set to an
         empty string, no match on the substring expression is done."
    DEFVAL      { "" }
    ::= { tmnxBsxCustProtExprEntry 7 }

tmnxBsxAaSubAsoValTable          OBJECT-TYPE
    SYNTAX      SEQUENCE OF TmnxBsxAaSubAsoValEntry
    MAX-ACCESS  not-accessible
    STATUS      current
    DESCRIPTION
        "The tmnxBsxAaSubAsoValTable contains an entry for each ISA-AA
         subscriber in the system. Each row contains an Application Service
         Option (ASO) characteristic and value applied to the subscriber."
    ::= { tmnxBsxPolicyObjs 19 }

tmnxBsxAaSubAsoValEntry          OBJECT-TYPE
    SYNTAX      TmnxBsxAaSubAsoValEntry
    MAX-ACCESS  not-accessible
    STATUS      current
    DESCRIPTION
        "Each tmnxBsxAaSubAsoValEntry contains an ASO Characteristic and value
         assigned to an ISA-AA subscriber."
    INDEX       {
        tmnxBsxAaGrpPartIndex,
        tmnxBsxAaSubscriberType,
        tmnxBsxAaSubscriber,
        tmnxBsxAsoValCharName
    }
    ::= { tmnxBsxAaSubAsoValTable 1 }

TmnxBsxAaSubAsoValEntry          ::= SEQUENCE
{
    tmnxBsxAaSubAsoValName           TNamedItem,
    tmnxBsxAaSubAsoValDerivedFrom    TmnxBsxAaSubAsoValDerivedFrom
}

tmnxBsxAaSubAsoValName           OBJECT-TYPE
    SYNTAX      TNamedItem
    MAX-ACCESS  read-only
    STATUS      current
    DESCRIPTION
        "The value of tmnxBsxAaSubAsoValName indicates the characteristic value
         applied to the Application assurance subscriber."
    ::= { tmnxBsxAaSubAsoValEntry 1 }

tmnxBsxAaSubAsoValDerivedFrom    OBJECT-TYPE
    SYNTAX      TmnxBsxAaSubAsoValDerivedFrom
    MAX-ACCESS  read-only
    STATUS      current
    DESCRIPTION
        "The value of tmnxBsxAaSubAsoValDerivedFrom indicates from where the
         characteristic value is derived from for the Application Assurance
         subscriber."
    ::= { tmnxBsxAaSubAsoValEntry 2 }

tmnxBsxAaSubPolicerTable         OBJECT-TYPE
    SYNTAX      SEQUENCE OF TmnxBsxAaSubPolicerEntry
    MAX-ACCESS  not-accessible
    STATUS      current
    DESCRIPTION
        "The tmnxBsxAaSubPolicerTable contains an entry for each Application
         Assurance subscriber in the system. Each row contains information on
         Policer resources applied to the subscriber.

         The typical usage of this table is to fill in the part of the index
         that identifies a subscriber (tmnxBsxAaGrpPartIndex,
         tmnxBsxAaSubscriberType and tmnxBsxAaSubscriber), and perform a
         partial walk to retrieve the policer information. In order to prevent
         real-time issues, an SNMP get next request which results in a change
         in subscriber will return not-found."
    ::= { tmnxBsxPolicyObjs 20 }

tmnxBsxAaSubPolicerEntry         OBJECT-TYPE
    SYNTAX      TmnxBsxAaSubPolicerEntry
    MAX-ACCESS  not-accessible
    STATUS      current
    DESCRIPTION
        "Each tmnxBsxAaSubPolicerEntry contains information on Policer
         resources applied to the subscriber."
    INDEX       {
        tmnxBsxAaGrpPartIndex,
        tmnxBsxAaSubscriberType,
        tmnxBsxAaSubscriber,
        tmnxBsxAaSubPolicerType,
        tmnxBsxAaSubPolicerDirection,
        tmnxBsxAaSubPolicerIndex
    }
    ::= { tmnxBsxAaSubPolicerTable 1 }

TmnxBsxAaSubPolicerEntry         ::= SEQUENCE
{
    tmnxBsxAaSubPolicerType          TmnxBsxPolicerType,
    tmnxBsxAaSubPolicerDirection     TmnxBsxDirection,
    tmnxBsxAaSubPolicerIndex         Integer32,
    tmnxBsxAaSubPolicerAqpEntryId    TEntryId,
    tmnxBsxAaSubPolicerName          TNamedItem
}

tmnxBsxAaSubPolicerType          OBJECT-TYPE
    SYNTAX      TmnxBsxPolicerType
    MAX-ACCESS  not-accessible
    STATUS      current
    DESCRIPTION
        "The value of tmnxBsxAaSubPolicerType indicates if the policer being
         applied to the subscriber is a bandwidth, flow rate, or a flow count
         policer."
    ::= { tmnxBsxAaSubPolicerEntry 1 }

tmnxBsxAaSubPolicerDirection     OBJECT-TYPE
    SYNTAX      TmnxBsxDirection
    MAX-ACCESS  not-accessible
    STATUS      current
    DESCRIPTION
        "The value of tmnxBsxAaSubPolicerDirection indicates the traffic
         direction of the policer being applied to the subscriber."
    ::= { tmnxBsxAaSubPolicerEntry 2 }

tmnxBsxAaSubPolicerIndex         OBJECT-TYPE
    SYNTAX      Integer32 (1..4096)
    MAX-ACCESS  not-accessible
    STATUS      current
    DESCRIPTION
        "The value of tmnxBsxAaSubPolicerIndex indicates the index into a list
         of policers being applied to the subscriber."
    ::= { tmnxBsxAaSubPolicerEntry 3 }

tmnxBsxAaSubPolicerAqpEntryId    OBJECT-TYPE
    SYNTAX      TEntryId
    MAX-ACCESS  read-only
    STATUS      current
    DESCRIPTION
        "The value of tmnxBsxAaSubPolicerAqpEntryId indicates the
         tmnxBsxAqpBaseEntryId that references the policer."
    ::= { tmnxBsxAaSubPolicerEntry 4 }

tmnxBsxAaSubPolicerName          OBJECT-TYPE
    SYNTAX      TNamedItem
    MAX-ACCESS  read-only
    STATUS      current
    DESCRIPTION
        "The value of tmnxBsxAaSubPolicerName indicates the policer name being
         applied to the subscriber."
    ::= { tmnxBsxAaSubPolicerEntry 5 }

tmnxBsxAaSubPolResExTable        OBJECT-TYPE
    SYNTAX      SEQUENCE OF TmnxBsxAaSubPolResExEntry
    MAX-ACCESS  not-accessible
    STATUS      obsolete
    DESCRIPTION
        "The tmnxBsxAaSubPolResExTable contains an entry for each Application
         Assurance subscriber which has exceeded policer resources.

         This table was obsoleted in SR13.0R1"
    ::= { tmnxBsxPolicyObjs 21 }

tmnxBsxAaSubPolResExEntry        OBJECT-TYPE
    SYNTAX      TmnxBsxAaSubPolResExEntry
    MAX-ACCESS  not-accessible
    STATUS      obsolete
    DESCRIPTION
        "Each tmnxBsxAaSubPolResExEntry contains information on a subscriber
         that has exceeded policer resources.

         This entry was obsoleted in SR13.0R1"
    INDEX       {
        tmnxBsxAaGrpPartIndex,
        tmnxBsxAaSubscriberType,
        tmnxBsxAaSubscriber
    }
    ::= { tmnxBsxAaSubPolResExTable 1 }

TmnxBsxAaSubPolResExEntry        ::= SEQUENCE
{ tmnxBsxAaSubPolResExStatus       TmnxBsxAaSubPolicerResStatus }

tmnxBsxAaSubPolResExStatus       OBJECT-TYPE
    SYNTAX      TmnxBsxAaSubPolicerResStatus
    MAX-ACCESS  read-only
    STATUS      obsolete
    DESCRIPTION
        "The value of tmnxBsxAaSubPolResExStatus indicates the status of
         policer resources being applied to the subscriber.

         This object was obsoleted in SR13.0R1"
    ::= { tmnxBsxAaSubPolResExEntry 1 }

tmnxBsxPolicyScalars             OBJECT IDENTIFIER ::= { tmnxBsxPolicyObjs 22 }

tmnxBsxPlcyCfgLastChTime         OBJECT-TYPE
    SYNTAX      TimeStamp
    MAX-ACCESS  read-only
    STATUS      current
    DESCRIPTION
        "The value of tmnxBsxPlcyCfgLastChTime indicates the last time, since
         system startup, a successful set was performed on the
         tmnxBsxPlcyCfgTable."
    ::= { tmnxBsxPolicyScalars 1 }

tmnxBsxChargeGrpLastChTime       OBJECT-TYPE
    SYNTAX      TimeStamp
    MAX-ACCESS  read-only
    STATUS      current
    DESCRIPTION
        "The value of tmnxBsxChargeGrpLastChTime indicates the last time, since
         system startup, a successful set was performed on the
         tmnxBsxChargeGrpCfgTable."
    ::= { tmnxBsxPolicyScalars 2 }

tmnxBsxPolicerLastChTime         OBJECT-TYPE
    SYNTAX      TimeStamp
    MAX-ACCESS  read-only
    STATUS      current
    DESCRIPTION
        "The value of tmnxBsxPolicerLastChTime indicates the last time, since
         system startup, a successful set was performed on the
         tmnxBsxPolicerTable."
    ::= { tmnxBsxPolicyScalars 3 }

tmnxBsxPolicerOvrdLastChTime     OBJECT-TYPE
    SYNTAX      TimeStamp
    MAX-ACCESS  read-only
    STATUS      current
    DESCRIPTION
        "The value of tmnxBsxPolicerOvrdLastChTime indicates the last time,
         since system startup, a successful set was performed on the
         tmnxBsxPolicerOvrdTable."
    ::= { tmnxBsxPolicyScalars 4 }

tmnxBsxAppGrpLastChTime          OBJECT-TYPE
    SYNTAX      TimeStamp
    MAX-ACCESS  read-only
    STATUS      current
    DESCRIPTION
        "The value of tmnxBsxAppGrpLastChTime indicates the last time, since
         system startup, a successful set was performed on the
         tmnxBsxAppGrpCfgTable."
    ::= { tmnxBsxPolicyScalars 5 }

tmnxBsxAqpLastChTime             OBJECT-TYPE
    SYNTAX      TimeStamp
    MAX-ACCESS  read-only
    STATUS      obsolete
    DESCRIPTION
        "The value of tmnxBsxAqpLastChTime indicates the last time, since
         system startup, a successful set was performed on the tmnxBsxAqpTable."
    ::= { tmnxBsxPolicyScalars 6 }

tmnxBsxAppLastChTime             OBJECT-TYPE
    SYNTAX      TimeStamp
    MAX-ACCESS  read-only
    STATUS      current
    DESCRIPTION
        "The value of tmnxBsxAppLastChTime indicates the last time, since
         system startup, a successful set was performed on the
         tmnxBsxAppCfgTable."
    ::= { tmnxBsxPolicyScalars 7 }

tmnxBsxAppFilterLastChTime       OBJECT-TYPE
    SYNTAX      TimeStamp
    MAX-ACCESS  read-only
    STATUS      current
    DESCRIPTION
        "The value of tmnxBsxAppFilterLastChTime indicates the last time, since
         system startup, a successful set was performed on the
         tmnxBsxAppFilterTable."
    ::= { tmnxBsxPolicyScalars 8 }

tmnxBsxProtLastChTime            OBJECT-TYPE
    SYNTAX      TimeStamp
    MAX-ACCESS  read-only
    STATUS      current
    DESCRIPTION
        "The value of tmnxBsxProtLastChTime indicates the last time, since
         system startup, a successful set was performed on the
         tmnxBsxProtTable."
    ::= { tmnxBsxPolicyScalars 9 }

tmnxBsxCustProtLastChTime        OBJECT-TYPE
    SYNTAX      TimeStamp
    MAX-ACCESS  read-only
    STATUS      current
    DESCRIPTION
        "The value of tmnxBsxCustProtLastChTime indicates the last time, since
         system startup, a successful set was performed on the
         tmnxBsxCustProtTable."
    ::= { tmnxBsxPolicyScalars 10 }

tmnxBsxCustProtExprLastChTime    OBJECT-TYPE
    SYNTAX      TimeStamp
    MAX-ACCESS  read-only
    STATUS      current
    DESCRIPTION
        "The value of tmnxBsxCustProtExprLastChTime indicates the last time,
         since system startup, a successful set was performed on the
         tmnxBsxCustProtExprTable."
    ::= { tmnxBsxPolicyScalars 11 }

tmnxBsxAsoLastChTime             OBJECT-TYPE
    SYNTAX      TimeStamp
    MAX-ACCESS  read-only
    STATUS      current
    DESCRIPTION
        "The value of tmnxBsxAsoLastChTime indicates the last time, since
         system startup, a successful set was performed on the tmnxBsxAsoTable."
    ::= { tmnxBsxPolicyScalars 12 }

tmnxBsxAsoValLastChTime          OBJECT-TYPE
    SYNTAX      TimeStamp
    MAX-ACCESS  read-only
    STATUS      current
    DESCRIPTION
        "The value of tmnxBsxAsoValLastChTime indicates the last time, since
         system startup, a successful set was performed on the
         tmnxBsxAsoValTable."
    ::= { tmnxBsxPolicyScalars 13 }

tmnxBsxAppProfLastChTime         OBJECT-TYPE
    SYNTAX      TimeStamp
    MAX-ACCESS  read-only
    STATUS      current
    DESCRIPTION
        "The value of tmnxBsxAppProfLastChTime indicates the last time, since
         system startup, a successful set was performed on the
         tmnxBsxAppProfTable."
    ::= { tmnxBsxPolicyScalars 14 }

tmnxBsxAppProfCharLastChTime     OBJECT-TYPE
    SYNTAX      TimeStamp
    MAX-ACCESS  read-only
    STATUS      current
    DESCRIPTION
        "The value of tmnxBsxAppProfCharLastChTime indicates the last time,
         since system startup, a successful set was performed on the
         tmnxBsxAppProfCharTable."
    ::= { tmnxBsxPolicyScalars 15 }

tmnxBsxAqpCharLastChTime         OBJECT-TYPE
    SYNTAX      TimeStamp
    MAX-ACCESS  read-only
    STATUS      current
    DESCRIPTION
        "The value of tmnxBsxAqpCharLastChTime indicates the last time, since
         system startup, a successful set was performed on the
         tmnxBsxAqpCharTable."
    ::= { tmnxBsxPolicyScalars 16 }

tmnxBsxAppFilterExprLastChTime   OBJECT-TYPE
    SYNTAX      TimeStamp
    MAX-ACCESS  read-only
    STATUS      current
    DESCRIPTION
        "The value of tmnxBsxAppFilterExprLastChTime indicates the last time,
         since system startup, a successful set was performed on the
         tmnxBsxAppFilterExprTable."
    ::= { tmnxBsxPolicyScalars 17 }

tmnxBsxPrefixListLastChTime      OBJECT-TYPE
    SYNTAX      TimeStamp
    MAX-ACCESS  read-only
    STATUS      current
    DESCRIPTION
        "The value of tmnxBsxPrefixListLastChTime indicates the last time,
         since system startup, a successful set was performed on the
         tmnxBsxPrefixListLastChTime."
    ::= { tmnxBsxPolicyScalars 18 }

tmnxBsxPrefixLastChTime          OBJECT-TYPE
    SYNTAX      TimeStamp
    MAX-ACCESS  read-only
    STATUS      current
    DESCRIPTION
        "The value of tmnxBsxPrefixLastChTime indicates the last time, since
         system startup, a successful set was performed on the
         tmnxBsxPrefixTable."
    ::= { tmnxBsxPolicyScalars 19 }

tmnxBsxEventLogLastChTime        OBJECT-TYPE
    SYNTAX      TimeStamp
    MAX-ACCESS  read-only
    STATUS      current
    DESCRIPTION
        "The value of tmnxBsxEventLogLastChTime indicates the last time, since
         system startup, a successful set was performed on the
         tmnxBsxEventLogTable."
    ::= { tmnxBsxPolicyScalars 20 }

tmnxBsxAqpBaseLastChTime         OBJECT-TYPE
    SYNTAX      TimeStamp
    MAX-ACCESS  read-only
    STATUS      current
    DESCRIPTION
        "The value of tmnxBsxAqpBaseLastChTime indicates the last time, since
         system startup, a successful set was performed on the
         tmnxBsxAqpBaseTable."
    ::= { tmnxBsxPolicyScalars 21 }

tmnxBsxAqpMatchLastChTime        OBJECT-TYPE
    SYNTAX      TimeStamp
    MAX-ACCESS  read-only
    STATUS      current
    DESCRIPTION
        "The value of tmnxBsxAqpMatchLastChTime indicates the last time, since
         system startup, a successful set was performed on the
         tmnxBsxAqpMatchTable."
    ::= { tmnxBsxPolicyScalars 22 }

tmnxBsxAqpActionLastChTime       OBJECT-TYPE
    SYNTAX      TimeStamp
    MAX-ACCESS  read-only
    STATUS      current
    DESCRIPTION
        "The value of tmnxBsxAqpActionLastChTime indicates the last time, since
         system startup, a successful set was performed on the
         tmnxBsxAqpActionTable."
    ::= { tmnxBsxPolicyScalars 23 }

tmnxBsxCflowdRecFieldLastChTime  OBJECT-TYPE
    SYNTAX      TimeStamp
    MAX-ACCESS  read-only
    STATUS      current
    DESCRIPTION
        "The value of tmnxBsxCflowdRecFieldLastChTime indicates the last time,
         since system startup, a successful set was performed on the
         tmnxBsxCflowdRecordFieldTable."
    ::= { tmnxBsxPolicyScalars 24 }

tmnxBsxHttpNotifyTmplLastChTime  OBJECT-TYPE
    SYNTAX      TimeStamp
    MAX-ACCESS  read-only
    STATUS      current
    DESCRIPTION
        "The value of tmnxBsxHttpNotifyTmplLastChTime indicates the last time,
         since system startup, a successful set was performed on the
         tmnxBsxHttpNotifyTmplTable."
    ::= { tmnxBsxPolicyScalars 25 }

tmnxBsxHttpRedirTmplLastChTime   OBJECT-TYPE
    SYNTAX      TimeStamp
    MAX-ACCESS  read-only
    STATUS      current
    DESCRIPTION
        "The value of tmnxBsxHttpRedirTmplLastChTime indicates the last time,
         since system startup, a successful set was performed on the
         tmnxBsxHttpRedirTmplTable."
    ::= { tmnxBsxPolicyScalars 27 }

tmnxBsxHttpErrRedirTmpLastChTime OBJECT-TYPE
    SYNTAX      TimeStamp
    MAX-ACCESS  read-only
    STATUS      current
    DESCRIPTION
        "The value of tmnxBsxHttpErrRedirTmpLastChTime indicates the last time,
         since system startup, a successful set was performed on the
         tmnxBsxHttpErrRedirTmplTable."
    ::= { tmnxBsxPolicyScalars 28 }

tmnxBsxHttpRedirErrCodLastChTime OBJECT-TYPE
    SYNTAX      TimeStamp
    MAX-ACCESS  read-only
    STATUS      current
    DESCRIPTION
        "The value of tmnxBsxHttpRedirErrCodLastChTime indicates the last time,
         since system startup, a successful set was performed on the
         tmnxBsxHttpRedirErrorCodeTable."
    ::= { tmnxBsxPolicyScalars 29 }

tmnxBsxHttpEnrFieldLastChTime    OBJECT-TYPE
    SYNTAX      TimeStamp
    MAX-ACCESS  read-only
    STATUS      current
    DESCRIPTION
        "The value of tmnxBsxHttpEnrFieldLastChTime indicates the last time,
         since system startup, a successful set was performed on the
         tmnxBsxHttpEnrFieldTable."
    ::= { tmnxBsxPolicyScalars 30 }

tmnxBsxFlowAttrLastChTime        OBJECT-TYPE
    SYNTAX      TimeStamp
    MAX-ACCESS  read-only
    STATUS      current
    DESCRIPTION
        "The value of tmnxBsxFlowAttrLastChTime indicates the last time, since
         system startup, a successful set was performed on the
         tmnxBsxFlowAttrTable."
    ::= { tmnxBsxPolicyScalars 31 }

tmnxBsxChargeGrpCfgTable         OBJECT-TYPE
    SYNTAX      SEQUENCE OF TmnxBsxChargeGrpCfgEntry
    MAX-ACCESS  not-accessible
    STATUS      current
    DESCRIPTION
        "The tmnxBsxChargeGrpCfgTable contains an entry for each Application
         Assurance charging group."
    ::= { tmnxBsxPolicyObjs 23 }

tmnxBsxChargeGrpCfgEntry         OBJECT-TYPE
    SYNTAX      TmnxBsxChargeGrpCfgEntry
    MAX-ACCESS  not-accessible
    STATUS      current
    DESCRIPTION
        "Each tmnxBsxChargeGrpCfgEntry indicates a charging group configured by
         the operator.

         Rows in this table are created and destroyed using the
         tmnxBsxChargeGrpRowStatus object."
    INDEX       {
        tmnxBsxChargeGrpPolicyVersion,
        tmnxBsxAaGrpPartIndex,
        IMPLIED tmnxBsxChargeGrpName
    }
    ::= { tmnxBsxChargeGrpCfgTable 1 }

TmnxBsxChargeGrpCfgEntry         ::= SEQUENCE
{
    tmnxBsxChargeGrpPolicyVersion    TmnxBsxPolicyVersion,
    tmnxBsxChargeGrpName             TNamedItem,
    tmnxBsxChargeGrpRowStatus        RowStatus,
    tmnxBsxChargeGrpRowLastCh        TimeStamp,
    tmnxBsxChargeGrpDescription      TItemDescription,
    tmnxBsxChargeGrpExportId         Unsigned32,
    tmnxBsxChargeGrpNotifyStartStop  INTEGER
}

tmnxBsxChargeGrpPolicyVersion    OBJECT-TYPE
    SYNTAX      TmnxBsxPolicyVersion
    MAX-ACCESS  not-accessible
    STATUS      current
    DESCRIPTION
        "The value of tmnxBsxChargeGrpPolicyVersion indicates the
         version of the table being accessed.  The row
         is read-create only for the 'admin' version of
         the table.  The 'oper' version is read-only."
    ::= { tmnxBsxChargeGrpCfgEntry 1 }

tmnxBsxChargeGrpName             OBJECT-TYPE
    SYNTAX      TNamedItem
    MAX-ACCESS  not-accessible
    STATUS      current
    DESCRIPTION
        "The value of tmnxBsxChargeGrpName specifies the charging group name."
    ::= { tmnxBsxChargeGrpCfgEntry 2 }

tmnxBsxChargeGrpRowStatus        OBJECT-TYPE
    SYNTAX      RowStatus
    MAX-ACCESS  read-create
    STATUS      current
    DESCRIPTION
        "The value of tmnxBsxChargeGrpRowStatus specifies the
         row status.  It allows entries to be created
         and deleted in the tmnxBsxChargeGrpCfgTable.  To
         delete an entry, all references to this charging
         group must be removed.

         References in the tmnxBsxAppCfgTable can be found where the
         tmnxBsxAaGrpPartIndex are equal and tmnxBsxAppChargeGrp matches the
         tmnxBsxChargeGrpName.

         References in the tmnxBsxAppGrpCfgTable can be found where the
         tmnxBsxAaGrpPartIndex are equal and tmnxBsxAppGrpChargeGrp matches the
         tmnxBsxChargeGrpName.

         References in the tmnxBsxPlcyCfgTable can be found where the
         tmnxBsxAaGrpPartIndex are equal and tmnxBsxPlcyDefChargeGrp matches
         the tmnxBsxChargeGrpName.

         Rows are created by specifying the value of 'createAndGo (4)', and
         deleted by specifying the value of 'destroy (6)'."
    ::= { tmnxBsxChargeGrpCfgEntry 3 }

tmnxBsxChargeGrpRowLastCh        OBJECT-TYPE
    SYNTAX      TimeStamp
    MAX-ACCESS  read-only
    STATUS      current
    DESCRIPTION
        "The value of tmnxBsxChargeGrpRowLastCh indicates the last time, since
         system startup, a successful set was performed on this row."
    ::= { tmnxBsxChargeGrpCfgEntry 4 }

tmnxBsxChargeGrpDescription      OBJECT-TYPE
    SYNTAX      TItemDescription
    MAX-ACCESS  read-create
    STATUS      current
    DESCRIPTION
        "The value of tmnxBsxChargeGrpDescription specifies the description of
         the charging group."
    DEFVAL      { "" }
    ::= { tmnxBsxChargeGrpCfgEntry 5 }

tmnxBsxChargeGrpExportId         OBJECT-TYPE
    SYNTAX      Unsigned32 (0 | 1..255)
    MAX-ACCESS  read-create
    STATUS      current
    DESCRIPTION
        "The value of tmnxBsxChargeGrpExportId specifies the identifier used to
         represent the charging group in the accounting records.  This
         identifier must be unique within the policy.

         When tmnxBsxChargeGrpExportId has a value of 0, RADIUS accounting
         records will not be exported for this charging group."
    DEFVAL      { 0 }
    ::= { tmnxBsxChargeGrpCfgEntry 6 }

tmnxBsxChargeGrpNotifyStartStop  OBJECT-TYPE
    SYNTAX      INTEGER {
        none          (1),
        flow          (2),
        chargingGroup (3),
        reserved4     (4)
    }
    MAX-ACCESS  read-create
    STATUS      current
    DESCRIPTION
        "The value of tmnxBsxChargeGrpNotifyStartStop specifies the type
         of start-stop notifications to generate.
         The type may be one of:
           none          (1) - no start-stop notifications are generated
           flow          (2) - an application start event may be sent to the
                               ISA-MG for each flow matching the
                               charging-group and a stop event when each flow
                               terminates, or times out
           chargingGroup (3) - an application start event may be sent to the
                               ISA-MG for the first flow matching the
                               charging-group and a stop event when the last
                               flow terminates, or times out
           dynamicRating (4) - enables dynamic rating start and stop notifications.
                               An application-start will be sent when AA detects
                               traffic matching the app-filter configured with
                               dynamic-rating-action=start. An application-stop
                               will be sent when aa detects traffic matching the
                               app-filter configured with dynamic-rating-action=stop
                               or if dynamic-rating timeout has expired and AA has
                               not detected traffic matching an app-filter configured
                               with dynamic-rating-action=keep-alive."
    DEFVAL      { none }
    ::= { tmnxBsxChargeGrpCfgEntry 7 }

tmnxBsxPlcyCfgTable              OBJECT-TYPE
    SYNTAX      SEQUENCE OF TmnxBsxPlcyCfgEntry
    MAX-ACCESS  not-accessible
    STATUS      current
    DESCRIPTION
        "The tmnxBsxPlcyCfgTable contains policy configuration for each
         application-assurance group."
    ::= { tmnxBsxPolicyObjs 24 }

tmnxBsxPlcyCfgEntry              OBJECT-TYPE
    SYNTAX      TmnxBsxPlcyCfgEntry
    MAX-ACCESS  not-accessible
    STATUS      current
    DESCRIPTION
        "Each tmnxBsxPlcyCfgEntry specifies the policy information configured
         by the operator.

         The tmnxBsxPlcyCfgEntry is automatically created when the AA group is
         created in the tmnxBsxAaGrpPartTable."
    INDEX       {
        tmnxBsxPlcyPolicyVersion,
        tmnxBsxAaGrpPartIndex
    }
    ::= { tmnxBsxPlcyCfgTable 1 }

TmnxBsxPlcyCfgEntry              ::= SEQUENCE
{
    tmnxBsxPlcyPolicyVersion         TmnxBsxPolicyVersion,
    tmnxBsxPlcyRowLastCh             TimeStamp,
    tmnxBsxPlcyDefChargeGrp          TNamedItemOrEmpty,
    tmnxBsxPlcyDefTetherChargeGrp    TNamedItemOrEmpty
}

tmnxBsxPlcyPolicyVersion         OBJECT-TYPE
    SYNTAX      TmnxBsxPolicyVersion
    MAX-ACCESS  not-accessible
    STATUS      current
    DESCRIPTION
        "The value of tmnxBsxPlcyPolicyVersion specifies the
         version of the table being accessed.  The table
         is read-create only for the 'admin' version of
         the table.  The 'oper' version is read-only."
    ::= { tmnxBsxPlcyCfgEntry 1 }

tmnxBsxPlcyRowLastCh             OBJECT-TYPE
    SYNTAX      TimeStamp
    MAX-ACCESS  read-only
    STATUS      current
    DESCRIPTION
        "The value of tmnxBsxPlcyRowLastCh indicates the last time, since
         system startup, a successful set was performed on this row of the
         tmnxBsxPlcyCfgTable."
    ::= { tmnxBsxPlcyCfgEntry 2 }

tmnxBsxPlcyDefChargeGrp          OBJECT-TYPE
    SYNTAX      TNamedItemOrEmpty
    MAX-ACCESS  read-create
    STATUS      current
    DESCRIPTION
        "The value of tmnxBsxPlcyDefChargeGrp specifies the name of the default
         charging group to be applied to an AA transit subscriber."
    DEFVAL      { "" }
    ::= { tmnxBsxPlcyCfgEntry 3 }

tmnxBsxPlcyDefTetherChargeGrp    OBJECT-TYPE
    SYNTAX      TNamedItemOrEmpty
    MAX-ACCESS  read-create
    STATUS      current
    DESCRIPTION
        "The value of tmnxBsxPlcyDefTetherChargeGrp specifies the name of the
         default tethered charging group to be applied to an AA transit
         subscriber for tethered traffic."
    DEFVAL      { "" }
    ::= { tmnxBsxPlcyCfgEntry 4 }

tmnxBsxPolicerOvrdTable          OBJECT-TYPE
    SYNTAX      SEQUENCE OF TmnxBsxPolicerOvrdEntry
    MAX-ACCESS  not-accessible
    STATUS      current
    DESCRIPTION
        "The tmnxBsxPolicerOvrdTable contains the policer time of day override
         templates for adjusting the policer's rules for rate limiting
         bandwidth and flows and limiting the number of flows depending on the
         type of policer defined by tmnxBsxPolicerType."
    ::= { tmnxBsxPolicyObjs 25 }

tmnxBsxPolicerOvrdEntry          OBJECT-TYPE
    SYNTAX      TmnxBsxPolicerOvrdEntry
    MAX-ACCESS  not-accessible
    STATUS      current
    DESCRIPTION
        "Each tmnxBsxPolicerOvrdEntry indicates a policer time of day override
         template.

         The specification of time range must include the specification
         of the following objects:
            - tmnxBsxPolicerOvrdDayList or
                    tmnxBsxPolicerOvrdStartDay and tmnxBsxPolicerOvrdEndDay
            - tmnxBsxPolicerOvrdStartHour and tmnxBsxPolicerOvrdStartMinute
            - tmnxBsxPolicerOvrdEndHour and tmnxBsxPolicerOvrdEndMinute.

         Additionally, when a policer, tmnxBsxPolicerName, is delete the
         corresponding overrides for that policer will also be deleted by the
         system."
    INDEX       {
        tmnxBsxIsaAaGroupIndex,
        tmnxBsxPolicerName,
        tmnxBsxPolicerOvrdIndex
    }
    ::= { tmnxBsxPolicerOvrdTable 1 }

TmnxBsxPolicerOvrdEntry          ::= SEQUENCE
{
    tmnxBsxPolicerOvrdIndex          Integer32,
    tmnxBsxPolicerOvrdRowStatus      RowStatus,
    tmnxBsxPolicerOvrdRowLastChange  TimeStamp,
    tmnxBsxPolicerOvrdDescription    TItemDescription,
    tmnxBsxPolicerOvrdAdminState     TmnxAdminState,
    tmnxBsxPolicerOvrdDayList        TmnxDayOfWeekList,
    tmnxBsxPolicerOvrdStartDay       TmnxDayOfWeek,
    tmnxBsxPolicerOvrdStartHour      Integer32,
    tmnxBsxPolicerOvrdStartMinute    Integer32,
    tmnxBsxPolicerOvrdEndDay         TmnxDayOfWeek,
    tmnxBsxPolicerOvrdEndHour        Integer32,
    tmnxBsxPolicerOvrdEndMinute      Integer32,
    tmnxBsxPolicerOvrdAdminPIR       TPIRRateOrZero,
    tmnxBsxPolicerOvrdAdminCIR       TCIRRate,
    tmnxBsxPolicerOvrdMBS            TmnxBsxBurstSize,
    tmnxBsxPolicerOvrdCBS            TmnxBsxBurstSize
}

tmnxBsxPolicerOvrdIndex          OBJECT-TYPE
    SYNTAX      Integer32 (1..255)
    MAX-ACCESS  not-accessible
    STATUS      current
    DESCRIPTION
        "The value of tmnxBsxPolicerOvrdIndex specifies the index defined for
         the time of day override of the policer.

         When there are multiple overrides which apply to the same time period
         the override with the highest index value will be applied."
    ::= { tmnxBsxPolicerOvrdEntry 1 }

tmnxBsxPolicerOvrdRowStatus      OBJECT-TYPE
    SYNTAX      RowStatus
    MAX-ACCESS  read-create
    STATUS      current
    DESCRIPTION
        "The value of tmnxBsxPolicerOvrdRowStatus specifies the
         row status.  It allows entries to be created
         and deleted in the tmnxBsxPolicerOvrdTable."
    ::= { tmnxBsxPolicerOvrdEntry 2 }

tmnxBsxPolicerOvrdRowLastChange  OBJECT-TYPE
    SYNTAX      TimeStamp
    MAX-ACCESS  read-only
    STATUS      current
    DESCRIPTION
        "The value of tmnxBsxPolicerOvrdRowLastChange indicates the last time,
         since system startup, a successful set was performed on this row."
    ::= { tmnxBsxPolicerOvrdEntry 3 }

tmnxBsxPolicerOvrdDescription    OBJECT-TYPE
    SYNTAX      TItemDescription
    MAX-ACCESS  read-create
    STATUS      current
    DESCRIPTION
        "The value of tmnxBsxPolicerOvrdDescription specifies the description
         of the policer time of day override."
    DEFVAL      { "" }
    ::= { tmnxBsxPolicerOvrdEntry 4 }

tmnxBsxPolicerOvrdAdminState     OBJECT-TYPE
    SYNTAX      TmnxAdminState
    MAX-ACCESS  read-create
    STATUS      current
    DESCRIPTION
        "The value of tmnxBsxPolicerOvrdAdminState specifies the administrative
         state of the Policer override. When the value is 'outOfService(3)' the
         override is disabled."
    DEFVAL      { outOfService }
    ::= { tmnxBsxPolicerOvrdEntry 5 }

tmnxBsxPolicerOvrdDayList        OBJECT-TYPE
    SYNTAX      TmnxDayOfWeekList
    MAX-ACCESS  read-create
    STATUS      current
    DESCRIPTION
        "The value of tmnxBsxPolicerOvrdDayList specifies the days for which
         this override applies.

         The specification of tmnxBsxPolicerOvrdDayList is mutually exclusive
         with the specification of tmnxBsxPolicerOvrdStartDay and
         tmnxBsxPolicerOvrdEndDay."
    DEFVAL      { {} }
    ::= { tmnxBsxPolicerOvrdEntry 6 }

tmnxBsxPolicerOvrdStartDay       OBJECT-TYPE
    SYNTAX      TmnxDayOfWeek
    MAX-ACCESS  read-create
    STATUS      current
    DESCRIPTION
        "The value of tmnxBsxPolicerOvrdStartDay specifies the start day of the
         time range for which this override applies.

         The specification of tmnxBsxPolicerOvrdStartDay is mutually exclusive
         with the specification of tmnxBsxPolicerOvrdDayList."
    DEFVAL      { unspecified }
    ::= { tmnxBsxPolicerOvrdEntry 7 }

tmnxBsxPolicerOvrdStartHour      OBJECT-TYPE
    SYNTAX      Integer32 (0..23)
    MAX-ACCESS  read-create
    STATUS      current
    DESCRIPTION
        "The value of tmnxBsxPolicerOvrdStartHour specifies the start hour for
         this override."
    DEFVAL      { 0 }
    ::= { tmnxBsxPolicerOvrdEntry 8 }

tmnxBsxPolicerOvrdStartMinute    OBJECT-TYPE
    SYNTAX      Integer32 (0..59)
    MAX-ACCESS  read-create
    STATUS      current
    DESCRIPTION
        "The value of tmnxBsxPolicerOvrdStartMinute specifies the start minute
         for this override in 15 minute increments (0, 15, 30, or 45)."
    DEFVAL      { 0 }
    ::= { tmnxBsxPolicerOvrdEntry 9 }

tmnxBsxPolicerOvrdEndDay         OBJECT-TYPE
    SYNTAX      TmnxDayOfWeek
    MAX-ACCESS  read-create
    STATUS      current
    DESCRIPTION
        "The value of tmnxBsxPolicerOvrdEndDay specifies the last day of the
         time range for which this override applies.

         The specification of tmnxBsxPolicerOvrdEndDay is mutually exclusive
         with the specification of tmnxBsxPolicerOvrdDayList."
    DEFVAL      { unspecified }
    ::= { tmnxBsxPolicerOvrdEntry 10 }

tmnxBsxPolicerOvrdEndHour        OBJECT-TYPE
    SYNTAX      Integer32 (0..24)
    MAX-ACCESS  read-create
    STATUS      current
    DESCRIPTION
        "The value of tmnxBsxPolicerOvrdEndHour specifies the end hour for this
         override."
    DEFVAL      { 24 }
    ::= { tmnxBsxPolicerOvrdEntry 11 }

tmnxBsxPolicerOvrdEndMinute      OBJECT-TYPE
    SYNTAX      Integer32 (0..59)
    MAX-ACCESS  read-create
    STATUS      current
    DESCRIPTION
        "The value of tmnxBsxPolicerOvrdEndMinute specifies the start minute
         for this override in 15 minute increments (0, 15, 30, or 45)."
    DEFVAL      { 0 }
    ::= { tmnxBsxPolicerOvrdEntry 12 }

tmnxBsxPolicerOvrdAdminPIR       OBJECT-TYPE
    SYNTAX      TPIRRateOrZero
    UNITS       "kbps or flows"
    MAX-ACCESS  read-create
    STATUS      current
    DESCRIPTION
        "The value of tmnxBsxPolicerOvrdAdminPIR specifies the administrative
         PIR (Peak Information Rate).

         A value of 0, meaning block flows, is only applicable for rows where
         tmnxBsxPolicerType has a value of 'flowCountLimit (4)'."
    DEFVAL      { -1 }
    ::= { tmnxBsxPolicerOvrdEntry 13 }

tmnxBsxPolicerOvrdAdminCIR       OBJECT-TYPE
    SYNTAX      TCIRRate
    UNITS       "kbps or flows"
    MAX-ACCESS  read-create
    STATUS      current
    DESCRIPTION
        "The value of tmnxBsxPolicerOvrdAdminCIR specifies the administrative
         CIR (Committed Information Rate)."
    DEFVAL      { 0 }
    ::= { tmnxBsxPolicerOvrdEntry 14 }

tmnxBsxPolicerOvrdMBS            OBJECT-TYPE
    SYNTAX      TmnxBsxBurstSize
    UNITS       "KB or flows"
    MAX-ACCESS  read-create
    STATUS      current
    DESCRIPTION
        "The value of tmnxBsxPolicerOvrdMBS specifies the maximum burst size
         specified by the user to be used in conjunction with the PIR."
    DEFVAL      { 0 }
    ::= { tmnxBsxPolicerOvrdEntry 15 }

tmnxBsxPolicerOvrdCBS            OBJECT-TYPE
    SYNTAX      TmnxBsxBurstSize
    UNITS       "KB or flows"
    MAX-ACCESS  read-create
    STATUS      current
    DESCRIPTION
        "The value of tmnxBsxPolicerOvrdCBS specifies the committed burst size
         specified by the user to be used in conjunction with the CIR."
    DEFVAL      { 0 }
    ::= { tmnxBsxPolicerOvrdEntry 16 }

tmnxBsxPrefixListTable           OBJECT-TYPE
    SYNTAX      SEQUENCE OF TmnxBsxPrefixListEntry
    MAX-ACCESS  not-accessible
    STATUS      current
    DESCRIPTION
        "The tmnxBsxPrefixListTable contains an entry for each prefix list
         defined in Application Assurance."
    ::= { tmnxBsxPolicyObjs 26 }

tmnxBsxPrefixListEntry           OBJECT-TYPE
    SYNTAX      TmnxBsxPrefixListEntry
    MAX-ACCESS  not-accessible
    STATUS      current
    DESCRIPTION
        "Each tmnxBsxPrefixListEntry specifies an IP prefix list which may be
         referenced in the following tables:
             - tmnxBsxAppFilterTable
             - tmnxBsxAqpMatchTable
             - tmnxBsxSessFltrTable"
    INDEX       {
        tmnxBsxAaGrpPartIndex,
        tmnxBsxPrefixListName
    }
    ::= { tmnxBsxPrefixListTable 1 }

TmnxBsxPrefixListEntry           ::= SEQUENCE
{
    tmnxBsxPrefixListName            TNamedItem,
    tmnxBsxPrefixListRowStatus       RowStatus,
    tmnxBsxPrefixListRowLastChange   TimeStamp,
    tmnxBsxPrefixListDescription     TItemDescription
}

tmnxBsxPrefixListName            OBJECT-TYPE
    SYNTAX      TNamedItem
    MAX-ACCESS  not-accessible
    STATUS      current
    DESCRIPTION
        "The value of tmnxBsxPrefixListName specifies the name of the IP Prefix
         List."
    ::= { tmnxBsxPrefixListEntry 1 }

tmnxBsxPrefixListRowStatus       OBJECT-TYPE
    SYNTAX      RowStatus
    MAX-ACCESS  read-create
    STATUS      current
    DESCRIPTION
        "The value of tmnxBsxPrefixListRowStatus specifies the
         row status.  It allows entries to be created
         and deleted in the tmnxBsxPrefixListTable."
    ::= { tmnxBsxPrefixListEntry 2 }

tmnxBsxPrefixListRowLastChange   OBJECT-TYPE
    SYNTAX      TimeStamp
    MAX-ACCESS  read-only
    STATUS      current
    DESCRIPTION
        "The value of tmnxBsxPrefixListRowLastChange indicates the last time,
         since system startup, a successful set was performed on this row."
    ::= { tmnxBsxPrefixListEntry 3 }

tmnxBsxPrefixListDescription     OBJECT-TYPE
    SYNTAX      TItemDescription
    MAX-ACCESS  read-create
    STATUS      current
    DESCRIPTION
        "The value of tmnxBsxPrefixListDescription specifies the description of
         the IP Prefix List."
    DEFVAL      { "" }
    ::= { tmnxBsxPrefixListEntry 4 }

tmnxBsxPrefixTable               OBJECT-TYPE
    SYNTAX      SEQUENCE OF TmnxBsxPrefixEntry
    MAX-ACCESS  not-accessible
    STATUS      current
    DESCRIPTION
        "The tmnxBsxPrefixTable contains an entry for each prefix defined in an
         Application Assurance prefix list."
    ::= { tmnxBsxPolicyObjs 27 }

tmnxBsxPrefixEntry               OBJECT-TYPE
    SYNTAX      TmnxBsxPrefixEntry
    MAX-ACCESS  not-accessible
    STATUS      current
    DESCRIPTION
        "Each tmnxBsxPrefixEntry specifies an IP prefix within an Application
         Assurance prefix list (tmnxBsxPrefixListTable)."
    INDEX       {
        tmnxBsxAaGrpPartIndex,
        tmnxBsxPrefixListName,
        tmnxBsxPrefixType,
        tmnxBsxPrefixAddr,
        tmnxBsxPrefixLength
    }
    ::= { tmnxBsxPrefixTable 1 }

TmnxBsxPrefixEntry               ::= SEQUENCE
{
    tmnxBsxPrefixType                InetAddressType,
    tmnxBsxPrefixAddr                InetAddress,
    tmnxBsxPrefixLength              InetAddressPrefixLength,
    tmnxBsxPrefixRowStatus           RowStatus,
    tmnxBsxPrefixName                TNamedItemOrEmpty
}

tmnxBsxPrefixType                OBJECT-TYPE
    SYNTAX      InetAddressType
    MAX-ACCESS  not-accessible
    STATUS      current
    DESCRIPTION
        "The object tmnxBsxPrefixType specifies the type of prefix specified in
         tmnxBsxPrefixAddr."
    ::= { tmnxBsxPrefixEntry 1 }

tmnxBsxPrefixAddr                OBJECT-TYPE
    SYNTAX      InetAddress (SIZE (4|16))
    MAX-ACCESS  not-accessible
    STATUS      current
    DESCRIPTION
        "The value of tmnxBsxPrefixAddr specifies the address portion of this
         IP prefix."
    ::= { tmnxBsxPrefixEntry 2 }

tmnxBsxPrefixLength              OBJECT-TYPE
    SYNTAX      InetAddressPrefixLength (0..128)
    MAX-ACCESS  not-accessible
    STATUS      current
    DESCRIPTION
        "The value of tmnxBsxPrefixLength specifies the prefix length of this
         IP prefix."
    ::= { tmnxBsxPrefixEntry 3 }

tmnxBsxPrefixRowStatus           OBJECT-TYPE
    SYNTAX      RowStatus
    MAX-ACCESS  read-create
    STATUS      current
    DESCRIPTION
        "The value of tmnxBsxPrefixRowStatus specifies the
         row status.  It allows entries to be created
         and deleted in the tmnxBsxPrefixTable."
    ::= { tmnxBsxPrefixEntry 4 }

tmnxBsxPrefixName                OBJECT-TYPE
    SYNTAX      TNamedItemOrEmpty
    MAX-ACCESS  read-create
    STATUS      current
    DESCRIPTION
        "The value of tmnxBsxPrefixName specifies the name of the IP Prefix
         List Item."
    DEFVAL      { "" }
    ::= { tmnxBsxPrefixEntry 5 }

tmnxBsxEventLogTable             OBJECT-TYPE
    SYNTAX      SEQUENCE OF TmnxBsxEventLogEntry
    MAX-ACCESS  not-accessible
    STATUS      current
    DESCRIPTION
        "The tmnxBsxEventLogTable contains an entry for each event log defined
         in Application Assurance."
    ::= { tmnxBsxPolicyObjs 28 }

tmnxBsxEventLogEntry             OBJECT-TYPE
    SYNTAX      TmnxBsxEventLogEntry
    MAX-ACCESS  not-accessible
    STATUS      current
    DESCRIPTION
        "Each tmnxBsxEventLogEntry specifies an event log which will be used
         when event logging is enabled by all of the following tables:
             - tmnxBsxAqpActionTable
             - tmnxBsxSessFltrTable"
    INDEX       {
        tmnxBsxAaGrpPartIndex,
        tmnxBsxEventLogName
    }
    ::= { tmnxBsxEventLogTable 1 }

TmnxBsxEventLogEntry             ::= SEQUENCE
{
    tmnxBsxEventLogName              TNamedItem,
    tmnxBsxEventLogRowStatus         RowStatus,
    tmnxBsxEventLogRowLastChange     TimeStamp,
    tmnxBsxEventLogBufferType        INTEGER,
    tmnxBsxEventLogMaxEntries        Unsigned32,
    tmnxBsxEventLogAdminState        TmnxAdminState,
    tmnxBsxEventLogSyslogAddrType    InetAddressType,
    tmnxBsxEventLogSyslogAddr        InetAddress,
    tmnxBsxEventLogSyslogPort        TmnxUdpPort,
    tmnxBsxEventLogSyslogDescription TItemDescription,
    tmnxBsxEventLogSyslogVlan        VlanIdOrNone,
    tmnxBsxEventLogSyslogFacility    TmnxSyslogFacility,
    tmnxBsxEventLogSyslogSeverity    TmnxSyslogSeverity
}

tmnxBsxEventLogName              OBJECT-TYPE
    SYNTAX      TNamedItem
    MAX-ACCESS  not-accessible
    STATUS      current
    DESCRIPTION
        "The value of tmnxBsxEventLogName specifies the name of the event log."
    ::= { tmnxBsxEventLogEntry 1 }

tmnxBsxEventLogRowStatus         OBJECT-TYPE
    SYNTAX      RowStatus
    MAX-ACCESS  read-create
    STATUS      current
    DESCRIPTION
        "The value of tmnxBsxEventLogRowStatus specifies the row status.  It
         allows entries to be created and deleted in the tmnxBsxEventLogTable."
    ::= { tmnxBsxEventLogEntry 2 }

tmnxBsxEventLogRowLastChange     OBJECT-TYPE
    SYNTAX      TimeStamp
    MAX-ACCESS  read-only
    STATUS      current
    DESCRIPTION
        "The value of tmnxBsxEventLogRowLastChange indicates the last time,
         since system startup, a successful set was performed on this row."
    ::= { tmnxBsxEventLogEntry 3 }

tmnxBsxEventLogBufferType        OBJECT-TYPE
    SYNTAX      INTEGER {
        linear   (1),
        circular (2),
        syslog   (3)
    }
    MAX-ACCESS  read-create
    STATUS      current
    DESCRIPTION
        "The value of tmnxBsxEventLogBufferType specifies the type of event log.
         The type may be one of:
            linear   (1) - a linear buffer which once full will stop recording
                           events until it is cleared
            circular (2) - a circular buffer whereby older entries will be
                           overwritten by newer entries
            syslog   (3) - a remote syslog collector target is defined in
                           tmnxBsxEventLogSyslogAddr where events are sent"
    DEFVAL      { linear }
    ::= { tmnxBsxEventLogEntry 4 }

tmnxBsxEventLogMaxEntries        OBJECT-TYPE
    SYNTAX      Unsigned32 (1..100000)
    MAX-ACCESS  read-create
    STATUS      current
    DESCRIPTION
        "The value of tmnxBsxEventLogMaxEntries specifies the maximum number of
         entries in the buffer.

         If tmnxBsxEventLogBufferType is set to 'syslog (3)', the value of
         tmnxBsxEventLogMaxEntries has no impact."
    DEFVAL      { 500 }
    ::= { tmnxBsxEventLogEntry 5 }

tmnxBsxEventLogAdminState        OBJECT-TYPE
    SYNTAX      TmnxAdminState
    MAX-ACCESS  read-create
    STATUS      current
    DESCRIPTION
        "The value of tmnxBsxEventLogAdminState specifies the administrative
         state of the event log. When the value is 'outOfService (3)', the
         event log is disabled and no new log entries are inserted.

         If the value of tmnxBsxEventLogBufferType is set to 'syslog (3)', the
         value of tmnxBsxEventLogAdminState may only be changed to 'inService
         (2)' if the values of tmnxBsxEventLogSyslogAddr,
         tmnxBsxEventLogSyslogAddrType and tmnxBsxEventLogSyslogVlan are
         non-default."
    DEFVAL      { outOfService }
    ::= { tmnxBsxEventLogEntry 6 }

tmnxBsxEventLogSyslogAddrType    OBJECT-TYPE
    SYNTAX      InetAddressType
    MAX-ACCESS  read-create
    STATUS      current
    DESCRIPTION
        "The value of tmnxBsxEventLogSyslogAddrType specifies the type of
         address stored in tmnxBsxEventLogSyslogAddr.

         When specifying the value of tmnxBsxEventLogSyslogAddrType,
         tmnxBsxEventLogSyslogAddr must also be specified in the same SNMP Set
         PDU."
    DEFVAL      { unknown }
    ::= { tmnxBsxEventLogEntry 7 }

tmnxBsxEventLogSyslogAddr        OBJECT-TYPE
    SYNTAX      InetAddress (SIZE (0|4|16))
    MAX-ACCESS  read-create
    STATUS      current
    DESCRIPTION
        "The value of tmnxBsxEventLogSyslogAddr specifies the IP address of the
         syslog collector target.

         When specifying the value of tmnxBsxEventLogSyslogAddr,
         tmnxBsxEventLogSyslogAddrType must also be specified in the same SNMP
         Set PDU."
    DEFVAL      { ''H }
    ::= { tmnxBsxEventLogEntry 8 }

tmnxBsxEventLogSyslogPort        OBJECT-TYPE
    SYNTAX      TmnxUdpPort
    MAX-ACCESS  read-create
    STATUS      current
    DESCRIPTION
        "The value of tmnxBsxEventLogSyslogPort specifies the syslog collector
         target UDP port."
    DEFVAL      { 514 }
    ::= { tmnxBsxEventLogEntry 9 }

tmnxBsxEventLogSyslogDescription OBJECT-TYPE
    SYNTAX      TItemDescription
    MAX-ACCESS  read-create
    STATUS      current
    DESCRIPTION
        "The value of tmnxBsxEventLogSyslogDescription specifies the
         description of the syslog collector target."
    DEFVAL      { "" }
    ::= { tmnxBsxEventLogEntry 10 }

tmnxBsxEventLogSyslogVlan        OBJECT-TYPE
    SYNTAX      VlanIdOrNone
    MAX-ACCESS  read-create
    STATUS      current
    DESCRIPTION
        "The value of tmnxBsxEventLogSyslogVlan specifies the ISA-AA service
         port VLAN which is used to generate traffic to the syslog collector
         target via UDP.

         A VLAN ID of 0 specifies that no traffic is sent."
    DEFVAL      { 0 }
    ::= { tmnxBsxEventLogEntry 11 }

tmnxBsxEventLogSyslogFacility    OBJECT-TYPE
    SYNTAX      TmnxSyslogFacility
    MAX-ACCESS  read-create
    STATUS      current
    DESCRIPTION
        "The value of tmnxBsxEventLogSyslogFacility specifies the syslog
         facility number that will be encoded in messages sent to the syslog
         collector target."
    DEFVAL      { local7 }
    ::= { tmnxBsxEventLogEntry 12 }

tmnxBsxEventLogSyslogSeverity    OBJECT-TYPE
    SYNTAX      TmnxSyslogSeverity
    MAX-ACCESS  read-create
    STATUS      current
    DESCRIPTION
        "The value of tmnxBsxEventLogSyslogSeverity specifies the maximum
         severity level of the messages that will be forwarded to the syslog
         collector target."
    DEFVAL      { info }
    ::= { tmnxBsxEventLogEntry 13 }

tmnxBsxAqpObjs                   OBJECT IDENTIFIER ::= { tmnxBsxPolicyObjs 29 }

tmnxBsxAqpBaseTable              OBJECT-TYPE
    SYNTAX      SEQUENCE OF TmnxBsxAqpBaseEntry
    MAX-ACCESS  not-accessible
    STATUS      current
    DESCRIPTION
        "The tmnxBsxAqpBaseTable contains the application QoS policy which is a
         set of entries containing match criteria defining actions to be taken
         within the AEM MDA."
    ::= { tmnxBsxAqpObjs 1 }

tmnxBsxAqpBaseEntry              OBJECT-TYPE
    SYNTAX      TmnxBsxAqpBaseEntry
    MAX-ACCESS  not-accessible
    STATUS      current
    DESCRIPTION
        "Each tmnxBsxAqpBaseEntry indicates a set of match criteria and
         corresponding actions to take."
    INDEX       {
        tmnxBsxAqpBasePolicyVersion,
        tmnxBsxAaGrpPartIndex,
        tmnxBsxAqpBaseEntryId
    }
    ::= { tmnxBsxAqpBaseTable 1 }

TmnxBsxAqpBaseEntry              ::= SEQUENCE
{
    tmnxBsxAqpBasePolicyVersion      TmnxBsxPolicyVersion,
    tmnxBsxAqpBaseEntryId            TEntryId,
    tmnxBsxAqpBaseRowStatus          RowStatus,
    tmnxBsxAqpBaseRowLastChange      TimeStamp,
    tmnxBsxAqpBaseDescription        TItemDescription,
    tmnxBsxAqpBaseAdminState         TmnxAdminState
}

tmnxBsxAqpBasePolicyVersion      OBJECT-TYPE
    SYNTAX      TmnxBsxPolicyVersion
    MAX-ACCESS  not-accessible
    STATUS      current
    DESCRIPTION
        "The value of tmnxBsxAqpBasePolicyVersion specifies the
         version of the table being accessed.  The table
         is read-create only for the 'admin' version of
         the table.  The 'oper' version is read-only."
    ::= { tmnxBsxAqpBaseEntry 1 }

tmnxBsxAqpBaseEntryId            OBJECT-TYPE
    SYNTAX      TEntryId
    MAX-ACCESS  not-accessible
    STATUS      current
    DESCRIPTION
        "The value of tmnxBsxAqpBaseEntryId specifies the index into the
         Application QoS Policy list that resolve applications."
    ::= { tmnxBsxAqpBaseEntry 2 }

tmnxBsxAqpBaseRowStatus          OBJECT-TYPE
    SYNTAX      RowStatus
    MAX-ACCESS  read-create
    STATUS      current
    DESCRIPTION
        "The value of tmnxBsxAqpBaseRowStatus specifies
         the row status.  It allows entries to be created
         and deleted in the tmnxBsxAqpBaseTable."
    ::= { tmnxBsxAqpBaseEntry 3 }

tmnxBsxAqpBaseRowLastChange      OBJECT-TYPE
    SYNTAX      TimeStamp
    MAX-ACCESS  read-only
    STATUS      current
    DESCRIPTION
        "The value of tmnxBsxAqpBaseRowLastChange indicates the last time,
         since system startup, a successful set was performed on this row."
    ::= { tmnxBsxAqpBaseEntry 4 }

tmnxBsxAqpBaseDescription        OBJECT-TYPE
    SYNTAX      TItemDescription
    MAX-ACCESS  read-create
    STATUS      current
    DESCRIPTION
        "The value of tmnxBsxAqpBaseDescription specifies the description of
         the Application QoS Policy Entry."
    DEFVAL      { "" }
    ::= { tmnxBsxAqpBaseEntry 5 }

tmnxBsxAqpBaseAdminState         OBJECT-TYPE
    SYNTAX      TmnxAdminState
    MAX-ACCESS  read-create
    STATUS      current
    DESCRIPTION
        "The value of tmnxBsxAqpBaseAdminState specifies the
         administrative state for the application.  When
         'outOfService', any match entries referring to this
         application are skipped."
    DEFVAL      { outOfService }
    ::= { tmnxBsxAqpBaseEntry 6 }

tmnxBsxAqpMatchTable             OBJECT-TYPE
    SYNTAX      SEQUENCE OF TmnxBsxAqpMatchEntry
    MAX-ACCESS  not-accessible
    STATUS      current
    DESCRIPTION
        "The tmnxBsxAqpMatchTable augments the tmnxBsxAqpBaseTable
         and tmnxBsxAqpActionTable.  It contains the match criteria
         for actions (defined in tmnxBsxAqpActionTable) to be taken
         within the AEM MDA."
    ::= { tmnxBsxAqpObjs 2 }

tmnxBsxAqpMatchEntry             OBJECT-TYPE
    SYNTAX      TmnxBsxAqpMatchEntry
    MAX-ACCESS  not-accessible
    STATUS      current
    DESCRIPTION
        "Each tmnxBsxAqpMatchEntry indicates a set of match criteria and
         corresponding actions to take."
    AUGMENTS    { tmnxBsxAqpBaseEntry }
    ::= { tmnxBsxAqpMatchTable 1 }

TmnxBsxAqpMatchEntry             ::= SEQUENCE
{
    tmnxBsxAqpMatchRowLastChange     TimeStamp,
    tmnxBsxAqpMatchApplication       TNamedItemOrEmpty,
    tmnxBsxAqpMatchApplicationOp     TmnxBsxOperator,
    tmnxBsxAqpMatchAppGroup          TNamedItemOrEmpty,
    tmnxBsxAqpMatchAppGroupOp        TmnxBsxOperator,
    tmnxBsxAqpMatchTrafficDir        TmnxBsxDirection,
    tmnxBsxAqpMatchDscp              TDSCPNameOrEmpty,
    tmnxBsxAqpMatchDscpOp            TmnxBsxOperator,
    tmnxBsxAqpMatchSrcAddressType    InetAddressType,
    tmnxBsxAqpMatchSrcAddress        InetAddress,
    tmnxBsxAqpMatchSrcAddressLength  InetAddressPrefixLength,
    tmnxBsxAqpMatchSrcAddressOp      TmnxBsxOperator,
    tmnxBsxAqpMatchSrcPortOp         TmnxBsxOperator,
    tmnxBsxAqpMatchSrcPortLowValue   TTcpUdpPort,
    tmnxBsxAqpMatchSrcPortHighValue  TTcpUdpPort,
    tmnxBsxAqpMatchDstAddressType    InetAddressType,
    tmnxBsxAqpMatchDstAddress        InetAddress,
    tmnxBsxAqpMatchDstAddressLength  InetAddressPrefixLength,
    tmnxBsxAqpMatchDstAddressOp      TmnxBsxOperator,
    tmnxBsxAqpMatchDstPortOp         TmnxBsxOperator,
    tmnxBsxAqpMatchDstPortLowValue   TTcpUdpPort,
    tmnxBsxAqpMatchDstPortHighValue  TTcpUdpPort,
    tmnxBsxAqpMatchAaSubscriberType  TmnxBsxAaSubscriberType,
    tmnxBsxAqpMatchAaSubscriber      TmnxBsxAaSubscriber,
    tmnxBsxAqpMatchAaSubscriberOp    TmnxBsxOperator,
    tmnxBsxAqpMatchChargeGrp         TNamedItemOrEmpty,
    tmnxBsxAqpMatchChargeGrpOp       TmnxBsxOperator,
    tmnxBsxAqpMatchIpProtocolNum     TIpProtocol,
    tmnxBsxAqpMatchIpProtocolNumOp   TmnxBsxOperator,
    tmnxBsxAqpMatchSrcPfxList        TNamedItemOrEmpty,
    tmnxBsxAqpMatchDstPfxList        TNamedItemOrEmpty,
    tmnxBsxAqpMatchAaSubTetherState  TmnxBsxAaSubTetherState,
    tmnxBsxAqpMatchSrcPortList       TNamedItemOrEmpty,
    tmnxBsxAqpMatchDstPortList       TNamedItemOrEmpty
}

tmnxBsxAqpMatchRowLastChange     OBJECT-TYPE
    SYNTAX      TimeStamp
    MAX-ACCESS  read-only
    STATUS      current
    DESCRIPTION
        "The value of tmnxBsxAqpMatchRowLastChange indicates the last time,
         since system startup, a successful set was performed on this row."
    ::= { tmnxBsxAqpMatchEntry 1 }

tmnxBsxAqpMatchApplication       OBJECT-TYPE
    SYNTAX      TNamedItemOrEmpty
    MAX-ACCESS  read-create
    STATUS      current
    DESCRIPTION
        "The value of tmnxBsxAqpMatchApplication specifies
         the particular application to match against
         to resolve to an AQP action.  If set to an empty
         string, no match on application is done.

         If an attempt is made to set this object to a string that does not
         match a tmnxBsxAppName value from the tmnxBsxAppCfgTable, an
         'inconsistentValue' error is returned."
    DEFVAL      { "" }
    ::= { tmnxBsxAqpMatchEntry 2 }

tmnxBsxAqpMatchApplicationOp     OBJECT-TYPE
    SYNTAX      TmnxBsxOperator
    MAX-ACCESS  read-create
    STATUS      current
    DESCRIPTION
        "The value of tmnxBsxAqpMatchApplicationOp specifies the operator to
         apply in relation to tmnxBsxAqpMatchApplication to match against to
         resolve an AQP action."
    DEFVAL      { none }
    ::= { tmnxBsxAqpMatchEntry 3 }

tmnxBsxAqpMatchAppGroup          OBJECT-TYPE
    SYNTAX      TNamedItemOrEmpty
    MAX-ACCESS  read-create
    STATUS      current
    DESCRIPTION
        "The value of tmnxBsxAqpMatchAppGroup specifies the
         particular application group to match against to
         resolve to an AQP action.  If set to an empty string,
         no match on application group is done.

         If an attempt is made to set this object to a string that does not
         match a tmnxBsxAppGrpName value from the tmnxBsxAppGrpCfgTable, an
         'inconsistentValue' error is returned."
    DEFVAL      { "" }
    ::= { tmnxBsxAqpMatchEntry 4 }

tmnxBsxAqpMatchAppGroupOp        OBJECT-TYPE
    SYNTAX      TmnxBsxOperator
    MAX-ACCESS  read-create
    STATUS      current
    DESCRIPTION
        "The value of tmnxBsxAqpMatchAppGroupOp specifies the operator to apply
         in relation to tmnxBsxAqpMatchAppGroup to match against to resolve an
         AQP action."
    DEFVAL      { none }
    ::= { tmnxBsxAqpMatchEntry 5 }

tmnxBsxAqpMatchTrafficDir        OBJECT-TYPE
    SYNTAX      TmnxBsxDirection
    MAX-ACCESS  read-create
    STATUS      current
    DESCRIPTION
        "The value of tmnxBsxAqpMatchTrafficDir specifies the
         traffic direction(s) to match against to resolve to
         an AQP action.  This allows different policer
         bandwidths to apply in each direction."
    DEFVAL      { both }
    ::= { tmnxBsxAqpMatchEntry 6 }

tmnxBsxAqpMatchDscp              OBJECT-TYPE
    SYNTAX      TDSCPNameOrEmpty
    MAX-ACCESS  read-create
    STATUS      current
    DESCRIPTION
        "The value of tmnxBsxAqpMatchDscp specifies the DSCP name to match to
         resolve to an AQP action. An empty string will allow all DHCP values
         to match."
    DEFVAL      { "" }
    ::= { tmnxBsxAqpMatchEntry 7 }

tmnxBsxAqpMatchDscpOp            OBJECT-TYPE
    SYNTAX      TmnxBsxOperator
    MAX-ACCESS  read-create
    STATUS      current
    DESCRIPTION
        "The value of tmnxBsxAqpMatchDscpOp specifies the operator to apply in
         relation to tmnxBsxAqpMatchDscp to match against to resolve an AQP
         action."
    DEFVAL      { none }
    ::= { tmnxBsxAqpMatchEntry 8 }

tmnxBsxAqpMatchSrcAddressType    OBJECT-TYPE
    SYNTAX      InetAddressType
    MAX-ACCESS  read-create
    STATUS      current
    DESCRIPTION
        "The value of tmnxBsxAqpMatchSrcAddressType specifies the type of
         address contained in tmnxBsxAqpMatchSrcAddress.

         A value of 'unknown (0)' specifies that no matching is to be done to
         resolve to an AQP action."
    DEFVAL      { unknown }
    ::= { tmnxBsxAqpMatchEntry 9 }

tmnxBsxAqpMatchSrcAddress        OBJECT-TYPE
    SYNTAX      InetAddress (SIZE (0|4|16))
    MAX-ACCESS  read-create
    STATUS      current
    DESCRIPTION
        "The value of tmnxBsxAqpMatchSrcAddress specifies the source address to
         match to resolve to an AQP action."
    DEFVAL      { ''H }
    ::= { tmnxBsxAqpMatchEntry 10 }

tmnxBsxAqpMatchSrcAddressLength  OBJECT-TYPE
    SYNTAX      InetAddressPrefixLength (0..128)
    MAX-ACCESS  read-create
    STATUS      current
    DESCRIPTION
        "The value of tmnxBsxAqpMatchSrcAddressLength specifies the number of
         relevant bits of the tmnxBsxAqpMatchSrcAddress."
    DEFVAL      { 0 }
    ::= { tmnxBsxAqpMatchEntry 11 }

tmnxBsxAqpMatchSrcAddressOp      OBJECT-TYPE
    SYNTAX      TmnxBsxOperator
    MAX-ACCESS  read-create
    STATUS      current
    DESCRIPTION
        "The value of tmnxBsxAqpMatchSrcAddressOp specifies the operator to
         apply in relation to tmnxBsxAqpMatchSrcAddressType,
         tmnxBsxAqpMatchSrcAddress, and tmnxBsxAqpMatchSrcAddressLength to
         match against to resolve to an AQP action."
    DEFVAL      { none }
    ::= { tmnxBsxAqpMatchEntry 12 }

tmnxBsxAqpMatchSrcPortOp         OBJECT-TYPE
    SYNTAX      TmnxBsxOperator
    MAX-ACCESS  read-create
    STATUS      current
    DESCRIPTION
        "The value of tmnxBsxAqpMatchSrcPortOp specifies the operator to apply
         in relation to the tmnxBsxAqpMatchSrcPortLowValue and
         tmnxBsxAqpMatchSrcPortHighValue objects.

         A value of 'none (0)' indicates that no match is done on the
         tmnxBsxAqpMatchSrcPortLowValue and tmnxBsxAqpMatchSrcPortHighValue
         objects."
    DEFVAL      { none }
    ::= { tmnxBsxAqpMatchEntry 13 }

tmnxBsxAqpMatchSrcPortLowValue   OBJECT-TYPE
    SYNTAX      TTcpUdpPort
    MAX-ACCESS  read-create
    STATUS      current
    DESCRIPTION
        "The value of tmnxBsxAqpMatchSrcPortLowValue specifies the low source
         TCP or UDP port number to match to resolve to an AQP action.
         tmnxBsxAqpMatchSrcPortLowValue must be less than or equal to
         tmnxBsxAqpMatchSrcPortHighValue, and is used when the
         tmnxBsxAqpMatchSrcPortOp is not 'none (0)'."
    DEFVAL      { 0 }
    ::= { tmnxBsxAqpMatchEntry 14 }

tmnxBsxAqpMatchSrcPortHighValue  OBJECT-TYPE
    SYNTAX      TTcpUdpPort
    MAX-ACCESS  read-create
    STATUS      current
    DESCRIPTION
        "The value of tmnxBsxAqpMatchSrcPortHighValue specifies the high source
         TCP or UDP port number to match to resolve to an AQP action.
         tmnxBsxAqpMatchSrcPortHighValue must be greater than or equal to
         tmnxBsxAqpMatchSrcPortLowValue, and is used when the
         tmnxBsxAqpMatchSrcPortOp is not 'none (0)'."
    DEFVAL      { 0 }
    ::= { tmnxBsxAqpMatchEntry 15 }

tmnxBsxAqpMatchDstAddressType    OBJECT-TYPE
    SYNTAX      InetAddressType
    MAX-ACCESS  read-create
    STATUS      current
    DESCRIPTION
        "The value of tmnxBsxAqpMatchDstAddressType specifies the type of
         address contained in tmnxBsxAqpMatchDstAddress.

         A value of 'unknown (0)' specifies that no matching is to be done to
         resolve to an AQP action."
    DEFVAL      { unknown }
    ::= { tmnxBsxAqpMatchEntry 16 }

tmnxBsxAqpMatchDstAddress        OBJECT-TYPE
    SYNTAX      InetAddress (SIZE (0|4|16))
    MAX-ACCESS  read-create
    STATUS      current
    DESCRIPTION
        "The value of tmnxBsxAqpMatchDstAddress specifies the destination
         address to match to resolve to an AQP action."
    DEFVAL      { ''H }
    ::= { tmnxBsxAqpMatchEntry 17 }

tmnxBsxAqpMatchDstAddressLength  OBJECT-TYPE
    SYNTAX      InetAddressPrefixLength (0..128)
    MAX-ACCESS  read-create
    STATUS      current
    DESCRIPTION
        "The value of tmnxBsxAqpMatchDstAddressLength specifies the number of
         relevant bits of the tmnxBsxAqpMatchDstAddress."
    DEFVAL      { 0 }
    ::= { tmnxBsxAqpMatchEntry 18 }

tmnxBsxAqpMatchDstAddressOp      OBJECT-TYPE
    SYNTAX      TmnxBsxOperator
    MAX-ACCESS  read-create
    STATUS      current
    DESCRIPTION
        "The value of tmnxBsxAqpMatchDstAddressOp specifies the operator to
         apply in relation to tmnxBsxAqpMatchDstAddressType,
         tmnxBsxAqpMatchDstAddress, and tmnxBsxAqpMatchDstAddressLength to
         match against to resolve to an AQP action."
    DEFVAL      { none }
    ::= { tmnxBsxAqpMatchEntry 19 }

tmnxBsxAqpMatchDstPortOp         OBJECT-TYPE
    SYNTAX      TmnxBsxOperator
    MAX-ACCESS  read-create
    STATUS      current
    DESCRIPTION
        "The value of tmnxBsxAqpMatchDstPortOp specifies the operator to apply
         in relation to the tmnxBsxAqpMatchDstPortLowValue and
         tmnxBsxAqpMatchDstPortHighValue objects.

         A value of 'none (0)' indicates that no match is done on the
         tmnxBsxAqpMatchDstPortLowValue and tmnxBsxAqpMatchDstPortHighValue
         objects."
    DEFVAL      { none }
    ::= { tmnxBsxAqpMatchEntry 20 }

tmnxBsxAqpMatchDstPortLowValue   OBJECT-TYPE
    SYNTAX      TTcpUdpPort
    MAX-ACCESS  read-create
    STATUS      current
    DESCRIPTION
        "The value of tmnxBsxAqpMatchDstPortLowValue specifies the low
         destination TCP or UDP port number to match to resolve to an AQP
         action. tmnxBsxAqpMatchDstPortLowValue must be less than or equal to
         tmnxBsxAqpMatchDstPortHighValue, and is used when the
         tmnxBsxAqpMatchDstPortOp is not 'none (0)'."
    DEFVAL      { 0 }
    ::= { tmnxBsxAqpMatchEntry 21 }

tmnxBsxAqpMatchDstPortHighValue  OBJECT-TYPE
    SYNTAX      TTcpUdpPort
    MAX-ACCESS  read-create
    STATUS      current
    DESCRIPTION
        "The value of tmnxBsxAqpMatchDstPortHighValue specifies the high
         destination TCP or UDP port number to match to resolve to an AQP
         action. tmnxBsxAqpMatchDstPortHighValue must be greater than or equal
         to tmnxBsxAqpMatchDstPortLowValue, and is used when the
         tmnxBsxAqpMatchDstPortOp is not 'none (0)'."
    DEFVAL      { 0 }
    ::= { tmnxBsxAqpMatchEntry 22 }

tmnxBsxAqpMatchAaSubscriberType  OBJECT-TYPE
    SYNTAX      TmnxBsxAaSubscriberType
    MAX-ACCESS  read-create
    STATUS      current
    DESCRIPTION
        "The value of tmnxBsxAqpMatchAaSubscriberType specifies the type of
         subscriber identified by tmnxBsxAqpMatchAaSubscriber. The values of
         tmnxBsxAqpMatchAaSubscriberType and tmnxBsxAqpMatchAaSubscriber must
         be set together in a single SNMP multi-variable SetRequest-PDU.

         If set to 'unknown(0)', no match on a subscriber is done."
    DEFVAL      { unknown }
    ::= { tmnxBsxAqpMatchEntry 23 }

tmnxBsxAqpMatchAaSubscriber      OBJECT-TYPE
    SYNTAX      TmnxBsxAaSubscriber
    MAX-ACCESS  read-create
    STATUS      current
    DESCRIPTION
        "The value of tmnxBsxAqpMatchAaSubscriber specifies the subscriber of
         type tmnxBsxAqpMatchAaSubscriberType to match against to resolve to an
         AQP action. The values of tmnxBsxAqpMatchAaSubscriberType and
         tmnxBsxAqpMatchAaSubscriber must be set together in a single SNMP
         multi-variable SetRequest-PDU.

         If set to an empty string, no match on a subscriber is done."
    DEFVAL      { "" }
    ::= { tmnxBsxAqpMatchEntry 24 }

tmnxBsxAqpMatchAaSubscriberOp    OBJECT-TYPE
    SYNTAX      TmnxBsxOperator
    MAX-ACCESS  read-create
    STATUS      current
    DESCRIPTION
        "The value of tmnxBsxAqpMatchAaSubscriberOp specifies the operator to
         apply in relation to tmnxBsxAqpMatchAaSubscriber to match against to
         resolve an AQP action.

         If set to 'none(0)', no match on a subscriber is done."
    DEFVAL      { none }
    ::= { tmnxBsxAqpMatchEntry 25 }

tmnxBsxAqpMatchChargeGrp         OBJECT-TYPE
    SYNTAX      TNamedItemOrEmpty
    MAX-ACCESS  read-create
    STATUS      current
    DESCRIPTION
        "The value of tmnxBsxAqpMatchChargeGrp along with
         tmnxBsxAqpMatchChargeGrpOp specifies the charging group and operation
         to match against to resolve to an AQP action.

         If set to an empty string or the operation is none, no match on the
         charging group is done.

         If an attempt is made to set this object to a non-empty string that
         does not match a tmnxBsxChargeGrpName value from the
         tmnxBsxChargeGrpCfgTable, an 'inconsistentValue' error is returned."
    DEFVAL      { "" }
    ::= { tmnxBsxAqpMatchEntry 26 }

tmnxBsxAqpMatchChargeGrpOp       OBJECT-TYPE
    SYNTAX      TmnxBsxOperator
    MAX-ACCESS  read-create
    STATUS      current
    DESCRIPTION
        "The value of tmnxBsxAqpMatchChargeGrpOp specifies the operator to
         apply in relation to tmnxBsxAqpMatchChargeGrp to match against to
         resolve an AQP action."
    DEFVAL      { none }
    ::= { tmnxBsxAqpMatchEntry 27 }

tmnxBsxAqpMatchIpProtocolNum     OBJECT-TYPE
    SYNTAX      TIpProtocol
    MAX-ACCESS  read-create
    STATUS      current
    DESCRIPTION
        "The value of tmnxBsxAqpMatchIpProtocolNum along with
         tmnxBsxAqpMatchIpProtocolNumOp specifies the IP protocol number to
         match to resolve to an AQP action.

         A value of '-1' specifies that no matching is to be done. A value of
         '-2' along with an operation not equal to none specifies that a match
         will occur if the protocol is TCP or UDP."
    DEFVAL      { -1 }
    ::= { tmnxBsxAqpMatchEntry 28 }

tmnxBsxAqpMatchIpProtocolNumOp   OBJECT-TYPE
    SYNTAX      TmnxBsxOperator
    MAX-ACCESS  read-create
    STATUS      current
    DESCRIPTION
        "The value of tmnxBsxAqpMatchIpProtocolNumOp specifies the operator to
         apply in relation to tmnxBsxAqpMatchIpProtocolNum to match against to
         resolve an AQP action."
    DEFVAL      { none }
    ::= { tmnxBsxAqpMatchEntry 29 }

tmnxBsxAqpMatchSrcPfxList        OBJECT-TYPE
    SYNTAX      TNamedItemOrEmpty
    MAX-ACCESS  read-create
    STATUS      current
    DESCRIPTION
        "The value of tmnxBsxAqpMatchSrcPfxList specifies the prefix list to
         use when matching the source address.

         The specification of the source IP prefix list may be done only when
         tmnxBsxAqpMatchSrcAddress, tmnxBsxAqpMatchSrcAddressType, and
         tmnxBsxAqpMatchSrcAddressLength are set to their default value.

         Furthermore, the specification of the source IP prefix list must be
         done with the specification of a non-default
         tmnxBsxAqpMatchSrcAddressOp."
    DEFVAL      { "" }
    ::= { tmnxBsxAqpMatchEntry 30 }

tmnxBsxAqpMatchDstPfxList        OBJECT-TYPE
    SYNTAX      TNamedItemOrEmpty
    MAX-ACCESS  read-create
    STATUS      current
    DESCRIPTION
        "The value of tmnxBsxAqpMatchDstPfxList specifies the prefix list to
         use when matching the destination address.

         The specification of the destination IP prefix list may be done only
         when tmnxBsxAqpMatchDstAddress, tmnxBsxAqpMatchDstAddressType, and
         tmnxBsxAqpMatchDstAddressLength are set to their default value.

         Furthermore, the specification of the destination IP prefix list must
         be done with the specification of a non-default
         tmnxBsxAqpMatchDstAddressOp."
    DEFVAL      { "" }
    ::= { tmnxBsxAqpMatchEntry 31 }

tmnxBsxAqpMatchAaSubTetherState  OBJECT-TYPE
    SYNTAX      TmnxBsxAaSubTetherState
    MAX-ACCESS  read-create
    STATUS      current
    DESCRIPTION
        "The value of tmnxBsxAqpMatchAaSubTetherState specifies the tethering
         state of an Application Assurance Subscriber to match against to
         resolve an AQP action.

         This match criteria will only be applied when tmnxBsxTetherAdminState
         is set to 'inService (2)' for the same tmnxBsxAaGrpPartIndex.
         The tethering state may be one of:
               notApplicable (0) - indicates tethering state is not used for
                                   matching
               detected      (1) - indicates that matching on detecting
                                   tethering
               notDetected   (2) - indicates that matching on not detecting
                                   tethering"
    DEFVAL      { notApplicable }
    ::= { tmnxBsxAqpMatchEntry 32 }

tmnxBsxAqpMatchSrcPortList       OBJECT-TYPE
    SYNTAX      TNamedItemOrEmpty
    MAX-ACCESS  read-create
    STATUS      current
    DESCRIPTION
        "The value of tmnxBsxAqpMatchSrcPortList specifies the port list to use
         when matching the source address."
    DEFVAL      { "" }
    ::= { tmnxBsxAqpMatchEntry 33 }

tmnxBsxAqpMatchDstPortList       OBJECT-TYPE
    SYNTAX      TNamedItemOrEmpty
    MAX-ACCESS  read-create
    STATUS      current
    DESCRIPTION
        "The value of tmnxBsxAqpMatchDstPortList specifies the port list to use
         when matching the destination address."
    DEFVAL      { "" }
    ::= { tmnxBsxAqpMatchEntry 34 }

tmnxBsxAqpActionTable            OBJECT-TYPE
    SYNTAX      SEQUENCE OF TmnxBsxAqpActionEntry
    MAX-ACCESS  not-accessible
    STATUS      current
    DESCRIPTION
        "The tmnxBsxAqpActionTable augments the tmnxBsxAqpBaseTable
         and tmnxBsxAqpMatchTable.  It contains the actions to be
         taken within the AEM MDA for the match criteria defined in
         tmnxBsxAqpMatchTable."
    ::= { tmnxBsxAqpObjs 3 }

tmnxBsxAqpActionEntry            OBJECT-TYPE
    SYNTAX      TmnxBsxAqpActionEntry
    MAX-ACCESS  not-accessible
    STATUS      current
    DESCRIPTION
        "Each tmnxBsxAqpActionEntry indicates a set of actions to take."
    AUGMENTS    { tmnxBsxAqpBaseEntry }
    ::= { tmnxBsxAqpActionTable 1 }

TmnxBsxAqpActionEntry            ::= SEQUENCE
{
    tmnxBsxAqpActRowLastChange       TimeStamp,
    tmnxBsxAqpActDrop                TruthValue,
    tmnxBsxAqpActBwLimitPolicer      TNamedItemOrEmpty,
    tmnxBsxAqpActFlowRatePolicer     TNamedItemOrEmpty,
    tmnxBsxAqpActFlowCountPolicer    TNamedItemOrEmpty,
    tmnxBsxAqpActRemarkFc            TFCNameOrEmpty,
    tmnxBsxAqpActRemarkPriority      TPriorityOrDefault,
    tmnxBsxAqpActRemarkDscpInProf    TDSCPNameOrEmpty,
    tmnxBsxAqpActRemarkDscpOutProf   TDSCPNameOrEmpty,
    tmnxBsxAqpActMirrorSource        TmnxServId,
    tmnxBsxAqpActMirrorSourceAllIncl TruthValue,
    tmnxBsxAqpActHttpErrRedirName    TNamedItemOrEmpty,
    tmnxBsxAqpActHttpRedirName       TNamedItemOrEmpty,
    tmnxBsxAqpActHttpRedirFlowType   TmnxBsxAqpHttpRedirFlowType,
    tmnxBsxAqpActHttpEnrichName      TNamedItemOrEmpty,
    tmnxBsxAqpActSessionFilter       TNamedItemOrEmpty,
    tmnxBsxAqpActUrlFilter           TNamedItemOrEmpty,
    tmnxBsxAqpActHttpNotif           TNamedItemOrEmpty,
    tmnxBsxAqpActOverloadDrop        TruthValue,
    tmnxBsxAqpActEvtLogOverloadDrop  TNamedItemOrEmpty,
    tmnxBsxAqpActErrorDrop           TruthValue,
    tmnxBsxAqpActEvtLogErrorDrop     TNamedItemOrEmpty,
    tmnxBsxAqpActFragDrop            INTEGER,
    tmnxBsxAqpActEvtLogFragDrop      TNamedItemOrEmpty,
    tmnxBsxAqpActDnsIpCache          TNamedItemOrEmpty,
    tmnxBsxAqpActGtpFilter           TNamedItemOrEmpty,
    tmnxBsxAqpActSctpFilter          TNamedItemOrEmpty,
    tmnxBsxAqpActFlowRatePlcrEvtLog  TNamedItemOrEmpty,
    tmnxBsxAqpActFlowCountPlcrEvtLog TNamedItemOrEmpty,
    tmnxBsxAqpActUrlFiltrXHeaderChar TNamedItemOrEmpty,
    tmnxBsxAqpActTcpMaxSegSize       Unsigned32,
    tmnxBsxAqpActTcpValidate         TNamedItemOrEmpty,
    tmnxBsxAqpActTlsEnrichName       TNamedItemOrEmpty,
    tmnxBsxAqpActAbandonTcpOpt       TmnxEnabledDisabled
}

tmnxBsxAqpActRowLastChange       OBJECT-TYPE
    SYNTAX      TimeStamp
    MAX-ACCESS  read-only
    STATUS      current
    DESCRIPTION
        "The value of tmnxBsxAqpActRowLastChange indicates the last time, since
         system startup, a successful set was performed on this row."
    ::= { tmnxBsxAqpActionEntry 1 }

tmnxBsxAqpActDrop                OBJECT-TYPE
    SYNTAX      TruthValue
    MAX-ACCESS  read-create
    STATUS      current
    DESCRIPTION
        "The value of tmnxBsxAqpActDrop specifies that flows matching this
         policy are to be dropped."
    DEFVAL      { false }
    ::= { tmnxBsxAqpActionEntry 2 }

tmnxBsxAqpActBwLimitPolicer      OBJECT-TYPE
    SYNTAX      TNamedItemOrEmpty
    MAX-ACCESS  read-create
    STATUS      current
    DESCRIPTION
        "The value of tmnxBsxAqpActBwLimitPolicer specifies flows matching this
         policy are to be policed using the template defined in
         tmnxBsxPolicerTable.

         If more than one AQP entry refers to the same policer, the same
         policer instances will be used.

         If an attempt is made to set this object to a string that does not
         match a tmnxBsxPolicerName value from the tmnxBsxPolicerTable, an
         'inconsistentValue' error is returned."
    DEFVAL      { "" }
    ::= { tmnxBsxAqpActionEntry 3 }

tmnxBsxAqpActFlowRatePolicer     OBJECT-TYPE
    SYNTAX      TNamedItemOrEmpty
    MAX-ACCESS  read-create
    STATUS      current
    DESCRIPTION
        "The value of tmnxBsxAqpActFlowRatePolicer specifies flows matching
         this policy are to be policed using the template defined in
         tmnxBsxPolicerTable.

         If more than one AQP entry refers to the same policer, the same
         policer instances will be used.

         If an attempt is made to set this object to a string that does not
         match a tmnxBsxPolicerName value from the tmnxBsxPolicerTable, an
         'inconsistentValue' error is returned."
    DEFVAL      { "" }
    ::= { tmnxBsxAqpActionEntry 4 }

tmnxBsxAqpActFlowCountPolicer    OBJECT-TYPE
    SYNTAX      TNamedItemOrEmpty
    MAX-ACCESS  read-create
    STATUS      current
    DESCRIPTION
        "The value of tmnxBsxAqpActFlowCountPolicer specifies flows matching
         this policy are to be limited using the template defined in
         tmnxBsxPolicerTable.

         If more than one AQP entry refers to the same policer, the same
         policer instances will be used.

         If an attempt is made to set this object to a string that does not
         match a tmnxBsxPolicerName value from the tmnxBsxPolicerTable, an
         'inconsistentValue' error is returned."
    DEFVAL      { "" }
    ::= { tmnxBsxAqpActionEntry 5 }

tmnxBsxAqpActRemarkFc            OBJECT-TYPE
    SYNTAX      TFCNameOrEmpty
    MAX-ACCESS  read-create
    STATUS      current
    DESCRIPTION
        "The value of tmnxBsxAqpActRemarkFc specifies the name of the
         forwarding class to use to remark flows that match this policy. An
         empty string value, ''H, specifies no modification to the forwarding
         class."
    DEFVAL      { ''H }
    ::= { tmnxBsxAqpActionEntry 6 }

tmnxBsxAqpActRemarkPriority      OBJECT-TYPE
    SYNTAX      TPriorityOrDefault
    MAX-ACCESS  read-create
    STATUS      current
    DESCRIPTION
        "The value of tmnxBsxAqpActRemarkPriority specifies the priority to use
         to remark flows that match this policy. A value of 'default' specifies
         no modification to the priority."
    DEFVAL      { default }
    ::= { tmnxBsxAqpActionEntry 7 }

tmnxBsxAqpActRemarkDscpInProf    OBJECT-TYPE
    SYNTAX      TDSCPNameOrEmpty
    MAX-ACCESS  read-create
    STATUS      current
    DESCRIPTION
        "The value of tmnxBsxAqpActRemarkDscpInProf specifies the DSCP name to
         use to remark in-profile flows that match this policy. An empty string
         value, ''H, specifies no modification to the DSCP value."
    DEFVAL      { ''H }
    ::= { tmnxBsxAqpActionEntry 8 }

tmnxBsxAqpActRemarkDscpOutProf   OBJECT-TYPE
    SYNTAX      TDSCPNameOrEmpty
    MAX-ACCESS  read-create
    STATUS      current
    DESCRIPTION
        "The value of tmnxBsxAqpActRemarkDscpOutProf specifies the DSCP name to
         use to remark out-of-profile flows that match this policy. An empty
         string value, ''H, specifies no modification to the DSCP value."
    DEFVAL      { ''H }
    ::= { tmnxBsxAqpActionEntry 9 }

tmnxBsxAqpActMirrorSource        OBJECT-TYPE
    SYNTAX      TmnxServId
    MAX-ACCESS  read-create
    STATUS      current
    DESCRIPTION
        "The value of tmnxBsxAqpActMirrorSource specifies the mirror source
         service id, as defined in the TIMETRA-MIRROR-MIB, to use for flows
         that match this policy. A value of 0 specifies no mirror is set."
    DEFVAL      { 0 }
    ::= { tmnxBsxAqpActionEntry 10 }

tmnxBsxAqpActMirrorSourceAllIncl OBJECT-TYPE
    SYNTAX      TruthValue
    MAX-ACCESS  read-create
    STATUS      current
    DESCRIPTION
        "The value of tmnxBsxAqpActMirrorSourceAllIncl specifies that all flows
         matching the subscriber default policy will be mirrored until the
         protocol is identified. The tmnxBsxAqpActMirrorSource must be set to a
         valid mirror."
    DEFVAL      { false }
    ::= { tmnxBsxAqpActionEntry 11 }

tmnxBsxAqpActHttpErrRedirName    OBJECT-TYPE
    SYNTAX      TNamedItemOrEmpty
    MAX-ACCESS  read-create
    STATUS      current
    DESCRIPTION
        "The value of tmnxBsxAqpActHttpErrRedirName specifies the HTTP error
         redirect that will be applied as defined in the
         tmnxBsxHttpRedirErrTable. An empty value specifies no HTTP error
         redirect."
    DEFVAL      { "" }
    ::= { tmnxBsxAqpActionEntry 12 }

tmnxBsxAqpActHttpRedirName       OBJECT-TYPE
    SYNTAX      TNamedItemOrEmpty
    MAX-ACCESS  read-create
    STATUS      current
    DESCRIPTION
        "The value of tmnxBsxAqpActHttpRedirName specifies the HTTP redirect
         that will be applied as defined in the tmnxBsxHttpRedirTable. An empty
         value specifies no HTTP redirect.

         A tmnxBsxAqpActHttpRedirFlowType must have a value other than
         'none(0)' if tmnxBsxAqpActHttpRedirName is not an empty string."
    DEFVAL      { "" }
    ::= { tmnxBsxAqpActionEntry 13 }

tmnxBsxAqpActHttpRedirFlowType   OBJECT-TYPE
    SYNTAX      TmnxBsxAqpHttpRedirFlowType
    MAX-ACCESS  read-create
    STATUS      current
    DESCRIPTION
        "The value of tmnxBsxAqpActHttpRedirFlowType specifies the type of flow
         that will be redirected.

         A tmnxBsxAqpActHttpRedirName must be specified if
         tmnxBsxAqpActHttpRedirFlowType has a value other than 'none(0)'."
    DEFVAL      { none }
    ::= { tmnxBsxAqpActionEntry 14 }

tmnxBsxAqpActHttpEnrichName      OBJECT-TYPE
    SYNTAX      TNamedItemOrEmpty
    MAX-ACCESS  read-create
    STATUS      current
    DESCRIPTION
        "The value of tmnxBsxAqpActHttpEnrichName specifies the HTTP header
         enrichment template that will be applied as defined in the
         tmnxBsxHttpEnrichTable. An empty value specifies no HTTP header
         enrichment template."
    DEFVAL      { "" }
    ::= { tmnxBsxAqpActionEntry 15 }

tmnxBsxAqpActSessionFilter       OBJECT-TYPE
    SYNTAX      TNamedItemOrEmpty
    MAX-ACCESS  read-create
    STATUS      current
    DESCRIPTION
        "The value of tmnxBsxAqpActSessionFilter specifies the
         Application-Assurance session filter that will be evaluated. An empty
         value specifies no session filters will be evaluated."
    DEFVAL      { "" }
    ::= { tmnxBsxAqpActionEntry 16 }

tmnxBsxAqpActUrlFilter           OBJECT-TYPE
    SYNTAX      TNamedItemOrEmpty
    MAX-ACCESS  read-create
    STATUS      current
    DESCRIPTION
        "The value of tmnxBsxAqpActUrlFilter specifies the
         Application-Assurance URL filter that will be evaluated. An empty
         value specifies no URL filters will be evaluated."
    DEFVAL      { "" }
    ::= { tmnxBsxAqpActionEntry 17 }

tmnxBsxAqpActHttpNotif           OBJECT-TYPE
    SYNTAX      TNamedItemOrEmpty
    MAX-ACCESS  read-create
    STATUS      current
    DESCRIPTION
        "The value of tmnxBsxAqpActHttpNotif specifies the
         Application-Assurance Http Notification that will be applied as
         defined in the tmnxBsxHttpNotifTable. An empty value specifies no HTTP
         notification will occur."
    DEFVAL      { "" }
    ::= { tmnxBsxAqpActionEntry 18 }

tmnxBsxAqpActOverloadDrop        OBJECT-TYPE
    SYNTAX      TruthValue
    MAX-ACCESS  read-create
    STATUS      current
    DESCRIPTION
        "The value of tmnxBsxAqpActOverloadDrop specifies if all traffic for
         which the system is unable to create a required flow record should be
         dropped."
    DEFVAL      { false }
    ::= { tmnxBsxAqpActionEntry 19 }

tmnxBsxAqpActEvtLogOverloadDrop  OBJECT-TYPE
    SYNTAX      TNamedItemOrEmpty
    MAX-ACCESS  read-create
    STATUS      current
    DESCRIPTION
        "The value of tmnxBsxAqpActEvtLogOverloadDrop specifies if the dropping
         of overload traffic should be event logged to the named
         tmnxBsxEventLogEntry.

         tmnxBsxAqpActEvtLogOverloadDrop can only be set to a non-default value
         when tmnxBsxAqpActOverloadDrop has a value of 'true'."
    DEFVAL      { "" }
    ::= { tmnxBsxAqpActionEntry 20 }

tmnxBsxAqpActErrorDrop           OBJECT-TYPE
    SYNTAX      TruthValue
    MAX-ACCESS  read-create
    STATUS      current
    DESCRIPTION
        "The value of tmnxBsxAqpActErrorDrop specifies if all errored frames
         (such as bad IP checksums, invalid tcp/udp port, etc.) should be
         dropped as the information cannot be trusted and a flow record cannot
         be reliably found."
    DEFVAL      { false }
    ::= { tmnxBsxAqpActionEntry 21 }

tmnxBsxAqpActEvtLogErrorDrop     OBJECT-TYPE
    SYNTAX      TNamedItemOrEmpty
    MAX-ACCESS  read-create
    STATUS      current
    DESCRIPTION
        "The value of tmnxBsxAqpActEvtLogErrorDrop specifies if the dropping of
         errored frames should be event logged to the named
         tmnxBsxEventLogEntry.

         tmnxBsxAqpActEvtLogErrorDrop can only be set to a non-default value
         when tmnxBsxAqpActErrorDrop value of 'true'."
    DEFVAL      { "" }
    ::= { tmnxBsxAqpActionEntry 22 }

tmnxBsxAqpActFragDrop            OBJECT-TYPE
    SYNTAX      INTEGER {
        none       (0),
        all        (1),
        outOfOrder (2)
    }
    MAX-ACCESS  read-create
    STATUS      current
    DESCRIPTION
        "The value of tmnxBsxAqpActFragDrop specifies the action to apply
         to IP fragments.
                none       (0) - no action will be taken
                all        (1) - all fragments will be dropped
                outOfOrder (2) - all out of order fragments will be dropped
                                 as its flow record cannot be found due to
                                 lack of TCP/UDP ports"
    DEFVAL      { none }
    ::= { tmnxBsxAqpActionEntry 23 }

tmnxBsxAqpActEvtLogFragDrop      OBJECT-TYPE
    SYNTAX      TNamedItemOrEmpty
    MAX-ACCESS  read-create
    STATUS      current
    DESCRIPTION
        "The value of tmnxBsxAqpActEvtLogFragDrop specifies if the dropping of
         fragments should be event logged to the named tmnxBsxEventLogEntry.

         tmnxBsxAqpActEvtLogFragDrop can only set to a non-default value when
         tmnxBsxAqpActFragDrop has a value of 'all (1)' or 'outOfOrder (2)'."
    DEFVAL      { "" }
    ::= { tmnxBsxAqpActionEntry 24 }

tmnxBsxAqpActDnsIpCache          OBJECT-TYPE
    SYNTAX      TNamedItemOrEmpty
    MAX-ACCESS  read-create
    STATUS      current
    DESCRIPTION
        "The value of tmnxBsxAqpActDnsIpCache specifies a DNS IP cache. When a
         cache is specified, all traffic is examined as described in the
         tmnxBsxDnsIpCacheTable. An empty value specifies no DNS IP cache will
         be associated."
    DEFVAL      { "" }
    ::= { tmnxBsxAqpActionEntry 25 }

tmnxBsxAqpActGtpFilter           OBJECT-TYPE
    SYNTAX      TNamedItemOrEmpty
    MAX-ACCESS  read-create
    STATUS      current
    DESCRIPTION
        "The value of tmnxBsxAqpActGtpFilter specifies a GTP filter. When a
         filter is specified, all traffic is examined as described in the
         tmnxBsxGtpFltrTable. An empty value specifies no GTP filter will be
         associated."
    DEFVAL      { "" }
    ::= { tmnxBsxAqpActionEntry 26 }

tmnxBsxAqpActSctpFilter          OBJECT-TYPE
    SYNTAX      TNamedItemOrEmpty
    MAX-ACCESS  read-create
    STATUS      current
    DESCRIPTION
        "The value of tmnxBsxAqpActSctpFilter specifies an SCTP filter. When a
         filter is specified, all traffic is examined as described in the
         tmnxBsxSctpFltrTable. An empty value specifies no SCTP filter will be
         associated."
    DEFVAL      { "" }
    ::= { tmnxBsxAqpActionEntry 27 }

tmnxBsxAqpActFlowRatePlcrEvtLog  OBJECT-TYPE
    SYNTAX      TNamedItemOrEmpty
    MAX-ACCESS  read-create
    STATUS      current
    DESCRIPTION
        "The value of tmnxBsxAqpActFlowRatePlcrEvtLog specifies a
         tmnxBsxEventLogName in tmnxBsxEventLogEntry. Entries are added to the
         event log each time a flow policed by tmnxBsxAqpActFlowRatePolicer
         exceeds the flow setup rate tmnxBsxPolicerAdminPIR. If set to an empty
         string, no event logging is performed.

         tmnxBsxAqpActFlowRatePlcrEvtLog can only be set to a non-default value
         when tmnxBsxAqpActFlowRatePolicer is a non-default value."
    DEFVAL      { "" }
    ::= { tmnxBsxAqpActionEntry 28 }

tmnxBsxAqpActFlowCountPlcrEvtLog OBJECT-TYPE
    SYNTAX      TNamedItemOrEmpty
    MAX-ACCESS  read-create
    STATUS      current
    DESCRIPTION
        "The value of tmnxBsxAqpActFlowCountPlcrEvtLog specifies a
         tmnxBsxEventLogName in tmnxBsxEventLogEntry. Entries are added to the
         event log each time a flow policed by tmnxBsxAqpActFlowCountPolicer
         exceeds the flow count tmnxBsxPolicerAdminPIR. If set to an empty
         string, no event logging is performed.

         tmnxBsxAqpActFlowCountPlcrEvtLog can only be set to a non-default
         value when tmnxBsxAqpActFlowCountPolicer is a non-default value."
    DEFVAL      { "" }
    ::= { tmnxBsxAqpActionEntry 29 }

tmnxBsxAqpActUrlFiltrXHeaderChar OBJECT-TYPE
    SYNTAX      TNamedItemOrEmpty
    MAX-ACCESS  read-create
    STATUS      current
    DESCRIPTION
        "The value of tmnxBsxAqpActUrlFiltrXHeaderChar specifies a
         tmnxBsxAsoCharName in tmnxBsxAsoTable. The associated value in
         tmnxBsxAsoValTable is used in either of these two ways: 1. When the
         URL-filter is providing a service using ICAP, the value in the
         tmnxBsxAsoValTable is used as the custom X-Header field value in ICAP
         Request messages for flows matching this policy. If set to an empty
         string the X-Header field value will not be set. 2. When the URL
         filter is providing a web-service, the value in the tmnxBsxAsoValTable
         is used as the profile name, from which the configured categories will
         be blocked. If set to an empty the default profile will be used, from
         which the configured categories are blocked.

         tmnxBsxAqpActUrlFiltrXHeaderChar can only be set to a non-default
         value when tmnxBsxAqpActUrlFilter is a non-default value."
    DEFVAL      { "" }
    ::= { tmnxBsxAqpActionEntry 30 }

tmnxBsxAqpActTcpMaxSegSize       OBJECT-TYPE
    SYNTAX      Unsigned32 (0 | 160..10240)
    MAX-ACCESS  read-create
    STATUS      current
    DESCRIPTION
        "The value of tmnxBsxAqpActTcpMaxSegSize specifies the intended value
         for the Maximum Segment Size (MSS) option in transmitted TCP headers
         containing the SYN flag.

         The value zero specifies that no MSS adjustment is performed.

         If the MSS option is present and its value is less than or equal to
         the value of tmnxBsxAqpActTcpMaxSegSize, no MSS adjustment is
         performed.

         If the MSS option is present and its value is greater than the value
         of tmnxBsxAqpActTcpMaxSegSize, the value of MSS is replaced with
         tmnxBsxAqpActTcpMaxSegSize.

         If the MSS option is not present, one is inserted with a value of
         tmnxBsxAqpActTcpMaxSegSize."
    REFERENCE
        "RFC 793 Transmission Control Protocol Functional Specification section
         3.1. Header Format. RFC 879 The TCP Maximum Segment Size and Related
         Topics. RFC 6691 TCP Options and Maximum Segment Size (MSS)."
    DEFVAL      { 0 }
    ::= { tmnxBsxAqpActionEntry 31 }

tmnxBsxAqpActTcpValidate         OBJECT-TYPE
    SYNTAX      TNamedItemOrEmpty
    MAX-ACCESS  read-create
    STATUS      current
    DESCRIPTION
        "The value of tmnxBsxAqpActTcpValidate specifies a TCP validation
         template. When a template is specified, all traffic is examined as
         described in the tmnxBsxTcpValTable. An empty value specifies no TCP
         validation will be performed."
    DEFVAL      { "" }
    ::= { tmnxBsxAqpActionEntry 32 }

tmnxBsxAqpActTlsEnrichName       OBJECT-TYPE
    SYNTAX      TNamedItemOrEmpty
    MAX-ACCESS  read-create
    STATUS      current
    DESCRIPTION
        "The value of tmnxBsxAqpActTlsEnrichName specifies the enrichment
         template that will be applied as defined in the
         tmnxBsxHttpEnrichTable. An empty value specifies no TLS enrichment
         template."
    DEFVAL      { "" }
    ::= { tmnxBsxAqpActionEntry 35 }

tmnxBsxAqpActAbandonTcpOpt       OBJECT-TYPE
    SYNTAX      TmnxEnabledDisabled
    MAX-ACCESS  read-create
    STATUS      current
    DESCRIPTION
        "The value of tmnxBsxAqpActAbandonTcpOpt specifies whether or not TCP
         optimization will be abandoned after identification concludes."
    DEFVAL      { disabled }
    ::= { tmnxBsxAqpActionEntry 36 }

tmnxBsxAqpFlowAttrTable          OBJECT-TYPE
    SYNTAX      SEQUENCE OF TmnxBsxAqpFlowAttrEntry
    MAX-ACCESS  not-accessible
    STATUS      current
    DESCRIPTION
        "The tmnxBsxAqpFlowAttrTable contains the flow attribute matches for
         the application qos policy table."
    ::= { tmnxBsxAqpObjs 4 }

tmnxBsxAqpFlowAttrEntry          OBJECT-TYPE
    SYNTAX      TmnxBsxAqpFlowAttrEntry
    MAX-ACCESS  not-accessible
    STATUS      current
    DESCRIPTION
        "Each tmnxBsxAqpFlowAttrEntry specifies a match criterion for the
         application qos policy specified by the second and third indices
         tmnxBsxAaGrpPartIndex, and tmnxBsxAqpBaseEntryId. The
         tmnxBsxAqpFlowAttr index uniquely specifies the flow attribute.

         Rows can only be created and destroyed by specifying the
         tmnxBsxAqpFlowAttrRowStatus if the first index,
         tmnxBsxAqpBasePolicyVersion, is set to 'admin'."
    INDEX       {
        tmnxBsxAqpBasePolicyVersion,
        tmnxBsxAaGrpPartIndex,
        tmnxBsxAqpBaseEntryId,
        IMPLIED tmnxBsxAqpFlowAttr
    }
    ::= { tmnxBsxAqpFlowAttrTable 1 }

TmnxBsxAqpFlowAttrEntry          ::= SEQUENCE
{
    tmnxBsxAqpFlowAttr               TNamedItem,
    tmnxBsxAqpFlowAttrRowStatus      RowStatus,
    tmnxBsxAqpFlowAttrRowLstChg      TimeStamp,
    tmnxBsxAqpFlowAttrConf           Unsigned32,
    tmnxBsxAqpFlowAttrOperator       TmnxBsxOperator
}

tmnxBsxAqpFlowAttr               OBJECT-TYPE
    SYNTAX      TNamedItem
    MAX-ACCESS  not-accessible
    STATUS      current
    DESCRIPTION
        "The value of tmnxBsxAqpFlowAttr specifies the flow attribute(s) to
         match against to resolve to an AQP action."
    ::= { tmnxBsxAqpFlowAttrEntry 1 }

tmnxBsxAqpFlowAttrRowStatus      OBJECT-TYPE
    SYNTAX      RowStatus
    MAX-ACCESS  read-create
    STATUS      current
    DESCRIPTION
        "The value of tmnxBsxAqpFlowAttrRowStatus specifies
         the row status.  It allows entries to be created
         and deleted in the tmnxBsxAqpFlowAttrTable.

         Rows are created by specifying the value of 'createAndGo (4)', and
         deleted by specifying the value of 'destroy (6)'."
    ::= { tmnxBsxAqpFlowAttrEntry 2 }

tmnxBsxAqpFlowAttrRowLstChg      OBJECT-TYPE
    SYNTAX      TimeStamp
    MAX-ACCESS  read-only
    STATUS      current
    DESCRIPTION
        "The value of tmnxBsxAqpFlowAttrRowLstChg indicates the last time,
         since system startup, a successful set was performed on this row."
    ::= { tmnxBsxAqpFlowAttrEntry 3 }

tmnxBsxAqpFlowAttrConf           OBJECT-TYPE
    SYNTAX      Unsigned32 (0..100)
    MAX-ACCESS  read-create
    STATUS      current
    DESCRIPTION
        "The value of tmnxBsxAqpFlowAttrConf specifies the confidence of a flow
         attribute to match against to resolve to an AQP action."
    DEFVAL      { 0 }
    ::= { tmnxBsxAqpFlowAttrEntry 4 }

tmnxBsxAqpFlowAttrOperator       OBJECT-TYPE
    SYNTAX      TmnxBsxOperator
    MAX-ACCESS  read-create
    STATUS      current
    DESCRIPTION
        "The value of tmnxBsxAqpFlowAttrOperator specifies the comparison
         operator applied to the corresponding row in the
         tmnxBsxAqpFlowAttrTable."
    DEFVAL      { none }
    ::= { tmnxBsxAqpFlowAttrEntry 5 }

tmnxBsxCflowdRecTmplTable        OBJECT-TYPE
    SYNTAX      SEQUENCE OF TmnxBsxCflowdRecTmplEntry
    MAX-ACCESS  not-accessible
    STATUS      current
    DESCRIPTION
        "The tmnxBsxCflowdRecTmplTable contains the cflowd record template
         configuration."
    ::= { tmnxBsxAqpObjs 5 }

tmnxBsxCflowdRecTmplEntry        OBJECT-TYPE
    SYNTAX      TmnxBsxCflowdRecTmplEntry
    MAX-ACCESS  not-accessible
    STATUS      current
    DESCRIPTION
        "Each tmnxBsxCflowdRecTmplEntry specifies a cflowd record template."
    INDEX       {
        tmnxBsxIsaAaGroupIndex,
        tmnxBsxCflowdRecTemplate
    }
    ::= { tmnxBsxCflowdRecTmplTable 1 }

TmnxBsxCflowdRecTmplEntry        ::= SEQUENCE
{
    tmnxBsxCflowdRecTemplate         TmnxBsxCflowdRecTemplate,
    tmnxBsxCflowdRecTmplAdmin        TmnxAdminState,
    tmnxBsxCflowdRecTmplFldsSelType  TmnxBsxCflowdFieldSelType,
    tmnxBsxCflowdRecTmplRowLstChg    TimeStamp
}

tmnxBsxCflowdRecTemplate         OBJECT-TYPE
    SYNTAX      TmnxBsxCflowdRecTemplate
    MAX-ACCESS  not-accessible
    STATUS      current
    DESCRIPTION
        "The value of tmnxBsxCflowdRecTemplate template type."
    ::= { tmnxBsxCflowdRecTmplEntry 1 }

tmnxBsxCflowdRecTmplAdmin        OBJECT-TYPE
    SYNTAX      TmnxAdminState
    MAX-ACCESS  read-create
    STATUS      current
    DESCRIPTION
        "The value of tmnxBsxCflowdRecTmplAdmin specifies whether the
         configured fields under such template are sent to the collector. If
         the value is disabled, the fields are not sent."
    DEFVAL      { outOfService }
    ::= { tmnxBsxCflowdRecTmplEntry 2 }

tmnxBsxCflowdRecTmplFldsSelType  OBJECT-TYPE
    SYNTAX      TmnxBsxCflowdFieldSelType
    MAX-ACCESS  read-create
    STATUS      current
    DESCRIPTION
        "The tmnxBsxCflowdRecTmplFldsSelType specifies the kind of field
         selection required by the user."
    DEFVAL      { legacy }
    ::= { tmnxBsxCflowdRecTmplEntry 3 }

tmnxBsxCflowdRecTmplRowLstChg    OBJECT-TYPE
    SYNTAX      TimeStamp
    MAX-ACCESS  read-only
    STATUS      current
    DESCRIPTION
        "The value of tmnxBsxCflowdRecTmplRowLstChg indicates the last time,
         since system startup, a successful set was performed on this row."
    ::= { tmnxBsxCflowdRecTmplEntry 4 }

tmnxBsxCflowdRecFieldTable       OBJECT-TYPE
    SYNTAX      SEQUENCE OF TmnxBsxCflowdRecFieldEntry
    MAX-ACCESS  not-accessible
    STATUS      current
    DESCRIPTION
        "The tmnxBsxCflowdRecFieldTable contains the cflowd record template
         configuration."
    ::= { tmnxBsxAqpObjs 6 }

tmnxBsxCflowdRecFieldEntry       OBJECT-TYPE
    SYNTAX      TmnxBsxCflowdRecFieldEntry
    MAX-ACCESS  not-accessible
    STATUS      current
    DESCRIPTION
        "Each tmnxBsxCflowdRecFieldEntry specifies a cflowd record field."
    INDEX       {
        tmnxBsxIsaAaGroupIndex,
        tmnxBsxCflowdRecTemplate,
        tmnxBsxCflowdRecField
    }
    ::= { tmnxBsxCflowdRecFieldTable 1 }

TmnxBsxCflowdRecFieldEntry       ::= SEQUENCE
{
    tmnxBsxCflowdRecField            Unsigned32,
    tmnxBsxCflowdRecFldRowStatus     RowStatus,
    tmnxBsxCflowdRecFieldName        TNamedItem,
    tmnxBsxCflowdRecFieldDescr       TItemDescription,
    tmnxBsxCflowdRecFieldSize        Unsigned32,
    tmnxBsxCflowdRecFieldId          Unsigned32,
    tmnxBsxCflowdRecFieldEnterprise  TruthValue,
    tmnxBsxCflowdRecFldRowLstChg     TimeStamp
}

tmnxBsxCflowdRecField            OBJECT-TYPE
    SYNTAX      Unsigned32 (1..65535)
    MAX-ACCESS  not-accessible
    STATUS      current
    DESCRIPTION
        "The value of tmnxBsxCflowdRecField specifies the Cflowd record field
         Id. Enterprise field IDs are encoded as the Id plus 32768, while the
         IANA field IDs are used as is.

         Ids are defined in the tmnxBsxTListAttribTable in rows where the index
         tmnxBsxTListName has a value of 'cflowd-record-fields' and the index
         tmnxBsxTListAttribName has a value of 'id'."
    ::= { tmnxBsxCflowdRecFieldEntry 1 }

tmnxBsxCflowdRecFldRowStatus     OBJECT-TYPE
    SYNTAX      RowStatus
    MAX-ACCESS  read-create
    STATUS      current
    DESCRIPTION
        "The value of tmnxBsxCflowdRecFldRowStatus specifies
         the row status.  It allows entries to be created
         and deleted in the tmnxBsxCflowdRecFieldTable.

         Rows are created by specifying the value of 'createAndGo (4)', and
         deleted by specifying the value of 'destroy (6)'."
    ::= { tmnxBsxCflowdRecFieldEntry 2 }

tmnxBsxCflowdRecFieldName        OBJECT-TYPE
    SYNTAX      TNamedItem
    MAX-ACCESS  read-only
    STATUS      current
    DESCRIPTION
        "The value of tmnxBsxCflowdRecFieldName specifies the Cflowd record
         field name.

         Field names are defined in the tmnxBsxTListAttribTable in rows where
         the index tmnxBsxTListName has a value of 'cflowd-record-fields' and
         the index tmnxBsxTListAttribName has a value of 'name'."
    ::= { tmnxBsxCflowdRecFieldEntry 3 }

tmnxBsxCflowdRecFieldDescr       OBJECT-TYPE
    SYNTAX      TItemDescription
    MAX-ACCESS  read-only
    STATUS      current
    DESCRIPTION
        "The value of tmnxBsxCflowdRecFieldDescr specifies the Cflowd record
         field description.

         Field description is defined in the tmnxBsxTListAttribTable in rows
         where the index tmnxBsxTListName has a value of 'cflowd-record-fields'
         and the index tmnxBsxTListAttribName has a value of 'description'."
    ::= { tmnxBsxCflowdRecFieldEntry 4 }

tmnxBsxCflowdRecFieldSize        OBJECT-TYPE
    SYNTAX      Unsigned32
    UNITS       "bytes"
    MAX-ACCESS  read-only
    STATUS      current
    DESCRIPTION
        "The value of tmnxBsxCflowdRecFieldSize  specifies the
         Cflowd record field size.

         Field size is defined in the tmnxBsxTListAttribTable in rows where the
         index tmnxBsxTListName has a value of 'cflowd-record-fields' and the
         index tmnxBsxTListAttribName has a value of 'size'."
    ::= { tmnxBsxCflowdRecFieldEntry 5 }

tmnxBsxCflowdRecFieldId          OBJECT-TYPE
    SYNTAX      Unsigned32
    MAX-ACCESS  read-only
    STATUS      current
    DESCRIPTION
        "The value of tmnxBsxCflowdRecFieldId specifies the Cflowd record field
         identifier excluding the mask of 32768 used in the key."
    ::= { tmnxBsxCflowdRecFieldEntry 6 }

tmnxBsxCflowdRecFieldEnterprise  OBJECT-TYPE
    SYNTAX      TruthValue
    MAX-ACCESS  read-only
    STATUS      current
    DESCRIPTION
        "The value of tmnxBsxCflowdRecFieldEnterprise specifies if the Cflowd
         record field is an enterprise field."
    ::= { tmnxBsxCflowdRecFieldEntry 7 }

tmnxBsxCflowdRecFldRowLstChg     OBJECT-TYPE
    SYNTAX      TimeStamp
    MAX-ACCESS  read-only
    STATUS      current
    DESCRIPTION
        "The value of tmnxBsxCflowdRecFldRowLstChg indicates the last time,
         since system startup, a successful set was performed on this row."
    ::= { tmnxBsxCflowdRecFieldEntry 8 }

tmnxBsxWebServiceCategoryTable   OBJECT-TYPE
    SYNTAX      SEQUENCE OF TmnxBsxWebServiceCategoryEntry
    MAX-ACCESS  not-accessible
    STATUS      current
    DESCRIPTION
        "The tmnxBsxWebServiceCategoryTable contains an entry for each web
         service url classification category pre-configured by the agent. Rows
         in this table are created by the agent at initialization and cannot be
         created or destroyed by SNMP Get or Set requests."
    ::= { tmnxBsxAqpObjs 7 }

tmnxBsxWebServiceCategoryEntry   OBJECT-TYPE
    SYNTAX      TmnxBsxWebServiceCategoryEntry
    MAX-ACCESS  not-accessible
    STATUS      current
    DESCRIPTION
        "Each tmnxBsxWebServiceCategoryEntry indicates a URL classification
         category pre-configured by the agent."
    INDEX       {
        tmnxBsxWebServCategorySetId,
        tmnxBsxWebServCategoryId
    }
    ::= { tmnxBsxWebServiceCategoryTable 1 }

TmnxBsxWebServiceCategoryEntry   ::= SEQUENCE
{
    tmnxBsxWebServCategorySetId      TmnxBsxWebServCategorySetIdKey,
    tmnxBsxWebServCategoryId         TmnxBsxWebServiceCategoryIdKey,
    tmnxBsxWebServCategoryName       TNamedItem,
    tmnxBsxWebServCategRowLastChg    TimeStamp,
    tmnxBsxWebServCategDescr         TXLNamedItem
}

tmnxBsxWebServCategorySetId      OBJECT-TYPE
    SYNTAX      TmnxBsxWebServCategorySetIdKey
    MAX-ACCESS  not-accessible
    STATUS      current
    DESCRIPTION
        "The value of tmnxBsxWebServCategorySetId indicates the category set
         identifier."
    ::= { tmnxBsxWebServiceCategoryEntry 1 }

tmnxBsxWebServCategoryId         OBJECT-TYPE
    SYNTAX      TmnxBsxWebServiceCategoryIdKey
    MAX-ACCESS  not-accessible
    STATUS      current
    DESCRIPTION
        "The value of tmnxBsxWebServCategoryId indicates the URL classification
         category identifier."
    ::= { tmnxBsxWebServiceCategoryEntry 2 }

tmnxBsxWebServCategoryName       OBJECT-TYPE
    SYNTAX      TNamedItem
    MAX-ACCESS  read-only
    STATUS      current
    DESCRIPTION
        "The value of tmnxBsxWebServCategoryName indicates the name defined for
         the URL classification category."
    ::= { tmnxBsxWebServiceCategoryEntry 3 }

tmnxBsxWebServCategRowLastChg    OBJECT-TYPE
    SYNTAX      TimeStamp
    MAX-ACCESS  read-only
    STATUS      current
    DESCRIPTION
        "The value of tmnxBsxWebServCategRowLastChg indicates the last time,
         since system startup, a successful set was performed on this row."
    ::= { tmnxBsxWebServiceCategoryEntry 4 }

tmnxBsxWebServCategDescr         OBJECT-TYPE
    SYNTAX      TXLNamedItem
    MAX-ACCESS  read-only
    STATUS      current
    DESCRIPTION
        "The value of tmnxBsxWebServCategDescr indicates the category
         description."
    ::= { tmnxBsxWebServiceCategoryEntry 5 }

tmnxBsxUrlFltrWebServProfTable   OBJECT-TYPE
    SYNTAX      SEQUENCE OF TmnxBsxUrlFltrWebServProfEntry
    MAX-ACCESS  not-accessible
    STATUS      current
    DESCRIPTION
        "The tmnxBsxUrlFltrWebServProfTable contains the URL filter web service
         category profile configuration."
    ::= { tmnxBsxAqpObjs 8 }

tmnxBsxUrlFltrWebServProfEntry   OBJECT-TYPE
    SYNTAX      TmnxBsxUrlFltrWebServProfEntry
    MAX-ACCESS  not-accessible
    STATUS      current
    DESCRIPTION
        "Each tmnxBsxUrlFltrWebServProfEntry specifies a a URL filter profile
         associated with a web service."
    INDEX       {
        tmnxBsxIsaAaGroupIndex,
        tmnxBsxUrlFilterName,
        tmnxBsxUrlFltrWebServProfile
    }
    ::= { tmnxBsxUrlFltrWebServProfTable 1 }

TmnxBsxUrlFltrWebServProfEntry   ::= SEQUENCE
{
    tmnxBsxUrlFltrWebServProfile     TNamedItem,
    tmnxBsxUrlFltWebSerProfRowStatus RowStatus,
    tmnxBsxUrlFltWebSerProfDescr     TItemDescription,
    tmnxBsxUrlFltWebSerProfRoLstChg  TimeStamp
}

tmnxBsxUrlFltrWebServProfile     OBJECT-TYPE
    SYNTAX      TNamedItem
    MAX-ACCESS  not-accessible
    STATUS      current
    DESCRIPTION
        "The value of tmnxBsxUrlFltrWebServProfile specifies the web service
         category profile name."
    ::= { tmnxBsxUrlFltrWebServProfEntry 1 }

tmnxBsxUrlFltWebSerProfRowStatus OBJECT-TYPE
    SYNTAX      RowStatus
    MAX-ACCESS  read-create
    STATUS      current
    DESCRIPTION
        "The value of tmnxBsxUrlFltWebSerProfRowStatus specifies
         the row status.  It allows entries to be created
         and deleted in the tmnxBsxUrlFltrWebServProfTable.

         Rows are created by specifying the value of 'createAndGo (4)', and
         deleted by specifying the value of 'destroy (6)'."
    ::= { tmnxBsxUrlFltrWebServProfEntry 2 }

tmnxBsxUrlFltWebSerProfDescr     OBJECT-TYPE
    SYNTAX      TItemDescription
    MAX-ACCESS  read-create
    STATUS      current
    DESCRIPTION
        "The value of tmnxBsxUrlFltWebSerProfDescr specifies the description of
         the URL filter web service profile."
    DEFVAL      { "" }
    ::= { tmnxBsxUrlFltrWebServProfEntry 3 }

tmnxBsxUrlFltWebSerProfRoLstChg  OBJECT-TYPE
    SYNTAX      TimeStamp
    MAX-ACCESS  read-only
    STATUS      current
    DESCRIPTION
        "The value of tmnxBsxUrlFltWebSerProfRoLstChg indicates the last time,
         since system startup, a successful set was performed on this row."
    ::= { tmnxBsxUrlFltrWebServProfEntry 4 }

tmnxBsxUrlFltWebSerCategoryTable OBJECT-TYPE
    SYNTAX      SEQUENCE OF TmnxBsxUrlFltWebSerCategoryEntry
    MAX-ACCESS  not-accessible
    STATUS      current
    DESCRIPTION
        "The tmnxBsxUrlFltWebSerCategoryTable contains the URL filter web
         service category configuration associated with a web service profile."
    ::= { tmnxBsxAqpObjs 9 }

tmnxBsxUrlFltWebSerCategoryEntry OBJECT-TYPE
    SYNTAX      TmnxBsxUrlFltWebSerCategoryEntry
    MAX-ACCESS  not-accessible
    STATUS      current
    DESCRIPTION
        "Each tmnxBsxUrlFltWebSerCategoryEntry specifies a a URL filter
         category associated with a web service URL classifier software
         versioned product."
    INDEX       {
        tmnxBsxIsaAaGroupIndex,
        tmnxBsxUrlFilterName,
        tmnxBsxUrlFltrWebServProfile,
        tmnxBsxUrlFltrWebServCategory
    }
    ::= { tmnxBsxUrlFltWebSerCategoryTable 1 }

TmnxBsxUrlFltWebSerCategoryEntry ::= SEQUENCE
{
    tmnxBsxUrlFltrWebServCategory    Unsigned32,
    tmnxBsxUrlFltWebServCategRowSt   RowStatus,
    tmnxBsxUrlFltWebServCategName    TNamedItem,
    tmnxBsxUrlFltWebSerCategRoLstChg TimeStamp
}

tmnxBsxUrlFltrWebServCategory    OBJECT-TYPE
    SYNTAX      Unsigned32 (1..65535)
    MAX-ACCESS  not-accessible
    STATUS      current
    DESCRIPTION
        "The value of tmnxBsxUrlFltrWebServCategory specifies the web service
         category Id."
    ::= { tmnxBsxUrlFltWebSerCategoryEntry 1 }

tmnxBsxUrlFltWebServCategRowSt   OBJECT-TYPE
    SYNTAX      RowStatus
    MAX-ACCESS  read-create
    STATUS      current
    DESCRIPTION
        "The value of tmnxBsxUrlFltWebServCategRowSt specifies
         the row status.  It allows entries to be created
         and deleted in the tmnxBsxUrlFltWebSerCategoryTable.

         Rows are created by specifying the value of 'createAndGo (4)', and
         deleted by specifying the value of 'destroy (6)'."
    ::= { tmnxBsxUrlFltWebSerCategoryEntry 2 }

tmnxBsxUrlFltWebServCategName    OBJECT-TYPE
    SYNTAX      TNamedItem
    MAX-ACCESS  read-only
    STATUS      current
    DESCRIPTION
        "The value of tmnxBsxUrlFltWebServCategName indicates the name of the
         category."
    ::= { tmnxBsxUrlFltWebSerCategoryEntry 3 }

tmnxBsxUrlFltWebSerCategRoLstChg OBJECT-TYPE
    SYNTAX      TimeStamp
    MAX-ACCESS  read-only
    STATUS      current
    DESCRIPTION
        "The value of tmnxBsxUrlFltWebSerCategRoLstChg indicates the last time,
         since system startup, a successful set was performed on this row."
    ::= { tmnxBsxUrlFltWebSerCategoryEntry 4 }

tmnxBsxWebUrlCategorySetTable    OBJECT-TYPE
    SYNTAX      SEQUENCE OF TmnxBsxWebUrlCategorySetEntry
    MAX-ACCESS  not-accessible
    STATUS      current
    DESCRIPTION
        "The tmnxBsxWebUrlCategorySetTable contains an entry for each web
         service url classification category set pre-configured by the agent.
         Rows in this table are created by the agent at initialization and
         cannot be created or destroyed by SNMP Set requests."
    ::= { tmnxBsxAqpObjs 10 }

tmnxBsxWebUrlCategorySetEntry    OBJECT-TYPE
    SYNTAX      TmnxBsxWebUrlCategorySetEntry
    MAX-ACCESS  not-accessible
    STATUS      current
    DESCRIPTION
        "Each tmnxBsxWebUrlCategorySetEntry indicates a URL classification
         category set pre-configured by the agent."
    INDEX       {
        tmnxBsxWebUrlCategorySetId,
        tmnxBsxWebUrlClassifier
    }
    ::= { tmnxBsxWebUrlCategorySetTable 1 }

TmnxBsxWebUrlCategorySetEntry    ::= SEQUENCE
{
    tmnxBsxWebUrlCategorySetId       TmnxBsxWebServCategorySetIdKey,
    tmnxBsxWebUrlClassifier          TmnxBsxWebServClassifierIdKey,
    tmnxBsxWebUrlClassifierDescr     TItemDescription,
    tmnxBsxWebUrlCategSetRowLastChg  TimeStamp
}

tmnxBsxWebUrlCategorySetId       OBJECT-TYPE
    SYNTAX      TmnxBsxWebServCategorySetIdKey
    MAX-ACCESS  not-accessible
    STATUS      current
    DESCRIPTION
        "The value of tmnxBsxWebUrlCategorySetId indicates the category set
         identifier."
    ::= { tmnxBsxWebUrlCategorySetEntry 1 }

tmnxBsxWebUrlClassifier          OBJECT-TYPE
    SYNTAX      TmnxBsxWebServClassifierIdKey
    MAX-ACCESS  not-accessible
    STATUS      current
    DESCRIPTION
        "The value of tmnxBsxWebUrlClassifier indicates the web URL classifier
         identifier."
    ::= { tmnxBsxWebUrlCategorySetEntry 2 }

tmnxBsxWebUrlClassifierDescr     OBJECT-TYPE
    SYNTAX      TItemDescription
    MAX-ACCESS  read-only
    STATUS      current
    DESCRIPTION
        "The value of tmnxBsxWebUrlClassifierDescr  specifies the description of
         the UR classifier."
    ::= { tmnxBsxWebUrlCategorySetEntry 3 }

tmnxBsxWebUrlCategSetRowLastChg  OBJECT-TYPE
    SYNTAX      TimeStamp
    MAX-ACCESS  read-only
    STATUS      current
    DESCRIPTION
        "The value of tmnxBsxWebUrlCategSetRowLastChg indicates the last time,
         since system startup, a successful set was performed on this row."
    ::= { tmnxBsxWebUrlCategorySetEntry 4 }

tmnxBsxUrlFltrWSClassOvrdTable   OBJECT-TYPE
    SYNTAX      SEQUENCE OF TmnxBsxUrlFltrWSClassOvrdEntry
    MAX-ACCESS  not-accessible
    STATUS      current
    DESCRIPTION
        "The tmnxBsxUrlFltrWSClassOvrdTable contains the URL filter web service
         classification override configuration."
    ::= { tmnxBsxAqpObjs 11 }

tmnxBsxUrlFltrWSClassOvrdEntry   OBJECT-TYPE
    SYNTAX      TmnxBsxUrlFltrWSClassOvrdEntry
    MAX-ACCESS  not-accessible
    STATUS      current
    DESCRIPTION
        "Each tmnxBsxUrlFltrWSClassOvrdEntry specifies a a URL filter Web
         Service classification override entry."
    INDEX       {
        tmnxBsxIsaAaGroupIndex,
        tmnxBsxUrlFilterName,
        tmnxBsxUrlFltrWSClassOvrdEntryId
    }
    ::= { tmnxBsxUrlFltrWSClassOvrdTable 1 }

TmnxBsxUrlFltrWSClassOvrdEntry   ::= SEQUENCE
{
    tmnxBsxUrlFltrWSClassOvrdEntryId Unsigned32,
    tmnxBsxUrlFltWSClassOvrdRowSt    RowStatus,
    tmnxBsxUrlFltWSClassOvrdUrlExpr  TmnxBsxExprSubString,
    tmnxBsxUrlFltWSClassOvrdUrlCateg TmnxBsxWebServiceCategoryId,
    tmnxBsxUrlFltWSClassOvrdLstChg   TimeStamp,
    tmnxBsxUrlFltWSClassOvrdCategNam TNamedItem
}

tmnxBsxUrlFltrWSClassOvrdEntryId OBJECT-TYPE
    SYNTAX      Unsigned32 (1..65535)
    MAX-ACCESS  not-accessible
    STATUS      current
    DESCRIPTION
        "The value of tmnxBsxUrlFltrWSClassOvrdEntryId specifies the web
         service classification override entry index."
    ::= { tmnxBsxUrlFltrWSClassOvrdEntry 1 }

tmnxBsxUrlFltWSClassOvrdRowSt    OBJECT-TYPE
    SYNTAX      RowStatus
    MAX-ACCESS  read-create
    STATUS      current
    DESCRIPTION
        "The value of tmnxBsxUrlFltWSClassOvrdRowSt specifies
         the row status.  It allows entries to be created
         and deleted in the tmnxBsxUrlFltrWSClassOvrdTable.

         Rows are created by specifying the value of 'createAndGo (4)', and
         deleted by specifying the value of 'destroy (6)'."
    ::= { tmnxBsxUrlFltrWSClassOvrdEntry 2 }

tmnxBsxUrlFltWSClassOvrdUrlExpr  OBJECT-TYPE
    SYNTAX      TmnxBsxExprSubString
    MAX-ACCESS  read-create
    STATUS      current
    DESCRIPTION
        "The value of tmnxBsxUrlFltWSClassOvrdUrlExpr specifies the URL
         expression that will be overridden to a category."
    DEFVAL      { "" }
    ::= { tmnxBsxUrlFltrWSClassOvrdEntry 3 }

tmnxBsxUrlFltWSClassOvrdUrlCateg OBJECT-TYPE
    SYNTAX      TmnxBsxWebServiceCategoryId
    MAX-ACCESS  read-create
    STATUS      current
    DESCRIPTION
        "The value of tmnxBsxUrlFltWSClassOvrdUrlCateg specifies the web
         service category associated with the URL expression indicated in
         tmnxBsxUrlFltWSClassOvrdUrlExpr."
    DEFVAL      { 0 }
    ::= { tmnxBsxUrlFltrWSClassOvrdEntry 4 }

tmnxBsxUrlFltWSClassOvrdLstChg   OBJECT-TYPE
    SYNTAX      TimeStamp
    MAX-ACCESS  read-only
    STATUS      current
    DESCRIPTION
        "The value of tmnxBsxUrlFltWSClassOvrdLstChg indicates the last time,
         since system startup, a successful set was performed on this row."
    ::= { tmnxBsxUrlFltrWSClassOvrdEntry 5 }

tmnxBsxUrlFltWSClassOvrdCategNam OBJECT-TYPE
    SYNTAX      TNamedItem
    MAX-ACCESS  read-only
    STATUS      current
    DESCRIPTION
        "The value of tmnxBsxUrlFltWSClassOvrdCategNam indicates the name of
         the category."
    ::= { tmnxBsxUrlFltrWSClassOvrdEntry 6 }

tmnxBsxAnlTable                  OBJECT-TYPE
    SYNTAX      SEQUENCE OF TmnxBsxAnlEntry
    MAX-ACCESS  not-accessible
    STATUS      current
    DESCRIPTION
        "The tmnxBsxAnlTable contains the configuration relating to Access
         Network Location (ANL)."
    ::= { tmnxBsxPolicyObjs 30 }

tmnxBsxAnlEntry                  OBJECT-TYPE
    SYNTAX      TmnxBsxAnlEntry
    MAX-ACCESS  not-accessible
    STATUS      current
    DESCRIPTION
        "Each tmnxBsxAnlEntry indicates the ANL configuration for a given group
         and/or partition.

         Entries in this table are created and destroyed via SNMP set
         operations to tmnxBsxAnlRowStatus."
    INDEX       {
        tmnxBsxAaGrpPartIndex,
        tmnxBsxAnlSource
    }
    ::= { tmnxBsxAnlTable 1 }

TmnxBsxAnlEntry                  ::= SEQUENCE
{
    tmnxBsxAnlSource                 TmnxBsxAnlSource,
    tmnxBsxAnlRowLastChange          TimeStamp,
    tmnxBsxAnlRowStatus              RowStatus,
    tmnxBsxAnlSourceLevel            TmnxBsxAnlSourceLevel,
    tmnxBsxAnlRttThreshold           Unsigned32,
    tmnxBsxAnlRttThresholdTolerance  Unsigned32
}

tmnxBsxAnlSource                 OBJECT-TYPE
    SYNTAX      TmnxBsxAnlSource
    MAX-ACCESS  read-create
    STATUS      current
    DESCRIPTION
        "The value of tmnxBsxAnlSource specifies the the access network
         location source."
    DEFVAL      { mobile-3g }
    ::= { tmnxBsxAnlEntry 1 }

tmnxBsxAnlRowLastChange          OBJECT-TYPE
    SYNTAX      TimeStamp
    MAX-ACCESS  read-only
    STATUS      current
    DESCRIPTION
        "The value of tmnxBsxAnlRowLastChange indicates the last time, since
         the system startup, the row was modified."
    ::= { tmnxBsxAnlEntry 2 }

tmnxBsxAnlRowStatus              OBJECT-TYPE
    SYNTAX      RowStatus
    MAX-ACCESS  read-create
    STATUS      current
    DESCRIPTION
        "The value of tmnxBsxAnlRowStatus indicates the row status. It allows
         rows to be created and deleted in the tmnxBsxAnlTable table."
    ::= { tmnxBsxAnlEntry 3 }

tmnxBsxAnlSourceLevel            OBJECT-TYPE
    SYNTAX      TmnxBsxAnlSourceLevel
    MAX-ACCESS  read-create
    STATUS      current
    DESCRIPTION
        "The value of tmnxBsxAnlSourceLevel specifies the the type of the
         access network location source level."
    DEFVAL      { cell }
    ::= { tmnxBsxAnlEntry 4 }

tmnxBsxAnlRttThreshold           OBJECT-TYPE
    SYNTAX      Unsigned32 (0 | 1..500)
    UNITS       "milliseconds"
    MAX-ACCESS  read-create
    STATUS      current
    DESCRIPTION
        "The value of tmnxBsxAnlRttThreshold specifies the maximum tolerable
         Round Trip Time (RTT) delay (in milliseconds).

         The value '0' disables RTT threshold."
    DEFVAL      { 173 }
    ::= { tmnxBsxAnlEntry 5 }

tmnxBsxAnlRttThresholdTolerance  OBJECT-TYPE
    SYNTAX      Unsigned32 (0..100)
    MAX-ACCESS  read-create
    STATUS      current
    DESCRIPTION
        "The value of tmnxBsxAnlRttThresholdTolerance specifies the percentage
         of RTT samples (number of excessive RTT samples / total RTT samples)
         in a collection period that is considered tolerable and does not
         trigger a congestion event.

         tmnxBsxAnlRttThresholdTolerance is applicable only when the value of
         tmnxBsxAnlRttThreshold is non-zero."
    DEFVAL      { 50 }
    ::= { tmnxBsxAnlEntry 6 }

tmnxBsxPortListTable             OBJECT-TYPE
    SYNTAX      SEQUENCE OF TmnxBsxPortListEntry
    MAX-ACCESS  not-accessible
    STATUS      current
    DESCRIPTION
        "The tmnxBsxPortListTable contains entries for the port lists defined
         in Application Assurance.

         The rows in this table are created and destroyed by the user."
    ::= { tmnxBsxPolicyObjs 31 }

tmnxBsxPortListEntry             OBJECT-TYPE
    SYNTAX      TmnxBsxPortListEntry
    MAX-ACCESS  not-accessible
    STATUS      current
    DESCRIPTION
        "Each tmnxBsxPortListEntry specifies an IP port list which may be
         referenced in the following tables:
             - tmnxBsxAppFilterTable"
    INDEX       {
        tmnxBsxAaGrpPartIndex,
        IMPLIED tmnxBsxPortListName
    }
    ::= { tmnxBsxPortListTable 1 }

TmnxBsxPortListEntry             ::= SEQUENCE
{
    tmnxBsxPortListName              TNamedItem,
    tmnxBsxPortListRowStatus         RowStatus,
    tmnxBsxPortListRowLastChange     TimeStamp,
    tmnxBsxPortListDescription       TItemDescription
}

tmnxBsxPortListName              OBJECT-TYPE
    SYNTAX      TNamedItem
    MAX-ACCESS  not-accessible
    STATUS      current
    DESCRIPTION
        "The value of tmnxBsxPortListName specifies the name of the IP Port
         List."
    ::= { tmnxBsxPortListEntry 1 }

tmnxBsxPortListRowStatus         OBJECT-TYPE
    SYNTAX      RowStatus
    MAX-ACCESS  read-create
    STATUS      current
    DESCRIPTION
        "The value of tmnxBsxPortListRowStatus specifies the row status. It
         allows entries to be created and deleted in the tmnxBsxPortListTable."
    ::= { tmnxBsxPortListEntry 2 }

tmnxBsxPortListRowLastChange     OBJECT-TYPE
    SYNTAX      TimeStamp
    MAX-ACCESS  read-only
    STATUS      current
    DESCRIPTION
        "The value of tmnxBsxPortListRowLastChange indicates the last time,
         since system startup, a successful set was performed on this row."
    ::= { tmnxBsxPortListEntry 3 }

tmnxBsxPortListDescription       OBJECT-TYPE
    SYNTAX      TItemDescription
    MAX-ACCESS  read-create
    STATUS      current
    DESCRIPTION
        "The value of tmnxBsxPortListDescription specifies the description of
         the IP Port List."
    DEFVAL      { "" }
    ::= { tmnxBsxPortListEntry 4 }

tmnxBsxPortTable                 OBJECT-TYPE
    SYNTAX      SEQUENCE OF TmnxBsxPortEntry
    MAX-ACCESS  not-accessible
    STATUS      current
    DESCRIPTION
        "The tmnxBsxPortTable contains an entry for each port range defined in
         an Application Assurance port list.

         A row in this table is created and destroyed by the user and is
         dependent on the corresponding tmnxBsxPortListEntry as indicated by
         tmnxBsxPortListName."
    ::= { tmnxBsxPolicyObjs 32 }

tmnxBsxPortEntry                 OBJECT-TYPE
    SYNTAX      TmnxBsxPortEntry
    MAX-ACCESS  not-accessible
    STATUS      current
    DESCRIPTION
        "Each tmnxBsxPortEntry specifies an IP port or port range within an
         Application Assurance port list (tmnxBsxPortListTable).

         When a port range contains just one port, the tmnxBsxPortLow and
         tmnxBsxPortHigh will contain the same port number."
    INDEX       {
        tmnxBsxAaGrpPartIndex,
        tmnxBsxPortListName,
        tmnxBsxPortLow,
        tmnxBsxPortHigh
    }
    ::= { tmnxBsxPortTable 1 }

TmnxBsxPortEntry                 ::= SEQUENCE
{
    tmnxBsxPortRowStatus             RowStatus,
    tmnxBsxPortLow                   TTcpUdpPort,
    tmnxBsxPortHigh                  TTcpUdpPort
}

tmnxBsxPortRowStatus             OBJECT-TYPE
    SYNTAX      RowStatus
    MAX-ACCESS  read-create
    STATUS      current
    DESCRIPTION
        "The value of tmnxBsxPortRowStatus specifies the row status. It allows
         entries to be created and deleted in the tmnxBsxPortTable."
    ::= { tmnxBsxPortEntry 1 }

tmnxBsxPortLow                   OBJECT-TYPE
    SYNTAX      TTcpUdpPort
    MAX-ACCESS  read-create
    STATUS      current
    DESCRIPTION
        "The value of tmnxBsxPortLow specifies the lowest port number in the
         port range being defined."
    ::= { tmnxBsxPortEntry 2 }

tmnxBsxPortHigh                  OBJECT-TYPE
    SYNTAX      TTcpUdpPort
    MAX-ACCESS  read-create
    STATUS      current
    DESCRIPTION
        "The value of tmnxBsxPortHigh specifies the highest port number in the
         port range being defined"
    ::= { tmnxBsxPortEntry 3 }

tmnxBsxCertProfileTable          OBJECT-TYPE
    SYNTAX      SEQUENCE OF TmnxBsxCertProfileEntry
    MAX-ACCESS  not-accessible
    STATUS      current
    DESCRIPTION
        "The tmnxBsxCertProfileTable contains configuration of AA certificate
         profile parameters.

         A row in this table is created and destroyed by the user."
    ::= { tmnxBsxPolicyObjs 33 }

tmnxBsxCertProfileEntry          OBJECT-TYPE
    SYNTAX      TmnxBsxCertProfileEntry
    MAX-ACCESS  not-accessible
    STATUS      current
    DESCRIPTION
        "Each tmnxBsxCertProfileEntry specifies the configuration of a
         certificate profile.

         Entries in this table can be created and deleted via configuration set
         operations to tmnxBsxCertProfileRowStatus. Entries have a presumed
         StorageType of nonVolatile."
    INDEX       {
        tmnxBsxIsaAaGroupIndex,
        IMPLIED tmnxBsxCertProfileName
    }
    ::= { tmnxBsxCertProfileTable 1 }

TmnxBsxCertProfileEntry          ::= SEQUENCE
{
    tmnxBsxCertProfileName           TNamedItem,
    tmnxBsxCertProfileRowStatus      RowStatus,
    tmnxBsxCertProfileLastChgd       TimeStamp,
    tmnxBsxCertProfileAdminState     TmnxAdminState,
    tmnxBsxCertProfileOperState      TmnxOperState,
    tmnxBsxCertProfileOperFlags      BITS,
    tmnxBsxCertProfileCertFile       DisplayString,
    tmnxBsxCertProfileDescription    TItemDescription,
    tmnxBsxCertProfileReferenceCount Counter32
}

tmnxBsxCertProfileName           OBJECT-TYPE
    SYNTAX      TNamedItem
    MAX-ACCESS  not-accessible
    STATUS      current
    DESCRIPTION
        "The value of tmnxBsxCertProfileName specifies a AA certificate profile
         name."
    ::= { tmnxBsxCertProfileEntry 1 }

tmnxBsxCertProfileRowStatus      OBJECT-TYPE
    SYNTAX      RowStatus
    MAX-ACCESS  read-create
    STATUS      current
    DESCRIPTION
        "The value of tmnxBsxCertProfileRowStatus specifies the row status. It
         allows entries to be created and deleted in the
         tmnxBsxCertProfileTable."
    ::= { tmnxBsxCertProfileEntry 2 }

tmnxBsxCertProfileLastChgd       OBJECT-TYPE
    SYNTAX      TimeStamp
    MAX-ACCESS  read-only
    STATUS      current
    DESCRIPTION
        "The value of tmnxBsxCertProfileLastChgd indicates the last time, since
         system startup, a successful set was performed on this row."
    ::= { tmnxBsxCertProfileEntry 3 }

tmnxBsxCertProfileAdminState     OBJECT-TYPE
    SYNTAX      TmnxAdminState
    MAX-ACCESS  read-create
    STATUS      current
    DESCRIPTION
        "The value of tmnxBsxCertProfileAdminState specifies the administrative
         state of the tmnxBsxCertProfileEntry."
    DEFVAL      { outOfService }
    ::= { tmnxBsxCertProfileEntry 4 }

tmnxBsxCertProfileOperState      OBJECT-TYPE
    SYNTAX      TmnxOperState
    MAX-ACCESS  read-only
    STATUS      current
    DESCRIPTION
        "The value of tmnxBsxCertProfileOperState indicates the operational
         status of tmnxBsxCertProfileEntry."
    ::= { tmnxBsxCertProfileEntry 5 }

tmnxBsxCertProfileOperFlags      OBJECT-TYPE
    SYNTAX      BITS {
        profileAdminDown             (0),
        invalidCertFile              (1),
        invalidCertFilePublicKey     (2),
        invalidPublicKeyModulus      (3),
        invalidPublicKeyExponent     (4),
        unsupportedCertFileAlgorithm (5),
        reserved6                    (6),
        reserved7                    (7)
    }
    MAX-ACCESS  read-only
    STATUS      current
    DESCRIPTION
        "The value of tmnxBsxCertProfileOperFlags indicates the operational
         condition of the certificate profile. The operational condition is
         interpreted based on the aggregated value of the flags."
    ::= { tmnxBsxCertProfileEntry 6 }

tmnxBsxCertProfileCertFile       OBJECT-TYPE
    SYNTAX      DisplayString (SIZE (0..95))
    MAX-ACCESS  read-create
    STATUS      current
    DESCRIPTION
        "The value of tmnxBsxCertProfileCertFile specifies the location of the
         file, containing the certificate, to be used with this AA certificate
         profile entry."
    DEFVAL      { ''H }
    ::= { tmnxBsxCertProfileEntry 7 }

tmnxBsxCertProfileDescription    OBJECT-TYPE
    SYNTAX      TItemDescription
    MAX-ACCESS  read-create
    STATUS      current
    DESCRIPTION
        "The value of tmnxBsxCertProfileDescription specifies the description
         of the certificate profile."
    DEFVAL      { "" }
    ::= { tmnxBsxCertProfileEntry 8 }

tmnxBsxCertProfileReferenceCount OBJECT-TYPE
    SYNTAX      Counter32
    MAX-ACCESS  read-only
    STATUS      current
    DESCRIPTION
        "The value of tmnxBsxCertProfileReferenceCount indicates the number of
         clients configured with this profile."
    ::= { tmnxBsxCertProfileEntry 9 }

tmnxBsxSubCongDetectTable        OBJECT-TYPE
    SYNTAX      SEQUENCE OF TmnxBsxSubCongDetectEntry
    MAX-ACCESS  not-accessible
    STATUS      current
    DESCRIPTION
        "The tmnxBsxSubCongDetectTable contains the configuration relating to
         AA subscriber congestion detection."
    ::= { tmnxBsxPolicyObjs 34 }

tmnxBsxSubCongDetectEntry        OBJECT-TYPE
    SYNTAX      TmnxBsxSubCongDetectEntry
    MAX-ACCESS  not-accessible
    STATUS      current
    DESCRIPTION
        "tmnxBsxSubCongDetectEntry indicates the AA subscriber congestion
         detection configuration for a given group and/or partition."
    INDEX       { tmnxBsxAaGrpPartIndex }
    ::= { tmnxBsxSubCongDetectTable 1 }

TmnxBsxSubCongDetectEntry        ::= SEQUENCE
{
    tmnxBsxSubCongDetectRowLastChg   TimeStamp,
    tmnxBsxSubCongDetectAdminState   TmnxAdminState,
    tmnxBsxSubRttThreshold           Unsigned32,
    tmnxBsxSubRttThresholdTolerance  Unsigned32
}

tmnxBsxSubCongDetectRowLastChg   OBJECT-TYPE
    SYNTAX      TimeStamp
    MAX-ACCESS  read-only
    STATUS      current
    DESCRIPTION
        "The value of tmnxBsxSubCongDetectRowLastChg indicates the last time,
         since the system startup, the row was modified."
    ::= { tmnxBsxSubCongDetectEntry 1 }

tmnxBsxSubCongDetectAdminState   OBJECT-TYPE
    SYNTAX      TmnxAdminState
    MAX-ACCESS  read-create
    STATUS      current
    DESCRIPTION
        "The value of tmnxBsxSubCongDetectAdminState specifies the
         administrative state of AA subscriber congestion detection support for
         a group-partition. When the value is 'outOfService(3)' support for AA
         subscriber congestion detection is disabled."
    DEFVAL      { outOfService }
    ::= { tmnxBsxSubCongDetectEntry 2 }

tmnxBsxSubRttThreshold           OBJECT-TYPE
    SYNTAX      Unsigned32 (0 | 1..500)
    UNITS       "milliseconds"
    MAX-ACCESS  read-create
    STATUS      current
    DESCRIPTION
        "The value of tmnxBsxSubRttThreshold specifies the maximum tolerable
         Round Trip Time (RTT) delay (in milliseconds).

         The value '0' disables RTT threshold."
    DEFVAL      { 173 }
    ::= { tmnxBsxSubCongDetectEntry 3 }

tmnxBsxSubRttThresholdTolerance  OBJECT-TYPE
    SYNTAX      Unsigned32 (0..100)
    MAX-ACCESS  read-create
    STATUS      current
    DESCRIPTION
        "The value of tmnxBsxSubRttThresholdTolerance specifies the percentage
         of RTT samples (number of excessive RTT samples / total RTT samples)
         in a collection period that is considered tolerable and does not
         trigger a congestion event.

         tmnxBsxSubRttThresholdTolerance is applicable only when the value of
         tmnxBsxSubRttThreshold is non-zero."
    DEFVAL      { 50 }
    ::= { tmnxBsxSubCongDetectEntry 4 }

tmnxBsxSubCongRatTable           OBJECT-TYPE
    SYNTAX      SEQUENCE OF TmnxBsxSubCongRatEntry
    MAX-ACCESS  not-accessible
    STATUS      current
    DESCRIPTION
        "The tmnxBsxSubCongRatTable contains the configuration relating to AA
         subscriber congestion detection per RAT type."
    ::= { tmnxBsxPolicyObjs 35 }

tmnxBsxSubCongRatEntry           OBJECT-TYPE
    SYNTAX      TmnxBsxSubCongRatEntry
    MAX-ACCESS  not-accessible
    STATUS      current
    DESCRIPTION
        "Each tmnxBsxSubCongRatEntry contains the definition of a RAT type and
         the configuration for that RAT type."
    INDEX       {
        tmnxBsxAaGrpPartIndex,
        tmnxBsxSubRatType
    }
    ::= { tmnxBsxSubCongRatTable 1 }

TmnxBsxSubCongRatEntry           ::= SEQUENCE
{
    tmnxBsxSubRatType                TmnxBsxHttpEnrichRATType,
    tmnxBsxSubRatRowStatus           RowStatus,
    tmnxBsxSubRatRowLastChg          TimeStamp,
    tmnxBsxSubRatRttThreshold        Integer32
}

tmnxBsxSubRatType                OBJECT-TYPE
    SYNTAX      TmnxBsxHttpEnrichRATType
    MAX-ACCESS  not-accessible
    STATUS      current
    DESCRIPTION
        "The value of tmnxBsxSubRatType indicates the RAT type of this entry."
    ::= { tmnxBsxSubCongRatEntry 1 }

tmnxBsxSubRatRowStatus           OBJECT-TYPE
    SYNTAX      RowStatus
    MAX-ACCESS  read-create
    STATUS      current
    DESCRIPTION
        "The value of tmnxBsxSubRatRowStatus specifies the row status. It
         allows entries to be created and deleted in the
         tmnxBsxSubCongRatTable.

         A value for tmnxBsxSubRatRttThreshold must be specified in order to
         create a row."
    ::= { tmnxBsxSubCongRatEntry 2 }

tmnxBsxSubRatRowLastChg          OBJECT-TYPE
    SYNTAX      TimeStamp
    MAX-ACCESS  read-only
    STATUS      current
    DESCRIPTION
        "The value of tmnxBsxSubRatRowLastChg indicates the last time, since
         the system startup, the row was modified."
    ::= { tmnxBsxSubCongRatEntry 3 }

tmnxBsxSubRatRttThreshold        OBJECT-TYPE
    SYNTAX      Integer32 (0 | 1..500)
    UNITS       "milliseconds"
    MAX-ACCESS  read-create
    STATUS      current
    DESCRIPTION
        "The value of tmnxBsxSubRatRttThreshold overrides the maximum tolerable
         Round Trip Time (RTT) delay (in milliseconds) specified in
         tmnxBsxSubRttThreshold.

         The value '0' disables RTT threshold for the RAT type."
    ::= { tmnxBsxSubCongRatEntry 4 }

tmnxBsxAnlRatTable               OBJECT-TYPE
    SYNTAX      SEQUENCE OF TmnxBsxAnlRatEntry
    MAX-ACCESS  not-accessible
    STATUS      current
    DESCRIPTION
        "The tmnxBsxAnlRatTable contains the configuration relating to Access
         Network Location (ANL) per RAT type."
    ::= { tmnxBsxPolicyObjs 36 }

tmnxBsxAnlRatEntry               OBJECT-TYPE
    SYNTAX      TmnxBsxAnlRatEntry
    MAX-ACCESS  not-accessible
    STATUS      current
    DESCRIPTION
        "Each tmnxBsxAnlRatEntry contains the definition of a RAT type and the
         configuration for that RAT type."
    INDEX       {
        tmnxBsxAaGrpPartIndex,
        tmnxBsxAnlSource,
        tmnxBsxAnlRatType
    }
    ::= { tmnxBsxAnlRatTable 1 }

TmnxBsxAnlRatEntry               ::= SEQUENCE
{
    tmnxBsxAnlRatType                TmnxBsxHttpEnrichRATType,
    tmnxBsxAnlRatRowStatus           RowStatus,
    tmnxBsxAnlRatRowLastChg          TimeStamp,
    tmnxBsxAnlRatRttThreshold        Integer32
}

tmnxBsxAnlRatType                OBJECT-TYPE
    SYNTAX      TmnxBsxHttpEnrichRATType
    MAX-ACCESS  not-accessible
    STATUS      current
    DESCRIPTION
        "The value of tmnxBsxAnlRatType indicates the RAT type of this entry."
    ::= { tmnxBsxAnlRatEntry 1 }

tmnxBsxAnlRatRowStatus           OBJECT-TYPE
    SYNTAX      RowStatus
    MAX-ACCESS  read-create
    STATUS      current
    DESCRIPTION
        "The value of tmnxBsxAnlRatRowStatus specifies the row status. It
         allows entries to be created and deleted in the tmnxBsxAnlRatTable.

         A value for tmnxBsxAnlRatRttThreshold must be specified in order to
         create a row."
    ::= { tmnxBsxAnlRatEntry 2 }

tmnxBsxAnlRatRowLastChg          OBJECT-TYPE
    SYNTAX      TimeStamp
    MAX-ACCESS  read-only
    STATUS      current
    DESCRIPTION
        "The value of tmnxBsxAnlRatRowLastChg indicates the last time, since
         the system startup, the row was modified."
    ::= { tmnxBsxAnlRatEntry 3 }

tmnxBsxAnlRatRttThreshold        OBJECT-TYPE
    SYNTAX      Integer32 (0 | 1..500)
    UNITS       "milliseconds"
    MAX-ACCESS  read-create
    STATUS      current
    DESCRIPTION
        "The value of tmnxBsxAnlRatRttThreshold overrides the maximum tolerable
         Round Trip Time (RTT) delay (in milliseconds) specified in
         tmnxBsxAnlRttThreshold.

         The value '0' disables RTT threshold for the RAT type."
    ::= { tmnxBsxAnlRatEntry 4 }

tmnxBsxAqpMatchCharTable         OBJECT-TYPE
    SYNTAX      SEQUENCE OF TmnxBsxAqpMatchCharEntry
    MAX-ACCESS  not-accessible
    STATUS      current
    DESCRIPTION
        "The tmnxBsxAqpMatchCharTable contains the ASO characteristic matches
         for the application qos policy table.  This table replaces tmnxBsxAqpCharTable."
    ::= { tmnxBsxPolicyObjs 37 }

tmnxBsxAqpMatchCharEntry         OBJECT-TYPE
    SYNTAX      TmnxBsxAqpMatchCharEntry
    MAX-ACCESS  not-accessible
    STATUS      current
    DESCRIPTION
        "Each tmnxBsxAqpMatchCharEntry specifies a match criterion and
         corresponding action for the application qos policy specified by the
         second and third indices tmnxBsxAaGrpPartIndex, and
         tmnxBsxAqpBaseEntryId. The tmnxBsxAsoCharName index uniquely specifies
         the characteristic in the tmnxBsxAsoTable.

         Rows can only be created and destroyed by specifying the
         tmnxBsxAqpCharRowStatus if the first index,
         tmnxBsxAqpBasePolicyVersion, is set to 'admin'. When creating,
         tmnxBsxAqpMatchCharOperator and tmnxBsxAqpMatchCharVal must also be
         specified."
    INDEX       {
        tmnxBsxAqpBasePolicyVersion,
        tmnxBsxAaGrpPartIndex,
        tmnxBsxAqpBaseEntryId,
        IMPLIED tmnxBsxAsoCharName
    }
    ::= { tmnxBsxAqpMatchCharTable 1 }

TmnxBsxAqpMatchCharEntry         ::= SEQUENCE
{
    tmnxBsxAqpMatchCharRowLastChange TimeStamp,
    tmnxBsxAqpMatchCharRowStatus     RowStatus,
    tmnxBsxAqpMatchCharOperator      TmnxBsxOperator,
    tmnxBsxAqpMatchCharVal           TNamedItemOrEmpty
}

tmnxBsxAqpMatchCharRowLastChange OBJECT-TYPE
    SYNTAX      TimeStamp
    MAX-ACCESS  read-only
    STATUS      current
    DESCRIPTION
        "The value of tmnxBsxAqpMatchCharRowLastChange indicates the last time,
         since system startup, a successful set was performed on this row."
    ::= { tmnxBsxAqpMatchCharEntry 1 }

tmnxBsxAqpMatchCharRowStatus     OBJECT-TYPE
    SYNTAX      RowStatus
    MAX-ACCESS  read-create
    STATUS      current
    DESCRIPTION
        "The value of tmnxBsxAqpMatchCharRowStatus specifies
         the row status.  It allows entries to be created
         and deleted in the tmnxBsxAqpMatchCharTable.

         Rows are created by specifying the value of 'createAndGo (4)', and
         deleted by specifying the value of 'destroy (6)'."
    ::= { tmnxBsxAqpMatchCharEntry 2 }

tmnxBsxAqpMatchCharOperator      OBJECT-TYPE
    SYNTAX      TmnxBsxOperator
    MAX-ACCESS  read-create
    STATUS      current
    DESCRIPTION
        "The value of tmnxBsxAqpMatchCharOperator specifies the comparison
         operator applied to the corresponding row in the tmnxBsxAsoValTable."
    DEFVAL      { none }
    ::= { tmnxBsxAqpMatchCharEntry 3 }

tmnxBsxAqpMatchCharVal           OBJECT-TYPE
    SYNTAX      TNamedItemOrEmpty
    MAX-ACCESS  read-create
    STATUS      current
    DESCRIPTION
        "The value of tmnxBsxAqpMatchCharVal specifies a particular value for a
         characteristic to match from the tmnxBsxAsoValTable."
    DEFVAL      { "" }
    ::= { tmnxBsxAqpMatchCharEntry 4 }

tmnxBsxIpIdentAssistObjs         OBJECT IDENTIFIER ::= { tmnxBsxPolicyObjs 38 }

tmnxBsxIpIdentAssistTable        OBJECT-TYPE
    SYNTAX      SEQUENCE OF TmnxBsxIpIdentAssistEntry
    MAX-ACCESS  not-accessible
    STATUS      current
    DESCRIPTION
        "The tmnxBsxIpIdentAssistTable contains the configurations related to
         IP-address-based application identification assist.  This is an optional
         configuration that can be used to identify some fully encrypted traffic."
    ::= { tmnxBsxIpIdentAssistObjs 1 }

tmnxBsxIpIdentAssistEntry        OBJECT-TYPE
    SYNTAX      TmnxBsxIpIdentAssistEntry
    MAX-ACCESS  not-accessible
    STATUS      current
    DESCRIPTION
        "Each tmnxBsxIpIdentAssistEntry specifies IP-Address-based
         identification configurations within an Application Assurance group"
    INDEX       { tmnxBsxIsaAaGroupIndex }
    ::= { tmnxBsxIpIdentAssistTable 1 }

TmnxBsxIpIdentAssistEntry        ::= SEQUENCE
{
    tmnxBsxIpIdentAssistRowLastChg   TimeStamp,
    tmnxBsxIpIdentAssistAdminState   TmnxAdminState,
    tmnxBsxIpIdentAssistPsvDnsMon    TmnxEnabledDisabled,
    tmnxBsxIpIdentAssistPosAppIdEnbl TmnxEnabledDisabled
}

tmnxBsxIpIdentAssistRowLastChg   OBJECT-TYPE
    SYNTAX      TimeStamp
    MAX-ACCESS  read-only
    STATUS      current
    DESCRIPTION
        "The value of tmnxBsxIpIdentAssistRowLastChg indicates the last time a
         successful set was performed on this row of the
         tmnxBsxIpIdentAssistTable."
    ::= { tmnxBsxIpIdentAssistEntry 1 }

tmnxBsxIpIdentAssistAdminState   OBJECT-TYPE
    SYNTAX      TmnxAdminState
    MAX-ACCESS  read-write
    STATUS      current
    DESCRIPTION
        "The value of tmnxBsxIpIdentAssistAdminState specifies the
         administrative state for Application Assurance IP-Address-based
         identification assist. When set to 'outOfService', no assist is
         performed for this group."
    DEFVAL      { inService }
    ::= { tmnxBsxIpIdentAssistEntry 2 }

tmnxBsxIpIdentAssistPsvDnsMon    OBJECT-TYPE
    SYNTAX      TmnxEnabledDisabled
    MAX-ACCESS  read-write
    STATUS      current
    DESCRIPTION
        "The value of tmnxBsxIpIdentAssistPsvDnsMon specifies whether to
         passively monitor DNS exchanges for domain names related to the
         assisted applications in order to populate the IP address cache."
    DEFVAL      { enabled }
    ::= { tmnxBsxIpIdentAssistEntry 3 }

tmnxBsxIpIdentAssistPosAppIdEnbl OBJECT-TYPE
    SYNTAX      TmnxEnabledDisabled
    MAX-ACCESS  read-write
    STATUS      current
    DESCRIPTION
        "The value of tmnxBsxIpIdentAssistPosAppIdEnbl specifies whether the
         Positive Application Identification mechanism contributes to the IP
         identification assist address cache. When enabled, the mechanism
         correlates IP addresses with applications that are identified with a
         high degree of confidence independently of any IP identification
         assist mechanism."
    DEFVAL      { enabled }
    ::= { tmnxBsxIpIdentAssistEntry 4 }

tmnxBsxIpIdAsstPDnsSrvTable      OBJECT-TYPE
    SYNTAX      SEQUENCE OF TmnxBsxIpIdAsstPDnsSrvEntry
    MAX-ACCESS  not-accessible
    STATUS      current
    DESCRIPTION
        "The tmnxBsxIpIdAsstPDnsSrvTable contains a list of trusted DNS server
         IP addresses for passive DNS monitoring for IP Identification Assist
         (tmnxBsxIpIdentAssistTable).

         Entries in this table are created and deleted via SNMP set operations
         to tmnxBsxIpIdAsstPDnsSrvRowStatus."
    ::= { tmnxBsxIpIdentAssistObjs 2 }

tmnxBsxIpIdAsstPDnsSrvEntry      OBJECT-TYPE
    SYNTAX      TmnxBsxIpIdAsstPDnsSrvEntry
    MAX-ACCESS  not-accessible
    STATUS      current
    DESCRIPTION
        "Each tmnxBsxIpIdAsstPDnsSrvEntry indicates the IP address of a trusted
         DNS server. Passive DNS monitoring only extracts IP to application
         mappings from trusted servers. If no IP addresses are specified, all
         DNS is monitored."
    INDEX       {
        tmnxBsxIsaAaGroupIndex,
        tmnxBsxIpIdAsstPDnsSrvAddrType,
        tmnxBsxIpIdAsstPDnsSrvAddr
    }
    ::= { tmnxBsxIpIdAsstPDnsSrvTable 1 }

TmnxBsxIpIdAsstPDnsSrvEntry      ::= SEQUENCE
{
    tmnxBsxIpIdAsstPDnsSrvAddrType   InetAddressType,
    tmnxBsxIpIdAsstPDnsSrvAddr       InetAddress,
    tmnxBsxIpIdAsstPDnsSrvRowStatus  RowStatus,
    tmnxBsxIpIdAsstPDnsSrvRowLastCh  TimeStamp,
    tmnxBsxIpIdAsstPDnsSrvComment    TNamedItemOrEmpty
}

tmnxBsxIpIdAsstPDnsSrvAddrType   OBJECT-TYPE
    SYNTAX      InetAddressType
    MAX-ACCESS  not-accessible
    STATUS      current
    DESCRIPTION
        "The value of tmnxBsxIpIdAsstPDnsSrvAddrType specifies the type of
         address contained in tmnxBsxIpIdAsstPDnsSrvAddr."
    ::= { tmnxBsxIpIdAsstPDnsSrvEntry 1 }

tmnxBsxIpIdAsstPDnsSrvAddr       OBJECT-TYPE
    SYNTAX      InetAddress (SIZE (4|16))
    MAX-ACCESS  not-accessible
    STATUS      current
    DESCRIPTION
        "The value of tmnxBsxIpIdAsstPDnsSrvAddr specifies the DNS server IP
         address."
    ::= { tmnxBsxIpIdAsstPDnsSrvEntry 2 }

tmnxBsxIpIdAsstPDnsSrvRowStatus  OBJECT-TYPE
    SYNTAX      RowStatus
    MAX-ACCESS  read-create
    STATUS      current
    DESCRIPTION
        "The value of tmnxBsxIpIdAsstPDnsSrvRowStatus specifies the row status.
         It allows entries to be created and deleted in the
         tmnxBsxIpIdAsstPDnsSrvTable.

         Rows are created by specifying the value of 'createAndGo (4)', and
         deleted by specifying the value of 'destroy (6)'."
    ::= { tmnxBsxIpIdAsstPDnsSrvEntry 3 }

tmnxBsxIpIdAsstPDnsSrvRowLastCh  OBJECT-TYPE
    SYNTAX      TimeStamp
    MAX-ACCESS  read-only
    STATUS      current
    DESCRIPTION
        "The value of tmnxBsxIpIdAsstPDnsSrvRowLastCh indicates the last time,
         since system startup, a successful SNMP set caused a value in this row
         to change."
    ::= { tmnxBsxIpIdAsstPDnsSrvEntry 4 }

tmnxBsxIpIdAsstPDnsSrvComment    OBJECT-TYPE
    SYNTAX      TNamedItemOrEmpty (SIZE (0..32))
    MAX-ACCESS  read-create
    STATUS      current
    DESCRIPTION
        "The value of tmnxBsxIpIdAsstPDnsSrvComment specifies a comment such as
         a name or description associated with this trusted DNS server IP
         address."
    DEFVAL      { "" }
    ::= { tmnxBsxIpIdAsstPDnsSrvEntry 5 }

tmnxBsxChrgFltrObjs              OBJECT IDENTIFIER ::= { tmnxBsxPolicyObjs 39 }

tmnxBsxChrgFltrTable             OBJECT-TYPE
    SYNTAX      SEQUENCE OF TmnxBsxChrgFltrEntry
    MAX-ACCESS  not-accessible
    STATUS      current
    DESCRIPTION
        "The tmnxBsxChrgFltrTable contains an entry for each set of match
         criteria defining the charging-group assignment to an application
         assurance session."
    ::= { tmnxBsxChrgFltrObjs 1 }

tmnxBsxChrgFltrEntry             OBJECT-TYPE
    SYNTAX      TmnxBsxChrgFltrEntry
    MAX-ACCESS  not-accessible
    STATUS      current
    DESCRIPTION
        "Each tmnxBsxChrgFltrEntry indicates a set of match criteria and
         corresponding charging-group assignment to an application assurance
         session. Entries are traversed in order and the first matching
         criteria entry is taken."
    INDEX       {
        tmnxBsxChrgFltrPolicyVersion,
        tmnxBsxAaGrpPartIndex,
        tmnxBsxChrgFltrEntryId
    }
    ::= { tmnxBsxChrgFltrTable 1 }

TmnxBsxChrgFltrEntry             ::= SEQUENCE
{
    tmnxBsxChrgFltrPolicyVersion     TmnxBsxPolicyVersion,
    tmnxBsxChrgFltrEntryId           TEntryId,
    tmnxBsxChrgFltrRowStatus         RowStatus,
    tmnxBsxChrgFltrRowLastChange     TimeStamp,
    tmnxBsxChrgFltrDescription       TItemDescription,
    tmnxBsxChrgFltrAdminState        TmnxAdminState,
    tmnxBsxChrgFltrMatchApplication  TNamedItemOrEmpty,
    tmnxBsxChrgFltrMatchApplOp       TmnxBsxOperator,
    tmnxBsxChrgFltrMatchAppGroup     TNamedItemOrEmpty,
    tmnxBsxChrgFltrMatchAppGroupOp   TmnxBsxOperator,
    tmnxBsxChrgFltrMatchTetherState  TruthValue,
    tmnxBsxChrgFltrChargingGroup     TNamedItemOrEmpty
}

tmnxBsxChrgFltrPolicyVersion     OBJECT-TYPE
    SYNTAX      TmnxBsxPolicyVersion
    MAX-ACCESS  not-accessible
    STATUS      current
    DESCRIPTION
        "The value of tmnxBsxChrgFltrPolicyVersion indicates the version of the
         table being accessed.  The row is read-create only for the 'admin' version of
         the table.  The 'oper' version is read-only."
    ::= { tmnxBsxChrgFltrEntry 1 }

tmnxBsxChrgFltrEntryId           OBJECT-TYPE
    SYNTAX      TEntryId
    MAX-ACCESS  not-accessible
    STATUS      current
    DESCRIPTION
        "The value of tmnxBsxChrgFltrEntryId specifies the index into the
         charging filter table corresponding to match criteria and
         charging-group to apply to the session."
    ::= { tmnxBsxChrgFltrEntry 2 }

tmnxBsxChrgFltrRowStatus         OBJECT-TYPE
    SYNTAX      RowStatus
    MAX-ACCESS  read-create
    STATUS      current
    DESCRIPTION
        "The value of tmnxBsxChrgFltrRowStatus specifies the row status. It
         allows entries to be created and deleted in the tmnxBsxChrgFltrTable."
    ::= { tmnxBsxChrgFltrEntry 3 }

tmnxBsxChrgFltrRowLastChange     OBJECT-TYPE
    SYNTAX      TimeStamp
    MAX-ACCESS  read-only
    STATUS      current
    DESCRIPTION
        "The value of tmnxBsxChrgFltrRowLastChange indicates the last time,
         since system startup, a successful set was performed on this row."
    ::= { tmnxBsxChrgFltrEntry 4 }

tmnxBsxChrgFltrDescription       OBJECT-TYPE
    SYNTAX      TItemDescription
    MAX-ACCESS  read-create
    STATUS      current
    DESCRIPTION
        "The value of tmnxBsxChrgFltrDescription specifies the description of
         the charging group entry."
    DEFVAL      { "" }
    ::= { tmnxBsxChrgFltrEntry 5 }

tmnxBsxChrgFltrAdminState        OBJECT-TYPE
    SYNTAX      TmnxAdminState
    MAX-ACCESS  read-create
    STATUS      current
    DESCRIPTION
        "The value of tmnxBsxChrgFltrAdminState specifies the administrative state
         for the entry.  When 'outOfService', any match entries referring to this
         entry are skipped."
    DEFVAL      { outOfService }
    ::= { tmnxBsxChrgFltrEntry 6 }

tmnxBsxChrgFltrMatchApplication  OBJECT-TYPE
    SYNTAX      TNamedItemOrEmpty
    MAX-ACCESS  read-create
    STATUS      current
    DESCRIPTION
        "The value of tmnxBsxChrgFltrMatchApplication specifies the particular
         application to match against to resolve the charging-group to apply to
         the session. If set to an empty string, no match on application is
         done.

         If an attempt is made to set this object to a string that does not
         match a tmnxBsxAppName value from the tmnxBsxAppCfgTable, an
         'inconsistentValue' error is returned."
    DEFVAL      { "" }
    ::= { tmnxBsxChrgFltrEntry 7 }

tmnxBsxChrgFltrMatchApplOp       OBJECT-TYPE
    SYNTAX      TmnxBsxOperator
    MAX-ACCESS  read-create
    STATUS      current
    DESCRIPTION
        "The value of tmnxBsxChrgFltrMatchApplOp specifies the operator to
         apply in relation to tmnxBsxChrgFltrMatchApplication to match against
         to resolve the charging-group to apply to the session."
    DEFVAL      { none }
    ::= { tmnxBsxChrgFltrEntry 8 }

tmnxBsxChrgFltrMatchAppGroup     OBJECT-TYPE
    SYNTAX      TNamedItemOrEmpty
    MAX-ACCESS  read-create
    STATUS      current
    DESCRIPTION
        "The value of tmnxBsxChrgFltrMatchAppGroup specifies the particular
         application group to match against to resolve the charging-group to
         apply to the session. If set to an empty string, no match on
         application group is done.

         If an attempt is made to set this object to a string that does not
         match a tmnxBsxAppGrpName value from the tmnxBsxAppGrpCfgTable, an
         'inconsistentValue' error is returned."
    DEFVAL      { "" }
    ::= { tmnxBsxChrgFltrEntry 9 }

tmnxBsxChrgFltrMatchAppGroupOp   OBJECT-TYPE
    SYNTAX      TmnxBsxOperator
    MAX-ACCESS  read-create
    STATUS      current
    DESCRIPTION
        "The value of tmnxBsxChrgFltrMatchAppGroupOp specifies the operator to
         apply in relation to tmnxBsxChrgFltrMatchAppGroup to match against to
         resolve the charging-group to apply to the session."
    DEFVAL      { none }
    ::= { tmnxBsxChrgFltrEntry 10 }

tmnxBsxChrgFltrMatchTetherState  OBJECT-TYPE
    SYNTAX      TruthValue
    MAX-ACCESS  read-create
    STATUS      current
    DESCRIPTION
        "The value of tmnxBsxChrgFltrMatchTetherState specifies that matching a
         tethered application assurance session is enabled in resolving the
         charging-group to apply to the session."
    DEFVAL      { false }
    ::= { tmnxBsxChrgFltrEntry 11 }

tmnxBsxChrgFltrChargingGroup     OBJECT-TYPE
    SYNTAX      TNamedItemOrEmpty
    MAX-ACCESS  read-create
    STATUS      current
    DESCRIPTION
        "The value of tmnxBsxChrgFltrChargingGroup specifies the charging group
         (tmnxBsxChargeGrpName) that will be applied to the session.

         If an attempt is made to set this object to a non-empty string that
         does not match a tmnxBsxChargeGrpName value from the
         tmnxBsxChargeGrpCfgTable, an 'inconsistentValue' error is returned."
    DEFVAL      { "" }
    ::= { tmnxBsxChrgFltrEntry 12 }

tmnxBsxChrgFltrFlowAttrTable     OBJECT-TYPE
    SYNTAX      SEQUENCE OF TmnxBsxChrgFltrFlowAttrEntry
    MAX-ACCESS  not-accessible
    STATUS      current
    DESCRIPTION
        "The tmnxBsxChrgFltrFlowAttrTable contains the flow attribute matches
         for the charging filter table."
    ::= { tmnxBsxChrgFltrObjs 2 }

tmnxBsxChrgFltrFlowAttrEntry     OBJECT-TYPE
    SYNTAX      TmnxBsxChrgFltrFlowAttrEntry
    MAX-ACCESS  not-accessible
    STATUS      current
    DESCRIPTION
        "Each tmnxBsxChrgFltrFlowAttrEntry specifies a match criterion for the
         charging filter specified by the second and third indices
         tmnxBsxAaGrpPartIndex, and tmnxBsxChrgFltrEntryId. The
         tmnxBsxChrgFltrFlowAttr index uniquely specifies the flow attribute.

         Rows can only be created and destroyed by specifying the
         tmnxBsxChrgFltrFlowAttrRowStatus if the first index,
         tmnxBsxChrgFltrPolicyVersion, is set to 'admin'."
    INDEX       {
        tmnxBsxChrgFltrPolicyVersion,
        tmnxBsxAaGrpPartIndex,
        tmnxBsxChrgFltrEntryId,
        IMPLIED tmnxBsxChrgFltrFlowAttr
    }
    ::= { tmnxBsxChrgFltrFlowAttrTable 1 }

TmnxBsxChrgFltrFlowAttrEntry     ::= SEQUENCE
{
    tmnxBsxChrgFltrFlowAttr          TNamedItem,
    tmnxBsxChrgFltrFlowAttrRowStatus RowStatus,
    tmnxBsxChrgFltrFlowAttrRowLstChg TimeStamp,
    tmnxBsxChrgFltrFlowAttrConf      Unsigned32,
    tmnxBsxChrgFltrFlowAttrOp        TmnxBsxOperator
}

tmnxBsxChrgFltrFlowAttr          OBJECT-TYPE
    SYNTAX      TNamedItem
    MAX-ACCESS  not-accessible
    STATUS      current
    DESCRIPTION
        "The value of tmnxBsxChrgFltrFlowAttr specifies the flow attribute(s)
         to match against to resolve the charging-group to apply to the
         session."
    ::= { tmnxBsxChrgFltrFlowAttrEntry 1 }

tmnxBsxChrgFltrFlowAttrRowStatus OBJECT-TYPE
    SYNTAX      RowStatus
    MAX-ACCESS  read-create
    STATUS      current
    DESCRIPTION
        "The value of tmnxBsxChrgFltrFlowAttrRowStatus specifies the row status.  It allows entries to be created
         and deleted in the tmnxBsxChrgFltrFlowAttrTable.

         Rows are created by specifying the value of 'createAndGo (4)', and
         deleted by specifying the value of 'destroy (6)'."
    ::= { tmnxBsxChrgFltrFlowAttrEntry 2 }

tmnxBsxChrgFltrFlowAttrRowLstChg OBJECT-TYPE
    SYNTAX      TimeStamp
    MAX-ACCESS  read-only
    STATUS      current
    DESCRIPTION
        "The value of tmnxBsxChrgFltrFlowAttrRowLstChg indicates the last time,
         since system startup, a successful set was performed on this row."
    ::= { tmnxBsxChrgFltrFlowAttrEntry 3 }

tmnxBsxChrgFltrFlowAttrConf      OBJECT-TYPE
    SYNTAX      Unsigned32 (0..100)
    MAX-ACCESS  read-create
    STATUS      current
    DESCRIPTION
        "The value of tmnxBsxChrgFltrFlowAttrConf specifies the confidence of a
         flow attribute to match against to resolve the charging-group to apply
         to the session."
    DEFVAL      { 0 }
    ::= { tmnxBsxChrgFltrFlowAttrEntry 4 }

tmnxBsxChrgFltrFlowAttrOp        OBJECT-TYPE
    SYNTAX      TmnxBsxOperator
    MAX-ACCESS  read-create
    STATUS      current
    DESCRIPTION
        "The value of tmnxBsxChrgFltrFlowAttrOp specifies the comparison
         operator applied to the corresponding row in the
         tmnxBsxChrgFltrFlowAttrTable."
    DEFVAL      { none }
    ::= { tmnxBsxChrgFltrFlowAttrEntry 5 }

tmnxBsxChrgFltrStatsTable        OBJECT-TYPE
    SYNTAX      SEQUENCE OF TmnxBsxChrgFltrStatsEntry
    MAX-ACCESS  not-accessible
    STATUS      current
    DESCRIPTION
        "The tmnxBsxChrgFltrStatsTable contains the charging filter statistics."
    ::= { tmnxBsxChrgFltrObjs 3 }

tmnxBsxChrgFltrStatsEntry        OBJECT-TYPE
    SYNTAX      TmnxBsxChrgFltrStatsEntry
    MAX-ACCESS  not-accessible
    STATUS      current
    DESCRIPTION
        "Each tmnxBsxChrgFltrStatsEntry indicates statistics available to
         collect for each charging filter entry."
    INDEX       {
        tmnxBsxAaGrpPartIndex,
        tmnxBsxChrgFltrEntryId
    }
    ::= { tmnxBsxChrgFltrStatsTable 1 }

TmnxBsxChrgFltrStatsEntry        ::= SEQUENCE
{ tmnxBsxChrgFltrStatsHitCntFlows  Counter64 }

tmnxBsxChrgFltrStatsHitCntFlows  OBJECT-TYPE
    SYNTAX      Counter64
    MAX-ACCESS  read-only
    STATUS      current
    DESCRIPTION
        "The value of tmnxBsxChrgFltrStatsHitCntFlows indicates the number of
         flows that have hit this entry.

         In certain cases, a flow may change its attributes thus undergoing a
         charging group reevaluation. In these cases, the flow may be counted
         against multiple different charging filter entries."
    ::= { tmnxBsxChrgFltrStatsEntry 1 }

tmnxBsxStatsObjs                 OBJECT IDENTIFIER ::= { tmnxBsxObjs 3 }

tmnxBsxStatsAccounting           OBJECT IDENTIFIER ::= { tmnxBsxStatsObjs 1 }

tmnxBsxStatAaAcctLastChTime      OBJECT-TYPE
    SYNTAX      TimeStamp
    MAX-ACCESS  read-only
    STATUS      current
    DESCRIPTION
        "The value of tmnxBsxStatAaAcctLastChTime indicates the last time a
         successful set was performed on any row of the
         tmnxBsxStatAaAcctCfgTable."
    ::= { tmnxBsxStatsAccounting 1 }

tmnxBsxStatAaSubLastChTime       OBJECT-TYPE
    SYNTAX      TimeStamp
    MAX-ACCESS  read-only
    STATUS      current
    DESCRIPTION
        "The value of tmnxBsxStatAaSubLastChTime indicates the last time a
         successful set was performed on any row of the
         tmnxBsxStatAaSubCfgTable."
    ::= { tmnxBsxStatsAccounting 2 }

tmnxBsxStatAaSubSdyLastChTime    OBJECT-TYPE
    SYNTAX      TimeStamp
    MAX-ACCESS  read-only
    STATUS      current
    DESCRIPTION
        "The value of tmnxBsxStatAaSubSdyLastChTime indicates the last time a
         successful set was performed on any row of the
         tmnxBsxStatAaSubSdyCfgTable."
    ::= { tmnxBsxStatsAccounting 3 }

tmnxBsxStatIsaAaCfgLastChTime    OBJECT-TYPE
    SYNTAX      TimeStamp
    MAX-ACCESS  read-only
    STATUS      current
    DESCRIPTION
        "The value of tmnxBsxStatIsaAaCfgLastChTime indicates the last time a
         successful set was performed on any row of the
         tmnxBsxStatIsaAaCfgTable."
    ::= { tmnxBsxStatsAccounting 4 }

tmnxBsxPartAcctCfgLastChTime     OBJECT-TYPE
    SYNTAX      TimeStamp
    MAX-ACCESS  read-only
    STATUS      current
    DESCRIPTION
        "The value of tmnxBsxPartAcctCfgLastChTime indicates the last time a
         successful set was performed on any row of the
         tmnxBsxPartAcctCfgTable."
    ::= { tmnxBsxStatsAccounting 5 }

tmnxBsxStatTcaCfgTableLastCh     OBJECT-TYPE
    SYNTAX      TimeStamp
    MAX-ACCESS  read-only
    STATUS      current
    DESCRIPTION
        "The value of tmnxBsxStatTcaCfgTableLastCh indicates the last time,
         since system startup, a successful SNMP set on any row of
         tmnxBsxStatTcaCfgTable caused a value to change."
    ::= { tmnxBsxStatsAccounting 6 }

tmnxBsxStatTcaPolcrCfgTableLstCh OBJECT-TYPE
    SYNTAX      TimeStamp
    MAX-ACCESS  read-only
    STATUS      current
    DESCRIPTION
        "The value of tmnxBsxStatTcaPolcrCfgTableLstCh indicates the last time,
         since system startup, a successful SNMP set on any row of
         tmnxBsxStatTcaPolcrCfgTable caused a value to change."
    ::= { tmnxBsxStatsAccounting 7 }

tmnxBsxStatTcaFtrCfgTableLastCh  OBJECT-TYPE
    SYNTAX      TimeStamp
    MAX-ACCESS  read-only
    STATUS      current
    DESCRIPTION
        "The value of tmnxBsxStatTcaFtrCfgTableLastCh indicates the last time,
         since system startup, a successful SNMP set on any row of
         tmnxBsxStatTcaFtrCfgTable caused a value to change."
    ::= { tmnxBsxStatsAccounting 8 }

tmnxBsxStatTcaFtrEnCfgTableLstCh OBJECT-TYPE
    SYNTAX      TimeStamp
    MAX-ACCESS  read-only
    STATUS      current
    DESCRIPTION
        "The value of tmnxBsxStatTcaFtrEnCfgTableLstCh indicates the last time,
         since system startup, a successful SNMP set on any row of
         tmnxBsxStatTcaFtrEnCfgTable caused a value to change."
    ::= { tmnxBsxStatsAccounting 9 }

tmnxBsxAdmitDenyAcctTableLastCh  OBJECT-TYPE
    SYNTAX      TimeStamp
    MAX-ACCESS  read-only
    STATUS      current
    DESCRIPTION
        "The value of tmnxBsxAdmitDenyAcctTableLastCh indicates the last time,
         since system startup, a successful SNMP set on any row of
         tmnxBsxAdmitDenyAcctTable caused a value to change."
    ::= { tmnxBsxStatsAccounting 10 }

tmnxBsxStatAaAcctCfgTable        OBJECT-TYPE
    SYNTAX      SEQUENCE OF TmnxBsxStatAaAcctCfgEntry
    MAX-ACCESS  not-accessible
    STATUS      current
    DESCRIPTION
        "The tmnxBsxStatAaAcctCfgTable contains an entry for each ISA-AA Group,
         Partition and Statistics type in the system. Each row contains the
         accounting policy and statistics configuration for ISA-AA
         application-groups, applications, protocols for system wide,
         per-subscriber and per-special study subscribers."
    ::= { tmnxBsxStatsObjs 2 }

tmnxBsxStatAaAcctCfgEntry        OBJECT-TYPE
    SYNTAX      TmnxBsxStatAaAcctCfgEntry
    MAX-ACCESS  not-accessible
    STATUS      current
    DESCRIPTION
        "Each tmnxBsxStatAaAcctCfgEntry indicates the ISA-AA statistics that
         are configured per ISA-AA group, partition and statistics type."
    INDEX       {
        tmnxBsxAaGrpPartIndex,
        tmnxBsxStatAaAcctCfgType
    }
    ::= { tmnxBsxStatAaAcctCfgTable 1 }

TmnxBsxStatAaAcctCfgEntry        ::= SEQUENCE
{
    tmnxBsxStatAaAcctCfgType         TmnxBsxStatAaAcctCfgType,
    tmnxBsxStatAaAcctCfgCollStats    TruthValue,
    tmnxBsxStatAaAcctCfgPolicy       Unsigned32,
    tmnxBsxStatAaAcctCfgAggrStats    TruthValue,
    tmnxBsxStatAaAcctCfgAdminState   TmnxAdminState,
    tmnxBsxStatAaAcctCfgMaxThruStats TruthValue,
    tmnxBsxStatAaAcctCfgRadiusPlcy   TNamedItemOrEmpty,
    tmnxBsxStatAaAcctCfgExTcpRetrans TruthValue,
    tmnxBsxStatAaAcctCfgRowLastCh    TimeStamp,
    tmnxBsxStatAaAcctCfgUMStats      TmnxEnabledDisabled,
    tmnxBsxStatAaAcctCfgAggrExpMeth  TmnxBsxAaStatExportMethod
}

tmnxBsxStatAaAcctCfgType         OBJECT-TYPE
    SYNTAX      TmnxBsxStatAaAcctCfgType
    MAX-ACCESS  not-accessible
    STATUS      current
    DESCRIPTION
        "The value of tmnxBsxStatAaAcctCfgType specifies the accounting
         configurable type for the row."
    ::= { tmnxBsxStatAaAcctCfgEntry 1 }

tmnxBsxStatAaAcctCfgCollStats    OBJECT-TYPE
    SYNTAX      TruthValue
    MAX-ACCESS  read-write
    STATUS      current
    DESCRIPTION
        "The value of tmnxBsxStatAaAcctCfgCollStats specifies that statistics
         collection is enabled."
    DEFVAL      { false }
    ::= { tmnxBsxStatAaAcctCfgEntry 2 }

tmnxBsxStatAaAcctCfgPolicy       OBJECT-TYPE
    SYNTAX      Unsigned32 (0..99)
    MAX-ACCESS  read-write
    STATUS      current
    DESCRIPTION
        "The value of tmnxBsxStatAaAcctCfgPolicy specifies the accounting
         policy to use. The value 0 is used to disable the accounting policy."
    DEFVAL      { 0 }
    ::= { tmnxBsxStatAaAcctCfgEntry 3 }

tmnxBsxStatAaAcctCfgAggrStats    OBJECT-TYPE
    SYNTAX      TruthValue
    MAX-ACCESS  read-write
    STATUS      obsolete
    DESCRIPTION
        "The value of tmnxBsxStatAaAcctCfgAggrStats specifies whether aggregate
         statistics collection is enabled.

         tmnxBsxStatAaAcctCfgAggrStats can only be modified when
         tmnxBsxStatAaAcctCfgType of the corresponding row is equal to 'aa-sub
         (4)'.

         tmnxBsxStatAaAcctCfgAggrStats was replaced by
         tmnxBsxStatAaAcctCfgAggrExpMeth as of release 13.0R1"
    DEFVAL      { false }
    ::= { tmnxBsxStatAaAcctCfgEntry 4 }

tmnxBsxStatAaAcctCfgAdminState   OBJECT-TYPE
    SYNTAX      TmnxAdminState
    MAX-ACCESS  read-write
    STATUS      current
    DESCRIPTION
        "The value of tmnxBsxStatAaAcctCfgAdminState specifies from an
         administrative perspective whether the statistics are actually
         collected for the corresponding tmnxBsxStatAaAcctCfgType. An
         administrative state of 'outOfService(3)' indicates statistics will
         not be collected even if tmnxBsxStatAaAcctCfgCollStats is enabled.

         tmnxBsxStatAaAcctCfgAdminState can only be modified for the
         tmnxBsxStatAaAcctCfgType of 'protocol(1)'. The default value of
         tmnxBsxStatAaAcctCfgAdminState is 'outOfService(3)' when
         tmnxBsxStatAaAcctCfgType is 'protocol(1)'."
    DEFVAL      { inService }
    ::= { tmnxBsxStatAaAcctCfgEntry 5 }

tmnxBsxStatAaAcctCfgMaxThruStats OBJECT-TYPE
    SYNTAX      TruthValue
    MAX-ACCESS  read-write
    STATUS      current
    DESCRIPTION
        "The value of tmnxBsxStatAaAcctCfgMaxThruStats specifies whether or not
         maximum throughput statistics collection is enabled.

         tmnxBsxStatAaAcctCfgMaxThruStats can only be modified when
         tmnxBsxStatAaAcctCfgType of the corresponding row is equal to
         'aa-sub(4)'."
    DEFVAL      { false }
    ::= { tmnxBsxStatAaAcctCfgEntry 6 }

tmnxBsxStatAaAcctCfgRadiusPlcy   OBJECT-TYPE
    SYNTAX      TNamedItemOrEmpty
    MAX-ACCESS  read-write
    STATUS      current
    DESCRIPTION
        "The value of tmnxBsxStatAaAcctCfgRadiusPlcy specifies the RADIUS
         accounting policy to use.

         The accounting policy must be an existing row within the
         tmnxBsxRadApTable specified by the index tmnxBsxRadApName.

         tmnxBsxStatAaAcctCfgRadiusPlcy can only be modified when
         tmnxBsxStatAaAcctCfgType of the corresponding row is equal to
         'aa-sub(4)'."
    DEFVAL      { "" }
    ::= { tmnxBsxStatAaAcctCfgEntry 7 }

tmnxBsxStatAaAcctCfgExTcpRetrans OBJECT-TYPE
    SYNTAX      TruthValue
    MAX-ACCESS  read-write
    STATUS      current
    DESCRIPTION
        "The value of tmnxBsxStatAaAcctCfgExTcpRetrans specifies whether or not
         TCP retransmission packets are excluded from being counted by the AA
         ISA for content based billing.

         tmnxBsxStatAaAcctCfgExTcpRetrans can only be modified when
         tmnxBsxStatAaAcctCfgType of the corresponding row is equal to
         'aa-sub(4)' and when the corresponding ISA AA group has a
         tmnxBsxIsaAaGrpAaSubScale equal to 'mobileGateway(2)'."
    DEFVAL      { false }
    ::= { tmnxBsxStatAaAcctCfgEntry 8 }

tmnxBsxStatAaAcctCfgRowLastCh    OBJECT-TYPE
    SYNTAX      TimeStamp
    MAX-ACCESS  read-only
    STATUS      current
    DESCRIPTION
        "The value of tmnxBsxStatAaAcctCfgRowLastCh indicates the last time,
         since system startup, a successful set was performed on this row."
    ::= { tmnxBsxStatAaAcctCfgEntry 9 }

tmnxBsxStatAaAcctCfgUMStats      OBJECT-TYPE
    SYNTAX      TmnxEnabledDisabled
    MAX-ACCESS  read-write
    STATUS      current
    DESCRIPTION
        "The value of tmnxBsxStatAaAcctCfgUMStats specifies whether or not
         usage monitoring statistics collection is enabled.

         tmnxBsxStatAaAcctCfgUMStats can only be modified when
         tmnxBsxStatAaAcctCfgType of the corresponding row is equal to
         'aa-sub(4)'."
    DEFVAL      { disabled }
    ::= { tmnxBsxStatAaAcctCfgEntry 10 }

tmnxBsxStatAaAcctCfgAggrExpMeth  OBJECT-TYPE
    SYNTAX      TmnxBsxAaStatExportMethod
    MAX-ACCESS  read-write
    STATUS      current
    DESCRIPTION
        "The value of tmnxBsxStatAaAcctCfgAggrExpMeth specifies the method used
         to export aggregate statistics.

         tmnxBsxStatAaAcctCfgAggrExpMeth can only be modified when
         tmnxBsxStatAaAcctCfgType of the corresponding row is equal to
         'aa-sub(4)'."
    DEFVAL      { {} }
    ::= { tmnxBsxStatAaAcctCfgEntry 11 }

tmnxBsxStatAaSubTable            OBJECT-TYPE
    SYNTAX      SEQUENCE OF TmnxBsxStatAaSubEntry
    MAX-ACCESS  not-accessible
    STATUS      current
    DESCRIPTION
        "The tmnxBsxStatAaSubTable contains an entry for each
         application-assurance subscriber for each statistics type within a
         group, partition and statistics interval. Each row contains the
         application assurance per-subscriber statistics collected for the
         subscriber. A subscriber is uniquely identified by a
         tmnxBsxAaSubscriberType and tmnxBsxAaSubscriber."
    ::= { tmnxBsxStatsObjs 3 }

tmnxBsxStatAaSubEntry            OBJECT-TYPE
    SYNTAX      TmnxBsxStatAaSubEntry
    MAX-ACCESS  not-accessible
    STATUS      current
    DESCRIPTION
        "Each tmnxBsxStatAaSubEntry contains the application assurance
         per-subscriber statistics for a combination of group, partition,
         statistics interval, subscriber, statistics type, and statistics name."
    INDEX       {
        tmnxBsxAaGrpPartIndex,
        tmnxBsxAaSubStatsInterval,
        tmnxBsxAaSubscriberType,
        tmnxBsxAaSubscriber,
        tmnxBsxStatAaType,
        IMPLIED tmnxBsxStatAaName
    }
    ::= { tmnxBsxStatAaSubTable 1 }

TmnxBsxStatAaSubEntry            ::= SEQUENCE
{
    tmnxBsxAaSubscriberType          TmnxBsxAaSubscriberType,
    tmnxBsxAaSubscriber              TmnxBsxAaSubscriber,
    tmnxBsxStatAaType                TmnxBsxAaStatType,
    tmnxBsxStatAaName                TNamedItem,
    tmnxBsxStatAaSubDiscontTime      TimeStamp,
    tmnxBsxStatAaSubOctsAdmFmSb      Counter32,
    tmnxBsxStatAaSubPktsAdmFmSb      Counter32,
    tmnxBsxStatAaSubFlwsAdmFmSb      Counter32,
    tmnxBsxStatAaSubOctsDnyFmSb      Counter32,
    tmnxBsxStatAaSubPktsDnyFmSb      Counter32,
    tmnxBsxStatAaSubFlwsDnyFmSb      Counter32,
    tmnxBsxStatAaSubOctsAdmToSb      Counter32,
    tmnxBsxStatAaSubPktsAdmToSb      Counter32,
    tmnxBsxStatAaSubFlwsAdmToSb      Counter32,
    tmnxBsxStatAaSubOctsDnyToSb      Counter32,
    tmnxBsxStatAaSubPktsDnyToSb      Counter32,
    tmnxBsxStatAaSubFlwsDnyToSb      Counter32,
    tmnxBsxStatAaSubTermFlwDur       Counter32,
    tmnxBsxStatAaSubTermFlws         Counter32,
    tmnxBsxStatAaSubShrtDurFlws      Counter32,
    tmnxBsxStatAaSubMedDurFlws       Counter32,
    tmnxBsxStatAaSubLngDurFlws       Counter32,
    tmnxBsxStatAaSubActFlwsFmSb      Gauge32,
    tmnxBsxStatAaSubActFlwsToSb      Gauge32,
    tmnxBsxStatAaSubHCOctsAdmFmSb    Counter64,
    tmnxBsxStatAaSubHCPktsAdmFmSb    Counter64,
    tmnxBsxStatAaSubHCFlwsAdmFmSb    Counter64,
    tmnxBsxStatAaSubHCOctsDnyFmSb    Counter64,
    tmnxBsxStatAaSubHCPktsDnyFmSb    Counter64,
    tmnxBsxStatAaSubHCFlwsDnyFmSb    Counter64,
    tmnxBsxStatAaSubHCOctsAdmToSb    Counter64,
    tmnxBsxStatAaSubHCPktsAdmToSb    Counter64,
    tmnxBsxStatAaSubHCFlwsAdmToSb    Counter64,
    tmnxBsxStatAaSubHCOctsDnyToSb    Counter64,
    tmnxBsxStatAaSubHCPktsDnyToSb    Counter64,
    tmnxBsxStatAaSubHCFlwsDnyToSb    Counter64,
    tmnxBsxStatAaSubHCTermFlwDur     Counter64,
    tmnxBsxStatAaSubHCTermFlws       Counter64,
    tmnxBsxStatAaSubHCShrtDurFlws    Counter64,
    tmnxBsxStatAaSubHCMedDurFlws     Counter64,
    tmnxBsxStatAaSubHCLngDurFlws     Counter64
}

tmnxBsxAaSubscriberType          OBJECT-TYPE
    SYNTAX      TmnxBsxAaSubscriberType
    MAX-ACCESS  not-accessible
    STATUS      current
    DESCRIPTION
        "The value of tmnxBsxAaSubscriberType specifies the format of the
         Application Assurance Subscriber identifier."
    ::= { tmnxBsxStatAaSubEntry 1 }

tmnxBsxAaSubscriber              OBJECT-TYPE
    SYNTAX      TmnxBsxAaSubscriber
    MAX-ACCESS  not-accessible
    STATUS      current
    DESCRIPTION
        "The Application Assurance Subscriber identifier. The format of this
         object is determined by the value of the tmnxBsxAaSubscriberType."
    ::= { tmnxBsxStatAaSubEntry 2 }

tmnxBsxStatAaType                OBJECT-TYPE
    SYNTAX      TmnxBsxAaStatType
    MAX-ACCESS  not-accessible
    STATUS      current
    DESCRIPTION
        "The value of tmnxBsxStatAaType specifies the type of the Application
         Assurance subscriber statistic."
    ::= { tmnxBsxStatAaSubEntry 3 }

tmnxBsxStatAaName                OBJECT-TYPE
    SYNTAX      TNamedItem
    MAX-ACCESS  not-accessible
    STATUS      current
    DESCRIPTION
        "The value of tmnxBsxStatAaName specifies either the ISA-AA protocol,
         application or app-group name for which statistics are requested. The
         tmnxBsxStatAaType is used to determine the statistics type."
    ::= { tmnxBsxStatAaSubEntry 4 }

tmnxBsxStatAaSubDiscontTime      OBJECT-TYPE
    SYNTAX      TimeStamp
    MAX-ACCESS  read-only
    STATUS      current
    DESCRIPTION
        "The value of tmnxBsxStatAaSubDiscontTime indicates the
         SNMPv2-MIB::sysUpTime (centiseconds) when any of the active ISA-AA
         MDAs within the group have last changed status."
    ::= { tmnxBsxStatAaSubEntry 5 }

tmnxBsxStatAaSubOctsAdmFmSb      OBJECT-TYPE
    SYNTAX      Counter32
    UNITS       "bytes"
    MAX-ACCESS  read-only
    STATUS      current
    DESCRIPTION
        "The value of tmnxBsxStatAaSubOctsAdmFmSb indicates the total number of
         bytes permitted for the subscriber to network direction."
    ::= { tmnxBsxStatAaSubEntry 6 }

tmnxBsxStatAaSubPktsAdmFmSb      OBJECT-TYPE
    SYNTAX      Counter32
    UNITS       "packets"
    MAX-ACCESS  read-only
    STATUS      current
    DESCRIPTION
        "The value of tmnxBsxStatAaSubPktsAdmFmSb indicates the total number of
         packets permitted for the subscriber to network direction."
    ::= { tmnxBsxStatAaSubEntry 7 }

tmnxBsxStatAaSubFlwsAdmFmSb      OBJECT-TYPE
    SYNTAX      Counter32
    UNITS       "flows"
    MAX-ACCESS  read-only
    STATUS      current
    DESCRIPTION
        "The value of tmnxBsxStatAaSubFlwsAdmFmSb indicates the total number of
         flows permitted for the subscriber to network direction."
    ::= { tmnxBsxStatAaSubEntry 8 }

tmnxBsxStatAaSubOctsDnyFmSb      OBJECT-TYPE
    SYNTAX      Counter32
    UNITS       "bytes"
    MAX-ACCESS  read-only
    STATUS      current
    DESCRIPTION
        "The value of tmnxBsxStatAaSubOctsDnyFmSb indicates the total number of
         bytes dropped for the subscriber to network direction."
    ::= { tmnxBsxStatAaSubEntry 9 }

tmnxBsxStatAaSubPktsDnyFmSb      OBJECT-TYPE
    SYNTAX      Counter32
    UNITS       "packets"
    MAX-ACCESS  read-only
    STATUS      current
    DESCRIPTION
        "The value of tmnxBsxStatAaSubPktsDnyFmSb indicates the total number of
         packets dropped for the subscriber to network direction."
    ::= { tmnxBsxStatAaSubEntry 10 }

tmnxBsxStatAaSubFlwsDnyFmSb      OBJECT-TYPE
    SYNTAX      Counter32
    UNITS       "flows"
    MAX-ACCESS  read-only
    STATUS      current
    DESCRIPTION
        "The value of tmnxBsxStatAaSubFlwsDnyFmSb indicates the total number of
         flows that dropped subsequent packets in the subscriber to network
         direction."
    ::= { tmnxBsxStatAaSubEntry 11 }

tmnxBsxStatAaSubOctsAdmToSb      OBJECT-TYPE
    SYNTAX      Counter32
    UNITS       "bytes"
    MAX-ACCESS  read-only
    STATUS      current
    DESCRIPTION
        "The value of tmnxBsxStatAaSubOctsAdmToSb indicates the total number of
         bytes permitted for the network to subscriber direction."
    ::= { tmnxBsxStatAaSubEntry 12 }

tmnxBsxStatAaSubPktsAdmToSb      OBJECT-TYPE
    SYNTAX      Counter32
    UNITS       "packets"
    MAX-ACCESS  read-only
    STATUS      current
    DESCRIPTION
        "The value of tmnxBsxStatAaSubPktsAdmToSb indicates the total number of
         packets permitted for the network to subscriber direction."
    ::= { tmnxBsxStatAaSubEntry 13 }

tmnxBsxStatAaSubFlwsAdmToSb      OBJECT-TYPE
    SYNTAX      Counter32
    UNITS       "flows"
    MAX-ACCESS  read-only
    STATUS      current
    DESCRIPTION
        "The value of tmnxBsxStatAaSubFlwsAdmToSb indicates the total number of
         flows permitted for the network to subscriber direction."
    ::= { tmnxBsxStatAaSubEntry 14 }

tmnxBsxStatAaSubOctsDnyToSb      OBJECT-TYPE
    SYNTAX      Counter32
    UNITS       "bytes"
    MAX-ACCESS  read-only
    STATUS      current
    DESCRIPTION
        "The value of tmnxBsxStatAaSubOctsDnyToSb indicates the total number of
         bytes dropped for the network to subscriber direction."
    ::= { tmnxBsxStatAaSubEntry 15 }

tmnxBsxStatAaSubPktsDnyToSb      OBJECT-TYPE
    SYNTAX      Counter32
    UNITS       "packets"
    MAX-ACCESS  read-only
    STATUS      current
    DESCRIPTION
        "The value of tmnxBsxStatAaSubPktsDnyToSb indicates the total number of
         packets dropped for the network to subscriber direction."
    ::= { tmnxBsxStatAaSubEntry 16 }

tmnxBsxStatAaSubFlwsDnyToSb      OBJECT-TYPE
    SYNTAX      Counter32
    UNITS       "flows"
    MAX-ACCESS  read-only
    STATUS      current
    DESCRIPTION
        "The value of tmnxBsxStatAaSubFlwsDnyToSb indicates the total number of
         flows that dropped subsequent packets in the network to subscriber
         direction."
    ::= { tmnxBsxStatAaSubEntry 17 }

tmnxBsxStatAaSubTermFlwDur       OBJECT-TYPE
    SYNTAX      Counter32
    UNITS       "seconds"
    MAX-ACCESS  read-only
    STATUS      current
    DESCRIPTION
        "The value of tmnxBsxStatAaSubTermFlwDur indicates the sum of all flow
         durations from first packet seen to last packet seen for flows that
         have terminated."
    ::= { tmnxBsxStatAaSubEntry 18 }

tmnxBsxStatAaSubTermFlws         OBJECT-TYPE
    SYNTAX      Counter32
    UNITS       "flows"
    MAX-ACCESS  read-only
    STATUS      current
    DESCRIPTION
        "The value of tmnxBsxStatAaSubTermFlws indicates the total number of
         allowed flows that have terminated."
    ::= { tmnxBsxStatAaSubEntry 19 }

tmnxBsxStatAaSubShrtDurFlws      OBJECT-TYPE
    SYNTAX      Counter32
    UNITS       "flows"
    MAX-ACCESS  read-only
    STATUS      current
    DESCRIPTION
        "The value of tmnxBsxStatAaSubShrtDurFlws indicates the total number of
         flows with a duration less than or equal to 30 seconds, that have
         completed."
    ::= { tmnxBsxStatAaSubEntry 20 }

tmnxBsxStatAaSubMedDurFlws       OBJECT-TYPE
    SYNTAX      Counter32
    UNITS       "flows"
    MAX-ACCESS  read-only
    STATUS      current
    DESCRIPTION
        "The value of tmnxBsxStatAaSubMedDurFlws indicates the total number of
         flows with a duration less than or equal to 180 seconds, but greater
         than 30 seconds, that have completed."
    ::= { tmnxBsxStatAaSubEntry 21 }

tmnxBsxStatAaSubLngDurFlws       OBJECT-TYPE
    SYNTAX      Counter32
    UNITS       "flows"
    MAX-ACCESS  read-only
    STATUS      current
    DESCRIPTION
        "The value of tmnxBsxStatAaSubLngDurFlws indicates the total number of
         flows with a duration greater than 180 seconds, that have completed."
    ::= { tmnxBsxStatAaSubEntry 22 }

tmnxBsxStatAaSubActFlwsFmSb      OBJECT-TYPE
    SYNTAX      Gauge32
    UNITS       "flows"
    MAX-ACCESS  read-only
    STATUS      current
    DESCRIPTION
        "The value of tmnxBsxStatAaSubActFlwsFmSb indicates the number of
         allowed flows in the subscriber to network direction that are active."
    ::= { tmnxBsxStatAaSubEntry 23 }

tmnxBsxStatAaSubActFlwsToSb      OBJECT-TYPE
    SYNTAX      Gauge32
    UNITS       "flows"
    MAX-ACCESS  read-only
    STATUS      current
    DESCRIPTION
        "The value of tmnxBsxStatAaSubActFlwsToSb indicates the number of
         allowed flows in the network to subscriber direction that are active."
    ::= { tmnxBsxStatAaSubEntry 24 }

tmnxBsxStatAaSubHCOctsAdmFmSb    OBJECT-TYPE
    SYNTAX      Counter64
    UNITS       "bytes"
    MAX-ACCESS  read-only
    STATUS      current
    DESCRIPTION
        "The value of tmnxBsxStatAaSubHCOctsAdmFmSb indicates the total number
         of bytes permitted for the subscriber to network direction. This
         object is a 64-bit version of tmnxBsxStatAaSubOctsAdmFmSb."
    ::= { tmnxBsxStatAaSubEntry 25 }

tmnxBsxStatAaSubHCPktsAdmFmSb    OBJECT-TYPE
    SYNTAX      Counter64
    UNITS       "packets"
    MAX-ACCESS  read-only
    STATUS      current
    DESCRIPTION
        "The value of tmnxBsxStatAaSubHCPktsAdmFmSb indicates the total number
         of packets permitted for the subscriber to network direction. This
         object is a 64-bit version of tmnxBsxStatAaSubPktsAdmFmSb."
    ::= { tmnxBsxStatAaSubEntry 26 }

tmnxBsxStatAaSubHCFlwsAdmFmSb    OBJECT-TYPE
    SYNTAX      Counter64
    UNITS       "flows"
    MAX-ACCESS  read-only
    STATUS      current
    DESCRIPTION
        "The value of tmnxBsxStatAaSubHCFlwsAdmFmSb indicates the total number
         of flows permitted for the subscriber to network direction. This
         object is a 64-bit version of tmnxBsxStatAaSubFlwsAdmFmSb."
    ::= { tmnxBsxStatAaSubEntry 27 }

tmnxBsxStatAaSubHCOctsDnyFmSb    OBJECT-TYPE
    SYNTAX      Counter64
    UNITS       "bytes"
    MAX-ACCESS  read-only
    STATUS      current
    DESCRIPTION
        "The value of tmnxBsxStatAaSubHCOctsDnyFmSb indicates the total number
         of bytes dropped for the subscriber to network direction. This object
         is a 64-bit version of tmnxBsxStatAaSubOctsDnyFmSb."
    ::= { tmnxBsxStatAaSubEntry 28 }

tmnxBsxStatAaSubHCPktsDnyFmSb    OBJECT-TYPE
    SYNTAX      Counter64
    UNITS       "packets"
    MAX-ACCESS  read-only
    STATUS      current
    DESCRIPTION
        "The value of tmnxBsxStatAaSubHCPktsDnyFmSb indicates the total number
         of packets dropped for the subscriber to network direction. This
         object is a 64-bit version of tmnxBsxStatAaSubPktsDnyFmSb."
    ::= { tmnxBsxStatAaSubEntry 29 }

tmnxBsxStatAaSubHCFlwsDnyFmSb    OBJECT-TYPE
    SYNTAX      Counter64
    UNITS       "flows"
    MAX-ACCESS  read-only
    STATUS      current
    DESCRIPTION
        "The value of tmnxBsxStatAaSubHCFlwsDnyFmSb indicates the total number
         of flows that dropped subsequent packets in the subscriber to network
         direction. This object is a 64-bit version of
         tmnxBsxStatAaSubFlwsDnyFmSb."
    ::= { tmnxBsxStatAaSubEntry 30 }

tmnxBsxStatAaSubHCOctsAdmToSb    OBJECT-TYPE
    SYNTAX      Counter64
    UNITS       "bytes"
    MAX-ACCESS  read-only
    STATUS      current
    DESCRIPTION
        "The value of tmnxBsxStatAaSubHCOctsAdmToSb indicates the total number
         of bytes permitted for the network to subscriber direction. This
         object is a 64-bit version of tmnxBsxStatAaSubOctsAdmToSb."
    ::= { tmnxBsxStatAaSubEntry 31 }

tmnxBsxStatAaSubHCPktsAdmToSb    OBJECT-TYPE
    SYNTAX      Counter64
    UNITS       "packets"
    MAX-ACCESS  read-only
    STATUS      current
    DESCRIPTION
        "The value of tmnxBsxStatAaSubHCPktsAdmToSb indicates the total number
         of packets permitted for the network to subscriber direction. This
         object is a 64-bit version of tmnxBsxStatAaSubPktsAdmToSb."
    ::= { tmnxBsxStatAaSubEntry 32 }

tmnxBsxStatAaSubHCFlwsAdmToSb    OBJECT-TYPE
    SYNTAX      Counter64
    UNITS       "flows"
    MAX-ACCESS  read-only
    STATUS      current
    DESCRIPTION
        "The value of tmnxBsxStatAaSubHCFlwsAdmToSb indicates the total number
         of flows permitted for the network to subscriber direction. This
         object is a 64-bit version of tmnxBsxStatAaSubFlwsAdmToSb."
    ::= { tmnxBsxStatAaSubEntry 33 }

tmnxBsxStatAaSubHCOctsDnyToSb    OBJECT-TYPE
    SYNTAX      Counter64
    UNITS       "bytes"
    MAX-ACCESS  read-only
    STATUS      current
    DESCRIPTION
        "The value of tmnxBsxStatAaSubHCOctsDnyToSb indicates the total number
         of bytes dropped for the network to subscriber direction. This object
         is a 64-bit version of tmnxBsxStatAaSubOctsDnyToSb."
    ::= { tmnxBsxStatAaSubEntry 34 }

tmnxBsxStatAaSubHCPktsDnyToSb    OBJECT-TYPE
    SYNTAX      Counter64
    UNITS       "packets"
    MAX-ACCESS  read-only
    STATUS      current
    DESCRIPTION
        "The value of tmnxBsxStatAaSubHCPktsDnyToSb indicates the total number
         of packets dropped for the network to subscriber direction. This
         object is a 64-bit version of tmnxBsxStatAaSubPktsDnyToSb."
    ::= { tmnxBsxStatAaSubEntry 35 }

tmnxBsxStatAaSubHCFlwsDnyToSb    OBJECT-TYPE
    SYNTAX      Counter64
    UNITS       "flows"
    MAX-ACCESS  read-only
    STATUS      current
    DESCRIPTION
        "The value of tmnxBsxStatAaSubHCFlwsDnyToSb indicates the total number
         of flows that dropped subsequent packets in the network to subscriber
         direction. This object is the 64-bit version of
         tmnxBsxStatAaSubFlwsDnyToSb."
    ::= { tmnxBsxStatAaSubEntry 36 }

tmnxBsxStatAaSubHCTermFlwDur     OBJECT-TYPE
    SYNTAX      Counter64
    UNITS       "seconds"
    MAX-ACCESS  read-only
    STATUS      current
    DESCRIPTION
        "The value of tmnxBsxStatAaSubHCTermFlwDur indicates the sum of all
         flow durations from first packet seen to last packet seen for flows
         that have terminated. This object is a 64-bit version of
         tmnxBsxStatAaSubTermFlwDur."
    ::= { tmnxBsxStatAaSubEntry 37 }

tmnxBsxStatAaSubHCTermFlws       OBJECT-TYPE
    SYNTAX      Counter64
    UNITS       "flows"
    MAX-ACCESS  read-only
    STATUS      current
    DESCRIPTION
        "The value of tmnxBsxStatAaSubHCTermFlws indicates the total number of
         allowed flows that have terminated. This object is a 64-bit version of
         tmnxBsxStatAaSubTermFlws."
    ::= { tmnxBsxStatAaSubEntry 38 }

tmnxBsxStatAaSubHCShrtDurFlws    OBJECT-TYPE
    SYNTAX      Counter64
    UNITS       "flows"
    MAX-ACCESS  read-only
    STATUS      current
    DESCRIPTION
        "The value of tmnxBsxStatAaSubHCShrtDurFlws indicates the total number
         of flows with a duration less than or equal to 30 seconds, that have
         completed. This object is a 64-bit version of
         tmnxBsxStatAaSubShrtDurFlws."
    ::= { tmnxBsxStatAaSubEntry 39 }

tmnxBsxStatAaSubHCMedDurFlws     OBJECT-TYPE
    SYNTAX      Counter64
    UNITS       "flows"
    MAX-ACCESS  read-only
    STATUS      current
    DESCRIPTION
        "The value of tmnxBsxStatAaSubHCMedDurFlws indicates the total number
         of flows with a duration less than or equal to 180 seconds, but
         greater than 30 seconds, that have completed. This object is a 64-bit
         version of tmnxBsxStatAaSubMedDurFlws."
    ::= { tmnxBsxStatAaSubEntry 40 }

tmnxBsxStatAaSubHCLngDurFlws     OBJECT-TYPE
    SYNTAX      Counter64
    UNITS       "flows"
    MAX-ACCESS  read-only
    STATUS      current
    DESCRIPTION
        "The value of tmnxBsxStatAaSubHCLngDurFlws indicates the total number
         of flows with a duration greater than 180 seconds, that have
         completed. This object is a 64-bit version of
         tmnxBsxStatAaSubLngDurFlws."
    ::= { tmnxBsxStatAaSubEntry 41 }

tmnxBsxStatAaSubSdyTable         OBJECT-TYPE
    SYNTAX      SEQUENCE OF TmnxBsxStatAaSubSdyEntry
    MAX-ACCESS  not-accessible
    STATUS      current
    DESCRIPTION
        "The tmnxBsxStatAaSubSdyTable contains an entry for each
         application-assurance special study subscriber for each statistics
         type within a group, partition and statistics interval. Each row
         contains the application assurance per-subscriber statistics collected
         for the special study subscriber. A subscriber is uniquely identified
         by a tmnxBsxAaSubscriberType and tmnxBsxAaSubscriber."
    ::= { tmnxBsxStatsObjs 4 }

tmnxBsxStatAaSubSdyEntry         OBJECT-TYPE
    SYNTAX      TmnxBsxStatAaSubSdyEntry
    MAX-ACCESS  not-accessible
    STATUS      current
    DESCRIPTION
        "Each tmnxBsxStatAaSubSdyEntry contains the application assurance
         per-special study subscriber statistics for a combination of group,
         partition, statistics interval, statistics type, subscriber, and
         statistics name.

         A value of 'chargingGroup (4)' is not supported for the
         tmnxBsxStatAaType. "
    INDEX       {
        tmnxBsxAaGrpPartIndex,
        tmnxBsxAaSubStatsInterval,
        tmnxBsxStatAaType,
        tmnxBsxAaSubscriberType,
        tmnxBsxAaSubscriber,
        IMPLIED tmnxBsxStatAaName
    }
    ::= { tmnxBsxStatAaSubSdyTable 1 }

TmnxBsxStatAaSubSdyEntry         ::= SEQUENCE
{
    tmnxBsxStatAaSubSdyDiscontTime   TimeStamp,
    tmnxBsxStatAaSubSdyOctsAdmFmSb   Counter32,
    tmnxBsxStatAaSubSdyPktsAdmFmSb   Counter32,
    tmnxBsxStatAaSubSdyFlwsAdmFmSb   Counter32,
    tmnxBsxStatAaSubSdyOctsDnyFmSb   Counter32,
    tmnxBsxStatAaSubSdyPktsDnyFmSb   Counter32,
    tmnxBsxStatAaSubSdyFlwsDnyFmSb   Counter32,
    tmnxBsxStatAaSubSdyOctsAdmToSb   Counter32,
    tmnxBsxStatAaSubSdyPktsAdmToSb   Counter32,
    tmnxBsxStatAaSubSdyFlwsAdmToSb   Counter32,
    tmnxBsxStatAaSubSdyOctsDnyToSb   Counter32,
    tmnxBsxStatAaSubSdyPktsDnyToSb   Counter32,
    tmnxBsxStatAaSubSdyFlwsDnyToSb   Counter32,
    tmnxBsxStatAaSubSdyTermFlwDur    Counter32,
    tmnxBsxStatAaSubSdyTermFlws      Counter32,
    tmnxBsxStatAaSubSdyShrtDurFlws   Counter32,
    tmnxBsxStatAaSubSdyMedDurFlws    Counter32,
    tmnxBsxStatAaSubSdyLngDurFlws    Counter32,
    tmnxBsxStatAaSubSdyActFlwsFmSb   Gauge32,
    tmnxBsxStatAaSubSdyActFlwsToSb   Gauge32,
    tmnxBsxStatAaSubSdyHCOctsAdmFmSb Counter64,
    tmnxBsxStatAaSubSdyHCPktsAdmFmSb Counter64,
    tmnxBsxStatAaSubSdyHCFlwsAdmFmSb Counter64,
    tmnxBsxStatAaSubSdyHCOctsDnyFmSb Counter64,
    tmnxBsxStatAaSubSdyHCPktsDnyFmSb Counter64,
    tmnxBsxStatAaSubSdyHCFlwsDnyFmSb Counter64,
    tmnxBsxStatAaSubSdyHCOctsAdmToSb Counter64,
    tmnxBsxStatAaSubSdyHCPktsAdmToSb Counter64,
    tmnxBsxStatAaSubSdyHCFlwsAdmToSb Counter64,
    tmnxBsxStatAaSubSdyHCOctsDnyToSb Counter64,
    tmnxBsxStatAaSubSdyHCPktsDnyToSb Counter64,
    tmnxBsxStatAaSubSdyHCFlwsDnyToSb Counter64,
    tmnxBsxStatAaSubSdyHCTermFlwDur  Counter64,
    tmnxBsxStatAaSubSdyHCTermFlws    Counter64,
    tmnxBsxStatAaSubSdyHCShrtDurFlws Counter64,
    tmnxBsxStatAaSubSdyHCMedDurFlws  Counter64,
    tmnxBsxStatAaSubSdyHCLngDurFlws  Counter64
}

tmnxBsxStatAaSubSdyDiscontTime   OBJECT-TYPE
    SYNTAX      TimeStamp
    MAX-ACCESS  read-only
    STATUS      current
    DESCRIPTION
        "The value of tmnxBsxStatAaSubSdyDiscontTime indicates the
         SNMPv2-MIB::sysUpTime (centiseconds) when any of the active ISA-AA
         MDAs within the group have last changed status."
    ::= { tmnxBsxStatAaSubSdyEntry 1 }

tmnxBsxStatAaSubSdyOctsAdmFmSb   OBJECT-TYPE
    SYNTAX      Counter32
    UNITS       "bytes"
    MAX-ACCESS  read-only
    STATUS      current
    DESCRIPTION
        "The value of tmnxBsxStatAaSubSdyOctsAdmFmSb indicates the total number
         of bytes permitted for the subscriber to network direction."
    ::= { tmnxBsxStatAaSubSdyEntry 2 }

tmnxBsxStatAaSubSdyPktsAdmFmSb   OBJECT-TYPE
    SYNTAX      Counter32
    UNITS       "packets"
    MAX-ACCESS  read-only
    STATUS      current
    DESCRIPTION
        "The value of tmnxBsxStatAaSubSdyPktsAdmFmSb indicates the total number
         of packets permitted for the subscriber to network direction."
    ::= { tmnxBsxStatAaSubSdyEntry 3 }

tmnxBsxStatAaSubSdyFlwsAdmFmSb   OBJECT-TYPE
    SYNTAX      Counter32
    UNITS       "flows"
    MAX-ACCESS  read-only
    STATUS      current
    DESCRIPTION
        "The value of tmnxBsxStatAaSubSdyFlwsAdmFmSb indicates the total number
         of flows permitted for the subscriber to network direction."
    ::= { tmnxBsxStatAaSubSdyEntry 4 }

tmnxBsxStatAaSubSdyOctsDnyFmSb   OBJECT-TYPE
    SYNTAX      Counter32
    UNITS       "bytes"
    MAX-ACCESS  read-only
    STATUS      current
    DESCRIPTION
        "The value of tmnxBsxStatAaSubSdyOctsDnyFmSb indicates the total number
         of bytes dropped for the subscriber to network direction."
    ::= { tmnxBsxStatAaSubSdyEntry 5 }

tmnxBsxStatAaSubSdyPktsDnyFmSb   OBJECT-TYPE
    SYNTAX      Counter32
    UNITS       "packets"
    MAX-ACCESS  read-only
    STATUS      current
    DESCRIPTION
        "The value of tmnxBsxStatAaSubSdyPktsDnyFmSb indicates the total number
         of packets dropped for the subscriber to network direction."
    ::= { tmnxBsxStatAaSubSdyEntry 6 }

tmnxBsxStatAaSubSdyFlwsDnyFmSb   OBJECT-TYPE
    SYNTAX      Counter32
    UNITS       "flows"
    MAX-ACCESS  read-only
    STATUS      current
    DESCRIPTION
        "The value of tmnxBsxStatAaSubSdyFlwsDnyFmSb indicates the total number
         of flows that dropped subsequent packets in the subscriber to network
         direction."
    ::= { tmnxBsxStatAaSubSdyEntry 7 }

tmnxBsxStatAaSubSdyOctsAdmToSb   OBJECT-TYPE
    SYNTAX      Counter32
    UNITS       "bytes"
    MAX-ACCESS  read-only
    STATUS      current
    DESCRIPTION
        "The value of tmnxBsxStatAaSubSdyOctsAdmToSb indicates the total number
         of bytes permitted for the network to subscriber direction."
    ::= { tmnxBsxStatAaSubSdyEntry 8 }

tmnxBsxStatAaSubSdyPktsAdmToSb   OBJECT-TYPE
    SYNTAX      Counter32
    UNITS       "packets"
    MAX-ACCESS  read-only
    STATUS      current
    DESCRIPTION
        "The value of tmnxBsxStatAaSubSdyPktsAdmToSb indicates the total number
         of packets permitted for the network to subscriber direction."
    ::= { tmnxBsxStatAaSubSdyEntry 9 }

tmnxBsxStatAaSubSdyFlwsAdmToSb   OBJECT-TYPE
    SYNTAX      Counter32
    UNITS       "flows"
    MAX-ACCESS  read-only
    STATUS      current
    DESCRIPTION
        "The value of tmnxBsxStatAaSubSdyFlwsAdmToSb indicates the total number
         of flows permitted for the network to subscriber direction."
    ::= { tmnxBsxStatAaSubSdyEntry 10 }

tmnxBsxStatAaSubSdyOctsDnyToSb   OBJECT-TYPE
    SYNTAX      Counter32
    UNITS       "bytes"
    MAX-ACCESS  read-only
    STATUS      current
    DESCRIPTION
        "The value of tmnxBsxStatAaSubSdyOctsDnyToSb indicates the total number
         of bytes dropped for the network to subscriber direction."
    ::= { tmnxBsxStatAaSubSdyEntry 11 }

tmnxBsxStatAaSubSdyPktsDnyToSb   OBJECT-TYPE
    SYNTAX      Counter32
    UNITS       "packets"
    MAX-ACCESS  read-only
    STATUS      current
    DESCRIPTION
        "The value of tmnxBsxStatAaSubSdyPktsDnyToSb indicates the total number
         of packets dropped for the network to subscriber direction."
    ::= { tmnxBsxStatAaSubSdyEntry 12 }

tmnxBsxStatAaSubSdyFlwsDnyToSb   OBJECT-TYPE
    SYNTAX      Counter32
    UNITS       "flows"
    MAX-ACCESS  read-only
    STATUS      current
    DESCRIPTION
        "The value of tmnxBsxStatAaSubSdyFlwsDnyToSb indicates the total number
         of flows that dropped subsequent packets in the network to subscriber
         direction."
    ::= { tmnxBsxStatAaSubSdyEntry 13 }

tmnxBsxStatAaSubSdyTermFlwDur    OBJECT-TYPE
    SYNTAX      Counter32
    UNITS       "seconds"
    MAX-ACCESS  read-only
    STATUS      current
    DESCRIPTION
        "The value of tmnxBsxStatAaSubSdyTermFlwDur indicates the sum of all
         flow durations from first packet seen to last packet seen for flows
         that have terminated."
    ::= { tmnxBsxStatAaSubSdyEntry 14 }

tmnxBsxStatAaSubSdyTermFlws      OBJECT-TYPE
    SYNTAX      Counter32
    UNITS       "flows"
    MAX-ACCESS  read-only
    STATUS      current
    DESCRIPTION
        "The value of tmnxBsxStatAaSubSdyTermFlws indicates the total number of
         allowed flows that have terminated."
    ::= { tmnxBsxStatAaSubSdyEntry 15 }

tmnxBsxStatAaSubSdyShrtDurFlws   OBJECT-TYPE
    SYNTAX      Counter32
    UNITS       "flows"
    MAX-ACCESS  read-only
    STATUS      current
    DESCRIPTION
        "The value of tmnxBsxStatAaSubSdyShrtDurFlws indicates the total number
         of flows with a duration less than or equal to 30 seconds, that have
         completed."
    ::= { tmnxBsxStatAaSubSdyEntry 16 }

tmnxBsxStatAaSubSdyMedDurFlws    OBJECT-TYPE
    SYNTAX      Counter32
    UNITS       "flows"
    MAX-ACCESS  read-only
    STATUS      current
    DESCRIPTION
        "The value of tmnxBsxStatAaSubSdyMedDurFlws indicates the total number
         of flows with a duration less than or equal to 180 seconds, but
         greater than 30 seconds, that have completed."
    ::= { tmnxBsxStatAaSubSdyEntry 17 }

tmnxBsxStatAaSubSdyLngDurFlws    OBJECT-TYPE
    SYNTAX      Counter32
    UNITS       "flows"
    MAX-ACCESS  read-only
    STATUS      current
    DESCRIPTION
        "The value of tmnxBsxStatAaSubSdyLngDurFlws indicates the total number
         of flows with a duration greater than 180 seconds, that have
         completed."
    ::= { tmnxBsxStatAaSubSdyEntry 18 }

tmnxBsxStatAaSubSdyActFlwsFmSb   OBJECT-TYPE
    SYNTAX      Gauge32
    UNITS       "flows"
    MAX-ACCESS  read-only
    STATUS      current
    DESCRIPTION
        "The value of tmnxBsxStatAaSubSdyActFlwsFmSb indicates the number of
         allowed flows in the subscriber to network direction that are active."
    ::= { tmnxBsxStatAaSubSdyEntry 19 }

tmnxBsxStatAaSubSdyActFlwsToSb   OBJECT-TYPE
    SYNTAX      Gauge32
    UNITS       "flows"
    MAX-ACCESS  read-only
    STATUS      current
    DESCRIPTION
        "The value of tmnxBsxStatAaSubSdyActFlwsToSb indicates the number of
         allowed flows in the network to subscriber direction that are active."
    ::= { tmnxBsxStatAaSubSdyEntry 20 }

tmnxBsxStatAaSubSdyHCOctsAdmFmSb OBJECT-TYPE
    SYNTAX      Counter64
    UNITS       "bytes"
    MAX-ACCESS  read-only
    STATUS      current
    DESCRIPTION
        "The value of tmnxBsxStatAaSubSdyHCOctsAdmFmSb indicates the total
         number of bytes permitted for the subscriber to network direction.
         This object is a 64-bit version of tmnxBsxStatAaSubSdyOctsAdmFmSb."
    ::= { tmnxBsxStatAaSubSdyEntry 21 }

tmnxBsxStatAaSubSdyHCPktsAdmFmSb OBJECT-TYPE
    SYNTAX      Counter64
    UNITS       "packets"
    MAX-ACCESS  read-only
    STATUS      current
    DESCRIPTION
        "The value of tmnxBsxStatAaSubSdyHCPktsAdmFmSb indicates the total
         number of packets permitted for the subscriber to network direction.
         This object is a 64-bit version of tmnxBsxStatAaSubSdyPktsAdmFmSb."
    ::= { tmnxBsxStatAaSubSdyEntry 22 }

tmnxBsxStatAaSubSdyHCFlwsAdmFmSb OBJECT-TYPE
    SYNTAX      Counter64
    UNITS       "flows"
    MAX-ACCESS  read-only
    STATUS      current
    DESCRIPTION
        "The value of tmnxBsxStatAaSubSdyHCFlwsAdmFmSb indicates the total
         number of flows permitted for the subscriber to network direction.
         This object is a 64-bit version of tmnxBsxStatAaSubSdyFlwsAdmFmSb."
    ::= { tmnxBsxStatAaSubSdyEntry 23 }

tmnxBsxStatAaSubSdyHCOctsDnyFmSb OBJECT-TYPE
    SYNTAX      Counter64
    UNITS       "bytes"
    MAX-ACCESS  read-only
    STATUS      current
    DESCRIPTION
        "The value of tmnxBsxStatAaSubSdyHCOctsDnyFmSb indicates the total
         number of bytes dropped for the subscriber to network direction. This
         object is a 64-bit version of tmnxBsxStatAaSubSdyOctsDnyFmSb."
    ::= { tmnxBsxStatAaSubSdyEntry 24 }

tmnxBsxStatAaSubSdyHCPktsDnyFmSb OBJECT-TYPE
    SYNTAX      Counter64
    UNITS       "packets"
    MAX-ACCESS  read-only
    STATUS      current
    DESCRIPTION
        "The value of tmnxBsxStatAaSubSdyHCPktsDnyFmSb indicates the total
         number of packets dropped for the subscriber to network direction.
         This object is a 64-bit version of tmnxBsxStatAaSubSdyPktsDnyFmSb."
    ::= { tmnxBsxStatAaSubSdyEntry 25 }

tmnxBsxStatAaSubSdyHCFlwsDnyFmSb OBJECT-TYPE
    SYNTAX      Counter64
    UNITS       "flows"
    MAX-ACCESS  read-only
    STATUS      current
    DESCRIPTION
        "The value of tmnxBsxStatAaSubSdyHCFlwsDnyFmSb indicates the total
         number of flows that dropped subsequent packets in the subscriber to
         network direction. This object is a 64-bit version of
         tmnxBsxStatAaSubSdyFlwsDnyFmSb."
    ::= { tmnxBsxStatAaSubSdyEntry 26 }

tmnxBsxStatAaSubSdyHCOctsAdmToSb OBJECT-TYPE
    SYNTAX      Counter64
    UNITS       "bytes"
    MAX-ACCESS  read-only
    STATUS      current
    DESCRIPTION
        "The value of tmnxBsxStatAaSubSdyHCOctsAdmToSb indicates the total
         number of bytes permitted for the network to subscriber direction.
         This object is a 64-bit version of tmnxBsxStatAaSubSdyOctsAdmToSb."
    ::= { tmnxBsxStatAaSubSdyEntry 27 }

tmnxBsxStatAaSubSdyHCPktsAdmToSb OBJECT-TYPE
    SYNTAX      Counter64
    UNITS       "packets"
    MAX-ACCESS  read-only
    STATUS      current
    DESCRIPTION
        "The value of tmnxBsxStatAaSubSdyHCPktsAdmToSb indicates the total
         number of packets permitted for the network to subscriber direction.
         This object is a 64-bit version of tmnxBsxStatAaSubSdyPktsAdmToSb."
    ::= { tmnxBsxStatAaSubSdyEntry 28 }

tmnxBsxStatAaSubSdyHCFlwsAdmToSb OBJECT-TYPE
    SYNTAX      Counter64
    UNITS       "flows"
    MAX-ACCESS  read-only
    STATUS      current
    DESCRIPTION
        "The value of tmnxBsxStatAaSubSdyHCFlwsAdmToSb indicates the total
         number of flows permitted for the network to subscriber direction.
         This object is a 64-bit version of tmnxBsxStatAaSubSdyFlwsAdmToSb."
    ::= { tmnxBsxStatAaSubSdyEntry 29 }

tmnxBsxStatAaSubSdyHCOctsDnyToSb OBJECT-TYPE
    SYNTAX      Counter64
    UNITS       "bytes"
    MAX-ACCESS  read-only
    STATUS      current
    DESCRIPTION
        "The value of tmnxBsxStatAaSubSdyHCOctsDnyToSb indicates the total
         number of bytes dropped for the network to subscriber direction. This
         object is a 64-bit version of tmnxBsxStatAaSubSdyOctsDnyToSb."
    ::= { tmnxBsxStatAaSubSdyEntry 30 }

tmnxBsxStatAaSubSdyHCPktsDnyToSb OBJECT-TYPE
    SYNTAX      Counter64
    UNITS       "packets"
    MAX-ACCESS  read-only
    STATUS      current
    DESCRIPTION
        "The value of tmnxBsxStatAaSubSdyHCPktsDnyToSb indicates the total
         number of packets dropped for the network to subscriber direction.
         This object is a 64-bit version of tmnxBsxStatAaSubSdyPktsDnyToSb."
    ::= { tmnxBsxStatAaSubSdyEntry 31 }

tmnxBsxStatAaSubSdyHCFlwsDnyToSb OBJECT-TYPE
    SYNTAX      Counter64
    UNITS       "flows"
    MAX-ACCESS  read-only
    STATUS      current
    DESCRIPTION
        "The value of tmnxBsxStatAaSubSdyHCFlwsDnyToSb indicates the total
         number of flows that dropped subsequent packets in the network to
         subscriber direction. This object is a 64-bit version of
         tmnxBsxStatAaSubSdyFlwsDnyToSb."
    ::= { tmnxBsxStatAaSubSdyEntry 32 }

tmnxBsxStatAaSubSdyHCTermFlwDur  OBJECT-TYPE
    SYNTAX      Counter64
    UNITS       "seconds"
    MAX-ACCESS  read-only
    STATUS      current
    DESCRIPTION
        "The value of tmnxBsxStatAaSubSdyHCTermFlwDur indicates the sum of all
         flow durations from first packet seen to last packet seen for flows
         that have terminated. This object is a 64-bit version of
         tmnxBsxStatAaSubSdyTermFlwDur."
    ::= { tmnxBsxStatAaSubSdyEntry 33 }

tmnxBsxStatAaSubSdyHCTermFlws    OBJECT-TYPE
    SYNTAX      Counter64
    UNITS       "flows"
    MAX-ACCESS  read-only
    STATUS      current
    DESCRIPTION
        "The value of tmnxBsxStatAaSubSdyHCTermFlws indicates the total number
         of allowed flows that have terminated. This object is a 64-bit version
         of tmnxBsxStatAaSubSdyTermFlws."
    ::= { tmnxBsxStatAaSubSdyEntry 34 }

tmnxBsxStatAaSubSdyHCShrtDurFlws OBJECT-TYPE
    SYNTAX      Counter64
    UNITS       "flows"
    MAX-ACCESS  read-only
    STATUS      current
    DESCRIPTION
        "The value of tmnxBsxStatAaSubSdyHCShrtDurFlws indicates the total
         number of flows with a duration less than or equal to 30 seconds, that
         have completed. This object is a 64-bit version of
         tmnxBsxStatAaSubSdyShrtDurFlws."
    ::= { tmnxBsxStatAaSubSdyEntry 35 }

tmnxBsxStatAaSubSdyHCMedDurFlws  OBJECT-TYPE
    SYNTAX      Counter64
    UNITS       "flows"
    MAX-ACCESS  read-only
    STATUS      current
    DESCRIPTION
        "The value of tmnxBsxStatAaSubSdyHCMedDurFlws indicates the total
         number of flows with a duration less than or equal to 180 seconds, but
         greater than 30 seconds, that have completed. This object is a 64-bit
         version of tmnxBsxStatAaSubSdyMedDurFlws."
    ::= { tmnxBsxStatAaSubSdyEntry 36 }

tmnxBsxStatAaSubSdyHCLngDurFlws  OBJECT-TYPE
    SYNTAX      Counter64
    UNITS       "flows"
    MAX-ACCESS  read-only
    STATUS      current
    DESCRIPTION
        "The value of tmnxBsxStatAaSubSdyHCLngDurFlws indicates the total
         number of flows with a duration greater than 180 seconds, that have
         completed. This object is a 64-bit version of
         tmnxBsxStatAaSubSdyLngDurFlws."
    ::= { tmnxBsxStatAaSubSdyEntry 37 }

tmnxBsxStatAaSubCfgTable         OBJECT-TYPE
    SYNTAX      SEQUENCE OF TmnxBsxStatAaSubCfgEntry
    MAX-ACCESS  not-accessible
    STATUS      current
    DESCRIPTION
        "The tmnxBsxStatAaSubCfgTable contains an entry for each ISA-AA
         statistics type that has per-subscriber statistics enabled."
    ::= { tmnxBsxStatsObjs 5 }

tmnxBsxStatAaSubCfgEntry         OBJECT-TYPE
    SYNTAX      TmnxBsxStatAaSubCfgEntry
    MAX-ACCESS  not-accessible
    STATUS      current
    DESCRIPTION
        "Each tmnxBsxStatAaSubCfgEntry specifies an application assurance
         group, partition and statistic type and name for which subscriber
         statistics are enabled."
    INDEX       {
        tmnxBsxAaGrpPartIndex,
        tmnxBsxStatAaType,
        IMPLIED tmnxBsxStatAaName
    }
    ::= { tmnxBsxStatAaSubCfgTable 1 }

TmnxBsxStatAaSubCfgEntry         ::= SEQUENCE
{
    tmnxBsxStatAaSubCfgRowStatus     RowStatus,
    tmnxBsxStatAaSubCfgExportMethod  TmnxBsxAaStatExportMethod
}

tmnxBsxStatAaSubCfgRowStatus     OBJECT-TYPE
    SYNTAX      RowStatus
    MAX-ACCESS  read-create
    STATUS      current
    DESCRIPTION
        "The value of tmnxBsxStatAaSubCfgRowStatus specifies
         the row status.  It allows entries to be created
         and deleted in the tmnxBsxStatAaSubCfgTable.

         Rows are created by specifying the value of 'createAndGo (4)', and
         deleted by specifying the value of 'destroy (6)'."
    ::= { tmnxBsxStatAaSubCfgEntry 1 }

tmnxBsxStatAaSubCfgExportMethod  OBJECT-TYPE
    SYNTAX      TmnxBsxAaStatExportMethod
    MAX-ACCESS  read-create
    STATUS      current
    DESCRIPTION
        "The value of tmnxBsxStatAaSubCfgExportMethod specifies the method used
         to export subscriber statistics."
    ::= { tmnxBsxStatAaSubCfgEntry 2 }

tmnxBsxStatAaSubSdyCfgTable      OBJECT-TYPE
    SYNTAX      SEQUENCE OF TmnxBsxStatAaSubSdyCfgEntry
    MAX-ACCESS  not-accessible
    STATUS      current
    DESCRIPTION
        "The tmnxBsxStatAaSubSdyCfgTable contains an entry for each special
         study subscriber and statistics type that has statistics enabled."
    ::= { tmnxBsxStatsObjs 6 }

tmnxBsxStatAaSubSdyCfgEntry      OBJECT-TYPE
    SYNTAX      TmnxBsxStatAaSubSdyCfgEntry
    MAX-ACCESS  not-accessible
    STATUS      current
    DESCRIPTION
        "Each tmnxBsxStatAaSubSdyCfgEntry specifies an application assurance
         group index, statistics type, and subscriber for which protocol
         statistics are enabled."
    INDEX       {
        tmnxBsxAaGrpPartIndex,
        tmnxBsxStatAaType,
        tmnxBsxAaSubscriberType,
        tmnxBsxAaSubscriber
    }
    ::= { tmnxBsxStatAaSubSdyCfgTable 1 }

TmnxBsxStatAaSubSdyCfgEntry      ::= SEQUENCE
{ tmnxBsxStatAaSubSdyRowStatus     RowStatus }

tmnxBsxStatAaSubSdyRowStatus     OBJECT-TYPE
    SYNTAX      RowStatus
    MAX-ACCESS  read-create
    STATUS      current
    DESCRIPTION
        "The value of tmnxBsxStatAaSubSdyRowStatus specifies
         the row status.  It allows entries to be created
         and deleted in the tmnxBsxStatAaSubSdyCfgTable.

         Rows are created by specifying the value of 'createAndGo (4)', and
         deleted by specifying the value of 'destroy (6)'."
    ::= { tmnxBsxStatAaSubSdyCfgEntry 1 }

tmnxBsxStatAaTable               OBJECT-TYPE
    SYNTAX      SEQUENCE OF TmnxBsxStatAaEntry
    MAX-ACCESS  not-accessible
    STATUS      current
    DESCRIPTION
        "The tmnxBsxStatAaTable contains an entry for each system wide
         statistics type and statistics name per group and partition."
    ::= { tmnxBsxStatsObjs 7 }

tmnxBsxStatAaEntry               OBJECT-TYPE
    SYNTAX      TmnxBsxStatAaEntry
    MAX-ACCESS  not-accessible
    STATUS      current
    DESCRIPTION
        "Each tmnxBsxStatAaEntry contains the statistics for a particular
         group, partition, statistics type and statistics name.

         A value of 'chargingGroup (4)' is not supported for the
         tmnxBsxStatAaType. "
    INDEX       {
        tmnxBsxAaGrpPartIndex,
        tmnxBsxStatAaType,
        IMPLIED tmnxBsxStatAaName
    }
    ::= { tmnxBsxStatAaTable 1 }

TmnxBsxStatAaEntry               ::= SEQUENCE
{
    tmnxBsxStatAaDiscontTime         TimeStamp,
    tmnxBsxStatAaOctsAdmFmSb         Counter32,
    tmnxBsxStatAaPktsAdmFmSb         Counter32,
    tmnxBsxStatAaFlwsAdmFmSb         Counter32,
    tmnxBsxStatAaOctsDnyFmSb         Counter32,
    tmnxBsxStatAaPktsDnyFmSb         Counter32,
    tmnxBsxStatAaFlwsDnyFmSb         Counter32,
    tmnxBsxStatAaOctsAdmToSb         Counter32,
    tmnxBsxStatAaPktsAdmToSb         Counter32,
    tmnxBsxStatAaFlwsAdmToSb         Counter32,
    tmnxBsxStatAaOctsDnyToSb         Counter32,
    tmnxBsxStatAaPktsDnyToSb         Counter32,
    tmnxBsxStatAaFlwsDnyToSb         Counter32,
    tmnxBsxStatAaTermFlwDur          Counter32,
    tmnxBsxStatAaTermFlws            Counter32,
    tmnxBsxStatAaShrtDurFlws         Counter32,
    tmnxBsxStatAaMedDurFlws          Counter32,
    tmnxBsxStatAaLngDurFlws          Counter32,
    tmnxBsxStatAaActFlwsFmSb         Gauge32,
    tmnxBsxStatAaActFlwsToSb         Gauge32,
    tmnxBsxStatAaNumSubscribers      Gauge32,
    tmnxBsxStatAaHCOctsAdmFmSb       Counter64,
    tmnxBsxStatAaHCPktsAdmFmSb       Counter64,
    tmnxBsxStatAaHCFlwsAdmFmSb       Counter64,
    tmnxBsxStatAaHCOctsDnyFmSb       Counter64,
    tmnxBsxStatAaHCPktsDnyFmSb       Counter64,
    tmnxBsxStatAaHCFlwsDnyFmSb       Counter64,
    tmnxBsxStatAaHCOctsAdmToSb       Counter64,
    tmnxBsxStatAaHCPktsAdmToSb       Counter64,
    tmnxBsxStatAaHCFlwsAdmToSb       Counter64,
    tmnxBsxStatAaHCOctsDnyToSb       Counter64,
    tmnxBsxStatAaHCPktsDnyToSb       Counter64,
    tmnxBsxStatAaHCFlwsDnyToSb       Counter64,
    tmnxBsxStatAaHCTermFlwDur        Counter64,
    tmnxBsxStatAaHCTermFlws          Counter64,
    tmnxBsxStatAaHCShrtDurFlws       Counter64,
    tmnxBsxStatAaHCMedDurFlws        Counter64,
    tmnxBsxStatAaHCLngDurFlws        Counter64
}

tmnxBsxStatAaDiscontTime         OBJECT-TYPE
    SYNTAX      TimeStamp
    MAX-ACCESS  read-only
    STATUS      current
    DESCRIPTION
        "The value of tmnxBsxStatAaDiscontTime indicates the
         SNMPv2-MIB::sysUpTime (centiseconds) when any of the active ISA-AA
         within the group last changed status."
    ::= { tmnxBsxStatAaEntry 1 }

tmnxBsxStatAaOctsAdmFmSb         OBJECT-TYPE
    SYNTAX      Counter32
    UNITS       "bytes"
    MAX-ACCESS  read-only
    STATUS      current
    DESCRIPTION
        "The value of tmnxBsxStatAaOctsAdmFmSb indicates the total number of
         bytes permitted for the subscriber to network direction."
    ::= { tmnxBsxStatAaEntry 2 }

tmnxBsxStatAaPktsAdmFmSb         OBJECT-TYPE
    SYNTAX      Counter32
    UNITS       "packets"
    MAX-ACCESS  read-only
    STATUS      current
    DESCRIPTION
        "The value of tmnxBsxStatAaPktsAdmFmSb indicates the total number of
         packets permitted for the subscriber to network direction."
    ::= { tmnxBsxStatAaEntry 3 }

tmnxBsxStatAaFlwsAdmFmSb         OBJECT-TYPE
    SYNTAX      Counter32
    UNITS       "flows"
    MAX-ACCESS  read-only
    STATUS      current
    DESCRIPTION
        "The value of tmnxBsxStatAaFlwsAdmFmSb indicates the total number of
         flows permitted for the subscriber to network direction."
    ::= { tmnxBsxStatAaEntry 4 }

tmnxBsxStatAaOctsDnyFmSb         OBJECT-TYPE
    SYNTAX      Counter32
    UNITS       "bytes"
    MAX-ACCESS  read-only
    STATUS      current
    DESCRIPTION
        "The value of tmnxBsxStatAaOctsDnyFmSb indicates the total number of
         bytes dropped for the subscriber to network direction."
    ::= { tmnxBsxStatAaEntry 5 }

tmnxBsxStatAaPktsDnyFmSb         OBJECT-TYPE
    SYNTAX      Counter32
    UNITS       "packets"
    MAX-ACCESS  read-only
    STATUS      current
    DESCRIPTION
        "The value of tmnxBsxStatAaPktsDnyFmSb indicates the total number of
         packets dropped for the subscriber to network direction."
    ::= { tmnxBsxStatAaEntry 6 }

tmnxBsxStatAaFlwsDnyFmSb         OBJECT-TYPE
    SYNTAX      Counter32
    UNITS       "flows"
    MAX-ACCESS  read-only
    STATUS      current
    DESCRIPTION
        "The value of tmnxBsxStatAaFlwsDnyFmSb indicates the total number of
         flows the dropped subsequent packets in the subscriber to network
         direction."
    ::= { tmnxBsxStatAaEntry 7 }

tmnxBsxStatAaOctsAdmToSb         OBJECT-TYPE
    SYNTAX      Counter32
    UNITS       "bytes"
    MAX-ACCESS  read-only
    STATUS      current
    DESCRIPTION
        "The value of tmnxBsxStatAaOctsAdmToSb indicates the total number of
         bytes permitted for the network to subscriber direction."
    ::= { tmnxBsxStatAaEntry 8 }

tmnxBsxStatAaPktsAdmToSb         OBJECT-TYPE
    SYNTAX      Counter32
    UNITS       "packets"
    MAX-ACCESS  read-only
    STATUS      current
    DESCRIPTION
        "The value of tmnxBsxStatAaPktsAdmToSb indicates the total number of
         packets permitted for the network to subscriber direction."
    ::= { tmnxBsxStatAaEntry 9 }

tmnxBsxStatAaFlwsAdmToSb         OBJECT-TYPE
    SYNTAX      Counter32
    UNITS       "flows"
    MAX-ACCESS  read-only
    STATUS      current
    DESCRIPTION
        "The value of tmnxBsxStatAaFlwsAdmToSb indicates the total number of
         flows permitted for the network to subscriber direction."
    ::= { tmnxBsxStatAaEntry 10 }

tmnxBsxStatAaOctsDnyToSb         OBJECT-TYPE
    SYNTAX      Counter32
    UNITS       "bytes"
    MAX-ACCESS  read-only
    STATUS      current
    DESCRIPTION
        "The value of tmnxBsxStatAaOctsDnyToSb indicates the total number of
         bytes dropped for the network to subscriber direction."
    ::= { tmnxBsxStatAaEntry 11 }

tmnxBsxStatAaPktsDnyToSb         OBJECT-TYPE
    SYNTAX      Counter32
    UNITS       "packets"
    MAX-ACCESS  read-only
    STATUS      current
    DESCRIPTION
        "The value of tmnxBsxStatAaPktsDnyToSb indicates the total number of
         packets dropped for the network to subscriber direction."
    ::= { tmnxBsxStatAaEntry 12 }

tmnxBsxStatAaFlwsDnyToSb         OBJECT-TYPE
    SYNTAX      Counter32
    UNITS       "flows"
    MAX-ACCESS  read-only
    STATUS      current
    DESCRIPTION
        "The value of tmnxBsxStatAaFlwsDnyToSb indicates the total number of
         flows that dropped subsequent packets in the network to subscriber
         direction."
    ::= { tmnxBsxStatAaEntry 13 }

tmnxBsxStatAaTermFlwDur          OBJECT-TYPE
    SYNTAX      Counter32
    UNITS       "seconds"
    MAX-ACCESS  read-only
    STATUS      current
    DESCRIPTION
        "The value of tmnxBsxStatAaTermFlwDur indicates the sum of all flow
         durations from first packet seen to last packet seen for flows that
         have terminated."
    ::= { tmnxBsxStatAaEntry 14 }

tmnxBsxStatAaTermFlws            OBJECT-TYPE
    SYNTAX      Counter32
    UNITS       "flows"
    MAX-ACCESS  read-only
    STATUS      current
    DESCRIPTION
        "The value of tmnxBsxStatAaTermFlws indicates the total number of
         allowed flows in both directions that have terminated."
    ::= { tmnxBsxStatAaEntry 15 }

tmnxBsxStatAaShrtDurFlws         OBJECT-TYPE
    SYNTAX      Counter32
    UNITS       "flows"
    MAX-ACCESS  read-only
    STATUS      current
    DESCRIPTION
        "The value of tmnxBsxStatAaShrtDurFlws indicates the total number of
         flows with a duration less than or equal to 30 seconds, that have
         completed."
    ::= { tmnxBsxStatAaEntry 16 }

tmnxBsxStatAaMedDurFlws          OBJECT-TYPE
    SYNTAX      Counter32
    UNITS       "flows"
    MAX-ACCESS  read-only
    STATUS      current
    DESCRIPTION
        "The value of tmnxBsxStatAaMedDurFlws indicates the total number of
         flows with a duration less than or equal to 180 seconds, but greater
         than 30 seconds, that have completed."
    ::= { tmnxBsxStatAaEntry 17 }

tmnxBsxStatAaLngDurFlws          OBJECT-TYPE
    SYNTAX      Counter32
    UNITS       "flows"
    MAX-ACCESS  read-only
    STATUS      current
    DESCRIPTION
        "The value of tmnxBsxStatAaLngDurFlws indicates the total number of
         flows with a duration greater than 180 seconds, that have completed."
    ::= { tmnxBsxStatAaEntry 18 }

tmnxBsxStatAaActFlwsFmSb         OBJECT-TYPE
    SYNTAX      Gauge32
    UNITS       "flows"
    MAX-ACCESS  read-only
    STATUS      current
    DESCRIPTION
        "The value of tmnxBsxStatAaActFlwsFmSb indicates the number of allowed
         flows in the subscriber to network direction that are active."
    ::= { tmnxBsxStatAaEntry 19 }

tmnxBsxStatAaActFlwsToSb         OBJECT-TYPE
    SYNTAX      Gauge32
    UNITS       "flows"
    MAX-ACCESS  read-only
    STATUS      current
    DESCRIPTION
        "The value of tmnxBsxStatAaActFlwsToSb indicates the number of allowed
         flows in the network to subscriber direction that are active."
    ::= { tmnxBsxStatAaEntry 20 }

tmnxBsxStatAaNumSubscribers      OBJECT-TYPE
    SYNTAX      Gauge32
    UNITS       "subscribers"
    MAX-ACCESS  read-only
    STATUS      current
    DESCRIPTION
        "The value of tmnxBsxStatAaNumSubscribers indicates the number of
         subscribers at the most recent 5-minute snapshot of statistics."
    ::= { tmnxBsxStatAaEntry 21 }

tmnxBsxStatAaHCOctsAdmFmSb       OBJECT-TYPE
    SYNTAX      Counter64
    UNITS       "bytes"
    MAX-ACCESS  read-only
    STATUS      current
    DESCRIPTION
        "The value of tmnxBsxStatAaHCOctsAdmFmSb indicates the total number of
         bytes permitted for the subscriber to network direction. This object
         is a 64-bit version of tmnxBsxStatAaOctsAdmFmSb."
    ::= { tmnxBsxStatAaEntry 22 }

tmnxBsxStatAaHCPktsAdmFmSb       OBJECT-TYPE
    SYNTAX      Counter64
    UNITS       "packets"
    MAX-ACCESS  read-only
    STATUS      current
    DESCRIPTION
        "The value of tmnxBsxStatAaHCPktsAdmFmSb indicates the total number of
         packets permitted for the subscriber to network direction. This object
         is a 64-bit version of tmnxBsxStatAaPktsAdmFmSb."
    ::= { tmnxBsxStatAaEntry 23 }

tmnxBsxStatAaHCFlwsAdmFmSb       OBJECT-TYPE
    SYNTAX      Counter64
    UNITS       "flows"
    MAX-ACCESS  read-only
    STATUS      current
    DESCRIPTION
        "The value of tmnxBsxStatAaHCFlwsAdmFmSb indicates the total number of
         flows permitted for the subscriber to network direction. This object
         is a 64-bit version of tmnxBsxStatAaFlwsAdmFmSb."
    ::= { tmnxBsxStatAaEntry 24 }

tmnxBsxStatAaHCOctsDnyFmSb       OBJECT-TYPE
    SYNTAX      Counter64
    UNITS       "bytes"
    MAX-ACCESS  read-only
    STATUS      current
    DESCRIPTION
        "The value of tmnxBsxStatAaHCOctsDnyFmSb indicates the total number of
         bytes dropped for the subscriber to network direction. This object is
         a 64-bit version of tmnxBsxStatAaOctsDnyFmSb."
    ::= { tmnxBsxStatAaEntry 25 }

tmnxBsxStatAaHCPktsDnyFmSb       OBJECT-TYPE
    SYNTAX      Counter64
    UNITS       "packets"
    MAX-ACCESS  read-only
    STATUS      current
    DESCRIPTION
        "The value of tmnxBsxStatAaHCPktsDnyFmSb indicates the total number of
         packets dropped for the subscriber to network direction. This object
         is a 64-bit version of tmnxBsxStatAaPktsDnyFmSb."
    ::= { tmnxBsxStatAaEntry 26 }

tmnxBsxStatAaHCFlwsDnyFmSb       OBJECT-TYPE
    SYNTAX      Counter64
    UNITS       "flows"
    MAX-ACCESS  read-only
    STATUS      current
    DESCRIPTION
        "The value of tmnxBsxStatAaHCFlwsDnyFmSb indicates the total number of
         flows the dropped subsequent packets in the subscriber to network
         direction. This object is a 64-bit version of
         tmnxBsxStatAaFlwsDnyFmSb."
    ::= { tmnxBsxStatAaEntry 27 }

tmnxBsxStatAaHCOctsAdmToSb       OBJECT-TYPE
    SYNTAX      Counter64
    UNITS       "bytes"
    MAX-ACCESS  read-only
    STATUS      current
    DESCRIPTION
        "The value of tmnxBsxStatAaHCOctsAdmToSb indicates the total number of
         bytes permitted for the network to subscriber direction. This object
         is a 64-bit version of tmnxBsxStatAaOctsAdmToSb."
    ::= { tmnxBsxStatAaEntry 28 }

tmnxBsxStatAaHCPktsAdmToSb       OBJECT-TYPE
    SYNTAX      Counter64
    UNITS       "packets"
    MAX-ACCESS  read-only
    STATUS      current
    DESCRIPTION
        "The value of tmnxBsxStatAaHCPktsAdmToSb indicates the total number of
         packets permitted for the network to subscriber direction. This object
         is a 64-bit version of tmnxBsxStatAaPktsAdmToSb."
    ::= { tmnxBsxStatAaEntry 29 }

tmnxBsxStatAaHCFlwsAdmToSb       OBJECT-TYPE
    SYNTAX      Counter64
    UNITS       "flows"
    MAX-ACCESS  read-only
    STATUS      current
    DESCRIPTION
        "The value of tmnxBsxStatAaHCFlwsAdmToSb indicates the total number of
         flows permitted for the network to subscriber direction. This object
         is a 64-bit version of tmnxBsxStatAaFlwsAdmToSb."
    ::= { tmnxBsxStatAaEntry 30 }

tmnxBsxStatAaHCOctsDnyToSb       OBJECT-TYPE
    SYNTAX      Counter64
    UNITS       "bytes"
    MAX-ACCESS  read-only
    STATUS      current
    DESCRIPTION
        "The value of tmnxBsxStatAaHCOctsDnyToSb indicates the total number of
         bytes dropped for the network to subscriber direction. This object is
         a 64-bit version of tmnxBsxStatAaOctsDnyToSb."
    ::= { tmnxBsxStatAaEntry 31 }

tmnxBsxStatAaHCPktsDnyToSb       OBJECT-TYPE
    SYNTAX      Counter64
    UNITS       "packets"
    MAX-ACCESS  read-only
    STATUS      current
    DESCRIPTION
        "The value of tmnxBsxStatAaHCPktsDnyToSb indicates the total number of
         packets dropped for the network to subscriber direction. This object
         is a 64-bit version of tmnxBsxStatAaPktsDnyToSb."
    ::= { tmnxBsxStatAaEntry 32 }

tmnxBsxStatAaHCFlwsDnyToSb       OBJECT-TYPE
    SYNTAX      Counter64
    UNITS       "flows"
    MAX-ACCESS  read-only
    STATUS      current
    DESCRIPTION
        "The value of tmnxBsxStatAaHCFlwsDnyToSb indicates the total number of
         flows that dropped subsequent packets in the network to subscriber
         direction. This object is a 64-bit version of
         tmnxBsxStatAaFlwsDnyToSb."
    ::= { tmnxBsxStatAaEntry 33 }

tmnxBsxStatAaHCTermFlwDur        OBJECT-TYPE
    SYNTAX      Counter64
    UNITS       "seconds"
    MAX-ACCESS  read-only
    STATUS      current
    DESCRIPTION
        "The value of tmnxBsxStatAaHCTermFlwDur indicates the sum of all flow
         durations from first packet seen to last packet seen for flows that
         have terminated. This object is a 64-bit version of
         tmnxBsxStatAaTermFlwDur."
    ::= { tmnxBsxStatAaEntry 34 }

tmnxBsxStatAaHCTermFlws          OBJECT-TYPE
    SYNTAX      Counter64
    UNITS       "flows"
    MAX-ACCESS  read-only
    STATUS      current
    DESCRIPTION
        "The value of tmnxBsxStatAaHCTermFlws indicates the total number of
         allowed flows in both directions that have terminated. This object is
         a 64-bit version of tmnxBsxStatAaTermFlws."
    ::= { tmnxBsxStatAaEntry 35 }

tmnxBsxStatAaHCShrtDurFlws       OBJECT-TYPE
    SYNTAX      Counter64
    UNITS       "flows"
    MAX-ACCESS  read-only
    STATUS      current
    DESCRIPTION
        "The value of tmnxBsxStatAaHCShrtDurFlws indicates the total number of
         flows with a duration less than or equal to 30 seconds, that have
         completed. This object is a 64-bit version of
         tmnxBsxStatAaShrtDurFlws."
    ::= { tmnxBsxStatAaEntry 36 }

tmnxBsxStatAaHCMedDurFlws        OBJECT-TYPE
    SYNTAX      Counter64
    UNITS       "flows"
    MAX-ACCESS  read-only
    STATUS      current
    DESCRIPTION
        "The value of tmnxBsxStatAaHCMedDurFlws indicates the total number of
         flows with a duration less than or equal to 180 seconds, but greater
         than 30 seconds, that have completed. This object is a 64-bit version
         of tmnxBsxStatAaMedDurFlws."
    ::= { tmnxBsxStatAaEntry 37 }

tmnxBsxStatAaHCLngDurFlws        OBJECT-TYPE
    SYNTAX      Counter64
    UNITS       "flows"
    MAX-ACCESS  read-only
    STATUS      current
    DESCRIPTION
        "The value of tmnxBsxStatAaHCLngDurFlws indicates the total number of
         flows with a duration greater than 180 seconds, that have completed.
         This object is a 64-bit version of tmnxBsxStatAaLngDurFlws."
    ::= { tmnxBsxStatAaEntry 38 }

tmnxBsxStatAaAppFilterTable      OBJECT-TYPE
    SYNTAX      SEQUENCE OF TmnxBsxStatAaAppFilterEntry
    MAX-ACCESS  not-accessible
    STATUS      current
    DESCRIPTION
        "The tmnxBsxStatAaAppFilterTable contains statistics for application
         filters as defined in the tmnxBsxAppFilterTable."
    ::= { tmnxBsxStatsObjs 8 }

tmnxBsxStatAaAppFilterEntry      OBJECT-TYPE
    SYNTAX      TmnxBsxStatAaAppFilterEntry
    MAX-ACCESS  not-accessible
    STATUS      current
    DESCRIPTION
        "Each tmnxBsxStatAaAppFilterEntry row contains statistics for a
         specific filter entry."
    INDEX       {
        tmnxBsxAaGrpPartIndex,
        tmnxBsxAppFilterEntryId
    }
    ::= { tmnxBsxStatAaAppFilterTable 1 }

TmnxBsxStatAaAppFilterEntry      ::= SEQUENCE
{
    tmnxBsxStatAaAppFilterHCFlows    Counter64,
    tmnxBsxStatAaAppFilterFlowsLo    Counter32,
    tmnxBsxStatAaAppFilterFlowsHi    Counter32,
    tmnxBsxStatAaAppFilterFlowHCOctC Counter64,
    tmnxBsxStatAaAppFilterFlowOctCLo Counter32,
    tmnxBsxStatAaAppFilterFlowOctCHi Counter32,
    tmnxBsxStatAaAppFltIpIdFlows     Counter64,
    tmnxBsxStatAaAppFltIpIdOcts      Counter64
}

tmnxBsxStatAaAppFilterHCFlows    OBJECT-TYPE
    SYNTAX      Counter64
    UNITS       "flows"
    MAX-ACCESS  read-only
    STATUS      current
    DESCRIPTION
        "The value of tmnxBsxStatAaAppFilterHCFlows indicates the number of
         flows that have matched this entry."
    ::= { tmnxBsxStatAaAppFilterEntry 1 }

tmnxBsxStatAaAppFilterFlowsLo    OBJECT-TYPE
    SYNTAX      Counter32
    UNITS       "flows"
    MAX-ACCESS  read-only
    STATUS      current
    DESCRIPTION
        "The value of tmnxBsxStatAaAppFilterFlowsLo indicates the lower 32-bits
         of tmnxBsxStatAaAppFilterHCFlows."
    ::= { tmnxBsxStatAaAppFilterEntry 2 }

tmnxBsxStatAaAppFilterFlowsHi    OBJECT-TYPE
    SYNTAX      Counter32
    UNITS       "flows"
    MAX-ACCESS  read-only
    STATUS      current
    DESCRIPTION
        "The value of tmnxBsxStatAaAppFilterFlowsHi indicates the upper 32-bits
         of tmnxBsxStatAaAppFilterHCFlows."
    ::= { tmnxBsxStatAaAppFilterEntry 3 }

tmnxBsxStatAaAppFilterFlowHCOctC OBJECT-TYPE
    SYNTAX      Counter64
    UNITS       "octets"
    MAX-ACCESS  read-only
    STATUS      current
    DESCRIPTION
        "The value of tmnxBsxStatAaAppFilterFlowHCOctC indicates the number of
         octets in the flows that have matched this entry."
    ::= { tmnxBsxStatAaAppFilterEntry 4 }

tmnxBsxStatAaAppFilterFlowOctCLo OBJECT-TYPE
    SYNTAX      Counter32
    UNITS       "octets"
    MAX-ACCESS  read-only
    STATUS      current
    DESCRIPTION
        "The value of tmnxBsxStatAaAppFilterFlowOctCLo indicates the lower
         32-bits of tmnxBsxStatAaAppFilterFlowHCOctC."
    ::= { tmnxBsxStatAaAppFilterEntry 5 }

tmnxBsxStatAaAppFilterFlowOctCHi OBJECT-TYPE
    SYNTAX      Counter32
    UNITS       "octets"
    MAX-ACCESS  read-only
    STATUS      current
    DESCRIPTION
        "The value of tmnxBsxStatAaAppFilterFlowOctCHi indicates the upper
         32-bits of tmnxBsxStatAaAppFilterFlowHCOctC."
    ::= { tmnxBsxStatAaAppFilterEntry 6 }

tmnxBsxStatAaAppFltIpIdFlows     OBJECT-TYPE
    SYNTAX      Counter64
    UNITS       "flows"
    MAX-ACCESS  read-only
    STATUS      current
    DESCRIPTION
        "The value of tmnxBsxStatAaAppFltIpIdFlows indicates
         the number of flows that matched this app-filter entry and
         the ip-identification-assist database.  These flows use
         the ip-assisted application as opposed to the app-filter
         entry application."
    ::= { tmnxBsxStatAaAppFilterEntry 7 }

tmnxBsxStatAaAppFltIpIdOcts      OBJECT-TYPE
    SYNTAX      Counter64
    UNITS       "octets"
    MAX-ACCESS  read-only
    STATUS      current
    DESCRIPTION
        "The value of tmnxBsxStatAaAppFltIpIdOcts indicates the
         number of packets that matched this app-filter entry and
         the ip-identification-assist database.  These flows use
         the ip-assisted application as opposed to the app-filter
         entry application."
    ::= { tmnxBsxStatAaAppFilterEntry 8 }

tmnxBsxStatIsaAaCfgTable         OBJECT-TYPE
    SYNTAX      SEQUENCE OF TmnxBsxStatIsaAaCfgEntry
    MAX-ACCESS  not-accessible
    STATUS      current
    DESCRIPTION
        "The tmnxBsxStatIsaAaCfgTable contains an entry for each ISA-AA group
         and ISA-AA group statistics type in the system. Each row contains the
         accounting policy and statistics configuration for the applicable
         ISA-AA group and ISA-AA group statistics type."
    ::= { tmnxBsxStatsObjs 9 }

tmnxBsxStatIsaAaCfgEntry         OBJECT-TYPE
    SYNTAX      TmnxBsxStatIsaAaCfgEntry
    MAX-ACCESS  not-accessible
    STATUS      current
    DESCRIPTION
        "The tmnxBsxStatIsaAaCfgEntry consists of the statistics configuration
         for an ISA-AA group."
    INDEX       {
        tmnxBsxIsaAaGroupIndex,
        tmnxBsxStatIsaAaCfgType
    }
    ::= { tmnxBsxStatIsaAaCfgTable 1 }

TmnxBsxStatIsaAaCfgEntry         ::= SEQUENCE
{
    tmnxBsxStatIsaAaCfgType          TmnxBsxStatIsaAaCfgType,
    tmnxBsxStatIsaAaCfgCollStats     TruthValue,
    tmnxBsxStatIsaAaCfgPolicy        Unsigned32
}

tmnxBsxStatIsaAaCfgType          OBJECT-TYPE
    SYNTAX      TmnxBsxStatIsaAaCfgType
    MAX-ACCESS  not-accessible
    STATUS      current
    DESCRIPTION
        "The value of tmnxBsxStatIsaAaCfgType specifies the ISA-AA group
         statistics configuration type for the row. The tmnxBsxStatIsaAaCfgType
         of 'unknown(0)' is not a valid index value."
    ::= { tmnxBsxStatIsaAaCfgEntry 1 }

tmnxBsxStatIsaAaCfgCollStats     OBJECT-TYPE
    SYNTAX      TruthValue
    MAX-ACCESS  read-write
    STATUS      current
    DESCRIPTION
        "The value of tmnxBsxStatIsaAaCfgCollStats specifies that statistics
         collection is enabled."
    DEFVAL      { false }
    ::= { tmnxBsxStatIsaAaCfgEntry 2 }

tmnxBsxStatIsaAaCfgPolicy        OBJECT-TYPE
    SYNTAX      Unsigned32 (0..99)
    MAX-ACCESS  read-write
    STATUS      current
    DESCRIPTION
        "The value of tmnxBsxStatIsaAaCfgPolicy specifies the accounting policy
         to use. The value 0 is used to disable the accounting policy."
    DEFVAL      { 0 }
    ::= { tmnxBsxStatIsaAaCfgEntry 3 }

tmnxBsxTrafStatTable             OBJECT-TYPE
    SYNTAX      SEQUENCE OF TmnxBsxTrafStatEntry
    MAX-ACCESS  not-accessible
    STATUS      current
    DESCRIPTION
        "The tmnxBsxTrafStatTable contains an entry for each system wide IP
         Protocol and IP Family pairing per group and partition."
    ::= { tmnxBsxStatsObjs 10 }

tmnxBsxTrafStatEntry             OBJECT-TYPE
    SYNTAX      TmnxBsxTrafStatEntry
    MAX-ACCESS  not-accessible
    STATUS      current
    DESCRIPTION
        "Each tmnxBsxTrafStatEntry contains the traffic statistics for a
         particular group, partition, IP Protocol and IP Family. "
    INDEX       {
        tmnxBsxAaGrpPartIndex,
        tmnxBsxTrafStatIpProtocol,
        tmnxBsxTrafStatIpFamily
    }
    ::= { tmnxBsxTrafStatTable 1 }

TmnxBsxTrafStatEntry             ::= SEQUENCE
{
    tmnxBsxTrafStatIpProtocol        INTEGER,
    tmnxBsxTrafStatIpFamily          INTEGER,
    tmnxBsxTrafStatDiscontTime       TimeStamp,
    tmnxBsxTrafStatOctsAdmFmSb       Counter64,
    tmnxBsxTrafStatPktsAdmFmSb       Counter64,
    tmnxBsxTrafStatFlwsAdmFmSb       Counter64,
    tmnxBsxTrafStatOctsDnyFmSb       Counter64,
    tmnxBsxTrafStatPktsDnyFmSb       Counter64,
    tmnxBsxTrafStatFlwsDnyFmSb       Counter64,
    tmnxBsxTrafStatOctsAdmToSb       Counter64,
    tmnxBsxTrafStatPktsAdmToSb       Counter64,
    tmnxBsxTrafStatFlwsAdmToSb       Counter64,
    tmnxBsxTrafStatOctsDnyToSb       Counter64,
    tmnxBsxTrafStatPktsDnyToSb       Counter64,
    tmnxBsxTrafStatFlwsDnyToSb       Counter64,
    tmnxBsxTrafStatTermFlwDur        Counter64,
    tmnxBsxTrafStatTermFlws          Counter64,
    tmnxBsxTrafStatShrtDurFlws       Counter64,
    tmnxBsxTrafStatMedDurFlws        Counter64,
    tmnxBsxTrafStatLngDurFlws        Counter64,
    tmnxBsxTrafStatActFlwsFmSb       Gauge32,
    tmnxBsxTrafStatActFlwsToSb       Gauge32
}

tmnxBsxTrafStatIpProtocol        OBJECT-TYPE
    SYNTAX      INTEGER {
        other (1),
        tcp   (2),
        udp   (3)
    }
    MAX-ACCESS  not-accessible
    STATUS      current
    DESCRIPTION
        "The value of tmnxBsxTrafStatIpProtocol specifies the IP Protocol for
         the traffic statistics.

         IP Protocol values may be one of:
                   other (1) - all IP protocols not listed below
                   tcp   (2) - TCP traffic
                   udp   (3) - UDP traffic"
    ::= { tmnxBsxTrafStatEntry 1 }

tmnxBsxTrafStatIpFamily          OBJECT-TYPE
    SYNTAX      INTEGER {
        ipv4      (1),
        ipv6      (2),
        dsLite    (3),
        sixRd     (4),
        teredo    (5),
        v4inv4Gtp (6),
        v4inv6Gtp (7),
        v6inv4Gtp (8),
        v6inv6Gtp (9)
    }
    MAX-ACCESS  not-accessible
    STATUS      current
    DESCRIPTION
        "The value of tmnxBsxTrafStatIpFamily specifies the IP Family for the
         traffic statistics.

         IP Family values may be one of:
                ipv4      (1) - IPv4
                ipv6      (2) - IPv6
                dsLite    (3) - IPv4 tunneled inside IPv6
                sixRd     (4) - IPv6 tunneled inside IPv4, includes 6rd, 6to4
                teredo    (5) - IPv6 tunneled inside UDP, tunneled inside IPv4
                v4inv4Gtp (6) - IPv4 tunneled inside IPv4 GTP
                v4inv6Gtp (7) - IPv4 tunneled inside IPv6 GTP
                v6inv4Gtp (8) - IPv6 tunneled inside IPv4 GTP
                v6inv6Gtp (9) - IPv6 tunneled inside IPv6 GTP"
    ::= { tmnxBsxTrafStatEntry 2 }

tmnxBsxTrafStatDiscontTime       OBJECT-TYPE
    SYNTAX      TimeStamp
    MAX-ACCESS  read-only
    STATUS      current
    DESCRIPTION
        "The value of tmnxBsxTrafStatDiscontTime indicates the
         SNMPv2-MIB::sysUpTime (centiseconds) when any of the active ISA-AA
         within the group last changed status."
    ::= { tmnxBsxTrafStatEntry 3 }

tmnxBsxTrafStatOctsAdmFmSb       OBJECT-TYPE
    SYNTAX      Counter64
    UNITS       "bytes"
    MAX-ACCESS  read-only
    STATUS      current
    DESCRIPTION
        "The value of tmnxBsxTrafStatOctsAdmFmSb indicates the total number of
         bytes permitted for the subscriber to network direction."
    ::= { tmnxBsxTrafStatEntry 4 }

tmnxBsxTrafStatPktsAdmFmSb       OBJECT-TYPE
    SYNTAX      Counter64
    UNITS       "packets"
    MAX-ACCESS  read-only
    STATUS      current
    DESCRIPTION
        "The value of tmnxBsxTrafStatPktsAdmFmSb indicates the total number of
         packets permitted for the subscriber to network direction."
    ::= { tmnxBsxTrafStatEntry 5 }

tmnxBsxTrafStatFlwsAdmFmSb       OBJECT-TYPE
    SYNTAX      Counter64
    UNITS       "flows"
    MAX-ACCESS  read-only
    STATUS      current
    DESCRIPTION
        "The value of tmnxBsxTrafStatFlwsAdmFmSb indicates the total number of
         flows permitted for the subscriber to network direction."
    ::= { tmnxBsxTrafStatEntry 6 }

tmnxBsxTrafStatOctsDnyFmSb       OBJECT-TYPE
    SYNTAX      Counter64
    UNITS       "bytes"
    MAX-ACCESS  read-only
    STATUS      current
    DESCRIPTION
        "The value of tmnxBsxTrafStatOctsDnyFmSb indicates the total number of
         bytes dropped for the subscriber to network direction."
    ::= { tmnxBsxTrafStatEntry 7 }

tmnxBsxTrafStatPktsDnyFmSb       OBJECT-TYPE
    SYNTAX      Counter64
    UNITS       "packets"
    MAX-ACCESS  read-only
    STATUS      current
    DESCRIPTION
        "The value of tmnxBsxTrafStatPktsDnyFmSb indicates the total number of
         packets dropped for the subscriber to network direction."
    ::= { tmnxBsxTrafStatEntry 8 }

tmnxBsxTrafStatFlwsDnyFmSb       OBJECT-TYPE
    SYNTAX      Counter64
    UNITS       "flows"
    MAX-ACCESS  read-only
    STATUS      current
    DESCRIPTION
        "The value of tmnxBsxTrafStatFlwsDnyFmSb indicates the total number of
         flows that dropped subsequent packets in the subscriber to network
         direction."
    ::= { tmnxBsxTrafStatEntry 9 }

tmnxBsxTrafStatOctsAdmToSb       OBJECT-TYPE
    SYNTAX      Counter64
    UNITS       "bytes"
    MAX-ACCESS  read-only
    STATUS      current
    DESCRIPTION
        "The value of tmnxBsxTrafStatOctsAdmToSb indicates the total number of
         bytes permitted for the network to subscriber direction."
    ::= { tmnxBsxTrafStatEntry 10 }

tmnxBsxTrafStatPktsAdmToSb       OBJECT-TYPE
    SYNTAX      Counter64
    UNITS       "packets"
    MAX-ACCESS  read-only
    STATUS      current
    DESCRIPTION
        "The value of tmnxBsxTrafStatPktsAdmToSb indicates the total number of
         packets permitted for the network to subscriber direction."
    ::= { tmnxBsxTrafStatEntry 11 }

tmnxBsxTrafStatFlwsAdmToSb       OBJECT-TYPE
    SYNTAX      Counter64
    UNITS       "flows"
    MAX-ACCESS  read-only
    STATUS      current
    DESCRIPTION
        "The value of tmnxBsxTrafStatFlwsAdmToSb indicates the total number of
         flows permitted for the network to subscriber direction."
    ::= { tmnxBsxTrafStatEntry 12 }

tmnxBsxTrafStatOctsDnyToSb       OBJECT-TYPE
    SYNTAX      Counter64
    UNITS       "bytes"
    MAX-ACCESS  read-only
    STATUS      current
    DESCRIPTION
        "The value of tmnxBsxTrafStatOctsDnyToSb indicates the total number of
         bytes dropped for the network to subscriber direction."
    ::= { tmnxBsxTrafStatEntry 13 }

tmnxBsxTrafStatPktsDnyToSb       OBJECT-TYPE
    SYNTAX      Counter64
    UNITS       "packets"
    MAX-ACCESS  read-only
    STATUS      current
    DESCRIPTION
        "The value of tmnxBsxTrafStatPktsDnyToSb indicates the total number of
         packets dropped for the network to subscriber direction."
    ::= { tmnxBsxTrafStatEntry 14 }

tmnxBsxTrafStatFlwsDnyToSb       OBJECT-TYPE
    SYNTAX      Counter64
    UNITS       "flows"
    MAX-ACCESS  read-only
    STATUS      current
    DESCRIPTION
        "The value of tmnxBsxTrafStatFlwsDnyToSb indicates the total number of
         flows that dropped subsequent packets in the network to subscriber
         direction."
    ::= { tmnxBsxTrafStatEntry 15 }

tmnxBsxTrafStatTermFlwDur        OBJECT-TYPE
    SYNTAX      Counter64
    UNITS       "seconds"
    MAX-ACCESS  read-only
    STATUS      current
    DESCRIPTION
        "The value of tmnxBsxTrafStatTermFlwDur indicates the sum of all flow
         durations from first packet seen to last packet seen for flows that
         have terminated."
    ::= { tmnxBsxTrafStatEntry 16 }

tmnxBsxTrafStatTermFlws          OBJECT-TYPE
    SYNTAX      Counter64
    UNITS       "flows"
    MAX-ACCESS  read-only
    STATUS      current
    DESCRIPTION
        "The value of tmnxBsxTrafStatTermFlws indicates the total number of
         allowed flows in both directions that have terminated."
    ::= { tmnxBsxTrafStatEntry 17 }

tmnxBsxTrafStatShrtDurFlws       OBJECT-TYPE
    SYNTAX      Counter64
    UNITS       "flows"
    MAX-ACCESS  read-only
    STATUS      current
    DESCRIPTION
        "The value of tmnxBsxTrafStatShrtDurFlws indicates the total number of
         flows with a duration less than or equal to 30 seconds, that have
         completed."
    ::= { tmnxBsxTrafStatEntry 18 }

tmnxBsxTrafStatMedDurFlws        OBJECT-TYPE
    SYNTAX      Counter64
    UNITS       "flows"
    MAX-ACCESS  read-only
    STATUS      current
    DESCRIPTION
        "The value of tmnxBsxTrafStatMedDurFlws indicates the total number of
         flows with a duration less than or equal to 180 seconds, but greater
         than 30 seconds, that have completed."
    ::= { tmnxBsxTrafStatEntry 19 }

tmnxBsxTrafStatLngDurFlws        OBJECT-TYPE
    SYNTAX      Counter64
    UNITS       "flows"
    MAX-ACCESS  read-only
    STATUS      current
    DESCRIPTION
        "The value of tmnxBsxTrafStatLngDurFlws indicates the total number of
         flows with a duration greater than 180 seconds, that have completed."
    ::= { tmnxBsxTrafStatEntry 20 }

tmnxBsxTrafStatActFlwsFmSb       OBJECT-TYPE
    SYNTAX      Gauge32
    UNITS       "flows"
    MAX-ACCESS  read-only
    STATUS      current
    DESCRIPTION
        "The value of tmnxBsxTrafStatActFlwsFmSb indicates the number of
         allowed flows in the subscriber to network direction that are active."
    ::= { tmnxBsxTrafStatEntry 21 }

tmnxBsxTrafStatActFlwsToSb       OBJECT-TYPE
    SYNTAX      Gauge32
    UNITS       "flows"
    MAX-ACCESS  read-only
    STATUS      current
    DESCRIPTION
        "The value of tmnxBsxTrafStatActFlwsToSb indicates the number of
         allowed flows in the network to subscriber direction that are active."
    ::= { tmnxBsxTrafStatEntry 22 }

tmnxBsxPartAcctCfgTable          OBJECT-TYPE
    SYNTAX      SEQUENCE OF TmnxBsxPartAcctCfgEntry
    MAX-ACCESS  not-accessible
    STATUS      current
    DESCRIPTION
        "The tmnxBsxPartAcctCfgTable contains an entry for each configured ISA
         AA Group and Partition configured in the system.

         Rows in this table are automatically created and destroyed when the AA
         Partition is created or destroyed using the tmnxBsxAaGrpPartTable."
    ::= { tmnxBsxStatsObjs 11 }

tmnxBsxPartAcctCfgEntry          OBJECT-TYPE
    SYNTAX      TmnxBsxPartAcctCfgEntry
    MAX-ACCESS  not-accessible
    STATUS      current
    DESCRIPTION
        "Each tmnxBsxPartAcctCfgEntry indicates the ISA-AA statistics that are
         configured per ISA-AA Group and Partition."
    INDEX       { tmnxBsxAaGrpPartIndex }
    ::= { tmnxBsxPartAcctCfgTable 1 }

TmnxBsxPartAcctCfgEntry          ::= SEQUENCE
{
    tmnxBsxPartAcctCfgRowLastCh      TimeStamp,
    tmnxBsxPartAcctCfgCollStats      TmnxEnabledDisabled,
    tmnxBsxPartAcctCfgPolicy         Unsigned32,
    tmnxBsxPartAcctCfgTrafStats      TmnxEnabledDisabled,
    tmnxBsxPartAcctCfgTetherStats    TmnxEnabledDisabled
}

tmnxBsxPartAcctCfgRowLastCh      OBJECT-TYPE
    SYNTAX      TimeStamp
    MAX-ACCESS  read-only
    STATUS      current
    DESCRIPTION
        "The value of tmnxBsxPartAcctCfgRowLastCh indicates the last time,
         since system startup, a successful set was performed on this row."
    ::= { tmnxBsxPartAcctCfgEntry 1 }

tmnxBsxPartAcctCfgCollStats      OBJECT-TYPE
    SYNTAX      TmnxEnabledDisabled
    MAX-ACCESS  read-write
    STATUS      current
    DESCRIPTION
        "The value of tmnxBsxPartAcctCfgCollStats specifies whether or not
         statistics collection is enabled."
    DEFVAL      { disabled }
    ::= { tmnxBsxPartAcctCfgEntry 2 }

tmnxBsxPartAcctCfgPolicy         OBJECT-TYPE
    SYNTAX      Unsigned32 (0..99)
    MAX-ACCESS  read-write
    STATUS      current
    DESCRIPTION
        "The value of tmnxBsxPartAcctCfgPolicy specifies the accounting policy
         to use. The value 0 is used to disable the accounting policy."
    DEFVAL      { 0 }
    ::= { tmnxBsxPartAcctCfgEntry 3 }

tmnxBsxPartAcctCfgTrafStats      OBJECT-TYPE
    SYNTAX      TmnxEnabledDisabled
    MAX-ACCESS  read-write
    STATUS      current
    DESCRIPTION
        "The value of tmnxBsxPartAcctCfgTrafStats specifies whether traffic
         statistics collection will occur when tmnxBsxPartAcctCfgCollStats is
         enabled."
    DEFVAL      { disabled }
    ::= { tmnxBsxPartAcctCfgEntry 4 }

tmnxBsxPartAcctCfgTetherStats    OBJECT-TYPE
    SYNTAX      TmnxEnabledDisabled
    MAX-ACCESS  read-write
    STATUS      current
    DESCRIPTION
        "The value of tmnxBsxPartAcctCfgTetherStats specifies whether tethering
         statistics collection will occur when tmnxBsxPartAcctCfgCollStats is
         enabled."
    DEFVAL      { disabled }
    ::= { tmnxBsxPartAcctCfgEntry 5 }

tmnxBsxAaSubUsageMonTable        OBJECT-TYPE
    SYNTAX      SEQUENCE OF TmnxBsxAaSubUsageMonEntry
    MAX-ACCESS  not-accessible
    STATUS      current
    DESCRIPTION
        "The value of object tmnxBsxAaSubUsageMonTable specifies an entry for
         each Application-Assurance subscriber for each statistics type within
         a group, partition and statistics interval.

         Each row contains the Application Assurance usage monitoring
         statistics collected for the subscriber, based on configuration in
         tmnxBsxStatAaSubCfgTable. Entries are based on Policy and Charging
         Control (PCC) rules received from the policy server which contain
         subscriber, and statistic type/name information. A subscriber is
         uniquely identified by a tmnxBsxAaSubscriberType and
         tmnxBsxAaSubscriber.

         The typical usage of this table is to fill in the part of the index
         that identifies a subscriber (tmnxBsxAaGrpPartIndex,
         tmnxBsxAaSubStatsInterval, tmnxBsxAaSubscriberType and
         tmnxBsxAaSubscriber), and perform a partial walk to retrieve the usage
         information. In order to prevent real-time issues, an SNMP get next
         request which results in a change in subscriber will return not-found."
    ::= { tmnxBsxStatsObjs 12 }

tmnxBsxAaSubUsageMonEntry        OBJECT-TYPE
    SYNTAX      TmnxBsxAaSubUsageMonEntry
    MAX-ACCESS  not-accessible
    STATUS      current
    DESCRIPTION
        "The value of object tmnxBsxAaSubUsageMonEntry specifies an entry which
         stores the Application Assurance usage monitoring statistics for a
         combination of group, partition, statistics interval, subscriber,
         statistics type, and statistics name. An entry is added when a new
         rule is sent from the policy server.

         As protocols are not supported by Application Assurance usage
         monitoring, the tmnxBsxStatAaType value of 'protocol (1)' will never
         appear as part of the index.

         As only snapshot statistics collection is supported by Application
         Assurance usage monitoring, the tmnxBsxAaSubStatsInterval value of
         'snapshot (2)' will always appear as part of the index. "
    INDEX       {
        tmnxBsxAaGrpPartIndex,
        tmnxBsxAaSubStatsInterval,
        tmnxBsxAaSubscriberType,
        tmnxBsxAaSubscriber,
        tmnxBsxStatAaType,
        IMPLIED tmnxBsxStatAaName
    }
    ::= { tmnxBsxAaSubUsageMonTable 1 }

TmnxBsxAaSubUsageMonEntry        ::= SEQUENCE
{
    tmnxBsxAaSubUMOperStatus         TmnxBsxUmOperStatus,
    tmnxBsxAaSubUMToSubGrantStatus   TmnxBsxUmGrantStatus,
    tmnxBsxAaSubUMFmSubGrantStatus   TmnxBsxUmGrantStatus,
    tmnxBsxAaSubUMBothGrantStatus    TmnxBsxUmGrantStatus,
    tmnxBsxAaSubUMToSubGrantCredit   Counter64,
    tmnxBsxAaSubUMFmSubGrantCredit   Counter64,
    tmnxBsxAaSubUMBothGrantCredit    Counter64,
    tmnxBsxAaSubUMToSubUsedCredit    Counter64,
    tmnxBsxAaSubUMFmSubUsedCredit    Counter64,
    tmnxBsxAaSubUMBothUsedCredit     Counter64
}

tmnxBsxAaSubUMOperStatus         OBJECT-TYPE
    SYNTAX      TmnxBsxUmOperStatus
    MAX-ACCESS  read-only
    STATUS      current
    DESCRIPTION
        "The value of tmnxBsxAaSubUMOperStatus indicates the operational state
         for the usage monitor. When 'active (2)', a rule has been received and
         credits have been sent from policy server. When 'inactive (1)', a rule
         has been received but no credits have been sent from policy server.
         When 'adminDisabled (0)', a rule has been 'shutdown' on the policy
         server."
    ::= { tmnxBsxAaSubUsageMonEntry 1 }

tmnxBsxAaSubUMToSubGrantStatus   OBJECT-TYPE
    SYNTAX      TmnxBsxUmGrantStatus
    MAX-ACCESS  read-only
    STATUS      current
    DESCRIPTION
        "The value of tmnxBsxAaSubUMToSubGrantStatus indicates grant status for
         the network to subscriber direction."
    ::= { tmnxBsxAaSubUsageMonEntry 2 }

tmnxBsxAaSubUMFmSubGrantStatus   OBJECT-TYPE
    SYNTAX      TmnxBsxUmGrantStatus
    MAX-ACCESS  read-only
    STATUS      current
    DESCRIPTION
        "The value of tmnxBsxAaSubUMFmSubGrantStatus indicates grant status for
         the subscriber to network direction."
    ::= { tmnxBsxAaSubUsageMonEntry 3 }

tmnxBsxAaSubUMBothGrantStatus    OBJECT-TYPE
    SYNTAX      TmnxBsxUmGrantStatus
    MAX-ACCESS  read-only
    STATUS      current
    DESCRIPTION
        "The value of tmnxBsxAaSubUMBothGrantStatus indicates grant status for
         the network to subscriber direction."
    ::= { tmnxBsxAaSubUsageMonEntry 4 }

tmnxBsxAaSubUMToSubGrantCredit   OBJECT-TYPE
    SYNTAX      Counter64
    UNITS       "octets"
    MAX-ACCESS  read-only
    STATUS      current
    DESCRIPTION
        "The value of tmnxBsxAaSubUMToSubGrantCredit indicates the amount of
         credits allocated by the policy server for the network to subscriber
         direction."
    ::= { tmnxBsxAaSubUsageMonEntry 5 }

tmnxBsxAaSubUMFmSubGrantCredit   OBJECT-TYPE
    SYNTAX      Counter64
    UNITS       "octets"
    MAX-ACCESS  read-only
    STATUS      current
    DESCRIPTION
        "The value of tmnxBsxAaSubUMFmSubGrantCredit indicates the amount of
         credits allocated by the policy server for the subscriber to network
         direction."
    ::= { tmnxBsxAaSubUsageMonEntry 6 }

tmnxBsxAaSubUMBothGrantCredit    OBJECT-TYPE
    SYNTAX      Counter64
    UNITS       "octets"
    MAX-ACCESS  read-only
    STATUS      current
    DESCRIPTION
        "The value of tmnxBsxAaSubUMBothGrantCredit indicates the amount of
         credits allocated by the policy server for either direction."
    ::= { tmnxBsxAaSubUsageMonEntry 7 }

tmnxBsxAaSubUMToSubUsedCredit    OBJECT-TYPE
    SYNTAX      Counter64
    UNITS       "octets"
    MAX-ACCESS  read-only
    STATUS      current
    DESCRIPTION
        "The value of tmnxBsxAaSubUMToSubUsedCredit indicates the amount of
         credits used by the network to subscriber direction."
    ::= { tmnxBsxAaSubUsageMonEntry 8 }

tmnxBsxAaSubUMFmSubUsedCredit    OBJECT-TYPE
    SYNTAX      Counter64
    UNITS       "octets"
    MAX-ACCESS  read-only
    STATUS      current
    DESCRIPTION
        "The value of tmnxBsxAaSubUMFmSubUsedCredit indicates the amount of
         credits used by the subscriber to network direction."
    ::= { tmnxBsxAaSubUsageMonEntry 9 }

tmnxBsxAaSubUMBothUsedCredit     OBJECT-TYPE
    SYNTAX      Counter64
    UNITS       "octets"
    MAX-ACCESS  read-only
    STATUS      current
    DESCRIPTION
        "The value of tmnxBsxAaSubUMBothUsedCredit indicates the amount of
         credits used by either direction."
    ::= { tmnxBsxAaSubUsageMonEntry 10 }

tmnxBsxDnsIpCacheStatTable       OBJECT-TYPE
    SYNTAX      SEQUENCE OF TmnxBsxDnsIpCacheStatEntry
    MAX-ACCESS  not-accessible
    STATUS      current
    DESCRIPTION
        "The tmnxBsxDnsIpCacheStatTable contains an entry for each configured
         Application Assurance DNS IP Cache.

         Rows in this table are automatically created and destroyed when DNS IP
         Caches are created or destroyed using the tmnxBsxDnsIpCacheTable."
    ::= { tmnxBsxStatsObjs 13 }

tmnxBsxDnsIpCacheStatEntry       OBJECT-TYPE
    SYNTAX      TmnxBsxDnsIpCacheStatEntry
    MAX-ACCESS  not-accessible
    STATUS      current
    DESCRIPTION
        "Each tmnxBsxDnsIpCacheStatEntry specifies Application Assurance DNS IP
         Cache statistics.

         An index with a valid DNS IP Cache (an existing row in
         tmnxBsxDnsIpCacheTable) and tmnxChassisIndex set to one with a zero
         value for each of tmnxBsxCardSlotEsaId and tmnxBsxMdaSlotEsaVmId will
         return the summarized statistics per group and DNS IP Cache."
    INDEX       {
        tmnxBsxIsaAaGroupIndex,
        tmnxBsxDnsIpCacheName,
        tmnxChassisIndex,
        tmnxBsxCardSlotEsaId,
        tmnxBsxMdaSlotEsaVmId
    }
    ::= { tmnxBsxDnsIpCacheStatTable 1 }

TmnxBsxDnsIpCacheStatEntry       ::= SEQUENCE
{
    tmnxBsxDnsIpCacheStatDnsResp     Counter64,
    tmnxBsxDnsIpCacheStatDomMtch     Counter64,
    tmnxBsxDnsIpCacheStatDomSerMtch  Counter64,
    tmnxBsxDnsIpCacheStatAlarmClear  TruthValue,
    tmnxBsxDnsIpCacheStatEntrAdd     Counter64,
    tmnxBsxDnsIpCacheStatEntrRmvd    Counter64,
    tmnxBsxDnsIpCacheStatFullCnt     Counter64,
    tmnxBsxDnsIpCacheStatHitCnt      Counter64,
    tmnxBsxDnsIpCacheStatMissCnt     Counter64,
    tmnxBsxDnsIpCacheStatDiscntTime  TimeStamp,
    tmnxBsxDnsIpCacheStatPrxyMtchCnt Counter64
}

tmnxBsxDnsIpCacheStatDnsResp     OBJECT-TYPE
    SYNTAX      Counter64
    MAX-ACCESS  read-only
    STATUS      current
    DESCRIPTION
        "The value of tmnxBsxDnsIpCacheStatDnsResp indicates the number of DNS
         responses that have been compared to the entries in the
         tmnxBsxDnsIpCacheDomainTable and the tmnxBsxDnsIpCacheServerTable
         associated with this cache."
    ::= { tmnxBsxDnsIpCacheStatEntry 1 }

tmnxBsxDnsIpCacheStatDomMtch     OBJECT-TYPE
    SYNTAX      Counter64
    MAX-ACCESS  read-only
    STATUS      current
    DESCRIPTION
        "The value of tmnxBsxDnsIpCacheStatDomMtch indicates the number of DNS
         response domains that have matched an entry in the
         tmnxBsxDnsIpCacheDomainTable associated with this cache."
    ::= { tmnxBsxDnsIpCacheStatEntry 2 }

tmnxBsxDnsIpCacheStatDomSerMtch  OBJECT-TYPE
    SYNTAX      Counter64
    MAX-ACCESS  read-only
    STATUS      current
    DESCRIPTION
        "The value of tmnxBsxDnsIpCacheStatDomSerMtch indicates the number of
         DNS responses whose domain matched an entry in the
         tmnxBsxDnsIpCacheDomainTable and server IP address matched an entry in
         the tmnxBsxDnsIpCacheServerTable associated with this cache."
    ::= { tmnxBsxDnsIpCacheStatEntry 3 }

tmnxBsxDnsIpCacheStatAlarmClear  OBJECT-TYPE
    SYNTAX      TruthValue
    MAX-ACCESS  read-only
    STATUS      current
    DESCRIPTION
        "The value of tmnxBsxDnsIpCacheStatAlarmClear indicates the state of
         the threshold alarm for this cache. A value of 'true (1)' indicates
         the alarm is clear, and a value of 'false (2)' indicates the alarm is
         set."
    ::= { tmnxBsxDnsIpCacheStatEntry 4 }

tmnxBsxDnsIpCacheStatEntrAdd     OBJECT-TYPE
    SYNTAX      Counter64
    MAX-ACCESS  read-only
    STATUS      current
    DESCRIPTION
        "The value of tmnxBsxDnsIpCacheStatEntrAdd indicates the total number
         of entries that have been added to this cache."
    ::= { tmnxBsxDnsIpCacheStatEntry 5 }

tmnxBsxDnsIpCacheStatEntrRmvd    OBJECT-TYPE
    SYNTAX      Counter64
    MAX-ACCESS  read-only
    STATUS      current
    DESCRIPTION
        "The value of tmnxBsxDnsIpCacheStatEntrRmvd indicates the total number
         of entries that have been removed from this cache."
    ::= { tmnxBsxDnsIpCacheStatEntry 6 }

tmnxBsxDnsIpCacheStatFullCnt     OBJECT-TYPE
    SYNTAX      Counter64
    MAX-ACCESS  read-only
    STATUS      current
    DESCRIPTION
        "The value of tmnxBsxDnsIpCacheStatFullCnt indicates the number of
         times an entry could not be added because the cache was full."
    ::= { tmnxBsxDnsIpCacheStatEntry 7 }

tmnxBsxDnsIpCacheStatHitCnt      OBJECT-TYPE
    SYNTAX      Counter64
    MAX-ACCESS  read-only
    STATUS      current
    DESCRIPTION
        "The value of tmnxBsxDnsIpCacheStatHitCnt indicates the number of times
         an IP address lookup in this cache was successful."
    ::= { tmnxBsxDnsIpCacheStatEntry 8 }

tmnxBsxDnsIpCacheStatMissCnt     OBJECT-TYPE
    SYNTAX      Counter64
    MAX-ACCESS  read-only
    STATUS      current
    DESCRIPTION
        "The value of tmnxBsxDnsIpCacheStatMissCnt indicates the number of
         times an IP address lookup in this cache was unsuccessful."
    ::= { tmnxBsxDnsIpCacheStatEntry 9 }

tmnxBsxDnsIpCacheStatDiscntTime  OBJECT-TYPE
    SYNTAX      TimeStamp
    MAX-ACCESS  read-only
    STATUS      current
    DESCRIPTION
        "The value of tmnxBsxDnsIpCacheStatDiscntTime indicates the
         SNMPv2-MIB::sysUpTime (centiseconds) when the ISA-AA MDA within the
         group has last changed status."
    ::= { tmnxBsxDnsIpCacheStatEntry 10 }

tmnxBsxDnsIpCacheStatPrxyMtchCnt OBJECT-TYPE
    SYNTAX      Counter64
    MAX-ACCESS  read-only
    STATUS      current
    DESCRIPTION
        "The value of tmnxBsxDnsIpCacheStatPrxyMtchCnt indicates the number of
         times a DNS static IP address matched an address in the
         tmnxBsxDnsIpCacheProxyTable."
    ::= { tmnxBsxDnsIpCacheStatEntry 11 }

tmnxBsxUrlListStatusTable        OBJECT-TYPE
    SYNTAX      SEQUENCE OF TmnxBsxUrlListStatusEntry
    MAX-ACCESS  not-accessible
    STATUS      current
    DESCRIPTION
        "The tmnxBsxUrlListStatusTable contains an entry for each configured
         Application Assurance URL list.

         Rows in this table are automatically created and destroyed when URL
         lists are created or destroyed using the tmnxBsxUrlListTable."
    ::= { tmnxBsxStatsObjs 15 }

tmnxBsxUrlListStatusEntry        OBJECT-TYPE
    SYNTAX      TmnxBsxUrlListStatusEntry
    MAX-ACCESS  not-accessible
    STATUS      current
    DESCRIPTION
        "Each tmnxBsxUrlListStatusEntry specifies Application Assurance URL
         list operational status."
    INDEX       {
        tmnxBsxIsaAaGroupIndex,
        tmnxBsxUrlListName
    }
    ::= { tmnxBsxUrlListStatusTable 1 }

TmnxBsxUrlListStatusEntry        ::= SEQUENCE
{
    tmnxBsxUrlListStatusOperState    TmnxOperState,
    tmnxBsxUrlListStatusOperFlags    TmnxBsxUrlListFlags,
    tmnxBsxUrlListStatusNumEntries   Gauge32,
    tmnxBsxUrlListStatusUpgAttemptTm TimeStamp,
    tmnxBsxUrlListStatusUpgSuccessTm TimeStamp,
    tmnxBsxUrlListStatusUpgErrorLine Integer32,
    tmnxBsxUrlListStatusUpgErrReason TmnxBsxUrlListFlags,
    tmnxBsxUrlListStatusUpgErrDetail DisplayString,
    tmnxBsxUrlListStatusUpgLineSkipd Gauge32,
    tmnxBsxUrlListStatusUrlDeployed  TmnxDisplayStringURL,
    tmnxBsxUrlListStatusUrlAttempted TmnxDisplayStringURL,
    tmnxBsxUrlListStatusIsCfgUrlDpld TruthValue,
    tmnxBsxUrlListStatusNumChars     Gauge32,
    tmnxBsxUrlListStatusUpgInProgres TruthValue,
    tmnxBsxUrlListRegExprNumEntries  Gauge32
}

tmnxBsxUrlListStatusOperState    OBJECT-TYPE
    SYNTAX      TmnxOperState
    MAX-ACCESS  read-only
    STATUS      current
    DESCRIPTION
        "The value of tmnxBsxUrlListStatusOperState indicates the operational
         state of the URL list. When the value is 'outOfService (3)' the URL
         list is not active."
    ::= { tmnxBsxUrlListStatusEntry 1 }

tmnxBsxUrlListStatusOperFlags    OBJECT-TYPE
    SYNTAX      TmnxBsxUrlListFlags
    MAX-ACCESS  read-only
    STATUS      current
    DESCRIPTION
        "The value of tmnxBsxUrlListStatusOperFlags indicates the conditions
         that affect the operating status of the URL list."
    ::= { tmnxBsxUrlListStatusEntry 2 }

tmnxBsxUrlListStatusNumEntries   OBJECT-TYPE
    SYNTAX      Gauge32
    MAX-ACCESS  read-only
    STATUS      current
    DESCRIPTION
        "The value of tmnxBsxUrlListStatusNumEntries indicates the number of
         entries in the URL list, which were retrieved from the specified
         tmnxBsxUrlListFileUrl."
    ::= { tmnxBsxUrlListStatusEntry 3 }

tmnxBsxUrlListStatusUpgAttemptTm OBJECT-TYPE
    SYNTAX      TimeStamp
    MAX-ACCESS  read-only
    STATUS      current
    DESCRIPTION
        "The value of tmnxBsxUrlListStatusUpgAttemptTm indicates the most
         recent upgrade attempt time since system startup.

         When an upgrade is successful, tmnxBsxUrlListStatusUpgAttemptTm and
         tmnxBsxUrlListStatusUpgSuccessTm will be the same and the value of
         tmnxBsxUrlListStatusUpgInProgres will be 'false (2)'.

         A value of 0 indicates an upgrade has not been started since system
         startup."
    ::= { tmnxBsxUrlListStatusEntry 4 }

tmnxBsxUrlListStatusUpgSuccessTm OBJECT-TYPE
    SYNTAX      TimeStamp
    MAX-ACCESS  read-only
    STATUS      current
    DESCRIPTION
        "The value of tmnxBsxUrlListStatusUpgSuccessTm indicates the most
         recent successful upgrade time.

         When an upgrade is successful, tmnxBsxUrlListStatusUpgAttemptTm and
         tmnxBsxUrlListStatusUpgSuccessTm will be the same and the value of
         tmnxBsxUrlListStatusUpgInProgres will be 'false (2)'.

         A value of 0 indicates there has not been a successful upgrade of the
         URL list since system startup."
    ::= { tmnxBsxUrlListStatusEntry 5 }

tmnxBsxUrlListStatusUpgErrorLine OBJECT-TYPE
    SYNTAX      Integer32 (-1..2147483647)
    MAX-ACCESS  read-only
    STATUS      current
    DESCRIPTION
        "The value of tmnxBsxUrlListStatusUpgErrorLine indicates the
         approximate line from the specified tmnxBsxUrlListFileUrl which had an
         error while performing a URL list upgrade.

         A value of 0 indicates there was an error not associated with any
         line.

         A value of -1 indicates there was no error in the last upgrade."
    ::= { tmnxBsxUrlListStatusEntry 6 }

tmnxBsxUrlListStatusUpgErrReason OBJECT-TYPE
    SYNTAX      TmnxBsxUrlListFlags
    MAX-ACCESS  read-only
    STATUS      current
    DESCRIPTION
        "The value of tmnxBsxUrlListStatusUpgErrReason indicates the reason for
         the failure of the URL list upgrade, if applicable.

         The bit value 'adminDown (0)' is not supported on this object."
    ::= { tmnxBsxUrlListStatusEntry 7 }

tmnxBsxUrlListStatusUpgErrDetail OBJECT-TYPE
    SYNTAX      DisplayString
    MAX-ACCESS  read-only
    STATUS      current
    DESCRIPTION
        "The value of tmnxBsxUrlListStatusUpgErrDetail indicates the text
         reason for the failure of the URL list upgrade, if applicable."
    ::= { tmnxBsxUrlListStatusEntry 8 }

tmnxBsxUrlListStatusUpgLineSkipd OBJECT-TYPE
    SYNTAX      Gauge32
    MAX-ACCESS  read-only
    STATUS      current
    DESCRIPTION
        "The value of tmnxBsxUrlListStatusUpgLineSkipd indicates the number of
         lines that were skipped while processing the file configured in
         tmnxBsxUrlListFileUrl because they were empty (or comments) during the
         last URL list upgrade."
    ::= { tmnxBsxUrlListStatusEntry 9 }

tmnxBsxUrlListStatusUrlDeployed  OBJECT-TYPE
    SYNTAX      TmnxDisplayStringURL
    MAX-ACCESS  read-only
    STATUS      current
    DESCRIPTION
        "The value of tmnxBsxUrlListStatusUrlDeployed indicates the filename on
         compact flash at the time of the most recent URL list upgrade success.

         An empty string indicates there hasn't been a successful upgrade."
    ::= { tmnxBsxUrlListStatusEntry 10 }

tmnxBsxUrlListStatusUrlAttempted OBJECT-TYPE
    SYNTAX      TmnxDisplayStringURL
    MAX-ACCESS  read-only
    STATUS      current
    DESCRIPTION
        "The value of tmnxBsxUrlListStatusUrlAttempted indicates the filename
         on compact flash at the time of the most recent URL list upgrade
         attempt.

         An empty string indicates there hasn't been an upgrade attempt."
    ::= { tmnxBsxUrlListStatusEntry 11 }

tmnxBsxUrlListStatusIsCfgUrlDpld OBJECT-TYPE
    SYNTAX      TruthValue
    MAX-ACCESS  read-only
    STATUS      current
    DESCRIPTION
        "The value of tmnxBsxUrlListStatusIsCfgUrlDpld indicates whether or not
         the configured file has been deployed to all AA-ISAs in this group. A
         value of 'true (1)' indicates the configured url-list file is currently
         deployed on AA-ISAs in this group.  A value of 'false (2)' indicates
         the configured url-list file is different from the one currently
         deployed on AA-ISAs in this group. tmnxBsxUrlListUpgrade or
         tmnxBsxUrlListAdminState can be used to deploy the configured list."
    ::= { tmnxBsxUrlListStatusEntry 12 }

tmnxBsxUrlListStatusNumChars     OBJECT-TYPE
    SYNTAX      Gauge32
    MAX-ACCESS  read-only
    STATUS      current
    DESCRIPTION
        "The value of tmnxBsxUrlListStatusNumChars indicates the number of
         characters in the URLs retrieved from the specified
         tmnxBsxUrlListFileUrl."
    ::= { tmnxBsxUrlListStatusEntry 13 }

tmnxBsxUrlListStatusUpgInProgres OBJECT-TYPE
    SYNTAX      TruthValue
    MAX-ACCESS  read-only
    STATUS      current
    DESCRIPTION
        "The value of tmnxBsxUrlListStatusUpgInProgres indicates the status of
         the most recent URL list upgrade. A value of 'true (1)' indicates the
         upgrade is in progress and a value of 'false (2)' indicates otherwise."
    ::= { tmnxBsxUrlListStatusEntry 14 }

tmnxBsxUrlListRegExprNumEntries  OBJECT-TYPE
    SYNTAX      Gauge32
    MAX-ACCESS  read-only
    STATUS      current
    DESCRIPTION
        "The value of tmnxBsxUrlListRegExprNumEntries indicates the number of
         host expression entries in the URL list, which were retrieved from the
         specified tmnxBsxUrlListFileUrl."
    ::= { tmnxBsxUrlListStatusEntry 15 }

tmnxBsxGtpStatsTable             OBJECT-TYPE
    SYNTAX      SEQUENCE OF TmnxBsxGtpStatsEntry
    MAX-ACCESS  not-accessible
    STATUS      current
    DESCRIPTION
        "The tmnxBsxGtpStatsTable contains an entry for each configured ISA AA
         group/partition configured in the system.

         Rows in this table are automatically created and destroyed when an
         entry is created or destroyed in the tmnxBsxAaGrpPartTable."
    ::= { tmnxBsxStatsObjs 16 }

tmnxBsxGtpStatsEntry             OBJECT-TYPE
    SYNTAX      TmnxBsxGtpStatsEntry
    MAX-ACCESS  not-accessible
    STATUS      current
    DESCRIPTION
        "Each tmnxBsxGtpStatsEntry indicates the GTP statistics that are
         collected per ISA and per ISA-AA group/partition.

         Indexing with tmnxChassisIndex set to one with a zero value for each
         of tmnxBsxCardSlotEsaId and tmnxBsxMdaSlotEsaVmId will return the
         summarized statistics per group/partition."
    INDEX       {
        tmnxBsxAaGrpPartIndex,
        tmnxChassisIndex,
        tmnxBsxCardSlotEsaId,
        tmnxBsxMdaSlotEsaVmId
    }
    ::= { tmnxBsxGtpStatsTable 1 }

TmnxBsxGtpStatsEntry             ::= SEQUENCE
{
    tmnxBsxGtpStatsDiscntTime        TimeStamp,
    tmnxBsxGtpStatsPkPermittedFmSb   Counter64,
    tmnxBsxGtpStatsPkPermittedToSb   Counter64,
    tmnxBsxGtpStatsPkPrmtNoFltrFmSb  Counter64,
    tmnxBsxGtpStatsPkPrmtNoFltrToSb  Counter64,
    tmnxBsxGtpStatsPkDndUdpLenFmSb   Counter64,
    tmnxBsxGtpStatsPkDndUdpLenToSb   Counter64,
    tmnxBsxGtpStatsPkDndGtpLenFmSb   Counter64,
    tmnxBsxGtpStatsPkDndGtpLenToSb   Counter64,
    tmnxBsxGtpStatsPkDndGtpVerFmSb   Counter64,
    tmnxBsxGtpStatsPkDndGtpVerToSb   Counter64,
    tmnxBsxGtpStatsPkDndFlPlcrFmSb   Counter64,
    tmnxBsxGtpStatsPkDndFlPlcrToSb   Counter64,
    tmnxBsxGtpStatsPkDndGtpFltrFmSb  Counter64,
    tmnxBsxGtpStatsPkDndGtpFltrToSb  Counter64,
    tmnxBsxGtpStatsPkDndPlcyOthrFmSb Counter64,
    tmnxBsxGtpStatsPkDndPlcyOthrToSb Counter64
}

tmnxBsxGtpStatsDiscntTime        OBJECT-TYPE
    SYNTAX      TimeStamp
    MAX-ACCESS  read-only
    STATUS      current
    DESCRIPTION
        "The value of tmnxBsxGtpStatsDiscntTime indicates discontinuity time.
         This is the SNMPv2-MIB::sysUpTime (centiseconds) when the ISA-AA MDA
         within the group last changed status."
    ::= { tmnxBsxGtpStatsEntry 1 }

tmnxBsxGtpStatsPkPermittedFmSb   OBJECT-TYPE
    SYNTAX      Counter64
    MAX-ACCESS  read-only
    STATUS      current
    DESCRIPTION
        "The value of tmnxBsxGtpStatsPkPermittedFmSb indicates the number of
         GTP packets permitted in the subscriber to network direction."
    ::= { tmnxBsxGtpStatsEntry 2 }

tmnxBsxGtpStatsPkPermittedToSb   OBJECT-TYPE
    SYNTAX      Counter64
    MAX-ACCESS  read-only
    STATUS      current
    DESCRIPTION
        "The value of tmnxBsxGtpStatsPkPermittedToSb indicates the number of
         GTP packets permitted in the network to subscriber direction."
    ::= { tmnxBsxGtpStatsEntry 3 }

tmnxBsxGtpStatsPkPrmtNoFltrFmSb  OBJECT-TYPE
    SYNTAX      Counter64
    MAX-ACCESS  read-only
    STATUS      current
    DESCRIPTION
        "The value of tmnxBsxGtpStatsPkPrmtNoFltrFmSb indicates the number of
         GTP packets permitted in the subscriber to network direction which
         were not subject to a GTP filter. This value is a subset of
         tmnxBsxGtpStatsPkPermittedFmSb."
    ::= { tmnxBsxGtpStatsEntry 4 }

tmnxBsxGtpStatsPkPrmtNoFltrToSb  OBJECT-TYPE
    SYNTAX      Counter64
    MAX-ACCESS  read-only
    STATUS      current
    DESCRIPTION
        "The value of tmnxBsxGtpStatsPkPrmtNoFltrToSb indicates the number of
         GTP packets permitted in the network to subscriber direction which
         were not subject to a GTP filter. This value is a subset of
         tmnxBsxGtpStatsPkPermittedToSb."
    ::= { tmnxBsxGtpStatsEntry 5 }

tmnxBsxGtpStatsPkDndUdpLenFmSb   OBJECT-TYPE
    SYNTAX      Counter64
    MAX-ACCESS  read-only
    STATUS      current
    DESCRIPTION
        "The value of tmnxBsxGtpStatsPkDndUdpLenFmSb indicates the number of
         GTP packets denied in the subscriber to network direction due to
         improper UDP packet length."
    ::= { tmnxBsxGtpStatsEntry 6 }

tmnxBsxGtpStatsPkDndUdpLenToSb   OBJECT-TYPE
    SYNTAX      Counter64
    MAX-ACCESS  read-only
    STATUS      current
    DESCRIPTION
        "The value of tmnxBsxGtpStatsPkDndUdpLenToSb indicates the number of
         GTP packets denied in the network to subscriber direction due to
         improper UDP packet length."
    ::= { tmnxBsxGtpStatsEntry 7 }

tmnxBsxGtpStatsPkDndGtpLenFmSb   OBJECT-TYPE
    SYNTAX      Counter64
    MAX-ACCESS  read-only
    STATUS      current
    DESCRIPTION
        "The value of tmnxBsxGtpStatsPkDndGtpLenFmSb indicates the number of
         GTP packets denied in the subscriber to network direction due to
         improper GTP message length."
    ::= { tmnxBsxGtpStatsEntry 8 }

tmnxBsxGtpStatsPkDndGtpLenToSb   OBJECT-TYPE
    SYNTAX      Counter64
    MAX-ACCESS  read-only
    STATUS      current
    DESCRIPTION
        "The value of tmnxBsxGtpStatsPkDndGtpLenToSb indicates the number of
         GTP packets denied in the network to subscriber direction due to
         improper GTP message length."
    ::= { tmnxBsxGtpStatsEntry 9 }

tmnxBsxGtpStatsPkDndGtpVerFmSb   OBJECT-TYPE
    SYNTAX      Counter64
    MAX-ACCESS  read-only
    STATUS      current
    DESCRIPTION
        "The value of tmnxBsxGtpStatsPkDndGtpVerFmSb indicates the number of
         GTP packets denied in the subscriber to network direction due to
         unsupported GTP version."
    ::= { tmnxBsxGtpStatsEntry 10 }

tmnxBsxGtpStatsPkDndGtpVerToSb   OBJECT-TYPE
    SYNTAX      Counter64
    MAX-ACCESS  read-only
    STATUS      current
    DESCRIPTION
        "The value of tmnxBsxGtpStatsPkDndGtpVerToSb indicates the number of
         GTP packets denied in the network to subscriber direction due to
         unsupported GTP version."
    ::= { tmnxBsxGtpStatsEntry 11 }

tmnxBsxGtpStatsPkDndFlPlcrFmSb   OBJECT-TYPE
    SYNTAX      Counter64
    MAX-ACCESS  read-only
    STATUS      current
    DESCRIPTION
        "The value of tmnxBsxGtpStatsPkDndFlPlcrFmSb indicates the number of
         packets denied in the subscriber to network direction by the policer
         flow-count limit due to the configuration of
         tmnxBsxPolicerGtpFlowCountLmt in tmnxBsxPolicerTable."
    ::= { tmnxBsxGtpStatsEntry 12 }

tmnxBsxGtpStatsPkDndFlPlcrToSb   OBJECT-TYPE
    SYNTAX      Counter64
    MAX-ACCESS  read-only
    STATUS      current
    DESCRIPTION
        "The value of tmnxBsxGtpStatsPkDndFlPlcrToSb indicates the number of
         packets denied in the network to subscriber direction by the policer
         flow-count limit due to the configuration of
         tmnxBsxPolicerGtpFlowCountLmt in tmnxBsxPolicerTable."
    ::= { tmnxBsxGtpStatsEntry 13 }

tmnxBsxGtpStatsPkDndGtpFltrFmSb  OBJECT-TYPE
    SYNTAX      Counter64
    MAX-ACCESS  read-only
    STATUS      current
    DESCRIPTION
        "The value of tmnxBsxGtpStatsPkDndGtpFltrFmSb indicates the number of
         packets denied in the subscriber to network direction due to GTP
         filter configuration in tmnxBsxGtpFltrTable."
    ::= { tmnxBsxGtpStatsEntry 14 }

tmnxBsxGtpStatsPkDndGtpFltrToSb  OBJECT-TYPE
    SYNTAX      Counter64
    MAX-ACCESS  read-only
    STATUS      current
    DESCRIPTION
        "The value of tmnxBsxGtpStatsPkDndGtpFltrToSb indicates the number of
         packets denied in the network to subscriber direction due to GTP
         filter configuration in tmnxBsxGtpFltrTable."
    ::= { tmnxBsxGtpStatsEntry 15 }

tmnxBsxGtpStatsPkDndPlcyOthrFmSb OBJECT-TYPE
    SYNTAX      Counter64
    MAX-ACCESS  read-only
    STATUS      current
    DESCRIPTION
        "The value of tmnxBsxGtpStatsPkDndPlcyOthrFmSb indicates the number of
         packets denied in the subscriber to network direction due to non
         gtp-traffic policers, session filters, or flow resource exhaustion."
    ::= { tmnxBsxGtpStatsEntry 16 }

tmnxBsxGtpStatsPkDndPlcyOthrToSb OBJECT-TYPE
    SYNTAX      Counter64
    MAX-ACCESS  read-only
    STATUS      current
    DESCRIPTION
        "The value of tmnxBsxGtpStatsPkDndPlcyOthrToSb indicates the number of
         packets denied in the network to subscriber direction due to non
         gtp-traffic policers, session filters, or flow resource exhaustion."
    ::= { tmnxBsxGtpStatsEntry 17 }

tmnxBsxGtpFltrStatsTable         OBJECT-TYPE
    SYNTAX      SEQUENCE OF TmnxBsxGtpFltrStatsEntry
    MAX-ACCESS  not-accessible
    STATUS      current
    DESCRIPTION
        "The tmnxBsxGtpFltrStatsTable contains an entry for each configured
         Application Assurance GTP filter per ISA.

         Rows in this table are automatically created and destroyed when GTP
         filters are created or destroyed in the tmnxBsxGtpFltrTable."
    ::= { tmnxBsxStatsObjs 17 }

tmnxBsxGtpFltrStatsEntry         OBJECT-TYPE
    SYNTAX      TmnxBsxGtpFltrStatsEntry
    MAX-ACCESS  not-accessible
    STATUS      current
    DESCRIPTION
        "Each tmnxBsxGtpFltrStatsEntry specifies Application Assurance GTP
         filter statistics.

         Indexing with a valid GTP filter (an existing row in
         tmnxBsxGtpFltrTable) and tmnxChassisIndex set to one with a zero value
         for each of tmnxBsxCardSlotEsaId and tmnxBsxMdaSlotEsaVmId will return
         the summarized statistics per group/partition and GTP filter."
    INDEX       {
        tmnxBsxAaGrpPartIndex,
        tmnxBsxGtpFltrName,
        tmnxChassisIndex,
        tmnxBsxCardSlotEsaId,
        tmnxBsxMdaSlotEsaVmId
    }
    ::= { tmnxBsxGtpFltrStatsTable 1 }

TmnxBsxGtpFltrStatsEntry         ::= SEQUENCE
{
    tmnxBsxGtpFltrStatsDiscntTime    TimeStamp,
    tmnxBsxGtpFltrStatsPkPermitted   Counter64,
    tmnxBsxGtpFltrStatsPkDndPayldLen Counter64,
    tmnxBsxGtpFltrStatsPkDndMsgType  Counter64,
    tmnxBsxGtpFltrStatsPkDndMandHdr  Counter64,
    tmnxBsxGtpFltrStatsPkDndExtHdr   Counter64,
    tmnxBsxGtpFltrStatsPkDndInfoElem Counter64,
    tmnxBsxGtpFltrStatsPkDndV2MsgTyp Counter64,
    tmnxBsxGtpFltrStatsPkDndImsiApn  Counter64,
    tmnxBsxGtpFltrStatsPkDndInvSeqNo Counter64,
    tmnxBsxGtpFltrStatsPkDndInvTeid  Counter64,
    tmnxBsxGtpFltrStatsPkDndInvSubIp Counter64,
    tmnxBsxGtpFltrStatsPkDndGtpInGtp Counter64,
    tmnxBsxGtpFltrStatsPkDndMandIE   Counter64,
    tmnxBsxGtpFltrStatsPkDndTunDbRes Counter64,
    tmnxBsxGtpFltrStatsPkDndTunEpLmt Counter64
}

tmnxBsxGtpFltrStatsDiscntTime    OBJECT-TYPE
    SYNTAX      TimeStamp
    MAX-ACCESS  read-only
    STATUS      current
    DESCRIPTION
        "The value of tmnxBsxGtpFltrStatsDiscntTime indicates discontinuity
         time. This is the SNMPv2-MIB::sysUpTime (centiseconds) when the ISA-AA
         MDA within the group last changed status."
    ::= { tmnxBsxGtpFltrStatsEntry 1 }

tmnxBsxGtpFltrStatsPkPermitted   OBJECT-TYPE
    SYNTAX      Counter64
    MAX-ACCESS  read-only
    STATUS      current
    DESCRIPTION
        "The value of tmnxBsxGtpFltrStatsPkPermitted indicates the number of
         packets permitted through the GTP filter."
    ::= { tmnxBsxGtpFltrStatsEntry 2 }

tmnxBsxGtpFltrStatsPkDndPayldLen OBJECT-TYPE
    SYNTAX      Counter64
    MAX-ACCESS  read-only
    STATUS      current
    DESCRIPTION
        "The value of tmnxBsxGtpFltrStatsPkDndPayldLen indicates the number of
         packets denied by the GTP filter due to the corresponding
         tmnxBsxGtpFltrMaxPayloadLength in tmnxBsxGtpFltrTable."
    ::= { tmnxBsxGtpFltrStatsEntry 3 }

tmnxBsxGtpFltrStatsPkDndMsgType  OBJECT-TYPE
    SYNTAX      Counter64
    MAX-ACCESS  read-only
    STATUS      current
    DESCRIPTION
        "The value of tmnxBsxGtpFltrStatsPkDndMsgType indicates the number of
         packets denied by the GTP filter due to message ID configuration in
         tmnxBsxGtpFltrMsgTable."
    ::= { tmnxBsxGtpFltrStatsEntry 4 }

tmnxBsxGtpFltrStatsPkDndMandHdr  OBJECT-TYPE
    SYNTAX      Counter64
    MAX-ACCESS  read-only
    STATUS      current
    DESCRIPTION
        "The value of tmnxBsxGtpFltrStatsPkDndMandHdr indicates the number of
         packets denied by the GTP filter due to a missing mandatory header."
    ::= { tmnxBsxGtpFltrStatsEntry 5 }

tmnxBsxGtpFltrStatsPkDndExtHdr   OBJECT-TYPE
    SYNTAX      Counter64
    MAX-ACCESS  read-only
    STATUS      current
    DESCRIPTION
        "The value of tmnxBsxGtpFltrStatsPkDndExtHdr indicates the number of
         packets denied by the GTP filter due to a missing extension header."
    ::= { tmnxBsxGtpFltrStatsEntry 7 }

tmnxBsxGtpFltrStatsPkDndInfoElem OBJECT-TYPE
    SYNTAX      Counter64
    MAX-ACCESS  read-only
    STATUS      current
    DESCRIPTION
        "The value of tmnxBsxGtpFltrStatsPkDndInfoElem indicates the number of
         packets denied by the GTP filter due to a missing, invalid, or
         malformed information element."
    ::= { tmnxBsxGtpFltrStatsEntry 8 }

tmnxBsxGtpFltrStatsPkDndV2MsgTyp OBJECT-TYPE
    SYNTAX      Counter64
    MAX-ACCESS  read-only
    STATUS      current
    DESCRIPTION
        "The value of tmnxBsxGtpFltrStatsPkDndV2MsgTyp indicates the number of
         packets denied by the GTP filter due to GTP V2 message ID
         configuration in tmnxBsxGtpFltrV2MsgTable."
    ::= { tmnxBsxGtpFltrStatsEntry 9 }

tmnxBsxGtpFltrStatsPkDndImsiApn  OBJECT-TYPE
    SYNTAX      Counter64
    MAX-ACCESS  read-only
    STATUS      current
    DESCRIPTION
        "The value of tmnxBsxGtpFltrStatsPkDndImsiApn indicates the number of
         packets denied by the GTP filter due to imsi-apn-filter configuration
         in tmnxBsxGtpFltrImsiApnTable."
    ::= { tmnxBsxGtpFltrStatsEntry 10 }

tmnxBsxGtpFltrStatsPkDndInvSeqNo OBJECT-TYPE
    SYNTAX      Counter64
    MAX-ACCESS  read-only
    STATUS      current
    DESCRIPTION
        "The value of tmnxBsxGtpFltrStatsPkDndInvSeqNo indicates the number of
         packets denied by the GTP filter due to invalid sequence number."
    ::= { tmnxBsxGtpFltrStatsEntry 11 }

tmnxBsxGtpFltrStatsPkDndInvTeid  OBJECT-TYPE
    SYNTAX      Counter64
    MAX-ACCESS  read-only
    STATUS      current
    DESCRIPTION
        "The value of tmnxBsxGtpFltrStatsPkDndInvTeid indicates the number of
         packets denied by the GTP filter due to invalid TEID."
    ::= { tmnxBsxGtpFltrStatsEntry 12 }

tmnxBsxGtpFltrStatsPkDndInvSubIp OBJECT-TYPE
    SYNTAX      Counter64
    MAX-ACCESS  read-only
    STATUS      current
    DESCRIPTION
        "The value of tmnxBsxGtpFltrStatsPkDndInvSubIp indicates the number of
         packets denied by the GTP filter due to invalid subscriber IP address."
    ::= { tmnxBsxGtpFltrStatsEntry 13 }

tmnxBsxGtpFltrStatsPkDndGtpInGtp OBJECT-TYPE
    SYNTAX      Counter64
    MAX-ACCESS  read-only
    STATUS      current
    DESCRIPTION
        "The value of tmnxBsxGtpFltrStatsPkDndGtpInGtp indicates the number of
         packets denied by the GTP filter due to GTP in GTP configuration in
         tmnxBsxGtpFltrTable."
    ::= { tmnxBsxGtpFltrStatsEntry 14 }

tmnxBsxGtpFltrStatsPkDndMandIE   OBJECT-TYPE
    SYNTAX      Counter64
    MAX-ACCESS  read-only
    STATUS      current
    DESCRIPTION
        "The value of tmnxBsxGtpFltrStatsPkDndMandIE indicates the number of
         packets denied by the GTP filter due to missing mandatory information
         elements."
    ::= { tmnxBsxGtpFltrStatsEntry 15 }

tmnxBsxGtpFltrStatsPkDndTunDbRes OBJECT-TYPE
    SYNTAX      Counter64
    MAX-ACCESS  read-only
    STATUS      current
    DESCRIPTION
        "The value of tmnxBsxGtpFltrStatsPkDndTunDbRes indicates the number of
         packets denied by the GTP filter due to the GTP Tunnel Database being
         full when a new tunnel needed to be allocated."
    ::= { tmnxBsxGtpFltrStatsEntry 16 }

tmnxBsxGtpFltrStatsPkDndTunEpLmt OBJECT-TYPE
    SYNTAX      Counter64
    MAX-ACCESS  read-only
    STATUS      current
    DESCRIPTION
        "The value of tmnxBsxGtpFltrStatsPkDndTunEpLmt indicates the number of
         packets denied by the GTP filter due to receiving a 'create session
         request' at the time the GTP TEID default limit has already been
         reached."
    ::= { tmnxBsxGtpFltrStatsEntry 17 }

tmnxBsxSctpFltrStatsTable        OBJECT-TYPE
    SYNTAX      SEQUENCE OF TmnxBsxSctpFltrStatsEntry
    MAX-ACCESS  not-accessible
    STATUS      current
    DESCRIPTION
        "The tmnxBsxSctpFltrStatsTable contains an entry for each configured
         Application Assurance SCTP filter per ISA.

         Rows in this table are automatically created and destroyed when SCTP
         filters are created or destroyed in the tmnxBsxSctpFltrTable."
    ::= { tmnxBsxStatsObjs 18 }

tmnxBsxSctpFltrStatsEntry        OBJECT-TYPE
    SYNTAX      TmnxBsxSctpFltrStatsEntry
    MAX-ACCESS  not-accessible
    STATUS      current
    DESCRIPTION
        "Each tmnxBsxSctpFltrStatsEntry specifies Application Assurance SCTP
         filter statistics.

         Indexing with a valid SCTP filter (an existing row in
         tmnxBsxSctpFltrTable) and tmnxChassisIndex set to one with a zero
         value for each of tmnxBsxCardSlotEsaId and tmnxBsxMdaSlotEsaVmId will
         return the summarized statistics per group/partition and SCTP filter."
    INDEX       {
        tmnxBsxAaGrpPartIndex,
        tmnxBsxSctpFltrName,
        tmnxChassisIndex,
        tmnxBsxCardSlotEsaId,
        tmnxBsxMdaSlotEsaVmId
    }
    ::= { tmnxBsxSctpFltrStatsTable 1 }

TmnxBsxSctpFltrStatsEntry        ::= SEQUENCE
{
    tmnxBsxSctpFltrStatsDiscntTime   TimeStamp,
    tmnxBsxSctpFltrStatsPkPermitted  Counter64,
    tmnxBsxSctpFltrStatsPkDndMalfd   Counter64,
    tmnxBsxSctpFltrStatsPkDndPpidOOR Counter64,
    tmnxBsxSctpFltrStatsPkDndPpidVal Counter64
}

tmnxBsxSctpFltrStatsDiscntTime   OBJECT-TYPE
    SYNTAX      TimeStamp
    MAX-ACCESS  read-only
    STATUS      current
    DESCRIPTION
        "The value of tmnxBsxSctpFltrStatsDiscntTime indicates discontinuity
         time. This is the SNMPv2-MIB::sysUpTime (centiseconds) when the ISA-AA
         MDA within the group last changed status."
    ::= { tmnxBsxSctpFltrStatsEntry 1 }

tmnxBsxSctpFltrStatsPkPermitted  OBJECT-TYPE
    SYNTAX      Counter64
    MAX-ACCESS  read-only
    STATUS      current
    DESCRIPTION
        "The value of tmnxBsxSctpFltrStatsPkPermitted indicates the number of
         packets permitted through the SCTP filter."
    ::= { tmnxBsxSctpFltrStatsEntry 2 }

tmnxBsxSctpFltrStatsPkDndMalfd   OBJECT-TYPE
    SYNTAX      Counter64
    MAX-ACCESS  read-only
    STATUS      current
    DESCRIPTION
        "The value of tmnxBsxSctpFltrStatsPkDndMalfd indicates the number of
         packets denied by the SCTP filter due to the packet being malformed."
    ::= { tmnxBsxSctpFltrStatsEntry 3 }

tmnxBsxSctpFltrStatsPkDndPpidOOR OBJECT-TYPE
    SYNTAX      Counter64
    MAX-ACCESS  read-only
    STATUS      current
    DESCRIPTION
        "The value of tmnxBsxSctpFltrStatsPkDndPpidOOR indicates the number of
         packets denied by the SCTP filter due to PPID being out of range of
         the corresponding
         tmnxBsxSctpFltrPpidRangeMin/tmnxBsxSctpFltrPpidRangeMax in
         tmnxBsxSctpFltrTable."
    ::= { tmnxBsxSctpFltrStatsEntry 4 }

tmnxBsxSctpFltrStatsPkDndPpidVal OBJECT-TYPE
    SYNTAX      Counter64
    MAX-ACCESS  read-only
    STATUS      current
    DESCRIPTION
        "The value of tmnxBsxSctpFltrStatsPkDndPpidVal indicates the number of
         packets denied by the SCTP filter due to PPID value configuration in
         tmnxBsxSctpFltrPpidTable."
    ::= { tmnxBsxSctpFltrStatsEntry 5 }

tmnxBsxSyslogStatsTable          OBJECT-TYPE
    SYNTAX      SEQUENCE OF TmnxBsxSyslogStatsEntry
    MAX-ACCESS  not-accessible
    STATUS      current
    DESCRIPTION
        "The tmnxBsxSyslogStatsTable contains an entry for each configured
         Application Assurance event log per ISA.

         Rows in this table are automatically created and destroyed when event
         logs are created or destroyed in the tmnxBsxEventLogTable."
    ::= { tmnxBsxStatsObjs 19 }

tmnxBsxSyslogStatsEntry          OBJECT-TYPE
    SYNTAX      TmnxBsxSyslogStatsEntry
    MAX-ACCESS  not-accessible
    STATUS      current
    DESCRIPTION
        "Each tmnxBsxSyslogStatsEntry specifies Application Assurance event log
         syslog statistics.

         Only event logs that have tmnxBsxEventLogBufferType set to 'syslog
         (3)' will ever have non-zero statistics.

         Indexing with a valid event log (an existing row in
         tmnxBsxEventLogTable) and tmnxChassisIndex set to one with a zero
         value for each of tmnxBsxCardSlotEsaId and tmnxBsxMdaSlotEsaVmId will
         return the summarized statistics per group/partition and event log."
    INDEX       {
        tmnxBsxAaGrpPartIndex,
        tmnxBsxEventLogName,
        tmnxChassisIndex,
        tmnxBsxCardSlotEsaId,
        tmnxBsxMdaSlotEsaVmId
    }
    ::= { tmnxBsxSyslogStatsTable 1 }

TmnxBsxSyslogStatsEntry          ::= SEQUENCE
{
    tmnxBsxSyslogStatsDiscntTime     TimeStamp,
    tmnxBsxSyslogStatsEventsSent     Counter64,
    tmnxBsxSyslogStatsEventsFailed   Counter64
}

tmnxBsxSyslogStatsDiscntTime     OBJECT-TYPE
    SYNTAX      TimeStamp
    MAX-ACCESS  read-only
    STATUS      current
    DESCRIPTION
        "The value of tmnxBsxSyslogStatsDiscntTime indicates discontinuity
         time. This is the SNMPv2-MIB::sysUpTime (centiseconds) when the ISA-AA
         MDA within the group last changed status."
    ::= { tmnxBsxSyslogStatsEntry 1 }

tmnxBsxSyslogStatsEventsSent     OBJECT-TYPE
    SYNTAX      Counter64
    MAX-ACCESS  read-only
    STATUS      current
    DESCRIPTION
        "The value of tmnxBsxSyslogStatsEventsSent indicates the number of
         events that were sent to the configured syslog collector target."
    ::= { tmnxBsxSyslogStatsEntry 2 }

tmnxBsxSyslogStatsEventsFailed   OBJECT-TYPE
    SYNTAX      Counter64
    MAX-ACCESS  read-only
    STATUS      current
    DESCRIPTION
        "The value of tmnxBsxSyslogStatsEventsFailed indicates the number of
         events that could not be sent to the configured syslog collector
         target due to configuration or processing problems."
    ::= { tmnxBsxSyslogStatsEntry 3 }

tmnxBsxStatTcaCfgTable           OBJECT-TYPE
    SYNTAX      SEQUENCE OF TmnxBsxStatTcaCfgEntry
    MAX-ACCESS  not-accessible
    STATUS      current
    DESCRIPTION
        "The tmnxBsxStatTcaCfgTable contains threshold crossing alert (TCA)
         configuration information.

         Entries in this table are created and destroyed via SNMP set
         operations to tmnxBsxStatTcaCfgRowStatus."
    ::= { tmnxBsxStatsObjs 20 }

tmnxBsxStatTcaCfgEntry           OBJECT-TYPE
    SYNTAX      TmnxBsxStatTcaCfgEntry
    MAX-ACCESS  not-accessible
    STATUS      current
    DESCRIPTION
        "Each tmnxBsxStatTcaCfgEntry indicates the TCA watermarks that are
         configured per ISA-AA Group and Partition.

         Note that the calculation to determine if a TCA is required (using the
         configured watermarks) is based on the utilization during the past
         minute. The utilization is calculated based on the number of matches
         due to the value of tmnxBsxStatTcaCfgType."
    INDEX       {
        tmnxBsxAaGrpPartIndex,
        tmnxBsxStatTcaCfgType,
        tmnxBsxStatTcaCfgDirection
    }
    ::= { tmnxBsxStatTcaCfgTable 1 }

TmnxBsxStatTcaCfgEntry           ::= SEQUENCE
{
    tmnxBsxStatTcaCfgType            INTEGER,
    tmnxBsxStatTcaCfgDirection       INTEGER,
    tmnxBsxStatTcaCfgRowLastCh       TimeStamp,
    tmnxBsxStatTcaCfgRowStatus       RowStatus,
    tmnxBsxStatTcaCfgHiWmark         Unsigned32,
    tmnxBsxStatTcaCfgLoWmark         Unsigned32
}

tmnxBsxStatTcaCfgType            OBJECT-TYPE
    SYNTAX      INTEGER {
        errorDrop              (1),
        fragmentDropOutOfOrder (2),
        fragmentDropAll        (3),
        overloadDrop           (4),
        gtpSanityDrop          (5)
    }
    MAX-ACCESS  not-accessible
    STATUS      current
    DESCRIPTION
        "The value of tmnxBsxStatTcaCfgType specifies the TCA type.

         The TCA type may be one of:
           errorDrop              (1) - based on AQP action error-drop
           fragmentDropOutOfOrder (2) - based on AQP action fragment-drop
                                        out-of-order
           fragmentDropAll        (3) - based on AQP action fragment-drop all
           overloadDrop           (4) - based on AQP action overload-drop
           gtpSanityDrop          (5) - based on AQP initial lookup"
    ::= { tmnxBsxStatTcaCfgEntry 1 }

tmnxBsxStatTcaCfgDirection       OBJECT-TYPE
    SYNTAX      INTEGER {
        fromSub (1),
        toSub   (2)
    }
    MAX-ACCESS  not-accessible
    STATUS      current
    DESCRIPTION
        "The value of tmnxBsxStatTcaCfgDirection specifies the TCA direction.

         The TCA direction may be one of:
           fromSub (1) - subscriber to network direction
           toSub   (2) - network to subscriber direction"
    ::= { tmnxBsxStatTcaCfgEntry 2 }

tmnxBsxStatTcaCfgRowLastCh       OBJECT-TYPE
    SYNTAX      TimeStamp
    MAX-ACCESS  read-only
    STATUS      current
    DESCRIPTION
        "The value of tmnxBsxStatTcaCfgRowLastCh indicates the last time, since
         system startup, a successful SNMP set caused a value in this row to
         change."
    ::= { tmnxBsxStatTcaCfgEntry 3 }

tmnxBsxStatTcaCfgRowStatus       OBJECT-TYPE
    SYNTAX      RowStatus
    MAX-ACCESS  read-create
    STATUS      current
    DESCRIPTION
        "The value of tmnxBsxStatTcaCfgRowStatus specifies the row status. It
         allows entries to be created and destroyed in the
         tmnxBsxStatTcaCfgTable."
    ::= { tmnxBsxStatTcaCfgEntry 4 }

tmnxBsxStatTcaCfgHiWmark         OBJECT-TYPE
    SYNTAX      Unsigned32
    MAX-ACCESS  read-create
    STATUS      current
    DESCRIPTION
        "The value of tmnxBsxStatTcaCfgHiWmark specifies the utilization
         high-watermark.

         This value must be set in the same PDU as tmnxBsxStatTcaCfgLoWmark and
         must be greater than tmnxBsxStatTcaCfgLoWmark."
    DEFVAL      { 'FFFFFFFF'H }
    ::= { tmnxBsxStatTcaCfgEntry 5 }

tmnxBsxStatTcaCfgLoWmark         OBJECT-TYPE
    SYNTAX      Unsigned32
    MAX-ACCESS  read-create
    STATUS      current
    DESCRIPTION
        "The value of tmnxBsxStatTcaCfgLoWmark specifies the utilization
         low-watermark.

         This value must be set in the same PDU as tmnxBsxStatTcaCfgHiWmark and
         must be less than tmnxBsxStatTcaCfgHiWmark."
    DEFVAL      { 0 }
    ::= { tmnxBsxStatTcaCfgEntry 6 }

tmnxBsxStatTcaPolcrCfgTable      OBJECT-TYPE
    SYNTAX      SEQUENCE OF TmnxBsxStatTcaPolcrCfgEntry
    MAX-ACCESS  not-accessible
    STATUS      current
    DESCRIPTION
        "The tmnxBsxStatTcaPolcrCfgTable contains policer TCA configuration
         information.

         Entries in this table are created and destroyed via SNMP set
         operations to tmnxBsxStatTcaPolcrCfgRowStatus."
    ::= { tmnxBsxStatsObjs 21 }

tmnxBsxStatTcaPolcrCfgEntry      OBJECT-TYPE
    SYNTAX      TmnxBsxStatTcaPolcrCfgEntry
    MAX-ACCESS  not-accessible
    STATUS      current
    DESCRIPTION
        "Each tmnxBsxStatTcaPolcrCfgEntry indicates the policer TCA watermarks
         that are configured per policer, as defined in tmnxBsxPolicerTable.

         Note that the calculation to determine if a TCA is required (using the
         configured watermarks) is based on the utilization during the past
         minute. The utilization is calculated based on the number of matches
         due to the specified policer."
    INDEX       {
        tmnxBsxAaGrpPartIndex,
        tmnxBsxPolicerName,
        tmnxBsxStatTcaCfgDirection
    }
    ::= { tmnxBsxStatTcaPolcrCfgTable 1 }

TmnxBsxStatTcaPolcrCfgEntry      ::= SEQUENCE
{
    tmnxBsxStatTcaPolcrCfgRowLastCh  TimeStamp,
    tmnxBsxStatTcaPolcrCfgRowStatus  RowStatus,
    tmnxBsxStatTcaPolcrCfgHiWmark    Unsigned32,
    tmnxBsxStatTcaPolcrCfgLoWmark    Unsigned32
}

tmnxBsxStatTcaPolcrCfgRowLastCh  OBJECT-TYPE
    SYNTAX      TimeStamp
    MAX-ACCESS  read-only
    STATUS      current
    DESCRIPTION
        "The value of tmnxBsxStatTcaPolcrCfgRowLastCh indicates the last time,
         since system startup, a successful SNMP set caused a value in this row
         to change."
    ::= { tmnxBsxStatTcaPolcrCfgEntry 1 }

tmnxBsxStatTcaPolcrCfgRowStatus  OBJECT-TYPE
    SYNTAX      RowStatus
    MAX-ACCESS  read-create
    STATUS      current
    DESCRIPTION
        "The value of tmnxBsxStatTcaPolcrCfgRowStatus specifies the row status.
         It allows entries to be created and destroyed in the
         tmnxBsxStatTcaPolcrCfgTable."
    ::= { tmnxBsxStatTcaPolcrCfgEntry 2 }

tmnxBsxStatTcaPolcrCfgHiWmark    OBJECT-TYPE
    SYNTAX      Unsigned32
    MAX-ACCESS  read-create
    STATUS      current
    DESCRIPTION
        "The value of tmnxBsxStatTcaPolcrCfgHiWmark specifies the policer
         utilization high-watermark.

         This value must be set in the same PDU as
         tmnxBsxStatTcaPolcrCfgLoWmark and must be greater than
         tmnxBsxStatTcaPolcrCfgLoWmark."
    DEFVAL      { 'FFFFFFFF'H }
    ::= { tmnxBsxStatTcaPolcrCfgEntry 3 }

tmnxBsxStatTcaPolcrCfgLoWmark    OBJECT-TYPE
    SYNTAX      Unsigned32
    MAX-ACCESS  read-create
    STATUS      current
    DESCRIPTION
        "The value of tmnxBsxStatTcaPolcrCfgLoWmark specifies the policer
         utilization low-watermark.

         This value must be set in the same PDU as
         tmnxBsxStatTcaPolcrCfgHiWmark and must be less than
         tmnxBsxStatTcaPolcrCfgHiWmark."
    DEFVAL      { 0 }
    ::= { tmnxBsxStatTcaPolcrCfgEntry 4 }

tmnxBsxStatTcaFtrCfgTable        OBJECT-TYPE
    SYNTAX      SEQUENCE OF TmnxBsxStatTcaFtrCfgEntry
    MAX-ACCESS  not-accessible
    STATUS      current
    DESCRIPTION
        "The tmnxBsxStatTcaFtrCfgTable contains filter TCA configuration
         information.

         Entries in this table are created and destroyed via SNMP set
         operations to tmnxBsxStatTcaFtrCfgRowStatus."
    ::= { tmnxBsxStatsObjs 22 }

tmnxBsxStatTcaFtrCfgEntry        OBJECT-TYPE
    SYNTAX      TmnxBsxStatTcaFtrCfgEntry
    MAX-ACCESS  not-accessible
    STATUS      current
    DESCRIPTION
        "Each tmnxBsxStatTcaFtrCfgEntry indicates the filter TCA watermarks
         that are configured per filter, as defined by the values of
         tmnxBsxStatTcaCfgFilterType and tmnxBsxStatTcaCfgFilterName.

         Note that the calculation to determine if a TCA is required (using the
         configured watermarks) is based on the utilization during the past
         minute. The utilization is calculated based on the number of matches
         due to the specified filter."
    INDEX       {
        tmnxBsxAaGrpPartIndex,
        tmnxBsxStatTcaCfgFilterType,
        tmnxBsxStatTcaCfgFilterName,
        tmnxBsxStatTcaCfgFilterWmarkType,
        tmnxBsxStatTcaCfgDirection
    }
    ::= { tmnxBsxStatTcaFtrCfgTable 1 }

TmnxBsxStatTcaFtrCfgEntry        ::= SEQUENCE
{
    tmnxBsxStatTcaCfgFilterType      INTEGER,
    tmnxBsxStatTcaCfgFilterName      TNamedItem,
    tmnxBsxStatTcaCfgFilterWmarkType INTEGER,
    tmnxBsxStatTcaFtrCfgRowLastCh    TimeStamp,
    tmnxBsxStatTcaFtrCfgRowStatus    RowStatus,
    tmnxBsxStatTcaFtrCfgHiWmark      Unsigned32,
    tmnxBsxStatTcaFtrCfgLoWmark      Unsigned32
}

tmnxBsxStatTcaCfgFilterType      OBJECT-TYPE
    SYNTAX      INTEGER {
        gtpFilter     (1),
        sctpFilter    (2),
        sessionFilter (3)
    }
    MAX-ACCESS  not-accessible
    STATUS      current
    DESCRIPTION
        "The value of tmnxBsxStatTcaCfgFilterType specifies the filter type.

         The TCA filter type may be one of:
           gtpFilter     (1) - as defined in tmnxBsxGtpFltrTable and
                               tmnxBsxGtpFltrMsgTable
           sctpFilter    (2) - as defined in tmnxBsxSctpFltrTable and
                               tmnxBsxSctpFltrPpidTable
           sessionFilter (3) - as defined in tmnxBsxSessFltrTable and
                               tmnxBsxSessFltrParamsTable"
    ::= { tmnxBsxStatTcaFtrCfgEntry 1 }

tmnxBsxStatTcaCfgFilterName      OBJECT-TYPE
    SYNTAX      TNamedItem
    MAX-ACCESS  not-accessible
    STATUS      current
    DESCRIPTION
        "The value of tmnxBsxStatTcaCfgFilterName specifies the name of the
         filter. A row for this filter must already exist in the table
         corresponding to the filter type, as outlined in the DESCRIPTION
         clause of tmnxBsxStatTcaCfgFilterType."
    ::= { tmnxBsxStatTcaFtrCfgEntry 2 }

tmnxBsxStatTcaCfgFilterWmarkType OBJECT-TYPE
    SYNTAX      INTEGER {
        payloadOutOfRange    (1),
        idOutOfRange         (2),
        defaultAction        (3),
        headerSanity         (4),
        packetSanity         (5),
        gtpv2DefAction       (6),
        gtpImsiApnDefAction  (7),
        gtpTeidValidity      (8),
        gtpSeqNumValidity    (9),
        gtpSrcIpAddrValidity (10),
        gtpMissingMandIE     (11),
        gtpInGtp             (12),
        gtpTunDbRes          (13),
        gtpDefTunEpLimit     (14)
    }
    MAX-ACCESS  not-accessible
    STATUS      current
    DESCRIPTION
        "The value of tmnxBsxStatTcaCfgFilterWmarkType specifies the filter
         watermark type.

         The TCA filter watermark type may be one of:
           payloadOutOfRange (1) - based on the filter's allowable payload
                                   range, only valid if
                                   tmnxBsxStatTcaCfgFilterType is set to
                                   'gtpFilter (1)'
           idOutOfRange      (2) - based on the filter's allowable ID range,
                                   only valid if tmnxBsxStatTcaCfgFilterType is
                                   set to 'sctpFilter (2)'
           defaultAction     (3) - based on the filter's default action
           headerSanity      (4) - based on the filter header's sanity checks,
                                   only valid if tmnxBsxStatTcaCfgFilterType is
                                   set to 'gtpFilter (1)'
           packetSanity      (5) - based on the filter's packet sanity checks,
                                   only valid if tmnxBsxStatTcaCfgFilterType is
                                   set to 'sctpFilter (2)'
           gtpv2DefAction       (6)  - GTP message-type version 2 default action
           gtpImsiApnDefAction  (7)  - GTP IMSI-APN filter default action
           gtpTeidValidity      (8)  - GTP TEID validity
           gtpSeqNumValidity    (9)  - GTP sequence number validity
           gtpSrcIpAddrValidity (10) - GTP source IP address (subscriber) validity
           gtpMissingMandIE     (11) - Missing mandatory IE in the GTP packet
           gtpInGtp             (12) - GTP in GTP action
           gtpTunDbRes          (13) - gtp tunnel database out of resources
           gtpDefTunEpLimit     (14) - gtp default tunnel endpoint limit"
    ::= { tmnxBsxStatTcaFtrCfgEntry 3 }

tmnxBsxStatTcaFtrCfgRowLastCh    OBJECT-TYPE
    SYNTAX      TimeStamp
    MAX-ACCESS  read-only
    STATUS      current
    DESCRIPTION
        "The value of tmnxBsxStatTcaFtrCfgRowLastCh indicates the last time,
         since system startup, a successful SNMP set caused a value in this row
         to change."
    ::= { tmnxBsxStatTcaFtrCfgEntry 4 }

tmnxBsxStatTcaFtrCfgRowStatus    OBJECT-TYPE
    SYNTAX      RowStatus
    MAX-ACCESS  read-create
    STATUS      current
    DESCRIPTION
        "The value of tmnxBsxStatTcaFtrCfgRowStatus specifies the row status.
         It allows entries to be created and destroyed in the
         tmnxBsxStatTcaFtrCfgTable."
    ::= { tmnxBsxStatTcaFtrCfgEntry 5 }

tmnxBsxStatTcaFtrCfgHiWmark      OBJECT-TYPE
    SYNTAX      Unsigned32
    MAX-ACCESS  read-create
    STATUS      current
    DESCRIPTION
        "The value of tmnxBsxStatTcaFtrCfgHiWmark specifies the filter's
         utilization high-watermark.

         This value must be set in the same PDU as tmnxBsxStatTcaFtrCfgLoWmark
         and must be greater than tmnxBsxStatTcaFtrCfgLoWmark."
    DEFVAL      { 'FFFFFFFF'H }
    ::= { tmnxBsxStatTcaFtrCfgEntry 6 }

tmnxBsxStatTcaFtrCfgLoWmark      OBJECT-TYPE
    SYNTAX      Unsigned32
    MAX-ACCESS  read-create
    STATUS      current
    DESCRIPTION
        "The value of tmnxBsxStatTcaFtrCfgLoWmark specifies the filter's
         utilization low-watermark.

         This value must be set in the same PDU as tmnxBsxStatTcaFtrCfgHiWmark
         and must be less than tmnxBsxStatTcaFtrCfgHiWmark."
    DEFVAL      { 0 }
    ::= { tmnxBsxStatTcaFtrCfgEntry 7 }

tmnxBsxStatTcaFtrEnCfgTable      OBJECT-TYPE
    SYNTAX      SEQUENCE OF TmnxBsxStatTcaFtrEnCfgEntry
    MAX-ACCESS  not-accessible
    STATUS      current
    DESCRIPTION
        "The tmnxBsxStatTcaFtrEnCfgTable contains filter entry TCA
         configuration information.

         Entries in this table are created and destroyed via SNMP set
         operations to tmnxBsxStatTcaFtrEnCfgRowStatus."
    ::= { tmnxBsxStatsObjs 23 }

tmnxBsxStatTcaFtrEnCfgEntry      OBJECT-TYPE
    SYNTAX      TmnxBsxStatTcaFtrEnCfgEntry
    MAX-ACCESS  not-accessible
    STATUS      current
    DESCRIPTION
        "Each tmnxBsxStatTcaFtrEnCfgEntry indicates the filter entry TCA
         watermarks that are configured per filter entry, as defined by the
         values of tmnxBsxStatTcaCfgFilterType, tmnxBsxStatTcaCfgFilterName,
         and tmnxBsxStatTcaFtrEnCfgEntryId.

         Note that the calculation to determine if a TCA is required (using the
         configured watermarks) is based on the utilization during the past
         minute. The utilization is calculated based on the number of matches
         due to the specified filter entry."
    INDEX       {
        tmnxBsxAaGrpPartIndex,
        tmnxBsxStatTcaCfgFilterType,
        tmnxBsxStatTcaCfgFilterName,
        tmnxBsxStatTcaFtrEnCfgEntryId,
        tmnxBsxStatTcaCfgDirection
    }
    ::= { tmnxBsxStatTcaFtrEnCfgTable 1 }

TmnxBsxStatTcaFtrEnCfgEntry      ::= SEQUENCE
{
    tmnxBsxStatTcaFtrEnCfgEntryId    Unsigned32,
    tmnxBsxStatTcaFtrEnCfgRowLastCh  TimeStamp,
    tmnxBsxStatTcaFtrEnCfgRowStatus  RowStatus,
    tmnxBsxStatTcaFtrEnCfgHiWmark    Unsigned32,
    tmnxBsxStatTcaFtrEnCfgLoWmark    Unsigned32
}

tmnxBsxStatTcaFtrEnCfgEntryId    OBJECT-TYPE
    SYNTAX      Unsigned32 (1..65535)
    MAX-ACCESS  not-accessible
    STATUS      current
    DESCRIPTION
        "The value of tmnxBsxStatTcaFtrEnCfgEntryId specifies the index into
         the filter's corresponding entry table. A row for this entry must
         already exist in the table corresponding to the filter type, as
         outlined in the DESCRIPTION clause of tmnxBsxStatTcaCfgFilterType."
    ::= { tmnxBsxStatTcaFtrEnCfgEntry 1 }

tmnxBsxStatTcaFtrEnCfgRowLastCh  OBJECT-TYPE
    SYNTAX      TimeStamp
    MAX-ACCESS  read-only
    STATUS      current
    DESCRIPTION
        "The value of tmnxBsxStatTcaFtrEnCfgRowLastCh indicates the last time,
         since system startup, a successful SNMP set caused a value in this row
         to change."
    ::= { tmnxBsxStatTcaFtrEnCfgEntry 2 }

tmnxBsxStatTcaFtrEnCfgRowStatus  OBJECT-TYPE
    SYNTAX      RowStatus
    MAX-ACCESS  read-create
    STATUS      current
    DESCRIPTION
        "The value of tmnxBsxStatTcaFtrEnCfgRowStatus specifies the row status.
         It allows entries to be created and destroyed in the
         tmnxBsxStatTcaFtrEnCfgTable."
    ::= { tmnxBsxStatTcaFtrEnCfgEntry 3 }

tmnxBsxStatTcaFtrEnCfgHiWmark    OBJECT-TYPE
    SYNTAX      Unsigned32
    MAX-ACCESS  read-create
    STATUS      current
    DESCRIPTION
        "The value of tmnxBsxStatTcaFtrEnCfgHiWmark specifies the filter
         entry's utilization high-watermark.

         This value must be set in the same PDU as
         tmnxBsxStatTcaFtrEnCfgLoWmark and must be greater than
         tmnxBsxStatTcaFtrEnCfgLoWmark."
    DEFVAL      { 'FFFFFFFF'H }
    ::= { tmnxBsxStatTcaFtrEnCfgEntry 4 }

tmnxBsxStatTcaFtrEnCfgLoWmark    OBJECT-TYPE
    SYNTAX      Unsigned32
    MAX-ACCESS  read-create
    STATUS      current
    DESCRIPTION
        "The value of tmnxBsxStatTcaFtrEnCfgLoWmark specifies the filter
         entry's utilization low-watermark.

         This value must be set in the same PDU as
         tmnxBsxStatTcaFtrEnCfgHiWmark and must be less than
         tmnxBsxStatTcaFtrEnCfgHiWmark."
    DEFVAL      { 0 }
    ::= { tmnxBsxStatTcaFtrEnCfgEntry 5 }

tmnxBsxAdmitDenyAcctTable        OBJECT-TYPE
    SYNTAX      SEQUENCE OF TmnxBsxAdmitDenyAcctEntry
    MAX-ACCESS  not-accessible
    STATUS      current
    DESCRIPTION
        "The tmnxBsxAdmitDenyAcctTable contains an entry for each ISA-AA Group
         and Partition configured in the system.

         Rows in this table are automatically created and destroyed when the
         corresponding tmnxBsxAaGrpPartEntry is created or destroyed."
    ::= { tmnxBsxStatsObjs 24 }

tmnxBsxAdmitDenyAcctEntry        OBJECT-TYPE
    SYNTAX      TmnxBsxAdmitDenyAcctEntry
    MAX-ACCESS  not-accessible
    STATUS      current
    DESCRIPTION
        "Each tmnxBsxAdmitDenyAcctEntry indicates the ISA-AA admit-deny
         statistics configuration per ISA-AA Group and Partition."
    INDEX       { tmnxBsxAaGrpPartIndex }
    ::= { tmnxBsxAdmitDenyAcctTable 1 }

TmnxBsxAdmitDenyAcctEntry        ::= SEQUENCE
{
    tmnxBsxAdmitDenyAcctRowLastCh    TimeStamp,
    tmnxBsxAdmitDenyAcctPolicy       Unsigned32,
    tmnxBsxAdmitDenyAcctCollStats    TmnxEnabledDisabled,
    tmnxBsxAdmitDenyAcctSctpFtrStats TmnxEnabledDisabled,
    tmnxBsxAdmitDenyAcctGtpFtrStats  TmnxEnabledDisabled,
    tmnxBsxAdmitDenyAcctSessFtrStats TmnxEnabledDisabled,
    tmnxBsxAdmitDenyAcctPolcrStats   TmnxEnabledDisabled,
    tmnxBsxAdmitDenyAcctPolcrResrcs  TmnxEnabledDisabled,
    tmnxBsxAdmitDenyAcctTcpValStats  TmnxEnabledDisabled
}

tmnxBsxAdmitDenyAcctRowLastCh    OBJECT-TYPE
    SYNTAX      TimeStamp
    MAX-ACCESS  read-only
    STATUS      current
    DESCRIPTION
        "The value of tmnxBsxAdmitDenyAcctRowLastCh indicates the last time,
         since system startup, a successful SNMP set caused a value in this row
         to change."
    ::= { tmnxBsxAdmitDenyAcctEntry 1 }

tmnxBsxAdmitDenyAcctPolicy       OBJECT-TYPE
    SYNTAX      Unsigned32 (0..99)
    MAX-ACCESS  read-write
    STATUS      current
    DESCRIPTION
        "The value of tmnxBsxAdmitDenyAcctPolicy specifies the accounting
         policy to use, as defined in TIMETRA-LOG-MIB::tmnxLogApEntry.

         A value of '0' specifies that no accounting policy is in use."
    DEFVAL      { 0 }
    ::= { tmnxBsxAdmitDenyAcctEntry 2 }

tmnxBsxAdmitDenyAcctCollStats    OBJECT-TYPE
    SYNTAX      TmnxEnabledDisabled
    MAX-ACCESS  read-write
    STATUS      current
    DESCRIPTION
        "The value of tmnxBsxAdmitDenyAcctCollStats specifies whether or not
         admit-deny statistics collection for accounting is enabled."
    DEFVAL      { disabled }
    ::= { tmnxBsxAdmitDenyAcctEntry 3 }

tmnxBsxAdmitDenyAcctSctpFtrStats OBJECT-TYPE
    SYNTAX      TmnxEnabledDisabled
    MAX-ACCESS  read-write
    STATUS      current
    DESCRIPTION
        "The value of tmnxBsxAdmitDenyAcctSctpFtrStats specifies whether or not
         SCTP filter admit-deny statistics are included in accounting. Note
         that tmnxBsxAdmitDenyAcctCollStats must have a value of 'enabled (1)'
         in order for statistics collection to occur."
    DEFVAL      { disabled }
    ::= { tmnxBsxAdmitDenyAcctEntry 4 }

tmnxBsxAdmitDenyAcctGtpFtrStats  OBJECT-TYPE
    SYNTAX      TmnxEnabledDisabled
    MAX-ACCESS  read-write
    STATUS      current
    DESCRIPTION
        "The value of tmnxBsxAdmitDenyAcctGtpFtrStats specifies whether or not
         GTP filter admit-deny statistics are included in accounting. Note that
         tmnxBsxAdmitDenyAcctCollStats must have a value of 'enabled (1)' in
         order for statistics collection to occur."
    DEFVAL      { disabled }
    ::= { tmnxBsxAdmitDenyAcctEntry 5 }

tmnxBsxAdmitDenyAcctSessFtrStats OBJECT-TYPE
    SYNTAX      TmnxEnabledDisabled
    MAX-ACCESS  read-write
    STATUS      current
    DESCRIPTION
        "The value of tmnxBsxAdmitDenyAcctSessFtrStats specifies whether or not
         session filter admit-deny statistics are included in accounting. Note
         that tmnxBsxAdmitDenyAcctCollStats must have a value of 'enabled (1)'
         in order for statistics collection to occur."
    DEFVAL      { disabled }
    ::= { tmnxBsxAdmitDenyAcctEntry 6 }

tmnxBsxAdmitDenyAcctPolcrStats   OBJECT-TYPE
    SYNTAX      TmnxEnabledDisabled
    MAX-ACCESS  read-write
    STATUS      current
    DESCRIPTION
        "The value of tmnxBsxAdmitDenyAcctPolcrStats specifies whether or not
         policer admit-deny statistics are included in accounting. Note that
         tmnxBsxAdmitDenyAcctCollStats must have a value of 'enabled (1)' in
         order for statistics collection to occur."
    DEFVAL      { disabled }
    ::= { tmnxBsxAdmitDenyAcctEntry 7 }

tmnxBsxAdmitDenyAcctPolcrResrcs  OBJECT-TYPE
    SYNTAX      TmnxEnabledDisabled
    MAX-ACCESS  read-write
    STATUS      current
    DESCRIPTION
        "The value of tmnxBsxAdmitDenyAcctPolcrResrcs specifies whether or not
         ISA resources are allocated for policer admit-deny statistics
         collection."
    DEFVAL      { disabled }
    ::= { tmnxBsxAdmitDenyAcctEntry 8 }

tmnxBsxAdmitDenyAcctTcpValStats  OBJECT-TYPE
    SYNTAX      TmnxEnabledDisabled
    MAX-ACCESS  read-write
    STATUS      current
    DESCRIPTION
        "The value of tmnxBsxAdmitDenyAcctTcpValStats specifies whether or not
         TCP validate admit-deny statistics are included in accounting. Note
         that tmnxBsxAdmitDenyAcctCollStats must have a value of 'enabled (1)'
         in order for statistics collection to occur."
    DEFVAL      { disabled }
    ::= { tmnxBsxAdmitDenyAcctEntry 9 }

tmnxBsxTcaStatsTable             OBJECT-TYPE
    SYNTAX      SEQUENCE OF TmnxBsxTcaStatsEntry
    MAX-ACCESS  not-accessible
    STATUS      current
    DESCRIPTION
        "The tmnxBsxTcaStatsTable contains an entry for each configured
         Application Assurance TCA, as configured in tmnxBsxStatTcaCfgTable."
    ::= { tmnxBsxStatsObjs 25 }

tmnxBsxTcaStatsEntry             OBJECT-TYPE
    SYNTAX      TmnxBsxTcaStatsEntry
    MAX-ACCESS  not-accessible
    STATUS      current
    DESCRIPTION
        "Each tmnxBsxTcaStatsEntry specifies Application Assurance TCA
         statistics per group/partition and TCA.

         Rows in this table are automatically created and destroyed when TCAs
         are created or destroyed in the tmnxBsxStatTcaCfgTable."
    INDEX       {
        tmnxBsxAaGrpPartIndex,
        tmnxBsxStatTcaCfgType,
        tmnxBsxStatTcaCfgDirection
    }
    ::= { tmnxBsxTcaStatsTable 1 }

TmnxBsxTcaStatsEntry             ::= SEQUENCE
{
    tmnxBsxTcaStatsTimeLastRaised    TimeStamp,
    tmnxBsxTcaStatsTimeLastCleared   TimeStamp,
    tmnxBsxTcaStatsTcaState          TmnxBsxTcaState,
    tmnxBsxTcaStatsTcaTrigType       TmnxBsxTcaTriggerType
}

tmnxBsxTcaStatsTimeLastRaised    OBJECT-TYPE
    SYNTAX      TimeStamp
    MAX-ACCESS  read-only
    STATUS      current
    DESCRIPTION
        "The value of tmnxBsxTcaStatsTimeLastRaised indicates the last time,
         since system startup, when the tmnxBsxTcaStatsTcaState changed from
         'cleared (0)' to 'raised (1)'."
    ::= { tmnxBsxTcaStatsEntry 1 }

tmnxBsxTcaStatsTimeLastCleared   OBJECT-TYPE
    SYNTAX      TimeStamp
    MAX-ACCESS  read-only
    STATUS      current
    DESCRIPTION
        "The value of tmnxBsxTcaStatsTimeLastCleared indicates the last time,
         since system startup, when the tmnxBsxTcaStatsTcaState changed from
         'raised (1)' to 'cleared (0)'."
    ::= { tmnxBsxTcaStatsEntry 2 }

tmnxBsxTcaStatsTcaState          OBJECT-TYPE
    SYNTAX      TmnxBsxTcaState
    MAX-ACCESS  read-only
    STATUS      current
    DESCRIPTION
        "The value of tmnxBsxTcaStatsTcaState indicates the state of the TCA."
    ::= { tmnxBsxTcaStatsEntry 3 }

tmnxBsxTcaStatsTcaTrigType       OBJECT-TYPE
    SYNTAX      TmnxBsxTcaTriggerType
    MAX-ACCESS  read-only
    STATUS      current
    DESCRIPTION
        "The value of tmnxBsxTcaStatsTcaTrigType indicates the trigger type
         used."
    ::= { tmnxBsxTcaStatsEntry 4 }

tmnxBsxTcaPolcrStatsTable        OBJECT-TYPE
    SYNTAX      SEQUENCE OF TmnxBsxTcaPolcrStatsEntry
    MAX-ACCESS  not-accessible
    STATUS      current
    DESCRIPTION
        "The tmnxBsxTcaPolcrStatsTable contains an entry for each configured
         Application Assurance policer TCA, as configured in
         tmnxBsxStatTcaPolcrCfgTable."
    ::= { tmnxBsxStatsObjs 26 }

tmnxBsxTcaPolcrStatsEntry        OBJECT-TYPE
    SYNTAX      TmnxBsxTcaPolcrStatsEntry
    MAX-ACCESS  not-accessible
    STATUS      current
    DESCRIPTION
        "Each tmnxBsxTcaPolcrStatsEntry specifies Application Assurance policer
         TCA statistics per group/partition and TCA.

         Rows in this table are automatically created and destroyed when TCAs
         are created or destroyed in the tmnxBsxStatTcaPolcrCfgTable."
    INDEX       {
        tmnxBsxAaGrpPartIndex,
        tmnxBsxPolicerName,
        tmnxBsxStatTcaCfgDirection
    }
    ::= { tmnxBsxTcaPolcrStatsTable 1 }

TmnxBsxTcaPolcrStatsEntry        ::= SEQUENCE
{
    tmnxBsxTcaPolcrStatsTmLastRaised TimeStamp,
    tmnxBsxTcaPolcrStatsTmLastCleard TimeStamp,
    tmnxBsxTcaPolcrStatsTcaState     TmnxBsxTcaState,
    tmnxBsxTcaPolcrStatsTcaTrigType  TmnxBsxTcaTriggerType
}

tmnxBsxTcaPolcrStatsTmLastRaised OBJECT-TYPE
    SYNTAX      TimeStamp
    MAX-ACCESS  read-only
    STATUS      current
    DESCRIPTION
        "The value of tmnxBsxTcaPolcrStatsTmLastRaised indicates the last time,
         since system startup, when the tmnxBsxTcaPolcrStatsTcaState changed
         from 'cleared (0)' to 'raised (1)'."
    ::= { tmnxBsxTcaPolcrStatsEntry 1 }

tmnxBsxTcaPolcrStatsTmLastCleard OBJECT-TYPE
    SYNTAX      TimeStamp
    MAX-ACCESS  read-only
    STATUS      current
    DESCRIPTION
        "The value of tmnxBsxTcaPolcrStatsTmLastCleard indicates the last time,
         since system startup, when the tmnxBsxTcaPolcrStatsTcaState changed
         from 'raised (1)' to 'cleared (0)'."
    ::= { tmnxBsxTcaPolcrStatsEntry 2 }

tmnxBsxTcaPolcrStatsTcaState     OBJECT-TYPE
    SYNTAX      TmnxBsxTcaState
    MAX-ACCESS  read-only
    STATUS      current
    DESCRIPTION
        "The value of tmnxBsxTcaPolcrStatsTcaState indicates the state of the
         policer TCA."
    ::= { tmnxBsxTcaPolcrStatsEntry 3 }

tmnxBsxTcaPolcrStatsTcaTrigType  OBJECT-TYPE
    SYNTAX      TmnxBsxTcaTriggerType
    MAX-ACCESS  read-only
    STATUS      current
    DESCRIPTION
        "The value of tmnxBsxTcaPolcrStatsTcaTrigType indicates the trigger
         type used."
    ::= { tmnxBsxTcaPolcrStatsEntry 4 }

tmnxBsxTcaFtrStatsTable          OBJECT-TYPE
    SYNTAX      SEQUENCE OF TmnxBsxTcaFtrStatsEntry
    MAX-ACCESS  not-accessible
    STATUS      current
    DESCRIPTION
        "The tmnxBsxTcaFtrStatsTable contains an entry for each configured
         Application Assurance filter TCA, as configured in
         tmnxBsxStatTcaFtrCfgTable."
    ::= { tmnxBsxStatsObjs 27 }

tmnxBsxTcaFtrStatsEntry          OBJECT-TYPE
    SYNTAX      TmnxBsxTcaFtrStatsEntry
    MAX-ACCESS  not-accessible
    STATUS      current
    DESCRIPTION
        "Each tmnxBsxTcaFtrStatsEntry specifies Application Assurance filter
         TCA statistics per group/partition and TCA.

         Rows in this table are automatically created and destroyed when TCAs
         are created or destroyed in the tmnxBsxStatTcaFtrCfgTable."
    INDEX       {
        tmnxBsxAaGrpPartIndex,
        tmnxBsxStatTcaCfgFilterType,
        tmnxBsxStatTcaCfgFilterName,
        tmnxBsxStatTcaCfgFilterWmarkType,
        tmnxBsxStatTcaCfgDirection
    }
    ::= { tmnxBsxTcaFtrStatsTable 1 }

TmnxBsxTcaFtrStatsEntry          ::= SEQUENCE
{
    tmnxBsxTcaFtrStatsTimeLastRaised TimeStamp,
    tmnxBsxTcaFtrStatsTimeLastCleard TimeStamp,
    tmnxBsxTcaFtrStatsTcaState       TmnxBsxTcaState,
    tmnxBsxTcaFtrStatsTcaTrigType    TmnxBsxTcaTriggerType
}

tmnxBsxTcaFtrStatsTimeLastRaised OBJECT-TYPE
    SYNTAX      TimeStamp
    MAX-ACCESS  read-only
    STATUS      current
    DESCRIPTION
        "The value of tmnxBsxTcaFtrStatsTimeLastRaised indicates the last time,
         since system startup, when the tmnxBsxTcaFtrStatsTcaState changed from
         'cleared (0)' to 'raised (1)'."
    ::= { tmnxBsxTcaFtrStatsEntry 1 }

tmnxBsxTcaFtrStatsTimeLastCleard OBJECT-TYPE
    SYNTAX      TimeStamp
    MAX-ACCESS  read-only
    STATUS      current
    DESCRIPTION
        "The value of tmnxBsxTcaFtrStatsTimeLastCleard indicates the last time,
         since system startup, when the tmnxBsxTcaFtrStatsTcaState changed from
         'raised (1)' to 'cleared (0)'."
    ::= { tmnxBsxTcaFtrStatsEntry 2 }

tmnxBsxTcaFtrStatsTcaState       OBJECT-TYPE
    SYNTAX      TmnxBsxTcaState
    MAX-ACCESS  read-only
    STATUS      current
    DESCRIPTION
        "The value of tmnxBsxTcaFtrStatsTcaState indicates the state of the
         filter TCA."
    ::= { tmnxBsxTcaFtrStatsEntry 3 }

tmnxBsxTcaFtrStatsTcaTrigType    OBJECT-TYPE
    SYNTAX      TmnxBsxTcaTriggerType
    MAX-ACCESS  read-only
    STATUS      current
    DESCRIPTION
        "The value of tmnxBsxTcaFtrStatsTcaTrigType indicates the trigger type
         used."
    ::= { tmnxBsxTcaFtrStatsEntry 4 }

tmnxBsxTcaFtrEnStatsTable        OBJECT-TYPE
    SYNTAX      SEQUENCE OF TmnxBsxTcaFtrEnStatsEntry
    MAX-ACCESS  not-accessible
    STATUS      current
    DESCRIPTION
        "The tmnxBsxTcaFtrEnStatsTable contains an entry for each configured
         Application Assurance filter entry TCA, as configured in
         tmnxBsxStatTcaFtrEnCfgTable."
    ::= { tmnxBsxStatsObjs 28 }

tmnxBsxTcaFtrEnStatsEntry        OBJECT-TYPE
    SYNTAX      TmnxBsxTcaFtrEnStatsEntry
    MAX-ACCESS  not-accessible
    STATUS      current
    DESCRIPTION
        "Each tmnxBsxTcaFtrEnStatsEntry specifies Application Assurance filter
         entry TCA statistics per group/partition and TCA.

         Rows in this table are automatically created and destroyed when TCAs
         are created or destroyed in the tmnxBsxStatTcaFtrEnCfgTable."
    INDEX       {
        tmnxBsxAaGrpPartIndex,
        tmnxBsxStatTcaCfgFilterType,
        tmnxBsxStatTcaCfgFilterName,
        tmnxBsxStatTcaFtrEnCfgEntryId,
        tmnxBsxStatTcaCfgDirection
    }
    ::= { tmnxBsxTcaFtrEnStatsTable 1 }

TmnxBsxTcaFtrEnStatsEntry        ::= SEQUENCE
{
    tmnxBsxTcaFtrEnStatsTmLastRaised TimeStamp,
    tmnxBsxTcaFtrEnStatsTmLastCleard TimeStamp,
    tmnxBsxTcaFtrEnStatsTcaState     TmnxBsxTcaState,
    tmnxBsxTcaFtrEnStatsTcaTrigType  TmnxBsxTcaTriggerType
}

tmnxBsxTcaFtrEnStatsTmLastRaised OBJECT-TYPE
    SYNTAX      TimeStamp
    MAX-ACCESS  read-only
    STATUS      current
    DESCRIPTION
        "The value of tmnxBsxTcaFtrEnStatsTmLastRaised indicates the last time,
         since system startup, when the tmnxBsxTcaFtrEnStatsTcaState changed
         from 'cleared (0)' to 'raised (1)'."
    ::= { tmnxBsxTcaFtrEnStatsEntry 1 }

tmnxBsxTcaFtrEnStatsTmLastCleard OBJECT-TYPE
    SYNTAX      TimeStamp
    MAX-ACCESS  read-only
    STATUS      current
    DESCRIPTION
        "The value of tmnxBsxTcaFtrEnStatsTmLastCleard indicates the last time,
         since system startup, when the tmnxBsxTcaFtrEnStatsTcaState changed
         from 'raised (1)' to 'cleared (0)'."
    ::= { tmnxBsxTcaFtrEnStatsEntry 2 }

tmnxBsxTcaFtrEnStatsTcaState     OBJECT-TYPE
    SYNTAX      TmnxBsxTcaState
    MAX-ACCESS  read-only
    STATUS      current
    DESCRIPTION
        "The value of tmnxBsxTcaFtrEnStatsTcaState indicates the state of the
         filter entry TCA."
    ::= { tmnxBsxTcaFtrEnStatsEntry 3 }

tmnxBsxTcaFtrEnStatsTcaTrigType  OBJECT-TYPE
    SYNTAX      TmnxBsxTcaTriggerType
    MAX-ACCESS  read-only
    STATUS      current
    DESCRIPTION
        "The value of tmnxBsxTcaFtrEnStatsTcaTrigType indicates the trigger
         type used."
    ::= { tmnxBsxTcaFtrEnStatsEntry 4 }

tmnxBsxStatsFlowAttrTable        OBJECT-TYPE
    SYNTAX      SEQUENCE OF TmnxBsxStatsFlowAttrEntry
    MAX-ACCESS  not-accessible
    STATUS      current
    DESCRIPTION
        "The tmnxBsxStatsFlowAttrTable contains an entry for each flow
         attribute and confidence bin pairing per ISA.

         Rows in this table are automatically created for every defined flow
         attribute/confidence bin."
    ::= { tmnxBsxStatsObjs 29 }

tmnxBsxStatsFlowAttrEntry        OBJECT-TYPE
    SYNTAX      TmnxBsxStatsFlowAttrEntry
    MAX-ACCESS  not-accessible
    STATUS      current
    DESCRIPTION
        "Each tmnxBsxStatsFlowAttrEntry specifies Application Assurance flow
         attributes/confidence bin statistics.

         Indexing with a valid flow attribute and confidence bin (an existing
         row in tmnxBsxStatsFlowAttrTable) and tmnxChassisIndex set to one with
         a zero value for each of tmnxBsxCardSlotEsaId and
         tmnxBsxMdaSlotEsaVmId will return the summarized statistics per
         group/partition and flow attribute/confidence bin."
    INDEX       {
        tmnxBsxAaGrpPartIndex,
        tmnxBsxAqpFlowAttr,
        tmnxBsxFlowAttrConfBin,
        tmnxChassisIndex,
        tmnxBsxCardSlotEsaId,
        tmnxBsxMdaSlotEsaVmId
    }
    ::= { tmnxBsxStatsFlowAttrTable 1 }

TmnxBsxStatsFlowAttrEntry        ::= SEQUENCE
{
    tmnxBsxFlowAttrConfBin           Unsigned32,
    tmnxBsxStatFlowAttrConfBinName   TNamedItem,
    tmnxBsxFlowAttrStatsDiscontTime  TimeStamp,
    tmnxBsxStatFlowAttrOctsFmSb      Counter64,
    tmnxBsxStatFlowAttrPktsFmSb      Counter64,
    tmnxBsxStatFlowAttrFlwsFmSb      Counter64,
    tmnxBsxStatFlowAttrOctsToSb      Counter64,
    tmnxBsxStatFlowAttrPktsToSb      Counter64,
    tmnxBsxStatFlowAttrFlwsToSb      Counter64
}

tmnxBsxFlowAttrConfBin           OBJECT-TYPE
    SYNTAX      Unsigned32 (0..99)
    MAX-ACCESS  not-accessible
    STATUS      current
    DESCRIPTION
        "The value of tmnxBsxFlowAttrConfBin specifies the confidence bin of
         the flow attribute."
    ::= { tmnxBsxStatsFlowAttrEntry 1 }

tmnxBsxStatFlowAttrConfBinName   OBJECT-TYPE
    SYNTAX      TNamedItem
    MAX-ACCESS  read-only
    STATUS      current
    DESCRIPTION
        "The value of tmnxBsxStatFlowAttrConfBinName specifies the name of the
         confidence bin of a flow attribute."
    ::= { tmnxBsxStatsFlowAttrEntry 2 }

tmnxBsxFlowAttrStatsDiscontTime  OBJECT-TYPE
    SYNTAX      TimeStamp
    MAX-ACCESS  read-only
    STATUS      current
    DESCRIPTION
        "The value of tmnxBsxFlowAttrStatsDiscontTime indicates discontinuity
         time. This is the SNMPv2-MIB::sysUpTime (centiseconds) when the ISA-AA
         MDA within the group last changed status."
    ::= { tmnxBsxStatsFlowAttrEntry 3 }

tmnxBsxStatFlowAttrOctsFmSb      OBJECT-TYPE
    SYNTAX      Counter64
    UNITS       "bytes"
    MAX-ACCESS  read-only
    STATUS      current
    DESCRIPTION
        "The value of tmnxBsxStatFlowAttrOctsFmSb indicates the number of bytes
         in the subscriber to network direction for a flow attribute/confidence
         pair."
    ::= { tmnxBsxStatsFlowAttrEntry 4 }

tmnxBsxStatFlowAttrPktsFmSb      OBJECT-TYPE
    SYNTAX      Counter64
    UNITS       "packets"
    MAX-ACCESS  read-only
    STATUS      current
    DESCRIPTION
        "The value of tmnxBsxStatFlowAttrPktsFmSb indicates the number of
         packets in the subscriber to network direction for a flow
         attribute/confidence pair."
    ::= { tmnxBsxStatsFlowAttrEntry 5 }

tmnxBsxStatFlowAttrFlwsFmSb      OBJECT-TYPE
    SYNTAX      Counter64
    UNITS       "flows"
    MAX-ACCESS  read-only
    STATUS      current
    DESCRIPTION
        "The value of tmnxBsxStatFlowAttrFlwsFmSb indicates the number of flows
         in the subscriber to network direction for a flow attribute/confidence
         pair."
    ::= { tmnxBsxStatsFlowAttrEntry 6 }

tmnxBsxStatFlowAttrOctsToSb      OBJECT-TYPE
    SYNTAX      Counter64
    UNITS       "bytes"
    MAX-ACCESS  read-only
    STATUS      current
    DESCRIPTION
        "The value of tmnxBsxStatFlowAttrOctsToSb indicates the number of bytes
         in the network to subscriber direction for a flow attribute/confidence
         pair."
    ::= { tmnxBsxStatsFlowAttrEntry 7 }

tmnxBsxStatFlowAttrPktsToSb      OBJECT-TYPE
    SYNTAX      Counter64
    UNITS       "packets"
    MAX-ACCESS  read-only
    STATUS      current
    DESCRIPTION
        "The value of tmnxBsxStatFlowAttrPktsToSb indicates the number of
         packets in the network to subscriber direction for a flow
         attribute/confidence pair."
    ::= { tmnxBsxStatsFlowAttrEntry 8 }

tmnxBsxStatFlowAttrFlwsToSb      OBJECT-TYPE
    SYNTAX      Counter64
    UNITS       "flows"
    MAX-ACCESS  read-only
    STATUS      current
    DESCRIPTION
        "The value of tmnxBsxStatFlowAttrFlwsToSb indicates the number of flows
         in the network to subscriber direction for a flow attribute/confidence
         pair."
    ::= { tmnxBsxStatsFlowAttrEntry 9 }

tmnxBsxTlsTrafficStatsTable      OBJECT-TYPE
    SYNTAX      SEQUENCE OF TmnxBsxTlsTrafficStatsEntry
    MAX-ACCESS  not-accessible
    STATUS      current
    DESCRIPTION
        "The tmnxBsxTlsTrafficStatsTable contains TLS traffic statistics per
         group and partition."
    ::= { tmnxBsxStatsObjs 30 }

tmnxBsxTlsTrafficStatsEntry      OBJECT-TYPE
    SYNTAX      TmnxBsxTlsTrafficStatsEntry
    MAX-ACCESS  not-accessible
    STATUS      current
    DESCRIPTION
        "Each tmnxBsxTlsTrafficStatsEntry contains the traffic statistics for a
         particular group and partition."
    INDEX       {
        tmnxBsxAaGrpPartIndex,
        tmnxChassisIndex,
        tmnxBsxCardSlotEsaId,
        tmnxBsxMdaSlotEsaVmId
    }
    ::= { tmnxBsxTlsTrafficStatsTable 1 }

TmnxBsxTlsTrafficStatsEntry      ::= SEQUENCE
{
    tmnxBsxTlsStatDiscontTime        TimeStamp,
    tmnxBsxTlsStatQuicOctsAdm        Counter64,
    tmnxBsxTlsStatQuicOctsDny        Counter64,
    tmnxBsxTlsStatQuicPktsAdm        Counter64,
    tmnxBsxTlsStatQuicPktsDny        Counter64,
    tmnxBsxTlsStatQuicFlwsAdm        Counter64,
    tmnxBsxTlsStatQuicFlwsDny        Counter64,
    tmnxBsxTlsStatQuicEsniOctsAdm    Counter64,
    tmnxBsxTlsStatQuicEsniOctsDny    Counter64,
    tmnxBsxTlsStatQuicEsniPktsAdm    Counter64,
    tmnxBsxTlsStatQuicEsniPktsDny    Counter64,
    tmnxBsxTlsStatQuicEsniFlwsAdm    Counter64,
    tmnxBsxTlsStatQuicEsniFlwsDny    Counter64,
    tmnxBsxTlsStatQuicExistOctsAdm   Counter64,
    tmnxBsxTlsStatQuicExistOctsDny   Counter64,
    tmnxBsxTlsStatQuicExistPktsAdm   Counter64,
    tmnxBsxTlsStatQuicExistPktsDny   Counter64,
    tmnxBsxTlsStatQuicExistFlwsAdm   Counter64,
    tmnxBsxTlsStatQuicExistFlwsDny   Counter64,
    tmnxBsxTlsStatQuicUnknwnOctsAdm  Counter64,
    tmnxBsxTlsStatQuicUnknwnOctsDny  Counter64,
    tmnxBsxTlsStatQuicUnknwnPktsAdm  Counter64,
    tmnxBsxTlsStatQuicUnknwnPktsDny  Counter64,
    tmnxBsxTlsStatQuicUnknwnFlwsAdm  Counter64,
    tmnxBsxTlsStatQuicUnknwnFlwsDny  Counter64,
    tmnxBsxTlsStatTls10OctsAdm       Counter64,
    tmnxBsxTlsStatTls10OctsDny       Counter64,
    tmnxBsxTlsStatTls10PktsAdm       Counter64,
    tmnxBsxTlsStatTls10PktsDny       Counter64,
    tmnxBsxTlsStatTls10FlwsAdm       Counter64,
    tmnxBsxTlsStatTls10FlwsDny       Counter64,
    tmnxBsxTlsStatTls11OctsAdm       Counter64,
    tmnxBsxTlsStatTls11OctsDny       Counter64,
    tmnxBsxTlsStatTls11PktsAdm       Counter64,
    tmnxBsxTlsStatTls11PktsDny       Counter64,
    tmnxBsxTlsStatTls11FlwsAdm       Counter64,
    tmnxBsxTlsStatTls11FlwsDny       Counter64,
    tmnxBsxTlsStatTls12OctsAdm       Counter64,
    tmnxBsxTlsStatTls12OctsDny       Counter64,
    tmnxBsxTlsStatTls12PktsAdm       Counter64,
    tmnxBsxTlsStatTls12PktsDny       Counter64,
    tmnxBsxTlsStatTls12FlwsAdm       Counter64,
    tmnxBsxTlsStatTls12FlwsDny       Counter64,
    tmnxBsxTlsStatTls13OctsAdm       Counter64,
    tmnxBsxTlsStatTls13OctsDny       Counter64,
    tmnxBsxTlsStatTls13PktsAdm       Counter64,
    tmnxBsxTlsStatTls13PktsDny       Counter64,
    tmnxBsxTlsStatTls13FlwsAdm       Counter64,
    tmnxBsxTlsStatTls13FlwsDny       Counter64,
    tmnxBsxTlsStatTls13EsniOctsAdm   Counter64,
    tmnxBsxTlsStatTls13EsniOctsDny   Counter64,
    tmnxBsxTlsStatTls13EsniPktsAdm   Counter64,
    tmnxBsxTlsStatTls13EsniPktsDny   Counter64,
    tmnxBsxTlsStatTls13EsniFlwsAdm   Counter64,
    tmnxBsxTlsStatTls13EsniFlwsDny   Counter64,
    tmnxBsxTlsStatTlsExistOctsAdm    Counter64,
    tmnxBsxTlsStatTlsExistOctsDny    Counter64,
    tmnxBsxTlsStatTlsExistPktsAdm    Counter64,
    tmnxBsxTlsStatTlsExistPktsDny    Counter64,
    tmnxBsxTlsStatTlsExistFlwsAdm    Counter64,
    tmnxBsxTlsStatTlsExistFlwsDny    Counter64,
    tmnxBsxTlsStatTlsUnknownOctsAdm  Counter64,
    tmnxBsxTlsStatTlsUnknownOctsDny  Counter64,
    tmnxBsxTlsStatTlsUnknownPktsAdm  Counter64,
    tmnxBsxTlsStatTlsUnknownPktsDny  Counter64,
    tmnxBsxTlsStatTlsUnknownFlwsAdm  Counter64,
    tmnxBsxTlsStatTlsUnknownFlwsDny  Counter64
}

tmnxBsxTlsStatDiscontTime        OBJECT-TYPE
    SYNTAX      TimeStamp
    MAX-ACCESS  read-only
    STATUS      current
    DESCRIPTION
        "The value of tmnxBsxTlsStatDiscontTime indicates the
         SNMPv2-MIB::sysUpTime (centiseconds) when any of the active ISA-AA
         within the group last changed status."
    ::= { tmnxBsxTlsTrafficStatsEntry 1 }

tmnxBsxTlsStatQuicOctsAdm        OBJECT-TYPE
    SYNTAX      Counter64
    UNITS       "bytes"
    MAX-ACCESS  read-only
    STATUS      current
    DESCRIPTION
        "The value of tmnxBsxTlsStatQuicOctsAdm indicates the total number of
         QUIC traffic bytes permitted."
    ::= { tmnxBsxTlsTrafficStatsEntry 2 }

tmnxBsxTlsStatQuicOctsDny        OBJECT-TYPE
    SYNTAX      Counter64
    UNITS       "packets"
    MAX-ACCESS  read-only
    STATUS      current
    DESCRIPTION
        "The value of tmnxBsxTlsStatQuicOctsDny indicates the total number of
         QUIC traffic bytes dropped."
    ::= { tmnxBsxTlsTrafficStatsEntry 3 }

tmnxBsxTlsStatQuicPktsAdm        OBJECT-TYPE
    SYNTAX      Counter64
    UNITS       "bytes"
    MAX-ACCESS  read-only
    STATUS      current
    DESCRIPTION
        "The value of tmnxBsxTlsStatQuicPktsAdm indicates the total number of
         QUIC traffic packets permitted."
    ::= { tmnxBsxTlsTrafficStatsEntry 4 }

tmnxBsxTlsStatQuicPktsDny        OBJECT-TYPE
    SYNTAX      Counter64
    UNITS       "packets"
    MAX-ACCESS  read-only
    STATUS      current
    DESCRIPTION
        "The value of tmnxBsxTlsStatQuicPktsDny indicates the total number of
         QUIC traffic packets dropped."
    ::= { tmnxBsxTlsTrafficStatsEntry 5 }

tmnxBsxTlsStatQuicFlwsAdm        OBJECT-TYPE
    SYNTAX      Counter64
    UNITS       "flows"
    MAX-ACCESS  read-only
    STATUS      current
    DESCRIPTION
        "The value of tmnxBsxTlsStatQuicFlwsAdm  indicates the
         total number of flows of QUIC traffic permitted."
    ::= { tmnxBsxTlsTrafficStatsEntry 6 }

tmnxBsxTlsStatQuicFlwsDny        OBJECT-TYPE
    SYNTAX      Counter64
    UNITS       "flows"
    MAX-ACCESS  read-only
    STATUS      current
    DESCRIPTION
        "The value of tmnxBsxTlsStatQuicFlwsDny indicates the total number of
         flows of QUIC traffic that dropped subsequent packets."
    ::= { tmnxBsxTlsTrafficStatsEntry 7 }

tmnxBsxTlsStatQuicEsniOctsAdm    OBJECT-TYPE
    SYNTAX      Counter64
    UNITS       "bytes"
    MAX-ACCESS  read-only
    STATUS      current
    DESCRIPTION
        "The value of tmnxBsxTlsStatQuicEsniOctsAdm indicates the total number
         of QUIC with eSNI traffic bytes permitted."
    ::= { tmnxBsxTlsTrafficStatsEntry 8 }

tmnxBsxTlsStatQuicEsniOctsDny    OBJECT-TYPE
    SYNTAX      Counter64
    UNITS       "bytes"
    MAX-ACCESS  read-only
    STATUS      current
    DESCRIPTION
        "The value of tmnxBsxTlsStatQuicEsniOctsDny indicates the total number
         of QUIC with eSNI traffic bytes dropped."
    ::= { tmnxBsxTlsTrafficStatsEntry 9 }

tmnxBsxTlsStatQuicEsniPktsAdm    OBJECT-TYPE
    SYNTAX      Counter64
    UNITS       "packets"
    MAX-ACCESS  read-only
    STATUS      current
    DESCRIPTION
        "The value of tmnxBsxTlsStatQuicEsniPktsAdm indicates the total number
         of QUIC with eSNI traffic packets permitted."
    ::= { tmnxBsxTlsTrafficStatsEntry 10 }

tmnxBsxTlsStatQuicEsniPktsDny    OBJECT-TYPE
    SYNTAX      Counter64
    UNITS       "packets"
    MAX-ACCESS  read-only
    STATUS      current
    DESCRIPTION
        "The value of tmnxBsxTlsStatQuicEsniPktsDny indicates the total number
         of QUIC with eSNI traffic packets dropped."
    ::= { tmnxBsxTlsTrafficStatsEntry 11 }

tmnxBsxTlsStatQuicEsniFlwsAdm    OBJECT-TYPE
    SYNTAX      Counter64
    UNITS       "flows"
    MAX-ACCESS  read-only
    STATUS      current
    DESCRIPTION
        "The value of tmnxBsxTlsStatQuicEsniFlwsAdm  indicates the
         total number of flows of QUIC with eSNI traffic permitted."
    ::= { tmnxBsxTlsTrafficStatsEntry 12 }

tmnxBsxTlsStatQuicEsniFlwsDny    OBJECT-TYPE
    SYNTAX      Counter64
    UNITS       "flows"
    MAX-ACCESS  read-only
    STATUS      current
    DESCRIPTION
        "The value of tmnxBsxTlsStatQuicEsniFlwsDny indicates the total number
         of flows of QUIC with eSNI traffic that dropped subsequent packets."
    ::= { tmnxBsxTlsTrafficStatsEntry 13 }

tmnxBsxTlsStatQuicExistOctsAdm   OBJECT-TYPE
    SYNTAX      Counter64
    UNITS       "bytes"
    MAX-ACCESS  read-only
    STATUS      current
    DESCRIPTION
        "The value of tmnxBsxTlsStatQuicExistOctsAdm indicates the total number
         of midstream-detected existing TLS quic traffic bytes permitted."
    ::= { tmnxBsxTlsTrafficStatsEntry 14 }

tmnxBsxTlsStatQuicExistOctsDny   OBJECT-TYPE
    SYNTAX      Counter64
    UNITS       "bytes"
    MAX-ACCESS  read-only
    STATUS      current
    DESCRIPTION
        "The value of tmnxBsxTlsStatQuicExistOctsDny indicates the total number
         of midstream-detected existing TLS quic traffic bytes dropped."
    ::= { tmnxBsxTlsTrafficStatsEntry 15 }

tmnxBsxTlsStatQuicExistPktsAdm   OBJECT-TYPE
    SYNTAX      Counter64
    UNITS       "packets"
    MAX-ACCESS  read-only
    STATUS      current
    DESCRIPTION
        "The value of tmnxBsxTlsStatQuicExistPktsAdm indicates the total number
         of midstream-detected existing TLS quic traffic packets permitted."
    ::= { tmnxBsxTlsTrafficStatsEntry 16 }

tmnxBsxTlsStatQuicExistPktsDny   OBJECT-TYPE
    SYNTAX      Counter64
    UNITS       "packets"
    MAX-ACCESS  read-only
    STATUS      current
    DESCRIPTION
        "The value of tmnxBsxTlsStatQuicExistPktsDny indicates the total number
         of midstream-detected existing TLS quic traffic packets dropped."
    ::= { tmnxBsxTlsTrafficStatsEntry 17 }

tmnxBsxTlsStatQuicExistFlwsAdm   OBJECT-TYPE
    SYNTAX      Counter64
    UNITS       "flows"
    MAX-ACCESS  read-only
    STATUS      current
    DESCRIPTION
        "The value of tmnxBsxTlsStatQuicExistFlwsAdm  indicates the
         total number of midstream-detected existing flows of TLS quic
         traffic permitted."
    ::= { tmnxBsxTlsTrafficStatsEntry 18 }

tmnxBsxTlsStatQuicExistFlwsDny   OBJECT-TYPE
    SYNTAX      Counter64
    UNITS       "flows"
    MAX-ACCESS  read-only
    STATUS      current
    DESCRIPTION
        "The value of tmnxBsxTlsStatQuicExistFlwsDny indicates the total number
         of midstream-detected existing flows of TLS quic traffic that dropped
         subsequent packets."
    ::= { tmnxBsxTlsTrafficStatsEntry 19 }

tmnxBsxTlsStatQuicUnknwnOctsAdm  OBJECT-TYPE
    SYNTAX      Counter64
    UNITS       "bytes"
    MAX-ACCESS  read-only
    STATUS      current
    DESCRIPTION
        "The value of tmnxBsxTlsStatQuicUnknwnOctsAdm indicates the total
         number of unknown TLS quic version traffic bytes permitted."
    ::= { tmnxBsxTlsTrafficStatsEntry 20 }

tmnxBsxTlsStatQuicUnknwnOctsDny  OBJECT-TYPE
    SYNTAX      Counter64
    UNITS       "bytes"
    MAX-ACCESS  read-only
    STATUS      current
    DESCRIPTION
        "The value of tmnxBsxTlsStatQuicUnknwnOctsDny indicates the total
         number of unknown TLS quic version traffic bytes dropped."
    ::= { tmnxBsxTlsTrafficStatsEntry 21 }

tmnxBsxTlsStatQuicUnknwnPktsAdm  OBJECT-TYPE
    SYNTAX      Counter64
    UNITS       "packets"
    MAX-ACCESS  read-only
    STATUS      current
    DESCRIPTION
        "The value of tmnxBsxTlsStatQuicUnknwnPktsAdm indicates the total
         number of unknown TLS quic version traffic packets permitted."
    ::= { tmnxBsxTlsTrafficStatsEntry 22 }

tmnxBsxTlsStatQuicUnknwnPktsDny  OBJECT-TYPE
    SYNTAX      Counter64
    UNITS       "packets"
    MAX-ACCESS  read-only
    STATUS      current
    DESCRIPTION
        "The value of tmnxBsxTlsStatQuicUnknwnPktsDny indicates the total
         number of unknown TLS quic version traffic packets dropped."
    ::= { tmnxBsxTlsTrafficStatsEntry 23 }

tmnxBsxTlsStatQuicUnknwnFlwsAdm  OBJECT-TYPE
    SYNTAX      Counter64
    UNITS       "flows"
    MAX-ACCESS  read-only
    STATUS      current
    DESCRIPTION
        "The value of tmnxBsxTlsStatQuicUnknwnFlwsAdm  indicates the
         total number of flows of unknown TLS quic version traffic
         permitted."
    ::= { tmnxBsxTlsTrafficStatsEntry 24 }

tmnxBsxTlsStatQuicUnknwnFlwsDny  OBJECT-TYPE
    SYNTAX      Counter64
    UNITS       "flows"
    MAX-ACCESS  read-only
    STATUS      current
    DESCRIPTION
        "The value of tmnxBsxTlsStatQuicUnknwnFlwsDny indicates the total
         number of flows of unknown TLS quic version traffic that dropped
         subsequent packets."
    ::= { tmnxBsxTlsTrafficStatsEntry 25 }

tmnxBsxTlsStatTls10OctsAdm       OBJECT-TYPE
    SYNTAX      Counter64
    UNITS       "bytes"
    MAX-ACCESS  read-only
    STATUS      current
    DESCRIPTION
        "The value of tmnxBsxTlsStatTls10OctsAdm indicates the total number of
         TLS version 1.0 traffic bytes permitted."
    ::= { tmnxBsxTlsTrafficStatsEntry 26 }

tmnxBsxTlsStatTls10OctsDny       OBJECT-TYPE
    SYNTAX      Counter64
    UNITS       "bytes"
    MAX-ACCESS  read-only
    STATUS      current
    DESCRIPTION
        "The value of tmnxBsxTlsStatTls10OctsDny indicates the total number of
         TLS version 1.0 traffic bytes dropped."
    ::= { tmnxBsxTlsTrafficStatsEntry 27 }

tmnxBsxTlsStatTls10PktsAdm       OBJECT-TYPE
    SYNTAX      Counter64
    UNITS       "packets"
    MAX-ACCESS  read-only
    STATUS      current
    DESCRIPTION
        "The value of tmnxBsxTlsStatTls10PktsAdm indicates the total number of
         TLS version 1.0 traffic packets permitted."
    ::= { tmnxBsxTlsTrafficStatsEntry 28 }

tmnxBsxTlsStatTls10PktsDny       OBJECT-TYPE
    SYNTAX      Counter64
    UNITS       "packets"
    MAX-ACCESS  read-only
    STATUS      current
    DESCRIPTION
        "The value of tmnxBsxTlsStatTls10PktsDny indicates the total number of
         TLS version 1.0 traffic packets dropped."
    ::= { tmnxBsxTlsTrafficStatsEntry 29 }

tmnxBsxTlsStatTls10FlwsAdm       OBJECT-TYPE
    SYNTAX      Counter64
    UNITS       "flows"
    MAX-ACCESS  read-only
    STATUS      current
    DESCRIPTION
        "The value of tmnxBsxTlsStatTls10FlwsAdm  indicates the
         total number of flows of TLS version 1.0 traffic permitted."
    ::= { tmnxBsxTlsTrafficStatsEntry 30 }

tmnxBsxTlsStatTls10FlwsDny       OBJECT-TYPE
    SYNTAX      Counter64
    UNITS       "flows"
    MAX-ACCESS  read-only
    STATUS      current
    DESCRIPTION
        "The value of tmnxBsxTlsStatTls10FlwsDny indicates the total number of
         flows of TLS version 1.0 traffic that dropped subsequent packets."
    ::= { tmnxBsxTlsTrafficStatsEntry 31 }

tmnxBsxTlsStatTls11OctsAdm       OBJECT-TYPE
    SYNTAX      Counter64
    UNITS       "bytes"
    MAX-ACCESS  read-only
    STATUS      current
    DESCRIPTION
        "The value of tmnxBsxTlsStatTls11OctsAdm indicates the total number of
         TLS version 1.1 traffic bytes permitted."
    ::= { tmnxBsxTlsTrafficStatsEntry 32 }

tmnxBsxTlsStatTls11OctsDny       OBJECT-TYPE
    SYNTAX      Counter64
    UNITS       "bytes"
    MAX-ACCESS  read-only
    STATUS      current
    DESCRIPTION
        "The value of tmnxBsxTlsStatTls11OctsDny indicates the total number of
         TLS version 1.1 traffic bytes dropped."
    ::= { tmnxBsxTlsTrafficStatsEntry 33 }

tmnxBsxTlsStatTls11PktsAdm       OBJECT-TYPE
    SYNTAX      Counter64
    UNITS       "packets"
    MAX-ACCESS  read-only
    STATUS      current
    DESCRIPTION
        "The value of tmnxBsxTlsStatTls11PktsAdm indicates the total number of
         TLS version 1.1 traffic packets permitted."
    ::= { tmnxBsxTlsTrafficStatsEntry 34 }

tmnxBsxTlsStatTls11PktsDny       OBJECT-TYPE
    SYNTAX      Counter64
    UNITS       "packets"
    MAX-ACCESS  read-only
    STATUS      current
    DESCRIPTION
        "The value of tmnxBsxTlsStatTls11PktsDny indicates the total number of
         TLS version 1.1 traffic packets dropped."
    ::= { tmnxBsxTlsTrafficStatsEntry 35 }

tmnxBsxTlsStatTls11FlwsAdm       OBJECT-TYPE
    SYNTAX      Counter64
    UNITS       "flows"
    MAX-ACCESS  read-only
    STATUS      current
    DESCRIPTION
        "The value of tmnxBsxTlsStatTls11FlwsAdm  indicates the
         total number of flows of TLS version 1.1 traffic permitted."
    ::= { tmnxBsxTlsTrafficStatsEntry 36 }

tmnxBsxTlsStatTls11FlwsDny       OBJECT-TYPE
    SYNTAX      Counter64
    UNITS       "flows"
    MAX-ACCESS  read-only
    STATUS      current
    DESCRIPTION
        "The value of tmnxBsxTlsStatTls11FlwsDny indicates the total number of
         flows of TLS version 1.1 traffic that dropped subsequent packets."
    ::= { tmnxBsxTlsTrafficStatsEntry 37 }

tmnxBsxTlsStatTls12OctsAdm       OBJECT-TYPE
    SYNTAX      Counter64
    UNITS       "bytes"
    MAX-ACCESS  read-only
    STATUS      current
    DESCRIPTION
        "The value of tmnxBsxTlsStatTls12OctsAdm indicates the total number of
         TLS version 1.2 traffic bytes permitted."
    ::= { tmnxBsxTlsTrafficStatsEntry 38 }

tmnxBsxTlsStatTls12OctsDny       OBJECT-TYPE
    SYNTAX      Counter64
    UNITS       "bytes"
    MAX-ACCESS  read-only
    STATUS      current
    DESCRIPTION
        "The value of tmnxBsxTlsStatTls12OctsDny indicates the total number of
         TLS version 1.2 traffic bytes dropped."
    ::= { tmnxBsxTlsTrafficStatsEntry 39 }

tmnxBsxTlsStatTls12PktsAdm       OBJECT-TYPE
    SYNTAX      Counter64
    UNITS       "packets"
    MAX-ACCESS  read-only
    STATUS      current
    DESCRIPTION
        "The value of tmnxBsxTlsStatTls12PktsAdm indicates the total number of
         TLS version 1.2 traffic packets permitted."
    ::= { tmnxBsxTlsTrafficStatsEntry 40 }

tmnxBsxTlsStatTls12PktsDny       OBJECT-TYPE
    SYNTAX      Counter64
    UNITS       "packets"
    MAX-ACCESS  read-only
    STATUS      current
    DESCRIPTION
        "The value of tmnxBsxTlsStatTls12PktsDny indicates the total number of
         TLS version 1.2 traffic packets dropped."
    ::= { tmnxBsxTlsTrafficStatsEntry 41 }

tmnxBsxTlsStatTls12FlwsAdm       OBJECT-TYPE
    SYNTAX      Counter64
    UNITS       "flows"
    MAX-ACCESS  read-only
    STATUS      current
    DESCRIPTION
        "The value of tmnxBsxTlsStatTls12FlwsAdm  indicates the
         total number of flows of TLS version 1.2 traffic permitted."
    ::= { tmnxBsxTlsTrafficStatsEntry 42 }

tmnxBsxTlsStatTls12FlwsDny       OBJECT-TYPE
    SYNTAX      Counter64
    UNITS       "flows"
    MAX-ACCESS  read-only
    STATUS      current
    DESCRIPTION
        "The value of tmnxBsxTlsStatTls12FlwsDny indicates the total number of
         flows of TLS version 1.2 traffic that dropped subsequent packets."
    ::= { tmnxBsxTlsTrafficStatsEntry 43 }

tmnxBsxTlsStatTls13OctsAdm       OBJECT-TYPE
    SYNTAX      Counter64
    UNITS       "bytes"
    MAX-ACCESS  read-only
    STATUS      current
    DESCRIPTION
        "The value of tmnxBsxTlsStatTls13OctsAdm indicates the total number of
         TLS version 1.3 traffic bytes permitted."
    ::= { tmnxBsxTlsTrafficStatsEntry 44 }

tmnxBsxTlsStatTls13OctsDny       OBJECT-TYPE
    SYNTAX      Counter64
    UNITS       "bytes"
    MAX-ACCESS  read-only
    STATUS      current
    DESCRIPTION
        "The value of tmnxBsxTlsStatTls13OctsDny indicates the total number of
         TLS version 1.3 traffic bytes dropped."
    ::= { tmnxBsxTlsTrafficStatsEntry 45 }

tmnxBsxTlsStatTls13PktsAdm       OBJECT-TYPE
    SYNTAX      Counter64
    UNITS       "packets"
    MAX-ACCESS  read-only
    STATUS      current
    DESCRIPTION
        "The value of tmnxBsxTlsStatTls13PktsAdm indicates the total number of
         TLS version 1.3 traffic packets permitted."
    ::= { tmnxBsxTlsTrafficStatsEntry 46 }

tmnxBsxTlsStatTls13PktsDny       OBJECT-TYPE
    SYNTAX      Counter64
    UNITS       "packets"
    MAX-ACCESS  read-only
    STATUS      current
    DESCRIPTION
        "The value of tmnxBsxTlsStatTls13PktsDny indicates the total number of
         TLS version 1.3 traffic packets dropped."
    ::= { tmnxBsxTlsTrafficStatsEntry 47 }

tmnxBsxTlsStatTls13FlwsAdm       OBJECT-TYPE
    SYNTAX      Counter64
    UNITS       "flows"
    MAX-ACCESS  read-only
    STATUS      current
    DESCRIPTION
        "The value of tmnxBsxTlsStatTls13FlwsAdm  indicates the
         total number of flows of TLS version 1.3 traffic permitted."
    ::= { tmnxBsxTlsTrafficStatsEntry 48 }

tmnxBsxTlsStatTls13FlwsDny       OBJECT-TYPE
    SYNTAX      Counter64
    UNITS       "flows"
    MAX-ACCESS  read-only
    STATUS      current
    DESCRIPTION
        "The value of tmnxBsxTlsStatTls13FlwsDny indicates the total number of
         flows of TLS version 1.3 traffic that dropped subsequent packets."
    ::= { tmnxBsxTlsTrafficStatsEntry 49 }

tmnxBsxTlsStatTls13EsniOctsAdm   OBJECT-TYPE
    SYNTAX      Counter64
    UNITS       "bytes"
    MAX-ACCESS  read-only
    STATUS      current
    DESCRIPTION
        "The value of tmnxBsxTlsStatTls13EsniOctsAdm indicates the total number
         of TLS version 1.3 with eSNI traffic bytes permitted."
    ::= { tmnxBsxTlsTrafficStatsEntry 50 }

tmnxBsxTlsStatTls13EsniOctsDny   OBJECT-TYPE
    SYNTAX      Counter64
    UNITS       "bytes"
    MAX-ACCESS  read-only
    STATUS      current
    DESCRIPTION
        "The value of tmnxBsxTlsStatTls13EsniOctsDny indicates the total number
         of TLS version 1.3 esni traffic bytes dropped."
    ::= { tmnxBsxTlsTrafficStatsEntry 51 }

tmnxBsxTlsStatTls13EsniPktsAdm   OBJECT-TYPE
    SYNTAX      Counter64
    UNITS       "packets"
    MAX-ACCESS  read-only
    STATUS      current
    DESCRIPTION
        "The value of tmnxBsxTlsStatTls13EsniPktsAdm indicates the total number
         of TLS version 1.3 with eSNI traffic packets permitted."
    ::= { tmnxBsxTlsTrafficStatsEntry 52 }

tmnxBsxTlsStatTls13EsniPktsDny   OBJECT-TYPE
    SYNTAX      Counter64
    UNITS       "packets"
    MAX-ACCESS  read-only
    STATUS      current
    DESCRIPTION
        "The value of tmnxBsxTlsStatTls13EsniPktsDny indicates the total number
         of TLS version 1.3 with eSNI traffic packets dropped."
    ::= { tmnxBsxTlsTrafficStatsEntry 53 }

tmnxBsxTlsStatTls13EsniFlwsAdm   OBJECT-TYPE
    SYNTAX      Counter64
    UNITS       "flows"
    MAX-ACCESS  read-only
    STATUS      current
    DESCRIPTION
        "The value of tmnxBsxTlsStatTls13EsniFlwsAdm  indicates the
         total number of flows of TLS version 1.3 with eSNI traffic permitted."
    ::= { tmnxBsxTlsTrafficStatsEntry 54 }

tmnxBsxTlsStatTls13EsniFlwsDny   OBJECT-TYPE
    SYNTAX      Counter64
    UNITS       "packets"
    MAX-ACCESS  read-only
    STATUS      current
    DESCRIPTION
        "The value of tmnxBsxTlsStatTls13EsniFlwsDny indicates the total number
         of flows of TLS version 1.3 with eSNI traffic that dropped subsequent
         packets."
    ::= { tmnxBsxTlsTrafficStatsEntry 55 }

tmnxBsxTlsStatTlsExistOctsAdm    OBJECT-TYPE
    SYNTAX      Counter64
    UNITS       "bytes"
    MAX-ACCESS  read-only
    STATUS      current
    DESCRIPTION
        "The value of tmnxBsxTlsStatTlsExistOctsAdm indicates the total number
         of midstream-detected existing TLS traffic bytes permitted."
    ::= { tmnxBsxTlsTrafficStatsEntry 56 }

tmnxBsxTlsStatTlsExistOctsDny    OBJECT-TYPE
    SYNTAX      Counter64
    UNITS       "bytes"
    MAX-ACCESS  read-only
    STATUS      current
    DESCRIPTION
        "The value of tmnxBsxTlsStatTlsExistOctsDny indicates the total number
         of TLS existing version traffic bytes dropped."
    ::= { tmnxBsxTlsTrafficStatsEntry 57 }

tmnxBsxTlsStatTlsExistPktsAdm    OBJECT-TYPE
    SYNTAX      Counter64
    UNITS       "packets"
    MAX-ACCESS  read-only
    STATUS      current
    DESCRIPTION
        "The value of tmnxBsxTlsStatTlsExistPktsAdm indicates the total number
         of midstream-detected existing TLS traffic packets permitted."
    ::= { tmnxBsxTlsTrafficStatsEntry 58 }

tmnxBsxTlsStatTlsExistPktsDny    OBJECT-TYPE
    SYNTAX      Counter64
    UNITS       "packets"
    MAX-ACCESS  read-only
    STATUS      current
    DESCRIPTION
        "The value of tmnxBsxTlsStatTlsExistPktsDny indicates the total number
         of midstream-detected existing TLS traffic packets dropped."
    ::= { tmnxBsxTlsTrafficStatsEntry 59 }

tmnxBsxTlsStatTlsExistFlwsAdm    OBJECT-TYPE
    SYNTAX      Counter64
    UNITS       "flows"
    MAX-ACCESS  read-only
    STATUS      current
    DESCRIPTION
        "The value of tmnxBsxTlsStatTlsExistFlwsAdm indicates the total number
         of midstream-detected existing TLS flows permitted."
    ::= { tmnxBsxTlsTrafficStatsEntry 60 }

tmnxBsxTlsStatTlsExistFlwsDny    OBJECT-TYPE
    SYNTAX      Counter64
    UNITS       "flows"
    MAX-ACCESS  read-only
    STATUS      current
    DESCRIPTION
        "The value of tmnxBsxTlsStatTlsExistFlwsDny indicates the total number
         of midstream-detected existing TLS flows that dropped subsequent
         packets."
    ::= { tmnxBsxTlsTrafficStatsEntry 61 }

tmnxBsxTlsStatTlsUnknownOctsAdm  OBJECT-TYPE
    SYNTAX      Counter64
    UNITS       "bytes"
    MAX-ACCESS  read-only
    STATUS      current
    DESCRIPTION
        "The value of tmnxBsxTlsStatTlsUnknownOctsAdm indicates the total
         number of unknown TLS version traffic bytes permitted."
    ::= { tmnxBsxTlsTrafficStatsEntry 62 }

tmnxBsxTlsStatTlsUnknownOctsDny  OBJECT-TYPE
    SYNTAX      Counter64
    UNITS       "bytes"
    MAX-ACCESS  read-only
    STATUS      current
    DESCRIPTION
        "The value of tmnxBsxTlsStatTlsUnknownOctsDny indicates the total
         number of unknown TLS version traffic bytes dropped."
    ::= { tmnxBsxTlsTrafficStatsEntry 63 }

tmnxBsxTlsStatTlsUnknownPktsAdm  OBJECT-TYPE
    SYNTAX      Counter64
    UNITS       "packets"
    MAX-ACCESS  read-only
    STATUS      current
    DESCRIPTION
        "The value of tmnxBsxTlsStatTlsUnknownPktsAdm indicates the total
         number of unknown TLS version traffic packets permitted."
    ::= { tmnxBsxTlsTrafficStatsEntry 64 }

tmnxBsxTlsStatTlsUnknownPktsDny  OBJECT-TYPE
    SYNTAX      Counter64
    UNITS       "packets"
    MAX-ACCESS  read-only
    STATUS      current
    DESCRIPTION
        "The value of tmnxBsxTlsStatTlsUnknownPktsDny indicates the total
         number of unknown TLS version traffic packets dropped."
    ::= { tmnxBsxTlsTrafficStatsEntry 65 }

tmnxBsxTlsStatTlsUnknownFlwsAdm  OBJECT-TYPE
    SYNTAX      Counter64
    UNITS       "flows"
    MAX-ACCESS  read-only
    STATUS      current
    DESCRIPTION
        "The value of tmnxBsxTlsStatTlsUnknownFlwsAdm  indicates the
         total number of flows of unknown TLS version traffic permitted."
    ::= { tmnxBsxTlsTrafficStatsEntry 66 }

tmnxBsxTlsStatTlsUnknownFlwsDny  OBJECT-TYPE
    SYNTAX      Counter64
    UNITS       "flows"
    MAX-ACCESS  read-only
    STATUS      current
    DESCRIPTION
        "The value of tmnxBsxTlsStatTlsUnknownFlwsDny indicates the total
         number of flows of unknown TLS version traffic that dropped subsequent
         packets."
    ::= { tmnxBsxTlsTrafficStatsEntry 67 }

tmnxBsxStatIpIdentAsstTable      OBJECT-TYPE
    SYNTAX      SEQUENCE OF TmnxBsxStatsIpIdAsstEntry
    MAX-ACCESS  not-accessible
    STATUS      current
    DESCRIPTION
        "The tmnxBsxStatIpIdentAsstTable contains an entry for IP
         Identification Assist statistics per group per ISA."
    ::= { tmnxBsxStatsObjs 31 }

tmnxBsxStatsIpIdAsstEntry        OBJECT-TYPE
    SYNTAX      TmnxBsxStatsIpIdAsstEntry
    MAX-ACCESS  not-accessible
    STATUS      current
    DESCRIPTION
        "Each tmnxBsxStatsIpIdAsstEntry specifies IP-Address-based
         identification statistics within an Application Assurance
         group.  Summarized statistics per group are returned with
         tmnxChassisIndex set to one and both tmnxBsxCardSlotEsaId
         and tmnxBsxMdaSlotEsaVmId set to zero."
    INDEX       {
        tmnxBsxIsaAaGroupIndex,
        tmnxChassisIndex,
        tmnxBsxCardSlotEsaId,
        tmnxBsxMdaSlotEsaVmId
    }
    ::= { tmnxBsxStatIpIdentAsstTable 1 }

TmnxBsxStatsIpIdAsstEntry        ::= SEQUENCE
{
    tmnxBsxStatIpIdAsstDiscntTime    TimeStamp,
    tmnxBsxStatIpIdAsstMax           Gauge32,
    tmnxBsxStatIpIdAsstActive        Counter32,
    tmnxBsxStatIpIdAsstApp           Counter32,
    tmnxBsxStatIpIdAsstParent        Counter32,
    tmnxBsxStatIpIdAsstNoId          Counter32,
    tmnxBsxStatIpIdAsstNoIdNon       Counter32,
    tmnxBsxStatIpIdAsstHit           Counter32,
    tmnxBsxStatIpIdAsstNoHit         Counter32,
    tmnxBsxStatIpIdAsstTotMiss       Counter64,
    tmnxBsxStatIpIdAsstTotHitApp     Counter64,
    tmnxBsxStatIpIdAsstTotHitPar     Counter64,
    tmnxBsxStatIpIdAsstTotHitNo      Counter64,
    tmnxBsxStatIpIdAsstTotHitNon     Counter64
}

tmnxBsxStatIpIdAsstDiscntTime    OBJECT-TYPE
    SYNTAX      TimeStamp
    MAX-ACCESS  read-only
    STATUS      current
    DESCRIPTION
        "The value of tmnxBsxStatIpIdAsstDiscntTime indicates discontinuity
         time. This is the SNMPv2-MIB::sysUpTime (centiseconds) when the ISA-AA
         MDA within the group last changed status."
    ::= { tmnxBsxStatsIpIdAsstEntry 1 }

tmnxBsxStatIpIdAsstMax           OBJECT-TYPE
    SYNTAX      Gauge32
    MAX-ACCESS  read-only
    STATUS      current
    DESCRIPTION
        "The value of tmnxBsxStatIpIdAsstMax indicates the maximum number of IP
         entries that are available on the ISA-AA MDA(s)."
    ::= { tmnxBsxStatsIpIdAsstEntry 2 }

tmnxBsxStatIpIdAsstActive        OBJECT-TYPE
    SYNTAX      Counter32
    MAX-ACCESS  read-only
    STATUS      current
    DESCRIPTION
        "The value of tmnxBsxStatIpIdAsstActive indicates the current number of
         active IP entries on the ISA-AA MDA(s)."
    ::= { tmnxBsxStatsIpIdAsstEntry 3 }

tmnxBsxStatIpIdAsstApp           OBJECT-TYPE
    SYNTAX      Counter32
    MAX-ACCESS  read-only
    STATUS      current
    DESCRIPTION
        "The value of tmnxBsxStatIpIdAsstApp indicates the current number of
         active IP entries that map to an application on the ISA-AA MDA(s)."
    ::= { tmnxBsxStatsIpIdAsstEntry 4 }

tmnxBsxStatIpIdAsstParent        OBJECT-TYPE
    SYNTAX      Counter32
    MAX-ACCESS  read-only
    STATUS      current
    DESCRIPTION
        "The value of tmnxBsxStatIpIdAsstParent indicates the current
         number of active IP entries that map to a parent application
         on the ISA-AA MDA(s).  This is due to the IP address being
         used by multiple applications that share the same parent
         application."
    ::= { tmnxBsxStatsIpIdAsstEntry 5 }

tmnxBsxStatIpIdAsstNoId          OBJECT-TYPE
    SYNTAX      Counter32
    MAX-ACCESS  read-only
    STATUS      current
    DESCRIPTION
        "The value of tmnxBsxStatIpIdAsstNoId indicates the current number of
         active IP entries that do not provide a positive identification due to
         an IP conflict between multiple assisted applications that have
         different parent applications on the ISA-AA MDA(s)."
    ::= { tmnxBsxStatsIpIdAsstEntry 6 }

tmnxBsxStatIpIdAsstNoIdNon       OBJECT-TYPE
    SYNTAX      Counter32
    MAX-ACCESS  read-only
    STATUS      current
    DESCRIPTION
        "The value of tmnxBsxStatIpIdAsstNoIdNon indicates the current number
         of active IP entries that do not provide a positive identification due
         to an IP conflict between assisted applications and non-assisted
         applications on the ISA-AA MDA(s)."
    ::= { tmnxBsxStatsIpIdAsstEntry 7 }

tmnxBsxStatIpIdAsstHit           OBJECT-TYPE
    SYNTAX      Counter32
    MAX-ACCESS  read-only
    STATUS      current
    DESCRIPTION
        "The value of tmnxBsxStatIpIdAsstHit indicates the number of active IP
         entries that have matched traffic on the ISA-AA MDA(s)."
    ::= { tmnxBsxStatsIpIdAsstEntry 8 }

tmnxBsxStatIpIdAsstNoHit         OBJECT-TYPE
    SYNTAX      Counter32
    MAX-ACCESS  read-only
    STATUS      current
    DESCRIPTION
        "The value of tmnxBsxStatIpIdAsstNoHit indicates the number of active
         IP entries that have not matched traffic on the ISA-AA ISA-AA MDA(s)."
    ::= { tmnxBsxStatsIpIdAsstEntry 9 }

tmnxBsxStatIpIdAsstTotMiss       OBJECT-TYPE
    SYNTAX      Counter64
    MAX-ACCESS  read-only
    STATUS      current
    DESCRIPTION
        "The value of tmnxBsxStatIpIdAsstTotMiss indicates the total number of
         IP lookups that did not match any entry on the ISA-AA MDA(s)."
    ::= { tmnxBsxStatsIpIdAsstEntry 10 }

tmnxBsxStatIpIdAsstTotHitApp     OBJECT-TYPE
    SYNTAX      Counter64
    MAX-ACCESS  read-only
    STATUS      current
    DESCRIPTION
        "The value of tmnxBsxStatIpIdAsstTotHitApp indicates the total number
         of IP lookups that matched an entry that identified an application for
         the flow/session on the ISA-AA MDA(s)."
    ::= { tmnxBsxStatsIpIdAsstEntry 11 }

tmnxBsxStatIpIdAsstTotHitPar     OBJECT-TYPE
    SYNTAX      Counter64
    MAX-ACCESS  read-only
    STATUS      current
    DESCRIPTION
        "The value of tmnxBsxStatIpIdAsstTotHitPar indicates the total number
         of IP lookups that matched an entry that identified a parent
         application for the flow/session on the ISA-AA MDA(s)."
    ::= { tmnxBsxStatsIpIdAsstEntry 12 }

tmnxBsxStatIpIdAsstTotHitNo      OBJECT-TYPE
    SYNTAX      Counter64
    MAX-ACCESS  read-only
    STATUS      current
    DESCRIPTION
        "The value of tmnxBsxStatIpIdAsstTotHitNo indicates the total
         number of IP lookups that matched an entry that did not
         provide an identification result for the flow/session on the
         ISA-AA MDA(s).  The IP entry matched was in use by multiple
         assisted applications that had conflicting parent applications."
    ::= { tmnxBsxStatsIpIdAsstEntry 13 }

tmnxBsxStatIpIdAsstTotHitNon     OBJECT-TYPE
    SYNTAX      Counter64
    MAX-ACCESS  read-only
    STATUS      current
    DESCRIPTION
        "The value of tmnxBsxStatIpIdAsstTotHitNon indicates the total
         number of IP lookups that matched an entry that did not
         provide an identification result for the flow/session on the
         ISA-AA MDA(s).  The IP entry matched was in use by assisted
         and non-assisted applications."
    ::= { tmnxBsxStatsIpIdAsstEntry 14 }

tmnxBsxIpIdAsstPartStatsTable    OBJECT-TYPE
    SYNTAX      SEQUENCE OF TmnxBsxIpIdAsstPartStatsEntry
    MAX-ACCESS  not-accessible
    STATUS      current
    DESCRIPTION
        "The tmnxBsxIpIdAsstPartStatsTable contains an entry for IP
         Identification Assist statistics per partition."
    ::= { tmnxBsxStatsObjs 32 }

tmnxBsxIpIdAsstPartStatsEntry    OBJECT-TYPE
    SYNTAX      TmnxBsxIpIdAsstPartStatsEntry
    MAX-ACCESS  not-accessible
    STATUS      current
    DESCRIPTION
        "Each tmnxBsxIpIdAsstPartStatsEntry specifies IP-Address-based
         identification statistics within an Application Assurance
         partition.  Summarized statistics per partition are returned
         with tmnxChassisIndex set to one and both tmnxBsxCardSlotEsaId
         and tmnxBsxMdaSlotEsaVmId set to zero."
    INDEX       {
        tmnxBsxAaGrpPartIndex,
        tmnxChassisIndex,
        tmnxBsxCardSlotEsaId,
        tmnxBsxMdaSlotEsaVmId
    }
    ::= { tmnxBsxIpIdAsstPartStatsTable 1 }

TmnxBsxIpIdAsstPartStatsEntry    ::= SEQUENCE
{
    tmnxBsxIpIdAsStatPDnsResponses   Counter64,
    tmnxBsxIpIdAsStatPDnsIgNoRvFlow  Counter64,
    tmnxBsxIpIdAsStatPDnsIgWrongDir  Counter64,
    tmnxBsxIpIdAsStatPDnsIgUntrustd  Counter64,
    tmnxBsxIpIdAsStatPDnsRspMtch     Counter64,
    tmnxBsxIpIdAsStatPDnsRspMtchIp4  Counter64,
    tmnxBsxIpIdAsStatPDnsRspMtchIp6  Counter64,
    tmnxBsxIpIdAsStatPDnsRspUnkn     Counter64,
    tmnxBsxIpIdAsStatPDnsRspUnknIp4  Counter64,
    tmnxBsxIpIdAsStatPDnsRspUnknIp6  Counter64,
    tmnxBsxIpIdAsStatPosGlbAppFlows  Counter64,
    tmnxBsxIpIdAsStatPosGlbIgnIpIdAs Counter64,
    tmnxBsxIpIdAsStatPosGlbIgnNoExpr Counter64,
    tmnxBsxIpIdAsStatPosCacheFlow    Counter64,
    tmnxBsxIpIdAsStatPosCacheFlowIp4 Counter64,
    tmnxBsxIpIdAsStatPosCacheFlowIp6 Counter64
}

tmnxBsxIpIdAsStatPDnsResponses   OBJECT-TYPE
    SYNTAX      Counter64
    MAX-ACCESS  read-only
    STATUS      current
    DESCRIPTION
        "The value of tmnxBsxIpIdAsStatPDnsResponses indicates the total number
         of DNS responses that Passive DNS Monitoring has seen."
    ::= { tmnxBsxIpIdAsstPartStatsEntry 1 }

tmnxBsxIpIdAsStatPDnsIgNoRvFlow  OBJECT-TYPE
    SYNTAX      Counter64
    MAX-ACCESS  read-only
    STATUS      current
    DESCRIPTION
        "The value of tmnxBsxIpIdAsStatPDnsIgNoRvFlow indicates the number of
         DNS responses that Passive DNS Monitoring ignored because they did not
         have a corresponding DNS request (no reverse flow)."
    ::= { tmnxBsxIpIdAsstPartStatsEntry 2 }

tmnxBsxIpIdAsStatPDnsIgWrongDir  OBJECT-TYPE
    SYNTAX      Counter64
    MAX-ACCESS  read-only
    STATUS      current
    DESCRIPTION
        "The value of tmnxBsxIpIdAsStatPDnsIgWrongDir indicates the number of
         DNS responses that Passive DNS Monitoring ignored because they came
         from the wrong direction (from-sub, where to-sub is expected)."
    ::= { tmnxBsxIpIdAsstPartStatsEntry 3 }

tmnxBsxIpIdAsStatPDnsIgUntrustd  OBJECT-TYPE
    SYNTAX      Counter64
    MAX-ACCESS  read-only
    STATUS      current
    DESCRIPTION
        "The value of tmnxBsxIpIdAsStatPDnsIgUntrustd indicates the number of
         DNS responses that Passive DNS Monitoring ignored because they did not
         come from a trusted DNS server, and a list of trusted DNS servers was
         configured."
    ::= { tmnxBsxIpIdAsstPartStatsEntry 4 }

tmnxBsxIpIdAsStatPDnsRspMtch     OBJECT-TYPE
    SYNTAX      Counter64
    MAX-ACCESS  read-only
    STATUS      current
    DESCRIPTION
        "The value of tmnxBsxIpIdAsStatPDnsRspMtch indicates the number of DNS
         responses in which Passive DNS Monitoring matched a domain name that
         is related to an application supported by IP Identification Assist."
    ::= { tmnxBsxIpIdAsstPartStatsEntry 5 }

tmnxBsxIpIdAsStatPDnsRspMtchIp4  OBJECT-TYPE
    SYNTAX      Counter64
    MAX-ACCESS  read-only
    STATUS      current
    DESCRIPTION
        "The value of tmnxBsxIpIdAsStatPDnsRspMtchIp4 indicates the number
         of IPv4 addresses that Passive DNS Monitoring reported to IP
         Identification Assist as potential mappings to supported
         applications.  Passive DNS Monitoring bases these potential mappings
         on the IPv4 addresses in the DNS responses counted in
         tmnxBsxIpIdAsStatPDnsRspMtch.  The tmnxBsxIpIdAsStatPDnsRspMtchIp4
         statistic only counts how many potential mappings Passive DNS
         Monitoring reported and does not account for what IP Identification
         Assist did with them."
    ::= { tmnxBsxIpIdAsstPartStatsEntry 6 }

tmnxBsxIpIdAsStatPDnsRspMtchIp6  OBJECT-TYPE
    SYNTAX      Counter64
    MAX-ACCESS  read-only
    STATUS      current
    DESCRIPTION
        "The value of tmnxBsxIpIdAsStatPDnsRspMtchIp6 indicates the number
         of IPv6 addresses that Passive DNS Monitoring reported to IP
         Identification Assist as potential mappings to supported
         applications.  Passive DNS Monitoring bases these potential mappings
         on the IPv6 addresses in the DNS responses counted in
         tmnxBsxIpIdAsStatPDnsRspMtch.  The tmnxBsxIpIdAsStatPDnsRspMtchIp6
         statistic only counts how many potential mappings Passive DNS
         Monitoring reported and does not account for what IP Identification
         Assist did with them."
    ::= { tmnxBsxIpIdAsstPartStatsEntry 7 }

tmnxBsxIpIdAsStatPDnsRspUnkn     OBJECT-TYPE
    SYNTAX      Counter64
    MAX-ACCESS  read-only
    STATUS      current
    DESCRIPTION
        "The value of tmnxBsxIpIdAsStatPDnsRspUnkn indicates the number
         of DNS responses where Passive DNS Monitoring looked at a domain
         name but was unable to match it to an application supported by
         IP Identification Assist.  Passive DNS Monitoring counts these
         DNS responses as related to an unknown application."
    ::= { tmnxBsxIpIdAsstPartStatsEntry 8 }

tmnxBsxIpIdAsStatPDnsRspUnknIp4  OBJECT-TYPE
    SYNTAX      Counter64
    MAX-ACCESS  read-only
    STATUS      current
    DESCRIPTION
        "The value of tmnxBsxIpIdAsStatPDnsRspUnknIp4 indicates the number
         of IPv4 addresses that Passive DNS Monitoring reported to IP
         Identification Assist as potential mappings to an unknown application.
         Passive DNS Monitoring bases these potential mappings on the IPv4
         addresses in the DNS responses counted in
         tmnxBsxIpIdAsStatPDnsRspUnkn.  The tmnxBsxIpIdAsStatPDnsRspUnknIp4
         statistic only counts how many potential mappings Passive DNS
         Monitoring reported and does not account for what IP Identification
         Assist did with them."
    ::= { tmnxBsxIpIdAsstPartStatsEntry 9 }

tmnxBsxIpIdAsStatPDnsRspUnknIp6  OBJECT-TYPE
    SYNTAX      Counter64
    MAX-ACCESS  read-only
    STATUS      current
    DESCRIPTION
        "The value of tmnxBsxIpIdAsStatPDnsRspUnknIp6 indicates the number
         of IPv6 addresses that Passive DNS Monitoring reported to IP
         Identification Assist as potential mappings to an unknown application.
         Passive DNS Monitoring bases these potential mappings on the IPv6
         addresses in the DNS responses counted in
         tmnxBsxIpIdAsStatPDnsRspUnkn.  The tmnxBsxIpIdAsStatPDnsRspUnknIp6
         statistic only counts how many potential mappings Passive DNS
         Monitoring reported and does not account for what IP Identification
         Assist did with them."
    ::= { tmnxBsxIpIdAsstPartStatsEntry 10 }

tmnxBsxIpIdAsStatPosGlbAppFlows  OBJECT-TYPE
    SYNTAX      Counter64
    MAX-ACCESS  read-only
    STATUS      current
    DESCRIPTION
        "The value of tmnxBsxIpIdAsStatPosGlbAppFlows indicates the total
         number of sessions (pair of flows) that were positively identified
         as a global application supported in ip-identification-assist.  Some
         of these sessions do not contribute to the ip-identification-assist
         database (see tmnxBsxIpIdAsStatPosGlbIgnIpIdAs and
         tmnxBsxIpIdAsStatPosGlbIgnNoExpr)."
    ::= { tmnxBsxIpIdAsstPartStatsEntry 11 }

tmnxBsxIpIdAsStatPosGlbIgnIpIdAs OBJECT-TYPE
    SYNTAX      Counter64
    MAX-ACCESS  read-only
    STATUS      current
    DESCRIPTION
        "The value of tmnxBsxIpIdAsStatPosGlbIgnIpIdAs indicates the number of
         sessions (pair of flows) within tmnxBsxIpIdAsStatPosGlbAppFlows that
         were identified as a global application through an app-filter entry
         using the ip-identification-assist mechanism.  These sessions do not
         contribute to the ip-identification-assist database/cache."
    ::= { tmnxBsxIpIdAsstPartStatsEntry 12 }

tmnxBsxIpIdAsStatPosGlbIgnNoExpr OBJECT-TYPE
    SYNTAX      Counter64
    MAX-ACCESS  read-only
    STATUS      current
    DESCRIPTION
        "The value of tmnxBsxIpIdAsStatPosGlbIgnNoExpr indicates the number of
         sessions (pair of flows) within tmnxBsxIpIdAsStatPosGlbAppFlows that were
         identified as a global application through an app-filter entry that did
         not contain an expression match.  These sessions do not contribute to the
         ip-identification-assist database/cache."
    ::= { tmnxBsxIpIdAsstPartStatsEntry 13 }

tmnxBsxIpIdAsStatPosCacheFlow    OBJECT-TYPE
    SYNTAX      Counter64
    MAX-ACCESS  read-only
    STATUS      current
    DESCRIPTION
        "The value of tmnxBsxIpIdAsStatPosCacheFlow indicates the number of
         sessions (pair of flows) that were identified as a global application
         and contributed to the ip-identification-assist database/cache."
    ::= { tmnxBsxIpIdAsstPartStatsEntry 14 }

tmnxBsxIpIdAsStatPosCacheFlowIp4 OBJECT-TYPE
    SYNTAX      Counter64
    MAX-ACCESS  read-only
    STATUS      current
    DESCRIPTION
        "The value of tmnxBsxIpIdAsStatPosCacheFlowIp4 indicates the number of
         IPv4 addresses populated in the ip-identification-assist
         database/cache by contributing sessions
         (tmnxBsxIpIdAsStatPosCacheFlow)."
    ::= { tmnxBsxIpIdAsstPartStatsEntry 15 }

tmnxBsxIpIdAsStatPosCacheFlowIp6 OBJECT-TYPE
    SYNTAX      Counter64
    MAX-ACCESS  read-only
    STATUS      current
    DESCRIPTION
        "The value of tmnxBsxIpIdAsStatPosCacheFlowIp6 indicates the number of
         IPv6 addresses populated in the ip-identification-assist
         database/cache by contributing sessions
         (tmnxBsxIpIdAsStatPosCacheFlow)."
    ::= { tmnxBsxIpIdAsstPartStatsEntry 16 }

tmnxBsxNotifObjs                 OBJECT IDENTIFIER ::= { tmnxBsxObjs 4 }

tmnxBsxNotifyIsaAaGroupIndex     OBJECT-TYPE
    SYNTAX      TmnxBsxIsaAaGroupIndex
    MAX-ACCESS  accessible-for-notify
    STATUS      current
    DESCRIPTION
        "Used by all traps to indicate the ISA-AA Group."
    ::= { tmnxBsxNotifObjs 1 }

tmnxBsxNotifyActiveMda           OBJECT-TYPE
    SYNTAX      TmnxHwIndexOrZero
    MAX-ACCESS  accessible-for-notify
    STATUS      current
    DESCRIPTION
        "Used by all traps to indicate the currently active MDA."
    ::= { tmnxBsxNotifObjs 2 }

tmnxBsxNotifyActionStatus        OBJECT-TYPE
    SYNTAX      TmnxBsxActionStatus
    MAX-ACCESS  accessible-for-notify
    STATUS      current
    DESCRIPTION
        "Used by traps to indicate the status of an action within the ISA-AA
         group."
    ::= { tmnxBsxNotifObjs 3 }

tmnxBsxNotifyAaSubscriberType    OBJECT-TYPE
    SYNTAX      TmnxBsxAaSubscriberType
    MAX-ACCESS  accessible-for-notify
    STATUS      current
    DESCRIPTION
        "Used by traps to indicate the Application Assurance subscriber type."
    ::= { tmnxBsxNotifObjs 4 }

tmnxBsxNotifyAaSubscriberName    OBJECT-TYPE
    SYNTAX      TmnxBsxAaSubscriber
    MAX-ACCESS  accessible-for-notify
    STATUS      current
    DESCRIPTION
        "Used by traps to indicate the Application Assurance subscriber name."
    ::= { tmnxBsxNotifObjs 5 }

tmnxBsxNotifyAaSubAcctLossReason OBJECT-TYPE
    SYNTAX      TmnxBsxAaSubAcctLossReason
    MAX-ACCESS  accessible-for-notify
    STATUS      current
    DESCRIPTION
        "Used by traps to indicate the reason for a loss of Application
         Assurance subscriber accounting statistics."
    ::= { tmnxBsxNotifObjs 6 }

tmnxBsxNotifyAaGrpPartIndex      OBJECT-TYPE
    SYNTAX      TmnxBsxAaGrpPartIndex
    MAX-ACCESS  accessible-for-notify
    STATUS      current
    DESCRIPTION
        "Used by notifications to indicate the Application Assurance Group and
         Partition."
    ::= { tmnxBsxNotifObjs 7 }

tmnxBsxNotifyTransitIpPolicyId   OBJECT-TYPE
    SYNTAX      TmnxBsxTransitIpPolicyId
    MAX-ACCESS  accessible-for-notify
    STATUS      current
    DESCRIPTION
        "Used by notifications to indicate the Transit IP Policy Id."
    ::= { tmnxBsxNotifObjs 8 }

tmnxBsxNotifyRadiusCoAAuditState OBJECT-TYPE
    SYNTAX      INTEGER {
        start (1),
        end   (2)
    }
    MAX-ACCESS  accessible-for-notify
    STATUS      current
    DESCRIPTION
        "Used by notifications to indicate the state of the RADIUS Change
         of Authorization (CoA) Audit. The status may be one of:
            start (1)       - the RADIUS CoA Audit has started
            end (2)         - the RADIUS CoA Audit has ended"
    ::= { tmnxBsxNotifObjs 9 }

tmnxBsxNotifyReason              OBJECT-TYPE
    SYNTAX      DisplayString
    MAX-ACCESS  accessible-for-notify
    STATUS      current
    DESCRIPTION
        "Used by notifications to indicate the reason for a notification."
    ::= { tmnxBsxNotifObjs 10 }

tmnxBsxNotifySubFailedAction     OBJECT-TYPE
    SYNTAX      INTEGER {
        create (1),
        modify (2)
    }
    MAX-ACCESS  accessible-for-notify
    STATUS      current
    DESCRIPTION
        "Used by notifications to indicate the action of a subscriber change
         that failed. The action may be one of:
            create (1)       - the subscriber creation failed
            modify (2)       - the subscriber modification failed."
    ::= { tmnxBsxNotifObjs 11 }

tmnxBsxNotifyTcaCfgType          OBJECT-TYPE
    SYNTAX      INTEGER {
        errorDrop              (1),
        fragmentDropOutOfOrder (2),
        fragmentDropAll        (3),
        overloadDrop           (4),
        gtpSanityDrop          (5)
    }
    MAX-ACCESS  accessible-for-notify
    STATUS      current
    DESCRIPTION
        "The value of tmnxBsxNotifyTcaCfgType specifies the TCA type.

         The TCA type may be one of:
           errorDrop              (1) - based on AQP action error-drop
           fragmentDropOutOfOrder (2) - based on AQP action fragment-drop
                                        out-of-order
           fragmentDropAll        (3) - based on AQP action fragment-drop all
           overloadDrop           (4) - based on AQP action overload-drop
           gtpSanityDrop          (5) - based on AQP initial lookup"
    ::= { tmnxBsxNotifObjs 12 }

tmnxBsxNotifyTcaCfgDirection     OBJECT-TYPE
    SYNTAX      INTEGER {
        fromSub (1),
        toSub   (2)
    }
    MAX-ACCESS  accessible-for-notify
    STATUS      current
    DESCRIPTION
        "The value of tmnxBsxNotifyTcaCfgDirection specifies the TCA direction.

         The TCA direction may be one of:
           fromSub (1) - subscriber to network direction
           toSub   (2) - network to subscriber direction"
    ::= { tmnxBsxNotifObjs 13 }

tmnxBsxNotifyTcaPolicerName      OBJECT-TYPE
    SYNTAX      TNamedItem
    MAX-ACCESS  accessible-for-notify
    STATUS      current
    DESCRIPTION
        "The value of tmnxBsxNotifyTcaPolicerName specifies the name defined
         for the policer action."
    ::= { tmnxBsxNotifObjs 14 }

tmnxBsxNotifyTcaCfgFilterType    OBJECT-TYPE
    SYNTAX      INTEGER {
        gtpFilter     (1),
        sctpFilter    (2),
        sessionFilter (3)
    }
    MAX-ACCESS  accessible-for-notify
    STATUS      current
    DESCRIPTION
        "The value of tmnxBsxNotifyTcaCfgFilterType specifies the filter type.

         The TCA filter type may be one of:
           gtpFilter     (1) - as defined in tmnxBsxGtpFltrTable and
                               tmnxBsxGtpFltrMsgTable
           sctpFilter    (2) - as defined in tmnxBsxSctpFltrTable and
                               tmnxBsxSctpFltrPpidTable
           sessionFilter (3) - as defined in tmnxBsxSessFltrTable and
                               tmnxBsxSessFltrParamsTable"
    ::= { tmnxBsxNotifObjs 15 }

tmnxBsxNotifyTcaCfgFilterName    OBJECT-TYPE
    SYNTAX      TNamedItem
    MAX-ACCESS  accessible-for-notify
    STATUS      current
    DESCRIPTION
        "The value of tmnxBsxNotifyTcaCfgFilterName specifies the name of the
         filter."
    ::= { tmnxBsxNotifObjs 16 }

tmnxBsxNotifyTcaCfgFltrWmarkType OBJECT-TYPE
    SYNTAX      INTEGER {
        payloadOutOfRange    (1),
        idOutOfRange         (2),
        defaultAction        (3),
        headerSanity         (4),
        packetSanity         (5),
        gtpv2DefAction       (6),
        gtpImsiApnDefAction  (7),
        gtpTeidValidity      (8),
        gtpSeqNumValidity    (9),
        gtpSrcIpAddrValidity (10),
        gtpMissingMandIE     (11),
        gtpInGtp             (12),
        gtpTunDbRes          (13),
        gtpDefTunEpLimit     (14)
    }
    MAX-ACCESS  accessible-for-notify
    STATUS      current
    DESCRIPTION
        "The value of tmnxBsxNotifyTcaCfgFltrWmarkType specifies the filter
         watermark type.

         The TCA filter watermark type may be one of:
           payloadOutOfRange (1) - based on the filter's allowable payload
                                   range, only valid if
                                   tmnxBsxNotifyTcaCfgFilterType is set to
                                   'gtpFilter (1)'
           idOutOfRange      (2) - based on the filter's allowable ID range,
                                   only valid if tmnxBsxNotifyTcaCfgFilterType
                                   is set to 'sctpFilter (2)'
           defaultAction     (3) - based on the filter's default action
           headerSanity      (4) - based on the filter header's sanity checks,
                                   only valid if tmnxBsxNotifyTcaCfgFilterType
                                   is set to 'gtpFilter (1)'
           packetSanity      (5) - based on the filter's packet sanity checks,
                                   only valid if tmnxBsxNotifyTcaCfgFilterType
                                   is set to 'sctpFilter (2)'

           gtpv2DefAction       (6)  - based on GTP V2 message-type default action,
                                       only valid if tmnxBsxNotifyTcaCfgFilterType is
                                       gtpFilter
           gtpImsiApnDefAction  (7)  - based on imsi-apn filter default action,
                                       only valid if tmnxBsxNotifyTcaCfgFilterType is
                                       gtpFilter
           gtpTeidValidity      (8)  - based on GTP TEID validity, only valid if
                                       tmnxBsxNotifyTcaCfgFilterType is gtpFilter
           gtpSeqNumValidity    (9)  - based on GTP sequence number validity,
                                       only valid if tmnxBsxNotifyTcaCfgFilterType is
                                       gtpFilter
           gtpSrcIpAddrValidity (10) - based on GTP source gateway IP address validity,
                                       only valid if tmnxBsxNotifyTcaCfgFilterType is
                                       gtpFilter
           gtpMissingMandIE     (11) - based on GTP packet missing mandatory IE,
                                       only valid if tmnxBsxNotifyTcaCfgFilterType is
                                       gtpFilter
           gtpInGtp             (12) - based on GTP in GTP action, only valid if
                                       tmnxBsxNotifyTcaCfgFilterType is gtpFilter
           gtpTunDbRes          (13) - based on GTP tunnel database resource,
                                       only valid if tmnxBsxNotifyTcaCfgFilterType
                                       is gtpFilter
           gtpDefTunEpLimit     (14) - based on GTP default tunnel endpoint  limit, only
                                       valid if tmnxBsxNotifyTcaCfgFilterType is
                                       gtpFilter"
    ::= { tmnxBsxNotifObjs 17 }

tmnxBsxNotifyTcaFtrEnCfgEntryId  OBJECT-TYPE
    SYNTAX      Unsigned32 (1..65535)
    MAX-ACCESS  accessible-for-notify
    STATUS      current
    DESCRIPTION
        "The value of tmnxBsxNotifyTcaFtrEnCfgEntryId specifies the index into
         the filter's corresponding entry table."
    ::= { tmnxBsxNotifObjs 18 }

tmnxBsxNotifyTcpValTcaName       OBJECT-TYPE
    SYNTAX      TNamedItem
    MAX-ACCESS  accessible-for-notify
    STATUS      current
    DESCRIPTION
        "The value of tmnxBsxNotifyTcpValTcaName specifies the name defined for
         the TCP validate."
    ::= { tmnxBsxNotifObjs 19 }

tmnxBsxNotifyTcpValTcaWmarkType  OBJECT-TYPE
    SYNTAX      INTEGER {
        tcpVal (1)
    }
    MAX-ACCESS  accessible-for-notify
    STATUS      current
    DESCRIPTION
        "The value of tmnxBsxNotifyTcpValTcaWmarkType specifies the TCP
         validation TCA watermark type.

         The watermark type may be one of:
           tcpVal            (1) - based on the TCP validation template        "
    ::= { tmnxBsxNotifObjs 20 }

tmnxBsxNotifyCertProfileName     OBJECT-TYPE
    SYNTAX      TNamedItem
    MAX-ACCESS  accessible-for-notify
    STATUS      current
    DESCRIPTION
        "The value of tmnxBsxNotifyCertProfileName specifies the name of the
         certificate profile."
    ::= { tmnxBsxNotifObjs 21 }

tmnxBsxNotifyCertProfOperState   OBJECT-TYPE
    SYNTAX      TmnxOperState
    MAX-ACCESS  accessible-for-notify
    STATUS      current
    DESCRIPTION
        "The value of tmnxBsxNotifyCertProfOperState specifies the operational
         state of the certificate profile."
    ::= { tmnxBsxNotifObjs 22 }

tmnxBsxNotifyIsaSlotNum          OBJECT-TYPE
    SYNTAX      Integer32
    MAX-ACCESS  accessible-for-notify
    STATUS      current
    DESCRIPTION
        "The value of tmnxBsxNotifyIsaSlotNum indicates the slot number of this
         ISA-AA card slot or the ESA slot and is used for notifications."
    ::= { tmnxBsxNotifObjs 23 }

tmnxBsxNotifyIsaMdaNum           OBJECT-TYPE
    SYNTAX      Unsigned32
    MAX-ACCESS  accessible-for-notify
    STATUS      current
    DESCRIPTION
        "The value of tmnxBsxNotifyIsaMdaNum indicates the MDA slot number of
         this ISA-AA MDA or the ESA VM ID and is used for notifications."
    ::= { tmnxBsxNotifObjs 24 }

tmnxBsxCflowdObjs                OBJECT IDENTIFIER ::= { tmnxBsxObjs 5 }

tmnxBsxCflowdScalars             OBJECT IDENTIFIER ::= { tmnxBsxCflowdObjs 1 }

tmnxBsxCflowdLastChangeTime      OBJECT-TYPE
    SYNTAX      TimeStamp
    MAX-ACCESS  read-only
    STATUS      current
    DESCRIPTION
        "The value of tmnxBsxCflowdLastChangeTime indicates the last time a
         successful set was performed on the tmnxBsxCflowdTable."
    ::= { tmnxBsxCflowdScalars 1 }

tmnxBsxCflowdCollLastChangeTime  OBJECT-TYPE
    SYNTAX      TimeStamp
    MAX-ACCESS  read-only
    STATUS      current
    DESCRIPTION
        "The value of tmnxBsxCflowdCollLastChangeTime indicates the last time a
         successful set was performed on the tmnxBsxCflowdCollTable."
    ::= { tmnxBsxCflowdScalars 2 }

tmnxBsxCflowdPerfLastChangeTime  OBJECT-TYPE
    SYNTAX      TimeStamp
    MAX-ACCESS  read-only
    STATUS      current
    DESCRIPTION
        "The value of tmnxBsxCflowdPerfLastChangeTime indicates the last time a
         successful set was performed on the tmnxBsxCflowdPerfTable."
    ::= { tmnxBsxCflowdScalars 3 }

tmnxBsxCflowdExpLastChangeTime   OBJECT-TYPE
    SYNTAX      TimeStamp
    MAX-ACCESS  read-only
    STATUS      current
    DESCRIPTION
        "The value of tmnxBsxCflowdExpLastChangeTime indicates the last time a
         successful set was performed on the tmnxBsxCflowdExpTable."
    ::= { tmnxBsxCflowdScalars 4 }

tmnxBsxCflowdPerfExpLastChTime   OBJECT-TYPE
    SYNTAX      TimeStamp
    MAX-ACCESS  read-only
    STATUS      current
    DESCRIPTION
        "The value of tmnxBsxCflowdPerfExpLastChTime indicates the last time a
         successful set was performed on the tmnxBsxCflowdPerfExpTable."
    ::= { tmnxBsxCflowdScalars 5 }

tmnxBsxCflowdDirectExpLastChTime OBJECT-TYPE
    SYNTAX      TimeStamp
    MAX-ACCESS  read-only
    STATUS      current
    DESCRIPTION
        "The value of tmnxBsxCflowdDirectExpLastChTime indicates the last time
         a successful set was performed on the tmnxBsxCflowdDirectExpTable."
    ::= { tmnxBsxCflowdScalars 6 }

tmnxBsxCflowdDirExpAddrLastChTim OBJECT-TYPE
    SYNTAX      TimeStamp
    MAX-ACCESS  read-only
    STATUS      current
    DESCRIPTION
        "The value of tmnxBsxCflowdDirExpAddrLastChTim indicates the last time
         a successful set was performed on the tmnxBsxCflowdDirExpAddrTable."
    ::= { tmnxBsxCflowdScalars 7 }

tmnxBsxCflowdTemplateLastChTim   OBJECT-TYPE
    SYNTAX      TimeStamp
    MAX-ACCESS  read-only
    STATUS      current
    DESCRIPTION
        "The value of tmnxBsxCflowdTemplateLastChTim indicates the last time a
         successful set was performed on the tmnxBsxCflowdRecTmplTable."
    ::= { tmnxBsxCflowdScalars 8 }

tmnxBsxCflowdTmplFieldLastChTim  OBJECT-TYPE
    SYNTAX      TimeStamp
    MAX-ACCESS  read-only
    STATUS      current
    DESCRIPTION
        "The value of tmnxBsxCflowdTmplFieldLastChTim indicates the last time a
         successful set was performed on the tmnxBsxCflowdRecFieldTable."
    ::= { tmnxBsxCflowdScalars 9 }

tmnxBsxCflowdTable               OBJECT-TYPE
    SYNTAX      SEQUENCE OF TmnxBsxCflowdEntry
    MAX-ACCESS  not-accessible
    STATUS      current
    DESCRIPTION
        "The tmnxBsxCflowdTable contains the Application Assurance Cflowd
         configuration within an Application Assurance group."
    ::= { tmnxBsxCflowdObjs 2 }

tmnxBsxCflowdEntry               OBJECT-TYPE
    SYNTAX      TmnxBsxCflowdEntry
    MAX-ACCESS  not-accessible
    STATUS      current
    DESCRIPTION
        "Each tmnxBsxCflowdEntry specifies an Application Assurance Cflowd
         configuration within an Application Assurance group."
    INDEX       { tmnxBsxIsaAaGroupIndex }
    ::= { tmnxBsxCflowdTable 1 }

TmnxBsxCflowdEntry               ::= SEQUENCE
{
    tmnxBsxCflowdRowLastChange       TimeStamp,
    tmnxBsxCflowdAdminState          TmnxAdminState,
    tmnxBsxCflowdVolRate             Unsigned32,
    tmnxBsxCflowdTemplateRetransmit  Unsigned32,
    tmnxBsxCflowdDirectExportVlan    VlanIdOrNone,
    tmnxBsxCflowdExpOvdMode          TmnxBsxCflowdExpOvdMode,
    tmnxBsxCflowdExpOvdPrefix        SnmpAdminString,
    tmnxBsxCflowdAes128EncrptKey     OCTET STRING,
    tmnxBsxCflowdAes256EncrptKey     OCTET STRING,
    tmnxBsxCflowdSystemName          TNamedItemOrEmpty
}

tmnxBsxCflowdRowLastChange       OBJECT-TYPE
    SYNTAX      TimeStamp
    MAX-ACCESS  read-only
    STATUS      current
    DESCRIPTION
        "The value of tmnxBsxCflowdRowLastChange indicates the last time a
         successful set was performed on this row of the tmnxBsxCflowdTable."
    ::= { tmnxBsxCflowdEntry 1 }

tmnxBsxCflowdAdminState          OBJECT-TYPE
    SYNTAX      TmnxAdminState
    MAX-ACCESS  read-write
    STATUS      current
    DESCRIPTION
        "The value of tmnxBsxCflowdAdminState specifies the administrative
         state for Application Assurance Cflowd collection and export. When set
         to 'outOfService', no application assurance Cflowd records are
         collected or exported for this group."
    DEFVAL      { outOfService }
    ::= { tmnxBsxCflowdEntry 2 }

tmnxBsxCflowdVolRate             OBJECT-TYPE
    SYNTAX      Unsigned32 (0..10000)
    MAX-ACCESS  read-write
    STATUS      current
    DESCRIPTION
        "The value of tmnxBsxCflowdVolRate specifies the sampling rate of
         packets for the Cflowd export of Application Assurance volume
         statistics."
    DEFVAL      { 0 }
    ::= { tmnxBsxCflowdEntry 3 }

tmnxBsxCflowdTemplateRetransmit  OBJECT-TYPE
    SYNTAX      Unsigned32 (10..600)
    UNITS       "seconds"
    MAX-ACCESS  read-write
    STATUS      current
    DESCRIPTION
        "The value of tmnxBsxCflowdTemplateRetransmit specifies the period of
         time, in seconds, for the template to be retransmitted."
    DEFVAL      { 600 }
    ::= { tmnxBsxCflowdEntry 4 }

tmnxBsxCflowdDirectExportVlan    OBJECT-TYPE
    SYNTAX      VlanIdOrNone
    MAX-ACCESS  read-write
    STATUS      current
    DESCRIPTION
        "The value of tmnxBsxCflowdDirectExportVlan specifies the ISA-AA
         service port VLAN ID which is used to generate Cflowd direct export
         collector traffic. There must be at least one corresponding entry in
         the Cflowd direct export table in order to change the VLAN ID to a
         non-default value.

         A VLAN ID of 0 specifies that collector traffic is sent via the
         collectors configured in tmnxBsxCflowdCollTable."
    DEFVAL      { 0 }
    ::= { tmnxBsxCflowdEntry 5 }

tmnxBsxCflowdExpOvdMode          OBJECT-TYPE
    SYNTAX      TmnxBsxCflowdExpOvdMode
    MAX-ACCESS  read-write
    STATUS      current
    DESCRIPTION
        "The value of tmnxBsxCflowdExpOvdMode specifies the export override mode
         applied on each flow of Application Assurance cflowd.  This applies to
         all cflowd export types (volume, comprehensive, ...)"
    DEFVAL      { none }
    ::= { tmnxBsxCflowdEntry 6 }

tmnxBsxCflowdExpOvdPrefix        OBJECT-TYPE
    SYNTAX      SnmpAdminString (SIZE (0..8))
    MAX-ACCESS  read-write
    STATUS      current
    DESCRIPTION
        "The value of tmnxBsxCflowdExpOvdPrefix specifies the ifname prefix used
         in the cflowd records generated when the tmnxBsxCflowdExpOvdMode is set
         to the mobile value.  This item is ignored when the override mode is set
         to default or ifname-obfuscate."
    DEFVAL      { "" }
    ::= { tmnxBsxCflowdEntry 7 }

tmnxBsxCflowdAes128EncrptKey     OBJECT-TYPE
    SYNTAX      OCTET STRING (SIZE (0|16))
    MAX-ACCESS  read-write
    STATUS      current
    DESCRIPTION
        "The value of tmnxBsxCflowdAes128EncrptKey specifies the AES-128 key to
         encrypt cflowd fields that are defined to be AES-128 encrypted fields
         before transmitting from the SR router to a configured collector.

         This value is write-only and will appear empty when reading from SNMP."
    DEFVAL      { ''H }
    ::= { tmnxBsxCflowdEntry 8 }

tmnxBsxCflowdAes256EncrptKey     OBJECT-TYPE
    SYNTAX      OCTET STRING (SIZE (0|32))
    MAX-ACCESS  read-write
    STATUS      current
    DESCRIPTION
        "The value of tmnxBsxCflowdAes256EncrptKey specifies the AES-256 key to
         encrypt cflowd fields that are defined to be AES-256 encrypted before
         transmitting from the SR router to a configured collector.

         This value is write-only and will appear empty when reading from SNMP."
    DEFVAL      { ''H }
    ::= { tmnxBsxCflowdEntry 9 }

tmnxBsxCflowdSystemName          OBJECT-TYPE
    SYNTAX      TNamedItemOrEmpty
    MAX-ACCESS  read-write
    STATUS      current
    DESCRIPTION
        "The value of tmnxBsxCflowdSystemName specifies the text string that
         can be exported in comprehensive cflowd as the proprietary
         'aaSystemName' field"
    DEFVAL      { "" }
    ::= { tmnxBsxCflowdEntry 10 }

tmnxBsxCflowdCollTable           OBJECT-TYPE
    SYNTAX      SEQUENCE OF TmnxBsxCflowdCollEntry
    MAX-ACCESS  not-accessible
    STATUS      current
    DESCRIPTION
        "The tmnxBsxCflowdCollTable contains the Application Assurance remote
         Cflowd collector configuration within an Application Assurance group."
    ::= { tmnxBsxCflowdObjs 3 }

tmnxBsxCflowdCollEntry           OBJECT-TYPE
    SYNTAX      TmnxBsxCflowdCollEntry
    MAX-ACCESS  not-accessible
    STATUS      current
    DESCRIPTION
        "Each tmnxBsxCflowdCollEntry specifies an Application Assurance remote
         Cflowd collector within an Application Assurance group."
    INDEX       {
        tmnxBsxIsaAaGroupIndex,
        tmnxBsxCflowdCollAddressType,
        tmnxBsxCflowdCollAddress,
        tmnxBsxCflowdCollPort
    }
    ::= { tmnxBsxCflowdCollTable 1 }

TmnxBsxCflowdCollEntry           ::= SEQUENCE
{
    tmnxBsxCflowdCollAddressType     InetAddressType,
    tmnxBsxCflowdCollAddress         InetAddress,
    tmnxBsxCflowdCollPort            TTcpUdpPort,
    tmnxBsxCflowdCollRowStatus       RowStatus,
    tmnxBsxCflowdCollRowLastChange   TimeStamp,
    tmnxBsxCflowdCollDescription     TItemDescription,
    tmnxBsxCflowdCollAdminState      TmnxAdminState,
    tmnxBsxCflowdCollOperState       TmnxOperState,
    tmnxBsxCflowdCollVersion         Unsigned32
}

tmnxBsxCflowdCollAddressType     OBJECT-TYPE
    SYNTAX      InetAddressType
    MAX-ACCESS  not-accessible
    STATUS      current
    DESCRIPTION
        "The value of tmnxBsxCflowdCollAddressType specifies the address type
         of the tmnxBsxCflowdCollAddress."
    ::= { tmnxBsxCflowdCollEntry 1 }

tmnxBsxCflowdCollAddress         OBJECT-TYPE
    SYNTAX      InetAddress (SIZE (0|4|16))
    MAX-ACCESS  not-accessible
    STATUS      current
    DESCRIPTION
        "The value of tmnxBsxCflowdCollAddress specifies the address of the
         remote Cflowd collector to receive exported Application Assurance
         Cflowd records. Only IPv4 addresses are supported."
    ::= { tmnxBsxCflowdCollEntry 2 }

tmnxBsxCflowdCollPort            OBJECT-TYPE
    SYNTAX      TTcpUdpPort (1..65535)
    MAX-ACCESS  not-accessible
    STATUS      current
    DESCRIPTION
        "The value of tmnxBsxCflowdCollPort specifies the port number of the
         remote Cflowd collector to receive exported Application Assurance
         Cflowd records."
    ::= { tmnxBsxCflowdCollEntry 3 }

tmnxBsxCflowdCollRowStatus       OBJECT-TYPE
    SYNTAX      RowStatus
    MAX-ACCESS  read-create
    STATUS      current
    DESCRIPTION
        "The value of tmnxBsxCflowdCollRowStatus specifies the row status. Rows
         in the tmnxBsxCflowdCollTable are created by specifying the value of
         'createAndGo (4)', and deleted by specifying the value of 'destroy
         (6)'."
    ::= { tmnxBsxCflowdCollEntry 4 }

tmnxBsxCflowdCollRowLastChange   OBJECT-TYPE
    SYNTAX      TimeStamp
    MAX-ACCESS  read-only
    STATUS      current
    DESCRIPTION
        "The value of tmnxBsxCflowdCollRowLastChange indicates the last time a
         successful set was performed on this row of the
         tmnxBsxCflowdCollTable."
    ::= { tmnxBsxCflowdCollEntry 5 }

tmnxBsxCflowdCollDescription     OBJECT-TYPE
    SYNTAX      TItemDescription
    MAX-ACCESS  read-create
    STATUS      current
    DESCRIPTION
        "The value of tmnxBsxCflowdCollDescription specifies the description of
         the remote Cflowd collector."
    DEFVAL      { "" }
    ::= { tmnxBsxCflowdCollEntry 6 }

tmnxBsxCflowdCollAdminState      OBJECT-TYPE
    SYNTAX      TmnxAdminState
    MAX-ACCESS  read-create
    STATUS      current
    DESCRIPTION
        "The value of tmnxBsxCflowdCollAdminState specifies the administrative
         state for the remote Cflowd collector. When 'outOfService', no
         application assurance Cflowd records are sent to the collector."
    DEFVAL      { outOfService }
    ::= { tmnxBsxCflowdCollEntry 7 }

tmnxBsxCflowdCollOperState       OBJECT-TYPE
    SYNTAX      TmnxOperState
    MAX-ACCESS  read-only
    STATUS      current
    DESCRIPTION
        "The value of tmnxBsxCflowdCollOperState indicates the
         operational state for the collector.  When 'outOfService',
         no application assurance Cflowd records are sent to the
         collector."
    DEFVAL      { outOfService }
    ::= { tmnxBsxCflowdCollEntry 8 }

tmnxBsxCflowdCollVersion         OBJECT-TYPE
    SYNTAX      Unsigned32 (10)
    MAX-ACCESS  read-create
    STATUS      current
    DESCRIPTION
        "The value of tmnxBsxCflowdCollVersion specifies the version of this
         collector."
    DEFVAL      { 10 }
    ::= { tmnxBsxCflowdCollEntry 9 }

tmnxBsxCflowdPerfTable           OBJECT-TYPE
    SYNTAX      SEQUENCE OF TmnxBsxCflowdPerfEntry
    MAX-ACCESS  not-accessible
    STATUS      current
    DESCRIPTION
        "The tmnxBsxCflowdPerfTable contains the Application Assurance Cflowd
         configuration for performance statistics sampling within an
         Application Assurance group and measurement type."
    ::= { tmnxBsxCflowdObjs 4 }

tmnxBsxCflowdPerfEntry           OBJECT-TYPE
    SYNTAX      TmnxBsxCflowdPerfEntry
    MAX-ACCESS  not-accessible
    STATUS      current
    DESCRIPTION
        "Each tmnxBsxCflowdPerfEntry specifies an Application Assurance Cflowd
         configuration of performance statistics sampling within an Application
         Assurance group and measurement type."
    INDEX       {
        tmnxBsxIsaAaGroupIndex,
        tmnxBsxCflowdPerfMeasType
    }
    ::= { tmnxBsxCflowdPerfTable 1 }

TmnxBsxCflowdPerfEntry           ::= SEQUENCE
{
    tmnxBsxCflowdPerfMeasType        TmnxBsxCflowdPerfMeasType,
    tmnxBsxCflowdPerfRowLastChange   TimeStamp,
    tmnxBsxCflowdPerfFlowRate        Unsigned32,
    tmnxBsxCflowdPerfFlowRate2       Unsigned32
}

tmnxBsxCflowdPerfMeasType        OBJECT-TYPE
    SYNTAX      TmnxBsxCflowdPerfMeasType
    MAX-ACCESS  not-accessible
    STATUS      current
    DESCRIPTION
        "The value of tmnxBsxCflowdPerfMeasType specifies the performance
         measurement type which has Cflowd export of Application Assurance
         per-flow performance statistics enabled."
    ::= { tmnxBsxCflowdPerfEntry 1 }

tmnxBsxCflowdPerfRowLastChange   OBJECT-TYPE
    SYNTAX      TimeStamp
    MAX-ACCESS  read-only
    STATUS      current
    DESCRIPTION
        "The value of tmnxBsxCflowdPerfRowLastChange indicates the last time a
         successful set was performed on this row of the
         tmnxBsxCflowdPerfTable."
    ::= { tmnxBsxCflowdPerfEntry 2 }

tmnxBsxCflowdPerfFlowRate        OBJECT-TYPE
    SYNTAX      Unsigned32 (0..1000)
    MAX-ACCESS  read-write
    STATUS      current
    DESCRIPTION
        "The value of tmnxBsxCflowdPerfFlowRate specifies the per-flow sampling
         rate for the Cflowd export of Application Assurance performance
         statistics.

         tmnxBsxCflowdPerfFlowRate applies when the associated
         tmnxBsxCflowdPerfExpRateNum has the value of 1."
    DEFVAL      { 0 }
    ::= { tmnxBsxCflowdPerfEntry 3 }

tmnxBsxCflowdPerfFlowRate2       OBJECT-TYPE
    SYNTAX      Unsigned32 (0..1000)
    MAX-ACCESS  read-write
    STATUS      current
    DESCRIPTION
        "The value of tmnxBsxCflowdPerfFlowRate2 specifies an additional
         per-flow sampling rate for the Cflowd export of Application Assurance
         performance statistics.

         tmnxBsxCflowdPerfFlowRate2 applies when the associated
         tmnxBsxCflowdPerfExpRateNum has the value of 2."
    DEFVAL      { 0 }
    ::= { tmnxBsxCflowdPerfEntry 4 }

tmnxBsxCflowdExpTable            OBJECT-TYPE
    SYNTAX      SEQUENCE OF TmnxBsxCflowdExpEntry
    MAX-ACCESS  not-accessible
    STATUS      current
    DESCRIPTION
        "The tmnxBsxCflowdExpTable contains an entry for each Application
         Assurance group and partition in the system. Each row contains the
         configuration for the Cflowd export of Application Assurance per-flow
         volume, performance, or comprehensive statistics."
    ::= { tmnxBsxCflowdObjs 5 }

tmnxBsxCflowdExpEntry            OBJECT-TYPE
    SYNTAX      TmnxBsxCflowdExpEntry
    MAX-ACCESS  not-accessible
    STATUS      current
    DESCRIPTION
        "Each tmnxBsxCflowdExpEntry indicates the configuration of the Cflowd
         export of Application Assurance per-flow volume, performance, or
         comprehensive statistics for an Application Assurance group and
         partition."
    INDEX       {
        tmnxBsxAaGrpPartIndex,
        tmnxBsxCflowdExpType
    }
    ::= { tmnxBsxCflowdExpTable 1 }

TmnxBsxCflowdExpEntry            ::= SEQUENCE
{
    tmnxBsxCflowdExpType             TmnxBsxCflowdExpType,
    tmnxBsxCflowdExpRowLastChange    TimeStamp,
    tmnxBsxCflowdExpAdminState       TmnxAdminState
}

tmnxBsxCflowdExpType             OBJECT-TYPE
    SYNTAX      TmnxBsxCflowdExpType
    MAX-ACCESS  not-accessible
    STATUS      current
    DESCRIPTION
        "The value of tmnxBsxCflowdExpType specifies the type of the
         Application Assurance statistic exported using Cflowd."
    ::= { tmnxBsxCflowdExpEntry 1 }

tmnxBsxCflowdExpRowLastChange    OBJECT-TYPE
    SYNTAX      TimeStamp
    MAX-ACCESS  read-only
    STATUS      current
    DESCRIPTION
        "The value of tmnxBsxCflowdExpRowLastChange indicates the last time a
         successful set was performed on this row of the tmnxBsxCflowdExpTable."
    ::= { tmnxBsxCflowdExpEntry 2 }

tmnxBsxCflowdExpAdminState       OBJECT-TYPE
    SYNTAX      TmnxAdminState
    MAX-ACCESS  read-write
    STATUS      current
    DESCRIPTION
        "The value of tmnxBsxCflowdExpAdminState specifies the administrative
         state for the collection of records for cflowd export. When
         'outOfService', no application assurance Cflowd records are collected."
    DEFVAL      { outOfService }
    ::= { tmnxBsxCflowdExpEntry 3 }

tmnxBsxCflowdPerfExpTable        OBJECT-TYPE
    SYNTAX      SEQUENCE OF TmnxBsxCflowdPerfExpEntry
    MAX-ACCESS  not-accessible
    STATUS      current
    DESCRIPTION
        "The tmnxBsxCflowdPerfExpTable contains an entry for each Application
         Assurance application and application-group that has Cflowd export of
         Application Assurance per-flow performance statistics enabled."
    ::= { tmnxBsxCflowdObjs 6 }

tmnxBsxCflowdPerfExpEntry        OBJECT-TYPE
    SYNTAX      TmnxBsxCflowdPerfExpEntry
    MAX-ACCESS  not-accessible
    STATUS      current
    DESCRIPTION
        "Each tmnxBsxCflowdPerfExpEntry specifies an Application Assurance
         group, partition, statistics type, statistics name, and performance
         measurement type for which Cflowd export of Application Assurance
         per-flow performance statistics are enabled.

         A value of 'chargingGroup (4)' is not supported for the
         tmnxBsxStatAaType. "
    INDEX       {
        tmnxBsxAaGrpPartIndex,
        tmnxBsxStatAaType,
        tmnxBsxStatAaName,
        tmnxBsxCflowdPerfMeasType
    }
    ::= { tmnxBsxCflowdPerfExpTable 1 }

TmnxBsxCflowdPerfExpEntry        ::= SEQUENCE
{
    tmnxBsxCflowdPerfExpRowStatus    RowStatus,
    tmnxBsxCflowdPerfExpRowLastChnge TimeStamp,
    tmnxBsxCflowdPerfExpRateNum      Unsigned32
}

tmnxBsxCflowdPerfExpRowStatus    OBJECT-TYPE
    SYNTAX      RowStatus
    MAX-ACCESS  read-create
    STATUS      current
    DESCRIPTION
        "The value of tmnxBsxCflowdPerfExpRowStatus specifies
         the row status.  It allows entries to be created
         and deleted in the tmnxBsxCflowdPerfExpTable.

         Rows are created by specifying the value of 'createAndGo (4)', and
         deleted by specifying the value of 'destroy (6)'."
    ::= { tmnxBsxCflowdPerfExpEntry 1 }

tmnxBsxCflowdPerfExpRowLastChnge OBJECT-TYPE
    SYNTAX      TimeStamp
    MAX-ACCESS  read-only
    STATUS      current
    DESCRIPTION
        "The value of tmnxBsxCflowdPerfExpRowLastChnge indicates the last time
         a successful set was performed on this row of the
         tmnxBsxCflowdPerfExpTable."
    ::= { tmnxBsxCflowdPerfExpEntry 2 }

tmnxBsxCflowdPerfExpRateNum      OBJECT-TYPE
    SYNTAX      Unsigned32 (1..2)
    MAX-ACCESS  read-create
    STATUS      current
    DESCRIPTION
        "The value of tmnxBsxCflowdPerfExpRateNum indicates which rate in
         tmnxBsxCflowdPerfTable applies. A value of 1 indicates
         tmnxBsxCflowdPerfFlowRate. A value of 2 indicates
         tmnxBsxCflowdPerfFlowRate2"
    DEFVAL      { 1 }
    ::= { tmnxBsxCflowdPerfExpEntry 3 }

tmnxBsxCflowdStatusTable         OBJECT-TYPE
    SYNTAX      SEQUENCE OF TmnxBsxCflowdStatusEntry
    MAX-ACCESS  not-accessible
    STATUS      current
    DESCRIPTION
        "The tmnxBsxCflowdStatusTable contains an entry for each ISA-AA MDA and
         Group in the system. Each row contains the Cflowd status information
         per group and Cflowd export type for an ISA-AA MDA uniquely identified
         by the tmnxChassisIndex, tmnxBsxCardSlotEsaId, and the
         tmnxBsxMdaSlotEsaVmId."
    ::= { tmnxBsxCflowdObjs 7 }

tmnxBsxCflowdStatusEntry         OBJECT-TYPE
    SYNTAX      TmnxBsxCflowdStatusEntry
    MAX-ACCESS  not-accessible
    STATUS      current
    DESCRIPTION
        "Each tmnxBsxCflowdStatusEntry contains the Cflowd status information
         for a particular group, Cflowd export type and ISA-AA MDA.

         An index with a valid tmnxBsxIsaAaGroupIndex and a valid
         tmnxBsxCflowdExpType, tmnxChassisIndex set to one, and a zero value
         for each of the tmnxBsxCardSlotEsaId/tmnxBsxMdaSlotEsaVmId indices
         will return the summarized per group status."
    INDEX       {
        tmnxBsxIsaAaGroupIndex,
        tmnxBsxCflowdExpType,
        tmnxChassisIndex,
        tmnxBsxCardSlotEsaId,
        tmnxBsxMdaSlotEsaVmId
    }
    ::= { tmnxBsxCflowdStatusTable 1 }

TmnxBsxCflowdStatusEntry         ::= SEQUENCE
{
    tmnxBsxCflowdStatusDiscontTime   TimeStamp,
    tmnxBsxCflowdStatusActFlowsCurr  Gauge32,
    tmnxBsxCflowdStatusRecRateCurr   Gauge32,
    tmnxBsxCflowdStatusPktRateCurr   Gauge32,
    tmnxBsxCflowdStatusRecReported   Counter32,
    tmnxBsxCflowdStatusHCRecReported Counter64,
    tmnxBsxCflowdStatusRecDropped    Counter32,
    tmnxBsxCflowdStatusHCRecDropped  Counter64,
    tmnxBsxCflowdStatusPktsSent      Counter32,
    tmnxBsxCflowdStatusHCPktsSent    Counter64,
    tmnxBsxCflowdStatusFlowsNoRes    Counter32,
    tmnxBsxCflowdStatusHCFlowsNoRes  Counter64,
    tmnxBsxCflowdStatusHCUSupSSRCSt  Counter64,
    tmnxBsxCflowdStatusUSupSSRCStLo  Counter32,
    tmnxBsxCflowdStatusUSupSSRCStHi  Counter32
}

tmnxBsxCflowdStatusDiscontTime   OBJECT-TYPE
    SYNTAX      TimeStamp
    MAX-ACCESS  read-only
    STATUS      current
    DESCRIPTION
        "The value of tmnxBsxCflowdStatusDiscontTime indicates the
         SNMPv2-MIB::sysUpTime (centiseconds) when the ISA-AA MDA within the
         group has last changed status."
    ::= { tmnxBsxCflowdStatusEntry 1 }

tmnxBsxCflowdStatusActFlowsCurr  OBJECT-TYPE
    SYNTAX      Gauge32
    UNITS       "flows"
    MAX-ACCESS  read-only
    STATUS      current
    DESCRIPTION
        "The value of tmnxBsxCflowdStatusActFlowsCurr indicates the number of
         active flows currently marked for export using Cflowd in the ISA-AA
         MDA(s)."
    ::= { tmnxBsxCflowdStatusEntry 2 }

tmnxBsxCflowdStatusRecRateCurr   OBJECT-TYPE
    SYNTAX      Gauge32
    UNITS       "records per second"
    MAX-ACCESS  read-only
    STATUS      current
    DESCRIPTION
        "The value of tmnxBsxCflowdStatusRecRateCurr indicates the
         number of flow records per second being exported using
         Cflowd from the ISA-AA MDA(s).  The calculation is based
         on the number of flow records inserted into Cflowd packets
         within the last 10 seconds."
    ::= { tmnxBsxCflowdStatusEntry 3 }

tmnxBsxCflowdStatusPktRateCurr   OBJECT-TYPE
    SYNTAX      Gauge32
    UNITS       "packets per second"
    MAX-ACCESS  read-only
    STATUS      current
    DESCRIPTION
        "The value of tmnxBsxCflowdStatusPktRateCurr indicates the number of
         Cflowd packets per second being exported from the ISA-AA MDA(s). The
         calculation is based on the number of Cflowd packets generated within
         the last 10 seconds."
    ::= { tmnxBsxCflowdStatusEntry 4 }

tmnxBsxCflowdStatusRecReported   OBJECT-TYPE
    SYNTAX      Counter32
    UNITS       "records"
    MAX-ACCESS  read-only
    STATUS      current
    DESCRIPTION
        "The value of tmnxBsxCflowdStatusRecReported indicates the total number
         of flow records reported from the ISA-AA MDA(s)."
    ::= { tmnxBsxCflowdStatusEntry 5 }

tmnxBsxCflowdStatusHCRecReported OBJECT-TYPE
    SYNTAX      Counter64
    UNITS       "records"
    MAX-ACCESS  read-only
    STATUS      current
    DESCRIPTION
        "The value of tmnxBsxCflowdStatusHCRecReported indicates the total
         number of flow records reported from the ISA-AA MDA(s). This object is
         the 64-bit version of tmnxBsxCflowdStatusRecReported."
    ::= { tmnxBsxCflowdStatusEntry 6 }

tmnxBsxCflowdStatusRecDropped    OBJECT-TYPE
    SYNTAX      Counter32
    UNITS       "records"
    MAX-ACCESS  read-only
    STATUS      current
    DESCRIPTION
        "The value of tmnxBsxCflowdStatusRecDropped indicates the total number
         of flow records dropped in the ISA-AA MDA(s)."
    ::= { tmnxBsxCflowdStatusEntry 7 }

tmnxBsxCflowdStatusHCRecDropped  OBJECT-TYPE
    SYNTAX      Counter64
    UNITS       "records"
    MAX-ACCESS  read-only
    STATUS      current
    DESCRIPTION
        "The value of tmnxBsxCflowdStatusHCRecDropped indicates the total
         number of flow records dropped in the ISA-AA MDA(s). This object is
         the 64-bit version of tmnxBsxCflowdStatusRecDropped."
    ::= { tmnxBsxCflowdStatusEntry 8 }

tmnxBsxCflowdStatusPktsSent      OBJECT-TYPE
    SYNTAX      Counter32
    UNITS       "packets"
    MAX-ACCESS  read-only
    STATUS      current
    DESCRIPTION
        "The value of tmnxBsxCflowdStatusPktsSent indicates the total number of
         Cflowd packets sent from the ISA-AA MDA(s)."
    ::= { tmnxBsxCflowdStatusEntry 9 }

tmnxBsxCflowdStatusHCPktsSent    OBJECT-TYPE
    SYNTAX      Counter64
    UNITS       "packets"
    MAX-ACCESS  read-only
    STATUS      current
    DESCRIPTION
        "The value of tmnxBsxCflowdStatusHCPktsSent indicates the total number
         of Cflowd packets sent from the ISA-AA MDA(s). This object is the
         64-bit version of tmnxBsxCflowdStatusPktsSent."
    ::= { tmnxBsxCflowdStatusEntry 10 }

tmnxBsxCflowdStatusFlowsNoRes    OBJECT-TYPE
    SYNTAX      Counter32
    UNITS       "flows"
    MAX-ACCESS  read-only
    STATUS      current
    DESCRIPTION
        "The value of tmnxBsxCflowdStatusFlowsNoRes indicates the total number
         of flows that were selected for export but failed to obtain Cflows
         resources in the ISA-AA MDA(s)."
    ::= { tmnxBsxCflowdStatusEntry 11 }

tmnxBsxCflowdStatusHCFlowsNoRes  OBJECT-TYPE
    SYNTAX      Counter64
    UNITS       "flows"
    MAX-ACCESS  read-only
    STATUS      current
    DESCRIPTION
        "The value of tmnxBsxCflowdStatusHCFlowsNoRes indicates the total
         number of flows that were selected for export but failed to obtain
         Cflows resources in the ISA-AA MDA(s). This object is the 64-bit
         version of tmnxBsxCflowdStatusFlowsNoRes."
    ::= { tmnxBsxCflowdStatusEntry 12 }

tmnxBsxCflowdStatusHCUSupSSRCSt  OBJECT-TYPE
    SYNTAX      Counter64
    MAX-ACCESS  read-only
    STATUS      obsolete
    DESCRIPTION
        "The value of tmnxBsxCflowdStatusHCUSupSSRCSt indicates the number of
         synchronization source (SSRC) records which had to be aborted (due to
         reasons such as unknown codec type, non media stream, codec switch,
         etc).

         This value applies only when the index tmnxBsxCflowdExpType has a
         value of 'rtpPerformance(3)' and is otherwise zero."
    ::= { tmnxBsxCflowdStatusEntry 13 }

tmnxBsxCflowdStatusUSupSSRCStLo  OBJECT-TYPE
    SYNTAX      Counter32
    MAX-ACCESS  read-only
    STATUS      obsolete
    DESCRIPTION
        "The value of tmnxBsxCflowdStatusUSupSSRCStLo indicates the lower
         32-bits of tmnxBsxCflowdStatusHCUSupSSRCSt.

         This value applies only when the index tmnxBsxCflowdExpType has a
         value of 'rtpPerformance(3)' and is otherwise zero."
    ::= { tmnxBsxCflowdStatusEntry 14 }

tmnxBsxCflowdStatusUSupSSRCStHi  OBJECT-TYPE
    SYNTAX      Counter32
    MAX-ACCESS  read-only
    STATUS      obsolete
    DESCRIPTION
        "The value of tmnxBsxCflowdStatusUSupSSRCStHi indicates the upper
         32-bits of tmnxBsxCflowdStatusHCUSupSSRCSt.

         This value applies only when the index tmnxBsxCflowdExpType has a
         value of 'rtpPerformance(3)' and is otherwise zero."
    ::= { tmnxBsxCflowdStatusEntry 15 }

tmnxBsxCflowdCollStatTable       OBJECT-TYPE
    SYNTAX      SEQUENCE OF TmnxBsxCflowdCollStatEntry
    MAX-ACCESS  not-accessible
    STATUS      current
    DESCRIPTION
        "The tmnxBsxCflowdCollStatTable contains statistics on the Application
         Assurance Cflowd collectors within an Application Assurance group."
    ::= { tmnxBsxCflowdObjs 8 }

tmnxBsxCflowdCollStatEntry       OBJECT-TYPE
    SYNTAX      TmnxBsxCflowdCollStatEntry
    MAX-ACCESS  not-accessible
    STATUS      current
    DESCRIPTION
        "Each tmnxBsxCflowdCollStatEntry contains the statistics for an
         Application Assurance Cflowd collector within an Application Assurance
         group."
    INDEX       {
        tmnxBsxIsaAaGroupIndex,
        tmnxBsxCflowdCollAddressType,
        tmnxBsxCflowdCollAddress,
        tmnxBsxCflowdCollPort
    }
    ::= { tmnxBsxCflowdCollStatTable 1 }

TmnxBsxCflowdCollStatEntry       ::= SEQUENCE
{
    tmnxBsxCflowdCollStatDiscontTime TimeStamp,
    tmnxBsxCflowdCollStatRecSent     Counter32,
    tmnxBsxCflowdCollStatHCRecSent   Counter64
}

tmnxBsxCflowdCollStatDiscontTime OBJECT-TYPE
    SYNTAX      TimeStamp
    MAX-ACCESS  read-only
    STATUS      current
    DESCRIPTION
        "The value of tmnxBsxCflowdCollStatDiscontTime indicates the
         SNMPv2-MIB::sysUpTime (centiseconds) when the Cflowd collector has
         last changed status."
    ::= { tmnxBsxCflowdCollStatEntry 1 }

tmnxBsxCflowdCollStatRecSent     OBJECT-TYPE
    SYNTAX      Counter32
    UNITS       "records"
    MAX-ACCESS  read-only
    STATUS      current
    DESCRIPTION
        "The value of tmnxBsxCflowdCollStatRecSent indicates the total number
         of flow records sent to the remote Cflowd collector."
    ::= { tmnxBsxCflowdCollStatEntry 2 }

tmnxBsxCflowdCollStatHCRecSent   OBJECT-TYPE
    SYNTAX      Counter64
    UNITS       "records"
    MAX-ACCESS  read-only
    STATUS      current
    DESCRIPTION
        "The value of tmnxBsxCflowdCollStatHCRecSent indicates the total number
         of flow records sent to the remote Cflowd collector. This object is
         the 64-bit version of tmnxBsxCflowdCollStatRecSent."
    ::= { tmnxBsxCflowdCollStatEntry 3 }

tmnxBsxCflowdExpStatTable        OBJECT-TYPE
    SYNTAX      SEQUENCE OF TmnxBsxCflowdExpStatEntry
    MAX-ACCESS  not-accessible
    STATUS      current
    DESCRIPTION
        "The tmnxBsxCflowdExpStatTable contains statistics on the Cflowd export
         of Application Assurance per-flow volume, performance, or
         comprehensive records within an Application Assurance group and
         partition."
    ::= { tmnxBsxCflowdObjs 9 }

tmnxBsxCflowdExpStatEntry        OBJECT-TYPE
    SYNTAX      TmnxBsxCflowdExpStatEntry
    MAX-ACCESS  not-accessible
    STATUS      current
    DESCRIPTION
        "Each tmnxBsxCflowdExpStatEntry contains the statistics on the Cflowd
         export of Application Assurance per-flow volume, performance, or
         comprehensive records for an Application Assurance group and
         partition."
    INDEX       {
        tmnxBsxAaGrpPartIndex,
        tmnxBsxCflowdExpType
    }
    ::= { tmnxBsxCflowdExpStatTable 1 }

TmnxBsxCflowdExpStatEntry        ::= SEQUENCE
{
    tmnxBsxCflowdExpStatDiscontTime  TimeStamp,
    tmnxBsxCflowdExpStatRecReport    Counter32,
    tmnxBsxCflowdExpStatHCRecReport  Counter64,
    tmnxBsxCflowdExpStatRecDropped   Counter32,
    tmnxBsxCflowdExpStatHCRecDropped Counter64,
    tmnxBsxCflowdExpStatFlowsNoRes   Counter32,
    tmnxBsxCflowdExpStatHCFlowsNoRes Counter64,
    tmnxBsxCflowdExpStatHCUSupSSRCSt Counter64,
    tmnxBsxCflowdExpStatUSupSSRCStLo Counter32,
    tmnxBsxCflowdExpStatUSupSSRCStHi Counter32
}

tmnxBsxCflowdExpStatDiscontTime  OBJECT-TYPE
    SYNTAX      TimeStamp
    MAX-ACCESS  read-only
    STATUS      current
    DESCRIPTION
        "The value of tmnxBsxCflowdExpStatDiscontTime indicates the
         SNMPv2-MIB::sysUpTime (centiseconds) when the export of cflowd records
         has last changed status."
    ::= { tmnxBsxCflowdExpStatEntry 1 }

tmnxBsxCflowdExpStatRecReport    OBJECT-TYPE
    SYNTAX      Counter32
    UNITS       "records"
    MAX-ACCESS  read-only
    STATUS      current
    DESCRIPTION
        "The value of tmnxBsxCflowdExpStatRecReport indicates the total number
         of flow records reported."
    ::= { tmnxBsxCflowdExpStatEntry 2 }

tmnxBsxCflowdExpStatHCRecReport  OBJECT-TYPE
    SYNTAX      Counter64
    UNITS       "records"
    MAX-ACCESS  read-only
    STATUS      current
    DESCRIPTION
        "The value of tmnxBsxCflowdExpStatHCRecReport indicates the total
         number of flow records reported. This object is the 64-bit version of
         tmnxBsxCflowdExpStatRecReport."
    ::= { tmnxBsxCflowdExpStatEntry 3 }

tmnxBsxCflowdExpStatRecDropped   OBJECT-TYPE
    SYNTAX      Counter32
    UNITS       "records"
    MAX-ACCESS  read-only
    STATUS      current
    DESCRIPTION
        "The value of tmnxBsxCflowdExpStatRecDropped indicates the total number
         of flow records dropped."
    ::= { tmnxBsxCflowdExpStatEntry 4 }

tmnxBsxCflowdExpStatHCRecDropped OBJECT-TYPE
    SYNTAX      Counter64
    UNITS       "records"
    MAX-ACCESS  read-only
    STATUS      current
    DESCRIPTION
        "The value of tmnxBsxCflowdExpStatHCRecDropped indicates the total
         number of Cflowd flow records dropped. This object is the 64-bit
         version of tmnxBsxCflowdExpStatRecDropped."
    ::= { tmnxBsxCflowdExpStatEntry 5 }

tmnxBsxCflowdExpStatFlowsNoRes   OBJECT-TYPE
    SYNTAX      Counter32
    UNITS       "flows"
    MAX-ACCESS  read-only
    STATUS      current
    DESCRIPTION
        "The value of tmnxBsxCflowdExpStatFlowsNoRes indicates the total number
         of flows that were selected for export but failed to obtain Cflowd
         resources."
    ::= { tmnxBsxCflowdExpStatEntry 6 }

tmnxBsxCflowdExpStatHCFlowsNoRes OBJECT-TYPE
    SYNTAX      Counter64
    UNITS       "flows"
    MAX-ACCESS  read-only
    STATUS      current
    DESCRIPTION
        "The value of tmnxBsxCflowdExpStatHCFlowsNoRes indicates the total
         number of flows that were selected for export but failed to obtain
         Cflowd resources. This object is the 64-bit version of
         tmnxBsxCflowdExpStatFlowsNoRes."
    ::= { tmnxBsxCflowdExpStatEntry 7 }

tmnxBsxCflowdExpStatHCUSupSSRCSt OBJECT-TYPE
    SYNTAX      Counter64
    MAX-ACCESS  read-only
    STATUS      obsolete
    DESCRIPTION
        "The value of tmnxBsxCflowdExpStatHCUSupSSRCSt indicates the number of
         synchronization source (SSRC) records which had to be aborted (due to
         reasons such as unknown codec type, non media stream, codec switch,
         etc).

         This value applies only when the index tmnxBsxCflowdExpType has a
         value of 'rtpPerformance(3)' and is otherwise zero."
    ::= { tmnxBsxCflowdExpStatEntry 8 }

tmnxBsxCflowdExpStatUSupSSRCStLo OBJECT-TYPE
    SYNTAX      Counter32
    MAX-ACCESS  read-only
    STATUS      obsolete
    DESCRIPTION
        "The value of tmnxBsxCflowdExpStatUSupSSRCStLo indicates the lower
         32-bits of tmnxBsxCflowdStatusHCUSupSSRCSt.

         This value applies only when the index tmnxBsxCflowdExpType has a
         value of 'rtpPerformance(3)' and is otherwise zero."
    ::= { tmnxBsxCflowdExpStatEntry 9 }

tmnxBsxCflowdExpStatUSupSSRCStHi OBJECT-TYPE
    SYNTAX      Counter32
    MAX-ACCESS  read-only
    STATUS      obsolete
    DESCRIPTION
        "The value of tmnxBsxCflowdExpStatUSupSSRCStHi indicates the upper
         32-bits of tmnxBsxCflowdStatusHCUSupSSRCSt.

         This value applies only when the index tmnxBsxCflowdExpType has a
         value of 'rtpPerformance(3)' and is otherwise zero."
    ::= { tmnxBsxCflowdExpStatEntry 10 }

tmnxBsxCflowdDirectExpTable      OBJECT-TYPE
    SYNTAX      SEQUENCE OF TmnxBsxCflowdDirectExpEntry
    MAX-ACCESS  not-accessible
    STATUS      current
    DESCRIPTION
        "The tmnxBsxCflowdDirectExpTable contains the Application Assurance
         Cflowd direct export collector configuration within an Application
         Assurance group. Only one entry per group is supported."
    ::= { tmnxBsxCflowdObjs 10 }

tmnxBsxCflowdDirectExpEntry      OBJECT-TYPE
    SYNTAX      TmnxBsxCflowdDirectExpEntry
    MAX-ACCESS  not-accessible
    STATUS      current
    DESCRIPTION
        "Each tmnxBsxCflowdDirectExpEntry specifies an Application Assurance
         Cflowd direct export collector within an Application Assurance group."
    INDEX       {
        tmnxBsxIsaAaGroupIndex,
        tmnxBsxCflowdDirectExpIndex
    }
    ::= { tmnxBsxCflowdDirectExpTable 1 }

TmnxBsxCflowdDirectExpEntry      ::= SEQUENCE
{
    tmnxBsxCflowdDirectExpIndex      Unsigned32,
    tmnxBsxCflowdDirectExpRowStatus  RowStatus,
    tmnxBsxCflowdDirectExpRowLastCh  TimeStamp,
    tmnxBsxCflowdDirectExpDescrption TItemDescription,
    tmnxBsxCflowdDirectExpVersion    Unsigned32
}

tmnxBsxCflowdDirectExpIndex      OBJECT-TYPE
    SYNTAX      Unsigned32 (1..65535)
    MAX-ACCESS  not-accessible
    STATUS      current
    DESCRIPTION
        "The value of tmnxBsxCflowdDirectExpIndex specifies the index
         identifying the Cflowd direct export collector."
    ::= { tmnxBsxCflowdDirectExpEntry 1 }

tmnxBsxCflowdDirectExpRowStatus  OBJECT-TYPE
    SYNTAX      RowStatus
    MAX-ACCESS  read-create
    STATUS      current
    DESCRIPTION
        "The value of tmnxBsxCflowdDirectExpRowStatus specifies the row status.
         Rows in the tmnxBsxCflowdDirectExpTable are created by specifying the
         value of 'createAndGo (4)', and destroyed by specifying the value of
         'destroy (6)'."
    ::= { tmnxBsxCflowdDirectExpEntry 2 }

tmnxBsxCflowdDirectExpRowLastCh  OBJECT-TYPE
    SYNTAX      TimeStamp
    MAX-ACCESS  read-only
    STATUS      current
    DESCRIPTION
        "The value of tmnxBsxCflowdDirectExpRowLastCh indicates the last time,
         since system startup, a successful SNMP set caused a value in this row
         to change."
    ::= { tmnxBsxCflowdDirectExpEntry 3 }

tmnxBsxCflowdDirectExpDescrption OBJECT-TYPE
    SYNTAX      TItemDescription
    MAX-ACCESS  read-create
    STATUS      current
    DESCRIPTION
        "The value of tmnxBsxCflowdDirectExpDescrption specifies the
         description of the Cflowd direct export collector."
    DEFVAL      { "" }
    ::= { tmnxBsxCflowdDirectExpEntry 4 }

tmnxBsxCflowdDirectExpVersion    OBJECT-TYPE
    SYNTAX      Unsigned32 (10)
    MAX-ACCESS  read-create
    STATUS      current
    DESCRIPTION
        "The value of tmnxBsxCflowdDirectExpVersion specifies the version of
         this collector."
    DEFVAL      { 10 }
    ::= { tmnxBsxCflowdDirectExpEntry 5 }

tmnxBsxCflowdDirExpAddrTable     OBJECT-TYPE
    SYNTAX      SEQUENCE OF TmnxBsxCflowdDirExpAddrEntry
    MAX-ACCESS  not-accessible
    STATUS      current
    DESCRIPTION
        "The tmnxBsxCflowdDirExpAddrTable contains the Application Assurance
         Cflowd direct export collector address configuration associated with a
         tmnxBsxCflowdDirectExpEntry. Only two addresses per
         tmnxBsxCflowdDirectExpEntry are supported."
    ::= { tmnxBsxCflowdObjs 11 }

tmnxBsxCflowdDirExpAddrEntry     OBJECT-TYPE
    SYNTAX      TmnxBsxCflowdDirExpAddrEntry
    MAX-ACCESS  not-accessible
    STATUS      current
    DESCRIPTION
        "Each tmnxBsxCflowdDirectExpEntry specifies an Application Assurance
         Cflowd direct export collector address within an Application Assurance
         group."
    INDEX       {
        tmnxBsxIsaAaGroupIndex,
        tmnxBsxCflowdDirectExpIndex,
        tmnxBsxCflowdDirExpAddrType,
        tmnxBsxCflowdDirExpAddrAddress,
        tmnxBsxCflowdDirExpAddrPort
    }
    ::= { tmnxBsxCflowdDirExpAddrTable 1 }

TmnxBsxCflowdDirExpAddrEntry     ::= SEQUENCE
{
    tmnxBsxCflowdDirExpAddrType      InetAddressType,
    tmnxBsxCflowdDirExpAddrAddress   InetAddress,
    tmnxBsxCflowdDirExpAddrPort      TTcpUdpPort,
    tmnxBsxCflowdDirExpAddrRowStatus RowStatus,
    tmnxBsxCflowdDirExpAddrRowLastCh TimeStamp,
    tmnxBsxCflowdDirExpAddrAdmnState TmnxAdminState,
    tmnxBsxCflowdDirExpAddrOperState TmnxOperState
}

tmnxBsxCflowdDirExpAddrType      OBJECT-TYPE
    SYNTAX      InetAddressType
    MAX-ACCESS  not-accessible
    STATUS      current
    DESCRIPTION
        "The value of tmnxBsxCflowdDirExpAddrType specifies the address type of
         the tmnxBsxCflowdDirExpAddrAddress."
    ::= { tmnxBsxCflowdDirExpAddrEntry 1 }

tmnxBsxCflowdDirExpAddrAddress   OBJECT-TYPE
    SYNTAX      InetAddress (SIZE (4|16))
    MAX-ACCESS  not-accessible
    STATUS      current
    DESCRIPTION
        "The value of tmnxBsxCflowdDirExpAddrAddress specifies the address of
         the Cflowd collector to receive direct exported Application Assurance
         Cflowd records. Only IPv4 addresses are supported."
    ::= { tmnxBsxCflowdDirExpAddrEntry 2 }

tmnxBsxCflowdDirExpAddrPort      OBJECT-TYPE
    SYNTAX      TTcpUdpPort (1..65535)
    MAX-ACCESS  not-accessible
    STATUS      current
    DESCRIPTION
        "The value of tmnxBsxCflowdDirExpAddrPort specifies the port number of
         the Cflowd collector to receive direct exported Application Assurance
         Cflowd records."
    ::= { tmnxBsxCflowdDirExpAddrEntry 3 }

tmnxBsxCflowdDirExpAddrRowStatus OBJECT-TYPE
    SYNTAX      RowStatus
    MAX-ACCESS  read-create
    STATUS      current
    DESCRIPTION
        "The value of tmnxBsxCflowdDirExpAddrRowStatus specifies the row
         status. Rows in the tmnxBsxCflowdDirExpAddrTable are created by
         specifying the value of 'createAndGo (4)', and destroyed by specifying
         the value of 'destroy (6)'."
    ::= { tmnxBsxCflowdDirExpAddrEntry 4 }

tmnxBsxCflowdDirExpAddrRowLastCh OBJECT-TYPE
    SYNTAX      TimeStamp
    MAX-ACCESS  read-only
    STATUS      current
    DESCRIPTION
        "The value of tmnxBsxCflowdDirExpAddrRowLastCh indicates the creation
         time of this row."
    ::= { tmnxBsxCflowdDirExpAddrEntry 5 }

tmnxBsxCflowdDirExpAddrAdmnState OBJECT-TYPE
    SYNTAX      TmnxAdminState
    MAX-ACCESS  read-create
    STATUS      current
    DESCRIPTION
        "The value of tmnxBsxCflowdDirExpAddrAdmnState specifies the
         administrative state for the Cflowd direct export collector address.
         When 'outOfService (3)', no Cflowd records are sent to the collector
         address."
    DEFVAL      { outOfService }
    ::= { tmnxBsxCflowdDirExpAddrEntry 6 }

tmnxBsxCflowdDirExpAddrOperState OBJECT-TYPE
    SYNTAX      TmnxOperState
    MAX-ACCESS  read-only
    STATUS      current
    DESCRIPTION
        "The value of tmnxBsxCflowdDirExpAddrOperState indicates the
         operational state for the Cflowd direct export collector address. When
         'outOfService (3)', no Cflowd records are sent to the collector
         address."
    ::= { tmnxBsxCflowdDirExpAddrEntry 7 }

tmnxBsxCflowdDirExpStatTable     OBJECT-TYPE
    SYNTAX      SEQUENCE OF TmnxBsxCflowdDirExpStatEntry
    MAX-ACCESS  not-accessible
    STATUS      current
    DESCRIPTION
        "The tmnxBsxCflowdDirExpStatTable contains statistics on the
         Application Assurance Cflowd direct export collectors within an
         Application Assurance group.

         Rows in this table are automatically created and destroyed when
         collectors are created or destroyed in the
         tmnxBsxCflowdDirExpAddrTable."
    ::= { tmnxBsxCflowdObjs 12 }

tmnxBsxCflowdDirExpStatEntry     OBJECT-TYPE
    SYNTAX      TmnxBsxCflowdDirExpStatEntry
    MAX-ACCESS  not-accessible
    STATUS      current
    DESCRIPTION
        "Each tmnxBsxCflowdDirExpStatEntry contains the statistics for an
         Application Assurance Cflowd direct export collector within an
         Application Assurance group."
    INDEX       {
        tmnxBsxIsaAaGroupIndex,
        tmnxBsxCflowdDirectExpIndex,
        tmnxBsxCflowdDirExpAddrType,
        tmnxBsxCflowdDirExpAddrAddress,
        tmnxBsxCflowdDirExpAddrPort
    }
    ::= { tmnxBsxCflowdDirExpStatTable 1 }

TmnxBsxCflowdDirExpStatEntry     ::= SEQUENCE
{
    tmnxBsxCflowdDirExpStatDscntTime TimeStamp,
    tmnxBsxCflowdDirExpStatRecSent   Counter64
}

tmnxBsxCflowdDirExpStatDscntTime OBJECT-TYPE
    SYNTAX      TimeStamp
    MAX-ACCESS  read-only
    STATUS      current
    DESCRIPTION
        "The value of tmnxBsxCflowdDirExpStatDscntTime indicates discontinuity
         time. This is the SNMPv2-MIB::sysUpTime (centiseconds) when the direct
         export collector last changed status."
    ::= { tmnxBsxCflowdDirExpStatEntry 1 }

tmnxBsxCflowdDirExpStatRecSent   OBJECT-TYPE
    SYNTAX      Counter64
    UNITS       "records"
    MAX-ACCESS  read-only
    STATUS      current
    DESCRIPTION
        "The value of tmnxBsxCflowdDirExpStatRecSent indicates the total number
         of flow records sent to the remote Cflowd direct export collector."
    ::= { tmnxBsxCflowdDirExpStatEntry 2 }

tmnxBsxCflowdDirExportStatTable  OBJECT-TYPE
    SYNTAX      SEQUENCE OF TmnxBsxCflowdDirExportStatEntry
    MAX-ACCESS  not-accessible
    STATUS      current
    DESCRIPTION
        "The tmnxBsxCflowdDirExportStatTable contains operational information
         related to a particular cflowd direct export collector. Each row
         contains the status and statistics information per group, cflowd
         direct export collector for an ISA-AA uniquely identified by the
         tmnxChassisIndex, tmnxBsxCardSlotEsaId, and the tmnxBsxMdaSlotEsaVmId."
    ::= { tmnxBsxCflowdObjs 13 }

tmnxBsxCflowdDirExportStatEntry  OBJECT-TYPE
    SYNTAX      TmnxBsxCflowdDirExportStatEntry
    MAX-ACCESS  not-accessible
    STATUS      current
    DESCRIPTION
        "Each tmnxBsxCflowdDirExportStatEntry represents the statistics for a
         particular AA cflowd direct export collectorURL filter.

         An index with a valid direct export collector (an existing row in
         tmnxBsxCflowdDirExpAddrTable) and tmnxChassisIndex set to one with
         zero value for each of tmnxBsxCardSlotEsaId and tmnxBsxMdaSlotEsaVmId
         will return the summarized statistics.

         Entries will appears in this table only for equipped ISA-AA MDAs
         associated with a particular cflowd direct export collector within an
         AA group."
    INDEX       {
        tmnxBsxIsaAaGroupIndex,
        tmnxBsxCflowdDirectExpIndex,
        tmnxBsxCflowdDirExpAddrType,
        tmnxBsxCflowdDirExpAddrAddress,
        tmnxBsxCflowdDirExpAddrPort,
        tmnxChassisIndex,
        tmnxBsxCardSlotEsaId,
        tmnxBsxMdaSlotEsaVmId
    }
    ::= { tmnxBsxCflowdDirExportStatTable 1 }

TmnxBsxCflowdDirExportStatEntry  ::= SEQUENCE
{
    tmnxBsxCflowdDirExportStatDsTime TimeStamp,
    tmnxBsxCflowdDirExportStatRecSnt Counter64,
    tmnxBsxCflowdDirExportStatOpStat TmnxOperState
}

tmnxBsxCflowdDirExportStatDsTime OBJECT-TYPE
    SYNTAX      TimeStamp
    MAX-ACCESS  read-only
    STATUS      current
    DESCRIPTION
        "The value of tmnxBsxCflowdDirExportStatDsTime indicates discontinuity
         time. This is the SNMPv2-MIB::sysUpTime (centiseconds) when the direct
         export collector last changed status."
    ::= { tmnxBsxCflowdDirExportStatEntry 1 }

tmnxBsxCflowdDirExportStatRecSnt OBJECT-TYPE
    SYNTAX      Counter64
    UNITS       "records"
    MAX-ACCESS  read-only
    STATUS      current
    DESCRIPTION
        "The value of tmnxBsxCflowdDirExportStatRecSnt indicates the total
         number of flow records sent to the remote Cflowd direct export
         collector."
    ::= { tmnxBsxCflowdDirExportStatEntry 2 }

tmnxBsxCflowdDirExportStatOpStat OBJECT-TYPE
    SYNTAX      TmnxOperState
    MAX-ACCESS  read-only
    STATUS      current
    DESCRIPTION
        "The value of tmnxBsxCflowdDirExportStatOpStat indicates the
         operational state of the direct export collector as on this ISA-AA."
    ::= { tmnxBsxCflowdDirExportStatEntry 3 }

tmnxBsxOvrdObjs                  OBJECT IDENTIFIER ::= { tmnxBsxObjs 6 }

tmnxBsxOvrdScalars               OBJECT IDENTIFIER ::= { tmnxBsxOvrdObjs 1 }

tmnxBsxOvrdAaSubLastChTime       OBJECT-TYPE
    SYNTAX      TimeStamp
    MAX-ACCESS  read-only
    STATUS      current
    DESCRIPTION
        "The value of tmnxBsxOvrdAaSubLastChTime indicates the last time a
         successful set was performed on the tmnxBsxOvrdAaSubTable."
    ::= { tmnxBsxOvrdScalars 1 }

tmnxBsxOvrdAaSubCharLastChTm     OBJECT-TYPE
    SYNTAX      TimeStamp
    MAX-ACCESS  read-only
    STATUS      current
    DESCRIPTION
        "The value of tmnxBsxOvrdAaSubCharLastChTm indicates the last time a
         successful set was performed on the tmnxBsxOvrdAaSubCharTable."
    ::= { tmnxBsxOvrdScalars 2 }

tmnxBsxOvrdAaSubTable            OBJECT-TYPE
    SYNTAX      SEQUENCE OF TmnxBsxOvrdAaSubEntry
    MAX-ACCESS  not-accessible
    STATUS      current
    DESCRIPTION
        "The tmnxBsxOvrdAaSubTable specifies overrides of Application Assurance
         subscriber policy.

         Each row specifies an override of policy configuration for an
         Application Assurance subscriber. A subscriber is uniquely identified
         by a tmnxBsxAaSubscriberType and tmnxBsxAaSubscriber."
    ::= { tmnxBsxOvrdObjs 2 }

tmnxBsxOvrdAaSubEntry            OBJECT-TYPE
    SYNTAX      TmnxBsxOvrdAaSubEntry
    MAX-ACCESS  not-accessible
    STATUS      current
    DESCRIPTION
        "Each tmnxBsxOvrdAaSubEntry specifies an override of policy
         configuration for an Application Assurance subscriber."
    INDEX       {
        tmnxBsxAaGrpPartIndex,
        tmnxBsxAaSubscriberType,
        tmnxBsxAaSubscriber
    }
    ::= { tmnxBsxOvrdAaSubTable 1 }

TmnxBsxOvrdAaSubEntry            ::= SEQUENCE
{
    tmnxBsxOvrdAaSubRowStatus        RowStatus,
    tmnxBsxOvrdAaSubRowLastCh        TimeStamp
}

tmnxBsxOvrdAaSubRowStatus        OBJECT-TYPE
    SYNTAX      RowStatus
    MAX-ACCESS  read-create
    STATUS      current
    DESCRIPTION
        "The value of tmnxBsxOvrdAaSubRowStatus specifies the row status. It
         allows entries to be created and deleted in the tmnxBsxOvrdAaSubTable.

         Rows are created by specifying the value of 'createAndGo (4)', and
         deleted by specifying the value of 'destroy (6)'."
    ::= { tmnxBsxOvrdAaSubEntry 1 }

tmnxBsxOvrdAaSubRowLastCh        OBJECT-TYPE
    SYNTAX      TimeStamp
    MAX-ACCESS  read-only
    STATUS      current
    DESCRIPTION
        "The value of tmnxBsxOvrdAaSubRowLastCh indicates the last time a
         successful set was performed on this row of the tmnxBsxOvrdAaSubTable."
    ::= { tmnxBsxOvrdAaSubEntry 2 }

tmnxBsxOvrdAaSubCharTable        OBJECT-TYPE
    SYNTAX      SEQUENCE OF TmnxBsxOvrdAaSubCharEntry
    MAX-ACCESS  not-accessible
    STATUS      current
    DESCRIPTION
        "The tmnxBsxOvrdAaSubCharTable specifies overrides of application
         profile characteristics for Application Assurance subscribers.

         Each row specifies an override of an application profile
         characteristic for an Application Assurance subscriber. A subscriber
         is uniquely identified by a tmnxBsxAaSubscriberType and
         tmnxBsxAaSubscriber."
    ::= { tmnxBsxOvrdObjs 3 }

tmnxBsxOvrdAaSubCharEntry        OBJECT-TYPE
    SYNTAX      TmnxBsxOvrdAaSubCharEntry
    MAX-ACCESS  not-accessible
    STATUS      current
    DESCRIPTION
        "Each tmnxBsxOvrdAaSubCharEntry specifies an override of an application
         profile characteristic for an Application Assurance subscriber."
    INDEX       {
        tmnxBsxAaGrpPartIndex,
        tmnxBsxAaSubscriberType,
        tmnxBsxAaSubscriber,
        IMPLIED tmnxBsxAsoCharName
    }
    ::= { tmnxBsxOvrdAaSubCharTable 1 }

TmnxBsxOvrdAaSubCharEntry        ::= SEQUENCE
{
    tmnxBsxOvrdAaSubCharRowStatus    RowStatus,
    tmnxBsxOvrdAaSubCharRowLastCh    TimeStamp,
    tmnxBsxOvrdAaSubCharValName      TNamedItem
}

tmnxBsxOvrdAaSubCharRowStatus    OBJECT-TYPE
    SYNTAX      RowStatus
    MAX-ACCESS  read-create
    STATUS      current
    DESCRIPTION
        "The value of tmnxBsxOvrdAaSubCharRowStatus specifies the row status.
         It allows entries to be created and deleted in the
         tmnxBsxOvrdAaSubCharTable.

         Rows are created by specifying the value of 'createAndGo (4)', and
         deleted by specifying the value of 'destroy (6)'."
    ::= { tmnxBsxOvrdAaSubCharEntry 1 }

tmnxBsxOvrdAaSubCharRowLastCh    OBJECT-TYPE
    SYNTAX      TimeStamp
    MAX-ACCESS  read-only
    STATUS      current
    DESCRIPTION
        "The value of tmnxBsxOvrdAaSubCharRowLastCh indicates the last time a
         successful set was performed on this row of the
         tmnxBsxOvrdAaSubCharTable."
    ::= { tmnxBsxOvrdAaSubCharEntry 2 }

tmnxBsxOvrdAaSubCharValName      OBJECT-TYPE
    SYNTAX      TNamedItem
    MAX-ACCESS  read-create
    STATUS      current
    DESCRIPTION
        "The value of tmnxBsxOvrdAaSubCharValName specifies the override
         characteristic value for the application profile characteristic used
         by the Application assurance subscriber."
    ::= { tmnxBsxOvrdAaSubCharEntry 3 }

tmnxBsxTransitObjs               OBJECT IDENTIFIER ::= { tmnxBsxObjs 7 }

tmnxBsxTransitScalars            OBJECT IDENTIFIER ::= { tmnxBsxTransitObjs 1 }

tmnxBsxTransitIpPolicyLastChTime OBJECT-TYPE
    SYNTAX      TimeStamp
    MAX-ACCESS  read-only
    STATUS      current
    DESCRIPTION
        "The value of tmnxBsxTransitIpPolicyLastChTime indicates the last time,
         since system startup, a successful set was performed on the
         tmnxBsxTransitIpPolicyTable."
    ::= { tmnxBsxTransitScalars 1 }

tmnxBsxTransIpPlcySubLastChTime  OBJECT-TYPE
    SYNTAX      TimeStamp
    MAX-ACCESS  read-only
    STATUS      current
    DESCRIPTION
        "The value of tmnxBsxTransIpPlcySubLastChTime indicates the last time,
         since system startup, a successful set was performed on the
         tmnxBsxTransitIpPolicySubTable."
    ::= { tmnxBsxTransitScalars 2 }

tmnxBsxTransIpPlcyAddrLastChTime OBJECT-TYPE
    SYNTAX      TimeStamp
    MAX-ACCESS  read-only
    STATUS      current
    DESCRIPTION
        "The value of tmnxBsxTransIpPlcyAddrLastChTime indicates the last time,
         since system startup, a successful set was performed on the
         tmnxBsxTransitIpPolicyAddrTable."
    ::= { tmnxBsxTransitScalars 3 }

tmnxBsxTransPrefPlcyLastChTime   OBJECT-TYPE
    SYNTAX      TimeStamp
    MAX-ACCESS  read-only
    STATUS      current
    DESCRIPTION
        "The value of tmnxBsxTransPrefPlcyLastChTime indicates the last time,
         since system startup, a successful set was performed on the
         tmnxBsxTransPrefPolicyTable."
    ::= { tmnxBsxTransitScalars 4 }

tmnxBsxTransPrefSubLastChTime    OBJECT-TYPE
    SYNTAX      TimeStamp
    MAX-ACCESS  read-only
    STATUS      current
    DESCRIPTION
        "The value of tmnxBsxTransPrefSubLastChTime indicates the last time,
         since system startup, a successful set was performed on the
         tmnxBsxTransPrefSubTable."
    ::= { tmnxBsxTransitScalars 5 }

tmnxBsxTransPrefEntryLastChTime  OBJECT-TYPE
    SYNTAX      TimeStamp
    MAX-ACCESS  read-only
    STATUS      current
    DESCRIPTION
        "The value of tmnxBsxTransPrefEntryLastChTime indicates the last time,
         since system startup, a successful set was performed on the
         tmnxBsxTransPrefTable."
    ::= { tmnxBsxTransitScalars 6 }

tmnxBsxTransitIpPolicyTable      OBJECT-TYPE
    SYNTAX      SEQUENCE OF TmnxBsxTransitIpPolicyEntry
    MAX-ACCESS  not-accessible
    STATUS      current
    DESCRIPTION
        "The tmnxBsxTransitIpPolicyTable contains an entry for each transit IP
         policy. These policies are used in cases when there is no system/IOM
         subscriber context such as in-line deployments of AA where the traffic
         from the AA subscriber is transitioning through the SR."
    ::= { tmnxBsxTransitObjs 2 }

tmnxBsxTransitIpPolicyEntry      OBJECT-TYPE
    SYNTAX      TmnxBsxTransitIpPolicyEntry
    MAX-ACCESS  not-accessible
    STATUS      current
    DESCRIPTION
        "Each tmnxBsxTransitIpPolicyEntry contains transit IP policy specific
         configuration."
    INDEX       {
        tmnxBsxAaGrpPartIndex,
        tmnxBsxTransitIpPolicyId
    }
    ::= { tmnxBsxTransitIpPolicyTable 1 }

TmnxBsxTransitIpPolicyEntry      ::= SEQUENCE
{
    tmnxBsxTransitIpPolicyId         TmnxBsxTransitIpPolicyId,
    tmnxBsxTransitIpPolicyRowStatus  RowStatus,
    tmnxBsxTransitIpPolicyRowLastCh  TimeStamp,
    tmnxBsxTransitIpPolicyDesc       TItemDescription,
    tmnxBsxTransitIpPolicyDefAppProf TNamedItemOrEmpty,
    tmnxBsxTransitIpPolicySubIdPlcy  TNamedItemOrEmpty,
    tmnxBsxTransitIpPolicyRadius     TmnxEnabledDisabled,
    tmnxBsxTransitIpPolicyRadAuthPlc TNamedItemOrEmpty,
    tmnxBsxTransitIpPolicyDhcp       TmnxEnabledDisabled,
    tmnxBsxTransitIpPolicyIPv6PfxLen InetAddressPrefixLength,
    tmnxBsxTransitIpPolicySubsCount  Counter32,
    tmnxBsxTransitIpPolicyIPv4EntCnt Counter32,
    tmnxBsxTransitIpPolicyIPv6EntCnt Counter32,
    tmnxBsxTransitIpPolicySeenIp     TmnxEnabledDisabled,
    tmnxBsxTransitIpPolicyAutoCreate TmnxEnabledDisabled,
    tmnxBsxTransitIpPolicySeenIpRad  TNamedItemOrEmpty,
    tmnxBsxTransitIpPolicyDiameter   TmnxEnabledDisabled,
    tmnxBsxTransitIpPolicyDiamAppPlc TNamedItemOrEmpty,
    tmnxBsxTransitIpPolicyAutoInact  TmnxEnabledDisabled
}

tmnxBsxTransitIpPolicyId         OBJECT-TYPE
    SYNTAX      TmnxBsxTransitIpPolicyId
    MAX-ACCESS  not-accessible
    STATUS      current
    DESCRIPTION
        "The value of tmnxBsxTransitIpPolicyId specifies, along with
         tmnxBsxAaGrpPartIndex, the index to a specific transit IP
         policy.  tmnxBsxTransitIpPolicyId is system unique across all
         group-partitions."
    ::= { tmnxBsxTransitIpPolicyEntry 1 }

tmnxBsxTransitIpPolicyRowStatus  OBJECT-TYPE
    SYNTAX      RowStatus
    MAX-ACCESS  read-create
    STATUS      current
    DESCRIPTION
        "The value of tmnxBsxTransitIpPolicyRowStatus specifies the row status.
         It allows entries to be created and deleted in the
         tmnxBsxTransitIpPolicyTable.

         Rows are created by specifying the value of 'createAndGo (4)', and
         deleted by specifying the value of 'destroy (6)'.

         To delete an entry, all references to this policy by
         TIMETRA-SAP-MIB::sapTransitIpPolicyId in the
         TIMETRA-SAP-MIB::sapBaseInfoTable or by
         TIMETRA-SDP-MIB::sdpBindTransitIpPolicyId in the
         TIMETRA-SDP-MIB::sdpBindTable must be deleted.

         The deletion of a row of this table implicitly deletes all the
         corresponding entries in the tmnxBsxTransitIpPolicySubTable and the
         tmnxBsxTransitIpPolicyAddrTable that are indexed on
         tmnxBsxTransitIpPolicyId."
    ::= { tmnxBsxTransitIpPolicyEntry 2 }

tmnxBsxTransitIpPolicyRowLastCh  OBJECT-TYPE
    SYNTAX      TimeStamp
    MAX-ACCESS  read-only
    STATUS      current
    DESCRIPTION
        "The value of tmnxBsxTransitIpPolicyRowLastCh indicates the last time,
         since system startup, a successful set was performed on this row of
         the tmnxBsxTransitIpPolicyTable."
    ::= { tmnxBsxTransitIpPolicyEntry 3 }

tmnxBsxTransitIpPolicyDesc       OBJECT-TYPE
    SYNTAX      TItemDescription
    MAX-ACCESS  read-create
    STATUS      current
    DESCRIPTION
        "The value of tmnxBsxTransitIpPolicyDesc specifies a user-provided
         description for this transit IP policy."
    DEFVAL      { "" }
    ::= { tmnxBsxTransitIpPolicyEntry 4 }

tmnxBsxTransitIpPolicyDefAppProf OBJECT-TYPE
    SYNTAX      TNamedItemOrEmpty
    MAX-ACCESS  read-create
    STATUS      current
    DESCRIPTION
        "The value of tmnxBsxTransitIpPolicyDefAppProf specifies the name of
         the default application profile to be applied to a dynamically learned
         AA transit subscriber."
    DEFVAL      { "" }
    ::= { tmnxBsxTransitIpPolicyEntry 5 }

tmnxBsxTransitIpPolicySubIdPlcy  OBJECT-TYPE
    SYNTAX      TNamedItemOrEmpty
    MAX-ACCESS  read-create
    STATUS      current
    DESCRIPTION
        "The value of tmnxBsxTransitIpPolicySubIdPlcy specifies the subscriber
         identification policy for this transit IP policy as defined in
         tmnxSubIdentPolicyTable in the TIMETRA-SUBSCRIBER-MGMT-MIB.

         The corresponding tmnxSubIPolName must exist in the
         tmnxSubIdentPolicyTable."
    DEFVAL      { "" }
    ::= { tmnxBsxTransitIpPolicyEntry 6 }

tmnxBsxTransitIpPolicyRadius     OBJECT-TYPE
    SYNTAX      TmnxEnabledDisabled
    MAX-ACCESS  read-create
    STATUS      current
    DESCRIPTION
        "The value of tmnxBsxTransitIpPolicyRadius specifies whether transit
         subscribers are dynamically learned via RADIUS.

         The use of RADIUS to learn transit subscribers is mutually exclusive
         with the use of DHCP, Auto Create, and Diameter for this purpose."
    DEFVAL      { disabled }
    ::= { tmnxBsxTransitIpPolicyEntry 7 }

tmnxBsxTransitIpPolicyRadAuthPlc OBJECT-TYPE
    SYNTAX      TNamedItemOrEmpty
    MAX-ACCESS  read-create
    STATUS      current
    DESCRIPTION
        "The value of tmnxBsxTransitIpPolicyRadAuthPlc specifies the RADIUS
         authentication policy to be used.

         The specified tmnxBsxTransitIpPolicyRadAuthPlc is not required to
         exist in the tmnxSubAuthPlcyTable in the TIMETRA-SUBSCRIBER-MGMT-MIB."
    DEFVAL      { "" }
    ::= { tmnxBsxTransitIpPolicyEntry 8 }

tmnxBsxTransitIpPolicyDhcp       OBJECT-TYPE
    SYNTAX      TmnxEnabledDisabled
    MAX-ACCESS  read-create
    STATUS      current
    DESCRIPTION
        "The value of tmnxBsxTransitIpPolicyDhcp specifies whether transit
         subscribers are dynamically learned via DHCP.

         The use of DHCP to learn transit subscribers is mutually exclusive
         with the use of RADIUS, Auto Create, and Diameter for this purpose."
    DEFVAL      { disabled }
    ::= { tmnxBsxTransitIpPolicyEntry 9 }

tmnxBsxTransitIpPolicyIPv6PfxLen OBJECT-TYPE
    SYNTAX      InetAddressPrefixLength (0..128)
    MAX-ACCESS  read-create
    STATUS      current
    DESCRIPTION
        "The value of tmnxBsxTransitIpPolicyIPv6PfxLen specifies the prefix
         length of IPv6 addresses in this policy for both static and dynamic
         transits.

         tmnxBsxTransitIpPolicyIPv6PfxLen can only be changed while no static
         IPv6 subscribers exist. If dynamic IPv6 addresses exist, they will be
         flushed."
    DEFVAL      { 0 }
    ::= { tmnxBsxTransitIpPolicyEntry 10 }

tmnxBsxTransitIpPolicySubsCount  OBJECT-TYPE
    SYNTAX      Counter32
    MAX-ACCESS  read-only
    STATUS      current
    DESCRIPTION
        "The value of tmnxBsxTransitIpPolicySubsCount indicates the total
         number of subscribers within this transit IP policy.

         The value of tmnxBsxTransitIpPolicySubsCount is the number of rows in
         the table tmnxBsxTransitIpPolicySubTable with matching
         tmnxBsxAaGrpPartIndex and tmnxBsxTransitIpPolicyId indices."
    ::= { tmnxBsxTransitIpPolicyEntry 11 }

tmnxBsxTransitIpPolicyIPv4EntCnt OBJECT-TYPE
    SYNTAX      Counter32
    MAX-ACCESS  read-only
    STATUS      current
    DESCRIPTION
        "The value of tmnxBsxTransitIpPolicyIPv4EntCnt indicates the total
         number of IPv4 address entries within this transit IP policy.

         The value of tmnxBsxTransitIpPolicyIPv4EntCnt is the number of rows in
         the table tmnxBsxTransitIpPolicyAddrTable with matching
         tmnxBsxAaGrpPartIndex and tmnxBsxTransitIpPolicyId indices when
         tmnxBsxTransitIpPolicyAddrType indicates an IPv4 address type."
    ::= { tmnxBsxTransitIpPolicyEntry 12 }

tmnxBsxTransitIpPolicyIPv6EntCnt OBJECT-TYPE
    SYNTAX      Counter32
    MAX-ACCESS  read-only
    STATUS      current
    DESCRIPTION
        "The value of tmnxBsxTransitIpPolicyIPv6EntCnt indicates the total
         number of IPv6 address entries within this transit IP policy.

         The value of tmnxBsxTransitIpPolicyIPv6EntCnt is the number of rows in
         the table tmnxBsxTransitIpPolicyAddrTable with matching
         tmnxBsxAaGrpPartIndex and tmnxBsxTransitIpPolicyId indices when
         tmnxBsxTransitIpPolicyAddrType indicates an IPv6 address type."
    ::= { tmnxBsxTransitIpPolicyEntry 13 }

tmnxBsxTransitIpPolicySeenIp     OBJECT-TYPE
    SYNTAX      TmnxEnabledDisabled
    MAX-ACCESS  read-create
    STATUS      current
    DESCRIPTION
        "The value of tmnxBsxTransitIpPolicySeenIp specifies whether or not to
         initiate dynamic transit subscriber creation when traffic is detected
         on a parent SAP or Spoke SDP.

         When tmnxBsxTransitIpPolicySeenIp and tmnxBsxTransitIpPolicyRadius
         are both enabled a RADIUS Access Request message is sent to the RADIUS
         server.  The RADIUS server must respond with a transit subscriber
         create message.

         When tmnxBsxTransitIpPolicySeenIp and tmnxBsxTransitIpPolicyAutoCreate
         are both enabled a transit subscriber will be dynamically created for
         each IP address without a policy server.

         The use of Seen IP to learn transit subscribers is mutually exclusive
         with the use of DHCP for this purpose."
    DEFVAL      { disabled }
    ::= { tmnxBsxTransitIpPolicyEntry 14 }

tmnxBsxTransitIpPolicyAutoCreate OBJECT-TYPE
    SYNTAX      TmnxEnabledDisabled
    MAX-ACCESS  read-create
    STATUS      current
    DESCRIPTION
        "The value of tmnxBsxTransitIpPolicyAutoCreate specifies whether
         transit subscribers are automatically created for each IP address
         without a policy server.

         Auto creation is only possible when a default application profile
         (tmnxBsxTransitIpPolicyDefAppProf) has been defined.

         The use of auto creation of transit subscribers is mutually exclusive
         with the use of DHCP, RADIUS, and Diameter for this purpose."
    DEFVAL      { disabled }
    ::= { tmnxBsxTransitIpPolicyEntry 15 }

tmnxBsxTransitIpPolicySeenIpRad  OBJECT-TYPE
    SYNTAX      TNamedItemOrEmpty
    MAX-ACCESS  read-create
    STATUS      current
    DESCRIPTION
        "The value of tmnxBsxTransitIpPolicySeenIpRad specifies the RADIUS
         accounting policy used to initiate dynamic transit subscriber
         creation.

         The accounting policy must be an existing row within the
         tmnxBsxRadApTable specified by the index tmnxBsxRadApName."
    DEFVAL      { "" }
    ::= { tmnxBsxTransitIpPolicyEntry 16 }

tmnxBsxTransitIpPolicyDiameter   OBJECT-TYPE
    SYNTAX      TmnxEnabledDisabled
    MAX-ACCESS  read-create
    STATUS      current
    DESCRIPTION
        "The value of tmnxBsxTransitIpPolicyDiameter specifies whether transit
         subscribers are dynamically learned via Diameter.

         When tmnxBsxTransitIpPolicySeenIp and tmnxBsxTransitIpPolicyDiameter
         are both enabled, a diameter session with the policy server will be
         created for each Seen IP address (IPCAN session). Upon successful
         session creation, a transit subscriber will be dynamically created
         with the PCC (Policy and Charging Control) rules from the policy
         server.

         The use of Diameter to learn transit subscribers is mutually exclusive
         with the use of DHCP, Auto Create, and RADIUS for this purpose."
    DEFVAL      { disabled }
    ::= { tmnxBsxTransitIpPolicyEntry 17 }

tmnxBsxTransitIpPolicyDiamAppPlc OBJECT-TYPE
    SYNTAX      TNamedItemOrEmpty
    MAX-ACCESS  read-create
    STATUS      current
    DESCRIPTION
        "The value of tmnxBsxTransitIpPolicyDiamAppPlc specifies the Diameter
         application policy to be used, as defined in
         TIMETRA-DIAMETER-MIB::tmnxDiamAppPlcyId. The application policy must
         have with TIMETRA-DIAMETER-MIB::tmnxDiamAppPlcyApplication set to 'gx
         (1)'."
    DEFVAL      { "" }
    ::= { tmnxBsxTransitIpPolicyEntry 18 }

tmnxBsxTransitIpPolicyAutoInact  OBJECT-TYPE
    SYNTAX      TmnxEnabledDisabled
    MAX-ACCESS  read-create
    STATUS      current
    DESCRIPTION
        "The value of tmnxBsxTransitIpPolicyAutoInact specifies whether transit
         subscribers will be monitored for inactivity. When
         tmnxBsxTransitIpPolicySeenIp, tmnxBsxTransitIpPolicyAutoCreate and
         tmnxBsxTransitIpPolicyAutoInact are set, auto-created transit
         subscribers will be monitored for inactivity and inactive subscribers
         will be removed. To change this object,
         tmnxBsxTransitIpPolicyAutoCreate must be disabled."
    DEFVAL      { disabled }
    ::= { tmnxBsxTransitIpPolicyEntry 19 }

tmnxBsxTransitIpPolicySubTable   OBJECT-TYPE
    SYNTAX      SEQUENCE OF TmnxBsxTransitIpPolicySubEntry
    MAX-ACCESS  not-accessible
    STATUS      current
    DESCRIPTION
        "The tmnxBsxTransitIpPolicySubTable contains the configuration of
         transit subscribers within a transit IP policy."
    ::= { tmnxBsxTransitObjs 3 }

tmnxBsxTransitIpPolicySubEntry   OBJECT-TYPE
    SYNTAX      TmnxBsxTransitIpPolicySubEntry
    MAX-ACCESS  not-accessible
    STATUS      current
    DESCRIPTION
        "Each tmnxBsxTransitIpPolicySubEntry contains information for an
         individual transit subscriber."
    INDEX       {
        tmnxBsxAaGrpPartIndex,
        tmnxBsxTransitIpPolicyId,
        tmnxBsxTransitIpPolicySubscriber
    }
    ::= { tmnxBsxTransitIpPolicySubTable 1 }

TmnxBsxTransitIpPolicySubEntry   ::= SEQUENCE
{
    tmnxBsxTransitIpPolicySubscriber TNamedItem,
    tmnxBsxTransIpPlcySubRowStatus   RowStatus,
    tmnxBsxTransIpPlcySubRowLastCh   TimeStamp,
    tmnxBsxTransIpPlcySubAppProfNm   TNamedItem,
    tmnxBsxTransIpPlcySubRefCount    Unsigned32
}

tmnxBsxTransitIpPolicySubscriber OBJECT-TYPE
    SYNTAX      TNamedItem
    MAX-ACCESS  not-accessible
    STATUS      current
    DESCRIPTION
        "The value of tmnxBsxTransitIpPolicySubscriber specifies the name of
         the Transit AA subscriber."
    ::= { tmnxBsxTransitIpPolicySubEntry 1 }

tmnxBsxTransIpPlcySubRowStatus   OBJECT-TYPE
    SYNTAX      RowStatus
    MAX-ACCESS  read-create
    STATUS      current
    DESCRIPTION
        "The value of tmnxBsxTransIpPlcySubRowStatus specifies the row status.
         It allows entries to be created and deleted in the
         tmnxBsxTransitIpPolicySubTable.

         Rows are created by specifying the value of 'createAndGo (4)', and
         deleted by specifying the value of 'destroy (6)'.

         A row of this table cannot be created unless a valid
         tmnxBsxTransIpPlcySubAppProfNm is also specified.

         The deletion of a row in this table implicitly deletes the
         corresponding entries in the tmnxBsxTransitIpPolicyAddrTable that
         reference the subscriber specified by
         tmnxBsxTransitIpPolicySubscriber."
    ::= { tmnxBsxTransitIpPolicySubEntry 2 }

tmnxBsxTransIpPlcySubRowLastCh   OBJECT-TYPE
    SYNTAX      TimeStamp
    MAX-ACCESS  read-only
    STATUS      current
    DESCRIPTION
        "The value of tmnxBsxTransIpPlcySubRowLastCh indicates the last time,
         since system startup, a successful set was performed on this row of
         the tmnxBsxTransitIpPolicySubTable."
    ::= { tmnxBsxTransitIpPolicySubEntry 3 }

tmnxBsxTransIpPlcySubAppProfNm   OBJECT-TYPE
    SYNTAX      TNamedItem
    MAX-ACCESS  read-create
    STATUS      current
    DESCRIPTION
        "The value of tmnxBsxTransIpPlcySubAppProfNm specifies the name of the
         application profile to be applied to the AA transit subscriber.

         The value of tmnxBsxTransIpPlcySubAppProfNm must be a valid
         app-profile that exists in the group/partition identified by
         tmnxBsxAaGrpPartIndex that is an index of this row entry.
         tmnxBsxTransIpPlcySubAppProfNm must be present in the same SNMP PDU as
         the row creation, otherwise the creation will fail."
    ::= { tmnxBsxTransitIpPolicySubEntry 4 }

tmnxBsxTransIpPlcySubRefCount    OBJECT-TYPE
    SYNTAX      Unsigned32
    MAX-ACCESS  read-only
    STATUS      current
    DESCRIPTION
        "The value of tmnxBsxTransIpPlcySubRefCount specifies the number of
         references in the tmnxBsxTransitIpPolicyAddrTable to the AA transit
         subscriber identified in this row."
    DEFVAL      { 0 }
    ::= { tmnxBsxTransitIpPolicySubEntry 5 }

tmnxBsxTransitIpPolicyAddrTable  OBJECT-TYPE
    SYNTAX      SEQUENCE OF TmnxBsxTransitIpPolicyAddrEntry
    MAX-ACCESS  not-accessible
    STATUS      current
    DESCRIPTION
        "The tmnxBsxTransitIpPolicyAddrTable contains IP addresses for the
         transit IP policies."
    ::= { tmnxBsxTransitObjs 4 }

tmnxBsxTransitIpPolicyAddrEntry  OBJECT-TYPE
    SYNTAX      TmnxBsxTransitIpPolicyAddrEntry
    MAX-ACCESS  not-accessible
    STATUS      current
    DESCRIPTION
        "Each tmnxBsxTransitIpPolicyAddrEntry contains an individual address
         associated with a transit AA subscriber."
    INDEX       {
        tmnxBsxAaGrpPartIndex,
        tmnxBsxTransitIpPolicyId,
        tmnxBsxTransitIpPolicyAddrType,
        tmnxBsxTransitIpPolicyAddr
    }
    ::= { tmnxBsxTransitIpPolicyAddrTable 1 }

TmnxBsxTransitIpPolicyAddrEntry  ::= SEQUENCE
{
    tmnxBsxTransitIpPolicyAddrType   InetAddressType,
    tmnxBsxTransitIpPolicyAddr       InetAddress,
    tmnxBsxTransIpPlcyAddrRowStatus  RowStatus,
    tmnxBsxTransIpPlcyAddrRowLastCh  TimeStamp,
    tmnxBsxTransIpPlcyAddrSubscriber TNamedItem
}

tmnxBsxTransitIpPolicyAddrType   OBJECT-TYPE
    SYNTAX      InetAddressType
    MAX-ACCESS  not-accessible
    STATUS      current
    DESCRIPTION
        "The value of tmnxBsxTransitIpPolicyAddrType specifies the type of the
         address."
    ::= { tmnxBsxTransitIpPolicyAddrEntry 1 }

tmnxBsxTransitIpPolicyAddr       OBJECT-TYPE
    SYNTAX      InetAddress (SIZE (0|4|16))
    MAX-ACCESS  not-accessible
    STATUS      current
    DESCRIPTION
        "The value of tmnxBsxTransitIpPolicyAddr specifies the the address
         associated with the transit AA subscriber.

         Addresses of type 'unknown(0)' maybe of zero-length."
    ::= { tmnxBsxTransitIpPolicyAddrEntry 2 }

tmnxBsxTransIpPlcyAddrRowStatus  OBJECT-TYPE
    SYNTAX      RowStatus
    MAX-ACCESS  read-create
    STATUS      current
    DESCRIPTION
        "The value of tmnxBsxTransIpPlcyAddrRowStatus specifies the row status.
         It allows entries to be created and deleted in the
         tmnxBsxTransitIpPolicyAddrTable.

         Rows are created by specifying the value of 'createAndGo (4)', and
         deleted by specifying the value of 'destroy (6)'

         When creating a row, the tmnxBsxTransIpPlcyAddrSubscriber must be
         specified in the same SNMP PDU."
    ::= { tmnxBsxTransitIpPolicyAddrEntry 3 }

tmnxBsxTransIpPlcyAddrRowLastCh  OBJECT-TYPE
    SYNTAX      TimeStamp
    MAX-ACCESS  read-only
    STATUS      current
    DESCRIPTION
        "The value of tmnxBsxTransIpPlcyAddrRowLastCh indicates the last time,
         since system startup, a successful set was performed on this row of
         the tmnxBsxTransitIpPolicyAddrTable."
    ::= { tmnxBsxTransitIpPolicyAddrEntry 4 }

tmnxBsxTransIpPlcyAddrSubscriber OBJECT-TYPE
    SYNTAX      TNamedItem
    MAX-ACCESS  read-create
    STATUS      current
    DESCRIPTION
        "The value of tmnxBsxTransIpPlcyAddrSubscriber specifies the name of
         the Transit AA subscriber associated with the address identified by
         this row of the tmnxBsxTransitIpPolicyAddrTable.

         The value of tmnxBsxTransIpPlcyAddrSubscriber must exist in the
         tmnxBsxTransitIpPolicySubTable and cannot be changed after the
         creation of the row entry. tmnxBsxTransIpPlcyAddrSubscriber must be
         present in the same SNMP PDU as the row creation, otherwise the
         creation will fail."
    ::= { tmnxBsxTransitIpPolicyAddrEntry 5 }

tmnxBsxTransitIpSumTable         OBJECT-TYPE
    SYNTAX      SEQUENCE OF TmnxBsxTransitIpSumEntry
    MAX-ACCESS  not-accessible
    STATUS      current
    DESCRIPTION
        "The tmnxBsxTransitIpSumTable contains summary information for all
         transit subscribers including dynamically created subscribers."
    ::= { tmnxBsxTransitObjs 5 }

tmnxBsxTransitIpSumEntry         OBJECT-TYPE
    SYNTAX      TmnxBsxTransitIpSumEntry
    MAX-ACCESS  not-accessible
    STATUS      current
    DESCRIPTION
        "Each tmnxBsxTransitIpSumEntry contains summary information for a
         transit subscriber."
    INDEX       {
        tmnxBsxAaGrpPartIndex,
        tmnxBsxTransitIpPolicyId,
        tmnxBsxTransitIpPolicySubscriber,
        tmnxBsxTransitIpPolicyAddrType,
        tmnxBsxTransitIpPolicyAddr
    }
    ::= { tmnxBsxTransitIpSumTable 1 }

TmnxBsxTransitIpSumEntry         ::= SEQUENCE
{
    tmnxBsxTransitIpSumUpdateTime    TimeStamp,
    tmnxBsxTransitIpSumParentSubType TmnxBsxAaSubscriberType,
    tmnxBsxTransitIpSumParentSub     TmnxBsxAaSubscriber,
    tmnxBsxTransitIpSumAppProfNm     TNamedItem,
    tmnxBsxTransitIpSumIpOriginMask  TmnxBsxTransitSubOrigin
}

tmnxBsxTransitIpSumUpdateTime    OBJECT-TYPE
    SYNTAX      TimeStamp
    MAX-ACCESS  read-only
    STATUS      current
    DESCRIPTION
        "The value of tmnxBsxTransitIpSumUpdateTime indicates the last time,
         since system startup, the contents of a row of the
         tmnxBsxTransitIpSumTable was updated."
    ::= { tmnxBsxTransitIpSumEntry 1 }

tmnxBsxTransitIpSumParentSubType OBJECT-TYPE
    SYNTAX      TmnxBsxAaSubscriberType
    MAX-ACCESS  read-only
    STATUS      current
    DESCRIPTION
        "The value of tmnxBsxTransitIpSumParentSubType indicates the type of
         the parent of the subscriber."
    ::= { tmnxBsxTransitIpSumEntry 2 }

tmnxBsxTransitIpSumParentSub     OBJECT-TYPE
    SYNTAX      TmnxBsxAaSubscriber
    MAX-ACCESS  read-only
    STATUS      current
    DESCRIPTION
        "The value of tmnxBsxTransitIpSumParentSub indicates the parent of the
         subscriber."
    ::= { tmnxBsxTransitIpSumEntry 3 }

tmnxBsxTransitIpSumAppProfNm     OBJECT-TYPE
    SYNTAX      TNamedItem
    MAX-ACCESS  read-only
    STATUS      current
    DESCRIPTION
        "The value of tmnxBsxTransitIpSumAppProfNm indicates the name of the
         application profile to be applied to the subscriber."
    ::= { tmnxBsxTransitIpSumEntry 4 }

tmnxBsxTransitIpSumIpOriginMask  OBJECT-TYPE
    SYNTAX      TmnxBsxTransitSubOrigin
    MAX-ACCESS  read-only
    STATUS      current
    DESCRIPTION
        "The value of tmnxBsxTransitIpSumIpOriginMask indicates the manner in
         which the transit subscriber was created."
    ::= { tmnxBsxTransitIpSumEntry 5 }

tmnxBsxTransPrefPolicyTable      OBJECT-TYPE
    SYNTAX      SEQUENCE OF TmnxBsxTransPrefPolicyEntry
    MAX-ACCESS  not-accessible
    STATUS      current
    DESCRIPTION
        "The tmnxBsxTransPrefPolicyTable contains an entry for each transit
         prefix policy. These policies are used in cases when there is no
         system/IOM subscriber context such as in-line deployments of AA where
         the traffic from the AA subscriber is transitioning through the SR."
    ::= { tmnxBsxTransitObjs 6 }

tmnxBsxTransPrefPolicyEntry      OBJECT-TYPE
    SYNTAX      TmnxBsxTransPrefPolicyEntry
    MAX-ACCESS  not-accessible
    STATUS      current
    DESCRIPTION
        "Each tmnxBsxTransPrefPolicyEntry contains transit prefix policy
         specific configuration."
    INDEX       {
        tmnxBsxAaGrpPartIndex,
        tmnxBsxTransPrefPolicyId
    }
    ::= { tmnxBsxTransPrefPolicyTable 1 }

TmnxBsxTransPrefPolicyEntry      ::= SEQUENCE
{
    tmnxBsxTransPrefPolicyId         TmnxBsxTransPrefPolicyId,
    tmnxBsxTransPrefPolicyRowStatus  RowStatus,
    tmnxBsxTransPrefPolicyRowLastCh  TimeStamp,
    tmnxBsxTransPrefPolicyDesc       TItemDescription,
    tmnxBsxTransPrefPolicySubsCount  Counter32,
    tmnxBsxTransPrefPolicyEntCount   Counter32,
    tmnxBsxTransPrefPolicyIPv4EntCnt Counter32,
    tmnxBsxTransPrefPolicyIPv6EntCnt Counter32
}

tmnxBsxTransPrefPolicyId         OBJECT-TYPE
    SYNTAX      TmnxBsxTransPrefPolicyId
    MAX-ACCESS  not-accessible
    STATUS      current
    DESCRIPTION
        "The value of tmnxBsxTransPrefPolicyId specifies, along with
         tmnxBsxAaGrpPartIndex, the index to a specific transit prefix policy.
         tmnxBsxTransPrefPolicyId is system unique across all group-partitions."
    ::= { tmnxBsxTransPrefPolicyEntry 1 }

tmnxBsxTransPrefPolicyRowStatus  OBJECT-TYPE
    SYNTAX      RowStatus
    MAX-ACCESS  read-create
    STATUS      current
    DESCRIPTION
        "The value of tmnxBsxTransPrefPolicyRowStatus specifies the row status.
         It allows entries to be created and deleted in the
         tmnxBsxTransPrefPolicyTable.

         Rows are created by specifying the value of 'createAndGo (4)', and
         deleted by specifying the value of 'destroy (6)'.

         The deletion of a row of this table implicitly deletes all the
         corresponding entries in the tmnxBsxTransPrefSubTable and
         tmnxBsxTransPrefTable that are indexed on tmnxBsxTransPrefPolicyId."
    ::= { tmnxBsxTransPrefPolicyEntry 2 }

tmnxBsxTransPrefPolicyRowLastCh  OBJECT-TYPE
    SYNTAX      TimeStamp
    MAX-ACCESS  read-only
    STATUS      current
    DESCRIPTION
        "The value of tmnxBsxTransPrefPolicyRowLastCh indicates the last time,
         since system startup, a successful set was performed on this row of
         the tmnxBsxTransPrefPolicyTable."
    ::= { tmnxBsxTransPrefPolicyEntry 3 }

tmnxBsxTransPrefPolicyDesc       OBJECT-TYPE
    SYNTAX      TItemDescription
    MAX-ACCESS  read-create
    STATUS      current
    DESCRIPTION
        "The value of tmnxBsxTransPrefPolicyDesc specifies a user-provided
         description for this transit prefix policy."
    DEFVAL      { "" }
    ::= { tmnxBsxTransPrefPolicyEntry 4 }

tmnxBsxTransPrefPolicySubsCount  OBJECT-TYPE
    SYNTAX      Counter32
    MAX-ACCESS  read-only
    STATUS      current
    DESCRIPTION
        "The value of tmnxBsxTransPrefPolicySubsCount indicates the total
         number of subscribers within this transit prefix policy.

         The value of tmnxBsxTransPrefPolicySubsCount is the number of rows in
         the table tmnxBsxTransPrefSubTable with matching tmnxBsxAaGrpPartIndex
         and tmnxBsxTransPrefPolicyId indices."
    ::= { tmnxBsxTransPrefPolicyEntry 5 }

tmnxBsxTransPrefPolicyEntCount   OBJECT-TYPE
    SYNTAX      Counter32
    MAX-ACCESS  read-only
    STATUS      current
    DESCRIPTION
        "The value of tmnxBsxTransPrefPolicyEntCount indicates the total number
         of entries within this transit prefix policy.

         The value of tmnxBsxTransPrefPolicyEntCount is the number of rows in
         the table tmnxBsxTransPrefTable with matching tmnxBsxAaGrpPartIndex
         and tmnxBsxTransPrefPolicyId indices."
    ::= { tmnxBsxTransPrefPolicyEntry 6 }

tmnxBsxTransPrefPolicyIPv4EntCnt OBJECT-TYPE
    SYNTAX      Counter32
    MAX-ACCESS  read-only
    STATUS      current
    DESCRIPTION
        "The value of tmnxBsxTransPrefPolicyIPv4EntCnt indicates the total
         number of valid IPv4 entries within this transit prefix policy.

         A valid entry is defined as an entry in the tmnxBsxTransPrefTable with
         matching tmnxBsxAaGrpPartIndex and tmnxBsxTransPrefPolicyId indices
         plus non-default values specified for the
         tmnxBsxTransPrefEntrySubscriber, and tmnxBsxTransPrefEntrySubAddr or
         tmnxBsxTransPrefEntryNetAddr objects."
    ::= { tmnxBsxTransPrefPolicyEntry 7 }

tmnxBsxTransPrefPolicyIPv6EntCnt OBJECT-TYPE
    SYNTAX      Counter32
    MAX-ACCESS  read-only
    STATUS      current
    DESCRIPTION
        "The value of tmnxBsxTransPrefPolicyIPv6EntCnt indicates the total
         number of valid IPv6 entries within this transit prefix policy.

         A valid entry is defined as an entry in the tmnxBsxTransPrefTable with
         matching tmnxBsxAaGrpPartIndex and tmnxBsxTransPrefPolicyId indices
         plus non-default values specified for the
         tmnxBsxTransPrefEntrySubscriber, and tmnxBsxTransPrefEntrySubAddr or
         tmnxBsxTransPrefEntryNetAddr objects."
    ::= { tmnxBsxTransPrefPolicyEntry 8 }

tmnxBsxTransPrefSubTable         OBJECT-TYPE
    SYNTAX      SEQUENCE OF TmnxBsxTransPrefSubEntry
    MAX-ACCESS  not-accessible
    STATUS      current
    DESCRIPTION
        "The tmnxBsxTransPrefSubTable contains the configuration of transit
         subscribers within a transit prefix policy."
    ::= { tmnxBsxTransitObjs 7 }

tmnxBsxTransPrefSubEntry         OBJECT-TYPE
    SYNTAX      TmnxBsxTransPrefSubEntry
    MAX-ACCESS  not-accessible
    STATUS      current
    DESCRIPTION
        "Each tmnxBsxTransPrefSubEntry contains transit prefix policy
         subscriber configuration."
    INDEX       {
        tmnxBsxAaGrpPartIndex,
        tmnxBsxTransPrefPolicyId,
        tmnxBsxTransPrefSubscriber
    }
    ::= { tmnxBsxTransPrefSubTable 1 }

TmnxBsxTransPrefSubEntry         ::= SEQUENCE
{
    tmnxBsxTransPrefSubscriber       TNamedItem,
    tmnxBsxTransPrefSubRowStatus     RowStatus,
    tmnxBsxTransPrefSubRowLastCh     TimeStamp,
    tmnxBsxTransPrefSubIsRemote      TruthValue,
    tmnxBsxTransPrefSubAppProfNm     TNamedItem,
    tmnxBsxTransPrefSubRefCount      Unsigned32
}

tmnxBsxTransPrefSubscriber       OBJECT-TYPE
    SYNTAX      TNamedItem
    MAX-ACCESS  not-accessible
    STATUS      current
    DESCRIPTION
        "The value of tmnxBsxTransPrefSubscriber specifies the name of the
         transit prefix AA subscriber."
    ::= { tmnxBsxTransPrefSubEntry 1 }

tmnxBsxTransPrefSubRowStatus     OBJECT-TYPE
    SYNTAX      RowStatus
    MAX-ACCESS  read-create
    STATUS      current
    DESCRIPTION
        "The value of tmnxBsxTransPrefSubRowStatus specifies the row status. It
         allows entries to be created and deleted in the
         tmnxBsxTransPrefSubTable.

         Rows are created by specifying the value of 'createAndGo (4)', and
         deleted by specifying the value of 'destroy (6)'."
    ::= { tmnxBsxTransPrefSubEntry 2 }

tmnxBsxTransPrefSubRowLastCh     OBJECT-TYPE
    SYNTAX      TimeStamp
    MAX-ACCESS  read-only
    STATUS      current
    DESCRIPTION
        "The value of tmnxBsxTransPrefSubRowLastCh indicates the last time,
         since system startup, a successful set was performed on this row of
         the tmnxBsxTransPrefSubTable."
    ::= { tmnxBsxTransPrefSubEntry 3 }

tmnxBsxTransPrefSubIsRemote      OBJECT-TYPE
    SYNTAX      TruthValue
    MAX-ACCESS  read-create
    STATUS      current
    DESCRIPTION
        "The value of tmnxBsxTransPrefSubIsRemote specifies whether the
         subscriber is remote.

         This value can only be set during row creation."
    DEFVAL      { false }
    ::= { tmnxBsxTransPrefSubEntry 4 }

tmnxBsxTransPrefSubAppProfNm     OBJECT-TYPE
    SYNTAX      TNamedItem
    MAX-ACCESS  read-create
    STATUS      current
    DESCRIPTION
        "The value of tmnxBsxTransPrefSubAppProfNm specifies the name of the
         application profile to be applied to the AA transit.

         The value of tmnxBsxTransPrefSubAppProfNm must be a valid app-profile
         that exists in the group/partition identified by tmnxBsxAaGrpPartIndex
         which is an index of this row entry. tmnxBsxTransIpPlcySubAppProfNm
         must be present in the same SNMP PDU as the row creation, otherwise
         the creation will fail."
    ::= { tmnxBsxTransPrefSubEntry 5 }

tmnxBsxTransPrefSubRefCount      OBJECT-TYPE
    SYNTAX      Unsigned32
    MAX-ACCESS  read-only
    STATUS      current
    DESCRIPTION
        "The value of tmnxBsxTransPrefSubRefCount specifies the number of
         references in the tmnxBsxTransPrefTable to the AA prefix subscriber
         identified in this row."
    ::= { tmnxBsxTransPrefSubEntry 6 }

tmnxBsxTransPrefTable            OBJECT-TYPE
    SYNTAX      SEQUENCE OF TmnxBsxTransPrefEntry
    MAX-ACCESS  not-accessible
    STATUS      current
    DESCRIPTION
        "The tmnxBsxTransPrefTable contains the configuration of entries within
         a transit prefix policy."
    ::= { tmnxBsxTransitObjs 8 }

tmnxBsxTransPrefEntry            OBJECT-TYPE
    SYNTAX      TmnxBsxTransPrefEntry
    MAX-ACCESS  not-accessible
    STATUS      current
    DESCRIPTION
        "Each tmnxBsxTransPrefEntry contains transit prefix policy entry
         configuration. When both the tmnxBsxTransPrefEntrySubAddrType and the
         tmnxBsxTransPrefEntryNetAddrType are not set to 'unknown(0)', these
         address types must have the same value."
    INDEX       {
        tmnxBsxAaGrpPartIndex,
        tmnxBsxTransPrefPolicyId,
        tmnxBsxTransPrefEntryId
    }
    ::= { tmnxBsxTransPrefTable 1 }

TmnxBsxTransPrefEntry            ::= SEQUENCE
{
    tmnxBsxTransPrefEntryId          Unsigned32,
    tmnxBsxTransPrefEntryRowStatus   RowStatus,
    tmnxBsxTransPrefEntryRowLastCh   TimeStamp,
    tmnxBsxTransPrefEntrySubAddrType InetAddressType,
    tmnxBsxTransPrefEntrySubAddr     InetAddress,
    tmnxBsxTransPrefEntrySubAddrLen  InetAddressPrefixLength,
    tmnxBsxTransPrefEntryNetAddrType InetAddressType,
    tmnxBsxTransPrefEntryNetAddr     InetAddress,
    tmnxBsxTransPrefEntryNetAddrLen  InetAddressPrefixLength,
    tmnxBsxTransPrefEntrySubscriber  TNamedItemOrEmpty
}

tmnxBsxTransPrefEntryId          OBJECT-TYPE
    SYNTAX      Unsigned32 (1..4294967295)
    MAX-ACCESS  not-accessible
    STATUS      current
    DESCRIPTION
        "The value of tmnxBsxTransPrefEntryId specifies, along with
         tmnxBsxAaGrpPartIndex and tmnxBsxTransPrefPolicyId, the index to a
         specific entry of a transit prefix policy."
    ::= { tmnxBsxTransPrefEntry 1 }

tmnxBsxTransPrefEntryRowStatus   OBJECT-TYPE
    SYNTAX      RowStatus
    MAX-ACCESS  read-create
    STATUS      current
    DESCRIPTION
        "The value of tmnxBsxTransPrefEntryRowStatus specifies the row status.
         It allows entries to be created and deleted in the
         tmnxBsxTransPrefTable.

         Rows are created by specifying the value of 'createAndGo (4)', and
         deleted by specifying the value of 'destroy (6)'."
    ::= { tmnxBsxTransPrefEntry 2 }

tmnxBsxTransPrefEntryRowLastCh   OBJECT-TYPE
    SYNTAX      TimeStamp
    MAX-ACCESS  read-only
    STATUS      current
    DESCRIPTION
        "The value of tmnxBsxTransPrefEntryRowLastCh indicates the last time,
         since system startup, a successful set was performed on this row of
         the tmnxBsxTransPrefTable."
    ::= { tmnxBsxTransPrefEntry 3 }

tmnxBsxTransPrefEntrySubAddrType OBJECT-TYPE
    SYNTAX      InetAddressType
    MAX-ACCESS  read-create
    STATUS      current
    DESCRIPTION
        "The value of tmnxBsxTransPrefEntrySubAddrType specifies the address
         type of the subscriber address prefix associated with this transit
         prefix policy entry.

         tmnxBsxTransPrefEntrySubAddrType can be 'unknown(0)' indicating the
         subscriber address prefix is not used for matching. If the value is
         not 'unknown(0)' and tmnxBsxTransPrefEntryNetAddrType is not
         'unknown(0)', then tmnxBsxTransPrefEntrySubAddrType must have the same
         value as tmnxBsxTransPrefEntryNetAddrType."
    DEFVAL      { unknown }
    ::= { tmnxBsxTransPrefEntry 4 }

tmnxBsxTransPrefEntrySubAddr     OBJECT-TYPE
    SYNTAX      InetAddress (SIZE (0|4|16))
    MAX-ACCESS  read-create
    STATUS      current
    DESCRIPTION
        "The value of tmnxBsxTransPrefEntrySubAddr specifies the subscriber
         address prefix associated with this transit prefix policy entry.

         If the associated tmnxBsxTransPrefEntrySubAddrType is 'unknown(0)'
         then the address prefix is not used for matching and the address
         prefix is not applicable."
    DEFVAL      { ''H }
    ::= { tmnxBsxTransPrefEntry 5 }

tmnxBsxTransPrefEntrySubAddrLen  OBJECT-TYPE
    SYNTAX      InetAddressPrefixLength (0..128)
    MAX-ACCESS  read-create
    STATUS      current
    DESCRIPTION
        "The value of tmnxBsxTransPrefEntrySubAddrLen specifies the length of
         the subscriber address prefix associated with this transit prefix
         policy entry.

         If the associated tmnxBsxTransPrefEntrySubAddrType is 'unknown(0)'
         then the address prefix is not used for matching and the length of the
         prefix is not applicable."
    DEFVAL      { 0 }
    ::= { tmnxBsxTransPrefEntry 6 }

tmnxBsxTransPrefEntryNetAddrType OBJECT-TYPE
    SYNTAX      InetAddressType
    MAX-ACCESS  read-create
    STATUS      current
    DESCRIPTION
        "The value of tmnxBsxTransPrefEntryNetAddrType specifies the address
         type of the network address prefix associated with this transit prefix
         policy entry.

         tmnxBsxTransPrefEntryNetAddrType can be 'unknown(0)' indicating the
         network address prefix is not used for matching. If the value is not
         'unknown(0)' and tmnxBsxTransPrefEntrySubAddrType is not 'unknown(0)',
         then tmnxBsxTransPrefEntryNetAddrType must have the same value as
         tmnxBsxTransPrefEntrySubAddrType."
    DEFVAL      { unknown }
    ::= { tmnxBsxTransPrefEntry 7 }

tmnxBsxTransPrefEntryNetAddr     OBJECT-TYPE
    SYNTAX      InetAddress (SIZE (0|4|16))
    MAX-ACCESS  read-create
    STATUS      current
    DESCRIPTION
        "The value of tmnxBsxTransPrefEntryNetAddr specifies the network
         address prefix associated with this transit prefix policy entry.

         If the associated tmnxBsxTransPrefEntryNetAddrType is 'unknown(0)'
         then the address prefix is not used for matching and the address
         prefix is not applicable."
    DEFVAL      { ''H }
    ::= { tmnxBsxTransPrefEntry 8 }

tmnxBsxTransPrefEntryNetAddrLen  OBJECT-TYPE
    SYNTAX      InetAddressPrefixLength (0..128)
    MAX-ACCESS  read-create
    STATUS      current
    DESCRIPTION
        "The value of tmnxBsxTransPrefEntryNetAddrLen specifies the length of
         the network address prefix associated with this transit prefix policy
         entry.

         If the associated tmnxBsxTransPrefEntryNetAddrType is 'unknown(0)'
         then the address prefix is not used for matching and the length of the
         prefix is not applicable."
    DEFVAL      { 0 }
    ::= { tmnxBsxTransPrefEntry 9 }

tmnxBsxTransPrefEntrySubscriber  OBJECT-TYPE
    SYNTAX      TNamedItemOrEmpty
    MAX-ACCESS  read-create
    STATUS      current
    DESCRIPTION
        "The value of tmnxBsxTransPrefEntrySubscriber specifies the transit
         prefix subscriber associated with this transit prefix policy entry."
    DEFVAL      { "" }
    ::= { tmnxBsxTransPrefEntry 10 }

tmnxBsxTransPrefSumTable         OBJECT-TYPE
    SYNTAX      SEQUENCE OF TmnxBsxTransPrefSumEntry
    MAX-ACCESS  not-accessible
    STATUS      current
    DESCRIPTION
        "The tmnxBsxTransPrefSumTable contains summary information for all
         transit prefix policy subscribers."
    ::= { tmnxBsxTransitObjs 9 }

tmnxBsxTransPrefSumEntry         OBJECT-TYPE
    SYNTAX      TmnxBsxTransPrefSumEntry
    MAX-ACCESS  not-accessible
    STATUS      current
    DESCRIPTION
        "Each tmnxBsxTransPrefSumEntry contains summary information for a
         transit prefix subscriber."
    INDEX       {
        tmnxBsxAaGrpPartIndex,
        tmnxBsxTransPrefPolicyId,
        tmnxBsxTransPrefSubscriber,
        tmnxBsxTransPrefEntryId
    }
    ::= { tmnxBsxTransPrefSumTable 1 }

TmnxBsxTransPrefSumEntry         ::= SEQUENCE
{
    tmnxBsxTransPrefSumUpdateTime    TimeStamp,
    tmnxBsxTransPrefSumSubAddrType   InetAddressType,
    tmnxBsxTransPrefSumSubAddr       InetAddress,
    tmnxBsxTransPrefSumSubAddrLen    InetAddressPrefixLength,
    tmnxBsxTransPrefSumNetAddrType   InetAddressType,
    tmnxBsxTransPrefSumNetAddr       InetAddress,
    tmnxBsxTransPrefSumNetAddrLen    InetAddressPrefixLength,
    tmnxBsxTransPrefSumParentSubType TmnxBsxAaSubscriberType,
    tmnxBsxTransPrefSumParentSub     TmnxBsxAaSubscriber,
    tmnxBsxTransPrefSumAppProfNm     TNamedItem
}

tmnxBsxTransPrefSumUpdateTime    OBJECT-TYPE
    SYNTAX      TimeStamp
    MAX-ACCESS  read-only
    STATUS      current
    DESCRIPTION
        "The value of tmnxBsxTransPrefSumUpdateTime indicates the last time,
         since system startup, the contents of a row of the
         tmnxBsxTransPrefSumTable was updated."
    ::= { tmnxBsxTransPrefSumEntry 1 }

tmnxBsxTransPrefSumSubAddrType   OBJECT-TYPE
    SYNTAX      InetAddressType
    MAX-ACCESS  read-only
    STATUS      current
    DESCRIPTION
        "The value of tmnxBsxTransPrefSumSubAddrType indicates the type of the
         subscriber address."
    ::= { tmnxBsxTransPrefSumEntry 2 }

tmnxBsxTransPrefSumSubAddr       OBJECT-TYPE
    SYNTAX      InetAddress (SIZE (0|4|16))
    MAX-ACCESS  read-only
    STATUS      current
    DESCRIPTION
        "The value of tmnxBsxTransPrefSumSubAddr indicates the subscriber
         address."
    ::= { tmnxBsxTransPrefSumEntry 3 }

tmnxBsxTransPrefSumSubAddrLen    OBJECT-TYPE
    SYNTAX      InetAddressPrefixLength (0..128)
    MAX-ACCESS  read-only
    STATUS      current
    DESCRIPTION
        "The value of tmnxBsxTransPrefSumSubAddrLen indicates the length of the
         subscriber address.

         Addresses of type 'unknown(0)' may be of zero-length."
    ::= { tmnxBsxTransPrefSumEntry 4 }

tmnxBsxTransPrefSumNetAddrType   OBJECT-TYPE
    SYNTAX      InetAddressType
    MAX-ACCESS  read-only
    STATUS      current
    DESCRIPTION
        "The value of tmnxBsxTransPrefSumNetAddrType indicates the type of the
         address in tmnxBsxTransPrefSumNetAddr."
    ::= { tmnxBsxTransPrefSumEntry 5 }

tmnxBsxTransPrefSumNetAddr       OBJECT-TYPE
    SYNTAX      InetAddress (SIZE (0|4|16))
    MAX-ACCESS  read-only
    STATUS      current
    DESCRIPTION
        "The value of tmnxBsxTransPrefSumNetAddr indicates the network address."
    ::= { tmnxBsxTransPrefSumEntry 6 }

tmnxBsxTransPrefSumNetAddrLen    OBJECT-TYPE
    SYNTAX      InetAddressPrefixLength (0..128)
    MAX-ACCESS  read-only
    STATUS      current
    DESCRIPTION
        "The value of tmnxBsxTransPrefSumNetAddrLen indicates the length of the
         network address.

         Addresses of type 'unknown(0)' may be of zero-length."
    ::= { tmnxBsxTransPrefSumEntry 7 }

tmnxBsxTransPrefSumParentSubType OBJECT-TYPE
    SYNTAX      TmnxBsxAaSubscriberType
    MAX-ACCESS  read-only
    STATUS      current
    DESCRIPTION
        "The value of tmnxBsxTransPrefSumParentSubType indicates the type of
         the parent of the subscriber."
    ::= { tmnxBsxTransPrefSumEntry 8 }

tmnxBsxTransPrefSumParentSub     OBJECT-TYPE
    SYNTAX      TmnxBsxAaSubscriber
    MAX-ACCESS  read-only
    STATUS      current
    DESCRIPTION
        "The value of tmnxBsxTransPrefSumParentSub indicates the parent of the
         subscriber."
    ::= { tmnxBsxTransPrefSumEntry 9 }

tmnxBsxTransPrefSumAppProfNm     OBJECT-TYPE
    SYNTAX      TNamedItem
    MAX-ACCESS  read-only
    STATUS      current
    DESCRIPTION
        "The value of tmnxBsxTransPrefSumAppProfNm indicates the name of the
         application profile to be applied to the subscriber."
    ::= { tmnxBsxTransPrefSumEntry 10 }

tmnxBsxHttpRedirObjs             OBJECT IDENTIFIER ::= { tmnxBsxObjs 8 }

tmnxBsxHttpRedirScalars          OBJECT IDENTIFIER ::= { tmnxBsxHttpRedirObjs 1 }

tmnxBsxHttpRedirErrLastChTime    OBJECT-TYPE
    SYNTAX      TimeStamp
    MAX-ACCESS  read-only
    STATUS      current
    DESCRIPTION
        "The value of tmnxBsxHttpRedirErrLastChTime indicates the last time,
         since system startup, a successful set was performed on the
         tmnxBsxHttpRedirErrTable."
    ::= { tmnxBsxHttpRedirScalars 1 }

tmnxBsxHttpRedirErrCodeLastCh    OBJECT-TYPE
    SYNTAX      TimeStamp
    MAX-ACCESS  read-only
    STATUS      current
    DESCRIPTION
        "The value of tmnxBsxHttpRedirErrCodeLastCh indicates the last time,
         since system startup, a successful set was performed on the
         tmnxBsxHttpRedirErrCodeTable."
    ::= { tmnxBsxHttpRedirScalars 2 }

tmnxBsxHttpRedirLastCh           OBJECT-TYPE
    SYNTAX      TimeStamp
    MAX-ACCESS  read-only
    STATUS      current
    DESCRIPTION
        "The value of tmnxBsxHttpRedirLastCh indicates the last time, since
         system startup, a successful set was performed on the
         tmnxBsxHttpRedirTable."
    ::= { tmnxBsxHttpRedirScalars 3 }

tmnxBsxHttpRedirErrTable         OBJECT-TYPE
    SYNTAX      SEQUENCE OF TmnxBsxHttpRedirErrEntry
    MAX-ACCESS  not-accessible
    STATUS      current
    DESCRIPTION
        "The tmnxBsxHttpRedirErrTable contains an entry for each instance of
         HTTP Error Redirect."
    ::= { tmnxBsxHttpRedirObjs 2 }

tmnxBsxHttpRedirErrEntry         OBJECT-TYPE
    SYNTAX      TmnxBsxHttpRedirErrEntry
    MAX-ACCESS  not-accessible
    STATUS      current
    DESCRIPTION
        "Each tmnxBsxHttpRedirErrEntry contains the configuration information
         for an instance of HTTP Error Redirect."
    INDEX       {
        tmnxBsxIsaAaGroupIndex,
        IMPLIED tmnxBsxHttpRedirErrName
    }
    ::= { tmnxBsxHttpRedirErrTable 1 }

TmnxBsxHttpRedirErrEntry         ::= SEQUENCE
{
    tmnxBsxHttpRedirErrName          TNamedItem,
    tmnxBsxHttpRedirErrRowStatus     RowStatus,
    tmnxBsxHttpRedirErrRowLastCh     TimeStamp,
    tmnxBsxHttpRedirErrEnabled       TmnxEnabledDisabled,
    tmnxBsxHttpRedirErrDescription   TItemDescription,
    tmnxBsxHttpRedirErrTemplateId    Unsigned32,
    tmnxBsxHttpRedirErrHttpHost      SnmpAdminString,
    tmnxBsxHttpRedirErrParticipantId SnmpAdminString
}

tmnxBsxHttpRedirErrName          OBJECT-TYPE
    SYNTAX      TNamedItem
    MAX-ACCESS  not-accessible
    STATUS      current
    DESCRIPTION
        "The value of tmnxBsxHttpRedirErrName specifies the name of the HTTP
         Error Redirect."
    ::= { tmnxBsxHttpRedirErrEntry 1 }

tmnxBsxHttpRedirErrRowStatus     OBJECT-TYPE
    SYNTAX      RowStatus
    MAX-ACCESS  read-create
    STATUS      current
    DESCRIPTION
        "The value of tmnxBsxHttpRedirErrRowStatus specifies the row status. It
         allows entries to be created and deleted in the
         tmnxBsxHttpRedirErrTable.

         Rows are created by specifying the value of 'createAndGo (4)', and
         deleted by specifying the value of 'destroy (6)'."
    ::= { tmnxBsxHttpRedirErrEntry 2 }

tmnxBsxHttpRedirErrRowLastCh     OBJECT-TYPE
    SYNTAX      TimeStamp
    MAX-ACCESS  read-only
    STATUS      current
    DESCRIPTION
        "The value of tmnxBsxHttpRedirErrRowLastCh indicates the last time,
         since system startup, a successful set was performed on this row of
         the tmnxBsxHttpRedirErrTable."
    ::= { tmnxBsxHttpRedirErrEntry 3 }

tmnxBsxHttpRedirErrEnabled       OBJECT-TYPE
    SYNTAX      TmnxEnabledDisabled
    MAX-ACCESS  read-create
    STATUS      current
    DESCRIPTION
        "The value of tmnxBsxHttpRedirErrEnabled specifies whether this HTTP
         Error Redirect is enabled."
    DEFVAL      { disabled }
    ::= { tmnxBsxHttpRedirErrEntry 4 }

tmnxBsxHttpRedirErrDescription   OBJECT-TYPE
    SYNTAX      TItemDescription
    MAX-ACCESS  read-create
    STATUS      current
    DESCRIPTION
        "The value of tmnxBsxHttpRedirErrDescription specifies the description
         of this HTTP Error Redirect."
    DEFVAL      { "" }
    ::= { tmnxBsxHttpRedirErrEntry 5 }

tmnxBsxHttpRedirErrTemplateId    OBJECT-TYPE
    SYNTAX      Unsigned32
    MAX-ACCESS  read-create
    STATUS      current
    DESCRIPTION
        "The value of tmnxBsxHttpRedirErrTemplateId specifies the template Id
         of this HTTP Error Redirect.

         A tmnxBsxHttpRedirErrTemplateId of 0 specifies no template Id.
         Template Ids are defined in the tmnxBsxTListAttribTable in rows where
         the index tmnxBsxTListName has a value of
         'http-error-redirect-template' and where the index
         tmnxBsxTListAttribName has a value of 'template'."
    DEFVAL      { 0 }
    ::= { tmnxBsxHttpRedirErrEntry 6 }

tmnxBsxHttpRedirErrHttpHost      OBJECT-TYPE
    SYNTAX      SnmpAdminString
    MAX-ACCESS  read-create
    STATUS      current
    DESCRIPTION
        "The value of tmnxBsxHttpRedirErrHttpHost specifies the HTTP host for
         this HTTP Error Redirect."
    DEFVAL      { "" }
    ::= { tmnxBsxHttpRedirErrEntry 7 }

tmnxBsxHttpRedirErrParticipantId OBJECT-TYPE
    SYNTAX      SnmpAdminString (SIZE (0..32))
    MAX-ACCESS  read-create
    STATUS      current
    DESCRIPTION
        "The value of tmnxBsxHttpRedirErrParticipantId specifies the
         participant Id for this HTTP Error Redirect."
    DEFVAL      { "" }
    ::= { tmnxBsxHttpRedirErrEntry 8 }

tmnxBsxHttpRedirErrCodeTable     OBJECT-TYPE
    SYNTAX      SEQUENCE OF TmnxBsxHttpRedirErrCodeEntry
    MAX-ACCESS  not-accessible
    STATUS      current
    DESCRIPTION
        "The tmnxBsxHttpRedirErrCodeTable contains HTTP error codes used in
         HTTP error redirection."
    ::= { tmnxBsxHttpRedirObjs 3 }

tmnxBsxHttpRedirErrCodeEntry     OBJECT-TYPE
    SYNTAX      TmnxBsxHttpRedirErrCodeEntry
    MAX-ACCESS  not-accessible
    STATUS      current
    DESCRIPTION
        "Each tmnxBsxHttpRedirErrCodeEntry contains the configuration
         information associated with an HTTP error code."
    INDEX       {
        tmnxBsxIsaAaGroupIndex,
        tmnxBsxHttpRedirErrName,
        tmnxBsxHttpRedirErrCode
    }
    ::= { tmnxBsxHttpRedirErrCodeTable 1 }

TmnxBsxHttpRedirErrCodeEntry     ::= SEQUENCE
{
    tmnxBsxHttpRedirErrCode          Unsigned32,
    tmnxBsxHttpRedirErrCodeRowStatus RowStatus,
    tmnxBsxHttpRedirErrCodeRowLastCh TimeStamp,
    tmnxBsxHttpRedirErrorCodeMsgSize Unsigned32
}

tmnxBsxHttpRedirErrCode          OBJECT-TYPE
    SYNTAX      Unsigned32 (400..999)
    MAX-ACCESS  not-accessible
    STATUS      current
    DESCRIPTION
        "The value of tmnxBsxHttpRedirErrCode specifies the error code for a
         HTTP Error Redirect.

         Error codes are defined in the tmnxBsxTListAttribTable in rows where
         the index tmnxBsxTListName has a value of
         'http-error-redirect-error-code' and the index tmnxBsxTListAttribName
         has a value of 'code'."
    ::= { tmnxBsxHttpRedirErrCodeEntry 1 }

tmnxBsxHttpRedirErrCodeRowStatus OBJECT-TYPE
    SYNTAX      RowStatus
    MAX-ACCESS  read-create
    STATUS      current
    DESCRIPTION
        "The value of tmnxBsxHttpRedirErrCodeRowStatus specifies the row
         status. It allows entries to be created and deleted in the
         tmnxBsxHttpRedirErrCodeTable.

         Rows are created by specifying the value of 'createAndGo (4)', and
         deleted by specifying the value of 'destroy (6)'."
    ::= { tmnxBsxHttpRedirErrCodeEntry 2 }

tmnxBsxHttpRedirErrCodeRowLastCh OBJECT-TYPE
    SYNTAX      TimeStamp
    MAX-ACCESS  read-only
    STATUS      current
    DESCRIPTION
        "The value of tmnxBsxHttpRedirErrCodeRowLastCh indicates the last time,
         since system startup, a successful set was performed on this row of
         the tmnxBsxHttpRedirErrCodeTable."
    ::= { tmnxBsxHttpRedirErrCodeEntry 3 }

tmnxBsxHttpRedirErrorCodeMsgSize OBJECT-TYPE
    SYNTAX      Unsigned32
    UNITS       "octets"
    MAX-ACCESS  read-create
    STATUS      current
    DESCRIPTION
        "The value of tmnxBsxHttpRedirErrorCodeMsgSize specifies the maximum
         message size above which redirect will not be done.

         The default tmnxBsxHttpRedirErrorCodeMsgSize is dependent on the error
         code. An initial table is shown below. The default message sizes are
         defined in the tmnxBsxTListAttribTable in rows where the index
         tmnxBsxTListName has a value of 'http-error-redirect-error-code' and
         the index tmnxBsxTListAttribName has a value of 'defaultMsgSize'. The
         corresponding error code can be correlated to this default message
         size by searching the tmnxBsxTListAttribTable where the index
         tmnxBsxTListName has a value of 'http-error-redirect-error-code', the
         index tmnxBsxTListAttribName has a value of 'code' and the
         tmnxBsxTListAttribSet matches the tmnxBsxTListAttribSet value that
         indexed the default maximum message size.


            Error Code      Default Message Size
            ------------------------------------
            404             1024 "
    DEFVAL      { 1024 }
    ::= { tmnxBsxHttpRedirErrCodeEntry 4 }

tmnxBsxHttpRdStatTable           OBJECT-TYPE
    SYNTAX      SEQUENCE OF TmnxBsxHttpRdStatEntry
    MAX-ACCESS  not-accessible
    STATUS      current
    DESCRIPTION
        "The tmnxBsxHttpRdStatTable contains statistics for HTTP error
         redirection."
    ::= { tmnxBsxHttpRedirObjs 4 }

tmnxBsxHttpRdStatEntry           OBJECT-TYPE
    SYNTAX      TmnxBsxHttpRdStatEntry
    MAX-ACCESS  not-accessible
    STATUS      current
    DESCRIPTION
        "Each tmnxBsxHttpRdStatEntry contains statistics for HTTP error
         redirection.

         An index with a valid tmnxBsxAaGrpPartIndex, tmnxBsxHttpRedirErrName,
         tmnxBsxHttpRedirErrCode (an existing row in
         tmnxBsxHttpRedirErrCodeTable), tmnxChassisIndex set to one, and a zero
         value for each of tmnxBsxCardSlotEsaId and tmnxBsxMdaSlotEsaVmId will
         return the summarized per group and HTTP error redirection code
         statistics."
    INDEX       {
        tmnxBsxAaGrpPartIndex,
        tmnxBsxHttpRedirErrName,
        tmnxBsxHttpRedirErrCode,
        tmnxChassisIndex,
        tmnxBsxCardSlotEsaId,
        tmnxBsxMdaSlotEsaVmId
    }
    ::= { tmnxBsxHttpRdStatTable 1 }

TmnxBsxHttpRdStatEntry           ::= SEQUENCE
{
    tmnxBsxHttpRdStatDiscontTime     TimeStamp,
    tmnxBsxHttpRdStatHCRedir         Counter64,
    tmnxBsxHttpRdStatRedirLo         Counter32,
    tmnxBsxHttpRdStatRedirHi         Counter32,
    tmnxBsxHttpRdStatHCSizeExceeded  Counter64,
    tmnxBsxHttpRdStatSizeExceededLo  Counter32,
    tmnxBsxHttpRdStatSizeExceededHi  Counter32,
    tmnxBsxHttpRdStatHCOutOfResource Counter64,
    tmnxBsxHttpRdStatOutOfResourceLo Counter32,
    tmnxBsxHttpRdStatOutOfResourceHi Counter32,
    tmnxBsxHttpRdStatHCNotRedirFType Counter64,
    tmnxBsxHttpRdStatNotRedirFTypeLo Counter32,
    tmnxBsxHttpRdStatNotRedirFTypeHi Counter32,
    tmnxBsxHttpRdStatHCNotRedir      Counter64,
    tmnxBsxHttpRdStatNotRedirLo      Counter32,
    tmnxBsxHttpRdStatNotRedirHi      Counter32
}

tmnxBsxHttpRdStatDiscontTime     OBJECT-TYPE
    SYNTAX      TimeStamp
    MAX-ACCESS  read-only
    STATUS      current
    DESCRIPTION
        "The value of tmnxBsxHttpRdStatDiscontTime indicates the
         SNMPv2-MIB::sysUpTime (centiseconds) when the ISA-AA MDA within the
         group has last changed status."
    ::= { tmnxBsxHttpRdStatEntry 1 }

tmnxBsxHttpRdStatHCRedir         OBJECT-TYPE
    SYNTAX      Counter64
    MAX-ACCESS  read-only
    STATUS      current
    DESCRIPTION
        "The value of tmnxBsxHttpRdStatHCRedir indicates the number of
         redirected messages."
    ::= { tmnxBsxHttpRdStatEntry 2 }

tmnxBsxHttpRdStatRedirLo         OBJECT-TYPE
    SYNTAX      Counter32
    MAX-ACCESS  read-only
    STATUS      current
    DESCRIPTION
        "The value of tmnxBsxHttpRdStatRedirLo indicates the lower 32-bits of
         tmnxBsxHttpRdStatHCRedir."
    ::= { tmnxBsxHttpRdStatEntry 3 }

tmnxBsxHttpRdStatRedirHi         OBJECT-TYPE
    SYNTAX      Counter32
    MAX-ACCESS  read-only
    STATUS      current
    DESCRIPTION
        "The value of tmnxBsxHttpRdStatRedirHi indicates the upper 32-bits of
         tmnxBsxHttpRdStatHCRedir."
    ::= { tmnxBsxHttpRdStatEntry 4 }

tmnxBsxHttpRdStatHCSizeExceeded  OBJECT-TYPE
    SYNTAX      Counter64
    MAX-ACCESS  read-only
    STATUS      current
    DESCRIPTION
        "The value of tmnxBsxHttpRdStatHCSizeExceeded indicates the number of
         messages that have exceeded the custom message size associated with
         the error code."
    ::= { tmnxBsxHttpRdStatEntry 5 }

tmnxBsxHttpRdStatSizeExceededLo  OBJECT-TYPE
    SYNTAX      Counter32
    MAX-ACCESS  read-only
    STATUS      current
    DESCRIPTION
        "The value of tmnxBsxHttpRdStatSizeExceededLo indicates the lower
         32-bits of tmnxBsxHttpRdStatHCSizeExceeded."
    ::= { tmnxBsxHttpRdStatEntry 6 }

tmnxBsxHttpRdStatSizeExceededHi  OBJECT-TYPE
    SYNTAX      Counter32
    MAX-ACCESS  read-only
    STATUS      current
    DESCRIPTION
        "The value of tmnxBsxHttpRdStatSizeExceededHi indicates the upper
         32-bits of tmnxBsxHttpRdStatHCSizeExceeded."
    ::= { tmnxBsxHttpRdStatEntry 7 }

tmnxBsxHttpRdStatHCOutOfResource OBJECT-TYPE
    SYNTAX      Counter64
    MAX-ACCESS  read-only
    STATUS      current
    DESCRIPTION
        "The value of tmnxBsxHttpRdStatHCOutOfResource indicates the number of
         message redirects that did not occur due to lack of resources."
    ::= { tmnxBsxHttpRdStatEntry 8 }

tmnxBsxHttpRdStatOutOfResourceLo OBJECT-TYPE
    SYNTAX      Counter32
    MAX-ACCESS  read-only
    STATUS      current
    DESCRIPTION
        "The value of tmnxBsxHttpRdStatOutOfResourceLo indicates the lower
         32-bits of tmnxBsxHttpRdStatHCOutOfResource."
    ::= { tmnxBsxHttpRdStatEntry 9 }

tmnxBsxHttpRdStatOutOfResourceHi OBJECT-TYPE
    SYNTAX      Counter32
    MAX-ACCESS  read-only
    STATUS      current
    DESCRIPTION
        "The value of tmnxBsxHttpRdStatOutOfResourceHi indicates the upper
         32-bits of tmnxBsxHttpRdStatHCOutOfResource."
    ::= { tmnxBsxHttpRdStatEntry 10 }

tmnxBsxHttpRdStatHCNotRedirFType OBJECT-TYPE
    SYNTAX      Counter64
    MAX-ACCESS  read-only
    STATUS      current
    DESCRIPTION
        "The value of tmnxBsxHttpRdStatHCNotRedirFType indicates the number of
         message redirects that did not occur due to the file type."
    ::= { tmnxBsxHttpRdStatEntry 11 }

tmnxBsxHttpRdStatNotRedirFTypeLo OBJECT-TYPE
    SYNTAX      Counter32
    MAX-ACCESS  read-only
    STATUS      current
    DESCRIPTION
        "The value of tmnxBsxHttpRdStatNotRedirFTypeLo indicates the lower
         32-bits of tmnxBsxHttpRdStatHCNotRedirFType."
    ::= { tmnxBsxHttpRdStatEntry 12 }

tmnxBsxHttpRdStatNotRedirFTypeHi OBJECT-TYPE
    SYNTAX      Counter32
    MAX-ACCESS  read-only
    STATUS      current
    DESCRIPTION
        "The value of tmnxBsxHttpRdStatNotRedirFTypeHi indicates the upper
         32-bits of tmnxBsxHttpRdStatHCNotRedirFType."
    ::= { tmnxBsxHttpRdStatEntry 13 }

tmnxBsxHttpRdStatHCNotRedir      OBJECT-TYPE
    SYNTAX      Counter64
    MAX-ACCESS  read-only
    STATUS      current
    DESCRIPTION
        "The value of tmnxBsxHttpRdStatHCNotRedir indicates the number of
         message redirects that did not occur due to errors."
    ::= { tmnxBsxHttpRdStatEntry 14 }

tmnxBsxHttpRdStatNotRedirLo      OBJECT-TYPE
    SYNTAX      Counter32
    MAX-ACCESS  read-only
    STATUS      current
    DESCRIPTION
        "The value of tmnxBsxHttpRdStatNotRedirLo indicates the lower 32-bits
         of tmnxBsxHttpRdStatHCNotRedir."
    ::= { tmnxBsxHttpRdStatEntry 15 }

tmnxBsxHttpRdStatNotRedirHi      OBJECT-TYPE
    SYNTAX      Counter32
    MAX-ACCESS  read-only
    STATUS      current
    DESCRIPTION
        "The value of tmnxBsxHttpRdStatNotRedirHi indicates the upper 32-bits
         of tmnxBsxHttpRdStatHCNotRedir."
    ::= { tmnxBsxHttpRdStatEntry 16 }

tmnxBsxHttpRedirTable            OBJECT-TYPE
    SYNTAX      SEQUENCE OF TmnxBsxHttpRedirEntry
    MAX-ACCESS  not-accessible
    STATUS      current
    DESCRIPTION
        "The tmnxBsxHttpRedirTable contains an entry for each instance of HTTP
         Redirect."
    ::= { tmnxBsxHttpRedirObjs 5 }

tmnxBsxHttpRedirEntry            OBJECT-TYPE
    SYNTAX      TmnxBsxHttpRedirEntry
    MAX-ACCESS  not-accessible
    STATUS      current
    DESCRIPTION
        "Each tmnxBsxHttpRedirEntry contains the configuration information for
         an instance of HTTP Redirect."
    INDEX       {
        tmnxBsxIsaAaGroupIndex,
        IMPLIED tmnxBsxHttpRedirName
    }
    ::= { tmnxBsxHttpRedirTable 1 }

TmnxBsxHttpRedirEntry            ::= SEQUENCE
{
    tmnxBsxHttpRedirName             TNamedItem,
    tmnxBsxHttpRedirRowStatus        RowStatus,
    tmnxBsxHttpRedirRowLastCh        TimeStamp,
    tmnxBsxHttpRedirEnabled          TmnxEnabledDisabled,
    tmnxBsxHttpRedirDescription      TItemDescription,
    tmnxBsxHttpRedirTemplateId       Unsigned32,
    tmnxBsxHttpRedirHttpHost         SnmpAdminString,
    tmnxBsxHttpRedirTcpReset         TmnxEnabledDisabled,
    tmnxBsxHttpRedirCaptivePortVlan  VlanIdOrNone,
    tmnxBsxHttpRedirCapHttpsEnbld    TmnxEnabledDisabled,
    tmnxBsxHttpRedirHttpsRedirEnbld  TmnxEnabledDisabled
}

tmnxBsxHttpRedirName             OBJECT-TYPE
    SYNTAX      TNamedItem
    MAX-ACCESS  not-accessible
    STATUS      current
    DESCRIPTION
        "The value of tmnxBsxHttpRedirName specifies the name of the HTTP
         Redirect."
    ::= { tmnxBsxHttpRedirEntry 1 }

tmnxBsxHttpRedirRowStatus        OBJECT-TYPE
    SYNTAX      RowStatus
    MAX-ACCESS  read-create
    STATUS      current
    DESCRIPTION
        "The value of tmnxBsxHttpRedirRowStatus specifies the row status. It
         allows entries to be created and deleted in the tmnxBsxHttpRedirTable.

         Rows are created by specifying the value of 'createAndGo (4)', and
         deleted by specifying the value of 'destroy (6)'."
    ::= { tmnxBsxHttpRedirEntry 2 }

tmnxBsxHttpRedirRowLastCh        OBJECT-TYPE
    SYNTAX      TimeStamp
    MAX-ACCESS  read-only
    STATUS      current
    DESCRIPTION
        "The value of tmnxBsxHttpRedirRowLastCh indicates the last time, since
         system startup, a successful set was performed on this row of the
         tmnxBsxHttpRedirTable."
    ::= { tmnxBsxHttpRedirEntry 3 }

tmnxBsxHttpRedirEnabled          OBJECT-TYPE
    SYNTAX      TmnxEnabledDisabled
    MAX-ACCESS  read-create
    STATUS      current
    DESCRIPTION
        "The value of tmnxBsxHttpRedirEnabled specifies whether this HTTP
         Redirect is enabled."
    DEFVAL      { disabled }
    ::= { tmnxBsxHttpRedirEntry 4 }

tmnxBsxHttpRedirDescription      OBJECT-TYPE
    SYNTAX      TItemDescription
    MAX-ACCESS  read-create
    STATUS      current
    DESCRIPTION
        "The value of tmnxBsxHttpRedirDescription specifies the description of
         this HTTP Redirect."
    DEFVAL      { "" }
    ::= { tmnxBsxHttpRedirEntry 5 }

tmnxBsxHttpRedirTemplateId       OBJECT-TYPE
    SYNTAX      Unsigned32
    MAX-ACCESS  read-create
    STATUS      current
    DESCRIPTION
        "The value of tmnxBsxHttpRedirTemplateId specifies the template Id of
         this HTTP Redirect. Template Ids are defined in the
         tmnxBsxTListAttribTable in rows where the index tmnxBsxTListName has a
         value of 'http-redirect-template' and where the index
         tmnxBsxTListAttribName has a value of 'template'.

         A template indicating macro insertion support is defined in the
         tmnxBsxTListAttribTable in a row where the tmnxBsxTListName has a
         value of 'http-redirect-template' and where the index
         tmnxBsxTListAttribName has a value of 'macrosupport' and the index
         tmnxBsxTListAttribSet is the value of the tmnxBsxTListAttribSet from
         the row containing the template id.

         A tmnxBsxHttpRedirTemplateId of 0 specifies no template Id."
    DEFVAL      { 0 }
    ::= { tmnxBsxHttpRedirEntry 6 }

tmnxBsxHttpRedirHttpHost         OBJECT-TYPE
    SYNTAX      SnmpAdminString
    MAX-ACCESS  read-create
    STATUS      current
    DESCRIPTION
        "The value of tmnxBsxHttpRedirHttpHost specifies the HTTP host for this
         HTTP Redirect.

         When the tmnxBsxHttpRedirTemplateId supports macro insertion
         tmnxBsxHttpRedirHttpHost specifies the redirect URL. "
    DEFVAL      { "" }
    ::= { tmnxBsxHttpRedirEntry 7 }

tmnxBsxHttpRedirTcpReset         OBJECT-TYPE
    SYNTAX      TmnxEnabledDisabled
    MAX-ACCESS  read-create
    STATUS      current
    DESCRIPTION
        "The value of tmnxBsxHttpRedirTcpReset specifies whether resetting of
         the TCP client is enabled.

         When tmnxBsxHttpRedirTcpReset is enabled, a reset will be sent to the
         client if this is a TCP flow and it not HTTP redirectable."
    DEFVAL      { disabled }
    ::= { tmnxBsxHttpRedirEntry 8 }

tmnxBsxHttpRedirCaptivePortVlan  OBJECT-TYPE
    SYNTAX      VlanIdOrNone
    MAX-ACCESS  read-create
    STATUS      current
    DESCRIPTION
        "The value of tmnxBsxHttpRedirCaptivePortVlan specifies the ISA-AA
         service port VLAN (Virtual Local Area Network) ID which is used to
         generate captive TCP response traffic.

         A VLAN ID of 0 specifies that no response traffic is sent."
    DEFVAL      { 0 }
    ::= { tmnxBsxHttpRedirEntry 9 }

tmnxBsxHttpRedirCapHttpsEnbld    OBJECT-TYPE
    SYNTAX      TmnxEnabledDisabled
    MAX-ACCESS  read-create
    STATUS      obsolete
    DESCRIPTION
        "The value of tmnxBsxHttpRedirCapHttpsEnbld specifies whether this HTTP
         redirect also supports redirecting captive HTTPS traffic.

         The object tmnxBsxHttpRedirCapHttpsEnbld is obsoleted in release 16.0
         and is replaced by tmnxBsxHttpRedirHttpsRedirEnbld"
    DEFVAL      { disabled }
    ::= { tmnxBsxHttpRedirEntry 10 }

tmnxBsxHttpRedirHttpsRedirEnbld  OBJECT-TYPE
    SYNTAX      TmnxEnabledDisabled
    MAX-ACCESS  read-create
    STATUS      current
    DESCRIPTION
        "The value of tmnxBsxHttpRedirHttpsRedirEnbld specifies whether this
         HTTP redirect also supports redirecting HTTPS traffic."
    DEFVAL      { disabled }
    ::= { tmnxBsxHttpRedirEntry 11 }

tmnxBsxHttpPcyRdStatTable        OBJECT-TYPE
    SYNTAX      SEQUENCE OF TmnxBsxHttpPcyRdStatEntry
    MAX-ACCESS  not-accessible
    STATUS      current
    DESCRIPTION
        "The tmnxBsxHttpPcyRdStatTable contains statistics for HTTP
         redirection."
    ::= { tmnxBsxHttpRedirObjs 6 }

tmnxBsxHttpPcyRdStatEntry        OBJECT-TYPE
    SYNTAX      TmnxBsxHttpPcyRdStatEntry
    MAX-ACCESS  not-accessible
    STATUS      current
    DESCRIPTION
        "Each tmnxBsxHttpPcyRdStatEntry contains statistics for HTTP
         redirection.

         An index with a valid tmnxBsxAaGrpPartIndex/tmnxBsxHttpRedirName (an
         existing row in tmnxBsxHttpRedirTable), tmnxChassisIndex set to one,
         and a zero value for each of tmnxBsxCardSlotEsaId and
         tmnxBsxMdaSlotEsaVmId will return the summarized per group and HTTP
         redirect name statistics."
    INDEX       {
        tmnxBsxAaGrpPartIndex,
        tmnxBsxHttpRedirName,
        tmnxChassisIndex,
        tmnxBsxCardSlotEsaId,
        tmnxBsxMdaSlotEsaVmId
    }
    ::= { tmnxBsxHttpPcyRdStatTable 1 }

TmnxBsxHttpPcyRdStatEntry        ::= SEQUENCE
{
    tmnxBsxHttpPcyRdStatDiscontTime  TimeStamp,
    tmnxBsxHttpPcyRdStatHCRedir      Counter64,
    tmnxBsxHttpPcyRdStatRedirLo      Counter32,
    tmnxBsxHttpPcyRdStatRedirHi      Counter32,
    tmnxBsxHttpPcyRdStatHCOutOfRes   Counter64,
    tmnxBsxHttpPcyRdStatOutOfResLo   Counter32,
    tmnxBsxHttpPcyRdStatOutOfResHi   Counter32,
    tmnxBsxHttpPcyRdStatHCNotRedir   Counter64,
    tmnxBsxHttpPcyRdStatNotRedirLo   Counter32,
    tmnxBsxHttpPcyRdStatNotRedirHi   Counter32,
    tmnxBsxHttpPcyRdStatTcpResets    Counter64,
    tmnxBsxHttpPcyRdStatConfigError  Counter64
}

tmnxBsxHttpPcyRdStatDiscontTime  OBJECT-TYPE
    SYNTAX      TimeStamp
    MAX-ACCESS  read-only
    STATUS      current
    DESCRIPTION
        "The value of tmnxBsxHttpPcyRdStatDiscontTime indicates the
         SNMPv2-MIB::sysUpTime (centiseconds) when the ISA-AA MDA within the
         group has last changed status."
    ::= { tmnxBsxHttpPcyRdStatEntry 1 }

tmnxBsxHttpPcyRdStatHCRedir      OBJECT-TYPE
    SYNTAX      Counter64
    MAX-ACCESS  read-only
    STATUS      current
    DESCRIPTION
        "The value of tmnxBsxHttpPcyRdStatHCRedir indicates the number of
         redirected sessions."
    ::= { tmnxBsxHttpPcyRdStatEntry 2 }

tmnxBsxHttpPcyRdStatRedirLo      OBJECT-TYPE
    SYNTAX      Counter32
    MAX-ACCESS  read-only
    STATUS      current
    DESCRIPTION
        "The value of tmnxBsxHttpPcyRdStatRedirLo indicates the lower 32-bits
         of tmnxBsxHttpPcyRdStatHCRedir."
    ::= { tmnxBsxHttpPcyRdStatEntry 3 }

tmnxBsxHttpPcyRdStatRedirHi      OBJECT-TYPE
    SYNTAX      Counter32
    MAX-ACCESS  read-only
    STATUS      current
    DESCRIPTION
        "The value of tmnxBsxHttpPcyRdStatRedirHi indicates the upper 32-bits
         of tmnxBsxHttpPcyRdStatHCRedir."
    ::= { tmnxBsxHttpPcyRdStatEntry 4 }

tmnxBsxHttpPcyRdStatHCOutOfRes   OBJECT-TYPE
    SYNTAX      Counter64
    MAX-ACCESS  read-only
    STATUS      current
    DESCRIPTION
        "The value of tmnxBsxHttpPcyRdStatHCOutOfRes indicates the number of
         sessions that were not redirected due to lack of resources."
    ::= { tmnxBsxHttpPcyRdStatEntry 5 }

tmnxBsxHttpPcyRdStatOutOfResLo   OBJECT-TYPE
    SYNTAX      Counter32
    MAX-ACCESS  read-only
    STATUS      current
    DESCRIPTION
        "The value of tmnxBsxHttpPcyRdStatOutOfResLo indicates the lower
         32-bits of tmnxBsxHttpPcyRdStatHCOutOfRes."
    ::= { tmnxBsxHttpPcyRdStatEntry 6 }

tmnxBsxHttpPcyRdStatOutOfResHi   OBJECT-TYPE
    SYNTAX      Counter32
    MAX-ACCESS  read-only
    STATUS      current
    DESCRIPTION
        "The value of tmnxBsxHttpPcyRdStatOutOfResHi indicates the upper
         32-bits of tmnxBsxHttpPcyRdStatHCOutOfRes."
    ::= { tmnxBsxHttpPcyRdStatEntry 7 }

tmnxBsxHttpPcyRdStatHCNotRedir   OBJECT-TYPE
    SYNTAX      Counter64
    MAX-ACCESS  read-only
    STATUS      current
    DESCRIPTION
        "The value of tmnxBsxHttpPcyRdStatHCNotRedir indicates the number of
         sessions that were not redirected due to traffic attributes."
    ::= { tmnxBsxHttpPcyRdStatEntry 8 }

tmnxBsxHttpPcyRdStatNotRedirLo   OBJECT-TYPE
    SYNTAX      Counter32
    MAX-ACCESS  read-only
    STATUS      current
    DESCRIPTION
        "The value of tmnxBsxHttpPcyRdStatNotRedirLo indicates the lower
         32-bits of tmnxBsxHttpPcyRdStatHCNotRedir."
    ::= { tmnxBsxHttpPcyRdStatEntry 9 }

tmnxBsxHttpPcyRdStatNotRedirHi   OBJECT-TYPE
    SYNTAX      Counter32
    MAX-ACCESS  read-only
    STATUS      current
    DESCRIPTION
        "The value of tmnxBsxHttpPcyRdStatNotRedirHi indicates the upper
         32-bits of tmnxBsxHttpPcyRdStatHCNotRedir."
    ::= { tmnxBsxHttpPcyRdStatEntry 10 }

tmnxBsxHttpPcyRdStatTcpResets    OBJECT-TYPE
    SYNTAX      Counter64
    MAX-ACCESS  read-only
    STATUS      current
    DESCRIPTION
        "The value of tmnxBsxHttpPcyRdStatTcpResets indicates the number of TCP
         client resets that have been sent."
    ::= { tmnxBsxHttpPcyRdStatEntry 11 }

tmnxBsxHttpPcyRdStatConfigError  OBJECT-TYPE
    SYNTAX      Counter64
    MAX-ACCESS  read-only
    STATUS      current
    DESCRIPTION
        "The value of tmnxBsxHttpPcyRdStatConfigError indicates the number of
         sessions that were not redirected due to configuration errors."
    ::= { tmnxBsxHttpPcyRdStatEntry 12 }

tmnxBsxStaticDataObjs            OBJECT IDENTIFIER ::= { tmnxBsxObjs 9 }

tmnxBsxStaticObjScalars          OBJECT IDENTIFIER ::= { tmnxBsxStaticDataObjs 1 }

tmnxBsxTListTableLastUpdateT     OBJECT-TYPE
    SYNTAX      TimeStamp
    MAX-ACCESS  read-only
    STATUS      current
    DESCRIPTION
        "The value of tmnxBsxTListTableLastUpdateT indicates the last time,
         since system startup, a successful update was performed on the
         tmnxBsxTListTable."
    ::= { tmnxBsxStaticObjScalars 1 }

tmnxBsxTListAttribTableLUpdateT  OBJECT-TYPE
    SYNTAX      TimeStamp
    MAX-ACCESS  read-only
    STATUS      current
    DESCRIPTION
        "The value of tmnxBsxTListAttribTableLUpdateT indicates the last time,
         since system startup, a successful update was performed on the
         tmnxBsxTListAttribTable."
    ::= { tmnxBsxStaticObjScalars 2 }

tmnxBsxTListTable                OBJECT-TYPE
    SYNTAX      SEQUENCE OF TmnxBsxTListEntry
    MAX-ACCESS  not-accessible
    STATUS      current
    DESCRIPTION
        "The tmnxBsxTListTable contains an entry for each tagged list stored in
         the ISA AA image file."
    ::= { tmnxBsxStaticDataObjs 2 }

tmnxBsxTListEntry                OBJECT-TYPE
    SYNTAX      TmnxBsxTListEntry
    MAX-ACCESS  not-accessible
    STATUS      current
    DESCRIPTION
        "Each tmnxBsxTListEntry contains the definition of a BSX tagged list."
    INDEX       { tmnxBsxTListName }
    ::= { tmnxBsxTListTable 1 }

TmnxBsxTListEntry                ::= SEQUENCE
{
    tmnxBsxTListName                 TNamedItem,
    tmnxBsxTListRowLastUpdateT       TimeStamp,
    tmnxBsxTListDescription          TItemDescription
}

tmnxBsxTListName                 OBJECT-TYPE
    SYNTAX      TNamedItem
    MAX-ACCESS  not-accessible
    STATUS      current
    DESCRIPTION
        "The value of tmnxBsxTListName specifies the name of the tagged list.
         The following tagged list names are supported:

         device-id device-os device-mfg http-header-field http-redirect-keyword
         http-redirect-template http-notification-template
         http-error-redirect-template http-error-redirect-error-code flow-attr
         cflowd-record-fields"
    ::= { tmnxBsxTListEntry 1 }

tmnxBsxTListRowLastUpdateT       OBJECT-TYPE
    SYNTAX      TimeStamp
    MAX-ACCESS  read-only
    STATUS      current
    DESCRIPTION
        "The value of tmnxBsxTListRowLastUpdateT indicates the last time, since
         system startup, a successful update was performed on this row of
         tmnxBsxTListTable."
    ::= { tmnxBsxTListEntry 2 }

tmnxBsxTListDescription          OBJECT-TYPE
    SYNTAX      TItemDescription
    MAX-ACCESS  read-only
    STATUS      current
    DESCRIPTION
        "The value of tmnxBsxTListDescription indicates a description of the
         tagged list."
    ::= { tmnxBsxTListEntry 3 }

tmnxBsxTListAttribTable          OBJECT-TYPE
    SYNTAX      SEQUENCE OF TmnxBsxTListAttribEntry
    MAX-ACCESS  not-accessible
    STATUS      current
    DESCRIPTION
        "The tmnxBsxTListAttribTable contains an entry for each attribute
         associated with an item of a tagged list."
    ::= { tmnxBsxStaticDataObjs 3 }

tmnxBsxTListAttribEntry          OBJECT-TYPE
    SYNTAX      TmnxBsxTListAttribEntry
    MAX-ACCESS  not-accessible
    STATUS      current
    DESCRIPTION
        "Each tmnxBsxTListAttribEntry contains the description of an attribute
         associated with an item of a tagged list."
    INDEX       {
        tmnxBsxTListName,
        tmnxBsxTListAttribName,
        tmnxBsxTListAttribSet
    }
    ::= { tmnxBsxTListAttribTable 1 }

TmnxBsxTListAttribEntry          ::= SEQUENCE
{
    tmnxBsxTListAttribName           TNamedItem,
    tmnxBsxTListAttribSet            Unsigned32,
    tmnxBsxTListAttribRowLastUpdateT TimeStamp,
    tmnxBsxTListAttribType           TmnxBsxTListAttribType,
    tmnxBsxTListAttribValue          TmnxBsxTListAttribValue
}

tmnxBsxTListAttribName           OBJECT-TYPE
    SYNTAX      TNamedItem
    MAX-ACCESS  not-accessible
    STATUS      current
    DESCRIPTION
        "The value of tmnxBsxTListAttribName specifies the name of the
         attribute of an item in the tagged list. The following attribute names
         for a given tagged list are supported:

         --------------------------------------------------------------------
         | tmnxBsxTListName               | tmnxBsxTListAttribName
         --------------------------------------------------------------------
         | device-id                      | id, name, description
         | device-os                      |
         | device-mfg                     |
         |                                |
         | http-header-field              | name, description, anti-spoof,
         |                                | applicability
         |                                |
         | http-redirect-keyword          | name, keyword, description
         |                                |
         | http-redirect-template         | template, description, macrosupport
         |                                |
         | http-notification-template     | template, description
         | http-error-redirect-template   |
         |                                |
         | http-error-redirect-error-code | code, description, defaultMsgSize
         | cflowd-record-fields           | name, id, size, optional,
         |                                | applicability, mandatory
         |                                | description
         |                                |
         | flow-attr                      | id, name, description
         --------------------------------------------------------------------"
    ::= { tmnxBsxTListAttribEntry 1 }

tmnxBsxTListAttribSet            OBJECT-TYPE
    SYNTAX      Unsigned32
    MAX-ACCESS  not-accessible
    STATUS      current
    DESCRIPTION
        "The value of tmnxBsxTListAttribSet specifies an attribute set. All
         attributes using the same tmnxBsxTListName and tmnxBsxTListAttribSet
         reference one item of a tagged list.

         For example, a tmnxBsxTListAttribSet=1 can have 2 attributes
         tmnxBsxTListAttribName = 'code' and tmnxBsxTListAttribName =
         'description'. Both of these are attributes belonging to a single
         item."
    ::= { tmnxBsxTListAttribEntry 2 }

tmnxBsxTListAttribRowLastUpdateT OBJECT-TYPE
    SYNTAX      TimeStamp
    MAX-ACCESS  read-only
    STATUS      current
    DESCRIPTION
        "The value of tmnxBsxTListAttribRowLastUpdateT indicates the last time,
         since system startup, a successful update was performed on this row of
         tmnxBsxTListAttribTable."
    ::= { tmnxBsxTListAttribEntry 3 }

tmnxBsxTListAttribType           OBJECT-TYPE
    SYNTAX      TmnxBsxTListAttribType
    MAX-ACCESS  read-only
    STATUS      current
    DESCRIPTION
        "The value of tmnxBsxTListAttribType indicates how the attribute value
         tmnxBsxTListAttribValue is encoded."
    ::= { tmnxBsxTListAttribEntry 4 }

tmnxBsxTListAttribValue          OBJECT-TYPE
    SYNTAX      TmnxBsxTListAttribValue
    MAX-ACCESS  read-only
    STATUS      current
    DESCRIPTION
        "The value of tmnxBsxTListAttribValue indicates the value of the
         attribute of an item in the tagged list."
    ::= { tmnxBsxTListAttribEntry 5 }

tmnxBsxRedundancyObjs            OBJECT IDENTIFIER ::= { tmnxBsxObjs 10 }

tmnxBsxRedundancyObjScalars      OBJECT IDENTIFIER ::= { tmnxBsxRedundancyObjs 1 }

tmnxBsxAarpTableLastChTime       OBJECT-TYPE
    SYNTAX      TimeStamp
    MAX-ACCESS  read-only
    STATUS      current
    DESCRIPTION
        "The value of tmnxBsxAarpTableLastChTime indicates the last time, since
         system startup, a successful set was performed on the
         tmnxBsxAarpInstTable."
    ::= { tmnxBsxRedundancyObjScalars 1 }

tmnxBsxAarpInstTable             OBJECT-TYPE
    SYNTAX      SEQUENCE OF TmnxBsxAarpInstEntry
    MAX-ACCESS  not-accessible
    STATUS      current
    DESCRIPTION
        "The tmnxBsxAarpInstTable contains an entry for each Application
         Assurance Redundancy Protocol (AARP) instance configured on this
         system."
    ::= { tmnxBsxRedundancyObjs 2 }

tmnxBsxAarpInstEntry             OBJECT-TYPE
    SYNTAX      TmnxBsxAarpInstEntry
    MAX-ACCESS  not-accessible
    STATUS      current
    DESCRIPTION
        "Each tmnxBsxAarpInstEntry represents a particular AARP instance."
    INDEX       { tmnxBsxAarpInstId }
    ::= { tmnxBsxAarpInstTable 1 }

TmnxBsxAarpInstEntry             ::= SEQUENCE
{
    tmnxBsxAarpInstId                TmnxBsxAarpId,
    tmnxBsxAarpInstRowStatus         RowStatus,
    tmnxBsxAarpInstLastCh            TimeStamp,
    tmnxBsxAarpInstDescription       TItemDescription,
    tmnxBsxAarpInstPeerIpType        InetAddressType,
    tmnxBsxAarpInstPeerIpAddr        InetAddress,
    tmnxBsxAarpInstPriority          Unsigned32,
    tmnxBsxAarpInstAdminState        TmnxAdminState,
    tmnxBsxAarpInstOperState         TmnxOperState,
    tmnxBsxAarpInstState             TmnxBsxAarpInstState,
    tmnxBsxAarpInstOperFlags         TmnxBsxAarpInstOperFlags,
    tmnxBsxAarpInstPeerPriority      Unsigned32,
    tmnxBsxAarpInstPeerState         TmnxBsxAarpInstState,
    tmnxBsxAarpInstPeerOperFlags     TmnxBsxAarpInstOperFlags,
    tmnxBsxAarpInstPeerSubRefType    TmnxBsxAaSubscriberType,
    tmnxBsxAarpInstPeerEPSapPortId   TmnxPortID,
    tmnxBsxAarpInstPeerEPSapEncap    TmnxEncapVal,
    tmnxBsxAarpInstPeerEPSapEncType  TmnxPortEncapType,
    tmnxBsxAarpInstPeerEPSdpBindId   SdpBindId,
    tmnxBsxAarpInstMasterSelectMode  INTEGER
}

tmnxBsxAarpInstId                OBJECT-TYPE
    SYNTAX      TmnxBsxAarpId
    MAX-ACCESS  not-accessible
    STATUS      current
    DESCRIPTION
        "The value of tmnxBsxAarpInstId specifies the unique Id of this AARP
         instance."
    ::= { tmnxBsxAarpInstEntry 1 }

tmnxBsxAarpInstRowStatus         OBJECT-TYPE
    SYNTAX      RowStatus
    MAX-ACCESS  read-create
    STATUS      current
    DESCRIPTION
        "The value of tmnxBsxAarpInstRowStatus specifies the row status. It
         allows entries to be created and deleted in the tmnxBsxAarpInstTable.

         Rows are created by specifying the value of 'createAndGo (4)', and
         deleted by specifying the value of 'destroy (6)'."
    ::= { tmnxBsxAarpInstEntry 2 }

tmnxBsxAarpInstLastCh            OBJECT-TYPE
    SYNTAX      TimeStamp
    MAX-ACCESS  read-only
    STATUS      current
    DESCRIPTION
        "The value of tmnxBsxAarpInstLastCh indicates the last time, since
         system startup, a successful set was performed on this row of the
         tmnxBsxAarpInstTable."
    ::= { tmnxBsxAarpInstEntry 3 }

tmnxBsxAarpInstDescription       OBJECT-TYPE
    SYNTAX      TItemDescription
    MAX-ACCESS  read-create
    STATUS      current
    DESCRIPTION
        "The value of tmnxBsxAarpInstDescription specifies the description of
         this AARP instance."
    DEFVAL      { "" }
    ::= { tmnxBsxAarpInstEntry 4 }

tmnxBsxAarpInstPeerIpType        OBJECT-TYPE
    SYNTAX      InetAddressType
    MAX-ACCESS  read-create
    STATUS      current
    DESCRIPTION
        "The value of tmnxBsxAarpInstPeerIpType specifies the type of the
         address in tmnxBsxAarpInstPeerIpAddr."
    DEFVAL      { unknown }
    ::= { tmnxBsxAarpInstEntry 5 }

tmnxBsxAarpInstPeerIpAddr        OBJECT-TYPE
    SYNTAX      InetAddress (SIZE (0|4|16))
    MAX-ACCESS  read-create
    STATUS      current
    DESCRIPTION
        "The value of tmnxBsxAarpInstPeerIpAddr specifies the address of the AA
         Redundancy Protocol instance peer."
    DEFVAL      { ''H }
    ::= { tmnxBsxAarpInstEntry 6 }

tmnxBsxAarpInstPriority          OBJECT-TYPE
    SYNTAX      Unsigned32 (0..255)
    MAX-ACCESS  read-create
    STATUS      current
    DESCRIPTION
        "The value of tmnxBsxAarpInstPriority specifies the priority of this
         AARP instance advertised to the AARP peer. It is compared to the
         peer's priority, and the AARP instance with the higher priority enters
         the master state and the one with the lower priority enters the backup
         state. If the priorities are identical, the instance peer IP addresses
         are used as a tiebreaker with the peer with the higher address
         entering the master state and the other the backup."
    DEFVAL      { 100 }
    ::= { tmnxBsxAarpInstEntry 7 }

tmnxBsxAarpInstAdminState        OBJECT-TYPE
    SYNTAX      TmnxAdminState
    MAX-ACCESS  read-create
    STATUS      current
    DESCRIPTION
        "The value of tmnxBsxAarpInstAdminState specifies the administrative
         state of the AARP instance. When the value is 'outOfService(3)' the
         AARP instance is disabled."
    DEFVAL      { outOfService }
    ::= { tmnxBsxAarpInstEntry 8 }

tmnxBsxAarpInstOperState         OBJECT-TYPE
    SYNTAX      TmnxOperState
    MAX-ACCESS  read-only
    STATUS      current
    DESCRIPTION
        "The value of tmnxBsxAarpInstOperState indicates the
         operational state of the AARP instance.  When the
         value is 'outOfService(3)' the AARP instance is not
         performing asymmetry removal."
    ::= { tmnxBsxAarpInstEntry 9 }

tmnxBsxAarpInstState             OBJECT-TYPE
    SYNTAX      TmnxBsxAarpInstState
    MAX-ACCESS  read-only
    STATUS      current
    DESCRIPTION
        "The value of tmnxBsxAarpInstState indicates the state of the AARP
         instance."
    ::= { tmnxBsxAarpInstEntry 10 }

tmnxBsxAarpInstOperFlags         OBJECT-TYPE
    SYNTAX      TmnxBsxAarpInstOperFlags
    MAX-ACCESS  read-only
    STATUS      current
    DESCRIPTION
        "The value of tmnxBsxAarpInstOperFlags indicates the different
         conditions that affect the operating status of the AARP instance."
    ::= { tmnxBsxAarpInstEntry 11 }

tmnxBsxAarpInstPeerPriority      OBJECT-TYPE
    SYNTAX      Unsigned32
    MAX-ACCESS  read-only
    STATUS      current
    DESCRIPTION
        "The value of tmnxBsxAarpInstPeerPriority indicates the priority
         advertised by the AARP instance peer."
    ::= { tmnxBsxAarpInstEntry 12 }

tmnxBsxAarpInstPeerState         OBJECT-TYPE
    SYNTAX      TmnxBsxAarpInstState
    MAX-ACCESS  read-only
    STATUS      current
    DESCRIPTION
        "The value of tmnxBsxAarpInstPeerState indicates the state advertised
         by the AARP instance peer."
    ::= { tmnxBsxAarpInstEntry 13 }

tmnxBsxAarpInstPeerOperFlags     OBJECT-TYPE
    SYNTAX      TmnxBsxAarpInstOperFlags
    MAX-ACCESS  read-only
    STATUS      current
    DESCRIPTION
        "The value of tmnxBsxAarpInstPeerOperFlags indicates the different
         conditions that affect the operating status of the peer of this AARP
         instance."
    ::= { tmnxBsxAarpInstEntry 14 }

tmnxBsxAarpInstPeerSubRefType    OBJECT-TYPE
    SYNTAX      TmnxBsxAaSubscriberType
    MAX-ACCESS  read-only
    STATUS      current
    DESCRIPTION
        "The value of tmnxBsxAarpInstPeerSubRefType indicates the type of the
         subscriber which the peer of this AARP instance references with a
         service type of 'dualHomed(1)'.

         The valid values are 'unknown(0)' indicating the lack of a service
         reference with type 'dualHomed(1)', 'sap(2)', and 'spokeSdp(3)'."
    ::= { tmnxBsxAarpInstEntry 15 }

tmnxBsxAarpInstPeerEPSapPortId   OBJECT-TYPE
    SYNTAX      TmnxPortID
    MAX-ACCESS  read-create
    STATUS      current
    DESCRIPTION
        "The value of tmnxBsxAarpInstPeerEPSapPortId along with
         tmnxBsxAarpInstPeerEPSapEncap and tmnxBsxAarpInstPeerEPSapEncType
         specifies the Service Access Point (SAP) end point for the dual homed
         peer.

         The specification of a tmnxBsxAarpInstPeerEPSapPortId is mutually
         exclusive with the specification of tmnxBsxAarpInstPeerEPSdpBindId.

         The default value indicates that this is an invalid port id."
    DEFVAL      { '1e000000'H }
    ::= { tmnxBsxAarpInstEntry 16 }

tmnxBsxAarpInstPeerEPSapEncap    OBJECT-TYPE
    SYNTAX      TmnxEncapVal
    MAX-ACCESS  read-create
    STATUS      current
    DESCRIPTION
        "The value of tmnxBsxAarpInstPeerEPSapEncap along with
         tmnxBsxAarpInstPeerEPSapPortId and tmnxBsxAarpInstPeerEPSapEncType
         specifies the Service Access Point (SAP) end point for the dual homed
         peer.

         The specification of a tmnxBsxAarpInstPeerEPSapEncap is mutually
         exclusive with the specification of tmnxBsxAarpInstPeerEPSdpBindId."
    DEFVAL      { 0 }
    ::= { tmnxBsxAarpInstEntry 17 }

tmnxBsxAarpInstPeerEPSapEncType  OBJECT-TYPE
    SYNTAX      TmnxPortEncapType
    MAX-ACCESS  read-create
    STATUS      current
    DESCRIPTION
        "The value of tmnxBsxAarpInstPeerEPSapEncType along with
         tmnxBsxAarpInstPeerEPSapPortId and tmnxBsxAarpInstPeerEPSapEncap
         specifies the Service Access Point (SAP) end point for the dual homed
         peer.

         The specification of a tmnxBsxAarpInstPeerEPSapEncType is mutually
         exclusive with the specification of tmnxBsxAarpInstPeerEPSdpBindId."
    DEFVAL      { unknown }
    ::= { tmnxBsxAarpInstEntry 18 }

tmnxBsxAarpInstPeerEPSdpBindId   OBJECT-TYPE
    SYNTAX      SdpBindId
    MAX-ACCESS  read-create
    STATUS      current
    DESCRIPTION
        "The value of tmnxBsxAarpInstPeerEPSdpBindId specifies the Spoke SDP
         end point for the dual homed peer.

         The specification of a tmnxBsxAarpInstPeerEPSdpBindId is mutually
         exclusive with the specification of tmnxBsxAarpInstPeerEPSapPortId,
         tmnxBsxAarpInstPeerEPSapEncap and tmnxBsxAarpInstPeerEPSapEncType."
    DEFVAL      { '0000000000000000'H }
    ::= { tmnxBsxAarpInstEntry 19 }

tmnxBsxAarpInstMasterSelectMode  OBJECT-TYPE
    SYNTAX      INTEGER {
        minimizeSwitchovers    (1),
        interChassisEfficiency (2),
        priorityBasedBalance   (3)
    }
    MAX-ACCESS  read-create
    STATUS      current
    DESCRIPTION
        "The value of tmnxBsxAarpInstMasterSelectMode specifies the methodology
         used by the system to select the master AARP instance. The value can
         be one of the following:

         minimizeSwitchovers    (0) - This mode maintains optimal AA flow
                                      detection continuity by minimizing AARP
                                      switchovers.

         interChassisEfficiency (1) - This mode minimizes inter-chassis
                                      traffic.

         priorityBasedBalance   (2) - This mode enables AA load balancing
                                      between AARP peers based on configured
                                      priority (tmnxBsxAarpInstPeerPriority)."
    DEFVAL      { minimizeSwitchovers }
    ::= { tmnxBsxAarpInstEntry 20 }

tmnxBsxAarpCommandTable          OBJECT-TYPE
    SYNTAX      SEQUENCE OF TmnxBsxAarpCommandEntry
    MAX-ACCESS  not-accessible
    STATUS      current
    DESCRIPTION
        "The tmnxBsxAarpCommandTable table allows commands to be performed on
         an AARP instance."
    ::= { tmnxBsxRedundancyObjs 3 }

tmnxBsxAarpCommandEntry          OBJECT-TYPE
    SYNTAX      TmnxBsxAarpCommandEntry
    MAX-ACCESS  not-accessible
    STATUS      current
    DESCRIPTION
        "Each tmnxBsxAarpCommandEntry allows commands to be performed on the
         corresponding AARP instance. The row exists only if the associated
         AARP instance identified by tmnxBsxAarpInstId exists in the
         tmnxBsxAarpInstTable."
    AUGMENTS    { tmnxBsxAarpInstEntry }
    ::= { tmnxBsxAarpCommandTable 1 }

TmnxBsxAarpCommandEntry          ::= SEQUENCE
{ tmnxBsxAarpCommandControl        TmnxBsxAarpCommand }

tmnxBsxAarpCommandControl        OBJECT-TYPE
    SYNTAX      TmnxBsxAarpCommand
    MAX-ACCESS  read-create
    STATUS      current
    DESCRIPTION
        "tmnxBsxAarpCommandControl allows the initiation of commands against an
         AARP instance.

         When read, this object returns the last command written to the object
         or 'noCmd(0)' if no command has been written to the object since
         initialization. The last command written may have already completed.

         When a valid command is written to tmnxBsxAarpCommandControl, the AARP
         instance performs the command."
    DEFVAL      { noCmd }
    ::= { tmnxBsxAarpCommandEntry 1 }

tmnxBsxAarpServPointTable        OBJECT-TYPE
    SYNTAX      SEQUENCE OF TmnxBsxAarpServPointEntry
    MAX-ACCESS  not-accessible
    STATUS      current
    DESCRIPTION
        "The tmnxBsxAarpServPointTable contains an entry for each service point
         associated with an AARP instance."
    ::= { tmnxBsxRedundancyObjs 4 }

tmnxBsxAarpServPointEntry        OBJECT-TYPE
    SYNTAX      TmnxBsxAarpServPointEntry
    MAX-ACCESS  not-accessible
    STATUS      current
    DESCRIPTION
        "Each tmnxBsxAarpServPointEntry represents a particular service point
         associated with an AARP instance."
    INDEX       {
        tmnxBsxAarpInstId,
        tmnxBsxAarpServPointRole,
        tmnxBsxAarpServPointType,
        tmnxBsxAarpServPoint
    }
    ::= { tmnxBsxAarpServPointTable 1 }

TmnxBsxAarpServPointEntry        ::= SEQUENCE
{
    tmnxBsxAarpServPointRole         TmnxBsxAarpServPointRole,
    tmnxBsxAarpServPointType         TmnxBsxAarpServPointType,
    tmnxBsxAarpServPoint             TmnxBsxAarpServPoint
}

tmnxBsxAarpServPointRole         OBJECT-TYPE
    SYNTAX      TmnxBsxAarpServPointRole
    MAX-ACCESS  not-accessible
    STATUS      current
    DESCRIPTION
        "The value of tmnxBsxAarpServPointRole specifies the role of the AARP
         instance service point."
    ::= { tmnxBsxAarpServPointEntry 1 }

tmnxBsxAarpServPointType         OBJECT-TYPE
    SYNTAX      TmnxBsxAarpServPointType
    MAX-ACCESS  not-accessible
    STATUS      current
    DESCRIPTION
        "The value of tmnxBsxAarpServPointType specifies the type of the AARP
         instance service point."
    ::= { tmnxBsxAarpServPointEntry 2 }

tmnxBsxAarpServPoint             OBJECT-TYPE
    SYNTAX      TmnxBsxAarpServPoint
    MAX-ACCESS  read-only
    STATUS      current
    DESCRIPTION
        "The value of tmnxBsxAarpServPoint indicates the AARP instance service
         point."
    ::= { tmnxBsxAarpServPointEntry 3 }

tmnxBsxHttpEnrichObjs            OBJECT IDENTIFIER ::= { tmnxBsxObjs 11 }

tmnxBsxHttpEnrichScalars         OBJECT IDENTIFIER ::= { tmnxBsxHttpEnrichObjs 1 }

tmnxBsxHttpEnrichLastChTime      OBJECT-TYPE
    SYNTAX      TimeStamp
    MAX-ACCESS  read-only
    STATUS      current
    DESCRIPTION
        "The value of tmnxBsxHttpEnrichLastChTime indicates the last time a
         successful set was performed on the tmnxBsxHttpEnrichTable."
    ::= { tmnxBsxHttpEnrichScalars 1 }

tmnxBsxHttpEnrichFieldLastChTime OBJECT-TYPE
    SYNTAX      TimeStamp
    MAX-ACCESS  read-only
    STATUS      current
    DESCRIPTION
        "The value of tmnxBsxHttpEnrichFieldLastChTime indicates the last time
         a successful set was performed on the tmnxBsxHttpEnrichFieldTable."
    ::= { tmnxBsxHttpEnrichScalars 2 }

tmnxBsxHttpEnrichTable           OBJECT-TYPE
    SYNTAX      SEQUENCE OF TmnxBsxHttpEnrichEntry
    MAX-ACCESS  not-accessible
    STATUS      current
    DESCRIPTION
        "The tmnxBsxHttpEnrichTable contains an entry for each HTTP header
         enrichment template configured on this system."
    ::= { tmnxBsxHttpEnrichObjs 2 }

tmnxBsxHttpEnrichEntry           OBJECT-TYPE
    SYNTAX      TmnxBsxHttpEnrichEntry
    MAX-ACCESS  not-accessible
    STATUS      current
    DESCRIPTION
        "Each tmnxBsxHttpEnrichEntry contains the definition of a HTTP header
         enrichment template."
    INDEX       {
        tmnxBsxIsaAaGroupIndex,
        IMPLIED tmnxBsxHttpEnrichName
    }
    ::= { tmnxBsxHttpEnrichTable 1 }

TmnxBsxHttpEnrichEntry           ::= SEQUENCE
{
    tmnxBsxHttpEnrichName            TNamedItem,
    tmnxBsxHttpEnrichRowStatus       RowStatus,
    tmnxBsxHttpEnrichRowLastCh       TimeStamp,
    tmnxBsxHttpEnrichEnabled         TmnxEnabledDisabled,
    tmnxBsxHttpEnrichDescription     TItemDescription
}

tmnxBsxHttpEnrichName            OBJECT-TYPE
    SYNTAX      TNamedItem
    MAX-ACCESS  not-accessible
    STATUS      current
    DESCRIPTION
        "The value of tmnxBsxHttpEnrichName specifies the name of the HTTP
         header enrichment template."
    ::= { tmnxBsxHttpEnrichEntry 1 }

tmnxBsxHttpEnrichRowStatus       OBJECT-TYPE
    SYNTAX      RowStatus
    MAX-ACCESS  read-create
    STATUS      current
    DESCRIPTION
        "The value of tmnxBsxHttpEnrichRowStatus specifies the row status. It
         allows entries to be created and deleted in the
         tmnxBsxHttpEnrichTable.

         Rows are created by specifying the value of 'createAndGo (4)', and
         deleted by specifying the value of 'destroy (6)'."
    ::= { tmnxBsxHttpEnrichEntry 2 }

tmnxBsxHttpEnrichRowLastCh       OBJECT-TYPE
    SYNTAX      TimeStamp
    MAX-ACCESS  read-only
    STATUS      current
    DESCRIPTION
        "The value of tmnxBsxHttpEnrichRowLastCh indicates the last time, since
         system startup, a successful set was performed on this row of the
         tmnxBsxHttpEnrichTable."
    ::= { tmnxBsxHttpEnrichEntry 3 }

tmnxBsxHttpEnrichEnabled         OBJECT-TYPE
    SYNTAX      TmnxEnabledDisabled
    MAX-ACCESS  read-create
    STATUS      current
    DESCRIPTION
        "The value of tmnxBsxHttpEnrichEnabled specifies whether this HTTP
         header enrichment template is enabled."
    DEFVAL      { disabled }
    ::= { tmnxBsxHttpEnrichEntry 4 }

tmnxBsxHttpEnrichDescription     OBJECT-TYPE
    SYNTAX      TItemDescription
    MAX-ACCESS  read-create
    STATUS      current
    DESCRIPTION
        "The value of tmnxBsxHttpEnrichDescription specifies the description of
         this HTTP header enrichment template."
    DEFVAL      { "" }
    ::= { tmnxBsxHttpEnrichEntry 5 }

tmnxBsxHttpEnrichFieldTable      OBJECT-TYPE
    SYNTAX      SEQUENCE OF TmnxBsxHttpEnrichFieldEntry
    MAX-ACCESS  not-accessible
    STATUS      current
    DESCRIPTION
        "The tmnxBsxHttpEnrichFieldTable contains an entry for each header
         field configured in the HTTP header enrichment template."
    ::= { tmnxBsxHttpEnrichObjs 3 }

tmnxBsxHttpEnrichFieldEntry      OBJECT-TYPE
    SYNTAX      TmnxBsxHttpEnrichFieldEntry
    MAX-ACCESS  not-accessible
    STATUS      current
    DESCRIPTION
        "Each tmnxBsxHttpEnrichEntry contains the definition of a header field
         configured in the HTTP header enrichment template."
    INDEX       {
        tmnxBsxIsaAaGroupIndex,
        tmnxBsxHttpEnrichName,
        IMPLIED tmnxBsxHttpEnrichFieldName
    }
    ::= { tmnxBsxHttpEnrichFieldTable 1 }

TmnxBsxHttpEnrichFieldEntry      ::= SEQUENCE
{
    tmnxBsxHttpEnrichFieldName       TNamedItem,
    tmnxBsxHttpEnrichFieldRowStatus  RowStatus,
    tmnxBsxHttpEnrichFieldRowLastCh  TimeStamp,
    tmnxBsxHttpEnrichFieldHeaderName SnmpAdminString,
    tmnxBsxHttpEnrichFieldAntiSpoof  TmnxEnabledDisabled,
    tmnxBsxHttpEnrichFieldEncodeType INTEGER,
    tmnxBsxHttpEnrichFieldEncodeKey  DisplayString,
    tmnxBsxHttpEnrichFieldStaticStr  SnmpAdminString,
    tmnxBsxHttpEnrichFieldCertProf   TNamedItemOrEmpty,
    tmnxBsxHttpEnrchFldCallingLineId TmnxEnabledDisabled,
    tmnxBsxHttpEnrichFieldMd5SaltStr DisplayString,
    tmnxBsxHttpEnrAesInitialVector   OCTET STRING
}

tmnxBsxHttpEnrichFieldName       OBJECT-TYPE
    SYNTAX      TNamedItem
    MAX-ACCESS  not-accessible
    STATUS      current
    DESCRIPTION
        "The value of tmnxBsxHttpEnrichFieldName specifies the header field
         configured in the HTTP header enrichment template.

         The supported HTTP header enrichment field names are defined in the
         tmnxBsxTListAttribTable in rows where the index tmnxBsxTListName has a
         value of 'http-header-field' and the index tmnxBsxTListAttribName has
         a value of 'name'."
    ::= { tmnxBsxHttpEnrichFieldEntry 1 }

tmnxBsxHttpEnrichFieldRowStatus  OBJECT-TYPE
    SYNTAX      RowStatus
    MAX-ACCESS  read-create
    STATUS      current
    DESCRIPTION
        "The value of tmnxBsxHttpEnrichFieldRowStatus specifies the row status.
         It allows entries to be created and deleted in the
         tmnxBsxHttpEnrichFieldTable.

         Rows are created by specifying the value of 'createAndGo (4)', and
         deleted by specifying the value of 'destroy (6)'."
    ::= { tmnxBsxHttpEnrichFieldEntry 2 }

tmnxBsxHttpEnrichFieldRowLastCh  OBJECT-TYPE
    SYNTAX      TimeStamp
    MAX-ACCESS  read-only
    STATUS      current
    DESCRIPTION
        "The value of tmnxBsxHttpEnrichFieldRowLastCh indicates the last time,
         since system startup, a successful set was performed on this row of
         the tmnxBsxHttpEnrichFieldTable."
    ::= { tmnxBsxHttpEnrichFieldEntry 3 }

tmnxBsxHttpEnrichFieldHeaderName OBJECT-TYPE
    SYNTAX      SnmpAdminString (SIZE (0..32))
    MAX-ACCESS  read-create
    STATUS      current
    DESCRIPTION
        "The value of tmnxBsxHttpEnrichFieldHeaderName specifies the name of
         the HTTP header field inserted by the HTTP header enrichment template.

         Once tmnxBsxHttpEnrichFieldHeaderName has a non-default value it may
         not be set back to its default."
    DEFVAL      { "" }
    ::= { tmnxBsxHttpEnrichFieldEntry 4 }

tmnxBsxHttpEnrichFieldAntiSpoof  OBJECT-TYPE
    SYNTAX      TmnxEnabledDisabled
    MAX-ACCESS  read-create
    STATUS      current
    DESCRIPTION
        "The value of tmnxBsxHttpEnrichFieldAntiSpoof specifies whether or not
         anti-spoofing is enabled. When the value of
         tmnxBsxHttpEnrichFieldAntiSpoof is enabled, if the
         tmnxBsxHttpEnrichFieldHeaderName is already included in the HTTP
         header, the system will overwrite it.

         tmnxBsxHttpEnrichFieldName is defined in tmnxBsxTListAttribTable as a
         tmnxBsxTListAttribValue with tmnxBsxTListName equal to
         'http-header-field' and with tmnxBsxTListAttribName equal to 'name'
         and with a given tmnxBsxTListAttribSet. For that given
         tmnxBsxTListAttribSet, if the tmnxBsxTListAttribValue with
         tmnxBsxTListName equal to 'http-header-field' and with
         tmnxBsxTListAttribName equal to 'anti-spoofing' has a value of '2',
         setting tmnxBsxHttpEnrichFieldAntiSpoof to 'enabled' will be rejected
         with error code 'inconsistentValue'.

         For example, if

         tmnxBsxHttpEnrichFieldName = 'imsi'
         tmnxBsxTListAttribValue.'http-header-field'.'name'.2 = 'imsi'
         tmnxBsxTListAttribValue.'http-header-field'.'anti-spoofing'.2 = '2'

         setting tmnxBsxHttpEnrichFieldAntiSpoof to 'enabled' will be rejected."
    DEFVAL      { disabled }
    ::= { tmnxBsxHttpEnrichFieldEntry 5 }

tmnxBsxHttpEnrichFieldEncodeType OBJECT-TYPE
    SYNTAX      INTEGER {
        none         (0),
        md5          (1),
        rc4          (2),
        certificate  (3),
        rc4md5Base64 (4),
        aes128       (5),
        aes256       (6),
        aes128cbc    (7),
        aes256cbc    (8),
        certBase64   (9)
    }
    MAX-ACCESS  read-create
    STATUS      current
    DESCRIPTION
        "The value of tmnxBsxHttpEnrichFieldEncodeType specifies the type of
         encoding that will be used on the field. Only the field value is
         encoded, not the field name. The encoding for rc4md5Base64 is
         Base64(RC4(<field>, MD5(key)))."
    DEFVAL      { none }
    ::= { tmnxBsxHttpEnrichFieldEntry 6 }

tmnxBsxHttpEnrichFieldEncodeKey  OBJECT-TYPE
    SYNTAX      DisplayString (SIZE (0..64))
    MAX-ACCESS  read-create
    STATUS      current
    DESCRIPTION
        "The value of tmnxBsxHttpEnrichFieldEncodeKey specifies the key
         associated with the encode method for the field name.

         A non-empty value must be specified when
         tmnxBsxHttpEnrichFieldEncodeType has been set to a value other than
         'none(0)'.

         An SNMP get request on this object always returns an empty string."
    DEFVAL      { "" }
    ::= { tmnxBsxHttpEnrichFieldEntry 7 }

tmnxBsxHttpEnrichFieldStaticStr  OBJECT-TYPE
    SYNTAX      SnmpAdminString (SIZE (0..16))
    MAX-ACCESS  read-create
    STATUS      current
    DESCRIPTION
        "The value of tmnxBsxHttpEnrichFieldStaticStr specifies the static
         string inserted by the HTTP header enrichment template."
    DEFVAL      { "" }
    ::= { tmnxBsxHttpEnrichFieldEntry 8 }

tmnxBsxHttpEnrichFieldCertProf   OBJECT-TYPE
    SYNTAX      TNamedItemOrEmpty
    MAX-ACCESS  read-create
    STATUS      current
    DESCRIPTION
        "The value of tmnxBsxHttpEnrichFieldCertProf specifies the name of the
         certificate profile to be used for encoding this field."
    DEFVAL      { "" }
    ::= { tmnxBsxHttpEnrichFieldEntry 9 }

tmnxBsxHttpEnrchFldCallingLineId OBJECT-TYPE
    SYNTAX      TmnxEnabledDisabled
    MAX-ACCESS  read-create
    STATUS      current
    DESCRIPTION
        "The value of tmnxBsxHttpEnrchFldCallingLineId specifies whether or not
         anti-spoofing is enabled for a header name of 'x-up-calling-line-id'.
         When the value of tmnxBsxHttpEnrchFldCallingLineId is enabled, if
         'x-up-calling-line-id' is already included in the HTTP header, the
         system will clear the session.

         tmnxBsxHttpEnrchFldCallingLineId only applies to field 'msisdn'.
         Setting tmnxBsxHttpEnrchFldCallingLineId to 'enabled' for any field
         other than 'msisdn' will be rejected."
    DEFVAL      { disabled }
    ::= { tmnxBsxHttpEnrichFieldEntry 10 }

tmnxBsxHttpEnrichFieldMd5SaltStr OBJECT-TYPE
    SYNTAX      DisplayString (SIZE (0..16))
    MAX-ACCESS  read-create
    STATUS      current
    DESCRIPTION
        "The value of tmnxBsxHttpEnrichFieldMd5SaltStr specifies the salt
         associated with the MD5 encode method for the field. The salt string
         is appended to the clear text field value before MD5 hash operation is
         performed."
    DEFVAL      { "" }
    ::= { tmnxBsxHttpEnrichFieldEntry 11 }

tmnxBsxHttpEnrAesInitialVector   OBJECT-TYPE
    SYNTAX      OCTET STRING (SIZE (0|16))
    MAX-ACCESS  read-create
    STATUS      current
    DESCRIPTION
        "The value of tmnxBsxHttpEnrAesInitialVector specifies the
         initialization vector associated with the encode method for AES."
    DEFVAL      { ''H }
    ::= { tmnxBsxHttpEnrichFieldEntry 12 }

tmnxBsxHttpEnrichStatTable       OBJECT-TYPE
    SYNTAX      SEQUENCE OF TmnxBsxHttpEnrichStatEntry
    MAX-ACCESS  not-accessible
    STATUS      current
    DESCRIPTION
        "The tmnxBsxHttpEnrichStatTable contains statistics for HTTP
         enrichment. Each row contains the performance-oriented statistics
         information per group and HTTP enrichment template for an ISA-AA
         uniquely identified by the tmnxChassisIndex, tmnxBsxCardSlotEsaId, and
         the tmnxBsxMdaSlotEsaVmId."
    ::= { tmnxBsxHttpEnrichObjs 4 }

tmnxBsxHttpEnrichStatEntry       OBJECT-TYPE
    SYNTAX      TmnxBsxHttpEnrichStatEntry
    MAX-ACCESS  not-accessible
    STATUS      current
    DESCRIPTION
        "Each tmnxBsxHttpEnrichStatEntry contains statistics for HTTP
         enrichment.

         An index with a valid tmnxBsxAaGrpPartIndex/tmnxBsxHttpEnrichName (an
         existing row in tmnxBsxHttpEnrichTable), tmnxChassisIndex set to one,
         and a zero value for each of tmnxBsxCardSlotEsaId and
         tmnxBsxMdaSlotEsaVmId will return the summarized per group and HTTP
         enrichment template statistics.

         Entries will appears in this table only for equipped ISA-AA MDAs
         associated with an AA group and an HTTP enrichment template."
    INDEX       {
        tmnxBsxAaGrpPartIndex,
        tmnxBsxHttpEnrichName,
        tmnxChassisIndex,
        tmnxBsxCardSlotEsaId,
        tmnxBsxMdaSlotEsaVmId
    }
    ::= { tmnxBsxHttpEnrichStatTable 1 }

TmnxBsxHttpEnrichStatEntry       ::= SEQUENCE
{
    tmnxBsxHttpEnrichStatDiscontTime TimeStamp,
    tmnxBsxHttpEnrichHCNumEnriched   Counter64,
    tmnxBsxHttpEnrichNumEnrichedLo   Counter32,
    tmnxBsxHttpEnrichNumEnrichedHi   Counter32,
    tmnxBsxHttpEnrichHCNumNoResource Counter64,
    tmnxBsxHttpEnrichNumNoResourceLo Counter32,
    tmnxBsxHttpEnrichNumNoResourceHi Counter32,
    tmnxBsxHttpEnrichHCMissngSubData Counter64,
    tmnxBsxHttpEnrichMissngSubDataLo Counter32,
    tmnxBsxHttpEnrichMissngSubDataHi Counter32,
    tmnxBsxHttpEnrichHCTplNotEnabled Counter64,
    tmnxBsxHttpEnrichTplNotEnabledLo Counter32,
    tmnxBsxHttpEnrichTplNotEnabledHi Counter32,
    tmnxBsxHttpEnrichHCTrafficChar   Counter64,
    tmnxBsxHttpEnrichTrafficCharLo   Counter32,
    tmnxBsxHttpEnrichTrafficCharHi   Counter32,
    tmnxBsxHttpEnrichHCExceedMaxPkt  Counter64,
    tmnxBsxHttpEnrichExceedMaxPktLo  Counter32,
    tmnxBsxHttpEnrichExceedMaxPktHi  Counter32,
    tmnxBsxHttpEnrichAntiSpoofMod    Counter64,
    tmnxBsxHttpEnrichNoAntiSpfShort  Counter64,
    tmnxBsxHttpEnrichSessionsDropped Counter64
}

tmnxBsxHttpEnrichStatDiscontTime OBJECT-TYPE
    SYNTAX      TimeStamp
    MAX-ACCESS  read-only
    STATUS      current
    DESCRIPTION
        "The value of tmnxBsxHttpEnrichStatDiscontTime indicates the
         SNMPv2-MIB::sysUpTime (centiseconds) when the ISA-AA MDA within the
         group has last changed status."
    ::= { tmnxBsxHttpEnrichStatEntry 1 }

tmnxBsxHttpEnrichHCNumEnriched   OBJECT-TYPE
    SYNTAX      Counter64
    MAX-ACCESS  read-only
    STATUS      current
    DESCRIPTION
        "The value of tmnxBsxHttpEnrichHCNumEnriched indicates the number of
         enriched requests."
    ::= { tmnxBsxHttpEnrichStatEntry 2 }

tmnxBsxHttpEnrichNumEnrichedLo   OBJECT-TYPE
    SYNTAX      Counter32
    MAX-ACCESS  read-only
    STATUS      current
    DESCRIPTION
        "The value of tmnxBsxHttpEnrichNumEnrichedLo indicates the lower
         32-bits of tmnxBsxHttpEnrichHCNumEnriched."
    ::= { tmnxBsxHttpEnrichStatEntry 3 }

tmnxBsxHttpEnrichNumEnrichedHi   OBJECT-TYPE
    SYNTAX      Counter32
    MAX-ACCESS  read-only
    STATUS      current
    DESCRIPTION
        "The value of tmnxBsxHttpEnrichNumEnrichedHi indicates the upper
         32-bits of tmnxBsxHttpEnrichHCNumEnriched."
    ::= { tmnxBsxHttpEnrichStatEntry 4 }

tmnxBsxHttpEnrichHCNumNoResource OBJECT-TYPE
    SYNTAX      Counter64
    MAX-ACCESS  read-only
    STATUS      current
    DESCRIPTION
        "The value of tmnxBsxHttpEnrichHCNumNoResource indicates the number of
         HTTP requests not enriched due to resource issues."
    ::= { tmnxBsxHttpEnrichStatEntry 5 }

tmnxBsxHttpEnrichNumNoResourceLo OBJECT-TYPE
    SYNTAX      Counter32
    MAX-ACCESS  read-only
    STATUS      current
    DESCRIPTION
        "The value of tmnxBsxHttpEnrichNumNoResourceLo indicates the lower
         32-bits of tmnxBsxHttpEnrichHCNumNoResource."
    ::= { tmnxBsxHttpEnrichStatEntry 6 }

tmnxBsxHttpEnrichNumNoResourceHi OBJECT-TYPE
    SYNTAX      Counter32
    MAX-ACCESS  read-only
    STATUS      current
    DESCRIPTION
        "The value of tmnxBsxHttpEnrichNumNoResourceHi indicates the upper
         32-bits of tmnxBsxHttpEnrichHCNumNoResource."
    ::= { tmnxBsxHttpEnrichStatEntry 7 }

tmnxBsxHttpEnrichHCMissngSubData OBJECT-TYPE
    SYNTAX      Counter64
    MAX-ACCESS  read-only
    STATUS      current
    DESCRIPTION
        "The value of tmnxBsxHttpEnrichHCMissngSubData indicates the number of
         HTTP requests not enriched due to missing subscriber data."
    ::= { tmnxBsxHttpEnrichStatEntry 8 }

tmnxBsxHttpEnrichMissngSubDataLo OBJECT-TYPE
    SYNTAX      Counter32
    MAX-ACCESS  read-only
    STATUS      current
    DESCRIPTION
        "The value of tmnxBsxHttpEnrichMissngSubDataLo indicates the lower
         32-bits of tmnxBsxHttpEnrichHCMissngSubData."
    ::= { tmnxBsxHttpEnrichStatEntry 9 }

tmnxBsxHttpEnrichMissngSubDataHi OBJECT-TYPE
    SYNTAX      Counter32
    MAX-ACCESS  read-only
    STATUS      current
    DESCRIPTION
        "The value of tmnxBsxHttpEnrichMissngSubDataHi indicates the upper
         32-bits of tmnxBsxHttpEnrichHCMissngSubData."
    ::= { tmnxBsxHttpEnrichStatEntry 10 }

tmnxBsxHttpEnrichHCTplNotEnabled OBJECT-TYPE
    SYNTAX      Counter64
    MAX-ACCESS  read-only
    STATUS      current
    DESCRIPTION
        "The value of tmnxBsxHttpEnrichHCTplNotEnabled indicates the number of
         HTTP requests not enriched due to the template not being enabled."
    ::= { tmnxBsxHttpEnrichStatEntry 11 }

tmnxBsxHttpEnrichTplNotEnabledLo OBJECT-TYPE
    SYNTAX      Counter32
    MAX-ACCESS  read-only
    STATUS      current
    DESCRIPTION
        "The value of tmnxBsxHttpEnrichTplNotEnabledLo indicates the lower
         32-bits of tmnxBsxHttpEnrichHCTplNotEnabled."
    ::= { tmnxBsxHttpEnrichStatEntry 12 }

tmnxBsxHttpEnrichTplNotEnabledHi OBJECT-TYPE
    SYNTAX      Counter32
    MAX-ACCESS  read-only
    STATUS      current
    DESCRIPTION
        "The value of tmnxBsxHttpEnrichTplNotEnabledHi indicates the upper
         32-bits of tmnxBsxHttpEnrichHCTplNotEnabled."
    ::= { tmnxBsxHttpEnrichStatEntry 13 }

tmnxBsxHttpEnrichHCTrafficChar   OBJECT-TYPE
    SYNTAX      Counter64
    MAX-ACCESS  read-only
    STATUS      current
    DESCRIPTION
        "The value of tmnxBsxHttpEnrichHCTrafficChar indicates the number of
         HTTP requests not enriched due to traffic characteristics."
    ::= { tmnxBsxHttpEnrichStatEntry 14 }

tmnxBsxHttpEnrichTrafficCharLo   OBJECT-TYPE
    SYNTAX      Counter32
    MAX-ACCESS  read-only
    STATUS      current
    DESCRIPTION
        "The value of tmnxBsxHttpEnrichTrafficCharLo indicates the lower
         32-bits of tmnxBsxHttpEnrichHCTrafficChar."
    ::= { tmnxBsxHttpEnrichStatEntry 15 }

tmnxBsxHttpEnrichTrafficCharHi   OBJECT-TYPE
    SYNTAX      Counter32
    MAX-ACCESS  read-only
    STATUS      current
    DESCRIPTION
        "The value of tmnxBsxHttpEnrichTrafficCharHi indicates the upper
         32-bits of tmnxBsxHttpEnrichHCTrafficChar."
    ::= { tmnxBsxHttpEnrichStatEntry 16 }

tmnxBsxHttpEnrichHCExceedMaxPkt  OBJECT-TYPE
    SYNTAX      Counter64
    MAX-ACCESS  read-only
    STATUS      current
    DESCRIPTION
        "The value of tmnxBsxHttpEnrichHCExceedMaxPkt indicates the number of
         HTTP requests not enriched due to the packet size being greater than
         the maximum HTTP enrichment packet size specified in
         tmnxBsxIsaAaGrpHttpEnrichMaxPkt."
    ::= { tmnxBsxHttpEnrichStatEntry 17 }

tmnxBsxHttpEnrichExceedMaxPktLo  OBJECT-TYPE
    SYNTAX      Counter32
    MAX-ACCESS  read-only
    STATUS      current
    DESCRIPTION
        "The value of tmnxBsxHttpEnrichExceedMaxPktLo indicates the lower
         32-bits of tmnxBsxHttpEnrichHCExceedMaxPkt."
    ::= { tmnxBsxHttpEnrichStatEntry 18 }

tmnxBsxHttpEnrichExceedMaxPktHi  OBJECT-TYPE
    SYNTAX      Counter32
    MAX-ACCESS  read-only
    STATUS      current
    DESCRIPTION
        "The value of tmnxBsxHttpEnrichExceedMaxPktHi indicates the upper
         32-bits of tmnxBsxHttpEnrichHCExceedMaxPkt."
    ::= { tmnxBsxHttpEnrichStatEntry 19 }

tmnxBsxHttpEnrichAntiSpoofMod    OBJECT-TYPE
    SYNTAX      Counter64
    MAX-ACCESS  read-only
    STATUS      current
    DESCRIPTION
        "The value of tmnxBsxHttpEnrichAntiSpoofMod indicates the number of
         HTTP header modifications that have been made for anti-spoofing. A
         value of 0 is returned if the value of tmnxBsxHttpEnrichFieldAntiSpoof
         is disabled."
    ::= { tmnxBsxHttpEnrichStatEntry 20 }

tmnxBsxHttpEnrichNoAntiSpfShort  OBJECT-TYPE
    SYNTAX      Counter64
    MAX-ACCESS  read-only
    STATUS      current
    DESCRIPTION
        "The value of tmnxBsxHttpEnrichNoAntiSpfShort indicates the number of
         HTTP header modifications that were not made for anti-spoofing due to
         an HTTP header field value being short enough to result in a packet
         size increase if anti-spoofing were applied.  A value of 0 is
         returned if the value of tmnxBsxHttpEnrichFieldAntiSpoof is disabled."
    ::= { tmnxBsxHttpEnrichStatEntry 21 }

tmnxBsxHttpEnrichSessionsDropped OBJECT-TYPE
    SYNTAX      Counter64
    MAX-ACCESS  read-only
    STATUS      current
    DESCRIPTION
        "The value of tmnxBsxHttpEnrichSessionsDropped indicates the number of
         sessions that have been dropped due to segmentation or antispoof."
    ::= { tmnxBsxHttpEnrichStatEntry 22 }

tmnxBsxHttpEnrichRATTable        OBJECT-TYPE
    SYNTAX      SEQUENCE OF TmnxBsxHttpEnrichRATEntry
    MAX-ACCESS  not-accessible
    STATUS      current
    DESCRIPTION
        "The tmnxBsxHttpEnrichRATTable contains an entry for each RAT
         configured on every HTTP-enrich field."
    ::= { tmnxBsxHttpEnrichObjs 6 }

tmnxBsxHttpEnrichRATEntry        OBJECT-TYPE
    SYNTAX      TmnxBsxHttpEnrichRATEntry
    MAX-ACCESS  not-accessible
    STATUS      current
    DESCRIPTION
        "Each tmnxBsxHttpEnrichRATEntry contains the definition of a RAT type
         and the value used for mapping it."
    INDEX       {
        tmnxBsxIsaAaGroupIndex,
        tmnxBsxHttpEnrichName,
        tmnxBsxHttpEnrichRATType
    }
    ::= { tmnxBsxHttpEnrichRATTable 1 }

TmnxBsxHttpEnrichRATEntry        ::= SEQUENCE
{
    tmnxBsxHttpEnrichRATType         TmnxBsxHttpEnrichRATType,
    tmnxBsxHttpEnrichRATString       DisplayString,
    tmnxBsxHttpEnrichRATRowStatus    RowStatus,
    tmnxBsxHttpEnrichRATRowLastChg   TimeStamp
}

tmnxBsxHttpEnrichRATType         OBJECT-TYPE
    SYNTAX      TmnxBsxHttpEnrichRATType
    MAX-ACCESS  not-accessible
    STATUS      current
    DESCRIPTION
        "The value of tmnxBsxHttpEnrichRATType indicates the RAT type of this
         entry."
    ::= { tmnxBsxHttpEnrichRATEntry 1 }

tmnxBsxHttpEnrichRATString       OBJECT-TYPE
    SYNTAX      DisplayString (SIZE (1..31))
    MAX-ACCESS  read-create
    STATUS      current
    DESCRIPTION
        "The value of tmnxBsxHttpEnrichRATString specifies the string value for
         this RAT type.

         A value for tmnxBsxHttpEnrichRATString must be specified in order to
         create a row."
    ::= { tmnxBsxHttpEnrichRATEntry 2 }

tmnxBsxHttpEnrichRATRowStatus    OBJECT-TYPE
    SYNTAX      RowStatus
    MAX-ACCESS  read-create
    STATUS      current
    DESCRIPTION
        "The value of tmnxBsxHttpEnrichRATRowStatus specifies the row status.
         It allows entries to be created and deleted in the
         tmnxBsxHttpEnrichRATTable.

         A value for tmnxBsxHttpEnrichRATString must be specified in order to
         create a row."
    ::= { tmnxBsxHttpEnrichRATEntry 3 }

tmnxBsxHttpEnrichRATRowLastChg   OBJECT-TYPE
    SYNTAX      TimeStamp
    MAX-ACCESS  read-only
    STATUS      current
    DESCRIPTION
        "The value of tmnxBsxHttpEnrichRATRowLastChg indicates the last time,
         since the system startup, the row was modified."
    ::= { tmnxBsxHttpEnrichRATEntry 4 }

tmnxBsxRadApObjs                 OBJECT IDENTIFIER ::= { tmnxBsxObjs 12 }

tmnxBsxRadApScalars              OBJECT IDENTIFIER ::= { tmnxBsxRadApObjs 1 }

tmnxBsxRadApLastChTime           OBJECT-TYPE
    SYNTAX      TimeStamp
    MAX-ACCESS  read-only
    STATUS      current
    DESCRIPTION
        "The value of tmnxBsxRadApLastChTime indicates the last time, since
         system startup, a successful set was performed on tmnxBsxRadApTable."
    ::= { tmnxBsxRadApScalars 1 }

tmnxBsxRadApServLastChTime       OBJECT-TYPE
    SYNTAX      TimeStamp
    MAX-ACCESS  read-only
    STATUS      current
    DESCRIPTION
        "The value of tmnxBsxRadApServLastChTime indicates the last time, since
         system startup, a successful set was performed on
         tmnxBsxRadApServTable."
    ::= { tmnxBsxRadApScalars 2 }

tmnxBsxRadApTable                OBJECT-TYPE
    SYNTAX      SEQUENCE OF TmnxBsxRadApEntry
    MAX-ACCESS  not-accessible
    STATUS      current
    DESCRIPTION
        "The tmnxBsxRadApTable allows configuration of RADIUS based AA
         accounting policies."
    ::= { tmnxBsxRadApObjs 2 }

tmnxBsxRadApEntry                OBJECT-TYPE
    SYNTAX      TmnxBsxRadApEntry
    MAX-ACCESS  not-accessible
    STATUS      current
    DESCRIPTION
        "Each entry represents the configuration for an AA RADIUS accounting
         policy.

         Entries in this table can be created and deleted via SNMP set
         operations to tmnxBsxRadApRowStatus.

         To delete an entry, all references to the policy must be deleted."
    INDEX       { tmnxBsxRadApName }
    ::= { tmnxBsxRadApTable 1 }

TmnxBsxRadApEntry                ::= SEQUENCE
{
    tmnxBsxRadApName                 TNamedItem,
    tmnxBsxRadApRowStatus            RowStatus,
    tmnxBsxRadApRowLastChange        TimeStamp,
    tmnxBsxRadApDescription          TItemDescription,
    tmnxBsxRadApServerRetry          Unsigned32,
    tmnxBsxRadApServerTimeout        Unsigned32,
    tmnxBsxRadApServerVRtrID         TmnxVRtrIDOrZero,
    tmnxBsxRadApServerSrcAddrType    InetAddressType,
    tmnxBsxRadApServerSrcAddr        InetAddress,
    tmnxBsxRadApServerAlgorithm      TmnxSubRadServAlgorithm,
    tmnxBsxRadApIntrmUpdateInterval  Unsigned32,
    tmnxBsxRadApSignfcntChangeDelta  Unsigned32
}

tmnxBsxRadApName                 OBJECT-TYPE
    SYNTAX      TNamedItem
    MAX-ACCESS  not-accessible
    STATUS      current
    DESCRIPTION
        "The value of tmnxBsxRadApName specifies the name of an AA RADIUS
         accounting policy."
    ::= { tmnxBsxRadApEntry 1 }

tmnxBsxRadApRowStatus            OBJECT-TYPE
    SYNTAX      RowStatus
    MAX-ACCESS  read-create
    STATUS      current
    DESCRIPTION
        "The value of tmnxBsxRadApRowStatus specifies the row status. It allows
         entries to be created and deleted in tmnxBsxRadApTable.

         Rows are created by specifying the value of 'createAndGo (4)', and
         deleted by specifying the value of 'destroy (6)'."
    ::= { tmnxBsxRadApEntry 2 }

tmnxBsxRadApRowLastChange        OBJECT-TYPE
    SYNTAX      TimeStamp
    MAX-ACCESS  read-only
    STATUS      current
    DESCRIPTION
        "The value of tmnxBsxRadApRowLastChange indicates the last time, since
         system startup, a successful set was performed on this row."
    ::= { tmnxBsxRadApEntry 3 }

tmnxBsxRadApDescription          OBJECT-TYPE
    SYNTAX      TItemDescription
    MAX-ACCESS  read-create
    STATUS      current
    DESCRIPTION
        "The value of tmnxBsxRadApDescription specifies the user provided
         description of this policy."
    DEFVAL      { "" }
    ::= { tmnxBsxRadApEntry 4 }

tmnxBsxRadApServerRetry          OBJECT-TYPE
    SYNTAX      Unsigned32 (1..10)
    MAX-ACCESS  read-create
    STATUS      current
    DESCRIPTION
        "The value of tmnxBsxRadApServerRetry specifies the maximum number of
         RADIUS request retries toward the same RADIUS server."
    DEFVAL      { 3 }
    ::= { tmnxBsxRadApEntry 5 }

tmnxBsxRadApServerTimeout        OBJECT-TYPE
    SYNTAX      Unsigned32 (1..90)
    UNITS       "seconds"
    MAX-ACCESS  read-create
    STATUS      current
    DESCRIPTION
        "The value of tmnxBsxRadApServerTimeout specifies the timeout between
         retries toward the same RADIUS server."
    DEFVAL      { 5 }
    ::= { tmnxBsxRadApEntry 6 }

tmnxBsxRadApServerVRtrID         OBJECT-TYPE
    SYNTAX      TmnxVRtrIDOrZero
    MAX-ACCESS  read-create
    STATUS      current
    DESCRIPTION
        "The value of tmnxBsxRadApServerVRtrID specifies the virtual router
         instance applicable for the set of configured RADIUS servers in
         tmnxBsxRadApServTable.

         The value of this object cannot be changed once a RADIUS server is
         configured for this policy.

         When the value is '0', both base and management router instances are
         available."
    DEFVAL      { 0 }
    ::= { tmnxBsxRadApEntry 7 }

tmnxBsxRadApServerSrcAddrType    OBJECT-TYPE
    SYNTAX      InetAddressType
    MAX-ACCESS  read-create
    STATUS      current
    DESCRIPTION
        "The value of tmnxBsxRadApServerSrcAddrType specifies the type of
         address stored in tmnxBsxRadApServerSrcAddr."
    DEFVAL      { unknown }
    ::= { tmnxBsxRadApEntry 8 }

tmnxBsxRadApServerSrcAddr        OBJECT-TYPE
    SYNTAX      InetAddress (SIZE (0|4|16))
    MAX-ACCESS  read-create
    STATUS      current
    DESCRIPTION
        "The value of tmnxBsxRadApServerSrcAddr specifies the source address of
         a RADIUS packet for AA accounting. It must be a valid unicast address;
         otherwise, a wrongValue error is returned.

         If this object is configured with the address of a router interface,
         TIMETRA-VRTR-MIB::vRiaIpAddress, the RADIUS client uses it in making a
         request to the RADIUS server.

         If the address is not configured or is not the address of one of the
         interfaces, the source address is based on the address of the RADIUS
         server. If the server address is in-band, the client uses the system
         IP address. If the server address is out-of-band, the source address
         is the address of the management interface found in
         TIMETRA-VRTR-MIB::vRiaIpAddress."
    DEFVAL      { ''H }
    ::= { tmnxBsxRadApEntry 9 }

tmnxBsxRadApServerAlgorithm      OBJECT-TYPE
    SYNTAX      TmnxSubRadServAlgorithm
    MAX-ACCESS  read-create
    STATUS      current
    DESCRIPTION
        "The value of tmnxBsxRadApServerAlgorithm specifies the algorithm used
         to select a RADIUS server from the list of configured servers in
         tmnxBsxRadApServTable."
    DEFVAL      { direct }
    ::= { tmnxBsxRadApEntry 10 }

tmnxBsxRadApIntrmUpdateInterval  OBJECT-TYPE
    SYNTAX      Unsigned32 (0 | 5..1080)
    UNITS       "minutes"
    MAX-ACCESS  read-create
    STATUS      current
    DESCRIPTION
        "The value of tmnxBsxRadApIntrmUpdateInterval specifies the interval at
         which subscriber accounting data will be updated. If set to '0', no
         interim updates will be sent."
    DEFVAL      { 0 }
    ::= { tmnxBsxRadApEntry 11 }

tmnxBsxRadApSignfcntChangeDelta  OBJECT-TYPE
    SYNTAX      Unsigned32 (0..1)
    MAX-ACCESS  read-create
    STATUS      current
    DESCRIPTION
        "The value of tmnxBsxRadApSignfcntChangeDelta specifies the delta, or
         significant change in any charging group counter, that is required for
         a RADIUS accounting request to be sent to the RADIUS server for a
         particular subscriber.

         The only supported significant change is value '1', which represents
         any change. If value '0' is specified, a request is sent even if there
         is no change."
    DEFVAL      { 0 }
    ::= { tmnxBsxRadApEntry 12 }

tmnxBsxRadApServTable            OBJECT-TYPE
    SYNTAX      SEQUENCE OF TmnxBsxRadApServEntry
    MAX-ACCESS  not-accessible
    STATUS      current
    DESCRIPTION
        "The tmnxBsxRadApServTable allows the configuration of objects related
         to a particular RADIUS server associated with a particular AA RADIUS
         accounting policy."
    ::= { tmnxBsxRadApObjs 3 }

tmnxBsxRadApServEntry            OBJECT-TYPE
    SYNTAX      TmnxBsxRadApServEntry
    MAX-ACCESS  not-accessible
    STATUS      current
    DESCRIPTION
        "Each entry represents the configuration for a particular AA RADIUS
         accounting policy and server.

         Entries in this table can be created and deleted via SNMP set
         operations to tmnxBsxRadApServRowStatus."
    INDEX       {
        tmnxBsxRadApName,
        tmnxBsxRadApServIndex
    }
    ::= { tmnxBsxRadApServTable 1 }

TmnxBsxRadApServEntry            ::= SEQUENCE
{
    tmnxBsxRadApServIndex            Unsigned32,
    tmnxBsxRadApServRowStatus        RowStatus,
    tmnxBsxRadApServRowLastChange    TimeStamp,
    tmnxBsxRadApServAddrType         InetAddressType,
    tmnxBsxRadApServAddr             InetAddress,
    tmnxBsxRadApServSecret           DisplayString,
    tmnxBsxRadApServAcctPort         Unsigned32,
    tmnxBsxRadApServOperState        TmnxOperState
}

tmnxBsxRadApServIndex            OBJECT-TYPE
    SYNTAX      Unsigned32 (1..5)
    MAX-ACCESS  not-accessible
    STATUS      current
    DESCRIPTION
        "The value of tmnxBsxRadApServIndex specifies the RADIUS server
         associated with an AA RADIUS accounting policy."
    ::= { tmnxBsxRadApServEntry 1 }

tmnxBsxRadApServRowStatus        OBJECT-TYPE
    SYNTAX      RowStatus
    MAX-ACCESS  read-create
    STATUS      current
    DESCRIPTION
        "The value of tmnxBsxRadApServRowStatus specifies the row status. It
         allows entries to be created and deleted in tmnxBsxRadApServTable.

         Rows are created by specifying the value of 'createAndGo (4)', and
         deleted by specifying the value of 'destroy (6)'."
    ::= { tmnxBsxRadApServEntry 2 }

tmnxBsxRadApServRowLastChange    OBJECT-TYPE
    SYNTAX      TimeStamp
    MAX-ACCESS  read-only
    STATUS      current
    DESCRIPTION
        "The value of tmnxBsxRadApServRowLastChange indicates the last time,
         since system startup, a successful set was performed on this row."
    ::= { tmnxBsxRadApServEntry 3 }

tmnxBsxRadApServAddrType         OBJECT-TYPE
    SYNTAX      InetAddressType
    MAX-ACCESS  read-create
    STATUS      current
    DESCRIPTION
        "The value of tmnxBsxRadApServAddrType specifies the type of address
         stored in tmnxBsxRadApServAddr."
    ::= { tmnxBsxRadApServEntry 4 }

tmnxBsxRadApServAddr             OBJECT-TYPE
    SYNTAX      InetAddress (SIZE (4|16))
    MAX-ACCESS  read-create
    STATUS      current
    DESCRIPTION
        "The value of tmnxBsxRadApServAddr specifies the IP address of the
         RADIUS server.

         A valid unicast IP address must be specified at row creation time."
    ::= { tmnxBsxRadApServEntry 5 }

tmnxBsxRadApServSecret           OBJECT-TYPE
    SYNTAX      DisplayString (SIZE (0|1..20))
    MAX-ACCESS  read-create
    STATUS      current
    DESCRIPTION
        "The value of tmnxBsxRadApServSecret specifies the secret key
         associated with the RADIUS server.

         A non-empty value must be specified at row creation time.

         An SNMP get request on this object always returns an empty string."
    ::= { tmnxBsxRadApServEntry 6 }

tmnxBsxRadApServAcctPort         OBJECT-TYPE
    SYNTAX      Unsigned32 (1..65535)
    MAX-ACCESS  read-create
    STATUS      current
    DESCRIPTION
        "The value of tmnxBsxRadApServAcctPort specifies the UDP port number on
         which to contact the RADIUS server for accounting."
    DEFVAL      { 1813 }
    ::= { tmnxBsxRadApServEntry 7 }

tmnxBsxRadApServOperState        OBJECT-TYPE
    SYNTAX      TmnxOperState
    MAX-ACCESS  read-only
    STATUS      current
    DESCRIPTION
        "The value of tmnxBsxRadApServOperState indicates the operational state
         of the RADIUS server."
    ::= { tmnxBsxRadApServEntry 8 }

tmnxBsxRadApStatTable            OBJECT-TYPE
    SYNTAX      SEQUENCE OF TmnxBsxRadApStatEntry
    MAX-ACCESS  not-accessible
    STATUS      current
    DESCRIPTION
        "The tmnxBsxRadApStatTable presents statistics of AA RADIUS accounting
         policies."
    ::= { tmnxBsxRadApObjs 4 }

tmnxBsxRadApStatEntry            OBJECT-TYPE
    SYNTAX      TmnxBsxRadApStatEntry
    MAX-ACCESS  not-accessible
    STATUS      current
    DESCRIPTION
        "Each row entry represents a collection of statistics for an AA RADIUS
         accounting policy.

         Rows in this table are created automatically by the system."
    AUGMENTS    { tmnxBsxRadApEntry }
    ::= { tmnxBsxRadApStatTable 1 }

TmnxBsxRadApStatEntry            ::= SEQUENCE
{
    tmnxBsxRadApTxRequests           Counter32,
    tmnxBsxRadApRxResponses          Counter32,
    tmnxBsxRadApReqTimeouts          Counter32,
    tmnxBsxRadApSendRetries          Counter32,
    tmnxBsxRadApSendFail             Counter32
}

tmnxBsxRadApTxRequests           OBJECT-TYPE
    SYNTAX      Counter32
    MAX-ACCESS  read-only
    STATUS      current
    DESCRIPTION
        "The value of tmnxBsxRadApTxRequests indicates the number of RADIUS
         accounting requests transmitted for this policy."
    ::= { tmnxBsxRadApStatEntry 1 }

tmnxBsxRadApRxResponses          OBJECT-TYPE
    SYNTAX      Counter32
    MAX-ACCESS  read-only
    STATUS      current
    DESCRIPTION
        "The value of tmnxBsxRadApRxResponses indicates the number of RADIUS
         accounting responses received for this policy."
    ::= { tmnxBsxRadApStatEntry 2 }

tmnxBsxRadApReqTimeouts          OBJECT-TYPE
    SYNTAX      Counter32
    MAX-ACCESS  read-only
    STATUS      current
    DESCRIPTION
        "The value of tmnxBsxRadApReqTimeouts indicates the number of RADIUS
         accounting requests which have timed out for this policy."
    ::= { tmnxBsxRadApStatEntry 3 }

tmnxBsxRadApSendRetries          OBJECT-TYPE
    SYNTAX      Counter32
    MAX-ACCESS  read-only
    STATUS      current
    DESCRIPTION
        "The value of tmnxBsxRadApSendRetries indicates the number of retries
         to a different server for a single RADIUS accounting request for this
         policy."
    ::= { tmnxBsxRadApStatEntry 4 }

tmnxBsxRadApSendFail             OBJECT-TYPE
    SYNTAX      Counter32
    MAX-ACCESS  read-only
    STATUS      current
    DESCRIPTION
        "The value of tmnxBsxRadApSendFail indicates how many RADIUS accounting
         requests failed because the packet could not be sent."
    ::= { tmnxBsxRadApStatEntry 5 }

tmnxBsxRadApServStatTable        OBJECT-TYPE
    SYNTAX      SEQUENCE OF TmnxBsxRadApServStatEntry
    MAX-ACCESS  not-accessible
    STATUS      current
    DESCRIPTION
        "The tmnxBsxRadApServStatTable presents statistics of AA RADIUS
         accounting policy servers."
    ::= { tmnxBsxRadApObjs 5 }

tmnxBsxRadApServStatEntry        OBJECT-TYPE
    SYNTAX      TmnxBsxRadApServStatEntry
    MAX-ACCESS  not-accessible
    STATUS      current
    DESCRIPTION
        "Each row represents statistics about a specific server for a specific
         AA RADIUS accounting policy.

         Rows in this table are created automatically by the system."
    AUGMENTS    { tmnxBsxRadApServEntry }
    ::= { tmnxBsxRadApServStatTable 1 }

TmnxBsxRadApServStatEntry        ::= SEQUENCE
{
    tmnxBsxRadApServTxRequests       Counter32,
    tmnxBsxRadApServRxResponses      Counter32,
    tmnxBsxRadApServReqTimeouts      Counter32,
    tmnxBsxRadApServReqSendFail      Counter32
}

tmnxBsxRadApServTxRequests       OBJECT-TYPE
    SYNTAX      Counter32
    MAX-ACCESS  read-only
    STATUS      current
    DESCRIPTION
        "The value of tmnxBsxRadApServTxRequests indicates the number of RADIUS
         accounting requests transmitted for this server."
    ::= { tmnxBsxRadApServStatEntry 1 }

tmnxBsxRadApServRxResponses      OBJECT-TYPE
    SYNTAX      Counter32
    MAX-ACCESS  read-only
    STATUS      current
    DESCRIPTION
        "The value of tmnxBsxRadApServRxResponses indicates the number of
         RADIUS accounting responses received for this server."
    ::= { tmnxBsxRadApServStatEntry 2 }

tmnxBsxRadApServReqTimeouts      OBJECT-TYPE
    SYNTAX      Counter32
    MAX-ACCESS  read-only
    STATUS      current
    DESCRIPTION
        "The value of tmnxBsxRadApServReqTimeouts indicates the number of
         RADIUS accounting requests that have timed out for this server."
    ::= { tmnxBsxRadApServStatEntry 3 }

tmnxBsxRadApServReqSendFail      OBJECT-TYPE
    SYNTAX      Counter32
    MAX-ACCESS  read-only
    STATUS      current
    DESCRIPTION
        "The value of tmnxBsxRadApServReqSendFail indicates the number of
         RADIUS accounting requests that failed because the packet could not be
         sent."
    ::= { tmnxBsxRadApServStatEntry 4 }

tmnxBsxSessionFilterObjs         OBJECT IDENTIFIER ::= { tmnxBsxObjs 13 }

tmnxBsxSessFltrScalars           OBJECT IDENTIFIER ::= { tmnxBsxSessionFilterObjs 1 }

tmnxBsxSessFltrLastChTime        OBJECT-TYPE
    SYNTAX      TimeStamp
    MAX-ACCESS  read-only
    STATUS      current
    DESCRIPTION
        "The value of tmnxBsxSessFltrLastChTime indicates the last time, since
         system startup, a successful set was performed on
         tmnxBsxSessFltrTable."
    ::= { tmnxBsxSessFltrScalars 1 }

tmnxBsxSessFltrParamsLastChTime  OBJECT-TYPE
    SYNTAX      TimeStamp
    MAX-ACCESS  read-only
    STATUS      current
    DESCRIPTION
        "The value of tmnxBsxSessFltrParamsLastChTime indicates the last time,
         since system startup, a successful set was performed on
         tmnxBsxSessFltrParamsTable."
    ::= { tmnxBsxSessFltrScalars 2 }

tmnxBsxSessFltrTable             OBJECT-TYPE
    SYNTAX      SEQUENCE OF TmnxBsxSessFltrEntry
    MAX-ACCESS  not-accessible
    STATUS      current
    DESCRIPTION
        "The tmnxBsxSessFltrTable contains a list of session filters for each
         application-assurance group."
    ::= { tmnxBsxSessionFilterObjs 2 }

tmnxBsxSessFltrEntry             OBJECT-TYPE
    SYNTAX      TmnxBsxSessFltrEntry
    MAX-ACCESS  not-accessible
    STATUS      current
    DESCRIPTION
        "Each entry represents the configuration for a particular AA session
         filter.

         Entries in this table can be created and deleted via SNMP set
         operations to tmnxBsxSessFltrRowStatus."
    INDEX       {
        tmnxBsxAaGrpPartIndex,
        tmnxBsxSessFltrName
    }
    ::= { tmnxBsxSessFltrTable 1 }

TmnxBsxSessFltrEntry             ::= SEQUENCE
{
    tmnxBsxSessFltrName              TNamedItem,
    tmnxBsxSessFltrRowStatus         RowStatus,
    tmnxBsxSessFltrRowLastChange     TimeStamp,
    tmnxBsxSessFltrDescription       TItemDescription,
    tmnxBsxSessFltrDefaultAction     TmnxBsxFltrAction,
    tmnxBsxSessFltrDefActEventLog    TNamedItemOrEmpty
}

tmnxBsxSessFltrName              OBJECT-TYPE
    SYNTAX      TNamedItem
    MAX-ACCESS  not-accessible
    STATUS      current
    DESCRIPTION
        "The value of tmnxBsxSessFltrName specifies the name of the session
         filter configuration."
    ::= { tmnxBsxSessFltrEntry 1 }

tmnxBsxSessFltrRowStatus         OBJECT-TYPE
    SYNTAX      RowStatus
    MAX-ACCESS  read-create
    STATUS      current
    DESCRIPTION
        "The value of tmnxBsxSessFltrRowStatus specifies the row status. It
         allows entries to be created and deleted in tmnxBsxSessFltrTable.

         Rows are created by specifying the value of 'createAndGo (4)', and
         deleted by specifying the value of 'destroy (6)'."
    ::= { tmnxBsxSessFltrEntry 2 }

tmnxBsxSessFltrRowLastChange     OBJECT-TYPE
    SYNTAX      TimeStamp
    MAX-ACCESS  read-only
    STATUS      current
    DESCRIPTION
        "The value of tmnxBsxSessFltrRowLastChange indicates the last time,
         since system startup, a successful set was performed on this row."
    ::= { tmnxBsxSessFltrEntry 3 }

tmnxBsxSessFltrDescription       OBJECT-TYPE
    SYNTAX      TItemDescription
    MAX-ACCESS  read-create
    STATUS      current
    DESCRIPTION
        "The value of tmnxBsxSessFltrDescription specifies the description of
         the session filter."
    DEFVAL      { "" }
    ::= { tmnxBsxSessFltrEntry 4 }

tmnxBsxSessFltrDefaultAction     OBJECT-TYPE
    SYNTAX      TmnxBsxFltrAction
    MAX-ACCESS  read-create
    STATUS      current
    DESCRIPTION
        "The value of tmnxBsxSessFltrDefaultAction specifies the default action
         to take for packets that do not match any filter entries."
    DEFVAL      { deny }
    ::= { tmnxBsxSessFltrEntry 5 }

tmnxBsxSessFltrDefActEventLog    OBJECT-TYPE
    SYNTAX      TNamedItemOrEmpty
    MAX-ACCESS  read-create
    STATUS      current
    DESCRIPTION
        "The value of tmnxBsxSessFltrDefActEventLog specifies if the default
         action taken (tmnxBsxSessFltrDefaultAction) should be event logged to
         the named tmnxBsxEventLogEntry."
    DEFVAL      { "" }
    ::= { tmnxBsxSessFltrEntry 6 }

tmnxBsxSessFltrParamsTable       OBJECT-TYPE
    SYNTAX      SEQUENCE OF TmnxBsxSessFltrParamsEntry
    MAX-ACCESS  not-accessible
    STATUS      current
    DESCRIPTION
        "The tmnxBsxSessFltrParamsTable contains a list of match entries for
         each application-assurance session filter."
    ::= { tmnxBsxSessionFilterObjs 3 }

tmnxBsxSessFltrParamsEntry       OBJECT-TYPE
    SYNTAX      TmnxBsxSessFltrParamsEntry
    MAX-ACCESS  not-accessible
    STATUS      current
    DESCRIPTION
        "Each entry represents the configuration for a particular
         Application-Assurance session filter match entry.  Every
         session filter can have zero or more session
         filter match entries.

         A session filter with no match entries will match every packet and the
         default action, as indicated by tmnxBsxSessFltrDefaultAction, will be
         taken.

         Entries in this table can be created and deleted via SNMP set
         operations to tmnxBsxSessFltrParamsRowStatus."
    INDEX       {
        tmnxBsxAaGrpPartIndex,
        tmnxBsxSessFltrName,
        tmnxBsxSessFltrParamsEntryId
    }
    ::= { tmnxBsxSessFltrParamsTable 1 }

TmnxBsxSessFltrParamsEntry       ::= SEQUENCE
{
    tmnxBsxSessFltrParamsEntryId     TEntryId,
    tmnxBsxSessFltrParamsRowStatus   RowStatus,
    tmnxBsxSessFltrParamsRowLastCh   TimeStamp,
    tmnxBsxSessFltrParamsDescription TItemDescription,
    tmnxBsxSessFltrParamsAction      TmnxBsxSessionFilterAction,
    tmnxBsxSessFltrParamsIpProtocol  TIpProtocol,
    tmnxBsxSessFltrParamsSrcAddrType InetAddressType,
    tmnxBsxSessFltrParamsSrcAddress  InetAddress,
    tmnxBsxSessFltrParamsSrcAddrLen  InetAddressPrefixLength,
    tmnxBsxSessFltrParamsDstAddrType InetAddressType,
    tmnxBsxSessFltrParamsDstAddress  InetAddress,
    tmnxBsxSessFltrParamsDstAddrLen  InetAddressPrefixLength,
    tmnxBsxSessFltrParamsSrcPortLVal TTcpUdpPort,
    tmnxBsxSessFltrParamsSrcPortHVal TTcpUdpPort,
    tmnxBsxSessFltrParamsSrcPortOp   TmnxBsxOperator,
    tmnxBsxSessFltrParamsDstPortLVal TTcpUdpPort,
    tmnxBsxSessFltrParamsDstPortHVal TTcpUdpPort,
    tmnxBsxSessFltrParamsDstPortOp   TmnxBsxOperator,
    tmnxBsxSessFltrParamsSrcPfxList  TNamedItemOrEmpty,
    tmnxBsxSessFltrParamsDstPfxList  TNamedItemOrEmpty,
    tmnxBsxSessFltrParamsActEventLog TNamedItemOrEmpty,
    tmnxBsxSessFltrParamsActHttpRedr TNamedItemOrEmpty,
    tmnxBsxSessFltrParamsDstDnsCache TNamedItemOrEmpty,
    tmnxBsxSessFltrParamsActTcpOpt   TNamedItemOrEmpty,
    tmnxBsxSessFltrParamsSrcPortList TNamedItemOrEmpty,
    tmnxBsxSessFltrParamsDstPortList TNamedItemOrEmpty,
    tmnxBsxSessFltrParamsReDirPort   TTcpUdpPort,
    tmnxBsxSessFltrParamsReDirAddr   InetAddress,
    tmnxBsxSessFltrParamsReDirAdrTyp InetAddressType
}

tmnxBsxSessFltrParamsEntryId     OBJECT-TYPE
    SYNTAX      TEntryId
    MAX-ACCESS  not-accessible
    STATUS      current
    DESCRIPTION
        "The value of tmnxBsxSessFltrParamsEntryId along with
         tmnxBsxSessFltrName specifies each session filter match entry."
    ::= { tmnxBsxSessFltrParamsEntry 1 }

tmnxBsxSessFltrParamsRowStatus   OBJECT-TYPE
    SYNTAX      RowStatus
    MAX-ACCESS  read-create
    STATUS      current
    DESCRIPTION
        "The value of tmnxBsxSessFltrParamsRowStatus specifies the row status.
         It allows entries to be created and deleted in
         tmnxBsxSessFltrParamsTable.

         Rows are created by specifying the value of 'createAndGo (4)', and
         deleted by specifying the value of 'destroy (6)'."
    ::= { tmnxBsxSessFltrParamsEntry 2 }

tmnxBsxSessFltrParamsRowLastCh   OBJECT-TYPE
    SYNTAX      TimeStamp
    MAX-ACCESS  read-only
    STATUS      current
    DESCRIPTION
        "The value of tmnxBsxSessFltrParamsRowLastCh indicates the last time,
         since system startup, a successful set was performed on this row."
    ::= { tmnxBsxSessFltrParamsEntry 3 }

tmnxBsxSessFltrParamsDescription OBJECT-TYPE
    SYNTAX      TItemDescription
    MAX-ACCESS  read-create
    STATUS      current
    DESCRIPTION
        "The value of tmnxBsxSessFltrParamsDescription specifies the
         description of the session filter entry."
    DEFVAL      { "" }
    ::= { tmnxBsxSessFltrParamsEntry 4 }

tmnxBsxSessFltrParamsAction      OBJECT-TYPE
    SYNTAX      TmnxBsxSessionFilterAction
    MAX-ACCESS  read-create
    STATUS      current
    DESCRIPTION
        "The value of tmnxBsxSessFltrParamsAction specifies the action to take
         for packets which match this session filter entry.

         The action 'httpRedirect (3)' is only supported when
         tmnxBsxSessFltrParamsActHttpRedr has a non-default value set in the
         same PDU.

         The action 'tcpOptimizer (4)' is only supported when
         tmnxBsxSessFltrParamsActTcpOpt has a non-default value set in the same
         PDU."
    DEFVAL      { deny }
    ::= { tmnxBsxSessFltrParamsEntry 5 }

tmnxBsxSessFltrParamsIpProtocol  OBJECT-TYPE
    SYNTAX      TIpProtocol
    MAX-ACCESS  read-create
    STATUS      current
    DESCRIPTION
        "The value of tmnxBsxSessFltrParamsIpProtocol specifies the
         IP protocol to match.  A value of -1 indicates disable matching on IP
         protocol. "
    DEFVAL      { -1 }
    ::= { tmnxBsxSessFltrParamsEntry 6 }

tmnxBsxSessFltrParamsSrcAddrType OBJECT-TYPE
    SYNTAX      InetAddressType
    MAX-ACCESS  read-create
    STATUS      current
    DESCRIPTION
        "The value of tmnxBsxSessFltrParamsSrcAddrType specifies the type of
         address contained in tmnxBsxSessFltrParamsSrcAddress.

         A value of 'unknown' specifies that no matching is to be done on
         source address basis.

         A non-default address type is only supported when
         tmnxBsxSessFltrParamsSrcPfxList has a default value."
    DEFVAL      { unknown }
    ::= { tmnxBsxSessFltrParamsEntry 7 }

tmnxBsxSessFltrParamsSrcAddress  OBJECT-TYPE
    SYNTAX      InetAddress (SIZE (0|4|16))
    MAX-ACCESS  read-create
    STATUS      current
    DESCRIPTION
        "The value of tmnxBsxSessFltrParamsSrcAddress specifies the source
         address to match.

         A non-default address is only supported when
         tmnxBsxSessFltrParamsSrcPfxList has a default value."
    DEFVAL      { ''H }
    ::= { tmnxBsxSessFltrParamsEntry 8 }

tmnxBsxSessFltrParamsSrcAddrLen  OBJECT-TYPE
    SYNTAX      InetAddressPrefixLength (0..128)
    MAX-ACCESS  read-create
    STATUS      current
    DESCRIPTION
        "The value of tmnxBsxSessFltrParamsSrcAddrLen specifies the number of
         relevant bits of the tmnxBsxSessFltrParamsSrcAddress.

         A non-default address length is only supported when
         tmnxBsxSessFltrParamsSrcPfxList has a default value."
    DEFVAL      { 0 }
    ::= { tmnxBsxSessFltrParamsEntry 9 }

tmnxBsxSessFltrParamsDstAddrType OBJECT-TYPE
    SYNTAX      InetAddressType
    MAX-ACCESS  read-create
    STATUS      current
    DESCRIPTION
        "The value of tmnxBsxSessFltrParamsDstAddrType specifies the type of
         address contained in tmnxBsxSessFltrParamsDstAddress.

         A value of 'unknown' specifies that no matching is to be done on
         destination address basis.

         A non-default address type is only supported when
         tmnxBsxSessFltrParamsDstDnsCache and tmnxBsxSessFltrParamsDstPfxList
         have default values."
    DEFVAL      { unknown }
    ::= { tmnxBsxSessFltrParamsEntry 10 }

tmnxBsxSessFltrParamsDstAddress  OBJECT-TYPE
    SYNTAX      InetAddress (SIZE (0|4|16))
    MAX-ACCESS  read-create
    STATUS      current
    DESCRIPTION
        "The value of tmnxBsxSessFltrParamsDstAddress specifies the destination
         address to match.

         A non-default address is only supported when
         tmnxBsxSessFltrParamsDstDnsCache and tmnxBsxSessFltrParamsDstPfxList
         have default values."
    DEFVAL      { ''H }
    ::= { tmnxBsxSessFltrParamsEntry 11 }

tmnxBsxSessFltrParamsDstAddrLen  OBJECT-TYPE
    SYNTAX      InetAddressPrefixLength (0..128)
    MAX-ACCESS  read-create
    STATUS      current
    DESCRIPTION
        "The value of tmnxBsxSessFltrParamsDstAddrLen specifies the number of
         relevant bits of the tmnxBsxSessFltrParamsDstAddress.

         A non-default address length is only supported when
         tmnxBsxSessFltrParamsDstDnsCache and tmnxBsxSessFltrParamsDstPfxList
         have default values."
    DEFVAL      { 0 }
    ::= { tmnxBsxSessFltrParamsEntry 12 }

tmnxBsxSessFltrParamsSrcPortLVal OBJECT-TYPE
    SYNTAX      TTcpUdpPort
    MAX-ACCESS  read-create
    STATUS      current
    DESCRIPTION
        "The value of tmnxBsxSessFltrParamsSrcPortLVal specifies the low source
         TCP or UDP port number to match. tmnxBsxSessFltrParamsSrcPortLVal must
         be less than or equal to tmnxBsxSessFltrParamsSrcPortHVal, and is used
         when tmnxBsxSessFltrParamsSrcPortOp is not 'none (0)'."
    DEFVAL      { 0 }
    ::= { tmnxBsxSessFltrParamsEntry 13 }

tmnxBsxSessFltrParamsSrcPortHVal OBJECT-TYPE
    SYNTAX      TTcpUdpPort
    MAX-ACCESS  read-create
    STATUS      current
    DESCRIPTION
        "The value of tmnxBsxSessFltrParamsSrcPortHVal specifies the high
         source TCP or UDP port number to match.
         tmnxBsxSessFltrParamsSrcPortHVal must be greater than or equal to
         tmnxBsxSessFltrParamsSrcPortLVal, and is used when
         tmnxBsxSessFltrParamsSrcPortOp is not 'none (0)'."
    DEFVAL      { 0 }
    ::= { tmnxBsxSessFltrParamsEntry 14 }

tmnxBsxSessFltrParamsSrcPortOp   OBJECT-TYPE
    SYNTAX      TmnxBsxOperator
    MAX-ACCESS  read-create
    STATUS      current
    DESCRIPTION
        "The value of tmnxBsxSessFltrParamsSrcPortOp specifies the operator to
         apply in relation to the tmnxBsxSessFltrParamsSrcPortLVal and
         tmnxBsxSessFltrParamsSrcPortHVal objects.

         A value of 'none (0)' indicates that no match is done on the
         tmnxBsxSessFltrParamsSrcPortLVal and tmnxBsxSessFltrParamsSrcPortHVal
         objects."
    DEFVAL      { none }
    ::= { tmnxBsxSessFltrParamsEntry 15 }

tmnxBsxSessFltrParamsDstPortLVal OBJECT-TYPE
    SYNTAX      TTcpUdpPort
    MAX-ACCESS  read-create
    STATUS      current
    DESCRIPTION
        "The value of tmnxBsxSessFltrParamsDstPortLVal specifies the low source
         TCP or UDP port number to match. tmnxBsxSessFltrParamsDstPortLVal must
         be less than or equal to tmnxBsxSessFltrParamsDstPortHVal, and is used
         when tmnxBsxSessFltrParamsDstPortOp is not 'none (0)'."
    DEFVAL      { 0 }
    ::= { tmnxBsxSessFltrParamsEntry 16 }

tmnxBsxSessFltrParamsDstPortHVal OBJECT-TYPE
    SYNTAX      TTcpUdpPort
    MAX-ACCESS  read-create
    STATUS      current
    DESCRIPTION
        "The value of tmnxBsxSessFltrParamsDstPortHVal specifies the high
         source TCP or UDP port number to match.
         tmnxBsxSessFltrParamsDstPortHVal must be greater than or equal to
         tmnxBsxSessFltrParamsDstPortLVal, and is used when
         tmnxBsxSessFltrParamsDstPortOp is not 'none (0)'."
    DEFVAL      { 0 }
    ::= { tmnxBsxSessFltrParamsEntry 17 }

tmnxBsxSessFltrParamsDstPortOp   OBJECT-TYPE
    SYNTAX      TmnxBsxOperator
    MAX-ACCESS  read-create
    STATUS      current
    DESCRIPTION
        "The value of tmnxBsxSessFltrParamsDstPortOp specifies the operator to
         apply in relation to the tmnxBsxSessFltrParamsDstPortLVal and
         tmnxBsxSessFltrParamsDstPortHVal objects.

         A value of 'none (0)' indicates that no match is done on the
         tmnxBsxSessFltrParamsDstPortLVal and tmnxBsxSessFltrParamsDstPortHVal
         objects."
    DEFVAL      { none }
    ::= { tmnxBsxSessFltrParamsEntry 18 }

tmnxBsxSessFltrParamsSrcPfxList  OBJECT-TYPE
    SYNTAX      TNamedItemOrEmpty
    MAX-ACCESS  read-create
    STATUS      current
    DESCRIPTION
        "The value of tmnxBsxSessFltrParamsSrcPfxList specifies the prefix list
         to use when matching the source address.

         A non-default prefix list is only supported when
         tmnxBsxSessFltrParamsSrcAddrType, tmnxBsxSessFltrParamsSrcAddrLen, and
         tmnxBsxSessFltrParamsSrcAddress have default values."
    DEFVAL      { "" }
    ::= { tmnxBsxSessFltrParamsEntry 19 }

tmnxBsxSessFltrParamsDstPfxList  OBJECT-TYPE
    SYNTAX      TNamedItemOrEmpty
    MAX-ACCESS  read-create
    STATUS      current
    DESCRIPTION
        "The value of tmnxBsxSessFltrParamsDstPfxList specifies the prefix list
         to use when matching the destination address.

         A non-default prefix list is only supported when
         tmnxBsxSessFltrParamsDstAddress, tmnxBsxSessFltrParamsDstAddrType,
         tmnxBsxSessFltrParamsDstAddrLen, and tmnxBsxSessFltrParamsDstDnsCache
         have default values."
    DEFVAL      { "" }
    ::= { tmnxBsxSessFltrParamsEntry 20 }

tmnxBsxSessFltrParamsActEventLog OBJECT-TYPE
    SYNTAX      TNamedItemOrEmpty
    MAX-ACCESS  read-create
    STATUS      current
    DESCRIPTION
        "The value of tmnxBsxSessFltrParamsActEventLog specifies if the action
         taken (tmnxBsxSessFltrParamsAction) should be event logged to the
         named tmnxBsxEventLogEntry."
    DEFVAL      { "" }
    ::= { tmnxBsxSessFltrParamsEntry 21 }

tmnxBsxSessFltrParamsActHttpRedr OBJECT-TYPE
    SYNTAX      TNamedItemOrEmpty
    MAX-ACCESS  read-create
    STATUS      current
    DESCRIPTION
        "The value of tmnxBsxSessFltrParamsActHttpRedr specifies the HTTP
         redirect that will be applied as defined in the tmnxBsxHttpRedirTable.
         An empty string indicates no HTTP redirect is performed.

         A non-default HTTP redirect is only supported when
         tmnxBsxSessFltrParamsAction has a value of 'httpRedirect (3)'."
    DEFVAL      { "" }
    ::= { tmnxBsxSessFltrParamsEntry 22 }

tmnxBsxSessFltrParamsDstDnsCache OBJECT-TYPE
    SYNTAX      TNamedItemOrEmpty
    MAX-ACCESS  read-create
    STATUS      current
    DESCRIPTION
        "The value of tmnxBsxSessFltrParamsDstDnsCache specifies the DNS IP
         cache to use when matching the destination address, as defined in the
         tmnxBsxDnsIpCacheTable.

         A non-default DNP IP cache is only supported when
         tmnxBsxSessFltrParamsDstAddress, tmnxBsxSessFltrParamsDstAddrType,
         tmnxBsxSessFltrParamsDstAddrLen, and tmnxBsxSessFltrParamsDstPfxList
         have default values."
    DEFVAL      { "" }
    ::= { tmnxBsxSessFltrParamsEntry 23 }

tmnxBsxSessFltrParamsActTcpOpt   OBJECT-TYPE
    SYNTAX      TNamedItemOrEmpty
    MAX-ACCESS  read-create
    STATUS      current
    DESCRIPTION
        "The value of tmnxBsxSessFltrParamsActTcpOpt specifies the TCP
         optimizer that will be applied as defined in the tmnxBsxTcpOptTable.
         An empty string indicates no TCP optimization is performed.

         A non-default TCP optimizer is only supported when
         tmnxBsxSessFltrParamsAction has a value of 'tcpOptimizer (4)'."
    DEFVAL      { "" }
    ::= { tmnxBsxSessFltrParamsEntry 24 }

tmnxBsxSessFltrParamsSrcPortList OBJECT-TYPE
    SYNTAX      TNamedItemOrEmpty
    MAX-ACCESS  read-create
    STATUS      current
    DESCRIPTION
        "The value of tmnxBsxSessFltrParamsSrcPortList specifies the port list
         to use when matching the source address.

         The value tmnxBsxSessFltrParamsSrcPortList can only be set if the
         value of tmnxBsxSessFltrParamsIpProtocol is set to a non-default
         value."
    DEFVAL      { "" }
    ::= { tmnxBsxSessFltrParamsEntry 26 }

tmnxBsxSessFltrParamsDstPortList OBJECT-TYPE
    SYNTAX      TNamedItemOrEmpty
    MAX-ACCESS  read-create
    STATUS      current
    DESCRIPTION
        "The value of tmnxBsxSessFltrParamsDstPortList specifies the port list
         to use when matching the destination address.

         The value tmnxBsxSessFltrParamsDstPortList can only be set if the
         value of tmnxBsxSessFltrParamsIpProtocol is set to non-default value."
    DEFVAL      { "" }
    ::= { tmnxBsxSessFltrParamsEntry 27 }

tmnxBsxSessFltrParamsReDirPort   OBJECT-TYPE
    SYNTAX      TTcpUdpPort
    MAX-ACCESS  read-create
    STATUS      current
    DESCRIPTION
        "The value of tmnxBsxSessFltrParamsReDirPort specifies the port used to
         remark the destination TCP/UDP port of the session's traffic.

         If 0 is specified, the destination port is not remarked.

         A non-default value is only supported when tmnxBsxSessFltrParamsAction
         has a value of 'l3l4Redirect (7)'."
    DEFVAL      { 0 }
    ::= { tmnxBsxSessFltrParamsEntry 28 }

tmnxBsxSessFltrParamsReDirAddr   OBJECT-TYPE
    SYNTAX      InetAddress (SIZE (0|4|16))
    MAX-ACCESS  read-create
    STATUS      current
    DESCRIPTION
        "The value of tmnxBsxSessFltrParamsReDirAddr specifies the address used
         to remark the destination address of the session's traffic.

         A non-default value is only supported when tmnxBsxSessFltrParamsAction
         has a value of 'l3l4Redirect (7)'."
    DEFVAL      { ''H }
    ::= { tmnxBsxSessFltrParamsEntry 29 }

tmnxBsxSessFltrParamsReDirAdrTyp OBJECT-TYPE
    SYNTAX      InetAddressType
    MAX-ACCESS  read-create
    STATUS      current
    DESCRIPTION
        "The value of tmnxBsxSessFltrParamsReDirAdrTyp specifies the type of
         address stored in tmnxBsxSessFltrParamsReDirAddr.

         When specifying the value of tmnxBsxSessFltrParamsReDirAdrTyp,
         tmnxBsxSessFltrParamsReDirAddr must also be specified in the same SNMP
         Set PDU.

         A non-default value is only supported when tmnxBsxSessFltrParamsAction
         has a value of 'l3l4Redirect (7)'."
    DEFVAL      { unknown }
    ::= { tmnxBsxSessFltrParamsEntry 30 }

tmnxBsxSessFltrStatsTable        OBJECT-TYPE
    SYNTAX      SEQUENCE OF TmnxBsxSessFltrStatsEntry
    MAX-ACCESS  not-accessible
    STATUS      current
    DESCRIPTION
        "The tmnxBsxSessFltrStatsTable contains the application assurance
         session filter statistics."
    ::= { tmnxBsxSessionFilterObjs 4 }

tmnxBsxSessFltrStatsEntry        OBJECT-TYPE
    SYNTAX      TmnxBsxSessFltrStatsEntry
    MAX-ACCESS  not-accessible
    STATUS      current
    DESCRIPTION
        "Each tmnxBsxSessFltrStatsEntry indicates statistics available for each
         application assurance session filter match entry."
    INDEX       {
        tmnxBsxAaGrpPartIndex,
        tmnxBsxSessFltrName,
        tmnxBsxSessFltrParamsEntryId
    }
    ::= { tmnxBsxSessFltrStatsTable 1 }

TmnxBsxSessFltrStatsEntry        ::= SEQUENCE
{
    tmnxBsxSessFltrStatsFlows        Counter64,
    tmnxBsxSessFltrStatsFlowsLo      Counter32,
    tmnxBsxSessFltrStatsFlowsHi      Counter32
}

tmnxBsxSessFltrStatsFlows        OBJECT-TYPE
    SYNTAX      Counter64
    MAX-ACCESS  read-only
    STATUS      current
    DESCRIPTION
        "The value of tmnxBsxSessFltrStatsFlows indicates the number of flows
         that have hit this entry."
    ::= { tmnxBsxSessFltrStatsEntry 1 }

tmnxBsxSessFltrStatsFlowsLo      OBJECT-TYPE
    SYNTAX      Counter32
    MAX-ACCESS  read-only
    STATUS      current
    DESCRIPTION
        "The value of tmnxBsxSessFltrStatsFlowsLo indicates the lower 32-bits
         of tmnxBsxSessFltrStatsFlows."
    ::= { tmnxBsxSessFltrStatsEntry 2 }

tmnxBsxSessFltrStatsFlowsHi      OBJECT-TYPE
    SYNTAX      Counter32
    MAX-ACCESS  read-only
    STATUS      current
    DESCRIPTION
        "The value of tmnxBsxSessFltrStatsFlowsHi indicates the upper 32-bits
         of tmnxBsxSessFltrStatsFlows."
    ::= { tmnxBsxSessFltrStatsEntry 3 }

tmnxBsxUrlFilterObjs             OBJECT IDENTIFIER ::= { tmnxBsxObjs 14 }

tmnxBsxUrlFilterScalars          OBJECT IDENTIFIER ::= { tmnxBsxUrlFilterObjs 1 }

tmnxBsxUrlFilterLastChangeTime   OBJECT-TYPE
    SYNTAX      TimeStamp
    MAX-ACCESS  read-only
    STATUS      current
    DESCRIPTION
        "The value of tmnxBsxUrlFilterLastChangeTime indicates the last time,
         since system startup, a successful set was performed on
         tmnxBsxUrlFilterTable."
    ::= { tmnxBsxUrlFilterScalars 1 }

tmnxBsxIcapServerLastChangeTime  OBJECT-TYPE
    SYNTAX      TimeStamp
    MAX-ACCESS  read-only
    STATUS      current
    DESCRIPTION
        "The value of tmnxBsxIcapServerLastChangeTime indicates the last time,
         since system startup, a successful set was performed on
         tmnxBsxIcapServerTable."
    ::= { tmnxBsxUrlFilterScalars 2 }

tmnxBsxUrlFltrUrlListLastCTime   OBJECT-TYPE
    SYNTAX      TimeStamp
    MAX-ACCESS  read-only
    STATUS      current
    DESCRIPTION
        "The value of tmnxBsxUrlFltrUrlListLastCTime indicates the last time,
         since system startup, a successful SNMP set on
         tmnxBsxUrlFltrUrlListTable caused a value to change."
    ::= { tmnxBsxUrlFilterScalars 3 }

tmnxBsxUrlFltrWsPrfListLastCTime OBJECT-TYPE
    SYNTAX      TimeStamp
    MAX-ACCESS  read-only
    STATUS      current
    DESCRIPTION
        "The value of tmnxBsxUrlFltrWsPrfListLastCTime indicates the last time,
         since system startup, a successful SNMP set on
         tmnxBsxUrlFltrWebServProfTable caused a value to change."
    ::= { tmnxBsxUrlFilterScalars 4 }

tmnxBsxUrlFltrWsCatListLastCTime OBJECT-TYPE
    SYNTAX      TimeStamp
    MAX-ACCESS  read-only
    STATUS      current
    DESCRIPTION
        "The value of tmnxBsxUrlFltrWsCatListLastCTime indicates the last time,
         since system startup, a successful SNMP set on
         tmnxBsxUrlFltWebSerCategoryTable caused a value to change."
    ::= { tmnxBsxUrlFilterScalars 5 }

tmnxBsxUrlFltrWsClasOvrLastCTime OBJECT-TYPE
    SYNTAX      TimeStamp
    MAX-ACCESS  read-only
    STATUS      current
    DESCRIPTION
        "The value of tmnxBsxUrlFltrWsClasOvrLastCTime indicates the last time,
         since system startup, a successful SNMP set on
         tmnxBsxUrlFltrWSClassOvrdTable  caused a value to change."
    ::= { tmnxBsxUrlFilterScalars 6 }

tmnxBsxWebServServerLastChgTime  OBJECT-TYPE
    SYNTAX      TimeStamp
    MAX-ACCESS  read-only
    STATUS      current
    DESCRIPTION
        "The value of tmnxBsxWebServServerLastChgTime indicates the last time,
         since system startup, a successful set was performed on
         tmnxBsxWebServServerTable."
    ::= { tmnxBsxUrlFilterScalars 7 }

tmnxBsxUrlFilterTable            OBJECT-TYPE
    SYNTAX      SEQUENCE OF TmnxBsxUrlFilterEntry
    MAX-ACCESS  not-accessible
    STATUS      current
    DESCRIPTION
        "The tmnxBsxUrlFilterTable contains a list of URL filters for each
         Application Assurance group."
    ::= { tmnxBsxUrlFilterObjs 2 }

tmnxBsxUrlFilterEntry            OBJECT-TYPE
    SYNTAX      TmnxBsxUrlFilterEntry
    MAX-ACCESS  not-accessible
    STATUS      current
    DESCRIPTION
        "Each entry represents the configuration for a particular AA URL
         filter.

         Entries in this table can be created and deleted via SNMP set
         operations to tmnxBsxUrlFilterRowStatus."
    INDEX       {
        tmnxBsxIsaAaGroupIndex,
        tmnxBsxUrlFilterName
    }
    ::= { tmnxBsxUrlFilterTable 1 }

TmnxBsxUrlFilterEntry            ::= SEQUENCE
{
    tmnxBsxUrlFilterName             TNamedItem,
    tmnxBsxUrlFilterRowStatus        RowStatus,
    tmnxBsxUrlFilterRowLastChange    TimeStamp,
    tmnxBsxUrlFilterAdminState       TmnxAdminState,
    tmnxBsxUrlFilterDescription      TItemDescription,
    tmnxBsxUrlFilterServicePortVlan  VlanIdOrNone,
    tmnxBsxUrlFilterDefaultAction    INTEGER,
    tmnxBsxUrlFilterHttpRedirName    TNamedItemOrEmpty,
    tmnxBsxUrlFilterIcapHttpRedir    TNamedItemOrEmpty,
    tmnxBsxUrlFilterHttpReqFilter    INTEGER,
    tmnxBsxUrlFilterIcapCustXHeader  TNamedItemOrEmpty,
    tmnxBsxUrlFltrWebServClassifyId  TmnxBsxWebServClassifierId,
    tmnxBsxUrlFltrWebServFqdn        TXLNamedItemOrEmpty,
    tmnxBsxUrlFltrWebServDnsAddrType InetAddressType,
    tmnxBsxUrlFltrWebServDnsAddr     InetAddress,
    tmnxBsxUrlFltrWebServDefaultProf TNamedItemOrEmpty,
    tmnxBsxUrlFilterWebServPortVlan  VlanIdOrNone,
    tmnxBsxUrlFltrWebServCategSetId  TmnxBsxWebServCategorySetId,
    tmnxBsxUrlFilterIcapDefAction    TmnxBsxUrlFilterDefaultAction,
    tmnxBsxUrlFilterIcapDefHttpRedir TNamedItemOrEmpty,
    tmnxBsxUrlFilterIcapHttpRedirObj TNamedItemOrEmpty,
    tmnxBsxUrlFilterWebDefAction     TmnxBsxUrlFilterDefaultAction,
    tmnxBsxUrlFilterWebDefHttpRedir  TNamedItemOrEmpty,
    tmnxBsxUrlFilterWebSerHttpRedir  TNamedItemOrEmpty,
    tmnxBsxUrlFilterUrlAllowList     TNamedItemOrEmpty,
    tmnxBsxUrlFltrApplyFuncBehavior  TruthValue
}

tmnxBsxUrlFilterName             OBJECT-TYPE
    SYNTAX      TNamedItem
    MAX-ACCESS  not-accessible
    STATUS      current
    DESCRIPTION
        "The value of tmnxBsxUrlFilterName specifies the name of the URL filter
         configuration."
    ::= { tmnxBsxUrlFilterEntry 1 }

tmnxBsxUrlFilterRowStatus        OBJECT-TYPE
    SYNTAX      RowStatus
    MAX-ACCESS  read-create
    STATUS      current
    DESCRIPTION
        "The value of tmnxBsxUrlFilterRowStatus specifies the row status. It
         allows entries to be created and deleted in tmnxBsxUrlFilterTable.

         Rows are created by specifying the value of 'createAndGo (4)', and
         deleted by specifying the value of 'destroy (6)'."
    ::= { tmnxBsxUrlFilterEntry 2 }

tmnxBsxUrlFilterRowLastChange    OBJECT-TYPE
    SYNTAX      TimeStamp
    MAX-ACCESS  read-only
    STATUS      current
    DESCRIPTION
        "The value of tmnxBsxUrlFilterRowLastChange indicates the last time,
         since system startup, a successful set was performed on this row."
    ::= { tmnxBsxUrlFilterEntry 3 }

tmnxBsxUrlFilterAdminState       OBJECT-TYPE
    SYNTAX      TmnxAdminState
    MAX-ACCESS  read-create
    STATUS      current
    DESCRIPTION
        "The value of tmnxBsxUrlFilterAdminState specifies the administrative
         state of the URL Filter."
    DEFVAL      { outOfService }
    ::= { tmnxBsxUrlFilterEntry 4 }

tmnxBsxUrlFilterDescription      OBJECT-TYPE
    SYNTAX      TItemDescription
    MAX-ACCESS  read-create
    STATUS      current
    DESCRIPTION
        "The value of tmnxBsxUrlFilterDescription specifies the description of
         the URL filter."
    DEFVAL      { "" }
    ::= { tmnxBsxUrlFilterEntry 5 }

tmnxBsxUrlFilterServicePortVlan  OBJECT-TYPE
    SYNTAX      VlanIdOrNone
    MAX-ACCESS  read-create
    STATUS      current
    DESCRIPTION
        "The value of tmnxBsxUrlFilterServicePortVlan specifies the VLAN ID on
         which the ISA-AA is expected to be emitting traffic."
    DEFVAL      { 0 }
    ::= { tmnxBsxUrlFilterEntry 6 }

tmnxBsxUrlFilterDefaultAction    OBJECT-TYPE
    SYNTAX      INTEGER {
        allow             (0),
        blockHttpRedirect (1),
        blockAll          (2)
    }
    MAX-ACCESS  read-create
    STATUS      current
    DESCRIPTION
        "The value of tmnxBsxUrlFilterDefaultAction specifies the default
         action to take when the ICAP server and local-filtering are out of
         service.

         The default actions are:
            allow(0)              - allow all requests
            blockRedirectHttp(1)  - block and redirect requests
            blockAll(2)           - block all requests

         A tmnxBsxUrlFilterHttpRedirName must be specified if
         tmnxBsxUrlFilterDefaultAction has a value of 'blockRedirectHttp(1)'."
    DEFVAL      { blockAll }
    ::= { tmnxBsxUrlFilterEntry 7 }

tmnxBsxUrlFilterHttpRedirName    OBJECT-TYPE
    SYNTAX      TNamedItemOrEmpty
    MAX-ACCESS  read-create
    STATUS      current
    DESCRIPTION
        "The value of tmnxBsxUrlFilterHttpRedirName specifies the HTTP redirect
         that will be applied as defined in the tmnxBsxHttpRedirTable. An empty
         value specifies no HTTP redirect.

         A tmnxBsxUrlFilterDefaultAction must have a value of
         'blockHttpRedirect(1)' if tmnxBsxUrlFilterHttpRedirName is not an
         empty string."
    DEFVAL      { "" }
    ::= { tmnxBsxUrlFilterEntry 8 }

tmnxBsxUrlFilterIcapHttpRedir    OBJECT-TYPE
    SYNTAX      TNamedItemOrEmpty
    MAX-ACCESS  read-create
    STATUS      current
    DESCRIPTION
        "The value of tmnxBsxUrlFilterIcapHttpRedir specifies the HTTP redirect
         that will be applied when the ICAP server or  local-filtering blocks
         an HTTP request. This HTTP redirect must exist in the
         tmnxBsxHttpRedirTable.

         An empty value specifies no HTTP redirect."
    DEFVAL      { "" }
    ::= { tmnxBsxUrlFilterEntry 9 }

tmnxBsxUrlFilterHttpReqFilter    OBJECT-TYPE
    SYNTAX      INTEGER {
        all   (1),
        first (2)
    }
    MAX-ACCESS  read-create
    STATUS      current
    DESCRIPTION
        "The value of tmnxBsxUrlFilterHttpReqFilter specifies the filtering of
         the URL of all or the first HTTP request in a TCP session."
    DEFVAL      { all }
    ::= { tmnxBsxUrlFilterEntry 10 }

tmnxBsxUrlFilterIcapCustXHeader  OBJECT-TYPE
    SYNTAX      TNamedItemOrEmpty
    MAX-ACCESS  read-create
    STATUS      current
    DESCRIPTION
        "The value of tmnxBsxUrlFilterIcapCustXHeader specifies the ICAP custom
         X-Header field name applied to ICAP Request messages."
    DEFVAL      { "" }
    ::= { tmnxBsxUrlFilterEntry 11 }

tmnxBsxUrlFltrWebServClassifyId  OBJECT-TYPE
    SYNTAX      TmnxBsxWebServClassifierId
    MAX-ACCESS  read-create
    STATUS      current
    DESCRIPTION
        "The value of tmnxBsxUrlFltrWebServClassifyId specifies the web service
         classifier Id."
    DEFVAL      { none }
    ::= { tmnxBsxUrlFilterEntry 12 }

tmnxBsxUrlFltrWebServFqdn        OBJECT-TYPE
    SYNTAX      TXLNamedItemOrEmpty
    MAX-ACCESS  read-create
    STATUS      current
    DESCRIPTION
        "The value of tmnxBsxUrlFltrWebServFqdn specifies the web service fully
         qualified domain name."
    DEFVAL      { "" }
    ::= { tmnxBsxUrlFilterEntry 13 }

tmnxBsxUrlFltrWebServDnsAddrType OBJECT-TYPE
    SYNTAX      InetAddressType
    MAX-ACCESS  read-create
    STATUS      current
    DESCRIPTION
        "The value of tmnxBsxUrlFltrWebServDnsAddrType specifies the type of
         address stored in tmnxBsxUrlFltrWebServDnsAddr.

         When specifying the value of tmnxBsxUrlFltrWebServDnsAddrType,
         tmnxBsxUrlFltrWebServDnsAddr must also be specified in the same SNMP
         Set PDU."
    DEFVAL      { unknown }
    ::= { tmnxBsxUrlFilterEntry 14 }

tmnxBsxUrlFltrWebServDnsAddr     OBJECT-TYPE
    SYNTAX      InetAddress (SIZE (0|4))
    MAX-ACCESS  read-create
    STATUS      current
    DESCRIPTION
        "The value of tmnxBsxUrlFltrWebServDnsAddr specifies the IP address of
         the DNS to use for resolving tmnxBsxUrlFltrWebServFqdn.

         When specifying the value of tmnxBsxUrlFltrWebServDnsAddr,
         tmnxBsxUrlFltrWebServDnsAddrType must also be specified in the same
         SNMP Set PDU."
    DEFVAL      { ''H }
    ::= { tmnxBsxUrlFilterEntry 15 }

tmnxBsxUrlFltrWebServDefaultProf OBJECT-TYPE
    SYNTAX      TNamedItemOrEmpty
    MAX-ACCESS  read-create
    STATUS      current
    DESCRIPTION
        "The value of tmnxBsxUrlFltrWebServDefaultProf specifies the default
         web service profile, which should be one of the profiles specified in
         tmnxBsxUrlFltrWebServProfTable, or empty."
    DEFVAL      { "" }
    ::= { tmnxBsxUrlFilterEntry 16 }

tmnxBsxUrlFilterWebServPortVlan  OBJECT-TYPE
    SYNTAX      VlanIdOrNone
    MAX-ACCESS  read-create
    STATUS      current
    DESCRIPTION
        "The value of tmnxBsxUrlFilterWebServPortVlan specifies the VLAN ID on
         which the ISA-AA is expected to be emitting traffic for web-service."
    DEFVAL      { 0 }
    ::= { tmnxBsxUrlFilterEntry 17 }

tmnxBsxUrlFltrWebServCategSetId  OBJECT-TYPE
    SYNTAX      TmnxBsxWebServCategorySetId
    MAX-ACCESS  read-create
    STATUS      current
    DESCRIPTION
        "The value of tmnxBsxUrlFltrWebServCategSetId specifies the web service
         category set Id."
    DEFVAL      { 0 }
    ::= { tmnxBsxUrlFilterEntry 18 }

tmnxBsxUrlFilterIcapDefAction    OBJECT-TYPE
    SYNTAX      TmnxBsxUrlFilterDefaultAction
    MAX-ACCESS  read-create
    STATUS      current
    DESCRIPTION
        "The value of tmnxBsxUrlFilterIcapDefAction specifies the default
         action to take when the ICAP server is out of service.

         A tmnxBsxUrlFilterIcapDefHttpRedir must be specified if
         tmnxBsxUrlFilterIcapDefAction has a value of 'blockRedirectHttp(1)'.

         This object can be changed when ICAP is configured (i.e.
         tmnxBsxUrlFilterServicePortVlan is not the default value)."
    DEFVAL      { blockAll }
    ::= { tmnxBsxUrlFilterEntry 19 }

tmnxBsxUrlFilterIcapDefHttpRedir OBJECT-TYPE
    SYNTAX      TNamedItemOrEmpty
    MAX-ACCESS  read-create
    STATUS      current
    DESCRIPTION
        "The value of tmnxBsxUrlFilterIcapDefHttpRedir specifies the HTTP
         redirect that will be applied as defined in the tmnxBsxHttpRedirTable.
         An empty value specifies no HTTP redirect.

         A tmnxBsxUrlFilterIcapDefAction must have a value of
         'blockHttpRedirect(1)' if tmnxBsxUrlFilterIcapDefHttpRedir is not an
         empty string.

         This object can be changed when ICAP is configured (i.e.
         tmnxBsxUrlFilterServicePortVlan is not the default value)."
    DEFVAL      { "" }
    ::= { tmnxBsxUrlFilterEntry 20 }

tmnxBsxUrlFilterIcapHttpRedirObj OBJECT-TYPE
    SYNTAX      TNamedItemOrEmpty
    MAX-ACCESS  read-create
    STATUS      current
    DESCRIPTION
        "The value of tmnxBsxUrlFilterIcapHttpRedirObj specifies the HTTP
         redirect that will be applied when the ICAP server blocks an HTTP
         request. This HTTP redirect must exist in the tmnxBsxHttpRedirTable.

         An empty value specifies no HTTP redirect.

         This object can be changed when ICAP is configured (i.e.
         tmnxBsxUrlFilterServicePortVlan is not the default value)."
    DEFVAL      { "" }
    ::= { tmnxBsxUrlFilterEntry 21 }

tmnxBsxUrlFilterWebDefAction     OBJECT-TYPE
    SYNTAX      TmnxBsxUrlFilterDefaultAction
    MAX-ACCESS  read-create
    STATUS      current
    DESCRIPTION
        "The value of tmnxBsxUrlFilterWebDefAction specifies the default action
         to take when the web service is out of service.

         A tmnxBsxUrlFilterWebDefHttpRedir must be specified if
         tmnxBsxUrlFilterWebDefAction has a value of 'blockRedirectHttp(1)'.

         This object can be changed when web service is configured (i.e.
         tmnxBsxUrlFltrWebServClassifyId is not the default value)."
    DEFVAL      { blockAll }
    ::= { tmnxBsxUrlFilterEntry 22 }

tmnxBsxUrlFilterWebDefHttpRedir  OBJECT-TYPE
    SYNTAX      TNamedItemOrEmpty
    MAX-ACCESS  read-create
    STATUS      current
    DESCRIPTION
        "The value of tmnxBsxUrlFilterWebDefHttpRedir specifies the HTTP
         redirect because of web service that will be applied as defined in the
         tmnxBsxHttpRedirTable. An empty value specifies no HTTP redirect.

         A tmnxBsxUrlFilterWebDefAction must have a value of
         'blockHttpRedirect(1)' if tmnxBsxUrlFilterWebDefHttpRedir is not an
         empty string.

         This object can be changed when web service is configured (i.e.
         tmnxBsxUrlFltrWebServClassifyId is not set to the default value)."
    DEFVAL      { "" }
    ::= { tmnxBsxUrlFilterEntry 23 }

tmnxBsxUrlFilterWebSerHttpRedir  OBJECT-TYPE
    SYNTAX      TNamedItemOrEmpty
    MAX-ACCESS  read-create
    STATUS      current
    DESCRIPTION
        "The value of tmnxBsxUrlFilterWebSerHttpRedir specifies the HTTP
         redirect that will be applied when the web service blocks an HTTP
         request. This HTTP redirect must exist in the tmnxBsxHttpRedirTable.

         An empty value specifies no HTTP redirect.

         This object can be changed when web service is configured (i.e.
         tmnxBsxUrlFltrWebServClassifyId is not set to the default value)."
    DEFVAL      { "" }
    ::= { tmnxBsxUrlFilterEntry 24 }

tmnxBsxUrlFilterUrlAllowList     OBJECT-TYPE
    SYNTAX      TNamedItemOrEmpty
    MAX-ACCESS  read-create
    STATUS      current
    DESCRIPTION
        "The value of tmnxBsxUrlFilterUrlAllowList specifies the local
         filtering URL allow-list name, as defined in the tmnxBsxUrlListTable.

         An empty value specifies no URL allow-list."
    DEFVAL      { "" }
    ::= { tmnxBsxUrlFilterEntry 25 }

tmnxBsxUrlFltrApplyFuncBehavior  OBJECT-TYPE
    SYNTAX      TruthValue
    MAX-ACCESS  read-create
    STATUS      current
    DESCRIPTION
        "The value of tmnxBsxUrlFltrApplyFuncBehavior configures whether
         function-specific or common url-filter level behaviours are applied.
         This can be used to provide function specific feedback to users for
         blocked URLs. It dictates the default action, default action HTTP
         redirect, and HTTP redirect that will be applied for all URL filter
         function types (i.e. web-service, ICAP, or local filtering URL list).
         When set to false, the default action (or
         tmnxBsxUrlFilterDefaultAction), the default action HTTP redirect (or
         tmnxBsxUrlFilterHttpRedirName) and the HTTP redirect (or
         tmnxBsxUrlFilterIcapHttpRedir) will be applied on all configured URL
         function types in this filter. When set to true, the forementioned
         objects are ignored and each URL filter function type will have its
         own set of default action, default action HTTP redirect and HTTP
         redirect objects that will be applied for that function. For
         web-service, the set of objects is tmnxBsxUrlFilterWebDefAction,
         tmnxBsxUrlFilterWebDefHttpRedir, and tmnxBsxUrlFilterWebSerHttpRedir
         respectively. For ICAP the set of objects is
         tmnxBsxUrlFilterIcapDefAction, tmnxBsxUrlFilterIcapDefHttpRedir, and
         tmnxBsxUrlFilterIcapHttpRedirObj respectively. For local filtering URL
         list the set of objects is tmnxBsxUrlFilterBlListDefAction,
         tmnxBsxUrlFilterBlListDefHtRedir, and tmnxBsxUrlFilterBlListHttpRedir
         respectively."
    DEFVAL      { false }
    ::= { tmnxBsxUrlFilterEntry 26 }

tmnxBsxIcapServerTable           OBJECT-TYPE
    SYNTAX      SEQUENCE OF TmnxBsxIcapServerEntry
    MAX-ACCESS  not-accessible
    STATUS      current
    DESCRIPTION
        "The tmnxBsxIcapServerTable allows the configuration of objects related
         to a particular ICAP server associated with a particular URL filter."
    ::= { tmnxBsxUrlFilterObjs 3 }

tmnxBsxIcapServerEntry           OBJECT-TYPE
    SYNTAX      TmnxBsxIcapServerEntry
    MAX-ACCESS  not-accessible
    STATUS      current
    DESCRIPTION
        "Each entry represents the configuration for a particular AA URL filter
         and ICAP server.

         Only IPv4 address types are supported for the ICAP server.

         The specification of an ICAP server may only be done when the
         tmnxBsxUrlFltrUrlListTable has no entries associated with the same URL
         filter and AA group.

         Entries in this table can be created and deleted via SNMP set
         operations to tmnxBsxIcapServerRowStatus."
    INDEX       {
        tmnxBsxIsaAaGroupIndex,
        tmnxBsxUrlFilterName,
        tmnxBsxIcapServerAddrType,
        tmnxBsxIcapServerAddr,
        tmnxBsxIcapServerPort
    }
    ::= { tmnxBsxIcapServerTable 1 }

TmnxBsxIcapServerEntry           ::= SEQUENCE
{
    tmnxBsxIcapServerAddrType        InetAddressType,
    tmnxBsxIcapServerAddr            InetAddress,
    tmnxBsxIcapServerPort            Unsigned32,
    tmnxBsxIcapServerRowStatus       RowStatus,
    tmnxBsxIcapServerRowLastChange   TimeStamp,
    tmnxBsxIcapServerDescription     TItemDescription,
    tmnxBsxIcapServerAdminState      TmnxAdminState
}

tmnxBsxIcapServerAddrType        OBJECT-TYPE
    SYNTAX      InetAddressType
    MAX-ACCESS  not-accessible
    STATUS      current
    DESCRIPTION
        "The value of tmnxBsxIcapServerAddrType specifies the type of address
         stored in tmnxBsxIcapServerAddr."
    ::= { tmnxBsxIcapServerEntry 1 }

tmnxBsxIcapServerAddr            OBJECT-TYPE
    SYNTAX      InetAddress (SIZE (4|16))
    MAX-ACCESS  not-accessible
    STATUS      current
    DESCRIPTION
        "The value of tmnxBsxIcapServerAddr specifies the IP address of the
         ICAP server.

         A valid unicast IP address must be specified at row creation time."
    ::= { tmnxBsxIcapServerEntry 2 }

tmnxBsxIcapServerPort            OBJECT-TYPE
    SYNTAX      Unsigned32 (1..65535)
    MAX-ACCESS  not-accessible
    STATUS      current
    DESCRIPTION
        "The value of tmnxBsxIcapServerPort specifies the ICAP server port."
    ::= { tmnxBsxIcapServerEntry 3 }

tmnxBsxIcapServerRowStatus       OBJECT-TYPE
    SYNTAX      RowStatus
    MAX-ACCESS  read-create
    STATUS      current
    DESCRIPTION
        "The value of tmnxBsxIcapServerRowStatus specifies the row status. It
         allows entries to be created and deleted in tmnxBsxIcapServerTable.

         Rows are created by specifying the value of 'createAndGo (4)', and
         deleted by specifying the value of 'destroy (6)'."
    ::= { tmnxBsxIcapServerEntry 4 }

tmnxBsxIcapServerRowLastChange   OBJECT-TYPE
    SYNTAX      TimeStamp
    MAX-ACCESS  read-only
    STATUS      current
    DESCRIPTION
        "The value of tmnxBsxIcapServerRowLastChange indicates the last time,
         since system startup, a successful set was performed on this row."
    ::= { tmnxBsxIcapServerEntry 5 }

tmnxBsxIcapServerDescription     OBJECT-TYPE
    SYNTAX      TItemDescription
    MAX-ACCESS  read-create
    STATUS      current
    DESCRIPTION
        "The value of tmnxBsxIcapServerDescription specifies the description of
         the ICAP server."
    DEFVAL      { "" }
    ::= { tmnxBsxIcapServerEntry 6 }

tmnxBsxIcapServerAdminState      OBJECT-TYPE
    SYNTAX      TmnxAdminState
    MAX-ACCESS  read-create
    STATUS      current
    DESCRIPTION
        "The value of tmnxBsxIcapServerAdminState specifies the administrative
         state of the ICAP server."
    DEFVAL      { outOfService }
    ::= { tmnxBsxIcapServerEntry 7 }

tmnxBsxIcapServerStatsTable      OBJECT-TYPE
    SYNTAX      SEQUENCE OF TmnxBsxIcapServerStatsEntry
    MAX-ACCESS  not-accessible
    STATUS      current
    DESCRIPTION
        "The tmnxBsxIcapServerStatsTable contains operational information
         related to a particular ICAP server associated with a particular URL
         filter.

         Each row contains the status and performance-oriented statistics
         information per group, URL filter and ICAP server for an ISA-AA
         uniquely identified by the tmnxChassisIndex, tmnxBsxCardSlotEsaId, and
         the tmnxBsxMdaSlotEsaVmId."
    ::= { tmnxBsxUrlFilterObjs 4 }

tmnxBsxIcapServerStatsEntry      OBJECT-TYPE
    SYNTAX      TmnxBsxIcapServerStatsEntry
    MAX-ACCESS  not-accessible
    STATUS      current
    DESCRIPTION
        "Each entry represents the statistics for a particular AA URL filter
         and ICAP server.

         An index with a valid ICAP server (an existing row in
         tmnxBsxIcapServerTable) and tmnxChassisIndex set to one with a
         zero value for each of tmnxBsxCardSlotEsaId and tmnxBsxMdaSlotEsaVmId will
         return the following per group, URL Filter and ICAP server:
            * the summarized statistics, and
            * the worst case values for tmnxBsxIcapServerStatsRoundTrip and
         tmnxBsxIcapServerStatsConnUtil

         Entries will appears in this table only for equipped ISA-AA MDAs
         associated with an AA group, URL filter and ICAP server."
    INDEX       {
        tmnxBsxIsaAaGroupIndex,
        tmnxBsxUrlFilterName,
        tmnxBsxIcapServerAddrType,
        tmnxBsxIcapServerAddr,
        tmnxBsxIcapServerPort,
        tmnxChassisIndex,
        tmnxBsxCardSlotEsaId,
        tmnxBsxMdaSlotEsaVmId
    }
    ::= { tmnxBsxIcapServerStatsTable 1 }

TmnxBsxIcapServerStatsEntry      ::= SEQUENCE
{
    tmnxBsxIcapServerOperState       TmnxOperState,
    tmnxBsxIcapServerOperFlags       BITS,
    tmnxBsxIcapServerStatsRequests   Counter64,
    tmnxBsxIcapServerStatsReqErrors  Counter64,
    tmnxBsxIcapServerStatsRespAllow  Counter64,
    tmnxBsxIcapServerStatsRespBlock  Counter64,
    tmnxBsxIcapServerStatsRespRedir  Counter64,
    tmnxBsxIcapServerStatsRoundTrip  Unsigned32,
    tmnxBsxIcapServerStatsReqRate    Unsigned32,
    tmnxBsxIcapServerStatsConnTotal  Unsigned32,
    tmnxBsxIcapServerStatsConnEst    Unsigned32,
    tmnxBsxIcapServerStatsConnUtil   Gauge32
}

tmnxBsxIcapServerOperState       OBJECT-TYPE
    SYNTAX      TmnxOperState
    MAX-ACCESS  read-only
    STATUS      current
    DESCRIPTION
        "The value of tmnxBsxIcapServerOperState indicates the operational
         state of the ICAP server."
    ::= { tmnxBsxIcapServerStatsEntry 1 }

tmnxBsxIcapServerOperFlags       OBJECT-TYPE
    SYNTAX      BITS {
        adminDown    (0),
        tcpConnError (1)
    }
    MAX-ACCESS  read-only
    STATUS      current
    DESCRIPTION
        "The value of tmnxBsxIcapServerOperFlags indicates the different
         conditions that affect the operating status of an ICAP server.

         The bit values are:
            adminDown(0)             - ICAP server instance is administratively
                                       down.
            tcpConnError(1)          - TCP communication error has occurred."
    ::= { tmnxBsxIcapServerStatsEntry 2 }

tmnxBsxIcapServerStatsRequests   OBJECT-TYPE
    SYNTAX      Counter64
    MAX-ACCESS  read-only
    STATUS      current
    DESCRIPTION
        "The value of tmnxBsxIcapServerStatsRequests indicates the number of
         ICAP requests which have been sent to this ICAP server."
    ::= { tmnxBsxIcapServerStatsEntry 3 }

tmnxBsxIcapServerStatsReqErrors  OBJECT-TYPE
    SYNTAX      Counter64
    MAX-ACCESS  read-only
    STATUS      current
    DESCRIPTION
        "The value of tmnxBsxIcapServerStatsReqErrors indicates the number of
         ICAP requests that were unable to be sent to the ICAP server."
    ::= { tmnxBsxIcapServerStatsEntry 4 }

tmnxBsxIcapServerStatsRespAllow  OBJECT-TYPE
    SYNTAX      Counter64
    MAX-ACCESS  read-only
    STATUS      current
    DESCRIPTION
        "The value of tmnxBsxIcapServerStatsRespAllow indicates the number of
         ICAP allow responses which have been received from the ICAP server."
    ::= { tmnxBsxIcapServerStatsEntry 5 }

tmnxBsxIcapServerStatsRespBlock  OBJECT-TYPE
    SYNTAX      Counter64
    MAX-ACCESS  read-only
    STATUS      current
    DESCRIPTION
        "The value of tmnxBsxIcapServerStatsRespBlock indicates the number of
         ICAP block responses which have been received from the ICAP server."
    ::= { tmnxBsxIcapServerStatsEntry 6 }

tmnxBsxIcapServerStatsRespRedir  OBJECT-TYPE
    SYNTAX      Counter64
    MAX-ACCESS  read-only
    STATUS      current
    DESCRIPTION
        "The value of tmnxBsxIcapServerStatsRespRedir indicates the number of
         ICAP redirect responses which have been received from the ICAP server."
    ::= { tmnxBsxIcapServerStatsEntry 7 }

tmnxBsxIcapServerStatsRoundTrip  OBJECT-TYPE
    SYNTAX      Unsigned32
    UNITS       "microseconds"
    MAX-ACCESS  read-only
    STATUS      current
    DESCRIPTION
        "The value of tmnxBsxIcapServerStatsRoundTrip indicates the average
         amount of time it took to receive ICAP Responses over the last 10
         second period."
    ::= { tmnxBsxIcapServerStatsEntry 8 }

tmnxBsxIcapServerStatsReqRate    OBJECT-TYPE
    SYNTAX      Unsigned32
    UNITS       "requests per second"
    MAX-ACCESS  read-only
    STATUS      current
    DESCRIPTION
        "The value of tmnxBsxIcapServerStatsReqRate indicates the average
         number of ICAP requests sent per second over the last 10 second
         period."
    ::= { tmnxBsxIcapServerStatsEntry 9 }

tmnxBsxIcapServerStatsConnTotal  OBJECT-TYPE
    SYNTAX      Unsigned32
    MAX-ACCESS  read-only
    STATUS      current
    DESCRIPTION
        "The value of tmnxBsxIcapServerStatsConnTotal indicates the number of
         TCP connections which can be established with the ICAP server."
    ::= { tmnxBsxIcapServerStatsEntry 10 }

tmnxBsxIcapServerStatsConnEst    OBJECT-TYPE
    SYNTAX      Unsigned32
    MAX-ACCESS  read-only
    STATUS      current
    DESCRIPTION
        "The value of tmnxBsxIcapServerStatsConnEst indicates the current
         number of TCP connections which are established with the ICAP server."
    ::= { tmnxBsxIcapServerStatsEntry 11 }

tmnxBsxIcapServerStatsConnUtil   OBJECT-TYPE
    SYNTAX      Gauge32 (0..100)
    UNITS       "percent"
    MAX-ACCESS  read-only
    STATUS      current
    DESCRIPTION
        "The value of tmnxBsxIcapServerStatsConnUtil indicates the percentage
         of TCP connections utilized over the last 10 second period."
    ::= { tmnxBsxIcapServerStatsEntry 12 }

tmnxBsxAaIfOperTable             OBJECT-TYPE
    SYNTAX      SEQUENCE OF TmnxBsxAaIfOperEntry
    MAX-ACCESS  not-accessible
    STATUS      current
    DESCRIPTION
        "The tmnxBsxAaIfOperTable contains operational information on the AA
         Interfaces."
    ::= { tmnxBsxUrlFilterObjs 5 }

tmnxBsxAaIfOperEntry             OBJECT-TYPE
    SYNTAX      TmnxBsxAaIfOperEntry
    MAX-ACCESS  not-accessible
    STATUS      current
    DESCRIPTION
        "Each entry represents the operational AA interface information
         associated with the ISA-AA service port."
    INDEX       {
        tmnxBsxIsaAaGroupIndex,
        tmnxChassisIndex,
        tmnxBsxCardSlotEsaId,
        tmnxBsxMdaSlotEsaVmId,
        tmnxBsxAaIfServicePortVlan
    }
    ::= { tmnxBsxAaIfOperTable 1 }

TmnxBsxAaIfOperEntry             ::= SEQUENCE
{
    tmnxBsxAaIfServicePortVlan       VlanId,
    tmnxBsxAaIfName                  TNamedItemOrEmpty,
    tmnxBsxAaIfServiceType           ServType,
    tmnxBsxAaIfServiceId             TmnxServId,
    tmnxBsxAaIfAddrType              InetAddressType,
    tmnxBsxAaIfAddr                  InetAddress,
    tmnxBsxAaIfAddrPrefixLength      InetAddressPrefixLength,
    tmnxBsxAaIfIsaAddrType           InetAddressType,
    tmnxBsxAaIfIsaAddr               InetAddress,
    tmnxBsxAaIfIsaAddrPrefixLength   InetAddressPrefixLength,
    tmnxBsxAaIfAdminState            ServiceAdminStatus,
    tmnxBsxAaIfOperState             ServiceOperStatus
}

tmnxBsxAaIfServicePortVlan       OBJECT-TYPE
    SYNTAX      VlanId
    MAX-ACCESS  not-accessible
    STATUS      current
    DESCRIPTION
        "The value of tmnxBsxAaIfServicePortVlan specifies the VLAN ID on which
         the ISA-AA is expected to be emitting traffic."
    ::= { tmnxBsxAaIfOperEntry 1 }

tmnxBsxAaIfName                  OBJECT-TYPE
    SYNTAX      TNamedItemOrEmpty
    MAX-ACCESS  read-only
    STATUS      current
    DESCRIPTION
        "The value of tmnxBsxAaIfName indicates the name of the AA interface."
    ::= { tmnxBsxAaIfOperEntry 2 }

tmnxBsxAaIfServiceType           OBJECT-TYPE
    SYNTAX      ServType
    MAX-ACCESS  read-only
    STATUS      current
    DESCRIPTION
        "The value of tmnxBsxAaIfServiceType indicates the service type of the
         AA interface."
    ::= { tmnxBsxAaIfOperEntry 3 }

tmnxBsxAaIfServiceId             OBJECT-TYPE
    SYNTAX      TmnxServId
    MAX-ACCESS  read-only
    STATUS      current
    DESCRIPTION
        "The value of tmnxBsxAaIfServiceId indicates the service identifier of
         the AA interface."
    ::= { tmnxBsxAaIfOperEntry 4 }

tmnxBsxAaIfAddrType              OBJECT-TYPE
    SYNTAX      InetAddressType
    MAX-ACCESS  read-only
    STATUS      current
    DESCRIPTION
        "The value of tmnxBsxAaIfAddrType indicates the type of address stored
         in tmnxBsxAaIfAddr."
    ::= { tmnxBsxAaIfOperEntry 5 }

tmnxBsxAaIfAddr                  OBJECT-TYPE
    SYNTAX      InetAddress (SIZE (0|4|16))
    MAX-ACCESS  read-only
    STATUS      current
    DESCRIPTION
        "The value of tmnxBsxAaIfAddr indicates the IP address of the AA
         interface."
    ::= { tmnxBsxAaIfOperEntry 6 }

tmnxBsxAaIfAddrPrefixLength      OBJECT-TYPE
    SYNTAX      InetAddressPrefixLength (0..128)
    MAX-ACCESS  read-only
    STATUS      current
    DESCRIPTION
        "The value of tmnxBsxAaIfAddrPrefixLength indicates the number of
         relevant bits of the tmnxBsxAaIfAddr."
    ::= { tmnxBsxAaIfOperEntry 7 }

tmnxBsxAaIfIsaAddrType           OBJECT-TYPE
    SYNTAX      InetAddressType
    MAX-ACCESS  read-only
    STATUS      current
    DESCRIPTION
        "The value of tmnxBsxAaIfIsaAddrType indicates the type of address
         stored in tmnxBsxAaIfIsaAddr."
    ::= { tmnxBsxAaIfOperEntry 8 }

tmnxBsxAaIfIsaAddr               OBJECT-TYPE
    SYNTAX      InetAddress (SIZE (0|4|16))
    MAX-ACCESS  read-only
    STATUS      current
    DESCRIPTION
        "The value of tmnxBsxAaIfIsaAddr indicates the IP address of the ISA's
         AA interface."
    ::= { tmnxBsxAaIfOperEntry 9 }

tmnxBsxAaIfIsaAddrPrefixLength   OBJECT-TYPE
    SYNTAX      InetAddressPrefixLength (0..128)
    MAX-ACCESS  read-only
    STATUS      current
    DESCRIPTION
        "The value of tmnxBsxAaIfIsaAddrPrefixLength indicates the number of
         relevant bits of the tmnxBsxAaIfIsaAddr."
    ::= { tmnxBsxAaIfOperEntry 10 }

tmnxBsxAaIfAdminState            OBJECT-TYPE
    SYNTAX      ServiceAdminStatus
    MAX-ACCESS  read-only
    STATUS      current
    DESCRIPTION
        "The value of tmnxBsxAaIfAdminState indicates the mirrored value of
         administrative state of the AA interface."
    ::= { tmnxBsxAaIfOperEntry 11 }

tmnxBsxAaIfOperState             OBJECT-TYPE
    SYNTAX      ServiceOperStatus
    MAX-ACCESS  read-only
    STATUS      current
    DESCRIPTION
        "The value of tmnxBsxAaIfOperState indicates the operational state of
         the AA interface."
    ::= { tmnxBsxAaIfOperEntry 12 }

tmnxBsxUrlFltrStatsTable         OBJECT-TYPE
    SYNTAX      SEQUENCE OF TmnxBsxUrlFltrStatsEntry
    MAX-ACCESS  not-accessible
    STATUS      current
    DESCRIPTION
        "The tmnxBsxUrlFltrStatsTable contains operational information related
         to a particular URL filter.

         Each row contains the status and performance-oriented statistics
         information per group and URL filter for an ISA-AA uniquely identified
         by the tmnxChassisIndex, tmnxBsxCardSlotEsaId, and the
         tmnxBsxMdaSlotEsaVmId."
    ::= { tmnxBsxUrlFilterObjs 6 }

tmnxBsxUrlFltrStatsEntry         OBJECT-TYPE
    SYNTAX      TmnxBsxUrlFltrStatsEntry
    MAX-ACCESS  not-accessible
    STATUS      current
    DESCRIPTION
        "Each entry represents the statistics for a particular AA URL filter.

         An index with a valid URL Filter (an existing row in
         tmnxBsxUrlFltrTable) and tmnxChassisIndex set to one with a zero value
         for each of tmnxBsxCardSlotEsaId and tmnxBsxMdaSlotEsaVmId will return
         the summarized per group and URL Filter statistics.

         Entries will appears in this table only for equipped ISA-AA MDAs
         associated with an AA group and URL filter."
    INDEX       {
        tmnxBsxIsaAaGroupIndex,
        tmnxBsxUrlFilterName,
        tmnxChassisIndex,
        tmnxBsxCardSlotEsaId,
        tmnxBsxMdaSlotEsaVmId
    }
    ::= { tmnxBsxUrlFltrStatsTable 1 }

TmnxBsxUrlFltrStatsEntry         ::= SEQUENCE
{
    tmnxBsxUrlFltrOperState          TmnxOperState,
    tmnxBsxUrlFltrOperFlags          BITS,
    tmnxBsxUrlFltrStatsHttpRequests  Counter64,
    tmnxBsxUrlFltrStatsHttpRespAllow Counter64,
    tmnxBsxUrlFltrStatsHttpRespRedir Counter64,
    tmnxBsxUrlFltrStatsHttpRespBlock Counter64,
    tmnxBsxUrlFltrStatsHttpRespDef   Counter64,
    tmnxBsxUrlFltrStatsHttpReqErrors Counter64,
    tmnxBsxUrlFltrStatsIcapLateResp  Counter64,
    tmnxBsxUrlFltrStatsIcapLRPktsDsc Counter64,
    tmnxBsxUrlFltrStatsIcapLRBytsDsc Counter64,
    tmnxBsxUrlFltrStatsWebSvLateRsp  Counter64,
    tmnxBsxUrlFltrStatsWebSvLRPktDsc Counter64,
    tmnxBsxUrlFltrStatsWebSvLRBytDsc Counter64,
    tmnxBsxUrlFltrStatsWebServReqs   Counter64,
    tmnxBsxUrlFltrStatsWebServReqErr Counter64,
    tmnxBsxUrlFltrWebServStatsRndTp  Unsigned32,
    tmnxBsxUrlFltrWebSvStatsReqRate  Unsigned32,
    tmnxBsxUrlFltrWebSvStatsConnTot  Unsigned32,
    tmnxBsxUrlFltrWebSvStatsConnEst  Unsigned32,
    tmnxBsxUrlFltrWebSerMaxCacheSize Unsigned32,
    tmnxBsxUrlFltrWebSvDnsOperState  TmnxOperState,
    tmnxBsxUrlFltrWebSvDnsOperFlags  BITS,
    tmnxBsxUrlFltrWebServCacheSize   Unsigned32,
    tmnxBsxUrlFltrWebSerStatCacheHit Counter64,
    tmnxBsxUrlFltrWebSerStatCacheMis Counter64,
    tmnxBsxUrlFltrStatsWebSvRspAllow Counter64,
    tmnxBsxUrlFltrStatsWebSvRspRedir Counter64,
    tmnxBsxUrlFltrStatsWebSvRspBlock Counter64,
    tmnxBsxUrlFltrStatsWebSvDefault  Counter64,
    tmnxBsxUrlFltrStatsAllowListLkup Counter64,
    tmnxBsxUrlFltrStatsAllowLstMatch Counter64,
    tmnxBsxUrlFltrStatsUrlAllow      Counter64,
    tmnxBsxUrlFltrStatsUrlBlockRedir Counter64,
    tmnxBsxUrlFltrStatsUrlDefAction  Counter64,
    tmnxBsxUrlFltrStatsIcapDefault   Counter64,
    tmnxBsxUrlFltrStatsWSClassOvrHit Counter64,
    tmnxBsxUrlFltrStatsWSClassOvrMis Counter64
}

tmnxBsxUrlFltrOperState          OBJECT-TYPE
    SYNTAX      TmnxOperState
    MAX-ACCESS  read-only
    STATUS      current
    DESCRIPTION
        "The value of tmnxBsxUrlFltrOperState indicates the operational state
         of the URL Filter."
    ::= { tmnxBsxUrlFltrStatsEntry 1 }

tmnxBsxUrlFltrOperFlags          OBJECT-TYPE
    SYNTAX      BITS {
        adminDown      (0),
        noAaIf         (1),
        aaIfDown       (2),
        icapServerDown (3),
        urlListDown    (4),
        webServiceDown (5)
    }
    MAX-ACCESS  read-only
    STATUS      current
    DESCRIPTION
        "The value of tmnxBsxUrlFltrOperFlags indicates the different
         conditions that affect the operating status of the URL Filter.

         The bit values are:
            adminDown(0)        - URL Filter is administratively down.
            noAaIf(1)           - missing AA interface configuration.
            aaIfDown(2)         - the AA interface is operationally down.
            icapServerDown(3)   - unable to establish connection with
                                  ICAP server(s).
            urlListDown(4)      - the referenced URL list is operationally
                                  down.
            webServiceDown(5)   - unable to establish a connection with the
                                  web service classifier."
    ::= { tmnxBsxUrlFltrStatsEntry 2 }

tmnxBsxUrlFltrStatsHttpRequests  OBJECT-TYPE
    SYNTAX      Counter64
    MAX-ACCESS  read-only
    STATUS      current
    DESCRIPTION
        "The value of tmnxBsxUrlFltrStatsHttpRequests indicates the number of
         HTTP requests received."
    ::= { tmnxBsxUrlFltrStatsEntry 3 }

tmnxBsxUrlFltrStatsHttpRespAllow OBJECT-TYPE
    SYNTAX      Counter64
    MAX-ACCESS  read-only
    STATUS      current
    DESCRIPTION
        "The value of tmnxBsxUrlFltrStatsHttpRespAllow indicates the number of
         times the HTTP response has been allowed."
    ::= { tmnxBsxUrlFltrStatsEntry 4 }

tmnxBsxUrlFltrStatsHttpRespRedir OBJECT-TYPE
    SYNTAX      Counter64
    MAX-ACCESS  read-only
    STATUS      current
    DESCRIPTION
        "The value of tmnxBsxUrlFltrStatsHttpRespRedir indicates the number of
         times the HTTP response has been redirected."
    ::= { tmnxBsxUrlFltrStatsEntry 5 }

tmnxBsxUrlFltrStatsHttpRespBlock OBJECT-TYPE
    SYNTAX      Counter64
    MAX-ACCESS  read-only
    STATUS      current
    DESCRIPTION
        "The value of tmnxBsxUrlFltrStatsHttpRespBlock indicates the number of
         times the HTTP response has been blocked."
    ::= { tmnxBsxUrlFltrStatsEntry 6 }

tmnxBsxUrlFltrStatsHttpRespDef   OBJECT-TYPE
    SYNTAX      Counter64
    MAX-ACCESS  read-only
    STATUS      current
    DESCRIPTION
        "The value of tmnxBsxUrlFltrStatsHttpRespDef indicates the number of
         times the tmnxBsxUrlFilterDefaultAction has been taken on the HTTP
         response."
    ::= { tmnxBsxUrlFltrStatsEntry 7 }

tmnxBsxUrlFltrStatsHttpReqErrors OBJECT-TYPE
    SYNTAX      Counter64
    MAX-ACCESS  read-only
    STATUS      current
    DESCRIPTION
        "The value of tmnxBsxUrlFltrStatsHttpReqErrors indicates the number of
         times the HTTP request that were unable to be sent to the ICAP server
         or web-service server."
    ::= { tmnxBsxUrlFltrStatsEntry 8 }

tmnxBsxUrlFltrStatsIcapLateResp  OBJECT-TYPE
    SYNTAX      Counter64
    MAX-ACCESS  read-only
    STATUS      current
    DESCRIPTION
        "The value of tmnxBsxUrlFltrStatsIcapLateResp indicates the number of
         times the HTTP response was received prior to the ICAP response."
    ::= { tmnxBsxUrlFltrStatsEntry 9 }

tmnxBsxUrlFltrStatsIcapLRPktsDsc OBJECT-TYPE
    SYNTAX      Counter64
    MAX-ACCESS  read-only
    STATUS      current
    DESCRIPTION
        "The value of tmnxBsxUrlFltrStatsIcapLRPktsDsc indicates the number of
         packets dropped while waiting for an ICAP response."
    ::= { tmnxBsxUrlFltrStatsEntry 10 }

tmnxBsxUrlFltrStatsIcapLRBytsDsc OBJECT-TYPE
    SYNTAX      Counter64
    MAX-ACCESS  read-only
    STATUS      current
    DESCRIPTION
        "The value of tmnxBsxUrlFltrStatsIcapLRBytsDsc indicates the number of
         bytes dropped while waiting for an ICAP response."
    ::= { tmnxBsxUrlFltrStatsEntry 11 }

tmnxBsxUrlFltrStatsWebSvLateRsp  OBJECT-TYPE
    SYNTAX      Counter64
    MAX-ACCESS  read-only
    STATUS      current
    DESCRIPTION
        "The value of tmnxBsxUrlFltrStatsWebSvLateRsp indicates the number of
         times the HTTP response was received prior to the web service server
         response."
    ::= { tmnxBsxUrlFltrStatsEntry 12 }

tmnxBsxUrlFltrStatsWebSvLRPktDsc OBJECT-TYPE
    SYNTAX      Counter64
    MAX-ACCESS  read-only
    STATUS      current
    DESCRIPTION
        "The value of tmnxBsxUrlFltrStatsWebSvLRPktDsc indicates the number of
         packets dropped while waiting for an web service server response."
    ::= { tmnxBsxUrlFltrStatsEntry 13 }

tmnxBsxUrlFltrStatsWebSvLRBytDsc OBJECT-TYPE
    SYNTAX      Counter64
    MAX-ACCESS  read-only
    STATUS      current
    DESCRIPTION
        "The value of tmnxBsxUrlFltrStatsWebSvLRBytDsc indicates the number of
         bytes dropped while waiting for a web service server response."
    ::= { tmnxBsxUrlFltrStatsEntry 14 }

tmnxBsxUrlFltrStatsWebServReqs   OBJECT-TYPE
    SYNTAX      Counter64
    MAX-ACCESS  read-only
    STATUS      current
    DESCRIPTION
        "The value of tmnxBsxUrlFltrStatsWebServReqs indicates the number of
         web service requests which have been sent to the web service server."
    ::= { tmnxBsxUrlFltrStatsEntry 15 }

tmnxBsxUrlFltrStatsWebServReqErr OBJECT-TYPE
    SYNTAX      Counter64
    MAX-ACCESS  read-only
    STATUS      current
    DESCRIPTION
        "The value of tmnxBsxUrlFltrStatsWebServReqErr indicates the number of
         web service requests that were unable to be sent to the web service
         server."
    ::= { tmnxBsxUrlFltrStatsEntry 16 }

tmnxBsxUrlFltrWebServStatsRndTp  OBJECT-TYPE
    SYNTAX      Unsigned32
    UNITS       "microseconds"
    MAX-ACCESS  read-only
    STATUS      current
    DESCRIPTION
        "The value of tmnxBsxUrlFltrWebServStatsRndTp indicates the average
         amount of time it took to receive web service Responses over the last
         10 second period."
    ::= { tmnxBsxUrlFltrStatsEntry 17 }

tmnxBsxUrlFltrWebSvStatsReqRate  OBJECT-TYPE
    SYNTAX      Unsigned32
    UNITS       "requests per second"
    MAX-ACCESS  read-only
    STATUS      current
    DESCRIPTION
        "The value of tmnxBsxUrlFltrWebSvStatsReqRate indicates the average
         number of web service requests sent per second over the last 10 second
         period."
    ::= { tmnxBsxUrlFltrStatsEntry 18 }

tmnxBsxUrlFltrWebSvStatsConnTot  OBJECT-TYPE
    SYNTAX      Unsigned32
    MAX-ACCESS  read-only
    STATUS      current
    DESCRIPTION
        "The value of tmnxBsxUrlFltrWebSvStatsConnTot indicates the number of
         TCP connections which can be established with the web service server."
    ::= { tmnxBsxUrlFltrStatsEntry 19 }

tmnxBsxUrlFltrWebSvStatsConnEst  OBJECT-TYPE
    SYNTAX      Unsigned32
    MAX-ACCESS  read-only
    STATUS      current
    DESCRIPTION
        "The value of tmnxBsxUrlFltrWebSvStatsConnEst indicates the current
         number of TCP connections which are established with the web service
         server."
    ::= { tmnxBsxUrlFltrStatsEntry 20 }

tmnxBsxUrlFltrWebSerMaxCacheSize OBJECT-TYPE
    SYNTAX      Unsigned32
    MAX-ACCESS  read-only
    STATUS      current
    DESCRIPTION
        "The value of tmnxBsxUrlFltrWebSerMaxCacheSize indicates the maximum
         cache size (cache entries) that can be allocated per URL filter
         providing web-service per ISA. For slot 0 and mda 0 the value presents
         the sum of all ISAs in the AA group."
    ::= { tmnxBsxUrlFltrStatsEntry 21 }

tmnxBsxUrlFltrWebSvDnsOperState  OBJECT-TYPE
    SYNTAX      TmnxOperState
    MAX-ACCESS  read-only
    STATUS      current
    DESCRIPTION
        "The value of tmnxBsxUrlFltrWebSvDnsOperState indicates the operational
         state of the DNS server."
    ::= { tmnxBsxUrlFltrStatsEntry 22 }

tmnxBsxUrlFltrWebSvDnsOperFlags  OBJECT-TYPE
    SYNTAX      BITS {
        notApplicable   (0),
        filterAdminDown (1),
        noAaIf          (2),
        aaIfDown        (3),
        dnsDown         (4),
        lookUpFailure   (5),
        unreachable     (6)
    }
    MAX-ACCESS  read-only
    STATUS      current
    DESCRIPTION
        "The value of tmnxBsxUrlFltrWebSvDnsOperFlags indicates the different
         conditions that affect the operating status of the web service DNS server.
         The bit values are:
            notApplicable (0)   - DNS is not applicable for the type of URL-filter.
            filterAdminDown(1)  - DNS is down because the URL-filter is admin-down.
            noAaIf(2)           - No AA interface is configured.
            aaIfDown(3)         - AA interface is operationally down.
            dnsDown(4)          - Not all DNS instances on all the AA group of MDAs are up.
                                  Not used for specific MDA.
            lookUpFailure(5)    - domain lookup failure.
            unreachable(6)      - DNS is not reachable."
    ::= { tmnxBsxUrlFltrStatsEntry 23 }

tmnxBsxUrlFltrWebServCacheSize   OBJECT-TYPE
    SYNTAX      Unsigned32
    MAX-ACCESS  read-only
    STATUS      current
    DESCRIPTION
        "The value of tmnxBsxUrlFltrWebServCacheSize indicates the current
         cache size (number of cache entries) per URL filter providing
         web-service per ISA. For slot 0 and mda 0 the value presents the sum
         of all ISAs in the AA group."
    ::= { tmnxBsxUrlFltrStatsEntry 24 }

tmnxBsxUrlFltrWebSerStatCacheHit OBJECT-TYPE
    SYNTAX      Counter64
    MAX-ACCESS  read-only
    STATUS      current
    DESCRIPTION
        "The value of tmnxBsxUrlFltrWebSerStatCacheHit indicates the number of
         cache hits while servicing url category classification requests."
    ::= { tmnxBsxUrlFltrStatsEntry 25 }

tmnxBsxUrlFltrWebSerStatCacheMis OBJECT-TYPE
    SYNTAX      Counter64
    MAX-ACCESS  read-only
    STATUS      current
    DESCRIPTION
        "The value of tmnxBsxUrlFltrWebSerStatCacheMis indicates the number of
         cache misses while servicing url category classification requests.
         These results in sending url category classification requests to the
         configured url-filter classifier."
    ::= { tmnxBsxUrlFltrStatsEntry 26 }

tmnxBsxUrlFltrStatsWebSvRspAllow OBJECT-TYPE
    SYNTAX      Counter64
    MAX-ACCESS  read-only
    STATUS      current
    DESCRIPTION
        "The value of tmnxBsxUrlFltrStatsWebSvRspAllow indicates the number of
         times the response from the web service server resulted to an 'allow'
         action by the URL filter."
    ::= { tmnxBsxUrlFltrStatsEntry 27 }

tmnxBsxUrlFltrStatsWebSvRspRedir OBJECT-TYPE
    SYNTAX      Counter64
    MAX-ACCESS  read-only
    STATUS      current
    DESCRIPTION
        "The value of tmnxBsxUrlFltrStatsWebSvRspRedir indicates the number of
         times the response from the web service server resulted to an
         'redirect' action by the URL filter."
    ::= { tmnxBsxUrlFltrStatsEntry 28 }

tmnxBsxUrlFltrStatsWebSvRspBlock OBJECT-TYPE
    SYNTAX      Counter64
    MAX-ACCESS  read-only
    STATUS      current
    DESCRIPTION
        "The value of tmnxBsxUrlFltrStatsWebSvRspBlock indicates the number of
         times the response from the web service server resulted to a 'block'
         action by the URL filter."
    ::= { tmnxBsxUrlFltrStatsEntry 29 }

tmnxBsxUrlFltrStatsWebSvDefault  OBJECT-TYPE
    SYNTAX      Counter64
    MAX-ACCESS  read-only
    STATUS      current
    DESCRIPTION
        "The value of tmnxBsxUrlFltrStatsWebSvDefault indicates the number of
         times the web service takes the default action due to the url filter's
         inability to send the request to the web-service server or receiving a
         malformed response from the web-service server."
    ::= { tmnxBsxUrlFltrStatsEntry 30 }

tmnxBsxUrlFltrStatsAllowListLkup OBJECT-TYPE
    SYNTAX      Counter64
    MAX-ACCESS  read-only
    STATUS      current
    DESCRIPTION
        "The value of tmnxBsxUrlFltrStatsAllowListLkup indicates the number of
         URL allow-list lookups."
    ::= { tmnxBsxUrlFltrStatsEntry 31 }

tmnxBsxUrlFltrStatsAllowLstMatch OBJECT-TYPE
    SYNTAX      Counter64
    MAX-ACCESS  read-only
    STATUS      current
    DESCRIPTION
        "The value of tmnxBsxUrlFltrStatsAllowLstMatch indicates the number of
         lookups that matched entries in the URL allow-list."
    ::= { tmnxBsxUrlFltrStatsEntry 32 }

tmnxBsxUrlFltrStatsUrlAllow      OBJECT-TYPE
    SYNTAX      Counter64
    MAX-ACCESS  read-only
    STATUS      current
    DESCRIPTION
        "The value of tmnxBsxUrlFltrStatsUrlAllow indicates the total number of
         URL lookup requests that resulted in an 'allow' action by the the last
         filtering type within the filter."
    ::= { tmnxBsxUrlFltrStatsEntry 33 }

tmnxBsxUrlFltrStatsUrlBlockRedir OBJECT-TYPE
    SYNTAX      Counter64
    MAX-ACCESS  read-only
    STATUS      current
    DESCRIPTION
        "The value of tmnxBsxUrlFltrStatsUrlBlockRedir indicates the total
         number of URL lookup requests that resulted in an action of 'redirect'
         or 'block' by the the last filtering type within the filter."
    ::= { tmnxBsxUrlFltrStatsEntry 34 }

tmnxBsxUrlFltrStatsUrlDefAction  OBJECT-TYPE
    SYNTAX      Counter64
    MAX-ACCESS  read-only
    STATUS      current
    DESCRIPTION
        "The value of tmnxBsxUrlFltrStatsUrlDefAction indicates the number of
         times the url filter resulted in taking the default action by the last
         filtering type within the filter."
    ::= { tmnxBsxUrlFltrStatsEntry 35 }

tmnxBsxUrlFltrStatsIcapDefault   OBJECT-TYPE
    SYNTAX      Counter64
    MAX-ACCESS  read-only
    STATUS      current
    DESCRIPTION
        "The value of tmnxBsxUrlFltrStatsIcapDefault indicates the number of
         times the ICAP filter takes the default action due to the url filter's
         inability to send the request to an ICAP server or receiving a
         malformed response from it."
    ::= { tmnxBsxUrlFltrStatsEntry 36 }

tmnxBsxUrlFltrStatsWSClassOvrHit OBJECT-TYPE
    SYNTAX      Counter64
    MAX-ACCESS  read-only
    STATUS      current
    DESCRIPTION
        "The value of tmnxBsxUrlFltrStatsWSClassOvrHit indicates the number of
         lookups that matched entries in the classification override entries."
    ::= { tmnxBsxUrlFltrStatsEntry 37 }

tmnxBsxUrlFltrStatsWSClassOvrMis OBJECT-TYPE
    SYNTAX      Counter64
    MAX-ACCESS  read-only
    STATUS      current
    DESCRIPTION
        "The value of tmnxBsxUrlFltrStatsWSClassOvrMis indicates the number of
         lookups that missed entries in the classification override entries."
    ::= { tmnxBsxUrlFltrStatsEntry 38 }

tmnxBsxUrlFltrUrlListTable       OBJECT-TYPE
    SYNTAX      SEQUENCE OF TmnxBsxUrlFltrUrlListEntry
    MAX-ACCESS  not-accessible
    STATUS      current
    DESCRIPTION
        "The tmnxBsxUrlFltrUrlListTable contains URL list names, as defined in
         the tmnxBsxUrlListTable. Each entry is associated with a URL filter,
         as defined in the tmnxBsxUrlFilterTable.

         The specification of a URL list may only be done when the
         tmnxBsxIcapServerTable has no entries associated with the same URL
         filter and AA group.

         Furthermore, there can only be one entry per URL filter."
    ::= { tmnxBsxUrlFilterObjs 7 }

tmnxBsxUrlFltrUrlListEntry       OBJECT-TYPE
    SYNTAX      TmnxBsxUrlFltrUrlListEntry
    MAX-ACCESS  not-accessible
    STATUS      current
    DESCRIPTION
        "Each tmnxBsxUrlFltrUrlListEntry represents a URL list.

         Entries can be created and deleted via SNMP set operations to
         tmnxBsxUrlFltrUrlListRowStatus."
    INDEX       {
        tmnxBsxIsaAaGroupIndex,
        tmnxBsxUrlFilterName,
        tmnxBsxUrlFltrUrlListName
    }
    ::= { tmnxBsxUrlFltrUrlListTable 1 }

TmnxBsxUrlFltrUrlListEntry       ::= SEQUENCE
{
    tmnxBsxUrlFltrUrlListName        TNamedItem,
    tmnxBsxUrlFltrUrlListRowStatus   RowStatus,
    tmnxBsxUrlFltrUrlListRowLastCh   TimeStamp,
    tmnxBsxUrlFilterBlListDefAction  TmnxBsxUrlFilterDefaultAction,
    tmnxBsxUrlFilterBlListDefHtRedir TNamedItemOrEmpty,
    tmnxBsxUrlFilterBlListHttpRedir  TNamedItemOrEmpty
}

tmnxBsxUrlFltrUrlListName        OBJECT-TYPE
    SYNTAX      TNamedItem
    MAX-ACCESS  not-accessible
    STATUS      current
    DESCRIPTION
        "The value of tmnxBsxUrlFltrUrlListName specifies the URL deny-list
         name, as defined in the tmnxBsxUrlListTable."
    ::= { tmnxBsxUrlFltrUrlListEntry 1 }

tmnxBsxUrlFltrUrlListRowStatus   OBJECT-TYPE
    SYNTAX      RowStatus
    MAX-ACCESS  read-create
    STATUS      current
    DESCRIPTION
        "The value of tmnxBsxUrlFltrUrlListRowStatus specifies the row status.
         It allows entries to be created and deleted in
         tmnxBsxUrlFltrUrlListTable."
    ::= { tmnxBsxUrlFltrUrlListEntry 2 }

tmnxBsxUrlFltrUrlListRowLastCh   OBJECT-TYPE
    SYNTAX      TimeStamp
    MAX-ACCESS  read-only
    STATUS      current
    DESCRIPTION
        "The value of tmnxBsxUrlFltrUrlListRowLastCh indicates the last time,
         since system startup, a successful SNMP set caused a value in this row
         to change."
    ::= { tmnxBsxUrlFltrUrlListEntry 3 }

tmnxBsxUrlFilterBlListDefAction  OBJECT-TYPE
    SYNTAX      TmnxBsxUrlFilterDefaultAction
    MAX-ACCESS  read-create
    STATUS      current
    DESCRIPTION
        "The value of tmnxBsxUrlFilterBlListDefAction
         specifies the default  action to take when this
         URL deny-list is out of service."
    DEFVAL      { blockAll }
    ::= { tmnxBsxUrlFltrUrlListEntry 4 }

tmnxBsxUrlFilterBlListDefHtRedir OBJECT-TYPE
    SYNTAX      TNamedItemOrEmpty
    MAX-ACCESS  read-create
    STATUS      current
    DESCRIPTION
        "The value of tmnxBsxUrlFilterBlListDefHtRedir specifies the HTTP
         redirect that will be applied as defined in the tmnxBsxHttpRedirTable.
         An empty value specifies no HTTP redirect.

         A tmnxBsxUrlFilterBlListDefAction must have a value of
         'blockHttpRedirect(1)' if tmnxBsxUrlFilterBlListDefHtRedir is not an
         empty string."
    DEFVAL      { "" }
    ::= { tmnxBsxUrlFltrUrlListEntry 5 }

tmnxBsxUrlFilterBlListHttpRedir  OBJECT-TYPE
    SYNTAX      TNamedItemOrEmpty
    MAX-ACCESS  read-create
    STATUS      current
    DESCRIPTION
        "The value of tmnxBsxUrlFilterBlListHttpRedir specifies the HTTP
         redirect that will be applied when the local-filtering URL deny-list
         blocks an HTTP request. This HTTP redirect must exist in the
         tmnxBsxHttpRedirTable.

         An empty value specifies no HTTP redirect."
    DEFVAL      { "" }
    ::= { tmnxBsxUrlFltrUrlListEntry 6 }

tmnxBsxUrlFltrUrlListStatsTable  OBJECT-TYPE
    SYNTAX      SEQUENCE OF TmnxBsxUrlFltrUrlListStatsEntry
    MAX-ACCESS  not-accessible
    STATUS      current
    DESCRIPTION
        "The tmnxBsxUrlFltrUrlListStatsTable contains operational information
         related to a particular URL deny-list associated with a particular URL
         filter in an AA group."
    ::= { tmnxBsxUrlFilterObjs 8 }

tmnxBsxUrlFltrUrlListStatsEntry  OBJECT-TYPE
    SYNTAX      TmnxBsxUrlFltrUrlListStatsEntry
    MAX-ACCESS  not-accessible
    STATUS      current
    DESCRIPTION
        "Each entry represents the statistics for a particular AA URL filter
         URL list.

         An index with a valid URL Filter URL list (an existing row in
         tmnxBsxUrlFltrUrlListTable) and tmnxChassisIndex set to one with a
         zero value for each of tmnxBsxCardSlotEsaId and tmnxBsxMdaSlotEsaVmId
         will return the summarized per group and URL Filter URL list
         statistics.

         Entries will appears in this table only for equipped ISA-AA MDAs
         associated with an AA group, URL filter and URL list."
    INDEX       {
        tmnxBsxIsaAaGroupIndex,
        tmnxBsxUrlFilterName,
        tmnxBsxUrlFltrUrlListName,
        tmnxChassisIndex,
        tmnxBsxCardSlotEsaId,
        tmnxBsxMdaSlotEsaVmId
    }
    ::= { tmnxBsxUrlFltrUrlListStatsTable 1 }

TmnxBsxUrlFltrUrlListStatsEntry  ::= SEQUENCE
{
    tmnxBsxUrlFltrUrlListStatLkup    Counter64,
    tmnxBsxUrlFltrUrlListStatMatch   Counter64,
    tmnxBsxUrlFltrUrlListStatDefault Counter64
}

tmnxBsxUrlFltrUrlListStatLkup    OBJECT-TYPE
    SYNTAX      Counter64
    MAX-ACCESS  read-only
    STATUS      current
    DESCRIPTION
        "The value of tmnxBsxUrlFltrUrlListStatLkup indicates the number of URL
         list lookups."
    ::= { tmnxBsxUrlFltrUrlListStatsEntry 1 }

tmnxBsxUrlFltrUrlListStatMatch   OBJECT-TYPE
    SYNTAX      Counter64
    MAX-ACCESS  read-only
    STATUS      current
    DESCRIPTION
        "The value of tmnxBsxUrlFltrUrlListStatMatch indicates the number of
         lookups that matched entries in the URL list."
    ::= { tmnxBsxUrlFltrUrlListStatsEntry 2 }

tmnxBsxUrlFltrUrlListStatDefault OBJECT-TYPE
    SYNTAX      Counter64
    MAX-ACCESS  read-only
    STATUS      current
    DESCRIPTION
        "The value of tmnxBsxUrlFltrUrlListStatDefault indicates the number of
         lookups that resulted in taking the URL list configured default
         action."
    ::= { tmnxBsxUrlFltrUrlListStatsEntry 3 }

tmnxBsxWebServServerTable        OBJECT-TYPE
    SYNTAX      SEQUENCE OF TmnxBsxWebServServerEntry
    MAX-ACCESS  not-accessible
    STATUS      current
    DESCRIPTION
        "The tmnxBsxWebServServerTable allows the configuration of objects
         related to a particular web services server associated with a
         particular URL filter."
    ::= { tmnxBsxUrlFilterObjs 9 }

tmnxBsxWebServServerEntry        OBJECT-TYPE
    SYNTAX      TmnxBsxWebServServerEntry
    MAX-ACCESS  not-accessible
    STATUS      current
    DESCRIPTION
        "Each entry represents the configuration for a particular AA URL filter
         and web services server.

         Only IPv4 address types are supported for the web services server.

         The specification of a web services server may only be done when the
         value of tmnxBsxUrlFltrWebServFqdn is default.

         Entries in this table can be created and deleted via SNMP set
         operations to tmnxBsxWebServServerRowStatus."
    INDEX       {
        tmnxBsxIsaAaGroupIndex,
        tmnxBsxUrlFilterName,
        tmnxBsxWebServServerAddrType,
        tmnxBsxWebServServerAddr,
        tmnxBsxWebServServerPort
    }
    ::= { tmnxBsxWebServServerTable 1 }

TmnxBsxWebServServerEntry        ::= SEQUENCE
{
    tmnxBsxWebServServerAddrType     InetAddressType,
    tmnxBsxWebServServerAddr         InetAddress,
    tmnxBsxWebServServerPort         Unsigned32,
    tmnxBsxWebServServerRowStatus    RowStatus,
    tmnxBsxWebServServerRowLastChg   TimeStamp,
    tmnxBsxWebServServerDescription  TItemDescription,
    tmnxBsxWebServServerAdminState   TmnxAdminState
}

tmnxBsxWebServServerAddrType     OBJECT-TYPE
    SYNTAX      InetAddressType
    MAX-ACCESS  not-accessible
    STATUS      current
    DESCRIPTION
        "The value of tmnxBsxWebServServerAddrType specifies the type of
         address stored in tmnxBsxWebServServerAddr."
    ::= { tmnxBsxWebServServerEntry 1 }

tmnxBsxWebServServerAddr         OBJECT-TYPE
    SYNTAX      InetAddress (SIZE (4|16))
    MAX-ACCESS  not-accessible
    STATUS      current
    DESCRIPTION
        "The value of tmnxBsxWebServServerAddr specifies the IP address of the
         web services server.

         A valid unicast IP address must be specified at row creation time."
    ::= { tmnxBsxWebServServerEntry 2 }

tmnxBsxWebServServerPort         OBJECT-TYPE
    SYNTAX      Unsigned32 (1..65535)
    MAX-ACCESS  not-accessible
    STATUS      current
    DESCRIPTION
        "The value of tmnxBsxWebServServerPort specifies the web services
         server port."
    ::= { tmnxBsxWebServServerEntry 3 }

tmnxBsxWebServServerRowStatus    OBJECT-TYPE
    SYNTAX      RowStatus
    MAX-ACCESS  read-create
    STATUS      current
    DESCRIPTION
        "The value of tmnxBsxWebServServerRowStatus specifies the row status.
         It allows entries to be created and deleted in
         tmnxBsxWebServServerTable.

         Rows are created by specifying the value of 'createAndGo (4)', and
         deleted by specifying the value of 'destroy (6)'."
    ::= { tmnxBsxWebServServerEntry 4 }

tmnxBsxWebServServerRowLastChg   OBJECT-TYPE
    SYNTAX      TimeStamp
    MAX-ACCESS  read-only
    STATUS      current
    DESCRIPTION
        "The value of tmnxBsxWebServServerRowLastChg indicates the last time,
         since system startup, a successful set was performed on this row."
    ::= { tmnxBsxWebServServerEntry 5 }

tmnxBsxWebServServerDescription  OBJECT-TYPE
    SYNTAX      TItemDescription
    MAX-ACCESS  read-create
    STATUS      current
    DESCRIPTION
        "The value of tmnxBsxWebServServerDescription specifies the description
         of the web services server."
    DEFVAL      { "" }
    ::= { tmnxBsxWebServServerEntry 6 }

tmnxBsxWebServServerAdminState   OBJECT-TYPE
    SYNTAX      TmnxAdminState
    MAX-ACCESS  read-create
    STATUS      current
    DESCRIPTION
        "The value of tmnxBsxWebServServerAdminState specifies the
         administrative state of the web services server."
    DEFVAL      { outOfService }
    ::= { tmnxBsxWebServServerEntry 7 }

tmnxBsxWebServServerStatsTable   OBJECT-TYPE
    SYNTAX      SEQUENCE OF TmnxBsxWebServServerStatsEntry
    MAX-ACCESS  not-accessible
    STATUS      current
    DESCRIPTION
        "The tmnxBsxWebServServerStatsTable contains operational information
         related to a particular Web Service server associated with a
         particular URL filter.

         Each row contains the status and performance-oriented statistics
         information per group, URL filter and Web Service server for an ISA-AA
         uniquely identified by the tmnxChassisIndex, tmnxBsxCardSlotEsaId, and
         the tmnxBsxMdaSlotEsaVmId."
    ::= { tmnxBsxUrlFilterObjs 10 }

tmnxBsxWebServServerStatsEntry   OBJECT-TYPE
    SYNTAX      TmnxBsxWebServServerStatsEntry
    MAX-ACCESS  not-accessible
    STATUS      current
    DESCRIPTION
        "Each entry represents the statistics for a particular AA URL filter
         and Web Service server.

         An index with a valid Web Service server (an existing row in
         tmnxBsxWebServServerTable) and tmnxChassisIndex set to one with a
         zero value for each of tmnxBsxCardSlotEsaId and tmnxBsxMdaSlotEsaVmId will
         return the following per group, URL Filter and Web Service server:
            * the summarized statistics, and
            * the worst case value for tmnxBsxWebServServerStatsRTT

         Entries will appears in this table only for equipped ISA-AA MDAs
         associated with an AA group, URL filter and Web Service server."
    INDEX       {
        tmnxBsxIsaAaGroupIndex,
        tmnxBsxUrlFilterName,
        tmnxBsxWebServServerAddrType,
        tmnxBsxWebServServerAddr,
        tmnxBsxWebServServerPort,
        tmnxChassisIndex,
        tmnxBsxCardSlotEsaId,
        tmnxBsxMdaSlotEsaVmId
    }
    ::= { tmnxBsxWebServServerStatsTable 1 }

TmnxBsxWebServServerStatsEntry   ::= SEQUENCE
{
    tmnxBsxWebServServerOperState    TmnxOperState,
    tmnxBsxWebServServerOperFlags    BITS,
    tmnxBsxWebServServerStatsReqs    Counter64,
    tmnxBsxWebServServerStatsReqErr  Counter64,
    tmnxBsxWebServServerStatsResp    Counter64,
    tmnxBsxWebServServerStatsRespErr Counter64,
    tmnxBsxWebServServerStatsRTT     Unsigned32,
    tmnxBsxWebServServerStatsReqRate Unsigned32,
    tmnxBsxWebServServerStatsConnCnt Unsigned32,
    tmnxBsxWebServServerStatsConnEst Unsigned32
}

tmnxBsxWebServServerOperState    OBJECT-TYPE
    SYNTAX      TmnxOperState
    MAX-ACCESS  read-only
    STATUS      current
    DESCRIPTION
        "The value of tmnxBsxWebServServerOperState indicates the operational
         state of the Web Service server."
    ::= { tmnxBsxWebServServerStatsEntry 1 }

tmnxBsxWebServServerOperFlags    OBJECT-TYPE
    SYNTAX      BITS {
        adminDown    (0),
        tcpConnError (1)
    }
    MAX-ACCESS  read-only
    STATUS      current
    DESCRIPTION
        "The value of tmnxBsxWebServServerOperFlags indicates the different
         conditions that affect the operating status of an Web Service server.

         The bit values are:
            adminDown(0)             - Web Service server instance is administratively
                                       down.
            tcpConnError(1)          - TCP communication error has occurred."
    ::= { tmnxBsxWebServServerStatsEntry 2 }

tmnxBsxWebServServerStatsReqs    OBJECT-TYPE
    SYNTAX      Counter64
    MAX-ACCESS  read-only
    STATUS      current
    DESCRIPTION
        "The value of tmnxBsxWebServServerStatsReqs indicates the number of
         rating requests which have been sent to this Web Service server."
    ::= { tmnxBsxWebServServerStatsEntry 3 }

tmnxBsxWebServServerStatsReqErr  OBJECT-TYPE
    SYNTAX      Counter64
    MAX-ACCESS  read-only
    STATUS      current
    DESCRIPTION
        "The value of tmnxBsxWebServServerStatsReqErr indicates the number of
         rating requests that were unable to be sent to the Web Service server."
    ::= { tmnxBsxWebServServerStatsEntry 4 }

tmnxBsxWebServServerStatsResp    OBJECT-TYPE
    SYNTAX      Counter64
    MAX-ACCESS  read-only
    STATUS      current
    DESCRIPTION
        "The value of tmnxBsxWebServServerStatsResp indicates the number of
         successful rating responses from the web-service server."
    ::= { tmnxBsxWebServServerStatsEntry 5 }

tmnxBsxWebServServerStatsRespErr OBJECT-TYPE
    SYNTAX      Counter64
    MAX-ACCESS  read-only
    STATUS      current
    DESCRIPTION
        "The value of tmnxBsxWebServServerStatsRespErr indicates the number of
         rating responses that contained an error."
    ::= { tmnxBsxWebServServerStatsEntry 6 }

tmnxBsxWebServServerStatsRTT     OBJECT-TYPE
    SYNTAX      Unsigned32
    UNITS       "microseconds"
    MAX-ACCESS  read-only
    STATUS      current
    DESCRIPTION
        "The value of tmnxBsxWebServServerStatsRTT indicates the average round
         trip time from the ISA to the Web Service server."
    ::= { tmnxBsxWebServServerStatsEntry 7 }

tmnxBsxWebServServerStatsReqRate OBJECT-TYPE
    SYNTAX      Unsigned32
    UNITS       "requests per second"
    MAX-ACCESS  read-only
    STATUS      current
    DESCRIPTION
        "The value of tmnxBsxWebServServerStatsReqRate indicates the average
         number of rating requests sent per second over the last 10 second
         period."
    ::= { tmnxBsxWebServServerStatsEntry 8 }

tmnxBsxWebServServerStatsConnCnt OBJECT-TYPE
    SYNTAX      Unsigned32
    MAX-ACCESS  read-only
    STATUS      current
    DESCRIPTION
        "The value of tmnxBsxWebServServerStatsConnCnt indicates the number of
         TCP connections which can be established with the Web Service server."
    ::= { tmnxBsxWebServServerStatsEntry 9 }

tmnxBsxWebServServerStatsConnEst OBJECT-TYPE
    SYNTAX      Unsigned32
    MAX-ACCESS  read-only
    STATUS      current
    DESCRIPTION
        "The value of tmnxBsxWebServServerStatsConnEst indicates the current
         number of TCP connections which are established with the Web Service
         server."
    ::= { tmnxBsxWebServServerStatsEntry 10 }

tmnxBsxHttpNotifObjs             OBJECT IDENTIFIER ::= { tmnxBsxObjs 15 }

tmnxBsxHttpNotifScalars          OBJECT IDENTIFIER ::= { tmnxBsxHttpNotifObjs 1 }

tmnxBsxHttpNotifLastChangeTime   OBJECT-TYPE
    SYNTAX      TimeStamp
    MAX-ACCESS  read-only
    STATUS      current
    DESCRIPTION
        "The value of tmnxBsxHttpNotifLastChangeTime indicates the last time,
         since system startup, a successful set was performed on
         tmnxBsxHttpNotifTable."
    ::= { tmnxBsxHttpNotifScalars 1 }

tmnxBsxHttpNotifTable            OBJECT-TYPE
    SYNTAX      SEQUENCE OF TmnxBsxHttpNotifEntry
    MAX-ACCESS  not-accessible
    STATUS      current
    DESCRIPTION
        "The tmnxBsxHttpNotifTable contains a list of HTTP Notification
         Templates for each Application Assurance group."
    ::= { tmnxBsxHttpNotifObjs 2 }

tmnxBsxHttpNotifEntry            OBJECT-TYPE
    SYNTAX      TmnxBsxHttpNotifEntry
    MAX-ACCESS  not-accessible
    STATUS      current
    DESCRIPTION
        "Each entry represents the configuration for a particular AA HTTP
         Notification Template.

         Entries in this table can be created and deleted via SNMP set
         operations to tmnxBsxHttpNotifRowStatus."
    INDEX       {
        tmnxBsxIsaAaGroupIndex,
        IMPLIED tmnxBsxHttpNotifName
    }
    ::= { tmnxBsxHttpNotifTable 1 }

TmnxBsxHttpNotifEntry            ::= SEQUENCE
{
    tmnxBsxHttpNotifName             TNamedItem,
    tmnxBsxHttpNotifRowStatus        RowStatus,
    tmnxBsxHttpNotifRowLastChange    TimeStamp,
    tmnxBsxHttpNotifAdminState       TmnxAdminState,
    tmnxBsxHttpNotifDescription      TItemDescription,
    tmnxBsxHttpNotifTemplateId       Unsigned32,
    tmnxBsxHttpNotifScriptUrl        SnmpAdminString,
    tmnxBsxHttpNotifInterval         Unsigned32
}

tmnxBsxHttpNotifName             OBJECT-TYPE
    SYNTAX      TNamedItem
    MAX-ACCESS  not-accessible
    STATUS      current
    DESCRIPTION
        "The value of tmnxBsxHttpNotifName specifies the name of the HTTP
         Notification configuration."
    ::= { tmnxBsxHttpNotifEntry 1 }

tmnxBsxHttpNotifRowStatus        OBJECT-TYPE
    SYNTAX      RowStatus
    MAX-ACCESS  read-create
    STATUS      current
    DESCRIPTION
        "The value of tmnxBsxHttpNotifRowStatus specifies the row status. It
         allows entries to be created and deleted in tmnxBsxHttpNotifTable.

         Rows are created by specifying the value of 'createAndGo (4)', and
         deleted by specifying the value of 'destroy (6)'."
    ::= { tmnxBsxHttpNotifEntry 2 }

tmnxBsxHttpNotifRowLastChange    OBJECT-TYPE
    SYNTAX      TimeStamp
    MAX-ACCESS  read-only
    STATUS      current
    DESCRIPTION
        "The value of tmnxBsxHttpNotifRowLastChange indicates the last time,
         since system startup, a successful set was performed on this row."
    ::= { tmnxBsxHttpNotifEntry 3 }

tmnxBsxHttpNotifAdminState       OBJECT-TYPE
    SYNTAX      TmnxAdminState
    MAX-ACCESS  read-create
    STATUS      current
    DESCRIPTION
        "The value of tmnxBsxHttpNotifAdminState specifies the administrative
         state of the HTTP Notification."
    DEFVAL      { outOfService }
    ::= { tmnxBsxHttpNotifEntry 4 }

tmnxBsxHttpNotifDescription      OBJECT-TYPE
    SYNTAX      TItemDescription
    MAX-ACCESS  read-create
    STATUS      current
    DESCRIPTION
        "The value of tmnxBsxHttpNotifDescription specifies the description of
         the HTTP Notification."
    DEFVAL      { "" }
    ::= { tmnxBsxHttpNotifEntry 5 }

tmnxBsxHttpNotifTemplateId       OBJECT-TYPE
    SYNTAX      Unsigned32
    MAX-ACCESS  read-create
    STATUS      current
    DESCRIPTION
        "The value of tmnxBsxHttpNotifTemplateId specifies the template Id of
         this HTTP Notification. Template Ids are defined in the
         tmnxBsxTListAttribTable in rows where the index tmnxBsxTListName has a
         value of 'http-notification-template' and where the index
         tmnxBsxTListAttribName has a value of 'template'.

         A tmnxBsxHttpNotifTemplateId of 0 specifies no template Id."
    DEFVAL      { 0 }
    ::= { tmnxBsxHttpNotifEntry 6 }

tmnxBsxHttpNotifScriptUrl        OBJECT-TYPE
    SYNTAX      SnmpAdminString
    MAX-ACCESS  read-create
    STATUS      current
    DESCRIPTION
        "The value of tmnxBsxHttpNotifScriptUrl specifies the URL of the script
         to insert into the HTTP response."
    DEFVAL      { "" }
    ::= { tmnxBsxHttpNotifEntry 7 }

tmnxBsxHttpNotifInterval         OBJECT-TYPE
    SYNTAX      Unsigned32 (0 | 1..1440)
    UNITS       "minutes"
    MAX-ACCESS  read-create
    STATUS      current
    DESCRIPTION
        "The value of tmnxBsxHttpNotifInterval specifies the minimum time to
         wait before re-inserting script URL into the HTTP response for a
         specific subscriber.

         A tmnxBsxHttpNotifInterval of 0 specifies the insertion of the script
         URL is to occur one-time."
    DEFVAL      { 0 }
    ::= { tmnxBsxHttpNotifEntry 8 }

tmnxBsxHttpNotifStatTable        OBJECT-TYPE
    SYNTAX      SEQUENCE OF TmnxBsxHttpNotifStatEntry
    MAX-ACCESS  not-accessible
    STATUS      current
    DESCRIPTION
        "The tmnxBsxHttpNotifStatTable contains statistics for HTTP
         Notification."
    ::= { tmnxBsxHttpNotifObjs 3 }

tmnxBsxHttpNotifStatEntry        OBJECT-TYPE
    SYNTAX      TmnxBsxHttpNotifStatEntry
    MAX-ACCESS  not-accessible
    STATUS      current
    DESCRIPTION
        "Each tmnxBsxHttpNotifStatEntry contains statistics for HTTP
         Notification.

         An index with a valid tmnxBsxAaGrpPartIndex/tmnxBsxHttpNotifName (an
         existing row in tmnxBsxHttpNotifTable), tmnxChassisIndex set to one,
         and a zero value for each of tmnxBsxCardSlotEsaId and
         tmnxBsxMdaSlotEsaVmId will return the summarized per group and HTTP
         notification name statistics."
    INDEX       {
        tmnxBsxAaGrpPartIndex,
        tmnxBsxHttpNotifName,
        tmnxChassisIndex,
        tmnxBsxCardSlotEsaId,
        tmnxBsxMdaSlotEsaVmId
    }
    ::= { tmnxBsxHttpNotifStatTable 1 }

TmnxBsxHttpNotifStatEntry        ::= SEQUENCE
{
    tmnxBsxHttpNotifStatDiscntTime   TimeStamp,
    tmnxBsxHttpNotifStatInserted     Counter64,
    tmnxBsxHttpNotifStatCritNoMtch   Counter64,
    tmnxBsxHttpNotifStatSuccess      Counter64,
    tmnxBsxHttpNotifStatFailed       Counter64
}

tmnxBsxHttpNotifStatDiscntTime   OBJECT-TYPE
    SYNTAX      TimeStamp
    MAX-ACCESS  read-only
    STATUS      current
    DESCRIPTION
        "The value of tmnxBsxHttpNotifStatDiscntTime indicates the
         SNMPv2-MIB::sysUpTime (centiseconds) when the ISA-AA MDA within the
         group has last changed status."
    ::= { tmnxBsxHttpNotifStatEntry 1 }

tmnxBsxHttpNotifStatInserted     OBJECT-TYPE
    SYNTAX      Counter64
    MAX-ACCESS  read-only
    STATUS      current
    DESCRIPTION
        "The value of tmnxBsxHttpNotifStatInserted indicates the number of
         times the script URL was inserted into a message."
    ::= { tmnxBsxHttpNotifStatEntry 2 }

tmnxBsxHttpNotifStatCritNoMtch   OBJECT-TYPE
    SYNTAX      Counter64
    MAX-ACCESS  read-only
    STATUS      current
    DESCRIPTION
        "The value of tmnxBsxHttpNotifStatCritNoMtch indicates the number of
         messages which did not match the selection criteria for insertion of
         the script URL."
    ::= { tmnxBsxHttpNotifStatEntry 3 }

tmnxBsxHttpNotifStatSuccess      OBJECT-TYPE
    SYNTAX      Counter64
    MAX-ACCESS  read-only
    STATUS      current
    DESCRIPTION
        "The value of tmnxBsxHttpNotifStatSuccess indicates the number of times
         a HTTP notification success report was received."
    ::= { tmnxBsxHttpNotifStatEntry 4 }

tmnxBsxHttpNotifStatFailed       OBJECT-TYPE
    SYNTAX      Counter64
    MAX-ACCESS  read-only
    STATUS      current
    DESCRIPTION
        "The value of tmnxBsxHttpNotifStatFailed indicates the number of times
         a HTTP notification is known to have failed."
    ::= { tmnxBsxHttpNotifStatEntry 5 }

tmnxBsxDnsIpCacheObjs            OBJECT IDENTIFIER ::= { tmnxBsxObjs 16 }

tmnxBsxDnsIpCacheScalars         OBJECT IDENTIFIER ::= { tmnxBsxDnsIpCacheObjs 1 }

tmnxBsxDnsIpCacheLastCTime       OBJECT-TYPE
    SYNTAX      TimeStamp
    MAX-ACCESS  read-only
    STATUS      current
    DESCRIPTION
        "The value of tmnxBsxDnsIpCacheLastCTime indicates the last time, since
         system startup, a successful SNMP set on tmnxBsxDnsIpCacheTable caused
         a value to change."
    ::= { tmnxBsxDnsIpCacheScalars 1 }

tmnxBsxDnsIpCacheDomainLastCTime OBJECT-TYPE
    SYNTAX      TimeStamp
    MAX-ACCESS  read-only
    STATUS      current
    DESCRIPTION
        "The value of tmnxBsxDnsIpCacheDomainLastCTime indicates the last time,
         since system startup, a successful SNMP set on
         tmnxBsxDnsIpCacheDomainTable caused a value to change."
    ::= { tmnxBsxDnsIpCacheScalars 2 }

tmnxBsxDnsIpCacheServerLastCTime OBJECT-TYPE
    SYNTAX      TimeStamp
    MAX-ACCESS  read-only
    STATUS      current
    DESCRIPTION
        "The value of tmnxBsxDnsIpCacheServerLastCTime indicates the last time,
         since system startup, a successful SNMP set on
         tmnxBsxDnsIpCacheServerTable caused a value to change."
    ::= { tmnxBsxDnsIpCacheScalars 3 }

tmnxBsxDnsIpCacheProxyLastCTime  OBJECT-TYPE
    SYNTAX      TimeStamp
    MAX-ACCESS  read-only
    STATUS      current
    DESCRIPTION
        "The value of tmnxBsxDnsIpCacheProxyLastCTime indicates the last time,
         since system startup, a configuration change caused a value to change
         in tmnxBsxDnsIpCacheProxyTable ."
    ::= { tmnxBsxDnsIpCacheScalars 4 }

tmnxBsxDnsIpCacheTable           OBJECT-TYPE
    SYNTAX      SEQUENCE OF TmnxBsxDnsIpCacheEntry
    MAX-ACCESS  not-accessible
    STATUS      current
    DESCRIPTION
        "The tmnxBsxDnsIpCacheTable contains a list of DNS IP caches that will
         be populated when specified by tmnxBsxAqpActDnsIpCache. An entry will
         be added to an internal IP address cache if the DNS response domain
         matches a configured domain expression in the
         tmnxBsxDnsIpCacheDomainTable and the DNS server IP address is listed
         in the tmnxBsxDnsIpCacheServerTable.

         Entries in this table are created and deleted via SNMP set operations
         to tmnxBsxDnsIpCacheRowStatus."
    ::= { tmnxBsxDnsIpCacheObjs 2 }

tmnxBsxDnsIpCacheEntry           OBJECT-TYPE
    SYNTAX      TmnxBsxDnsIpCacheEntry
    MAX-ACCESS  not-accessible
    STATUS      current
    DESCRIPTION
        "Each entry specifies the size and watermarks of a DNS IP cache.

         Entries in this table are created and deleted via SNMP set operations
         to tmnxBsxDnsIpCacheRowStatus."
    INDEX       {
        tmnxBsxIsaAaGroupIndex,
        tmnxBsxDnsIpCacheName
    }
    ::= { tmnxBsxDnsIpCacheTable 1 }

TmnxBsxDnsIpCacheEntry           ::= SEQUENCE
{
    tmnxBsxDnsIpCacheName            TNamedItem,
    tmnxBsxDnsIpCacheRowStatus       RowStatus,
    tmnxBsxDnsIpCacheRowLastChanged  TimeStamp,
    tmnxBsxDnsIpCacheSize            Unsigned32,
    tmnxBsxDnsIpCacheHighWatermark   Unsigned32,
    tmnxBsxDnsIpCacheLowWatermark    Unsigned32,
    tmnxBsxDnsIpCacheAdminState      TmnxAdminState,
    tmnxBsxDnsIpCacheDescription     TItemDescription
}

tmnxBsxDnsIpCacheName            OBJECT-TYPE
    SYNTAX      TNamedItem
    MAX-ACCESS  not-accessible
    STATUS      current
    DESCRIPTION
        "The value of tmnxBsxDnsIpCacheName specifies the name of the DNS IP
         cache configuration."
    ::= { tmnxBsxDnsIpCacheEntry 1 }

tmnxBsxDnsIpCacheRowStatus       OBJECT-TYPE
    SYNTAX      RowStatus
    MAX-ACCESS  read-create
    STATUS      current
    DESCRIPTION
        "The value of tmnxBsxDnsIpCacheRowStatus specifies the row status. It
         allows entries to be created and deleted in the
         tmnxBsxDnsIpCacheTable.

         Rows are created by specifying the value of 'createAndGo (4)', and
         deleted by specifying the value of 'destroy (6)'."
    ::= { tmnxBsxDnsIpCacheEntry 2 }

tmnxBsxDnsIpCacheRowLastChanged  OBJECT-TYPE
    SYNTAX      TimeStamp
    MAX-ACCESS  read-only
    STATUS      current
    DESCRIPTION
        "The value of tmnxBsxDnsIpCacheRowLastChanged indicates the last time,
         since system startup, a successful SNMP set caused a value in this row
         to change."
    ::= { tmnxBsxDnsIpCacheEntry 3 }

tmnxBsxDnsIpCacheSize            OBJECT-TYPE
    SYNTAX      Unsigned32 (10..64000)
    MAX-ACCESS  read-create
    STATUS      current
    DESCRIPTION
        "The value of tmnxBsxDnsIpCacheSize specifies the maximum number of IP
         addresses that can be stored in the cache. Decreasing the size of the
         cache will cause the cache to be cleared."
    DEFVAL      { 10 }
    ::= { tmnxBsxDnsIpCacheEntry 4 }

tmnxBsxDnsIpCacheHighWatermark   OBJECT-TYPE
    SYNTAX      Unsigned32 (0..100)
    MAX-ACCESS  read-create
    STATUS      current
    DESCRIPTION
        "The value of tmnxBsxDnsIpCacheHighWatermark specifies the percent
         utilization of the IP cache relative to the tmnxBsxDnsIpCacheSize.
         When the value is exceeded, the threshold alarm will be raised by the
         agent. The value must be larger than or equal to
         tmnxBsxDnsIpCacheLowWatermark."
    DEFVAL      { 90 }
    ::= { tmnxBsxDnsIpCacheEntry 5 }

tmnxBsxDnsIpCacheLowWatermark    OBJECT-TYPE
    SYNTAX      Unsigned32 (0..100)
    MAX-ACCESS  read-create
    STATUS      current
    DESCRIPTION
        "The value of tmnxBsxDnsIpCacheLowWatermark specifies the percent
         utilization of the IP cache relative to the tmnxBsxDnsIpCacheSize. If
         a threshold alarm was raised and this value is exceeded, the threshold
         alarm will be cleared by the agent. The value must be lower than or
         equal to tmnxBsxDnsIpCacheHighWatermark."
    DEFVAL      { 80 }
    ::= { tmnxBsxDnsIpCacheEntry 6 }

tmnxBsxDnsIpCacheAdminState      OBJECT-TYPE
    SYNTAX      TmnxAdminState
    MAX-ACCESS  read-create
    STATUS      current
    DESCRIPTION
        "The value of tmnxBsxDnsIpCacheAdminState specifies the administrative
         state for the DNS IP cache. When 'outOfService(3)', the cache is not
         in use."
    DEFVAL      { outOfService }
    ::= { tmnxBsxDnsIpCacheEntry 7 }

tmnxBsxDnsIpCacheDescription     OBJECT-TYPE
    SYNTAX      TItemDescription
    MAX-ACCESS  read-create
    STATUS      current
    DESCRIPTION
        "The value of tmnxBsxDnsIpCacheDescription specifies the description of
         the DNS IP cache."
    DEFVAL      { "" }
    ::= { tmnxBsxDnsIpCacheEntry 8 }

tmnxBsxDnsIpCacheDomainTable     OBJECT-TYPE
    SYNTAX      SEQUENCE OF TmnxBsxDnsIpCacheDomainEntry
    MAX-ACCESS  not-accessible
    STATUS      current
    DESCRIPTION
        "The tmnxBsxDnsIpCacheDomainTable contains a list of DNS domain
         expressions used for matching as described by the
         tmnxBsxDnsIpCacheTable.

         Entries in this table are created and deleted via SNMP set operations
         to tmnxBsxDnsIpCacheDomainRowStatus."
    ::= { tmnxBsxDnsIpCacheObjs 3 }

tmnxBsxDnsIpCacheDomainEntry     OBJECT-TYPE
    SYNTAX      TmnxBsxDnsIpCacheDomainEntry
    MAX-ACCESS  not-accessible
    STATUS      current
    DESCRIPTION
        "Each tmnxBsxDnsIpCacheDomainEntry indicates a DNS domain."
    INDEX       {
        tmnxBsxIsaAaGroupIndex,
        tmnxBsxDnsIpCacheName,
        IMPLIED tmnxBsxDnsIpCacheDomainName
    }
    ::= { tmnxBsxDnsIpCacheDomainTable 1 }

TmnxBsxDnsIpCacheDomainEntry     ::= SEQUENCE
{
    tmnxBsxDnsIpCacheDomainName      TNamedItem,
    tmnxBsxDnsIpCacheDomainRowStatus RowStatus,
    tmnxBsxDnsIpCacheDomainRowLastCh TimeStamp,
    tmnxBsxDnsIpCacheDomainExprStr   TmnxBsxExprSubString
}

tmnxBsxDnsIpCacheDomainName      OBJECT-TYPE
    SYNTAX      TNamedItem
    MAX-ACCESS  not-accessible
    STATUS      current
    DESCRIPTION
        "The value of tmnxBsxDnsIpCacheDomainName specifies a unique name for
         this DNS domain."
    ::= { tmnxBsxDnsIpCacheDomainEntry 1 }

tmnxBsxDnsIpCacheDomainRowStatus OBJECT-TYPE
    SYNTAX      RowStatus
    MAX-ACCESS  read-create
    STATUS      current
    DESCRIPTION
        "The value of tmnxBsxDnsIpCacheDomainRowStatus specifies the row
         status. It allows entries to be created and deleted in the
         tmnxBsxDnsIpCacheDomainTable.

         Rows are created by specifying the value of 'createAndGo (4)', and
         deleted by specifying the value of 'destroy (6)'."
    ::= { tmnxBsxDnsIpCacheDomainEntry 2 }

tmnxBsxDnsIpCacheDomainRowLastCh OBJECT-TYPE
    SYNTAX      TimeStamp
    MAX-ACCESS  read-only
    STATUS      current
    DESCRIPTION
        "The value of tmnxBsxDnsIpCacheDomainRowLastCh indicates the last time,
         since system startup, a successful SNMP set caused a value in this row
         to change."
    ::= { tmnxBsxDnsIpCacheDomainEntry 3 }

tmnxBsxDnsIpCacheDomainExprStr   OBJECT-TYPE
    SYNTAX      TmnxBsxExprSubString
    MAX-ACCESS  read-create
    STATUS      current
    DESCRIPTION
        "The value of tmnxBsxDnsIpCacheDomainExprStr specifies a DNS domain
         substring expression to match against.  If set to an empty string, no
         matching is done."
    DEFVAL      { "" }
    ::= { tmnxBsxDnsIpCacheDomainEntry 4 }

tmnxBsxDnsIpCacheServerTable     OBJECT-TYPE
    SYNTAX      SEQUENCE OF TmnxBsxDnsIpCacheServerEntry
    MAX-ACCESS  not-accessible
    STATUS      current
    DESCRIPTION
        "The tmnxBsxDnsIpCacheServerTable contains a list of trusted DNS server
         IP addresses as described by the tmnxBsxDnsIpCacheTable.

         Entries in this table are created and deleted via SNMP set operations
         to tmnxBsxDnsIpCacheServerRowStatus."
    ::= { tmnxBsxDnsIpCacheObjs 4 }

tmnxBsxDnsIpCacheServerEntry     OBJECT-TYPE
    SYNTAX      TmnxBsxDnsIpCacheServerEntry
    MAX-ACCESS  not-accessible
    STATUS      current
    DESCRIPTION
        "Each tmnxBsxDnsIpCacheServerEntry indicates a trusted DNS server."
    INDEX       {
        tmnxBsxIsaAaGroupIndex,
        tmnxBsxDnsIpCacheName,
        tmnxBsxDnsIpCacheServerAddrType,
        tmnxBsxDnsIpCacheServerAddr
    }
    ::= { tmnxBsxDnsIpCacheServerTable 1 }

TmnxBsxDnsIpCacheServerEntry     ::= SEQUENCE
{
    tmnxBsxDnsIpCacheServerAddrType  InetAddressType,
    tmnxBsxDnsIpCacheServerAddr      InetAddress,
    tmnxBsxDnsIpCacheServerRowStatus RowStatus,
    tmnxBsxDnsIpCacheServerRowLastCh TimeStamp,
    tmnxBsxDnsIpCacheServerName      TNamedItemOrEmpty
}

tmnxBsxDnsIpCacheServerAddrType  OBJECT-TYPE
    SYNTAX      InetAddressType
    MAX-ACCESS  not-accessible
    STATUS      current
    DESCRIPTION
        "The value of tmnxBsxDnsIpCacheServerAddrType specifies the type of
         address contained in tmnxBsxDnsIpCacheServerAddr."
    ::= { tmnxBsxDnsIpCacheServerEntry 1 }

tmnxBsxDnsIpCacheServerAddr      OBJECT-TYPE
    SYNTAX      InetAddress (SIZE (4|16))
    MAX-ACCESS  not-accessible
    STATUS      current
    DESCRIPTION
        "The value of tmnxBsxDnsIpCacheServerAddr specifies the DNS server IP
         address."
    ::= { tmnxBsxDnsIpCacheServerEntry 2 }

tmnxBsxDnsIpCacheServerRowStatus OBJECT-TYPE
    SYNTAX      RowStatus
    MAX-ACCESS  read-create
    STATUS      current
    DESCRIPTION
        "The value of tmnxBsxDnsIpCacheServerRowStatus specifies the row
         status. It allows entries to be created and deleted in the
         tmnxBsxDnsIpCacheServerTable.

         Rows are created by specifying the value of 'createAndGo (4)', and
         deleted by specifying the value of 'destroy (6)'."
    ::= { tmnxBsxDnsIpCacheServerEntry 3 }

tmnxBsxDnsIpCacheServerRowLastCh OBJECT-TYPE
    SYNTAX      TimeStamp
    MAX-ACCESS  read-only
    STATUS      current
    DESCRIPTION
        "The value of tmnxBsxDnsIpCacheServerRowLastCh indicates the last time,
         since system startup, a successful SNMP set caused a value in this row
         to change."
    ::= { tmnxBsxDnsIpCacheServerEntry 4 }

tmnxBsxDnsIpCacheServerName      OBJECT-TYPE
    SYNTAX      TNamedItemOrEmpty
    MAX-ACCESS  read-create
    STATUS      current
    DESCRIPTION
        "The value of tmnxBsxDnsIpCacheServerName specifies the DNS name
         associated with this server IP address."
    DEFVAL      { "" }
    ::= { tmnxBsxDnsIpCacheServerEntry 5 }

tmnxBsxDnsIpCacheProxyTable      OBJECT-TYPE
    SYNTAX      SEQUENCE OF TmnxBsxDnsIpCacheProxyEntry
    MAX-ACCESS  not-accessible
    STATUS      current
    DESCRIPTION
        "The tmnxBsxDnsIpCacheProxyTable contains a list of trusted static IP
         addresses.

         Entries in this table are created and deleted via set operations to
         tmnxBsxDnsIpCacheProxyRowStatus."
    ::= { tmnxBsxDnsIpCacheObjs 5 }

tmnxBsxDnsIpCacheProxyEntry      OBJECT-TYPE
    SYNTAX      TmnxBsxDnsIpCacheProxyEntry
    MAX-ACCESS  not-accessible
    STATUS      current
    DESCRIPTION
        "Each tmnxBsxDnsIpCacheProxyEntry indicates a trusted static IP
         address."
    INDEX       {
        tmnxBsxIsaAaGroupIndex,
        tmnxBsxDnsIpCacheName,
        tmnxBsxDnsIpCacheProxyAddrType,
        tmnxBsxDnsIpCacheProxyAddr
    }
    ::= { tmnxBsxDnsIpCacheProxyTable 1 }

TmnxBsxDnsIpCacheProxyEntry      ::= SEQUENCE
{
    tmnxBsxDnsIpCacheProxyAddrType   InetAddressType,
    tmnxBsxDnsIpCacheProxyAddr       InetAddress,
    tmnxBsxDnsIpCacheProxyRowStatus  RowStatus,
    tmnxBsxDnsIpCacheProxyRowLastCh  TimeStamp
}

tmnxBsxDnsIpCacheProxyAddrType   OBJECT-TYPE
    SYNTAX      InetAddressType
    MAX-ACCESS  not-accessible
    STATUS      current
    DESCRIPTION
        "The value of tmnxBsxDnsIpCacheProxyAddrType specifies the type of
         address contained in tmnxBsxDnsIpCacheProxyAddr."
    ::= { tmnxBsxDnsIpCacheProxyEntry 1 }

tmnxBsxDnsIpCacheProxyAddr       OBJECT-TYPE
    SYNTAX      InetAddress (SIZE (4|16))
    MAX-ACCESS  not-accessible
    STATUS      current
    DESCRIPTION
        "The value of tmnxBsxDnsIpCacheProxyAddr specifies the static IP
         address."
    ::= { tmnxBsxDnsIpCacheProxyEntry 2 }

tmnxBsxDnsIpCacheProxyRowStatus  OBJECT-TYPE
    SYNTAX      RowStatus
    MAX-ACCESS  read-create
    STATUS      current
    DESCRIPTION
        "The value of tmnxBsxDnsIpCacheProxyRowStatus specifies the row status.
         It allows entries to be created and deleted in the
         tmnxBsxDnsIpCacheProxyTable.

         Rows are created by specifying the value of 'createAndGo (4)', and
         deleted by specifying the value of 'destroy (6)'."
    ::= { tmnxBsxDnsIpCacheProxyEntry 3 }

tmnxBsxDnsIpCacheProxyRowLastCh  OBJECT-TYPE
    SYNTAX      TimeStamp
    MAX-ACCESS  read-only
    STATUS      current
    DESCRIPTION
        "The value of tmnxBsxDnsIpCacheProxyRowLastCh indicates the last time,
         since system startup, a successful set caused a value in this row to
         change."
    ::= { tmnxBsxDnsIpCacheProxyEntry 4 }

tmnxBsxUrlListObjs               OBJECT IDENTIFIER ::= { tmnxBsxObjs 17 }

tmnxBsxUrlListScalars            OBJECT IDENTIFIER ::= { tmnxBsxUrlListObjs 1 }

tmnxBsxUrlListLastChangedTime    OBJECT-TYPE
    SYNTAX      TimeStamp
    MAX-ACCESS  read-only
    STATUS      current
    DESCRIPTION
        "The value of tmnxBsxUrlListLastChangedTime indicates the last time,
         since system startup, a successful set was performed on
         tmnxBsxUrlListTable."
    ::= { tmnxBsxUrlListScalars 1 }

tmnxBsxUrlListTable              OBJECT-TYPE
    SYNTAX      SEQUENCE OF TmnxBsxUrlListEntry
    MAX-ACCESS  not-accessible
    STATUS      current
    DESCRIPTION
        "The tmnxBsxUrlListTable contains URL list configuration information."
    ::= { tmnxBsxUrlListObjs 2 }

tmnxBsxUrlListEntry              OBJECT-TYPE
    SYNTAX      TmnxBsxUrlListEntry
    MAX-ACCESS  not-accessible
    STATUS      current
    DESCRIPTION
        "Each entry specifies the configuration for a URL list. An entry can be
         referenced in a tmnxBsxUrlFilterEntry and can then be used to filter
         traffic.

         Entries in this table are created and deleted via SNMP set operations
         to tmnxBsxUrlListRowStatus."
    INDEX       {
        tmnxBsxIsaAaGroupIndex,
        IMPLIED tmnxBsxUrlListName
    }
    ::= { tmnxBsxUrlListTable 1 }

TmnxBsxUrlListEntry              ::= SEQUENCE
{
    tmnxBsxUrlListName               TNamedItem,
    tmnxBsxUrlListRowLastChanged     TimeStamp,
    tmnxBsxUrlListRowStatus          RowStatus,
    tmnxBsxUrlListAdminState         TmnxAdminState,
    tmnxBsxUrlListDecryptKey         DisplayString,
    tmnxBsxUrlListFileUrl            TmnxDisplayStringURL,
    tmnxBsxUrlListUpgrade            TmnxActionType,
    tmnxBsxUrlListDescription        TItemDescription,
    tmnxBsxUrlListSize               INTEGER,
    tmnxBsxUrlListHostExpressions    TruthValue
}

tmnxBsxUrlListName               OBJECT-TYPE
    SYNTAX      TNamedItem
    MAX-ACCESS  not-accessible
    STATUS      current
    DESCRIPTION
        "The value of tmnxBsxUrlListName specifies the name of the URL list."
    ::= { tmnxBsxUrlListEntry 1 }

tmnxBsxUrlListRowLastChanged     OBJECT-TYPE
    SYNTAX      TimeStamp
    MAX-ACCESS  read-only
    STATUS      current
    DESCRIPTION
        "The value of tmnxBsxUrlListRowLastChanged indicates the last time,
         since system startup, a successful set was performed on this row."
    ::= { tmnxBsxUrlListEntry 2 }

tmnxBsxUrlListRowStatus          OBJECT-TYPE
    SYNTAX      RowStatus
    MAX-ACCESS  read-create
    STATUS      current
    DESCRIPTION
        "The value of tmnxBsxUrlListRowStatus specifies the row status. It
         allows entries to be created and deleted in the tmnxBsxUrlListTable."
    ::= { tmnxBsxUrlListEntry 3 }

tmnxBsxUrlListAdminState         OBJECT-TYPE
    SYNTAX      TmnxAdminState
    MAX-ACCESS  read-create
    STATUS      current
    DESCRIPTION
        "The value of tmnxBsxUrlListAdminState specifies the administrative
         state for the URL list. When 'outOfService(3)', the list is not in
         use."
    DEFVAL      { outOfService }
    ::= { tmnxBsxUrlListEntry 4 }

tmnxBsxUrlListDecryptKey         OBJECT-TYPE
    SYNTAX      DisplayString (SIZE (0|1..64))
    MAX-ACCESS  read-create
    STATUS      current
    DESCRIPTION
        "The value of tmnxBsxUrlListDecryptKey specifies the key used to
         decrypt the URL list stored in tmnxBsxUrlListFileUrl.

         A value of 0 indicates tmnxBsxUrlListFileUrl is not encrypted."
    DEFVAL      { "" }
    ::= { tmnxBsxUrlListEntry 5 }

tmnxBsxUrlListFileUrl            OBJECT-TYPE
    SYNTAX      TmnxDisplayStringURL
    MAX-ACCESS  read-create
    STATUS      current
    DESCRIPTION
        "The value of tmnxBsxUrlListFileUrl specifies the filename on compact
         flash for the URL list."
    DEFVAL      { ''H }
    ::= { tmnxBsxUrlListEntry 6 }

tmnxBsxUrlListUpgrade            OBJECT-TYPE
    SYNTAX      TmnxActionType
    MAX-ACCESS  read-create
    STATUS      current
    DESCRIPTION
        "The value of tmnxBsxUrlListUpgrade specifies, when set to 'doAction
         (1)', that re-processing the tmnxBsxUrlListFileUrl will be performed.
         SNMP get operations on this object return 'notApplicable (2)'. Note
         the URL list must have a tmnxBsxUrlListAdminState of inService(2) in
         order for the upgrade to occur."
    DEFVAL      { notApplicable }
    ::= { tmnxBsxUrlListEntry 7 }

tmnxBsxUrlListDescription        OBJECT-TYPE
    SYNTAX      TItemDescription
    MAX-ACCESS  read-create
    STATUS      current
    DESCRIPTION
        "The value of tmnxBsxUrlListDescription specifies the description of
         the URL list."
    DEFVAL      { "" }
    ::= { tmnxBsxUrlListEntry 8 }

tmnxBsxUrlListSize               OBJECT-TYPE
    SYNTAX      INTEGER {
        standard (1),
        extended (2)
    }
    MAX-ACCESS  read-create
    STATUS      current
    DESCRIPTION
        "The value of tmnxBsxUrlListSize specifies the maximum number of URLs
         that are supported in the URL list.

         When set to 'standard (1)' the maximum number of URLs is 15000.

         When set to 'extended (2)' the maximum number of URLs is 2000000,
         based on an average URL size of 25 characters. If the average URL size
         is more, the maximum number of URLs will decrease accordingly."
    DEFVAL      { standard }
    ::= { tmnxBsxUrlListEntry 9 }

tmnxBsxUrlListHostExpressions    OBJECT-TYPE
    SYNTAX      TruthValue
    MAX-ACCESS  read-create
    STATUS      current
    DESCRIPTION
        "The value of tmnxBsxUrlListHostExpressions specifies URL entries in
         the file specified by tmnxBsxUrlListFileUrl may be host expressions
         that will be parsed based on rules defined in TmnxBsxExprSubString. If
         tmnxBsxUrlListHostExpressions is true, and an entry in the url-list
         starts with * or ^ then it will be parsed according to the rules
         defined by TmnxBsxExprSubString, and in addition, '/' will not be
         allowed. If tmnxBsxUrlListHostExpressions is set to false, then the
         entry will be parsed as flat alpha-numeric string."
    DEFVAL      { false }
    ::= { tmnxBsxUrlListEntry 10 }

tmnxBsxGtpObjs                   OBJECT IDENTIFIER ::= { tmnxBsxObjs 18 }

tmnxBsxGtpScalars                OBJECT IDENTIFIER ::= { tmnxBsxGtpObjs 1 }

tmnxBsxGtpLastChangedTime        OBJECT-TYPE
    SYNTAX      TimeStamp
    MAX-ACCESS  read-only
    STATUS      current
    DESCRIPTION
        "The value of tmnxBsxGtpLastChangedTime indicates the last time, since
         system startup, a successful SNMP set on tmnxBsxGtpTable caused a
         value to change."
    ::= { tmnxBsxGtpScalars 1 }

tmnxBsxGtpFltrLastChangedTime    OBJECT-TYPE
    SYNTAX      TimeStamp
    MAX-ACCESS  read-only
    STATUS      current
    DESCRIPTION
        "The value of tmnxBsxGtpFltrLastChangedTime indicates the last time,
         since system startup, a successful SNMP set on tmnxBsxGtpFltrTable
         caused a value to change."
    ::= { tmnxBsxGtpScalars 2 }

tmnxBsxGtpFltrMsgLastChangedTime OBJECT-TYPE
    SYNTAX      TimeStamp
    MAX-ACCESS  read-only
    STATUS      current
    DESCRIPTION
        "The value of tmnxBsxGtpFltrMsgLastChangedTime indicates the last time,
         since system startup, a successful SNMP set on tmnxBsxGtpFltrMsgTable
         caused a value to change."
    ::= { tmnxBsxGtpScalars 3 }

tmnxBsxSctpFltrLastChangedTime   OBJECT-TYPE
    SYNTAX      TimeStamp
    MAX-ACCESS  read-only
    STATUS      current
    DESCRIPTION
        "The value of tmnxBsxSctpFltrLastChangedTime indicates the last time,
         since system startup, a successful SNMP set on tmnxBsxSctpFltrTable
         caused a value to change."
    ::= { tmnxBsxGtpScalars 4 }

tmnxBsxSctpFltrPpidLastChngdTime OBJECT-TYPE
    SYNTAX      TimeStamp
    MAX-ACCESS  read-only
    STATUS      current
    DESCRIPTION
        "The value of tmnxBsxSctpFltrPpidLastChngdTime indicates the last time,
         since system startup, a successful SNMP set on
         tmnxBsxSctpFltrPpidTable caused a value to change."
    ::= { tmnxBsxGtpScalars 5 }

tmnxBsxGtpFltrImsiApnLastChgTime OBJECT-TYPE
    SYNTAX      TimeStamp
    MAX-ACCESS  read-only
    STATUS      current
    DESCRIPTION
        "The value of tmnxBsxGtpFltrImsiApnLastChgTime indicates the last time,
         since system startup, a successful SNMP set on
         tmnxBsxGtpFltrImsiApnTable caused a value to change."
    ::= { tmnxBsxGtpScalars 6 }

tmnxBsxGtpFltrV2MsgLastChgTime   OBJECT-TYPE
    SYNTAX      TimeStamp
    MAX-ACCESS  read-only
    STATUS      current
    DESCRIPTION
        "The value of tmnxBsxGtpFltrV2MsgLastChgTime indicates the last time,
         since system startup, a successful SNMP set on
         tmnxBsxGtpFltrV2MsgTable caused a value to change."
    ::= { tmnxBsxGtpScalars 7 }

tmnxBsxGtpTable                  OBJECT-TYPE
    SYNTAX      SEQUENCE OF TmnxBsxGtpEntry
    MAX-ACCESS  not-accessible
    STATUS      current
    DESCRIPTION
        "The tmnxBsxGtpTable contains GTP (General packet radio service
         Tunneling Protocol) configuration information."
    ::= { tmnxBsxGtpObjs 2 }

tmnxBsxGtpEntry                  OBJECT-TYPE
    SYNTAX      TmnxBsxGtpEntry
    MAX-ACCESS  not-accessible
    STATUS      current
    DESCRIPTION
        "Each entry specifies the GTP configuration for a specific ISA-AA group
         and partition."
    AUGMENTS    { tmnxBsxAaGrpPartEntry }
    ::= { tmnxBsxGtpTable 1 }

TmnxBsxGtpEntry                  ::= SEQUENCE
{
    tmnxBsxGtpRowLastChange          TimeStamp,
    tmnxBsxGtpAdminState             TmnxAdminState,
    tmnxBsxGtpEvtLog                 TNamedItemOrEmpty,
    tmnxBsxGtpMode                   INTEGER,
    tmnxBsxGtpcInspection            TruthValue,
    tmnxBsxGtpEventLogAction         TmnxBsxEventLogAction
}

tmnxBsxGtpRowLastChange          OBJECT-TYPE
    SYNTAX      TimeStamp
    MAX-ACCESS  read-only
    STATUS      current
    DESCRIPTION
        "The value of tmnxBsxGtpRowLastChange indicates the last time, since
         system startup, a successful SNMP set caused a value in this row to
         change."
    ::= { tmnxBsxGtpEntry 1 }

tmnxBsxGtpAdminState             OBJECT-TYPE
    SYNTAX      TmnxAdminState
    MAX-ACCESS  read-create
    STATUS      current
    DESCRIPTION
        "The value of tmnxBsxGtpAdminState specifies the administrative state
         of GTP support. When 'outOfService (3)', GTP support for this
         group-partition is disabled."
    DEFVAL      { outOfService }
    ::= { tmnxBsxGtpEntry 2 }

tmnxBsxGtpEvtLog                 OBJECT-TYPE
    SYNTAX      TNamedItemOrEmpty
    MAX-ACCESS  read-create
    STATUS      current
    DESCRIPTION
        "The value of tmnxBsxGtpEvtLog specifies the tmnxBsxEventLogEntry where
         non-conforming packets are logged. If set to an empty string, no event
         logging is performed."
    DEFVAL      { "" }
    ::= { tmnxBsxGtpEntry 3 }

tmnxBsxGtpMode                   OBJECT-TYPE
    SYNTAX      INTEGER {
        filtering   (1),
        untunneling (2)
    }
    MAX-ACCESS  read-create
    STATUS      current
    DESCRIPTION
        "The value of tmnxBsxGtpMode specifies the mode of GTP support. Note
         that tmnxBsxGtpAdminState must be set to 'outOfService(3)' in order to
         change the mode.
         Valid values are:
               filtering (1)   - GTP TEID (tunnel endpoint identifier) based
                                 tracking and GTP level filtering, as defined in
                                 tmnxBsxGtpFltrTable
               untunneling (2) - GTP tunnel IP payload flow based tracking and
                                 application analysis "
    DEFVAL      { filtering }
    ::= { tmnxBsxGtpEntry 4 }

tmnxBsxGtpcInspection            OBJECT-TYPE
    SYNTAX      TruthValue
    MAX-ACCESS  read-create
    STATUS      current
    DESCRIPTION
        "The value of tmnxBsxGtpcInspection specifies if GTP-c inspection is
         done. This object can be set to true only if
         tmnxBsxIsaAaGrpGtpTunnelDb is set to 100 and for VSR, VSR roaming
         license is available, in addition to the stateful firewall license."
    DEFVAL      { false }
    ::= { tmnxBsxGtpEntry 5 }

tmnxBsxGtpEventLogAction         OBJECT-TYPE
    SYNTAX      TmnxBsxEventLogAction
    MAX-ACCESS  read-create
    STATUS      current
    DESCRIPTION
        "The value of tmnxBsxGtpEventLogAction specifies the action based
         trigger of raising an event log."
    DEFVAL      { deny }
    ::= { tmnxBsxGtpEntry 6 }

tmnxBsxGtpFltrTable              OBJECT-TYPE
    SYNTAX      SEQUENCE OF TmnxBsxGtpFltrEntry
    MAX-ACCESS  not-accessible
    STATUS      current
    DESCRIPTION
        "The tmnxBsxGtpFltrTable contains GTP (General packet radio service
         Tunneling Protocol) filter configuration information."
    ::= { tmnxBsxGtpObjs 3 }

tmnxBsxGtpFltrEntry              OBJECT-TYPE
    SYNTAX      TmnxBsxGtpFltrEntry
    MAX-ACCESS  not-accessible
    STATUS      current
    DESCRIPTION
        "Each entry specifies the configuration for a GTP filter.

         Entries in this table are created and deleted via SNMP set operations
         to tmnxBsxGtpFltrRowStatus."
    INDEX       {
        tmnxBsxAaGrpPartIndex,
        tmnxBsxGtpFltrName
    }
    ::= { tmnxBsxGtpFltrTable 1 }

TmnxBsxGtpFltrEntry              ::= SEQUENCE
{
    tmnxBsxGtpFltrName               TNamedItem,
    tmnxBsxGtpFltrRowLastChange      TimeStamp,
    tmnxBsxGtpFltrRowStatus          RowStatus,
    tmnxBsxGtpFltrDescription        TItemDescription,
    tmnxBsxGtpFltrMaxPayloadLength   Integer32,
    tmnxBsxGtpFltrDefaultAction      TmnxBsxFltrAction,
    tmnxBsxGtpFltrEvtLog             TNamedItemOrEmpty,
    tmnxBsxGtpFltrGtpInGtp           TmnxBsxFltrAction,
    tmnxBsxGtpFltrValidateSeqNumber  TruthValue,
    tmnxBsxGtpFltrValidateSrcIpAddr  TruthValue,
    tmnxBsxGtpFltrImsiApnDefAction   TmnxBsxFltrAction,
    tmnxBsxGtpFltrValidateGtpTunnels TruthValue,
    tmnxBsxGtpFltrV2MsgDefAction     TmnxBsxFltrAction,
    tmnxBsxGtpFltrEventLogAction     TmnxBsxEventLogAction,
    tmnxBsxGtpFltrDefTunnelEpLimit   Unsigned32
}

tmnxBsxGtpFltrName               OBJECT-TYPE
    SYNTAX      TNamedItem
    MAX-ACCESS  not-accessible
    STATUS      current
    DESCRIPTION
        "The value of tmnxBsxGtpFltrName specifies the name of the GTP filter."
    ::= { tmnxBsxGtpFltrEntry 1 }

tmnxBsxGtpFltrRowLastChange      OBJECT-TYPE
    SYNTAX      TimeStamp
    MAX-ACCESS  read-only
    STATUS      current
    DESCRIPTION
        "The value of tmnxBsxGtpFltrRowLastChange indicates the last time,
         since system startup, a successful SNMP set caused a value in this row
         to change."
    ::= { tmnxBsxGtpFltrEntry 2 }

tmnxBsxGtpFltrRowStatus          OBJECT-TYPE
    SYNTAX      RowStatus
    MAX-ACCESS  read-create
    STATUS      current
    DESCRIPTION
        "The value of tmnxBsxGtpFltrRowStatus specifies the row status. It
         allows entries to be created and deleted in the tmnxBsxGtpFltrTable."
    ::= { tmnxBsxGtpFltrEntry 3 }

tmnxBsxGtpFltrDescription        OBJECT-TYPE
    SYNTAX      TItemDescription
    MAX-ACCESS  read-create
    STATUS      current
    DESCRIPTION
        "The value of tmnxBsxGtpFltrDescription specifies the description of
         the GTP filter."
    DEFVAL      { "" }
    ::= { tmnxBsxGtpFltrEntry 4 }

tmnxBsxGtpFltrMaxPayloadLength   OBJECT-TYPE
    SYNTAX      Integer32 (-1 | 0 | 1..65535)
    MAX-ACCESS  read-create
    STATUS      current
    DESCRIPTION
        "The value of tmnxBsxGtpFltrMaxPayloadLength specifies the maximum
         allowed GTP payload permitted by the filter. The payload represents
         the bytes after the header. A value of 0 indicates that all GTP
         packets are denied by the filter. A value of -1 indicates that the
         payload length is not checked."
    DEFVAL      { -1 }
    ::= { tmnxBsxGtpFltrEntry 5 }

tmnxBsxGtpFltrDefaultAction      OBJECT-TYPE
    SYNTAX      TmnxBsxFltrAction
    MAX-ACCESS  read-create
    STATUS      current
    DESCRIPTION
        "The value of tmnxBsxGtpFltrDefaultAction specifies the default action
         to take for packets that do not match any message entries."
    DEFVAL      { permit }
    ::= { tmnxBsxGtpFltrEntry 6 }

tmnxBsxGtpFltrEvtLog             OBJECT-TYPE
    SYNTAX      TNamedItemOrEmpty
    MAX-ACCESS  read-create
    STATUS      current
    DESCRIPTION
        "The value of tmnxBsxGtpFltrEvtLog specifies the named
         tmnxBsxEventLogEntry where packets dropped by the GTP filter are
         logged."
    DEFVAL      { "" }
    ::= { tmnxBsxGtpFltrEntry 7 }

tmnxBsxGtpFltrGtpInGtp           OBJECT-TYPE
    SYNTAX      TmnxBsxFltrAction
    MAX-ACCESS  read-create
    STATUS      current
    DESCRIPTION
        "The value of tmnxBsxGtpFltrGtpInGtp specifies the default action to
         take for GTP in GTP packets."
    DEFVAL      { permit }
    ::= { tmnxBsxGtpFltrEntry 8 }

tmnxBsxGtpFltrValidateSeqNumber  OBJECT-TYPE
    SYNTAX      TruthValue
    MAX-ACCESS  read-create
    STATUS      current
    DESCRIPTION
        "The value of tmnxBsxGtpFltrValidateSeqNumber specifies if GTP message
         sequence number validation is desired. This object can be set to true
         only if tmnxBsxGtpFltrValidateGtpTunnels is set to true."
    DEFVAL      { false }
    ::= { tmnxBsxGtpFltrEntry 9 }

tmnxBsxGtpFltrValidateSrcIpAddr  OBJECT-TYPE
    SYNTAX      TruthValue
    MAX-ACCESS  read-create
    STATUS      current
    DESCRIPTION
        "The value of tmnxBsxGtpFltrValidateSrcIpAddr specifies if GTP message
         source IP address validation is desired. This object can be set to
         true only if tmnxBsxGtpFltrValidateGtpTunnels is set to true."
    DEFVAL      { false }
    ::= { tmnxBsxGtpFltrEntry 10 }

tmnxBsxGtpFltrImsiApnDefAction   OBJECT-TYPE
    SYNTAX      TmnxBsxFltrAction
    MAX-ACCESS  read-create
    STATUS      current
    DESCRIPTION
        "The value of tmnxBsxGtpFltrImsiApnDefAction specifies the default
         action to take for packets that do not match any imsi-apn filter
         entries. The object's value can be changed only if
         tmnxBsxGtpcInspection is set to true."
    DEFVAL      { permit }
    ::= { tmnxBsxGtpFltrEntry 11 }

tmnxBsxGtpFltrValidateGtpTunnels OBJECT-TYPE
    SYNTAX      TruthValue
    MAX-ACCESS  read-create
    STATUS      current
    DESCRIPTION
        "The value of tmnxBsxGtpFltrValidateGtpTunnels specifies if GTP tunnel
         validation is enforced. This object can be set to true only if
         tmnxBsxGtpcInspection is set to true and tmnxBsxIsaAaGrpGtpTunnelDb is
         set to its maximum value."
    DEFVAL      { false }
    ::= { tmnxBsxGtpFltrEntry 12 }

tmnxBsxGtpFltrV2MsgDefAction     OBJECT-TYPE
    SYNTAX      TmnxBsxFltrAction
    MAX-ACCESS  read-create
    STATUS      current
    DESCRIPTION
        "The value of tmnxBsxGtpFltrV2MsgDefAction specifies the default action
         to take for packets that do not match any GTP V2 message entries."
    DEFVAL      { permit }
    ::= { tmnxBsxGtpFltrEntry 13 }

tmnxBsxGtpFltrEventLogAction     OBJECT-TYPE
    SYNTAX      TmnxBsxEventLogAction
    MAX-ACCESS  read-create
    STATUS      current
    DESCRIPTION
        "The value of tmnxBsxGtpFltrEventLogAction specifies the action based
         trigger of raising an event log."
    DEFVAL      { deny }
    ::= { tmnxBsxGtpFltrEntry 14 }

tmnxBsxGtpFltrDefTunnelEpLimit   OBJECT-TYPE
    SYNTAX      Unsigned32 (1..4294967295)
    MAX-ACCESS  read-create
    STATUS      current
    DESCRIPTION
        "The value of tmnxBsxGtpFltrDefTunnelEpLimit specifies the default
         limit used to limit gtp tunnel endpoint Id creations in response to to
         gtp create session requests."
    DEFVAL      { 4294967295 }
    ::= { tmnxBsxGtpFltrEntry 15 }

tmnxBsxGtpFltrMsgTable           OBJECT-TYPE
    SYNTAX      SEQUENCE OF TmnxBsxGtpFltrMsgEntry
    MAX-ACCESS  not-accessible
    STATUS      current
    DESCRIPTION
        "The tmnxBsxGtpFltrMsgTable contains GTP filter message action
         configuration information."
    ::= { tmnxBsxGtpObjs 4 }

tmnxBsxGtpFltrMsgEntry           OBJECT-TYPE
    SYNTAX      TmnxBsxGtpFltrMsgEntry
    MAX-ACCESS  not-accessible
    STATUS      current
    DESCRIPTION
        "Each entry specifies the configuration for a GTP filter message.

         Entries in this table are created and deleted via SNMP set operations
         to tmnxBsxGtpFltrMsgRowStatus."
    INDEX       {
        tmnxBsxAaGrpPartIndex,
        tmnxBsxGtpFltrName,
        tmnxBsxGtpFltrMsgEntryId
    }
    ::= { tmnxBsxGtpFltrMsgTable 1 }

TmnxBsxGtpFltrMsgEntry           ::= SEQUENCE
{
    tmnxBsxGtpFltrMsgEntryId         Unsigned32,
    tmnxBsxGtpFltrMsgValue           Unsigned32,
    tmnxBsxGtpFltrMsgRowLastChange   TimeStamp,
    tmnxBsxGtpFltrMsgRowStatus       RowStatus,
    tmnxBsxGtpFltrMsgAction          TmnxBsxFltrAction
}

tmnxBsxGtpFltrMsgEntryId         OBJECT-TYPE
    SYNTAX      Unsigned32 (1..255)
    MAX-ACCESS  not-accessible
    STATUS      current
    DESCRIPTION
        "The value of tmnxBsxGtpFltrMsgEntryId specifies the index into the GTP
         message value list that defines a custom message-type action."
    ::= { tmnxBsxGtpFltrMsgEntry 1 }

tmnxBsxGtpFltrMsgValue           OBJECT-TYPE
    SYNTAX      Unsigned32 (1..255)
    MAX-ACCESS  read-create
    STATUS      current
    DESCRIPTION
        "The value of tmnxBsxGtpFltrMsgValue specifies a GTP message value.

         Each possible value may only appear once in the
         tmnxBsxGtpFltrMsgTable, and can only be set on row create."
    REFERENCE
        "3GPP, TS 29.060 V7.9.0 'GPRS Tunnelling Protocol (GTP) across the Gn
         and Gp interface', Section 7.1, 'Message Formats' Rel 7, March, 2008."
    ::= { tmnxBsxGtpFltrMsgEntry 2 }

tmnxBsxGtpFltrMsgRowLastChange   OBJECT-TYPE
    SYNTAX      TimeStamp
    MAX-ACCESS  read-only
    STATUS      current
    DESCRIPTION
        "The value of tmnxBsxGtpFltrMsgRowLastChange indicates the last time,
         since system startup, a successful SNMP set caused a value in this row
         to change."
    ::= { tmnxBsxGtpFltrMsgEntry 3 }

tmnxBsxGtpFltrMsgRowStatus       OBJECT-TYPE
    SYNTAX      RowStatus
    MAX-ACCESS  read-create
    STATUS      current
    DESCRIPTION
        "The value of tmnxBsxGtpFltrMsgRowStatus specifies the row status. It
         allows entries to be created and deleted in the
         tmnxBsxGtpFltrMsgTable."
    ::= { tmnxBsxGtpFltrMsgEntry 4 }

tmnxBsxGtpFltrMsgAction          OBJECT-TYPE
    SYNTAX      TmnxBsxFltrAction
    MAX-ACCESS  read-create
    STATUS      current
    DESCRIPTION
        "The value of tmnxBsxGtpFltrMsgAction specifies the action to take for
         packets that match this GTP filter message entry."
    ::= { tmnxBsxGtpFltrMsgEntry 5 }

tmnxBsxSctpFltrTable             OBJECT-TYPE
    SYNTAX      SEQUENCE OF TmnxBsxSctpFltrEntry
    MAX-ACCESS  not-accessible
    STATUS      current
    DESCRIPTION
        "The tmnxBsxSctpFltrTable contains SCTP (Stream Control Transmission
         Protocol) filter configuration information."
    ::= { tmnxBsxGtpObjs 5 }

tmnxBsxSctpFltrEntry             OBJECT-TYPE
    SYNTAX      TmnxBsxSctpFltrEntry
    MAX-ACCESS  not-accessible
    STATUS      current
    DESCRIPTION
        "Each entry specifies the configuration for a SCTP filter.

         Entries in this table are created and deleted via SNMP set operations
         to tmnxBsxSctpFltrRowStatus."
    INDEX       {
        tmnxBsxAaGrpPartIndex,
        tmnxBsxSctpFltrName
    }
    ::= { tmnxBsxSctpFltrTable 1 }

TmnxBsxSctpFltrEntry             ::= SEQUENCE
{
    tmnxBsxSctpFltrName              TNamedItem,
    tmnxBsxSctpFltrRowLastChange     TimeStamp,
    tmnxBsxSctpFltrRowStatus         RowStatus,
    tmnxBsxSctpFltrDescription       TItemDescription,
    tmnxBsxSctpFltrPpidRangeMin      Unsigned32,
    tmnxBsxSctpFltrPpidRangeMax      Unsigned32,
    tmnxBsxSctpFltrDefaultAction     TmnxBsxFltrAction,
    tmnxBsxSctpFltrEvtLog            TNamedItemOrEmpty
}

tmnxBsxSctpFltrName              OBJECT-TYPE
    SYNTAX      TNamedItem
    MAX-ACCESS  not-accessible
    STATUS      current
    DESCRIPTION
        "The value of tmnxBsxSctpFltrName specifies the name of the SCTP
         filter."
    ::= { tmnxBsxSctpFltrEntry 1 }

tmnxBsxSctpFltrRowLastChange     OBJECT-TYPE
    SYNTAX      TimeStamp
    MAX-ACCESS  read-only
    STATUS      current
    DESCRIPTION
        "The value of tmnxBsxSctpFltrRowLastChange indicates the last time,
         since system startup, a successful SNMP set caused a value in this row
         to change."
    ::= { tmnxBsxSctpFltrEntry 2 }

tmnxBsxSctpFltrRowStatus         OBJECT-TYPE
    SYNTAX      RowStatus
    MAX-ACCESS  read-create
    STATUS      current
    DESCRIPTION
        "The value of tmnxBsxSctpFltrRowStatus specifies the row status. It
         allows entries to be created and deleted in the tmnxBsxSctpFltrTable."
    ::= { tmnxBsxSctpFltrEntry 3 }

tmnxBsxSctpFltrDescription       OBJECT-TYPE
    SYNTAX      TItemDescription
    MAX-ACCESS  read-create
    STATUS      current
    DESCRIPTION
        "The value of tmnxBsxSctpFltrDescription specifies the description of
         the SCTP filter."
    DEFVAL      { "" }
    ::= { tmnxBsxSctpFltrEntry 4 }

tmnxBsxSctpFltrPpidRangeMin      OBJECT-TYPE
    SYNTAX      Unsigned32
    MAX-ACCESS  read-create
    STATUS      current
    DESCRIPTION
        "The value of tmnxBsxSctpFltrPpidRangeMin specifies the minimum SCTP
         Payload Protocol Identifier (PPID) to be permitted by the SCTP filter.
         The value of tmnxBsxSctpFltrPpidRangeMin must be less than or equal to
         tmnxBsxSctpFltrPpidRangeMax."
    DEFVAL      { 0 }
    ::= { tmnxBsxSctpFltrEntry 5 }

tmnxBsxSctpFltrPpidRangeMax      OBJECT-TYPE
    SYNTAX      Unsigned32
    MAX-ACCESS  read-create
    STATUS      current
    DESCRIPTION
        "The value of tmnxBsxSctpFltrPpidRangeMax specifies the maximum SCTP
         PPID to be permitted by the SCTP filter. The value of
         tmnxBsxSctpFltrPpidRangeMax must be greater than or equal to
         tmnxBsxSctpFltrPpidRangeMin."
    DEFVAL      { 4294967295 }
    ::= { tmnxBsxSctpFltrEntry 6 }

tmnxBsxSctpFltrDefaultAction     OBJECT-TYPE
    SYNTAX      TmnxBsxFltrAction
    MAX-ACCESS  read-create
    STATUS      current
    DESCRIPTION
        "The value of tmnxBsxSctpFltrDefaultAction specifies the default action
         to take for packets that do not match any PPID entries."
    DEFVAL      { permit }
    ::= { tmnxBsxSctpFltrEntry 7 }

tmnxBsxSctpFltrEvtLog            OBJECT-TYPE
    SYNTAX      TNamedItemOrEmpty
    MAX-ACCESS  read-create
    STATUS      current
    DESCRIPTION
        "The value of tmnxBsxSctpFltrEvtLog specifies the named
         tmnxBsxEventLogEntry where packets dropped by the SCTP filter are
         logged."
    DEFVAL      { "" }
    ::= { tmnxBsxSctpFltrEntry 8 }

tmnxBsxSctpFltrPpidTable         OBJECT-TYPE
    SYNTAX      SEQUENCE OF TmnxBsxSctpFltrPpidEntry
    MAX-ACCESS  not-accessible
    STATUS      current
    DESCRIPTION
        "The tmnxBsxSctpFltrPpidTable contains SCTP filter PPID action
         configuration information."
    ::= { tmnxBsxGtpObjs 6 }

tmnxBsxSctpFltrPpidEntry         OBJECT-TYPE
    SYNTAX      TmnxBsxSctpFltrPpidEntry
    MAX-ACCESS  not-accessible
    STATUS      current
    DESCRIPTION
        "Each entry specifies the configuration for an SCTP filter PPID.

         Entries in this table are created and deleted via SNMP set operations
         to tmnxBsxSctpFltrPpidRowStatus."
    INDEX       {
        tmnxBsxAaGrpPartIndex,
        tmnxBsxSctpFltrName,
        tmnxBsxSctpFltrPpidEntryId
    }
    ::= { tmnxBsxSctpFltrPpidTable 1 }

TmnxBsxSctpFltrPpidEntry         ::= SEQUENCE
{
    tmnxBsxSctpFltrPpidEntryId       Unsigned32,
    tmnxBsxSctpFltrPpidVal           Unsigned32,
    tmnxBsxSctpFltrPpidRowLastChange TimeStamp,
    tmnxBsxSctpFltrPpidRowStatus     RowStatus,
    tmnxBsxSctpFltrPpidValAction     TmnxBsxFltrAction
}

tmnxBsxSctpFltrPpidEntryId       OBJECT-TYPE
    SYNTAX      Unsigned32 (1..255)
    MAX-ACCESS  not-accessible
    STATUS      current
    DESCRIPTION
        "The value of tmnxBsxSctpFltrPpidEntryId specifies the index into the
         PPID list that defines a custom PPID action."
    ::= { tmnxBsxSctpFltrPpidEntry 1 }

tmnxBsxSctpFltrPpidVal           OBJECT-TYPE
    SYNTAX      Unsigned32
    MAX-ACCESS  read-create
    STATUS      current
    DESCRIPTION
        "The value of tmnxBsxSctpFltrPpidVal specifies an SCTP PPID.

         Each possible value may only appear once in the
         tmnxBsxSctpFltrPpidTable, and can only be set on row create."
    REFERENCE
        "IANA, 'SCTP Payload Protocol Identifiers', 22 August, 2014."
    ::= { tmnxBsxSctpFltrPpidEntry 2 }

tmnxBsxSctpFltrPpidRowLastChange OBJECT-TYPE
    SYNTAX      TimeStamp
    MAX-ACCESS  read-only
    STATUS      current
    DESCRIPTION
        "The value of tmnxBsxSctpFltrPpidRowLastChange indicates the last time,
         since system startup, a successful SNMP set caused a value in this row
         to change."
    ::= { tmnxBsxSctpFltrPpidEntry 3 }

tmnxBsxSctpFltrPpidRowStatus     OBJECT-TYPE
    SYNTAX      RowStatus
    MAX-ACCESS  read-create
    STATUS      current
    DESCRIPTION
        "The value of tmnxBsxSctpFltrPpidRowStatus specifies the row status. It
         allows entries to be created and deleted in the
         tmnxBsxSctpFltrPpidTable."
    ::= { tmnxBsxSctpFltrPpidEntry 4 }

tmnxBsxSctpFltrPpidValAction     OBJECT-TYPE
    SYNTAX      TmnxBsxFltrAction
    MAX-ACCESS  read-create
    STATUS      current
    DESCRIPTION
        "The value of tmnxBsxSctpFltrPpidValAction specifies the action to take
         for packets that match this SCTP filter PPID entry."
    ::= { tmnxBsxSctpFltrPpidEntry 5 }

tmnxBsxGtpFltrImsiApnTable       OBJECT-TYPE
    SYNTAX      SEQUENCE OF TmnxBsxGtpFltrImsiApnEntry
    MAX-ACCESS  not-accessible
    STATUS      current
    DESCRIPTION
        "The tmnxBsxGtpFltrImsiApnTable contains GTP filter IMSI-APN filter
         entry action configuration information."
    ::= { tmnxBsxGtpObjs 7 }

tmnxBsxGtpFltrImsiApnEntry       OBJECT-TYPE
    SYNTAX      TmnxBsxGtpFltrImsiApnEntry
    MAX-ACCESS  not-accessible
    STATUS      current
    DESCRIPTION
        "Each entry specifies the configuration for a GTP filter IMSI APN
         filter entry.

         Entries in this table are created and deleted via SNMP set operations
         to tmnxBsxGtpFltrImsiApnRowStatus. Entries can be added if the GTP
         filter tmnxBsxGtpcInspection is set to true."
    INDEX       {
        tmnxBsxAaGrpPartIndex,
        tmnxBsxGtpFltrName,
        tmnxBsxGtpFltrImsiApnEntryId
    }
    ::= { tmnxBsxGtpFltrImsiApnTable 1 }

TmnxBsxGtpFltrImsiApnEntry       ::= SEQUENCE
{
    tmnxBsxGtpFltrImsiApnEntryId     Unsigned32,
    tmnxBsxGtpFltrImsiApnRowStatus   RowStatus,
    tmnxBsxGtpFltrMatchImsiPrefix    DisplayString,
    tmnxBsxGtpFltrMatchApn           DisplayString,
    tmnxBsxGtpFltrMatchSrcGsnAddr    InetAddress,
    tmnxBsxGtpFltrMatchSrcGsnAddrTyp InetAddressType,
    tmnxBsxGtpFltrMatchSrcGsnAddrLen InetAddressPrefixLength,
    tmnxBsxGtpFltrMatchSrcIpPfxList  TNamedItemOrEmpty,
    tmnxBsxGtpFltrImsiApnEntryAction TmnxBsxFltrAction,
    tmnxBsxGtpFilterImsiApnLastChg   TimeStamp
}

tmnxBsxGtpFltrImsiApnEntryId     OBJECT-TYPE
    SYNTAX      Unsigned32 (1031..2030)
    MAX-ACCESS  not-accessible
    STATUS      current
    DESCRIPTION
        "The value of tmnxBsxGtpFltrImsiApnEntryId specifies the index into the
         GTP IMSI-APN filter that defines an action based on match attributes
         such as imsi-prefix, APN, and source GSN IP address."
    ::= { tmnxBsxGtpFltrImsiApnEntry 1 }

tmnxBsxGtpFltrImsiApnRowStatus   OBJECT-TYPE
    SYNTAX      RowStatus
    MAX-ACCESS  read-create
    STATUS      current
    DESCRIPTION
        "The value of tmnxBsxGtpFltrImsiApnRowStatus specifies the row status.
         It allows entries to be created and deleted in the
         tmnxBsxGtpFltrImsiApnTable."
    ::= { tmnxBsxGtpFltrImsiApnEntry 2 }

tmnxBsxGtpFltrMatchImsiPrefix    OBJECT-TYPE
    SYNTAX      DisplayString (SIZE (0|1..8))
    MAX-ACCESS  read-create
    STATUS      current
    DESCRIPTION
        "The value of tmnxBsxGtpFltrMatchImsiPrefix specifies an IMSI prefix
         that consists of MCC and MNC, or keyword ANY_IMSI as a match criteria
         to resolve to an action."
    DEFVAL      { "" }
    ::= { tmnxBsxGtpFltrImsiApnEntry 3 }

tmnxBsxGtpFltrMatchApn           OBJECT-TYPE
    SYNTAX      DisplayString (SIZE (0..100))
    MAX-ACCESS  read-create
    STATUS      current
    DESCRIPTION
        "The value of tmnxBsxGtpFltrMatchApn specifies an APN (Access Point
         Name) expression, or keywords WILDCARD_APN, EMPTY_APN, or ANY_APN, as
         GTP filter match criteria to resolve to an action."
    DEFVAL      { ''H }
    ::= { tmnxBsxGtpFltrImsiApnEntry 4 }

tmnxBsxGtpFltrMatchSrcGsnAddr    OBJECT-TYPE
    SYNTAX      InetAddress (SIZE (0|4|16))
    MAX-ACCESS  read-create
    STATUS      current
    DESCRIPTION
        "The value of tmnxBsxGtpFltrMatchSrcGsnAddr specifies the source GSN
         address to match to resolve to an action."
    DEFVAL      { ''H }
    ::= { tmnxBsxGtpFltrImsiApnEntry 5 }

tmnxBsxGtpFltrMatchSrcGsnAddrTyp OBJECT-TYPE
    SYNTAX      InetAddressType
    MAX-ACCESS  read-create
    STATUS      current
    DESCRIPTION
        "The value of tmnxBsxGtpFltrMatchSrcGsnAddrTyp specifies the type of
         address contained in tmnxBsxGtpFltrMatchSrcGsnAddr.

         A value of 'unknown (0)' specifies that no matching is to be done to
         resolve to an action."
    DEFVAL      { unknown }
    ::= { tmnxBsxGtpFltrImsiApnEntry 6 }

tmnxBsxGtpFltrMatchSrcGsnAddrLen OBJECT-TYPE
    SYNTAX      InetAddressPrefixLength (0..128)
    MAX-ACCESS  read-create
    STATUS      current
    DESCRIPTION
        "The value of tmnxBsxGtpFltrMatchSrcGsnAddrLen specifies the number of
         relevant bits of the tmnxBsxGtpFltrMatchSrcGsnAddr."
    DEFVAL      { 0 }
    ::= { tmnxBsxGtpFltrImsiApnEntry 7 }

tmnxBsxGtpFltrMatchSrcIpPfxList  OBJECT-TYPE
    SYNTAX      TNamedItemOrEmpty
    MAX-ACCESS  read-create
    STATUS      current
    DESCRIPTION
        "The value of tmnxBsxGtpFltrMatchSrcIpPfxList specifies the prefix list
         to use when matching the source GSN address to resolve to an action.

         The specification of the server IP prefix list may be done only when
         tmnxBsxGtpFltrMatchSrcGsnAddr, tmnxBsxGtpFltrMatchSrcGsnAddrTyp, and
         tmnxBsxGtpFltrMatchSrcGsnAddrLen are set to their default value."
    DEFVAL      { "" }
    ::= { tmnxBsxGtpFltrImsiApnEntry 8 }

tmnxBsxGtpFltrImsiApnEntryAction OBJECT-TYPE
    SYNTAX      TmnxBsxFltrAction
    MAX-ACCESS  read-create
    STATUS      current
    DESCRIPTION
        "The value of tmnxBsxGtpFltrImsiApnEntryAction specifies the action to
         take for packets that match this GTP filter IMSI-APN entry. When
         creating a row in this table through tmnxBsxGtpFltrImsiApnRowStatus,
         tmnxBsxGtpFltrImsiApnEntryAction must be set as well as a
         multi-varbind."
    DEFVAL      { permit }
    ::= { tmnxBsxGtpFltrImsiApnEntry 9 }

tmnxBsxGtpFilterImsiApnLastChg   OBJECT-TYPE
    SYNTAX      TimeStamp
    MAX-ACCESS  read-only
    STATUS      current
    DESCRIPTION
        "The value of tmnxBsxGtpFilterImsiApnLastChg indicates the last time,
         since system startup, a successful SNMP set caused a value in this row
         to change."
    ::= { tmnxBsxGtpFltrImsiApnEntry 10 }

tmnxBsxGtpFltrV2MsgTable         OBJECT-TYPE
    SYNTAX      SEQUENCE OF TmnxBsxGtpFltrV2MsgEntry
    MAX-ACCESS  not-accessible
    STATUS      current
    DESCRIPTION
        "The tmnxBsxGtpFltrV2MsgTable contains GTP filter version 2 message
         action configuration information."
    ::= { tmnxBsxGtpObjs 8 }

tmnxBsxGtpFltrV2MsgEntry         OBJECT-TYPE
    SYNTAX      TmnxBsxGtpFltrV2MsgEntry
    MAX-ACCESS  not-accessible
    STATUS      current
    DESCRIPTION
        "Each entry specifies the configuration for a GTP filter version 2
         message.

         Entries in this table are created and deleted via SNMP set operations
         to tmnxBsxGtpFltrV2MsgRowStatus."
    INDEX       {
        tmnxBsxAaGrpPartIndex,
        tmnxBsxGtpFltrName,
        tmnxBsxGtpFltrV2MsgEntryId
    }
    ::= { tmnxBsxGtpFltrV2MsgTable 1 }

TmnxBsxGtpFltrV2MsgEntry         ::= SEQUENCE
{
    tmnxBsxGtpFltrV2MsgEntryId       Unsigned32,
    tmnxBsxGtpFltrV2MsgValue         Unsigned32,
    tmnxBsxGtpFltrV2MsgRowLastChg    TimeStamp,
    tmnxBsxGtpFltrV2MsgRowStatus     RowStatus,
    tmnxBsxGtpFltrV2MsgAction        TmnxBsxFltrAction
}

tmnxBsxGtpFltrV2MsgEntryId       OBJECT-TYPE
    SYNTAX      Unsigned32 (516..770)
    MAX-ACCESS  not-accessible
    STATUS      current
    DESCRIPTION
        "The value of tmnxBsxGtpFltrV2MsgEntryId specifies the index into the
         GTP message value list that defines a custom message-type action."
    ::= { tmnxBsxGtpFltrV2MsgEntry 1 }

tmnxBsxGtpFltrV2MsgValue         OBJECT-TYPE
    SYNTAX      Unsigned32 (1..255)
    MAX-ACCESS  read-create
    STATUS      current
    DESCRIPTION
        "The value of tmnxBsxGtpFltrV2MsgValue specifies a GTP V2 message
         value.

         Each possible value may only appear once in the
         tmnxBsxGtpFltrV2MsgTable, and can only be set on row create."
    REFERENCE
        "3GPP, TS 29.274 TS 29.060 V7.9.0 'GPRS Tunnelling Protocol (GTP) across the Gn
         and Gp interface', Section 7.1, 'Message Formats' Rel 7, March, 2008."
    ::= { tmnxBsxGtpFltrV2MsgEntry 2 }

tmnxBsxGtpFltrV2MsgRowLastChg    OBJECT-TYPE
    SYNTAX      TimeStamp
    MAX-ACCESS  read-only
    STATUS      current
    DESCRIPTION
        "The value of tmnxBsxGtpFltrV2MsgRowLastChg indicates the last time,
         since system startup, a successful SNMP set caused a value in this row
         to change."
    ::= { tmnxBsxGtpFltrV2MsgEntry 3 }

tmnxBsxGtpFltrV2MsgRowStatus     OBJECT-TYPE
    SYNTAX      RowStatus
    MAX-ACCESS  read-create
    STATUS      current
    DESCRIPTION
        "The value of tmnxBsxGtpFltrV2MsgRowStatus specifies the row status. It
         allows entries to be created and deleted in the
         tmnxBsxGtpFltrV2MsgTable."
    ::= { tmnxBsxGtpFltrV2MsgEntry 4 }

tmnxBsxGtpFltrV2MsgAction        OBJECT-TYPE
    SYNTAX      TmnxBsxFltrAction
    MAX-ACCESS  read-create
    STATUS      current
    DESCRIPTION
        "The value of tmnxBsxGtpFltrV2MsgAction specifies the action to take
         for packets that match this GTP filter V2 message entry."
    ::= { tmnxBsxGtpFltrV2MsgEntry 5 }

tmnxBsxTcpOptObjs                OBJECT IDENTIFIER ::= { tmnxBsxObjs 19 }

tmnxBsxTcpOptScalars             OBJECT IDENTIFIER ::= { tmnxBsxTcpOptObjs 1 }

tmnxBsxTcpOptLastChangedTime     OBJECT-TYPE
    SYNTAX      TimeStamp
    MAX-ACCESS  read-only
    STATUS      current
    DESCRIPTION
        "The value of tmnxBsxTcpOptLastChangedTime indicates the last time,
         since system startup, a successful SNMP set on tmnxBsxTcpOptTable
         caused a value to change."
    ::= { tmnxBsxTcpOptScalars 1 }

tmnxBsxTcpOptTable               OBJECT-TYPE
    SYNTAX      SEQUENCE OF TmnxBsxTcpOptEntry
    MAX-ACCESS  not-accessible
    STATUS      current
    DESCRIPTION
        "The tmnxBsxTcpOptTable contains TCP optimization configuration
         information."
    ::= { tmnxBsxTcpOptObjs 2 }

tmnxBsxTcpOptEntry               OBJECT-TYPE
    SYNTAX      TmnxBsxTcpOptEntry
    MAX-ACCESS  not-accessible
    STATUS      current
    DESCRIPTION
        "Each tmnxBsxTcpOptEntry specifies a TCP optimizer for a specific
         ISA-AA group.

         Entries in this table are created and destroyed via SNMP set
         operations to tmnxBsxTcpOptRowStatus."
    INDEX       {
        tmnxBsxIsaAaGroupIndex,
        tmnxBsxTcpOptName
    }
    ::= { tmnxBsxTcpOptTable 1 }

TmnxBsxTcpOptEntry               ::= SEQUENCE
{
    tmnxBsxTcpOptName                TNamedItem,
    tmnxBsxTcpOptRowLastChange       TimeStamp,
    tmnxBsxTcpOptRowStatus           RowStatus,
    tmnxBsxTcpOptDescription         TItemDescription,
    tmnxBsxTcpOptInitCwnd            Unsigned32,
    tmnxBsxTcpOptStackType           INTEGER,
    tmnxBsxTcpOptDAckTimeout         Unsigned32,
    tmnxBsxTcpOptInitSsThreshold     Unsigned32,
    tmnxBsxTcpOptNetworkRttThreshold Unsigned32,
    tmnxBsxTcpOptHighCpuBackoff      TruthValue
}

tmnxBsxTcpOptName                OBJECT-TYPE
    SYNTAX      TNamedItem
    MAX-ACCESS  not-accessible
    STATUS      current
    DESCRIPTION
        "The value of tmnxBsxTcpOptName specifies the name of the TCP
         optimizer."
    ::= { tmnxBsxTcpOptEntry 1 }

tmnxBsxTcpOptRowLastChange       OBJECT-TYPE
    SYNTAX      TimeStamp
    MAX-ACCESS  read-only
    STATUS      current
    DESCRIPTION
        "The value of tmnxBsxTcpOptRowLastChange indicates the last time, since
         system startup, a successful SNMP set caused a value in this row to
         change."
    ::= { tmnxBsxTcpOptEntry 2 }

tmnxBsxTcpOptRowStatus           OBJECT-TYPE
    SYNTAX      RowStatus
    MAX-ACCESS  read-create
    STATUS      current
    DESCRIPTION
        "The value of tmnxBsxTcpOptRowStatus specifies the row status. It
         allows entries to be created and deleted in the tmnxBsxTcpOptTable."
    ::= { tmnxBsxTcpOptEntry 3 }

tmnxBsxTcpOptDescription         OBJECT-TYPE
    SYNTAX      TItemDescription
    MAX-ACCESS  read-create
    STATUS      current
    DESCRIPTION
        "The value of tmnxBsxTcpOptDescription specifies the description of the
         TCP optimizer."
    DEFVAL      { "" }
    ::= { tmnxBsxTcpOptEntry 4 }

tmnxBsxTcpOptInitCwnd            OBJECT-TYPE
    SYNTAX      Unsigned32 (1..256)
    UNITS       "MSS"
    MAX-ACCESS  read-create
    STATUS      current
    DESCRIPTION
        "The value of tmnxBsxTcpOptInitCwnd specifies the initial congestion
         window (CWND) of the TCP optimizer."
    DEFVAL      { 8 }
    ::= { tmnxBsxTcpOptEntry 5 }

tmnxBsxTcpOptStackType           OBJECT-TYPE
    SYNTAX      INTEGER {
        tcpWestwood (1),
        tcpIllinois (2),
        tcpNewReno  (3),
        tcpBbr      (4),
        tcpBbrV2    (5)
    }
    MAX-ACCESS  read-create
    STATUS      current
    DESCRIPTION
        "The value of tmnxBsxTcpOptStackType specifies optimization type used
         on the client-facing TCP stack.
         Valid values are:
               tcpWestwood (1) - TCP-Westwood is used
               tcpIllinois (2) - TCP-Illinois is used
               tcpNewReno  (3) - TCP-New-Reno is used
               tcpBbr      (4) - TCP-BBR is used
               tcpBbrV2    (5) - TCP-BBR-V2 is used"
    DEFVAL      { tcpWestwood }
    ::= { tmnxBsxTcpOptEntry 6 }

tmnxBsxTcpOptDAckTimeout         OBJECT-TYPE
    SYNTAX      Unsigned32 (0 | 200)
    UNITS       "milliseconds"
    MAX-ACCESS  read-create
    STATUS      current
    DESCRIPTION
        "The value of tmnxBsxTcpOptDAckTimeout specifies the Delayed
         Acknowledgment (DACK) timeout used towards the client and server. If
         set to '0', DACK is disabled."
    DEFVAL      { 0 }
    ::= { tmnxBsxTcpOptEntry 7 }

tmnxBsxTcpOptInitSsThreshold     OBJECT-TYPE
    SYNTAX      Unsigned32 (0..1000000 | 1000001)
    UNITS       "KB"
    MAX-ACCESS  read-create
    STATUS      current
    DESCRIPTION
        "The value of tmnxBsxTcpOptInitSsThreshold specifies the initial
         slow-start threshold used towards the client and server.

         A value of 1000001 indicates 'auto'."
    DEFVAL      { 1000000 }
    ::= { tmnxBsxTcpOptEntry 8 }

tmnxBsxTcpOptNetworkRttThreshold OBJECT-TYPE
    SYNTAX      Unsigned32 (0 | 1..100)
    UNITS       "milliseconds"
    MAX-ACCESS  read-create
    STATUS      current
    DESCRIPTION
        "The value of tmnxBsxTcpOptNetworkRttThreshold specifies the network
         round trip time under which the connection will not be optimized.

         A value of 0 indicates disabled."
    DEFVAL      { 0 }
    ::= { tmnxBsxTcpOptEntry 9 }

tmnxBsxTcpOptHighCpuBackoff      OBJECT-TYPE
    SYNTAX      TruthValue
    MAX-ACCESS  read-create
    STATUS      current
    DESCRIPTION
        "The value of tmnxBsxTcpOptHighCpuBackoff specifies whether AA forgoes
         TCP optimization of some sessions when the CPU load is very high."
    DEFVAL      { false }
    ::= { tmnxBsxTcpOptEntry 10 }

tmnxBsxTcpOptStatTable           OBJECT-TYPE
    SYNTAX      SEQUENCE OF TmnxBsxTcpOptStatEntry
    MAX-ACCESS  not-accessible
    STATUS      current
    DESCRIPTION
        "The tmnxBsxTcpOptStatTable contains an entry for each configured
         Application Assurance TCP optimizer."
    ::= { tmnxBsxTcpOptObjs 3 }

tmnxBsxTcpOptStatEntry           OBJECT-TYPE
    SYNTAX      TmnxBsxTcpOptStatEntry
    MAX-ACCESS  not-accessible
    STATUS      current
    DESCRIPTION
        "Each tmnxBsxTcpOptStatEntry specifies Application Assurance TCP
         optimizer statistics.

         Entries are automatically created and destroyed when TCP optimizers
         are created or destroyed using the tmnxBsxTcpOptTable.

         An index with a valid TCP optimizer (an existing row in
         tmnxBsxTcpOptTable) and tmnxChassisIndex set to one with a zero value
         for each of tmnxBsxCardSlotEsaId and tmnxBsxMdaSlotEsaVmId will return
         the summarized statistics per group and TCP optimizer."
    INDEX       {
        tmnxBsxIsaAaGroupIndex,
        tmnxBsxTcpOptName,
        tmnxChassisIndex,
        tmnxBsxCardSlotEsaId,
        tmnxBsxMdaSlotEsaVmId
    }
    ::= { tmnxBsxTcpOptStatTable 1 }

TmnxBsxTcpOptStatEntry           ::= SEQUENCE
{
    tmnxBsxTcpOptStatSessOptimized   Counter64,
    tmnxBsxTcpOptStatOctsRxFmSub     Counter64,
    tmnxBsxTcpOptStatOctsTxFmSub     Counter64,
    tmnxBsxTcpOptStatOctsRetranFmSub Counter64,
    tmnxBsxTcpOptStatOctsRxToSub     Counter64,
    tmnxBsxTcpOptStatOctsTxToSub     Counter64,
    tmnxBsxTcpOptStatOctsRetranToSub Counter64,
    tmnxBsxTcpOptStatPktsRxFmSub     Counter64,
    tmnxBsxTcpOptStatPktsTxFmSub     Counter64,
    tmnxBsxTcpOptStatPktsRetranFmSub Counter64,
    tmnxBsxTcpOptStatPktsRxToSub     Counter64,
    tmnxBsxTcpOptStatPktsTxToSub     Counter64,
    tmnxBsxTcpOptStatPktsRetranToSub Counter64,
    tmnxBsxTcpOptStatDiscntTime      TimeStamp,
    tmnxBsxTcpOptStatSessActive      Counter64,
    tmnxBsxTcpOptStatSessAbUnsupPkt  Counter64,
    tmnxBsxTcpOptStatSessUnUnsupPkt  Counter64,
    tmnxBsxTcpOptStatSessAbPktErr    Counter64,
    tmnxBsxTcpOptStatSessUnPktErr    Counter64,
    tmnxBsxTcpOptStatSessAbInact     Counter64,
    tmnxBsxTcpOptStatSessUnInact     Counter64,
    tmnxBsxTcpOptStatSessUnNoBuffers Counter64,
    tmnxBsxTcpOptStatSessUnExistSess Counter64,
    tmnxBsxTcpOptStatSessAbOther     Counter64,
    tmnxBsxTcpOptStatSessUnOther     Counter64,
    tmnxBsxTcpOptStatMaxAvailBuffers Counter64,
    tmnxBsxTcpOptStatBuffersInUse    Counter64,
    tmnxBsxTcpOptStatSessUnLowNetRtt Counter64,
    tmnxBsxTcpOptStatSessPlcyAbandon Counter64,
    tmnxBsxTcpOptStatSessCpuAbandon  Counter64,
    tmnxBsxTcpOptStatSessCpuUnopt    Counter64
}

tmnxBsxTcpOptStatSessOptimized   OBJECT-TYPE
    SYNTAX      Counter64
    MAX-ACCESS  read-only
    STATUS      current
    DESCRIPTION
        "The value of tmnxBsxTcpOptStatSessOptimized indicates the number of
         sessions that have been optimized by the TCP optimizer."
    ::= { tmnxBsxTcpOptStatEntry 1 }

tmnxBsxTcpOptStatOctsRxFmSub     OBJECT-TYPE
    SYNTAX      Counter64
    UNITS       "octets"
    MAX-ACCESS  read-only
    STATUS      current
    DESCRIPTION
        "The value of tmnxBsxTcpOptStatOctsRxFmSub indicates the number of
         octets received by the TCP optimizer in the subscriber to network
         direction."
    ::= { tmnxBsxTcpOptStatEntry 2 }

tmnxBsxTcpOptStatOctsTxFmSub     OBJECT-TYPE
    SYNTAX      Counter64
    UNITS       "octets"
    MAX-ACCESS  read-only
    STATUS      current
    DESCRIPTION
        "The value of tmnxBsxTcpOptStatOctsTxFmSub indicates the number of
         octets transmitted by the TCP optimizer in the subscriber to network
         direction."
    ::= { tmnxBsxTcpOptStatEntry 3 }

tmnxBsxTcpOptStatOctsRetranFmSub OBJECT-TYPE
    SYNTAX      Counter64
    UNITS       "octets"
    MAX-ACCESS  read-only
    STATUS      current
    DESCRIPTION
        "The value of tmnxBsxTcpOptStatOctsRetranFmSub indicates the number of
         octets retransmitted by the TCP optimizer in the subscriber to network
         direction."
    ::= { tmnxBsxTcpOptStatEntry 4 }

tmnxBsxTcpOptStatOctsRxToSub     OBJECT-TYPE
    SYNTAX      Counter64
    UNITS       "octets"
    MAX-ACCESS  read-only
    STATUS      current
    DESCRIPTION
        "The value of tmnxBsxTcpOptStatOctsRxToSub indicates the number of
         octets received by the TCP optimizer in the network to subscriber
         direction."
    ::= { tmnxBsxTcpOptStatEntry 5 }

tmnxBsxTcpOptStatOctsTxToSub     OBJECT-TYPE
    SYNTAX      Counter64
    UNITS       "octets"
    MAX-ACCESS  read-only
    STATUS      current
    DESCRIPTION
        "The value of tmnxBsxTcpOptStatOctsTxToSub indicates the number of
         octets transmitted by the TCP optimizer in the network to subscriber
         direction."
    ::= { tmnxBsxTcpOptStatEntry 6 }

tmnxBsxTcpOptStatOctsRetranToSub OBJECT-TYPE
    SYNTAX      Counter64
    UNITS       "octets"
    MAX-ACCESS  read-only
    STATUS      current
    DESCRIPTION
        "The value of tmnxBsxTcpOptStatOctsRetranToSub indicates the number of
         octets retransmitted by the TCP optimizer in the network to subscriber
         direction."
    ::= { tmnxBsxTcpOptStatEntry 7 }

tmnxBsxTcpOptStatPktsRxFmSub     OBJECT-TYPE
    SYNTAX      Counter64
    UNITS       "packets"
    MAX-ACCESS  read-only
    STATUS      current
    DESCRIPTION
        "The value of tmnxBsxTcpOptStatPktsRxFmSub indicates the number of
         packets received by the TCP optimizer in the subscriber to network
         direction."
    ::= { tmnxBsxTcpOptStatEntry 8 }

tmnxBsxTcpOptStatPktsTxFmSub     OBJECT-TYPE
    SYNTAX      Counter64
    UNITS       "packets"
    MAX-ACCESS  read-only
    STATUS      current
    DESCRIPTION
        "The value of tmnxBsxTcpOptStatPktsTxFmSub indicates the number of
         packets transmitted by the TCP optimizer in the subscriber to network
         direction."
    ::= { tmnxBsxTcpOptStatEntry 9 }

tmnxBsxTcpOptStatPktsRetranFmSub OBJECT-TYPE
    SYNTAX      Counter64
    UNITS       "packets"
    MAX-ACCESS  read-only
    STATUS      current
    DESCRIPTION
        "The value of tmnxBsxTcpOptStatPktsRetranFmSub indicates the number of
         packets retransmitted by the TCP optimizer in the subscriber to
         network direction."
    ::= { tmnxBsxTcpOptStatEntry 10 }

tmnxBsxTcpOptStatPktsRxToSub     OBJECT-TYPE
    SYNTAX      Counter64
    UNITS       "packets"
    MAX-ACCESS  read-only
    STATUS      current
    DESCRIPTION
        "The value of tmnxBsxTcpOptStatPktsRxToSub indicates the number of
         packets received by the TCP optimizer in the network to subscriber
         direction."
    ::= { tmnxBsxTcpOptStatEntry 11 }

tmnxBsxTcpOptStatPktsTxToSub     OBJECT-TYPE
    SYNTAX      Counter64
    UNITS       "packets"
    MAX-ACCESS  read-only
    STATUS      current
    DESCRIPTION
        "The value of tmnxBsxTcpOptStatPktsTxToSub indicates the number of
         packets transmitted by the TCP optimizer in the network to subscriber
         direction."
    ::= { tmnxBsxTcpOptStatEntry 12 }

tmnxBsxTcpOptStatPktsRetranToSub OBJECT-TYPE
    SYNTAX      Counter64
    UNITS       "packets"
    MAX-ACCESS  read-only
    STATUS      current
    DESCRIPTION
        "The value of tmnxBsxTcpOptStatPktsRetranToSub indicates the number of
         packets retransmitted by the TCP optimizer in the network to
         subscriber direction."
    ::= { tmnxBsxTcpOptStatEntry 13 }

tmnxBsxTcpOptStatDiscntTime      OBJECT-TYPE
    SYNTAX      TimeStamp
    MAX-ACCESS  read-only
    STATUS      current
    DESCRIPTION
        "The value of tmnxBsxTcpOptStatDiscntTime indicates the
         SNMPv2-MIB::sysUpTime (centiseconds) when an ISA-AA MDA within the
         group last changed status."
    ::= { tmnxBsxTcpOptStatEntry 14 }

tmnxBsxTcpOptStatSessActive      OBJECT-TYPE
    SYNTAX      Counter64
    MAX-ACCESS  read-only
    STATUS      current
    DESCRIPTION
        "The value of tmnxBsxTcpOptStatSessActive indicates the number of
         sessions being optimized by the TCP optimizer."
    ::= { tmnxBsxTcpOptStatEntry 15 }

tmnxBsxTcpOptStatSessAbUnsupPkt  OBJECT-TYPE
    SYNTAX      Counter64
    MAX-ACCESS  read-only
    STATUS      current
    DESCRIPTION
        "The value of tmnxBsxTcpOptStatSessAbUnsupPkt indicates the number of
         sessions whose optimization was abandoned by the TCP optimizer due to
         an unsupported packet format."
    ::= { tmnxBsxTcpOptStatEntry 16 }

tmnxBsxTcpOptStatSessUnUnsupPkt  OBJECT-TYPE
    SYNTAX      Counter64
    MAX-ACCESS  read-only
    STATUS      current
    DESCRIPTION
        "The value of tmnxBsxTcpOptStatSessUnUnsupPkt indicates the number of
         sessions that have not been optimized by the TCP optimizer due to an
         unsupported packet format."
    ::= { tmnxBsxTcpOptStatEntry 17 }

tmnxBsxTcpOptStatSessAbPktErr    OBJECT-TYPE
    SYNTAX      Counter64
    MAX-ACCESS  read-only
    STATUS      current
    DESCRIPTION
        "The value of tmnxBsxTcpOptStatSessAbPktErr indicates the number of
         sessions whose optimization was abandoned by the TCP optimizer due to
         a packet error."
    ::= { tmnxBsxTcpOptStatEntry 18 }

tmnxBsxTcpOptStatSessUnPktErr    OBJECT-TYPE
    SYNTAX      Counter64
    MAX-ACCESS  read-only
    STATUS      current
    DESCRIPTION
        "The value of tmnxBsxTcpOptStatSessUnPktErr indicates the number of
         sessions that have not been optimized by the TCP optimizer due to a
         packet error."
    ::= { tmnxBsxTcpOptStatEntry 19 }

tmnxBsxTcpOptStatSessAbInact     OBJECT-TYPE
    SYNTAX      Counter64
    MAX-ACCESS  read-only
    STATUS      current
    DESCRIPTION
        "The value of tmnxBsxTcpOptStatSessAbInact indicates the number of
         sessions whose optimization was abandoned by the TCP optimizer due to
         inactivity."
    ::= { tmnxBsxTcpOptStatEntry 20 }

tmnxBsxTcpOptStatSessUnInact     OBJECT-TYPE
    SYNTAX      Counter64
    MAX-ACCESS  read-only
    STATUS      current
    DESCRIPTION
        "The value of tmnxBsxTcpOptStatSessUnInact indicates the number of
         sessions that have not been optimized by the TCP optimizer due to
         inactivity."
    ::= { tmnxBsxTcpOptStatEntry 21 }

tmnxBsxTcpOptStatSessUnNoBuffers OBJECT-TYPE
    SYNTAX      Counter64
    MAX-ACCESS  read-only
    STATUS      current
    DESCRIPTION
        "The value of tmnxBsxTcpOptStatSessUnNoBuffers indicates the number of
         sessions that have not been optimized by the TCP optimizer due to no
         available buffers."
    ::= { tmnxBsxTcpOptStatEntry 22 }

tmnxBsxTcpOptStatSessUnExistSess OBJECT-TYPE
    SYNTAX      Counter64
    MAX-ACCESS  read-only
    STATUS      current
    DESCRIPTION
        "The value of tmnxBsxTcpOptStatSessUnExistSess indicates the number of
         sessions that have not been optimized by the TCP optimizer due to an
         existing session."
    ::= { tmnxBsxTcpOptStatEntry 23 }

tmnxBsxTcpOptStatSessAbOther     OBJECT-TYPE
    SYNTAX      Counter64
    MAX-ACCESS  read-only
    STATUS      current
    DESCRIPTION
        "The value of tmnxBsxTcpOptStatSessAbOther indicates the number of
         sessions whose optimization was abandoned by the TCP optimizer due to
         other reasons."
    ::= { tmnxBsxTcpOptStatEntry 24 }

tmnxBsxTcpOptStatSessUnOther     OBJECT-TYPE
    SYNTAX      Counter64
    MAX-ACCESS  read-only
    STATUS      current
    DESCRIPTION
        "The value of tmnxBsxTcpOptStatSessUnOther indicates the number of
         sessions that have not been optimized by the TCP optimizer due to
         other reasons."
    ::= { tmnxBsxTcpOptStatEntry 25 }

tmnxBsxTcpOptStatMaxAvailBuffers OBJECT-TYPE
    SYNTAX      Counter64
    MAX-ACCESS  read-only
    STATUS      current
    DESCRIPTION
        "The value of tmnxBsxTcpOptStatMaxAvailBuffers indicates the maximum
         number of buffers available to the TCP optimizer."
    ::= { tmnxBsxTcpOptStatEntry 26 }

tmnxBsxTcpOptStatBuffersInUse    OBJECT-TYPE
    SYNTAX      Counter64
    MAX-ACCESS  read-only
    STATUS      current
    DESCRIPTION
        "The value of tmnxBsxTcpOptStatBuffersInUse indicates the number of
         buffers in use by the TCP optimizer."
    ::= { tmnxBsxTcpOptStatEntry 27 }

tmnxBsxTcpOptStatSessUnLowNetRtt OBJECT-TYPE
    SYNTAX      Counter64
    MAX-ACCESS  read-only
    STATUS      current
    DESCRIPTION
        "The value of tmnxBsxTcpOptStatSessUnLowNetRtt indicates the number of
         unoptimized TCP sessions due to low network flow RTT."
    ::= { tmnxBsxTcpOptStatEntry 28 }

tmnxBsxTcpOptStatSessPlcyAbandon OBJECT-TYPE
    SYNTAX      Counter64
    MAX-ACCESS  read-only
    STATUS      current
    DESCRIPTION
        "The value of tmnxBsxTcpOptStatSessPlcyAbandon indicates the number of
         sessions whose optimization was abandoned by the TCP optimizer due to
         policy."
    ::= { tmnxBsxTcpOptStatEntry 29 }

tmnxBsxTcpOptStatSessCpuAbandon  OBJECT-TYPE
    SYNTAX      Counter64
    MAX-ACCESS  read-only
    STATUS      current
    DESCRIPTION
        "The value of tmnxBsxTcpOptStatSessCpuAbandon indicates the number of
         sessions whose optimization was abandoned by the TCP optimizer due to
         high CPU usage."
    ::= { tmnxBsxTcpOptStatEntry 30 }

tmnxBsxTcpOptStatSessCpuUnopt    OBJECT-TYPE
    SYNTAX      Counter64
    MAX-ACCESS  read-only
    STATUS      current
    DESCRIPTION
        "The value of tmnxBsxTcpOptStatSessCpuUnopt indicates the number of
         sessions that the TCP optimizer did not optimize due to high CPU
         usage."
    ::= { tmnxBsxTcpOptStatEntry 31 }

tmnxBsxTcpValObjs                OBJECT IDENTIFIER ::= { tmnxBsxObjs 20 }

tmnxBsxTcpValScalars             OBJECT IDENTIFIER ::= { tmnxBsxTcpValObjs 1 }

tmnxBsxTcpValLastChangedTime     OBJECT-TYPE
    SYNTAX      TimeStamp
    MAX-ACCESS  read-only
    STATUS      current
    DESCRIPTION
        "The value of tmnxBsxTcpValLastChangedTime indicates the last time,
         since system startup, a successful SNMP set on tmnxBsxTcpValTable
         caused a value to change."
    ::= { tmnxBsxTcpValScalars 1 }

tmnxBsxTcpValTcaLastChangedTime  OBJECT-TYPE
    SYNTAX      TimeStamp
    MAX-ACCESS  read-only
    STATUS      current
    DESCRIPTION
        "The value of tmnxBsxTcpValTcaLastChangedTime indicates the last time,
         since system startup, a successful SNMP set on any row of
         tmnxBsxTcpValTcaTable caused a value to change."
    ::= { tmnxBsxTcpValScalars 2 }

tmnxBsxTcpValTable               OBJECT-TYPE
    SYNTAX      SEQUENCE OF TmnxBsxTcpValEntry
    MAX-ACCESS  not-accessible
    STATUS      current
    DESCRIPTION
        "The tmnxBsxTcpValTable contains TCP validation configuration
         information."
    ::= { tmnxBsxTcpValObjs 2 }

tmnxBsxTcpValEntry               OBJECT-TYPE
    SYNTAX      TmnxBsxTcpValEntry
    MAX-ACCESS  not-accessible
    STATUS      current
    DESCRIPTION
        "Each tmnxBsxTcpValEntry specifies a TCP validation template.

         Entries in this table are created and destroyed via SNMP set
         operations to tmnxBsxTcpValRowStatus."
    INDEX       {
        tmnxBsxAaGrpPartIndex,
        tmnxBsxTcpValName
    }
    ::= { tmnxBsxTcpValTable 1 }

TmnxBsxTcpValEntry               ::= SEQUENCE
{
    tmnxBsxTcpValName                TNamedItem,
    tmnxBsxTcpValRowLastChanged      TimeStamp,
    tmnxBsxTcpValRowStatus           RowStatus,
    tmnxBsxTcpValDescription         TItemDescription,
    tmnxBsxTcpValEventLog            TNamedItemOrEmpty,
    tmnxBsxTcpValEventLogAll         TruthValue,
    tmnxBsxTcpValStrict              TruthValue
}

tmnxBsxTcpValName                OBJECT-TYPE
    SYNTAX      TNamedItem
    MAX-ACCESS  not-accessible
    STATUS      current
    DESCRIPTION
        "The value of tmnxBsxTcpValName specifies the name of the TCP
         validation template."
    ::= { tmnxBsxTcpValEntry 1 }

tmnxBsxTcpValRowLastChanged      OBJECT-TYPE
    SYNTAX      TimeStamp
    MAX-ACCESS  read-only
    STATUS      current
    DESCRIPTION
        "The value of tmnxBsxTcpValRowLastChanged indicates the last time,
         since system startup, a successful SNMP set caused a value in this row
         to change."
    ::= { tmnxBsxTcpValEntry 2 }

tmnxBsxTcpValRowStatus           OBJECT-TYPE
    SYNTAX      RowStatus
    MAX-ACCESS  read-create
    STATUS      current
    DESCRIPTION
        "The value of tmnxBsxTcpValRowStatus specifies the row status. It
         allows entries to be created and deleted in the tmnxBsxTcpValTable."
    ::= { tmnxBsxTcpValEntry 3 }

tmnxBsxTcpValDescription         OBJECT-TYPE
    SYNTAX      TItemDescription
    MAX-ACCESS  read-create
    STATUS      current
    DESCRIPTION
        "The value of tmnxBsxTcpValDescription specifies the description of the
         TCP validation template."
    DEFVAL      { "" }
    ::= { tmnxBsxTcpValEntry 4 }

tmnxBsxTcpValEventLog            OBJECT-TYPE
    SYNTAX      TNamedItemOrEmpty
    MAX-ACCESS  read-create
    STATUS      current
    DESCRIPTION
        "The value of tmnxBsxTcpValEventLog specifies the tmnxBsxEventLogEntry
         where the dropping of problematic TCP packets is logged. If set to an
         empty string, no event logging is performed."
    DEFVAL      { "" }
    ::= { tmnxBsxTcpValEntry 5 }

tmnxBsxTcpValEventLogAll         OBJECT-TYPE
    SYNTAX      TruthValue
    MAX-ACCESS  read-create
    STATUS      current
    DESCRIPTION
        "The value of tmnxBsxTcpValEventLogAll specifies whether the TCP
         validation template event logging is complete. If set to 'true (1)',
         all dropped TCP packets will be logged. Note that
         tmnxBsxTcpValEventLogAll may only be changed to 'true (1)' if the
         value tmnxBsxTcpValEventLog is non-default "
    DEFVAL      { false }
    ::= { tmnxBsxTcpValEntry 6 }

tmnxBsxTcpValStrict              OBJECT-TYPE
    SYNTAX      TruthValue
    MAX-ACCESS  read-create
    STATUS      current
    DESCRIPTION
        "The value of tmnxBsxTcpValStrict specifies whether the TCP validation
         template is strict. If set to 'true (1)', additional TCP validation
         checking is performed."
    DEFVAL      { false }
    ::= { tmnxBsxTcpValEntry 7 }

tmnxBsxTcpValTcaTable            OBJECT-TYPE
    SYNTAX      SEQUENCE OF TmnxBsxTcpValTcaEntry
    MAX-ACCESS  not-accessible
    STATUS      current
    DESCRIPTION
        "The tmnxBsxTcpValTcaTable contains TCP validation TCA configuration
         information.

         Entries in this table are created and destroyed via SNMP set
         operations to tmnxBsxTcpValTcaRowStatus."
    ::= { tmnxBsxTcpValObjs 3 }

tmnxBsxTcpValTcaEntry            OBJECT-TYPE
    SYNTAX      TmnxBsxTcpValTcaEntry
    MAX-ACCESS  not-accessible
    STATUS      current
    DESCRIPTION
        "Each tmnxBsxTcpValTcaEntry indicates the TCA watermarks that are
         configured per TCP validation template, as defined by the value of
         tmnxBsxTcpValTcaName.

         Note that the calculation to determine if a TCA is required (using the
         configured watermarks) is based on the utilization during the past
         minute. The utilization is calculated based on the number of matches
         due to the specified TCP validation template."
    INDEX       {
        tmnxBsxAaGrpPartIndex,
        tmnxBsxTcpValTcaName,
        tmnxBsxTcpValTcaWatermarkType,
        tmnxBsxStatTcaCfgDirection
    }
    ::= { tmnxBsxTcpValTcaTable 1 }

TmnxBsxTcpValTcaEntry            ::= SEQUENCE
{
    tmnxBsxTcpValTcaName             TNamedItem,
    tmnxBsxTcpValTcaWatermarkType    INTEGER,
    tmnxBsxTcpValTcaRowLastChanged   TimeStamp,
    tmnxBsxTcpValTcaRowStatus        RowStatus,
    tmnxBsxTcpValTcaHighWatermark    Unsigned32,
    tmnxBsxTcpValTcaLowWatermark     Unsigned32
}

tmnxBsxTcpValTcaName             OBJECT-TYPE
    SYNTAX      TNamedItem
    MAX-ACCESS  not-accessible
    STATUS      current
    DESCRIPTION
        "The value of tmnxBsxTcpValTcaName specifies the name of the TCP
         validation template. A row for this template must already exist in the
         tmnxBsxTcpValTable."
    ::= { tmnxBsxTcpValTcaEntry 1 }

tmnxBsxTcpValTcaWatermarkType    OBJECT-TYPE
    SYNTAX      INTEGER {
        tcpVal (1)
    }
    MAX-ACCESS  not-accessible
    STATUS      current
    DESCRIPTION
        "The value of tmnxBsxTcpValTcaWatermarkType specifies the TCP
         validation TCA watermark type.

         The watermark type may be one of:
           tcpVal            (1) - based on the TCP validation template        "
    ::= { tmnxBsxTcpValTcaEntry 2 }

tmnxBsxTcpValTcaRowLastChanged   OBJECT-TYPE
    SYNTAX      TimeStamp
    MAX-ACCESS  read-only
    STATUS      current
    DESCRIPTION
        "The value of tmnxBsxTcpValTcaRowLastChanged indicates the last time,
         since system startup, a successful SNMP set caused a value in this row
         to change."
    ::= { tmnxBsxTcpValTcaEntry 3 }

tmnxBsxTcpValTcaRowStatus        OBJECT-TYPE
    SYNTAX      RowStatus
    MAX-ACCESS  read-create
    STATUS      current
    DESCRIPTION
        "The value of tmnxBsxTcpValTcaRowStatus specifies the row status. It
         allows entries to be created and destroyed in the
         tmnxBsxTcpValTcaTable."
    ::= { tmnxBsxTcpValTcaEntry 4 }

tmnxBsxTcpValTcaHighWatermark    OBJECT-TYPE
    SYNTAX      Unsigned32
    MAX-ACCESS  read-create
    STATUS      current
    DESCRIPTION
        "The value of tmnxBsxTcpValTcaHighWatermark specifies the TCP
         validation template's utilization high-watermark.

         This value must be set in the same PDU as tmnxBsxTcpValTcaLowWatermark
         and must be greater than tmnxBsxTcpValTcaLowWatermark."
    DEFVAL      { 'FFFFFFFF'H }
    ::= { tmnxBsxTcpValTcaEntry 5 }

tmnxBsxTcpValTcaLowWatermark     OBJECT-TYPE
    SYNTAX      Unsigned32
    MAX-ACCESS  read-create
    STATUS      current
    DESCRIPTION
        "The value of tmnxBsxTcpValTcaLowWatermark specifies the TCP validation
         template's utilization low-watermark.

         This value must be set in the same PDU as
         tmnxBsxTcpValTcaHighWatermark and must be less than
         tmnxBsxTcpValTcaHighWatermark."
    DEFVAL      { 0 }
    ::= { tmnxBsxTcpValTcaEntry 6 }

tmnxBsxTcpValTcaStatsTable       OBJECT-TYPE
    SYNTAX      SEQUENCE OF TmnxBsxTcpValTcaStatsEntry
    MAX-ACCESS  not-accessible
    STATUS      current
    DESCRIPTION
        "The tmnxBsxTcpValTcaStatsTable contains an entry for each configured
         Application Assurance TCP validate TCA, as configured in
         tmnxBsxTcpValTcaTable."
    ::= { tmnxBsxTcpValObjs 4 }

tmnxBsxTcpValTcaStatsEntry       OBJECT-TYPE
    SYNTAX      TmnxBsxTcpValTcaStatsEntry
    MAX-ACCESS  not-accessible
    STATUS      current
    DESCRIPTION
        "Each tmnxBsxTcpValTcaStatsEntry specifies Application Assurance TCP
         validate TCA statistics per group/partition and TCA.

         Rows in this table are automatically created and destroyed when TCAs
         are created or destroyed in the tmnxBsxTcpValTcaTable."
    INDEX       {
        tmnxBsxAaGrpPartIndex,
        tmnxBsxTcpValTcaName,
        tmnxBsxTcpValTcaWatermarkType,
        tmnxBsxStatTcaCfgDirection
    }
    ::= { tmnxBsxTcpValTcaStatsTable 1 }

TmnxBsxTcpValTcaStatsEntry       ::= SEQUENCE
{
    tmnxBsxTcpValTcaStatsLastRaised  TimeStamp,
    tmnxBsxTcpValTcaStatsLastCleard  TimeStamp,
    tmnxBsxTcpValTcaStatsTcaState    TmnxBsxTcaState,
    tmnxBsxTcpValTcaStatsTcaTrigType TmnxBsxTcaTriggerType
}

tmnxBsxTcpValTcaStatsLastRaised  OBJECT-TYPE
    SYNTAX      TimeStamp
    MAX-ACCESS  read-only
    STATUS      current
    DESCRIPTION
        "The value of tmnxBsxTcpValTcaStatsLastRaised indicates the last time,
         since system startup, when the tmnxBsxTcpValTcaStatsTcaState changed
         from 'cleared (0)' to 'raised (1)'."
    ::= { tmnxBsxTcpValTcaStatsEntry 1 }

tmnxBsxTcpValTcaStatsLastCleard  OBJECT-TYPE
    SYNTAX      TimeStamp
    MAX-ACCESS  read-only
    STATUS      current
    DESCRIPTION
        "The value of tmnxBsxTcpValTcaStatsLastCleard indicates the last time,
         since system startup, when the tmnxBsxTcpValTcaStatsTcaState changed
         from 'raised (1)' to 'cleared (0)'."
    ::= { tmnxBsxTcpValTcaStatsEntry 2 }

tmnxBsxTcpValTcaStatsTcaState    OBJECT-TYPE
    SYNTAX      TmnxBsxTcaState
    MAX-ACCESS  read-only
    STATUS      current
    DESCRIPTION
        "The value of tmnxBsxTcpValTcaStatsTcaState indicates the state of the
         policer TCA."
    ::= { tmnxBsxTcpValTcaStatsEntry 3 }

tmnxBsxTcpValTcaStatsTcaTrigType OBJECT-TYPE
    SYNTAX      TmnxBsxTcaTriggerType
    MAX-ACCESS  read-only
    STATUS      current
    DESCRIPTION
        "The value of tmnxBsxTcpValTcaStatsTcaTrigType indicates the trigger
         type used."
    ::= { tmnxBsxTcpValTcaStatsEntry 4 }

tmnxBsxTcpValStatsTable          OBJECT-TYPE
    SYNTAX      SEQUENCE OF TmnxBsxTcpValStatsEntry
    MAX-ACCESS  not-accessible
    STATUS      current
    DESCRIPTION
        "The tmnxBsxTcpValTcaStatsTable contains an entry for each configured
         Application Assurance TCP validation template, as configured in
         tmnxBsxTcpValTable."
    ::= { tmnxBsxTcpValObjs 5 }

tmnxBsxTcpValStatsEntry          OBJECT-TYPE
    SYNTAX      TmnxBsxTcpValStatsEntry
    MAX-ACCESS  not-accessible
    STATUS      current
    DESCRIPTION
        "Each tmnxBsxTcpValStatsEntry specifies Application Assurance TCP
         validation template statistics per group/partition.

         Rows in this table are automatically created and destroyed when
         validation templates are created or destroyed in the
         tmnxBsxTcpValTable.

         An index with a valid TCP validation template (an existing row in
         tmnxBsxTcpValTable) and tmnxChassisIndex set to one with a zero value
         for each of tmnxBsxCardSlotEsaId and tmnxBsxMdaSlotEsaVmId will return
         the summarized statistics per group and TCP validation template."
    INDEX       {
        tmnxBsxAaGrpPartIndex,
        tmnxBsxTcpValName,
        tmnxBsxTcpValStatsDirection,
        tmnxBsxTcpValStatsUnits,
        tmnxChassisIndex,
        tmnxBsxCardSlotEsaId,
        tmnxBsxMdaSlotEsaVmId
    }
    ::= { tmnxBsxTcpValStatsTable 1 }

TmnxBsxTcpValStatsEntry          ::= SEQUENCE
{
    tmnxBsxTcpValStatsDirection      TmnxBsxDirection,
    tmnxBsxTcpValStatsUnits          INTEGER,
    tmnxBsxTcpValStatsAllowed        Counter64,
    tmnxBsxTcpValStatsDropBadFlag    Counter64,
    tmnxBsxTcpValStatsDropBadOption  Counter64,
    tmnxBsxTcpValStatsDropBadSEQ     Counter64,
    tmnxBsxTcpValStatsDropBadACK     Counter64,
    tmnxBsxTcpValStatsDropNoEstment  Counter64,
    tmnxBsxTcpValStatsDropAlreadyEst Counter64,
    tmnxBsxTcpValStatsDropAsymmetric Counter64,
    tmnxBsxTcpValStatsDropAfterRST   Counter64,
    tmnxBsxTcpValStatsDropFragmented Counter64,
    tmnxBsxTcpValStatsDiscntTime     TimeStamp
}

tmnxBsxTcpValStatsDirection      OBJECT-TYPE
    SYNTAX      TmnxBsxDirection
    MAX-ACCESS  not-accessible
    STATUS      current
    DESCRIPTION
        "The value of tmnxBsxTcpValStatsDirection indicates the direction of
         the TCP validation template statistics."
    ::= { tmnxBsxTcpValStatsEntry 1 }

tmnxBsxTcpValStatsUnits          OBJECT-TYPE
    SYNTAX      INTEGER {
        octets  (1),
        packets (2)
    }
    MAX-ACCESS  not-accessible
    STATUS      current
    DESCRIPTION
        "The value of tmnxBsxTcpValStatsUnits indicates the units of the TCP
         validation template statistics."
    ::= { tmnxBsxTcpValStatsEntry 2 }

tmnxBsxTcpValStatsAllowed        OBJECT-TYPE
    SYNTAX      Counter64
    MAX-ACCESS  read-only
    STATUS      current
    DESCRIPTION
        "The value of tmnxBsxTcpValStatsAllowed indicates the number allowed by
         the TCP validation template."
    ::= { tmnxBsxTcpValStatsEntry 3 }

tmnxBsxTcpValStatsDropBadFlag    OBJECT-TYPE
    SYNTAX      Counter64
    MAX-ACCESS  read-only
    STATUS      current
    DESCRIPTION
        "The value of tmnxBsxTcpValStatsDropBadFlag indicates the number
         dropped by the TCP validation template due to an invalid flag."
    ::= { tmnxBsxTcpValStatsEntry 4 }

tmnxBsxTcpValStatsDropBadOption  OBJECT-TYPE
    SYNTAX      Counter64
    MAX-ACCESS  read-only
    STATUS      current
    DESCRIPTION
        "The value of tmnxBsxTcpValStatsDropBadOption indicates the number
         dropped by the TCP validation template due to an invalid Option."
    ::= { tmnxBsxTcpValStatsEntry 5 }

tmnxBsxTcpValStatsDropBadSEQ     OBJECT-TYPE
    SYNTAX      Counter64
    MAX-ACCESS  read-only
    STATUS      current
    DESCRIPTION
        "The value of tmnxBsxTcpValStatsDropBadSEQ indicates the number dropped
         by the TCP validation template due to an invalid sequence number
         (SEQ)."
    ::= { tmnxBsxTcpValStatsEntry 6 }

tmnxBsxTcpValStatsDropBadACK     OBJECT-TYPE
    SYNTAX      Counter64
    MAX-ACCESS  read-only
    STATUS      current
    DESCRIPTION
        "The value of tmnxBsxTcpValStatsDropBadACK indicates the number dropped
         by the TCP validation template due to an invalid acknowledgement
         number (ACK)."
    ::= { tmnxBsxTcpValStatsEntry 7 }

tmnxBsxTcpValStatsDropNoEstment  OBJECT-TYPE
    SYNTAX      Counter64
    MAX-ACCESS  read-only
    STATUS      current
    DESCRIPTION
        "The value of tmnxBsxTcpValStatsDropNoEstment indicates the number
         dropped by the TCP validation template due to no establishment."
    ::= { tmnxBsxTcpValStatsEntry 8 }

tmnxBsxTcpValStatsDropAlreadyEst OBJECT-TYPE
    SYNTAX      Counter64
    MAX-ACCESS  read-only
    STATUS      current
    DESCRIPTION
        "The value of tmnxBsxTcpValStatsDropAlreadyEst indicates the number
         dropped by the TCP validation template due to being already
         established."
    ::= { tmnxBsxTcpValStatsEntry 9 }

tmnxBsxTcpValStatsDropAsymmetric OBJECT-TYPE
    SYNTAX      Counter64
    MAX-ACCESS  read-only
    STATUS      current
    DESCRIPTION
        "The value of tmnxBsxTcpValStatsDropAsymmetric indicates the number
         dropped by the TCP validation template due to asymmetric routing."
    ::= { tmnxBsxTcpValStatsEntry 10 }

tmnxBsxTcpValStatsDropAfterRST   OBJECT-TYPE
    SYNTAX      Counter64
    MAX-ACCESS  read-only
    STATUS      current
    DESCRIPTION
        "The value of tmnxBsxTcpValStatsDropAfterRST indicates the number
         dropped by the TCP validation template due to use after a reset (RST)."
    ::= { tmnxBsxTcpValStatsEntry 11 }

tmnxBsxTcpValStatsDropFragmented OBJECT-TYPE
    SYNTAX      Counter64
    MAX-ACCESS  read-only
    STATUS      current
    DESCRIPTION
        "The value of tmnxBsxTcpValStatsDropFragmented indicates the number
         dropped by the TCP validation template due to fragmentation."
    ::= { tmnxBsxTcpValStatsEntry 12 }

tmnxBsxTcpValStatsDiscntTime     OBJECT-TYPE
    SYNTAX      TimeStamp
    MAX-ACCESS  read-only
    STATUS      current
    DESCRIPTION
        "The value of tmnxBsxTcpValStatsDiscntTime indicates the
         SNMPv2-MIB::sysUpTime (centiseconds) when an ISA-AA MDA within the
         group last changed status."
    ::= { tmnxBsxTcpValStatsEntry 13 }

tmnxBsxEsmMacObjs                OBJECT IDENTIFIER ::= { tmnxBsxObjs 21 }

tmnxBsxEsmMacSubSumTable         OBJECT-TYPE
    SYNTAX      SEQUENCE OF TmnxBsxEsmMacSubSumEntry
    MAX-ACCESS  not-accessible
    STATUS      current
    DESCRIPTION
        "The tmnxBsxEsmMacSubSumTable contains summary information for esm-mac
         subscribers."
    ::= { tmnxBsxEsmMacObjs 1 }

tmnxBsxEsmMacSubSumEntry         OBJECT-TYPE
    SYNTAX      TmnxBsxEsmMacSubSumEntry
    MAX-ACCESS  not-accessible
    STATUS      current
    DESCRIPTION
        "Each tmnxBsxEsmMacSubSumEntry contains summary information for an
         esm-mac subscriber.

         Rows are created/deleted in this table by the system when esm-mac
         subscribers are created/deleted."
    INDEX       {
        tmnxBsxEsmMacSubscriber,
        tmnxBsxEsmMacIpAddrType,
        tmnxBsxEsmMacIpAddr
    }
    ::= { tmnxBsxEsmMacSubSumTable 1 }

TmnxBsxEsmMacSubSumEntry         ::= SEQUENCE
{
    tmnxBsxEsmMacSubscriber          TNamedItem,
    tmnxBsxEsmMacIpAddrType          InetAddressType,
    tmnxBsxEsmMacIpAddr              InetAddress,
    tmnxBsxEsmMacSubSumUpdateTime    TimeStamp,
    tmnxBsxEsmMacSubSumMacAddress    MacAddress,
    tmnxBsxEsmMacSubSumEsmSubscriber TNamedItem,
    tmnxBsxEsmMacSubSumAppProfNm     TNamedItem
}

tmnxBsxEsmMacSubscriber          OBJECT-TYPE
    SYNTAX      TNamedItem
    MAX-ACCESS  not-accessible
    STATUS      current
    DESCRIPTION
        "The value of tmnxBsxEsmMacSubscriber specifies the name of the esm-mac
         subscriber."
    ::= { tmnxBsxEsmMacSubSumEntry 1 }

tmnxBsxEsmMacIpAddrType          OBJECT-TYPE
    SYNTAX      InetAddressType
    MAX-ACCESS  not-accessible
    STATUS      current
    DESCRIPTION
        "The value of tmnxBsxEsmMacIpAddrType specifies the type of the
         esm-mac's IP address contained in tmnxBsxEsmMacIpAddr."
    ::= { tmnxBsxEsmMacSubSumEntry 2 }

tmnxBsxEsmMacIpAddr              OBJECT-TYPE
    SYNTAX      InetAddress (SIZE (4|16))
    MAX-ACCESS  not-accessible
    STATUS      current
    DESCRIPTION
        "The value of tmnxBsxEsmMacIpAddr specifies the the IP address
         associated with this esm-mac subscriber."
    ::= { tmnxBsxEsmMacSubSumEntry 3 }

tmnxBsxEsmMacSubSumUpdateTime    OBJECT-TYPE
    SYNTAX      TimeStamp
    MAX-ACCESS  read-only
    STATUS      current
    DESCRIPTION
        "The value of tmnxBsxEsmMacSubSumUpdateTime indicates the last time,
         since system startup, the contents of a row of the
         tmnxBsxEsmMacSubSumTable was updated."
    ::= { tmnxBsxEsmMacSubSumEntry 4 }

tmnxBsxEsmMacSubSumMacAddress    OBJECT-TYPE
    SYNTAX      MacAddress
    MAX-ACCESS  read-only
    STATUS      current
    DESCRIPTION
        "The value of tmnxBsxEsmMacSubSumMacAddress indicates the MAC address
         of this esm-mac subscriber."
    ::= { tmnxBsxEsmMacSubSumEntry 5 }

tmnxBsxEsmMacSubSumEsmSubscriber OBJECT-TYPE
    SYNTAX      TNamedItem
    MAX-ACCESS  read-only
    STATUS      current
    DESCRIPTION
        "The value of tmnxBsxEsmMacSubSumEsmSubscriber indicates the esm
         subscriber name to whom this esm-mac belongs."
    ::= { tmnxBsxEsmMacSubSumEntry 6 }

tmnxBsxEsmMacSubSumAppProfNm     OBJECT-TYPE
    SYNTAX      TNamedItem
    MAX-ACCESS  read-only
    STATUS      current
    DESCRIPTION
        "The value of tmnxBsxEsmMacSubSumAppProfNm indicates the name of the
         application profile to be applied to this esm-mac subscriber."
    ::= { tmnxBsxEsmMacSubSumEntry 7 }

tmnxBsxConformance               OBJECT IDENTIFIER ::= { tmnxSRConfs 63 }

tmnxBsxCompliances               OBJECT IDENTIFIER ::= { tmnxBsxConformance 1 }

tmnxBsxCompliance                MODULE-COMPLIANCE
    STATUS      obsolete
    DESCRIPTION
        "The compliance statement for management of BSX features in the
         TIMETRA-BSX-NG-MIB."
    MODULE
        MANDATORY-GROUPS {
            tmnxBsxMdaGroup,
            tmnxBsxPolicyGroup,
            tmnxBsxStatsGroup,
            tmnxBsxNotificationGroup
        }
    ::= { tmnxBsxCompliances 1 }

tmnxBsxComplianceV7v0            MODULE-COMPLIANCE
    STATUS      obsolete
    DESCRIPTION
        "The compliance statement for management of BSX features in the
         TIMETRA-BSX-MIB for SROS release 7.0"
    MODULE
        MANDATORY-GROUPS {
            tmnxBsxMdaGroupV7v0,
            tmnxBsxPolicyGroup,
            tmnxBsxStatsGroup,
            tmnxBsxNotificationGroup
        }
    ::= { tmnxBsxCompliances 2 }

tmnxBsxComplianceV8v0            MODULE-COMPLIANCE
    STATUS      obsolete
    DESCRIPTION
        "The compliance statement for management of BSX features in the
         TIMETRA-BSX-MIB for SROS release 8.0"
    MODULE
        MANDATORY-GROUPS {
            tmnxBsxMdaGroupV7v0,
            tmnxBsxMdaGroupV8v0,
            tmnxBsxMdaGroupMG3v0,
            tmnxBsxPolicyGroupV8v0,
            tmnxBsxStatsGroup,
            tmnxBsxNotifyObjsGroup,
            tmnxBsxNotifyObjsGroupV7v0,
            tmnxBsxNotificationGroup,
            tmnxBsxNotificationGroupV7v0,
            tmnxBsxNotificationGroupV8v0,
            tmnxBsxCflowdGroup,
            tmnxBsxOvrdGroup,
            tmnxBsxMobileGatewayGroup
        }
    ::= { tmnxBsxCompliances 3 }

tmnxBsxComplianceV9v0            MODULE-COMPLIANCE
    STATUS      obsolete
    DESCRIPTION
        "The compliance statement for management of BSX features in the
         TIMETRA-BSX-MIB for SROS release 9.0"
    MODULE
        MANDATORY-GROUPS {
            tmnxBsxMdaGroupV7v0,
            tmnxBsxMdaGroupV8v0,
            tmnxBsxMdaGroupV9v0,
            tmnxBsxPolicyGroupV9v0,
            tmnxBsxStatsGroup,
            tmnxBsxStatsGroupV9v0,
            tmnxBsxNotifyObjsGroup,
            tmnxBsxNotifyObjsGroupV7v0,
            tmnxBsxNotifyObjsGroupV8v0,
            tmnxBsxNotificationGroup,
            tmnxBsxNotificationGroupV7v0,
            tmnxBsxNotificationGroupV8v0,
            tmnxBsxNotificationGroupV9v0,
            tmnxBsxCflowdGroup,
            tmnxBsxCflowdGroupV9v0,
            tmnxBsxOvrdGroup,
            tmnxBsxTransitGroup,
            tmnxBsxMobileGatewayGroup,
            tmnxBsxHttpRedirErrGroup,
            tmnxBsxStaticObjGroup
        }
    ::= { tmnxBsxCompliances 4 }

tmnxBsxComplianceV10v0           MODULE-COMPLIANCE
    STATUS      obsolete
    DESCRIPTION
        "The compliance statement for management of BSX features in the
         TIMETRA-BSX-MIB for SROS release 10.0"
    MODULE
        MANDATORY-GROUPS {
            tmnxBsxMdaGroupV7v0,
            tmnxBsxMdaGroupV8v0,
            tmnxBsxMdaGroupV10v0,
            tmnxBsxPolicyGroupV10v0,
            tmnxBsxStatsGroup,
            tmnxBsxStatsGroupV9v0,
            tmnxBsxNotifyObjsGroup,
            tmnxBsxNotifyObjsGroupV7v0,
            tmnxBsxNotifyObjsGroupV8v0,
            tmnxBsxNotificationGroup,
            tmnxBsxNotificationGroupV7v0,
            tmnxBsxNotificationGroupV8v0,
            tmnxBsxNotificationGroupV9v0,
            tmnxBsxNotificationGroupV10v0,
            tmnxBsxRadApNotificationGroup,
            tmnxBsxCflowdGroup,
            tmnxBsxCflowdGroupV9v0,
            tmnxBsxCflowdGroupV10v0,
            tmnxBsxOvrdGroup,
            tmnxBsxTransitGroup,
            tmnxBsxTransitGroupV10v0,
            tmnxBsxMobileGatewayGroup,
            tmnxBsxHttpRedirErrGroup,
            tmnxBsxHttpRedirGroup,
            tmnxBsxStaticObjGroup,
            tmnxBsxRedundancyObjGroup,
            tmnxBsxHttpEnrichObjGroup,
            tmnxBsxHttpEnrichStatObjGroup,
            tmnxBsxTransitSeenIpGroup,
            tmnxBsxRadiusAccountingObjGroup,
            tmnxBsxRadApObjGroup,
            tmnxBsxRadApStatObjGroup
        }
    ::= { tmnxBsxCompliances 5 }

tmnxBsxComplianceV11v0           MODULE-COMPLIANCE
    STATUS      obsolete
    DESCRIPTION
        "The compliance statement for management of BSX features in the
         TIMETRA-BSX-NG-MIB for SROS release 11.0"
    MODULE
        MANDATORY-GROUPS {
            tmnxBsxMdaGroupV7v0,
            tmnxBsxMdaGroupV8v0,
            tmnxBsxMdaGroupV10v0,
            tmnxBsxMdaGroupV11v0,
            tmnxBsxPolicyAqpExtObjGrp,
            tmnxBsxPolicyGroupV10v0,
            tmnxBsxPolicyTodObjGrp,
            tmnxBsxStatsGroup,
            tmnxBsxStatsGroupV9v0,
            tmnxBsxNotifyObjsGroup,
            tmnxBsxNotifyObjsGroupV7v0,
            tmnxBsxNotifyObjsGroupV8v0,
            tmnxBsxNotificationGroup,
            tmnxBsxNotificationGroupV7v0,
            tmnxBsxNotificationGroupV8v0,
            tmnxBsxNotificationGroupV9v0,
            tmnxBsxNotificationGroupV10v0,
            tmnxBsxNotificationGroupV11v0,
            tmnxBsxRadApNotificationGroup,
            tmnxBsxCflowdGroup,
            tmnxBsxCflowdGroupV9v0,
            tmnxBsxCflowdGroupV10v0,
            tmnxBsxOvrdGroup,
            tmnxBsxTransitGroup,
            tmnxBsxTransitGroupV10v0,
            tmnxBsxMobileGatewayGroup,
            tmnxBsxHttpRedirErrGroup,
            tmnxBsxHttpRedirGroup,
            tmnxBsxStaticObjGroup,
            tmnxBsxRedundancyObjGroup,
            tmnxBsxHttpEnrichObjGroup,
            tmnxBsxHttpEnrichStatObjGroup,
            tmnxBsxMgBillingExclusionsGroup,
            tmnxBsxMgTetherDetectGroup,
            tmnxBsxTransitSeenIpGroup,
            tmnxBsxRadiusAccountingObjGroup,
            tmnxBsxRadApObjGroup,
            tmnxBsxRadApStatObjGroup,
            tmnxBsxRedundancyEnhObjGroup,
            tmnxBsxRadiusAcctObjGroupV11v0,
            tmnxBsxSessionFilterObjGrp,
            tmnxBsxPolicyTimeStampExtObjGrp,
            tmnxBsxUrlFilterObjGrp,
            tmnxBsxUrlFilterStatsObjGrp,
            tmnxBsxHttpNotifObjGrp,
            tmnxBsxHttpEnrAntiSpfObjGrpV11v0,
            tmnxBsxHttpEnAntiSpfStObGrpV11v0,
            tmnxBsxHttpEnrEncObjGrpV11v0
        }
    ::= { tmnxBsxCompliances 6 }

tmnxBsxComplianceV12v0           MODULE-COMPLIANCE
    STATUS      obsolete
    DESCRIPTION
        "The compliance statement for management of BSX features in the
         TIMETRA-BSX-NG-MIB for SROS release 12.0"
    MODULE
        MANDATORY-GROUPS {
            tmnxBsxMdaGroupV7v0,
            tmnxBsxMdaGroupV8v0,
            tmnxBsxMdaGroupV10v0,
            tmnxBsxMdaGroupV11v0,
            tmnxBsxPolicyObjGrp12v0,
            tmnxBsxPolicyTodObjGrp,
            tmnxBsxStatsGroup,
            tmnxBsxStatsGroupV9v0,
            tmnxBsxNotifyObjsGroup,
            tmnxBsxNotifyObjsGroupV7v0,
            tmnxBsxNotifyObjsGroupV8v0,
            tmnxBsxNotificationGroup,
            tmnxBsxNotificationGroupV7v0,
            tmnxBsxNotificationGroupV8v0,
            tmnxBsxNotificationGroupV9v0,
            tmnxBsxNotificationGroupV10v0,
            tmnxBsxNotificationGroupV11v0,
            tmnxBsxNotificationGroupV12v0,
            tmnxBsxRadApNotificationGroup,
            tmnxBsxCflowdGroup,
            tmnxBsxCflowdGroupV9v0,
            tmnxBsxCflowdGroupV10v0,
            tmnxBsxOvrdGroup,
            tmnxBsxTransitGroup,
            tmnxBsxTransitGroupV10v0,
            tmnxBsxMobileGatewayGroup,
            tmnxBsxHttpRedirErrGroup,
            tmnxBsxHttpRedirGroup,
            tmnxBsxStaticObjGroup,
            tmnxBsxRedundancyObjGroup,
            tmnxBsxHttpEnrichObjGroup,
            tmnxBsxHttpEnrichStatObjGroup,
            tmnxBsxMgBillingExclusionsGroup,
            tmnxBsxMgTetherDetectGroup,
            tmnxBsxTransitSeenIpGroup,
            tmnxBsxRadiusAccountingObjGroup,
            tmnxBsxRadApObjGroup,
            tmnxBsxRadApStatObjGroup,
            tmnxBsxRedundancyEnhObjGroup,
            tmnxBsxRadiusAcctObjGroupV11v0,
            tmnxBsxSessionFilterObjGrp,
            tmnxBsxPolicyTimeStampExtObjGrp,
            tmnxBsxUrlFilterObjGrp,
            tmnxBsxUrlFilterStatsObjGrp,
            tmnxBsxUrlFilterObjGrpV12v0,
            tmnxBsxHttpNotifObjGrp,
            tmnxBsxHttpEnrAntiSpfObjGrpV11v0,
            tmnxBsxHttpEnAntiSpfStObGrpV11v0,
            tmnxBsxHttpEnrEncObjGrpV11v0,
            tmnxBsxIpPrefixListObjGrpV12v0,
            tmnxBsxHttpEnrStStrObjGrpV12v0,
            tmnxBsxTrafficStatsObjGrpV12v0,
            tmnxBsxHttpRedirObjGrpV12v0,
            tmnxBsxUsageMonObjGrpV12v0,
            tmnxBsxLwObjGrpV12v0,
            tmnxBsxMdaGroupV12v0
        }
    ::= { tmnxBsxCompliances 7 }

tmnxBsxComplianceV13v0           MODULE-COMPLIANCE
    STATUS      current
    DESCRIPTION
        "The compliance statement for management of BSX features in the
         TIMETRA-BSX-NG-MIB for SROS release 13.0"
    MODULE
        MANDATORY-GROUPS {
            tmnxBsxDnsIpCacheGroupV13v0,
            tmnxBsxUrlListGroupV13v0,
            tmnxBsxNotificationGroupV13v0,
            tmnxBsxPolicyObjGrp13v0,
            tmnxBsxTrafficStatsObjGrpV13v0,
            tmnxBsxNotifyObjsGroupV13v0,
            tmnxBsxGtpGroupV13v0,
            tmnxBsxHttpRedirObjGrpV13v0,
            tmnxBsxHttpNotifObjGrpV13v0,
            tmnxBsxIsa2ObjGroup,
            tmnxBsxXHeaderObjGroup
        }
    ::= { tmnxBsxCompliances 8 }

tmnxBsxComplianceV14v0           MODULE-COMPLIANCE
    STATUS      current
    DESCRIPTION
        "The compliance statement for management of BSX features for SROS
         release 14.0 in the TIMETRA-BSX-NG-MIB."
    MODULE
        MANDATORY-GROUPS {
            tmnxBsxStflFwEnhacementsObjGrp,
            tmnxBsxEventLogSyslogObjGrp,
            tmnxBsxTransitIpPolicyDiamObjGrp,
            tmnxBsxUrlListExtendedGroup,
            tmnxBsxHttpsCaptiveRedirObjGrp,
            tmnxBsxTcpMssObjGrp,
            tmnxBsxCflowdDirectExportGroup,
            tmnxBsxNotificationGroupV14v0,
            tmnxBsxNotifyObjsGroupV14v0,
            tmnxBsxGtpUntunnelingObjGrp,
            tmnxBsxTcpOptObjGrp,
            tmnxBsxTrapPerfObjGrp,
            tmnxBsxTcpValObjGrp
        }
    ::= { tmnxBsxCompliances 9 }

tmnxBsxComplianceV15v0           MODULE-COMPLIANCE
    STATUS      current
    DESCRIPTION
        "The compliance statement for management of BSX features for SROS
         release 15.0 in the TIMETRA-BSX-NG-MIB."
    MODULE
        MANDATORY-GROUPS {
            tmnxBsx15v0ObjGrp,
            tmnxBsxTcpOptV15v0ObjGrp,
            tmnxBsxDEMV15v0ObjGrp,
            tmnxBsxEsmMacV15v0ObjGrp,
            tmnxBsxAppFilterV15v0ObjGrp,
            tmnxBsxPortListV15v0ObjGrp,
            tmnxBsxDEMCngParamsV15v0ObjGrp,
            tmnxBsxPortListRefsV15v0ObjGrp,
            tmnxBsxCflowdExpOvdObjGrp
        }
    ::= { tmnxBsxCompliances 10 }

tmnxBsxComplianceV16v0           MODULE-COMPLIANCE
    STATUS      current
    DESCRIPTION
        "The compliance statement for management of BSX features for SROS
         release 16.0 in the TIMETRA-BSX-NG-MIB."
    MODULE
        MANDATORY-GROUPS {
            tmnxBsxDnsIpCacheProxy16v0ObjGrp,
            tmnxBsxHttpEnrichObjGrp,
            tmnxBsxCertProfileObjGrp,
            tmnxBsxCertProfileNotifyObjsGrp,
            tmnxBsxCertProfileNotifyGrp,
            tmnxBsxSubCongDetObjGrp,
            tmnxBsxSubCongRenamedObjGrp,
            tmnxBsxHttpsRedirHttpsRdrObjGrp,
            tmnxBsxGrpStatHttpsRedirObjGrp,
            tmnxBsxTlsExtensionInsert2ObjGrp,
            tmnxBsxOverloadSubQuarantineGrp,
            tmnxBsxLateIcapBlockObjGrp,
            tmnxBsxGrpStatusDirectionObjGrp,
            tmnxBsxHttpCallingLineIdObjGrp,
            tmnxBsxTetheringDetectionObjGrp,
            tmnxBsxOverloadSubQuarNotifyGrp,
            tmnxBsxRATTypeObjGrp,
            tmnxBsxShallowInspectionGrp,
            tmnxBsxTcpAdvFctGrp,
            tmnxBsxTcpOptEnhanceGrp
        }
    ::= { tmnxBsxCompliances 11 }

tmnxBsxComplianceV17v0           MODULE-COMPLIANCE
    STATUS      current
    DESCRIPTION
        "The compliance statement for management of BSX features for SROS
         release 17.0 in the TIMETRA-BSX-NG-MIB."
    MODULE
        MANDATORY-GROUPS {
            tmnxBsxTcpOptNetObjGrp,
            tmnxBsxFlowAttrObjGrp,
            tmnxBsxPartitionObsoleteGroup,
            tmnxBsxIsaAaVmTrafDistribByIpGrp,
            tmnxBsxSessionRedirectL3L4Group,
            tmnxBsxAbandonTcpOptGroup,
            tmnxBsxCflowConfigFieldsGroup,
            tmnxBsxTetherStateObjGrp,
            tmnxBsxTetherDetectObjGrp,
            tmnxBsxUrlFltrWebServiceGroup,
            tmnxBsxFlowAttrObsoleteGroup,
            tmnxBsxGtpStatefulFirwallObjGrp,
            tmnxBsxUrlFltrWebServNotifGrp,
            tmnxBsxTlsTrafficStatsObjGrp
        }
    ::= { tmnxBsxCompliances 12 }

tmnxBsxComplianceV20v0           MODULE-COMPLIANCE
    STATUS      current
    DESCRIPTION
        "The compliance statement for management of BSX features for SROS
         release 20.0 in the TIMETRA-BSX-NG-MIB."
    MODULE
        MANDATORY-GROUPS {
            tmnxBsxUrlListEnhancementObjGrp,
            tmnxBsxUrlFilterEnhancementGrp,
            tmnxBsxCflowdFieldEncryptObjGrp,
            tmnxBsxCflowdDirExpMultColObjGrp,
            tmnxBsxHttpEnrichRatEntryObjGrp
        }
    ::= { tmnxBsxCompliances 13 }

tmnxBsxComplianceV21v0           MODULE-COMPLIANCE
    STATUS      current
    DESCRIPTION
        "The compliance statement for management of BSX features for SROS
         release 21.0 in the TIMETRA-BSX-NG-MIB."
    MODULE
        MANDATORY-GROUPS {
            tmnxBsxDemEnhancementsObjGrp,
            tmnxBsxAnlSubCongPolEnhObjGrp,
            tmnxBsxPolicyEnhObjGrp,
            tmnxBsxAqpMatchCharGrp,
            tmnxBsxAaFwaBngMobileAccessGrp,
            tmnxBsxAgentGenTablesGrp
        }
    ::= { tmnxBsxCompliances 14 }

tmnxBsxComplianceV22v0           MODULE-COMPLIANCE
    STATUS      current
    DESCRIPTION
        "The compliance statement for management of BSX features for SROS
         release 22.0 in the TIMETRA-BSX-NG-MIB."
    MODULE
        MANDATORY-GROUPS {
            tmnxBsxWebServEnhancementsGrp,
            tmnxBsxIpIdentAssistGrp,
            tmnxBsxHttpEnrEncodeEnhObjGrp,
            tmnxBsxChrgFltrObjGrp
        }
    ::= { tmnxBsxCompliances 15 }

tmnxBsxComplianceV23v0           MODULE-COMPLIANCE
    STATUS      current
    DESCRIPTION
        "The compliance statement for management of BSX features for SROS
         release 23.0 in the TIMETRA-BSX-NG-MIB."
    MODULE
        MANDATORY-GROUPS {
            tmnxBsxTetherDetectObjGrpV23v0,
            tmnxBsxIpIdentAssistGrpV23v0,
            tmnxBsxGrpDistributeByIpV23v0,
            tmnxBsxTcpOptPerfGrpV23v0
        }
    ::= { tmnxBsxCompliances 16 }

tmnxBsxComplianceV24v0           MODULE-COMPLIANCE
    STATUS      current
    DESCRIPTION
        "The compliance statement for management of BSX features in the
         TIMETRA-BSX-NG-MIB for SROS release 24.0"
    MODULE
        MANDATORY-GROUPS {
            tmnxBsxMdaGroupV7v0,
            tmnxBsxMdaGroupV8v0,
            tmnxBsxMdaGroupV10v0,
            tmnxBsxMdaGroupV11v0,
            tmnxBsxPolicyObjGrp12v0,
            tmnxBsxPolicyTodObjGrp,
            tmnxBsxStatsGroup,
            tmnxBsxStatsGroupV9v0,
            tmnxBsxNotifyObjsGroup,
            tmnxBsxNotifyObjsGroupV7v0,
            tmnxBsxNotifyObjsGroupV8v0,
            tmnxBsxNotificationGroup,
            tmnxBsxNotificationGroupV7v0,
            tmnxBsxNotificationGroupV8v0,
            tmnxBsxNotificationGroupV9v0,
            tmnxBsxNotificationGroupV10v0,
            tmnxBsxNotificationGroupV11v0,
            tmnxBsxNotificationGroupV12v0,
            tmnxBsxRadApNotificationGroup,
            tmnxBsxCflowdGroup,
            tmnxBsxCflowdGroupV10v0,
            tmnxBsxOvrdGroup,
            tmnxBsxTransitGroup,
            tmnxBsxTransitGroupV10v0,
            tmnxBsxMobileGatewayGroup,
            tmnxBsxHttpRedirErrGroup,
            tmnxBsxHttpRedirGroup,
            tmnxBsxStaticObjGroup,
            tmnxBsxRedundancyObjGroup,
            tmnxBsxHttpEnrichObjGroup,
            tmnxBsxHttpEnrichStatObjGroup,
            tmnxBsxMgBillingExclusionsGroup,
            tmnxBsxMgTetherDetectGroup,
            tmnxBsxTransitSeenIpGroup,
            tmnxBsxRadiusAccountingObjGroup,
            tmnxBsxRadApObjGroup,
            tmnxBsxRadApStatObjGroup,
            tmnxBsxRedundancyEnhObjGroup,
            tmnxBsxRadiusAcctObjGroupV11v0,
            tmnxBsxSessionFilterObjGrp,
            tmnxBsxPolicyTimeStampExtObjGrp,
            tmnxBsxUrlFilterObjGrp,
            tmnxBsxUrlFilterStatsObjGrp,
            tmnxBsxUrlFilterObjGrpV12v0,
            tmnxBsxHttpNotifObjGrp,
            tmnxBsxHttpEnrAntiSpfObjGrpV11v0,
            tmnxBsxHttpEnAntiSpfStObGrpV11v0,
            tmnxBsxHttpEnrEncObjGrpV11v0,
            tmnxBsxIpPrefixListObjGrpV12v0,
            tmnxBsxHttpEnrStStrObjGrpV12v0,
            tmnxBsxTrafficStatsObjGrpV12v0,
            tmnxBsxHttpRedirObjGrpV12v0,
            tmnxBsxUsageMonObjGrpV12v0,
            tmnxBsxLwObjGrpV12v0,
            tmnxBsxMdaGroupV12v0,
            tmnxBsxAaCflowdFwaFieldsGrpV24v0,
            tmnxBsxAaCflowdFwaMoreGrpV24v0,
            tmnxBsxCflowdEnhObjGrpV24v0,
            tmnxBsxAaTrafficStatsGrpV24v0
        }
    ::= { tmnxBsxCompliances 17 }

tmnxBsxGroups                    OBJECT IDENTIFIER ::= { tmnxBsxConformance 2 }

tmnxBsxMdaGroup                  OBJECT-GROUP
    OBJECTS     {
        tmnxBsxIsaAaGrpLastChangeTime,
        tmnxBsxIsaAaGrpFcLastChangeTime,
        tmnxBsxIsaAaGrpMdaLastChangeTime,
        tmnxBsxIsaAaGrpRowStatus,
        tmnxBsxIsaAaGrpRowLastChange,
        tmnxBsxIsaAaGrpDescription,
        tmnxBsxIsaAaGrpAdminState,
        tmnxBsxIsaAaGrpOperState,
        tmnxBsxIsaAaGrpFailToMode,
        tmnxBsxIsaAaGrpFromSubPool,
        tmnxBsxIsaAaGrpFromSubResvCbs,
        tmnxBsxIsaAaGrpFromSubSlpPolicy,
        tmnxBsxIsaAaGrpFromSubQuePolicy,
        tmnxBsxIsaAaGrpFromSubSchPolicy,
        tmnxBsxIsaAaGrpToSubPool,
        tmnxBsxIsaAaGrpToSubResvCbs,
        tmnxBsxIsaAaGrpToSubSlpPolicy,
        tmnxBsxIsaAaGrpToSubQuePolicy,
        tmnxBsxIsaAaGrpToSubSchPolicy,
        tmnxBsxIsaAaGrpIngressPool,
        tmnxBsxIsaAaGrpIngressResvCbs,
        tmnxBsxIsaAaGrpIngressSlpPolicy,
        tmnxBsxIsaAaGrpIngressQuePolicy,
        tmnxBsxIsaAaGrpFcRowStatus,
        tmnxBsxIsaAaGrpFcRowLastChange,
        tmnxBsxGrpMdaRowStatus,
        tmnxBsxGrpMdaRowLastChange,
        tmnxBsxGrpMdaActivityState,
        tmnxBsxGrpMdaActivityChange,
        tmnxBsxGrpMdaRole,
        tmnxBsxIsaAaGrpActivityChange,
        tmnxBsxGrpStatusDiscontTime,
        tmnxBsxGrpStatusOctsIn,
        tmnxBsxGrpStatusPktsIn,
        tmnxBsxGrpStatusPktsInPChipErs,
        tmnxBsxGrpStatusOctsDiscCongIn,
        tmnxBsxGrpStatusPktsDiscCongIn,
        tmnxBsxGrpStatusOctsToMda,
        tmnxBsxGrpStatusPktsToMda,
        tmnxBsxGrpStatusOctsDisCongMda,
        tmnxBsxGrpStatusPktsDisCongMda,
        tmnxBsxGrpStatusOctsDiscErrors,
        tmnxBsxGrpStatusPktsDiscErrors,
        tmnxBsxGrpStatusOctsPolicyByps,
        tmnxBsxGrpStatusPktsPolicyByps,
        tmnxBsxGrpStatusOctsInspected,
        tmnxBsxGrpStatusPktsInspected,
        tmnxBsxGrpStatusOctsDiscPolicy,
        tmnxBsxGrpStatusPktsDiscPolicy,
        tmnxBsxGrpStatusOctsInMda,
        tmnxBsxGrpStatusPktsInMda,
        tmnxBsxGrpStatusOctsFromMda,
        tmnxBsxGrpStatusPktsFromMda,
        tmnxBsxGrpStatusPktsOutPChipEr,
        tmnxBsxGrpStatusOctsDisCongOut,
        tmnxBsxGrpStatusPktsDisCongOut,
        tmnxBsxGrpStatusOctsOut,
        tmnxBsxGrpStatusPktsOut,
        tmnxBsxGrpStatusFlows,
        tmnxBsxGrpStatusFlowsCurrent,
        tmnxBsxGrpStatusFlowSetupRate,
        tmnxBsxGrpStatusSubsDiverted,
        tmnxBsxGrpStatusSubsCurrent,
        tmnxBsxGrpStatusTrafficRate,
        tmnxBsxGrpStatusHCOctsIn,
        tmnxBsxGrpStatusHCPktsIn,
        tmnxBsxGrpStatusHCPktsInPChipErs,
        tmnxBsxGrpStatusHCOctsDiscCongIn,
        tmnxBsxGrpStatusHCPktsDiscCongIn,
        tmnxBsxGrpStatusHCOctsToMda,
        tmnxBsxGrpStatusHCPktsToMda,
        tmnxBsxGrpStatusHCOctsDisCongMda,
        tmnxBsxGrpStatusHCPktsDisCongMda,
        tmnxBsxGrpStatusHCOctsDiscErrors,
        tmnxBsxGrpStatusHCPktsDiscErrors,
        tmnxBsxGrpStatusHCOctsPolicyByps,
        tmnxBsxGrpStatusHCPktsPolicyByps,
        tmnxBsxGrpStatusHCOctsInspected,
        tmnxBsxGrpStatusHCPktsInspected,
        tmnxBsxGrpStatusHCOctsDiscPolicy,
        tmnxBsxGrpStatusHCPktsDiscPolicy,
        tmnxBsxGrpStatusHCOctsInMda,
        tmnxBsxGrpStatusHCPktsInMda,
        tmnxBsxGrpStatusHCOctsFromMda,
        tmnxBsxGrpStatusHCPktsFromMda,
        tmnxBsxGrpStatusHCPktsOutPChipEr,
        tmnxBsxGrpStatusHCOctsDisCongOut,
        tmnxBsxGrpStatusHCPktsDisCongOut,
        tmnxBsxGrpStatusHCOctsOut,
        tmnxBsxGrpStatusHCPktsOut,
        tmnxBsxGrpStatusHCFlows,
        tmnxBsxGrpStatusIngQDiscontTime,
        tmnxBsxGrpStatusIngQFwdInPPkts,
        tmnxBsxGrpStatusIngQFwdOutPPkts,
        tmnxBsxGrpStatusIngQFwdInPOcts,
        tmnxBsxGrpStatusIngQFwdOutPOcts,
        tmnxBsxGrpStatusIngQDroInPPkts,
        tmnxBsxGrpStatusIngQDroOutPPkts,
        tmnxBsxGrpStatusIngQDroInPOcts,
        tmnxBsxGrpStatusIngQDroOutPOcts,
        tmnxBsxGrpStatusIngQHCFwdInPPkts,
        tmnxBsxGrpStatusIngQHCFwdOutPPkts,
        tmnxBsxGrpStatusIngQHCFwdInPOcts,
        tmnxBsxGrpStatusIngQHCFwdOutPOcts,
        tmnxBsxGrpStatusIngQHCDroInPPkts,
        tmnxBsxGrpStatusIngQHCDroOutPPkts,
        tmnxBsxGrpStatusIngQHCDroInPOcts,
        tmnxBsxGrpStatusIngQHCDroOutPOcts,
        tmnxBsxGrpStatusEgrQDiscontTime,
        tmnxBsxGrpStatusEgrQFwdInPPkts,
        tmnxBsxGrpStatusEgrQFwdOutPPkts,
        tmnxBsxGrpStatusEgrQFwdInPOcts,
        tmnxBsxGrpStatusEgrQFwdOutPOcts,
        tmnxBsxGrpStatusEgrQDroInPPkts,
        tmnxBsxGrpStatusEgrQDroOutPPkts,
        tmnxBsxGrpStatusEgrQDroInPOcts,
        tmnxBsxGrpStatusEgrQDroOutPOcts,
        tmnxBsxGrpStatusEgrQHCFwdInPPkts,
        tmnxBsxGrpStatusEgrQHCFwdOutPPkts,
        tmnxBsxGrpStatusEgrQHCFwdInPOcts,
        tmnxBsxGrpStatusEgrQHCFwdOutPOcts,
        tmnxBsxGrpStatusEgrQHCDroInPPkts,
        tmnxBsxGrpStatusEgrQHCDroOutPPkts,
        tmnxBsxGrpStatusEgrQHCDroInPOcts,
        tmnxBsxGrpStatusEgrQHCDroOutPOcts,
        tmnxBsxGrpMdaEsmSubscribers,
        tmnxBsxGrpMdaSapSubscribers,
        tmnxBsxAaSubSumMdaSlotNum,
        tmnxBsxAaSubSumMdaMdaNum,
        tmnxBsxAaSubSumAppProfName,
        tmnxBsxAaSubSumDiscontTime,
        tmnxBsxAaSubSumOctsAdmFmSb,
        tmnxBsxAaSubSumPktsAdmFmSb,
        tmnxBsxAaSubSumFlwsAdmFmSb,
        tmnxBsxAaSubSumOctsDnyFmSb,
        tmnxBsxAaSubSumPktsDnyFmSb,
        tmnxBsxAaSubSumFlwsDnyFmSb,
        tmnxBsxAaSubSumOctsAdmToSb,
        tmnxBsxAaSubSumPktsAdmToSb,
        tmnxBsxAaSubSumFlwsAdmToSb,
        tmnxBsxAaSubSumOctsDnyToSb,
        tmnxBsxAaSubSumPktsDnyToSb,
        tmnxBsxAaSubSumFlwsDnyToSb,
        tmnxBsxAaSubSumTermFlwDur,
        tmnxBsxAaSubSumTermFlws,
        tmnxBsxAaSubSumShrtDurFlws,
        tmnxBsxAaSubSumMedDurFlws,
        tmnxBsxAaSubSumLngDurFlws,
        tmnxBsxAaSubSumActFlwsFmSb,
        tmnxBsxAaSubSumActFlwsToSb,
        tmnxBsxAaSubSumHCOctsAdmFmSb,
        tmnxBsxAaSubSumHCPktsAdmFmSb,
        tmnxBsxAaSubSumHCFlwsAdmFmSb,
        tmnxBsxAaSubSumHCOctsDnyFmSb,
        tmnxBsxAaSubSumHCPktsDnyFmSb,
        tmnxBsxAaSubSumHCFlwsDnyFmSb,
        tmnxBsxAaSubSumHCOctsAdmToSb,
        tmnxBsxAaSubSumHCPktsAdmToSb,
        tmnxBsxAaSubSumHCFlwsAdmToSb,
        tmnxBsxAaSubSumHCOctsDnyToSb,
        tmnxBsxAaSubSumHCPktsDnyToSb,
        tmnxBsxAaSubSumHCFlwsDnyToSb,
        tmnxBsxAaSubSumHCTermFlwDur,
        tmnxBsxAaSubSumHCTermFlws,
        tmnxBsxAaSubSumHCShrtDurFlws,
        tmnxBsxAaSubSumHCMedDurFlws,
        tmnxBsxAaSubSumHCLngDurFlws
    }
    STATUS      obsolete
    DESCRIPTION
        "The group of objects supporting management of BSX MDA capabilities on
         Nokia SROS series systems."
    ::= { tmnxBsxGroups 1 }

tmnxBsxPolicyGroup               OBJECT-GROUP
    OBJECTS     {
        tmnxBsxProtDescription,
        tmnxBsxAppGrpRowStatus,
        tmnxBsxAppGrpStorageType,
        tmnxBsxAppGrpDescription,
        tmnxBsxAppGrpAdminState,
        tmnxBsxAppRowStatus,
        tmnxBsxAppStorageType,
        tmnxBsxAppDescription,
        tmnxBsxAppAppGroup,
        tmnxBsxAppFilterRowStatus,
        tmnxBsxAppFilterDescription,
        tmnxBsxAppFilterAdminState,
        tmnxBsxAppFilterProtocol,
        tmnxBsxAppFilterProtocolOp,
        tmnxBsxAppFilterFlowSetupDir,
        tmnxBsxAppFilterIpProtocolNum,
        tmnxBsxAppFilterIpProtocolNumOp,
        tmnxBsxAppFilterServerAddrType,
        tmnxBsxAppFilterServerAddr,
        tmnxBsxAppFilterServerAddrLen,
        tmnxBsxAppFilterServerAddrOp,
        tmnxBsxAppFilterServerPort,
        tmnxBsxAppFilterServerPortOp,
        tmnxBsxAppFilterServerPortFpp,
        tmnxBsxAppFilterApplication,
        tmnxBsxAppFilterExprRowStatus,
        tmnxBsxAppFilterExprType,
        tmnxBsxAppFilterExprOperator,
        tmnxBsxAppFilterExprStr,
        tmnxBsxAsoRowStatus,
        tmnxBsxAsoDefValName,
        tmnxBsxAsoValRowStatus,
        tmnxBsxAppProfRowStatus,
        tmnxBsxAppProfDescription,
        tmnxBsxAppProfDivert,
        tmnxBsxAppProfCharRowStatus,
        tmnxBsxAppProfCharValName,
        tmnxBsxPolicerRowStatus,
        tmnxBsxPolicerDescription,
        tmnxBsxPolicerType,
        tmnxBsxPolicerGranularity,
        tmnxBsxPolicerAction,
        tmnxBsxPolicerAdminPIR,
        tmnxBsxPolicerAdminCIR,
        tmnxBsxPolicerCBS,
        tmnxBsxPolicerMBS,
        tmnxBsxPolicerCIRAdaptation,
        tmnxBsxPolicerPIRAdaptation,
        tmnxBsxAqpRowStatus,
        tmnxBsxAqpDescription,
        tmnxBsxAqpAdminState,
        tmnxBsxAqpApplication,
        tmnxBsxAqpApplicationOp,
        tmnxBsxAqpAppGroup,
        tmnxBsxAqpAppGroupOp,
        tmnxBsxAqpTrafficDir,
        tmnxBsxAqpSubscriber,
        tmnxBsxAqpSubscriberOp,
        tmnxBsxAqpDscp,
        tmnxBsxAqpDscpOp,
        tmnxBsxAqpDrop,
        tmnxBsxAqpBwLimitPolicer,
        tmnxBsxAqpFlowRatePolicer,
        tmnxBsxAqpFlowCountPolicer,
        tmnxBsxAdminOwner,
        tmnxBsxAdminControlApply,
        tmnxBsxAdminLastChangeTime,
        tmnxBsxUpgrade,
        tmnxBsxVersion,
        tmnxBsxAqpStatsFlows,
        tmnxBsxFlowFullHighWatermark,
        tmnxBsxFlowFullLowWatermark,
        tmnxBsxAqpCharRowStatus,
        tmnxBsxAqpCharOperator,
        tmnxBsxAqpStatsConflicts,
        tmnxBsxAqpSapSubscrPortId,
        tmnxBsxAqpSapSubscrEncapValue,
        tmnxBsxAqpSapSubscrOp,
        tmnxBsxAqpSrcAddressType,
        tmnxBsxAqpSrcAddress,
        tmnxBsxAqpSrcAddressLength,
        tmnxBsxAqpSrcAddressOp,
        tmnxBsxAqpSrcPortOp,
        tmnxBsxAqpSrcPortLowValue,
        tmnxBsxAqpSrcPortHighValue,
        tmnxBsxAqpDstAddressType,
        tmnxBsxAqpDstAddress,
        tmnxBsxAqpDstAddressLength,
        tmnxBsxAqpDstAddressOp,
        tmnxBsxAqpDstPortOp,
        tmnxBsxAqpDstPortLowValue,
        tmnxBsxAqpDstPortHighValue,
        tmnxBsxAqpRemarkFc,
        tmnxBsxAqpRemarkPriority,
        tmnxBsxAqpRemarkDscpInProfile,
        tmnxBsxAqpRemarkDscpOutProfile,
        tmnxBsxAqpMirrorSource,
        tmnxBsxAqpMirrorSourceAllIncl,
        tmnxBsxAdminCtrlLastChTime,
        tmnxBsxAdminCtrlConfigOwner,
        tmnxBsxAdminCtrlApply
    }
    STATUS      obsolete
    DESCRIPTION
        "The group of objects supporting management of BSX Policy capabilities
         on Nokia SROS series systems."
    ::= { tmnxBsxGroups 2 }

tmnxBsxStatsGroup                OBJECT-GROUP
    OBJECTS     {
        tmnxBsxStatAaAcctLastChTime,
        tmnxBsxStatAaAcctCfgCollStats,
        tmnxBsxStatAaAcctCfgPolicy,
        tmnxBsxStatAaSubLastChTime,
        tmnxBsxStatAaSubSdyLastChTime,
        tmnxBsxStatAaSubDiscontTime,
        tmnxBsxStatAaSubOctsAdmFmSb,
        tmnxBsxStatAaSubPktsAdmFmSb,
        tmnxBsxStatAaSubFlwsAdmFmSb,
        tmnxBsxStatAaSubOctsDnyFmSb,
        tmnxBsxStatAaSubPktsDnyFmSb,
        tmnxBsxStatAaSubFlwsDnyFmSb,
        tmnxBsxStatAaSubOctsAdmToSb,
        tmnxBsxStatAaSubPktsAdmToSb,
        tmnxBsxStatAaSubFlwsAdmToSb,
        tmnxBsxStatAaSubOctsDnyToSb,
        tmnxBsxStatAaSubPktsDnyToSb,
        tmnxBsxStatAaSubFlwsDnyToSb,
        tmnxBsxStatAaSubTermFlwDur,
        tmnxBsxStatAaSubTermFlws,
        tmnxBsxStatAaSubShrtDurFlws,
        tmnxBsxStatAaSubMedDurFlws,
        tmnxBsxStatAaSubLngDurFlws,
        tmnxBsxStatAaSubActFlwsFmSb,
        tmnxBsxStatAaSubActFlwsToSb,
        tmnxBsxStatAaSubHCOctsAdmFmSb,
        tmnxBsxStatAaSubHCPktsAdmFmSb,
        tmnxBsxStatAaSubHCFlwsAdmFmSb,
        tmnxBsxStatAaSubHCOctsDnyFmSb,
        tmnxBsxStatAaSubHCPktsDnyFmSb,
        tmnxBsxStatAaSubHCFlwsDnyFmSb,
        tmnxBsxStatAaSubHCOctsAdmToSb,
        tmnxBsxStatAaSubHCPktsAdmToSb,
        tmnxBsxStatAaSubHCFlwsAdmToSb,
        tmnxBsxStatAaSubHCOctsDnyToSb,
        tmnxBsxStatAaSubHCPktsDnyToSb,
        tmnxBsxStatAaSubHCFlwsDnyToSb,
        tmnxBsxStatAaSubHCTermFlwDur,
        tmnxBsxStatAaSubHCTermFlws,
        tmnxBsxStatAaSubHCShrtDurFlws,
        tmnxBsxStatAaSubHCMedDurFlws,
        tmnxBsxStatAaSubHCLngDurFlws,
        tmnxBsxStatAaSubSdyDiscontTime,
        tmnxBsxStatAaSubSdyOctsAdmFmSb,
        tmnxBsxStatAaSubSdyPktsAdmFmSb,
        tmnxBsxStatAaSubSdyFlwsAdmFmSb,
        tmnxBsxStatAaSubSdyOctsDnyFmSb,
        tmnxBsxStatAaSubSdyPktsDnyFmSb,
        tmnxBsxStatAaSubSdyFlwsDnyFmSb,
        tmnxBsxStatAaSubSdyOctsAdmToSb,
        tmnxBsxStatAaSubSdyPktsAdmToSb,
        tmnxBsxStatAaSubSdyFlwsAdmToSb,
        tmnxBsxStatAaSubSdyOctsDnyToSb,
        tmnxBsxStatAaSubSdyPktsDnyToSb,
        tmnxBsxStatAaSubSdyFlwsDnyToSb,
        tmnxBsxStatAaSubSdyTermFlwDur,
        tmnxBsxStatAaSubSdyTermFlws,
        tmnxBsxStatAaSubSdyShrtDurFlws,
        tmnxBsxStatAaSubSdyMedDurFlws,
        tmnxBsxStatAaSubSdyLngDurFlws,
        tmnxBsxStatAaSubSdyActFlwsFmSb,
        tmnxBsxStatAaSubSdyActFlwsToSb,
        tmnxBsxStatAaSubSdyHCOctsAdmFmSb,
        tmnxBsxStatAaSubSdyHCPktsAdmFmSb,
        tmnxBsxStatAaSubSdyHCFlwsAdmFmSb,
        tmnxBsxStatAaSubSdyHCOctsDnyFmSb,
        tmnxBsxStatAaSubSdyHCPktsDnyFmSb,
        tmnxBsxStatAaSubSdyHCFlwsDnyFmSb,
        tmnxBsxStatAaSubSdyHCOctsAdmToSb,
        tmnxBsxStatAaSubSdyHCPktsAdmToSb,
        tmnxBsxStatAaSubSdyHCFlwsAdmToSb,
        tmnxBsxStatAaSubSdyHCOctsDnyToSb,
        tmnxBsxStatAaSubSdyHCPktsDnyToSb,
        tmnxBsxStatAaSubSdyHCFlwsDnyToSb,
        tmnxBsxStatAaSubSdyHCTermFlwDur,
        tmnxBsxStatAaSubSdyHCTermFlws,
        tmnxBsxStatAaSubSdyHCShrtDurFlws,
        tmnxBsxStatAaSubSdyHCMedDurFlws,
        tmnxBsxStatAaSubSdyHCLngDurFlws,
        tmnxBsxStatAaSubCfgRowStatus,
        tmnxBsxStatAaSubSdyRowStatus,
        tmnxBsxStatAaDiscontTime,
        tmnxBsxStatAaOctsAdmFmSb,
        tmnxBsxStatAaPktsAdmFmSb,
        tmnxBsxStatAaFlwsAdmFmSb,
        tmnxBsxStatAaOctsDnyFmSb,
        tmnxBsxStatAaPktsDnyFmSb,
        tmnxBsxStatAaFlwsDnyFmSb,
        tmnxBsxStatAaOctsAdmToSb,
        tmnxBsxStatAaPktsAdmToSb,
        tmnxBsxStatAaFlwsAdmToSb,
        tmnxBsxStatAaOctsDnyToSb,
        tmnxBsxStatAaPktsDnyToSb,
        tmnxBsxStatAaFlwsDnyToSb,
        tmnxBsxStatAaTermFlwDur,
        tmnxBsxStatAaTermFlws,
        tmnxBsxStatAaShrtDurFlws,
        tmnxBsxStatAaMedDurFlws,
        tmnxBsxStatAaLngDurFlws,
        tmnxBsxStatAaActFlwsFmSb,
        tmnxBsxStatAaActFlwsToSb,
        tmnxBsxStatAaNumSubscribers,
        tmnxBsxStatAaHCOctsAdmFmSb,
        tmnxBsxStatAaHCPktsAdmFmSb,
        tmnxBsxStatAaHCFlwsAdmFmSb,
        tmnxBsxStatAaHCOctsDnyFmSb,
        tmnxBsxStatAaHCPktsDnyFmSb,
        tmnxBsxStatAaHCFlwsDnyFmSb,
        tmnxBsxStatAaHCOctsAdmToSb,
        tmnxBsxStatAaHCPktsAdmToSb,
        tmnxBsxStatAaHCFlwsAdmToSb,
        tmnxBsxStatAaHCOctsDnyToSb,
        tmnxBsxStatAaHCPktsDnyToSb,
        tmnxBsxStatAaHCFlwsDnyToSb,
        tmnxBsxStatAaHCTermFlwDur,
        tmnxBsxStatAaHCTermFlws,
        tmnxBsxStatAaHCShrtDurFlws,
        tmnxBsxStatAaHCMedDurFlws,
        tmnxBsxStatAaHCLngDurFlws
    }
    STATUS      current
    DESCRIPTION
        "The group of objects supporting management of BSX Stats capabilities
         on Nokia SROS series systems."
    ::= { tmnxBsxGroups 3 }

tmnxBsxNotifyObjsGroup           OBJECT-GROUP
    OBJECTS     {
        tmnxBsxNotifyIsaAaGroupIndex,
        tmnxBsxNotifyActiveMda,
        tmnxBsxNotifyActionStatus,
        tmnxBsxNotifyIsaSlotNum,
        tmnxBsxNotifyIsaMdaNum
    }
    STATUS      current
    DESCRIPTION
        "The group of objects supporting BSX Notification capabilities on Nokia
         SROS series systems."
    ::= { tmnxBsxGroups 4 }

tmnxBsxNotificationGroup         NOTIFICATION-GROUP
    NOTIFICATIONS {
        tmnxBsxIsaAaGrpFailureV2,
        tmnxBsxIsaAaGrpFailureClearV2,
        tmnxBsxIsaAaGrpNonRedundantV2,
        tmnxBsxIsaAaGrpNonRedundantClear,
        tmnxBsxIsaAaGrpSwitchover,
        tmnxBsxIsaAaGrpFlowFull,
        tmnxBsxIsaAaGrpFlowFullClear,
        tmnxBsxIsaAaSubLoadBalance
    }
    STATUS      current
    DESCRIPTION
        "The group of notifications supporting BSX capabilities on Nokia SROS
         series systems."
    ::= { tmnxBsxGroups 5 }

tmnxBsxMdaGroups                 OBJECT IDENTIFIER ::= { tmnxBsxGroups 6 }

tmnxBsxMdaGroupV7v0              OBJECT-GROUP
    OBJECTS     {
        tmnxBsxIsaAaGrpLastChangeTime,
        tmnxBsxIsaAaGrpFcLastChangeTime,
        tmnxBsxIsaAaGrpMdaLastChangeTime,
        tmnxBsxIsaAaGrpRowStatus,
        tmnxBsxIsaAaGrpRowLastChange,
        tmnxBsxIsaAaGrpDescription,
        tmnxBsxIsaAaGrpAdminState,
        tmnxBsxIsaAaGrpOperState,
        tmnxBsxIsaAaGrpFailToMode,
        tmnxBsxIsaAaGrpFromSubPool,
        tmnxBsxIsaAaGrpFromSubResvCbs,
        tmnxBsxIsaAaGrpFromSubSlpPolicy,
        tmnxBsxIsaAaGrpFromSubQuePolicy,
        tmnxBsxIsaAaGrpFromSubSchPolicy,
        tmnxBsxIsaAaGrpToSubPool,
        tmnxBsxIsaAaGrpToSubResvCbs,
        tmnxBsxIsaAaGrpToSubSlpPolicy,
        tmnxBsxIsaAaGrpToSubQuePolicy,
        tmnxBsxIsaAaGrpToSubSchPolicy,
        tmnxBsxIsaAaGrpFcRowStatus,
        tmnxBsxIsaAaGrpFcRowLastChange,
        tmnxBsxGrpMdaRowStatus,
        tmnxBsxGrpMdaRowLastChange,
        tmnxBsxGrpMdaActivityState,
        tmnxBsxGrpMdaActivityChange,
        tmnxBsxGrpMdaRole,
        tmnxBsxIsaAaGrpActivityChange,
        tmnxBsxGrpStatusDiscontTime,
        tmnxBsxGrpStatusOctsIn,
        tmnxBsxGrpStatusPktsIn,
        tmnxBsxGrpStatusPktsInPChipErs,
        tmnxBsxGrpStatusOctsDiscCongIn,
        tmnxBsxGrpStatusPktsDiscCongIn,
        tmnxBsxGrpStatusOctsToMda,
        tmnxBsxGrpStatusPktsToMda,
        tmnxBsxGrpStatusOctsDisCongMda,
        tmnxBsxGrpStatusPktsDisCongMda,
        tmnxBsxGrpStatusOctsDiscErrors,
        tmnxBsxGrpStatusPktsDiscErrors,
        tmnxBsxGrpStatusOctsPolicyByps,
        tmnxBsxGrpStatusPktsPolicyByps,
        tmnxBsxGrpStatusOctsInspected,
        tmnxBsxGrpStatusPktsInspected,
        tmnxBsxGrpStatusOctsDiscPolicy,
        tmnxBsxGrpStatusPktsDiscPolicy,
        tmnxBsxGrpStatusOctsInMda,
        tmnxBsxGrpStatusPktsInMda,
        tmnxBsxGrpStatusOctsFromMda,
        tmnxBsxGrpStatusPktsFromMda,
        tmnxBsxGrpStatusPktsOutPChipEr,
        tmnxBsxGrpStatusOctsDisCongOut,
        tmnxBsxGrpStatusPktsDisCongOut,
        tmnxBsxGrpStatusOctsOut,
        tmnxBsxGrpStatusPktsOut,
        tmnxBsxGrpStatusFlows,
        tmnxBsxGrpStatusFlowsCurrent,
        tmnxBsxGrpStatusFlowSetupRate,
        tmnxBsxGrpStatusSubsDiverted,
        tmnxBsxGrpStatusSubsCurrent,
        tmnxBsxGrpStatusTrafficRate,
        tmnxBsxGrpStatusHCOctsIn,
        tmnxBsxGrpStatusHCPktsIn,
        tmnxBsxGrpStatusHCPktsInPChipErs,
        tmnxBsxGrpStatusHCOctsDiscCongIn,
        tmnxBsxGrpStatusHCPktsDiscCongIn,
        tmnxBsxGrpStatusHCOctsToMda,
        tmnxBsxGrpStatusHCPktsToMda,
        tmnxBsxGrpStatusHCOctsDisCongMda,
        tmnxBsxGrpStatusHCPktsDisCongMda,
        tmnxBsxGrpStatusHCOctsDiscErrors,
        tmnxBsxGrpStatusHCPktsDiscErrors,
        tmnxBsxGrpStatusHCOctsPolicyByps,
        tmnxBsxGrpStatusHCPktsPolicyByps,
        tmnxBsxGrpStatusHCOctsInspected,
        tmnxBsxGrpStatusHCPktsInspected,
        tmnxBsxGrpStatusHCOctsDiscPolicy,
        tmnxBsxGrpStatusHCPktsDiscPolicy,
        tmnxBsxGrpStatusHCOctsInMda,
        tmnxBsxGrpStatusHCPktsInMda,
        tmnxBsxGrpStatusHCOctsFromMda,
        tmnxBsxGrpStatusHCPktsFromMda,
        tmnxBsxGrpStatusHCPktsOutPChipEr,
        tmnxBsxGrpStatusHCOctsDisCongOut,
        tmnxBsxGrpStatusHCPktsDisCongOut,
        tmnxBsxGrpStatusHCOctsOut,
        tmnxBsxGrpStatusHCPktsOut,
        tmnxBsxGrpStatusHCFlows,
        tmnxBsxGrpStatusIngQDiscontTime,
        tmnxBsxGrpStatusIngQFwdInPPkts,
        tmnxBsxGrpStatusIngQFwdOutPPkts,
        tmnxBsxGrpStatusIngQFwdInPOcts,
        tmnxBsxGrpStatusIngQFwdOutPOcts,
        tmnxBsxGrpStatusIngQDroInPPkts,
        tmnxBsxGrpStatusIngQDroOutPPkts,
        tmnxBsxGrpStatusIngQDroInPOcts,
        tmnxBsxGrpStatusIngQDroOutPOcts,
        tmnxBsxGrpStatusIngQHCFwdInPPkts,
        tmnxBsxGrpStatusIngQHCFwdOutPPkts,
        tmnxBsxGrpStatusIngQHCFwdInPOcts,
        tmnxBsxGrpStatusIngQHCFwdOutPOcts,
        tmnxBsxGrpStatusIngQHCDroInPPkts,
        tmnxBsxGrpStatusIngQHCDroOutPPkts,
        tmnxBsxGrpStatusIngQHCDroInPOcts,
        tmnxBsxGrpStatusIngQHCDroOutPOcts,
        tmnxBsxGrpStatusEgrQDiscontTime,
        tmnxBsxGrpStatusEgrQFwdInPPkts,
        tmnxBsxGrpStatusEgrQFwdOutPPkts,
        tmnxBsxGrpStatusEgrQFwdInPOcts,
        tmnxBsxGrpStatusEgrQFwdOutPOcts,
        tmnxBsxGrpStatusEgrQDroInPPkts,
        tmnxBsxGrpStatusEgrQDroOutPPkts,
        tmnxBsxGrpStatusEgrQDroInPOcts,
        tmnxBsxGrpStatusEgrQDroOutPOcts,
        tmnxBsxGrpStatusEgrQHCFwdInPPkts,
        tmnxBsxGrpStatusEgrQHCFwdOutPPkts,
        tmnxBsxGrpStatusEgrQHCFwdInPOcts,
        tmnxBsxGrpStatusEgrQHCFwdOutPOcts,
        tmnxBsxGrpStatusEgrQHCDroInPPkts,
        tmnxBsxGrpStatusEgrQHCDroOutPPkts,
        tmnxBsxGrpStatusEgrQHCDroInPOcts,
        tmnxBsxGrpStatusEgrQHCDroOutPOcts,
        tmnxBsxGrpMdaEsmSubscribers,
        tmnxBsxGrpMdaSapSubscribers,
        tmnxBsxAaSubSumMdaSlotNum,
        tmnxBsxAaSubSumMdaMdaNum,
        tmnxBsxAaSubSumAppProfName,
        tmnxBsxAaSubSumDiscontTime,
        tmnxBsxAaSubSumOctsAdmFmSb,
        tmnxBsxAaSubSumPktsAdmFmSb,
        tmnxBsxAaSubSumFlwsAdmFmSb,
        tmnxBsxAaSubSumOctsDnyFmSb,
        tmnxBsxAaSubSumPktsDnyFmSb,
        tmnxBsxAaSubSumFlwsDnyFmSb,
        tmnxBsxAaSubSumOctsAdmToSb,
        tmnxBsxAaSubSumPktsAdmToSb,
        tmnxBsxAaSubSumFlwsAdmToSb,
        tmnxBsxAaSubSumOctsDnyToSb,
        tmnxBsxAaSubSumPktsDnyToSb,
        tmnxBsxAaSubSumFlwsDnyToSb,
        tmnxBsxAaSubSumTermFlwDur,
        tmnxBsxAaSubSumTermFlws,
        tmnxBsxAaSubSumShrtDurFlws,
        tmnxBsxAaSubSumMedDurFlws,
        tmnxBsxAaSubSumLngDurFlws,
        tmnxBsxAaSubSumActFlwsFmSb,
        tmnxBsxAaSubSumActFlwsToSb,
        tmnxBsxAaSubSumHCOctsAdmFmSb,
        tmnxBsxAaSubSumHCPktsAdmFmSb,
        tmnxBsxAaSubSumHCFlwsAdmFmSb,
        tmnxBsxAaSubSumHCOctsDnyFmSb,
        tmnxBsxAaSubSumHCPktsDnyFmSb,
        tmnxBsxAaSubSumHCFlwsDnyFmSb,
        tmnxBsxAaSubSumHCOctsAdmToSb,
        tmnxBsxAaSubSumHCPktsAdmToSb,
        tmnxBsxAaSubSumHCFlwsAdmToSb,
        tmnxBsxAaSubSumHCOctsDnyToSb,
        tmnxBsxAaSubSumHCPktsDnyToSb,
        tmnxBsxAaSubSumHCFlwsDnyToSb,
        tmnxBsxAaSubSumHCTermFlwDur,
        tmnxBsxAaSubSumHCTermFlws,
        tmnxBsxAaSubSumHCShrtDurFlws,
        tmnxBsxAaSubSumHCMedDurFlws,
        tmnxBsxAaSubSumHCLngDurFlws
    }
    STATUS      current
    DESCRIPTION
        "The group of objects supporting management of BSX MDA capabilities on
         Nokia SROS series systems for release 7.0"
    ::= { tmnxBsxMdaGroups 1 }

tmnxBsxMdaGroupV8v0              OBJECT-GROUP
    OBJECTS     {
        tmnxBsxAaGrpPartLastChangeTime,
        tmnxBsxAaGrpPartRowStatus,
        tmnxBsxAaGrpPartRowLastChange,
        tmnxBsxAaGrpPartDescription,
        tmnxBsxIsaAaGrpPartitions,
        tmnxBsxIsaAaGrpCapCostLowThres,
        tmnxBsxIsaAaGrpCapCostHighThres,
        tmnxBsxIsaAaGrpLoadBalanceStatus,
        tmnxBsxIsaAaGrpUnassignedEsmSubs,
        tmnxBsxIsaAaGrpUnassignedSapSubs,
        tmnxBsxIsaAaGrpUnassignedSpkSubs,
        tmnxBsxIsaAaGrpAaSubScale,
        tmnxBsxIsaAaGrpOverloadCutThru,
        tmnxBsxGrpMdaSpokeSdpSubscribers,
        tmnxBsxGrpMdaCapacityCost,
        tmnxBsxGrpMdaStatsResourceCount,
        tmnxBsxGrpStatusFlowsAverage,
        tmnxBsxGrpStatusFlowsPeak,
        tmnxBsxGrpStatusFlowSetupRateAvg,
        tmnxBsxGrpStatusFlowSetupRatePk,
        tmnxBsxGrpStatusSubsDivertedAvg,
        tmnxBsxGrpStatusSubsDivertedPk,
        tmnxBsxGrpStatusSubsAverage,
        tmnxBsxGrpStatusSubsPeak,
        tmnxBsxGrpStatusTrafficRateAvg,
        tmnxBsxGrpStatusTrafficRatePeak,
        tmnxBsxIsaLoadBalUnSub,
        tmnxBsxAaSubMdaSlotNum,
        tmnxBsxAaSubMdaMdaNum,
        tmnxBsxAaSubAppProfName,
        tmnxBsxAaSubHasOverrides
    }
    STATUS      current
    DESCRIPTION
        "The group of objects supporting management of BSX MDA capabilities on
         Nokia SROS series systems for release 8.0"
    ::= { tmnxBsxMdaGroups 2 }

tmnxBsxMdaGroupV9v0              OBJECT-GROUP
    OBJECTS     {
        tmnxBsxGrpStatusPacketRate,
        tmnxBsxGrpStatusPacketRateAvg,
        tmnxBsxGrpStatusPacketRatePeak,
        tmnxBsxGrpStatusFlowResInUse,
        tmnxBsxGrpMdaTransitIpSubs,
        tmnxBsxGrpMdaTransitIpAddrs,
        tmnxBsxGrpMdaTransitSubs,
        tmnxBsxGrpMdaTransPrefEntries,
        tmnxBsxIsaAaGrpFromSubWaSBfHiWmk,
        tmnxBsxIsaAaGrpFromSubWaSBfLoWmk,
        tmnxBsxIsaAaGrpToSubWaSBfHiWmk,
        tmnxBsxIsaAaGrpToSubWaSBfLoWmk,
        tmnxBsxAaSubTransitIpPolicyId,
        tmnxBsxAaSubTransPrefPolicyId,
        tmnxBsxIsaAaGrpTransPrefV4NmEntr,
        tmnxBsxIsaLoadBalUnSubTransit,
        tmnxBsxAaGrpPartXOnlineHost,
        tmnxBsxAaGrpPartHttpMatchAllReq,
        tmnxBsxGrpStatusHCPktSzIncPk,
        tmnxBsxGrpStatusPktSzIncPkLo,
        tmnxBsxGrpStatusPktSzIncPkHi,
        tmnxBsxGrpStatusHCPktSzDecPk,
        tmnxBsxGrpStatusPktSzDecPkLo,
        tmnxBsxGrpStatusPktSzDecPkHi,
        tmnxBsxGrpStatusHCPktSzIncOc,
        tmnxBsxGrpStatusPktSzIncOcLo,
        tmnxBsxGrpStatusPktSzIncOcHi,
        tmnxBsxGrpStatusHCPktSzDecOc,
        tmnxBsxGrpStatusPktSzDecOcLo,
        tmnxBsxGrpStatusPktSzDecOcHi
    }
    STATUS      obsolete
    DESCRIPTION
        "The group of additional objects introduced in release 9.0 to support
         management of BSX MDA capabilities on Nokia SROS series systems."
    ::= { tmnxBsxMdaGroups 3 }

tmnxBsxMdaGroupV10v0             OBJECT-GROUP
    OBJECTS     {
        tmnxBsxGrpStatusPacketRate,
        tmnxBsxGrpStatusPacketRateAvg,
        tmnxBsxGrpStatusPacketRatePeak,
        tmnxBsxGrpStatusFlowResInUse,
        tmnxBsxGrpMdaTransitIpSubs,
        tmnxBsxGrpMdaTransitIpAddrs,
        tmnxBsxGrpMdaTransitSubs,
        tmnxBsxIsaAaGrpFromSubWaSBfHiWmk,
        tmnxBsxIsaAaGrpFromSubWaSBfLoWmk,
        tmnxBsxIsaAaGrpToSubWaSBfHiWmk,
        tmnxBsxIsaAaGrpToSubWaSBfLoWmk,
        tmnxBsxAaSubTransitIpPolicyId,
        tmnxBsxAaSubTransPrefPolicyId,
        tmnxBsxIsaAaGrpTransPrefV4NmEntr,
        tmnxBsxIsaLoadBalUnSubTransit,
        tmnxBsxAaGrpPartXOnlineHost,
        tmnxBsxAaGrpPartHttpMatchAllReq,
        tmnxBsxAaGrpPartAaSubRemote,
        tmnxBsxGrpStatusHCPktSzIncPk,
        tmnxBsxGrpStatusPktSzIncPkLo,
        tmnxBsxGrpStatusPktSzIncPkHi,
        tmnxBsxGrpStatusHCPktSzDecPk,
        tmnxBsxGrpStatusPktSzDecPkLo,
        tmnxBsxGrpStatusPktSzDecPkHi,
        tmnxBsxGrpStatusHCPktSzIncOc,
        tmnxBsxGrpStatusPktSzIncOcLo,
        tmnxBsxGrpStatusPktSzIncOcHi,
        tmnxBsxGrpStatusHCPktSzDecOc,
        tmnxBsxGrpStatusPktSzDecOcLo,
        tmnxBsxGrpStatusPktSzDecOcHi,
        tmnxBsxIsaAaGrpTransPrefV6NmEntr,
        tmnxBsxIsaAaGrpTransPrefV6RmEntr,
        tmnxBsxGrpMdaTransPrefV4Entr,
        tmnxBsxGrpMdaTransPrefV6Entr,
        tmnxBsxGrpMdaTransPrefV6RemEntr
    }
    STATUS      current
    DESCRIPTION
        "The group of objects supporting management of BSX MDA capabilities on
         Nokia SROS series systems for release 10.0."
    ::= { tmnxBsxMdaGroups 4 }

tmnxBsxMdaGroupMG3v0             OBJECT-GROUP
    OBJECTS     {
        tmnxBsxAaGrpPartXOnlineHost,
        tmnxBsxAaGrpPartHttpMatchAllReq
    }
    STATUS      obsolete
    DESCRIPTION
        "The group of objects supporting management of BSX MDA capabilities on
         Nokia Mobile Gateway systems for the MG 3.0 release."
    ::= { tmnxBsxMdaGroups 5 }

tmnxBsxMdaGroupV11v0             OBJECT-GROUP
    OBJECTS     {
        tmnxBsxGrpStatusHCSeenIpReqSent,
        tmnxBsxGrpStatusSeenIpReqSentLo,
        tmnxBsxGrpStatusSeenIpReqSentHi,
        tmnxBsxGrpStatusHCSeenIpReqDrop,
        tmnxBsxGrpStatusSeenIpReqDropLo,
        tmnxBsxGrpStatusSeenIpReqDropHi,
        tmnxBsxGrpStatusHCSubsCreated,
        tmnxBsxGrpStatusSubsCreatedLo,
        tmnxBsxGrpStatusSubsCreatedHi,
        tmnxBsxGrpStatusHCSubsDeleted,
        tmnxBsxGrpStatusSubsDeletedLo,
        tmnxBsxGrpStatusSubsDeletedHi,
        tmnxBsxGrpStatusHCSubsModified,
        tmnxBsxGrpStatusSubsModifiedLo,
        tmnxBsxGrpStatusSubsModifiedHi
    }
    STATUS      current
    DESCRIPTION
        "The group of objects extending the management of BSX MDA capabilities
         on Nokia SROS series systems for release 11.0."
    ::= { tmnxBsxMdaGroups 6 }

tmnxBsxObsoleteGroups            OBJECT IDENTIFIER ::= { tmnxBsxGroups 7 }

tmnxBsxObsoleteGroupV7v0         OBJECT-GROUP
    OBJECTS     {
        tmnxBsxIsaAaGrpIngressPool,
        tmnxBsxIsaAaGrpIngressResvCbs,
        tmnxBsxIsaAaGrpIngressSlpPolicy,
        tmnxBsxIsaAaGrpIngressQuePolicy
    }
    STATUS      current
    DESCRIPTION
        "The group of objects in TIMETRA-BSX-NG-MIB which were obsoleted in
         Nokia SROS series systems for release 7.0."
    ::= { tmnxBsxObsoleteGroups 1 }

tmnxBsxObsoleteGroupV8v0         OBJECT-GROUP
    OBJECTS     {
        tmnxBsxAdminOwner,
        tmnxBsxAdminControlApply,
        tmnxBsxAdminLastChangeTime,
        tmnxBsxAppFilterServerPort
    }
    STATUS      current
    DESCRIPTION
        "The group of objects in TIMETRA-BSX-NG-MIB which were obsoleted in
         Nokia SROS series systems for release 8.0."
    ::= { tmnxBsxObsoleteGroups 2 }

tmnxBsxObsoleteGroupsV9v0        OBJECT-GROUP
    OBJECTS     {
        tmnxBsxAqpStatsFlows,
        tmnxBsxAqpStatsConflicts,
        tmnxBsxAqpSubscriber,
        tmnxBsxAqpSubscriberOp,
        tmnxBsxAqpSapSubscrPortId,
        tmnxBsxAqpSapSubscrEncapValue,
        tmnxBsxAqpSapSubscrOp,
        tmnxBsxAqpSpokeSdpSubscr,
        tmnxBsxAqpSpokeSdpSubscrOp,
        tmnxBsxIsaAaGrpUnassignedTIpSubs
    }
    STATUS      current
    DESCRIPTION
        "The group of objects in TIMETRA-BSX-NG-MIB which were obsoleted in
         Nokia SROS series systems for release 9.0."
    ::= { tmnxBsxObsoleteGroups 3 }

tmnxBsxObsoleteGroupV10v0        OBJECT-GROUP
    OBJECTS     {
        tmnxBsxGrpMdaTransPrefEntries,
        tmnxBsxAppGrpAdminState
    }
    STATUS      current
    DESCRIPTION
        "The group of objects in TIMETRA-BSX-NG-MIB which were obsoleted in
         Nokia SROS series systems for release 10.0."
    ::= { tmnxBsxObsoleteGroups 4 }

tmnxBsxObsoleteGroupV12v0        OBJECT-GROUP
    OBJECTS     {
        tmnxBsxAqpAaSubCutThru,
        tmnxBsxAqpAaSubErrors,
        tmnxBsxAqpAaSubscriber,
        tmnxBsxAqpAaSubscriberOp,
        tmnxBsxAqpAaSubscriberType,
        tmnxBsxAqpAdminState,
        tmnxBsxAqpAppGroup,
        tmnxBsxAqpAppGroupOp,
        tmnxBsxAqpApplication,
        tmnxBsxAqpApplicationOp,
        tmnxBsxAqpBwLimitPolicer,
        tmnxBsxAqpChargeGrp,
        tmnxBsxAqpChargeGrpOp,
        tmnxBsxAqpDescription,
        tmnxBsxAqpDrop,
        tmnxBsxAqpDscp,
        tmnxBsxAqpDscpOp,
        tmnxBsxAqpDstAddress,
        tmnxBsxAqpDstAddressLength,
        tmnxBsxAqpDstAddressOp,
        tmnxBsxAqpDstAddressType,
        tmnxBsxAqpDstPortHighValue,
        tmnxBsxAqpDstPortLowValue,
        tmnxBsxAqpDstPortOp,
        tmnxBsxAqpFlowCountPolicer,
        tmnxBsxAqpFlowRatePolicer,
        tmnxBsxAqpHttpEnrichName,
        tmnxBsxAqpHttpErrRedirName,
        tmnxBsxAqpHttpNotif,
        tmnxBsxAqpHttpRedirFlowType,
        tmnxBsxAqpHttpRedirName,
        tmnxBsxAqpIpProtocolNum,
        tmnxBsxAqpIpProtocolNumOp,
        tmnxBsxAqpLastChTime,
        tmnxBsxAqpMirrorSource,
        tmnxBsxAqpMirrorSourceAllIncl,
        tmnxBsxAqpOutOfOrderFrags,
        tmnxBsxAqpRemarkDscpInProfile,
        tmnxBsxAqpRemarkDscpOutProfile,
        tmnxBsxAqpRemarkFc,
        tmnxBsxAqpRemarkPriority,
        tmnxBsxAqpRowLastChange,
        tmnxBsxAqpRowStatus,
        tmnxBsxAqpSessionFilter,
        tmnxBsxAqpSrcAddress,
        tmnxBsxAqpSrcAddressLength,
        tmnxBsxAqpSrcAddressOp,
        tmnxBsxAqpSrcAddressType,
        tmnxBsxAqpSrcPortHighValue,
        tmnxBsxAqpSrcPortLowValue,
        tmnxBsxAqpSrcPortOp,
        tmnxBsxAqpTrafficDir,
        tmnxBsxAqpUrlFilter,
        tmnxBsxAqpLastChTime
    }
    STATUS      current
    DESCRIPTION
        "The group of objects in TIMETRA-BSX-NG-MIB which were obsoleted in
         Nokia SROS series systems for release 12.0."
    ::= { tmnxBsxObsoleteGroups 5 }

tmnxBsxObsoleteGroupV13v0        OBJECT-GROUP
    OBJECTS     {
        tmnxBsxStatAaAcctCfgAggrStats,
        tmnxBsxAaSubPolResExStatus
    }
    STATUS      current
    DESCRIPTION
        "The group of objects in TIMETRA-BSX-NG-MIB which were obsoleted in
         Nokia SROS series systems for release 13.0."
    ::= { tmnxBsxObsoleteGroups 6 }

tmnxBsxPolicyGroups              OBJECT IDENTIFIER ::= { tmnxBsxGroups 8 }

tmnxBsxPolicyGroupV8v0           OBJECT-GROUP
    OBJECTS     {
        tmnxBsxProtDescription,
        tmnxBsxProtParentName,
        tmnxBsxProtAdminState,
        tmnxBsxAppGrpRowStatus,
        tmnxBsxAppGrpStorageType,
        tmnxBsxAppGrpDescription,
        tmnxBsxAppGrpAdminState,
        tmnxBsxAppRowStatus,
        tmnxBsxAppStorageType,
        tmnxBsxAppDescription,
        tmnxBsxAppAppGroup,
        tmnxBsxAppFilterRowStatus,
        tmnxBsxAppFilterDescription,
        tmnxBsxAppFilterAdminState,
        tmnxBsxAppFilterProtocol,
        tmnxBsxAppFilterProtocolOp,
        tmnxBsxAppFilterFlowSetupDir,
        tmnxBsxAppFilterIpProtocolNum,
        tmnxBsxAppFilterIpProtocolNumOp,
        tmnxBsxAppFilterServerAddrType,
        tmnxBsxAppFilterServerAddr,
        tmnxBsxAppFilterServerAddrLen,
        tmnxBsxAppFilterServerAddrOp,
        tmnxBsxAppFilterServerPortOp,
        tmnxBsxAppFilterServerPortFpp,
        tmnxBsxAppFilterServerPortLow,
        tmnxBsxAppFilterServerPortHigh,
        tmnxBsxAppFilterApplication,
        tmnxBsxAppFilterExprRowStatus,
        tmnxBsxAppFilterExprType,
        tmnxBsxAppFilterExprOperator,
        tmnxBsxAppFilterExprStr,
        tmnxBsxAsoRowStatus,
        tmnxBsxAsoDefValName,
        tmnxBsxAsoValRowStatus,
        tmnxBsxAppProfRowStatus,
        tmnxBsxAppProfDescription,
        tmnxBsxAppProfDivert,
        tmnxBsxAppProfCapacityCost,
        tmnxBsxAppProfCharRowStatus,
        tmnxBsxAppProfCharValName,
        tmnxBsxPolicerRowStatus,
        tmnxBsxPolicerDescription,
        tmnxBsxPolicerType,
        tmnxBsxPolicerGranularity,
        tmnxBsxPolicerAction,
        tmnxBsxPolicerAdminPIR,
        tmnxBsxPolicerAdminCIR,
        tmnxBsxPolicerCBS,
        tmnxBsxPolicerMBS,
        tmnxBsxPolicerCIRAdaptation,
        tmnxBsxPolicerPIRAdaptation,
        tmnxBsxAqpRowStatus,
        tmnxBsxAqpDescription,
        tmnxBsxAqpAdminState,
        tmnxBsxAqpApplication,
        tmnxBsxAqpApplicationOp,
        tmnxBsxAqpAppGroup,
        tmnxBsxAqpAppGroupOp,
        tmnxBsxAqpTrafficDir,
        tmnxBsxAqpSubscriber,
        tmnxBsxAqpSubscriberOp,
        tmnxBsxAqpDscp,
        tmnxBsxAqpDscpOp,
        tmnxBsxAqpDrop,
        tmnxBsxAqpBwLimitPolicer,
        tmnxBsxAqpFlowRatePolicer,
        tmnxBsxAqpFlowCountPolicer,
        tmnxBsxUpgrade,
        tmnxBsxVersion,
        tmnxBsxAqpStatsFlows,
        tmnxBsxFlowFullHighWatermark,
        tmnxBsxFlowFullLowWatermark,
        tmnxBsxAqpCharRowStatus,
        tmnxBsxAqpCharOperator,
        tmnxBsxAqpStatsConflicts,
        tmnxBsxAqpSapSubscrPortId,
        tmnxBsxAqpSapSubscrEncapValue,
        tmnxBsxAqpSapSubscrOp,
        tmnxBsxAqpSrcAddressType,
        tmnxBsxAqpSrcAddress,
        tmnxBsxAqpSrcAddressLength,
        tmnxBsxAqpSrcAddressOp,
        tmnxBsxAqpSrcPortOp,
        tmnxBsxAqpSrcPortLowValue,
        tmnxBsxAqpSrcPortHighValue,
        tmnxBsxAqpDstAddressType,
        tmnxBsxAqpDstAddress,
        tmnxBsxAqpDstAddressLength,
        tmnxBsxAqpDstAddressOp,
        tmnxBsxAqpDstPortOp,
        tmnxBsxAqpDstPortLowValue,
        tmnxBsxAqpDstPortHighValue,
        tmnxBsxAqpSpokeSdpSubscr,
        tmnxBsxAqpSpokeSdpSubscrOp,
        tmnxBsxAqpRemarkFc,
        tmnxBsxAqpRemarkPriority,
        tmnxBsxAqpRemarkDscpInProfile,
        tmnxBsxAqpRemarkDscpOutProfile,
        tmnxBsxAqpMirrorSource,
        tmnxBsxAqpMirrorSourceAllIncl,
        tmnxBsxAdminCtrlLastChTime,
        tmnxBsxAdminCtrlConfigOwner,
        tmnxBsxAdminCtrlApply,
        tmnxBsxCustProtRowStatus,
        tmnxBsxCustProtRowLastChange,
        tmnxBsxCustProtIpProtocolNum,
        tmnxBsxCustProtDescription,
        tmnxBsxCustProtAdminState,
        tmnxBsxCustProtExprRowStatus,
        tmnxBsxCustProtExprRowLastChange,
        tmnxBsxCustProtExprOffset,
        tmnxBsxCustProtExprDirection,
        tmnxBsxCustProtExprOperator,
        tmnxBsxCustProtExprStr,
        tmnxBsxAaSubAsoValName,
        tmnxBsxAaSubAsoValDerivedFrom,
        tmnxBsxAaSubPolicerAqpEntryId,
        tmnxBsxAaSubPolicerName,
        tmnxBsxAaSubPolResExStatus
    }
    STATUS      obsolete
    DESCRIPTION
        "The group of objects supporting management of BSX Policy capabilities
         on Nokia SROS series systems for release 8.0."
    ::= { tmnxBsxPolicyGroups 1 }

tmnxBsxPolicyGroupV9v0           OBJECT-GROUP
    OBJECTS     {
        tmnxBsxProtDescription,
        tmnxBsxProtParentName,
        tmnxBsxProtAdminState,
        tmnxBsxAppGrpRowStatus,
        tmnxBsxAppGrpStorageType,
        tmnxBsxAppGrpDescription,
        tmnxBsxAppGrpAdminState,
        tmnxBsxAppRowStatus,
        tmnxBsxAppStorageType,
        tmnxBsxAppDescription,
        tmnxBsxAppAppGroup,
        tmnxBsxAppFilterRowStatus,
        tmnxBsxAppFilterDescription,
        tmnxBsxAppFilterAdminState,
        tmnxBsxAppFilterProtocol,
        tmnxBsxAppFilterProtocolOp,
        tmnxBsxAppFilterFlowSetupDir,
        tmnxBsxAppFilterIpProtocolNum,
        tmnxBsxAppFilterIpProtocolNumOp,
        tmnxBsxAppFilterServerAddrType,
        tmnxBsxAppFilterServerAddr,
        tmnxBsxAppFilterServerAddrLen,
        tmnxBsxAppFilterServerAddrOp,
        tmnxBsxAppFilterServerPortOp,
        tmnxBsxAppFilterServerPortFpp,
        tmnxBsxAppFilterServerPortLow,
        tmnxBsxAppFilterServerPortHigh,
        tmnxBsxAppFilterApplication,
        tmnxBsxAppFilterExprRowStatus,
        tmnxBsxAppFilterExprType,
        tmnxBsxAppFilterExprOperator,
        tmnxBsxAppFilterExprStr,
        tmnxBsxAsoRowStatus,
        tmnxBsxAsoDefValName,
        tmnxBsxAsoValRowStatus,
        tmnxBsxAppProfRowStatus,
        tmnxBsxAppProfDescription,
        tmnxBsxAppProfDivert,
        tmnxBsxAppProfCapacityCost,
        tmnxBsxAppProfCharRowStatus,
        tmnxBsxAppProfCharValName,
        tmnxBsxPolicerRowStatus,
        tmnxBsxPolicerDescription,
        tmnxBsxPolicerType,
        tmnxBsxPolicerGranularity,
        tmnxBsxPolicerAction,
        tmnxBsxPolicerAdminPIR,
        tmnxBsxPolicerAdminCIR,
        tmnxBsxPolicerCBS,
        tmnxBsxPolicerMBS,
        tmnxBsxPolicerCIRAdaptation,
        tmnxBsxPolicerPIRAdaptation,
        tmnxBsxAqpRowStatus,
        tmnxBsxAqpDescription,
        tmnxBsxAqpAdminState,
        tmnxBsxAqpApplication,
        tmnxBsxAqpApplicationOp,
        tmnxBsxAqpAppGroup,
        tmnxBsxAqpAppGroupOp,
        tmnxBsxAqpTrafficDir,
        tmnxBsxAqpDscp,
        tmnxBsxAqpDscpOp,
        tmnxBsxAqpDrop,
        tmnxBsxAqpBwLimitPolicer,
        tmnxBsxAqpFlowRatePolicer,
        tmnxBsxAqpFlowCountPolicer,
        tmnxBsxUpgrade,
        tmnxBsxVersion,
        tmnxBsxFlowFullHighWatermark,
        tmnxBsxFlowFullLowWatermark,
        tmnxBsxAqpCharRowStatus,
        tmnxBsxAqpCharOperator,
        tmnxBsxAqpSrcAddressType,
        tmnxBsxAqpSrcAddress,
        tmnxBsxAqpSrcAddressLength,
        tmnxBsxAqpSrcAddressOp,
        tmnxBsxAqpSrcPortOp,
        tmnxBsxAqpSrcPortLowValue,
        tmnxBsxAqpSrcPortHighValue,
        tmnxBsxAqpDstAddressType,
        tmnxBsxAqpDstAddress,
        tmnxBsxAqpDstAddressLength,
        tmnxBsxAqpDstAddressOp,
        tmnxBsxAqpDstPortOp,
        tmnxBsxAqpDstPortLowValue,
        tmnxBsxAqpDstPortHighValue,
        tmnxBsxAqpRemarkFc,
        tmnxBsxAqpRemarkPriority,
        tmnxBsxAqpRemarkDscpInProfile,
        tmnxBsxAqpRemarkDscpOutProfile,
        tmnxBsxAqpMirrorSource,
        tmnxBsxAqpMirrorSourceAllIncl,
        tmnxBsxAdminCtrlLastChTime,
        tmnxBsxAdminCtrlConfigOwner,
        tmnxBsxAdminCtrlApply,
        tmnxBsxCustProtRowStatus,
        tmnxBsxCustProtRowLastChange,
        tmnxBsxCustProtIpProtocolNum,
        tmnxBsxCustProtDescription,
        tmnxBsxCustProtAdminState,
        tmnxBsxCustProtExprRowStatus,
        tmnxBsxCustProtExprRowLastChange,
        tmnxBsxCustProtExprOffset,
        tmnxBsxCustProtExprDirection,
        tmnxBsxCustProtExprOperator,
        tmnxBsxCustProtExprStr,
        tmnxBsxAaSubAsoValName,
        tmnxBsxAaSubAsoValDerivedFrom,
        tmnxBsxAaSubPolicerAqpEntryId,
        tmnxBsxAaSubPolicerName,
        tmnxBsxAaSubPolResExStatus,
        tmnxBsxAqpAaSubscriberType,
        tmnxBsxAqpAaSubscriber,
        tmnxBsxAqpAaSubscriberOp,
        tmnxBsxFlowSetupHighWatermark,
        tmnxBsxFlowSetupLowWatermark,
        tmnxBsxPacketRateHighWatermark,
        tmnxBsxPacketRateLowWatermark,
        tmnxBsxBitRateHighWatermark,
        tmnxBsxBitRateLowWatermark,
        tmnxBsxAqpStatsHCFlows,
        tmnxBsxAqpStatsFlowsLo,
        tmnxBsxAqpStatsFlowsHi,
        tmnxBsxAqpStatsHCConflicts,
        tmnxBsxAqpStatsConflictsLo,
        tmnxBsxAqpStatsConflictsHi,
        tmnxBsxAqpHttpErrRedirName
    }
    STATUS      obsolete
    DESCRIPTION
        "The group of objects supporting management of BSX Policy capabilities
         on Nokia SROS series systems for release 9.0."
    ::= { tmnxBsxPolicyGroups 2 }

tmnxBsxPolicyGroupV10v0          OBJECT-GROUP
    OBJECTS     {
        tmnxBsxProtDescription,
        tmnxBsxProtParentName,
        tmnxBsxProtAdminState,
        tmnxBsxProtObsolete,
        tmnxBsxAppGrpRowStatus,
        tmnxBsxAppGrpStorageType,
        tmnxBsxAppGrpDescription,
        tmnxBsxAppRowStatus,
        tmnxBsxAppStorageType,
        tmnxBsxAppDescription,
        tmnxBsxAppAppGroup,
        tmnxBsxAppFilterRowStatus,
        tmnxBsxAppFilterDescription,
        tmnxBsxAppFilterAdminState,
        tmnxBsxAppFilterProtocol,
        tmnxBsxAppFilterProtocolOp,
        tmnxBsxAppFilterFlowSetupDir,
        tmnxBsxAppFilterIpProtocolNum,
        tmnxBsxAppFilterIpProtocolNumOp,
        tmnxBsxAppFilterServerAddrType,
        tmnxBsxAppFilterServerAddr,
        tmnxBsxAppFilterServerAddrLen,
        tmnxBsxAppFilterServerAddrOp,
        tmnxBsxAppFilterServerPortOp,
        tmnxBsxAppFilterServerPortFpp,
        tmnxBsxAppFilterServerPortLow,
        tmnxBsxAppFilterServerPortHigh,
        tmnxBsxAppFilterApplication,
        tmnxBsxAppFilterExprRowStatus,
        tmnxBsxAppFilterExprType,
        tmnxBsxAppFilterExprOperator,
        tmnxBsxAppFilterExprStr,
        tmnxBsxAsoRowStatus,
        tmnxBsxAsoDefValName,
        tmnxBsxAsoValRowStatus,
        tmnxBsxAppProfRowStatus,
        tmnxBsxAppProfDescription,
        tmnxBsxAppProfDivert,
        tmnxBsxAppProfCapacityCost,
        tmnxBsxAppProfCharRowStatus,
        tmnxBsxAppProfCharValName,
        tmnxBsxPolicerRowStatus,
        tmnxBsxPolicerDescription,
        tmnxBsxPolicerType,
        tmnxBsxPolicerGranularity,
        tmnxBsxPolicerAction,
        tmnxBsxPolicerAdminPIR,
        tmnxBsxPolicerAdminCIR,
        tmnxBsxPolicerCBS,
        tmnxBsxPolicerMBS,
        tmnxBsxPolicerCIRAdaptation,
        tmnxBsxPolicerPIRAdaptation,
        tmnxBsxAqpRowStatus,
        tmnxBsxAqpDescription,
        tmnxBsxAqpAdminState,
        tmnxBsxAqpApplication,
        tmnxBsxAqpApplicationOp,
        tmnxBsxAqpAppGroup,
        tmnxBsxAqpAppGroupOp,
        tmnxBsxAqpTrafficDir,
        tmnxBsxAqpDscp,
        tmnxBsxAqpDscpOp,
        tmnxBsxAqpDrop,
        tmnxBsxAqpBwLimitPolicer,
        tmnxBsxAqpFlowRatePolicer,
        tmnxBsxAqpFlowCountPolicer,
        tmnxBsxUpgrade,
        tmnxBsxVersion,
        tmnxBsxFlowFullHighWatermark,
        tmnxBsxFlowFullLowWatermark,
        tmnxBsxAqpCharRowStatus,
        tmnxBsxAqpCharOperator,
        tmnxBsxAqpSrcAddressType,
        tmnxBsxAqpSrcAddress,
        tmnxBsxAqpSrcAddressLength,
        tmnxBsxAqpSrcAddressOp,
        tmnxBsxAqpSrcPortOp,
        tmnxBsxAqpSrcPortLowValue,
        tmnxBsxAqpSrcPortHighValue,
        tmnxBsxAqpDstAddressType,
        tmnxBsxAqpDstAddress,
        tmnxBsxAqpDstAddressLength,
        tmnxBsxAqpDstAddressOp,
        tmnxBsxAqpDstPortOp,
        tmnxBsxAqpDstPortLowValue,
        tmnxBsxAqpDstPortHighValue,
        tmnxBsxAqpRemarkFc,
        tmnxBsxAqpRemarkPriority,
        tmnxBsxAqpRemarkDscpInProfile,
        tmnxBsxAqpRemarkDscpOutProfile,
        tmnxBsxAqpMirrorSource,
        tmnxBsxAqpMirrorSourceAllIncl,
        tmnxBsxAdminCtrlLastChTime,
        tmnxBsxAdminCtrlConfigOwner,
        tmnxBsxAdminCtrlApply,
        tmnxBsxCustProtRowStatus,
        tmnxBsxCustProtRowLastChange,
        tmnxBsxCustProtIpProtocolNum,
        tmnxBsxCustProtDescription,
        tmnxBsxCustProtAdminState,
        tmnxBsxCustProtExprRowStatus,
        tmnxBsxCustProtExprRowLastChange,
        tmnxBsxCustProtExprOffset,
        tmnxBsxCustProtExprDirection,
        tmnxBsxCustProtExprOperator,
        tmnxBsxCustProtExprStr,
        tmnxBsxAaSubAsoValName,
        tmnxBsxAaSubAsoValDerivedFrom,
        tmnxBsxAaSubPolicerAqpEntryId,
        tmnxBsxAaSubPolicerName,
        tmnxBsxAaSubPolResExStatus,
        tmnxBsxAqpAaSubscriberType,
        tmnxBsxAqpAaSubscriber,
        tmnxBsxAqpAaSubscriberOp,
        tmnxBsxFlowSetupHighWatermark,
        tmnxBsxFlowSetupLowWatermark,
        tmnxBsxPacketRateHighWatermark,
        tmnxBsxPacketRateLowWatermark,
        tmnxBsxBitRateHighWatermark,
        tmnxBsxBitRateLowWatermark,
        tmnxBsxAqpStatsHCFlows,
        tmnxBsxAqpStatsFlowsLo,
        tmnxBsxAqpStatsFlowsHi,
        tmnxBsxAqpStatsHCConflicts,
        tmnxBsxAqpStatsConflictsLo,
        tmnxBsxAqpStatsConflictsHi,
        tmnxBsxAqpHttpErrRedirName
    }
    STATUS      obsolete
    DESCRIPTION
        "The group of objects supporting management of BSX Policy capabilities
         on Nokia SROS series systems for release 10.0."
    ::= { tmnxBsxPolicyGroups 3 }

tmnxBsxPolicyTodObjGrp           OBJECT-GROUP
    OBJECTS     {
        tmnxBsxPolicerLastChTime,
        tmnxBsxPolicerOvrdAdminCIR,
        tmnxBsxPolicerOvrdAdminPIR,
        tmnxBsxPolicerOvrdAdminState,
        tmnxBsxPolicerOvrdCBS,
        tmnxBsxPolicerOvrdDayList,
        tmnxBsxPolicerOvrdDescription,
        tmnxBsxPolicerOvrdEndDay,
        tmnxBsxPolicerOvrdEndHour,
        tmnxBsxPolicerOvrdEndMinute,
        tmnxBsxPolicerOvrdLastChTime,
        tmnxBsxPolicerOvrdMBS,
        tmnxBsxPolicerOvrdRowLastChange,
        tmnxBsxPolicerOvrdRowStatus,
        tmnxBsxPolicerOvrdStartDay,
        tmnxBsxPolicerOvrdStartHour,
        tmnxBsxPolicerOvrdStartMinute,
        tmnxBsxPolicerRowLastChange,
        tmnxBsxPolicerOperTodOverride
    }
    STATUS      current
    DESCRIPTION
        "The group of objects supporting management of BSX Policy Time of Day
         Policer Override capabilities on Nokia SROS series systems for release
         11.0."
    ::= { tmnxBsxPolicyGroups 4 }

tmnxBsxPolicyAqpExtObjGrp        OBJECT-GROUP
    OBJECTS     {
        tmnxBsxAqpChargeGrp,
        tmnxBsxAqpChargeGrpOp,
        tmnxBsxAqpIpProtocolNum,
        tmnxBsxAqpIpProtocolNumOp,
        tmnxBsxAqpRowLastChange,
        tmnxBsxAqpLastChTime
    }
    STATUS      obsolete
    DESCRIPTION
        "The group of additional objects supporting management of BSX QOS
         Policy capabilities on Nokia SROS series systems for release 11.0."
    ::= { tmnxBsxPolicyGroups 5 }

tmnxBsxPolicyTimeStampExtObjGrp  OBJECT-GROUP
    OBJECTS     {
        tmnxBsxAppFilterExprLastChTime,
        tmnxBsxAppFilterExprRowLastCh,
        tmnxBsxAppFilterLastChTime,
        tmnxBsxAppFilterRowLastChange,
        tmnxBsxAppProfCharLastChTime,
        tmnxBsxAppProfCharRowLastChange,
        tmnxBsxAppProfLastChTime,
        tmnxBsxAppProfRowLastChange,
        tmnxBsxAqpCharLastChTime,
        tmnxBsxAqpCharRowLastChange,
        tmnxBsxAsoLastChTime,
        tmnxBsxAsoRowLastChange,
        tmnxBsxAsoValLastChTime,
        tmnxBsxAsoValRowLastChange,
        tmnxBsxCustProtExprLastChTime,
        tmnxBsxCustProtLastChTime,
        tmnxBsxProtLastChTime,
        tmnxBsxProtRowLastChange,
        tmnxBsxStatAaAcctCfgRowLastCh
    }
    STATUS      current
    DESCRIPTION
        "The group of additional objects supporting management of BSX Policy
         capabilities on Nokia SROS series systems for release 11.0."
    ::= { tmnxBsxPolicyGroups 6 }

tmnxBsxNotificationGroups        OBJECT IDENTIFIER ::= { tmnxBsxGroups 10 }

tmnxBsxNotificationGroupV8v0     NOTIFICATION-GROUP
    NOTIFICATIONS {
        tmnxBsxIsaAaGrpCapCostThres,
        tmnxBsxIsaAaGrpCapCostThresClear,
        tmnxBsxAaSubscribersUnassigned,
        tmnxBsxAaSubPolResExceeded,
        tmnxBsxAaSubPolResExceededClear
    }
    STATUS      current
    DESCRIPTION
        "The group of notifications supporting BSX capabilities on Nokia SROS
         series systems for release 8.0"
    ::= { tmnxBsxNotificationGroups 1 }

tmnxBsxNotificationGroupV7v0     NOTIFICATION-GROUP
    NOTIFICATIONS {
        tmnxBsxAaSubscriberAcctDataLoss
    }
    STATUS      current
    DESCRIPTION
        "The group of notifications supporting BSX capabilities on Nokia SROS
         series systems for release 7.0"
    ::= { tmnxBsxNotificationGroups 2 }

tmnxBsxNotificationGroupV9v0     NOTIFICATION-GROUP
    NOTIFICATIONS {
        tmnxBsxIsaAaGrpBitRate,
        tmnxBsxIsaAaGrpBitRateClear,
        tmnxBsxIsaAaGrpFlowSetup,
        tmnxBsxIsaAaGrpFlowSetupClear,
        tmnxBsxIsaAaGrpPacketRate,
        tmnxBsxIsaAaGrpPacketRateClear,
        tmnxBsxTransIpPolAaSubCreated,
        tmnxBsxTransIpPolAaSubDeleted,
        tmnxBsxTransIpPolRadCoAAudit,
        tmnxBsxTransIpPolRadCoAError,
        tmnxBsxTransIpPolRadDiscError,
        tmnxBsxTransIpPolDhcpAddWarning,
        tmnxBsxTransIpPolDhcpDelWarning,
        tmnxBsxIsaAaGrpFmSbWaSBufOvld,
        tmnxBsxIsaAaGrpFmSbWaSBufOvldClr,
        tmnxBsxIsaAaGrpToSbWaSBufOvld,
        tmnxBsxIsaAaGrpToSbWaSBufOvldClr,
        tmnxBsxIsaAaGrpOvrldCutthru,
        tmnxBsxIsaAaGrpOvrldCutthruClr,
        tmnxBsxTransitIpPersistenceWarn
    }
    STATUS      current
    DESCRIPTION
        "The group of notifications supporting BSX capabilities on Nokia SROS
         series systems for release 9.0"
    ::= { tmnxBsxNotificationGroups 3 }

tmnxBsxNotificationGroupV10v0    NOTIFICATION-GROUP
    NOTIFICATIONS {
        tmnxBsxAarpInstOperStateChanged,
        tmnxBsxAarpInstStateChanged
    }
    STATUS      current
    DESCRIPTION
        "The group of notifications supporting BSX capabilities on Nokia SROS
         series systems for release 10.0"
    ::= { tmnxBsxNotificationGroups 4 }

tmnxBsxRadApNotificationGroup    NOTIFICATION-GROUP
    NOTIFICATIONS {
        tmnxBsxRadApFailure,
        tmnxBsxRadApServOperStateChange
    }
    STATUS      current
    DESCRIPTION
        "The group of additional notifications supporting Application Assurance
         RADIUS Accounting Policy capabilities on Nokia SROS series systems for
         release 10.0."
    ::= { tmnxBsxNotificationGroups 5 }

tmnxBsxNotificationGroupV11v0    NOTIFICATION-GROUP
    NOTIFICATIONS {
        tmnxBsxMobileSubModifyFailure,
        tmnxBsxRadApIntrmUpdateSkipped,
        tmnxBsxHttpUrlParamLimitExceeded,
        tmnxBsxUrlFilterOperStateChange
    }
    STATUS      current
    DESCRIPTION
        "The group of notifications extending BSX capabilities on Nokia SROS
         series systems for release 11.0"
    ::= { tmnxBsxNotificationGroups 6 }

tmnxBsxNotificationGroupV12v0    NOTIFICATION-GROUP
    NOTIFICATIONS {
        tmnxBsxSubModifyFailure
    }
    STATUS      current
    DESCRIPTION
        "The group of notifications extending BSX capabilities on Nokia SROS
         series systems for release 12.0"
    ::= { tmnxBsxNotificationGroups 7 }

tmnxBsxNotificationGroupV13v0    NOTIFICATION-GROUP
    NOTIFICATIONS {
        tmnxBsxDnsIpCacheFull,
        tmnxBsxDnsIpCacheFullClear,
        tmnxBsxUrlListUpdate,
        tmnxBsxUrlListFailure,
        tmnxBsxIsaAaTimFileProcFailure
    }
    STATUS      current
    DESCRIPTION
        "The group of notifications extending BSX capabilities on Nokia SROS
         series systems for release 13.0"
    ::= { tmnxBsxNotificationGroups 8 }

tmnxBsxNotificationGroupV14v0    NOTIFICATION-GROUP
    NOTIFICATIONS {
        tmnxBsxStatTcaThreshCrossed,
        tmnxBsxStatTcaThreshCrossedClear,
        tmnxBsxStatPolcrTcaThreshCrossed,
        tmnxBsxStatPolcrTcaThreshCrClear,
        tmnxBsxStatFtrTcaThreshCrossed,
        tmnxBsxStatFtrTcaThreshCrClear,
        tmnxBsxStatFtrEnTcaThreshCrossed,
        tmnxBsxStatFtrEnTcaThreshCrClear,
        tmnxBsxTransIpPolDiamGxError,
        tmnxBsxDatapathCpuUsage,
        tmnxBsxDatapathCpuUsageClear,
        tmnxBsxTcpValTcaCrossed,
        tmnxBsxTcpValTcaCrossedClear
    }
    STATUS      current
    DESCRIPTION
        "The group of notifications introduced in SROS Release 14.0 for
         Application Assurance on Nokia systems."
    ::= { tmnxBsxNotificationGroups 9 }

tmnxBsxCflowdGroups              OBJECT IDENTIFIER ::= { tmnxBsxGroups 11 }

tmnxBsxCflowdGroup               OBJECT-GROUP
    OBJECTS     {
        tmnxBsxCflowdLastChangeTime,
        tmnxBsxCflowdCollLastChangeTime,
        tmnxBsxCflowdPerfLastChangeTime,
        tmnxBsxCflowdExpLastChangeTime,
        tmnxBsxCflowdPerfExpLastChTime,
        tmnxBsxCflowdRowLastChange,
        tmnxBsxCflowdVolRate,
        tmnxBsxCflowdTemplateRetransmit,
        tmnxBsxCflowdAdminState,
        tmnxBsxCflowdCollRowStatus,
        tmnxBsxCflowdCollRowLastChange,
        tmnxBsxCflowdCollDescription,
        tmnxBsxCflowdCollAdminState,
        tmnxBsxCflowdCollOperState,
        tmnxBsxCflowdCollVersion,
        tmnxBsxCflowdPerfRowLastChange,
        tmnxBsxCflowdPerfFlowRate,
        tmnxBsxCflowdExpRowLastChange,
        tmnxBsxCflowdExpAdminState,
        tmnxBsxCflowdPerfExpRowStatus,
        tmnxBsxCflowdPerfExpRowLastChnge,
        tmnxBsxCflowdStatusDiscontTime,
        tmnxBsxCflowdStatusRecReported,
        tmnxBsxCflowdStatusRecDropped,
        tmnxBsxCflowdStatusPktsSent,
        tmnxBsxCflowdStatusFlowsNoRes,
        tmnxBsxCflowdStatusActFlowsCurr,
        tmnxBsxCflowdStatusRecRateCurr,
        tmnxBsxCflowdStatusPktRateCurr,
        tmnxBsxCflowdStatusHCRecReported,
        tmnxBsxCflowdStatusHCRecDropped,
        tmnxBsxCflowdStatusHCPktsSent,
        tmnxBsxCflowdStatusHCFlowsNoRes,
        tmnxBsxCflowdCollStatDiscontTime,
        tmnxBsxCflowdCollStatRecSent,
        tmnxBsxCflowdCollStatHCRecSent,
        tmnxBsxCflowdExpStatDiscontTime,
        tmnxBsxCflowdExpStatRecReport,
        tmnxBsxCflowdExpStatHCRecReport,
        tmnxBsxCflowdExpStatRecDropped,
        tmnxBsxCflowdExpStatHCRecDropped,
        tmnxBsxCflowdExpStatFlowsNoRes,
        tmnxBsxCflowdExpStatHCFlowsNoRes
    }
    STATUS      current
    DESCRIPTION
        "The group of objects supporting management of BSX Cflowd capabilities
         on Nokia SROS series systems."
    ::= { tmnxBsxCflowdGroups 1 }

tmnxBsxCflowdGroupV9v0           OBJECT-GROUP
    OBJECTS     {
        tmnxBsxCflowdStatusHCUSupSSRCSt,
        tmnxBsxCflowdStatusUSupSSRCStLo,
        tmnxBsxCflowdStatusUSupSSRCStHi,
        tmnxBsxCflowdExpStatHCUSupSSRCSt,
        tmnxBsxCflowdExpStatUSupSSRCStLo,
        tmnxBsxCflowdExpStatUSupSSRCStHi
    }
    STATUS      obsolete
    DESCRIPTION
        "The group of additional objects introduced in release 9.0 to support
         management of BSX Cflowd on Nokia SROS series systems."
    ::= { tmnxBsxCflowdGroups 2 }

tmnxBsxCflowdGroupV10v0          OBJECT-GROUP
    OBJECTS     {
        tmnxBsxCflowdPerfFlowRate2,
        tmnxBsxCflowdPerfExpRateNum
    }
    STATUS      current
    DESCRIPTION
        "The group of additional objects introduced in release 10.0 to support
         management of BSX Cflowd on Nokia SROS series systems."
    ::= { tmnxBsxCflowdGroups 3 }

tmnxBsxCflowdDirectExportGroup   OBJECT-GROUP
    OBJECTS     {
        tmnxBsxCflowdDirectExpLastChTime,
        tmnxBsxCflowdDirExpAddrLastChTim,
        tmnxBsxCflowdDirectExportVlan,
        tmnxBsxCflowdDirectExpRowStatus,
        tmnxBsxCflowdDirectExpRowLastCh,
        tmnxBsxCflowdDirectExpDescrption,
        tmnxBsxCflowdDirectExpVersion,
        tmnxBsxCflowdDirExpAddrRowStatus,
        tmnxBsxCflowdDirExpAddrRowLastCh,
        tmnxBsxCflowdDirExpAddrAdmnState,
        tmnxBsxCflowdDirExpAddrOperState,
        tmnxBsxCflowdDirExpStatDscntTime,
        tmnxBsxCflowdDirExpStatRecSent
    }
    STATUS      current
    DESCRIPTION
        "The group of objects introduced in SROS Release 14.0 for Application
         Assurance support for Cflowd direct export on Nokia systems."
    ::= { tmnxBsxCflowdGroups 4 }

tmnxBsxOvrdGroups                OBJECT IDENTIFIER ::= { tmnxBsxGroups 12 }

tmnxBsxOvrdGroup                 OBJECT-GROUP
    OBJECTS     {
        tmnxBsxOvrdAaSubLastChTime,
        tmnxBsxOvrdAaSubCharLastChTm,
        tmnxBsxOvrdAaSubRowStatus,
        tmnxBsxOvrdAaSubRowLastCh,
        tmnxBsxOvrdAaSubCharRowStatus,
        tmnxBsxOvrdAaSubCharRowLastCh,
        tmnxBsxOvrdAaSubCharValName
    }
    STATUS      current
    DESCRIPTION
        "The group of objects supporting management of BSX Override
         capabilities on Nokia SROS series systems."
    ::= { tmnxBsxOvrdGroups 1 }

tmnxBsxNotifyObjsGroups          OBJECT IDENTIFIER ::= { tmnxBsxGroups 13 }

tmnxBsxNotifyObjsGroupV7v0       OBJECT-GROUP
    OBJECTS     {
        tmnxBsxNotifyAaSubscriberType,
        tmnxBsxNotifyAaSubscriberName,
        tmnxBsxNotifyAaSubAcctLossReason
    }
    STATUS      current
    DESCRIPTION
        "The group of objects supporting BSX Notification capabilities on Nokia
         SROS series systems for release 7.0"
    ::= { tmnxBsxNotifyObjsGroups 1 }

tmnxBsxNotifyObjsGroupV8v0       OBJECT-GROUP
    OBJECTS     {
        tmnxBsxNotifyAaGrpPartIndex
    }
    STATUS      current
    DESCRIPTION
        "The group of objects supporting BSX Notification capabilities on Nokia
         SROS series systems for release 8.0"
    ::= { tmnxBsxNotifyObjsGroups 2 }

tmnxBsxNotifyObjsGroupV9v0       OBJECT-GROUP
    OBJECTS     {
        tmnxBsxNotifyRadiusCoAAuditState,
        tmnxBsxNotifyReason,
        tmnxBsxNotifyTransitIpPolicyId
    }
    STATUS      current
    DESCRIPTION
        "The group of objects supporting BSX Notification capabilities on Nokia
         SROS series systems for release 9.0"
    ::= { tmnxBsxNotifyObjsGroups 3 }

tmnxBsxNotifyObjsGroupV13v0      OBJECT-GROUP
    OBJECTS     {
        tmnxBsxNotifySubFailedAction
    }
    STATUS      current
    DESCRIPTION
        "The group of objects supporting BSX Notification capabilities on Nokia
         SROS series systems for release 13.0"
    ::= { tmnxBsxNotifyObjsGroups 4 }

tmnxBsxNotifyObjsGroupV14v0      OBJECT-GROUP
    OBJECTS     {
        tmnxBsxNotifyTcaCfgType,
        tmnxBsxNotifyTcaCfgDirection,
        tmnxBsxNotifyTcaPolicerName,
        tmnxBsxNotifyTcaCfgFilterType,
        tmnxBsxNotifyTcaCfgFilterName,
        tmnxBsxNotifyTcaCfgFltrWmarkType,
        tmnxBsxNotifyTcaFtrEnCfgEntryId,
        tmnxBsxNotifyTcpValTcaName,
        tmnxBsxNotifyTcpValTcaWmarkType
    }
    STATUS      current
    DESCRIPTION
        "The group of notification objects introduced in SROS Release 14.0 for
         Application Assurance on Nokia systems."
    ::= { tmnxBsxNotifyObjsGroups 5 }

tmnxBsxTransitGroups             OBJECT IDENTIFIER ::= { tmnxBsxGroups 14 }

tmnxBsxTransitGroup              OBJECT-GROUP
    OBJECTS     {
        tmnxBsxTransitIpPolicyLastChTime,
        tmnxBsxTransIpPlcySubLastChTime,
        tmnxBsxTransIpPlcyAddrLastChTime,
        tmnxBsxTransitIpPolicyRowStatus,
        tmnxBsxTransitIpPolicyRowLastCh,
        tmnxBsxTransitIpPolicyDesc,
        tmnxBsxTransitIpPolicyDefAppProf,
        tmnxBsxTransitIpPolicySubIdPlcy,
        tmnxBsxTransitIpPolicyRadius,
        tmnxBsxTransitIpPolicyRadAuthPlc,
        tmnxBsxTransitIpPolicyDhcp,
        tmnxBsxTransIpPlcySubRowStatus,
        tmnxBsxTransIpPlcySubRowLastCh,
        tmnxBsxTransIpPlcySubAppProfNm,
        tmnxBsxTransIpPlcySubRefCount,
        tmnxBsxTransIpPlcyAddrRowStatus,
        tmnxBsxTransIpPlcyAddrRowLastCh,
        tmnxBsxTransIpPlcyAddrSubscriber,
        tmnxBsxTransitIpSumParentSubType,
        tmnxBsxTransitIpSumParentSub,
        tmnxBsxTransitIpSumAppProfNm,
        tmnxBsxTransitIpSumIpOriginMask,
        tmnxBsxTransitIpSumUpdateTime,
        tmnxBsxTransPrefPlcyLastChTime,
        tmnxBsxTransPrefSubLastChTime,
        tmnxBsxTransPrefEntryLastChTime,
        tmnxBsxTransPrefPolicyRowStatus,
        tmnxBsxTransPrefPolicyRowLastCh,
        tmnxBsxTransPrefPolicyDesc,
        tmnxBsxTransPrefSubRowStatus,
        tmnxBsxTransPrefSubRowLastCh,
        tmnxBsxTransPrefSubIsRemote,
        tmnxBsxTransPrefSubAppProfNm,
        tmnxBsxTransPrefSubRefCount,
        tmnxBsxTransPrefEntryRowStatus,
        tmnxBsxTransPrefEntryRowLastCh,
        tmnxBsxTransPrefEntrySubAddrType,
        tmnxBsxTransPrefEntrySubAddr,
        tmnxBsxTransPrefEntrySubAddrLen,
        tmnxBsxTransPrefEntryNetAddrType,
        tmnxBsxTransPrefEntryNetAddr,
        tmnxBsxTransPrefEntryNetAddrLen,
        tmnxBsxTransPrefEntrySubscriber,
        tmnxBsxTransPrefSumSubAddrType,
        tmnxBsxTransPrefSumSubAddr,
        tmnxBsxTransPrefSumSubAddrLen,
        tmnxBsxTransPrefSumNetAddrType,
        tmnxBsxTransPrefSumNetAddr,
        tmnxBsxTransPrefSumNetAddrLen,
        tmnxBsxTransPrefSumUpdateTime,
        tmnxBsxTransPrefSumParentSubType,
        tmnxBsxTransPrefSumParentSub,
        tmnxBsxTransPrefSumAppProfNm,
        tmnxBsxTransitIpPolicySubsCount,
        tmnxBsxTransitIpPolicyIPv4EntCnt,
        tmnxBsxTransPrefPolicySubsCount,
        tmnxBsxTransPrefPolicyEntCount,
        tmnxBsxTransPrefPolicyIPv4EntCnt
    }
    STATUS      current
    DESCRIPTION
        "The group of objects supporting management of BSX Transit subscribers
         on Nokia SROS series systems."
    ::= { tmnxBsxTransitGroups 1 }

tmnxBsxTransitGroupV10v0         OBJECT-GROUP
    OBJECTS     {
        tmnxBsxTransitIpPolicyIPv6PfxLen,
        tmnxBsxTransitIpPolicyIPv6EntCnt,
        tmnxBsxTransPrefPolicyIPv6EntCnt
    }
    STATUS      current
    DESCRIPTION
        "The group of additional objects introduced in release 10.0 to support
         management of BSX Transit subscribers on Nokia SROS series systems."
    ::= { tmnxBsxTransitGroups 2 }

tmnxBsxTransitSeenIpGroup        OBJECT-GROUP
    OBJECTS     {
        tmnxBsxTransitIpPolicySeenIp,
        tmnxBsxTransitIpPolicyAutoCreate,
        tmnxBsxTransitIpPolicySeenIpRad,
        tmnxBsxAarpInstPeerEPSapPortId,
        tmnxBsxAarpInstPeerEPSapEncap,
        tmnxBsxAarpInstPeerEPSapEncType,
        tmnxBsxAarpInstPeerEPSdpBindId,
        tmnxBsxTransitIpPolicyAutoInact
    }
    STATUS      current
    DESCRIPTION
        "The group of objects supporting management of AA initiating Transit
         subscriber creation through the Seen IP feature on Nokia SROS series
         systems."
    ::= { tmnxBsxTransitGroups 3 }

tmnxBsxStatsGroups               OBJECT IDENTIFIER ::= { tmnxBsxGroups 15 }

tmnxBsxStatsGroupV9v0            OBJECT-GROUP
    OBJECTS     {
        tmnxBsxStatAaAppFilterHCFlows,
        tmnxBsxStatAaAppFilterFlowsLo,
        tmnxBsxStatAaAppFilterFlowsHi,
        tmnxBsxStatAaAppFilterFlowHCOctC,
        tmnxBsxStatAaAppFilterFlowOctCLo,
        tmnxBsxStatAaAppFilterFlowOctCHi,
        tmnxBsxStatAaAcctCfgAdminState,
        tmnxBsxStatAaAcctCfgMaxThruStats,
        tmnxBsxStatIsaAaCfgLastChTime,
        tmnxBsxStatIsaAaCfgCollStats,
        tmnxBsxStatIsaAaCfgPolicy
    }
    STATUS      current
    DESCRIPTION
        "The group of additional objects introduced in release 9.0 to support
         management of BSX Stats on Nokia SROS series systems."
    ::= { tmnxBsxStatsGroups 1 }

tmnxBsxMobileGatewayGroups       OBJECT IDENTIFIER ::= { tmnxBsxGroups 16 }

tmnxBsxMobileGatewayGroup        OBJECT-GROUP
    OBJECTS     {
        tmnxBsxAaWap1xLastChangeTime,
        tmnxBsxAaWap1xRowLastChange,
        tmnxBsxAaWap1xAdminState
    }
    STATUS      current
    DESCRIPTION
        "The group of additional objects introduced for Application Assurance
         support for Mobile Gateway on Nokia SROS systems."
    ::= { tmnxBsxMobileGatewayGroups 1 }

tmnxBsxMgBillingExclusionsGroup  OBJECT-GROUP
    OBJECTS     {
        tmnxBsxStatAaAcctCfgExTcpRetrans
    }
    STATUS      current
    DESCRIPTION
        "The group of additional objects introduced for Application Assurance
         support for Mobile Gateway content based billing exclusions on Nokia
         SROS systems."
    ::= { tmnxBsxMobileGatewayGroups 2 }

tmnxBsxMgTetherDetectGroup       OBJECT-GROUP
    OBJECTS     {
        tmnxBsxTetherLastChangeTime,
        tmnxBsxTetherRowLastChange,
        tmnxBsxTetherAdminState
    }
    STATUS      current
    DESCRIPTION
        "The group of additional objects introduced for Application Assurance
         support for Mobile Gateway tethering detection on Nokia SROS systems."
    ::= { tmnxBsxMobileGatewayGroups 3 }

tmnxBsxHttpRedirGroups           OBJECT IDENTIFIER ::= { tmnxBsxGroups 17 }

tmnxBsxHttpRedirErrGroup         OBJECT-GROUP
    OBJECTS     {
        tmnxBsxHttpRedirErrLastChTime,
        tmnxBsxHttpRedirErrCodeLastCh,
        tmnxBsxHttpRedirErrRowStatus,
        tmnxBsxHttpRedirErrRowLastCh,
        tmnxBsxHttpRedirErrEnabled,
        tmnxBsxHttpRedirErrDescription,
        tmnxBsxHttpRedirErrTemplateId,
        tmnxBsxHttpRedirErrHttpHost,
        tmnxBsxHttpRedirErrParticipantId,
        tmnxBsxHttpRedirErrCodeRowStatus,
        tmnxBsxHttpRedirErrCodeRowLastCh,
        tmnxBsxHttpRedirErrorCodeMsgSize,
        tmnxBsxHttpRdStatDiscontTime,
        tmnxBsxHttpRdStatHCRedir,
        tmnxBsxHttpRdStatRedirLo,
        tmnxBsxHttpRdStatRedirHi,
        tmnxBsxHttpRdStatHCSizeExceeded,
        tmnxBsxHttpRdStatSizeExceededLo,
        tmnxBsxHttpRdStatSizeExceededHi,
        tmnxBsxHttpRdStatHCOutOfResource,
        tmnxBsxHttpRdStatOutOfResourceLo,
        tmnxBsxHttpRdStatOutOfResourceHi,
        tmnxBsxHttpRdStatHCNotRedirFType,
        tmnxBsxHttpRdStatNotRedirFTypeLo,
        tmnxBsxHttpRdStatNotRedirFTypeHi,
        tmnxBsxHttpRdStatHCNotRedir,
        tmnxBsxHttpRdStatNotRedirLo,
        tmnxBsxHttpRdStatNotRedirHi
    }
    STATUS      current
    DESCRIPTION
        "The group of additional objects introduced for Application Assurance
         support for HTTP Error Redirect on Nokia SROS systems."
    ::= { tmnxBsxHttpRedirGroups 1 }

tmnxBsxHttpRedirGroup            OBJECT-GROUP
    OBJECTS     {
        tmnxBsxHttpRedirLastCh,
        tmnxBsxHttpRedirRowStatus,
        tmnxBsxHttpRedirRowLastCh,
        tmnxBsxHttpRedirEnabled,
        tmnxBsxHttpRedirDescription,
        tmnxBsxHttpRedirTemplateId,
        tmnxBsxHttpRedirHttpHost,
        tmnxBsxAqpHttpRedirName,
        tmnxBsxAqpHttpRedirFlowType,
        tmnxBsxHttpPcyRdStatDiscontTime,
        tmnxBsxHttpPcyRdStatHCRedir,
        tmnxBsxHttpPcyRdStatRedirLo,
        tmnxBsxHttpPcyRdStatRedirHi,
        tmnxBsxHttpPcyRdStatHCOutOfRes,
        tmnxBsxHttpPcyRdStatOutOfResLo,
        tmnxBsxHttpPcyRdStatOutOfResHi,
        tmnxBsxHttpPcyRdStatHCNotRedir,
        tmnxBsxHttpPcyRdStatNotRedirLo,
        tmnxBsxHttpPcyRdStatNotRedirHi
    }
    STATUS      current
    DESCRIPTION
        "The group of additional objects introduced in release 10.0 for the
         support of HTTP Redirect on Nokia SROS systems."
    ::= { tmnxBsxHttpRedirGroups 2 }

tmnxBsxStaticObjGroups           OBJECT IDENTIFIER ::= { tmnxBsxGroups 18 }

tmnxBsxStaticObjGroup            OBJECT-GROUP
    OBJECTS     {
        tmnxBsxTListTableLastUpdateT,
        tmnxBsxTListAttribTableLUpdateT,
        tmnxBsxTListRowLastUpdateT,
        tmnxBsxTListDescription,
        tmnxBsxTListAttribRowLastUpdateT,
        tmnxBsxTListAttribType,
        tmnxBsxTListAttribValue
    }
    STATUS      current
    DESCRIPTION
        "The group of additional objects introduced for Application Assurance
         support for static objects on Nokia SROS systems."
    ::= { tmnxBsxStaticObjGroups 1 }

tmnxBsxRedundancyObjGroups       OBJECT IDENTIFIER ::= { tmnxBsxGroups 19 }

tmnxBsxRedundancyObjGroup        OBJECT-GROUP
    OBJECTS     {
        tmnxBsxAarpTableLastChTime,
        tmnxBsxAarpInstRowStatus,
        tmnxBsxAarpInstLastCh,
        tmnxBsxAarpInstDescription,
        tmnxBsxAarpInstPeerIpType,
        tmnxBsxAarpInstPeerIpAddr,
        tmnxBsxAarpInstPriority,
        tmnxBsxAarpInstAdminState,
        tmnxBsxAarpInstOperState,
        tmnxBsxAarpInstState,
        tmnxBsxAarpInstOperFlags,
        tmnxBsxAarpInstPeerPriority,
        tmnxBsxAarpInstPeerState,
        tmnxBsxAarpInstPeerOperFlags,
        tmnxBsxAarpInstPeerSubRefType,
        tmnxBsxAarpCommandControl,
        tmnxBsxAarpServPoint,
        tmnxBsxAaSubAarpId
    }
    STATUS      current
    DESCRIPTION
        "The group of additional objects introduced for Application Assurance
         support for BSX Redundancy on Nokia SROS systems."
    ::= { tmnxBsxRedundancyObjGroups 1 }

tmnxBsxRedundancyEnhObjGroup     OBJECT-GROUP
    OBJECTS     {
        tmnxBsxAarpInstMasterSelectMode
    }
    STATUS      current
    DESCRIPTION
        "The group of additional objects introduced for Application Assurance
         support for BSX Redundancy Enhancements on Nokia SROS systems."
    ::= { tmnxBsxRedundancyObjGroups 2 }

tmnxBsxHttpEnrichObjGroups       OBJECT IDENTIFIER ::= { tmnxBsxGroups 20 }

tmnxBsxHttpEnrichObjGroup        OBJECT-GROUP
    OBJECTS     {
        tmnxBsxHttpEnrichLastChTime,
        tmnxBsxHttpEnrichFieldLastChTime,
        tmnxBsxHttpEnrichRowStatus,
        tmnxBsxHttpEnrichRowLastCh,
        tmnxBsxHttpEnrichEnabled,
        tmnxBsxHttpEnrichDescription,
        tmnxBsxHttpEnrichFieldRowStatus,
        tmnxBsxHttpEnrichFieldRowLastCh,
        tmnxBsxHttpEnrichFieldHeaderName,
        tmnxBsxAqpHttpEnrichName,
        tmnxBsxIsaAaGrpHttpEnrichMaxPkt
    }
    STATUS      current
    DESCRIPTION
        "The group of additional objects introduced for Application Assurance
         support for HTTP header enrichment on Nokia SROS systems."
    ::= { tmnxBsxHttpEnrichObjGroups 1 }

tmnxBsxHttpEnrichStatObjGroup    OBJECT-GROUP
    OBJECTS     {
        tmnxBsxHttpEnrichStatDiscontTime,
        tmnxBsxHttpEnrichHCNumEnriched,
        tmnxBsxHttpEnrichNumEnrichedLo,
        tmnxBsxHttpEnrichNumEnrichedHi,
        tmnxBsxHttpEnrichHCNumNoResource,
        tmnxBsxHttpEnrichNumNoResourceLo,
        tmnxBsxHttpEnrichNumNoResourceHi,
        tmnxBsxHttpEnrichHCMissngSubData,
        tmnxBsxHttpEnrichMissngSubDataLo,
        tmnxBsxHttpEnrichMissngSubDataHi,
        tmnxBsxHttpEnrichHCTplNotEnabled,
        tmnxBsxHttpEnrichTplNotEnabledLo,
        tmnxBsxHttpEnrichTplNotEnabledHi,
        tmnxBsxHttpEnrichHCTrafficChar,
        tmnxBsxHttpEnrichTrafficCharLo,
        tmnxBsxHttpEnrichTrafficCharHi,
        tmnxBsxHttpEnrichHCExceedMaxPkt,
        tmnxBsxHttpEnrichExceedMaxPktLo,
        tmnxBsxHttpEnrichExceedMaxPktHi
    }
    STATUS      current
    DESCRIPTION
        "The group of additional objects introduced for Application Assurance
         support for HTTP header enrichment statistics on Nokia SROS systems."
    ::= { tmnxBsxHttpEnrichObjGroups 2 }

tmnxBsxRadiusAccountingGroups    OBJECT IDENTIFIER ::= { tmnxBsxGroups 21 }

tmnxBsxRadiusAccountingObjGroup  OBJECT-GROUP
    OBJECTS     {
        tmnxBsxAppChargeGrp,
        tmnxBsxAppGrpChargeGrp,
        tmnxBsxChargeGrpRowStatus,
        tmnxBsxChargeGrpDescription,
        tmnxBsxChargeGrpExportId,
        tmnxBsxChargeGrpLastChTime,
        tmnxBsxChargeGrpRowLastCh,
        tmnxBsxPlcyCfgLastChTime,
        tmnxBsxPlcyDefChargeGrp,
        tmnxBsxPlcyRowLastCh,
        tmnxBsxStatAaAcctCfgRadiusPlcy,
        tmnxBsxStatAaSubCfgExportMethod
    }
    STATUS      current
    DESCRIPTION
        "The group of additional objects introduced in Release 10.0 for
         Application Assurance support for RADIUS Accounting on Nokia SROS
         systems."
    ::= { tmnxBsxRadiusAccountingGroups 1 }

tmnxBsxRadApObjGroup             OBJECT-GROUP
    OBJECTS     {
        tmnxBsxRadApLastChTime,
        tmnxBsxRadApServLastChTime,
        tmnxBsxRadApRowStatus,
        tmnxBsxRadApRowLastChange,
        tmnxBsxRadApDescription,
        tmnxBsxRadApServerRetry,
        tmnxBsxRadApServerTimeout,
        tmnxBsxRadApServerVRtrID,
        tmnxBsxRadApServerSrcAddrType,
        tmnxBsxRadApServerSrcAddr,
        tmnxBsxRadApServerAlgorithm,
        tmnxBsxRadApIntrmUpdateInterval,
        tmnxBsxRadApSignfcntChangeDelta,
        tmnxBsxRadApServRowStatus,
        tmnxBsxRadApServRowLastChange,
        tmnxBsxRadApServAddrType,
        tmnxBsxRadApServAddr,
        tmnxBsxRadApServSecret,
        tmnxBsxRadApServAcctPort,
        tmnxBsxRadApServOperState
    }
    STATUS      current
    DESCRIPTION
        "The group of additional objects introduced in Release 10.0 for
         Application Assurance support for RADIUS Accounting Policy on Nokia
         SROS systems."
    ::= { tmnxBsxRadiusAccountingGroups 2 }

tmnxBsxRadApStatObjGroup         OBJECT-GROUP
    OBJECTS     {
        tmnxBsxRadApTxRequests,
        tmnxBsxRadApRxResponses,
        tmnxBsxRadApReqTimeouts,
        tmnxBsxRadApSendRetries,
        tmnxBsxRadApSendFail,
        tmnxBsxRadApServTxRequests,
        tmnxBsxRadApServRxResponses,
        tmnxBsxRadApServReqTimeouts,
        tmnxBsxRadApServReqSendFail
    }
    STATUS      current
    DESCRIPTION
        "The group of additional objects introduced in Release 10.0 for
         Application Assurance support for RADIUS Accounting Policy statistics
         on Nokia SROS systems."
    ::= { tmnxBsxRadiusAccountingGroups 3 }

tmnxBsxRadiusAcctObjGroupV11v0   OBJECT-GROUP
    OBJECTS     {
        tmnxBsxAppGrpRowLastCh,
        tmnxBsxAppGrpExportId,
        tmnxBsxAppGrpLastChTime,
        tmnxBsxAppRowLastCh,
        tmnxBsxAppExportId,
        tmnxBsxAppLastChTime
    }
    STATUS      current
    DESCRIPTION
        "The group of additional objects introduced in Release 11 for
         Application Assurance support for RADIUS Accounting on Nokia SROS
         systems."
    ::= { tmnxBsxRadiusAccountingGroups 4 }

tmnxBsxSessionFilterGroups       OBJECT IDENTIFIER ::= { tmnxBsxGroups 22 }

tmnxBsxSessionFilterObjGrp       OBJECT-GROUP
    OBJECTS     {
        tmnxBsxSessFltrDefaultAction,
        tmnxBsxSessFltrDescription,
        tmnxBsxSessFltrParamsLastChTime,
        tmnxBsxSessFltrLastChTime,
        tmnxBsxSessFltrParamsAction,
        tmnxBsxSessFltrParamsDescription,
        tmnxBsxSessFltrParamsIpProtocol,
        tmnxBsxSessFltrParamsRowLastCh,
        tmnxBsxSessFltrParamsRowStatus,
        tmnxBsxSessFltrRowLastChange,
        tmnxBsxSessFltrRowStatus,
        tmnxBsxSessFltrStatsFlows,
        tmnxBsxSessFltrStatsFlowsLo,
        tmnxBsxSessFltrStatsFlowsHi,
        tmnxBsxAqpSessionFilter,
        tmnxBsxAqpAaSubErrors,
        tmnxBsxAqpOutOfOrderFrags,
        tmnxBsxAqpAaSubCutThru,
        tmnxBsxSessFltrParamsSrcAddrType,
        tmnxBsxSessFltrParamsSrcAddress,
        tmnxBsxSessFltrParamsSrcAddrLen,
        tmnxBsxSessFltrParamsDstAddrType,
        tmnxBsxSessFltrParamsDstAddress,
        tmnxBsxSessFltrParamsDstAddrLen,
        tmnxBsxSessFltrParamsSrcPortLVal,
        tmnxBsxSessFltrParamsSrcPortHVal,
        tmnxBsxSessFltrParamsSrcPortOp,
        tmnxBsxSessFltrParamsDstPortLVal,
        tmnxBsxSessFltrParamsDstPortHVal,
        tmnxBsxSessFltrParamsDstPortOp
    }
    STATUS      current
    DESCRIPTION
        "The group of objects introduced in Release 11 for Application
         Assurance support for session filters on Nokia SROS systems."
    ::= { tmnxBsxSessionFilterGroups 1 }

tmnxBsxUrlFilterGroups           OBJECT IDENTIFIER ::= { tmnxBsxGroups 23 }

tmnxBsxUrlFilterObjGrp           OBJECT-GROUP
    OBJECTS     {
        tmnxBsxAqpUrlFilter,
        tmnxBsxUrlFilterLastChangeTime,
        tmnxBsxUrlFilterRowStatus,
        tmnxBsxUrlFilterRowLastChange,
        tmnxBsxUrlFilterAdminState,
        tmnxBsxUrlFilterDescription,
        tmnxBsxUrlFilterDefaultAction,
        tmnxBsxUrlFilterServicePortVlan,
        tmnxBsxUrlFilterHttpRedirName,
        tmnxBsxUrlFilterIcapHttpRedir,
        tmnxBsxIcapServerLastChangeTime,
        tmnxBsxIcapServerRowStatus,
        tmnxBsxIcapServerRowLastChange,
        tmnxBsxIcapServerDescription,
        tmnxBsxIcapServerAdminState,
        tmnxBsxWebServServerRowStatus,
        tmnxBsxWebServServerRowLastChg,
        tmnxBsxWebServServerDescription,
        tmnxBsxWebServServerAdminState
    }
    STATUS      current
    DESCRIPTION
        "The group of objects introduced in Release 11.0 for Application
         Assurance support for URL filters on Nokia SROS systems."
    ::= { tmnxBsxUrlFilterGroups 1 }

tmnxBsxUrlFilterStatsObjGrp      OBJECT-GROUP
    OBJECTS     {
        tmnxBsxIcapServerOperState,
        tmnxBsxIcapServerOperFlags,
        tmnxBsxIcapServerStatsRequests,
        tmnxBsxIcapServerStatsReqErrors,
        tmnxBsxIcapServerStatsRespAllow,
        tmnxBsxIcapServerStatsRespBlock,
        tmnxBsxIcapServerStatsRespRedir,
        tmnxBsxIcapServerStatsRoundTrip,
        tmnxBsxIcapServerStatsReqRate,
        tmnxBsxIcapServerStatsConnTotal,
        tmnxBsxIcapServerStatsConnEst,
        tmnxBsxIcapServerStatsConnUtil,
        tmnxBsxAaIfName,
        tmnxBsxAaIfServiceType,
        tmnxBsxAaIfServiceId,
        tmnxBsxAaIfAddrType,
        tmnxBsxAaIfAddr,
        tmnxBsxAaIfAddrPrefixLength,
        tmnxBsxAaIfIsaAddrType,
        tmnxBsxAaIfIsaAddr,
        tmnxBsxAaIfIsaAddrPrefixLength,
        tmnxBsxAaIfAdminState,
        tmnxBsxAaIfOperState,
        tmnxBsxUrlFltrOperState,
        tmnxBsxUrlFltrOperFlags,
        tmnxBsxUrlFltrStatsHttpRequests,
        tmnxBsxUrlFltrStatsHttpRespAllow,
        tmnxBsxUrlFltrStatsHttpRespRedir,
        tmnxBsxUrlFltrStatsHttpRespBlock,
        tmnxBsxUrlFltrStatsHttpRespDef,
        tmnxBsxUrlFltrStatsHttpReqErrors,
        tmnxBsxUrlFltrStatsIcapLateResp
    }
    STATUS      current
    DESCRIPTION
        "The group of objects introduced in Release 11.0 for Application
         Assurance support for URL filter statistics on Nokia SROS systems."
    ::= { tmnxBsxUrlFilterGroups 2 }

tmnxBsxHttpNotifGroups           OBJECT IDENTIFIER ::= { tmnxBsxGroups 24 }

tmnxBsxHttpNotifObjGrp           OBJECT-GROUP
    OBJECTS     {
        tmnxBsxAqpHttpNotif,
        tmnxBsxHttpNotifLastChangeTime,
        tmnxBsxHttpNotifRowStatus,
        tmnxBsxHttpNotifRowLastChange,
        tmnxBsxHttpNotifAdminState,
        tmnxBsxHttpNotifDescription,
        tmnxBsxHttpNotifScriptUrl,
        tmnxBsxHttpNotifTemplateId,
        tmnxBsxHttpNotifInterval,
        tmnxBsxHttpNotifStatDiscntTime,
        tmnxBsxHttpNotifStatInserted,
        tmnxBsxHttpNotifStatCritNoMtch,
        tmnxBsxAaSubHttpNotifLastTime,
        tmnxBsxAaSubHttpUrlParam
    }
    STATUS      current
    DESCRIPTION
        "The group of objects introduced in Release 11.0 for Application
         Assurance support for HTTP Notification on Nokia SROS systems."
    ::= { tmnxBsxHttpNotifGroups 1 }

tmnxBsxGroupsV11v0               OBJECT IDENTIFIER ::= { tmnxBsxGroups 25 }

tmnxBsxHttpEnrAntiSpfObjGrpV11v0 OBJECT-GROUP
    OBJECTS     {
        tmnxBsxHttpEnrichFieldAntiSpoof
    }
    STATUS      current
    DESCRIPTION
        "The group of objects introduced in Release 11.0 for Application
         Assurance support for HTTP Enrichment Anti-Spoofing on Nokia SROS
         systems."
    ::= { tmnxBsxGroupsV11v0 1 }

tmnxBsxHttpEnAntiSpfStObGrpV11v0 OBJECT-GROUP
    OBJECTS     {
        tmnxBsxHttpEnrichAntiSpoofMod,
        tmnxBsxHttpEnrichNoAntiSpfShort
    }
    STATUS      current
    DESCRIPTION
        "The group of objects introduced in Release 11.0 for Application
         Assurance support for HTTP Enrichment Anti-Spoofing statistics on
         Nokia SROS systems."
    ::= { tmnxBsxGroupsV11v0 2 }

tmnxBsxHttpEnrEncObjGrpV11v0     OBJECT-GROUP
    OBJECTS     {
        tmnxBsxHttpEnrichFieldEncodeType,
        tmnxBsxHttpEnrichFieldEncodeKey
    }
    STATUS      current
    DESCRIPTION
        "The group of objects introduced in Release 11.0 for Application
         Assurance support for HTTP Enrichment Encoding on Nokia SROS systems."
    ::= { tmnxBsxGroupsV11v0 3 }

tmnxBsxGroupsV12v0               OBJECT IDENTIFIER ::= { tmnxBsxGroups 26 }

tmnxBsxPolicyObjGrp12v0          OBJECT-GROUP
    OBJECTS     {
        tmnxBsxAaSubAsoValDerivedFrom,
        tmnxBsxAaSubAsoValName,
        tmnxBsxAaSubPolResExStatus,
        tmnxBsxAaSubPolicerAqpEntryId,
        tmnxBsxAaSubPolicerName,
        tmnxBsxAdminCtrlApply,
        tmnxBsxAdminCtrlConfigOwner,
        tmnxBsxAdminCtrlLastChTime,
        tmnxBsxAppAppGroup,
        tmnxBsxAppDescription,
        tmnxBsxAppFilterAdminState,
        tmnxBsxAppFilterApplication,
        tmnxBsxAppFilterDescription,
        tmnxBsxAppFilterExprOperator,
        tmnxBsxAppFilterExprRowStatus,
        tmnxBsxAppFilterExprStr,
        tmnxBsxAppFilterExprType,
        tmnxBsxAppFilterFlowSetupDir,
        tmnxBsxAppFilterHttpMatchAllReq,
        tmnxBsxAppFilterIpProtocolNum,
        tmnxBsxAppFilterIpProtocolNumOp,
        tmnxBsxAppFilterProtocol,
        tmnxBsxAppFilterProtocolOp,
        tmnxBsxAppFilterRowStatus,
        tmnxBsxAppFilterServerAddr,
        tmnxBsxAppFilterServerAddrLen,
        tmnxBsxAppFilterServerAddrOp,
        tmnxBsxAppFilterServerAddrType,
        tmnxBsxAppFilterServerPortFpp,
        tmnxBsxAppFilterServerPortHigh,
        tmnxBsxAppFilterServerPortLow,
        tmnxBsxAppFilterServerPortOp,
        tmnxBsxAppGrpDescription,
        tmnxBsxAppGrpRowStatus,
        tmnxBsxAppGrpStorageType,
        tmnxBsxAppProfCapacityCost,
        tmnxBsxAppProfCharRowStatus,
        tmnxBsxAppProfCharValName,
        tmnxBsxAppProfDescription,
        tmnxBsxAppProfDivert,
        tmnxBsxAppProfRowStatus,
        tmnxBsxAppRowStatus,
        tmnxBsxAppStorageType,
        tmnxBsxAqpCharOperator,
        tmnxBsxAqpCharRowStatus,
        tmnxBsxAqpStatsConflictsHi,
        tmnxBsxAqpStatsConflictsLo,
        tmnxBsxAqpStatsFlowsHi,
        tmnxBsxAqpStatsFlowsLo,
        tmnxBsxAqpStatsHCConflicts,
        tmnxBsxAqpStatsHCFlows,
        tmnxBsxAsoDefValName,
        tmnxBsxAsoRowStatus,
        tmnxBsxAsoValRowStatus,
        tmnxBsxBitRateHighWatermark,
        tmnxBsxBitRateLowWatermark,
        tmnxBsxCustProtAdminState,
        tmnxBsxCustProtDescription,
        tmnxBsxCustProtExprDirection,
        tmnxBsxCustProtExprOffset,
        tmnxBsxCustProtExprOperator,
        tmnxBsxCustProtExprRowLastChange,
        tmnxBsxCustProtExprRowStatus,
        tmnxBsxCustProtExprStr,
        tmnxBsxCustProtIpProtocolNum,
        tmnxBsxCustProtRowLastChange,
        tmnxBsxCustProtRowStatus,
        tmnxBsxFlowFullHighWatermark,
        tmnxBsxFlowFullLowWatermark,
        tmnxBsxFlowSetupHighWatermark,
        tmnxBsxFlowSetupLowWatermark,
        tmnxBsxPacketRateHighWatermark,
        tmnxBsxPacketRateLowWatermark,
        tmnxBsxPolicerAction,
        tmnxBsxPolicerAdminCIR,
        tmnxBsxPolicerAdminPIR,
        tmnxBsxPolicerCBS,
        tmnxBsxPolicerCIRAdaptation,
        tmnxBsxPolicerDescription,
        tmnxBsxPolicerGranularity,
        tmnxBsxPolicerMBS,
        tmnxBsxPolicerPIRAdaptation,
        tmnxBsxPolicerRowStatus,
        tmnxBsxPolicerType,
        tmnxBsxProtAdminState,
        tmnxBsxProtDescription,
        tmnxBsxProtObsolete,
        tmnxBsxProtParentName,
        tmnxBsxUpgrade,
        tmnxBsxVersion,
        tmnxBsxAqpBaseRowStatus,
        tmnxBsxAqpBaseDescription,
        tmnxBsxAqpBaseAdminState,
        tmnxBsxAqpBaseRowLastChange,
        tmnxBsxAqpBaseLastChTime,
        tmnxBsxAqpMatchRowLastChange,
        tmnxBsxAqpMatchLastChTime,
        tmnxBsxAqpMatchApplication,
        tmnxBsxAqpMatchApplicationOp,
        tmnxBsxAqpMatchAppGroup,
        tmnxBsxAqpMatchAppGroupOp,
        tmnxBsxAqpMatchTrafficDir,
        tmnxBsxAqpMatchDscp,
        tmnxBsxAqpMatchDscpOp,
        tmnxBsxAqpMatchSrcAddressType,
        tmnxBsxAqpMatchSrcAddress,
        tmnxBsxAqpMatchSrcAddressLength,
        tmnxBsxAqpMatchSrcAddressOp,
        tmnxBsxAqpMatchSrcPortOp,
        tmnxBsxAqpMatchSrcPortLowValue,
        tmnxBsxAqpMatchSrcPortHighValue,
        tmnxBsxAqpMatchDstAddressType,
        tmnxBsxAqpMatchDstAddress,
        tmnxBsxAqpMatchDstAddressLength,
        tmnxBsxAqpMatchDstAddressOp,
        tmnxBsxAqpMatchDstPortOp,
        tmnxBsxAqpMatchDstPortLowValue,
        tmnxBsxAqpMatchDstPortHighValue,
        tmnxBsxAqpMatchAaSubscriberType,
        tmnxBsxAqpMatchAaSubscriber,
        tmnxBsxAqpMatchAaSubscriberOp,
        tmnxBsxAqpMatchChargeGrp,
        tmnxBsxAqpMatchChargeGrpOp,
        tmnxBsxAqpMatchIpProtocolNum,
        tmnxBsxAqpMatchIpProtocolNumOp,
        tmnxBsxAqpActRowLastChange,
        tmnxBsxAqpActionLastChTime,
        tmnxBsxAqpActDrop,
        tmnxBsxAqpActBwLimitPolicer,
        tmnxBsxAqpActFlowRatePolicer,
        tmnxBsxAqpActFlowCountPolicer,
        tmnxBsxAqpActRemarkFc,
        tmnxBsxAqpActRemarkPriority,
        tmnxBsxAqpActRemarkDscpInProf,
        tmnxBsxAqpActRemarkDscpOutProf,
        tmnxBsxAqpActMirrorSource,
        tmnxBsxAqpActMirrorSourceAllIncl,
        tmnxBsxAqpActHttpErrRedirName,
        tmnxBsxAqpActHttpRedirName,
        tmnxBsxAqpActHttpRedirFlowType,
        tmnxBsxAqpActHttpEnrichName,
        tmnxBsxAqpActSessionFilter,
        tmnxBsxAqpActUrlFilter,
        tmnxBsxAqpActHttpNotif,
        tmnxBsxAsoPersistId,
        tmnxBsxAsoValPersistId
    }
    STATUS      current
    DESCRIPTION
        "The group of objects introduced in Release 12.0 for Application
         Assurance support for Policy Management on Nokia SROS systems."
    ::= { tmnxBsxGroupsV12v0 1 }

tmnxBsxIpPrefixListObjGrpV12v0   OBJECT-GROUP
    OBJECTS     {
        tmnxBsxAppFilterServerPfxList,
        tmnxBsxPrefixListDescription,
        tmnxBsxPrefixListRowLastChange,
        tmnxBsxPrefixListRowStatus,
        tmnxBsxPrefixListLastChTime,
        tmnxBsxPrefixRowStatus,
        tmnxBsxPrefixName,
        tmnxBsxPrefixLastChTime,
        tmnxBsxSessFltrParamsDstPfxList,
        tmnxBsxSessFltrParamsSrcPfxList,
        tmnxBsxEventLogLastChTime,
        tmnxBsxEventLogRowStatus,
        tmnxBsxEventLogRowLastChange,
        tmnxBsxEventLogBufferType,
        tmnxBsxEventLogMaxEntries,
        tmnxBsxEventLogAdminState,
        tmnxBsxSessFltrParamsActEventLog,
        tmnxBsxSessFltrDefActEventLog,
        tmnxBsxAqpMatchSrcPfxList,
        tmnxBsxAqpMatchDstPfxList,
        tmnxBsxAqpActOverloadDrop,
        tmnxBsxAqpActErrorDrop,
        tmnxBsxAqpActFragDrop,
        tmnxBsxAqpActEvtLogOverloadDrop,
        tmnxBsxAqpActEvtLogErrorDrop,
        tmnxBsxAqpActEvtLogFragDrop
    }
    STATUS      current
    DESCRIPTION
        "The group of objects introduced in Release 12.0 for Application
         Assurance support for IP Prefix Lists on Nokia SROS systems."
    ::= { tmnxBsxGroupsV12v0 2 }

tmnxBsxHttpEnrStStrObjGrpV12v0   OBJECT-GROUP
    OBJECTS     {
        tmnxBsxHttpEnrichFieldStaticStr
    }
    STATUS      current
    DESCRIPTION
        "The group of objects introduced in Release 12.0 for Application
         Assurance support for HTTP Enrichment static string on Nokia SROS
         systems."
    ::= { tmnxBsxGroupsV12v0 3 }

tmnxBsxTrafficStatsObjGrpV12v0   OBJECT-GROUP
    OBJECTS     {
        tmnxBsxTrafStatDiscontTime,
        tmnxBsxTrafStatOctsAdmFmSb,
        tmnxBsxTrafStatPktsAdmFmSb,
        tmnxBsxTrafStatFlwsAdmFmSb,
        tmnxBsxTrafStatOctsDnyFmSb,
        tmnxBsxTrafStatPktsDnyFmSb,
        tmnxBsxTrafStatFlwsDnyFmSb,
        tmnxBsxTrafStatOctsAdmToSb,
        tmnxBsxTrafStatPktsAdmToSb,
        tmnxBsxTrafStatFlwsAdmToSb,
        tmnxBsxTrafStatOctsDnyToSb,
        tmnxBsxTrafStatPktsDnyToSb,
        tmnxBsxTrafStatFlwsDnyToSb,
        tmnxBsxTrafStatTermFlwDur,
        tmnxBsxTrafStatTermFlws,
        tmnxBsxTrafStatShrtDurFlws,
        tmnxBsxTrafStatMedDurFlws,
        tmnxBsxTrafStatLngDurFlws,
        tmnxBsxTrafStatActFlwsFmSb,
        tmnxBsxTrafStatActFlwsToSb,
        tmnxBsxPartAcctCfgLastChTime,
        tmnxBsxPartAcctCfgRowLastCh,
        tmnxBsxPartAcctCfgCollStats,
        tmnxBsxPartAcctCfgPolicy,
        tmnxBsxPartAcctCfgTrafStats,
        tmnxBsxPartAcctCfgTetherStats
    }
    STATUS      current
    DESCRIPTION
        "The group of objects introduced in Release 12.0 for Application
         Assurance support for AA Partition Accounting and Traffic Statistics
         on Nokia SROS systems."
    ::= { tmnxBsxGroupsV12v0 4 }

tmnxBsxHttpRedirObjGrpV12v0      OBJECT-GROUP
    OBJECTS     {
        tmnxBsxHttpRedirTcpReset,
        tmnxBsxHttpPcyRdStatTcpResets
    }
    STATUS      current
    DESCRIPTION
        "The group of objects introduced in Release 12.0 for Application
         Assurance support for HTTP Redirect Enhancements on Nokia SROS
         systems."
    ::= { tmnxBsxGroupsV12v0 6 }

tmnxBsxUsageMonObjGrpV12v0       OBJECT-GROUP
    OBJECTS     {
        tmnxBsxAaSubUMOperStatus,
        tmnxBsxAaSubUMToSubGrantStatus,
        tmnxBsxAaSubUMFmSubGrantStatus,
        tmnxBsxAaSubUMBothGrantStatus,
        tmnxBsxAaSubUMToSubGrantCredit,
        tmnxBsxAaSubUMFmSubGrantCredit,
        tmnxBsxAaSubUMBothGrantCredit,
        tmnxBsxAaSubUMToSubUsedCredit,
        tmnxBsxAaSubUMFmSubUsedCredit,
        tmnxBsxAaSubUMBothUsedCredit,
        tmnxBsxStatAaAcctCfgUMStats
    }
    STATUS      current
    DESCRIPTION
        "The group of objects introduced in Release 12.0 for Application
         Assurance support for GX Usage Monitoring on Nokia SROS systems."
    ::= { tmnxBsxGroupsV12v0 7 }

tmnxBsxUrlFilterObjGrpV12v0      OBJECT-GROUP
    OBJECTS     {
        tmnxBsxUrlFilterHttpReqFilter
    }
    STATUS      current
    DESCRIPTION
        "The group of objects introduced in Release 12.0 for Application
         Assurance support for URL Filtering on Nokia SROS systems."
    ::= { tmnxBsxGroupsV12v0 9 }

tmnxBsxLwObjGrpV12v0             OBJECT-GROUP
    OBJECTS     {
        tmnxBsxIsaAaGrpWlanGwGrpId
    }
    STATUS      current
    DESCRIPTION
        "The group of objects introduced in Release 12.0 for Application
         Assurance support for Distributed Subscriber Management on Nokia SROS
         systems."
    ::= { tmnxBsxGroupsV12v0 10 }

tmnxBsxMdaGroupV12v0             OBJECT-GROUP
    OBJECTS     {
        tmnxBsxIsaAaGrpTransPrefV4RmEntr,
        tmnxBsxGrpMdaTransPrefV4RemEntr
    }
    STATUS      current
    DESCRIPTION
        "The group of objects supporting management of Application Assurance
         MDA capabilities on Nokia SROS series systems for release 12.0."
    ::= { tmnxBsxGroupsV12v0 11 }

tmnxBsxGroupsV13v0               OBJECT IDENTIFIER ::= { tmnxBsxGroups 27 }

tmnxBsxDnsIpCacheGroupV13v0      OBJECT-GROUP
    OBJECTS     {
        tmnxBsxAppFilterServerDnsIpCache,
        tmnxBsxAqpActDnsIpCache,
        tmnxBsxDnsIpCacheLastCTime,
        tmnxBsxDnsIpCacheDomainLastCTime,
        tmnxBsxDnsIpCacheServerLastCTime,
        tmnxBsxDnsIpCacheRowStatus,
        tmnxBsxDnsIpCacheRowLastChanged,
        tmnxBsxDnsIpCacheSize,
        tmnxBsxDnsIpCacheHighWatermark,
        tmnxBsxDnsIpCacheLowWatermark,
        tmnxBsxDnsIpCacheAdminState,
        tmnxBsxDnsIpCacheDomainExprStr,
        tmnxBsxDnsIpCacheDomainRowStatus,
        tmnxBsxDnsIpCacheDomainRowLastCh,
        tmnxBsxDnsIpCacheServerRowLastCh,
        tmnxBsxDnsIpCacheServerRowStatus,
        tmnxBsxDnsIpCacheServerName,
        tmnxBsxDnsIpCacheStatDnsResp,
        tmnxBsxDnsIpCacheStatDomMtch,
        tmnxBsxDnsIpCacheStatDomSerMtch,
        tmnxBsxDnsIpCacheStatAlarmClear,
        tmnxBsxDnsIpCacheStatEntrAdd,
        tmnxBsxDnsIpCacheStatEntrRmvd,
        tmnxBsxDnsIpCacheStatFullCnt,
        tmnxBsxDnsIpCacheStatHitCnt,
        tmnxBsxDnsIpCacheStatMissCnt,
        tmnxBsxDnsIpCacheStatDiscntTime,
        tmnxBsxDnsIpCacheDescription
    }
    STATUS      current
    DESCRIPTION
        "The group of objects supporting management of Application Assurance
         DNS IP Cache feature capabilities on Nokia series systems for SROS
         release 13.0."
    ::= { tmnxBsxGroupsV13v0 1 }

tmnxBsxUrlListGroupV13v0         OBJECT-GROUP
    OBJECTS     {
        tmnxBsxUrlFltrUrlListLastCTime,
        tmnxBsxUrlFltrUrlListRowStatus,
        tmnxBsxUrlFltrUrlListRowLastCh,
        tmnxBsxUrlListLastChangedTime,
        tmnxBsxUrlListRowLastChanged,
        tmnxBsxUrlListRowStatus,
        tmnxBsxUrlListAdminState,
        tmnxBsxUrlListDecryptKey,
        tmnxBsxUrlListFileUrl,
        tmnxBsxUrlListUpgrade,
        tmnxBsxUrlListDescription,
        tmnxBsxUrlListStatusOperState,
        tmnxBsxUrlListStatusOperFlags,
        tmnxBsxUrlListStatusNumEntries,
        tmnxBsxUrlListStatusUpgAttemptTm,
        tmnxBsxUrlListStatusUpgSuccessTm,
        tmnxBsxUrlListStatusUpgErrorLine,
        tmnxBsxUrlListStatusUpgErrReason,
        tmnxBsxUrlListStatusUpgErrDetail,
        tmnxBsxUrlListStatusUpgLineSkipd,
        tmnxBsxUrlListStatusUrlDeployed,
        tmnxBsxUrlListStatusUrlAttempted,
        tmnxBsxUrlListStatusIsCfgUrlDpld
    }
    STATUS      current
    DESCRIPTION
        "The group of objects supporting management of Application Assurance
         URL list feature capabilities on Nokia series systems for SROS release
         13.0."
    ::= { tmnxBsxGroupsV13v0 2 }

tmnxBsxPolicyObjGrp13v0          OBJECT-GROUP
    OBJECTS     {
        tmnxBsxAppProfSubSuppressible,
        tmnxBsxChargeGrpNotifyStartStop
    }
    STATUS      current
    DESCRIPTION
        "The group of objects introduced in SROS Release 13.0 for Application
         Assurance support for Policy Management on Nokia systems."
    ::= { tmnxBsxGroupsV13v0 3 }

tmnxBsxTrafficStatsObjGrpV13v0   OBJECT-GROUP
    OBJECTS     {
        tmnxBsxStatAaAcctCfgAggrExpMeth,
        tmnxBsxAppFilterNetworkAddrType,
        tmnxBsxAppFilterNetworkAddr,
        tmnxBsxAppFilterNetworkAddrLen,
        tmnxBsxAppFilterNetworkAddrOp,
        tmnxBsxAppFilterNetworkPfxList
    }
    STATUS      current
    DESCRIPTION
        "The group of objects introduced in SROS Release 13.0 for Application
         Assurance support for AA Partition Accounting and Traffic Statistics
         on Nokia systems."
    ::= { tmnxBsxGroupsV13v0 4 }

tmnxBsxGtpGroupV13v0             OBJECT-GROUP
    OBJECTS     {
        tmnxBsxGtpLastChangedTime,
        tmnxBsxGtpFltrLastChangedTime,
        tmnxBsxGtpFltrMsgLastChangedTime,
        tmnxBsxSctpFltrLastChangedTime,
        tmnxBsxSctpFltrPpidLastChngdTime,
        tmnxBsxGtpRowLastChange,
        tmnxBsxGtpAdminState,
        tmnxBsxGtpEvtLog,
        tmnxBsxPolicerGtpFlowCountLmt,
        tmnxBsxGtpFltrRowLastChange,
        tmnxBsxGtpFltrRowStatus,
        tmnxBsxGtpFltrDescription,
        tmnxBsxGtpFltrMaxPayloadLength,
        tmnxBsxGtpFltrDefaultAction,
        tmnxBsxGtpFltrMsgValue,
        tmnxBsxGtpFltrMsgRowLastChange,
        tmnxBsxGtpFltrMsgRowStatus,
        tmnxBsxGtpFltrMsgAction,
        tmnxBsxGtpFltrEvtLog,
        tmnxBsxSctpFltrRowLastChange,
        tmnxBsxSctpFltrRowStatus,
        tmnxBsxSctpFltrDescription,
        tmnxBsxSctpFltrPpidRangeMin,
        tmnxBsxSctpFltrPpidRangeMax,
        tmnxBsxSctpFltrDefaultAction,
        tmnxBsxSctpFltrEvtLog,
        tmnxBsxSctpFltrPpidVal,
        tmnxBsxSctpFltrPpidRowLastChange,
        tmnxBsxSctpFltrPpidRowStatus,
        tmnxBsxSctpFltrPpidValAction,
        tmnxBsxAaGrpPartAqpInitialLookup,
        tmnxBsxAqpActGtpFilter,
        tmnxBsxAqpActSctpFilter,
        tmnxBsxAqpActFlowRatePlcrEvtLog,
        tmnxBsxAqpActFlowCountPlcrEvtLog,
        tmnxBsxGtpStatsDiscntTime,
        tmnxBsxGtpStatsPkPermittedFmSb,
        tmnxBsxGtpStatsPkPermittedToSb,
        tmnxBsxGtpStatsPkPrmtNoFltrFmSb,
        tmnxBsxGtpStatsPkPrmtNoFltrToSb,
        tmnxBsxGtpStatsPkDndUdpLenFmSb,
        tmnxBsxGtpStatsPkDndUdpLenToSb,
        tmnxBsxGtpStatsPkDndGtpLenFmSb,
        tmnxBsxGtpStatsPkDndGtpLenToSb,
        tmnxBsxGtpStatsPkDndGtpVerFmSb,
        tmnxBsxGtpStatsPkDndGtpVerToSb,
        tmnxBsxGtpStatsPkDndFlPlcrFmSb,
        tmnxBsxGtpStatsPkDndFlPlcrToSb,
        tmnxBsxGtpStatsPkDndGtpFltrFmSb,
        tmnxBsxGtpStatsPkDndGtpFltrToSb,
        tmnxBsxGtpStatsPkDndPlcyOthrFmSb,
        tmnxBsxGtpStatsPkDndPlcyOthrToSb,
        tmnxBsxGtpFltrStatsDiscntTime,
        tmnxBsxGtpFltrStatsPkPermitted,
        tmnxBsxGtpFltrStatsPkDndPayldLen,
        tmnxBsxGtpFltrStatsPkDndMsgType,
        tmnxBsxGtpFltrStatsPkDndMandHdr,
        tmnxBsxGtpFltrStatsPkDndExtHdr,
        tmnxBsxGtpFltrStatsPkDndInfoElem,
        tmnxBsxSctpFltrStatsDiscntTime,
        tmnxBsxSctpFltrStatsPkPermitted,
        tmnxBsxSctpFltrStatsPkDndMalfd,
        tmnxBsxSctpFltrStatsPkDndPpidOOR,
        tmnxBsxSctpFltrStatsPkDndPpidVal
    }
    STATUS      current
    DESCRIPTION
        "The group of objects supporting management of Application Assurance
         GTP feature capabilities on Nokia series systems for SROS release
         13.0."
    ::= { tmnxBsxGroupsV13v0 5 }

tmnxBsxHttpRedirObjGrpV13v0      OBJECT-GROUP
    OBJECTS     {
        tmnxBsxHttpRedirCaptivePortVlan,
        tmnxBsxSessFltrParamsActHttpRedr,
        tmnxBsxSessFltrParamsDstDnsCache,
        tmnxBsxHttpPcyRdStatConfigError
    }
    STATUS      current
    DESCRIPTION
        "The group of objects introduced in SROS Release 13.0 for Application
         Assurance support for Captive Redirect DNS IP Cache enhancements on
         Nokia systems."
    ::= { tmnxBsxGroupsV13v0 6 }

tmnxBsxHttpNotifObjGrpV13v0      OBJECT-GROUP
    OBJECTS     {
        tmnxBsxHttpNotifStatSuccess,
        tmnxBsxHttpNotifStatFailed
    }
    STATUS      current
    DESCRIPTION
        "The group of objects introduced in SROS Release 13.0 for Application
         Assurance support for HTTP Notification enhancements on Nokia systems."
    ::= { tmnxBsxGroupsV13v0 7 }

tmnxBsxIsa2ObjGroup              OBJECT-GROUP
    OBJECTS     {
        tmnxBsxIsaAaGrpMinIsaGeneration
    }
    STATUS      current
    DESCRIPTION
        "The group of objects introduced in SROS Release 13.0 for Application
         Assurance support for ISA 2 on Nokia systems."
    ::= { tmnxBsxGroupsV13v0 8 }

tmnxBsxXHeaderObjGroup           OBJECT-GROUP
    OBJECTS     {
        tmnxBsxUrlFilterIcapCustXHeader,
        tmnxBsxAqpActUrlFiltrXHeaderChar
    }
    STATUS      current
    DESCRIPTION
        "The group of objects introduced in SROS Release 13.0 for Application
         Assurance support for X-Header enhancements on Nokia systems."
    ::= { tmnxBsxGroupsV13v0 9 }

tmnxBsxGroupsV14v0               OBJECT IDENTIFIER ::= { tmnxBsxGroups 28 }

tmnxBsxStflFwEnhacementsObjGrp   OBJECT-GROUP
    OBJECTS     {
        tmnxBsxAdmitDenyAcctTableLastCh,
        tmnxBsxAdmitDenyAcctRowLastCh,
        tmnxBsxAdmitDenyAcctPolicy,
        tmnxBsxAdmitDenyAcctCollStats,
        tmnxBsxAdmitDenyAcctSctpFtrStats,
        tmnxBsxAdmitDenyAcctGtpFtrStats,
        tmnxBsxAdmitDenyAcctSessFtrStats,
        tmnxBsxAdmitDenyAcctPolcrStats,
        tmnxBsxAdmitDenyAcctPolcrResrcs,
        tmnxBsxStatTcaCfgTableLastCh,
        tmnxBsxStatTcaCfgRowLastCh,
        tmnxBsxStatTcaCfgRowStatus,
        tmnxBsxStatTcaCfgHiWmark,
        tmnxBsxStatTcaCfgLoWmark,
        tmnxBsxStatTcaPolcrCfgTableLstCh,
        tmnxBsxStatTcaPolcrCfgRowLastCh,
        tmnxBsxStatTcaPolcrCfgRowStatus,
        tmnxBsxStatTcaPolcrCfgHiWmark,
        tmnxBsxStatTcaPolcrCfgLoWmark,
        tmnxBsxStatTcaFtrCfgTableLastCh,
        tmnxBsxStatTcaFtrCfgRowLastCh,
        tmnxBsxStatTcaFtrCfgRowStatus,
        tmnxBsxStatTcaFtrCfgHiWmark,
        tmnxBsxStatTcaFtrCfgLoWmark,
        tmnxBsxStatTcaFtrEnCfgTableLstCh,
        tmnxBsxStatTcaFtrEnCfgRowLastCh,
        tmnxBsxStatTcaFtrEnCfgRowStatus,
        tmnxBsxStatTcaFtrEnCfgHiWmark,
        tmnxBsxStatTcaFtrEnCfgLoWmark,
        tmnxBsxTcaStatsTimeLastRaised,
        tmnxBsxTcaStatsTimeLastCleared,
        tmnxBsxTcaStatsTcaState,
        tmnxBsxTcaStatsTcaTrigType,
        tmnxBsxTcaPolcrStatsTmLastRaised,
        tmnxBsxTcaPolcrStatsTmLastCleard,
        tmnxBsxTcaPolcrStatsTcaState,
        tmnxBsxTcaPolcrStatsTcaTrigType,
        tmnxBsxTcaFtrStatsTimeLastRaised,
        tmnxBsxTcaFtrStatsTimeLastCleard,
        tmnxBsxTcaFtrStatsTcaState,
        tmnxBsxTcaFtrStatsTcaTrigType,
        tmnxBsxTcaFtrEnStatsTmLastRaised,
        tmnxBsxTcaFtrEnStatsTmLastCleard,
        tmnxBsxTcaFtrEnStatsTcaState,
        tmnxBsxTcaFtrEnStatsTcaTrigType
    }
    STATUS      current
    DESCRIPTION
        "The group of objects introduced in SROS Release 14.0 for Application
         Assurance support for stateful firewall enhancements on Nokia systems."
    ::= { tmnxBsxGroupsV14v0 1 }

tmnxBsxEventLogSyslogObjGrp      OBJECT-GROUP
    OBJECTS     {
        tmnxBsxEventLogSyslogAddrType,
        tmnxBsxEventLogSyslogAddr,
        tmnxBsxEventLogSyslogPort,
        tmnxBsxEventLogSyslogDescription,
        tmnxBsxEventLogSyslogVlan,
        tmnxBsxEventLogSyslogFacility,
        tmnxBsxEventLogSyslogSeverity,
        tmnxBsxSyslogStatsDiscntTime,
        tmnxBsxSyslogStatsEventsSent,
        tmnxBsxSyslogStatsEventsFailed
    }
    STATUS      current
    DESCRIPTION
        "The group of objects introduced in SROS Release 14.0 for Application
         Assurance support on Nokia systems for event-logging to a remote
         syslog collector target."
    ::= { tmnxBsxGroupsV14v0 2 }

tmnxBsxTransitIpPolicyDiamObjGrp OBJECT-GROUP
    OBJECTS     {
        tmnxBsxTransitIpPolicyDiamAppPlc,
        tmnxBsxTransitIpPolicyDiameter
    }
    STATUS      current
    DESCRIPTION
        "The group of objects introduced in SROS Release 14.0 for Application
         Assurance support on Nokia systems for Diameter support in transit IP
         policy."
    ::= { tmnxBsxGroupsV14v0 3 }

tmnxBsxUrlListExtendedGroup      OBJECT-GROUP
    OBJECTS     {
        tmnxBsxUrlListSize,
        tmnxBsxUrlListStatusNumChars,
        tmnxBsxUrlListStatusUpgInProgres
    }
    STATUS      current
    DESCRIPTION
        "The group of objects introduced in SROS Release 14.0 for Application
         Assurance support for extended URL lists on Nokia systems"
    ::= { tmnxBsxGroupsV14v0 4 }

tmnxBsxHttpsCaptiveRedirObjGrp   OBJECT-GROUP
    OBJECTS     {
        tmnxBsxHttpRedirCapHttpsEnbld
    }
    STATUS      current
    DESCRIPTION
        "The group of objects introduced in SROS Release 14.0 for Application
         Assurance support for Captive Redirect enhancements on Nokia systems."
    ::= { tmnxBsxGroupsV14v0 5 }

tmnxBsxTcpMssObjGrp              OBJECT-GROUP
    OBJECTS     {
        tmnxBsxAqpActTcpMaxSegSize
    }
    STATUS      current
    DESCRIPTION
        "The group of objects introduced in SROS Release 14.0 for Application
         Assurance support for TCP MSS adjustment on Nokia systems."
    ::= { tmnxBsxGroupsV14v0 6 }

tmnxBsxGtpUntunnelingObjGrp      OBJECT-GROUP
    OBJECTS     {
        tmnxBsxGtpMode
    }
    STATUS      current
    DESCRIPTION
        "The group of objects introduced in SROS Release 14.0 for Application
         Assurance support for GTP untunneling on Nokia systems."
    ::= { tmnxBsxGroupsV14v0 7 }

tmnxBsxTcpOptObjGrp              OBJECT-GROUP
    OBJECTS     {
        tmnxBsxTcpOptLastChangedTime,
        tmnxBsxTcpOptRowLastChange,
        tmnxBsxTcpOptRowStatus,
        tmnxBsxTcpOptDescription,
        tmnxBsxTcpOptInitCwnd,
        tmnxBsxTcpOptStackType,
        tmnxBsxTcpOptDAckTimeout,
        tmnxBsxTcpOptInitSsThreshold,
        tmnxBsxSessFltrParamsActTcpOpt,
        tmnxBsxTcpOptStatSessOptimized,
        tmnxBsxTcpOptStatOctsRxFmSub,
        tmnxBsxTcpOptStatOctsTxFmSub,
        tmnxBsxTcpOptStatOctsRetranFmSub,
        tmnxBsxTcpOptStatOctsRxToSub,
        tmnxBsxTcpOptStatOctsTxToSub,
        tmnxBsxTcpOptStatOctsRetranToSub,
        tmnxBsxTcpOptStatPktsRxFmSub,
        tmnxBsxTcpOptStatPktsTxFmSub,
        tmnxBsxTcpOptStatPktsRetranFmSub,
        tmnxBsxTcpOptStatPktsRxToSub,
        tmnxBsxTcpOptStatPktsTxToSub,
        tmnxBsxTcpOptStatPktsRetranToSub,
        tmnxBsxTcpOptStatDiscntTime,
        tmnxBsxGrpStatusPktsDiscTcpOpt,
        tmnxBsxGrpStatusOctsDiscTcpOpt,
        tmnxBsxGrpStatusPktsGenTcpOpt,
        tmnxBsxGrpStatusOctsGenTcpOpt,
        tmnxBsxGrpStatusPktDisTcOptToSub,
        tmnxBsxGrpStatusPktDisTcOptFrSub,
        tmnxBsxGrpStatusOctDisTcOptToSub,
        tmnxBsxGrpStatusOctDisTcOptFrSub,
        tmnxBsxGrpStatusPktGenTcOptToSub,
        tmnxBsxGrpStatusPktGenTcOptFrSub,
        tmnxBsxGrpStatusOctGenTcOptToSub,
        tmnxBsxGrpStatusOctGenTcOptFrSub
    }
    STATUS      current
    DESCRIPTION
        "The group of objects introduced in SROS Release 14.0 for Application
         Assurance support for TCP optimization on Nokia systems."
    ::= { tmnxBsxGroupsV14v0 8 }

tmnxBsxTrapPerfObjGrp            OBJECT-GROUP
    OBJECTS     {
        tmnxBsxDatapathCpuHighWatermark,
        tmnxBsxDatapathCpuLowWatermark,
        tmnxBsxGrpStatusFlowResMax,
        tmnxBsxGrpStatusFlowResAvg,
        tmnxBsxGrpStatusFlowResPeak,
        tmnxBsxGrpStatusFlowResState,
        tmnxBsxGrpStatusFlowResRsdCount,
        tmnxBsxGrpStatusFlowResRaisdTime,
        tmnxBsxGrpStatusFlowSetupState,
        tmnxBsxGrpStatusFlowSetupRsdCnt,
        tmnxBsxGrpStatusFlowSetupRsdTime,
        tmnxBsxGrpStatusBitRateState,
        tmnxBsxGrpStatusBitRateRsdCount,
        tmnxBsxGrpStatusBitRateRsdTime,
        tmnxBsxGrpStatusPktRateState,
        tmnxBsxGrpStatusPktRateRsdCount,
        tmnxBsxGrpStatusPktRateRaisdTime,
        tmnxBsxGrpStatusDatapathCpu,
        tmnxBsxGrpStatusDatapathCpuAvg,
        tmnxBsxGrpStatusDatapathCpuPeak,
        tmnxBsxGrpStatusDatapathCpuState,
        tmnxBsxGrpStatusDatapathCpuRsdCt,
        tmnxBsxGrpStatusDatapathCpuRsdTm,
        tmnxBsxGrpStatusMgmtCpu,
        tmnxBsxGrpStatusMgmtCpuAvg,
        tmnxBsxGrpStatusMgmtCpuPeak,
        tmnxBsxGrpStatusWaSBfFmSub,
        tmnxBsxGrpStatusWaSBfFmSubState,
        tmnxBsxGrpStatusWaSBfFmSubRsdCnt,
        tmnxBsxGrpStatusWaSBfFmSubRsdTm,
        tmnxBsxGrpStatusWaSBfToSub,
        tmnxBsxGrpStatusWaSBfToSubState,
        tmnxBsxGrpStatusWaSBfToSubRsdCnt,
        tmnxBsxGrpStatusWaSBfToSubRsdTm,
        tmnxBsxGrpStatusFlwResCtThruOcts,
        tmnxBsxGrpStatusFlwResCtThruPkts,
        tmnxBsxGrpStatusOvrldCtThruOcts,
        tmnxBsxGrpStatusOvrldCtThruPkts,
        tmnxBsxGrpStatusOvrldCtThruState,
        tmnxBsxGrpStatusOvrldCtThruRsdCt,
        tmnxBsxGrpStatusOvrldCtThruRsdTm
    }
    STATUS      current
    DESCRIPTION
        "The group of objects introduced in SROS Release 14.0 for Application
         Assurance support for additional trap performance stats on Nokia
         systems."
    ::= { tmnxBsxGroupsV14v0 9 }

tmnxBsxTcpValObjGrp              OBJECT-GROUP
    OBJECTS     {
        tmnxBsxTcpValLastChangedTime,
        tmnxBsxTcpValRowLastChanged,
        tmnxBsxTcpValRowStatus,
        tmnxBsxTcpValDescription,
        tmnxBsxTcpValEventLog,
        tmnxBsxTcpValEventLogAll,
        tmnxBsxTcpValStrict,
        tmnxBsxAqpActTcpValidate,
        tmnxBsxTcpValTcaLastChangedTime,
        tmnxBsxTcpValTcaRowLastChanged,
        tmnxBsxTcpValTcaRowStatus,
        tmnxBsxTcpValTcaHighWatermark,
        tmnxBsxTcpValTcaLowWatermark,
        tmnxBsxAdmitDenyAcctTcpValStats,
        tmnxBsxTcpValTcaStatsLastRaised,
        tmnxBsxTcpValTcaStatsLastCleard,
        tmnxBsxTcpValTcaStatsTcaState,
        tmnxBsxTcpValTcaStatsTcaTrigType,
        tmnxBsxTcpValStatsAllowed,
        tmnxBsxTcpValStatsDropBadFlag,
        tmnxBsxTcpValStatsDropBadOption,
        tmnxBsxTcpValStatsDropBadSEQ,
        tmnxBsxTcpValStatsDropBadACK,
        tmnxBsxTcpValStatsDropNoEstment,
        tmnxBsxTcpValStatsDropAlreadyEst,
        tmnxBsxTcpValStatsDropAsymmetric,
        tmnxBsxTcpValStatsDropAfterRST,
        tmnxBsxTcpValStatsDropFragmented,
        tmnxBsxTcpValStatsDiscntTime
    }
    STATUS      current
    DESCRIPTION
        "The group of objects introduced in SROS Release 14.0 for Application
         Assurance support for TCP validation on Nokia systems."
    ::= { tmnxBsxGroupsV14v0 10 }

tmnxBsxGroupsV15v0               OBJECT IDENTIFIER ::= { tmnxBsxGroups 29 }

tmnxBsx15v0ObjGrp                OBJECT-GROUP
    OBJECTS     {
        tmnxBsxAaSubCircuitId,
        tmnxBsxAaSubRemoteId,
        tmnxBsxAaSubMacAddr,
        tmnxBsxAaSubSapPortId,
        tmnxBsxAaSubSapEncapVal
    }
    STATUS      current
    DESCRIPTION
        "The group of objects introduced in SROS Release 15.0 for Application
         Assurance in SROS in Nokia systems."
    ::= { tmnxBsxGroupsV15v0 1 }

tmnxBsxTcpOptV15v0ObjGrp         OBJECT-GROUP
    OBJECTS     {
        tmnxBsxTcpOptStatSessActive,
        tmnxBsxTcpOptStatSessAbUnsupPkt,
        tmnxBsxTcpOptStatSessUnUnsupPkt,
        tmnxBsxTcpOptStatSessAbPktErr,
        tmnxBsxTcpOptStatSessUnPktErr,
        tmnxBsxTcpOptStatSessAbInact,
        tmnxBsxTcpOptStatSessUnInact,
        tmnxBsxTcpOptStatSessUnNoBuffers,
        tmnxBsxTcpOptStatSessUnExistSess,
        tmnxBsxTcpOptStatSessAbOther,
        tmnxBsxTcpOptStatSessUnOther,
        tmnxBsxTcpOptStatMaxAvailBuffers,
        tmnxBsxTcpOptStatBuffersInUse
    }
    STATUS      current
    DESCRIPTION
        "The group of objects introduced in SROS Release 15.0 for Application
         Assurance support for TCP optimization on Nokia systems."
    ::= { tmnxBsxGroupsV15v0 2 }

tmnxBsxDEMV15v0ObjGrp            OBJECT-GROUP
    OBJECTS     {
        tmnxBsxPolicerRatePercentage,
        tmnxBsxAnlRowLastChange,
        tmnxBsxAnlRowStatus,
        tmnxBsxAnlSource,
        tmnxBsxAnlSourceLevel,
        tmnxBsxAnlRttThreshold,
        tmnxBsxAnlRttThresholdTolerance
    }
    STATUS      current
    DESCRIPTION
        "The group of objects introduced in SROS Release 15.0 for Application
         Assurance support for DEM feature on Nokia systems."
    ::= { tmnxBsxGroupsV15v0 3 }

tmnxBsxEsmMacV15v0ObjGrp         OBJECT-GROUP
    OBJECTS     {
        tmnxBsxIsaAaGrpUnassEsmMacSubs,
        tmnxBsxGrpMdaEsmMacSubscribers,
        tmnxBsxEsmMacSubSumUpdateTime,
        tmnxBsxEsmMacSubSumMacAddress,
        tmnxBsxEsmMacSubSumEsmSubscriber,
        tmnxBsxEsmMacSubSumAppProfNm
    }
    STATUS      current
    DESCRIPTION
        "The group of objects introduced in SROS Release 15.0 for Application
         Assurance support for Enhanced Subscriber Management (ESM) MAC Hosts
         on Nokia systems."
    ::= { tmnxBsxGroupsV15v0 4 }

tmnxBsxAppFilterV15v0ObjGrp      OBJECT-GROUP
    OBJECTS     {
        tmnxBsxAppFilterHttpPort,
        tmnxBsxAppFilterHttpPortOp
    }
    STATUS      current
    DESCRIPTION
        "The group of objects introduced in SROS Release 15.0 for Application
         Assurance support for Application Filter on Nokia systems."
    ::= { tmnxBsxGroupsV15v0 5 }

tmnxBsxPortListV15v0ObjGrp       OBJECT-GROUP
    OBJECTS     {
        tmnxBsxPortListRowStatus,
        tmnxBsxPortListRowLastChange,
        tmnxBsxPortListDescription,
        tmnxBsxPortLow,
        tmnxBsxPortHigh,
        tmnxBsxPortRowStatus,
        tmnxBsxAppFilterServerPortList,
        tmnxBsxAppFilterHttpPortList
    }
    STATUS      current
    DESCRIPTION
        "The group of objects introduced in SROS Release 15.0 for Application
         Assurance support for Application Port List on Nokia systems."
    ::= { tmnxBsxGroupsV15v0 6 }

tmnxBsxDEMCngParamsV15v0ObjGrp   OBJECT-GROUP
    OBJECTS     {
        tmnxBsxPolicerCongestedAnlPIR,
        tmnxBsxPolicerCongestedAnlCIR,
        tmnxBsxPolicerCongestedAnlMBS,
        tmnxBsxPolicerCongestedAnlCBS
    }
    STATUS      current
    DESCRIPTION
        "The group of objects introduced in SROS Release 15.0 for Application
         Assurance support for DEM ANL congestion parameters on Nokia systems."
    ::= { tmnxBsxGroupsV15v0 8 }

tmnxBsxPortListRefsV15v0ObjGrp   OBJECT-GROUP
    OBJECTS     {
        tmnxBsxAqpMatchSrcPortList,
        tmnxBsxAqpMatchDstPortList,
        tmnxBsxSessFltrParamsSrcPortList,
        tmnxBsxSessFltrParamsDstPortList
    }
    STATUS      current
    DESCRIPTION
        "The group of objects introduced in SROS Release 15.0 for Application
         Assurance support for port-list feature extension on Nokia systems."
    ::= { tmnxBsxGroupsV15v0 9 }

tmnxBsxCflowdExpOvdObjGrp        OBJECT-GROUP
    OBJECTS     {
        tmnxBsxCflowdExpOvdMode,
        tmnxBsxCflowdExpOvdPrefix
    }
    STATUS      current
    DESCRIPTION
        "The group of objects introduced in SROS Release 15.0 for Application
         Assurance support for cflowd export override on Nokia systems."
    ::= { tmnxBsxGroupsV15v0 10 }

tmnxBsxGroupsV16v0               OBJECT IDENTIFIER ::= { tmnxBsxGroups 30 }

tmnxBsxDnsIpCacheProxy16v0ObjGrp OBJECT-GROUP
    OBJECTS     {
        tmnxBsxDnsIpCacheProxyRowLastCh,
        tmnxBsxDnsIpCacheProxyRowStatus,
        tmnxBsxDnsIpCacheStatPrxyMtchCnt,
        tmnxBsxDnsIpCacheProxyLastCTime
    }
    STATUS      current
    DESCRIPTION
        "The group of objects introduced in SROS Release 16.0 for Application
         Assurance support for DNS Domain IP Cache Proxy IP addresses on Nokia
         systems."
    ::= { tmnxBsxGroupsV16v0 2 }

tmnxBsxHttpEnrichObjGrp          OBJECT-GROUP
    OBJECTS     {
        tmnxBsxHttpEnrichFieldCertProf
    }
    STATUS      current
    DESCRIPTION
        "The group of objects introduced in SROS Release 16.0 for Application
         Assurance support for HTTP enrichment on Nokia systems."
    ::= { tmnxBsxGroupsV16v0 3 }

tmnxBsxCertProfileObjGrp         OBJECT-GROUP
    OBJECTS     {
        tmnxBsxCertProfileRowStatus,
        tmnxBsxCertProfileLastChgd,
        tmnxBsxCertProfileAdminState,
        tmnxBsxCertProfileOperState,
        tmnxBsxCertProfileOperFlags,
        tmnxBsxCertProfileCertFile,
        tmnxBsxCertProfileDescription,
        tmnxBsxCertProfileReferenceCount
    }
    STATUS      current
    DESCRIPTION
        "The group of objects introduced in SROS Release 16.0 for Application
         Assurance support for AA certificate profile on Nokia systems."
    ::= { tmnxBsxGroupsV16v0 4 }

tmnxBsxCertProfileNotifyObjsGrp  OBJECT-GROUP
    OBJECTS     {
        tmnxBsxNotifyCertProfileName,
        tmnxBsxNotifyCertProfOperState
    }
    STATUS      current
    DESCRIPTION
        "The group of notification objects introduced in SROS Release 16.0 for
         Application Assurance support for AA certificate profile on Nokia
         systems."
    ::= { tmnxBsxGroupsV16v0 5 }

tmnxBsxCertProfileNotifyGrp      NOTIFICATION-GROUP
    NOTIFICATIONS {
        tmnxBsxCertProfileOperStateChngd
    }
    STATUS      current
    DESCRIPTION
        "The group of notifications introduced in SROS Release 16.0 for
         Application Assurance support for AA certificate profile on Nokia
         systems."
    ::= { tmnxBsxGroupsV16v0 6 }

tmnxBsxSubCongDetObjGrp          OBJECT-GROUP
    OBJECTS     {
        tmnxBsxSubCongDetectRowLastChg,
        tmnxBsxSubRttThreshold,
        tmnxBsxSubRttThresholdTolerance,
        tmnxBsxSubCongDetectAdminState,
        tmnxBsxPolicerCongestedPIR,
        tmnxBsxPolicerCongestedCIR,
        tmnxBsxPolicerCongestedMBS,
        tmnxBsxPolicerCongestedCBS
    }
    STATUS      current
    DESCRIPTION
        "The group of objects introduced in SROS Release 16.0 for Application
         Assurance support for AA subscriber congestion detection feature on
         Nokia systems."
    ::= { tmnxBsxGroupsV16v0 8 }

tmnxBsxDEMObsoletedObjGrp        OBJECT-GROUP
    OBJECTS     {
        tmnxBsxPolicerCongestedAnlPIR,
        tmnxBsxPolicerCongestedAnlCIR,
        tmnxBsxPolicerCongestedAnlMBS,
        tmnxBsxPolicerCongestedAnlCBS
    }
    STATUS      current
    DESCRIPTION
        "The group of objects obsoleted in SROS Release 16.0 for Application
         Assurance support for DEM ANL congestion parameters on Nokia systems."
    ::= { tmnxBsxGroupsV16v0 9 }

tmnxBsxSubCongRenamedObjGrp      OBJECT-GROUP
    OBJECTS     {
        tmnxBsxPolicerCongestedPIR,
        tmnxBsxPolicerCongestedCIR,
        tmnxBsxPolicerCongestedMBS,
        tmnxBsxPolicerCongestedCBS
    }
    STATUS      current
    DESCRIPTION
        "The group of objects introduced in SROS Release 16.0 for Application
         Assurance support for AA subscriber congestion detection feature on
         Nokia systems."
    ::= { tmnxBsxGroupsV16v0 10 }

tmnxBsxHttpsRedirObsoletedObjGrp OBJECT-GROUP
    OBJECTS     {
        tmnxBsxHttpRedirCapHttpsEnbld
    }
    STATUS      current
    DESCRIPTION
        "The group of objects introduced in SROS Release 16.0 for Application
         Assurance support for Captive Redirect object obsoletion on Nokia
         systems."
    ::= { tmnxBsxGroupsV16v0 11 }

tmnxBsxHttpsRedirHttpsRdrObjGrp  OBJECT-GROUP
    OBJECTS     {
        tmnxBsxHttpRedirHttpsRedirEnbld
    }
    STATUS      current
    DESCRIPTION
        "The group of objects introduced in SROS Release 16.0 for Application
         Assurance support for HTTPS Redirect enhancement on Nokia systems."
    ::= { tmnxBsxGroupsV16v0 12 }

tmnxBsxGrpStatHttpsRedirObjGrp   OBJECT-GROUP
    OBJECTS     {
        tmnxBsxGrpStatusOctsGenHttpRedir,
        tmnxBsxGrpStatusPktsGenHttpRedir
    }
    STATUS      current
    DESCRIPTION
        "The group of objects introduced in SROS Release 16.0 for Application
         Assurance support for HTTPS Redirect stats enhancement on Nokia
         systems."
    ::= { tmnxBsxGroupsV16v0 13 }

tmnxBsxOverloadSubQuarantineGrp  OBJECT-GROUP
    OBJECTS     {
        tmnxBsxIsaAaGrpOvrldSubQuarAdmin,
        tmnxBsxAaSubQuarantined,
        tmnxBsxGrpStatusSubsQuarantined
    }
    STATUS      current
    DESCRIPTION
        "The group of objects for Overload Sub Quarantine support on Nokia SROS
         systems introduced in release 16.0."
    ::= { tmnxBsxGroupsV16v0 15 }

tmnxBsxLateIcapBlockObjGrp       OBJECT-GROUP
    OBJECTS     {
        tmnxBsxUrlFltrStatsIcapLRPktsDsc,
        tmnxBsxUrlFltrStatsIcapLRBytsDsc
    }
    STATUS      current
    DESCRIPTION
        "The group of objects introduced in SROS Release 16.0 for Application
         Assurance support for the Late ICAP block enhancement on Nokia
         systems."
    ::= { tmnxBsxGroupsV16v0 16 }

tmnxBsxGrpStatusDirectionObjGrp  OBJECT-GROUP
    OBJECTS     {
        tmnxBsxGrpStatusPktsInToSub,
        tmnxBsxGrpStatusPktsInFrSub,
        tmnxBsxGrpStatusOctsInToSub,
        tmnxBsxGrpStatusOctsInFrSub,
        tmnxBsxGrpStatusPktDisCngInToSub,
        tmnxBsxGrpStatusPktDisCngInFrSub,
        tmnxBsxGrpStatusOctDisCngInToSub,
        tmnxBsxGrpStatusOctDisCngInFrSub,
        tmnxBsxGrpStatusPktInPChpErToSub,
        tmnxBsxGrpStatusPktInPChpErFrSub,
        tmnxBsxGrpStatusPktsToMdaToSub,
        tmnxBsxGrpStatusPktsToMdaFrSub,
        tmnxBsxGrpStatusPktsInMdaToSub,
        tmnxBsxGrpStatusPktsInMdaFrSub,
        tmnxBsxGrpStatusPkDisCngMdaToSub,
        tmnxBsxGrpStatusPkDisCngMdaFrSub,
        tmnxBsxGrpStatusPktDiscErrToSub,
        tmnxBsxGrpStatusPktDiscErrFrSub,
        tmnxBsxGrpStatusPktDiscPlcyToSub,
        tmnxBsxGrpStatusPktDiscPlcyFrSub,
        tmnxBsxGrpStatusOcDisCngMdaToSub,
        tmnxBsxGrpStatusOcDisCngMdaFrSub,
        tmnxBsxGrpStatusOctDiscErrToSub,
        tmnxBsxGrpStatusOctDiscErrFrSub,
        tmnxBsxGrpStatusOctDiscPlcyToSub,
        tmnxBsxGrpStatusOctDiscPlcyFrSub,
        tmnxBsxGrpStatusPktSzIncPkToSub,
        tmnxBsxGrpStatusPktSzIncPkFrSub,
        tmnxBsxGrpStatusPktSzDecPkToSub,
        tmnxBsxGrpStatusPktSzDecPkFrSub,
        tmnxBsxGrpStatusPktSzIncOcToSub,
        tmnxBsxGrpStatusPktSzIncOcFrSub,
        tmnxBsxGrpStatusPktSzDecOcToSub,
        tmnxBsxGrpStatusPktSzDecOcFrSub,
        tmnxBsxGrpStatusPktPlcyBypsToSub,
        tmnxBsxGrpStatusPktPlcyBypsFrSub,
        tmnxBsxGrpStatusOctPlcyBypsToSub,
        tmnxBsxGrpStatusOctPlcyBypsFrSub,
        tmnxBsxGrpStatusPkGenHttpRdToSub,
        tmnxBsxGrpStatusPkGenHttpRdFrSub,
        tmnxBsxGrpStatusOcGenHttpRdToSub,
        tmnxBsxGrpStatusOcGenHttpRdFrSub,
        tmnxBsxGrpStatusPktsFromMdaToSub,
        tmnxBsxGrpStatusPktsFromMdaFrSub,
        tmnxBsxGrpStatusOctsFromMdaToSub,
        tmnxBsxGrpStatusOctsFromMdaFrSub,
        tmnxBsxGrpStatusPkDisConOutToSub,
        tmnxBsxGrpStatusPkDisConOutFrSub,
        tmnxBsxGrpStatusOcDisConOutToSub,
        tmnxBsxGrpStatusOcDisConOutFrSub,
        tmnxBsxGrpStatusPktOutPChErToSub,
        tmnxBsxGrpStatusPktOutPChErFrSub,
        tmnxBsxGrpStatusPktsOutToSub,
        tmnxBsxGrpStatusPktsOutFrSub,
        tmnxBsxGrpStatusOctsOutToSub,
        tmnxBsxGrpStatusOctsOutFrSub,
        tmnxBsxGrpStatusPktCutThrough,
        tmnxBsxGrpStatusPktCutThrouToSub,
        tmnxBsxGrpStatusPktCutThrouFrSub,
        tmnxBsxGrpStatusOctCutThrough,
        tmnxBsxGrpStatusOctCutThrouToSub,
        tmnxBsxGrpStatusOctCutThrouFrSub,
        tmnxBsxGrpStatusOctsToMdaToSub,
        tmnxBsxGrpStatusOctsToMdaFrSub,
        tmnxBsxGrpStatusOctsInMdaToSub,
        tmnxBsxGrpStatusOctsInMdaFrSub
    }
    STATUS      current
    DESCRIPTION
        "The group of objects supporting directions to-sub and from-sub of BSX
         group status in SROS Release 16.0."
    ::= { tmnxBsxGroupsV16v0 17 }

tmnxBsxHttpCallingLineIdObjGrp   OBJECT-GROUP
    OBJECTS     {
        tmnxBsxHttpEnrchFldCallingLineId,
        tmnxBsxHttpEnrichSessionsDropped
    }
    STATUS      current
    DESCRIPTION
        "The group of objects introduced in SROS Release 16.0 for Application
         Assurance support for HTTP header anti-spoof of x-up-calling-line-id
         on Nokia systems."
    ::= { tmnxBsxGroupsV16v0 19 }

tmnxBsxTetheringDetectionObjGrp  OBJECT-GROUP
    OBJECTS     {
        tmnxBsxPlcyDefTetherChargeGrp
    }
    STATUS      current
    DESCRIPTION
        "The group of objects introduced for supporting tethering detection
         enhancement on Nokia series routers."
    ::= { tmnxBsxGroupsV16v0 20 }

tmnxBsxOverloadSubQuarNotifyGrp  NOTIFICATION-GROUP
    NOTIFICATIONS {
        tmnxBsxSubQuarantined,
        tmnxBsxSubQuarantinedClear
    }
    STATUS      current
    DESCRIPTION
        "The group of notifications to support Application Assurance Overload
         Subscriber Quarantine on Nokia systems."
    ::= { tmnxBsxGroupsV16v0 21 }

tmnxBsxRATTypeObjGrp             OBJECT-GROUP
    OBJECTS     {
        tmnxBsxHttpEnrichRATString
    }
    STATUS      current
    DESCRIPTION
        "The group of objects for supporting RAT type  mapping on Nokia
         series routers."
    ::= { tmnxBsxGroupsV16v0 22 }

tmnxBsxShallowInspectionGrp      OBJECT-GROUP
    OBJECTS     {
        tmnxBsxAaGrpPartShallowInspect
    }
    STATUS      current
    DESCRIPTION
        "The group of objects supporting shallow inspection on Nokia series
         routers."
    ::= { tmnxBsxGroupsV16v0 23 }

tmnxBsxTcpAdvFctGrp              OBJECT-GROUP
    OBJECTS     {
        tmnxBsxIsaAaGrpSRTcpAdvFnSize,
        tmnxBsxGrpMdaSRTcpAdvFnBufMem,
        tmnxBsxGrpMdaSRTcpAdvFnBufUtil,
        tmnxBsxGrpMdaSRTcpAdvFnSessUtil
    }
    STATUS      current
    DESCRIPTION
        "The group of objects was created as part of the MP-TCP
         Proxy feature development.  They are relevant for any
         TCP Advanced functions (e.g. TCP-Optimizer, MP-TCP Proxy,
         or (in later releases) HTTP Proxy on Nokia
         series routers."
    ::= { tmnxBsxGroupsV16v0 24 }

tmnxBsxTcpOptEnhanceGrp          OBJECT-GROUP
    OBJECTS     {
        tmnxBsxGrpMdaAdFnMxConcSesTcpo
    }
    STATUS      current
    DESCRIPTION
        "The group of objects was created as part of the MP-TCP Proxy
         feature development.  They are relevant for TCP-Optimizer
         on the supporting shallow inspection on Nokia series routers."
    ::= { tmnxBsxGroupsV16v0 25 }

tmnxBsxTlsExtensionInsert2ObjGrp OBJECT-GROUP
    OBJECTS     {
        tmnxBsxAqpActTlsEnrichName
    }
    STATUS      current
    DESCRIPTION
        "The group of objects introduced in SROS Release 16.0 for Application
         Assurance support for TLS extension insertions on Nokia systems."
    ::= { tmnxBsxGroupsV16v0 26 }

tmnxBsxGroupsV17v0               OBJECT IDENTIFIER ::= { tmnxBsxGroups 31 }

tmnxBsxTcpOptNetObjGrp           OBJECT-GROUP
    OBJECTS     {
        tmnxBsxTcpOptStatSessUnLowNetRtt,
        tmnxBsxTcpOptNetworkRttThreshold
    }
    STATUS      current
    DESCRIPTION
        "The group of objects introduced in SROS Release 17.0 for Application
         Assurance support for TCP Optimization on Nokia systems."
    ::= { tmnxBsxGroupsV17v0 1 }

tmnxBsxFlowAttrObjGrp            OBJECT-GROUP
    OBJECTS     {
        tmnxBsxAqpFlowAttrRowStatus,
        tmnxBsxAqpFlowAttrRowLstChg,
        tmnxBsxAqpFlowAttrConf,
        tmnxBsxAqpFlowAttrOperator,
        tmnxBsxStatFlowAttrConfBinName,
        tmnxBsxFlowAttrStatsDiscontTime,
        tmnxBsxStatFlowAttrOctsFmSb,
        tmnxBsxStatFlowAttrPktsFmSb,
        tmnxBsxStatFlowAttrFlwsFmSb,
        tmnxBsxStatFlowAttrOctsToSb,
        tmnxBsxStatFlowAttrPktsToSb,
        tmnxBsxStatFlowAttrFlwsToSb,
        tmnxBsxIsaAaGrpFlowAttrRowStatus,
        tmnxBsxIsaAaGrpFlowAttrRowLastCh
    }
    STATUS      current
    DESCRIPTION
        "The group of objects introduced in SROS Release 17.0 for Application
         Assurance support for flow attributes on Nokia systems."
    ::= { tmnxBsxGroupsV17v0 4 }

tmnxBsxPartitionObsoleteGroup    OBJECT-GROUP
    OBJECTS     {
        tmnxBsxIsaAaGrpPartitions
    }
    STATUS      current
    DESCRIPTION
        "The group of objects in Application Assurance obsoleted with the
         removal of non partitioned groups on Nokia series routers."
    ::= { tmnxBsxGroupsV17v0 6 }

tmnxBsxIsaAaVmTrafDistribByIpGrp OBJECT-GROUP
    OBJECTS     {
        tmnxBsxIsaAaGrpVmTrafficDistByIp
    }
    STATUS      current
    DESCRIPTION
        "The group of objects introduced in SROS Release 17.0 for Application
         Assurance and ISA support of packet IP address inclusion in the
         traffic distribution mechanism."
    ::= { tmnxBsxGroupsV17v0 7 }

tmnxBsxSessionRedirectL3L4Group  OBJECT-GROUP
    OBJECTS     {
        tmnxBsxSessFltrParamsReDirPort,
        tmnxBsxSessFltrParamsReDirAddr,
        tmnxBsxSessFltrParamsReDirAdrTyp
    }
    STATUS      current
    DESCRIPTION
        "The group of objects introduced in SROS Release 17.0 for Application
         Assurance support of session remarking of destaintion IP address
         and/or destination tcp/udp port."
    ::= { tmnxBsxGroupsV17v0 8 }

tmnxBsxAbandonTcpOptGroup        OBJECT-GROUP
    OBJECTS     {
        tmnxBsxAqpActAbandonTcpOpt,
        tmnxBsxTcpOptStatSessPlcyAbandon
    }
    STATUS      current
    DESCRIPTION
        "The group of objects supporting abandoning TCP optimizations after
         identifications in SROS Release 17.0"
    ::= { tmnxBsxGroupsV17v0 9 }

tmnxBsxCflowConfigFieldsGroup    OBJECT-GROUP
    OBJECTS     {
        tmnxBsxCflowdRecTmplAdmin,
        tmnxBsxCflowdRecTmplFldsSelType,
        tmnxBsxCflowdRecTmplRowLstChg,
        tmnxBsxCflowdRecFldRowStatus,
        tmnxBsxCflowdRecFieldName,
        tmnxBsxCflowdRecFieldDescr,
        tmnxBsxCflowdRecFieldSize,
        tmnxBsxCflowdRecFieldId,
        tmnxBsxCflowdRecFieldEnterprise,
        tmnxBsxCflowdRecFldRowLstChg,
        tmnxBsxCflowdTemplateLastChTim,
        tmnxBsxCflowdTmplFieldLastChTim
    }
    STATUS      current
    DESCRIPTION
        "The group of objects supporting configurable cflowd record fileds for
         each template in SROS Release 17.0"
    ::= { tmnxBsxGroupsV17v0 10 }

tmnxBsxTetherStateObjGrp         OBJECT-GROUP
    OBJECTS     {
        tmnxBsxAqpMatchAaSubTetherState,
        tmnxBsxAaSubSumTetherState
    }
    STATUS      current
    DESCRIPTION
        "The group of objects introduced in Release 17.0 for Application
         Assurance support for Subscriber Tethering State on Nokia SROS
         systems. "
    ::= { tmnxBsxGroupsV17v0 11 }

tmnxBsxTetherDetectObjGrp        OBJECT-GROUP
    OBJECTS     {
        tmnxBsxTetherSingleDevRowStatus,
        tmnxBsxTetherSingleDeviceExpTTL
    }
    STATUS      current
    DESCRIPTION
        "The group of objects introduced in SROS Release 17.0 for Application
         Assurance support for Tethering Detection on Nokia systems."
    ::= { tmnxBsxGroupsV17v0 12 }

tmnxBsxUrlFltrWebServiceGroup    OBJECT-GROUP
    OBJECTS     {
        tmnxBsxWebServCategoryName,
        tmnxBsxWebServCategRowLastChg,
        tmnxBsxWebServCategDescr,
        tmnxBsxUrlFltrWebServClassifyId,
        tmnxBsxUrlFltrWebServFqdn,
        tmnxBsxUrlFltrWebServDnsAddrType,
        tmnxBsxUrlFltrWebServDnsAddr,
        tmnxBsxUrlFltrWebServDefaultProf,
        tmnxBsxUrlFilterWebServPortVlan,
        tmnxBsxUrlFltrWebServCategSetId,
        tmnxBsxUrlFltWebSerProfRowStatus,
        tmnxBsxUrlFltWebSerProfDescr,
        tmnxBsxUrlFltWebSerProfRoLstChg,
        tmnxBsxUrlFltWebServCategRowSt,
        tmnxBsxUrlFltWebServCategName,
        tmnxBsxUrlFltWebSerCategRoLstChg,
        tmnxBsxUrlFltrWsPrfListLastCTime,
        tmnxBsxUrlFltrWsCatListLastCTime,
        tmnxBsxUrlFltrStatsWebSvLateRsp,
        tmnxBsxUrlFltrStatsWebSvLRPktDsc,
        tmnxBsxUrlFltrStatsWebSvLRBytDsc,
        tmnxBsxUrlFltrStatsWebServReqs,
        tmnxBsxUrlFltrStatsWebServReqErr,
        tmnxBsxUrlFltrWebServStatsRndTp,
        tmnxBsxUrlFltrWebSvStatsReqRate,
        tmnxBsxUrlFltrWebSvStatsConnTot,
        tmnxBsxUrlFltrWebSvStatsConnEst,
        tmnxBsxUrlFltrWebSerMaxCacheSize,
        tmnxBsxUrlFltrWebSvDnsOperState,
        tmnxBsxUrlFltrWebSvDnsOperFlags,
        tmnxBsxIsaAaGrpSRWebServCachSize,
        tmnxBsxWebUrlClassifierDescr,
        tmnxBsxWebUrlCategSetRowLastChg,
        tmnxBsxUrlFltrWebServCacheSize,
        tmnxBsxUrlFltrWebSerStatCacheHit,
        tmnxBsxUrlFltrWebSerStatCacheMis
    }
    STATUS      current
    DESCRIPTION
        "The group of objects supporting URL filter web service in SROS Release
         17.0"
    ::= { tmnxBsxGroupsV17v0 13 }

tmnxBsxFlowAttrObsoleteGroup     OBJECT-GROUP
    OBJECTS     {
        tmnxBsxIsaAaGrpFlowAttributes
    }
    STATUS      current
    DESCRIPTION
        "The group of objects in Application Assurance obsoleted in SROS
         Release 19.0."
    ::= { tmnxBsxGroupsV17v0 15 }

tmnxBsxGtpStatefulFirwallObjGrp  OBJECT-GROUP
    OBJECTS     {
        tmnxBsxIsaAaGrpGtpTunnelDb,
        tmnxBsxGtpcInspection,
        tmnxBsxGtpFltrGtpInGtp,
        tmnxBsxGtpFltrValidateSeqNumber,
        tmnxBsxGtpFltrValidateSrcIpAddr,
        tmnxBsxGtpFltrImsiApnDefAction,
        tmnxBsxGtpFltrValidateGtpTunnels,
        tmnxBsxGtpFltrImsiApnRowStatus,
        tmnxBsxGtpFltrMatchImsiPrefix,
        tmnxBsxGtpFltrMatchApn,
        tmnxBsxGtpFltrMatchSrcGsnAddr,
        tmnxBsxGtpFltrMatchSrcGsnAddrTyp,
        tmnxBsxGtpFltrMatchSrcGsnAddrLen,
        tmnxBsxGtpFltrMatchSrcIpPfxList,
        tmnxBsxGtpFltrImsiApnEntryAction,
        tmnxBsxGtpFltrImsiApnLastChgTime,
        tmnxBsxGtpFltrV2MsgLastChgTime,
        tmnxBsxGtpFltrV2MsgDefAction,
        tmnxBsxGtpFltrV2MsgValue,
        tmnxBsxGtpFltrV2MsgRowLastChg,
        tmnxBsxGtpFltrV2MsgRowStatus,
        tmnxBsxGtpFltrV2MsgAction,
        tmnxBsxGtpFilterImsiApnLastChg,
        tmnxBsxGtpFltrStatsPkDndV2MsgTyp,
        tmnxBsxGtpFltrStatsPkDndImsiApn,
        tmnxBsxGtpFltrStatsPkDndInvSeqNo,
        tmnxBsxGtpFltrStatsPkDndInvTeid,
        tmnxBsxGtpFltrStatsPkDndInvSubIp,
        tmnxBsxGtpFltrStatsPkDndGtpInGtp,
        tmnxBsxGtpFltrStatsPkDndMandIE,
        tmnxBsxGtpFltrStatsPkDndTunDbRes,
        tmnxBsxGtpEventLogAction,
        tmnxBsxGtpFltrEventLogAction,
        tmnxBsxGrpMdaSRGtpTunDbSize,
        tmnxBsxGrpMdaSRGtpTunDbUtil,
        tmnxBsxGtpFltrDefTunnelEpLimit,
        tmnxBsxGtpFltrStatsPkDndTunEpLmt,
        tmnxBsxIsaAaGrpVmTrafficDistTeid
    }
    STATUS      current
    DESCRIPTION
        "The group of objects introduced in SROS Release 17.0 for Application
         Assurance support for stateful GTP firewall on Nokia systems."
    ::= { tmnxBsxGroupsV17v0 16 }

tmnxBsxUrlFltrWebServNotifGrp    NOTIFICATION-GROUP
    NOTIFICATIONS {
        tmnxBsxUrlFltrWebServOprStateChg
    }
    STATUS      current
    DESCRIPTION
        "The group of notification objects to support URL Filter Web Service on
         Nokia Systems."
    ::= { tmnxBsxGroupsV17v0 17 }

tmnxBsxIsaAaVmTrafDistribTeidGrp OBJECT-GROUP
    OBJECTS     {
        tmnxBsxIsaAaGrpVmTrafficDistTeid
    }
    STATUS      obsolete
    DESCRIPTION
        "The group of objects introduced in SROS Release 19.0 for Application
         Assurance and ISA support of GTP packet TEID inclusion in the traffic
         distribution mechanism."
    ::= { tmnxBsxGroupsV17v0 20 }

tmnxBsxTlsTrafficStatsObjGrp     OBJECT-GROUP
    OBJECTS     {
        tmnxBsxTlsStatDiscontTime,
        tmnxBsxTlsStatQuicOctsAdm,
        tmnxBsxTlsStatQuicOctsDny,
        tmnxBsxTlsStatQuicPktsAdm,
        tmnxBsxTlsStatQuicPktsDny,
        tmnxBsxTlsStatQuicFlwsDny,
        tmnxBsxTlsStatQuicFlwsAdm,
        tmnxBsxTlsStatQuicEsniOctsAdm,
        tmnxBsxTlsStatQuicEsniOctsDny,
        tmnxBsxTlsStatQuicEsniPktsAdm,
        tmnxBsxTlsStatQuicEsniPktsDny,
        tmnxBsxTlsStatQuicEsniFlwsDny,
        tmnxBsxTlsStatQuicEsniFlwsAdm,
        tmnxBsxTlsStatQuicExistOctsAdm,
        tmnxBsxTlsStatQuicExistOctsDny,
        tmnxBsxTlsStatQuicExistPktsAdm,
        tmnxBsxTlsStatQuicExistPktsDny,
        tmnxBsxTlsStatQuicExistFlwsDny,
        tmnxBsxTlsStatQuicExistFlwsAdm,
        tmnxBsxTlsStatQuicUnknwnOctsAdm,
        tmnxBsxTlsStatQuicUnknwnOctsDny,
        tmnxBsxTlsStatQuicUnknwnPktsAdm,
        tmnxBsxTlsStatQuicUnknwnPktsDny,
        tmnxBsxTlsStatQuicUnknwnFlwsDny,
        tmnxBsxTlsStatQuicUnknwnFlwsAdm,
        tmnxBsxTlsStatTls10OctsAdm,
        tmnxBsxTlsStatTls10OctsDny,
        tmnxBsxTlsStatTls10PktsAdm,
        tmnxBsxTlsStatTls10PktsDny,
        tmnxBsxTlsStatTls10FlwsDny,
        tmnxBsxTlsStatTls10FlwsAdm,
        tmnxBsxTlsStatTls11OctsAdm,
        tmnxBsxTlsStatTls11OctsDny,
        tmnxBsxTlsStatTls11PktsAdm,
        tmnxBsxTlsStatTls11PktsDny,
        tmnxBsxTlsStatTls11FlwsDny,
        tmnxBsxTlsStatTls11FlwsAdm,
        tmnxBsxTlsStatTls12OctsAdm,
        tmnxBsxTlsStatTls12OctsDny,
        tmnxBsxTlsStatTls12PktsAdm,
        tmnxBsxTlsStatTls12PktsDny,
        tmnxBsxTlsStatTls12FlwsDny,
        tmnxBsxTlsStatTls12FlwsAdm,
        tmnxBsxTlsStatTls13OctsAdm,
        tmnxBsxTlsStatTls13OctsDny,
        tmnxBsxTlsStatTls13PktsAdm,
        tmnxBsxTlsStatTls13PktsDny,
        tmnxBsxTlsStatTls13FlwsDny,
        tmnxBsxTlsStatTls13FlwsAdm,
        tmnxBsxTlsStatTls13EsniOctsAdm,
        tmnxBsxTlsStatTls13EsniOctsDny,
        tmnxBsxTlsStatTls13EsniPktsAdm,
        tmnxBsxTlsStatTls13EsniPktsDny,
        tmnxBsxTlsStatTls13EsniFlwsDny,
        tmnxBsxTlsStatTls13EsniFlwsAdm,
        tmnxBsxTlsStatTlsExistOctsAdm,
        tmnxBsxTlsStatTlsExistOctsDny,
        tmnxBsxTlsStatTlsExistPktsAdm,
        tmnxBsxTlsStatTlsExistPktsDny,
        tmnxBsxTlsStatTlsExistFlwsDny,
        tmnxBsxTlsStatTlsExistFlwsAdm,
        tmnxBsxTlsStatTlsUnknownOctsAdm,
        tmnxBsxTlsStatTlsUnknownOctsDny,
        tmnxBsxTlsStatTlsUnknownPktsAdm,
        tmnxBsxTlsStatTlsUnknownPktsDny,
        tmnxBsxTlsStatTlsUnknownFlwsDny,
        tmnxBsxTlsStatTlsUnknownFlwsAdm
    }
    STATUS      current
    DESCRIPTION
        "The group of objects introduced in Release 19.0 for Application
         Assurance support for AA Partition TLS Traffic Statistics on Nokia
         SROS systems."
    ::= { tmnxBsxGroupsV17v0 22 }

tmnxBsxGroupsV20v0               OBJECT IDENTIFIER ::= { tmnxBsxGroups 32 }

tmnxBsxUrlListEnhancementObjGrp  OBJECT-GROUP
    OBJECTS     {
        tmnxBsxUrlListHostExpressions
    }
    STATUS      current
    DESCRIPTION
        "The group of objects introduced in SROS Release 20.0 for Application
         Assurance support for URL list with host expression support on Nokia
         systems."
    ::= { tmnxBsxGroupsV20v0 1 }

tmnxBsxUrlFilterEnhancementGrp   OBJECT-GROUP
    OBJECTS     {
        tmnxBsxUrlFilterIcapDefAction,
        tmnxBsxUrlFilterIcapDefHttpRedir,
        tmnxBsxUrlFilterIcapHttpRedirObj,
        tmnxBsxUrlFilterWebDefAction,
        tmnxBsxUrlFilterWebDefHttpRedir,
        tmnxBsxUrlFilterWebSerHttpRedir,
        tmnxBsxUrlFilterUrlAllowList,
        tmnxBsxUrlFltrApplyFuncBehavior,
        tmnxBsxUrlFilterBlListDefAction,
        tmnxBsxUrlFilterBlListDefHtRedir,
        tmnxBsxUrlFilterBlListHttpRedir,
        tmnxBsxUrlListRegExprNumEntries,
        tmnxBsxUrlFltrUrlListStatLkup,
        tmnxBsxUrlFltrUrlListStatMatch,
        tmnxBsxUrlFltrUrlListStatDefault,
        tmnxBsxUrlFltrStatsWebSvRspAllow,
        tmnxBsxUrlFltrStatsWebSvRspRedir,
        tmnxBsxUrlFltrStatsWebSvRspBlock,
        tmnxBsxUrlFltrStatsWebSvDefault,
        tmnxBsxUrlFltrStatsAllowListLkup,
        tmnxBsxUrlFltrStatsAllowLstMatch,
        tmnxBsxUrlFltrStatsUrlAllow,
        tmnxBsxUrlFltrStatsUrlBlockRedir,
        tmnxBsxUrlFltrStatsUrlDefAction,
        tmnxBsxUrlFltrStatsIcapDefault,
        tmnxBsxUrlFltWSClassOvrdRowSt,
        tmnxBsxUrlFltWSClassOvrdUrlExpr,
        tmnxBsxUrlFltWSClassOvrdUrlCateg,
        tmnxBsxUrlFltWSClassOvrdLstChg,
        tmnxBsxUrlFltrStatsWSClassOvrHit,
        tmnxBsxUrlFltrStatsWSClassOvrMis,
        tmnxBsxUrlFltrWsClasOvrLastCTime,
        tmnxBsxUrlFltWSClassOvrdCategNam
    }
    STATUS      current
    DESCRIPTION
        "The group of objects introduced in SROS Release 20.0 for Application
         Assurance support for URL filter enhancement on Nokia systems."
    ::= { tmnxBsxGroupsV20v0 2 }

tmnxBsxCflowdFieldEncryptObjGrp  OBJECT-GROUP
    OBJECTS     {
        tmnxBsxCflowdAes128EncrptKey,
        tmnxBsxCflowdAes256EncrptKey
    }
    STATUS      current
    DESCRIPTION
        "The group of objects introduced in SROS Release 20.0 for Application
         Assurance support for transmition of encrypted dynamic cflowd fields
         on Nokia systems."
    ::= { tmnxBsxGroupsV20v0 3 }

tmnxBsxDemEnhancementsObjGrp     OBJECT-GROUP
    OBJECTS     {
        tmnxBsxSubRatRowStatus,
        tmnxBsxSubRatRowLastChg,
        tmnxBsxAnlRatRowStatus,
        tmnxBsxAnlRatRowLastChg,
        tmnxBsxSubRatRttThreshold,
        tmnxBsxAnlRatRttThreshold
    }
    STATUS      current
    DESCRIPTION
        "The group of objects supporting Application Assurance ANL/subscriber
         RAT RTT thresholds on Nokia systems."
    ::= { tmnxBsxGroupsV20v0 4 }

tmnxBsxAnlSubCongPolEnhObjGrp    OBJECT-GROUP
    OBJECTS     {
        tmnxBsxPolicerCongestedStage2PIR,
        tmnxBsxPolicerCongestedStage2CIR,
        tmnxBsxPolicerCongestedStage2MBS,
        tmnxBsxPolicerCongestedStage2CBS,
        tmnxBsxPolicerRatePercentageStg2
    }
    STATUS      current
    DESCRIPTION
        "The group of objects supporting AA ANL and subscriber congestion
         policing enhancements on Nokia series routers."
    ::= { tmnxBsxGroupsV20v0 5 }

tmnxBsxCflowdDirExpMultColObjGrp OBJECT-GROUP
    OBJECTS     {
        tmnxBsxCflowdDirExportStatDsTime,
        tmnxBsxCflowdDirExportStatRecSnt,
        tmnxBsxCflowdDirExportStatOpStat,
        tmnxBsxGrpMdaCflowdColl,
        tmnxBsxGrpMdaMgCardGroupId
    }
    STATUS      current
    DESCRIPTION
        "The group of objects introduced in SROS Release 20.0 for Application
         Assurance support for cflowd direct export multi collector where not
         all ISA-AAs within the group use the same collector on Nokia systems."
    ::= { tmnxBsxGroupsV20v0 6 }

tmnxBsxHttpEnrichRatEntryObjGrp  OBJECT-GROUP
    OBJECTS     {
        tmnxBsxHttpEnrichRATRowStatus,
        tmnxBsxHttpEnrichRATRowLastChg
    }
    STATUS      current
    DESCRIPTION
        "The group of objects for supporting row creation/deletion in
         tmnxBsxHttpEnrichRATTable."
    ::= { tmnxBsxGroupsV20v0 7 }

tmnxBsxPolicyEnhObjGrp           OBJECT-GROUP
    OBJECTS     {
        tmnxBsxAppFilterSrvAddrMaskedIp,
        tmnxBsxAppFilterSrvAddrMask,
        tmnxBsxAppFilterSrvAddrMaskType
    }
    STATUS      current
    DESCRIPTION
        "The group of objects supporting AA policy enhancements on Nokia series
         routers."
    ::= { tmnxBsxGroupsV20v0 8 }

tmnxBsxGroupsV21v0               OBJECT IDENTIFIER ::= { tmnxBsxGroups 33 }

tmnxBsxAqpMatchCharGrp           OBJECT-GROUP
    OBJECTS     {
        tmnxBsxAqpMatchCharRowLastChange,
        tmnxBsxAqpMatchCharRowStatus,
        tmnxBsxAqpMatchCharOperator,
        tmnxBsxAqpMatchCharVal
    }
    STATUS      current
    DESCRIPTION
        "The group of objects introduced in SROS Release 21.0 for Application
         Assurance application qos policy characteristic matching."
    ::= { tmnxBsxGroupsV21v0 1 }

tmnxBsxAqpCharObsoletedGrp       OBJECT-GROUP
    OBJECTS     {
        tmnxBsxAqpCharRowStatus,
        tmnxBsxAqpCharOperator,
        tmnxBsxAqpCharRowLastChange
    }
    STATUS      current
    DESCRIPTION
        "The group of objects obsoleted in SROS Release 21.0 for Application
         Assurance application qos policy characteristic matching."
    ::= { tmnxBsxGroupsV21v0 2 }

tmnxBsxAaFwaBngMobileAccessGrp   OBJECT-GROUP
    OBJECTS     {
        tmnxBsxAaSubImsi,
        tmnxBsxAaSubImei,
        tmnxBsxAaSubMsisdn,
        tmnxBsxAaSubApn,
        tmnxBsxAaSubUserLocation,
        tmnxBsxAaSubRatType,
        tmnxBsxAaSubChargingId,
        tmnxBsxAaSubBillingType,
        tmnxBsxAaSubPlmnId,
        tmnxBsxAaSubPdnGatewayAddr,
        tmnxBsxAaSubPdnGatewayAddrType
    }
    STATUS      current
    DESCRIPTION
        "The group of objects introduced in SROS Release 21.0 for Application
         Assurance FWA BNG Mobile Access."
    ::= { tmnxBsxGroupsV21v0 3 }

tmnxBsxAgentGenTablesGrp         OBJECT-GROUP
    OBJECTS     {
        tmnxBsxFlowAttrDescr,
        tmnxBsxFlowAttrId,
        tmnxBsxFlowAttrLastChange,
        tmnxBsxFlowAttrComment,
        tmnxBsxHttpEnrFieldDescr,
        tmnxBsxHttpEnrFieldAntiSpoof,
        tmnxBsxHttpEnrFieldAntiSpoofXCli,
        tmnxBsxHttpEnrFieldTls,
        tmnxBsxHttpEnrFieldSubscale,
        tmnxBsxHttpEnrFieldId,
        tmnxBsxHttpEnrFieldComment,
        tmnxBsxHttpEnrFieldLastChange,
        tmnxBsxHttpRedirErrCodeDescr,
        tmnxBsxHttpRedirErrCodeMsgSize,
        tmnxBsxHttpRedirErrCodeComment,
        tmnxBsxHttpRedirErrCodeLastChg,
        tmnxBsxHttpErrRedirTmplDescr,
        tmnxBsxHttpErrRedirTmplComment,
        tmnxBsxHttpErrRedirTmplLastChg,
        tmnxBsxHttpRedirTmplDescr,
        tmnxBsxHttpRedirTmplMacro,
        tmnxBsxHttpRedirTmplComment,
        tmnxBsxHttpRedirTmplLastChg,
        tmnxBsxHttpNotifyTmplDescr,
        tmnxBsxHttpNotifyTmplComment,
        tmnxBsxHttpNotifyTmplLastChg,
        tmnxBsxCflowdRecordFieldId,
        tmnxBsxCflowdRecordFieldSize,
        tmnxBsxCflowdRecFieldSubscale,
        tmnxBsxCflowdRecFieldEncryption,
        tmnxBsxCflowdRecFieldEncryptGrp,
        tmnxBsxCflowdRecFieldExportOpt,
        tmnxBsxCflowdRecFieldExportMand,
        tmnxBsxCflowdRecordFieldDescr,
        tmnxBsxCflowdRecFieldComment,
        tmnxBsxCflowdRecFieldLastChg,
        tmnxBsxFlowAttrLastChTime,
        tmnxBsxHttpEnrFieldLastChTime,
        tmnxBsxHttpRedirErrCodLastChTime,
        tmnxBsxHttpErrRedirTmpLastChTime,
        tmnxBsxHttpRedirTmplLastChTime,
        tmnxBsxHttpNotifyTmplLastChTime,
        tmnxBsxCflowdRecFieldLastChTime
    }
    STATUS      current
    DESCRIPTION
        "The group of objects introduced in SROS Release 21.0 for Application
         Assurance system generated tables."
    ::= { tmnxBsxGroupsV21v0 5 }

tmnxBsxGroupsV22v0               OBJECT IDENTIFIER ::= { tmnxBsxGroups 34 }

tmnxBsxWebServEnhancementsGrp    OBJECT-GROUP
    OBJECTS     {
        tmnxBsxWebServServerRowStatus,
        tmnxBsxWebServServerRowLastChg,
        tmnxBsxWebServServerDescription,
        tmnxBsxWebServServerAdminState,
        tmnxBsxWebServServerLastChgTime,
        tmnxBsxWebServServerOperState,
        tmnxBsxWebServServerOperFlags,
        tmnxBsxWebServServerStatsReqs,
        tmnxBsxWebServServerStatsReqErr,
        tmnxBsxWebServServerStatsResp,
        tmnxBsxWebServServerStatsRespErr,
        tmnxBsxWebServServerStatsRTT,
        tmnxBsxWebServServerStatsReqRate,
        tmnxBsxWebServServerStatsConnCnt,
        tmnxBsxWebServServerStatsConnEst,
        tmnxBsxGrpMdaSRWebServCacheUtil
    }
    STATUS      current
    DESCRIPTION
        "The group of objects introduced in SROS Release 22.0 for Application
         Assurance application web services enhancements."
    ::= { tmnxBsxGroupsV22v0 1 }

tmnxBsxIpIdentAssistGrp          OBJECT-GROUP
    OBJECTS     {
        tmnxBsxIpIdentAssistRowLastChg,
        tmnxBsxIpIdentAssistAdminState,
        tmnxBsxIpIdentAssistPsvDnsMon,
        tmnxBsxAaGrpPartIpIdentContrib,
        tmnxBsxAppFilterIpIdentAssist,
        tmnxBsxStatAaAppFltIpIdFlows,
        tmnxBsxStatAaAppFltIpIdOcts,
        tmnxBsxStatIpIdAsstDiscntTime,
        tmnxBsxStatIpIdAsstMax,
        tmnxBsxStatIpIdAsstActive,
        tmnxBsxStatIpIdAsstApp,
        tmnxBsxStatIpIdAsstParent,
        tmnxBsxStatIpIdAsstNoId,
        tmnxBsxStatIpIdAsstNoIdNon,
        tmnxBsxStatIpIdAsstHit,
        tmnxBsxStatIpIdAsstNoHit,
        tmnxBsxStatIpIdAsstTotMiss,
        tmnxBsxStatIpIdAsstTotHitApp,
        tmnxBsxStatIpIdAsstTotHitPar,
        tmnxBsxStatIpIdAsstTotHitNo,
        tmnxBsxStatIpIdAsstTotHitNon,
        tmnxBsxIpIdAsstPDnsSrvRowStatus,
        tmnxBsxIpIdAsstPDnsSrvRowLastCh,
        tmnxBsxIpIdAsstPDnsSrvComment,
        tmnxBsxIpIdAsStatPDnsResponses,
        tmnxBsxIpIdAsStatPDnsIgNoRvFlow,
        tmnxBsxIpIdAsStatPDnsIgWrongDir,
        tmnxBsxIpIdAsStatPDnsIgUntrustd,
        tmnxBsxIpIdAsStatPDnsRspMtch,
        tmnxBsxIpIdAsStatPDnsRspMtchIp4,
        tmnxBsxIpIdAsStatPDnsRspMtchIp6,
        tmnxBsxIpIdAsStatPDnsRspUnkn,
        tmnxBsxIpIdAsStatPDnsRspUnknIp4,
        tmnxBsxIpIdAsStatPDnsRspUnknIp6
    }
    STATUS      current
    DESCRIPTION
        "The group of objects introduced in SROS Release 22.0 for Application
         Assurance ip-address-based application identification assist."
    ::= { tmnxBsxGroupsV22v0 2 }

tmnxBsxHttpEnrEncodeEnhObjGrp    OBJECT-GROUP
    OBJECTS     {
        tmnxBsxHttpEnrichFieldMd5SaltStr,
        tmnxBsxHttpEnrAesInitialVector
    }
    STATUS      current
    DESCRIPTION
        "The group of objects introduced in SROS Release 22.0 for Application
         Assurance support for HTTP enrichment enhancements of MD5 and AES
         encode types on Nokia systems."
    ::= { tmnxBsxGroupsV22v0 3 }

tmnxBsxChrgFltrObjGrp            OBJECT-GROUP
    OBJECTS     {
        tmnxBsxChrgFltrRowStatus,
        tmnxBsxChrgFltrRowLastChange,
        tmnxBsxChrgFltrDescription,
        tmnxBsxChrgFltrAdminState,
        tmnxBsxChrgFltrMatchApplication,
        tmnxBsxChrgFltrMatchApplOp,
        tmnxBsxChrgFltrMatchAppGroup,
        tmnxBsxChrgFltrMatchAppGroupOp,
        tmnxBsxChrgFltrMatchTetherState,
        tmnxBsxChrgFltrChargingGroup,
        tmnxBsxChrgFltrFlowAttrRowStatus,
        tmnxBsxChrgFltrFlowAttrRowLstChg,
        tmnxBsxChrgFltrFlowAttrConf,
        tmnxBsxChrgFltrFlowAttrOp,
        tmnxBsxChrgFltrStatsHitCntFlows
    }
    STATUS      current
    DESCRIPTION
        "The group of objects introduced in SROS Release 22.0 for Application
         Assurance support for charging filters on Nokia systems."
    ::= { tmnxBsxGroupsV22v0 4 }

tmnxBsxGroupsV23v0               OBJECT IDENTIFIER ::= { tmnxBsxGroups 35 }

tmnxBsxTetherDetectObjGrpV23v0   OBJECT-GROUP
    OBJECTS     {
        tmnxBsxTetherTtlMonitorTcp,
        tmnxBsxTetherTtlMonitorUdp,
        tmnxBsxTetherTtlInvertMatch
    }
    STATUS      current
    DESCRIPTION
        "The group of objects introduced in SROS Release 23.0 for Application
         Assurance support of TTL-based tethering detection."
    ::= { tmnxBsxGroupsV23v0 1 }

tmnxBsxIpIdentAssistGrpV23v0     OBJECT-GROUP
    OBJECTS     {
        tmnxBsxIpIdentAssistPosAppIdEnbl,
        tmnxBsxIpIdAsStatPosGlbAppFlows,
        tmnxBsxIpIdAsStatPosGlbIgnIpIdAs,
        tmnxBsxIpIdAsStatPosGlbIgnNoExpr,
        tmnxBsxIpIdAsStatPosCacheFlow,
        tmnxBsxIpIdAsStatPosCacheFlowIp4,
        tmnxBsxIpIdAsStatPosCacheFlowIp6
    }
    STATUS      current
    DESCRIPTION
        "The group of objects introduced in SROS Release 23.0 for Application
         Assurance ip-address-based application identification assist."
    ::= { tmnxBsxGroupsV23v0 2 }

tmnxBsxGrpDistributeByIpV23v0    OBJECT-GROUP
    OBJECTS     {
        tmnxBsxIsaAaGrpDistributeByIp,
        tmnxBsxAppProfDistributeByIp,
        tmnxBsxAaSubTrafficDistByIp
    }
    STATUS      current
    DESCRIPTION
        "The group of objects introduced in SROS Release 23.* for Application
         Assurance to support distributing diverted traffic across a group of
         service adapters based on IP hash."
    ::= { tmnxBsxGroupsV23v0 5 }

tmnxBsxTcpOptPerfGrpV23v0        OBJECT-GROUP
    OBJECTS     {
        tmnxBsxTcpOptHighCpuBackoff,
        tmnxBsxTcpOptStatSessCpuAbandon,
        tmnxBsxTcpOptStatSessCpuUnopt
    }
    STATUS      current
    DESCRIPTION
        "The group of objects introduced in SROS Release 23.* for Application
         Assurance support for TCP Optimization performance configuration."
    ::= { tmnxBsxGroupsV23v0 6 }

tmnxBsxGroupsV24v0               OBJECT IDENTIFIER ::= { tmnxBsxGroups 36 }

tmnxBsxCflowdObsoletedGroupV24v0 OBJECT-GROUP
    OBJECTS     {
        tmnxBsxCflowdStatusHCUSupSSRCSt,
        tmnxBsxCflowdStatusUSupSSRCStLo,
        tmnxBsxCflowdStatusUSupSSRCStHi,
        tmnxBsxCflowdExpStatHCUSupSSRCSt,
        tmnxBsxCflowdExpStatUSupSSRCStLo,
        tmnxBsxCflowdExpStatUSupSSRCStHi
    }
    STATUS      current
    DESCRIPTION
        "The group of BSX Cflowd objects obsoleted in release 24.0 on Nokia
         SROS series systems."
    ::= { tmnxBsxGroupsV24v0 1 }

tmnxBsxAaCflowdFwaFieldsGrpV24v0 OBJECT-GROUP
    OBJECTS     {
        tmnxBsxAaSubQci,
        tmnxBsxAaSubSliceId,
        tmnxBsxAaSubMmeAmfAddr,
        tmnxBsxAaSubMmeAmfAddrType
    }
    STATUS      current
    DESCRIPTION
        "The group of objects introduced in SROS Release 24.0 for additional
         cflowd fields in Application Assurance FWA."
    ::= { tmnxBsxGroupsV24v0 2 }

tmnxBsxAaCflowdFwaMoreGrpV24v0   OBJECT-GROUP
    OBJECTS     {
        tmnxBsxAaSubPolicyRuleName
    }
    STATUS      current
    DESCRIPTION
        "The group of objects introduced in SROS Release 24.0 for even more
         cflowd fields in Application Assurance FWA."
    ::= { tmnxBsxGroupsV24v0 3 }

tmnxBsxCflowdEnhObjGrpV24v0      OBJECT-GROUP
    OBJECTS     {
        tmnxBsxCflowdSystemName
    }
    STATUS      current
    DESCRIPTION
        "The group of objects introduced in SROS Release 24.0 for Application
         Assurance support of DNS enrichment."
    ::= { tmnxBsxGroupsV24v0 6 }

tmnxBsxAaTrafficStatsGrpV24v0    OBJECT-GROUP
    OBJECTS     {
        tmnxBsxGrpStsTcpPktFrSub,
        tmnxBsxGrpStsTcpOctFrSub,
        tmnxBsxGrpStsTcpRetPktFrSub,
        tmnxBsxGrpStsTcpRetOctFrSub,
        tmnxBsxGrpStsTcpPktToSub,
        tmnxBsxGrpStsTcpOctToSub,
        tmnxBsxGrpStsTcpRetPktToSub,
        tmnxBsxGrpStsTcpRetOctToSub
    }
    STATUS      current
    DESCRIPTION
        "The group of objects introduced in SROS Release 24.0 for traffic
         statistics in Application Assurance."
    ::= { tmnxBsxGroupsV24v0 7 }

tmnxBsxNotifyPrefix              OBJECT IDENTIFIER ::= { tmnxSRNotifyPrefix 63 }

tmnxBsxNotifications             OBJECT IDENTIFIER ::= { tmnxBsxNotifyPrefix 0 }

tmnxBsxIsaAaGrpNonRedundantClear NOTIFICATION-TYPE
    OBJECTS     {
        tmnxBsxNotifyIsaAaGroupIndex,
        tmnxBsxNotifyActiveMda
    }
    STATUS      current
    DESCRIPTION
        "A tmnxBsxIsaAaGrpNonRedundantClear notification is generated when an
         ISA-AA Group has two configured MDAs and there are now two available
         MDAs."
    ::= { tmnxBsxNotifications 1 }

tmnxBsxIsaAaGrpSwitchover        NOTIFICATION-TYPE
    OBJECTS     {
        tmnxBsxNotifyIsaAaGroupIndex,
        tmnxBsxNotifyActiveMda,
        tmnxBsxNotifyIsaSlotNum,
        tmnxBsxNotifyIsaMdaNum
    }
    STATUS      current
    DESCRIPTION
        "A tmnxBsxIsaAaGrpSwitchover notification is generated when an ISA-AA
         Group has experienced a switch in activity from one ISA-AA to another."
    ::= { tmnxBsxNotifications 2 }

tmnxBsxIsaAaGrpFlowFull          NOTIFICATION-TYPE
    OBJECTS     {
        tmnxBsxNotifyIsaAaGroupIndex,
        tmnxBsxNotifyActiveMda,
        tmnxBsxNotifyIsaSlotNum,
        tmnxBsxNotifyIsaMdaNum
    }
    STATUS      current
    DESCRIPTION
        "A tmnxBsxIsaAaGrpFlowFull notification is generated when an ISA-AA
         Group has currently used greater than or equal to the percentage value
         tmnxBsxFlowFullHighWatermark of its flow records and the previous
         percentage value was less than this threshold.

         This trap is only raised once per hour.  In the case where
         there are more occurrences of this trap, a
         TIMETRA-SYSTEM-MIB::tmnxTrapDropped notification is raised."
    ::= { tmnxBsxNotifications 3 }

tmnxBsxIsaAaGrpFlowFullClear     NOTIFICATION-TYPE
    OBJECTS     {
        tmnxBsxNotifyIsaAaGroupIndex,
        tmnxBsxNotifyActiveMda,
        tmnxBsxNotifyIsaSlotNum,
        tmnxBsxNotifyIsaMdaNum
    }
    STATUS      current
    DESCRIPTION
        "A tmnxBsxIsaAaGrpFlowFullClear notification is generated when an
         ISA-AA Group has currently dropped to less than or equal to the
         percentage value tmnxBsxFlowFullLowWatermark of its flow records and
         the previous percentage value was greater than this threshold.

         This trap is only raised once per hour.  In the case where
         there are more occurrences of this trap, a
         TIMETRA-SYSTEM-MIB::tmnxTrapDropped notification is raised."
    ::= { tmnxBsxNotifications 4 }

tmnxBsxIsaAaGrpFailureV2         NOTIFICATION-TYPE
    OBJECTS     {
        tmnxBsxNotifyIsaAaGroupIndex
    }
    STATUS      current
    DESCRIPTION
        "A tmnxBsxIsaAaGrpFailureV2 notification is generated when an ISA-AA
         Group has no configured primary MDA or the number of active MDAs is
         not equal to the number of configured primary MDAs."
    ::= { tmnxBsxNotifications 5 }

tmnxBsxIsaAaGrpFailureClearV2    NOTIFICATION-TYPE
    OBJECTS     {
        tmnxBsxNotifyIsaAaGroupIndex
    }
    STATUS      current
    DESCRIPTION
        "A tmnxBsxIsaAaGrpFailureClearV2 notification is generated when an
         ISA-AA Group has at least one configured primary MDA and all
         configured MDAs are either active or standby."
    ::= { tmnxBsxNotifications 6 }

tmnxBsxIsaAaGrpNonRedundantV2    NOTIFICATION-TYPE
    OBJECTS     {
        tmnxBsxNotifyIsaAaGroupIndex
    }
    STATUS      current
    DESCRIPTION
        "A tmnxBsxIsaAaGrpNonRedundantV2 notification is generated when an
         ISA-AA Group has a configured backup MDA but there is no standby MDA
         available."
    ::= { tmnxBsxNotifications 7 }

tmnxBsxIsaAaSubLoadBalance       NOTIFICATION-TYPE
    OBJECTS     {
        tmnxBsxNotifyIsaAaGroupIndex,
        tmnxBsxNotifyActionStatus
    }
    STATUS      current
    DESCRIPTION
        "A tmnxBsxIsaAaSubLoadBalance notification is generated when a
         subscriber load-balance action for an application-assurance group
         starts and stops."
    ::= { tmnxBsxNotifications 8 }

tmnxBsxIsaAaGrpCapCostThres      NOTIFICATION-TYPE
    OBJECTS     {
        tmnxBsxNotifyActiveMda,
        tmnxBsxIsaAaGrpCapCostHighThres,
        tmnxBsxNotifyIsaSlotNum,
        tmnxBsxNotifyIsaMdaNum
    }
    STATUS      current
    DESCRIPTION
        "A tmnxBsxIsaAaGrpCapCostThres notification is generated when the
         current capacity cost for an MDA within an ISA-AA Group is greater
         than or equal to the threshold specified by
         tmnxBsxIsaAaGrpCapCostHighThres and the prior cost was less than this
         threshold."
    ::= { tmnxBsxNotifications 9 }

tmnxBsxIsaAaGrpCapCostThresClear NOTIFICATION-TYPE
    OBJECTS     {
        tmnxBsxNotifyActiveMda,
        tmnxBsxIsaAaGrpCapCostLowThres,
        tmnxBsxNotifyIsaSlotNum,
        tmnxBsxNotifyIsaMdaNum
    }
    STATUS      current
    DESCRIPTION
        "A tmnxBsxIsaAaGrpCapCostThresClear notification is generated when the
         current capacity cost for an MDA within an ISA-AA Group is less than
         or equal to the threshold specified by tmnxBsxIsaAaGrpCapCostLowThres
         and the prior cost was greater than this threshold."
    ::= { tmnxBsxNotifications 10 }

tmnxBsxAaSubscribersUnassigned   NOTIFICATION-TYPE
    OBJECTS     {
        tmnxBsxNotifyIsaAaGroupIndex
    }
    STATUS      current
    DESCRIPTION
        "A tmnxBsxAaSubscribersUnassigned notification is generated when one or
         more subscribers for a particular service-id cannot be assigned to an
         ISA-AA MDA within an Application Assurance group due to insufficient
         resources. The resources in question include service queues, AA
         subscriber counts or AA subscriber statistics.

         Unassigned subscribers will behave as specified by the fail-to mode
         configured within the Application Assurance group. Recovery from this
         condition requires the removal and recreation of the AA subscribers
         when sufficient resources become available."
    ::= { tmnxBsxNotifications 11 }

tmnxBsxAaSubscriberAcctDataLoss  NOTIFICATION-TYPE
    OBJECTS     {
        tmnxLogFileIdLogId,
        tmnxLogNotifyApInterval,
        tmnxBsxNotifyAaSubscriberType,
        tmnxBsxNotifyAaSubscriberName,
        tmnxBsxNotifyAaSubAcctLossReason
    }
    STATUS      current
    DESCRIPTION
        "A tmnxBsxAaSubscriberAcctDataLoss notification is generated
         when Application Assurance subscriber statistics cannot be
         written to the accounting file.  This can occur if the accounting
         interval expires while collecting statistics.

         When this notification is generated it signifies that the statistic
         records, for this application assurance subscriber, are missing from
         the accounting file for the indicated interval."
    ::= { tmnxBsxNotifications 12 }

tmnxBsxAaSubPolResExceeded       NOTIFICATION-TYPE
    OBJECTS     {
        tmnxBsxNotifyAaGrpPartIndex
    }
    STATUS      current
    DESCRIPTION
        "A tmnxBsxAaSubPolResExceeded notification is generated when
         Application Assurance policer resources have been exceeded for
         subscribers with the ISA-AA group and partition.

         CAUSE: Configured policy for subscribers has caused policer resources
         to be exceeded.

         EFFECT: Subscriber policing is degraded.

         RECOVERY: Recovery from this condition requires the reconfiguration of
         subscriber policy to reduce the number of policers being applied."
    ::= { tmnxBsxNotifications 13 }

tmnxBsxAaSubPolResExceededClear  NOTIFICATION-TYPE
    OBJECTS     {
        tmnxBsxNotifyAaGrpPartIndex
    }
    STATUS      current
    DESCRIPTION
        "A tmnxBsxAaSubPolResExceededClear notification is generated when
         Application Assurance policer resources are no longer exceeded for
         subscribers with the ISA-AA group and partition.

         CAUSE: Policer resources are no longer exceeded for subscribers.

         EFFECT: Subscriber policing is no longer degraded.

         RECOVERY: None."
    ::= { tmnxBsxNotifications 14 }

tmnxBsxIsaAaGrpFlowSetup         NOTIFICATION-TYPE
    OBJECTS     {
        tmnxBsxNotifyIsaAaGroupIndex,
        tmnxBsxNotifyActiveMda,
        tmnxBsxFlowSetupHighWatermark,
        tmnxBsxNotifyIsaSlotNum,
        tmnxBsxNotifyIsaMdaNum
    }
    STATUS      current
    DESCRIPTION
        "A tmnxBsxIsaAaGrpFlowSetup notification is generated when the current
         flow setup rate on the MDA in the ISA-AA group is greater than or
         equal to tmnxBsxFlowSetupHighWatermark and the prior rate was less
         than this threshold."
    ::= { tmnxBsxNotifications 15 }

tmnxBsxIsaAaGrpFlowSetupClear    NOTIFICATION-TYPE
    OBJECTS     {
        tmnxBsxNotifyIsaAaGroupIndex,
        tmnxBsxNotifyActiveMda,
        tmnxBsxFlowSetupLowWatermark,
        tmnxBsxNotifyIsaSlotNum,
        tmnxBsxNotifyIsaMdaNum
    }
    STATUS      current
    DESCRIPTION
        "A tmnxBsxIsaAaGrpFlowSetupClear notification is generated to indicate
         a prior tmnxBsxIsaAaGrpFlowSetup notification has cleared due to one
         of the following reasons:

         1. The current flow setup rate on the MDA in the ISA-AA group is less
         than or equal to tmnxBsxFlowSetupLowWatermark.

         2. The corresponding tmnxBsxIsaAaGrpFlowSetup notification has been
         disabled by raising the tmnxBsxFlowSetupHighWatermark to maximum."
    ::= { tmnxBsxNotifications 16 }

tmnxBsxIsaAaGrpPacketRate        NOTIFICATION-TYPE
    OBJECTS     {
        tmnxBsxNotifyIsaAaGroupIndex,
        tmnxBsxNotifyActiveMda,
        tmnxBsxPacketRateHighWatermark,
        tmnxBsxNotifyIsaSlotNum,
        tmnxBsxNotifyIsaMdaNum
    }
    STATUS      current
    DESCRIPTION
        "A tmnxBsxIsaAaGrpPacketRate notification is generated when the current
         packet rate on the MDA in the ISA-AA group is greater than or equal to
         the tmnxBsxPacketRateHighWatermark and the prior rate was less than
         this threshold."
    ::= { tmnxBsxNotifications 17 }

tmnxBsxIsaAaGrpPacketRateClear   NOTIFICATION-TYPE
    OBJECTS     {
        tmnxBsxNotifyIsaAaGroupIndex,
        tmnxBsxNotifyActiveMda,
        tmnxBsxPacketRateLowWatermark,
        tmnxBsxNotifyIsaSlotNum,
        tmnxBsxNotifyIsaMdaNum
    }
    STATUS      current
    DESCRIPTION
        "A tmnxBsxIsaAaGrpPacketRateClear notification is generated to indicate
         a prior tmnxBsxIsaAaGrpPacketRate notification has cleared due to one
         of the following reasons:

         1. The current packet rate on the MDA in the ISA-AA group is less than
         or equal to the tmnxBsxPacketRateLowWatermark.

         2. The corresponding tmnxBsxIsaAaGrpPacketRate notification has been
         disabled by raising the tmnxBsxPacketRateHighWatermark to maximum."
    ::= { tmnxBsxNotifications 18 }

tmnxBsxIsaAaGrpBitRate           NOTIFICATION-TYPE
    OBJECTS     {
        tmnxBsxNotifyIsaAaGroupIndex,
        tmnxBsxNotifyActiveMda,
        tmnxBsxBitRateHighWatermark,
        tmnxBsxNotifyIsaSlotNum,
        tmnxBsxNotifyIsaMdaNum
    }
    STATUS      current
    DESCRIPTION
        "A tmnxBsxIsaAaGrpBitRate notification is generated when the current
         bit rate on the MDA in the ISA-AA group is greater than or equal to
         the tmnxBsxBitRateHighWatermark and the prior rate was less than this
         threshold."
    ::= { tmnxBsxNotifications 19 }

tmnxBsxIsaAaGrpBitRateClear      NOTIFICATION-TYPE
    OBJECTS     {
        tmnxBsxNotifyIsaAaGroupIndex,
        tmnxBsxNotifyActiveMda,
        tmnxBsxBitRateLowWatermark,
        tmnxBsxNotifyIsaSlotNum,
        tmnxBsxNotifyIsaMdaNum
    }
    STATUS      current
    DESCRIPTION
        "A tmnxBsxIsaAaGrpBitRateClear notification is generated to indicate a
         prior tmnxBsxIsaAaGrpBitRate notification has cleared due to one of
         the following reasons:

         1. The current bit rate on the MDA in the ISA-AA group is less than or
         equal to the tmnxBsxBitRateLowWatermark.

         2. The corresponding tmnxBsxIsaAaGrpBitRate notification has been
         disabled by raising the tmnxBsxBitRateHighWatermark to maximum."
    ::= { tmnxBsxNotifications 20 }

tmnxBsxTransIpPolAaSubCreated    NOTIFICATION-TYPE
    OBJECTS     {
        tmnxBsxNotifyAaGrpPartIndex,
        tmnxBsxNotifyTransitIpPolicyId,
        tmnxBsxNotifyAaSubscriberName,
        tmnxBsxIsaAaGrpAaSubScale
    }
    STATUS      current
    DESCRIPTION
        "A tmnxBsxTransIpPolAaSubCreated notification is generated when a
         dynamic subscriber is created in a Transit IP Policy."
    ::= { tmnxBsxNotifications 21 }

tmnxBsxTransIpPolAaSubDeleted    NOTIFICATION-TYPE
    OBJECTS     {
        tmnxBsxNotifyAaGrpPartIndex,
        tmnxBsxNotifyTransitIpPolicyId,
        tmnxBsxNotifyAaSubscriberName,
        tmnxBsxNotifyReason
    }
    STATUS      current
    DESCRIPTION
        "A tmnxBsxTransIpPolAaSubDeleted notification is generated when a
         dynamic subscriber is deleted in a Transit IP Policy."
    ::= { tmnxBsxNotifications 22 }

tmnxBsxTransIpPolRadCoAAudit     NOTIFICATION-TYPE
    OBJECTS     {
        tmnxBsxNotifyAaGrpPartIndex,
        tmnxBsxNotifyTransitIpPolicyId,
        tmnxBsxNotifyRadiusCoAAuditState
    }
    STATUS      current
    DESCRIPTION
        "A tmnxBsxTransIpPolRadCoAAudit notification is generated when a Change
         of Authorization (CoA) Audit starts or ends."
    ::= { tmnxBsxNotifications 23 }

tmnxBsxTransIpPolRadCoAError     NOTIFICATION-TYPE
    OBJECTS     {
        tmnxBsxNotifyAaGrpPartIndex,
        tmnxBsxNotifyTransitIpPolicyId,
        tmnxBsxNotifyReason
    }
    STATUS      current
    DESCRIPTION
        "[CAUSE] A tmnxBsxTransIpPolRadCoAError notification is generated when
         an error occurs while processing a Change of Authorization (CoA)
         request from a RADIUS server. The tmnxBsxNotifyReason will identify
         the reason for failing to process the CoA request.

         [EFFECT] The addition or modification of a transit subscriber
         indicated in the CoA will not have been performed."
    ::= { tmnxBsxNotifications 24 }

tmnxBsxTransIpPolRadDiscError    NOTIFICATION-TYPE
    OBJECTS     {
        tmnxBsxNotifyAaGrpPartIndex,
        tmnxBsxNotifyTransitIpPolicyId,
        tmnxBsxNotifyReason
    }
    STATUS      current
    DESCRIPTION
        "[CAUSE] A tmnxBsxTransIpPolRadDiscError notification is generated when
         an error occurs while processing a Disconnect request from a RADIUS
         server. The tmnxBsxNotifyReason will identify the reason for failing
         to process the Disconnect request.

         [EFFECT] The removal of a transit subscriber indicated by a Disconnect
         request will not have been performed."
    ::= { tmnxBsxNotifications 25 }

tmnxBsxTransIpPolDhcpAddWarning  NOTIFICATION-TYPE
    OBJECTS     {
        tmnxBsxNotifyAaGrpPartIndex,
        tmnxBsxNotifyTransitIpPolicyId,
        tmnxBsxNotifyReason
    }
    STATUS      current
    DESCRIPTION
        "A tmnxBsxTransIpPolDhcpAddWarning notification is generated when a
         problem occurs while attempting to add a dynamic transit subscriber
         learned via DHCP. The notification is informational and may not be an
         error.

         The tmnxBsxNotifyReason will identify the reason this trap was raised."
    ::= { tmnxBsxNotifications 26 }

tmnxBsxTransIpPolDhcpDelWarning  NOTIFICATION-TYPE
    OBJECTS     {
        tmnxBsxNotifyAaGrpPartIndex,
        tmnxBsxNotifyTransitIpPolicyId,
        tmnxBsxNotifyReason
    }
    STATUS      current
    DESCRIPTION
        "A tmnxBsxTransIpPolDhcpDelWarning notification is generated when a
         problem occurs while attempting to delete a dynamic transit subscriber
         learned via DHCP. The notification is informational and may not be an
         error.

         The tmnxBsxNotifyReason will identify the reason this trap was raised."
    ::= { tmnxBsxNotifications 27 }

tmnxBsxIsaAaGrpFmSbWaSBufOvld    NOTIFICATION-TYPE
    OBJECTS     {
        tmnxBsxIsaAaGrpFromSubWaSBfHiWmk,
        tmnxBsxNotifyActiveMda
    }
    STATUS      current
    DESCRIPTION
        "[CAUSE] A tmnxBsxIsaAaGrpFmSbWaSBufOvld is generated when the current
         weighted average shared buffer use for an ISA in the from-subscriber
         direction is greater than or equal to a high watermark after being in
         a normal, non-overloaded, state.

         [EFFECT] If ISA overload cut-through is enabled, the ISA MDA performs
         subscriber level cut-through of all traffic."
    ::= { tmnxBsxNotifications 28 }

tmnxBsxIsaAaGrpFmSbWaSBufOvldClr NOTIFICATION-TYPE
    OBJECTS     {
        tmnxBsxIsaAaGrpFromSubWaSBfLoWmk,
        tmnxBsxNotifyActiveMda
    }
    STATUS      current
    DESCRIPTION
        "[CAUSE] A tmnxBsxIsaAaGrpFmSbWaSBufOvldClr is generated to indicate a
         prior tmnxBsxIsaAaGrpFmSbWaSBufOvld notification has cleared due to
         one of the following reasons:

         1. The current weighted average shared buffer use in the from
         subscriber direction is less than or equal to a low water mark.

         2. The corresponding tmnxBsxIsaAaGrpFmSbWaSBufOvld notification has
         been disabled by raising the tmnxBsxIsaAaGrpFromSubWaSBfHiWmk to
         maximum.

         [EFFECT] The buffer pool in the from-subscriber direction exits
         overload. ISA MDA overload cut-through ends if it was in effect and
         the buffer pools in both directions are no longer overloaded."
    ::= { tmnxBsxNotifications 29 }

tmnxBsxIsaAaGrpToSbWaSBufOvld    NOTIFICATION-TYPE
    OBJECTS     {
        tmnxBsxIsaAaGrpToSubWaSBfHiWmk,
        tmnxBsxNotifyActiveMda
    }
    STATUS      current
    DESCRIPTION
        "[CAUSE] A tmnxBsxIsaAaGrpToSbWaSBufOvld is generated when the current
         weighted average shared buffer use for an ISA in the to subscriber
         direction is greater than or equal to a high water mark after being in
         a normal, non-overloaded, state.

         [EFFECT] If ISA overload cut-through is enabled, the ISA MDA performs
         subscriber level cut-through of all traffic."
    ::= { tmnxBsxNotifications 30 }

tmnxBsxIsaAaGrpToSbWaSBufOvldClr NOTIFICATION-TYPE
    OBJECTS     {
        tmnxBsxIsaAaGrpToSubWaSBfLoWmk,
        tmnxBsxNotifyActiveMda
    }
    STATUS      current
    DESCRIPTION
        "[CAUSE] A tmnxBsxIsaAaGrpToSbWaSBufOvldClr is generated to indicate a
         prior tmnxBsxIsaAaGrpToSbWaSBufOvld notification has cleared due to
         one of the following reasons:

         1. The weighted average shared buffer use for an ISA in the
         to-subscriber direction is less than or equal to a low watermark.

         2. The corresponding tmnxBsxIsaAaGrpToSbWaSBufOvld notification has
         been disabled by raising the tmnxBsxIsaAaGrpToSubWaSBfHiWmk to
         maximum.

         [EFFECT] The buffer pool in the to-subscriber direction exits
         overload. ISA MDA overload cut-through ends if it was in effect and
         the buffer pools in both directions are no longer overloaded."
    ::= { tmnxBsxNotifications 31 }

tmnxBsxIsaAaGrpOvrldCutthru      NOTIFICATION-TYPE
    OBJECTS     {
        tmnxBsxNotifyIsaAaGroupIndex,
        tmnxBsxNotifyActiveMda,
        tmnxBsxNotifyIsaSlotNum,
        tmnxBsxNotifyIsaMdaNum
    }
    STATUS      current
    DESCRIPTION
        "[CAUSE] A tmnxBsxIsaAaGrpOvrldCutthru is generated when cut through
         processing starts on an ISA MDA.

         [EFFECT] The ISA MDA performs subscriber level cut-through of all
         traffic."
    ::= { tmnxBsxNotifications 32 }

tmnxBsxIsaAaGrpOvrldCutthruClr   NOTIFICATION-TYPE
    OBJECTS     {
        tmnxBsxNotifyIsaAaGroupIndex,
        tmnxBsxNotifyActiveMda,
        tmnxBsxNotifyIsaSlotNum,
        tmnxBsxNotifyIsaMdaNum
    }
    STATUS      current
    DESCRIPTION
        "[CAUSE] A tmnxBsxIsaAaGrpOvrldCutthru is generated when cut through
         processing ends on an ISA MDA.

         [EFFECT] The ISA MDA stops performing subscriber level cut-through of
         all traffic."
    ::= { tmnxBsxNotifications 33 }

tmnxBsxTransitIpPersistenceWarn  NOTIFICATION-TYPE
    OBJECTS     {
        tmnxBsxNotifyAaGrpPartIndex,
        tmnxBsxNotifyTransitIpPolicyId,
        tmnxBsxNotifyReason
    }
    STATUS      current
    DESCRIPTION
        "[CAUSE] A tmnxBsxTransitIpPersistenceWarn notification is generated
         when a problem occurs while attempting to register a dynamic transit
         subscriber address with the persistence infrastructure. The
         tmnxBsxNotifyReason will identify the reason this trap was raised.

         [EFFECT] The affected transit subscriber address will not be
         persistent across a system reboot."
    ::= { tmnxBsxNotifications 34 }

tmnxBsxAarpInstOperStateChanged  NOTIFICATION-TYPE
    OBJECTS     {
        tmnxBsxAarpInstOperState,
        tmnxBsxAarpInstOperFlags
    }
    STATUS      current
    DESCRIPTION
        "[CAUSE] A tmnxBsxAarpInstOperStateChanged notification is generated
         when the operational state of the AARP instance changes.

         [EFFECT] The transition to an operational state of 'outOfService(3)'
         indicates that the AARP instance is not performing asymmetry removal."
    ::= { tmnxBsxNotifications 35 }

tmnxBsxAarpInstStateChanged      NOTIFICATION-TYPE
    OBJECTS     {
        tmnxBsxAarpInstState,
        tmnxBsxAarpInstOperFlags
    }
    STATUS      current
    DESCRIPTION
        "[CAUSE] A tmnxBsxAarpInstStateChanged notification is generated when
         the state of the AARP instance changes."
    ::= { tmnxBsxNotifications 36 }

tmnxBsxRadApFailure              NOTIFICATION-TYPE
    OBJECTS     {
        tmnxBsxRadApDescription,
        tmnxBsxNotifyReason
    }
    STATUS      current
    DESCRIPTION
        "[CAUSE] The tmnxBsxRadApFailure notification is generated when a
         RADIUS accounting request was not successfully sent to any of the
         RADIUS servers in the accounting policy.

         [EFFECT] Accounting data for current subscribers will not be exported
         externally.

         [RECOVERY] Based on the reason noted in tmnxBsxNotifyReason, if
         necessary, take action to ensure that the next RADIUS accounting
         request will be successfully sent."
    ::= { tmnxBsxNotifications 37 }

tmnxBsxRadApServOperStateChange  NOTIFICATION-TYPE
    OBJECTS     {
        tmnxBsxRadApServAddrType,
        tmnxBsxRadApServAddr,
        tmnxBsxRadApServOperState
    }
    STATUS      current
    DESCRIPTION
        "The tmnxBsxRadApServOperStateChange notification is generated when the
         operational status of an AA RADIUS accounting policy server has
         transitioned either from 'inService' to 'outOfService' or from
         'outOfService' to 'inService'."
    ::= { tmnxBsxNotifications 38 }

tmnxBsxMobileSubModifyFailure    NOTIFICATION-TYPE
    OBJECTS     {
        tmnxBsxNotifyAaGrpPartIndex,
        tmnxBsxNotifyReason
    }
    STATUS      current
    DESCRIPTION
        "[CAUSE] A tmnxBsxMobileSubModifyFailure notification is generated when
         a problem is encountered while attempting to apply an override
         (app-profile or ASO) to a subscriber based on information received
         from the ISA-MG.

         The tmnxBsxNotifyReason will identify the reason this notification was
         raised.

         [EFFECT] The override is not be applied to the subscriber.

         [RECOVERY] Based on the reason noted in tmnxBsxNotifyReason, if
         necessary, take action to ensure that a configuration mismatch has not
         occurred to allow the overrides to be applied appropriately."
    ::= { tmnxBsxNotifications 39 }

tmnxBsxRadApIntrmUpdateSkipped   NOTIFICATION-TYPE
    OBJECTS     {
        tmnxBsxRadApIntrmUpdateInterval
    }
    STATUS      current
    DESCRIPTION
        "[CAUSE] The tmnxBsxRadApIntrmUpdateSkipped notification is generated
         when a RADIUS interim update has been triggered while subscriber
         accounting information is still being sent for the previous interim
         update interval.

         [EFFECT] Accounting data for this interim update will not be sent.

         [RECOVERY] If this continues to occur, consider increasing the RADIUS
         Accounting interim update interval (tmnxBsxRadApIntrmUpdateInterval)."
    ::= { tmnxBsxNotifications 40 }

tmnxBsxHttpUrlParamLimitExceeded NOTIFICATION-TYPE
    OBJECTS     {
        tmnxBsxNotifyIsaAaGroupIndex,
        tmnxBsxNotifyReason
    }
    STATUS      current
    DESCRIPTION
        "[CAUSE] A tmnxBsxHttpUrlParamLimitExceeded notification is generated
         when the group limit of unique tmnxBsxAaSubHttpUrlParam has been
         exceeded.

         The tmnxBsxNotifyReason will identify the reason this notification was
         raised.

         [EFFECT] Some subscribers will not have their HTTP URL Parameters
         applied."
    ::= { tmnxBsxNotifications 41 }

tmnxBsxUrlFilterOperStateChange  NOTIFICATION-TYPE
    OBJECTS     {
        tmnxBsxUrlFltrOperState,
        tmnxBsxUrlFltrOperFlags
    }
    STATUS      current
    DESCRIPTION
        "The tmnxBsxUrlFilterOperStateChange notification is generated when the
         operational status of a URL Filter has transitioned either from
         'inService' to 'outOfService' or from 'outOfService' to 'inService'."
    ::= { tmnxBsxNotifications 42 }

tmnxBsxSubModifyFailure          NOTIFICATION-TYPE
    OBJECTS     {
        tmnxBsxNotifyAaGrpPartIndex,
        tmnxBsxNotifyReason,
        tmnxBsxNotifyActiveMda,
        tmnxBsxNotifySubFailedAction,
        tmnxBsxNotifyIsaSlotNum,
        tmnxBsxNotifyIsaMdaNum
    }
    STATUS      current
    DESCRIPTION
        "[CAUSE] A tmnxBsxSubModifyFailure notification is generated when a
         problem is encountered while attempting to apply an override
         (app-profile or ASO) to a subscriber based on information received
         from the Policy Server.

         The tmnxBsxNotifyReason will identify the reason this notification was
         raised.

         [EFFECT] The override is not applied to the subscriber.

         [RECOVERY] Based on the reason noted in tmnxBsxNotifyReason, if
         necessary, take action to ensure that a configuration mismatch has not
         occurred to allow the overrides to be applied appropriately."
    ::= { tmnxBsxNotifications 43 }

tmnxBsxDnsIpCacheFull            NOTIFICATION-TYPE
    OBJECTS     {
        tmnxBsxNotifyActiveMda,
        tmnxBsxDnsIpCacheHighWatermark,
        tmnxBsxDnsIpCacheSize,
        tmnxBsxNotifyIsaSlotNum,
        tmnxBsxNotifyIsaMdaNum
    }
    STATUS      current
    DESCRIPTION
        "[CAUSE] A tmnxBsxDnsIpCacheFull notification is generated when the
         number of entries in a DNS IP Cache is greater than or equal to the
         percentage value tmnxBsxDnsIpCacheHighWatermark of its
         tmnxBsxDnsIpCacheSize and the previous percentage value was less than
         this threshold.

         [EFFECT] There is no immediate effect, but when the usage actually
         hits the limit of tmnxBsxDnsIpCacheSize, new entries will not be added
         to the cache.

         [RECOVERY] The notification can be cleared if enough cache entries
         timeout to drop below the threshold, or if the cache is cleared, or
         tmnxBsxDnsIpCacheSize is sufficiently increased."
    ::= { tmnxBsxNotifications 44 }

tmnxBsxDnsIpCacheFullClear       NOTIFICATION-TYPE
    OBJECTS     {
        tmnxBsxNotifyActiveMda,
        tmnxBsxDnsIpCacheLowWatermark,
        tmnxBsxDnsIpCacheSize,
        tmnxBsxNotifyIsaSlotNum,
        tmnxBsxNotifyIsaMdaNum
    }
    STATUS      current
    DESCRIPTION
        "[CAUSE] A tmnxBsxDnsIpCacheFullClear notification is generated when
         the number of entries in a DNS IP Cache is less than or equal to the
         percentage value tmnxBsxDnsIpCacheLowWatermark of its
         tmnxBsxDnsIpCacheSize and the previous percentage value was greater
         than this threshold.

         [EFFECT] The tmnxBsxDnsIpCacheFull notification of the cache is
         cleared."
    ::= { tmnxBsxNotifications 45 }

tmnxBsxUrlListUpdate             NOTIFICATION-TYPE
    OBJECTS     {
        tmnxBsxUrlListStatusNumEntries
    }
    STATUS      current
    DESCRIPTION
        "[CAUSE] A tmnxBsxUrlListUpdate notification is generated when a URL
         list has been updated.

         [EFFECT] The URL list is installed on each ISA-AA in the group.

         [RECOVERY] There is no recovery for this notification."
    ::= { tmnxBsxNotifications 46 }

tmnxBsxUrlListFailure            NOTIFICATION-TYPE
    OBJECTS     {
        tmnxBsxUrlListStatusOperState,
        tmnxBsxUrlListStatusOperFlags
    }
    STATUS      current
    DESCRIPTION
        "[CAUSE] A tmnxBsxUrlListFailure notification is generated when a URL
         list has failed.

         [EFFECT] If the operational state is 'inService (2)', the URL list is
         operating using the last successfully processed list. If the
         operational state is 'outOfService (3)', there was no previous
         successful update and the URL list will be operationally down.

         [RECOVERY] The customer should ensure the correct file is configured
         in tmnxBsxUrlListFileUrl, and use tmnxBsxUrlListAdminState or
         tmnxBsxUrlListUpgrade to restart the URL list."
    ::= { tmnxBsxNotifications 47 }

tmnxBsxIsaAaTimFileProcFailure   NOTIFICATION-TYPE
    OBJECTS     {
        tmnxBsxNotifyReason
    }
    STATUS      current
    DESCRIPTION
        "[CAUSE] A tmnxBsxIsaAaTimFileProcFailure notification is generated
         when a problem is encountered while attempting to process the
         isa-aa.tim file from the boot options file (BOF) images directory.

         The tmnxBsxNotifyReason will identify the reason this notification was
         raised.

         [EFFECT] The isa-aa.tim file cannot be processed.

         [RECOVERY] Based on the reason noted in tmnxBsxNotifyReason, if
         necessary take action to ensure that a valid isa-aa.tim file,
         compatible with the running CPM software version, is located in the
         images directory configured in the BOF.

         If successive attempts to load the isa-aa.tim fail, please contact
         Nokia customer support."
    ::= { tmnxBsxNotifications 48 }

tmnxBsxStatTcaThreshCrossed      NOTIFICATION-TYPE
    OBJECTS     {
        tmnxBsxNotifyAaGrpPartIndex,
        tmnxBsxNotifyTcaCfgType,
        tmnxBsxNotifyTcaCfgDirection,
        tmnxBsxNotifyReason
    }
    STATUS      current
    DESCRIPTION
        "[CAUSE] A tmnxBsxStatTcaThreshCrossed notification is generated when
         the utilization matching a tmnxBsxStatTcaCfgEntry in the past minute
         is greater than or equal to the value of tmnxBsxStatTcaCfgHiWmark and
         the notification is not currently raised for the same entry.

         The tmnxBsxNotifyReason will identify the utilization.

         [EFFECT] There is no effect for this notification.

         [RECOVERY] There is no recovery for this notification."
    ::= { tmnxBsxNotifications 49 }

tmnxBsxStatTcaThreshCrossedClear NOTIFICATION-TYPE
    OBJECTS     {
        tmnxBsxNotifyAaGrpPartIndex,
        tmnxBsxNotifyTcaCfgType,
        tmnxBsxNotifyTcaCfgDirection,
        tmnxBsxNotifyReason
    }
    STATUS      current
    DESCRIPTION
        "[CAUSE] A tmnxBsxStatTcaThreshCrossedClear notification is generated
         when the utilization matching a tmnxBsxStatTcaCfgEntry in the past
         minute is less than or equal to the value of tmnxBsxStatTcaCfgLoWmark
         and tmnxBsxStatTcaThreshCrossed is currently raised.

         The tmnxBsxNotifyReason will identify the utilization.

         [EFFECT] The tmnxBsxStatTcaThreshCrossed notification is cleared.

         [RECOVERY] There is no recovery for this notification."
    ::= { tmnxBsxNotifications 50 }

tmnxBsxStatPolcrTcaThreshCrossed NOTIFICATION-TYPE
    OBJECTS     {
        tmnxBsxNotifyAaGrpPartIndex,
        tmnxBsxNotifyTcaPolicerName,
        tmnxBsxNotifyTcaCfgDirection,
        tmnxBsxNotifyReason
    }
    STATUS      current
    DESCRIPTION
        "[CAUSE] A tmnxBsxStatPolcrTcaThreshCrossed notification is generated
         when the utilization matching a tmnxBsxStatTcaPolcrCfgEntry in the
         past minute is greater than or equal to the value of
         tmnxBsxStatTcaPolcrCfgHiWmark and the notification is not currently
         raised for the same entry.

         The tmnxBsxNotifyReason will identify the utilization.

         [EFFECT] There is no effect for this notification.

         [RECOVERY] There is no recovery for this notification."
    ::= { tmnxBsxNotifications 51 }

tmnxBsxStatPolcrTcaThreshCrClear NOTIFICATION-TYPE
    OBJECTS     {
        tmnxBsxNotifyAaGrpPartIndex,
        tmnxBsxNotifyTcaPolicerName,
        tmnxBsxNotifyTcaCfgDirection,
        tmnxBsxNotifyReason
    }
    STATUS      current
    DESCRIPTION
        "[CAUSE] A tmnxBsxStatPolcrTcaThreshCrClear notification is generated
         when the utilization matching a tmnxBsxStatTcaPolcrCfgEntry in the
         past minute is less than or equal to the value of
         tmnxBsxStatTcaPolcrCfgLoWmark and tmnxBsxStatPolcrTcaThreshCrossed is
         currently raised.

         The tmnxBsxNotifyReason will identify the utilization.

         [EFFECT] The tmnxBsxStatPolcrTcaThreshCrossed notification is cleared.

         [RECOVERY] There is no recovery for this notification."
    ::= { tmnxBsxNotifications 52 }

tmnxBsxStatFtrTcaThreshCrossed   NOTIFICATION-TYPE
    OBJECTS     {
        tmnxBsxNotifyAaGrpPartIndex,
        tmnxBsxNotifyTcaCfgFilterType,
        tmnxBsxNotifyTcaCfgFilterName,
        tmnxBsxNotifyTcaCfgFltrWmarkType,
        tmnxBsxNotifyTcaCfgDirection,
        tmnxBsxNotifyReason
    }
    STATUS      current
    DESCRIPTION
        "[CAUSE] A tmnxBsxStatFtrTcaThreshCrossed notification is generated
         when the utilization matching a tmnxBsxStatTcaFtrCfgEntry in the past
         minute is greater than or equal to the value of
         tmnxBsxStatTcaFtrCfgHiWmark and the notification is not currently
         raised for the same entry.

         The tmnxBsxNotifyReason will identify the utilization.

         [EFFECT] There is no effect for this notification.

         [RECOVERY] There is no recovery for this notification."
    ::= { tmnxBsxNotifications 53 }

tmnxBsxStatFtrTcaThreshCrClear   NOTIFICATION-TYPE
    OBJECTS     {
        tmnxBsxNotifyAaGrpPartIndex,
        tmnxBsxNotifyTcaCfgFilterType,
        tmnxBsxNotifyTcaCfgFilterName,
        tmnxBsxNotifyTcaCfgFltrWmarkType,
        tmnxBsxNotifyTcaCfgDirection,
        tmnxBsxNotifyReason
    }
    STATUS      current
    DESCRIPTION
        "[CAUSE] A tmnxBsxStatFtrTcaThreshCrClear notification is generated
         when the utilization matching a tmnxBsxStatTcaFtrCfgEntry in the past
         minute is less than or equal to the value of
         tmnxBsxStatTcaFtrCfgLoWmark and tmnxBsxStatFtrTcaThreshCrossed is
         currently raised.

         The tmnxBsxNotifyReason will identify the utilization.

         [EFFECT] The tmnxBsxStatFtrTcaThreshCrossed notification is cleared.

         [RECOVERY] There is no recovery for this notification."
    ::= { tmnxBsxNotifications 54 }

tmnxBsxStatFtrEnTcaThreshCrossed NOTIFICATION-TYPE
    OBJECTS     {
        tmnxBsxNotifyAaGrpPartIndex,
        tmnxBsxNotifyTcaCfgFilterType,
        tmnxBsxNotifyTcaCfgFilterName,
        tmnxBsxNotifyTcaFtrEnCfgEntryId,
        tmnxBsxNotifyTcaCfgDirection,
        tmnxBsxNotifyReason
    }
    STATUS      current
    DESCRIPTION
        "[CAUSE] A tmnxBsxStatFtrEnTcaThreshCrossed notification is generated
         when the utilization matching a tmnxBsxStatTcaFtrEnCfgEntry in the
         past minute is greater than or equal to the value of
         tmnxBsxStatTcaFtrEnCfgHiWmark and the notification is not currently
         raised for the same entry.

         The tmnxBsxNotifyReason will identify the utilization.

         [EFFECT] There is no effect for this notification.

         [RECOVERY] There is no recovery for this notification."
    ::= { tmnxBsxNotifications 55 }

tmnxBsxStatFtrEnTcaThreshCrClear NOTIFICATION-TYPE
    OBJECTS     {
        tmnxBsxNotifyAaGrpPartIndex,
        tmnxBsxNotifyTcaCfgFilterType,
        tmnxBsxNotifyTcaCfgFilterName,
        tmnxBsxNotifyTcaFtrEnCfgEntryId,
        tmnxBsxNotifyTcaCfgDirection,
        tmnxBsxNotifyReason
    }
    STATUS      current
    DESCRIPTION
        "[CAUSE] A tmnxBsxStatFtrEnTcaThreshCrClear notification is generated
         when the utilization matching a tmnxBsxStatTcaFtrEnCfgEntry in the
         past minute is less than or equal to the value of
         tmnxBsxStatTcaFtrEnCfgLoWmark and tmnxBsxStatFtrEnTcaThreshCrossed is
         currently raised.

         The tmnxBsxNotifyReason will identify the utilization.

         [EFFECT] The tmnxBsxStatFtrEnTcaThreshCrossed notification is cleared.

         [RECOVERY] There is no recovery for this notification."
    ::= { tmnxBsxNotifications 56 }

tmnxBsxTransIpPolDiamGxError     NOTIFICATION-TYPE
    OBJECTS     {
        tmnxBsxNotifyAaGrpPartIndex,
        tmnxBsxNotifyTransitIpPolicyId,
        tmnxBsxNotifyReason
    }
    STATUS      current
    DESCRIPTION
        "[CAUSE] A tmnxBsxTransIpPolDiamGxError notification is generated when
         an error occurs while processing a Credit-Control Answer (CCA) or
         Reauthorization Request (RAR) from a Diameter server over Gx.

         The tmnxBsxNotifyReason will identify the reason for failing to
         process the Diameter answer/request.

         [EFFECT] The addition or modification of a transit subscriber
         indicated in the Diameter Gx message will not have been performed.

         [RECOVERY] There is no recovery for this notification."
    ::= { tmnxBsxNotifications 57 }

tmnxBsxDatapathCpuUsage          NOTIFICATION-TYPE
    OBJECTS     {
        tmnxBsxNotifyIsaAaGroupIndex,
        tmnxBsxNotifyActiveMda,
        tmnxBsxDatapathCpuHighWatermark,
        tmnxBsxNotifyIsaSlotNum,
        tmnxBsxNotifyIsaMdaNum
    }
    STATUS      current
    DESCRIPTION
        "[CAUSE] A tmnxBsxDatapathCpuUsage notification is generated when the
         current datapath CPU usage on the MDA in the ISA-AA group is greater
         than or equal to the tmnxBsxDatapathCpuHighWatermark and the prior
         usage was less than this threshold.

         [EFFECT] There is no immediate effect, but when the usage hits the
         limit of 100%, traffic will be dropped unless the value of
         tmnxBsxIsaAaGrpOverloadCutThru is 'enabled (1)' for the Application
         Assurance group.

         [RECOVERY] There is no recovery for this notification."
    ::= { tmnxBsxNotifications 58 }

tmnxBsxDatapathCpuUsageClear     NOTIFICATION-TYPE
    OBJECTS     {
        tmnxBsxNotifyIsaAaGroupIndex,
        tmnxBsxNotifyActiveMda,
        tmnxBsxDatapathCpuLowWatermark,
        tmnxBsxNotifyIsaSlotNum,
        tmnxBsxNotifyIsaMdaNum
    }
    STATUS      current
    DESCRIPTION
        "[CAUSE] A tmnxBsxDatapathCpuUsageClear notification is generated to
         indicate a prior tmnxBsxDatapathCpuUsage notification has cleared due
         to the current datapath CPU usage on the MDA in the ISA-AA group being
         less than or equal to the tmnxBsxDatapathCpuLowWatermark.

         [EFFECT] The tmnxBsxDatapathCpuUsage notification is cleared.

         [RECOVERY] There is no recovery for this notification."
    ::= { tmnxBsxNotifications 59 }

tmnxBsxTcpValTcaCrossed          NOTIFICATION-TYPE
    OBJECTS     {
        tmnxBsxNotifyAaGrpPartIndex,
        tmnxBsxNotifyTcpValTcaName,
        tmnxBsxNotifyTcpValTcaWmarkType,
        tmnxBsxNotifyTcaCfgDirection,
        tmnxBsxNotifyReason
    }
    STATUS      current
    DESCRIPTION
        "[CAUSE] A tmnxBsxTcpValTcaCrossed notification is generated when the
         utilization matching a tmnxBsxTcpValTcaEntry in the past minute is
         greater than or equal to the value of tmnxBsxTcpValTcaHighWatermark
         and the notification is not currently raised for the same entry.

         The tmnxBsxNotifyReason will identify the utilization.

         [EFFECT] There is no effect for this notification.

         [RECOVERY] There is no recovery for this notification."
    ::= { tmnxBsxNotifications 60 }

tmnxBsxTcpValTcaCrossedClear     NOTIFICATION-TYPE
    OBJECTS     {
        tmnxBsxNotifyAaGrpPartIndex,
        tmnxBsxNotifyTcpValTcaName,
        tmnxBsxNotifyTcpValTcaWmarkType,
        tmnxBsxNotifyTcaCfgDirection,
        tmnxBsxNotifyReason
    }
    STATUS      current
    DESCRIPTION
        "[CAUSE] A tmnxBsxTcpValTcaCrossedClear notification is generated when
         the utilization matching a tmnxBsxTcpValTcaEntry in the past minute is
         less than or equal to the value of tmnxBsxTcpValTcaLowWatermark and
         tmnxBsxTcpValTcaCrossed is currently raised.

         The tmnxBsxNotifyReason will identify the utilization.

         [EFFECT] The tmnxBsxTcpValTcaCrossed notification is cleared.

         [RECOVERY] There is no recovery for this notification."
    ::= { tmnxBsxNotifications 61 }

tmnxBsxCertProfileOperStateChngd NOTIFICATION-TYPE
    OBJECTS     {
        tmnxBsxNotifyIsaAaGroupIndex,
        tmnxBsxNotifyCertProfileName,
        tmnxBsxNotifyCertProfOperState,
        tmnxBsxNotifyReason
    }
    STATUS      current
    DESCRIPTION
        "[CAUSE] A tmnxBsxCertProfileOperStateChngd notification is generated
         when the operational state of the certificate-profile is changed.

         The tmnxBsxNotifyReason will identify the reason.

         Most common cause are:
           - use of an unsupported algorithm.
           - use of a key with unsupported key length.
           - file permissions

         [EFFECT] Functions dependent on the certificate profiles may not work
         as expected, if the operational state is outOfService(3).

         [RECOVERY] Resolve the condition as reported in tmnxBsxNotifyReason."
    ::= { tmnxBsxNotifications 62 }

tmnxBsxSubQuarantined            NOTIFICATION-TYPE
    OBJECTS     {
        tmnxBsxAaSubQuarantined
    }
    STATUS      current
    DESCRIPTION
        "[CAUSE] A tmnxBsxSubQuarantined notification is generated when a
         subscriber enters quarantined state.

         [EFFECT] The subscriber traffic will be marked as 'best effort' and
         colored as 'exceed profile' which will cause early discards.

         [RECOVERY] The subscriber quarantine must be removed manually using
         the tools command."
    ::= { tmnxBsxNotifications 63 }

tmnxBsxSubQuarantinedClear       NOTIFICATION-TYPE
    OBJECTS     {
        tmnxBsxAaSubQuarantined
    }
    STATUS      current
    DESCRIPTION
        "[CAUSE] A tmnxBsxSubQuarantined notification is generated when a
         subscriber exits quarantined state.

         [EFFECT] The tmnxBsxTcpValTcaCrossed notification is cleared.

         [RECOVERY] There is no recovery for this notification."
    ::= { tmnxBsxNotifications 64 }

tmnxBsxUrlFltrWebServOprStateChg NOTIFICATION-TYPE
    OBJECTS     {
        tmnxBsxUrlFltrWebSvDnsOperState,
        tmnxBsxUrlFltrWebSvDnsOperFlags
    }
    STATUS      current
    DESCRIPTION
        "The tmnxBsxUrlFltrWebServOprStateChg notification is generated when
         the operational status of a URL Filter Web Service DNS Server has
         transitioned either from 'inService' to 'outOfService' or from
         'outOfService' to 'inService'."
    ::= { tmnxBsxNotifications 65 }

END
