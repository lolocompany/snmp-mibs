TIMETRA-LOCAL-USER-DB-MIB DEFINITIONS ::= BEGIN

IMPORTS
    InetAddress, InetAddressPrefixLength,
    InetAddressType
                                                         FROM INET-ADDRESS-MIB
    MODULE-COMPLIANCE, NOTIFICATION-GROUP,
    OBJECT-GROUP
                                                         FROM SNMPv2-CONF
    Integer32, MODULE-IDENTITY,
    NOTIFICATION-TYPE, OBJECT-TYPE,
    Unsigned32
                                                         FROM SNMPv2-SMI
    DisplayString, MacAddress, RowStatus,
    TEXTUAL-CONVENTION, TimeStamp,
    TruthValue
                                                         FROM SNMPv2-TC
    TIPFilterIdOrEmpty
                                                         FROM TIMETRA-FILTER-MIB
    timetraSRMIBModules, tmnxSRConfs,
    tmnxSRNotifyPrefix, tmnxSRObjs
                                                         FROM TIMETRA-GLOBAL-MIB
    TmnxPortEncapType
                                                         FROM TIMETRA-PORT-MIB
    TItemDescription, TLNamedItemOrEmpty,
    TNamedItem, TNamedItemOrEmpty,
    TPolicyStatementName,
    TPolicyStatementNameOrEmpty,
    TmnxActionType, TmnxAdminState,
    TmnxAncpStringOrZero, TmnxCreateOrigin,
    TmnxDhcpOptionDisplay,
    TmnxDhcpOptionType, TmnxEncapVal,
    TmnxFilterProfileStringOrEmpty,
    TmnxL2tpTunnelGroupNameOrEmpty,
    TmnxMacSpecification,
    TmnxPppoePadoDelay,
    TmnxPppoeUserNameOrEmpty, TmnxServId,
    TmnxSlaProfileStringOrEmpty,
    TmnxSubAleOffset, TmnxSubAleOffsetMode,
    TmnxSubIdentStringOrEmpty,
    TmnxSubProfileStringOrEmpty,
    TmnxSubSpiGroupId
                                                         FROM TIMETRA-TC-MIB
    ;

timetraLocalUserDbMIBModule      MODULE-IDENTITY
    LAST-UPDATED "201803010000Z"
    ORGANIZATION "Nokia"
    CONTACT-INFO
        "Nokia SROS Support
         Web: http://www.nokia.com"
    DESCRIPTION
        "This document is the SNMP MIB module to manage and provision the local
         user database for the Nokia SROS device.

         Copyright 2008-2018 Nokia. All rights reserved. Reproduction of this
         document is authorized on the condition that the foregoing copyright
         notice is included.

         This SNMP MIB module (Specification) embodies Nokia's
         proprietary intellectual property.  Nokia retains
         all title and ownership in the Specification, including any
         revisions.

         Nokia grants all interested parties a non-exclusive license to use and
         distribute an unmodified copy of this Specification in connection with
         management of Nokia products, and without fee, provided this copyright
         notice and license appear on all copies.

         This Specification is supplied 'as is', and Nokia makes no warranty,
         either express or implied, as to the use, operation, condition, or
         performance of the Specification."

    REVISION    "201803010000Z"
    DESCRIPTION
        "Rev 16.0               01 April 2018 00:00
         16.0 release of the TIMETRA-LOCAL-USER-DB-MIB."

    REVISION    "201703010000Z"
    DESCRIPTION
        "Rev 15.0               01 April 2017 00:00
         15.0 release of the TIMETRA-LOCAL-USER-DB-MIB."

    REVISION    "201601010000Z"
    DESCRIPTION
        "Rev 14.0               01 Jan 2016 00:00
         14.0 release of the TIMETRA-LOCAL-USER-DB-MIB."

    REVISION    "201501010000Z"
    DESCRIPTION
        "Rev 13.0               01 Jan 2015 00:00
         13.0 release of the TIMETRA-LOCAL-USER-DB-MIB."

    REVISION    "201401010000Z"
    DESCRIPTION
        "Rev 12.0               01 Jan 2014 00:00
         12.0 release of the TIMETRA-LOCAL-USER-DB-MIB."

    REVISION    "201102010000Z"
    DESCRIPTION
        "Rev 9.0                01 Feb 2011 00:00
         9.0 release of the TIMETRA-LOCAL-USER-DB-MIB."

    REVISION    "200902280000Z"
    DESCRIPTION
        "Rev 7.0                28 Feb 2009 00:00
         7.0 release of the TIMETRA-LOCAL-USER-DB-MIB."

    REVISION    "200807010000Z"
    DESCRIPTION
        "Rev 6.1                01 Jul 2008 00:00
         6.1 release of the TIMETRA-LOCAL-USER-DB-MIB."

    REVISION    "200801010000Z"
    DESCRIPTION
        "Rev 0.1                01 Jan 2008 00:00
         Initial version of the TIMETRA-LOCAL-USER-DB-MIB."

    ::= { timetraSRMIBModules 51 }

TmnxLocUsrDbUserNameFormat       ::= TEXTUAL-CONVENTION
    STATUS      current
    DESCRIPTION
        "The data type TmnxLocUsrDbUserNameFormat represents how the username
         is specified:
         - 'none       (0)': no username is specified
         - 'full       (1)': both the host part and domain part are specified,
                             example: joe@nokia.com
         - 'hostOnly   (2)': only the host part of the username is specified,
                             example: joe
         - 'domainOnly (3)': only the domain part of the username is specified,
                             example: nokia.com"
    SYNTAX      INTEGER {
        none       (0),
        full       (1),
        hostOnly   (2),
        domainOnly (3)
    }

TmnxLocUsrDbPasswordType         ::= TEXTUAL-CONVENTION
    STATUS      current
    DESCRIPTION
        "The data type TmnxLocUsrDbPasswordType represents what type of
         password is specified:
         - 'none   (0)': no password is specified
         - 'ignore (1)': the password is ignored
         - 'pap    (2)': password for PAP (Password Authentication Protocol)
         - 'chap   (3)': password for CHAP (Challenge-Handshake Authentication
                         Protocol) is specified"
    SYNTAX      INTEGER {
        none   (0),
        ignore (1),
        pap    (2),
        chap   (3)
    }

TmnxLocUsrDbMatchTypePppoe       ::= TEXTUAL-CONVENTION
    STATUS      current
    DESCRIPTION
        "The data type TmnxLocUsrDbMatchTypePppoe represents the type of
         matching done to identify a PPPoE user.

         The match type refers to one of these objects in the
         tmnxLocUsrDbPppoeTable or tmnxLudbPpp2Table:

         match type     | object
         ---------------------------------------------
         circuitId      | tmnxLocUsrDbPppoeCircuitId
         macAddr        | tmnxLocUsrDbPppoeMacAddress
         remoteId       | tmnxLocUsrDbPppoeRemoteId
         userName       | tmnxLocUsrDbPppoeUserName
         serviceName    | tmnxLocUsrDbPppoeServiceName
         sapId          | tmnxLocUsrDbPppoeSapId
         derivedId      | tmnxLocUsrDbPppoeDerivedId
         encTagRange    | tmnxLocUsrDbPppoeEncTagRangeType
         encTagSepRange | tmnxLudbPpp2EncTagRgOuterStart
                          tmnxLudbPpp2EncTagRgOuterEnd
                          tmnxLudbPpp2EncTagRgInnerStart
                          tmnxLudbPpp2EncTagRgInnerEnd"
    SYNTAX      INTEGER {
        none           (0),
        circuitId      (1),
        macAddr        (2),
        remoteId       (3),
        userName       (4),
        serviceName    (5),
        sapId          (6),
        encTagRange    (7),
        derivedId      (8),
        encTagSepRange (9)
    }

TmnxLocUsrDbMatchTypeDhcp        ::= TEXTUAL-CONVENTION
    STATUS      current
    DESCRIPTION
        "The data type TmnxLocUsrDbMatchTypeDhcp represents the type of
         matching done to identify a DHCP host.

         The match type refers to one of these objects in the
         tmnxLocUsrDbDhcpTable or tmnxLudbDhcp2Table:

         match type        | object
         ------------------------------------------------
         circuitId         | tmnxLocUsrDbDhcpCircuitId
         macAddr           | tmnxLocUsrDbDhcpMacAddress
         remoteId          | tmnxLocUsrDbDhcpRemoteId
         sapId             | tmnxLocUsrDbDhcpSapId
         serviceId         | tmnxLocUsrDbDhcpServiceId
         string            | tmnxLocUsrDbDhcpString
         systemId          | tmnxLocUsrDbDhcpSystemId
         option60          | tmnxLocUsrDbDhcpOption60
         dualStackRemoteId | tmnxLocUsrDbDhcpRemoteId
                             after stripping the enterprise ID
         derivedId         | ASCII string that uniquely identifies a host, and is
                             derived by a Python script from packet content
                             available during a DHCP transaction
         ip                | tmnxLocUsrDbDhcpIpPrefixAddr and related objects
         encTagSepRange    | tmnxLudbDhcp2EncTagRgOuterStart
                             tmnxLudbDhcp2EncTagRgOuterEnd
                             tmnxLudbDhcp2EncTagRgInnerStart
                             tmnxLudbDhcp2EncTagRgInnerEnd
         duidEn            | tmnxLudbDhcp2DuidEn
         duidLlLlt         | tmnxLudbDhcp2DuidLlLlt"
    SYNTAX      INTEGER {
        none              (0),
        circuitId         (1),
        macAddr           (2),
        remoteId          (3),
        sapId             (4),
        serviceId         (5),
        string            (6),
        systemId          (7),
        option60          (8),
        encTagRange       (9),
        dualStackRemoteId (10),
        derivedId         (11),
        ip                (12),
        encTagSepRange    (13),
        duidEn            (14),
        duidLlLlt         (15)
    }

TmnxLocUsrDbHostType             ::= TEXTUAL-CONVENTION
    STATUS      current
    DESCRIPTION
        "The data type TmnxLocUsrDbHostType represents the usage type of
         a local user database host template:
         - 'any': any host can use this template; this type of host template
                  is also referred to as 'generic';
         - 'dhcp': only DHCP hosts can use this template;
         - 'ppp': only PPP hosts can use this template."
    SYNTAX      INTEGER {
        any  (0),
        dhcp (1),
        ppp  (2)
    }

TmnxLocUsrDbHostApplications     ::= TEXTUAL-CONVENTION
    STATUS      current
    DESCRIPTION
        "The data type TmnxLocUsrDbHostApplications represents the usage types
         allowed for a particular local user database host template of type 'any':
         - 'dhcp': DHCP hosts can use this template;
         - 'ppp': PPP hosts can use this template."
    SYNTAX      BITS {
        bitDHCP (0),
        bitPPP  (1)
    }

TmnxLocUsrDbUnmatchedReason      ::= TEXTUAL-CONVENTION
    STATUS      current
    DESCRIPTION
        "The data type TmnxLocUsrDbUnmatchedReason denotes why this host was
         unmatched.

         - noMatchTypes  : This host has no objects configured to match against.
         - duplicate     : Another host was already matched with the same values
                           of the objects to match against.
         - genError      : The system failed to try the match.
         - overlap       : encap tag separate range overlaps with an another host.
         - limitExceeded : exceeding maximum number of non-overlapping encap
                           tag
                           separate ranges."
    SYNTAX      INTEGER {
        noMatchTypes  (1),
        duplicate     (2),
        genError      (3),
        overlap       (4),
        limitExceeded (5)
    }

TmnxLocUsrDbDataFormat           ::= TEXTUAL-CONVENTION
    STATUS      current
    DESCRIPTION
        "The data type TmnxLocUsrDbDataFormat represents how the input data
         is specified:
         - 'ascii (2)': the data contains seven-bit ASCII characters
         - 'hex   (3)': the data contains octets. It must be displayed in
                        hexadecimal format because it contains non-printable
                        characters."
    SYNTAX      INTEGER {
        ascii (2),
        hex   (3)
    }

TmnxLocUsrDbMaskString           ::= TEXTUAL-CONVENTION
    STATUS      current
    DESCRIPTION
        "The TmnxLocUsrDbMaskString data type contains a a substring that is
         stripped off the start or the end of an incoming string before it is
         matched.

         This string can only contain printable ASCII characters. Character '*'
         is a wildcard that matches any substring; it can be escaped by
         character '\'."
    SYNTAX      DisplayString (SIZE (0..127))

TmnxLudbDataFormat               ::= TEXTUAL-CONVENTION
    STATUS      current
    DESCRIPTION
        "The data type TmnxLudbDataFormat represents how the input data is
         specified:
         - 'none  (1) : the format is unknown or not applicable
         - 'ascii (2)': the data contains seven-bit ASCII characters
         - 'hex   (3)': the data contains octets. It must be displayed in
                        hexadecimal format because it contains non-printable
                        characters."
    SYNTAX      INTEGER {
        none  (1),
        ascii (2),
        hex   (3)
    }

TmnxLudbMsapGrpIfPfxSfxType      ::= TEXTUAL-CONVENTION
    STATUS      current
    DESCRIPTION
        "The data type TmnxLudbMsapGrpIfPfxSfxType represents the
         group-interface prefix or suffix format:
         - 'none    (1) : the format is unknown or not applicable
         - 'port-id (2)': the data contains the port-id"
    SYNTAX      INTEGER {
        none   (1),
        portId (2)
    }

tmnxLocalUserDb                  OBJECT IDENTIFIER ::= { tmnxSRObjs 51 }

tmnxLocalUserDbObjs              OBJECT IDENTIFIER ::= { tmnxLocalUserDb 1 }

tmnxLocalUserDbTableLastChange   OBJECT-TYPE
    SYNTAX      TimeStamp
    MAX-ACCESS  read-only
    STATUS      current
    DESCRIPTION
        "The value of the object tmnxLocalUserDbTableLastChange indicates the
         value of sysUpTime at the time of the last modification of an entry in
         the tmnxLocalUserDbTable."
    ::= { tmnxLocalUserDbObjs 1 }

tmnxLocalUserDbTable             OBJECT-TYPE
    SYNTAX      SEQUENCE OF TmnxLocalUserDbEntry
    MAX-ACCESS  not-accessible
    STATUS      current
    DESCRIPTION
        "The table tmnxLocalUserDbTable contains objects to configure the local
         user database.

         The local database is used for authentication by either PPPoE
         (TIMETRA-PPPOE-MIB::tmnxPppoeIesIfPapChapUserDb) or a local DHCP
         server (TIMETRA-DHCP-SERVER-MIB::tmnxDhcpServerCfgUserDatabase)."
    ::= { tmnxLocalUserDbObjs 2 }

tmnxLocalUserDbEntry             OBJECT-TYPE
    SYNTAX      TmnxLocalUserDbEntry
    MAX-ACCESS  not-accessible
    STATUS      current
    DESCRIPTION
        "Each row represents a local user database.

         Entries in this table can be created or deleted via SNMP operations."
    INDEX       { IMPLIED tmnxLocUsrDbUserDatabaseName }
    ::= { tmnxLocalUserDbTable 1 }

TmnxLocalUserDbEntry             ::= SEQUENCE
{
    tmnxLocUsrDbUserDatabaseName     TNamedItem,
    tmnxLocUsrDbRowStatus            RowStatus,
    tmnxLocUsrDbLastChangeTime       TimeStamp,
    tmnxLocUsrDbAdminState           TmnxAdminState,
    tmnxLocUsrDbDescription          TItemDescription,
    tmnxLocUsrDbMatchTypeDhcp1       TmnxLocUsrDbMatchTypeDhcp,
    tmnxLocUsrDbMatchTypeDhcp2       TmnxLocUsrDbMatchTypeDhcp,
    tmnxLocUsrDbMatchTypeDhcp3       TmnxLocUsrDbMatchTypeDhcp,
    tmnxLocUsrDbMatchTypeDhcp4       TmnxLocUsrDbMatchTypeDhcp,
    tmnxLocUsrDbMatchTypePppoe1      TmnxLocUsrDbMatchTypePppoe,
    tmnxLocUsrDbMatchTypePppoe2      TmnxLocUsrDbMatchTypePppoe,
    tmnxLocUsrDbMatchTypePppoe3      TmnxLocUsrDbMatchTypePppoe,
    tmnxLocUsrDbPppoeCIdMaskPreStr   TmnxLocUsrDbMaskString,
    tmnxLocUsrDbPppoeCIdMaskPreNum   Unsigned32,
    tmnxLocUsrDbPppoeCIdMaskSufStr   TmnxLocUsrDbMaskString,
    tmnxLocUsrDbPppoeCIdMaskSufNum   Unsigned32,
    tmnxLocUsrDbDhcpCIdMaskPreStr    TmnxLocUsrDbMaskString,
    tmnxLocUsrDbDhcpCIdMaskPreNum    Unsigned32,
    tmnxLocUsrDbDhcpCIdMaskSufStr    TmnxLocUsrDbMaskString,
    tmnxLocUsrDbDhcpCIdMaskSufNum    Unsigned32,
    tmnxLocUsrDbHostCount            Unsigned32,
    tmnxLocUsrDbCreationOrigin       TmnxCreateOrigin
}

tmnxLocUsrDbUserDatabaseName     OBJECT-TYPE
    SYNTAX      TNamedItem
    MAX-ACCESS  not-accessible
    STATUS      current
    DESCRIPTION
        "The value of the object tmnxLocUsrDbUserDatabaseName specifies the
         name of this local user database."
    ::= { tmnxLocalUserDbEntry 1 }

tmnxLocUsrDbRowStatus            OBJECT-TYPE
    SYNTAX      RowStatus
    MAX-ACCESS  read-create
    STATUS      current
    DESCRIPTION
        "The value of tmnxLocUsrDbRowStatus specifies the row status of this
         row."
    ::= { tmnxLocalUserDbEntry 2 }

tmnxLocUsrDbLastChangeTime       OBJECT-TYPE
    SYNTAX      TimeStamp
    MAX-ACCESS  read-only
    STATUS      current
    DESCRIPTION
        "The value of the object tmnxLocUsrDbLastChangeTime indicates the
         sysUpTime at the time of the last modification of this entry."
    ::= { tmnxLocalUserDbEntry 3 }

tmnxLocUsrDbAdminState           OBJECT-TYPE
    SYNTAX      TmnxAdminState
    MAX-ACCESS  read-create
    STATUS      current
    DESCRIPTION
        "The value of the object tmnxLocUsrDbAdminState specifies the
         administrative state of the tmnxLocalUserDbEntry."
    DEFVAL      { outOfService }
    ::= { tmnxLocalUserDbEntry 4 }

tmnxLocUsrDbDescription          OBJECT-TYPE
    SYNTAX      TItemDescription
    MAX-ACCESS  read-create
    STATUS      current
    DESCRIPTION
        "The value of the object tmnxLocUsrDbDescription specifies a user
         provided description for this local user database."
    DEFVAL      { "" }
    ::= { tmnxLocalUserDbEntry 5 }

tmnxLocUsrDbMatchTypeDhcp1       OBJECT-TYPE
    SYNTAX      TmnxLocUsrDbMatchTypeDhcp
    MAX-ACCESS  read-create
    STATUS      current
    DESCRIPTION
        "The value of the object tmnxLocUsrDbMatchTypeDhcp1 specifies the type
         of the first user match criterion.

         The purpose of a user match criterion is to identify a DHCP host. The
         order of the user match criteria in the tmnxLocalUserDbEntry specifies
         the evaluation order.

         The match type specifies which of the index objects in the
         tmnxLocUsrDbDhcpTable must be used as the user match criterion.

         The values of the objects tmnxLocUsrDbMatchTypeDhcp1,2,3,4 must
         be set consistently, such that, if the value of
         tmnxLocUsrDbMatchTypeDhcp1 is equal to 'none', all subsequent
         tmnxLocUsrDbMatchTypeDhcp2,3,4 objects are also equal  to 'none'.

         The value of the object tmnxLocUsrDbMatchTypeDhcp1 can only be
         modified while the value of tmnxLocUsrDbAdminState is equal to
         'outOfService'."
    DEFVAL      { none }
    ::= { tmnxLocalUserDbEntry 6 }

tmnxLocUsrDbMatchTypeDhcp2       OBJECT-TYPE
    SYNTAX      TmnxLocUsrDbMatchTypeDhcp
    MAX-ACCESS  read-create
    STATUS      current
    DESCRIPTION
        "The value of the object tmnxLocUsrDbMatchTypeDhcp2 specifies the type
         of the second user match criterion.

         The value of the object tmnxLocUsrDbMatchTypeDhcp2 can only be
         modified while the value of tmnxLocUsrDbAdminState is equal to
         'outOfService'."
    DEFVAL      { none }
    ::= { tmnxLocalUserDbEntry 7 }

tmnxLocUsrDbMatchTypeDhcp3       OBJECT-TYPE
    SYNTAX      TmnxLocUsrDbMatchTypeDhcp
    MAX-ACCESS  read-create
    STATUS      current
    DESCRIPTION
        "The value of the object tmnxLocUsrDbMatchTypeDhcp3 specifies the type
         of the third user match criterion.

         The value of the object tmnxLocUsrDbMatchTypeDhcp3 can only be
         modified while the value of tmnxLocUsrDbAdminState is equal to
         'outOfService'."
    DEFVAL      { none }
    ::= { tmnxLocalUserDbEntry 8 }

tmnxLocUsrDbMatchTypeDhcp4       OBJECT-TYPE
    SYNTAX      TmnxLocUsrDbMatchTypeDhcp
    MAX-ACCESS  read-create
    STATUS      current
    DESCRIPTION
        "The value of the object tmnxLocUsrDbMatchTypeDhcp4 specifies the type
         of the fourth user match criterion.

         The value of the object tmnxLocUsrDbMatchTypeDhcp4 can only be
         modified while the value of tmnxLocUsrDbAdminState is equal to
         'outOfService'."
    DEFVAL      { none }
    ::= { tmnxLocalUserDbEntry 9 }

tmnxLocUsrDbMatchTypePppoe1      OBJECT-TYPE
    SYNTAX      TmnxLocUsrDbMatchTypePppoe
    MAX-ACCESS  read-create
    STATUS      current
    DESCRIPTION
        "The value of the object tmnxLocUsrDbMatchTypePppoe1 specifies the type
         of the first user match criterion.

         The purpose of a user match criterion is to identify a PPPoE user. The
         order of the user match criteria in the tmnxLocalUserDbEntry specifies
         the evaluation order.

         The match type specifies which of the index objects in the
         tmnxLocUsrDbPppoeTable must be used as the user match criterion.

         The values of the objects tmnxLocUsrDbMatchTypePppoe1,2,3 must
         be set consistently, such that, if the value of
         tmnxLocUsrDbMatchTypePppoe1 is equal to 'none', all subsequent
         tmnxLocUsrDbMatchTypePppoe2,3 objects are also equal  to 'none'.

         The value of the object tmnxLocUsrDbMatchTypePppoe1 can only be
         modified while the value of tmnxLocUsrDbAdminState is equal to
         'outOfService'."
    DEFVAL      { none }
    ::= { tmnxLocalUserDbEntry 10 }

tmnxLocUsrDbMatchTypePppoe2      OBJECT-TYPE
    SYNTAX      TmnxLocUsrDbMatchTypePppoe
    MAX-ACCESS  read-create
    STATUS      current
    DESCRIPTION
        "The value of the object tmnxLocUsrDbMatchTypePppoe2 specifies the type
         of the second user match criterion.

         The value of the object tmnxLocUsrDbMatchTypePppoe2 can only be
         modified while the value of tmnxLocUsrDbAdminState is equal to
         'outOfService'."
    DEFVAL      { none }
    ::= { tmnxLocalUserDbEntry 11 }

tmnxLocUsrDbMatchTypePppoe3      OBJECT-TYPE
    SYNTAX      TmnxLocUsrDbMatchTypePppoe
    MAX-ACCESS  read-create
    STATUS      current
    DESCRIPTION
        "The value of the object tmnxLocUsrDbMatchTypePppoe3 specifies the type
         of the third user match criterion.

         The value of the object tmnxLocUsrDbMatchTypePppoe3 can only be
         modified while the value of tmnxLocUsrDbAdminState is equal to
         'outOfService'."
    DEFVAL      { none }
    ::= { tmnxLocalUserDbEntry 12 }

tmnxLocUsrDbPppoeCIdMaskPreStr   OBJECT-TYPE
    SYNTAX      TmnxLocUsrDbMaskString
    MAX-ACCESS  read-create
    STATUS      obsolete
    DESCRIPTION
        "The value of the object tmnxLocUsrDbPppoeCIdMaskPreStr specifies a
         substring that is stripped of the start of the incoming circuitId
         before it is matched against the value configured in
         tmnxLocUsrDbPppoeCircuitId.

         This string can only contain printable ASCII characters. Character '*'
         is a wildcard that matches any substring. It can be escaped by
         character '\'."
    DEFVAL      { "" }
    ::= { tmnxLocalUserDbEntry 13 }

tmnxLocUsrDbPppoeCIdMaskPreNum   OBJECT-TYPE
    SYNTAX      Unsigned32 (0..127)
    MAX-ACCESS  read-create
    STATUS      obsolete
    DESCRIPTION
        "The value of the object tmnxLocUsrDbPppoeCIdMaskPreNum specifies the
         number of characters to remove from the start of the incoming
         circuitId before it is matched against the value configured in
         tmnxLocUsrDbPppoeCircuitId."
    DEFVAL      { 0 }
    ::= { tmnxLocalUserDbEntry 14 }

tmnxLocUsrDbPppoeCIdMaskSufStr   OBJECT-TYPE
    SYNTAX      TmnxLocUsrDbMaskString
    MAX-ACCESS  read-create
    STATUS      obsolete
    DESCRIPTION
        "The value of the object tmnxLocUsrDbPppoeCIdMaskSufStr specifies a
         substring that is stripped of the end of the incoming circuitId before
         it is matched against the value configured in
         tmnxLocUsrDbPppoeCircuitId.

         This string can only contain printable ASCII characters. Character '*'
         is a wildcard that matches any substring. It can be escaped by
         character '\'."
    DEFVAL      { "" }
    ::= { tmnxLocalUserDbEntry 15 }

tmnxLocUsrDbPppoeCIdMaskSufNum   OBJECT-TYPE
    SYNTAX      Unsigned32 (0..127)
    MAX-ACCESS  read-create
    STATUS      obsolete
    DESCRIPTION
        "The value of the object tmnxLocUsrDbPppoeCIdMaskSufNum specifies the
         number of characters to remove from the end of the incoming circuitId
         before it is matched against the value configured in
         tmnxLocUsrDbPppoeCircuitId."
    DEFVAL      { 0 }
    ::= { tmnxLocalUserDbEntry 16 }

tmnxLocUsrDbDhcpCIdMaskPreStr    OBJECT-TYPE
    SYNTAX      TmnxLocUsrDbMaskString
    MAX-ACCESS  read-create
    STATUS      obsolete
    DESCRIPTION
        "The value of the object tmnxLocUsrDbDhcpCIdMaskPreStr specifies a
         substring that is stripped of the start of the incoming circuitId
         before it is matched against the value configured in
         tmnxLocUsrDbDhcpCircuitId.

         This string can only contain printable ASCII characters. Character '*'
         is a wildcard that matches any substring. It can be escaped by
         character '\'."
    DEFVAL      { "" }
    ::= { tmnxLocalUserDbEntry 17 }

tmnxLocUsrDbDhcpCIdMaskPreNum    OBJECT-TYPE
    SYNTAX      Unsigned32 (0..127)
    MAX-ACCESS  read-create
    STATUS      obsolete
    DESCRIPTION
        "The value of the object tmnxLocUsrDbDhcpCIdMaskPreNum specifies the
         number of characters to remove from the start of the incoming
         circuitId before it is matched against the value configured in
         tmnxLocUsrDbDhcpCircuitId."
    DEFVAL      { 0 }
    ::= { tmnxLocalUserDbEntry 18 }

tmnxLocUsrDbDhcpCIdMaskSufStr    OBJECT-TYPE
    SYNTAX      TmnxLocUsrDbMaskString
    MAX-ACCESS  read-create
    STATUS      obsolete
    DESCRIPTION
        "The value of the object tmnxLocUsrDbDhcpCIdMaskSufStr specifies a
         substring that is stripped of the end of the incoming circuitId before
         it is matched against the value configured in
         tmnxLocUsrDbDhcpCircuitId.

         This string can only contain printable ASCII characters. Character '*'
         is a wildcard that matches any substring. It can be escaped by
         character '\'."
    DEFVAL      { "" }
    ::= { tmnxLocalUserDbEntry 19 }

tmnxLocUsrDbDhcpCIdMaskSufNum    OBJECT-TYPE
    SYNTAX      Unsigned32 (0..127)
    MAX-ACCESS  read-create
    STATUS      obsolete
    DESCRIPTION
        "The value of the object tmnxLocUsrDbDhcpCIdMaskSufNum specifies the
         number of characters to remove from the end of the incoming circuitId
         before it is matched against the value configured in
         tmnxLocUsrDbDhcpCircuitId."
    DEFVAL      { 0 }
    ::= { tmnxLocalUserDbEntry 20 }

tmnxLocUsrDbHostCount            OBJECT-TYPE
    SYNTAX      Unsigned32
    MAX-ACCESS  read-only
    STATUS      current
    DESCRIPTION
        "The value of the object tmnxLocUsrDbHostCount indicates how many host
         there are configured in this local user database."
    ::= { tmnxLocalUserDbEntry 21 }

tmnxLocUsrDbCreationOrigin       OBJECT-TYPE
    SYNTAX      TmnxCreateOrigin
    MAX-ACCESS  read-only
    STATUS      current
    DESCRIPTION
        "The value of tmnxLocUsrDbCreationOrigin indicates the mechanism which
         created this local user database."
    ::= { tmnxLocalUserDbEntry 22 }

tmnxLocUsrDbPppoeTableLastChange OBJECT-TYPE
    SYNTAX      TimeStamp
    MAX-ACCESS  read-only
    STATUS      current
    DESCRIPTION
        "The value of the object tmnxLocUsrDbPppoeTableLastChange indicates the
         value of sysUpTime at the time of the last modification of an entry in
         the tmnxLocUsrDbPppoeTable."
    ::= { tmnxLocalUserDbObjs 3 }

tmnxLocUsrDbPppoeTable           OBJECT-TYPE
    SYNTAX      SEQUENCE OF TmnxLocUsrDbPppoeEntry
    MAX-ACCESS  not-accessible
    STATUS      current
    DESCRIPTION
        "The table tmnxLocUsrDbPppoeTable contains objects to configure PPPoE
         hosts."
    ::= { tmnxLocalUserDbObjs 4 }

tmnxLocUsrDbPppoeEntry           OBJECT-TYPE
    SYNTAX      TmnxLocUsrDbPppoeEntry
    MAX-ACCESS  not-accessible
    STATUS      current
    DESCRIPTION
        "Each row represents a (set of) host.

         Entries in this table can be created or deleted via SNMP operations."
    INDEX       {
        tmnxLocUsrDbUserDatabaseName,
        tmnxLocUsrDbPppoeHostName
    }
    ::= { tmnxLocUsrDbPppoeTable 1 }

TmnxLocUsrDbPppoeEntry           ::= SEQUENCE
{
    tmnxLocUsrDbPppoeHostName        DisplayString,
    tmnxLocUsrDbPppoeRowStatus       RowStatus,
    tmnxLocUsrDbPppoeLastChangeTime  TimeStamp,
    tmnxLocUsrDbPppoeAdminState      TmnxAdminState,
    tmnxLocUsrDbPppoeMacAddress      MacAddress,
    tmnxLocUsrDbPppoeCircuitIdFmt    TmnxLocUsrDbDataFormat,
    tmnxLocUsrDbPppoeCircuitId       OCTET STRING,
    tmnxLocUsrDbPppoeRemoteId        OCTET STRING,
    tmnxLocUsrDbPppoeUserNameFormat  TmnxLocUsrDbUserNameFormat,
    tmnxLocUsrDbPppoeUserName        TmnxPppoeUserNameOrEmpty,
    tmnxLocUsrDbPppoePasswordType    TmnxLocUsrDbPasswordType,
    tmnxLocUsrDbPppoePassword        OCTET STRING,
    tmnxLocUsrDbPppoeAddrType        InetAddressType,
    tmnxLocUsrDbPppoeAddress         InetAddress,
    tmnxLocUsrDbPppoePool            TNamedItemOrEmpty,
    tmnxLocUsrDbPppoeUseGiAddress    TruthValue,
    tmnxLocUsrDbPppoeIdStringOptNum  Unsigned32,
    tmnxLocUsrDbPppoeSubscriberId    TmnxSubIdentStringOrEmpty,
    tmnxLocUsrDbPppoeSlaProfString   TmnxSlaProfileStringOrEmpty,
    tmnxLocUsrDbPppoeSubProfString   TmnxSubProfileStringOrEmpty,
    tmnxLocUsrDbPppoeAppProfString   DisplayString,
    tmnxLocUsrDbPppoeAncpString      TmnxAncpStringOrZero,
    tmnxLocUsrDbPppoeInterDestId     TNamedItemOrEmpty,
    tmnxLocUsrDbPppoeUseClientPool   TruthValue,
    tmnxLocUsrDbPppoePadoDelay       TmnxPppoePadoDelay,
    tmnxLocUsrDbPppoeServiceName     DisplayString,
    tmnxLocUsrDbPppoeL2tpTunnelGroup TmnxL2tpTunnelGroupNameOrEmpty,
    tmnxLocUsrDbPppoeAuthPolicy      TNamedItemOrEmpty,
    tmnxLocUsrDbPppoeRetailerSvcId   TmnxServId,
    tmnxLocUsrDbPppoeCategoryMapName TNamedItemOrEmpty,
    tmnxLocUsrDbPppoeDefMsapPolicy   TPolicyStatementNameOrEmpty,
    tmnxLocUsrDbPppoeDefMsapService  TmnxServId,
    tmnxLocUsrDbPppoeDefMsapGroupIf  TNamedItemOrEmpty,
    tmnxLocUsrDbPppoeRemoteIdFmt     TmnxLocUsrDbDataFormat,
    tmnxLocUsrDbPppoeL2tpSvcId       TmnxServId,
    tmnxLocUsrDbPppoeService         TmnxServId,
    tmnxLocUsrDbPppoeInterface       TNamedItemOrEmpty,
    tmnxLocUsrDbPppoePrefixLength    InetAddressPrefixLength,
    tmnxLocUsrDbPppoeFltrProfString  TmnxFilterProfileStringOrEmpty,
    tmnxLocUsrDbPppoeSapId           DisplayString,
    tmnxLocUsrDbPppoeIngIpv4FltrId   TIPFilterIdOrEmpty,
    tmnxLocUsrDbPppoeEgrIpv4FltrId   TIPFilterIdOrEmpty,
    tmnxLocUsrDbPppoeIngIpv6FltrId   TIPFilterIdOrEmpty,
    tmnxLocUsrDbPppoeEgrIpv6FltrId   TIPFilterIdOrEmpty,
    tmnxLocUsrDbPppoeUseGiAddrScope  INTEGER,
    tmnxLocUsrDbPppoeSecPool         TNamedItemOrEmpty,
    tmnxLocUsrDbPppoePreAuthPolicy   TNamedItemOrEmpty,
    tmnxLocUsrDbPppoeUseCPDelimiter  DisplayString,
    tmnxLocUsrDbPppoeEncTagRangeType TmnxPortEncapType,
    tmnxLocUsrDbPppoeEncTagRangeStrt TmnxEncapVal,
    tmnxLocUsrDbPppoeEncTagRangeEnd  TmnxEncapVal,
    tmnxLocUsrDbPppoeMsapGroupIfPfx  TmnxLudbMsapGrpIfPfxSfxType,
    tmnxLocUsrDbPppoeMsapGroupIfSfx  TmnxLudbMsapGrpIfPfxSfxType,
    tmnxLocUsrDbPppoeAcctPolicy      TNamedItemOrEmpty,
    tmnxLocUsrDbPppoeDuplAcctPolicy  TNamedItemOrEmpty,
    tmnxLocUsrDbPppoeIpv6Addr        InetAddress,
    tmnxLocUsrDbPppoeIpv6DelPfx      InetAddress,
    tmnxLocUsrDbPppoeIpv6DelPfxLen   InetAddressPrefixLength,
    tmnxLocUsrDbPppoeIpv6ReqDelPfxLn InetAddressPrefixLength,
    tmnxLocUsrDbPppoeIpv6SlaacPfx    InetAddress,
    tmnxLocUsrDbPppoeIpv6SlaacPfxLen InetAddressPrefixLength,
    tmnxLocUsrDbPppoeForceIpv6cp     TruthValue,
    tmnxLocUsrDbPppoeIpv6DelPfxPool  TNamedItemOrEmpty,
    tmnxLocUsrDbPppoeIpv6WanAddrPool TNamedItemOrEmpty,
    tmnxLocUsrDbPppoeIpv6SlaacPfxPl  TNamedItemOrEmpty,
    tmnxLocUsrDbPppoeDerivedId       DisplayString
}

tmnxLocUsrDbPppoeHostName        OBJECT-TYPE
    SYNTAX      DisplayString (SIZE (1..32))
    MAX-ACCESS  not-accessible
    STATUS      current
    DESCRIPTION
        "The value of the object tmnxLocUsrDbPppoeHostName specifies the name
         of this host or set of hosts.

         To identify the hosts, the PPPoE parameters are matched against the
         values of these objects: tmnxLocUsrDbPppoeMacAddress,
         tmnxLocUsrDbPppoeCircuitId, tmnxLocUsrDbPppoeRemoteId,
         tmnxLocUsrDbPppoeUserName, tmnxLocUsrDbPppoeServiceName and
         tmnxLocUsrDbPppoeSapId."
    ::= { tmnxLocUsrDbPppoeEntry 1 }

tmnxLocUsrDbPppoeRowStatus       OBJECT-TYPE
    SYNTAX      RowStatus
    MAX-ACCESS  read-create
    STATUS      current
    DESCRIPTION
        "The value of the object tmnxLocUsrDbPppoeRowStatus specifies the row
         status of this entry."
    ::= { tmnxLocUsrDbPppoeEntry 2 }

tmnxLocUsrDbPppoeLastChangeTime  OBJECT-TYPE
    SYNTAX      TimeStamp
    MAX-ACCESS  read-only
    STATUS      current
    DESCRIPTION
        "The value of the object tmnxLocUsrDbPppoeLastChangeTime indicates the
         sysUpTime at the time of the last modification of this entry."
    ::= { tmnxLocUsrDbPppoeEntry 3 }

tmnxLocUsrDbPppoeAdminState      OBJECT-TYPE
    SYNTAX      TmnxAdminState
    MAX-ACCESS  read-create
    STATUS      current
    DESCRIPTION
        "The value of the object tmnxLocUsrDbPppoeAdminState specifies the
         administrative state of the tmnxLocUsrDbPppoeEntry."
    DEFVAL      { outOfService }
    ::= { tmnxLocUsrDbPppoeEntry 4 }

tmnxLocUsrDbPppoeMacAddress      OBJECT-TYPE
    SYNTAX      MacAddress
    MAX-ACCESS  read-create
    STATUS      current
    DESCRIPTION
        "The value of the object tmnxLocUsrDbPppoeMacAddress specifies the MAC
         address to match against.

         If the value of this object is set to all zeros, then it is not used."
    DEFVAL      { '000000000000'H }
    ::= { tmnxLocUsrDbPppoeEntry 5 }

tmnxLocUsrDbPppoeCircuitIdFmt    OBJECT-TYPE
    SYNTAX      TmnxLocUsrDbDataFormat
    MAX-ACCESS  read-create
    STATUS      current
    DESCRIPTION
        "The value of the object tmnxLocUsrDbPppoeCircuitIdFmt specifies how
         the value of tmnxLocUsrDbPppoeCircuitId must be formatted."
    DEFVAL      { ascii }
    ::= { tmnxLocUsrDbPppoeEntry 6 }

tmnxLocUsrDbPppoeCircuitId       OBJECT-TYPE
    SYNTAX      OCTET STRING (SIZE (0..127))
    MAX-ACCESS  read-create
    STATUS      current
    DESCRIPTION
        "The value of the object tmnxLocUsrDbPppoeCircuitId specifies the
         circuit Id to match against.

         If the value of this object is the empty string, then it is not used."
    DEFVAL      { ''H }
    ::= { tmnxLocUsrDbPppoeEntry 7 }

tmnxLocUsrDbPppoeRemoteId        OBJECT-TYPE
    SYNTAX      OCTET STRING (SIZE (0..255))
    MAX-ACCESS  read-create
    STATUS      current
    DESCRIPTION
        "The value of the object tmnxLocUsrDbPppoeRemoteId specifies the remote
         Id to match against.

         If the value of this object is the empty string, then it is not used."
    DEFVAL      { "" }
    ::= { tmnxLocUsrDbPppoeEntry 8 }

tmnxLocUsrDbPppoeUserNameFormat  OBJECT-TYPE
    SYNTAX      TmnxLocUsrDbUserNameFormat
    MAX-ACCESS  read-create
    STATUS      current
    DESCRIPTION
        "The value of the object tmnxLocUsrDbPppoeUserNameFormat specifies the
         format of tmnxLocUsrDbPppoeUserName."
    DEFVAL      { none }
    ::= { tmnxLocUsrDbPppoeEntry 9 }

tmnxLocUsrDbPppoeUserName        OBJECT-TYPE
    SYNTAX      TmnxPppoeUserNameOrEmpty
    MAX-ACCESS  read-create
    STATUS      current
    DESCRIPTION
        "The value of the object tmnxLocUsrDbPppoeUserName specifies the PPPoE
         username to match against.

         If the value of this object is the empty string, then it is not used.
         In that case, tmnxLocUsrDbPppoeUserNameFormat must be 'none (0)'."
    DEFVAL      { "" }
    ::= { tmnxLocUsrDbPppoeEntry 10 }

tmnxLocUsrDbPppoePasswordType    OBJECT-TYPE
    SYNTAX      TmnxLocUsrDbPasswordType
    MAX-ACCESS  read-create
    STATUS      current
    DESCRIPTION
        "The value of the object tmnxLocUsrDbPppoePasswordType specifies the
         type of tmnxLocUsrDbPppoePassword."
    DEFVAL      { none }
    ::= { tmnxLocUsrDbPppoeEntry 11 }

tmnxLocUsrDbPppoePassword        OBJECT-TYPE
    SYNTAX      OCTET STRING (SIZE (0..64))
    MAX-ACCESS  read-create
    STATUS      current
    DESCRIPTION
        "The value of the object tmnxLocUsrDbPppoePassword specifies the
         password of this host.

         This object can only be set if tmnxLocUsrDbPppoeUserName is not an
         empty string.

         If the value of this object is not an empty string, then the value of
         tmnxLocUsrDbPppoePasswordType must be either 'pap(2)' or 'chap(3)'.

         This object will always return an empty string on a read."
    DEFVAL      { ''H }
    ::= { tmnxLocUsrDbPppoeEntry 12 }

tmnxLocUsrDbPppoeAddrType        OBJECT-TYPE
    SYNTAX      InetAddressType
    MAX-ACCESS  read-create
    STATUS      current
    DESCRIPTION
        "The value of the object tmnxLocUsrDbPppoeAddrType specifies the type
         of tmnxLocUsrDbPppoeAddress."
    DEFVAL      { unknown }
    ::= { tmnxLocUsrDbPppoeEntry 13 }

tmnxLocUsrDbPppoeAddress         OBJECT-TYPE
    SYNTAX      InetAddress (SIZE (0|4|16))
    MAX-ACCESS  read-create
    STATUS      current
    DESCRIPTION
        "The value of the object tmnxLocUsrDbPppoeAddress specifies the IP
         address of this host.

         This object can only be configured if object tmnxLocUsrDbPppoePool
         contains the empty string and object tmnxLocUsrDbPppoeUseGiAddress is
         'false(2)'."
    DEFVAL      { ''H }
    ::= { tmnxLocUsrDbPppoeEntry 14 }

tmnxLocUsrDbPppoePool            OBJECT-TYPE
    SYNTAX      TNamedItemOrEmpty
    MAX-ACCESS  read-create
    STATUS      current
    DESCRIPTION
        "The value of the object tmnxLocUsrDbPppoePool specifies the IP address
         pool which is used to search for an IP address for this host.

         This object can only be configured if object tmnxLocUsrDbPppoeAddrType
         is 'unknown(0)' and the values of the objects
         tmnxLocUsrDbPppoeUseGiAddress and tmnxLocUsrDbPppoeUseClientPool are
         'false (2)'."
    DEFVAL      { "" }
    ::= { tmnxLocUsrDbPppoeEntry 15 }

tmnxLocUsrDbPppoeUseGiAddress    OBJECT-TYPE
    SYNTAX      TruthValue
    MAX-ACCESS  read-create
    STATUS      current
    DESCRIPTION
        "The value of the object tmnxLocUsrDbPppoeUseGiAddress specifies
         whether the GI address is used to search for an IP address for this
         host.

         If the value of this object is set to 'true(1)', then the Gateway IP
         address is used.

         This object can only be set to 'true(1)' when the value of
         tmnxLocUsrDbPppoeAddrType is 'unknown(0)' and tmnxLocUsrDbPppoePool
         contains the empty string."
    DEFVAL      { false }
    ::= { tmnxLocUsrDbPppoeEntry 16 }

tmnxLocUsrDbPppoeIdStringOptNum  OBJECT-TYPE
    SYNTAX      Unsigned32 (0..254)
    MAX-ACCESS  read-create
    STATUS      current
    DESCRIPTION
        "The value of the object tmnxLocUsrDbPppoeIdStringOptNum specifies the
         option number that the DHCP server uses to send the identification
         strings to the PPPoE client.

         If the value of this object is 0, then no identification strings will
         be sent."
    DEFVAL      { 0 }
    ::= { tmnxLocUsrDbPppoeEntry 17 }

tmnxLocUsrDbPppoeSubscriberId    OBJECT-TYPE
    SYNTAX      TmnxSubIdentStringOrEmpty
    MAX-ACCESS  read-create
    STATUS      current
    DESCRIPTION
        "The value of the object tmnxLocUsrDbPppoeSubscriberId specifies the
         subscriber Id which is encoded in the identification strings."
    DEFVAL      { "" }
    ::= { tmnxLocUsrDbPppoeEntry 18 }

tmnxLocUsrDbPppoeSlaProfString   OBJECT-TYPE
    SYNTAX      TmnxSlaProfileStringOrEmpty
    MAX-ACCESS  read-create
    STATUS      current
    DESCRIPTION
        "The value of the object tmnxLocUsrDbPppoeSlaProfString specifies the
         SLA profile string which is encoded in the identification strings."
    DEFVAL      { "" }
    ::= { tmnxLocUsrDbPppoeEntry 19 }

tmnxLocUsrDbPppoeSubProfString   OBJECT-TYPE
    SYNTAX      TmnxSubProfileStringOrEmpty
    MAX-ACCESS  read-create
    STATUS      current
    DESCRIPTION
        "The value of the object tmnxLocUsrDbPppoeSubProfString specifies the
         subscriber profile string which is encoded in the identification
         strings."
    DEFVAL      { "" }
    ::= { tmnxLocUsrDbPppoeEntry 20 }

tmnxLocUsrDbPppoeAppProfString   OBJECT-TYPE
    SYNTAX      DisplayString (SIZE (0..16))
    MAX-ACCESS  read-create
    STATUS      current
    DESCRIPTION
        "The value of the object tmnxLocUsrDbPppoeAppProfString specifies the
         application profile string which is encoded in the identification
         strings."
    DEFVAL      { "" }
    ::= { tmnxLocUsrDbPppoeEntry 21 }

tmnxLocUsrDbPppoeAncpString      OBJECT-TYPE
    SYNTAX      TmnxAncpStringOrZero
    MAX-ACCESS  read-create
    STATUS      current
    DESCRIPTION
        "The value of the object tmnxLocUsrDbPppoeAncpString specifies the ANCP
         string which is encoded in the identification strings."
    DEFVAL      { "" }
    ::= { tmnxLocUsrDbPppoeEntry 22 }

tmnxLocUsrDbPppoeInterDestId     OBJECT-TYPE
    SYNTAX      TNamedItemOrEmpty
    MAX-ACCESS  read-create
    STATUS      current
    DESCRIPTION
        "The value of the object tmnxLocUsrDbPppoeInterDestId specifies the
         intermediate destination identifier which is encoded in the
         identification strings."
    DEFVAL      { "" }
    ::= { tmnxLocUsrDbPppoeEntry 23 }

tmnxLocUsrDbPppoeUseClientPool   OBJECT-TYPE
    SYNTAX      TruthValue
    MAX-ACCESS  read-create
    STATUS      current
    DESCRIPTION
        "The value of the object tmnxLocUsrDbPppoeUseClientPool specifies if
         the IP address pool used to search for an IP address for this host is
         to be indicated by the vendor-specific sub-option 13 of the DHCP
         option 82.

         If the value of this object is set to 'true (1)', the IP address pool
         indicated by the sub-option 13 is used.

         This object can only be set to 'true (1)' when the value of
         tmnxLocUsrDbPppoeAddrType is 'unknown (0)' and tmnxLocUsrDbPppoePool
         contains the empty string."
    DEFVAL      { false }
    ::= { tmnxLocUsrDbPppoeEntry 24 }

tmnxLocUsrDbPppoePadoDelay       OBJECT-TYPE
    SYNTAX      TmnxPppoePadoDelay
    UNITS       "deciseconds"
    MAX-ACCESS  read-create
    STATUS      current
    DESCRIPTION
        "The value of the object tmnxLocUsrDbPppoePadoDelay specifies the delay
         timeout before sending a PADO (PPPoE Active Discovery Offer)."
    DEFVAL      { 0 }
    ::= { tmnxLocUsrDbPppoeEntry 25 }

tmnxLocUsrDbPppoeServiceName     OBJECT-TYPE
    SYNTAX      DisplayString (SIZE (0..255))
    MAX-ACCESS  read-create
    STATUS      current
    DESCRIPTION
        "The value of the object tmnxLocUsrDbPppoeServiceName specifies the
         PPPoE service name to match against.

         If the value of this object is the empty string, then it is not used."
    DEFVAL      { "" }
    ::= { tmnxLocUsrDbPppoeEntry 26 }

tmnxLocUsrDbPppoeL2tpTunnelGroup OBJECT-TYPE
    SYNTAX      TmnxL2tpTunnelGroupNameOrEmpty
    MAX-ACCESS  read-create
    STATUS      current
    DESCRIPTION
        "The value of the object tmnxLocUsrDbPppoeL2tpTunnelGroup specifies the
         tunnel group to use to setup an L2TP tunnel/session.

         If the value of this object is the empty string, no L2TP tunneling
         will be done."
    DEFVAL      { "" }
    ::= { tmnxLocUsrDbPppoeEntry 27 }

tmnxLocUsrDbPppoeAuthPolicy      OBJECT-TYPE
    SYNTAX      TNamedItemOrEmpty
    MAX-ACCESS  read-create
    STATUS      current
    DESCRIPTION
        "The value of the object tmnxLocUsrDbPppoeAuthPolicy specifies the
         RADIUS authentication policy to use to authenticate the PPPoE host."
    DEFVAL      { "" }
    ::= { tmnxLocUsrDbPppoeEntry 28 }

tmnxLocUsrDbPppoeRetailerSvcId   OBJECT-TYPE
    SYNTAX      TmnxServId
    MAX-ACCESS  read-create
    STATUS      current
    DESCRIPTION
        "The value of the object tmnxLocUsrDbPppoeRetailerSvcId specifies the
         retailer service Id for this host.

         This object is deprecated, please use tmnxLudbPpp2RetailerServiceName."
    DEFVAL      { 0 }
    ::= { tmnxLocUsrDbPppoeEntry 29 }

tmnxLocUsrDbPppoeCategoryMapName OBJECT-TYPE
    SYNTAX      TNamedItemOrEmpty
    MAX-ACCESS  read-create
    STATUS      current
    DESCRIPTION
        "The value of the object tmnxLocUsrDbPppoeCategoryMapName specifies the
         name of the category map used when credit control is active for this
         host."
    DEFVAL      { "" }
    ::= { tmnxLocUsrDbPppoeEntry 30 }

tmnxLocUsrDbPppoeDefMsapPolicy   OBJECT-TYPE
    SYNTAX      TPolicyStatementNameOrEmpty
    MAX-ACCESS  read-create
    STATUS      current
    DESCRIPTION
        "The value of the object tmnxLocUsrDbPppoeDefMsapPolicy specifies the
         default Managed SAP policy to use to create Managed SAPs when the
         response from the Radius server does not specify a Managed SAP policy."
    DEFVAL      { "" }
    ::= { tmnxLocUsrDbPppoeEntry 31 }

tmnxLocUsrDbPppoeDefMsapService  OBJECT-TYPE
    SYNTAX      TmnxServId
    MAX-ACCESS  read-create
    STATUS      current
    DESCRIPTION
        "The value of the object tmnxLocUsrDbPppoeDefMsapService specifies the
         service ID of the service where Managed SAPs are created when there is
         no Radius server available, or the Radius server does not specify the
         service ID.

         While the value of sapTlsDefMsapService is equal to zero, no Managed
         SAPs are created when there is no Radius server-specified service ID
         available."
    DEFVAL      { 0 }
    ::= { tmnxLocUsrDbPppoeEntry 32 }

tmnxLocUsrDbPppoeDefMsapGroupIf  OBJECT-TYPE
    SYNTAX      TNamedItemOrEmpty
    MAX-ACCESS  read-create
    STATUS      current
    DESCRIPTION
        "The value of the object tmnxLocUsrDbPppoeDefMsapGroupIf specifies the
         name of the group interface where Managed SAPs are created when there
         is no Radius server available, or the Radius server does not specify
         the group interface.

         While the value of sapTlsDefMsapGroupIf is the empty string, no
         Managed SAPs are created when there is no Radius server-specified
         group interface available."
    DEFVAL      { "" }
    ::= { tmnxLocUsrDbPppoeEntry 33 }

tmnxLocUsrDbPppoeRemoteIdFmt     OBJECT-TYPE
    SYNTAX      TmnxLocUsrDbDataFormat
    MAX-ACCESS  read-create
    STATUS      current
    DESCRIPTION
        "The value of the object tmnxLocUsrDbPppoeRemoteIdFmt specifies how the
         value of tmnxLocUsrDbPppoeRemoteIdFmt must be formatted."
    DEFVAL      { ascii }
    ::= { tmnxLocUsrDbPppoeEntry 34 }

tmnxLocUsrDbPppoeL2tpSvcId       OBJECT-TYPE
    SYNTAX      TmnxServId
    MAX-ACCESS  read-create
    STATUS      current
    DESCRIPTION
        "The value of the object tmnxLocUsrDbPppoeL2tpSvcId specifies the
         service ID of the service from where to take the tunnel group
         (tmnxLocUsrDbPppoeL2tpTunnelGroup) to use to setup an L2TP LAC
         tunnel/session.

         If the value of this object is 0, L2TP tunneling will be done from the
         base router context."
    DEFVAL      { 0 }
    ::= { tmnxLocUsrDbPppoeEntry 35 }

tmnxLocUsrDbPppoeService         OBJECT-TYPE
    SYNTAX      TmnxServId
    MAX-ACCESS  read-create
    STATUS      current
    DESCRIPTION
        "The value of the object tmnxLocUsrDbPppoeService specifies the service
         ID of the service where the group interface is configured that is
         specified by the object tmnxLocUsrDbPppoeInterface."
    DEFVAL      { 0 }
    ::= { tmnxLocUsrDbPppoeEntry 36 }

tmnxLocUsrDbPppoeInterface       OBJECT-TYPE
    SYNTAX      TNamedItemOrEmpty
    MAX-ACCESS  read-create
    STATUS      current
    DESCRIPTION
        "The value of the object tmnxLocUsrDbPppoeInterface specifies the name
         of the group interface where the PPP sessions are established"
    DEFVAL      { "" }
    ::= { tmnxLocUsrDbPppoeEntry 37 }

tmnxLocUsrDbPppoePrefixLength    OBJECT-TYPE
    SYNTAX      InetAddressPrefixLength
    MAX-ACCESS  read-create
    STATUS      current
    DESCRIPTION
        "The value of the object tmnxLocUsrDbPppoePrefixLength specifies the
         prefix length of tmnxLocUsrDbPppoeAddress.

         The value of the object tmnxLocUsrDbPppoePrefixLength is only relevant
         if the value of the object tmnxLocUsrDbPppoeAddrType is not 'unknown';
         if the value of the object tmnxLocUsrDbPppoeAddrType is equal to
         'unknown', the value of tmnxLocUsrDbPppoePrefixLength is ignored."
    DEFVAL      { 32 }
    ::= { tmnxLocUsrDbPppoeEntry 38 }

tmnxLocUsrDbPppoeFltrProfString  OBJECT-TYPE
    SYNTAX      TmnxFilterProfileStringOrEmpty
    MAX-ACCESS  read-create
    STATUS      current
    DESCRIPTION
        "The value of the object tmnxLocUsrDbPppoeFltrProfString specifies the
         filter profile string which is encoded in the identification strings."
    DEFVAL      { "" }
    ::= { tmnxLocUsrDbPppoeEntry 39 }

tmnxLocUsrDbPppoeSapId           OBJECT-TYPE
    SYNTAX      DisplayString (SIZE (0..255))
    MAX-ACCESS  read-create
    STATUS      current
    DESCRIPTION
        "The value of the object tmnxLocUsrDbPppoeSapId specifies the sapId to
         match against.

         If the value of this object is the empty string, then it is not used."
    DEFVAL      { "" }
    ::= { tmnxLocUsrDbPppoeEntry 40 }

tmnxLocUsrDbPppoeIngIpv4FltrId   OBJECT-TYPE
    SYNTAX      TIPFilterIdOrEmpty
    MAX-ACCESS  read-create
    STATUS      current
    DESCRIPTION
        "The value of the object tmnxLocUsrDbPppoeIngIpv4FltrId specifies the
         ingress ipv4 filter-id to be applied to this host.

         If the value of this object is '0', then the filter as specified in
         the applicable SLA-profile will be applied.

         If the value of this object is '-1', then no filter will be applied to
         this host, irrespective of the value specified in the applicable
         SLA-profile.

         If any value between 1 and 65535 is specified this value will be used
         as filter-id for this host irrespective of the value specified in the
         applicable SLA-profile"
    DEFVAL      { 0 }
    ::= { tmnxLocUsrDbPppoeEntry 41 }

tmnxLocUsrDbPppoeEgrIpv4FltrId   OBJECT-TYPE
    SYNTAX      TIPFilterIdOrEmpty
    MAX-ACCESS  read-create
    STATUS      current
    DESCRIPTION
        "The value of the object tmnxLocUsrDbPppoeEgrIpv4FltrId specifies the
         egress ipv4 filter-id to be applied to this host.

         If the value of this object is '0', then the filter as specified in
         the applicable SLA-profile will be applied.

         If the value of this object is '-1', then no filter will be applied to
         this host, irrespective of the value specified in the applicable
         SLA-profile.

         If any value between 1 and 65535 is specified this value will be used
         as filter-id for this host irrespective of the value specified in the
         applicable SLA-profile"
    DEFVAL      { 0 }
    ::= { tmnxLocUsrDbPppoeEntry 42 }

tmnxLocUsrDbPppoeIngIpv6FltrId   OBJECT-TYPE
    SYNTAX      TIPFilterIdOrEmpty
    MAX-ACCESS  read-create
    STATUS      current
    DESCRIPTION
        "The value of the object tmnxLocUsrDbPppoeIngIpv6FltrId specifies the
         egress ipv4 filter-id to be applied to this host.

         If the value of this object is '0', then the filter as specified in
         the applicable SLA-profile will be applied.

         If the value of this object is '-1', then no filter will be applied to
         this host, irrespective of the value specified in the applicable
         SLA-profile.

         If any value between 1 and 65535 is specified this value will be used
         as filter-id for this host irrespective of the value specified in the
         applicable SLA-profile"
    DEFVAL      { 0 }
    ::= { tmnxLocUsrDbPppoeEntry 43 }

tmnxLocUsrDbPppoeEgrIpv6FltrId   OBJECT-TYPE
    SYNTAX      TIPFilterIdOrEmpty
    MAX-ACCESS  read-create
    STATUS      current
    DESCRIPTION
        "The value of the object tmnxLocUsrDbPppoeEgrIpv6FltrId specifies the
         egress ipv4 filter-id to be applied to this host.

         If the value of this object is '0', then the filter as specified in
         the applicable SLA-profile will be applied.

         If the value of this object is '-1', then no filter will be applied to
         this host, irrespective of the value specified in the applicable
         SLA-profile.

         If any value between 1 and 65535 is specified this value will be used
         as filter-id for this host irrespective of the value specified in the
         applicable SLA-profile"
    DEFVAL      { 0 }
    ::= { tmnxLocUsrDbPppoeEntry 44 }

tmnxLocUsrDbPppoeUseGiAddrScope  OBJECT-TYPE
    SYNTAX      INTEGER {
        subnet (0),
        pool   (1)
    }
    MAX-ACCESS  read-create
    STATUS      current
    DESCRIPTION
        "The value of tmnxLocUsrDbPppoeUseGiAddrScope specifies whether the GI
         address selects a single subnet or a pool.

         The value of this object is only meaningful when the value of
         tmnxLocUsrDbPppoeUseGiAddress is set to 'true(1)'."
    DEFVAL      { subnet }
    ::= { tmnxLocUsrDbPppoeEntry 45 }

tmnxLocUsrDbPppoeSecPool         OBJECT-TYPE
    SYNTAX      TNamedItemOrEmpty
    MAX-ACCESS  read-create
    STATUS      current
    DESCRIPTION
        "The value of the object tmnxLocUsrDbPppoeSecPool specifies the
         secondary IP address pool which is used to search for an IP address
         for this host.

         This object can only be configured if object tmnxLocUsrDbPppoeAddrType
         is 'unknown(0)' and the values of the objects
         tmnxLocUsrDbPppoeUseGiAddress and tmnxLocUsrDbPppoeUseClientPool are
         'false (2)'."
    DEFVAL      { "" }
    ::= { tmnxLocUsrDbPppoeEntry 46 }

tmnxLocUsrDbPppoePreAuthPolicy   OBJECT-TYPE
    SYNTAX      TNamedItemOrEmpty
    MAX-ACCESS  read-create
    STATUS      current
    DESCRIPTION
        "The value of the object tmnxLocUsrDbPppoePreAuthPolicy specifies the
         RADIUS pre-authentication policy to use to authenticate the PPPoE
         host."
    DEFVAL      { "" }
    ::= { tmnxLocUsrDbPppoeEntry 47 }

tmnxLocUsrDbPppoeUseCPDelimiter  OBJECT-TYPE
    SYNTAX      DisplayString (SIZE (0..1))
    MAX-ACCESS  read-create
    STATUS      current
    DESCRIPTION
        "A delimiter character to combine primary and secondary pool names."
    DEFVAL      { "" }
    ::= { tmnxLocUsrDbPppoeEntry 48 }

tmnxLocUsrDbPppoeEncTagRangeType OBJECT-TYPE
    SYNTAX      TmnxPortEncapType
    MAX-ACCESS  read-create
    STATUS      current
    DESCRIPTION
        "The value of tmnxLocUsrDbPppoeEncTagRangeType specifies the type of
         encapsulation protocol configured for the SAP encap tag range start
         and end values.

         Can either unknown, qEncap, qinqEncap or atmEncap."
    ::= { tmnxLocUsrDbPppoeEntry 49 }

tmnxLocUsrDbPppoeEncTagRangeStrt OBJECT-TYPE
    SYNTAX      TmnxEncapVal
    MAX-ACCESS  read-create
    STATUS      current
    DESCRIPTION
        "The value of the start label in the range of SAPs allowed on this
         host.

         A value of 0 iso 1 will be used when vci=*."
    ::= { tmnxLocUsrDbPppoeEntry 50 }

tmnxLocUsrDbPppoeEncTagRangeEnd  OBJECT-TYPE
    SYNTAX      TmnxEncapVal
    MAX-ACCESS  read-create
    STATUS      current
    DESCRIPTION
        "The value of the end label in the range of SAPs allowed on this host.

         A value of 0 iso 1 will be used when vci=*."
    ::= { tmnxLocUsrDbPppoeEntry 51 }

tmnxLocUsrDbPppoeMsapGroupIfPfx  OBJECT-TYPE
    SYNTAX      TmnxLudbMsapGrpIfPfxSfxType
    MAX-ACCESS  read-create
    STATUS      current
    DESCRIPTION
        "The value of tmnxLocUsrDbPppoeMsapGroupIfPfx specifies the type of
         prefix to be applied to the value of tmnxLocUsrDbPppoeDefMsapGroupIf
         when a local user database lookup is being performed."
    DEFVAL      { none }
    ::= { tmnxLocUsrDbPppoeEntry 52 }

tmnxLocUsrDbPppoeMsapGroupIfSfx  OBJECT-TYPE
    SYNTAX      TmnxLudbMsapGrpIfPfxSfxType
    MAX-ACCESS  read-create
    STATUS      current
    DESCRIPTION
        "The value of tmnxLocUsrDbPppoeMsapGroupIfSfx specifies the type of
         suffix to be applied to the value of tmnxLocUsrDbPppoeDefMsapGroupIf
         when a local user database lookup is being performed."
    DEFVAL      { none }
    ::= { tmnxLocUsrDbPppoeEntry 53 }

tmnxLocUsrDbPppoeAcctPolicy      OBJECT-TYPE
    SYNTAX      TNamedItemOrEmpty
    MAX-ACCESS  read-create
    STATUS      current
    DESCRIPTION
        "The value of the object tmnxLocUsrDbPppoeAcctPolicy specifies the
         RADIUS accounting policy to be used for generating accounting
         information."
    DEFVAL      { "" }
    ::= { tmnxLocUsrDbPppoeEntry 54 }

tmnxLocUsrDbPppoeDuplAcctPolicy  OBJECT-TYPE
    SYNTAX      TNamedItemOrEmpty
    MAX-ACCESS  read-create
    STATUS      current
    DESCRIPTION
        "The value of the object tmnxLocUsrDbPppoeDuplAcctPolicy specifies the
         RADIUS accounting policy to be used for generating duplicate
         accounting information."
    DEFVAL      { "" }
    ::= { tmnxLocUsrDbPppoeEntry 55 }

tmnxLocUsrDbPppoeIpv6Addr        OBJECT-TYPE
    SYNTAX      InetAddress (SIZE (16))
    MAX-ACCESS  read-create
    STATUS      current
    DESCRIPTION
        "The value of the object tmnxLocUsrDbPppoeIpv6Addr specifies the IPv6
         non temporary address of this host.

         A value of 0::0 means that the address is not configured."
    DEFVAL      { '00000000000000000000000000000000'H }
    ::= { tmnxLocUsrDbPppoeEntry 56 }

tmnxLocUsrDbPppoeIpv6DelPfx      OBJECT-TYPE
    SYNTAX      InetAddress (SIZE (16))
    MAX-ACCESS  read-create
    STATUS      current
    DESCRIPTION
        "The value of the object tmnxLocUsrDbPppoeIpv6DelPfx specifies the
         delegated IPv6 prefix of this host.

         A value of 0::0 means that the prefix-address is not configured.

         The value of tmnxLocUsrDbPppoeIpv6DelPfx must be set together with the
         value of tmnxLocUsrDbPppoeIpv6DelPfxLen."
    DEFVAL      { '00000000000000000000000000000000'H }
    ::= { tmnxLocUsrDbPppoeEntry 57 }

tmnxLocUsrDbPppoeIpv6DelPfxLen   OBJECT-TYPE
    SYNTAX      InetAddressPrefixLength (0 | 48..64)
    MAX-ACCESS  read-create
    STATUS      current
    DESCRIPTION
        "The value of tmnxLocUsrDbPppoeIpv6DelPfxLen indicates the length of
         the prefix-address stored in tmnxLocUsrDbPppoeIpv6DelPfx.

         A value of 0 means that tmnxLocUsrDbPppoeIpv6DelPfx is not configured.

         The value of tmnxLocUsrDbPppoeIpv6DelPfxLen must be set together with
         the value of tmnxLocUsrDbPppoeIpv6DelPfx."
    ::= { tmnxLocUsrDbPppoeEntry 58 }

tmnxLocUsrDbPppoeIpv6ReqDelPfxLn OBJECT-TYPE
    SYNTAX      InetAddressPrefixLength (0 | 48..64)
    MAX-ACCESS  read-create
    STATUS      current
    DESCRIPTION
        "The value of tmnxLocUsrDbPppoeIpv6ReqDelPfxLn specifies the number of
         bits that can be allocated to a Delegated Prefix for IPv6."
    DEFVAL      { 0 }
    ::= { tmnxLocUsrDbPppoeEntry 59 }

tmnxLocUsrDbPppoeIpv6SlaacPfx    OBJECT-TYPE
    SYNTAX      InetAddress (SIZE (16))
    MAX-ACCESS  read-create
    STATUS      current
    DESCRIPTION
        "The value of the object tmnxLocUsrDbPppoeIpv6SlaacPfx specifies the
         IPv6 prefix used for stateless address autoconfiguration.

         A value of 0::0 means that the prefix-address is not configured.

         The value of tmnxLocUsrDbPppoeIpv6SlaacPfx must be set together with
         the value of tmnxLocUsrDbPppoeIpv6SlaacPfxLen."
    DEFVAL      { '00000000000000000000000000000000'H }
    ::= { tmnxLocUsrDbPppoeEntry 60 }

tmnxLocUsrDbPppoeIpv6SlaacPfxLen OBJECT-TYPE
    SYNTAX      InetAddressPrefixLength (0 | 64)
    MAX-ACCESS  read-create
    STATUS      current
    DESCRIPTION
        "The value of tmnxLocUsrDbPppoeIpv6SlaacPfxLen indicates the length of
         the prefix-address stored in tmnxLocUsrDbPppoeIpv6SlaacPfx.

         A value of 0 means that tmnxLocUsrDbPppoeIpv6SlaacPfx is not
         configured.

         The value of tmnxLocUsrDbPppoeIpv6SlaacPfxLen must be set together
         with the value of tmnxLocUsrDbPppoeIpv6SlaacPfx."
    ::= { tmnxLocUsrDbPppoeEntry 61 }

tmnxLocUsrDbPppoeForceIpv6cp     OBJECT-TYPE
    SYNTAX      TruthValue
    MAX-ACCESS  read-create
    STATUS      current
    DESCRIPTION
        "The value of tmnxLocUsrDbPppoeForceIpv6cp specifies if the IPv6
         control protocol should be negotiated after PPP reaches the
         Network-Layer Protocol phase.

         If the value of this object is set to 'true(1)', then the IPv6 control
         protocol should be negotiated."
    DEFVAL      { false }
    ::= { tmnxLocUsrDbPppoeEntry 62 }

tmnxLocUsrDbPppoeIpv6DelPfxPool  OBJECT-TYPE
    SYNTAX      TNamedItemOrEmpty
    MAX-ACCESS  read-create
    STATUS      current
    DESCRIPTION
        "The value of tmnxLocUsrDbPppoeIpv6DelPfxPool specifies the IPv6
         address pool which is used to search for an IPv6 prefix for this host."
    DEFVAL      { "" }
    ::= { tmnxLocUsrDbPppoeEntry 63 }

tmnxLocUsrDbPppoeIpv6WanAddrPool OBJECT-TYPE
    SYNTAX      TNamedItemOrEmpty
    MAX-ACCESS  read-create
    STATUS      current
    DESCRIPTION
        "The value of tmnxLocUsrDbPppoeIpv6WanAddrPool specifies the IPv6
         address pool which is used to search for an IPv6 address for this
         host."
    DEFVAL      { "" }
    ::= { tmnxLocUsrDbPppoeEntry 64 }

tmnxLocUsrDbPppoeIpv6SlaacPfxPl  OBJECT-TYPE
    SYNTAX      TNamedItemOrEmpty
    MAX-ACCESS  read-create
    STATUS      current
    DESCRIPTION
        "The value of tmnxLocUsrDbPppoeIpv6SlaacPfxPl specifies the IPv6
         address pool which is used to search for an IPv6 address for this
         host."
    DEFVAL      { "" }
    ::= { tmnxLocUsrDbPppoeEntry 65 }

tmnxLocUsrDbPppoeDerivedId       OBJECT-TYPE
    SYNTAX      DisplayString (SIZE (0..255))
    MAX-ACCESS  read-create
    STATUS      current
    DESCRIPTION
        "The value of the object tmnxLocUsrDbPppoeDerivedId specifies a string
         to be matched with a string that uniquely identifies a host and is
         derived by a Python script from packet content available during a PPP
         setup.

         If the value of this object is the empty string, it is not used."
    DEFVAL      { "" }
    ::= { tmnxLocUsrDbPppoeEntry 66 }

tmnxLocUsrDbPppoeUnmatchedTable  OBJECT-TYPE
    SYNTAX      SEQUENCE OF TmnxLocUsrDbPppoeUnmatchedEntry
    MAX-ACCESS  not-accessible
    STATUS      current
    DESCRIPTION
        "The table tmnxLocUsrDbPppoeUnmatchedTable contains information about
         unmatched PPPoE hosts."
    ::= { tmnxLocalUserDbObjs 5 }

tmnxLocUsrDbPppoeUnmatchedEntry  OBJECT-TYPE
    SYNTAX      TmnxLocUsrDbPppoeUnmatchedEntry
    MAX-ACCESS  not-accessible
    STATUS      current
    DESCRIPTION
        "Each row represents a host (or set of hosts) that is unmatched.

         Objects tmnxLocUsrDbMatchTypePppoe1, tmnxLocUsrDbMatchTypePppoe2 and
         tmnxLocUsrDbMatchTypePppoe3 specify which objects in the
         tmnxLocUsrDbPppoeTable are used to match the PPPoE parameters against.

         This table has entries for each host in the tmnxLocUsrDbPppoeTable
         that:
         - has no objects configured that correspond with the match types, or
         - has identical values configured for the objects that correspond
           with the match types, as another DHCP host.

         Entries in this table cannot be created or deleted via SNMP
         operations."
    INDEX       {
        tmnxLocUsrDbUserDatabaseName,
        tmnxLocUsrDbPppoeHostName
    }
    ::= { tmnxLocUsrDbPppoeUnmatchedTable 1 }

TmnxLocUsrDbPppoeUnmatchedEntry  ::= SEQUENCE
{
    tmnxLocUsrDbPppoeUnMacAddress    MacAddress,
    tmnxLocUsrDbPppoeUnCircuitId     OCTET STRING,
    tmnxLocUsrDbPppoeUnRemoteId      OCTET STRING,
    tmnxLocUsrDbPppoeUnUserNameFmt   TmnxLocUsrDbUserNameFormat,
    tmnxLocUsrDbPppoeUnUserName      TmnxPppoeUserNameOrEmpty,
    tmnxLocUsrDbPppoeUnmatchedReason TmnxLocUsrDbUnmatchedReason,
    tmnxLocUsrDbPppoeUnDuplicateHost DisplayString,
    tmnxLocUsrDbPppoeUnServiceName   DisplayString,
    tmnxLocUsrDbPppoeUnSapId         DisplayString,
    tmnxLocUsrDbPppoeUnDerivedId     DisplayString,
    tmnxLocUsrDbPppoeUnEncTgRgType   TmnxPortEncapType,
    tmnxLocUsrDbPppoeUnEncTgRgStart  TmnxEncapVal,
    tmnxLocUsrDbPppoeUnEncTgRgEnd    TmnxEncapVal,
    tmnxLocUsrDbPppoeUnEncTgRgOutSta Integer32,
    tmnxLocUsrDbPppoeUnEncTgRgOutEnd Integer32,
    tmnxLocUsrDbPppoeUnEncTgRgInnSta Integer32,
    tmnxLocUsrDbPppoeUnEncTgRgInnEnd Integer32
}

tmnxLocUsrDbPppoeUnMacAddress    OBJECT-TYPE
    SYNTAX      MacAddress
    MAX-ACCESS  read-only
    STATUS      current
    DESCRIPTION
        "The value of the object tmnxLocUsrDbPppoeUnMacAddress indicates the
         MAC address of the unmatched host."
    ::= { tmnxLocUsrDbPppoeUnmatchedEntry 1 }

tmnxLocUsrDbPppoeUnCircuitId     OBJECT-TYPE
    SYNTAX      OCTET STRING (SIZE (0..127))
    MAX-ACCESS  read-only
    STATUS      current
    DESCRIPTION
        "The value of the object tmnxLocUsrDbPppoeUnCircuitId indicates the
         circuit Id of the unmatched host."
    ::= { tmnxLocUsrDbPppoeUnmatchedEntry 2 }

tmnxLocUsrDbPppoeUnRemoteId      OBJECT-TYPE
    SYNTAX      OCTET STRING (SIZE (0..255))
    MAX-ACCESS  read-only
    STATUS      current
    DESCRIPTION
        "The value of the object tmnxLocUsrDbPppoeUnRemoteId indicates the
         remote Id of the unmatched host."
    ::= { tmnxLocUsrDbPppoeUnmatchedEntry 3 }

tmnxLocUsrDbPppoeUnUserNameFmt   OBJECT-TYPE
    SYNTAX      TmnxLocUsrDbUserNameFormat
    MAX-ACCESS  read-only
    STATUS      current
    DESCRIPTION
        "The value of the object tmnxLocUsrDbPppoeUnUserNameFmt indicates the
         format of tmnxLocUsrDbPppoeUnUserName."
    ::= { tmnxLocUsrDbPppoeUnmatchedEntry 4 }

tmnxLocUsrDbPppoeUnUserName      OBJECT-TYPE
    SYNTAX      TmnxPppoeUserNameOrEmpty
    MAX-ACCESS  read-only
    STATUS      current
    DESCRIPTION
        "The value of the object tmnxLocUsrDbPppoeUnUserName indicates the
         PPPoE username of the unmatched host."
    ::= { tmnxLocUsrDbPppoeUnmatchedEntry 5 }

tmnxLocUsrDbPppoeUnmatchedReason OBJECT-TYPE
    SYNTAX      TmnxLocUsrDbUnmatchedReason
    MAX-ACCESS  read-only
    STATUS      current
    DESCRIPTION
        "The value of the object tmnxLocUsrDbPppoeUnmatchedReason indicates why
         this host is not matched."
    ::= { tmnxLocUsrDbPppoeUnmatchedEntry 6 }

tmnxLocUsrDbPppoeUnDuplicateHost OBJECT-TYPE
    SYNTAX      DisplayString (SIZE (0..32))
    MAX-ACCESS  read-only
    STATUS      current
    DESCRIPTION
        "The value of the object tmnxLocUsrDbPppoeUnDuplicateHost indicates the
         name of the host that is already matched and that has the same values,
         configured for the objects that correspond with the match types, as
         this unmatched host.

         This value of this object is the empty string, unless the value of
         tmnxLocUsrDbPppoeUnmatchedReason is 'duplicate (2)'."
    ::= { tmnxLocUsrDbPppoeUnmatchedEntry 7 }

tmnxLocUsrDbPppoeUnServiceName   OBJECT-TYPE
    SYNTAX      DisplayString (SIZE (0..255))
    MAX-ACCESS  read-only
    STATUS      current
    DESCRIPTION
        "The value of the object tmnxLocUsrDbPppoeUnServiceName indicates the
         PPPoE service name of the unmatched host."
    ::= { tmnxLocUsrDbPppoeUnmatchedEntry 8 }

tmnxLocUsrDbPppoeUnSapId         OBJECT-TYPE
    SYNTAX      DisplayString (SIZE (0..255))
    MAX-ACCESS  read-only
    STATUS      current
    DESCRIPTION
        "The value of the object tmnxLocUsrDbPppoeUnSapId indicates the sapId
         of the unmatched host."
    ::= { tmnxLocUsrDbPppoeUnmatchedEntry 9 }

tmnxLocUsrDbPppoeUnDerivedId     OBJECT-TYPE
    SYNTAX      DisplayString (SIZE (0..255))
    MAX-ACCESS  read-only
    STATUS      current
    DESCRIPTION
        "The value of the object tmnxLocUsrDbPppoeUnDerivedId indicates the
         string to be matched with a string that uniquely identifies a host and
         is derived by a Python script from packet content available during a
         PPP setup.

         If the value of this object is the empty string, it is not used."
    ::= { tmnxLocUsrDbPppoeUnmatchedEntry 10 }

tmnxLocUsrDbPppoeUnEncTgRgType   OBJECT-TYPE
    SYNTAX      TmnxPortEncapType
    MAX-ACCESS  read-only
    STATUS      current
    DESCRIPTION
        "The value of the object tmnxLocUsrDbPppoeUnEncTgRgType indicates the
         type of encapsulation protocol configured for the SAP encap tag range
         start and end values.

         Can either be unknown, qEncap, qinqEncap or atmEncap."
    ::= { tmnxLocUsrDbPppoeUnmatchedEntry 11 }

tmnxLocUsrDbPppoeUnEncTgRgStart  OBJECT-TYPE
    SYNTAX      TmnxEncapVal
    MAX-ACCESS  read-only
    STATUS      current
    DESCRIPTION
        "The value of the object tmnxLocUsrDbPppoeUnEncTgRgStart indicates the
         start label in the range of SAPs allowed on this host.

         A value of 0 iso 1 is used when vci=*."
    ::= { tmnxLocUsrDbPppoeUnmatchedEntry 12 }

tmnxLocUsrDbPppoeUnEncTgRgEnd    OBJECT-TYPE
    SYNTAX      TmnxEncapVal
    MAX-ACCESS  read-only
    STATUS      current
    DESCRIPTION
        "The value of the object tmnxLocUsrDbPppoeUnEncTgRgEnd indicates the
         end label in the range of SAPs allowed on this host.

         A value of 0 iso 1 is used when vci=*."
    ::= { tmnxLocUsrDbPppoeUnmatchedEntry 13 }

tmnxLocUsrDbPppoeUnEncTgRgOutSta OBJECT-TYPE
    SYNTAX      Integer32 (-1 | 0..4094)
    MAX-ACCESS  read-only
    STATUS      current
    DESCRIPTION
        "The value of the object tmnxLocUsrDbPppoeUnEncTgRgOutSta indicates the
         left bound (i.e. minimum value) of a range of outer VLANs allowed on
         this PPP host. Value -1 indicates tmnxLocUsrDbPppoeUnEncTgRgOutSta is
         not applicable."
    ::= { tmnxLocUsrDbPppoeUnmatchedEntry 14 }

tmnxLocUsrDbPppoeUnEncTgRgOutEnd OBJECT-TYPE
    SYNTAX      Integer32 (-1 | 0..4094)
    MAX-ACCESS  read-only
    STATUS      current
    DESCRIPTION
        "The value of the object tmnxLocUsrDbPppoeUnEncTgRgOutEnd indicates the
         right bound (i.e. maximum value) of a range of outer VLANs allowed on
         this PPP host. Value -1 indicates tmnxLocUsrDbPppoeUnEncTgRgOutEnd is
         not applicable."
    ::= { tmnxLocUsrDbPppoeUnmatchedEntry 15 }

tmnxLocUsrDbPppoeUnEncTgRgInnSta OBJECT-TYPE
    SYNTAX      Integer32 (-1 | 0..4094)
    MAX-ACCESS  read-only
    STATUS      current
    DESCRIPTION
        "The value of the object tmnxLocUsrDbPppoeUnEncTgRgInnSta indicates the
         left bound (i.e. minimum value) of a range of inner VLANs allowed on
         this PPP host. Value -1 indicates tmnxLocUsrDbPppoeUnEncTgRgInnSta is
         not applicable."
    ::= { tmnxLocUsrDbPppoeUnmatchedEntry 16 }

tmnxLocUsrDbPppoeUnEncTgRgInnEnd OBJECT-TYPE
    SYNTAX      Integer32 (-1 | 0..4094)
    MAX-ACCESS  read-only
    STATUS      current
    DESCRIPTION
        "The value of the object tmnxLocUsrDbPppoeUnEncTgRgInnEnd indicates the
         right bound (i.e. maximum value) of a range of inner VLANs allowed on
         this PPP host. Value -1 indicates tmnxLocUsrDbPppoeUnEncTgRgInnEnd is
         not applicable."
    ::= { tmnxLocUsrDbPppoeUnmatchedEntry 17 }

tmnxLocUsrDbPppoeOptionTbleLstCh OBJECT-TYPE
    SYNTAX      TimeStamp
    MAX-ACCESS  read-only
    STATUS      current
    DESCRIPTION
        "The value of the object tmnxLocUsrDbPppoeOptionTbleLstCh indicates the
         value of sysUpTime at the time of the last modification of an entry in
         the tmnxLocUsrDbPppoeOptionTable."
    ::= { tmnxLocalUserDbObjs 6 }

tmnxLocUsrDbPppoeOptionTable     OBJECT-TYPE
    SYNTAX      SEQUENCE OF TmnxLocUsrDbPppoeOptionEntry
    MAX-ACCESS  not-accessible
    STATUS      current
    DESCRIPTION
        "The table tmnxLocUsrDbPppoeOptionTable contains objects to configure
         the DHCP options of each PPPoE host."
    ::= { tmnxLocalUserDbObjs 7 }

tmnxLocUsrDbPppoeOptionEntry     OBJECT-TYPE
    SYNTAX      TmnxLocUsrDbPppoeOptionEntry
    MAX-ACCESS  not-accessible
    STATUS      current
    DESCRIPTION
        "Each row represents a DHCP option that is encoded in the DHCP reply
         message of this PPPoE host.

         Entries in this table can be created or deleted via SNMP operations."
    INDEX       {
        tmnxLocUsrDbUserDatabaseName,
        tmnxLocUsrDbPppoeHostName,
        tmnxLocUsrDbPppoeOptionNumber
    }
    ::= { tmnxLocUsrDbPppoeOptionTable 1 }

TmnxLocUsrDbPppoeOptionEntry     ::= SEQUENCE
{
    tmnxLocUsrDbPppoeOptionNumber    Unsigned32,
    tmnxLocUsrDbPppoeOptionRowStatus RowStatus,
    tmnxLocUsrDbPppoeOptionLstChngTm TimeStamp,
    tmnxLocUsrDbPppoeOptionType      TmnxDhcpOptionType,
    tmnxLocUsrDbPppoeOptionValue     OCTET STRING,
    tmnxLocUsrDbPppoeOptionDisplay   TmnxDhcpOptionDisplay
}

tmnxLocUsrDbPppoeOptionNumber    OBJECT-TYPE
    SYNTAX      Unsigned32 (1..254)
    MAX-ACCESS  not-accessible
    STATUS      current
    DESCRIPTION
        "The value of the object tmnxLocUsrDbPppoeOptionNumber specifies the
         number of this DHCP option."
    REFERENCE
        "RFC 2132"
    ::= { tmnxLocUsrDbPppoeOptionEntry 1 }

tmnxLocUsrDbPppoeOptionRowStatus OBJECT-TYPE
    SYNTAX      RowStatus
    MAX-ACCESS  read-create
    STATUS      current
    DESCRIPTION
        "The value of the object tmnxLocUsrDbPppoeOptionRowStatus specifies the
         row status of this row.

         Objects tmnxLocUsrDbPppoeOptionType and tmnxLocUsrDbPppoeOptionValue
         must be set when creating a new row."
    ::= { tmnxLocUsrDbPppoeOptionEntry 2 }

tmnxLocUsrDbPppoeOptionLstChngTm OBJECT-TYPE
    SYNTAX      TimeStamp
    MAX-ACCESS  read-only
    STATUS      current
    DESCRIPTION
        "The value of the object tmnxLocUsrDbPppoeOptionLstChngTm indicates the
         sysUpTime at the time of the last modification of this entry."
    ::= { tmnxLocUsrDbPppoeOptionEntry 3 }

tmnxLocUsrDbPppoeOptionType      OBJECT-TYPE
    SYNTAX      TmnxDhcpOptionType
    MAX-ACCESS  read-create
    STATUS      current
    DESCRIPTION
        "The value of the object tmnxLocUsrDbPppoeOptionType specifies how the
         value of this option is stored in tmnxLocUsrDbPppoeOptionValue.

         This object is mandatory at creation time."
    ::= { tmnxLocUsrDbPppoeOptionEntry 4 }

tmnxLocUsrDbPppoeOptionValue     OBJECT-TYPE
    SYNTAX      OCTET STRING (SIZE (0..127))
    MAX-ACCESS  read-create
    STATUS      current
    DESCRIPTION
        "The value of the object tmnxLocUsrDbPppoeOptionValue specifies the
         value of this option.

         This object is mandatory at creation time. A zero length value is only
         allowed when the value of tmnxLocUsrDbPppoeOptionType is 'hex (3)'."
    ::= { tmnxLocUsrDbPppoeOptionEntry 5 }

tmnxLocUsrDbPppoeOptionDisplay   OBJECT-TYPE
    SYNTAX      TmnxDhcpOptionDisplay
    MAX-ACCESS  read-only
    STATUS      current
    DESCRIPTION
        "The value of the object tmnxLocUsrDbPppoeOptionDisplay indicates a
         hint of how the tmnxLocUsrDbPppoeOptionValue can be displayed."
    ::= { tmnxLocUsrDbPppoeOptionEntry 6 }

tmnxLocUsrDbDhcpTableLastChange  OBJECT-TYPE
    SYNTAX      TimeStamp
    MAX-ACCESS  read-only
    STATUS      current
    DESCRIPTION
        "The value of the object tmnxLocUsrDbDhcpTableLastChange indicates the
         value of sysUpTime at the time of the last modification of an entry in
         the tmnxLocUsrDbDhcpTable."
    ::= { tmnxLocalUserDbObjs 8 }

tmnxLocUsrDbDhcpTable            OBJECT-TYPE
    SYNTAX      SEQUENCE OF TmnxLocUsrDbDhcpEntry
    MAX-ACCESS  not-accessible
    STATUS      current
    DESCRIPTION
        "The table tmnxLocUsrDbDhcpTable contains objects to configure DHCP
         hosts."
    ::= { tmnxLocalUserDbObjs 9 }

tmnxLocUsrDbDhcpEntry            OBJECT-TYPE
    SYNTAX      TmnxLocUsrDbDhcpEntry
    MAX-ACCESS  not-accessible
    STATUS      current
    DESCRIPTION
        "Each row represents a (set of) host.

         Entries in this table can be created or deleted via SNMP operations."
    INDEX       {
        tmnxLocUsrDbUserDatabaseName,
        tmnxLocUsrDbDhcpHostName
    }
    ::= { tmnxLocUsrDbDhcpTable 1 }

TmnxLocUsrDbDhcpEntry            ::= SEQUENCE
{
    tmnxLocUsrDbDhcpHostName         DisplayString,
    tmnxLocUsrDbDhcpRowStatus        RowStatus,
    tmnxLocUsrDbDhcpLastChangeTime   TimeStamp,
    tmnxLocUsrDbDhcpAdminState       TmnxAdminState,
    tmnxLocUsrDbDhcpMacAddress       MacAddress,
    tmnxLocUsrDbDhcpCircuitIdFmt     TmnxLocUsrDbDataFormat,
    tmnxLocUsrDbDhcpCircuitId        OCTET STRING,
    tmnxLocUsrDbDhcpRemoteId         OCTET STRING,
    tmnxLocUsrDbDhcpSystemId         DisplayString,
    tmnxLocUsrDbDhcpServiceId        TmnxServId,
    tmnxLocUsrDbDhcpSapId            DisplayString,
    tmnxLocUsrDbDhcpString           DisplayString,
    tmnxLocUsrDbDhcpOption60         OCTET STRING,
    tmnxLocUsrDbDhcpAddrType         InetAddressType,
    tmnxLocUsrDbDhcpAddress          InetAddress,
    tmnxLocUsrDbDhcpPool             TNamedItemOrEmpty,
    tmnxLocUsrDbDhcpUseGiAddress     TruthValue,
    tmnxLocUsrDbDhcpIdStringOptNum   Unsigned32,
    tmnxLocUsrDbDhcpSubscriberId     TmnxSubIdentStringOrEmpty,
    tmnxLocUsrDbDhcpSlaProfString    TmnxSlaProfileStringOrEmpty,
    tmnxLocUsrDbDhcpSubProfString    TmnxSubProfileStringOrEmpty,
    tmnxLocUsrDbDhcpAppProfString    DisplayString,
    tmnxLocUsrDbDhcpAncpString       TmnxAncpStringOrZero,
    tmnxLocUsrDbDhcpInterDestId      TNamedItemOrEmpty,
    tmnxLocUsrDbDhcpAuthPolicy       TNamedItemOrEmpty,
    tmnxLocUsrDbDhcpServerAddrType   InetAddressType,
    tmnxLocUsrDbDhcpServerAddress    InetAddress,
    tmnxLocUsrDbDhcpAuthDomainName   DisplayString,
    tmnxLocUsrDbDhcpCategoryMapName  TNamedItemOrEmpty,
    tmnxLocUsrDbDhcpOption60Fmt      TmnxLocUsrDbDataFormat,
    tmnxLocUsrDbDhcpUseClientPool    TruthValue,
    tmnxLocUsrDbDhcpDefMsapPolicy    TPolicyStatementNameOrEmpty,
    tmnxLocUsrDbDhcpDefMsapService   TmnxServId,
    tmnxLocUsrDbDhcpDefMsapGroupIf   TNamedItemOrEmpty,
    tmnxLocUsrDbDhcpRetailerSvcId    TmnxServId,
    tmnxLocUsrDbDhcpRemoteIdFmt      TmnxLocUsrDbDataFormat,
    tmnxLocUsrDbDhcpIpv6Addr         InetAddress,
    tmnxLocUsrDbDhcpIpv6Pfx          InetAddress,
    tmnxLocUsrDbDhcpIpv6PfxLen       InetAddressPrefixLength,
    tmnxLocUsrDbDhcpIpv6WanAddrPool  TNamedItemOrEmpty,
    tmnxLocUsrDbDhcpIpv6DelPfxPool   TNamedItemOrEmpty,
    tmnxLocUsrDbDhcpFltrProfString   TmnxFilterProfileStringOrEmpty,
    tmnxLocUsrDbDhcpIngIpv4FltrId    TIPFilterIdOrEmpty,
    tmnxLocUsrDbDhcpEgrIpv4FltrId    TIPFilterIdOrEmpty,
    tmnxLocUsrDbDhcpIngIpv6FltrId    TIPFilterIdOrEmpty,
    tmnxLocUsrDbDhcpEgrIpv6FltrId    TIPFilterIdOrEmpty,
    tmnxLocUsrDbDhcpUseGiAddrScope   INTEGER,
    tmnxLocUsrDbDhcpSecPool          TNamedItemOrEmpty,
    tmnxLocUsrDbDhcpUseCPDelimiter   DisplayString,
    tmnxLocUsrDbDhcpEncTagRangeType  TmnxPortEncapType,
    tmnxLocUsrDbDhcpEncTagRangeStrt  TmnxEncapVal,
    tmnxLocUsrDbDhcpEncTagRangeEnd   TmnxEncapVal,
    tmnxLocUsrDbDhcpMsapGroupIfPfx   TmnxLudbMsapGrpIfPfxSfxType,
    tmnxLocUsrDbDhcpMsapGroupIfSfx   TmnxLudbMsapGrpIfPfxSfxType,
    tmnxLocUsrDbDhcpIpv6ReqDelPfxLn  Unsigned32,
    tmnxLocUsrDbDhcpAcctPolicy       TNamedItemOrEmpty,
    tmnxLocUsrDbDhcpDuplAcctPolicy   TNamedItemOrEmpty,
    tmnxLocUsrDbDhcpIpv6SlaacPfx     InetAddress,
    tmnxLocUsrDbDhcpIpv6SlaacPfxLen  InetAddressPrefixLength,
    tmnxLocUsrDbDhcpDerivedId        DisplayString,
    tmnxLocUsrDbDhcpIpv6SlaacPfxPl   TNamedItemOrEmpty,
    tmnxLocUsrDbDhcpIpPrefixAddrType InetAddressType,
    tmnxLocUsrDbDhcpIpPrefixAddr     InetAddress,
    tmnxLocUsrDbDhcpIpPrefixLength   InetAddressPrefixLength,
    tmnxLocUsrDbDhcpSpiGroupId       TmnxSubSpiGroupId
}

tmnxLocUsrDbDhcpHostName         OBJECT-TYPE
    SYNTAX      DisplayString (SIZE (1..32))
    MAX-ACCESS  not-accessible
    STATUS      current
    DESCRIPTION
        "The value of the object tmnxLocUsrDbDhcpHostName specifies the name of
         this host or set of hosts.

         To identify the hosts, the DHCP parameters are matched against the
         values of these objects: tmnxLocUsrDbDhcpMacAddress,
         tmnxLocUsrDbDhcpCircuitId, tmnxLocUsrDbDhcpRemoteId,
         tmnxLocUsrDbDhcpSystemId, tmnxLocUsrDbDhcpServiceId,
         tmnxLocUsrDbDhcpSapId, tmnxLocUsrDbDhcpString and
         tmnxLocUsrDbDhcpOption60."
    ::= { tmnxLocUsrDbDhcpEntry 1 }

tmnxLocUsrDbDhcpRowStatus        OBJECT-TYPE
    SYNTAX      RowStatus
    MAX-ACCESS  read-create
    STATUS      current
    DESCRIPTION
        "The value of the object tmnxLocUsrDbDhcpRowStatus specifies the row
         status of this entry."
    ::= { tmnxLocUsrDbDhcpEntry 2 }

tmnxLocUsrDbDhcpLastChangeTime   OBJECT-TYPE
    SYNTAX      TimeStamp
    MAX-ACCESS  read-only
    STATUS      current
    DESCRIPTION
        "The value of the object tmnxLocUsrDbDhcpLastChangeTime indicates the
         sysUpTime at the time of the last modification of this entry."
    ::= { tmnxLocUsrDbDhcpEntry 3 }

tmnxLocUsrDbDhcpAdminState       OBJECT-TYPE
    SYNTAX      TmnxAdminState
    MAX-ACCESS  read-create
    STATUS      current
    DESCRIPTION
        "The value of the object tmnxLocUsrDbDhcpAdminState specifies the
         administrative state of the tmnxLocUsrDbDhcpEntry."
    DEFVAL      { outOfService }
    ::= { tmnxLocUsrDbDhcpEntry 4 }

tmnxLocUsrDbDhcpMacAddress       OBJECT-TYPE
    SYNTAX      MacAddress
    MAX-ACCESS  read-create
    STATUS      current
    DESCRIPTION
        "The value of the object tmnxLocUsrDbDhcpMacAddress specifies the MAC
         address to match against.

         If the value of this object is set to all zeros, then it is not used."
    DEFVAL      { '000000000000'H }
    ::= { tmnxLocUsrDbDhcpEntry 5 }

tmnxLocUsrDbDhcpCircuitIdFmt     OBJECT-TYPE
    SYNTAX      TmnxLocUsrDbDataFormat
    MAX-ACCESS  read-create
    STATUS      current
    DESCRIPTION
        "The value of the object tmnxLocUsrDbDhcpCircuitIdFmt specifies how the
         value of the value of tmnxLocUsrDbDhcpCircuitId must be formatted."
    DEFVAL      { ascii }
    ::= { tmnxLocUsrDbDhcpEntry 6 }

tmnxLocUsrDbDhcpCircuitId        OBJECT-TYPE
    SYNTAX      OCTET STRING (SIZE (0..127))
    MAX-ACCESS  read-create
    STATUS      current
    DESCRIPTION
        "The value of the object tmnxLocUsrDbDhcpCircuitId specifies the
         circuit Id from option 82 to match against.

         If the value of this object is the empty string, then it is not used."
    DEFVAL      { ''H }
    ::= { tmnxLocUsrDbDhcpEntry 7 }

tmnxLocUsrDbDhcpRemoteId         OBJECT-TYPE
    SYNTAX      OCTET STRING (SIZE (0..255))
    MAX-ACCESS  read-create
    STATUS      current
    DESCRIPTION
        "The value of the object tmnxLocUsrDbDhcpRemoteId specifies the remote
         Id from option 82 to match against.

         If the value of this object is the empty string, then it is not used."
    DEFVAL      { "" }
    ::= { tmnxLocUsrDbDhcpEntry 8 }

tmnxLocUsrDbDhcpSystemId         OBJECT-TYPE
    SYNTAX      DisplayString (SIZE (0..255))
    MAX-ACCESS  read-create
    STATUS      current
    DESCRIPTION
        "The value of the object tmnxLocUsrDbDhcpSystemId specifies the system
         Id from the Nokia vendor specific sub-option in option 82 to match
         against.

         If the value of this object is the empty string, then it is not used."
    DEFVAL      { "" }
    ::= { tmnxLocUsrDbDhcpEntry 9 }

tmnxLocUsrDbDhcpServiceId        OBJECT-TYPE
    SYNTAX      TmnxServId
    MAX-ACCESS  read-create
    STATUS      current
    DESCRIPTION
        "The value of the object tmnxLocUsrDbDhcpServiceId specifies
         the service ID to match during host identification with
         - the Nokia vendor specific sub-option in option 82, or
         - the service where the IPoE session is established.

         If the value of this object is 0, then it is not used.

         The service where the IPoE session is established can be specified by
         name using the object tmnxLudbDhcp2IdentServiceName."
    DEFVAL      { 0 }
    ::= { tmnxLocUsrDbDhcpEntry 10 }

tmnxLocUsrDbDhcpSapId            OBJECT-TYPE
    SYNTAX      DisplayString (SIZE (0..255))
    MAX-ACCESS  read-create
    STATUS      current
    DESCRIPTION
        "The value of the object tmnxLocUsrDbDhcpSapId specifies the sapId from
         the Nokia vendor specific sub-option in option 82 to match against.

         If the value of this object is the empty string, then it is not used."
    DEFVAL      { "" }
    ::= { tmnxLocUsrDbDhcpEntry 11 }

tmnxLocUsrDbDhcpString           OBJECT-TYPE
    SYNTAX      DisplayString (SIZE (0..255))
    MAX-ACCESS  read-create
    STATUS      current
    DESCRIPTION
        "The value of the object tmnxLocUsrDbDhcpString specifies the string
         from the Nokia vendor specific sub-option in option 82 to match
         against.

         If the value of this object is the empty string, then it is not used."
    DEFVAL      { "" }
    ::= { tmnxLocUsrDbDhcpEntry 12 }

tmnxLocUsrDbDhcpOption60         OBJECT-TYPE
    SYNTAX      OCTET STRING (SIZE (0..32))
    MAX-ACCESS  read-create
    STATUS      current
    DESCRIPTION
        "The value of the object tmnxLocUsrDbDhcpOption60 specifies the
         Vendor-Identifying Vendor Option to match against. Option 60 is
         encoded as Type - Length - Value. The Value portion of Option 60 in
         the received DHCP request is used to match against
         tmnxLocUsrDbDhcpOption60.

         If the value of this object is the empty string, then it is not used."
    REFERENCE
        "RFC 3925"
    DEFVAL      { "" }
    ::= { tmnxLocUsrDbDhcpEntry 13 }

tmnxLocUsrDbDhcpAddrType         OBJECT-TYPE
    SYNTAX      InetAddressType
    MAX-ACCESS  read-create
    STATUS      current
    DESCRIPTION
        "The value of the object tmnxLocUsrDbDhcpAddrType specifies the type of
         tmnxLocUsrDbDhcpAddress."
    DEFVAL      { unknown }
    ::= { tmnxLocUsrDbDhcpEntry 14 }

tmnxLocUsrDbDhcpAddress          OBJECT-TYPE
    SYNTAX      InetAddress (SIZE (0|4|16))
    MAX-ACCESS  read-create
    STATUS      current
    DESCRIPTION
        "The value of the object tmnxLocUsrDbDhcpAddress specifies the IP
         address of this host.

         This object can only be configured if object tmnxLocUsrDbDhcpPool
         contains the empty string and object tmnxLocUsrDbDhcpUseGiAddress is
         'false(2)'."
    DEFVAL      { ''H }
    ::= { tmnxLocUsrDbDhcpEntry 15 }

tmnxLocUsrDbDhcpPool             OBJECT-TYPE
    SYNTAX      TNamedItemOrEmpty
    MAX-ACCESS  read-create
    STATUS      current
    DESCRIPTION
        "The value of the object tmnxLocUsrDbDhcpPool specifies the IP address
         pool which is used to search for an IP address for this host.

         This object can only be configured if the value of
         tmnxLocUsrDbDhcpAddrType is 'unknown(0)' and the values of
         tmnxLocUsrDbDhcpUseGiAddress and tmnxLocUsrDbDhcpUseClientPool are
         'false(2)'."
    DEFVAL      { "" }
    ::= { tmnxLocUsrDbDhcpEntry 16 }

tmnxLocUsrDbDhcpUseGiAddress     OBJECT-TYPE
    SYNTAX      TruthValue
    MAX-ACCESS  read-create
    STATUS      current
    DESCRIPTION
        "The value of the object tmnxLocUsrDbDhcpUseGiAddress specifies whether
         the GI address is used to search for an IP address for this host.

         If the value of this object is set to 'true(1)', then the Gateway IP
         address is used.

         This object can only be set to 'true(1)' when the value of
         tmnxLocUsrDbDhcpAddrType is 'unknown(0)' and tmnxLocUsrDbDhcpPool
         contains the empty string."
    DEFVAL      { false }
    ::= { tmnxLocUsrDbDhcpEntry 17 }

tmnxLocUsrDbDhcpIdStringOptNum   OBJECT-TYPE
    SYNTAX      Unsigned32 (0..254)
    MAX-ACCESS  read-create
    STATUS      current
    DESCRIPTION
        "The value of the object tmnxLocUsrDbDhcpIdStringOptNum specifies the
         option number that the DHCP server uses to send the identification
         strings to the DHCP client.

         If the value of this object is 0, then no identification strings will
         be sent."
    DEFVAL      { 0 }
    ::= { tmnxLocUsrDbDhcpEntry 18 }

tmnxLocUsrDbDhcpSubscriberId     OBJECT-TYPE
    SYNTAX      TmnxSubIdentStringOrEmpty
    MAX-ACCESS  read-create
    STATUS      current
    DESCRIPTION
        "The value of the object tmnxLocUsrDbDhcpSubscriberId specifies the
         subscriber Id which is encoded in the identification strings."
    DEFVAL      { "" }
    ::= { tmnxLocUsrDbDhcpEntry 19 }

tmnxLocUsrDbDhcpSlaProfString    OBJECT-TYPE
    SYNTAX      TmnxSlaProfileStringOrEmpty
    MAX-ACCESS  read-create
    STATUS      current
    DESCRIPTION
        "The value of the object tmnxLocUsrDbDhcpSlaProfString specifies the
         SLA profile string which is encoded in the identification strings."
    DEFVAL      { "" }
    ::= { tmnxLocUsrDbDhcpEntry 20 }

tmnxLocUsrDbDhcpSubProfString    OBJECT-TYPE
    SYNTAX      TmnxSubProfileStringOrEmpty
    MAX-ACCESS  read-create
    STATUS      current
    DESCRIPTION
        "The value of the object tmnxLocUsrDbDhcpSubProfString specifies the
         subscriber profile string which is encoded in the identification
         strings."
    DEFVAL      { "" }
    ::= { tmnxLocUsrDbDhcpEntry 21 }

tmnxLocUsrDbDhcpAppProfString    OBJECT-TYPE
    SYNTAX      DisplayString (SIZE (0..16))
    MAX-ACCESS  read-create
    STATUS      current
    DESCRIPTION
        "The value of the object tmnxLocUsrDbDhcpAppProfString specifies the
         application profile string which is encoded in the identification
         strings."
    DEFVAL      { "" }
    ::= { tmnxLocUsrDbDhcpEntry 22 }

tmnxLocUsrDbDhcpAncpString       OBJECT-TYPE
    SYNTAX      TmnxAncpStringOrZero
    MAX-ACCESS  read-create
    STATUS      current
    DESCRIPTION
        "The value of the object tmnxLocUsrDbDhcpAncpString specifies the ANCP
         string which is encoded in the identification strings."
    DEFVAL      { "" }
    ::= { tmnxLocUsrDbDhcpEntry 23 }

tmnxLocUsrDbDhcpInterDestId      OBJECT-TYPE
    SYNTAX      TNamedItemOrEmpty
    MAX-ACCESS  read-create
    STATUS      current
    DESCRIPTION
        "The value of the object tmnxLocUsrDbDhcpInterDestId specifies the
         intermediate destination identifier which is encoded in the
         identification strings."
    DEFVAL      { "" }
    ::= { tmnxLocUsrDbDhcpEntry 24 }

tmnxLocUsrDbDhcpAuthPolicy       OBJECT-TYPE
    SYNTAX      TNamedItemOrEmpty
    MAX-ACCESS  read-create
    STATUS      current
    DESCRIPTION
        "The value of the object tmnxLocUsrDbDhcpAuthPolicy specifies the
         RADIUS authentication policy to use to authenticate the DHCP host."
    DEFVAL      { "" }
    ::= { tmnxLocUsrDbDhcpEntry 25 }

tmnxLocUsrDbDhcpServerAddrType   OBJECT-TYPE
    SYNTAX      InetAddressType
    MAX-ACCESS  read-create
    STATUS      current
    DESCRIPTION
        "The value of the object tmnxLocUsrDbDhcpServerAddrType specifies the
         type of tmnxLocUsrDbDhcpServerAddress."
    DEFVAL      { unknown }
    ::= { tmnxLocUsrDbDhcpEntry 26 }

tmnxLocUsrDbDhcpServerAddress    OBJECT-TYPE
    SYNTAX      InetAddress (SIZE (0|4|16))
    MAX-ACCESS  read-create
    STATUS      current
    DESCRIPTION
        "The value of the object tmnxLocUsrDbDhcpServerAddress specifies the
         address of the DHCP server to relay to."
    DEFVAL      { ''H }
    ::= { tmnxLocUsrDbDhcpEntry 27 }

tmnxLocUsrDbDhcpAuthDomainName   OBJECT-TYPE
    SYNTAX      DisplayString (SIZE (0..32))
    MAX-ACCESS  read-create
    STATUS      current
    DESCRIPTION
        "The value of the object tmnxLocUsrDbDhcpAuthDomainName specifies the
         domain name to use when RADIUS authentication is applicable."
    DEFVAL      { "" }
    ::= { tmnxLocUsrDbDhcpEntry 28 }

tmnxLocUsrDbDhcpCategoryMapName  OBJECT-TYPE
    SYNTAX      TNamedItemOrEmpty
    MAX-ACCESS  read-create
    STATUS      current
    DESCRIPTION
        "The value of the object tmnxLocUsrDbDhcpCategoryMapName specifies the
         name of the category map used when credit control is active for this
         host."
    DEFVAL      { "" }
    ::= { tmnxLocUsrDbDhcpEntry 29 }

tmnxLocUsrDbDhcpOption60Fmt      OBJECT-TYPE
    SYNTAX      TmnxLocUsrDbDataFormat
    MAX-ACCESS  read-create
    STATUS      current
    DESCRIPTION
        "The value of the object tmnxLocUsrDbDhcpOption60Fmt specifies how the
         value of the value of tmnxLocUsrDbDhcpOption60 must be formatted."
    DEFVAL      { hex }
    ::= { tmnxLocUsrDbDhcpEntry 30 }

tmnxLocUsrDbDhcpUseClientPool    OBJECT-TYPE
    SYNTAX      TruthValue
    MAX-ACCESS  read-create
    STATUS      current
    DESCRIPTION
        "The value of the object tmnxLocUsrDbDhcpUseClientPool specifies if the
         IP address pool used to search for an IP address for this host is to
         be indicated by the vendor-specific sub-option 13 of the DHCP option
         82.

         If the value of this object is set to 'true (1)', the IP address pool
         indicated by the sub-option 13 is used.

         This object can only be set to 'true (1)' when the value of
         tmnxLocUsrDbDhcpAddrType is 'unknown (0)' and tmnxLocUsrDbDhcpPool
         contains the empty string."
    DEFVAL      { false }
    ::= { tmnxLocUsrDbDhcpEntry 31 }

tmnxLocUsrDbDhcpDefMsapPolicy    OBJECT-TYPE
    SYNTAX      TPolicyStatementNameOrEmpty
    MAX-ACCESS  read-create
    STATUS      current
    DESCRIPTION
        "The value of the object tmnxLocUsrDbDhcpDefMsapPolicy specifies the
         default Managed SAP policy to use to create Managed SAPs when the
         response from the Radius server does not specify a Managed SAP policy."
    DEFVAL      { "" }
    ::= { tmnxLocUsrDbDhcpEntry 32 }

tmnxLocUsrDbDhcpDefMsapService   OBJECT-TYPE
    SYNTAX      TmnxServId
    MAX-ACCESS  read-create
    STATUS      current
    DESCRIPTION
        "The value of the object tmnxLocUsrDbDhcpDefMsapService specifies
         specifies the service ID of the service where Managed SAPs are created
         when there is no Radius server available, or the Radius server does
         not specify the service ID.

         While the value of sapTlsDefMsapService is equal to zero, no Managed
         SAPs are created when there is no Radius server-specified service ID
         available."
    DEFVAL      { 0 }
    ::= { tmnxLocUsrDbDhcpEntry 33 }

tmnxLocUsrDbDhcpDefMsapGroupIf   OBJECT-TYPE
    SYNTAX      TNamedItemOrEmpty
    MAX-ACCESS  read-create
    STATUS      current
    DESCRIPTION
        "The value of the object tmnxLocUsrDbDhcpDefMsapGroupIf specifies the
         name of the group interface where Managed SAPs are created when there
         is no Radius server available, or the Radius server does not specify
         the group interface.

         While the value of sapTlsDefMsapGroupIf is the empty string, no
         Managed SAPs are created when there is no Radius server-specified
         group interface available."
    DEFVAL      { "" }
    ::= { tmnxLocUsrDbDhcpEntry 34 }

tmnxLocUsrDbDhcpRetailerSvcId    OBJECT-TYPE
    SYNTAX      TmnxServId
    MAX-ACCESS  read-create
    STATUS      current
    DESCRIPTION
        "The value of the object tmnxLocUsrDbDhcpRetailerSvcId specifies the
         retailer service Id for this host."
    DEFVAL      { 0 }
    ::= { tmnxLocUsrDbDhcpEntry 35 }

tmnxLocUsrDbDhcpRemoteIdFmt      OBJECT-TYPE
    SYNTAX      TmnxLocUsrDbDataFormat
    MAX-ACCESS  read-create
    STATUS      current
    DESCRIPTION
        "The value of the object tmnxLocUsrDbDhcpRemoteIdFmt specifies how the
         value of the value of tmnxLocUsrDbDhcpRemoteId must be formatted."
    DEFVAL      { ascii }
    ::= { tmnxLocUsrDbDhcpEntry 36 }

tmnxLocUsrDbDhcpIpv6Addr         OBJECT-TYPE
    SYNTAX      InetAddress (SIZE (16))
    MAX-ACCESS  read-create
    STATUS      current
    DESCRIPTION
        "The value of the object tmnxLocUsrDbDhcpIpv6Addr specifies the IPv6
         non temporary address of this host.

         A value of 0::0 means that the address is not configured."
    DEFVAL      { '00000000000000000000000000000000'H }
    ::= { tmnxLocUsrDbDhcpEntry 37 }

tmnxLocUsrDbDhcpIpv6Pfx          OBJECT-TYPE
    SYNTAX      InetAddress (SIZE (16))
    MAX-ACCESS  read-create
    STATUS      current
    DESCRIPTION
        "The value of the object tmnxLocUsrDbDhcpIpv6Pfx specifies the IPv6
         prefix of this host.

         A value of 0::0 means that the prefix-address is not configured.

         The value of tmnxLocUsrDbDhcpIpv6Pfx must be set together with the
         value of tmnxLocUsrDbDhcpIpv6PfxLen."
    DEFVAL      { '00000000000000000000000000000000'H }
    ::= { tmnxLocUsrDbDhcpEntry 38 }

tmnxLocUsrDbDhcpIpv6PfxLen       OBJECT-TYPE
    SYNTAX      InetAddressPrefixLength (0 | 48..64)
    MAX-ACCESS  read-create
    STATUS      current
    DESCRIPTION
        "The value of tmnxLocUsrDbDhcpIpv6PfxLen indicates the length of the
         prefix-address stored in tmnxLocUsrDbDhcpIpv6Pfx.

         A value of 0 means that tmnxLocUsrDbDhcpIpv6Pfx is not configured.

         The value of tmnxLocUsrDbDhcpIpv6PfxLen must be set together with the
         value of tmnxLocUsrDbDhcpIpv6Pfx."
    ::= { tmnxLocUsrDbDhcpEntry 39 }

tmnxLocUsrDbDhcpIpv6WanAddrPool  OBJECT-TYPE
    SYNTAX      TNamedItemOrEmpty
    MAX-ACCESS  read-create
    STATUS      current
    DESCRIPTION
        "The value of tmnxLocUsrDbDhcpIpv6WanAddrPool specifies the IPv6
         address pool which is used to search for an IPv6 address for this
         host."
    DEFVAL      { "" }
    ::= { tmnxLocUsrDbDhcpEntry 40 }

tmnxLocUsrDbDhcpIpv6DelPfxPool   OBJECT-TYPE
    SYNTAX      TNamedItemOrEmpty
    MAX-ACCESS  read-create
    STATUS      current
    DESCRIPTION
        "The value of tmnxLocUsrDbDhcpIpv6DelPfxPool specifies the IPv6 address
         pool which is used to search for an IPv6 prefix for this host."
    DEFVAL      { "" }
    ::= { tmnxLocUsrDbDhcpEntry 41 }

tmnxLocUsrDbDhcpFltrProfString   OBJECT-TYPE
    SYNTAX      TmnxFilterProfileStringOrEmpty
    MAX-ACCESS  read-create
    STATUS      current
    DESCRIPTION
        "The value of the object tmnxLocUsrDbDhcpFltrProfString specifies the
         filter profile string which is encoded in the identification strings."
    DEFVAL      { "" }
    ::= { tmnxLocUsrDbDhcpEntry 42 }

tmnxLocUsrDbDhcpIngIpv4FltrId    OBJECT-TYPE
    SYNTAX      TIPFilterIdOrEmpty
    MAX-ACCESS  read-create
    STATUS      current
    DESCRIPTION
        "The value of the object tmnxLocUsrDbDhcpIngIpv4FltrId specifies the
         ingress ipv4 filter-id to be applied to this host.

         If the value of this object is '0', then the filter as specified in
         the applicable SLA-profile will be applied.

         If the value of this object is '-1', then no filter will be applied to
         this host, irrespective of the value specified in the applicable
         SLA-profile.

         If any value between 1 and 65535 is specified this value will be used
         as filter-id for this host irrespective of the value specified in the
         applicable SLA-profile"
    DEFVAL      { 0 }
    ::= { tmnxLocUsrDbDhcpEntry 43 }

tmnxLocUsrDbDhcpEgrIpv4FltrId    OBJECT-TYPE
    SYNTAX      TIPFilterIdOrEmpty
    MAX-ACCESS  read-create
    STATUS      current
    DESCRIPTION
        "The value of the object tmnxLocUsrDbDhcpEgrIpv4FltrId specifies the
         egress ipv4 filter-id to be applied to this host.

         If the value of this object is '0', then the filter as specified in
         the applicable SLA-profile will be applied.

         If the value of this object is '-1', then no filter will be applied to
         this host, irrespective of the value specified in the applicable
         SLA-profile.

         If any value between 1 and 65535 is specified this value will be used
         as filter-id for this host irrespective of the value specified in the
         applicable SLA-profile"
    DEFVAL      { 0 }
    ::= { tmnxLocUsrDbDhcpEntry 44 }

tmnxLocUsrDbDhcpIngIpv6FltrId    OBJECT-TYPE
    SYNTAX      TIPFilterIdOrEmpty
    MAX-ACCESS  read-create
    STATUS      current
    DESCRIPTION
        "The value of the object tmnxLocUsrDbDhcpIngIpv6FltrId specifies the
         ingress ipv6 filter-id to be applied to this host.

         If the value of this object is '0', then the filter as specified in
         the applicable SLA-profile will be applied.

         If the value of this object is '-1', then no filter will be applied to
         this host, irrespective of the value specified in the applicable
         SLA-profile.

         If any value between 1 and 65535 is specified this value will be used
         as filter-id for this host irrespective of the value specified in the
         applicable SLA-profile"
    DEFVAL      { 0 }
    ::= { tmnxLocUsrDbDhcpEntry 45 }

tmnxLocUsrDbDhcpEgrIpv6FltrId    OBJECT-TYPE
    SYNTAX      TIPFilterIdOrEmpty
    MAX-ACCESS  read-create
    STATUS      current
    DESCRIPTION
        "The value of the object tmnxLocUsrDbDhcpEgrIpv6FltrId specifies the
         egress ipv6 filter-id to be applied to this host.

         If the value of this object is '0', then the filter as specified in
         the applicable SLA-profile will be applied.

         If the value of this object is '-1', then no filter will be applied to
         this host, irrespective of the value specified in the applicable
         SLA-profile.

         If any value between 1 and 65535 is specified this value will be used
         as filter-id for this host irrespective of the value specified in the
         applicable SLA-profile"
    DEFVAL      { 0 }
    ::= { tmnxLocUsrDbDhcpEntry 46 }

tmnxLocUsrDbDhcpUseGiAddrScope   OBJECT-TYPE
    SYNTAX      INTEGER {
        subnet (0),
        pool   (1)
    }
    MAX-ACCESS  read-create
    STATUS      current
    DESCRIPTION
        "The value of tmnxLocUsrDbDhcpUseGiAddrScope specifies whether the GI
         address selects a single subnet or a pool.

         The value of this object is only meaningful when the value of
         tmnxLocUsrDbDhcpUseGiAddress is set to 'true(1)'."
    DEFVAL      { subnet }
    ::= { tmnxLocUsrDbDhcpEntry 47 }

tmnxLocUsrDbDhcpSecPool          OBJECT-TYPE
    SYNTAX      TNamedItemOrEmpty
    MAX-ACCESS  read-create
    STATUS      current
    DESCRIPTION
        "The value of the object tmnxLocUsrDbDhcpSecPool specifies the
         secondary IP address pool which is used to search for an IP address
         for this host.

         This object can only be configured if the value of
         tmnxLocUsrDbDhcpAddrType is 'unknown(0)' and the values of
         tmnxLocUsrDbDhcpUseGiAddress and tmnxLocUsrDbDhcpUseClientPool are
         'false(2)'."
    DEFVAL      { "" }
    ::= { tmnxLocUsrDbDhcpEntry 48 }

tmnxLocUsrDbDhcpUseCPDelimiter   OBJECT-TYPE
    SYNTAX      DisplayString (SIZE (0..1))
    MAX-ACCESS  read-create
    STATUS      current
    DESCRIPTION
        "A delimiter character to combine primary and secondary pool names."
    DEFVAL      { "" }
    ::= { tmnxLocUsrDbDhcpEntry 49 }

tmnxLocUsrDbDhcpEncTagRangeType  OBJECT-TYPE
    SYNTAX      TmnxPortEncapType
    MAX-ACCESS  read-create
    STATUS      current
    DESCRIPTION
        "The value of tmnxLocUsrDbDhcpEncTagRangeType specifies the type of
         encapsulation protocol configured for the SAP encap tag range start
         and end values.

         Can either unknown, qEncap or qinqEncap."
    ::= { tmnxLocUsrDbDhcpEntry 50 }

tmnxLocUsrDbDhcpEncTagRangeStrt  OBJECT-TYPE
    SYNTAX      TmnxEncapVal
    MAX-ACCESS  read-create
    STATUS      current
    DESCRIPTION
        "The value of the start label in the range of SAPs allowed on this
         host.

         A value of 0 iso 1 will be used when vci=*."
    ::= { tmnxLocUsrDbDhcpEntry 51 }

tmnxLocUsrDbDhcpEncTagRangeEnd   OBJECT-TYPE
    SYNTAX      TmnxEncapVal
    MAX-ACCESS  read-create
    STATUS      current
    DESCRIPTION
        "The value of the end label in the range of SAPs allowed on this host.

         A value of 0 iso 1 will be used when vci=*."
    ::= { tmnxLocUsrDbDhcpEntry 52 }

tmnxLocUsrDbDhcpMsapGroupIfPfx   OBJECT-TYPE
    SYNTAX      TmnxLudbMsapGrpIfPfxSfxType
    MAX-ACCESS  read-create
    STATUS      current
    DESCRIPTION
        "The value of tmnxLocUsrDbDhcpMsapGroupIfPfx specifies the type of
         prefix to be applied to the value of tmnxLocUsrDbDhcpDefMsapGroupIf
         when a local user database lookup is being performed."
    DEFVAL      { none }
    ::= { tmnxLocUsrDbDhcpEntry 53 }

tmnxLocUsrDbDhcpMsapGroupIfSfx   OBJECT-TYPE
    SYNTAX      TmnxLudbMsapGrpIfPfxSfxType
    MAX-ACCESS  read-create
    STATUS      current
    DESCRIPTION
        "The value of tmnxLocUsrDbDhcpMsapGroupIfSfx specifies the type of
         suffix to be applied to the value of tmnxLocUsrDbDhcpDefMsapGroupIf
         when a local user database lookup is being performed."
    DEFVAL      { none }
    ::= { tmnxLocUsrDbDhcpEntry 54 }

tmnxLocUsrDbDhcpIpv6ReqDelPfxLn  OBJECT-TYPE
    SYNTAX      Unsigned32 (0 | 48..64)
    MAX-ACCESS  read-create
    STATUS      current
    DESCRIPTION
        "The value of tmnxLocUsrDbDhcpIpv6ReqDelPfxLn specifies the number of
         bits that can be allocated to a Delegated Prefix for IPv6."
    DEFVAL      { 0 }
    ::= { tmnxLocUsrDbDhcpEntry 55 }

tmnxLocUsrDbDhcpAcctPolicy       OBJECT-TYPE
    SYNTAX      TNamedItemOrEmpty
    MAX-ACCESS  read-create
    STATUS      current
    DESCRIPTION
        "The value of the object tmnxLocUsrDbDhcpAcctPolicy specifies the
         RADIUS accounting policy to be used for generating accounting
         information."
    DEFVAL      { "" }
    ::= { tmnxLocUsrDbDhcpEntry 56 }

tmnxLocUsrDbDhcpDuplAcctPolicy   OBJECT-TYPE
    SYNTAX      TNamedItemOrEmpty
    MAX-ACCESS  read-create
    STATUS      current
    DESCRIPTION
        "The value of the object tmnxLocUsrDbDhcpDuplAcctPolicy specifies the
         RADIUS accounting policy to be used for generating duplicate
         accounting information."
    DEFVAL      { "" }
    ::= { tmnxLocUsrDbDhcpEntry 57 }

tmnxLocUsrDbDhcpIpv6SlaacPfx     OBJECT-TYPE
    SYNTAX      InetAddress (SIZE (16))
    MAX-ACCESS  read-create
    STATUS      current
    DESCRIPTION
        "The value of the object tmnxLocUsrDbDhcpIpv6SlaacPfx specifies the
         IPv6 prefix used for stateless address autoconfiguration.

         A value of 0::0 means that the prefix-address is not configured.

         The value of tmnxLocUsrDbDhcpIpv6SlaacPfx must be set together with
         the value of tmnxLocUsrDbDhcpIpv6SlaacPfxLen."
    DEFVAL      { '00000000000000000000000000000000'H }
    ::= { tmnxLocUsrDbDhcpEntry 58 }

tmnxLocUsrDbDhcpIpv6SlaacPfxLen  OBJECT-TYPE
    SYNTAX      InetAddressPrefixLength (0 | 64)
    MAX-ACCESS  read-create
    STATUS      current
    DESCRIPTION
        "The value of tmnxLocUsrDbDhcpIpv6SlaacPfxLen indicates the length of
         the prefix-address stored in tmnxLocUsrDbDhcpIpv6SlaacPfx.

         A value of 0 means that tmnxLocUsrDbDhcpIpv6SlaacPfx is not
         configured.

         The value of tmnxLocUsrDbDhcpIpv6SlaacPfxLen must be set together with
         the value of tmnxLocUsrDbDhcpIpv6SlaacPfx."
    ::= { tmnxLocUsrDbDhcpEntry 59 }

tmnxLocUsrDbDhcpDerivedId        OBJECT-TYPE
    SYNTAX      DisplayString (SIZE (0..255))
    MAX-ACCESS  read-create
    STATUS      current
    DESCRIPTION
        "The value of the object tmnxLocUsrDbDhcpDerivedId specifies a string
         to be matched with a string that uniquely identifies a host and is
         derived by a Python script from packet content available during a DHCP
         transaction.

         If the value of this object is the empty string, it is not used."
    DEFVAL      { "" }
    ::= { tmnxLocUsrDbDhcpEntry 60 }

tmnxLocUsrDbDhcpIpv6SlaacPfxPl   OBJECT-TYPE
    SYNTAX      TNamedItemOrEmpty
    MAX-ACCESS  read-create
    STATUS      current
    DESCRIPTION
        "The value of tmnxLocUsrDbDhcpIpv6SlaacPfxPl specifies the IPv6 address
         pool which is used to search for an IPv6 address for this host."
    DEFVAL      { "" }
    ::= { tmnxLocUsrDbDhcpEntry 61 }

tmnxLocUsrDbDhcpIpPrefixAddrType OBJECT-TYPE
    SYNTAX      InetAddressType
    MAX-ACCESS  read-create
    STATUS      current
    DESCRIPTION
        "The value of tmnxLocUsrDbDhcpIpPrefixAddrType specifies the type of
         address stored in tmnxLocUsrDbDhcpIpPrefixAddr."
    DEFVAL      { unknown }
    ::= { tmnxLocUsrDbDhcpEntry 62 }

tmnxLocUsrDbDhcpIpPrefixAddr     OBJECT-TYPE
    SYNTAX      InetAddress (SIZE (0|4|16))
    MAX-ACCESS  read-create
    STATUS      current
    DESCRIPTION
        "The value of tmnxLocUsrDbDhcpIpPrefixAddr specifies the IP prefix
         address used as match in host identification."
    DEFVAL      { ''H }
    ::= { tmnxLocUsrDbDhcpEntry 63 }

tmnxLocUsrDbDhcpIpPrefixLength   OBJECT-TYPE
    SYNTAX      InetAddressPrefixLength (0..128)
    MAX-ACCESS  read-create
    STATUS      current
    DESCRIPTION
        "The value of tmnxLocUsrDbDhcpIpPrefixLength specifies the prefix
         length of the IP prefix."
    DEFVAL      { 0 }
    ::= { tmnxLocUsrDbDhcpEntry 64 }

tmnxLocUsrDbDhcpSpiGroupId       OBJECT-TYPE
    SYNTAX      TmnxSubSpiGroupId
    MAX-ACCESS  read-create
    STATUS      current
    DESCRIPTION
        "The value of the object tmnxLocUsrDbDhcpSpiGroupId specifies the SLA
         profile instance group identifier in the identification strings.

         A value of minus one means that there is no group identifier
         configured."
    DEFVAL      { -1 }
    ::= { tmnxLocUsrDbDhcpEntry 65 }

tmnxLocUsrDbDhcpUnmatchedTable   OBJECT-TYPE
    SYNTAX      SEQUENCE OF TmnxLocUsrDbDhcpUnmatchedEntry
    MAX-ACCESS  not-accessible
    STATUS      current
    DESCRIPTION
        "The table tmnxLocUsrDbDhcpUnmatchedTable contains information about
         unmatched DHCP hosts."
    ::= { tmnxLocalUserDbObjs 10 }

tmnxLocUsrDbDhcpUnmatchedEntry   OBJECT-TYPE
    SYNTAX      TmnxLocUsrDbDhcpUnmatchedEntry
    MAX-ACCESS  not-accessible
    STATUS      current
    DESCRIPTION
        "Each row represents a host (or set of hosts) that is unmatched.

         Objects tmnxLocUsrDbMatchTypeDhcp1, tmnxLocUsrDbMatchTypeDhcp2,
         tmnxLocUsrDbMatchTypeDhcp3 and tmnxLocUsrDbMatchTypeDhcp4 specify
         which objects in the tmnxLocUsrDbDhcpTable are used to match the DHCP
         parameters against.

         This table has entries for each host in the tmnxLocUsrDbDhcpTable
         that:
         - has no objects configured that correspond with the match types, or
         - has identical values configured for the objects that correspond
           with the match types, as another PPPoE host.

         Entries in this table cannot be created or deleted via SNMP
         operations."
    INDEX       {
        tmnxLocUsrDbUserDatabaseName,
        tmnxLocUsrDbDhcpHostName
    }
    ::= { tmnxLocUsrDbDhcpUnmatchedTable 1 }

TmnxLocUsrDbDhcpUnmatchedEntry   ::= SEQUENCE
{
    tmnxLocUsrDbDhcpUnMacAddress     MacAddress,
    tmnxLocUsrDbDhcpUnCircuitId      OCTET STRING,
    tmnxLocUsrDbDhcpUnRemoteId       OCTET STRING,
    tmnxLocUsrDbDhcpUnSystemId       DisplayString,
    tmnxLocUsrDbDhcpUnServiceId      TmnxServId,
    tmnxLocUsrDbDhcpUnSapId          DisplayString,
    tmnxLocUsrDbDhcpUnString         DisplayString,
    tmnxLocUsrDbDhcpUnOption60       OCTET STRING,
    tmnxLocUsrDbDhcpUnmatchedReason  TmnxLocUsrDbUnmatchedReason,
    tmnxLocUsrDbDhcpUnDuplicateHost  DisplayString,
    tmnxLocUsrDbDhcpUnDerivedId      DisplayString,
    tmnxLocUsrDbDhcpUnEncTagRgType   TmnxPortEncapType,
    tmnxLocUsrDbDhcpUnEncTagRgStart  TmnxEncapVal,
    tmnxLocUsrDbDhcpUnEncTagRgEnd    TmnxEncapVal,
    tmnxLocUsrDbDhcpUnIpPrefAddrType InetAddressType,
    tmnxLocUsrDbDhcpUnIpPrefAddr     InetAddress,
    tmnxLocUsrDbDhcpUnIpPrefLength   InetAddressPrefixLength,
    tmnxLocUsrDbDhcpUnEncTagRgOutSta Integer32,
    tmnxLocUsrDbDhcpUnEncTagRgOutEnd Integer32,
    tmnxLocUsrDbDhcpUnEncTagRgInnSta Integer32,
    tmnxLocUsrDbDhcpUnEncTagRgInnEnd Integer32
}

tmnxLocUsrDbDhcpUnMacAddress     OBJECT-TYPE
    SYNTAX      MacAddress
    MAX-ACCESS  read-only
    STATUS      current
    DESCRIPTION
        "The value of the object tmnxLocUsrDbDhcpUnMacAddress indicates the MAC
         address of the unmatched host."
    ::= { tmnxLocUsrDbDhcpUnmatchedEntry 1 }

tmnxLocUsrDbDhcpUnCircuitId      OBJECT-TYPE
    SYNTAX      OCTET STRING (SIZE (0..127))
    MAX-ACCESS  read-only
    STATUS      current
    DESCRIPTION
        "The value of the object tmnxLocUsrDbDhcpUnCircuitId indicates the
         circuit Id from option 82 of the unmatched host."
    ::= { tmnxLocUsrDbDhcpUnmatchedEntry 2 }

tmnxLocUsrDbDhcpUnRemoteId       OBJECT-TYPE
    SYNTAX      OCTET STRING (SIZE (0..255))
    MAX-ACCESS  read-only
    STATUS      current
    DESCRIPTION
        "The value of the object tmnxLocUsrDbDhcpUnRemoteId indicates the
         remote Id from option 82 of the unmatched host."
    ::= { tmnxLocUsrDbDhcpUnmatchedEntry 3 }

tmnxLocUsrDbDhcpUnSystemId       OBJECT-TYPE
    SYNTAX      DisplayString (SIZE (0..255))
    MAX-ACCESS  read-only
    STATUS      current
    DESCRIPTION
        "The value of the object tmnxLocUsrDbDhcpUnSystemId indicates the
         system Id from the Nokia vendor specific sub-option in option 82 of
         the unmatched host."
    ::= { tmnxLocUsrDbDhcpUnmatchedEntry 4 }

tmnxLocUsrDbDhcpUnServiceId      OBJECT-TYPE
    SYNTAX      TmnxServId
    MAX-ACCESS  read-only
    STATUS      current
    DESCRIPTION
        "The value of the object tmnxLocUsrDbDhcpUnServiceId indicates the
         service Id from the Nokia vendor specific sub-option in option 82 of
         the unmatched host."
    ::= { tmnxLocUsrDbDhcpUnmatchedEntry 5 }

tmnxLocUsrDbDhcpUnSapId          OBJECT-TYPE
    SYNTAX      DisplayString (SIZE (0..255))
    MAX-ACCESS  read-only
    STATUS      current
    DESCRIPTION
        "The value of the object tmnxLocUsrDbDhcpUnSapId indicates the sapId
         from the Nokia vendor specific sub-option in option 82 of the
         unmatched host."
    ::= { tmnxLocUsrDbDhcpUnmatchedEntry 6 }

tmnxLocUsrDbDhcpUnString         OBJECT-TYPE
    SYNTAX      DisplayString (SIZE (0..255))
    MAX-ACCESS  read-only
    STATUS      current
    DESCRIPTION
        "The value of the object tmnxLocUsrDbDhcpUnString indicates the string
         from the Nokia vendor specific sub-option in option 82 of the
         unmatched host."
    ::= { tmnxLocUsrDbDhcpUnmatchedEntry 7 }

tmnxLocUsrDbDhcpUnOption60       OBJECT-TYPE
    SYNTAX      OCTET STRING (SIZE (0..32))
    MAX-ACCESS  read-only
    STATUS      current
    DESCRIPTION
        "The value of the object tmnxLocUsrDbDhcpUnOption60 indicates the
         option 60 of the unmatched host."
    ::= { tmnxLocUsrDbDhcpUnmatchedEntry 8 }

tmnxLocUsrDbDhcpUnmatchedReason  OBJECT-TYPE
    SYNTAX      TmnxLocUsrDbUnmatchedReason
    MAX-ACCESS  read-only
    STATUS      current
    DESCRIPTION
        "The value of the object tmnxLocUsrDbDhcpUnmatchedReason indicates why
         this host is not matched."
    ::= { tmnxLocUsrDbDhcpUnmatchedEntry 9 }

tmnxLocUsrDbDhcpUnDuplicateHost  OBJECT-TYPE
    SYNTAX      DisplayString (SIZE (0..32))
    MAX-ACCESS  read-only
    STATUS      current
    DESCRIPTION
        "The value of the object tmnxLocUsrDbDhcpUnDuplicateHost indicates the
         name of the host that is already matched and that has the same values,
         configured for the objects that correspond with the match types, as
         this unmatched host.

         This value of this object is the empty string, unless the value of
         tmnxLocUsrDbDhcpUnmatchedReason is 'duplicate (2)'."
    ::= { tmnxLocUsrDbDhcpUnmatchedEntry 10 }

tmnxLocUsrDbDhcpUnDerivedId      OBJECT-TYPE
    SYNTAX      DisplayString (SIZE (0..255))
    MAX-ACCESS  read-only
    STATUS      current
    DESCRIPTION
        "The value of the object tmnxLocUsrDbDhcpUnDerivedId indicates the
         string to be matched with a string that uniquely identifies a host and
         is derived by a Python script from packet content available during a
         DHCP transaction.

         If the value of this object is the empty string, it is not used."
    ::= { tmnxLocUsrDbDhcpUnmatchedEntry 11 }

tmnxLocUsrDbDhcpUnEncTagRgType   OBJECT-TYPE
    SYNTAX      TmnxPortEncapType
    MAX-ACCESS  read-only
    STATUS      current
    DESCRIPTION
        "The value of the object tmnxLocUsrDbDhcpUnEncTagRgType indicates the
         type of encapsulation protocol configured for the SAP encap tag range
         start and end values.

         Can either be unknown, qEncap or qinqEncap."
    ::= { tmnxLocUsrDbDhcpUnmatchedEntry 12 }

tmnxLocUsrDbDhcpUnEncTagRgStart  OBJECT-TYPE
    SYNTAX      TmnxEncapVal
    MAX-ACCESS  read-only
    STATUS      current
    DESCRIPTION
        "The value of the object tmnxLocUsrDbDhcpUnEncTagRgStart indicates the
         start label in the range of SAPs allowed on this host.

         A value of 0 iso 1 is used when vci=*."
    ::= { tmnxLocUsrDbDhcpUnmatchedEntry 13 }

tmnxLocUsrDbDhcpUnEncTagRgEnd    OBJECT-TYPE
    SYNTAX      TmnxEncapVal
    MAX-ACCESS  read-only
    STATUS      current
    DESCRIPTION
        "The value of the object tmnxLocUsrDbDhcpUnEncTagRgEnd indicates the
         end label in the range of SAPs allowed on this host.

         A value of 0 iso 1 is used when vci=*."
    ::= { tmnxLocUsrDbDhcpUnmatchedEntry 14 }

tmnxLocUsrDbDhcpUnIpPrefAddrType OBJECT-TYPE
    SYNTAX      InetAddressType
    MAX-ACCESS  read-only
    STATUS      current
    DESCRIPTION
        "The value of tmnxLocUsrDbDhcpUnIpPrefAddrType indicates the type of
         address stored in tmnxLocUsrDbDhcpIpPrefixAddr."
    ::= { tmnxLocUsrDbDhcpUnmatchedEntry 15 }

tmnxLocUsrDbDhcpUnIpPrefAddr     OBJECT-TYPE
    SYNTAX      InetAddress (SIZE (0|4|16))
    MAX-ACCESS  read-only
    STATUS      current
    DESCRIPTION
        "The value of tmnxLocUsrDbDhcpUnIpPrefAddr indicates the IP prefix
         address used as match in host identification."
    ::= { tmnxLocUsrDbDhcpUnmatchedEntry 16 }

tmnxLocUsrDbDhcpUnIpPrefLength   OBJECT-TYPE
    SYNTAX      InetAddressPrefixLength (0..128)
    MAX-ACCESS  read-only
    STATUS      current
    DESCRIPTION
        "The value of tmnxLocUsrDbDhcpUnIpPrefLength indicates the prefix
         length of the IP prefix."
    ::= { tmnxLocUsrDbDhcpUnmatchedEntry 17 }

tmnxLocUsrDbDhcpUnEncTagRgOutSta OBJECT-TYPE
    SYNTAX      Integer32 (-1 | 0..4094)
    MAX-ACCESS  read-only
    STATUS      current
    DESCRIPTION
        "The value of the object tmnxLocUsrDbDhcpUnEncTagRgOutSta indicates the
         left bound (i.e. minimum value) of a range of outer VLANs allowed on
         this DHCP host. Value -1 indicates tmnxLocUsrDbDhcpUnEncTagRgOutSta is
         not applicable."
    ::= { tmnxLocUsrDbDhcpUnmatchedEntry 18 }

tmnxLocUsrDbDhcpUnEncTagRgOutEnd OBJECT-TYPE
    SYNTAX      Integer32 (-1 | 0..4094)
    MAX-ACCESS  read-only
    STATUS      current
    DESCRIPTION
        "The value of the object tmnxLocUsrDbDhcpUnEncTagRgOutEnd indicates the
         right bound (i.e. maximum value) of a range of outer VLANs allowed on
         this DHCP host. Value -1 indicates tmnxLocUsrDbDhcpUnEncTagRgOutEnd is
         not applicable."
    ::= { tmnxLocUsrDbDhcpUnmatchedEntry 19 }

tmnxLocUsrDbDhcpUnEncTagRgInnSta OBJECT-TYPE
    SYNTAX      Integer32 (-1 | 0..4094)
    MAX-ACCESS  read-only
    STATUS      current
    DESCRIPTION
        "The value of the object tmnxLocUsrDbDhcpUnEncTagRgInnSta indicates the
         left bound (i.e. minimum value) of a range of inner VLANs allowed on
         this DHCP host. Value -1 indicates tmnxLocUsrDbDhcpUnEncTagRgInnSta is
         not applicable."
    ::= { tmnxLocUsrDbDhcpUnmatchedEntry 20 }

tmnxLocUsrDbDhcpUnEncTagRgInnEnd OBJECT-TYPE
    SYNTAX      Integer32 (-1 | 0..4094)
    MAX-ACCESS  read-only
    STATUS      current
    DESCRIPTION
        "The value of the object tmnxLocUsrDbDhcpUnEncTagRgInnEnd indicates the
         right bound (i.e. maximum value) of a range of inner VLANs allowed on
         this DHCP host. Value -1 indicates tmnxLocUsrDbDhcpUnEncTagRgInnEnd is
         not applicable."
    ::= { tmnxLocUsrDbDhcpUnmatchedEntry 21 }

tmnxLocUsrDbDhcpOptionTableLstCh OBJECT-TYPE
    SYNTAX      TimeStamp
    MAX-ACCESS  read-only
    STATUS      current
    DESCRIPTION
        "The value of the object tmnxLocUsrDbDhcpOptionTableLstCh indicates the
         value of sysUpTime at the time of the last modification of an entry in
         the tmnxLocUsrDbDhcpOptionTable."
    ::= { tmnxLocalUserDbObjs 11 }

tmnxLocUsrDbDhcpOptionTable      OBJECT-TYPE
    SYNTAX      SEQUENCE OF TmnxLocUsrDbDhcpOptionEntry
    MAX-ACCESS  not-accessible
    STATUS      current
    DESCRIPTION
        "The table tmnxLocUsrDbDhcpOptionTable contains objects to configure
         the DHCP options of each DHCP host."
    ::= { tmnxLocalUserDbObjs 12 }

tmnxLocUsrDbDhcpOptionEntry      OBJECT-TYPE
    SYNTAX      TmnxLocUsrDbDhcpOptionEntry
    MAX-ACCESS  not-accessible
    STATUS      current
    DESCRIPTION
        "Each row represents a DHCP option that is encoded in the DHCP reply
         message of this DHCP host.

         Entries in this table can be created or deleted via SNMP operations."
    INDEX       {
        tmnxLocUsrDbUserDatabaseName,
        tmnxLocUsrDbDhcpHostName,
        tmnxLocUsrDbDhcpOptionNumber
    }
    ::= { tmnxLocUsrDbDhcpOptionTable 1 }

TmnxLocUsrDbDhcpOptionEntry      ::= SEQUENCE
{
    tmnxLocUsrDbDhcpOptionNumber     Unsigned32,
    tmnxLocUsrDbDhcpOptionRowStatus  RowStatus,
    tmnxLocUsrDbDhcpOptionLastChngTm TimeStamp,
    tmnxLocUsrDbDhcpOptionType       TmnxDhcpOptionType,
    tmnxLocUsrDbDhcpOptionValue      OCTET STRING,
    tmnxLocUsrDbDhcpOptionDisplay    TmnxDhcpOptionDisplay
}

tmnxLocUsrDbDhcpOptionNumber     OBJECT-TYPE
    SYNTAX      Unsigned32 (1..254)
    MAX-ACCESS  not-accessible
    STATUS      current
    DESCRIPTION
        "The value of the object tmnxLocUsrDbDhcpOptionNumber specifies the
         number of this DHCP option."
    REFERENCE
        "RFC 2132"
    ::= { tmnxLocUsrDbDhcpOptionEntry 1 }

tmnxLocUsrDbDhcpOptionRowStatus  OBJECT-TYPE
    SYNTAX      RowStatus
    MAX-ACCESS  read-create
    STATUS      current
    DESCRIPTION
        "The value of the object tmnxLocUsrDbDhcpOptionRowStatus specifies the
         row status of this row.

         Objects tmnxLocUsrDbDhcpOptionType and tmnxLocUsrDbDhcpOptionValue
         must be set when creating a new row."
    ::= { tmnxLocUsrDbDhcpOptionEntry 2 }

tmnxLocUsrDbDhcpOptionLastChngTm OBJECT-TYPE
    SYNTAX      TimeStamp
    MAX-ACCESS  read-only
    STATUS      current
    DESCRIPTION
        "The value of the object tmnxLocUsrDbDhcpOptionLastChngTm indicates the
         sysUpTime at the time of the last modification of this entry."
    ::= { tmnxLocUsrDbDhcpOptionEntry 3 }

tmnxLocUsrDbDhcpOptionType       OBJECT-TYPE
    SYNTAX      TmnxDhcpOptionType
    MAX-ACCESS  read-create
    STATUS      current
    DESCRIPTION
        "The value of the object tmnxLocUsrDbDhcpOptionType specifies how the
         value of this option in stored in tmnxLocUsrDbDhcpOptionValue.

         This object is mandatory at creation time."
    ::= { tmnxLocUsrDbDhcpOptionEntry 4 }

tmnxLocUsrDbDhcpOptionValue      OBJECT-TYPE
    SYNTAX      OCTET STRING (SIZE (0..127))
    MAX-ACCESS  read-create
    STATUS      current
    DESCRIPTION
        "The value of the object tmnxLocUsrDbDhcpOptionValue specifies the
         value of this option.

         This object is mandatory at creation time. A zero length value is only
         allowed when the value of tmnxLocUsrDbDhcpOptionType is 'hex (3)'."
    ::= { tmnxLocUsrDbDhcpOptionEntry 5 }

tmnxLocUsrDbDhcpOptionDisplay    OBJECT-TYPE
    SYNTAX      TmnxDhcpOptionDisplay
    MAX-ACCESS  read-only
    STATUS      current
    DESCRIPTION
        "The value of the object tmnxLocUsrDbDhcpOptionDisplay indicates a hint
         of how the tmnxLocUsrDbDhcpOptionValue can be displayed."
    ::= { tmnxLocUsrDbDhcpOptionEntry 6 }

tmnxLocUsrDbPppoeAuthTool        OBJECT IDENTIFIER ::= { tmnxLocalUserDbObjs 13 }

tmnxLocUsrDbPppoeAuthDbName      OBJECT-TYPE
    SYNTAX      TNamedItemOrEmpty
    MAX-ACCESS  read-write
    STATUS      current
    DESCRIPTION
        "The value of the object tmnxLocUsrDbPppoeAuthDbName specifies the name
         of the local user database in which to perform the match."
    DEFVAL      { "" }
    ::= { tmnxLocUsrDbPppoeAuthTool 1 }

tmnxLocUsrDbPppoeAuthUsrName     OBJECT-TYPE
    SYNTAX      TmnxPppoeUserNameOrEmpty
    MAX-ACCESS  read-write
    STATUS      current
    DESCRIPTION
        "The value of the object tmnxLocUsrDbPppoeAuthUsrName specifies the
         username to match."
    DEFVAL      { "" }
    ::= { tmnxLocUsrDbPppoeAuthTool 2 }

tmnxLocUsrDbPppoeAuthPwd         OBJECT-TYPE
    SYNTAX      DisplayString (SIZE (0..32))
    MAX-ACCESS  read-write
    STATUS      current
    DESCRIPTION
        "The value of the object tmnxLocUsrDbPppoeAuthPwd indicates the
         password to match for the given username. This is optional.

         This object will always return an empty string on a read."
    ::= { tmnxLocUsrDbPppoeAuthTool 3 }

tmnxLocUsrDbPppoeAuthenticate    OBJECT-TYPE
    SYNTAX      TmnxActionType
    MAX-ACCESS  read-write
    STATUS      current
    DESCRIPTION
        "Setting this object to 'doAction (1)' triggers an attempt to match the
         tmnxLocUsrDbPppoeAuthUsrName to a PPPoE user in the
         tmnxLocUsrDbPppoeTable. If a user is found and the value of
         tmnxLocUsrDbPppoeAuthPwd is not the empty string, the password will be
         verified.

         Reading this object returns the value 'notApplicable'."
    DEFVAL      { notApplicable }
    ::= { tmnxLocUsrDbPppoeAuthTool 4 }

tmnxLocUsrDbPppoeAuthSuccessful  OBJECT-TYPE
    SYNTAX      TruthValue
    MAX-ACCESS  read-only
    STATUS      current
    DESCRIPTION
        "The value of the object tmnxLocUsrDbPppoeAuthSuccessful indicates
         whether the authentication was successful.

         If the value of the object equals 'true (1)', then the value of
         tmnxLocUsrDbPppoeAuthHostName identifies the PPPoE user in the
         tmnxLocUsrDbPppoeTable."
    ::= { tmnxLocUsrDbPppoeAuthTool 5 }

tmnxLocUsrDbPppoeAuthErrorMsg    OBJECT-TYPE
    SYNTAX      DisplayString (SIZE (0..255))
    MAX-ACCESS  read-only
    STATUS      current
    DESCRIPTION
        "The value of the object tmnxLocUsrDbPppoeAuthErrorMsg indicates the
         reason of failure, in case the value of the object
         tmnxLocUsrDbPppoeAuthSuccessful is equal to 'false (2)'.

         If the value of the object tmnxLocUsrDbPppoeAuthSuccessful is equal to
         'true (1)', this object contains an empty string."
    ::= { tmnxLocUsrDbPppoeAuthTool 6 }

tmnxLocUsrDbPppoeAuthTime        OBJECT-TYPE
    SYNTAX      TimeStamp
    MAX-ACCESS  read-only
    STATUS      current
    DESCRIPTION
        "The value of the object tmnxLocUsrDbPppoeAuthTime indicates the value
         of sysUpTime at the last time that the object
         tmnxLocUsrDbPppoeAuthSuccessful was written by the system."
    ::= { tmnxLocUsrDbPppoeAuthTool 7 }

tmnxLocUsrDbPppoeAuthHostName    OBJECT-TYPE
    SYNTAX      DisplayString (SIZE (0..32))
    MAX-ACCESS  read-only
    STATUS      current
    DESCRIPTION
        "The value of the object tmnxLocUsrDbPppoeAuthHostName indicates the
         name of this host or set of hosts."
    ::= { tmnxLocUsrDbPppoeAuthTool 8 }

tmnxLocUsrDbPppoeAuthMacAddress  OBJECT-TYPE
    SYNTAX      MacAddress
    MAX-ACCESS  read-write
    STATUS      current
    DESCRIPTION
        "The value of the object tmnxLocUsrDbPppoeAuthMacAddress specifies the
         MAC address to match against.

         If the value of this object is set to all zeros, then it is not used."
    DEFVAL      { '000000000000'H }
    ::= { tmnxLocUsrDbPppoeAuthTool 9 }

tmnxLocUsrDbPppoeAuthRemoteId    OBJECT-TYPE
    SYNTAX      OCTET STRING (SIZE (0..255))
    MAX-ACCESS  read-write
    STATUS      current
    DESCRIPTION
        "The value of the object tmnxLocUsrDbPppoeAuthRemoteId specifies the
         remote Id to match against.

         If the value of this object is the empty string, then it is not used."
    DEFVAL      { "" }
    ::= { tmnxLocUsrDbPppoeAuthTool 10 }

tmnxLocUsrDbPppoeAuthCircuitIdFmt OBJECT-TYPE
    SYNTAX      TmnxLocUsrDbDataFormat
    MAX-ACCESS  read-write
    STATUS      current
    DESCRIPTION
        "The value of the object tmnxLocUsrDbPppoeAuthCircuitIdFmt specifies
         how the value of tmnxLocUsrDbPppoeCircuitId must be formatted."
    DEFVAL      { ascii }
    ::= { tmnxLocUsrDbPppoeAuthTool 11 }

tmnxLocUsrDbPppoeAuthCircuitId   OBJECT-TYPE
    SYNTAX      OCTET STRING (SIZE (0..127))
    MAX-ACCESS  read-write
    STATUS      current
    DESCRIPTION
        "The value of the object tmnxLocUsrDbPppoeAuthCircuitId specifies the
         circuit Id to match against.

         If the value of this object is the empty string, then it is not used."
    DEFVAL      { ''H }
    ::= { tmnxLocUsrDbPppoeAuthTool 12 }

tmnxLocUsrDbPppoeAuthServiceName OBJECT-TYPE
    SYNTAX      DisplayString (SIZE (0..255))
    MAX-ACCESS  read-write
    STATUS      current
    DESCRIPTION
        "The value of the object tmnxLocUsrDbPppoeAuthServiceName specifies the
         PPPoE service name to match against.

         If the value of this object is the empty string, then it is not used."
    DEFVAL      { "" }
    ::= { tmnxLocUsrDbPppoeAuthTool 13 }

tmnxLocUsrDbPppoeAuthRemoteIdFmt OBJECT-TYPE
    SYNTAX      TmnxLocUsrDbDataFormat
    MAX-ACCESS  read-write
    STATUS      current
    DESCRIPTION
        "The value of the object tmnxLocUsrDbPppoeAuthRemoteIdFmt specifies how
         the value of tmnxLocUsrDbPppoeRemoteId must be formatted."
    DEFVAL      { ascii }
    ::= { tmnxLocUsrDbPppoeAuthTool 14 }

tmnxLocUsrDbPppoeAuthSapId       OBJECT-TYPE
    SYNTAX      DisplayString (SIZE (0..255))
    MAX-ACCESS  read-write
    STATUS      current
    DESCRIPTION
        "The value of the object tmnxLocUsrDbPppoeAuthSapId specifies the sapId
         to match against.

         If the value of this object is the empty string, then it is not used."
    DEFVAL      { "" }
    ::= { tmnxLocUsrDbPppoeAuthTool 15 }

tmnxLocUsrDbPppoeAuthDerivedId   OBJECT-TYPE
    SYNTAX      DisplayString (SIZE (0..255))
    MAX-ACCESS  read-write
    STATUS      current
    DESCRIPTION
        "The value of the object tmnxLocUsrDbPppoeAuthDerivedId specifies the
         derivedId to match against.

         If the value of this object is the empty string, then it is not used."
    DEFVAL      { "" }
    ::= { tmnxLocUsrDbPppoeAuthTool 16 }

tmnxLocUsrDbDhcpMaskTableLstCh   OBJECT-TYPE
    SYNTAX      TimeStamp
    MAX-ACCESS  read-only
    STATUS      current
    DESCRIPTION
        "The value of the object tmnxLocUsrDbDhcpMaskTableLstCh indicates the
         value of sysUpTime at the time of the last modification of an entry in
         the tmnxLocUsrDbDhcpMaskTable."
    ::= { tmnxLocalUserDbObjs 14 }

tmnxLocUsrDbDhcpMaskTable        OBJECT-TYPE
    SYNTAX      SEQUENCE OF TmnxLocUsrDbDhcpMaskEntry
    MAX-ACCESS  not-accessible
    STATUS      current
    DESCRIPTION
        "The table tmnxLocUsrDbDhcpMaskTable contains objects to configure
         local user database masking for DHCP hosts."
    ::= { tmnxLocalUserDbObjs 15 }

tmnxLocUsrDbDhcpMaskEntry        OBJECT-TYPE
    SYNTAX      TmnxLocUsrDbDhcpMaskEntry
    MAX-ACCESS  not-accessible
    STATUS      current
    DESCRIPTION
        "Each row represents a local user database mask.

         Entries in this table can be created or deleted via SNMP operations.

         An incoming string of the type that corresponds to the value of the
         tmnxLocUsrDbDhcpMaskMatchType index of this conceptual row is matched
         with the object in the tmnxLocUsrDbDhcpTable that corresponds to the
         values of the tmnxLocUsrDbUserDatabaseName and
         tmnxLocUsrDbDhcpMaskMatchType indices in this conceptual row:

         match type    | object
         --------------------------------------------
         circuitId     | tmnxLocUsrDbDhcpCircuitId
         macAddr       | tmnxLocUsrDbDhcpMacAddress
         remoteId      | tmnxLocUsrDbDhcpRemoteId
         sapId         | tmnxLocUsrDbDhcpSapId
         serviceId     | tmnxLocUsrDbDhcpServiceId
         string        | tmnxLocUsrDbDhcpString
         systemId      | tmnxLocUsrDbDhcpSystemId
         option60      | tmnxLocUsrDbDhcpOption60
         duidEn        | tmnxLudbDhcp2DuidEn
         duidLlLlt     | tmnxLudbDhcp2DuidLlLlt"
    INDEX       {
        tmnxLocUsrDbUserDatabaseName,
        tmnxLocUsrDbDhcpMaskMatchType
    }
    ::= { tmnxLocUsrDbDhcpMaskTable 1 }

TmnxLocUsrDbDhcpMaskEntry        ::= SEQUENCE
{
    tmnxLocUsrDbDhcpMaskMatchType    TmnxLocUsrDbMatchTypeDhcp,
    tmnxLocUsrDbDhcpMaskRowStatus    RowStatus,
    tmnxLocUsrDbDhcpMaskPreStr       TmnxLocUsrDbMaskString,
    tmnxLocUsrDbDhcpMaskPreNum       Unsigned32,
    tmnxLocUsrDbDhcpMaskSufStr       TmnxLocUsrDbMaskString,
    tmnxLocUsrDbDhcpMaskSufNum       Unsigned32
}

tmnxLocUsrDbDhcpMaskMatchType    OBJECT-TYPE
    SYNTAX      TmnxLocUsrDbMatchTypeDhcp
    MAX-ACCESS  not-accessible
    STATUS      current
    DESCRIPTION
        "The type of matching done to identify the user.

         The value 'derivedId' is not supported."
    ::= { tmnxLocUsrDbDhcpMaskEntry 1 }

tmnxLocUsrDbDhcpMaskRowStatus    OBJECT-TYPE
    SYNTAX      RowStatus
    MAX-ACCESS  read-create
    STATUS      current
    DESCRIPTION
        "The value of the object tmnxLocUsrDbDhcpMaskRowStatus specifies the
         row status of this entry."
    ::= { tmnxLocUsrDbDhcpMaskEntry 2 }

tmnxLocUsrDbDhcpMaskPreStr       OBJECT-TYPE
    SYNTAX      TmnxLocUsrDbMaskString
    MAX-ACCESS  read-create
    STATUS      current
    DESCRIPTION
        "The value of the object tmnxLocUsrDbDhcpMaskPreStr specifies a
         substring that is stripped off the start of the incoming string before
         it is matched against the value configured in the corresponding object
         in the tmnxLocUsrDbDhcpTable.

         This string can only contain printable ASCII characters. Character '*'
         is a wildcard that matches any substring; it can be escaped by
         character '\'.

         At least one of the values of tmnxLocUsrDbDhcpMaskPreNum and
         tmnxLocUsrDbDhcpMaskPreStr must be equal to the default value."
    DEFVAL      { "" }
    ::= { tmnxLocUsrDbDhcpMaskEntry 3 }

tmnxLocUsrDbDhcpMaskPreNum       OBJECT-TYPE
    SYNTAX      Unsigned32 (0..127)
    MAX-ACCESS  read-create
    STATUS      current
    DESCRIPTION
        "The value of the object tmnxLocUsrDbDhcpMaskPreNum specifies the
         number of characters to remove from the start of the incoming string
         before it is matched against the value configured in the corresponding
         object in the tmnxLocUsrDbDhcpTable.

         At least one of the values of tmnxLocUsrDbDhcpMaskPreNum and
         tmnxLocUsrDbDhcpMaskPreStr must be equal to the default value."
    DEFVAL      { 0 }
    ::= { tmnxLocUsrDbDhcpMaskEntry 4 }

tmnxLocUsrDbDhcpMaskSufStr       OBJECT-TYPE
    SYNTAX      TmnxLocUsrDbMaskString
    MAX-ACCESS  read-create
    STATUS      current
    DESCRIPTION
        "The value of the object tmnxLocUsrDbDhcpMaskSufStr specifies a
         substring that is stripped off the end of the incoming string before
         it is matched against the value configured in the corresponding object
         in the tmnxLocUsrDbDhcpTable.

         This string can only contain printable ASCII characters. Character '*'
         is a wildcard that matches any substring; it can be escaped by
         character '\'.

         At least one of the values of tmnxLocUsrDbDhcpMaskSufNum and
         tmnxLocUsrDbDhcpMaskSufStr must be equal to the default value."
    DEFVAL      { "" }
    ::= { tmnxLocUsrDbDhcpMaskEntry 5 }

tmnxLocUsrDbDhcpMaskSufNum       OBJECT-TYPE
    SYNTAX      Unsigned32 (0..127)
    MAX-ACCESS  read-create
    STATUS      current
    DESCRIPTION
        "The value of the object tmnxLocUsrDbDhcpMaskSufNum specifies the
         number of characters to remove from the end of the incoming string
         before it is matched against the value configured in the corresponding
         object in the tmnxLocUsrDbDhcpTable.

         At least one of the values of tmnxLocUsrDbDhcpMaskSufNum and
         tmnxLocUsrDbDhcpMaskSufStr must be equal to the default value."
    DEFVAL      { 0 }
    ::= { tmnxLocUsrDbDhcpMaskEntry 6 }

tmnxLocUsrDbPppoeMaskTableLstCh  OBJECT-TYPE
    SYNTAX      TimeStamp
    MAX-ACCESS  read-only
    STATUS      current
    DESCRIPTION
        "The value of the object tmnxLocUsrDbPppoeMaskTableLstCh indicates the
         value of sysUpTime at the time of the last modification of an entry in
         the tmnxLocUsrDbPppoeMaskTable."
    ::= { tmnxLocalUserDbObjs 16 }

tmnxLocUsrDbPppoeMaskTable       OBJECT-TYPE
    SYNTAX      SEQUENCE OF TmnxLocUsrDbPppoeMaskEntry
    MAX-ACCESS  not-accessible
    STATUS      current
    DESCRIPTION
        "The table tmnxLocUsrDbPppoeMaskTable contains objects to configure
         local user database masking for PPPoE hosts."
    ::= { tmnxLocalUserDbObjs 17 }

tmnxLocUsrDbPppoeMaskEntry       OBJECT-TYPE
    SYNTAX      TmnxLocUsrDbPppoeMaskEntry
    MAX-ACCESS  not-accessible
    STATUS      current
    DESCRIPTION
        "Each row represents a local user database mask.

         Entries in this table can be created or deleted via SNMP operations.

         An incoming string of the type that corresponds to the value of the
         tmnxLocUsrDbPppoeMaskMatchType index of this conceptual row is matched
         with the object in the tmnxLocUsrDbPppoeTable that corresponds to the
         values of the tmnxLocUsrDbUserDatabaseName and
         tmnxLocUsrDbPppoeMaskMatchType indices in this conceptual row:

         match type    | object
         --------------------------------------------
         circuitId     | tmnxLocUsrDbPppoeCircuitId
         macAddr       | tmnxLocUsrDbPppoeMacAddress
         remoteId      | tmnxLocUsrDbPppoeRemoteId
         userName      | tmnxLocUsrDbPppoeUserName
         serviceName   | tmnxLocUsrDbPppoeServiceName
         sapId         | tmnxLocUsrDbPppoeSapId"
    INDEX       {
        tmnxLocUsrDbUserDatabaseName,
        tmnxLocUsrDbPppoeMaskMatchType
    }
    ::= { tmnxLocUsrDbPppoeMaskTable 1 }

TmnxLocUsrDbPppoeMaskEntry       ::= SEQUENCE
{
    tmnxLocUsrDbPppoeMaskMatchType   TmnxLocUsrDbMatchTypePppoe,
    tmnxLocUsrDbPppoeMaskRowStatus   RowStatus,
    tmnxLocUsrDbPppoeMaskPreStr      TmnxLocUsrDbMaskString,
    tmnxLocUsrDbPppoeMaskPreNum      Unsigned32,
    tmnxLocUsrDbPppoeMaskSufStr      TmnxLocUsrDbMaskString,
    tmnxLocUsrDbPppoeMaskSufNum      Unsigned32
}

tmnxLocUsrDbPppoeMaskMatchType   OBJECT-TYPE
    SYNTAX      TmnxLocUsrDbMatchTypePppoe
    MAX-ACCESS  not-accessible
    STATUS      current
    DESCRIPTION
        "The type of matching done to identify the user.

         The value 'derivedId' is not supported."
    ::= { tmnxLocUsrDbPppoeMaskEntry 1 }

tmnxLocUsrDbPppoeMaskRowStatus   OBJECT-TYPE
    SYNTAX      RowStatus
    MAX-ACCESS  read-create
    STATUS      current
    DESCRIPTION
        "The value of the object tmnxLocUsrDbPppoeMaskRowStatus specifies the
         row status of this entry."
    ::= { tmnxLocUsrDbPppoeMaskEntry 2 }

tmnxLocUsrDbPppoeMaskPreStr      OBJECT-TYPE
    SYNTAX      TmnxLocUsrDbMaskString
    MAX-ACCESS  read-create
    STATUS      current
    DESCRIPTION
        "The value of the object tmnxLocUsrDbPppoeMaskPreStr specifies a
         substring that is stripped off the start of the incoming string before
         it is matched against the value configured in the corresponding object
         in the tmnxLocUsrDbPppoeTable.

         This string can only contain printable ASCII characters. Character '*'
         is a wildcard that matches any substring; it can be escaped by
         character '\'.

         At least one of the values of tmnxLocUsrDbPppoeMaskPreNum and
         tmnxLocUsrDbPppoeMaskPreStr must be equal to the default value. This
         object is not supported when tmnxLocUsrDbPppoeMaskMatchType is set to
         value 'macAddr'."
    DEFVAL      { "" }
    ::= { tmnxLocUsrDbPppoeMaskEntry 3 }

tmnxLocUsrDbPppoeMaskPreNum      OBJECT-TYPE
    SYNTAX      Unsigned32 (0..127)
    MAX-ACCESS  read-create
    STATUS      current
    DESCRIPTION
        "The value of the object tmnxLocUsrDbPppoeMaskPreNum specifies the
         number of characters to remove from the start of the incoming string
         before it is matched against the value configured in the corresponding
         object in the tmnxLocUsrDbPppoeTable. If
         tmnxLocUsrDbPppoeMaskMatchType is set to value 'macAddr', this object
         specifies the number of leading bits that will be blanked out from the
         incoming MAC address before it is matched against the value configured
         in tmnxLocUsrDbPppoeMacAddress and only values within range 1..47 are
         allowed.

         At least one of the values of tmnxLocUsrDbPppoeMaskPreNum and
         tmnxLocUsrDbPppoeMaskPreStr must be equal to the default value."
    DEFVAL      { 0 }
    ::= { tmnxLocUsrDbPppoeMaskEntry 4 }

tmnxLocUsrDbPppoeMaskSufStr      OBJECT-TYPE
    SYNTAX      TmnxLocUsrDbMaskString
    MAX-ACCESS  read-create
    STATUS      current
    DESCRIPTION
        "The value of the object tmnxLocUsrDbPppoeMaskSufStr specifies a
         substring that is stripped of the end of the incoming string before it
         is matched against the value configured in the corresponding object in
         the tmnxLocUsrDbPppoeTable.

         This string can only contain printable ASCII characters. Character '*'
         is a wildcard that matches any substring; it can be escaped by
         character '\'.

         At least one of the values of tmnxLocUsrDbPppoeMaskSufNum and
         tmnxLocUsrDbPppoeMaskSufStr must be equal to the default value. This
         object is not supported when tmnxLocUsrDbPppoeMaskMatchType is set to
         value 'macAddr'."
    DEFVAL      { "" }
    ::= { tmnxLocUsrDbPppoeMaskEntry 5 }

tmnxLocUsrDbPppoeMaskSufNum      OBJECT-TYPE
    SYNTAX      Unsigned32 (0..127)
    MAX-ACCESS  read-create
    STATUS      current
    DESCRIPTION
        "The value of the object tmnxLocUsrDbPppoeMaskSufNum specifies the
         number of characters to remove from the end of the incoming string
         before it is matched against the value configured in the corresponding
         object in the tmnxLocUsrDbPppoeTable. If
         tmnxLocUsrDbPppoeMaskMatchType is set to value 'macAddr', this object
         specifies the number of trailing bits that will be blanked out from
         the incoming MAC address before it is matched against the value
         configured in tmnxLocUsrDbPppoeMacAddress and only values within range
         1..47 are allowed.

         At least one of the values of tmnxLocUsrDbPppoeMaskSufNum and
         tmnxLocUsrDbPppoeMaskSufStr must be equal to the default value."
    DEFVAL      { 0 }
    ::= { tmnxLocUsrDbPppoeMaskEntry 6 }

tmnxLudbHostTableLastChange      OBJECT-TYPE
    SYNTAX      TimeStamp
    MAX-ACCESS  read-only
    STATUS      current
    DESCRIPTION
        "The value of the object tmnxLudbHostTableLastChange indicates the
         value of sysUpTime at the time of the last modification of an entry in
         the tmnxLudbHostTable."
    ::= { tmnxLocalUserDbObjs 20 }

tmnxLudbHostTable                OBJECT-TYPE
    SYNTAX      SEQUENCE OF TmnxLudbHostEntry
    MAX-ACCESS  not-accessible
    STATUS      current
    DESCRIPTION
        "The table tmnxLudbHostTable contains objects to configure local user
         database host templates."
    ::= { tmnxLocalUserDbObjs 21 }

tmnxLudbHostEntry                OBJECT-TYPE
    SYNTAX      TmnxLudbHostEntry
    MAX-ACCESS  not-accessible
    STATUS      current
    DESCRIPTION
        "Each conceptual row represents a local user database host template.

         Entries in this table can be created or deleted via SNMP operations."
    INDEX       {
        tmnxLocUsrDbUserDatabaseName,
        tmnxLudbHostType,
        tmnxLudbHostName
    }
    ::= { tmnxLudbHostTable 1 }

TmnxLudbHostEntry                ::= SEQUENCE
{
    tmnxLudbHostType                 TmnxLocUsrDbHostType,
    tmnxLudbHostName                 DisplayString,
    tmnxLudbHostRowStatus            RowStatus,
    tmnxLudbHostLastChangeTime       TimeStamp,
    tmnxLudbHostApplications         TmnxLocUsrDbHostApplications,
    tmnxLudbHostAdminState           TmnxAdminState,
    tmnxLudbHostMacAddress           MacAddress,
    tmnxLudbHostCircuitIdFmt         TmnxLocUsrDbDataFormat,
    tmnxLudbHostCircuitId            OCTET STRING,
    tmnxLudbHostRemoteIdFmt          TmnxLocUsrDbDataFormat,
    tmnxLudbHostRemoteId             OCTET STRING,
    tmnxLudbHostAddrType             InetAddressType,
    tmnxLudbHostAddress              InetAddress,
    tmnxLudbHostPool                 TNamedItemOrEmpty,
    tmnxLudbHostUseGiAddress         TruthValue,
    tmnxLudbHostIdStringOptNum       Unsigned32,
    tmnxLudbHostSubscriberId         TmnxSubIdentStringOrEmpty,
    tmnxLudbHostSlaProfString        TmnxSlaProfileStringOrEmpty,
    tmnxLudbHostFltrProfString       TmnxFilterProfileStringOrEmpty,
    tmnxLudbHostSubProfString        TmnxSubProfileStringOrEmpty,
    tmnxLudbHostAppProfString        DisplayString,
    tmnxLudbHostAncpString           TmnxAncpStringOrZero,
    tmnxLudbHostInterDestId          TNamedItemOrEmpty,
    tmnxLudbHostUseClientPool        TruthValue,
    tmnxLudbHostAuthPolicy           TNamedItemOrEmpty,
    tmnxLudbHostRetailerSvcId        TmnxServId,
    tmnxLudbHostCategoryMapName      TNamedItemOrEmpty,
    tmnxLudbHostDefMsapPolicy        TPolicyStatementNameOrEmpty,
    tmnxLudbHostDefMsapService       TmnxServId,
    tmnxLudbHostDefMsapGroupIf       TNamedItemOrEmpty,
    tmnxLudbHostSystemId             DisplayString,
    tmnxLudbHostServiceId            TmnxServId,
    tmnxLudbHostSapId                DisplayString,
    tmnxLudbHostString               DisplayString,
    tmnxLudbHostIpv6Addr             InetAddress,
    tmnxLudbHostIpv6Pfx              InetAddress,
    tmnxLudbHostIpv6PfxLen           InetAddressPrefixLength,
    tmnxLudbHostAuthDomainName       DisplayString,
    tmnxLudbHostDhcpOption60Fmt      TmnxLudbDataFormat,
    tmnxLudbHostDhcpOption60         OCTET STRING,
    tmnxLudbHostDhcpRelayAddrType    InetAddressType,
    tmnxLudbHostDhcpRelayAddress     InetAddress,
    tmnxLudbHostPppUserNameFormat    TmnxLocUsrDbUserNameFormat,
    tmnxLudbHostPppUserName          TmnxPppoeUserNameOrEmpty,
    tmnxLudbHostPppPasswordType      TmnxLocUsrDbPasswordType,
    tmnxLudbHostPppPassword          DisplayString,
    tmnxLudbHostPppServiceName       DisplayString,
    tmnxLudbHostPppL2tpTunnelGroup   TmnxL2tpTunnelGroupNameOrEmpty,
    tmnxLudbHostPppL2tpSvcId         TmnxServId,
    tmnxLudbHostPppService           TmnxServId,
    tmnxLudbHostPppInterface         TNamedItemOrEmpty,
    tmnxLudbHostPppoePadoDelay       TmnxPppoePadoDelay
}

tmnxLudbHostType                 OBJECT-TYPE
    SYNTAX      TmnxLocUsrDbHostType
    MAX-ACCESS  not-accessible
    STATUS      current
    DESCRIPTION
        "The value of the object tmnxLudbHostType specifies the type of actual
         host this local user database host template is intended for."
    ::= { tmnxLudbHostEntry 1 }

tmnxLudbHostName                 OBJECT-TYPE
    SYNTAX      DisplayString (SIZE (1..32))
    MAX-ACCESS  not-accessible
    STATUS      current
    DESCRIPTION
        "The value of the object tmnxLudbHostName specifies the host name of
         this local user database host template."
    ::= { tmnxLudbHostEntry 2 }

tmnxLudbHostRowStatus            OBJECT-TYPE
    SYNTAX      RowStatus
    MAX-ACCESS  read-create
    STATUS      current
    DESCRIPTION
        "The value of the object tmnxLudbHostRowStatus specifies the row status
         of this entry."
    ::= { tmnxLudbHostEntry 3 }

tmnxLudbHostLastChangeTime       OBJECT-TYPE
    SYNTAX      TimeStamp
    MAX-ACCESS  read-only
    STATUS      current
    DESCRIPTION
        "The value of the object tmnxLudbHostLastChangeTime indicates the
         sysUpTime at the time of the last modification of this entry."
    ::= { tmnxLudbHostEntry 4 }

tmnxLudbHostApplications         OBJECT-TYPE
    SYNTAX      TmnxLocUsrDbHostApplications
    MAX-ACCESS  read-create
    STATUS      current
    DESCRIPTION
        "The value of the object tmnxLudbHostApplications specifies the types
         of actual host this local user database host template is intended for
         if it is a generic host template.

         The value of this object is not relevant unless the value of the
         object tmnxLudbHostType is equal to 'any'."
    ::= { tmnxLudbHostEntry 5 }

tmnxLudbHostAdminState           OBJECT-TYPE
    SYNTAX      TmnxAdminState
    MAX-ACCESS  read-create
    STATUS      current
    DESCRIPTION
        "The value of the object tmnxLudbHostAdminState specifies the
         administrative state of the tmnxLudbHostEntry."
    DEFVAL      { outOfService }
    ::= { tmnxLudbHostEntry 10 }

tmnxLudbHostMacAddress           OBJECT-TYPE
    SYNTAX      MacAddress
    MAX-ACCESS  read-create
    STATUS      current
    DESCRIPTION
        "The value of the object tmnxLudbHostMacAddress specifies the MAC
         address to match against.

         If the value of this object is set to all zeros, then it is not used."
    DEFVAL      { '000000000000'H }
    ::= { tmnxLudbHostEntry 11 }

tmnxLudbHostCircuitIdFmt         OBJECT-TYPE
    SYNTAX      TmnxLocUsrDbDataFormat
    MAX-ACCESS  read-create
    STATUS      current
    DESCRIPTION
        "The value of the object tmnxLudbHostCircuitIdFmt specifies how the
         value of tmnxLudbHostCircuitId must be formatted."
    DEFVAL      { ascii }
    ::= { tmnxLudbHostEntry 12 }

tmnxLudbHostCircuitId            OBJECT-TYPE
    SYNTAX      OCTET STRING (SIZE (0..127))
    MAX-ACCESS  read-create
    STATUS      current
    DESCRIPTION
        "The value of the object tmnxLudbHostCircuitId specifies the circuit Id
         to match against.

         If the value of this object is the empty string, then it is not used."
    DEFVAL      { ''H }
    ::= { tmnxLudbHostEntry 13 }

tmnxLudbHostRemoteIdFmt          OBJECT-TYPE
    SYNTAX      TmnxLocUsrDbDataFormat
    MAX-ACCESS  read-create
    STATUS      current
    DESCRIPTION
        "The value of the object tmnxLudbHostRemoteIdFmt specifies how the
         value of tmnxLudbHostRemoteIdFmt must be formatted."
    DEFVAL      { ascii }
    ::= { tmnxLudbHostEntry 14 }

tmnxLudbHostRemoteId             OBJECT-TYPE
    SYNTAX      OCTET STRING (SIZE (0..255))
    MAX-ACCESS  read-create
    STATUS      current
    DESCRIPTION
        "The value of the object tmnxLudbHostRemoteId specifies the remote Id
         to match against.

         If the value of this object is the empty string, then it is not used."
    DEFVAL      { "" }
    ::= { tmnxLudbHostEntry 15 }

tmnxLudbHostAddrType             OBJECT-TYPE
    SYNTAX      InetAddressType
    MAX-ACCESS  read-create
    STATUS      current
    DESCRIPTION
        "The value of the object tmnxLudbHostAddrType specifies the type of
         tmnxLudbHostAddress."
    DEFVAL      { unknown }
    ::= { tmnxLudbHostEntry 16 }

tmnxLudbHostAddress              OBJECT-TYPE
    SYNTAX      InetAddress (SIZE (0|4|16))
    MAX-ACCESS  read-create
    STATUS      current
    DESCRIPTION
        "The value of the object tmnxLudbHostAddress specifies the IP address
         of this host.

         This object can only be configured if object tmnxLudbHostPool contains
         the empty string and object tmnxLudbHostUseGiAddress is 'false(2)'."
    DEFVAL      { ''H }
    ::= { tmnxLudbHostEntry 17 }

tmnxLudbHostPool                 OBJECT-TYPE
    SYNTAX      TNamedItemOrEmpty
    MAX-ACCESS  read-create
    STATUS      current
    DESCRIPTION
        "The value of the object tmnxLudbHostPool specifies the IP address pool
         which is used to search for an IP address for this host.

         This object can only be configured if object tmnxLudbHostAddrType is
         'unknown(0)' and the values of the objects tmnxLudbHostUseGiAddress
         and tmnxLudbHostUseClientPool are 'false (2)'.

         This object is applicable if it is the local DHCP server that queries
         the local user database."
    DEFVAL      { "" }
    ::= { tmnxLudbHostEntry 18 }

tmnxLudbHostUseGiAddress         OBJECT-TYPE
    SYNTAX      TruthValue
    MAX-ACCESS  read-create
    STATUS      current
    DESCRIPTION
        "The value of the object tmnxLudbHostUseGiAddress specifies whether the
         GI address is used to search for an IP address for this host.

         If the value of this object is set to 'true(1)', then the Gateway IP
         address is used.

         This object can only be set to 'true(1)' when the value of
         tmnxLudbHostAddrType is 'unknown(0)' and tmnxLudbHostPool contains the
         empty string."
    DEFVAL      { false }
    ::= { tmnxLudbHostEntry 19 }

tmnxLudbHostIdStringOptNum       OBJECT-TYPE
    SYNTAX      Unsigned32 (0..254)
    MAX-ACCESS  read-create
    STATUS      current
    DESCRIPTION
        "The value of the object tmnxLudbHostIdStringOptNum specifies the
         option number that the DHCP server uses to send the identification
         strings.

         If the value of this object is 0, then no identification strings will
         be sent.

         This object is applicable if it is the local DHCP server that queries
         the local user database, regardless of the type of host template."
    DEFVAL      { 0 }
    ::= { tmnxLudbHostEntry 20 }

tmnxLudbHostSubscriberId         OBJECT-TYPE
    SYNTAX      TmnxSubIdentStringOrEmpty
    MAX-ACCESS  read-create
    STATUS      current
    DESCRIPTION
        "The value of the object tmnxLudbHostSubscriberId specifies the
         subscriber Id which is encoded in the identification strings."
    DEFVAL      { "" }
    ::= { tmnxLudbHostEntry 21 }

tmnxLudbHostSlaProfString        OBJECT-TYPE
    SYNTAX      TmnxSlaProfileStringOrEmpty
    MAX-ACCESS  read-create
    STATUS      current
    DESCRIPTION
        "The value of the object tmnxLudbHostSlaProfString specifies the SLA
         profile string which is encoded in the identification strings."
    DEFVAL      { "" }
    ::= { tmnxLudbHostEntry 22 }

tmnxLudbHostFltrProfString       OBJECT-TYPE
    SYNTAX      TmnxFilterProfileStringOrEmpty
    MAX-ACCESS  read-create
    STATUS      current
    DESCRIPTION
        "The value of the object tmnxLudbHostFltrProfString specifies the
         filter profile string which is encoded in the identification strings."
    DEFVAL      { "" }
    ::= { tmnxLudbHostEntry 23 }

tmnxLudbHostSubProfString        OBJECT-TYPE
    SYNTAX      TmnxSubProfileStringOrEmpty
    MAX-ACCESS  read-create
    STATUS      current
    DESCRIPTION
        "The value of the object tmnxLudbHostSubProfString specifies the
         subscriber profile string which is encoded in the identification
         strings."
    DEFVAL      { "" }
    ::= { tmnxLudbHostEntry 24 }

tmnxLudbHostAppProfString        OBJECT-TYPE
    SYNTAX      DisplayString (SIZE (0..16))
    MAX-ACCESS  read-create
    STATUS      current
    DESCRIPTION
        "The value of the object tmnxLudbHostAppProfString specifies the
         application profile string which is encoded in the identification
         strings."
    DEFVAL      { "" }
    ::= { tmnxLudbHostEntry 25 }

tmnxLudbHostAncpString           OBJECT-TYPE
    SYNTAX      TmnxAncpStringOrZero
    MAX-ACCESS  read-create
    STATUS      current
    DESCRIPTION
        "The value of the object tmnxLudbHostAncpString specifies the ANCP
         string which is encoded in the identification strings."
    DEFVAL      { "" }
    ::= { tmnxLudbHostEntry 26 }

tmnxLudbHostInterDestId          OBJECT-TYPE
    SYNTAX      TNamedItemOrEmpty
    MAX-ACCESS  read-create
    STATUS      current
    DESCRIPTION
        "The value of the object tmnxLudbHostInterDestId specifies the
         intermediate destination identifier which is encoded in the
         identification strings."
    DEFVAL      { "" }
    ::= { tmnxLudbHostEntry 27 }

tmnxLudbHostUseClientPool        OBJECT-TYPE
    SYNTAX      TruthValue
    MAX-ACCESS  read-create
    STATUS      current
    DESCRIPTION
        "The value of the object tmnxLudbHostUseClientPool specifies if the IP
         address pool used to search for an IP address for this host is to be
         indicated by the vendor-specific sub-option 13 of the DHCP option 82.

         If the value of this object is set to 'true (1)', the IP address pool
         indicated by the sub-option 13 is used.

         This object can only be set to 'true (1)' when the value of
         tmnxLudbHostAddrType is 'unknown (0)' and tmnxLudbHostPool contains
         the empty string."
    DEFVAL      { false }
    ::= { tmnxLudbHostEntry 28 }

tmnxLudbHostAuthPolicy           OBJECT-TYPE
    SYNTAX      TNamedItemOrEmpty
    MAX-ACCESS  read-create
    STATUS      current
    DESCRIPTION
        "The value of the object tmnxLudbHostAuthPolicy specifies the RADIUS
         authentication policy to use to authenticate the host."
    DEFVAL      { "" }
    ::= { tmnxLudbHostEntry 29 }

tmnxLudbHostRetailerSvcId        OBJECT-TYPE
    SYNTAX      TmnxServId
    MAX-ACCESS  read-create
    STATUS      current
    DESCRIPTION
        "The value of the object tmnxLudbHostRetailerSvcId specifies the
         retailer service Id for this host.

         This object is deprecated; please use
         tmnxLudbDhcp2RetailerServiceName."
    DEFVAL      { 0 }
    ::= { tmnxLudbHostEntry 30 }

tmnxLudbHostCategoryMapName      OBJECT-TYPE
    SYNTAX      TNamedItemOrEmpty
    MAX-ACCESS  read-create
    STATUS      current
    DESCRIPTION
        "The value of the object tmnxLudbHostCategoryMapName specifies the name
         of the category map used when credit control is active for this host."
    DEFVAL      { "" }
    ::= { tmnxLudbHostEntry 31 }

tmnxLudbHostDefMsapPolicy        OBJECT-TYPE
    SYNTAX      TPolicyStatementNameOrEmpty
    MAX-ACCESS  read-create
    STATUS      current
    DESCRIPTION
        "The value of the object tmnxLudbHostDefMsapPolicy specifies the
         default Managed SAP policy to use to create Managed SAPs.

         While the values of both this object and sapTlsDefMsapPolicy are
         empty, no Managed SAPs are created.

         This object is applicable in case of RADIUS fallback."
    DEFVAL      { "" }
    ::= { tmnxLudbHostEntry 32 }

tmnxLudbHostDefMsapService       OBJECT-TYPE
    SYNTAX      TmnxServId
    MAX-ACCESS  read-create
    STATUS      current
    DESCRIPTION
        "The value of the object tmnxLudbHostDefMsapService specifies the
         service ID of the service where Managed SAPs are created.

         While the values of both this object and sapTlsDefMsapService are
         equal to zero, no Managed SAPs are created.

         This object is applicable in case of RADIUS fallback."
    DEFVAL      { 0 }
    ::= { tmnxLudbHostEntry 33 }

tmnxLudbHostDefMsapGroupIf       OBJECT-TYPE
    SYNTAX      TNamedItemOrEmpty
    MAX-ACCESS  read-create
    STATUS      current
    DESCRIPTION
        "The value of the object tmnxLudbHostDefMsapGroupIf specifies the name
         of the group interface where Managed SAPs are created.

         While the values of both this object and sapTlsDefMsapGroupIf are
         empty, no Managed SAPs are created.

         This object is applicable in case of RADIUS fallback."
    DEFVAL      { "" }
    ::= { tmnxLudbHostEntry 34 }

tmnxLudbHostSystemId             OBJECT-TYPE
    SYNTAX      DisplayString (SIZE (0..255))
    MAX-ACCESS  read-create
    STATUS      current
    DESCRIPTION
        "The value of the object tmnxLudbHostSystemId specifies the system Id
         from the Nokia vendor specific sub-option in option 82 to match
         against.

         If the value of this object is the empty string, then it is not used."
    DEFVAL      { "" }
    ::= { tmnxLudbHostEntry 35 }

tmnxLudbHostServiceId            OBJECT-TYPE
    SYNTAX      TmnxServId
    MAX-ACCESS  read-create
    STATUS      current
    DESCRIPTION
        "The value of the object tmnxLudbHostServiceId specifies the service ID
         to match against.

         If it is the local DHCP server that queries the local user database,
         it uses the Nokia vendor specific sub-option in option 82.

         If the value of this object is 0, then it is not used."
    DEFVAL      { 0 }
    ::= { tmnxLudbHostEntry 36 }

tmnxLudbHostSapId                OBJECT-TYPE
    SYNTAX      DisplayString (SIZE (0..255))
    MAX-ACCESS  read-create
    STATUS      current
    DESCRIPTION
        "The value of the object tmnxLudbHostSapId specifies the SAP ID to
         match against.

         If it is the local DHCP server that queries the local user database,
         it uses the Nokia vendor specific sub-option in option 82.

         If the value of this object is the empty string, then it is not used."
    DEFVAL      { "" }
    ::= { tmnxLudbHostEntry 37 }

tmnxLudbHostString               OBJECT-TYPE
    SYNTAX      DisplayString (SIZE (0..255))
    MAX-ACCESS  read-create
    STATUS      current
    DESCRIPTION
        "The value of the object tmnxLudbHostString specifies the string to
         match against.

         If it is the local DHCP server that queries the local user database,
         it uses the Nokia vendor specific sub-option in option 82.

         If the value of this object is the empty string, then it is not used."
    DEFVAL      { "" }
    ::= { tmnxLudbHostEntry 38 }

tmnxLudbHostIpv6Addr             OBJECT-TYPE
    SYNTAX      InetAddress (SIZE (0|16))
    MAX-ACCESS  read-create
    STATUS      current
    DESCRIPTION
        "The value of the object tmnxLudbHostIpv6Addr specifies the IPv6
         address to assign to the hosts of this local user database host
         template."
    DEFVAL      { ''H }
    ::= { tmnxLudbHostEntry 39 }

tmnxLudbHostIpv6Pfx              OBJECT-TYPE
    SYNTAX      InetAddress (SIZE (0|16))
    MAX-ACCESS  read-create
    STATUS      current
    DESCRIPTION
        "The value of the object tmnxLudbHostIpv6Pfx specifies the IPv6 prefix
         to assign to the hosts of this local user database host template."
    DEFVAL      { ''H }
    ::= { tmnxLudbHostEntry 40 }

tmnxLudbHostIpv6PfxLen           OBJECT-TYPE
    SYNTAX      InetAddressPrefixLength (0 | 48..64)
    MAX-ACCESS  read-create
    STATUS      current
    DESCRIPTION
        "The value of the object tmnxLudbHostIpv6PfxLen specifies the IPv6
         prefix length to assign to the hosts of this local user database host
         template.

         The value zero means that the IPv6 prefix is not configured."
    ::= { tmnxLudbHostEntry 41 }

tmnxLudbHostAuthDomainName       OBJECT-TYPE
    SYNTAX      DisplayString (SIZE (0..32))
    MAX-ACCESS  read-create
    STATUS      current
    DESCRIPTION
        "The value of the object tmnxLudbHostAuthDomainName specifies the
         domain name to use when RADIUS authentication is applicable."
    DEFVAL      { "" }
    ::= { tmnxLudbHostEntry 42 }

tmnxLudbHostDhcpOption60Fmt      OBJECT-TYPE
    SYNTAX      TmnxLudbDataFormat
    MAX-ACCESS  read-create
    STATUS      current
    DESCRIPTION
        "The value of the object tmnxLudbHostDhcpOption60Fmt specifies how the
         value of the value of tmnxLudbHostDhcpOption60 must be formatted."
    DEFVAL      { hex }
    ::= { tmnxLudbHostEntry 100 }

tmnxLudbHostDhcpOption60         OBJECT-TYPE
    SYNTAX      OCTET STRING (SIZE (0..32))
    MAX-ACCESS  read-create
    STATUS      current
    DESCRIPTION
        "The value of the object tmnxLudbHostDhcpOption60 specifies the
         Vendor-Identifying Vendor Option to match against. Option 60 is
         encoded as Type - Length - Value. The Value portion of Option 60 in
         the received DHCP request is used to match against
         tmnxLudbHostDhcpOption60.

         If the value of this object is the empty string, then it is not used."
    REFERENCE
        "RFC 3925"
    DEFVAL      { "" }
    ::= { tmnxLudbHostEntry 101 }

tmnxLudbHostDhcpRelayAddrType    OBJECT-TYPE
    SYNTAX      InetAddressType
    MAX-ACCESS  read-create
    STATUS      current
    DESCRIPTION
        "The value of the object tmnxLudbHostDhcpRelayAddrType specifies the
         type of tmnxLudbHostDhcpRelayAddress."
    DEFVAL      { unknown }
    ::= { tmnxLudbHostEntry 102 }

tmnxLudbHostDhcpRelayAddress     OBJECT-TYPE
    SYNTAX      InetAddress (SIZE (0|4|16))
    MAX-ACCESS  read-create
    STATUS      current
    DESCRIPTION
        "The value of the object tmnxLudbHostDhcpRelayAddress specifies the
         address of the DHCP server to relay to."
    DEFVAL      { ''H }
    ::= { tmnxLudbHostEntry 103 }

tmnxLudbHostPppUserNameFormat    OBJECT-TYPE
    SYNTAX      TmnxLocUsrDbUserNameFormat
    MAX-ACCESS  read-create
    STATUS      current
    DESCRIPTION
        "The value of the object tmnxLudbHostPppUserNameFormat specifies the
         format of tmnxLudbHostPppUserName."
    DEFVAL      { none }
    ::= { tmnxLudbHostEntry 200 }

tmnxLudbHostPppUserName          OBJECT-TYPE
    SYNTAX      TmnxPppoeUserNameOrEmpty
    MAX-ACCESS  read-create
    STATUS      current
    DESCRIPTION
        "The value of the object tmnxLudbHostPppUserName specifies the PPPoE
         username to match against.

         If the value of this object is the empty string, then it is not used.
         In that case, tmnxLudbHostPppUserNameFormat must be 'none (0)'."
    DEFVAL      { "" }
    ::= { tmnxLudbHostEntry 201 }

tmnxLudbHostPppPasswordType      OBJECT-TYPE
    SYNTAX      TmnxLocUsrDbPasswordType
    MAX-ACCESS  read-create
    STATUS      current
    DESCRIPTION
        "The value of the object tmnxLudbHostPppPasswordType specifies the type
         of tmnxLudbHostPppPassword."
    DEFVAL      { none }
    ::= { tmnxLudbHostEntry 202 }

tmnxLudbHostPppPassword          OBJECT-TYPE
    SYNTAX      DisplayString (SIZE (0..64))
    MAX-ACCESS  read-create
    STATUS      current
    DESCRIPTION
        "The value of the object tmnxLudbHostPppPassword specifies the password
         of this host.

         This object can only be set if tmnxLudbHostPppUserName is not an empty
         string.

         If the value of this object is not an empty string, then the value of
         tmnxLudbHostPppPasswordType must be either 'pap(2)' or 'chap(3)'.

         This object will always return an empty string on a read."
    DEFVAL      { ''H }
    ::= { tmnxLudbHostEntry 203 }

tmnxLudbHostPppServiceName       OBJECT-TYPE
    SYNTAX      DisplayString (SIZE (0..255))
    MAX-ACCESS  read-create
    STATUS      current
    DESCRIPTION
        "The value of the object tmnxLudbHostPppServiceName specifies the PPPoE
         service name to match against.

         If the value of this object is the empty string, then it is not used."
    DEFVAL      { "" }
    ::= { tmnxLudbHostEntry 204 }

tmnxLudbHostPppL2tpTunnelGroup   OBJECT-TYPE
    SYNTAX      TmnxL2tpTunnelGroupNameOrEmpty
    MAX-ACCESS  read-create
    STATUS      current
    DESCRIPTION
        "The value of the object tmnxLudbHostPppL2tpTunnelGroup specifies the
         tunnel group to use to setup an L2TP tunnel/session.

         If the value of this object is the empty string, no L2TP tunneling
         will be done."
    DEFVAL      { "" }
    ::= { tmnxLudbHostEntry 205 }

tmnxLudbHostPppL2tpSvcId         OBJECT-TYPE
    SYNTAX      TmnxServId
    MAX-ACCESS  read-create
    STATUS      current
    DESCRIPTION
        "The value of the object tmnxLudbHostPppL2tpSvcId specifies the service
         ID of the service from where to take the tunnel group
         (tmnxLudbHostPppL2tpTunnelGroup) to use to setup an L2TP LAC
         tunnel/session.

         If the value of this object is 0, L2TP tunneling will be done from the
         base router context."
    DEFVAL      { 0 }
    ::= { tmnxLudbHostEntry 206 }

tmnxLudbHostPppService           OBJECT-TYPE
    SYNTAX      TmnxServId
    MAX-ACCESS  read-create
    STATUS      current
    DESCRIPTION
        "The value of the object tmnxLudbHostPppService specifies the service
         ID of the service where the PPP sessions are established."
    DEFVAL      { 0 }
    ::= { tmnxLudbHostEntry 207 }

tmnxLudbHostPppInterface         OBJECT-TYPE
    SYNTAX      TNamedItemOrEmpty
    MAX-ACCESS  read-create
    STATUS      current
    DESCRIPTION
        "The value of the object tmnxLudbHostPppInterface specifies the name of
         the group interface where the PPP sessions are established"
    DEFVAL      { "" }
    ::= { tmnxLudbHostEntry 208 }

tmnxLudbHostPppoePadoDelay       OBJECT-TYPE
    SYNTAX      TmnxPppoePadoDelay
    UNITS       "deciseconds"
    MAX-ACCESS  read-create
    STATUS      current
    DESCRIPTION
        "The value of the object tmnxLudbHostPppoePadoDelay specifies the delay
         timeout before sending a PADO (PPPoE Active Discovery Offer)."
    DEFVAL      { 0 }
    ::= { tmnxLudbHostEntry 290 }

tmnxLudbPppAleTableLastChange    OBJECT-TYPE
    SYNTAX      TimeStamp
    MAX-ACCESS  read-only
    STATUS      current
    DESCRIPTION
        "The value of the object tmnxLudbPppAleTableLastChange indicates the
         value of sysUpTime at the time of the last modification of an entry in
         the tmnxLudbPppAleTable."
    ::= { tmnxLocalUserDbObjs 22 }

tmnxLudbPppAleTable              OBJECT-TYPE
    SYNTAX      SEQUENCE OF TmnxLudbPppAleEntry
    MAX-ACCESS  not-accessible
    STATUS      current
    DESCRIPTION
        "The table tmnxLudbPppAleTable contains objects to configure
         information related to the Access Loop Encapsulation of PPP hosts."
    ::= { tmnxLocalUserDbObjs 23 }

tmnxLudbPppAleEntry              OBJECT-TYPE
    SYNTAX      TmnxLudbPppAleEntry
    MAX-ACCESS  not-accessible
    STATUS      current
    DESCRIPTION
        "Each row represents a template for PPP hosts.

         Rows in this table can be created or deleted via SNMP operations.

         A row in this table can only be created while a row exists in the
         tmnxLocUsrDbPppoeTable with the same index."
    INDEX       {
        tmnxLocUsrDbUserDatabaseName,
        tmnxLocUsrDbPppoeHostName
    }
    ::= { tmnxLudbPppAleTable 1 }

TmnxLudbPppAleEntry              ::= SEQUENCE
{
    tmnxLudbPppAleRowStatus          RowStatus,
    tmnxLudbPppAleLastChangeTime     TimeStamp,
    tmnxLudbPppAleEncapOffsetMode    TmnxSubAleOffsetMode,
    tmnxLudbPppAleEncapOffset        TmnxSubAleOffset,
    tmnxLudbPppAleRateDown           Unsigned32
}

tmnxLudbPppAleRowStatus          OBJECT-TYPE
    SYNTAX      RowStatus
    MAX-ACCESS  read-create
    STATUS      current
    DESCRIPTION
        "The value of the object tmnxLudbPppAleRowStatus specifies the row
         status of this entry."
    ::= { tmnxLudbPppAleEntry 1 }

tmnxLudbPppAleLastChangeTime     OBJECT-TYPE
    SYNTAX      TimeStamp
    MAX-ACCESS  read-only
    STATUS      current
    DESCRIPTION
        "The value of the object tmnxLudbPppAleLastChangeTime indicates the
         sysUpTime at the time of the last modification of this entry."
    ::= { tmnxLudbPppAleEntry 2 }

tmnxLudbPppAleEncapOffsetMode    OBJECT-TYPE
    SYNTAX      TmnxSubAleOffsetMode
    MAX-ACCESS  read-create
    STATUS      current
    DESCRIPTION
        "The value of tmnxLudbPppAleEncapOffsetMode specifies how the fixed
         packet offset will be derived.

         The tmnxLudbPppAleEncapOffset is used to convey the information about
         the Access Loop Encapsulation type for this host.

         The value 'none (0)' specifies that no adjustments are configured in
         this template.

         The value 'auto (1)' specifies that the adjustments be done according
         to the value of the object tmnxLudbPppAleEncapOffset."
    DEFVAL      { none }
    ::= { tmnxLudbPppAleEntry 3 }

tmnxLudbPppAleEncapOffset        OBJECT-TYPE
    SYNTAX      TmnxSubAleOffset
    MAX-ACCESS  read-create
    STATUS      current
    DESCRIPTION
        "The value of tmnxLudbPppAleEncapOffset specifies the fixed packet
         offset.

         The tmnxLudbPppAleEncapOffset is used to convey the information about
         the Access Loop Encapsulation type for this host.

         If the value of the object tmnxLudbPppAleEncapOffsetMode is equal to
         'none', the offset is ignored.

         If the value of the object tmnxLudbPppAleEncapOffsetMode is equal to
         'auto', the offset is used."
    DEFVAL      { none }
    ::= { tmnxLudbPppAleEntry 4 }

tmnxLudbPppAleRateDown           OBJECT-TYPE
    SYNTAX      Unsigned32 (0..100000)
    UNITS       "kilobps"
    MAX-ACCESS  read-create
    STATUS      current
    DESCRIPTION
        "The value of tmnxLudbPppAleRateDown specifies the last mile link
         downstream rate needed for proper (shaping) rate calculations and
         interleaving delay in the access loop.

         The value zero means that no speed is configured in this template."
    DEFVAL      { 0 }
    ::= { tmnxLudbPppAleEntry 6 }

tmnxLudbRadproxCacheTableLastCh  OBJECT-TYPE
    SYNTAX      TimeStamp
    MAX-ACCESS  read-only
    STATUS      current
    DESCRIPTION
        "The value of the object tmnxLudbRadproxCacheTableLastCh indicates the
         value of sysUpTime at the time of the last modification of an entry in
         the tmnxLudbRadproxCacheTable."
    ::= { tmnxLocalUserDbObjs 24 }

tmnxLudbRadproxCacheTable        OBJECT-TYPE
    SYNTAX      SEQUENCE OF TmnxLudbRadproxCacheEntry
    MAX-ACCESS  not-accessible
    STATUS      current
    DESCRIPTION
        "The table tmnxLudbRadproxCacheTable contains objects to configure
         information related to the RADIUS Proxy cache for DHCP hosts."
    ::= { tmnxLocalUserDbObjs 25 }

tmnxLudbRadproxCacheEntry        OBJECT-TYPE
    SYNTAX      TmnxLudbRadproxCacheEntry
    MAX-ACCESS  not-accessible
    STATUS      current
    DESCRIPTION
        "Each row represents RADIUS Proxy cache information for a specific
         host.

         A row in this table is present for each row in the
         tmnxLocUsrDbDhcpTable."
    AUGMENTS    { tmnxLocUsrDbDhcpEntry }
    ::= { tmnxLudbRadproxCacheTable 1 }

TmnxLudbRadproxCacheEntry        ::= SEQUENCE
{
    tmnxLudbRadproxCacheLastCh       TimeStamp,
    tmnxLudbRadproxCacheService      TmnxServId,
    tmnxLudbRadproxCacheServer       TNamedItemOrEmpty,
    tmnxLudbRadproxCacheMatchType    INTEGER,
    tmnxLudbRadproxCacheMatchOption  Unsigned32,
    tmnxLudbRadproxCacheFailAction   INTEGER,
    tmnxLudbRadproxCacheMacFormat    TmnxMacSpecification,
    tmnxLudbRadproxCacheMatchOption6 Unsigned32,
    tmnxLudbRadproxCacheServiceName  TLNamedItemOrEmpty
}

tmnxLudbRadproxCacheLastCh       OBJECT-TYPE
    SYNTAX      TimeStamp
    MAX-ACCESS  read-only
    STATUS      current
    DESCRIPTION
        "The value of the object tmnxLudbRadproxCacheLastCh indicates the
         sysUpTime at the time of the last modification of this entry."
    ::= { tmnxLudbRadproxCacheEntry 1 }

tmnxLudbRadproxCacheService      OBJECT-TYPE
    SYNTAX      TmnxServId
    MAX-ACCESS  read-create
    STATUS      current
    DESCRIPTION
        "The value of tmnxLudbRadproxCacheService specifies the VPRN service
         instance ID of the RADIUS Proxy server whose cache this row is
         referring to.

         This object is deprecated. Please use tmnxLudbRadproxCacheServiceName
         instead.

         The value zero means either
         - that the RADIUS Proxy server is not specified
          (tmnxLudbRadproxCacheServer is empty), or
         - that the RADIUS Proxy server is in the Base router instance
          (tmnxLudbRadproxCacheServer not empty)."
    DEFVAL      { 0 }
    ::= { tmnxLudbRadproxCacheEntry 2 }

tmnxLudbRadproxCacheServer       OBJECT-TYPE
    SYNTAX      TNamedItemOrEmpty
    MAX-ACCESS  read-create
    STATUS      current
    DESCRIPTION
        "The value of tmnxLudbRadproxCacheServer specifies the RADIUS Proxy
         server whose cache this row is referring to."
    DEFVAL      { "" }
    ::= { tmnxLudbRadproxCacheEntry 3 }

tmnxLudbRadproxCacheMatchType    OBJECT-TYPE
    SYNTAX      INTEGER {
        mac       (1),
        circuitId (2),
        remoteId  (3),
        option    (4)
    }
    MAX-ACCESS  read-create
    STATUS      current
    DESCRIPTION
        "The value of tmnxLudbRadproxCacheMatchType specifies how to find a
         match for a DHCP host in the cache of a RADIUS Proxy server.

         If the value of tmnxLudbRadproxCacheMatchType is equal to 'mac', the
         MAC address of the DHCP host is used as lookup key in the RADIUS Proxy
         cache.

         If the value of tmnxLudbRadproxCacheMatchType is equal to 'circuitId',
         the option-82 circuit-id sub-option of the DHCP host is used as lookup
         key in the RADIUS Proxy cache.

         If the value of tmnxLudbRadproxCacheMatchType is equal to 'remoteId',
         the option-82 remote-id sub-option of the DHCP host is used as lookup
         key in the RADIUS Proxy cache.

         If the value of tmnxLudbRadproxCacheMatchType is equal to 'option',
         the value of the object tmnxLudbRadproxCacheMatchOption or
         tmnxLudbRadproxCacheMatchOption6 is used as a lookup key in the RADIUS
         Proxy cache.

         In all cases, the cache in the corresponding RADIUS Proxy server must
         be configured accordingly."
    DEFVAL      { mac }
    ::= { tmnxLudbRadproxCacheEntry 4 }

tmnxLudbRadproxCacheMatchOption  OBJECT-TYPE
    SYNTAX      Unsigned32 (0 | 1..254)
    MAX-ACCESS  read-create
    STATUS      current
    DESCRIPTION
        "The value of tmnxLudbRadproxCacheMatchOption specifies in what DHCP
         option to retrieve the value to be used as lookup key in the RADIUS
         Proxy cache.

         The value of tmnxLudbRadproxCacheMatchOption is only relevant if the
         value of tmnxLudbRadproxCacheMatchType is equal to 'option'.

         The value zero means that this object is not configured."
    DEFVAL      { 0 }
    ::= { tmnxLudbRadproxCacheEntry 5 }

tmnxLudbRadproxCacheFailAction   OBJECT-TYPE
    SYNTAX      INTEGER {
        continue (1),
        drop     (2)
    }
    MAX-ACCESS  read-create
    STATUS      current
    DESCRIPTION
        "The value of tmnxLudbRadproxCacheFailAction specifies the action to
         take when no match is found in the cache."
    DEFVAL      { drop }
    ::= { tmnxLudbRadproxCacheEntry 6 }

tmnxLudbRadproxCacheMacFormat    OBJECT-TYPE
    SYNTAX      TmnxMacSpecification (SIZE (2..7))
    MAX-ACCESS  read-create
    STATUS      current
    DESCRIPTION
        "The value of tmnxLudbRadproxCacheMacFormat specifies how a MAC address
         is represented.

         This is only used while the value of tmnxLudbRadproxCacheMatchType is
         equal to 'mac'.

         Examples:

         'ab:'               00:0c:f1:99:85:b8  Nokia SROS style
         'XY-'               00-0C-F1-99-85-B8  IEEE canonical style
         'mmmm.'             0002.03aa.abff     Cisco style."
    DEFVAL      { "aa:" }
    ::= { tmnxLudbRadproxCacheEntry 7 }

tmnxLudbRadproxCacheMatchOption6 OBJECT-TYPE
    SYNTAX      Unsigned32 (0 | 1..65535)
    MAX-ACCESS  read-create
    STATUS      current
    DESCRIPTION
        "The value of tmnxLudbRadproxCacheMatchOption6 specifies in what DHCPv6
         option to retrieve the value to be used as lookup key in the RADIUS
         Proxy cache.

         The value of tmnxLudbRadproxCacheMatchOption6 is only relevant if the
         value of tmnxLudbRadproxCacheMatchType is equal to 'option'.

         The value zero means that this object is not configured."
    DEFVAL      { 0 }
    ::= { tmnxLudbRadproxCacheEntry 9 }

tmnxLudbRadproxCacheServiceName  OBJECT-TYPE
    SYNTAX      TLNamedItemOrEmpty
    MAX-ACCESS  read-create
    STATUS      current
    DESCRIPTION
        "The value of tmnxLudbRadproxCacheServiceName specifies the name of the
         VPRN service of the RADIUS Proxy server whose cache this row is
         referring to.

         An empty value means either
         - that the RADIUS Proxy server is not specified
          (tmnxLudbRadproxCacheServer is empty), or
         - that the RADIUS Proxy server is in the Base router instance
          (tmnxLudbRadproxCacheServer not empty)."
    DEFVAL      { "" }
    ::= { tmnxLudbRadproxCacheEntry 10 }

tmnxLocUsrDbDhcpOption6TblLstCh  OBJECT-TYPE
    SYNTAX      TimeStamp
    MAX-ACCESS  read-only
    STATUS      current
    DESCRIPTION
        "The value of the object tmnxLocUsrDbDhcpOption6TblLstCh indicates the
         value of sysUpTime at the time of the last modification of an entry in
         the tmnxLocUsrDbDhcpOption6Table."
    ::= { tmnxLocalUserDbObjs 26 }

tmnxLocUsrDbDhcpOption6Table     OBJECT-TYPE
    SYNTAX      SEQUENCE OF TmnxLocUsrDbDhcpOption6Entry
    MAX-ACCESS  not-accessible
    STATUS      current
    DESCRIPTION
        "The table tmnxLocUsrDbDhcpOption6Table contains objects to configure
         the DHCP6 options of each DHCP host."
    ::= { tmnxLocalUserDbObjs 27 }

tmnxLocUsrDbDhcpOption6Entry     OBJECT-TYPE
    SYNTAX      TmnxLocUsrDbDhcpOption6Entry
    MAX-ACCESS  not-accessible
    STATUS      current
    DESCRIPTION
        "Each row represents a DHCP6 option that is encoded in the DHCP reply
         message of this DHCP host.

         Entries in this table can be created or deleted via SNMP operations."
    INDEX       {
        tmnxLocUsrDbUserDatabaseName,
        tmnxLocUsrDbDhcpHostName,
        tmnxLocUsrDbDhcpOption6Number
    }
    ::= { tmnxLocUsrDbDhcpOption6Table 1 }

TmnxLocUsrDbDhcpOption6Entry     ::= SEQUENCE
{
    tmnxLocUsrDbDhcpOption6Number    Unsigned32,
    tmnxLocUsrDbDhcpOption6RowStatus RowStatus,
    tmnxLocUsrDbDhcpOption6LstChngTm TimeStamp,
    tmnxLocUsrDbDhcpOption6Type      TmnxDhcpOptionType,
    tmnxLocUsrDbDhcpOption6Value     OCTET STRING,
    tmnxLocUsrDbDhcpOption6Display   TmnxDhcpOptionDisplay
}

tmnxLocUsrDbDhcpOption6Number    OBJECT-TYPE
    SYNTAX      Unsigned32 (1..254)
    MAX-ACCESS  not-accessible
    STATUS      current
    DESCRIPTION
        "The value of the object tmnxLocUsrDbDhcpOption6Number specifies the
         number of this DHCP option."
    REFERENCE
        "RFC 2132"
    ::= { tmnxLocUsrDbDhcpOption6Entry 1 }

tmnxLocUsrDbDhcpOption6RowStatus OBJECT-TYPE
    SYNTAX      RowStatus
    MAX-ACCESS  read-create
    STATUS      current
    DESCRIPTION
        "The value of the object tmnxLocUsrDbDhcpOption6RowStatus specifies the
         row status of this row.

         Objects tmnxLocUsrDbDhcpOption6Type and tmnxLocUsrDbDhcpOption6Value
         must be set when creating a new row."
    ::= { tmnxLocUsrDbDhcpOption6Entry 2 }

tmnxLocUsrDbDhcpOption6LstChngTm OBJECT-TYPE
    SYNTAX      TimeStamp
    MAX-ACCESS  read-only
    STATUS      current
    DESCRIPTION
        "The value of the object tmnxLocUsrDbDhcpOption6LstChngTm indicates the
         sysUpTime at the time of the last modification of this entry."
    ::= { tmnxLocUsrDbDhcpOption6Entry 3 }

tmnxLocUsrDbDhcpOption6Type      OBJECT-TYPE
    SYNTAX      TmnxDhcpOptionType
    MAX-ACCESS  read-create
    STATUS      current
    DESCRIPTION
        "The value of the object tmnxLocUsrDbDhcpOption6Type specifies how the
         value of this option in stored in tmnxLocUsrDbDhcpOption6Value.

         This object is mandatory at creation time."
    ::= { tmnxLocUsrDbDhcpOption6Entry 4 }

tmnxLocUsrDbDhcpOption6Value     OBJECT-TYPE
    SYNTAX      OCTET STRING (SIZE (0..127))
    MAX-ACCESS  read-create
    STATUS      current
    DESCRIPTION
        "The value of the object tmnxLocUsrDbDhcpOption6Value specifies the
         value of this option.

         This object is mandatory at creation time. A zero length value is only
         allowed when the value of tmnxLocUsrDbDhcpOption6Type is 'hex (3)'."
    ::= { tmnxLocUsrDbDhcpOption6Entry 5 }

tmnxLocUsrDbDhcpOption6Display   OBJECT-TYPE
    SYNTAX      TmnxDhcpOptionDisplay
    MAX-ACCESS  read-only
    STATUS      current
    DESCRIPTION
        "The value of the object tmnxLocUsrDbDhcpOption6Display indicates a
         hint of how the tmnxLocUsrDbDhcpOption6Value can be displayed."
    ::= { tmnxLocUsrDbDhcpOption6Entry 6 }

tmnxLocUsrDbPppOption6TblLstCh   OBJECT-TYPE
    SYNTAX      TimeStamp
    MAX-ACCESS  read-only
    STATUS      current
    DESCRIPTION
        "The value of the object tmnxLocUsrDbPppOption6TblLstCh indicates the
         value of sysUpTime at the time of the last modification of an entry in
         the tmnxLocUsrDbPppOption6Table."
    ::= { tmnxLocalUserDbObjs 28 }

tmnxLocUsrDbPppOption6Table      OBJECT-TYPE
    SYNTAX      SEQUENCE OF TmnxLocUsrDbPppOption6Entry
    MAX-ACCESS  not-accessible
    STATUS      current
    DESCRIPTION
        "The table tmnxLocUsrDbPppOption6Table contains objects to configure
         the DHCP6 options of each PPPoE host."
    ::= { tmnxLocalUserDbObjs 29 }

tmnxLocUsrDbPppOption6Entry      OBJECT-TYPE
    SYNTAX      TmnxLocUsrDbPppOption6Entry
    MAX-ACCESS  not-accessible
    STATUS      current
    DESCRIPTION
        "Each row represents a DHCP6 option that is encoded in the DHCP reply
         message of this PPPoE host.

         Entries in this table can be created or deleted via SNMP operations."
    INDEX       {
        tmnxLocUsrDbUserDatabaseName,
        tmnxLocUsrDbPppoeHostName,
        tmnxLocUsrDbPppOption6Number
    }
    ::= { tmnxLocUsrDbPppOption6Table 1 }

TmnxLocUsrDbPppOption6Entry      ::= SEQUENCE
{
    tmnxLocUsrDbPppOption6Number     Unsigned32,
    tmnxLocUsrDbPppOption6RowSts     RowStatus,
    tmnxLocUsrDbPppOption6LstChgTm   TimeStamp,
    tmnxLocUsrDbPppOption6Type       TmnxDhcpOptionType,
    tmnxLocUsrDbPppOption6Value      OCTET STRING,
    tmnxLocUsrDbPppOption6Display    TmnxDhcpOptionDisplay
}

tmnxLocUsrDbPppOption6Number     OBJECT-TYPE
    SYNTAX      Unsigned32 (1..254)
    MAX-ACCESS  not-accessible
    STATUS      current
    DESCRIPTION
        "The value of the object tmnxLocUsrDbPppOption6Number specifies the
         number of this DHCP option."
    REFERENCE
        "RFC 2132"
    ::= { tmnxLocUsrDbPppOption6Entry 1 }

tmnxLocUsrDbPppOption6RowSts     OBJECT-TYPE
    SYNTAX      RowStatus
    MAX-ACCESS  read-create
    STATUS      current
    DESCRIPTION
        "The value of the object tmnxLocUsrDbPppOption6RowSts specifies the row
         status of this row.

         Objects tmnxLocUsrDbPppOption6Type and tmnxLocUsrDbPppOption6Value
         must be set when creating a new row."
    ::= { tmnxLocUsrDbPppOption6Entry 2 }

tmnxLocUsrDbPppOption6LstChgTm   OBJECT-TYPE
    SYNTAX      TimeStamp
    MAX-ACCESS  read-only
    STATUS      current
    DESCRIPTION
        "The value of the object tmnxLocUsrDbPppOption6LstChgTm indicates the
         sysUpTime at the time of the last modification of this entry."
    ::= { tmnxLocUsrDbPppOption6Entry 3 }

tmnxLocUsrDbPppOption6Type       OBJECT-TYPE
    SYNTAX      TmnxDhcpOptionType
    MAX-ACCESS  read-create
    STATUS      current
    DESCRIPTION
        "The value of the object tmnxLocUsrDbPppOption6Type specifies how the
         value of this option in stored in tmnxLocUsrDbPppOption6Value.

         This object is mandatory at creation time."
    ::= { tmnxLocUsrDbPppOption6Entry 4 }

tmnxLocUsrDbPppOption6Value      OBJECT-TYPE
    SYNTAX      OCTET STRING (SIZE (0..127))
    MAX-ACCESS  read-create
    STATUS      current
    DESCRIPTION
        "The value of the object tmnxLocUsrDbPppOption6Value specifies the
         value of this option.

         This object is mandatory at creation time. A zero length value is only
         allowed when the value of tmnxLocUsrDbPppOption6Type is 'hex (3)'."
    ::= { tmnxLocUsrDbPppOption6Entry 5 }

tmnxLocUsrDbPppOption6Display    OBJECT-TYPE
    SYNTAX      TmnxDhcpOptionDisplay
    MAX-ACCESS  read-only
    STATUS      current
    DESCRIPTION
        "The value of the object tmnxLocUsrDbPppOption6Display indicates a hint
         of how the tmnxLocUsrDbPppOption6Value can be displayed."
    ::= { tmnxLocUsrDbPppOption6Entry 6 }

tmnxLudbPppAliTableLastChange    OBJECT-TYPE
    SYNTAX      TimeStamp
    MAX-ACCESS  read-only
    STATUS      current
    DESCRIPTION
        "The value of the object tmnxLudbPppAliTableLastChange indicates the
         value of sysUpTime at the time of the last modification of an entry in
         the tmnxLudbPppAliTable."
    ::= { tmnxLocalUserDbObjs 30 }

tmnxLudbPppAliTable              OBJECT-TYPE
    SYNTAX      SEQUENCE OF TmnxLudbPppAliEntry
    MAX-ACCESS  not-accessible
    STATUS      current
    DESCRIPTION
        "The table tmnxLudbPppAliTable contains objects to configure the Access
         Loop Information of PPP hosts."
    ::= { tmnxLocalUserDbObjs 31 }

tmnxLudbPppAliEntry              OBJECT-TYPE
    SYNTAX      TmnxLudbPppAliEntry
    MAX-ACCESS  not-accessible
    STATUS      current
    DESCRIPTION
        "Each row represents a template for PPP hosts.

         Rows in this table are created and removed automatically by the
         system, together with the corresponding rows in the
         tmnxLocUsrDbPppoeTable."
    AUGMENTS    { tmnxLocUsrDbPppoeEntry }
    ::= { tmnxLudbPppAliTable 1 }

TmnxLudbPppAliEntry              ::= SEQUENCE
{
    tmnxLudbPppAliLastChangeTime     TimeStamp,
    tmnxLudbPppAliCircuitIdType      INTEGER,
    tmnxLudbPppAliCircuitId          OCTET STRING,
    tmnxLudbPppAliRemoteIdType       INTEGER,
    tmnxLudbPppAliRemoteId           OCTET STRING
}

tmnxLudbPppAliLastChangeTime     OBJECT-TYPE
    SYNTAX      TimeStamp
    MAX-ACCESS  read-only
    STATUS      current
    DESCRIPTION
        "The value of the object tmnxLudbPppAliLastChangeTime indicates the
         sysUpTime at the time of the last modification of this entry."
    ::= { tmnxLudbPppAliEntry 1 }

tmnxLudbPppAliCircuitIdType      OBJECT-TYPE
    SYNTAX      INTEGER {
        none  (0),
        ascii (1),
        sapId (2)
    }
    MAX-ACCESS  read-create
    STATUS      current
    DESCRIPTION
        "The value of the object tmnxLudbPppAliCircuitIdType specifies how the
         circuit-id is returned.

         If set to 'none', no circuit-id is returned.

         If set to 'ascii', the value of the object tmnxLudbPppAliCircuitId is
         returned as circuit-id.

         If set to 'sapId', the SAP-id is returned as circuit-id."
    DEFVAL      { none }
    ::= { tmnxLudbPppAliEntry 2 }

tmnxLudbPppAliCircuitId          OBJECT-TYPE
    SYNTAX      OCTET STRING (SIZE (0..63))
    MAX-ACCESS  read-create
    STATUS      current
    DESCRIPTION
        "The value of the object tmnxLudbPppAliCircuitId specifies the ASCII
         string to be returned as circuit-id.

         This object can only bet set if the value of
         tmnxLudbPppAliCircuitIdType is 'ascii'."
    REFERENCE
        "DSL Forum TR-101 Migration to Ethernet-Based DSL Aggregation
         Section 3.9.2 PPPoE Intermediate Agent"
    DEFVAL      { "" }
    ::= { tmnxLudbPppAliEntry 3 }

tmnxLudbPppAliRemoteIdType       OBJECT-TYPE
    SYNTAX      INTEGER {
        none  (0),
        ascii (1),
        mac   (2)
    }
    MAX-ACCESS  read-create
    STATUS      current
    DESCRIPTION
        "The value of the object tmnxLudbPppAliRemoteIdType specifies how the
         remote-id is returned.

         If set to 'none', no remote-id is returned.

         If set to 'ascii', the value of the object tmnxLudbPppAliRemoteId is
         returned as remote-id.

         If set to 'mac', the MAC address is returned as remote-id."
    DEFVAL      { none }
    ::= { tmnxLudbPppAliEntry 4 }

tmnxLudbPppAliRemoteId           OBJECT-TYPE
    SYNTAX      OCTET STRING (SIZE (0..63))
    MAX-ACCESS  read-create
    STATUS      current
    DESCRIPTION
        "The value of the object tmnxLudbPppAliRemoteId specifies the ASCII
         string to be returned as remote-id.

         This object can only bet set if the value of
         tmnxLudbPppAliRemoteIdType is 'ascii'."
    REFERENCE
        "DSL Forum TR-101 Migration to Ethernet-Based DSL Aggregation
         Section 3.9.2 PPPoE Intermediate Agent"
    DEFVAL      { "" }
    ::= { tmnxLudbPppAliEntry 5 }

tmnxLudbDhcp2TableLastChange     OBJECT-TYPE
    SYNTAX      TimeStamp
    MAX-ACCESS  read-only
    STATUS      current
    DESCRIPTION
        "The value of the object tmnxLudbDhcp2TableLastChange indicates the
         value of sysUpTime at the time of the last modification of an entry in
         the tmnxLudbDhcp2Table."
    ::= { tmnxLocalUserDbObjs 32 }

tmnxLudbDhcp2Table               OBJECT-TYPE
    SYNTAX      SEQUENCE OF TmnxLudbDhcp2Entry
    MAX-ACCESS  not-accessible
    STATUS      current
    DESCRIPTION
        "The table tmnxLudbDhcp2Table contains objects to configure IPOE hosts.

         It is an extension of the tmnxLocUsrDbDhcpTable."
    ::= { tmnxLocalUserDbObjs 33 }

tmnxLudbDhcp2Entry               OBJECT-TYPE
    SYNTAX      TmnxLudbDhcp2Entry
    MAX-ACCESS  not-accessible
    STATUS      current
    DESCRIPTION
        "Each row represents additional information for a (set of) host(s).

         Entries in this table are created and destroyed automatically by the
         system."
    AUGMENTS    { tmnxLocUsrDbDhcpEntry }
    ::= { tmnxLudbDhcp2Table 1 }

TmnxLudbDhcp2Entry               ::= SEQUENCE
{
    tmnxLudbDhcp2LastChangeTime      TimeStamp,
    tmnxLudbDhcp2WppPortalSvcId      TmnxServId,
    tmnxLudbDhcp2WppPortalName       TNamedItemOrEmpty,
    tmnxLudbDhcp2WppSubProfile       TNamedItemOrEmpty,
    tmnxLudbDhcp2WppSLAProfile       TNamedItemOrEmpty,
    tmnxLudbDhcp2WppAppProfile       TNamedItemOrEmpty,
    tmnxLudbDhcp2WppRestDiscon       INTEGER,
    tmnxLudbDhcp2GiAddrType          InetAddressType,
    tmnxLudbDhcp2GiAddr              InetAddress,
    tmnxLudbDhcp2LinkAddrType        InetAddressType,
    tmnxLudbDhcp2LinkAddr            InetAddress,
    tmnxLudbDhcp2Server6AddrType     InetAddressType,
    tmnxLudbDhcp2Server6Addr         InetAddress,
    tmnxLudbDhcp2DiamAppPlcy         TNamedItemOrEmpty,
    tmnxLudbDhcp2Ipv6LeaseRenew      Unsigned32,
    tmnxLudbDhcp2Ipv6LeaseRebind     Unsigned32,
    tmnxLudbDhcp2Ipv6LeaseValidLife  Unsigned32,
    tmnxLudbDhcp2Ipv6LeasePrefLife   Unsigned32,
    tmnxLudbDhcp2RipPolicy           TNamedItemOrEmpty,
    tmnxLudbDhcp2DiameterAuthPolicy  TNamedItemOrEmpty,
    tmnxLudbDhcp2WppPortalGroupName  TNamedItemOrEmpty,
    tmnxLudbDhcp2RtrAdvPlcy          TNamedItemOrEmpty,
    tmnxLudbDhcp2Service             TmnxServId,
    tmnxLudbDhcp2Interface           TNamedItemOrEmpty,
    tmnxLudbDhcp2GrpIfServiceName    TLNamedItemOrEmpty,
    tmnxLudbDhcp2RetailerServiceName TLNamedItemOrEmpty,
    tmnxLudbDhcp2IdentServiceName    TLNamedItemOrEmpty,
    tmnxLudbDhcp2EncTagRgOuterStart  Integer32,
    tmnxLudbDhcp2EncTagRgOuterEnd    Integer32,
    tmnxLudbDhcp2EncTagRgInnerStart  Integer32,
    tmnxLudbDhcp2EncTagRgInnerEnd    Integer32,
    tmnxLudbDhcp2DuidEn              OCTET STRING,
    tmnxLudbDhcp2DuidLlLlt           MacAddress
}

tmnxLudbDhcp2LastChangeTime      OBJECT-TYPE
    SYNTAX      TimeStamp
    MAX-ACCESS  read-only
    STATUS      current
    DESCRIPTION
        "The value of the object tmnxLudbDhcp2LastChangeTime indicates the
         sysUpTime at the time of the last modification of this row."
    ::= { tmnxLudbDhcp2Entry 1 }

tmnxLudbDhcp2WppPortalSvcId      OBJECT-TYPE
    SYNTAX      TmnxServId
    MAX-ACCESS  read-create
    STATUS      current
    DESCRIPTION
        "The value of tmnxLudbDhcp2WppPortalSvcId specifies the service ID of
         the WPP portal for this IPOE host.

         The service ID zero specifies the Base virtual router instance while
         the value of tmnxLudbDhcp2WppPortalName is not empty."
    DEFVAL      { 0 }
    ::= { tmnxLudbDhcp2Entry 2 }

tmnxLudbDhcp2WppPortalName       OBJECT-TYPE
    SYNTAX      TNamedItemOrEmpty
    MAX-ACCESS  read-create
    STATUS      current
    DESCRIPTION
        "The value of tmnxLudbDhcp2WppPortalName specifies the name of the WPP
         portal for this IPOE host."
    DEFVAL      { ''H }
    ::= { tmnxLudbDhcp2Entry 3 }

tmnxLudbDhcp2WppSubProfile       OBJECT-TYPE
    SYNTAX      TNamedItemOrEmpty
    MAX-ACCESS  read-create
    STATUS      current
    DESCRIPTION
        "The value of tmnxLudbDhcp2WppSubProfile specifies the initial
         subscriber profile, to be used during the WPP authentication phase of
         the IPOE host."
    DEFVAL      { ''H }
    ::= { tmnxLudbDhcp2Entry 4 }

tmnxLudbDhcp2WppSLAProfile       OBJECT-TYPE
    SYNTAX      TNamedItemOrEmpty
    MAX-ACCESS  read-create
    STATUS      current
    DESCRIPTION
        "The value of tmnxLudbDhcp2WppSLAProfile specifies the initial SLA
         profile, to be used during the WPP authentication phase of the IPOE
         host."
    DEFVAL      { ''H }
    ::= { tmnxLudbDhcp2Entry 5 }

tmnxLudbDhcp2WppAppProfile       OBJECT-TYPE
    SYNTAX      TNamedItemOrEmpty
    MAX-ACCESS  read-create
    STATUS      current
    DESCRIPTION
        "The value of tmnxLudbDhcp2WppAppProfile specifies the initial
         application profile, to be used during the WPP authentication phase of
         the IPOE hosts.

         The application profile is configured in
         TIMETRA-BSX-NG-MIB.mib::tmnxBsxAppProfTable."
    DEFVAL      { ''H }
    ::= { tmnxLudbDhcp2Entry 6 }

tmnxLudbDhcp2WppRestDiscon       OBJECT-TYPE
    SYNTAX      INTEGER {
        none      (0),
        restore   (1),
        noRestore (2)
    }
    MAX-ACCESS  read-create
    STATUS      current
    DESCRIPTION
        "The value of tmnxLudbDhcp2WppRestDiscon specifies if the initial
         profiles must be restored after the DHCP host has disconnected.

         The value 'none (0)' specifies that no restore adjustments are
         configured for this host."
    DEFVAL      { none }
    ::= { tmnxLudbDhcp2Entry 7 }

tmnxLudbDhcp2GiAddrType          OBJECT-TYPE
    SYNTAX      InetAddressType
    MAX-ACCESS  read-create
    STATUS      current
    DESCRIPTION
        "The value of tmnxLudbDhcp2GiAddrType specifies the type of address
         stored in tmnxLudbDhcp2GiAddr."
    DEFVAL      { unknown }
    ::= { tmnxLudbDhcp2Entry 10 }

tmnxLudbDhcp2GiAddr              OBJECT-TYPE
    SYNTAX      InetAddress (SIZE (0|4))
    MAX-ACCESS  read-create
    STATUS      current
    DESCRIPTION
        "The value of tmnxLudbDhcp2GiAddr specifies the DHCP giaddr (Relay
         agent IP address)."
    DEFVAL      { ''H }
    ::= { tmnxLudbDhcp2Entry 11 }

tmnxLudbDhcp2LinkAddrType        OBJECT-TYPE
    SYNTAX      InetAddressType
    MAX-ACCESS  read-create
    STATUS      current
    DESCRIPTION
        "The value of tmnxLudbDhcp2LinkAddrType specifies the type of address
         stored in tmnxLudbDhcp2LinkAddr."
    DEFVAL      { unknown }
    ::= { tmnxLudbDhcp2Entry 12 }

tmnxLudbDhcp2LinkAddr            OBJECT-TYPE
    SYNTAX      InetAddress (SIZE (0|16))
    MAX-ACCESS  read-create
    STATUS      current
    DESCRIPTION
        "The value of tmnxLudbDhcp2LinkAddr specifies the DHCP Relay
         link-address."
    REFERENCE
        "RFC 3315 DHCP for IPv6,
         Section 7.1. Relay-forward Message"
    DEFVAL      { ''H }
    ::= { tmnxLudbDhcp2Entry 13 }

tmnxLudbDhcp2Server6AddrType     OBJECT-TYPE
    SYNTAX      InetAddressType
    MAX-ACCESS  read-create
    STATUS      current
    DESCRIPTION
        "The value of tmnxLudbDhcp2Server6AddrType specifies the type of
         address stored in tmnxLudbDhcp2Server6Addr."
    DEFVAL      { unknown }
    ::= { tmnxLudbDhcp2Entry 14 }

tmnxLudbDhcp2Server6Addr         OBJECT-TYPE
    SYNTAX      InetAddress (SIZE (0|16))
    MAX-ACCESS  read-create
    STATUS      current
    DESCRIPTION
        "The value of tmnxLudbDhcp2Server6Addr specifies the IPv6 address of
         the DHCP server used by the DHCP Relay function on this system."
    DEFVAL      { ''H }
    ::= { tmnxLudbDhcp2Entry 15 }

tmnxLudbDhcp2DiamAppPlcy         OBJECT-TYPE
    SYNTAX      TNamedItemOrEmpty
    MAX-ACCESS  read-create
    STATUS      current
    DESCRIPTION
        "The value of tmnxLudbDhcp2DiamAppPlcy specifies the DIAMETER
         application policy.

         A non empty value must correspond to a conceptual row in the
         TIMETRA-DIAMETER-MIB.mib::tmnxDiamAppPlcyTable."
    DEFVAL      { ''H }
    ::= { tmnxLudbDhcp2Entry 16 }

tmnxLudbDhcp2Ipv6LeaseRenew      OBJECT-TYPE
    SYNTAX      Unsigned32 (0..604800 | 4294967295)
    MAX-ACCESS  read-create
    STATUS      current
    DESCRIPTION
        "The value of tmnxLudbDhcp2Ipv6LeaseRenew specifies the renew-timer
         (T1).

         The time at which the client contacts the server from which the
         addresses in the IA_NA or IA_PD were obtained to extend the lifetimes
         of the addresses or prefixes assigned to the client.

         The value 'FFFFFFFF'h means 'undefined', and specifies that the
         renew-timer must be taken from another source."
    DEFVAL      { 'FFFFFFFF'H }
    ::= { tmnxLudbDhcp2Entry 17 }

tmnxLudbDhcp2Ipv6LeaseRebind     OBJECT-TYPE
    SYNTAX      Unsigned32 (0..1209600 | 4294967295)
    MAX-ACCESS  read-create
    STATUS      current
    DESCRIPTION
        "The value of tmnxLudbDhcp2Ipv6LeaseRebind specifies the rebind-timer
         (T2).

         The time at which the client contacts any available server to extend
         the lifetimes of the addresses or prefixes assigned to the client.

         The value 'FFFFFFFF'h means 'undefined', and specifies that the
         rebind-timer must be taken from another source."
    DEFVAL      { 'FFFFFFFF'H }
    ::= { tmnxLudbDhcp2Entry 18 }

tmnxLudbDhcp2Ipv6LeaseValidLife  OBJECT-TYPE
    SYNTAX      Unsigned32 (0 | 300..315446399 | 4294967295)
    UNITS       "seconds"
    MAX-ACCESS  read-create
    STATUS      current
    DESCRIPTION
        "The value of tmnxLudbDhcp2Ipv6LeaseValidLife specifies the valid
         lifetime for an IPv6 lease.

         The value zero means 'undefined', and specifies that the valid
         lifetime must be taken from another source.

         The value 'FFFFFFFF'h means 'infinity'."
    DEFVAL      { 0 }
    ::= { tmnxLudbDhcp2Entry 19 }

tmnxLudbDhcp2Ipv6LeasePrefLife   OBJECT-TYPE
    SYNTAX      Unsigned32 (0 | 300..315446399 | 4294967295)
    UNITS       "seconds"
    MAX-ACCESS  read-create
    STATUS      current
    DESCRIPTION
        "The value of tmnxLudbDhcp2Ipv6LeasePrefLife specifies the preferred
         lifetime for an IPv6 lease.

         When the preferred lifetime expires, then any derived addresses are
         deprecated.

         The value zero means 'undefined', and specifies that the preferred
         lifetime must be taken from another source.

         The value 'FFFFFFFF'h means 'infinity'."
    DEFVAL      { 0 }
    ::= { tmnxLudbDhcp2Entry 20 }

tmnxLudbDhcp2RipPolicy           OBJECT-TYPE
    SYNTAX      TNamedItemOrEmpty
    MAX-ACCESS  read-create
    STATUS      current
    DESCRIPTION
        "The value of the object tmnxLudbDhcp2RipPolicy specifies the
         RIP/RIP-NG policy to be used on this host.

         A non empty value must correspond to a conceptual row in the
         TIMETRA-SUBSCRIBER-MGMT-MIB.mib::tmnxSubRipPlcyTable."
    DEFVAL      { "" }
    ::= { tmnxLudbDhcp2Entry 21 }

tmnxLudbDhcp2DiameterAuthPolicy  OBJECT-TYPE
    SYNTAX      TNamedItemOrEmpty
    MAX-ACCESS  read-create
    STATUS      current
    DESCRIPTION
        "The value of the object tmnxLudbDhcp2DiameterAuthPolicy specifies the
         Diameter authentication policy to be used on this host.

         A non empty value must correspond to a conceptual row in the
         TIMETRA-DIAMETER-MIB.mib::tmnxDiamApNqTable."
    DEFVAL      { "" }
    ::= { tmnxLudbDhcp2Entry 22 }

tmnxLudbDhcp2WppPortalGroupName  OBJECT-TYPE
    SYNTAX      TNamedItemOrEmpty
    MAX-ACCESS  read-create
    STATUS      current
    DESCRIPTION
        "The value of tmnxLudbDhcp2WppPortalGroupName specifies the name of the
         WPP portal group."
    DEFVAL      { "" }
    ::= { tmnxLudbDhcp2Entry 23 }

tmnxLudbDhcp2RtrAdvPlcy          OBJECT-TYPE
    SYNTAX      TNamedItemOrEmpty
    MAX-ACCESS  read-create
    STATUS      current
    DESCRIPTION
        "The value of tmnxLudbDhcp2RtrAdvPlcy specifies the name of the Router
         Advertisement policy."
    DEFVAL      { "" }
    ::= { tmnxLudbDhcp2Entry 24 }

tmnxLudbDhcp2Service             OBJECT-TYPE
    SYNTAX      TmnxServId
    MAX-ACCESS  read-create
    STATUS      current
    DESCRIPTION
        "The value of tmnxLudbDhcp2Service specifies the service ID of the
         service where the group interface is configured that is specified by
         the object tmnxLudbDhcp2Interface.

         This object is deprecated, please use tmnxLudbDhcp2GrpIfServiceName
         instead."
    DEFVAL      { 0 }
    ::= { tmnxLudbDhcp2Entry 25 }

tmnxLudbDhcp2Interface           OBJECT-TYPE
    SYNTAX      TNamedItemOrEmpty
    MAX-ACCESS  read-create
    STATUS      current
    DESCRIPTION
        "The value of the object tmnxLudbDhcp2Interface specifies the name of
         the group interface where the IPoE sessions are established"
    DEFVAL      { ''H }
    ::= { tmnxLudbDhcp2Entry 26 }

tmnxLudbDhcp2GrpIfServiceName    OBJECT-TYPE
    SYNTAX      TLNamedItemOrEmpty
    MAX-ACCESS  read-create
    STATUS      current
    DESCRIPTION
        "The value of tmnxLudbDhcp2GrpIfServiceName specifies the name of the
         service where the group interface is configured that is specified by
         the object tmnxLudbDhcp2Interface.

         A non empty value is mutually exclusive with a non zero value for the
         object tmnxLudbDhcp2Service."
    DEFVAL      { "" }
    ::= { tmnxLudbDhcp2Entry 27 }

tmnxLudbDhcp2RetailerServiceName OBJECT-TYPE
    SYNTAX      TLNamedItemOrEmpty
    MAX-ACCESS  read-create
    STATUS      current
    DESCRIPTION
        "The value of tmnxLudbDhcp2RetailerServiceName specifies the name of
         the retailer service.

         A non empty value is mutually exclusive with a non zero value for the
         object tmnxLocUsrDbDhcpRetailerSvcId."
    DEFVAL      { "" }
    ::= { tmnxLudbDhcp2Entry 28 }

tmnxLudbDhcp2IdentServiceName    OBJECT-TYPE
    SYNTAX      TLNamedItemOrEmpty
    MAX-ACCESS  read-create
    STATUS      current
    DESCRIPTION
        "The value of tmnxLudbDhcp2IdentServiceName specifies the name of the
         service where the IPoE sessions are established.

         A non empty value is mutually exclusive with a non zero value for the
         object tmnxLocUsrDbDhcpServiceId."
    DEFVAL      { "" }
    ::= { tmnxLudbDhcp2Entry 29 }

tmnxLudbDhcp2EncTagRgOuterStart  OBJECT-TYPE
    SYNTAX      Integer32 (-1 | 0..4094)
    MAX-ACCESS  read-create
    STATUS      current
    DESCRIPTION
        "The value of tmnxLudbDhcp2EncTagRgOuterStart specifies the left bound
         (i.e. minimum value) of a range of outer VLANs allowed on this DHCP
         host. Value -1 indicates tmnxLudbDhcp2EncTagRgOuterStart is not
         applicable and should not be used."
    DEFVAL      { -1 }
    ::= { tmnxLudbDhcp2Entry 30 }

tmnxLudbDhcp2EncTagRgOuterEnd    OBJECT-TYPE
    SYNTAX      Integer32 (-1 | 0..4094)
    MAX-ACCESS  read-create
    STATUS      current
    DESCRIPTION
        "The value of tmnxLudbDhcp2EncTagRgOuterEnd specifies the right bound
         (i.e. maximum value) of a range of outer VLANs allowed on this DHCP
         host. Value -1 indicates tmnxLudbDhcp2EncTagRgOuterEnd is not
         applicable and should not be used."
    DEFVAL      { -1 }
    ::= { tmnxLudbDhcp2Entry 31 }

tmnxLudbDhcp2EncTagRgInnerStart  OBJECT-TYPE
    SYNTAX      Integer32 (-1 | 0..4094)
    MAX-ACCESS  read-create
    STATUS      current
    DESCRIPTION
        "The value of tmnxLudbDhcp2EncTagRgInnerStart specifies the left bound
         (i.e. minimum value) of a range of inner VLANs allowed on this DHCP
         host. Value -1 indicates tmnxLudbDhcp2EncTagRgInnerStart is not
         applicable and should not be used."
    DEFVAL      { -1 }
    ::= { tmnxLudbDhcp2Entry 32 }

tmnxLudbDhcp2EncTagRgInnerEnd    OBJECT-TYPE
    SYNTAX      Integer32 (-1 | 0..4094)
    MAX-ACCESS  read-create
    STATUS      current
    DESCRIPTION
        "The value of tmnxLudbDhcp2EncTagRgInnerEnd specifies the right bound
         (i.e. maximum value) of a range of inner VLANs allowed on this DHCP
         host. Value -1 indicates tmnxLudbDhcp2EncTagRgInnerEnd is not
         applicable and should not be used."
    DEFVAL      { -1 }
    ::= { tmnxLudbDhcp2Entry 33 }

tmnxLudbDhcp2DuidEn              OBJECT-TYPE
    SYNTAX      OCTET STRING (SIZE (0..127))
    MAX-ACCESS  read-create
    STATUS      current
    DESCRIPTION
        "The value of the object tmnxLudbDhcp2DuidEn specifies the DUID based
         on Enterprise Number from option 1 duid-type 2 to match against.

         If the value of this object is the empty string, then it is not used."
    DEFVAL      { ''H }
    ::= { tmnxLudbDhcp2Entry 34 }

tmnxLudbDhcp2DuidLlLlt           OBJECT-TYPE
    SYNTAX      MacAddress
    MAX-ACCESS  read-create
    STATUS      current
    DESCRIPTION
        "The value of the object tmnxLudbDhcp2DuidLlLlt specifies the DUID
         based on Link-Layer Address from option 1 duid-type 1 or 3 to match
         against.

         If the value of this object is set to all zeros, then it is not used."
    DEFVAL      { '000000000000'H }
    ::= { tmnxLudbDhcp2Entry 35 }

tmnxLudbPpp2TableLastChange      OBJECT-TYPE
    SYNTAX      TimeStamp
    MAX-ACCESS  read-only
    STATUS      current
    DESCRIPTION
        "The value of the object tmnxLudbPpp2TableLastChange indicates the
         value of sysUpTime at the time of the last modification of an entry in
         the tmnxLudbPpp2Table."
    ::= { tmnxLocalUserDbObjs 34 }

tmnxLudbPpp2Table                OBJECT-TYPE
    SYNTAX      SEQUENCE OF TmnxLudbPpp2Entry
    MAX-ACCESS  not-accessible
    STATUS      current
    DESCRIPTION
        "The table tmnxLudbPpp2Table contains objects to configure PPP hosts."
    ::= { tmnxLocalUserDbObjs 35 }

tmnxLudbPpp2Entry                OBJECT-TYPE
    SYNTAX      TmnxLudbPpp2Entry
    MAX-ACCESS  not-accessible
    STATUS      current
    DESCRIPTION
        "Each row represents a template for PPP hosts.

         Rows in this table are created and removed automatically by the
         system, together with the corresponding rows in the
         tmnxLocUsrDbPppoeTable."
    AUGMENTS    { tmnxLocUsrDbPppoeEntry }
    ::= { tmnxLudbPpp2Table 1 }

TmnxLudbPpp2Entry                ::= SEQUENCE
{
    tmnxLudbPpp2LastChangeTime       TimeStamp,
    tmnxLudbPpp2DiamAppPlcy          TNamedItemOrEmpty,
    tmnxLudbPpp2Ipv6LeaseRenew       Unsigned32,
    tmnxLudbPpp2Ipv6LeaseRebind      Unsigned32,
    tmnxLudbPpp2Ipv6LeaseValidLife   Unsigned32,
    tmnxLudbPpp2Ipv6LeasePrefLife    Unsigned32,
    tmnxLudbPpp2RipPolicy            TNamedItemOrEmpty,
    tmnxLudbPpp2DiameterAuthPolicy   TNamedItemOrEmpty,
    tmnxLudbPpp2IgnoreDfBit          TruthValue,
    tmnxLudbPpp2UserDb               TNamedItemOrEmpty,
    tmnxLudbPpp2SteeringProfStr      TNamedItemOrEmpty,
    tmnxLudbPpp2PadiAuthPolicy       TNamedItemOrEmpty,
    tmnxLudbPpp2RtrAdvPlcy           TNamedItemOrEmpty,
    tmnxLudbPpp2SpiGroupId           TmnxSubSpiGroupId,
    tmnxLudbPpp2RetailerServiceName  TLNamedItemOrEmpty,
    tmnxLudbPpp2GrpIfServiceName     TLNamedItemOrEmpty,
    tmnxLudbPpp2L2tpGroupServiceName TLNamedItemOrEmpty,
    tmnxLudbPpp2EncTagRgOuterStart   Integer32,
    tmnxLudbPpp2EncTagRgOuterEnd     Integer32,
    tmnxLudbPpp2EncTagRgInnerStart   Integer32,
    tmnxLudbPpp2EncTagRgInnerEnd     Integer32,
    tmnxLudbPpp2MacMaxSessionsOvr    Unsigned32,
    tmnxLudbPpp2KaInterval           Unsigned32,
    tmnxLudbPpp2KaHoldUpMplier       Unsigned32
}

tmnxLudbPpp2LastChangeTime       OBJECT-TYPE
    SYNTAX      TimeStamp
    MAX-ACCESS  read-only
    STATUS      current
    DESCRIPTION
        "The value of the object tmnxLudbPpp2LastChangeTime indicates the
         sysUpTime at the time of the last modification of this entry."
    ::= { tmnxLudbPpp2Entry 1 }

tmnxLudbPpp2DiamAppPlcy          OBJECT-TYPE
    SYNTAX      TNamedItemOrEmpty
    MAX-ACCESS  read-create
    STATUS      current
    DESCRIPTION
        "The value of tmnxLudbPpp2DiamAppPlcy specifies the DIAMETER
         application policy.

         A non empty value must correspond to a conceptual row in the
         TIMETRA-DIAMETER-MIB.mib::tmnxDiamAppPlcyTable."
    DEFVAL      { ''H }
    ::= { tmnxLudbPpp2Entry 2 }

tmnxLudbPpp2Ipv6LeaseRenew       OBJECT-TYPE
    SYNTAX      Unsigned32 (0..604800 | 4294967295)
    MAX-ACCESS  read-create
    STATUS      current
    DESCRIPTION
        "The value of tmnxLudbPpp2Ipv6LeaseRenew specifies the renew-timer
         (T1).

         The time at which the client contacts the server from which the
         addresses in the IA_NA or IA_PD were obtained to extend the lifetimes
         of the addresses or prefixes assigned to the client.

         The value 'FFFFFFFF'h means 'undefined', and specifies that the
         renew-timer must be taken from another source."
    DEFVAL      { 'FFFFFFFF'H }
    ::= { tmnxLudbPpp2Entry 3 }

tmnxLudbPpp2Ipv6LeaseRebind      OBJECT-TYPE
    SYNTAX      Unsigned32 (0..1209600 | 4294967295)
    MAX-ACCESS  read-create
    STATUS      current
    DESCRIPTION
        "The value of tmnxLudbPpp2Ipv6LeaseRebind specifies the rebind-timer
         (T2).

         The time at which the client contacts any available server to extend
         the lifetimes of the addresses or prefixes assigned to the client.

         The value 'FFFFFFFF'h means 'undefined', and specifies that the
         rebind-timer must be taken from another source."
    DEFVAL      { 'FFFFFFFF'H }
    ::= { tmnxLudbPpp2Entry 4 }

tmnxLudbPpp2Ipv6LeaseValidLife   OBJECT-TYPE
    SYNTAX      Unsigned32 (0 | 300..315446399 | 4294967295)
    UNITS       "seconds"
    MAX-ACCESS  read-create
    STATUS      current
    DESCRIPTION
        "The value of tmnxLudbPpp2Ipv6LeaseValidLife specifies the valid
         lifetime for an IPv6 lease.

         The value zero means 'undefined', and specifies that the valid
         lifetime must be taken from another source.

         The value 'FFFFFFFF'h means 'infinity'."
    DEFVAL      { 0 }
    ::= { tmnxLudbPpp2Entry 5 }

tmnxLudbPpp2Ipv6LeasePrefLife    OBJECT-TYPE
    SYNTAX      Unsigned32 (0 | 300..315446399 | 4294967295)
    UNITS       "seconds"
    MAX-ACCESS  read-create
    STATUS      current
    DESCRIPTION
        "The value of tmnxLudbPpp2Ipv6LeasePrefLife specifies the preferred
         lifetime for an IPv6 lease.

         When the preferred lifetime expires, then any derived addresses are
         deprecated.

         The value zero means 'undefined', and specifies that the preferred
         lifetime must be taken from another source.

         The value 'FFFFFFFF'h means 'infinity'"
    DEFVAL      { 0 }
    ::= { tmnxLudbPpp2Entry 6 }

tmnxLudbPpp2RipPolicy            OBJECT-TYPE
    SYNTAX      TNamedItemOrEmpty
    MAX-ACCESS  read-create
    STATUS      current
    DESCRIPTION
        "The value of the object tmnxLudbPpp2RipPolicy specifies the RIP/RIP-NG
         policy to be used on this host.

         A non empty value must correspond to a conceptual row in the
         TIMETRA-SUBSCRIBER-MGMT-MIB.mib::tmnxSubRipPlcyTable."
    DEFVAL      { "" }
    ::= { tmnxLudbPpp2Entry 7 }

tmnxLudbPpp2DiameterAuthPolicy   OBJECT-TYPE
    SYNTAX      TNamedItemOrEmpty
    MAX-ACCESS  read-create
    STATUS      current
    DESCRIPTION
        "The value of tmnxLudbPpp2DiameterAuthPolicy specifies the DIAMETER
         authentication policy.

         A non empty value must correspond to a conceptual row in the
         TIMETRA-DIAMETER-MIB.mib::tmnxDiamApNqTable."
    DEFVAL      { ''H }
    ::= { tmnxLudbPpp2Entry 8 }

tmnxLudbPpp2IgnoreDfBit          OBJECT-TYPE
    SYNTAX      TruthValue
    MAX-ACCESS  read-create
    STATUS      current
    DESCRIPTION
        "The value of tmnxLudbPpp2IgnoreDfBit specifies if this system must
         fragment frames if necessary, even if they have the Don't Fragment
         (DF) bit set in the IPv4 header.

         If the value of this object is set to 'true(1)', then the system
         ignores the DF bit and does fragment if necessary."
    DEFVAL      { false }
    ::= { tmnxLudbPpp2Entry 9 }

tmnxLudbPpp2UserDb               OBJECT-TYPE
    SYNTAX      TNamedItemOrEmpty
    MAX-ACCESS  read-create
    STATUS      current
    DESCRIPTION
        "The value of tmnxLudbPpp2UserDb specifies the local user database to
         use for PPP PAP/CHAP based authentication."
    DEFVAL      { ''H }
    ::= { tmnxLudbPpp2Entry 10 }

tmnxLudbPpp2SteeringProfStr      OBJECT-TYPE
    SYNTAX      TNamedItemOrEmpty
    MAX-ACCESS  read-create
    STATUS      current
    DESCRIPTION
        "The value of the object tmnxLudbPpp2SteeringProfStr specifies the
         steering profile string which is encoded in the identification
         strings."
    DEFVAL      { ''H }
    ::= { tmnxLudbPpp2Entry 11 }

tmnxLudbPpp2PadiAuthPolicy       OBJECT-TYPE
    SYNTAX      TNamedItemOrEmpty
    MAX-ACCESS  read-create
    STATUS      current
    DESCRIPTION
        "The value of the object tmnxLudbPpp2PadiAuthPolicy specifies the
         authentication policy to use for PADI authentication."
    DEFVAL      { ''H }
    ::= { tmnxLudbPpp2Entry 12 }

tmnxLudbPpp2RtrAdvPlcy           OBJECT-TYPE
    SYNTAX      TNamedItemOrEmpty
    MAX-ACCESS  read-create
    STATUS      current
    DESCRIPTION
        "The value of tmnxLudbPpp2RtrAdvPlcy specifies the name of the Router
         Advertisement policy."
    DEFVAL      { ''H }
    ::= { tmnxLudbPpp2Entry 13 }

tmnxLudbPpp2SpiGroupId           OBJECT-TYPE
    SYNTAX      TmnxSubSpiGroupId
    MAX-ACCESS  read-create
    STATUS      current
    DESCRIPTION
        "The value of the object tmnxLudbPpp2SpiGroupId specifies the SLA
         profile instance group identifier in the identification strings.

         A value of minus one means that there is no group identifier
         configured."
    DEFVAL      { -1 }
    ::= { tmnxLudbPpp2Entry 14 }

tmnxLudbPpp2RetailerServiceName  OBJECT-TYPE
    SYNTAX      TLNamedItemOrEmpty
    MAX-ACCESS  read-create
    STATUS      current
    DESCRIPTION
        "The value of tmnxLudbPpp2RetailerServiceName specifies the name of the
         service where the PPP sessions are established.

         A non empty value is mutually exclusive with a non zero value for the
         object tmnxLocUsrDbPppoeRetailerSvcId."
    DEFVAL      { "" }
    ::= { tmnxLudbPpp2Entry 15 }

tmnxLudbPpp2GrpIfServiceName     OBJECT-TYPE
    SYNTAX      TLNamedItemOrEmpty
    MAX-ACCESS  read-create
    STATUS      current
    DESCRIPTION
        "The value of tmnxLudbPpp2GrpIfServiceName specifies the name of the
         service where the group interface is configured that is identified
         with the object tmnxLocUsrDbPppoeInterface.

         A non empty value is mutually exclusive with a non zero value for the
         object tmnxLocUsrDbPppoeService."
    DEFVAL      { "" }
    ::= { tmnxLudbPpp2Entry 16 }

tmnxLudbPpp2L2tpGroupServiceName OBJECT-TYPE
    SYNTAX      TLNamedItemOrEmpty
    MAX-ACCESS  read-create
    STATUS      current
    DESCRIPTION
        "The value of tmnxLudbPpp2L2tpGroupServiceName specifies the name of
         the service from where to take the tunnel group
         (tmnxLocUsrDbPppoeL2tpTunnelGroup) to use to setup an L2TP LAC
         tunnel/session.

         If the value of this object is empty and the value of
         tmnxLocUsrDbPppoeL2tpSvcId is zero, any L2TP tunneling will be done
         from the base router context"
    DEFVAL      { "" }
    ::= { tmnxLudbPpp2Entry 17 }

tmnxLudbPpp2EncTagRgOuterStart   OBJECT-TYPE
    SYNTAX      Integer32 (-1 | 0..4094)
    MAX-ACCESS  read-create
    STATUS      current
    DESCRIPTION
        "The value of tmnxLudbPpp2EncTagRgOuterStart specifies the left bound
         (i.e. minimum value) of a range of outer VLANs allowed on this PPP
         host. Value -1 indicates tmnxLudbPpp2EncTagRgOuterStart is not
         applicable and should not be used."
    DEFVAL      { -1 }
    ::= { tmnxLudbPpp2Entry 18 }

tmnxLudbPpp2EncTagRgOuterEnd     OBJECT-TYPE
    SYNTAX      Integer32 (-1 | 0..4094)
    MAX-ACCESS  read-create
    STATUS      current
    DESCRIPTION
        "The value of tmnxLudbPpp2EncTagRgOuterEnd specifies the right bound
         (i.e. maximum value) of a range of outer VLANs allowed on this PPP
         host. Value -1 indicates tmnxLudbPpp2EncTagRgOuterEnd is not
         applicable and should not be used."
    DEFVAL      { -1 }
    ::= { tmnxLudbPpp2Entry 19 }

tmnxLudbPpp2EncTagRgInnerStart   OBJECT-TYPE
    SYNTAX      Integer32 (-1 | 0..4094)
    MAX-ACCESS  read-create
    STATUS      current
    DESCRIPTION
        "The value of tmnxLudbPpp2EncTagRgInnerStart specifies the left bound
         (i.e. minimum value) of a range of inner VLANs allowed on this PPP
         host. Value -1 indicates tmnxLudbPpp2EncTagRgInnerStart is not
         applicable and should not be used."
    DEFVAL      { -1 }
    ::= { tmnxLudbPpp2Entry 20 }

tmnxLudbPpp2EncTagRgInnerEnd     OBJECT-TYPE
    SYNTAX      Integer32 (-1 | 0..4094)
    MAX-ACCESS  read-create
    STATUS      current
    DESCRIPTION
        "The value of tmnxLudbPpp2EncTagRgInnerEnd specifies the right bound
         (i.e. maximum value) of a range of inner VLANs allowed on this PPP
         host. Value -1 indicates tmnxLudbPpp2EncTagRgInnerEnd is not
         applicable and should not be used."
    DEFVAL      { -1 }
    ::= { tmnxLudbPpp2Entry 21 }

tmnxLudbPpp2MacMaxSessionsOvr    OBJECT-TYPE
    SYNTAX      Unsigned32 (0 | 1..8191)
    MAX-ACCESS  read-create
    STATUS      current
    DESCRIPTION
        "The value of tmnxLudbPpp2MacMaxSessionsOvr specifies the maximum
         number of PPPoE sessions created per MAC address. This number will
         override the value defined within the PPPoE policy. Value 0 indicates
         no override."
    DEFVAL      { 0 }
    ::= { tmnxLudbPpp2Entry 22 }

tmnxLudbPpp2KaInterval           OBJECT-TYPE
    SYNTAX      Unsigned32 (0 | 4..300)
    UNITS       "seconds"
    MAX-ACCESS  read-create
    STATUS      current
    DESCRIPTION
        "The value tmnxLudbPpp2KaInterval specifies the time interval in
         seconds at which LCP echo requests are transmitted. This number will
         override the value defined within the PPPoE policy."
    DEFVAL      { 0 }
    ::= { tmnxLudbPpp2Entry 23 }

tmnxLudbPpp2KaHoldUpMplier       OBJECT-TYPE
    SYNTAX      Unsigned32 (1..5)
    MAX-ACCESS  read-create
    STATUS      current
    DESCRIPTION
        "The value of tmnxLudbPpp2KaHoldUpMplier specifies how many  LCP
         keepalive messages can be missed before the related PPP session is
         brought down. This number will override the value defined within the
         PPPoE policy."
    DEFVAL      { 3 }
    ::= { tmnxLudbPpp2Entry 24 }

tmnxLudbToClntOptTableLstCh      OBJECT-TYPE
    SYNTAX      TimeStamp
    MAX-ACCESS  read-only
    STATUS      current
    DESCRIPTION
        "The value of the object tmnxLudbToClntOptTableLstCh indicates the
         value of sysUpTime at the time of the last modification of an entry in
         the tmnxLudbToClntOptTable."
    ::= { tmnxLocalUserDbObjs 36 }

tmnxLudbToClntOptTable           OBJECT-TYPE
    SYNTAX      SEQUENCE OF TmnxLudbToClntOptEntry
    MAX-ACCESS  not-accessible
    STATUS      current
    DESCRIPTION
        "The table tmnxLudbToClntOptTable contains objects to configure DHCP
         and DHCP6 options for this system to send to the DHCP client."
    ::= { tmnxLocalUserDbObjs 37 }

tmnxLudbToClntOptEntry           OBJECT-TYPE
    SYNTAX      TmnxLudbToClntOptEntry
    MAX-ACCESS  not-accessible
    STATUS      current
    DESCRIPTION
        "Each row represents a DHCP or DHCP6 option that this system appends to
         the DHCP reply message of this DHCP host.

         Entries in this table can be created or deleted via SNMP operations."
    INDEX       {
        tmnxLocUsrDbUserDatabaseName,
        tmnxLudbHostType,
        tmnxLudbHostName,
        tmnxLudbToClntOptAddrType,
        tmnxLudbToClntOptNumber
    }
    ::= { tmnxLudbToClntOptTable 1 }

TmnxLudbToClntOptEntry           ::= SEQUENCE
{
    tmnxLudbToClntOptAddrType        InetAddressType,
    tmnxLudbToClntOptNumber          Unsigned32,
    tmnxLudbToClntOptRowStatus       RowStatus,
    tmnxLudbToClntOptLastCh          TimeStamp,
    tmnxLudbToClntOptType            TmnxDhcpOptionType,
    tmnxLudbToClntOptValue           OCTET STRING,
    tmnxLudbToClntOptDisplay         TmnxDhcpOptionDisplay
}

tmnxLudbToClntOptAddrType        OBJECT-TYPE
    SYNTAX      InetAddressType
    MAX-ACCESS  not-accessible
    STATUS      current
    DESCRIPTION
        "The value of tmnxLudbToClntOptAddrType specifies the address type
         where this row applies to.

         The only values allowed are 'ipv4' and 'ipv6'."
    ::= { tmnxLudbToClntOptEntry 1 }

tmnxLudbToClntOptNumber          OBJECT-TYPE
    SYNTAX      Unsigned32 (1..254 | 255..65535)
    MAX-ACCESS  not-accessible
    STATUS      current
    DESCRIPTION
        "The value of the object tmnxLudbToClntOptNumber specifies the number
         of this DHCP option.

         The range is [1..254] for DHCP options, and [1..65535] for DHCP6
         options"
    REFERENCE
        "RFC 2132 DHCP Options and BOOTP Vendor Extensions.
         RFC 3315 Dynamic Host Configuration Protocol for IPv6 (DHCPv6),
         section 22. DHCP Options."
    ::= { tmnxLudbToClntOptEntry 2 }

tmnxLudbToClntOptRowStatus       OBJECT-TYPE
    SYNTAX      RowStatus
    MAX-ACCESS  read-create
    STATUS      current
    DESCRIPTION
        "The value of the object tmnxLudbToClntOptRowStatus specifies the row
         status of this row.

         Objects tmnxLudbToClntOptType and tmnxLudbToClntOptValue must be set
         when creating a new row."
    ::= { tmnxLudbToClntOptEntry 3 }

tmnxLudbToClntOptLastCh          OBJECT-TYPE
    SYNTAX      TimeStamp
    MAX-ACCESS  read-only
    STATUS      current
    DESCRIPTION
        "The value of the object tmnxLudbToClntOptLastCh indicates the
         sysUpTime at the time of the last modification of this entry."
    ::= { tmnxLudbToClntOptEntry 4 }

tmnxLudbToClntOptType            OBJECT-TYPE
    SYNTAX      TmnxDhcpOptionType
    MAX-ACCESS  read-create
    STATUS      current
    DESCRIPTION
        "The value of the object tmnxLudbToClntOptType specifies how the value
         of this option is stored in tmnxLudbToClntOptValue.

         This object is mandatory at creation time."
    ::= { tmnxLudbToClntOptEntry 5 }

tmnxLudbToClntOptValue           OBJECT-TYPE
    SYNTAX      OCTET STRING (SIZE (0..127))
    MAX-ACCESS  read-create
    STATUS      current
    DESCRIPTION
        "The value of the object tmnxLudbToClntOptValue specifies the value of
         this option.

         This object is mandatory at creation time. A zero length value is only
         allowed when the value of tmnxLudbToClntOptType is 'hex (3)'."
    ::= { tmnxLudbToClntOptEntry 6 }

tmnxLudbToClntOptDisplay         OBJECT-TYPE
    SYNTAX      TmnxDhcpOptionDisplay
    MAX-ACCESS  read-only
    STATUS      current
    DESCRIPTION
        "The value of the object tmnxLudbToClntOptDisplay indicates a hint of
         how the tmnxLudbToClntOptValue can be displayed."
    ::= { tmnxLudbToClntOptEntry 7 }

tmnxLudbToServerOptTableLstCh    OBJECT-TYPE
    SYNTAX      TimeStamp
    MAX-ACCESS  read-only
    STATUS      current
    DESCRIPTION
        "The value of the object tmnxLudbToServerOptTableLstCh indicates the
         value of sysUpTime at the time of the last modification of an entry in
         the tmnxLudbToServerOptTable."
    ::= { tmnxLocalUserDbObjs 38 }

tmnxLudbToServerOptTable         OBJECT-TYPE
    SYNTAX      SEQUENCE OF TmnxLudbToServerOptEntry
    MAX-ACCESS  not-accessible
    STATUS      current
    DESCRIPTION
        "The table tmnxLudbToServerOptTable contains objects to configure DHCP6
         options for this system to send to the DHCP server."
    ::= { tmnxLocalUserDbObjs 39 }

tmnxLudbToServerOptEntry         OBJECT-TYPE
    SYNTAX      TmnxLudbToServerOptEntry
    MAX-ACCESS  not-accessible
    STATUS      current
    DESCRIPTION
        "Each row represents a DHCP6 option that this system appends to the
         DHCP RELAY_FORWARD message when relaying a client packet of this DHCP
         host towards the DHCP6 server.

         Entries in this table can be created or deleted via SNMP operations."
    INDEX       {
        tmnxLocUsrDbUserDatabaseName,
        tmnxLudbHostType,
        tmnxLudbHostName,
        tmnxLudbToServerOptAddrType,
        tmnxLudbToServerOptNumber
    }
    ::= { tmnxLudbToServerOptTable 1 }

TmnxLudbToServerOptEntry         ::= SEQUENCE
{
    tmnxLudbToServerOptAddrType      InetAddressType,
    tmnxLudbToServerOptNumber        Unsigned32,
    tmnxLudbToServerOptRowStatus     RowStatus,
    tmnxLudbToServerOptLastCh        TimeStamp,
    tmnxLudbToServerOptType          TmnxDhcpOptionType,
    tmnxLudbToServerOptValue         OCTET STRING,
    tmnxLudbToServerOptDisplay       TmnxDhcpOptionDisplay
}

tmnxLudbToServerOptAddrType      OBJECT-TYPE
    SYNTAX      InetAddressType
    MAX-ACCESS  not-accessible
    STATUS      current
    DESCRIPTION
        "The value of tmnxLudbToServerOptAddrType specifies the address type
         where this row applies to.

         The only value allowed is 'ipv6'."
    ::= { tmnxLudbToServerOptEntry 1 }

tmnxLudbToServerOptNumber        OBJECT-TYPE
    SYNTAX      Unsigned32 (1..65535)
    MAX-ACCESS  not-accessible
    STATUS      current
    DESCRIPTION
        "The value of the object tmnxLudbToServerOptNumber specifies the number
         of this DHCP option."
    REFERENCE
        "RFC 2132 DHCP Options and BOOTP Vendor Extensions.
         RFC 3315 Dynamic Host Configuration Protocol for IPv6 (DHCPv6),
         section 22. DHCP Options."
    ::= { tmnxLudbToServerOptEntry 2 }

tmnxLudbToServerOptRowStatus     OBJECT-TYPE
    SYNTAX      RowStatus
    MAX-ACCESS  read-create
    STATUS      current
    DESCRIPTION
        "The value of the object tmnxLudbToServerOptRowStatus specifies the row
         status of this row.

         Objects tmnxLudbToServerOptType and tmnxLudbToServerOptValue must be
         set when creating a new row."
    ::= { tmnxLudbToServerOptEntry 3 }

tmnxLudbToServerOptLastCh        OBJECT-TYPE
    SYNTAX      TimeStamp
    MAX-ACCESS  read-only
    STATUS      current
    DESCRIPTION
        "The value of the object tmnxLudbToServerOptLastCh indicates the
         sysUpTime at the time of the last modification of this entry."
    ::= { tmnxLudbToServerOptEntry 4 }

tmnxLudbToServerOptType          OBJECT-TYPE
    SYNTAX      TmnxDhcpOptionType
    MAX-ACCESS  read-create
    STATUS      current
    DESCRIPTION
        "The value of the object tmnxLudbToServerOptType specifies how the
         value of this option is stored in tmnxLudbToServerOptValue.

         This object is mandatory at creation time."
    ::= { tmnxLudbToServerOptEntry 5 }

tmnxLudbToServerOptValue         OBJECT-TYPE
    SYNTAX      OCTET STRING (SIZE (0..127))
    MAX-ACCESS  read-create
    STATUS      current
    DESCRIPTION
        "The value of the object tmnxLudbToServerOptValue specifies the value
         of this option.

         This object is mandatory at creation time. A zero length value is only
         allowed when the value of tmnxLudbToServerOptType is 'hex (3)'."
    ::= { tmnxLudbToServerOptEntry 6 }

tmnxLudbToServerOptDisplay       OBJECT-TYPE
    SYNTAX      TmnxDhcpOptionDisplay
    MAX-ACCESS  read-only
    STATUS      current
    DESCRIPTION
        "The value of the object tmnxLudbToServerOptDisplay indicates a hint of
         how the tmnxLudbToServerOptValue can be displayed."
    ::= { tmnxLudbToServerOptEntry 7 }

tmnxLudbMldImpPlcyTableLstCh     OBJECT-TYPE
    SYNTAX      TimeStamp
    MAX-ACCESS  read-only
    STATUS      current
    DESCRIPTION
        "The value of the object tmnxLudbMldImpPlcyTableLstCh indicates the
         value of sysUpTime at the time of the last modification of an entry in
         the tmnxLudbMldImpPlcyTable."
    ::= { tmnxLocalUserDbObjs 46 }

tmnxLudbMldImpPlcyTable          OBJECT-TYPE
    SYNTAX      SEQUENCE OF TmnxLudbMldImpPlcyEntry
    MAX-ACCESS  not-accessible
    STATUS      current
    DESCRIPTION
        "The table tmnxLudbMldImpPlcyTable contains objects to configure
         multiple import policies for Multicast Listener Discovery (MLD) per
         IPoE host."
    ::= { tmnxLocalUserDbObjs 47 }

tmnxLudbMldImpPlcyEntry          OBJECT-TYPE
    SYNTAX      TmnxLudbMldImpPlcyEntry
    MAX-ACCESS  not-accessible
    STATUS      current
    DESCRIPTION
        "Each row represents an MLD import policy to be associated with a
         particular IPoE host.

         Entries in this table can be created or deleted via SNMP operations."
    INDEX       {
        tmnxLocUsrDbUserDatabaseName,
        tmnxLudbHostType,
        tmnxLudbHostName,
        IMPLIED tmnxLudbMldImpPlcyName
    }
    ::= { tmnxLudbMldImpPlcyTable 1 }

TmnxLudbMldImpPlcyEntry          ::= SEQUENCE
{
    tmnxLudbMldImpPlcyName           TPolicyStatementName,
    tmnxLudbMldImpPlcyRowStatus      RowStatus,
    tmnxLudbMldImpPlcyLastCh         TimeStamp
}

tmnxLudbMldImpPlcyName           OBJECT-TYPE
    SYNTAX      TPolicyStatementName
    MAX-ACCESS  not-accessible
    STATUS      current
    DESCRIPTION
        "The value of the object tmnxLudbMldImpPlcyName specifies the name of
         an import policy for MLD.

         The name may refer to a conceptual row in the
         TIMETRA-ROUTE-POLICY-MIB::tRPOperPolicyStatementTable and such a row
         should exist when this object is actually used for an IPoE host."
    ::= { tmnxLudbMldImpPlcyEntry 1 }

tmnxLudbMldImpPlcyRowStatus      OBJECT-TYPE
    SYNTAX      RowStatus
    MAX-ACCESS  read-create
    STATUS      current
    DESCRIPTION
        "The value of the object tmnxLudbMldImpPlcyRowStatus specifies the row
         status of this row."
    ::= { tmnxLudbMldImpPlcyEntry 2 }

tmnxLudbMldImpPlcyLastCh         OBJECT-TYPE
    SYNTAX      TimeStamp
    MAX-ACCESS  read-only
    STATUS      current
    DESCRIPTION
        "The value of the object tmnxLudbMldImpPlcyLastCh indicates the
         sysUpTime at the time of the last modification of this entry."
    ::= { tmnxLudbMldImpPlcyEntry 3 }

tmnxLocalUserDbNotificationObjs  OBJECT IDENTIFIER ::= { tmnxLocalUserDb 2 }

tmnxLudbNotifyPortId             OBJECT-TYPE
    SYNTAX      TNamedItem
    MAX-ACCESS  accessible-for-notify
    STATUS      current
    DESCRIPTION
        "The object tmnxLudbNotifyPortId indicates the port-id on which the
         host entered the system."
    ::= { tmnxLocalUserDbNotificationObjs 1 }

tmnxLocalUserDbConformance       OBJECT IDENTIFIER ::= { tmnxSRConfs 51 }

tmnxLocalUserDbCompliances       OBJECT IDENTIFIER ::= { tmnxLocalUserDbConformance 1 }

tmnxLocalUserDbCompliance        MODULE-COMPLIANCE
    STATUS      obsolete
    DESCRIPTION
        "The compliance statement for management of local user database on
         Nokia SROS series systems."
    MODULE
        MANDATORY-GROUPS {
            tmnxLocalUserDbGroup,
            tmnxLocalUserDbPppoeGroup,
            tmnxLocalUserDbDhcpGroup,
            tmnxLocalUserDbToolsGroup
        }
    ::= { tmnxLocalUserDbCompliances 1 }

tmnxLocalUserDbV6v1Compliance    MODULE-COMPLIANCE
    STATUS      obsolete
    DESCRIPTION
        "The compliance statement for management of local user database on
         Nokia SROS series systems."
    MODULE
        MANDATORY-GROUPS {
            tmnxLocalUserDbGroup,
            tmnxLocalUserDbPppoeV6v1Group,
            tmnxLocalUserDbDhcpGroup,
            tmnxLocalUserDbToolsGroup
        }
    ::= { tmnxLocalUserDbCompliances 2 }

tmnxLocalUserDbV7v0Compliance    MODULE-COMPLIANCE
    STATUS      obsolete
    DESCRIPTION
        "The compliance statement for management of local user database on
         Nokia SROS series systems."
    MODULE
        MANDATORY-GROUPS {
            tmnxLocalUserDbV7v0Group,
            tmnxLocalUserDbPppoeV7v0Group,
            tmnxLocalUserDbDhcpV7v0Group,
            tmnxLocalUserDbToolsV7v0Group,
            tmnxLocalUserDbObsoleteGroup
        }
    ::= { tmnxLocalUserDbCompliances 3 }

tmnxLocalUserDbV8v0Compliance    MODULE-COMPLIANCE
    STATUS      current
    DESCRIPTION
        "The compliance statement for management of local user database on
         Nokia SROS series systems."
    MODULE
        MANDATORY-GROUPS {
            tmnxLocalUserDbV7v0Group,
            tmnxLocalUserDbPppoeV8v0Group,
            tmnxLocalUserDbDhcpV8v0Group,
            tmnxLocalUserDbToolsV8v0Group,
            tmnxLocalUserDbRadiusFllbckGroup,
            tmnxLocalUserDbObsoleteGroup
        }
    ::= { tmnxLocalUserDbCompliances 4 }

tmnxLocalUserDbV9v0Compliance    MODULE-COMPLIANCE
    STATUS      obsolete
    DESCRIPTION
        "The compliance statement for management of local user database on
         Nokia SROS series systems."
    MODULE
        MANDATORY-GROUPS {
            tmnxLocalUserDbV7v0Group,
            tmnxLocalUserDbPppoeV8v0Group,
            tmnxLocalUserDbPppoeV9v0Group,
            tmnxLocalUserDbDhcpV8v0Group,
            tmnxLocalUserDbDhcpV9v0Group,
            tmnxLocalUserDbHostGroup,
            tmnxLocalUserDbToolsV8v0Group,
            tmnxLocalUserDbRadiusFllbckGroup,
            tmnxLocalUserDbObsoleteGroup,
            tmnxLocalUserDbFltrProfGroup
        }
    ::= { tmnxLocalUserDbCompliances 5 }

tmnxLocalUserDbV10v0Compliance   MODULE-COMPLIANCE
    STATUS      obsolete
    DESCRIPTION
        "The compliance statement for management of local user database on
         Nokia SROS series systems."
    MODULE
        MANDATORY-GROUPS {
            tmnxLocalUserDbV7v0Group,
            tmnxLocalUserDbPppoeV8v0Group,
            tmnxLocalUserDbPppoeV9v0Group,
            tmnxLocalUserDbDhcpV8v0Group,
            tmnxLocalUserDbDhcpV9v0Group,
            tmnxLocalUserDbHostGroup,
            tmnxLocalUserDbToolsV8v0Group,
            tmnxLocalUserDbRadiusFllbckGroup,
            tmnxLocalUserDbObsoleteGroup,
            tmnxLocalUserDbFltrProfGroup,
            tmnxLudbPppHostGroup,
            tmnxLudbRadproxGroup
        }
    ::= { tmnxLocalUserDbCompliances 6 }

tmnxLocalUserDbV11v0Compliance   MODULE-COMPLIANCE
    STATUS      obsolete
    DESCRIPTION
        "The compliance statement for management of local user database on
         Nokia SROS series systems."
    MODULE
        MANDATORY-GROUPS {
            tmnxLocalUserDbV7v0Group,
            tmnxLocalUserDbPppoeV8v0Group,
            tmnxLocalUserDbPppoeV9v0Group,
            tmnxLocalUserDbDhcpV8v0Group,
            tmnxLocalUserDbDhcpV9v0Group,
            tmnxLocalUserDbDhcpV11v0Group,
            tmnxLocalUserDbHostGroup,
            tmnxLocalUserDbToolsV8v0Group,
            tmnxLocalUserDbRadiusFllbckGroup,
            tmnxLocalUserDbObsoleteGroup,
            tmnxLocalUserDbFltrProfGroup,
            tmnxLudbPppHostGroup,
            tmnxLudbPppAliGroup,
            tmnxLudbRadproxGroup,
            tmnxLudbNotifV11v0Group
        }
    ::= { tmnxLocalUserDbCompliances 7 }

tmnxLocalUserDbV12v0Compliance   MODULE-COMPLIANCE
    STATUS      obsolete
    DESCRIPTION
        "The compliance statement for management of local user database on
         Nokia SROS series systems."
    MODULE
        MANDATORY-GROUPS {
            tmnxLocalUserDbV7v0Group,
            tmnxLocalUserDbPppoeV8v0Group,
            tmnxLocalUserDbPppoeV9v0Group,
            tmnxLocalUserDbDhcpV8v0Group,
            tmnxLocalUserDbDhcpV9v0Group,
            tmnxLocalUserDbDhcpV11v0Group,
            tmnxLocalUserDbDhcpV12v0Group,
            tmnxLocalUserDbHostGroup,
            tmnxLocalUserDbToolsV8v0Group,
            tmnxLocalUserDbRadiusFllbckGroup,
            tmnxLocalUserDbObsoleteGroup,
            tmnxLocalUserDbFltrProfGroup,
            tmnxLudbPppHostGroup,
            tmnxLudbPppAliGroup,
            tmnxLudbRadproxGroup,
            tmnxLudbNotifV11v0Group,
            tmnxLudbRadproxV12v0Group,
            tmnxLocalUserDbPppoeV12v0Group,
            tmnxLudbToClntOptGroup
        }
    ::= { tmnxLocalUserDbCompliances 8 }

tmnxLocalUserDbV13v0Compliance   MODULE-COMPLIANCE
    STATUS      obsolete
    DESCRIPTION
        "The compliance statement for management of local user database on
         Nokia SROS series systems."
    MODULE
        MANDATORY-GROUPS {
            tmnxLocalUserDbV7v0Group,
            tmnxLocalUserDbPppoeV8v0Group,
            tmnxLocalUserDbPppoeV9v0Group,
            tmnxLocalUserDbDhcpV8v0Group,
            tmnxLocalUserDbDhcpV9v0Group,
            tmnxLocalUserDbDhcpV11v0Group,
            tmnxLocalUserDbDhcpV12v0Group,
            tmnxLocalUserDbHostGroup,
            tmnxLocalUserDbToolsV8v0Group,
            tmnxLocalUserDbRadiusFllbckGroup,
            tmnxLocalUserDbObsoleteGroup,
            tmnxLocalUserDbFltrProfGroup,
            tmnxLudbPppHostGroup,
            tmnxLudbPppAliGroup,
            tmnxLudbRadproxGroup,
            tmnxLudbNotifV11v0Group,
            tmnxLudbRadproxV12v0Group,
            tmnxLocalUserDbPppoeV12v0Group,
            tmnxLudbToClntOptGroup,
            tmnxLudbRipPlcyV13v0Group,
            tmnxLudbDiameterAuthPlcyGroup,
            tmnxLocalUserDbPppoeDfGroup
        }
    ::= { tmnxLocalUserDbCompliances 9 }

tmnxLocalUserDbV14v0Compliance   MODULE-COMPLIANCE
    STATUS      obsolete
    DESCRIPTION
        "The compliance statement for management of local user database on
         Nokia SROS series systems."
    MODULE
        MANDATORY-GROUPS {
            tmnxLocalUserDbV7v0Group,
            tmnxLocalUserDbV14v0Group,
            tmnxLocalUserDbPppoeV8v0Group,
            tmnxLocalUserDbPppoeV9v0Group,
            tmnxLocalUserDbDhcpV8v0Group,
            tmnxLocalUserDbDhcpV9v0Group,
            tmnxLocalUserDbDhcpV11v0Group,
            tmnxLocalUserDbDhcpV12v0Group,
            tmnxLocalUserDbHostGroup,
            tmnxLocalUserDbToolsV8v0Group,
            tmnxLocalUserDbRadiusFllbckGroup,
            tmnxLocalUserDbObsoleteGroup,
            tmnxLocalUserDbFltrProfGroup,
            tmnxLudbPppHostGroup,
            tmnxLudbPppAliGroup,
            tmnxLudbRadproxGroup,
            tmnxLudbNotifV11v0Group,
            tmnxLudbRadproxV12v0Group,
            tmnxLocalUserDbPppoeV12v0Group,
            tmnxLocalUserDbPppoeV14v0Group,
            tmnxLudbToClntOptGroup,
            tmnxLudbToServerOptGroup,
            tmnxLudbRipPlcyV13v0Group,
            tmnxLudbDiameterAuthPlcyGroup,
            tmnxLocalUserDbPppoeDfGroup,
            tmnxLocalUserDbIpoeV14v0Group
        }
    ::= { tmnxLocalUserDbCompliances 10 }

tmnxLocalUserDbV15v0Compliance   MODULE-COMPLIANCE
    STATUS      obsolete
    DESCRIPTION
        "The compliance statement for management of local user database on
         Nokia SROS series systems."
    MODULE
        MANDATORY-GROUPS {
            tmnxLocalUserDbPppoeV15v0Group,
            tmnxLocalUserDbV15v0Group
        }
    ::= { tmnxLocalUserDbCompliances 11 }

tmnxLocalUserDbV16v0Compliance   MODULE-COMPLIANCE
    STATUS      current
    DESCRIPTION
        "The compliance statement for management of local user database on
         Nokia SROS series systems."
    MODULE
        MANDATORY-GROUPS {
            tmnxLocalUserDbV7v0Group,
            tmnxLocalUserDbV14v0Group,
            tmnxLocalUserDbPppoeV8v0Group,
            tmnxLocalUserDbPppoeV9v0Group,
            tmnxLocalUserDbDhcpV8v0Group,
            tmnxLocalUserDbDhcpV9v0Group,
            tmnxLocalUserDbDhcpV11v0Group,
            tmnxLocalUserDbDhcpV12v0Group,
            tmnxLocalUserDbHostGroup,
            tmnxLocalUserDbToolsV8v0Group,
            tmnxLocalUserDbRadiusFllbckGroup,
            tmnxLocalUserDbObsoleteGroup,
            tmnxLocalUserDbFltrProfGroup,
            tmnxLudbPppHostGroup,
            tmnxLudbPppAliGroup,
            tmnxLudbRadproxGroup,
            tmnxLudbNotifV11v0Group,
            tmnxLudbRadproxV12v0Group,
            tmnxLocalUserDbPppoeV12v0Group,
            tmnxLocalUserDbPppoeV14v0Group,
            tmnxLudbToClntOptGroup,
            tmnxLudbToServerOptGroup,
            tmnxLudbRipPlcyV13v0Group,
            tmnxLudbDiameterAuthPlcyGroup,
            tmnxLocalUserDbPppoeDfGroup,
            tmnxLocalUserDbIpoeV14v0Group,
            tmnxLocalUserDbPppoeV15v0Group,
            tmnxLocalUserDbV15v0Group,
            tmnxLocalUserDbV16v0Group
        }
    ::= { tmnxLocalUserDbCompliances 12 }

tmnxLocalUserDbV20v0Compliance   MODULE-COMPLIANCE
    STATUS      current
    DESCRIPTION
        "The compliance statement for management of local user database on
         Nokia SROS series systems."
    MODULE
        MANDATORY-GROUPS {
            tmnxLocalUserDbV20v0Group
        }
    ::= { tmnxLocalUserDbCompliances 13 }

tmnxLocalUserDbV22v0Compliance   MODULE-COMPLIANCE
    STATUS      current
    DESCRIPTION
        "The compliance statement for management of local user database on
         Nokia SROS series systems."
    MODULE
        MANDATORY-GROUPS {
            tmnxLocalUserDbPppoeV22v0Group
        }
    ::= { tmnxLocalUserDbCompliances 14 }

tmnxLocalUserDbV23v0Compliance   MODULE-COMPLIANCE
    STATUS      current
    DESCRIPTION
        "The compliance statement for management of local user database on
         Nokia SROS series systems."
    MODULE
        MANDATORY-GROUPS {
            tmnxLocalUserDbPppoeV23v0Group
        }
    ::= { tmnxLocalUserDbCompliances 15 }

tmnxLocalUserDbV24v0Compliance   MODULE-COMPLIANCE
    STATUS      current
    DESCRIPTION
        "The compliance statement for management of local user database on
         Nokia SROS series systems."
    MODULE
        MANDATORY-GROUPS {
            tmnxLocalUserDbV24v0Group
        }
    ::= { tmnxLocalUserDbCompliances 16 }

tmnxLocalUserDbGroups            OBJECT IDENTIFIER ::= { tmnxLocalUserDbConformance 2 }

tmnxLocalUserDbGroup             OBJECT-GROUP
    OBJECTS     {
        tmnxLocalUserDbTableLastChange,
        tmnxLocUsrDbRowStatus,
        tmnxLocUsrDbLastChangeTime,
        tmnxLocUsrDbAdminState,
        tmnxLocUsrDbDescription,
        tmnxLocUsrDbMatchTypeDhcp1,
        tmnxLocUsrDbMatchTypeDhcp2,
        tmnxLocUsrDbMatchTypeDhcp3,
        tmnxLocUsrDbMatchTypeDhcp4,
        tmnxLocUsrDbMatchTypePppoe1,
        tmnxLocUsrDbMatchTypePppoe2,
        tmnxLocUsrDbMatchTypePppoe3,
        tmnxLocUsrDbPppoeCIdMaskPreStr,
        tmnxLocUsrDbPppoeCIdMaskPreNum,
        tmnxLocUsrDbPppoeCIdMaskSufStr,
        tmnxLocUsrDbPppoeCIdMaskSufNum,
        tmnxLocUsrDbDhcpCIdMaskPreStr,
        tmnxLocUsrDbDhcpCIdMaskPreNum,
        tmnxLocUsrDbDhcpCIdMaskSufStr,
        tmnxLocUsrDbDhcpCIdMaskSufNum,
        tmnxLocUsrDbHostCount
    }
    STATUS      obsolete
    DESCRIPTION
        "The group of objects supporting local user database capability on
         Nokia SROS series systems."
    ::= { tmnxLocalUserDbGroups 1 }

tmnxLocalUserDbPppoeGroup        OBJECT-GROUP
    OBJECTS     {
        tmnxLocUsrDbPppoeTableLastChange,
        tmnxLocUsrDbPppoeRowStatus,
        tmnxLocUsrDbPppoeLastChangeTime,
        tmnxLocUsrDbPppoeAdminState,
        tmnxLocUsrDbPppoeMacAddress,
        tmnxLocUsrDbPppoeCircuitId,
        tmnxLocUsrDbPppoeCircuitIdFmt,
        tmnxLocUsrDbPppoeRemoteId,
        tmnxLocUsrDbPppoeUserNameFormat,
        tmnxLocUsrDbPppoeUserName,
        tmnxLocUsrDbPppoePasswordType,
        tmnxLocUsrDbPppoePassword,
        tmnxLocUsrDbPppoeAddrType,
        tmnxLocUsrDbPppoeAddress,
        tmnxLocUsrDbPppoePool,
        tmnxLocUsrDbPppoeUseGiAddress,
        tmnxLocUsrDbPppoeIdStringOptNum,
        tmnxLocUsrDbPppoeSubscriberId,
        tmnxLocUsrDbPppoeSlaProfString,
        tmnxLocUsrDbPppoeSubProfString,
        tmnxLocUsrDbPppoeAppProfString,
        tmnxLocUsrDbPppoeAncpString,
        tmnxLocUsrDbPppoeInterDestId,
        tmnxLocUsrDbPppoeUnMacAddress,
        tmnxLocUsrDbPppoeUnCircuitId,
        tmnxLocUsrDbPppoeUnRemoteId,
        tmnxLocUsrDbPppoeUnUserNameFmt,
        tmnxLocUsrDbPppoeUnUserName,
        tmnxLocUsrDbPppoeUnmatchedReason,
        tmnxLocUsrDbDhcpUnDuplicateHost,
        tmnxLocUsrDbPppoeUnDuplicateHost,
        tmnxLocUsrDbPppoeOptionTbleLstCh,
        tmnxLocUsrDbPppoeOptionRowStatus,
        tmnxLocUsrDbPppoeOptionLstChngTm,
        tmnxLocUsrDbPppoeOptionType,
        tmnxLocUsrDbPppoeOptionValue
    }
    STATUS      obsolete
    DESCRIPTION
        "The group of objects supporting local user databases for PPPoE hosts
         on Nokia SROS series systems."
    ::= { tmnxLocalUserDbGroups 2 }

tmnxLocalUserDbDhcpGroup         OBJECT-GROUP
    OBJECTS     {
        tmnxLocUsrDbDhcpTableLastChange,
        tmnxLocUsrDbDhcpRowStatus,
        tmnxLocUsrDbDhcpLastChangeTime,
        tmnxLocUsrDbDhcpAdminState,
        tmnxLocUsrDbDhcpMacAddress,
        tmnxLocUsrDbDhcpCircuitIdFmt,
        tmnxLocUsrDbDhcpCircuitId,
        tmnxLocUsrDbDhcpRemoteId,
        tmnxLocUsrDbDhcpSystemId,
        tmnxLocUsrDbDhcpServiceId,
        tmnxLocUsrDbDhcpSapId,
        tmnxLocUsrDbDhcpString,
        tmnxLocUsrDbDhcpOption60,
        tmnxLocUsrDbDhcpAddrType,
        tmnxLocUsrDbDhcpAddress,
        tmnxLocUsrDbDhcpPool,
        tmnxLocUsrDbDhcpUseGiAddress,
        tmnxLocUsrDbDhcpIdStringOptNum,
        tmnxLocUsrDbDhcpSubscriberId,
        tmnxLocUsrDbDhcpSlaProfString,
        tmnxLocUsrDbDhcpSubProfString,
        tmnxLocUsrDbDhcpAppProfString,
        tmnxLocUsrDbDhcpAncpString,
        tmnxLocUsrDbDhcpInterDestId,
        tmnxLocUsrDbDhcpUnMacAddress,
        tmnxLocUsrDbDhcpUnCircuitId,
        tmnxLocUsrDbDhcpUnRemoteId,
        tmnxLocUsrDbDhcpUnSystemId,
        tmnxLocUsrDbDhcpUnServiceId,
        tmnxLocUsrDbDhcpUnSapId,
        tmnxLocUsrDbDhcpUnString,
        tmnxLocUsrDbDhcpUnOption60,
        tmnxLocUsrDbDhcpUnmatchedReason,
        tmnxLocUsrDbDhcpOptionTableLstCh,
        tmnxLocUsrDbDhcpOptionRowStatus,
        tmnxLocUsrDbDhcpOptionLastChngTm,
        tmnxLocUsrDbDhcpOptionType,
        tmnxLocUsrDbDhcpOptionValue
    }
    STATUS      obsolete
    DESCRIPTION
        "The group of objects supporting local user databases for DHCP hosts on
         Nokia SROS series systems."
    ::= { tmnxLocalUserDbGroups 3 }

tmnxLocalUserDbToolsGroup        OBJECT-GROUP
    OBJECTS     {
        tmnxLocUsrDbPppoeAuthDbName,
        tmnxLocUsrDbPppoeAuthUsrName,
        tmnxLocUsrDbPppoeAuthPwd,
        tmnxLocUsrDbPppoeAuthenticate,
        tmnxLocUsrDbPppoeAuthSuccessful,
        tmnxLocUsrDbPppoeAuthErrorMsg,
        tmnxLocUsrDbPppoeAuthTime,
        tmnxLocUsrDbPppoeAuthHostName
    }
    STATUS      obsolete
    DESCRIPTION
        "The group of objects supporting local user database capability on
         Nokia SROS series systems."
    ::= { tmnxLocalUserDbGroups 4 }

tmnxLocalUserDbPppoeV6v1Group    OBJECT-GROUP
    OBJECTS     {
        tmnxLocUsrDbPppoeTableLastChange,
        tmnxLocUsrDbPppoeRowStatus,
        tmnxLocUsrDbPppoeLastChangeTime,
        tmnxLocUsrDbPppoeAdminState,
        tmnxLocUsrDbPppoeMacAddress,
        tmnxLocUsrDbPppoeCircuitId,
        tmnxLocUsrDbPppoeCircuitIdFmt,
        tmnxLocUsrDbPppoeRemoteId,
        tmnxLocUsrDbPppoeUserNameFormat,
        tmnxLocUsrDbPppoeUserName,
        tmnxLocUsrDbPppoePasswordType,
        tmnxLocUsrDbPppoePassword,
        tmnxLocUsrDbPppoeAddrType,
        tmnxLocUsrDbPppoeAddress,
        tmnxLocUsrDbPppoePool,
        tmnxLocUsrDbPppoeUseGiAddress,
        tmnxLocUsrDbPppoeIdStringOptNum,
        tmnxLocUsrDbPppoeSubscriberId,
        tmnxLocUsrDbPppoeSlaProfString,
        tmnxLocUsrDbPppoeSubProfString,
        tmnxLocUsrDbPppoeAppProfString,
        tmnxLocUsrDbPppoeAncpString,
        tmnxLocUsrDbPppoeInterDestId,
        tmnxLocUsrDbPppoeUseClientPool,
        tmnxLocUsrDbPppoeUnMacAddress,
        tmnxLocUsrDbPppoeUnCircuitId,
        tmnxLocUsrDbPppoeUnRemoteId,
        tmnxLocUsrDbPppoeUnUserNameFmt,
        tmnxLocUsrDbPppoeUnUserName,
        tmnxLocUsrDbPppoeUnmatchedReason,
        tmnxLocUsrDbDhcpUnDuplicateHost,
        tmnxLocUsrDbPppoeUnDuplicateHost,
        tmnxLocUsrDbPppoeOptionTbleLstCh,
        tmnxLocUsrDbPppoeOptionRowStatus,
        tmnxLocUsrDbPppoeOptionLstChngTm,
        tmnxLocUsrDbPppoeOptionType,
        tmnxLocUsrDbPppoeOptionValue
    }
    STATUS      obsolete
    DESCRIPTION
        "The group of objects supporting local user databases for PPPoE hosts
         on Nokia SROS series systems release 6.1."
    ::= { tmnxLocalUserDbGroups 5 }

tmnxLocalUserDbPppoeV7v0Group    OBJECT-GROUP
    OBJECTS     {
        tmnxLocUsrDbPppoeTableLastChange,
        tmnxLocUsrDbPppoeRowStatus,
        tmnxLocUsrDbPppoeLastChangeTime,
        tmnxLocUsrDbPppoeAdminState,
        tmnxLocUsrDbPppoeMacAddress,
        tmnxLocUsrDbPppoeCircuitId,
        tmnxLocUsrDbPppoeCircuitIdFmt,
        tmnxLocUsrDbPppoeRemoteId,
        tmnxLocUsrDbPppoeUserNameFormat,
        tmnxLocUsrDbPppoeUserName,
        tmnxLocUsrDbPppoePasswordType,
        tmnxLocUsrDbPppoePassword,
        tmnxLocUsrDbPppoeAddrType,
        tmnxLocUsrDbPppoeAddress,
        tmnxLocUsrDbPppoePool,
        tmnxLocUsrDbPppoeUseGiAddress,
        tmnxLocUsrDbPppoeIdStringOptNum,
        tmnxLocUsrDbPppoeSubscriberId,
        tmnxLocUsrDbPppoeSlaProfString,
        tmnxLocUsrDbPppoeSubProfString,
        tmnxLocUsrDbPppoeAppProfString,
        tmnxLocUsrDbPppoeAncpString,
        tmnxLocUsrDbPppoeInterDestId,
        tmnxLocUsrDbPppoeUseClientPool,
        tmnxLocUsrDbPppoePadoDelay,
        tmnxLocUsrDbPppoeServiceName,
        tmnxLocUsrDbPppoeL2tpTunnelGroup,
        tmnxLocUsrDbPppoeAuthPolicy,
        tmnxLocUsrDbPppoeRetailerSvcId,
        tmnxLocUsrDbPppoeCategoryMapName,
        tmnxLocUsrDbPppoeUnMacAddress,
        tmnxLocUsrDbPppoeUnCircuitId,
        tmnxLocUsrDbPppoeUnRemoteId,
        tmnxLocUsrDbPppoeUnUserNameFmt,
        tmnxLocUsrDbPppoeUnUserName,
        tmnxLocUsrDbPppoeUnmatchedReason,
        tmnxLocUsrDbDhcpUnDuplicateHost,
        tmnxLocUsrDbPppoeUnDuplicateHost,
        tmnxLocUsrDbPppoeUnServiceName,
        tmnxLocUsrDbPppoeOptionTbleLstCh,
        tmnxLocUsrDbPppoeOptionRowStatus,
        tmnxLocUsrDbPppoeOptionLstChngTm,
        tmnxLocUsrDbPppoeOptionType,
        tmnxLocUsrDbPppoeOptionValue,
        tmnxLocUsrDbPppoeMaskTableLstCh,
        tmnxLocUsrDbPppoeMaskRowStatus,
        tmnxLocUsrDbPppoeMaskPreStr,
        tmnxLocUsrDbPppoeMaskPreNum,
        tmnxLocUsrDbPppoeMaskSufStr,
        tmnxLocUsrDbPppoeMaskSufNum
    }
    STATUS      obsolete
    DESCRIPTION
        "The group of objects supporting local user databases for PPPoE hosts
         on Nokia SROX series systems release 7.0."
    ::= { tmnxLocalUserDbGroups 6 }

tmnxLocalUserDbDhcpV7v0Group     OBJECT-GROUP
    OBJECTS     {
        tmnxLocUsrDbDhcpTableLastChange,
        tmnxLocUsrDbDhcpRowStatus,
        tmnxLocUsrDbDhcpLastChangeTime,
        tmnxLocUsrDbDhcpAdminState,
        tmnxLocUsrDbDhcpMacAddress,
        tmnxLocUsrDbDhcpCircuitIdFmt,
        tmnxLocUsrDbDhcpCircuitId,
        tmnxLocUsrDbDhcpRemoteId,
        tmnxLocUsrDbDhcpSystemId,
        tmnxLocUsrDbDhcpServiceId,
        tmnxLocUsrDbDhcpSapId,
        tmnxLocUsrDbDhcpString,
        tmnxLocUsrDbDhcpOption60,
        tmnxLocUsrDbDhcpAddrType,
        tmnxLocUsrDbDhcpAddress,
        tmnxLocUsrDbDhcpPool,
        tmnxLocUsrDbDhcpUseGiAddress,
        tmnxLocUsrDbDhcpIdStringOptNum,
        tmnxLocUsrDbDhcpSubscriberId,
        tmnxLocUsrDbDhcpSlaProfString,
        tmnxLocUsrDbDhcpSubProfString,
        tmnxLocUsrDbDhcpAppProfString,
        tmnxLocUsrDbDhcpAncpString,
        tmnxLocUsrDbDhcpInterDestId,
        tmnxLocUsrDbDhcpAuthPolicy,
        tmnxLocUsrDbDhcpServerAddrType,
        tmnxLocUsrDbDhcpServerAddress,
        tmnxLocUsrDbDhcpAuthDomainName,
        tmnxLocUsrDbDhcpCategoryMapName,
        tmnxLocUsrDbDhcpOption60Fmt,
        tmnxLocUsrDbDhcpUseClientPool,
        tmnxLocUsrDbDhcpUnMacAddress,
        tmnxLocUsrDbDhcpUnCircuitId,
        tmnxLocUsrDbDhcpUnRemoteId,
        tmnxLocUsrDbDhcpUnSystemId,
        tmnxLocUsrDbDhcpUnServiceId,
        tmnxLocUsrDbDhcpUnSapId,
        tmnxLocUsrDbDhcpUnString,
        tmnxLocUsrDbDhcpUnOption60,
        tmnxLocUsrDbDhcpUnmatchedReason,
        tmnxLocUsrDbDhcpOptionTableLstCh,
        tmnxLocUsrDbDhcpOptionRowStatus,
        tmnxLocUsrDbDhcpOptionLastChngTm,
        tmnxLocUsrDbDhcpOptionType,
        tmnxLocUsrDbDhcpOptionValue,
        tmnxLocUsrDbDhcpMaskTableLstCh,
        tmnxLocUsrDbDhcpMaskRowStatus,
        tmnxLocUsrDbDhcpMaskPreStr,
        tmnxLocUsrDbDhcpMaskPreNum,
        tmnxLocUsrDbDhcpMaskSufStr,
        tmnxLocUsrDbDhcpMaskSufNum
    }
    STATUS      obsolete
    DESCRIPTION
        "The group of objects supporting local user databases for DHCP hosts on
         Nokia SROS series systems release 7.0."
    ::= { tmnxLocalUserDbGroups 7 }

tmnxLocalUserDbV7v0Group         OBJECT-GROUP
    OBJECTS     {
        tmnxLocalUserDbTableLastChange,
        tmnxLocUsrDbRowStatus,
        tmnxLocUsrDbLastChangeTime,
        tmnxLocUsrDbAdminState,
        tmnxLocUsrDbDescription,
        tmnxLocUsrDbMatchTypeDhcp1,
        tmnxLocUsrDbMatchTypeDhcp2,
        tmnxLocUsrDbMatchTypeDhcp3,
        tmnxLocUsrDbMatchTypeDhcp4,
        tmnxLocUsrDbMatchTypePppoe1,
        tmnxLocUsrDbMatchTypePppoe2,
        tmnxLocUsrDbMatchTypePppoe3,
        tmnxLocUsrDbHostCount
    }
    STATUS      current
    DESCRIPTION
        "The group of objects supporting local user database capability on
         Nokia SROS series systems release 7.0."
    ::= { tmnxLocalUserDbGroups 8 }

tmnxLocalUserDbObsoleteGroup     OBJECT-GROUP
    OBJECTS     {
        tmnxLocUsrDbPppoeCIdMaskPreStr,
        tmnxLocUsrDbPppoeCIdMaskPreNum,
        tmnxLocUsrDbPppoeCIdMaskSufStr,
        tmnxLocUsrDbPppoeCIdMaskSufNum,
        tmnxLocUsrDbDhcpCIdMaskPreStr,
        tmnxLocUsrDbDhcpCIdMaskPreNum,
        tmnxLocUsrDbDhcpCIdMaskSufStr,
        tmnxLocUsrDbDhcpCIdMaskSufNum
    }
    STATUS      current
    DESCRIPTION
        "The group of obsolete objects."
    ::= { tmnxLocalUserDbGroups 9 }

tmnxLocalUserDbToolsV7v0Group    OBJECT-GROUP
    OBJECTS     {
        tmnxLocUsrDbPppoeAuthDbName,
        tmnxLocUsrDbPppoeAuthUsrName,
        tmnxLocUsrDbPppoeAuthPwd,
        tmnxLocUsrDbPppoeAuthenticate,
        tmnxLocUsrDbPppoeAuthSuccessful,
        tmnxLocUsrDbPppoeAuthErrorMsg,
        tmnxLocUsrDbPppoeAuthTime,
        tmnxLocUsrDbPppoeAuthHostName,
        tmnxLocUsrDbPppoeAuthMacAddress,
        tmnxLocUsrDbPppoeAuthRemoteId,
        tmnxLocUsrDbPppoeAuthCircuitIdFmt,
        tmnxLocUsrDbPppoeAuthCircuitId,
        tmnxLocUsrDbPppoeAuthServiceName
    }
    STATUS      obsolete
    DESCRIPTION
        "The group of objects supporting local user database capability on
         Nokia SROS series systems."
    ::= { tmnxLocalUserDbGroups 10 }

tmnxLocalUserDbRadiusFllbckGroup OBJECT-GROUP
    OBJECTS     {
        tmnxLocUsrDbPppoeDefMsapPolicy,
        tmnxLocUsrDbPppoeDefMsapService,
        tmnxLocUsrDbPppoeDefMsapGroupIf,
        tmnxLocUsrDbDhcpDefMsapPolicy,
        tmnxLocUsrDbDhcpDefMsapService,
        tmnxLocUsrDbDhcpDefMsapGroupIf,
        tmnxLocUsrDbDhcpRetailerSvcId
    }
    STATUS      current
    DESCRIPTION
        "The group of objects supporting management of RADIUS fallback
         capabilities for local user databases on Nokia SROS series systems."
    ::= { tmnxLocalUserDbGroups 11 }

tmnxLocalUserDbDhcpV8v0Group     OBJECT-GROUP
    OBJECTS     {
        tmnxLocUsrDbDhcpTableLastChange,
        tmnxLocUsrDbDhcpRowStatus,
        tmnxLocUsrDbDhcpLastChangeTime,
        tmnxLocUsrDbDhcpAdminState,
        tmnxLocUsrDbDhcpMacAddress,
        tmnxLocUsrDbDhcpCircuitIdFmt,
        tmnxLocUsrDbDhcpCircuitId,
        tmnxLocUsrDbDhcpRemoteId,
        tmnxLocUsrDbDhcpSystemId,
        tmnxLocUsrDbDhcpServiceId,
        tmnxLocUsrDbDhcpSapId,
        tmnxLocUsrDbDhcpString,
        tmnxLocUsrDbDhcpOption60,
        tmnxLocUsrDbDhcpAddrType,
        tmnxLocUsrDbDhcpAddress,
        tmnxLocUsrDbDhcpPool,
        tmnxLocUsrDbDhcpUseGiAddress,
        tmnxLocUsrDbDhcpIdStringOptNum,
        tmnxLocUsrDbDhcpSubscriberId,
        tmnxLocUsrDbDhcpSlaProfString,
        tmnxLocUsrDbDhcpSubProfString,
        tmnxLocUsrDbDhcpAppProfString,
        tmnxLocUsrDbDhcpAncpString,
        tmnxLocUsrDbDhcpInterDestId,
        tmnxLocUsrDbDhcpAuthPolicy,
        tmnxLocUsrDbDhcpServerAddrType,
        tmnxLocUsrDbDhcpServerAddress,
        tmnxLocUsrDbDhcpAuthDomainName,
        tmnxLocUsrDbDhcpCategoryMapName,
        tmnxLocUsrDbDhcpOption60Fmt,
        tmnxLocUsrDbDhcpUseClientPool,
        tmnxLocUsrDbDhcpUnMacAddress,
        tmnxLocUsrDbDhcpUnCircuitId,
        tmnxLocUsrDbDhcpUnRemoteId,
        tmnxLocUsrDbDhcpUnSystemId,
        tmnxLocUsrDbDhcpUnServiceId,
        tmnxLocUsrDbDhcpUnSapId,
        tmnxLocUsrDbDhcpUnString,
        tmnxLocUsrDbDhcpUnOption60,
        tmnxLocUsrDbDhcpUnmatchedReason,
        tmnxLocUsrDbDhcpOptionTableLstCh,
        tmnxLocUsrDbDhcpOptionRowStatus,
        tmnxLocUsrDbDhcpOptionLastChngTm,
        tmnxLocUsrDbDhcpOptionType,
        tmnxLocUsrDbDhcpOptionValue,
        tmnxLocUsrDbDhcpMaskTableLstCh,
        tmnxLocUsrDbDhcpMaskRowStatus,
        tmnxLocUsrDbDhcpMaskPreStr,
        tmnxLocUsrDbDhcpMaskPreNum,
        tmnxLocUsrDbDhcpMaskSufStr,
        tmnxLocUsrDbDhcpMaskSufNum,
        tmnxLocUsrDbDhcpRemoteIdFmt,
        tmnxLocUsrDbDhcpIpv6Addr,
        tmnxLocUsrDbDhcpIpv6Pfx,
        tmnxLocUsrDbDhcpIpv6PfxLen
    }
    STATUS      current
    DESCRIPTION
        "The group of objects supporting local user databases for DHCP hosts on
         Nokia SROS series systems release 8.0."
    ::= { tmnxLocalUserDbGroups 12 }

tmnxLocalUserDbPppoeV8v0Group    OBJECT-GROUP
    OBJECTS     {
        tmnxLocUsrDbPppoeTableLastChange,
        tmnxLocUsrDbPppoeRowStatus,
        tmnxLocUsrDbPppoeLastChangeTime,
        tmnxLocUsrDbPppoeAdminState,
        tmnxLocUsrDbPppoeMacAddress,
        tmnxLocUsrDbPppoeCircuitId,
        tmnxLocUsrDbPppoeCircuitIdFmt,
        tmnxLocUsrDbPppoeRemoteId,
        tmnxLocUsrDbPppoeUserNameFormat,
        tmnxLocUsrDbPppoeUserName,
        tmnxLocUsrDbPppoePasswordType,
        tmnxLocUsrDbPppoePassword,
        tmnxLocUsrDbPppoeAddrType,
        tmnxLocUsrDbPppoeAddress,
        tmnxLocUsrDbPppoePool,
        tmnxLocUsrDbPppoeUseGiAddress,
        tmnxLocUsrDbPppoeIdStringOptNum,
        tmnxLocUsrDbPppoeSubscriberId,
        tmnxLocUsrDbPppoeSlaProfString,
        tmnxLocUsrDbPppoeSubProfString,
        tmnxLocUsrDbPppoeAppProfString,
        tmnxLocUsrDbPppoeAncpString,
        tmnxLocUsrDbPppoeInterDestId,
        tmnxLocUsrDbPppoeUseClientPool,
        tmnxLocUsrDbPppoePadoDelay,
        tmnxLocUsrDbPppoeServiceName,
        tmnxLocUsrDbPppoeL2tpTunnelGroup,
        tmnxLocUsrDbPppoeAuthPolicy,
        tmnxLocUsrDbPppoeRetailerSvcId,
        tmnxLocUsrDbPppoeCategoryMapName,
        tmnxLocUsrDbPppoeUnMacAddress,
        tmnxLocUsrDbPppoeUnCircuitId,
        tmnxLocUsrDbPppoeUnRemoteId,
        tmnxLocUsrDbPppoeUnUserNameFmt,
        tmnxLocUsrDbPppoeUnUserName,
        tmnxLocUsrDbPppoeUnmatchedReason,
        tmnxLocUsrDbDhcpUnDuplicateHost,
        tmnxLocUsrDbPppoeUnDuplicateHost,
        tmnxLocUsrDbPppoeUnServiceName,
        tmnxLocUsrDbPppoeOptionTbleLstCh,
        tmnxLocUsrDbPppoeOptionRowStatus,
        tmnxLocUsrDbPppoeOptionLstChngTm,
        tmnxLocUsrDbPppoeOptionType,
        tmnxLocUsrDbPppoeOptionValue,
        tmnxLocUsrDbPppoeMaskTableLstCh,
        tmnxLocUsrDbPppoeMaskRowStatus,
        tmnxLocUsrDbPppoeMaskPreStr,
        tmnxLocUsrDbPppoeMaskPreNum,
        tmnxLocUsrDbPppoeMaskSufStr,
        tmnxLocUsrDbPppoeMaskSufNum,
        tmnxLocUsrDbPppoeRemoteIdFmt,
        tmnxLocUsrDbPppoeL2tpSvcId,
        tmnxLocUsrDbPppoeService,
        tmnxLocUsrDbPppoeInterface
    }
    STATUS      current
    DESCRIPTION
        "The group of objects supporting local user databases for PPPoE hosts
         on Nokia SROS series systems release 8.0."
    ::= { tmnxLocalUserDbGroups 13 }

tmnxLocalUserDbToolsV8v0Group    OBJECT-GROUP
    OBJECTS     {
        tmnxLocUsrDbPppoeAuthDbName,
        tmnxLocUsrDbPppoeAuthUsrName,
        tmnxLocUsrDbPppoeAuthPwd,
        tmnxLocUsrDbPppoeAuthenticate,
        tmnxLocUsrDbPppoeAuthSuccessful,
        tmnxLocUsrDbPppoeAuthErrorMsg,
        tmnxLocUsrDbPppoeAuthTime,
        tmnxLocUsrDbPppoeAuthHostName,
        tmnxLocUsrDbPppoeAuthMacAddress,
        tmnxLocUsrDbPppoeAuthRemoteId,
        tmnxLocUsrDbPppoeAuthCircuitIdFmt,
        tmnxLocUsrDbPppoeAuthCircuitId,
        tmnxLocUsrDbPppoeAuthServiceName,
        tmnxLocUsrDbPppoeAuthRemoteIdFmt
    }
    STATUS      current
    DESCRIPTION
        "The group of objects supporting local user database capability on
         Nokia SROS series systems release 8.0."
    ::= { tmnxLocalUserDbGroups 14 }

tmnxLocalUserDbHostGroup         OBJECT-GROUP
    OBJECTS     {
        tmnxLudbHostTableLastChange,
        tmnxLudbHostRowStatus,
        tmnxLudbHostLastChangeTime,
        tmnxLudbHostAdminState,
        tmnxLudbHostApplications,
        tmnxLudbHostMacAddress,
        tmnxLudbHostCircuitIdFmt,
        tmnxLudbHostCircuitId,
        tmnxLudbHostRemoteIdFmt,
        tmnxLudbHostRemoteId,
        tmnxLudbHostAddrType,
        tmnxLudbHostAddress,
        tmnxLudbHostPool,
        tmnxLudbHostUseGiAddress,
        tmnxLudbHostIdStringOptNum,
        tmnxLudbHostSubscriberId,
        tmnxLudbHostSlaProfString,
        tmnxLudbHostSubProfString,
        tmnxLudbHostAppProfString,
        tmnxLudbHostAncpString,
        tmnxLudbHostInterDestId,
        tmnxLudbHostUseClientPool,
        tmnxLudbHostAuthPolicy,
        tmnxLudbHostRetailerSvcId,
        tmnxLudbHostCategoryMapName,
        tmnxLudbHostDefMsapPolicy,
        tmnxLudbHostDefMsapService,
        tmnxLudbHostDefMsapGroupIf,
        tmnxLudbHostSystemId,
        tmnxLudbHostServiceId,
        tmnxLudbHostSapId,
        tmnxLudbHostString,
        tmnxLudbHostIpv6Addr,
        tmnxLudbHostIpv6Pfx,
        tmnxLudbHostIpv6PfxLen,
        tmnxLudbHostAuthDomainName,
        tmnxLudbHostDhcpOption60Fmt,
        tmnxLudbHostDhcpOption60,
        tmnxLudbHostDhcpRelayAddrType,
        tmnxLudbHostDhcpRelayAddress,
        tmnxLudbHostPppUserNameFormat,
        tmnxLudbHostPppUserName,
        tmnxLudbHostPppPasswordType,
        tmnxLudbHostPppPassword,
        tmnxLudbHostPppServiceName,
        tmnxLudbHostPppL2tpTunnelGroup,
        tmnxLudbHostPppL2tpSvcId,
        tmnxLudbHostPppService,
        tmnxLudbHostPppInterface,
        tmnxLudbHostPppoePadoDelay
    }
    STATUS      current
    DESCRIPTION
        "The group of objects supporting configuration of local user database
         host templates on Nokia SROS series systems."
    ::= { tmnxLocalUserDbGroups 20 }

tmnxLocalUserDbPppoeV9v0Group    OBJECT-GROUP
    OBJECTS     {
        tmnxLocUsrDbPppoePrefixLength,
        tmnxLocUsrDbPppoeFltrProfString,
        tmnxLocUsrDbPppoeSapId,
        tmnxLocUsrDbPppoeUnSapId,
        tmnxLocUsrDbPppoeAuthSapId,
        tmnxLocUsrDbPppoeIngIpv4FltrId,
        tmnxLocUsrDbPppoeEgrIpv4FltrId,
        tmnxLocUsrDbPppoeIngIpv6FltrId,
        tmnxLocUsrDbPppoeEgrIpv6FltrId,
        tmnxLocUsrDbPppoeUseGiAddrScope
    }
    STATUS      current
    DESCRIPTION
        "The group of objects supporting local user databases for PPPoE hosts
         on Nokia SROS series systems added in release 9.0."
    ::= { tmnxLocalUserDbGroups 21 }

tmnxLocalUserDbDhcpV9v0Group     OBJECT-GROUP
    OBJECTS     {
        tmnxLocUsrDbDhcpIpv6WanAddrPool,
        tmnxLocUsrDbDhcpIpv6DelPfxPool,
        tmnxLocUsrDbDhcpFltrProfString,
        tmnxLocUsrDbDhcpIngIpv4FltrId,
        tmnxLocUsrDbDhcpEgrIpv4FltrId,
        tmnxLocUsrDbDhcpIngIpv6FltrId,
        tmnxLocUsrDbDhcpEgrIpv6FltrId,
        tmnxLocUsrDbDhcpUseGiAddrScope
    }
    STATUS      current
    DESCRIPTION
        "The group of objects supporting local user databases for DHCP hosts on
         Nokia SROS series systems release 9.0."
    ::= { tmnxLocalUserDbGroups 22 }

tmnxLocalUserDbFltrProfGroup     OBJECT-GROUP
    OBJECTS     {
        tmnxLudbHostFltrProfString
    }
    STATUS      current
    DESCRIPTION
        "The group of objects supporting configuration of local user database
         filter profiles on Nokia SROS series systems."
    ::= { tmnxLocalUserDbGroups 23 }

tmnxLudbPppHostGroup             OBJECT-GROUP
    OBJECTS     {
        tmnxLudbPppAleTableLastChange,
        tmnxLudbPppAleRowStatus,
        tmnxLudbPppAleLastChangeTime,
        tmnxLudbPppAleEncapOffsetMode,
        tmnxLudbPppAleEncapOffset,
        tmnxLudbPppAleRateDown
    }
    STATUS      current
    DESCRIPTION
        "The group of objects supporting local user databases for PPP hosts on
         Nokia SROS series systems."
    ::= { tmnxLocalUserDbGroups 24 }

tmnxLudbRadproxGroup             OBJECT-GROUP
    OBJECTS     {
        tmnxLudbRadproxCacheTableLastCh,
        tmnxLudbRadproxCacheLastCh,
        tmnxLudbRadproxCacheService,
        tmnxLudbRadproxCacheServer,
        tmnxLudbRadproxCacheMatchType,
        tmnxLudbRadproxCacheMatchOption,
        tmnxLudbRadproxCacheMacFormat,
        tmnxLudbRadproxCacheFailAction
    }
    STATUS      current
    DESCRIPTION
        "The group of objects supporting RADIUS Proxy cache lookup for local
         user database hosts on Nokia SROS series systems."
    ::= { tmnxLocalUserDbGroups 25 }

tmnxLocalUserDbDhcpV11v0Group    OBJECT-GROUP
    OBJECTS     {
        tmnxLocUsrDbDhcpSecPool,
        tmnxLocUsrDbDhcpUseCPDelimiter,
        tmnxLocUsrDbPppoeSecPool,
        tmnxLocUsrDbPppoePreAuthPolicy,
        tmnxLocUsrDbPppoeUseCPDelimiter,
        tmnxLocUsrDbDhcpEncTagRangeType,
        tmnxLocUsrDbDhcpEncTagRangeStrt,
        tmnxLocUsrDbDhcpEncTagRangeEnd,
        tmnxLocUsrDbPppoeEncTagRangeType,
        tmnxLocUsrDbPppoeEncTagRangeStrt,
        tmnxLocUsrDbPppoeEncTagRangeEnd,
        tmnxLocUsrDbDhcpMsapGroupIfPfx,
        tmnxLocUsrDbDhcpMsapGroupIfSfx,
        tmnxLocUsrDbPppoeMsapGroupIfPfx,
        tmnxLocUsrDbPppoeMsapGroupIfSfx,
        tmnxLocUsrDbPppoeAcctPolicy,
        tmnxLocUsrDbPppoeDuplAcctPolicy,
        tmnxLocUsrDbDhcpIpv6ReqDelPfxLn,
        tmnxLocUsrDbDhcpAcctPolicy,
        tmnxLocUsrDbDhcpDuplAcctPolicy,
        tmnxLocUsrDbDhcpOption6TblLstCh,
        tmnxLocUsrDbDhcpOption6RowStatus,
        tmnxLocUsrDbDhcpOption6LstChngTm,
        tmnxLocUsrDbDhcpOption6Type,
        tmnxLocUsrDbDhcpOption6Value,
        tmnxLocUsrDbDhcpIpv6SlaacPfx,
        tmnxLocUsrDbDhcpIpv6SlaacPfxLen,
        tmnxLocUsrDbPppoeIpv6Addr,
        tmnxLocUsrDbPppoeIpv6DelPfx,
        tmnxLocUsrDbPppoeIpv6DelPfxLen,
        tmnxLocUsrDbPppoeIpv6ReqDelPfxLn,
        tmnxLocUsrDbPppoeIpv6SlaacPfx,
        tmnxLocUsrDbPppoeIpv6SlaacPfxLen,
        tmnxLocUsrDbPppoeForceIpv6cp,
        tmnxLocUsrDbPppoeIpv6DelPfxPool,
        tmnxLocUsrDbPppoeIpv6WanAddrPool,
        tmnxLocUsrDbPppOption6TblLstCh,
        tmnxLocUsrDbPppOption6RowSts,
        tmnxLocUsrDbPppOption6LstChgTm,
        tmnxLocUsrDbPppOption6Type,
        tmnxLocUsrDbPppOption6Value
    }
    STATUS      current
    DESCRIPTION
        "The group of objects supporting local user databases for DHCP hosts on
         Nokia SROS series systems release 11.0."
    ::= { tmnxLocalUserDbGroups 26 }

tmnxLudbPppAliGroup              OBJECT-GROUP
    OBJECTS     {
        tmnxLudbPppAliTableLastChange,
        tmnxLudbPppAliLastChangeTime,
        tmnxLudbPppAliCircuitIdType,
        tmnxLudbPppAliCircuitId,
        tmnxLudbPppAliRemoteIdType,
        tmnxLudbPppAliRemoteId
    }
    STATUS      current
    DESCRIPTION
        "The group of objects supporting local user database Access Loop
         Information configuration for PPP hosts on Nokia SROS series systems."
    ::= { tmnxLocalUserDbGroups 27 }

tmnxLudbNotifyObjsV11v0Group     OBJECT-GROUP
    OBJECTS     {
        tmnxLudbNotifyPortId
    }
    STATUS      current
    DESCRIPTION
        "The group of objects supporting Local User Database notifications on
         Nokia SROS release 11.0 series systems."
    ::= { tmnxLocalUserDbGroups 28 }

tmnxLocalUserDbDhcpV12v0Group    OBJECT-GROUP
    OBJECTS     {
        tmnxLocUsrDbDhcpDerivedId,
        tmnxLudbDhcp2WppPortalSvcId,
        tmnxLudbDhcp2WppPortalName,
        tmnxLudbDhcp2WppSubProfile,
        tmnxLudbDhcp2WppSLAProfile,
        tmnxLudbDhcp2WppAppProfile,
        tmnxLudbDhcp2WppRestDiscon,
        tmnxLudbDhcp2TableLastChange,
        tmnxLudbDhcp2LastChangeTime,
        tmnxLudbDhcp2GiAddrType,
        tmnxLudbDhcp2GiAddr,
        tmnxLudbDhcp2LinkAddrType,
        tmnxLudbDhcp2LinkAddr,
        tmnxLudbDhcp2Server6AddrType,
        tmnxLudbDhcp2Server6Addr,
        tmnxLudbDhcp2Ipv6LeaseRenew,
        tmnxLudbDhcp2Ipv6LeaseRebind,
        tmnxLudbDhcp2Ipv6LeaseValidLife,
        tmnxLudbDhcp2Ipv6LeasePrefLife,
        tmnxLudbPpp2TableLastChange,
        tmnxLudbPpp2LastChangeTime,
        tmnxLudbPpp2Ipv6LeaseRenew,
        tmnxLudbPpp2Ipv6LeaseRebind,
        tmnxLudbPpp2Ipv6LeaseValidLife,
        tmnxLudbPpp2Ipv6LeasePrefLife,
        tmnxLocUsrDbDhcpIpv6SlaacPfxPl,
        tmnxLudbDhcp2DiamAppPlcy,
        tmnxLudbPpp2DiamAppPlcy
    }
    STATUS      current
    DESCRIPTION
        "The group of objects supporting local user databases for DHCP hosts on
         Nokia SROS series systems release 12.0."
    ::= { tmnxLocalUserDbGroups 29 }

tmnxLudbRadproxV12v0Group        OBJECT-GROUP
    OBJECTS     {
        tmnxLudbRadproxCacheMatchOption6
    }
    STATUS      current
    DESCRIPTION
        "The group of objects supporting RADIUS Proxy cache lookup for local
         user database hosts on Nokia SROS series systems release 12.0."
    ::= { tmnxLocalUserDbGroups 30 }

tmnxLocalUserDbPppoeV12v0Group   OBJECT-GROUP
    OBJECTS     {
        tmnxLocUsrDbPppoeIpv6SlaacPfxPl
    }
    STATUS      current
    DESCRIPTION
        "The group of new objects supporting local user databases for PPPoE
         hosts on Nokia SROS series systems release 12.0."
    ::= { tmnxLocalUserDbGroups 31 }

tmnxLudbToClntOptGroup           OBJECT-GROUP
    OBJECTS     {
        tmnxLudbToClntOptTableLstCh,
        tmnxLudbToClntOptRowStatus,
        tmnxLudbToClntOptLastCh,
        tmnxLudbToClntOptType,
        tmnxLudbToClntOptValue
    }
    STATUS      current
    DESCRIPTION
        "The group of objects supporting the configuration of DHCP and DHCP6
         options in the local user database to send towards the the DHCP client
         on Nokia SROS series systems."
    ::= { tmnxLocalUserDbGroups 32 }

tmnxLudbRipPlcyV13v0Group        OBJECT-GROUP
    OBJECTS     {
        tmnxLudbDhcp2RipPolicy,
        tmnxLudbPpp2RipPolicy
    }
    STATUS      current
    DESCRIPTION
        "The group of new objects supporting Rip Policy on local user databases
         for hosts on Nokia SROS series systems release 13.0."
    ::= { tmnxLocalUserDbGroups 33 }

tmnxLudbDiameterAuthPlcyGroup    OBJECT-GROUP
    OBJECTS     {
        tmnxLudbPpp2DiameterAuthPolicy,
        tmnxLudbDhcp2DiameterAuthPolicy
    }
    STATUS      current
    DESCRIPTION
        "The group of new objects supporting Diameter authentication on local
         user databases for hosts on Nokia SROS series systems release."
    ::= { tmnxLocalUserDbGroups 34 }

tmnxLocalUserDbPppoeDfGroup      OBJECT-GROUP
    OBJECTS     {
        tmnxLudbPpp2IgnoreDfBit
    }
    STATUS      current
    DESCRIPTION
        "The group of objects supporting Don't Fragment behavior control for
         PPPoE local user database hosts on Nokia SROS series systems."
    ::= { tmnxLocalUserDbGroups 35 }

tmnxLocalUserDbPppoeV14v0Group   OBJECT-GROUP
    OBJECTS     {
        tmnxLudbPpp2UserDb,
        tmnxLocUsrDbPppoeDerivedId,
        tmnxLocUsrDbPppoeAuthDerivedId
    }
    STATUS      current
    DESCRIPTION
        "The group of new objects supporting local user databases for PPPoE
         hosts on Nokia SROS series systems release 14.0."
    ::= { tmnxLocalUserDbGroups 36 }

tmnxLocalUserDbIpoeV14v0Group    OBJECT-GROUP
    OBJECTS     {
        tmnxLocUsrDbDhcpIpPrefixAddrType,
        tmnxLocUsrDbDhcpIpPrefixAddr,
        tmnxLocUsrDbDhcpIpPrefixLength
    }
    STATUS      current
    DESCRIPTION
        "The group of new objects supporting local user databases for IPOE
         hosts on Nokia SROS series systems release 14.0."
    ::= { tmnxLocalUserDbGroups 37 }

tmnxLudbToServerOptGroup         OBJECT-GROUP
    OBJECTS     {
        tmnxLudbToServerOptTableLstCh,
        tmnxLudbToServerOptRowStatus,
        tmnxLudbToServerOptLastCh,
        tmnxLudbToServerOptType,
        tmnxLudbToServerOptValue
    }
    STATUS      current
    DESCRIPTION
        "The group of objects supporting the configuration of DHCP6 options in
         the local user database to send towards the the DHCP server on Nokia
         SROS series systems."
    ::= { tmnxLocalUserDbGroups 38 }

tmnxLocalUserDbV14v0Group        OBJECT-GROUP
    OBJECTS     {
        tmnxLocUsrDbCreationOrigin
    }
    STATUS      current
    DESCRIPTION
        "The group of objects supporting local user database capability on
         Nokia SROS series systems in release 14.0."
    ::= { tmnxLocalUserDbGroups 39 }

tmnxLocalUserDbPppoeV15v0Group   OBJECT-GROUP
    OBJECTS     {
        tmnxLudbPpp2SteeringProfStr,
        tmnxLudbPpp2PadiAuthPolicy,
        tmnxLudbPpp2RtrAdvPlcy
    }
    STATUS      current
    DESCRIPTION
        "The group of new objects supporting local user databases for PPPoE
         hosts on Nokia SROS series systems release 15.0."
    ::= { tmnxLocalUserDbGroups 40 }

tmnxLocalUserDbV15v0Group        OBJECT-GROUP
    OBJECTS     {
        tmnxLudbDhcp2WppPortalGroupName,
        tmnxLudbMldImpPlcyTableLstCh,
        tmnxLudbMldImpPlcyRowStatus,
        tmnxLudbMldImpPlcyLastCh,
        tmnxLudbDhcp2RtrAdvPlcy,
        tmnxLudbDhcp2Service,
        tmnxLudbDhcp2Interface
    }
    STATUS      current
    DESCRIPTION
        "The group of objects supporting local user database capability on
         Nokia SROS series systems in release 15.0."
    ::= { tmnxLocalUserDbGroups 41 }

tmnxLocalUserDbV16v0Group        OBJECT-GROUP
    OBJECTS     {
        tmnxLocUsrDbDhcpSpiGroupId,
        tmnxLudbPpp2SpiGroupId,
        tmnxLudbRadproxCacheServiceName,
        tmnxLudbDhcp2GrpIfServiceName,
        tmnxLudbDhcp2RetailerServiceName,
        tmnxLudbDhcp2IdentServiceName,
        tmnxLudbPpp2RetailerServiceName,
        tmnxLudbPpp2GrpIfServiceName,
        tmnxLudbPpp2L2tpGroupServiceName,
        tmnxLocUsrDbPppoeOptionDisplay,
        tmnxLocUsrDbDhcpOptionDisplay,
        tmnxLudbToClntOptDisplay,
        tmnxLudbToServerOptDisplay,
        tmnxLocUsrDbDhcpOption6Display,
        tmnxLocUsrDbPppOption6Display
    }
    STATUS      current
    DESCRIPTION
        "The group of objects supporting local user database capability on
         Nokia SROS series systems added in release 16.0."
    ::= { tmnxLocalUserDbGroups 42 }

tmnxLocalUserDbV20v0Group        OBJECT-GROUP
    OBJECTS     {
        tmnxLudbDhcp2EncTagRgOuterStart,
        tmnxLudbDhcp2EncTagRgOuterEnd,
        tmnxLudbDhcp2EncTagRgInnerStart,
        tmnxLudbDhcp2EncTagRgInnerEnd,
        tmnxLudbPpp2EncTagRgOuterStart,
        tmnxLudbPpp2EncTagRgOuterEnd,
        tmnxLudbPpp2EncTagRgInnerStart,
        tmnxLudbPpp2EncTagRgInnerEnd,
        tmnxLocUsrDbDhcpUnDerivedId,
        tmnxLocUsrDbDhcpUnEncTagRgType,
        tmnxLocUsrDbDhcpUnEncTagRgStart,
        tmnxLocUsrDbDhcpUnEncTagRgEnd,
        tmnxLocUsrDbDhcpUnEncTagRgOutSta,
        tmnxLocUsrDbDhcpUnEncTagRgOutEnd,
        tmnxLocUsrDbDhcpUnEncTagRgInnSta,
        tmnxLocUsrDbDhcpUnEncTagRgInnEnd,
        tmnxLocUsrDbDhcpUnIpPrefAddrType,
        tmnxLocUsrDbDhcpUnIpPrefAddr,
        tmnxLocUsrDbDhcpUnIpPrefLength,
        tmnxLocUsrDbPppoeUnDerivedId,
        tmnxLocUsrDbPppoeUnEncTgRgType,
        tmnxLocUsrDbPppoeUnEncTgRgStart,
        tmnxLocUsrDbPppoeUnEncTgRgEnd,
        tmnxLocUsrDbPppoeUnEncTgRgOutSta,
        tmnxLocUsrDbPppoeUnEncTgRgOutEnd,
        tmnxLocUsrDbPppoeUnEncTgRgInnSta,
        tmnxLocUsrDbPppoeUnEncTgRgInnEnd
    }
    STATUS      current
    DESCRIPTION
        "The group of new objects supporting local user databases for PPPoE
         hosts on Nokia SROS series systems release 20.0."
    ::= { tmnxLocalUserDbGroups 43 }

tmnxLocalUserDbPppoeV22v0Group   OBJECT-GROUP
    OBJECTS     {
        tmnxLudbPpp2MacMaxSessionsOvr
    }
    STATUS      current
    DESCRIPTION
        "The group of new objects supporting local user databases for PPPoE
         hosts on Nokia SROS series systems release 22.0."
    ::= { tmnxLocalUserDbGroups 44 }

tmnxLocalUserDbPppoeV23v0Group   OBJECT-GROUP
    OBJECTS     {
        tmnxLudbPpp2KaInterval,
        tmnxLudbPpp2KaHoldUpMplier
    }
    STATUS      current
    DESCRIPTION
        "The group of new objects supporting local user databases for PPPoE
         hosts on Nokia SROS series systems release 23.0."
    ::= { tmnxLocalUserDbGroups 45 }

tmnxLocalUserDbV24v0Group        OBJECT-GROUP
    OBJECTS     {
        tmnxLudbDhcp2DuidEn,
        tmnxLudbDhcp2DuidLlLlt
    }
    STATUS      current
    DESCRIPTION
        "The group of objects supporting local user database capability on
         Nokia SROS series systems added in release 24.0."
    ::= { tmnxLocalUserDbGroups 46 }

tmnxLocalUserDbNotifGroups       OBJECT IDENTIFIER ::= { tmnxLocalUserDbConformance 3 }

tmnxLudbNotifV11v0Group          NOTIFICATION-GROUP
    NOTIFICATIONS {
        tmnxLudbDhcpGroupIfTooLong,
        tmnxLudbPppoeGroupIfTooLong
    }
    STATUS      current
    DESCRIPTION
        "The group of objects supporting traps for the Local User Database
         capability on Nokia SROS release 11.0 series systems."
    ::= { tmnxLocalUserDbNotifGroups 1 }

tmnxLocalUserDbNotifyPrefix      OBJECT IDENTIFIER ::= { tmnxSRNotifyPrefix 51 }

tmnxLocalUserDbNotifications     OBJECT IDENTIFIER ::= { tmnxLocalUserDbNotifyPrefix 0 }

tmnxLudbDhcpGroupIfTooLong       NOTIFICATION-TYPE
    OBJECTS     {
        tmnxLocUsrDbDhcpDefMsapGroupIf,
        tmnxLudbNotifyPortId
    }
    STATUS      current
    DESCRIPTION
        "The tmnxLudbDhcpGroupIfTooLong notification is generated for a DHCP
         host when the default MSAP group-interface name concatenated with the
         port-id is longer than 32 characters."
    ::= { tmnxLocalUserDbNotifications 1 }

tmnxLudbPppoeGroupIfTooLong      NOTIFICATION-TYPE
    OBJECTS     {
        tmnxLocUsrDbPppoeDefMsapGroupIf,
        tmnxLudbNotifyPortId
    }
    STATUS      current
    DESCRIPTION
        "The tmnxLudbPppoeGroupIfTooLong notification is generated for a DHCP
         host when the default MSAP group-interface name concatenated with the
         port-id is longer than 32 characters."
    ::= { tmnxLocalUserDbNotifications 2 }

END
