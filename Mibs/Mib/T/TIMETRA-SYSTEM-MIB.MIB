TIMETRA-SYSTEM-MIB DEFINITIONS ::= BEGIN

IMPORTS
    smLaunchEntry, smLaunchError,
    smLaunchName, smLaunchOwner,
    smLaunchScriptName, smLaunchScriptOwner,
    smRunEntry, smRunIndex
                                                         FROM DISMAN-SCRIPT-MIB
    CounterBasedGauge64
                                                         FROM HCNUM-TC
    InetAddress, InetAddressIPv6,
    InetAddressPrefixLength,
    InetAddressType, InetPortNumber
                                                         FROM INET-ADDRESS-MIB
    snmpCommunityEntry
                                                         FROM SNMP-COMMUNITY-MIB
    MODULE-COMPLIANCE, NOTIFICATION-GROUP,
    OBJECT-GROUP
                                                         FROM SNMPv2-CONF
    Counter32, Counter64, Gauge32,
    Integer32, IpAddress, MODULE-IDENTITY,
    NOTIFICATION-TYPE, OBJECT-TYPE,
    Unsigned32
                                                         FROM SNMPv2-SMI
    DateAndTime, DisplayString, MacAddress,
    RowPointer, RowStatus,
    TEXTUAL-CONVENTION, TimeStamp,
    TruthValue
                                                         FROM SNMPv2-TC
    TmnxSlotNum, tmnxChassisBaseMacAddress,
    tmnxChassisIndex,
    tmnxChassisNotifyHwIndex,
    tmnxCpmCardNum, tmnxCpmCardSlotNum,
    tmnxFabricSlotNum, tmnxHwClass, tmnxHwID
                                                         FROM TIMETRA-CHASSIS-MIB
    timetraSRMIBModules, tmnxSRConfs,
    tmnxSRNotifyPrefix, tmnxSRObjs
                                                         FROM TIMETRA-GLOBAL-MIB
    tmnxEhsHEntryMinDelay,
    tmnxEhsHEntryMinDelayInterval,
    tmnxEhsHEntryScriptPlcyName,
    tmnxEhsHEntryScriptPlcyOwner,
    tmnxEhsHandlerDescription,
    tmnxLogExecRollbackOpIndex,
    tmnxLogExecRollbackOpType
                                                         FROM TIMETRA-LOG-MIB
    IpAddressPrefixLength, TDSCPNameOrEmpty,
    TItemDescription, TLDisplayString,
    TLNamedItem, TLNamedItemOrEmpty,
    TNamedItem, TNamedItemOrEmpty,
    TTcpUdpPort, TmnxActionType,
    TmnxAdminState,
    TmnxAdminStateTruthValue,
    TmnxBofDisplayStringURL, TmnxCliEngine,
    TmnxDisplayStringURL,
    TmnxEnabledDisabled,
    TmnxEnabledDisabledAdminState,
    TmnxLongDisplayString, TmnxOperState,
    TmnxScriptAuthType, TmnxServId,
    TmnxUuid, TmnxVRtrID, TmnxVRtrIDOrZero
                                                         FROM TIMETRA-TC-MIB
    ;

timetraSysMIBModule              MODULE-IDENTITY
    LAST-UPDATED "201701010000Z"
    ORGANIZATION "Nokia"
    CONTACT-INFO
        "Nokia SROS Support
         Web: http://www.nokia.com"
    DESCRIPTION
        "This document is the System SNMP MIB module for the Nokia
         SROS device.  The System MIB module defines SNMP objects to
         manage and provision system features.

         Copyright 2003-2018 Nokia. All rights reserved. Reproduction of this
         document is authorized on the condition that the foregoing copyright
         notice is included.

         This SNMP MIB module (Specification) embodies Nokia's
         proprietary intellectual property.  Nokia retains
         all title and ownership in the Specification, including any
         revisions.

         Nokia grants all interested parties a non-exclusive license to use and
         distribute an unmodified copy of this Specification in connection with
         management of Nokia products, and without fee, provided this copyright
         notice and license appear on all copies.

         This Specification is supplied `as is', and Nokia makes no warranty,
         either express or implied, as to the use, operation, condition, or
         performance of the Specification."

    REVISION    "201701010000Z"
    DESCRIPTION
        "Rev 15.0               1 Jan 2017 00:00
         15.0 release of the TIMETRA-SYSTEM-MIB."

    REVISION    "201601010000Z"
    DESCRIPTION
        "Rev 14.0               1 Jan 2016 00:00
         14.0 release of the TIMETRA-SYSTEM-MIB."

    REVISION    "201406010000Z"
    DESCRIPTION
        "Rev 13.0               01 Jun 2014 00:00
         13.0 release of the TIMETRA-SYSTEM-MIB."

    REVISION    "201401010000Z"
    DESCRIPTION
        "Rev 12.0               01 Jan 2014 00:00
         12.0 release of the TIMETRA-SYSTEM-MIB."

    REVISION    "201102010000Z"
    DESCRIPTION
        "Rev 9.0                01 Feb 2011 00:00
         9.0 release of the TIMETRA-SYSTEM-MIB."

    REVISION    "201001010000Z"
    DESCRIPTION
        "Rev 8.0                01 Jan 2010 00:00
         8.0 release of the TIMETRA-SYSTEM-MIB."

    REVISION    "200902280000Z"
    DESCRIPTION
        "Rev 7.0                28 Feb 2009 00:00
         7.0 release of the TIMETRA-SYSTEM-MIB."

    REVISION    "200801010000Z"
    DESCRIPTION
        "Rev 6.0                01 Jan 2008 00:00
         6.0 release of the TIMETRA-SYSTEM-MIB."

    REVISION    "200701010000Z"
    DESCRIPTION
        "Rev 5.0                01 Jan 2007 00:00
         5.0 release of the TIMETRA-SYSTEM-MIB."

    REVISION    "200603150000Z"
    DESCRIPTION
        "Rev 4.0                15 Mar 2006 00:00
         4.0 release of the TIMETRA-SYSTEM-MIB."

    REVISION    "200508310000Z"
    DESCRIPTION
        "Rev 3.0                31 Aug 2005 00:00
         3.0 release of the TIMETRA-SYSTEM-MIB."

    REVISION    "200501240000Z"
    DESCRIPTION
        "Rev 2.1                24 Jan 2005 00:00
         2.1 release of the TIMETRA-SYSTEM-MIB."

    REVISION    "200401150000Z"
    DESCRIPTION
        "Rev 2.0                15 Jan 2004 00:00
         2.0 release of the TIMETRA-SYSTEM-MIB."

    REVISION    "200308150000Z"
    DESCRIPTION
        "Rev 1.2                15 Aug 2003 00:00
         1.2 release of the TIMETRA-SYSTEM-MIB."

    REVISION    "200301200000Z"
    DESCRIPTION
        "Rev 1.0                20 Jan 2003 00:00
         1.0 Release of the TIMETRA-SYSTEM-MIB."

    REVISION    "200008140000Z"
    DESCRIPTION
        "Rev 0.1                14 Aug 2000 00:00
         First version of the TIMETRA-SYSTEM-MIB."

    ::= { timetraSRMIBModules 1 }

TmnxSsiSyncMode                  ::= TEXTUAL-CONVENTION
    STATUS      current
    DESCRIPTION
        "The value of TmnxSsiSyncMode specifies the type of synchronization
         operation to perform between the primary and secondary CPMs after a
         change has been made to the configuration files or the boot
         environment information contained in the boot options file (bof)."
    SYNTAX      INTEGER {
        none    (1),
        config  (2),
        bootEnv (3)
    }

TmnxSsiSyncRollbackMode          ::= TEXTUAL-CONVENTION
    STATUS      current
    DESCRIPTION
        "The value of TmnxSsiSyncRollbackMode specifies the type of
         synchronization operation to perform between the primary and secondary
         CPMs after a change has been made to the rollback files."
    SYNTAX      INTEGER {
        none           (1),
        rollbackSingle (2),
        rollbackAll    (3)
    }

TmnxSysLicenseApplication        ::= TEXTUAL-CONVENTION
    STATUS      current
    DESCRIPTION
        "The textual convention TmnxSysLicenseApplication represents an
         application in a virtual machine implementation that is subject to
         licensing.

         NAT - Network Address Translation
         WLAN-GW - Wireless Local Area Network Gateway
         LNS - L2TP Network Server
         Subscriber Management
         AA  - Application Assurance"
    SYNTAX      INTEGER {
        none    (0),
        nat     (1),
        wlanGw  (2),
        lns     (3),
        subMgmt (4),
        aa      (5),
        ipsec   (6)
    }

TmnxSysLicenseAppStatsType       ::= TEXTUAL-CONVENTION
    STATUS      current
    DESCRIPTION
        "The textual convention TmnxSysLicenseAppStatsType represents the type
         of statistics collected about an application in a virtual machine
         implementation subject to licensing."
    SYNTAX      INTEGER {
        none                (0),
        lsnSubscribers      (1),
        lsnBandwidth        (2),
        wlanGwUserEquipment (1000),
        wlanGwGtpBearers    (1001),
        lnsTunnels          (2000),
        lnsSessions         (2001),
        subscriberHosts     (3000),
        aaSubscribers       (4000),
        aaBandwidth         (4001),
        ipsecTunnels        (5000),
        ipsecTnlBandwidth   (5001),
        ipTunnels           (5002),
        ipTnlBandwidth      (5003)
    }

TmnxSysLicensingGroup            ::= TEXTUAL-CONVENTION
    STATUS      current
    DESCRIPTION
        "The textual convention TmnxSysLicensingGroup represents a grouping of
         licensed applications.

         system   - System Level Licenses
         services - Service Type Licenses
         nsp      - Network Management Licenses
         isa      - Integrated Services Licenses
         iom      - IOM Card Licenses
         mda      - MDA Licenses
         ports    - Port Licenses"
    SYNTAX      INTEGER {
        system   (0),
        services (1),
        nsp      (2),
        isa      (3),
        iom      (4),
        mda      (5),
        ports    (6)
    }

TmnxSysMonSampleTime             ::= TEXTUAL-CONVENTION
    STATUS      current
    DESCRIPTION
        "The value of TmnxSysMonSampleTime specifies the monitoring sample time
         (in terms of seconds) for a system object."
    SYNTAX      Unsigned32 (1 | 60 | 300)

TmnxSysMonUtilization            ::= TEXTUAL-CONVENTION
    STATUS      current
    DESCRIPTION
        "The value of TmnxSysMonUtilization specifies the utilization/idle
         percentage (in terms 100ths of a percent) for a given sample-time."
    SYNTAX      Gauge32 (0..10000)

TmnxSysMgmtIfDstoreLockState     ::= TEXTUAL-CONVENTION
    STATUS      current
    DESCRIPTION
        "The value of TmnxSysMgmtIfDstoreLockState specifies the datastore lock
         state."
    SYNTAX      INTEGER {
        locked   (1),
        unlocked (2)
    }

TmnxSysNeid                      ::= TEXTUAL-CONVENTION
    DISPLAY-HINT "1x:"
    STATUS      current
    DESCRIPTION
        "The textual convention TmnxSysNeid represents the Network Element
         Identifier.

         The first 8 high-order bits indicate the subnet ID and the 16
         low-order bits indicate the basic ID."
    SYNTAX      OCTET STRING (SIZE (0|3))

TmnxConfigFileFormatType         ::= TEXTUAL-CONVENTION
    STATUS      current
    DESCRIPTION
        "The value of TmnxConfigFileFormatType specifies format of the
         configuration file."
    SYNTAX      INTEGER {
        classicCli (1),
        mdCli      (2)
    }

TmnxSchemaPathState              ::= TEXTUAL-CONVENTION
    STATUS      current
    DESCRIPTION
        "A value that represents a state of schema path.

         ok(0)            schema path value is valid

         errConnection(1) system was unable to determine the value of
                          the schema path due to network connection error

         errTooLong(2)    resulting schema path value is too long

         errInvalid(3)    resulting schema path value is invalid"
    SYNTAX      INTEGER {
        ok            (0),
        errConnection (1),
        errTooLong    (2),
        errInvalid    (3)
    }

TmnxSysRmtMgmtLastRegStatus      ::= TEXTUAL-CONVENTION
    STATUS      current
    DESCRIPTION
        "Status of device remote registration attempt."
    SYNTAX      INTEGER {
        unknown             (0),
        succeeded           (1),
        cancelled           (2),
        unreachable         (3),
        refused             (4),
        dnsResolutionFailed (5),
        outOfResources      (6),
        internal            (100)
    }

TmnxSysRmtMgmtSrcDefaultPort     ::= TEXTUAL-CONVENTION
    STATUS      current
    DESCRIPTION
        "Used default system port."
    SYNTAX      INTEGER {
        none (0),
        grpc (-1)
    }

TmnxSysFpRAPsAppId               ::= TEXTUAL-CONVENTION
    STATUS      current
    DESCRIPTION
        "The value of TmnxSysFpRAPsAppId specifies the Application type."
    SYNTAX      INTEGER {
        perFcUnicastBroadcastUnknownMulticast (1),
        perFcUnicastMultipoint                (2),
        perFc                                 (3),
        per2FcUnicastMultipoint               (4),
        per4FcUnicastMultipoint               (5),
        per2Fc                                (6),
        per4Fc                                (7),
        aggregatePolicers                     (8),
        sharedPolicers                        (9),
        fcPolicers                            (10)
    }

TmnxSysNetconfCallHomeConnType   ::= TEXTUAL-CONVENTION
    STATUS      current
    DESCRIPTION
        "The value of TmnxSysNetconfCallHomeConnType specifies server's
         preference for how the NETCONF connection is maintained."
    SYNTAX      INTEGER {
        persistent (1)
    }

tmnxSysObjs                      OBJECT IDENTIFIER ::= { tmnxSRObjs 1 }

sysGenInfo                       OBJECT IDENTIFIER ::= { tmnxSysObjs 1 }

sgiCpuUsage                      OBJECT-TYPE
    SYNTAX      Unsigned32 (0..100)
    UNITS       "percent"
    MAX-ACCESS  read-only
    STATUS      current
    DESCRIPTION
        "The value of sgiCpuUsage indicates the current CPU utilization for the
         system."
    ::= { sysGenInfo 1 }

sgiMemoryUsed                    OBJECT-TYPE
    SYNTAX      Unsigned32
    UNITS       "bytes"
    MAX-ACCESS  read-only
    STATUS      current
    DESCRIPTION
        "The value of sgiMemoryUsed indicates the total pre-allocated pool
         memory currently in use on the system.

         If the value is greater than the maximum value reportable by this
         object then this object reports its maximum value (4,294,967,295) and
         sgiKbMemoryUsed must be used to determine the total pre-allocated pool
         memory."
    ::= { sysGenInfo 2 }

sgiMemoryAvailable               OBJECT-TYPE
    SYNTAX      Unsigned32
    UNITS       "bytes"
    MAX-ACCESS  read-only
    STATUS      current
    DESCRIPTION
        "The value of sgiMemoryAvailable indicates the amount of free memory in
         the overall system that is not allocated to memory pools, but is
         available in case a memory pool needs to grow.

         If the value is greater than the maximum value reportable by this
         object then this object reports its maximum value (4,294,967,295) and
         sgiKbMemoryAvailable must be used to determine the total free memory."
    ::= { sysGenInfo 3 }

sgiMemoryPoolAllocated           OBJECT-TYPE
    SYNTAX      Unsigned32
    UNITS       "bytes"
    MAX-ACCESS  read-only
    STATUS      current
    DESCRIPTION
        "The value of sgiMemoryPoolAllocated indicates the total memory
         currently allocated in memory-pools on the system.

         This memory may or may not be currently in use, but is pre-allocated
         should the software need to use it.

         If the value is greater than the maximum value reportable by this
         object then this object reports its maximum value (4,294,967,295) and
         sgiKbMemoryPoolAllocated must be used to determine the total memory
         allocated in memory-pools."
    ::= { sysGenInfo 4 }

sgiSwMajorVersion                OBJECT-TYPE
    SYNTAX      Unsigned32
    MAX-ACCESS  read-only
    STATUS      current
    DESCRIPTION
        "The value of sgiSwMajorVersion indicates the major version number of
         the software running on the active CPM card."
    ::= { sysGenInfo 5 }

sgiSwMinorVersion                OBJECT-TYPE
    SYNTAX      Unsigned32
    MAX-ACCESS  read-only
    STATUS      current
    DESCRIPTION
        "The value of sgiSwMinorVersion indicates the minor version number of
         the software running on the active CPM card."
    ::= { sysGenInfo 6 }

sgiSwVersionModifier             OBJECT-TYPE
    SYNTAX      OCTET STRING (SIZE (0..255))
    MAX-ACCESS  read-only
    STATUS      current
    DESCRIPTION
        "The value of sgiSwVersionModifier indicates additional information
         about the version of software running on the active CPM card."
    ::= { sysGenInfo 7 }

sgiSnmpInGetBulks                OBJECT-TYPE
    SYNTAX      Counter32
    MAX-ACCESS  read-only
    STATUS      current
    DESCRIPTION
        "The value of sgiSnmpInGetBulks indicates the total number of SNMP
         Get-Next PDUs which have been accepted and processed by the SNMP
         protocol entity."
    ::= { sysGenInfo 8 }

sgiKbMemoryUsed                  OBJECT-TYPE
    SYNTAX      Unsigned32
    UNITS       "kilobytes"
    MAX-ACCESS  read-only
    STATUS      current
    DESCRIPTION
        "The value of sgiKbMemoryUsed indicates the total pre-allocated pool
         memory, in kilobytes, currently in use on the system."
    ::= { sysGenInfo 9 }

sgiKbMemoryAvailable             OBJECT-TYPE
    SYNTAX      Unsigned32
    UNITS       "kilobytes"
    MAX-ACCESS  read-only
    STATUS      current
    DESCRIPTION
        "The value of sgiKbMemoryAvailable indicates the amount of free memory,
         in kilobytes, in the overall system that is not allocated to memory
         pools, but is available in case a memory pool needs to grow."
    ::= { sysGenInfo 10 }

sgiKbMemoryPoolAllocated         OBJECT-TYPE
    SYNTAX      Unsigned32
    UNITS       "kilobytes"
    MAX-ACCESS  read-only
    STATUS      current
    DESCRIPTION
        "The value of sgiKbMemoryPoolAllocated indicates the total memory, in
         kilobytes, currently allocated in memory-pools on the system.

         This memory may or may not be currently in use, but is pre-allocated
         should the software need to use it."
    ::= { sysGenInfo 11 }

tmnxSysCpuMonTable               OBJECT-TYPE
    SYNTAX      SEQUENCE OF TmnxSysCpuMonEntry
    MAX-ACCESS  not-accessible
    STATUS      current
    DESCRIPTION
        "tmnxSysCpuMonTable consists of the system level CPU monitoring
         statistics."
    ::= { sysGenInfo 12 }

tmnxSysCpuMonEntry               OBJECT-TYPE
    SYNTAX      TmnxSysCpuMonEntry
    MAX-ACCESS  not-accessible
    STATUS      current
    DESCRIPTION
        "tmnxSysCpuMonEntry contains the system level CPU monitoring statistics
         over a specified sample-time."
    INDEX       { tmnxSysCpuMonSampleTime }
    ::= { tmnxSysCpuMonTable 1 }

TmnxSysCpuMonEntry               ::= SEQUENCE
{
    tmnxSysCpuMonSampleTime          TmnxSysMonSampleTime,
    tmnxSysCpuMonCpuIdle             TmnxSysMonUtilization,
    tmnxSysCpuMonBusyCoreUtil        TmnxSysMonUtilization,
    tmnxSysCpuMonBusyGroupName       OCTET STRING,
    tmnxSysCpuMonBusyGroupUtil       TmnxSysMonUtilization
}

tmnxSysCpuMonSampleTime          OBJECT-TYPE
    SYNTAX      TmnxSysMonSampleTime
    MAX-ACCESS  not-accessible
    STATUS      current
    DESCRIPTION
        "The value of tmnxSysCpuMonSampleTime specifies the sample-time used to
         calculate the utilization results for the row."
    ::= { tmnxSysCpuMonEntry 1 }

tmnxSysCpuMonCpuIdle             OBJECT-TYPE
    SYNTAX      TmnxSysMonUtilization
    MAX-ACCESS  read-only
    STATUS      current
    DESCRIPTION
        "The value of tmnxSysCpuMonCpuIdle indicates the overall percentage of
         CPU idleness over the specified sample-time."
    ::= { tmnxSysCpuMonEntry 2 }

tmnxSysCpuMonBusyCoreUtil        OBJECT-TYPE
    SYNTAX      TmnxSysMonUtilization
    MAX-ACCESS  read-only
    STATUS      current
    DESCRIPTION
        "The value of tmnxSysCpuMonBusyCoreUtil indicates the utilization
         percentage of the busiest processor core over the specified
         sample-time. On single core CPUs, this is the overall system
         utilization percentage over the specified sample-time."
    ::= { tmnxSysCpuMonEntry 3 }

tmnxSysCpuMonBusyGroupName       OBJECT-TYPE
    SYNTAX      OCTET STRING (SIZE (0..64))
    MAX-ACCESS  read-only
    STATUS      current
    DESCRIPTION
        "The value of tmnxSysCpuMonBusyGroupName indicates the name of the
         group that is running at the highest capacity utilization.

         Capacity utilization is the CPU utilization relative to the maximum CPU
         resources available to that group.  A group is a set of related
         applications, services, tasks or protocol handlers that consumes some
         part of the system CPU resources.

         The capacity utilization of the busiest group is indicated by
         tmnxSysCpuMonBusyGroupUtil."
    ::= { tmnxSysCpuMonEntry 4 }

tmnxSysCpuMonBusyGroupUtil       OBJECT-TYPE
    SYNTAX      TmnxSysMonUtilization
    MAX-ACCESS  read-only
    STATUS      current
    DESCRIPTION
        "The value of tmnxSysCpuMonBusyGroupUtil indicates the capacity
         utilization of the group that is running at the highest capacity
         utilization.

         Capacity utilization is the CPU utilization relative to the maximum CPU
         resources available to that group.  A group is a set of related
         applications, services, tasks or protocol handlers that consumes some
         part of the system CPU resources.

         The name of the busiest group is indicated by
         tmnxSysCpuMonBusyGroupName."
    ::= { tmnxSysCpuMonEntry 5 }

sgiGroupingIDs                   OBJECT IDENTIFIER ::= { sysGenInfo 13 }

sgiSystemGroupID                 OBJECT-TYPE
    SYNTAX      Unsigned32
    MAX-ACCESS  read-write
    STATUS      current
    DESCRIPTION
        "The value of sgiSystemGroupID specifies a group this
         system belongs to.  It is used by NMS applications to identify
         a set of systems for which the NMS wants to perform common
         tasks such as correlating alarms."
    DEFVAL      { 0 }
    ::= { sgiGroupingIDs 1 }

sgiSystemSubGroupID              OBJECT-TYPE
    SYNTAX      Unsigned32
    MAX-ACCESS  read-write
    STATUS      current
    DESCRIPTION
        "The value of sgiSystemSubGroupID specifies a sub-group within the
         sgiSystemGroupID group that this system belongs to. It is used by NMS
         applications to identify a subset of systems in the sgiSystemGroupID
         for which the NMS wants to perform common tasks such as correlating
         alarms."
    DEFVAL      { 0 }
    ::= { sgiGroupingIDs 2 }

sgiSnmpFailedSets                OBJECT-TYPE
    SYNTAX      Counter32
    MAX-ACCESS  read-only
    STATUS      current
    DESCRIPTION
        "The value of sgiSnmpFailedSets indicates the total number of SNMP set
         requests which have failed which failed due to another management
         interface (such as NETCONF) exclusively reserving the system
         resources."
    ::= { sysGenInfo 14 }

sgiCryptoModVersion              OBJECT-TYPE
    SYNTAX      DisplayString
    MAX-ACCESS  read-only
    STATUS      current
    DESCRIPTION
        "The value of sgiCryptoModVersion indicates the version of the
         cryptographic module software running on the system."
    ::= { sysGenInfo 15 }

tmnxSysUpTime                    OBJECT-TYPE
    SYNTAX      Counter64
    MAX-ACCESS  read-only
    STATUS      current
    DESCRIPTION
        "The value of tmnxSysUpTime indicates the time (in centiseconds) since
         the network management portion of the system was last re-initialized."
    ::= { sysGenInfo 16 }

sgiKernelVersion                 OBJECT-TYPE
    SYNTAX      DisplayString
    MAX-ACCESS  read-only
    STATUS      current
    DESCRIPTION
        "The value of sgiKernelVersion indicates the version of the operating
         kernel running on the system."
    ::= { sysGenInfo 17 }

sgiFIPSProviderVersion           OBJECT-TYPE
    SYNTAX      DisplayString
    MAX-ACCESS  read-only
    STATUS      current
    DESCRIPTION
        "The value of sgiFIPSProviderVersion indicates the version of the
         Federal Information Processing Standards (FIPS) provider in the
         cryptographic module software running on the system."
    ::= { sysGenInfo 18 }

sgiEntropySourceVersion          OBJECT-TYPE
    SYNTAX      DisplayString
    MAX-ACCESS  read-only
    STATUS      current
    DESCRIPTION
        "The value of sgiEntropySourceVersion indicates the version of the
         entropy source in the cryptographic module software running on the
         system."
    ::= { sysGenInfo 19 }

sysTimeInfo                      OBJECT IDENTIFIER ::= { tmnxSysObjs 2 }

stiDateAndTime                   OBJECT-TYPE
    SYNTAX      DateAndTime (SIZE (11))
    MAX-ACCESS  read-write
    STATUS      current
    DESCRIPTION
        "The current date and time (in UTC) maintained in this managed system."
    ::= { sysTimeInfo 1 }

stiActiveZone                    OBJECT-TYPE
    SYNTAX      DisplayString (SIZE (0..5))
    MAX-ACCESS  read-write
    STATUS      current
    DESCRIPTION
        "The time zone that is active in this managed system."
    DEFVAL      { "UTC" }
    ::= { sysTimeInfo 2 }

stiHoursOffset                   OBJECT-TYPE
    SYNTAX      Integer32 (-11..12)
    UNITS       "hours"
    MAX-ACCESS  read-write
    STATUS      current
    DESCRIPTION
        "The number of hours by which the time zone represented by
         stiActiveZone offsets from UTC (Coordinated Universal Time)."
    DEFVAL      { 0 }
    ::= { sysTimeInfo 3 }

stiMinutesOffset                 OBJECT-TYPE
    SYNTAX      Integer32 (0..59)
    UNITS       "minutes"
    MAX-ACCESS  read-write
    STATUS      current
    DESCRIPTION
        "The number of minutes (in addition to the hours offset defined by
         stiHoursOffset) by which the time zone represented by stiActiveZone
         offsets from UTC (Coordinated Universal Time). This value is used when
         the time zone does not have an offset that is an integral number of
         hours.

         If the hour offset is defined as '12', the minute offset cannot be
         anything other than zero."
    DEFVAL      { 0 }
    ::= { sysTimeInfo 4 }

stiZoneType                      OBJECT-TYPE
    SYNTAX      INTEGER {
        system (1),
        user   (2)
    }
    MAX-ACCESS  read-only
    STATUS      current
    DESCRIPTION
        "stiZoneType will be 'system' if the zone defined by stiActiveZone is a
         system-defined zone. It will be 'user' if the zone has been defined by
         the user."
    ::= { sysTimeInfo 5 }

stiSummerZoneTable               OBJECT-TYPE
    SYNTAX      SEQUENCE OF StiSummerZoneEntry
    MAX-ACCESS  not-accessible
    STATUS      current
    DESCRIPTION
        "The stiSummerZoneTable has an entry for each summer time zone
         information."
    ::= { sysTimeInfo 6 }

stiSummerZoneEntry               OBJECT-TYPE
    SYNTAX      StiSummerZoneEntry
    MAX-ACCESS  not-accessible
    STATUS      current
    DESCRIPTION
        "Each row entry contains information about a summer time zone. This
         information can be used to either override the default summer (or
         daylight savings) time information for a system-defined time zone or
         define the summer time information for a user-defined time zone."
    INDEX       { IMPLIED stiSummerZoneName }
    ::= { stiSummerZoneTable 1 }

StiSummerZoneEntry               ::= SEQUENCE
{
    stiSummerZoneName                OCTET STRING,
    stiSummerZoneRowStatus           RowStatus,
    stiSummerZoneStartDate           DateAndTime,
    stiSummerZoneEndDate             DateAndTime,
    stiSummerZoneOffset              Unsigned32,
    stiSummerZoneStartDay            INTEGER,
    stiSummerZoneStartWeek           INTEGER,
    stiSummerZoneStartMonth          INTEGER,
    stiSummerZoneStartHour           Unsigned32,
    stiSummerZoneStartMinute         Unsigned32,
    stiSummerZoneEndDay              INTEGER,
    stiSummerZoneEndWeek             INTEGER,
    stiSummerZoneEndMonth            INTEGER,
    stiSummerZoneEndHour             Unsigned32,
    stiSummerZoneEndMinute           Unsigned32
}

stiSummerZoneName                OBJECT-TYPE
    SYNTAX      OCTET STRING (SIZE (1..5))
    MAX-ACCESS  not-accessible
    STATUS      current
    DESCRIPTION
        "The name for a summer time zone. This name must be unique amongst the
         table entries. The summer time zone name should comprise only of
         uppercase letters A-Z and digits 0-9."
    ::= { stiSummerZoneEntry 1 }

stiSummerZoneRowStatus           OBJECT-TYPE
    SYNTAX      RowStatus
    MAX-ACCESS  read-create
    STATUS      current
    DESCRIPTION
        "The row status used to create and delete rows in this table."
    ::= { stiSummerZoneEntry 2 }

stiSummerZoneStartDate           OBJECT-TYPE
    SYNTAX      DateAndTime (SIZE (8))
    MAX-ACCESS  read-create
    STATUS      obsolete
    DESCRIPTION
        "The starting date and time when the summer time will take effect.

         This object was made obsolete in the 4.0 release."
    ::= { stiSummerZoneEntry 3 }

stiSummerZoneEndDate             OBJECT-TYPE
    SYNTAX      DateAndTime (SIZE (8))
    MAX-ACCESS  read-create
    STATUS      obsolete
    DESCRIPTION
        "The date and time when summer time will end.

         This object was made obsolete in the 4.0 release."
    ::= { stiSummerZoneEntry 4 }

stiSummerZoneOffset              OBJECT-TYPE
    SYNTAX      Unsigned32 (0..60)
    UNITS       "minutes"
    MAX-ACCESS  read-create
    STATUS      current
    DESCRIPTION
        "The number of minutes that will be added to the time when summer time
         takes effect. The same number of minutes will be subtracted from the
         time when the summer time ends."
    DEFVAL      { 60 }
    ::= { stiSummerZoneEntry 5 }

stiSummerZoneStartDay            OBJECT-TYPE
    SYNTAX      INTEGER {
        sunday    (0),
        monday    (1),
        tuesday   (2),
        wednesday (3),
        thursday  (4),
        friday    (5),
        saturday  (6)
    }
    MAX-ACCESS  read-create
    STATUS      current
    DESCRIPTION
        "The starting day of the week when the summer time will take effect."
    DEFVAL      { sunday }
    ::= { stiSummerZoneEntry 6 }

stiSummerZoneStartWeek           OBJECT-TYPE
    SYNTAX      INTEGER {
        first  (0),
        second (1),
        third  (2),
        fourth (3),
        last   (4)
    }
    MAX-ACCESS  read-create
    STATUS      current
    DESCRIPTION
        "The starting week of the month when the summer time will take effect."
    DEFVAL      { first }
    ::= { stiSummerZoneEntry 7 }

stiSummerZoneStartMonth          OBJECT-TYPE
    SYNTAX      INTEGER {
        january   (0),
        february  (1),
        march     (2),
        april     (3),
        may       (4),
        june      (5),
        july      (6),
        august    (7),
        september (8),
        october   (9),
        november  (10),
        december  (11)
    }
    MAX-ACCESS  read-create
    STATUS      current
    DESCRIPTION
        "The starting month of the year when the summer time will take effect."
    DEFVAL      { january }
    ::= { stiSummerZoneEntry 8 }

stiSummerZoneStartHour           OBJECT-TYPE
    SYNTAX      Unsigned32 (0..23)
    UNITS       "hours"
    MAX-ACCESS  read-create
    STATUS      current
    DESCRIPTION
        "The hour at which the summer time will take effect."
    DEFVAL      { 0 }
    ::= { stiSummerZoneEntry 9 }

stiSummerZoneStartMinute         OBJECT-TYPE
    SYNTAX      Unsigned32 (0..59)
    UNITS       "minutes"
    MAX-ACCESS  read-create
    STATUS      current
    DESCRIPTION
        "The number of minutes after the hours defined by
         stiSummerZoneStartHour when the summer time will take effect."
    DEFVAL      { 0 }
    ::= { stiSummerZoneEntry 10 }

stiSummerZoneEndDay              OBJECT-TYPE
    SYNTAX      INTEGER {
        sunday    (0),
        monday    (1),
        tuesday   (2),
        wednesday (3),
        thursday  (4),
        friday    (5),
        saturday  (6)
    }
    MAX-ACCESS  read-create
    STATUS      current
    DESCRIPTION
        "The day of the week when the summer time setting will end."
    DEFVAL      { sunday }
    ::= { stiSummerZoneEntry 11 }

stiSummerZoneEndWeek             OBJECT-TYPE
    SYNTAX      INTEGER {
        first  (0),
        second (1),
        third  (2),
        fourth (3),
        last   (4)
    }
    MAX-ACCESS  read-create
    STATUS      current
    DESCRIPTION
        "The week of the month when the summer time setting will end."
    DEFVAL      { first }
    ::= { stiSummerZoneEntry 12 }

stiSummerZoneEndMonth            OBJECT-TYPE
    SYNTAX      INTEGER {
        january   (0),
        february  (1),
        march     (2),
        april     (3),
        may       (4),
        june      (5),
        july      (6),
        august    (7),
        september (8),
        october   (9),
        november  (10),
        december  (11)
    }
    MAX-ACCESS  read-create
    STATUS      current
    DESCRIPTION
        "The month of the year when the summer time setting will end."
    DEFVAL      { january }
    ::= { stiSummerZoneEntry 13 }

stiSummerZoneEndHour             OBJECT-TYPE
    SYNTAX      Unsigned32 (0..23)
    UNITS       "hours"
    MAX-ACCESS  read-create
    STATUS      current
    DESCRIPTION
        "The hour at which the summer time will stop taking effect."
    DEFVAL      { 0 }
    ::= { stiSummerZoneEntry 14 }

stiSummerZoneEndMinute           OBJECT-TYPE
    SYNTAX      Unsigned32 (0..59)
    UNITS       "minutes"
    MAX-ACCESS  read-create
    STATUS      current
    DESCRIPTION
        "The number of minutes after the hours defined by stiSummerZoneEndHour
         when the summer time will stop taking effect."
    DEFVAL      { 0 }
    ::= { stiSummerZoneEntry 15 }

stiPreferLocalTime               OBJECT-TYPE
    SYNTAX      TruthValue
    MAX-ACCESS  read-write
    STATUS      current
    DESCRIPTION
        "The value of stiPreferLocalTime specifies the preference for the use
         of local or UTC time in the system for objects such as log file names,
         created/completed times reported in log files, rollback times
         displayed in show routines etc. Note that the time format for
         timestamps on log events themselves is controlled on a per log basis
         and not via prefer-local-time.

         A value of false(2) means use UTC time; true(1) means use the local
         system time, configured through 'configure system time' command"
    DEFVAL      { false }
    ::= { sysTimeInfo 7 }

sysSntpInfo                      OBJECT IDENTIFIER ::= { tmnxSysObjs 3 }

sntpState                        OBJECT-TYPE
    SYNTAX      INTEGER {
        unicast   (1),
        broadcast (2)
    }
    MAX-ACCESS  read-write
    STATUS      current
    DESCRIPTION
        "The mode for Simple Network Time Protocol (SNTP). 'Unicast' indicates
         that broadcast client is disabled. A value of 'broadcast' indicates
         that SNTP is listening to SNTP/NTP broadcast messages on interfaces
         with broadcast client enabled."
    DEFVAL      { unicast }
    ::= { sysSntpInfo 1 }

sntpServerTable                  OBJECT-TYPE
    SYNTAX      SEQUENCE OF SntpServerEntry
    MAX-ACCESS  not-accessible
    STATUS      current
    DESCRIPTION
        "The sntpServerEntry has an entry for each SNTP server for SNTP unicast
         client mode. SNTP can only receive the time from one of these SNTP
         servers. The table can have up to a maximum of 3 entries."
    ::= { sysSntpInfo 2 }

sntpServerEntry                  OBJECT-TYPE
    SYNTAX      SntpServerEntry
    MAX-ACCESS  not-accessible
    STATUS      current
    DESCRIPTION
        "Each row entry contains information about an SNTP server."
    INDEX       { sntpServerAddress }
    ::= { sntpServerTable 1 }

SntpServerEntry                  ::= SEQUENCE
{
    sntpServerAddress                IpAddress,
    sntpServerRowStatus              RowStatus,
    sntpServerVersion                Integer32,
    sntpServerPreference             INTEGER,
    sntpServerInterval               Unsigned32
}

sntpServerAddress                OBJECT-TYPE
    SYNTAX      IpAddress
    MAX-ACCESS  not-accessible
    STATUS      current
    DESCRIPTION
        "The IP address of the SNTP server."
    ::= { sntpServerEntry 1 }

sntpServerRowStatus              OBJECT-TYPE
    SYNTAX      RowStatus
    MAX-ACCESS  read-create
    STATUS      current
    DESCRIPTION
        "The row status used to create and delete rows in this table."
    ::= { sntpServerEntry 2 }

sntpServerVersion                OBJECT-TYPE
    SYNTAX      Integer32 (1..3)
    MAX-ACCESS  read-create
    STATUS      current
    DESCRIPTION
        "The SNTP Version supported by this server."
    DEFVAL      { 3 }
    ::= { sntpServerEntry 3 }

sntpServerPreference             OBJECT-TYPE
    SYNTAX      INTEGER {
        normal    (1),
        preferred (2)
    }
    MAX-ACCESS  read-create
    STATUS      current
    DESCRIPTION
        "The preference value for this SNTP server. When more then one
         time-server is configured it may be desirable that one server have
         preference over others. The value of sntpServerPreference for that
         server will be set to preferred(2). Only one server in the table can
         be a preferred server"
    DEFVAL      { normal }
    ::= { sntpServerEntry 4 }

sntpServerInterval               OBJECT-TYPE
    SYNTAX      Unsigned32 (64..1024)
    UNITS       "seconds"
    MAX-ACCESS  read-create
    STATUS      current
    DESCRIPTION
        "The frequency at which this server is queried."
    DEFVAL      { 64 }
    ::= { sntpServerEntry 5 }

sntpAdminState                   OBJECT-TYPE
    SYNTAX      INTEGER {
        noop         (1),
        inService    (2),
        outOfService (3)
    }
    MAX-ACCESS  read-write
    STATUS      current
    DESCRIPTION
        "The desired administrative state for SNTP."
    DEFVAL      { outOfService }
    ::= { sysSntpInfo 3 }

sntpOperStatus                   OBJECT-TYPE
    SYNTAX      TmnxOperState
    MAX-ACCESS  read-only
    STATUS      current
    DESCRIPTION
        "The value of sntpOperStatus indicates the current operational status
         of SNTP."
    ::= { sysSntpInfo 4 }

sysSyncInfo                      OBJECT IDENTIFIER ::= { tmnxSysObjs 4 }

ssiSaveConfig                    OBJECT-TYPE
    SYNTAX      TmnxActionType
    MAX-ACCESS  read-write
    STATUS      current
    DESCRIPTION
        "Setting this action variable to 'doAction' causes the current
         running configuration information to be saved to the location
         specified by ssiSaveConfigDest.  If no location is specified
         by ssiSaveConfigDest, the primary configuration file pointed to
         in the boot options file (bof) will be backed up and a new
         primary configuration file will be created with the current
         running configuration information.

         If ssiSaveConfigDetail has a value of 'true', default configuration
         values will be included in the saved configuration information.

         A corresponding persistent SNMP index file is created regardless of
         the setting of the persistence switch in the bof."
    DEFVAL      { notApplicable }
    ::= { sysSyncInfo 15 }

ssiSyncMode                      OBJECT-TYPE
    SYNTAX      TmnxSsiSyncMode
    MAX-ACCESS  read-write
    STATUS      current
    DESCRIPTION
        "The value of ssiSyncMode specifies the type of synchronization
         operation to perform between the primary and secondary CPMs after a
         change has been made to the configuration files or the boot
         environment information contained in the boot options file (bof)."
    DEFVAL      { none }
    ::= { sysSyncInfo 16 }

ssiSyncForce                     OBJECT-TYPE
    SYNTAX      TmnxSsiSyncMode
    MAX-ACCESS  read-write
    STATUS      current
    DESCRIPTION
        "The value of ssiSyncForce specifies the type of synchronization
         operation to perform when an SNMP set is made to this object. 'config'
         synchronizes only configuration files. 'bootEnv' synchronizes all
         files required to boot the system.

         The result of a read operation on this object is always 'none'."
    DEFVAL      { none }
    ::= { sysSyncInfo 17 }

ssiSyncStatus                    OBJECT-TYPE
    SYNTAX      INTEGER {
        unknown           (0),
        configOnly        (1),
        bootEnv           (2),
        configFail        (3),
        bootEnvFail       (4),
        configInProgress  (5),
        bootEnvInProgress (6)
    }
    MAX-ACCESS  read-only
    STATUS      current
    DESCRIPTION
        "The value of ssiSyncStatus indicates the results of the last
         synchronization operation between the primary and secondary CPMs."
    ::= { sysSyncInfo 18 }

ssiSyncConfigLastTime            OBJECT-TYPE
    SYNTAX      TimeStamp
    MAX-ACCESS  read-only
    STATUS      current
    DESCRIPTION
        "The value of ssiSyncConfigLastTime is the timestamp of the last
         successful synchronization of the configuration files."
    ::= { sysSyncInfo 19 }

ssiSyncBootEnvLastTime           OBJECT-TYPE
    SYNTAX      TimeStamp
    MAX-ACCESS  read-only
    STATUS      current
    DESCRIPTION
        "The value of ssiSyncBootEnvLastTime is the timestamp of the last
         successful synchronization of the boot environment files."
    ::= { sysSyncInfo 20 }

ssiConfigMaxBackupRevisions      OBJECT-TYPE
    SYNTAX      Unsigned32 (1..200)
    MAX-ACCESS  read-write
    STATUS      current
    DESCRIPTION
        "The value of ssiConfigMaxBackupRevisions is the maximum number of
         backup revisions maintained for a configuration file. This value also
         applies to the number of revisions maintained for the BOF file."
    ::= { sysSyncInfo 21 }

ssiSaveConfigResult              OBJECT-TYPE
    SYNTAX      INTEGER {
        none       (1),
        inProgress (2),
        success    (3),
        failed     (4)
    }
    MAX-ACCESS  read-only
    STATUS      current
    DESCRIPTION
        "The value of ssiSaveConfigResult represents the result of the
         last ssiSaveConfig action.
         none(1)            None of the following apply
         inProgress(2)      The action is still in progress
         success(3)         The action completed successfully
         failed(4)          The action failed"
    ::= { sysSyncInfo 22 }

ssiSaveBof                       OBJECT-TYPE
    SYNTAX      TmnxActionType
    MAX-ACCESS  read-write
    STATUS      current
    DESCRIPTION
        "Setting ssiSaveBof action variable to 'doAction' causes the existing
         BOF to be backed up and a new BOF file to be created with the current
         boot options information."
    DEFVAL      { notApplicable }
    ::= { sysSyncInfo 23 }

ssiSaveBofResult                 OBJECT-TYPE
    SYNTAX      INTEGER {
        none       (1),
        inProgress (2),
        success    (3),
        failed     (4)
    }
    MAX-ACCESS  read-only
    STATUS      current
    DESCRIPTION
        "The value of ssiSaveBofResult represents the result of the
         last ssiSaveBof action.
         none(1)            None of the following apply
         inProgress(2)      The action is still in progress
         success(3)         The action completed successfully
         failed(4)          The action failed"
    ::= { sysSyncInfo 24 }

ssiSaveConfigDest                OBJECT-TYPE
    SYNTAX      TmnxDisplayStringURL
    MAX-ACCESS  read-write
    STATUS      current
    DESCRIPTION
        "The value of ssiSaveConfigDest specifies the destination filepath
         or file-URL where the current running configuration information
         will be saved when ssiSaveConfig is set to 'doAction'.  If
         ssiSaveConfigDest is set to the empty string, ''H, the primary
         configuration file pointed to in the boot options file (bof) will
         be backed up and a new primary configuration file will be created
         with the current running configuration information.

         A corresponding persistent SNMP index file is created regardless of
         the setting of the persistence switch in the bof."
    DEFVAL      { ''H }
    ::= { sysSyncInfo 25 }

ssiSaveConfigDetail              OBJECT-TYPE
    SYNTAX      TruthValue
    MAX-ACCESS  read-write
    STATUS      current
    DESCRIPTION
        "When ssiSaveConfigDetail has a value of 'true', the default
         configuration values will also be included in the current running
         configuration information that will be saved when ssiSaveConfig is set
         to 'doAction'.

         When ssiSaveConfigDetail has a value of 'false', only non-default
         configuration values are saved. "
    DEFVAL      { false }
    ::= { sysSyncInfo 26 }

ssiRedFailoverTime               OBJECT-TYPE
    SYNTAX      TimeStamp
    MAX-ACCESS  read-only
    STATUS      current
    DESCRIPTION
        "The value of ssiRedFailoverTime is the timestamp when the last
         redundancy failover occurred causing a switchover from active
         to standby CPM.  If there is no redundant CPM card in this system
         or no failover has occurred since the system last booted,
         ssiRedFailoverTime will always return 0."
    ::= { sysSyncInfo 27 }

ssiRedFailoverReason             OBJECT-TYPE
    SYNTAX      DisplayString (SIZE (0..80))
    MAX-ACCESS  read-only
    STATUS      current
    DESCRIPTION
        "The value of ssiRedFailoverReason is a text string giving an
         explanation of the cause of the last redundancy failover. If no
         failover has occurred, the empty string, ''H, will be returned."
    ::= { sysSyncInfo 28 }

ssiSyncRollbackLastTime          OBJECT-TYPE
    SYNTAX      TimeStamp
    MAX-ACCESS  read-only
    STATUS      current
    DESCRIPTION
        "The value of ssiSyncRollbackLastTime is the timestamp of the last
         successful synchronization of the rollback files."
    ::= { sysSyncInfo 29 }

ssiSyncRollbackMode              OBJECT-TYPE
    SYNTAX      TmnxSsiSyncRollbackMode
    MAX-ACCESS  read-write
    STATUS      current
    DESCRIPTION
        "The value of ssiSyncRollbackMode specifies the type of synchronization
         operation to perform between the primary and secondary CPMs after a
         change has been made to the rollback files."
    DEFVAL      { none }
    ::= { sysSyncInfo 30 }

ssiSyncRollbackForce             OBJECT-TYPE
    SYNTAX      TmnxSsiSyncRollbackMode
    MAX-ACCESS  read-write
    STATUS      current
    DESCRIPTION
        "The value of ssiSyncRollbackForce specifies the type of synchronization
         operation to perform when an SNMP set is made to this object.
         'rollbackSingle' synchronizes only the rollback file that recently
          changed.
         'rollbackAll' synchronizes all rollback files.

         The result of a read operation on this object is always 'none'."
    DEFVAL      { none }
    ::= { sysSyncInfo 31 }

ssiSyncRollbackStatus            OBJECT-TYPE
    SYNTAX      INTEGER {
        unknown            (0),
        rollbackFail       (1),
        rollbackInProgress (2),
        rollbackSuccess    (3)
    }
    MAX-ACCESS  read-only
    STATUS      current
    DESCRIPTION
        "The value of ssiSyncRollbackStatus indicates the results of the last
         rollback synchronization operation between the primary and secondary
         CPMs."
    ::= { sysSyncInfo 32 }

ssiSyncCertLastTime              OBJECT-TYPE
    SYNTAX      TimeStamp
    MAX-ACCESS  read-only
    STATUS      current
    DESCRIPTION
        "The value of ssiSyncCertLastTime is the timestamp of the last
         successful synchronization of the certificate files."
    ::= { sysSyncInfo 33 }

ssiSyncCertMode                  OBJECT-TYPE
    SYNTAX      TruthValue
    MAX-ACCESS  read-write
    STATUS      current
    DESCRIPTION
        "The value of ssiSyncCertMode specifies whether to synchronize
         certificate files between the primary and secondary CPMs."
    DEFVAL      { true }
    ::= { sysSyncInfo 34 }

ssiSyncCertForce                 OBJECT-TYPE
    SYNTAX      TmnxActionType
    MAX-ACCESS  read-write
    STATUS      current
    DESCRIPTION
        "The value of ssiSyncCertForce specifies to perform action to
         synchronize certificate files between the primary and secondary CPMs
         when an SNMP set is made to this object.

         The value of ssiSyncCertForce will always be returned as
         'notApplicable'."
    DEFVAL      { notApplicable }
    ::= { sysSyncInfo 35 }

ssiSyncCertStatus                OBJECT-TYPE
    SYNTAX      INTEGER {
        unknown    (0),
        fail       (1),
        inProgress (2),
        success    (3)
    }
    MAX-ACCESS  read-only
    STATUS      current
    DESCRIPTION
        "The value of ssiSyncCertStatus indicates the results of the last
         certificate synchronization operation between the primary and
         secondary CPMs."
    ::= { sysSyncInfo 36 }

sysBootInfo                      OBJECT IDENTIFIER ::= { tmnxSysObjs 5 }

sbiConfigStatus                  OBJECT-TYPE
    SYNTAX      INTEGER {
        configRead        (1),
        configOK          (2),
        defaultBooted     (3),
        bootConfigFailed  (4),
        bootRestoreFailed (5),
        auto-provisioning (6)
    }
    MAX-ACCESS  read-only
    STATUS      current
    DESCRIPTION
        "The value of sbiConfigStatus indicates the result of the
         last attempt to execute the configuration file upon reboot
         of the system.
            configRead (1) - The configuration file is being read.
            configOK (2) - The configuration file was successfully
                    executed.
            defaultBooted (3) - There was no configuration file and
                    the system booted using a minimal
                    default configuration.
            bootConfigFailed (4) - An error occurred while the
                    configuration file was being executed.
                    The system configuration is incomplete.
            bootRestoreFailed (5) - An error occurred while the
                    restoration was being performed. The system
                    configuration is incomplete.
            auto-provisioning (6) - Auto-Boot feature running to
                    automatically provision and retrieve configuration
                    from network. Execution of boot configuration file
                    skipped."
    ::= { sysBootInfo 1 }

sbiPersistStatus                 OBJECT-TYPE
    SYNTAX      INTEGER {
        persistOK           (1),
        noPersistFile       (2),
        persistMismatch     (3),
        persistIndexFailure (4),
        persistDisabled     (5),
        persistInvalid      (6),
        persistBoot         (7),
        persistInit         (8),
        persistInProgress   (9)
    }
    MAX-ACCESS  read-only
    STATUS      current
    DESCRIPTION
        "The value of sbiPersistStatus indicates the state of the
         rebuild of the SNMP persistent index database upon reboot of the
         system.
            persistOK (1) - The persistent index database was
                successfully created.  Persistent SNMP managed
                objects were recreated with the same SNMP
                indexes they had prior to the system reboot.
            noPersistFile (2) - There was no persistent index file with
                the same pathname as the configuration file.
            persistMismatch (3) -The headers in the persistent index
                file and the configuration file with the same name
                do not match.
            persistIndexFailure (4) - An error occurred while creating
                the persistent index database.
            persistDisabled (5) - The system was administratively
                reconfigured without maintaining persistent SNMP index
                values because sbiPersistIndex has a value of 'false'.
            persistInvalid (6) - Persistent index database was not
                                 initialized.
            persistBoot(7) - The persistent index database was in the
                             pre-initial bootup state.
            persistInit(8) - The persistent index database is initializing.
            persistInProgress(9) - The initial bootup file is loading, using the
                                   persist index database. Once complete, the
                                   persist state will go to 'persistOk (1)' if
                                   successful.

         If sbiConfigStatus has a value of 'configOK' and
         sbiPersistStatus has any value other than 'persistOK', the
         system was reconfigured without maintaining persistent SNMP index
         values.  Unless sbiPersistIndex has a value of 'false',
         sbiSnmpdOperStatus returns 'disabled' and the SNMP daemon will not
         receive SNMP requests until sbiSnmpdAdminStatus variable has
         been set to 'inService'."
    ::= { sysBootInfo 2 }

sbiPersistIndex                  OBJECT-TYPE
    SYNTAX      TruthValue
    MAX-ACCESS  read-only
    STATUS      current
    DESCRIPTION
        "When sbiPersistIndex has a value of 'true', the SNMP persistent index
         database was rebuilt when the system was rebooted.  If there was an
         error during the processing of the configuration file the system may
         have been reconfigured without persistent SNMP indexes and the SNMP
         daemon will be suspended until it is manually enabled by setting
         sbiSnmpdAdminStatus to 'inService.  When sbiPersistIndex has a
         value of 'false' the system was reconfigured without maintaining
         persistent SNMP index values and the SNMP daemon was enabled."
    ::= { sysBootInfo 3 }

sbiSnmpdAdminStatus              OBJECT-TYPE
    SYNTAX      TmnxAdminState
    MAX-ACCESS  read-write
    STATUS      current
    DESCRIPTION
        "The value of sbiSnmpdAdminStatus is the desired administrative state
         for the SNMP daemon.  When sbiSnmpdAdminStatus is set to 'inService'
         the SNMP daemon will begin receiving SNMP requests from external
         SNMP managers.  When sbiSnmpdAdminStatus is set to 'outOfService'
         the SNMP daemon is suspended and will no longer receive SNMP requests
         from external SNMP managers."
    DEFVAL      { inService }
    ::= { sysBootInfo 4 }

sbiSnmpdOperStatus               OBJECT-TYPE
    SYNTAX      TmnxOperState
    MAX-ACCESS  read-only
    STATUS      current
    DESCRIPTION
        "When sbiSnmpdOperStatus has a value of 'inService', the SNMP daemon
         will receive SNMP requests from external SNMP managers.  When
         sbiSnmpdOperStatus has a value of 'outOfService', the SNMP daemon is
         suspended and will not receive SNMP requests from external SNMP
         managers."
    ::= { sysBootInfo 5 }

sbiSnmpdMaxPktSize               OBJECT-TYPE
    SYNTAX      Integer32 (484..9216)
    MAX-ACCESS  read-write
    STATUS      current
    DESCRIPTION
        "The value of sbiSnmpdMaxPktSize specifies the maximum length in octets
         of an SNMP message which the SNMP daemon can send or receive and
         process."
    DEFVAL      { 1500 }
    ::= { sysBootInfo 6 }

sbiSnmpdPortNum                  OBJECT-TYPE
    SYNTAX      TTcpUdpPort
    MAX-ACCESS  read-write
    STATUS      current
    DESCRIPTION
        "The value of sbiSnmpdPortNum specifies the UDP port to send and
         receive SNMP messages."
    DEFVAL      { 161 }
    ::= { sysBootInfo 7 }

sbiBootConfigOKScript            OBJECT-TYPE
    SYNTAX      DisplayString
    MAX-ACCESS  read-write
    STATUS      current
    DESCRIPTION
        "The value of sbiBootConfigOKScript specifies the location and name of
         the CLI script file executed following successful completion
         of the boot-up configuration file execution. I.e. sbiPersistStatus
         has a value of 'configOK'.  When this object has the empty string
         value, ''H, no CLI script file is executed."
    DEFVAL      { ''H }
    ::= { sysBootInfo 8 }

sbiConfigOKScriptStatus          OBJECT-TYPE
    SYNTAX      INTEGER {
        notRun  (0),
        success (1),
        fail    (2)
    }
    MAX-ACCESS  read-only
    STATUS      current
    DESCRIPTION
        "The value of sbiConfigOKScriptStatus indicates the results of
         executing the CLI script file specified in sbiBootConfigOKScript."
    ::= { sysBootInfo 9 }

sbiBootConfigFailScript          OBJECT-TYPE
    SYNTAX      DisplayString
    MAX-ACCESS  read-write
    STATUS      current
    DESCRIPTION
        "The value of sbiBootConfigFailScript specifies the location and
         name of the CLI script file executed following failure of the
         boot-up configuration file execution. I.e. sbiPersistStatus
         has a value other than 'configOK'.  When this object has the empty
         string value, ''H, no CLI script file is executed."
    DEFVAL      { ''H }
    ::= { sysBootInfo 10 }

sbiConfigFailScriptStatus        OBJECT-TYPE
    SYNTAX      INTEGER {
        notRun  (0),
        success (1),
        fail    (2)
    }
    MAX-ACCESS  read-only
    STATUS      current
    DESCRIPTION
        "The value of sbiConfigFailScriptStatus indicates the results of
         executing the CLI script file specified in sbiBootConfigFailScript."
    ::= { sysBootInfo 11 }

sbiRedSwitchoverScript           OBJECT-TYPE
    SYNTAX      DisplayString
    MAX-ACCESS  read-write
    STATUS      current
    DESCRIPTION
        "The value of sbiRedSwitchoverScript specifies the location and name of
         the CLI script file executed following a redundancy switchover from
         the previously active CPM card. A switchover can happen because of a
         fatal failure or by manual action. This CLI script file can contain
         commands for environment settings, debug and mirroring settings, and
         other commands not maintained by the configuration redundancy.

         When this object has the empty string value, ''H, no CLI script file
         is executed."
    DEFVAL      { ''H }
    ::= { sysBootInfo 12 }

sbiRedSwitchoverScriptStatus     OBJECT-TYPE
    SYNTAX      INTEGER {
        notRun  (0),
        success (1),
        fail    (2)
    }
    MAX-ACCESS  read-only
    STATUS      current
    DESCRIPTION
        "The value of sbiRedSwitchoverScriptStatus indicates the results of
         executing the CLI script file specified in sbiRedSwitchoverScript."
    ::= { sysBootInfo 13 }

sbiAllowBootLicenseViolations    OBJECT-TYPE
    SYNTAX      TruthValue
    MAX-ACCESS  read-write
    STATUS      current
    DESCRIPTION
        "The value of sbiAllowBootLicenseViolations specifies whether the system
         should allow successful execution of the boot-up configuration file
         even if it contains license violations.  When enabled, the system will
         not error on any configuration that causes a license violation permitting
         the system to come into service.  However, if violations are detected the
         system will reboot after one hour if the violations are not fixed."
    DEFVAL      { true }
    ::= { sysBootInfo 14 }

sbiSnmpdMaxBulkDuration          OBJECT-TYPE
    SYNTAX      Unsigned32 (100..5000 | 4294967295)
    UNITS       "milliseconds"
    MAX-ACCESS  read-write
    STATUS      current
    DESCRIPTION
        "The value of sbiSnmpdMaxBulkDuration specifies the maximum duration to
         process the SNMP BULK request before the response is returned.

         The value all ones (4294967295) means that there is no maximum
         duration."
    DEFVAL      { 4294967295 }
    ::= { sysBootInfo 15 }

sbiSnmpdTransportProtocol        OBJECT-TYPE
    SYNTAX      BITS {
        udp (0),
        tcp (1)
    }
    MAX-ACCESS  read-write
    STATUS      current
    DESCRIPTION
        "The value of sbiSnmpdTransportProtocol specifies the transport
         protocol that the SNMP agent uses."
    DEFVAL      { {udp} }
    ::= { sysBootInfo 16 }

sysRadiusInfo                    OBJECT IDENTIFIER ::= { tmnxSysObjs 6 }

radiusOperStatus                 OBJECT-TYPE
    SYNTAX      INTEGER {
        up   (1),
        down (2)
    }
    MAX-ACCESS  read-only
    STATUS      current
    DESCRIPTION
        "The radiusOperStatus will have a value of 'up' if any one of the
         RADIUS servers in the radiusServerTable has the radiusServerOperStatus
         value of 'up'. It will have a value of 'down' if all the RADIUS
         servers in the radiusServerTable have the radiusServerOperStatus value
         of 'down'."
    ::= { sysRadiusInfo 1 }

radiusServerTable                OBJECT-TYPE
    SYNTAX      SEQUENCE OF RadiusServerEntry
    MAX-ACCESS  not-accessible
    STATUS      current
    DESCRIPTION
        "The radiusServerEntry has an entry for each RADIUS server. The table
         can have up to a maximum of 5 entries.

         Use TIMETRA-SECURITY-MIB::tmnxRadiusServerTable to configure entries."
    ::= { sysRadiusInfo 2 }

radiusServerEntry                OBJECT-TYPE
    SYNTAX      RadiusServerEntry
    MAX-ACCESS  not-accessible
    STATUS      current
    DESCRIPTION
        "Each row entry contains information about a RADIUS server."
    INDEX       { radiusServerIndex }
    ::= { radiusServerTable 1 }

RadiusServerEntry                ::= SEQUENCE
{
    radiusServerIndex                Unsigned32,
    radiusServerAddress              IpAddress,
    radiusServerOperStatus           INTEGER,
    radiusServerInetAddressType      InetAddressType,
    radiusServerInetAddress          InetAddress
}

radiusServerIndex                OBJECT-TYPE
    SYNTAX      Unsigned32 (1..5)
    MAX-ACCESS  not-accessible
    STATUS      current
    DESCRIPTION
        "The unique value which identifies a specific radius server."
    ::= { radiusServerEntry 1 }

radiusServerAddress              OBJECT-TYPE
    SYNTAX      IpAddress
    MAX-ACCESS  read-only
    STATUS      obsolete
    DESCRIPTION
        "The IP address of the RADIUS server.

         This object was made obsolete in the 5.0 release."
    ::= { radiusServerEntry 2 }

radiusServerOperStatus           OBJECT-TYPE
    SYNTAX      INTEGER {
        up   (1),
        down (2)
    }
    MAX-ACCESS  read-only
    STATUS      current
    DESCRIPTION
        "Current status of the RADIUS server."
    ::= { radiusServerEntry 3 }

radiusServerInetAddressType      OBJECT-TYPE
    SYNTAX      InetAddressType
    MAX-ACCESS  read-only
    STATUS      current
    DESCRIPTION
        "The value of radiusServerInetAddressType indicates the address type of
         radiusServerInetAddress address."
    ::= { radiusServerEntry 4 }

radiusServerInetAddress          OBJECT-TYPE
    SYNTAX      InetAddress (SIZE (0|4|16|20))
    MAX-ACCESS  read-only
    STATUS      current
    DESCRIPTION
        "The value of radiusServerInetAddress indicates the address of the
         Radius server."
    ::= { radiusServerEntry 5 }

tmnxSysNotifyObjs                OBJECT IDENTIFIER ::= { tmnxSysObjs 7 }

tmnxNotifyRow                    OBJECT-TYPE
    SYNTAX      RowPointer
    MAX-ACCESS  accessible-for-notify
    STATUS      current
    DESCRIPTION
        "tmnxNotifyRow is used by the configuration modify, create and delete
         traps. tmnxNotifyRow specifies the OID of the MIB table entry that was
         changed."
    ::= { tmnxSysNotifyObjs 1 }

tmnxNotifyRowAdminState          OBJECT-TYPE
    SYNTAX      TmnxAdminState
    MAX-ACCESS  accessible-for-notify
    STATUS      current
    DESCRIPTION
        "tmnxNotifyRowAdminState is used by the state change notification to
         specify the administrative state of the MIB table entry reported in
         the notification."
    ::= { tmnxSysNotifyObjs 2 }

tmnxNotifyRowOperState           OBJECT-TYPE
    SYNTAX      TmnxOperState
    MAX-ACCESS  accessible-for-notify
    STATUS      current
    DESCRIPTION
        "tmnxNotifyRowOperState is used by the state change notification to
         specify the operational state of the MIB table entry reported in the
         notification."
    ::= { tmnxSysNotifyObjs 3 }

tmnxMemoryModule                 OBJECT-TYPE
    SYNTAX      TNamedItem
    MAX-ACCESS  accessible-for-notify
    STATUS      current
    DESCRIPTION
        "tmnxMemoryModule is used by the module malloc failed notification to
         specify the memory module for which the trap is generated."
    ::= { tmnxSysNotifyObjs 4 }

tmnxModuleMallocSize             OBJECT-TYPE
    SYNTAX      Unsigned32
    UNITS       "bytes"
    MAX-ACCESS  accessible-for-notify
    STATUS      current
    DESCRIPTION
        "tmnxModuleMallocSize is used by the module malloc failed notification
         to specify the memory size (in bytes) requested in the failed malloc
         call."
    ::= { tmnxSysNotifyObjs 5 }

tmnxDroppedTrapID                OBJECT-TYPE
    SYNTAX      OBJECT IDENTIFIER
    MAX-ACCESS  accessible-for-notify
    STATUS      current
    DESCRIPTION
        "tmnxDroppedTrapID is used by the trap dropped notification to specify
         the NOTIFICATION-TYPE object identifier of the dropped trap."
    ::= { tmnxSysNotifyObjs 6 }

tmnxTrapDroppedReasonCode        OBJECT-TYPE
    SYNTAX      INTEGER {
        frequencyExceeded (1)
    }
    MAX-ACCESS  accessible-for-notify
    STATUS      current
    DESCRIPTION
        "tmnxTrapDroppedReasonCode is used by the trap dropped notification to
         specify the reason for which a trap is dropped."
    ::= { tmnxSysNotifyObjs 7 }

tmnxTrapDroppedEntryID           OBJECT-TYPE
    SYNTAX      OBJECT IDENTIFIER
    MAX-ACCESS  accessible-for-notify
    STATUS      current
    DESCRIPTION
        "tmnxTrapDroppedEntryID is used by the trap dropped notification to
         specify the table entry associated with the dropped trap."
    ::= { tmnxSysNotifyObjs 8 }

tmnxNotifyEntryOID               OBJECT-TYPE
    SYNTAX      OBJECT IDENTIFIER
    MAX-ACCESS  accessible-for-notify
    STATUS      current
    DESCRIPTION
        "tmnxNotifyEntryOID is used by the configuration modify, create and
         delete traps. tmnxNotifyEntryOID specifies the OID of the MIB table
         that was changed."
    ::= { tmnxSysNotifyObjs 9 }

tmnxSnmpdErrorMsg                OBJECT-TYPE
    SYNTAX      DisplayString
    MAX-ACCESS  accessible-for-notify
    STATUS      current
    DESCRIPTION
        "tmnxSnmpdErrorMsg is used by the tmnxSnmpdError notification to
         indicate the type of SNMP daemon error detected."
    ::= { tmnxSysNotifyObjs 10 }

tmnxPersistencyClient            OBJECT-TYPE
    SYNTAX      DisplayString
    MAX-ACCESS  accessible-for-notify
    STATUS      current
    DESCRIPTION
        "tmnxPersistencyClient is used by the persistencyClosedAlarmRaised,
         persistencyClosedAlarmCleared, persistencyFileSysThresRaised and
         persistencyFileSysThresCleared notification to indicate the affected
         persistent application."
    ::= { tmnxSysNotifyObjs 11 }

tmnxPersistencyFileLocator       OBJECT-TYPE
    SYNTAX      DisplayString
    MAX-ACCESS  accessible-for-notify
    STATUS      current
    DESCRIPTION
        "tmnxPersistencyFileLocator is used by the
         persistencyClosedAlarmRaised, persistencyClosedAlarmCleared,
         persistencyFileSysThresRaised and persistencyFileSysThresCleared
         notification to indicate the affected file used to store persistence
         data."
    ::= { tmnxSysNotifyObjs 12 }

tmnxPersistencyNotifyMsg         OBJECT-TYPE
    SYNTAX      DisplayString
    MAX-ACCESS  accessible-for-notify
    STATUS      current
    DESCRIPTION
        "tmnxPersistencyNotifyMsg is used by the persistencyClosedAlarmRaised
         persistencyClosedAlarmCleared, persistencyEventReport,
         persistencyFileSysThresRaised and persistencyFileSysThresCleared
         notification to provide additional information related to the event
         that occurred."
    ::= { tmnxSysNotifyObjs 13 }

tmnxPersistenceAffectedCpm       OBJECT-TYPE
    SYNTAX      DisplayString
    MAX-ACCESS  accessible-for-notify
    STATUS      current
    DESCRIPTION
        "tmnxPersistenceAffectedCpm is used by the
         persistencyClosedAlarmRaised, persistencyClosedAlarmCleared,
         persistencyFileSysThresRaised and persistencyFileSysThresCleared
         notification to indicate the affected CPM."
    ::= { tmnxSysNotifyObjs 14 }

tmnxSysTimeSetBy                 OBJECT-TYPE
    SYNTAX      INTEGER {
        ntp      (1),
        sntp     (2),
        snmp     (3),
        manually (4),
        rtc      (5)
    }
    MAX-ACCESS  accessible-for-notify
    STATUS      current
    DESCRIPTION
        "tmnxSysTimeSetBy is used by tmnxSysTimeSetBy notification to indicate
         who set the time."
    ::= { tmnxSysNotifyObjs 15 }

tmnxFtpFailureMsg                OBJECT-TYPE
    SYNTAX      DisplayString
    MAX-ACCESS  accessible-for-notify
    STATUS      current
    DESCRIPTION
        "tmnxFtpFailureMsg is used by tmnxFtpClientFailure notification to
         indicate FTP error."
    ::= { tmnxSysNotifyObjs 16 }

tmnxFtpFailureDestAddressType    OBJECT-TYPE
    SYNTAX      InetAddressType
    MAX-ACCESS  accessible-for-notify
    STATUS      current
    DESCRIPTION
        "tmnxFtpFailureDestAddressType is used by tmnxFtpClientFailure
         notification to indicate the IP address type of the remote host."
    ::= { tmnxSysNotifyObjs 17 }

tmnxFtpFailureDestAddress        OBJECT-TYPE
    SYNTAX      InetAddress (SIZE (4|16|20))
    MAX-ACCESS  accessible-for-notify
    STATUS      current
    DESCRIPTION
        "The value of tmnxFtpFailureDestAddress indicates the IP address of the
         remote host to which an ftp operation is being attempted on. The value
         of tmnxFtpFailureDestAddress is used by tmnxFtpClientFailure
         notification."
    ::= { tmnxSysNotifyObjs 18 }

tmnxNotifyObjectName             OBJECT-TYPE
    SYNTAX      DisplayString
    MAX-ACCESS  accessible-for-notify
    STATUS      current
    DESCRIPTION
        "tmnxNotifyObjectName is used by the configuration modify, create,
         delete and state change traps. tmnxNotifyObjectName specifies the
         human readable name of the OID instance of the MIB table entry that
         was changed."
    ::= { tmnxSysNotifyObjs 19 }

tmnxSyncFailureReason            OBJECT-TYPE
    SYNTAX      DisplayString
    MAX-ACCESS  accessible-for-notify
    STATUS      current
    DESCRIPTION
        "tmnxSyncFailureReason is used by the ssiSyncConfigFailed,
         ssiSyncBootEnvFailed, and ssiSyncRollbackFailed traps to specify the
         reason for synchronization failure."
    ::= { tmnxSysNotifyObjs 20 }

tmnxSysExecScript                OBJECT-TYPE
    SYNTAX      DisplayString
    MAX-ACCESS  accessible-for-notify
    STATUS      current
    DESCRIPTION
        "The value of tmnxSysExecScript specifies the location and name of the
         CLI command script file executed by a SROS CLI 'exec' command when the
         value of tmnxLogExRbkOpType is 'exec (1)'.

         When the value of tmnxLogExRbkOpType is 'vsd (4)', then the value of
         tmnxSysExecScript specifies an empty string.

         It is used by the tmnxSysExecStarted and tmnxSysExecFinished
         notifications."
    ::= { tmnxSysNotifyObjs 21 }

tmnxSysExecResult                OBJECT-TYPE
    SYNTAX      INTEGER {
        none    (0),
        success (1),
        fail    (2)
    }
    MAX-ACCESS  accessible-for-notify
    STATUS      current
    DESCRIPTION
        "The value of tmnxSysExecResult indicates the results of executing the
         CLI script file specified in tmnxSysExecScript. It is used by the
         tmnxSysExecFinished notification."
    ::= { tmnxSysNotifyObjs 22 }

tmnxSysRollbackFileType          OBJECT-TYPE
    SYNTAX      INTEGER {
        rollback (1),
        rescue   (2)
    }
    MAX-ACCESS  accessible-for-notify
    STATUS      current
    DESCRIPTION
        "tmnxSysRollbackFileType is used by tmnxSysRollbackStarted,
         tmnxSysRollbackSaveStarted, tmnxSysRollbackDeleteStarted,
         tmnxSysRollbackStatusChange, tmnxSysRollbackSaveStatusChange, and
         tmnxSysRollbackFileDeleteStatus notifications to indicate the type of
         file involved in a rollback operation."
    ::= { tmnxSysNotifyObjs 23 }

tmnxSysFileErrorType             OBJECT-TYPE
    SYNTAX      INTEGER {
        read  (1),
        write (2)
    }
    MAX-ACCESS  accessible-for-notify
    STATUS      current
    DESCRIPTION
        "tmnxSysFileErrorType is used by tmnxSysNvsysFileError notification to
         indicate the type of file error occurred."
    ::= { tmnxSysNotifyObjs 24 }

tmnxTrapDroppedCount             OBJECT-TYPE
    SYNTAX      Unsigned32
    MAX-ACCESS  accessible-for-notify
    STATUS      current
    DESCRIPTION
        "The object tmnxTrapDroppedCount is used by the tmnxTrapDropped
         notification to indicate the number of traps dropped.

         The value zero indicates that the number of traps dropped is purposely
         not included in the notification, for example because it is not
         accurately known."
    ::= { tmnxSysNotifyObjs 25 }

tmnxSysDNSSecDomainName          OBJECT-TYPE
    SYNTAX      TmnxDisplayStringURL
    MAX-ACCESS  accessible-for-notify
    STATUS      current
    DESCRIPTION
        "tmnxSysDNSSecDomainName is used by the sysDNSSecFailedAuthentication
         notification to indicate the domain name of the DNS query."
    ::= { tmnxSysNotifyObjs 26 }

tmnxSysLicenseErrorReason        OBJECT-TYPE
    SYNTAX      TItemDescription
    MAX-ACCESS  accessible-for-notify
    STATUS      current
    DESCRIPTION
        "The object tmnxSysLicenseErrorReason indicates the reason for an
         invalid license."
    ::= { tmnxSysNotifyObjs 27 }

tmnxSysLicenseTimeLeft           OBJECT-TYPE
    SYNTAX      Unsigned32
    UNITS       "minutes"
    MAX-ACCESS  accessible-for-notify
    STATUS      current
    DESCRIPTION
        "The object tmnxSysLicenseTimeLeft indicates the time remaining for the
         system to reboot as the result of an invalid license."
    ::= { tmnxSysNotifyObjs 28 }

tmnxSysNotifVsdServerName        OBJECT-TYPE
    SYNTAX      TLDisplayString
    MAX-ACCESS  accessible-for-notify
    STATUS      current
    DESCRIPTION
        "The value of tmnxSysNotifVsdServerName specifies the VSD server name."
    ::= { tmnxSysNotifyObjs 30 }

tmnxSysNotifXmppServerName       OBJECT-TYPE
    SYNTAX      DisplayString (SIZE (0..32))
    MAX-ACCESS  accessible-for-notify
    STATUS      current
    DESCRIPTION
        "The value of tmnxSysNotifXmppServerName indicates the name associated
         with the XMPP Server."
    ::= { tmnxSysNotifyObjs 31 }

tmnxSysLicenseErrorAction        OBJECT-TYPE
    SYNTAX      TItemDescription
    MAX-ACCESS  accessible-for-notify
    STATUS      current
    DESCRIPTION
        "The object tmnxSysLicenseErrorAction indicates the system action taken
         as a result of tmnxSysLicenseErrorReason."
    ::= { tmnxSysNotifyObjs 32 }

tmnxSysNotifAppStatsApplication  OBJECT-TYPE
    SYNTAX      TmnxSysLicenseApplication
    MAX-ACCESS  accessible-for-notify
    STATUS      current
    DESCRIPTION
        "The object tmnxSysNotifAppStatsApplication indicates an application in
         a virtual machine implementation that is subject to licensing."
    ::= { tmnxSysNotifyObjs 33 }

tmnxSysNotifAppStatsType         OBJECT-TYPE
    SYNTAX      TmnxSysLicenseAppStatsType
    MAX-ACCESS  accessible-for-notify
    STATUS      current
    DESCRIPTION
        "The object tmnxSysNotifAppStatsType indicates a type of statistics
         collected about an application in a virtual machine implementation
         subject to licensing."
    ::= { tmnxSysNotifyObjs 34 }

tmnxSysNotifAppStatsTime         OBJECT-TYPE
    SYNTAX      DateAndTime
    MAX-ACCESS  accessible-for-notify
    STATUS      current
    DESCRIPTION
        "The object tmnxSysNotifAppStatsTime indicates the time that the system
         collected statistics' values."
    ::= { tmnxSysNotifyObjs 35 }

tmnxNotifySysMgmtIfOriginalMode  OBJECT-TYPE
    SYNTAX      INTEGER {
        classic     (1),
        modelDriven (2),
        mixed       (3)
    }
    MAX-ACCESS  accessible-for-notify
    STATUS      current
    DESCRIPTION
        "tmnxNotifySysMgmtIfOriginalMode indicates the active system interface
         management mode the system was in when the configuration mode change
         request was sent."
    ::= { tmnxSysNotifyObjs 36 }

tmnxSysLicensingNotifyGroup      OBJECT-TYPE
    SYNTAX      TmnxSysLicensingGroup
    MAX-ACCESS  accessible-for-notify
    STATUS      current
    DESCRIPTION
        "The object tmnxSysLicensingNotifyGroup specifies the licensing group
         of an application license"
    ::= { tmnxSysNotifyObjs 37 }

tmnxSysLicensedNotifyAppName     OBJECT-TYPE
    SYNTAX      TNamedItem
    MAX-ACCESS  accessible-for-notify
    STATUS      current
    DESCRIPTION
        "The object tmnxSysLicensedNotifyAppName specifies the name of the
         licensed application"
    ::= { tmnxSysNotifyObjs 38 }

tmnxPrimaryConfigFileFormatType  OBJECT-TYPE
    SYNTAX      TmnxConfigFileFormatType
    MAX-ACCESS  accessible-for-notify
    STATUS      current
    DESCRIPTION
        "The value of tmnxPrimaryConfigFileFormatType specifies format of the
         primary configuration file."
    ::= { tmnxSysNotifyObjs 39 }

tmnxLiConfigFileFormatType       OBJECT-TYPE
    SYNTAX      TmnxConfigFileFormatType
    MAX-ACCESS  accessible-for-notify
    STATUS      current
    DESCRIPTION
        "The value of tmnxLiConfigFileFormatType specifies format of the li
         configuration file."
    ::= { tmnxSysNotifyObjs 40 }

tmnxSysAdditionalInfo            OBJECT-TYPE
    SYNTAX      DisplayString
    MAX-ACCESS  accessible-for-notify
    STATUS      current
    DESCRIPTION
        "The value of the object tmnxSubAdditionalInfo is a printable character
         string which contains information about the reason why the
         notification was generated."
    ::= { tmnxSysNotifyObjs 41 }

sysLoginControlInfo              OBJECT IDENTIFIER ::= { tmnxSysObjs 8 }

slcFtpInboundMaxSessions         OBJECT-TYPE
    SYNTAX      Unsigned32 (0..5)
    MAX-ACCESS  read-write
    STATUS      current
    DESCRIPTION
        "The maximum number of concurrent inbound FTP sessions permitted."
    DEFVAL      { 3 }
    ::= { sysLoginControlInfo 1 }

slcTelnetInboundMaxSessions      OBJECT-TYPE
    SYNTAX      Unsigned32 (0..50)
    MAX-ACCESS  read-write
    STATUS      current
    DESCRIPTION
        "The value of slcTelnetInboundMaxSessions specifies the maximum number
         of concurrent inbound telnet sessions permitted.

         Note: The actual number of permitted concurrent inbound TELNET
         sessions may also be restricted by a system wide cumulative limit of
         50 concurrent inbound (SSH / TELNET) sessions."
    DEFVAL      { 5 }
    ::= { sysLoginControlInfo 2 }

slcTelnetOutboundMaxSessions     OBJECT-TYPE
    SYNTAX      Unsigned32 (0..15)
    MAX-ACCESS  read-write
    STATUS      current
    DESCRIPTION
        "The value of slcTelnetOutboundMaxSessions specifies the maximum number
         of concurrent outbound telnet sessions permitted."
    DEFVAL      { 5 }
    ::= { sysLoginControlInfo 3 }

slcPreLoginMessage               OBJECT-TYPE
    SYNTAX      TmnxLongDisplayString (SIZE (0..900))
    MAX-ACCESS  read-write
    STATUS      current
    DESCRIPTION
        "The message to be displayed prior to the login prompt of an inbound
         FTP or telnet session."
    DEFVAL      { ''H }
    ::= { sysLoginControlInfo 4 }

slcPreLoginMessageInclName       OBJECT-TYPE
    SYNTAX      TruthValue
    MAX-ACCESS  read-write
    STATUS      current
    DESCRIPTION
        "If the value of slcPreLoginMessageInclName is set to 'TRUE', the
         slcPreLoginMessage which is displayed prior to the login prompt will
         contain the system name."
    DEFVAL      { false }
    ::= { sysLoginControlInfo 5 }

slcMessageOfTheDay               OBJECT-TYPE
    SYNTAX      TmnxLongDisplayString (SIZE (0..900))
    MAX-ACCESS  read-write
    STATUS      current
    DESCRIPTION
        "The value of object slcMessageOfTheDay specifies the message to
         display when the user successfully logs in to an inbound FTP, Telnet,
         SSH or console session.

         If slcMessageOfTheDayType is set to 'motd-type-none(0)', the value of
         slcMessageOfTheDay is not displayed.

         If slcMessageOfTheDayType is set to 'motd-type-url(1)', the syntax of
         slcMessageOfTheDay is refined to TmnxDisplayStringURL.

         If slcMessageOfTheDayType is set to 'motd-type-text(2)', the value of
         slcMessageOfTheDay is the NVT ASCII text to display.

         Objects slcMessageOfTheDay and slcMessageOfTheDayType must be set
         together in the same SNMP SET request PDU."
    DEFVAL      { ''H }
    ::= { sysLoginControlInfo 6 }

slcMessageOfTheDayType           OBJECT-TYPE
    SYNTAX      INTEGER {
        motd-type-none (0),
        motd-type-url  (1),
        motd-type-text (2)
    }
    MAX-ACCESS  read-write
    STATUS      current
    DESCRIPTION
        "The value of object slcMessageOfTheDayType specifies the type of
         slcMessageOfTheDay.

         If the value of slcMessageOfTheDayType is set to 'motd-type-none(0)',
         then the message of the day is not displayed.

         If the value of slcMessageOfTheDayType is set to 'motd-type-url(1)',
         then the message is fetched from the URL specified in object
         slcMessageOfTheDay.

         If the value of slcMessageOfTheDayType is set to 'motd-type-text(2)',
         then the value of slcMessageOfTheDay is displayed.

         Objects slcMessageOfTheDay and slcMessageOfTheDayType must be set
         together in the same SNMP SET request PDU."
    DEFVAL      { motd-type-none }
    ::= { sysLoginControlInfo 7 }

slcLoginBanner                   OBJECT-TYPE
    SYNTAX      TruthValue
    MAX-ACCESS  read-write
    STATUS      current
    DESCRIPTION
        "If the value of slcLoginBanner is set to 'true', the login banner
         containing Nokia copyright and version information is displayed prior
         to the login prompt. If the value is set to 'false', the login banner
         is not displayed."
    DEFVAL      { false }
    ::= { sysLoginControlInfo 8 }

slcLoginExponentialBackOff       OBJECT-TYPE
    SYNTAX      TruthValue
    MAX-ACCESS  read-write
    STATUS      current
    DESCRIPTION
        "The value of slcLoginExponentialBackOff specifies if
         exponential-backoff of the login prompt is enabled.
         Exponential-backoff is used to deter dictionary attacks. A value of
         'true' specifies that exponential-backoff is enabled, while a value of
         'false' indicates that exponential-backoff is disabled."
    DEFVAL      { false }
    ::= { sysLoginControlInfo 9 }

slcTelnetGracefulShutdown        OBJECT-TYPE
    SYNTAX      TruthValue
    MAX-ACCESS  read-write
    STATUS      current
    DESCRIPTION
        "The value of slcTelnetGracefulShutdown specifies if graceful shutdown
         is enabled. A value of 'true' specifies that telnet sessions are
         closed gracefully by using a TCP FIN/ACK handshake. A value of 'false'
         indicates that telnet sessions are disconnected by sending a RST
         (reset) TCP packet."
    DEFVAL      { false }
    ::= { sysLoginControlInfo 10 }

slcSSHGracefulShutdown           OBJECT-TYPE
    SYNTAX      TruthValue
    MAX-ACCESS  read-write
    STATUS      current
    DESCRIPTION
        "The value of slcSSHGracefulShutdown specifies if graceful shutdown is
         enabled. A value of 'true' specifies that SSH sessions are closed
         gracefully by using a TCP FIN/ACK handshake. A value of 'false'
         indicates that SSH sessions are disconnected by sending a RST (reset)
         TCP packet."
    DEFVAL      { true }
    ::= { sysLoginControlInfo 11 }

slcTelnetMinTTLValue             OBJECT-TYPE
    SYNTAX      Unsigned32 (0..255)
    MAX-ACCESS  read-write
    STATUS      current
    DESCRIPTION
        "The value of slcTelnetMinTTLValue specifies the minimum TTL value for
         an incoming packet.

         This object can only be set if the value of tmnxCpmPerPeerQueuing is
         'true (1)'.

         This value is applied after restarting the Telnet server.

         If slcTelnetMinTTLValue is set to zero (0), the TTL Security feature
         is disabled."
    DEFVAL      { 0 }
    ::= { sysLoginControlInfo 12 }

slcSSHMinTTLValue                OBJECT-TYPE
    SYNTAX      Unsigned32 (0..255)
    MAX-ACCESS  read-write
    STATUS      current
    DESCRIPTION
        "The value of slcSSHMinTTLValue specifies the minimum TTL value for an
         incoming packet.

         This object can only be set if the value of tmnxCpmPerPeerQueuing is
         'true (1)'.

         This value is applied after restarting the SSH server.

         If slcSSHMinTTLValue is set to zero (0), the TTL Security feature is
         disabled."
    DEFVAL      { 0 }
    ::= { sysLoginControlInfo 13 }

slcSSHInboundMaxSessions         OBJECT-TYPE
    SYNTAX      Unsigned32 (0..50)
    MAX-ACCESS  read-write
    STATUS      current
    DESCRIPTION
        "The value of slcSSHInboundMaxSessions specifies the maximum number of
         concurrent inbound SSH sessions permitted.

         Note: The actual number of permitted concurrent inbound SSH sessions
         may also be restricted by a system wide cumulative limit of 50
         concurrent inbound (SSH / TELNET) sessions."
    DEFVAL      { 5 }
    ::= { sysLoginControlInfo 14 }

slcSSHOutboundMaxSessions        OBJECT-TYPE
    SYNTAX      Unsigned32 (0..15)
    MAX-ACCESS  read-write
    STATUS      current
    DESCRIPTION
        "The value of slcSSHOutboundMaxSessions specifies the maximum number of
         concurrent outbound SSH sessions permitted."
    DEFVAL      { 5 }
    ::= { sysLoginControlInfo 15 }

slcIdleTimeout                   OBJECT-TYPE
    SYNTAX      Unsigned32 (1..1440 | 9999)
    UNITS       "minutes"
    MAX-ACCESS  read-write
    STATUS      current
    DESCRIPTION
        "The value of the object slcIdleTimeout specifies the maximum time of
         how long a user initiated session (console, telnet, SSH, FTP) can be
         inactive before it will be automatically closed by the system. The
         value of 9999 specifies that the system will never automatically close
         an inactive user initiated session."
    DEFVAL      { 30 }
    ::= { sysLoginControlInfo 16 }

slcLoginScriptGlobal             OBJECT-TYPE
    SYNTAX      TmnxDisplayStringURL
    MAX-ACCESS  read-write
    STATUS      current
    DESCRIPTION
        "The value of the object slcLoginScriptGlobal specifies the URL of a
         CLI script that is executed when any user opens a CLI session.

         This allows an operator, for example, to define a common set of CLI
         aliases that are made available on the router for all users. This
         global login-exec script is executed before any user-specific
         login-exec file that may be configured."
    DEFVAL      { ''H }
    ::= { sysLoginControlInfo 17 }

slcLoginScriptPerUserDirectory   OBJECT-TYPE
    SYNTAX      TmnxDisplayStringURL
    MAX-ACCESS  read-write
    STATUS      current
    DESCRIPTION
        "The value of the object slcLoginScriptPerUserDirectory specifies the
         user-directory of the per-user login script configured in
         slcLoginScriptPerUserFilename.

         This per-user script is executed before any other user-specific login
         script, like the one configured in tmnxUserConsoleLoginExecFile or the
         one specified in RADIUS attribute Timetra-Exec-File (6527-8)."
    DEFVAL      { ''H }
    ::= { sysLoginControlInfo 18 }

slcLoginScriptPerUserFilename    OBJECT-TYPE
    SYNTAX      DisplayString (SIZE (0..180))
    MAX-ACCESS  read-write
    STATUS      current
    DESCRIPTION
        "The value of the object slcLoginScriptPerUserFilename specifies the
         filename of the per-user login script.

         The per-user login script is defined by concatenating the value of
         slcLoginScriptPerUserDirectory, the username, and the value of
         slcLoginScriptPerUserFilename. For example : If the value of
         slcLoginScriptPerUserDirectory is 'cf1:/local/users' and the value of
         slcLoginScriptPerUserFilename is 'login-script.txt', then file
         'cf1:/local/users/john/login-script.txt' is executed when user 'john'
         opens a CLI session."
    DEFVAL      { ''H }
    ::= { sysLoginControlInfo 19 }

slcSSHMaxChannelsPerConnection   OBJECT-TYPE
    SYNTAX      Unsigned32 (1..50)
    MAX-ACCESS  read-write
    STATUS      current
    DESCRIPTION
        "The value of slcSSHMaxChannelsPerConnection specifies the maximum
         number of concurrent channels per SSH connection permitted.

         Note: The actual number of permitted concurrent channels per SSH
         connection may also be restricted by a system wide cumulative limit of
         50 concurrent inbound (SSH / TELNET) sessions, by user profile max
         session limit and by slcSSHInboundMaxSessions limit"
    DEFVAL      { 5 }
    ::= { sysLoginControlInfo 20 }

sysLACPInfo                      OBJECT IDENTIFIER ::= { tmnxSysObjs 9 }

sysLACPSystemPriority            OBJECT-TYPE
    SYNTAX      Unsigned32 (1..65535)
    MAX-ACCESS  read-write
    STATUS      current
    DESCRIPTION
        "sysLACPSystemPriority is the Link Aggregation Control Protocol (LACP)
         system priority which is combined with the system MAC address to make
         up a unique system ID that is used by LACP in communications with LACP
         peer systems on Link Aggregation (LAG) ports."
    DEFVAL      { 32768 }
    ::= { sysLACPInfo 1 }

sysTacplusInfo                   OBJECT IDENTIFIER ::= { tmnxSysObjs 10 }

tacplusOperStatus                OBJECT-TYPE
    SYNTAX      INTEGER {
        up   (1),
        down (2)
    }
    MAX-ACCESS  read-only
    STATUS      current
    DESCRIPTION
        "The tacplusOperStatus will have a value of 'up' if any one of the
         TACACS+ servers in the tacplusServerTable has the
         tacplusServerOperStatus value of 'up'. It will have a value of 'down'
         if all the TACACS+ servers in the tacplusServerTable have the
         tacplusServerOperStatus value of 'down'."
    ::= { sysTacplusInfo 1 }

tacplusServerTable               OBJECT-TYPE
    SYNTAX      SEQUENCE OF TacplusServerEntry
    MAX-ACCESS  not-accessible
    STATUS      current
    DESCRIPTION
        "The tacplusServerEntry has an entry for each TACACS+ server. The table
         can have up to a maximum of 5 entries.

         Use TIMETRA-SECURITY-MIB::tmnxTacPlusServerTable to configure entries."
    ::= { sysTacplusInfo 2 }

tacplusServerEntry               OBJECT-TYPE
    SYNTAX      TacplusServerEntry
    MAX-ACCESS  not-accessible
    STATUS      current
    DESCRIPTION
        "Each row entry contains information about a TACACS+ server."
    INDEX       { tacplusServerIndex }
    ::= { tacplusServerTable 1 }

TacplusServerEntry               ::= SEQUENCE
{
    tacplusServerIndex               Unsigned32,
    tacplusServerAddress             IpAddress,
    tacplusServerOperStatus          INTEGER,
    tacPlusServerInetAddressType     InetAddressType,
    tacPlusServerInetAddress         InetAddress
}

tacplusServerIndex               OBJECT-TYPE
    SYNTAX      Unsigned32 (1..5)
    MAX-ACCESS  not-accessible
    STATUS      current
    DESCRIPTION
        "The unique value which identifies a specific TACACS+ server."
    ::= { tacplusServerEntry 1 }

tacplusServerAddress             OBJECT-TYPE
    SYNTAX      IpAddress
    MAX-ACCESS  read-only
    STATUS      obsolete
    DESCRIPTION
        "The IP address of the TACACS+ server.

         This object was made obsolete in the 5.0 release."
    ::= { tacplusServerEntry 2 }

tacplusServerOperStatus          OBJECT-TYPE
    SYNTAX      INTEGER {
        up   (1),
        down (2)
    }
    MAX-ACCESS  read-only
    STATUS      current
    DESCRIPTION
        "Current status of the TACACS+ server."
    ::= { tacplusServerEntry 3 }

tacPlusServerInetAddressType     OBJECT-TYPE
    SYNTAX      InetAddressType
    MAX-ACCESS  read-only
    STATUS      current
    DESCRIPTION
        "The value of tacPlusServerInetAddressType indicates the address type
         of tacPlusServerInetAddress address."
    ::= { tacplusServerEntry 4 }

tacPlusServerInetAddress         OBJECT-TYPE
    SYNTAX      InetAddress (SIZE (0|4|16|20))
    MAX-ACCESS  read-only
    STATUS      current
    DESCRIPTION
        "The value of tacPlusServerInetAddress indicates the address of the
         Tacplus server."
    ::= { tacplusServerEntry 5 }

sysBofInfo                       OBJECT IDENTIFIER ::= { tmnxSysObjs 11 }

sbiActiveIpAddr                  OBJECT-TYPE
    SYNTAX      IpAddress
    MAX-ACCESS  read-write
    STATUS      current
    DESCRIPTION
        "The value of sbiActiveIpAddr specifies the IP address of the ethernet
         port on the active CPM."
    DEFVAL      { 0 }
    ::= { sysBofInfo 1 }

sbiActiveIpMask                  OBJECT-TYPE
    SYNTAX      IpAddressPrefixLength
    MAX-ACCESS  read-write
    STATUS      current
    DESCRIPTION
        "The value of sbiActiveIpMask specifies the mask length of the subnet
         associated with the IP address of the ethernet port on the active CPM."
    DEFVAL      { 0 }
    ::= { sysBofInfo 2 }

sbiStandbyIpAddr                 OBJECT-TYPE
    SYNTAX      IpAddress
    MAX-ACCESS  read-write
    STATUS      current
    DESCRIPTION
        "The value of sbiStandbyIpAddr specifies the IP address of the ethernet
         port on the standby CPM."
    DEFVAL      { 0 }
    ::= { sysBofInfo 3 }

sbiStandbyIpMask                 OBJECT-TYPE
    SYNTAX      IpAddressPrefixLength
    MAX-ACCESS  read-write
    STATUS      current
    DESCRIPTION
        "The value of sbiStandbyIpMask specifies the mask length of the subnet
         associated with the IP address of the ethernet port on the standby
         CPM."
    DEFVAL      { 0 }
    ::= { sysBofInfo 4 }

sbiPrimaryImage                  OBJECT-TYPE
    SYNTAX      TmnxBofDisplayStringURL
    MAX-ACCESS  read-write
    STATUS      current
    DESCRIPTION
        "The value of sbiPrimaryImage specifies the primary location of the
         directory that contains the runtime image files."
    DEFVAL      { ''H }
    ::= { sysBofInfo 5 }

sbiSecondaryImage                OBJECT-TYPE
    SYNTAX      TmnxBofDisplayStringURL
    MAX-ACCESS  read-write
    STATUS      current
    DESCRIPTION
        "The value of sbiSecondaryImage specifies the secondary location of the
         directory that contains the runtime image files."
    DEFVAL      { ''H }
    ::= { sysBofInfo 6 }

sbiTertiaryImage                 OBJECT-TYPE
    SYNTAX      TmnxBofDisplayStringURL
    MAX-ACCESS  read-write
    STATUS      current
    DESCRIPTION
        "The value of sbiTertiaryImage specifies the tertiary location of the
         directory that contains the runtime image files."
    DEFVAL      { ''H }
    ::= { sysBofInfo 7 }

sbiPrimaryConfigFile             OBJECT-TYPE
    SYNTAX      TmnxBofDisplayStringURL
    MAX-ACCESS  read-write
    STATUS      current
    DESCRIPTION
        "The value of sbiPrimaryConfigFile specifies the location and name of
         the primary configuration file."
    DEFVAL      { ''H }
    ::= { sysBofInfo 8 }

sbiSecondaryConfigFile           OBJECT-TYPE
    SYNTAX      TmnxBofDisplayStringURL
    MAX-ACCESS  read-write
    STATUS      current
    DESCRIPTION
        "The value of sbiSecondaryConfigFile specifies the location and name of
         the secondary configuration file."
    DEFVAL      { ''H }
    ::= { sysBofInfo 9 }

sbiTertiaryConfigFile            OBJECT-TYPE
    SYNTAX      TmnxBofDisplayStringURL
    MAX-ACCESS  read-write
    STATUS      current
    DESCRIPTION
        "The value of sbiTertiaryConfigFile specifies the location and name of
         the tertiary configuration file."
    DEFVAL      { ''H }
    ::= { sysBofInfo 10 }

sbiPersist                       OBJECT-TYPE
    SYNTAX      TruthValue
    MAX-ACCESS  read-write
    STATUS      current
    DESCRIPTION
        "The value of sbiPersist specifies whether or not the system will
         preserve SNMP indexes between reboots. When set to 'true', persistent
         indexing is enabled."
    DEFVAL      { false }
    ::= { sysBofInfo 11 }

sbiConsoleSpeed                  OBJECT-TYPE
    SYNTAX      Unsigned32 (9600 | 19200 | 38400 | 57600 | 115200)
    UNITS       "bps"
    MAX-ACCESS  read-write
    STATUS      current
    DESCRIPTION
        "The value of sbiConsoleSpeed specifies the baud rate of the console
         port."
    DEFVAL      { 115200 }
    ::= { sysBofInfo 12 }

sbiAutoNegotiate                 OBJECT-TYPE
    SYNTAX      TruthValue
    MAX-ACCESS  read-write
    STATUS      current
    DESCRIPTION
        "The value of sbiAutoNegotiate determines whether or not the speed and
         duplex parameters will be automatically negotiated on the CPM ethernet
         port. When set to 'true', auto-negotiation is enabled."
    DEFVAL      { true }
    ::= { sysBofInfo 13 }

sbiSpeed                         OBJECT-TYPE
    SYNTAX      Unsigned32 (10 | 100 | 1000)
    UNITS       "megabps"
    MAX-ACCESS  read-write
    STATUS      current
    DESCRIPTION
        "The value of sbiSpeed specifies the speed of the CPM ethernet port.
         This value is ignored if auto-negotiation is enabled."
    ::= { sysBofInfo 14 }

sbiDuplex                        OBJECT-TYPE
    SYNTAX      INTEGER {
        full (1),
        half (2)
    }
    MAX-ACCESS  read-write
    STATUS      current
    DESCRIPTION
        "The value of sbiDuplex specifies the duplex mode for the CPM ethernet
         port. This value is ignored if auto-negotiation is enabled."
    DEFVAL      { full }
    ::= { sysBofInfo 15 }

sbiPrimaryDns                    OBJECT-TYPE
    SYNTAX      IpAddress
    MAX-ACCESS  read-write
    STATUS      current
    DESCRIPTION
        "The value of sbiPrimaryDns specifies the IP address of the primary DNS
         server to use for DNS name resolution."
    DEFVAL      { 0 }
    ::= { sysBofInfo 16 }

sbiSecondaryDns                  OBJECT-TYPE
    SYNTAX      IpAddress
    MAX-ACCESS  read-write
    STATUS      current
    DESCRIPTION
        "The value of sbiSecondaryDns specifies the IP address of the secondary
         DNS server to use for DNS name resolution."
    DEFVAL      { 0 }
    ::= { sysBofInfo 17 }

sbiTertiaryDns                   OBJECT-TYPE
    SYNTAX      IpAddress
    MAX-ACCESS  read-write
    STATUS      current
    DESCRIPTION
        "The value of sbiTertiaryDns specifies the IP address of the tertiary
         DNS server to use for DNS name resolution."
    DEFVAL      { 0 }
    ::= { sysBofInfo 18 }

sbiDnsDomain                     OBJECT-TYPE
    SYNTAX      DisplayString (SIZE (0..178))
    MAX-ACCESS  read-write
    STATUS      current
    DESCRIPTION
        "The value of sbiDnsDomain specifies the domain name to use when
         performing DNS address resolution."
    DEFVAL      { ''H }
    ::= { sysBofInfo 19 }

sbiWait                          OBJECT-TYPE
    SYNTAX      Unsigned32 (1..10)
    UNITS       "seconds"
    MAX-ACCESS  read-write
    STATUS      current
    DESCRIPTION
        "The value of sbiWait specifies the number of seconds the system pauses
         at the start of the boot process. This pause allows the operator to
         interrupt the system initialization at the console and manually
         override the parameters in the BOF."
    DEFVAL      { 3 }
    ::= { sysBofInfo 20 }

sbiStaticRouteTable              OBJECT-TYPE
    SYNTAX      SEQUENCE OF SbiStaticRouteEntry
    MAX-ACCESS  not-accessible
    STATUS      current
    DESCRIPTION
        "The sbiStaticRouteTable contains an entry for each static route
         configured for the CPM ethernet port. These static routes are only
         used to route traffic generated by the CPM ethernet port. The table
         can have up to a maximum of 10 entries."
    ::= { sysBofInfo 21 }

sbiStaticRouteEntry              OBJECT-TYPE
    SYNTAX      SbiStaticRouteEntry
    MAX-ACCESS  not-accessible
    STATUS      current
    DESCRIPTION
        "Each row entry contains information about a static route configured
         for the CPM ethernet port.

         Entries in this table can be created and deleted via SNMP SET
         operations to sbiStaticRouteRowStatus."
    INDEX       {
        sbiStaticRouteDest,
        sbiStaticRouteMask
    }
    ::= { sbiStaticRouteTable 1 }

SbiStaticRouteEntry              ::= SEQUENCE
{
    sbiStaticRouteDest               IpAddress,
    sbiStaticRouteMask               IpAddressPrefixLength,
    sbiStaticRouteNextHop            IpAddress,
    sbiStaticRouteRowStatus          RowStatus
}

sbiStaticRouteDest               OBJECT-TYPE
    SYNTAX      IpAddress
    MAX-ACCESS  not-accessible
    STATUS      current
    DESCRIPTION
        "The value of sbiStaticRouteDest specifies the destination IP address
         of this static route."
    ::= { sbiStaticRouteEntry 1 }

sbiStaticRouteMask               OBJECT-TYPE
    SYNTAX      IpAddressPrefixLength
    MAX-ACCESS  not-accessible
    STATUS      current
    DESCRIPTION
        "The value of sbiStaticRouteMask specifies the length of the subnet
         mask associated with the destination IP address of this static route."
    ::= { sbiStaticRouteEntry 2 }

sbiStaticRouteNextHop            OBJECT-TYPE
    SYNTAX      IpAddress
    MAX-ACCESS  read-create
    STATUS      current
    DESCRIPTION
        "The value of sbiStaticRouteNextHop specifies the IP address of the
         next hop for this static route. This IP address should be in the same
         subnet as the ethernet port on the active CPM. The value of
         sbiStaticRouteNextHop must be set to a valid IP address for the row
         creation to succeed."
    ::= { sbiStaticRouteEntry 3 }

sbiStaticRouteRowStatus          OBJECT-TYPE
    SYNTAX      RowStatus
    MAX-ACCESS  read-create
    STATUS      current
    DESCRIPTION
        "sbiStaticRouteRowStatus controls the creation and deletion of rows in
         the table. To create a row in this table, set the row status to
         createAndGo(4)'. The value of sbiStaticRouteNextHop must also be set
         to a valid IP address for the row creation to succeed. To delete a row
         in this table, set the row status to destroy(6)."
    ::= { sbiStaticRouteEntry 4 }

sbiActiveIPv6Addr                OBJECT-TYPE
    SYNTAX      InetAddressIPv6
    MAX-ACCESS  read-write
    STATUS      current
    DESCRIPTION
        "The value of sbiActiveIPv6Addr specifies the IPv6 address of the
         ethernet port on the active CPM."
    DEFVAL      { '00000000000000000000000000000000'H }
    ::= { sysBofInfo 22 }

sbiActiveIPv6PfxLen              OBJECT-TYPE
    SYNTAX      InetAddressPrefixLength (0..128)
    MAX-ACCESS  read-write
    STATUS      current
    DESCRIPTION
        "The value of sbiActiveIPv6PfxLen specifies the prefix length of the
         subnet associated with the sbiActiveIPv6Addr address of the ethernet
         port on the active CPM."
    DEFVAL      { 0 }
    ::= { sysBofInfo 23 }

sbiStandbyIPv6Addr               OBJECT-TYPE
    SYNTAX      InetAddressIPv6
    MAX-ACCESS  read-write
    STATUS      current
    DESCRIPTION
        "The value of sbiStandbyIPv6Addr specifies the IPv6 address of the
         ethernet port on the standby CPM."
    DEFVAL      { '00000000000000000000000000000000'H }
    ::= { sysBofInfo 24 }

sbiStandbyIPv6PfxLen             OBJECT-TYPE
    SYNTAX      InetAddressPrefixLength (0..128)
    MAX-ACCESS  read-write
    STATUS      current
    DESCRIPTION
        "The value of sbiStandbyIPv6PfxLen specifies the prefix length of the
         subnet associated with the sbiStandbyIPv6Addr address of the ethernet
         port on the active CPM."
    DEFVAL      { 0 }
    ::= { sysBofInfo 25 }

sbiPrimaryDnsIPv6Addr            OBJECT-TYPE
    SYNTAX      InetAddressIPv6
    MAX-ACCESS  read-write
    STATUS      current
    DESCRIPTION
        "The value of sbiPrimaryDnsIPv6Addr specifies the IPv6 address of the
         primary DNS server to use for DNS name resolution."
    DEFVAL      { '00000000000000000000000000000000'H }
    ::= { sysBofInfo 26 }

sbiSecondaryDnsIPv6Addr          OBJECT-TYPE
    SYNTAX      InetAddressIPv6
    MAX-ACCESS  read-write
    STATUS      current
    DESCRIPTION
        "The value of sbiSecondaryDnsIPv6Addr specifies the IPv6 address of the
         secondary DNS server to use for DNS name resolution."
    DEFVAL      { '00000000000000000000000000000000'H }
    ::= { sysBofInfo 27 }

sbiTertiaryDnsIPv6Addr           OBJECT-TYPE
    SYNTAX      InetAddressIPv6
    MAX-ACCESS  read-write
    STATUS      current
    DESCRIPTION
        "The value of sbiTertiaryDnsIPv6Addr specifies the IPv6 address of the
         tertiary DNS server to use for DNS name resolution."
    DEFVAL      { '00000000000000000000000000000000'H }
    ::= { sysBofInfo 28 }

sbiStaticRouteIPv6Table          OBJECT-TYPE
    SYNTAX      SEQUENCE OF SbiStaticRouteIPv6Entry
    MAX-ACCESS  not-accessible
    STATUS      current
    DESCRIPTION
        "The sbiStaticRouteIPv6Table contains an entry for each static IPv6
         route configured for the CPM ethernet port. These static routes are
         only used to route traffic generated by the CPM ethernet port. The
         table can have up to a maximum of 10 entries."
    ::= { sysBofInfo 29 }

sbiStaticRouteIPv6Entry          OBJECT-TYPE
    SYNTAX      SbiStaticRouteIPv6Entry
    MAX-ACCESS  not-accessible
    STATUS      current
    DESCRIPTION
        "Each row entry contains information about a static IPv6 route
         configured for the CPM ethernet port.

         Entries in this table can be created and deleted via SNMP SET
         operations to sbiStaticRouteIPv6RowStatus."
    INDEX       {
        sbiStaticRouteIPv6Dest,
        sbiStaticRouteIPv6PfxLen
    }
    ::= { sbiStaticRouteIPv6Table 1 }

SbiStaticRouteIPv6Entry          ::= SEQUENCE
{
    sbiStaticRouteIPv6Dest           InetAddressIPv6,
    sbiStaticRouteIPv6PfxLen         InetAddressPrefixLength,
    sbiStaticRouteIPv6NextHop        InetAddressIPv6,
    sbiStaticRouteIPv6RowStatus      RowStatus
}

sbiStaticRouteIPv6Dest           OBJECT-TYPE
    SYNTAX      InetAddressIPv6
    MAX-ACCESS  not-accessible
    STATUS      current
    DESCRIPTION
        "The value of sbiStaticRouteIPv6Dest specifies the destination IPv6
         address of this static route."
    ::= { sbiStaticRouteIPv6Entry 1 }

sbiStaticRouteIPv6PfxLen         OBJECT-TYPE
    SYNTAX      InetAddressPrefixLength (0..128)
    MAX-ACCESS  not-accessible
    STATUS      current
    DESCRIPTION
        "The value of sbiStaticRouteIPv6PfxLen specifies the prefix length of
         sbiStaticRouteIPv6Dest, the destination IPv6 address of this static
         route."
    ::= { sbiStaticRouteIPv6Entry 2 }

sbiStaticRouteIPv6NextHop        OBJECT-TYPE
    SYNTAX      InetAddressIPv6
    MAX-ACCESS  read-create
    STATUS      current
    DESCRIPTION
        "The value of sbiStaticRouteIPv6NextHop specifies the IPv6 address of
         the next hop for this static route. This IPv6 address should be in the
         same subnet as the ethernet port on the active CPM. The value of
         sbiStaticRouteIPv6NextHop must be set to a valid IPv6 address for the
         row creation to succeed."
    ::= { sbiStaticRouteIPv6Entry 3 }

sbiStaticRouteIPv6RowStatus      OBJECT-TYPE
    SYNTAX      RowStatus
    MAX-ACCESS  read-create
    STATUS      current
    DESCRIPTION
        "sbiStaticRouteIPv6RowStatus controls the creation and deletion of rows
         in the table. To create a row in this table, set the row status to
         createAndGo(4)'. The value of sbiStaticRouteIPv6NextHop must also be
         set to a valid IPv6 address for the row creation to succeed. To delete
         a row in this table, set the row status to destroy(6)."
    ::= { sbiStaticRouteIPv6Entry 4 }

sbiLiSeparate                    OBJECT-TYPE
    SYNTAX      TruthValue
    MAX-ACCESS  read-write
    STATUS      current
    DESCRIPTION
        "The value of sbiLiSeparate specifies whether or not a non-LI user has
         access to Lawful Intercept (LI) information.  When sbiLiSeparate has
         a value of 'true', a user who does not have the TIMETRA-SECURITY-MIB::
         tmnxUserAccess 'li' bit set will not be allowed to access CLI or
         SNMP objects in the 'li' context.

         A change to the value of this object does not take affect until the
         system is rebooted."
    DEFVAL      { false }
    ::= { sysBofInfo 30 }

sbiLiLocalSave                   OBJECT-TYPE
    SYNTAX      TruthValue
    MAX-ACCESS  read-write
    STATUS      current
    DESCRIPTION
        "The value of sbiLiLocalSave specifies whether or not Lawful Intercept
         (LI) configuration is allowed to be save to a local file.

         A change to the value of this object does not take affect until the
         system is rebooted."
    DEFVAL      { true }
    ::= { sysBofInfo 31 }

sbiLicenseFile                   OBJECT-TYPE
    SYNTAX      TmnxBofDisplayStringURL
    MAX-ACCESS  read-write
    STATUS      current
    DESCRIPTION
        "The value of sbiLicenseFile specifies the location and name of the
         license file."
    DEFVAL      { ''H }
    ::= { sysBofInfo 32 }

sbiFips1402Level1                OBJECT-TYPE
    SYNTAX      TruthValue
    MAX-ACCESS  read-create
    STATUS      current
    DESCRIPTION
        "The value of sbiFips1402Level1 specifies whether or not the security
         level 1 of Federal Information Processing Standards 140 series version
         2 (FIPS-140-2) is enabled.

         A change to the value of this object does not take effect until after
         a system reboot.  If the value of sbiFips1402Level1 is 'true (1)',
         after a system reboot, any configuration that is not supported by
         FIPS-140-2 level 1, will be retrievable via SNMP requests."
    REFERENCE
        "FIPS PUB 140-2, 'Security Requirement for Cryptographic Modules',
         May 2001."
    DEFVAL      { false }
    ::= { sysBofInfo 34 }

sbiSystemBaseMacAddress          OBJECT-TYPE
    SYNTAX      MacAddress
    MAX-ACCESS  read-write
    STATUS      current
    DESCRIPTION
        "The value of sbiSystemBaseMacAddress specifies the administratively
         configured base system ethernet MAC address. Special purpose MAC
         addresses used by the system software are constructed from this base
         address. The value is the first MAC address in a contiguous range of
         1024 addresses.

         If configured, sbiSystemBaseMacAddress will override the value given
         by tmnxChassisBaseMacAddress.

         A value of all zeroes indicates this object is not configured."
    DEFVAL      { '000000000000'H }
    ::= { sysBofInfo 35 }

sbiEssSystemType                 OBJECT-TYPE
    SYNTAX      TruthValue
    MAX-ACCESS  read-write
    STATUS      current
    DESCRIPTION
        "The value of sbiEssSystemType specifies whether or not the system is
         administratively configured to function as a Nokia SROS Ethernet
         Service Switch (ESS)."
    DEFVAL      { false }
    ::= { sysBofInfo 36 }

sbiSystemProfile                 OBJECT-TYPE
    SYNTAX      INTEGER {
        none     (0),
        profileA (1),
        profileB (2)
    }
    MAX-ACCESS  read-write
    STATUS      current
    DESCRIPTION
        "The value of sbiSystemProfile specifies the system profile in the BOF.

           'none (0)'   - No system profile set, permits the co-existence of
                          FP3 and FP4-based line cards in the system.
           'profileA (1)- This system profile is primarily targeted at
                          subscriber services and layer 2/3 VPN business
                          services.
           'profileB (2)- This system profile is primarily targeted at
                          infrastructure routing, core, peering, and DC-GW
                          applications."
    DEFVAL      { none }
    ::= { sysBofInfo 37 }

sbiAutoBoot                      OBJECT-TYPE
    SYNTAX      TruthValue
    MAX-ACCESS  read-write
    STATUS      current
    DESCRIPTION
        "The value of sbiAutoBoot specifies whether or not the system will run
         the auto-provisioning agent."
    DEFVAL      { false }
    ::= { sysBofInfo 38 }

sbiAutoBootClientId              OBJECT-TYPE
    SYNTAX      OCTET STRING (SIZE (0..58))
    MAX-ACCESS  read-write
    STATUS      current
    DESCRIPTION
        "The value of sbiAutoBootClientId specifies the identifier to use when
         performing network discovery requests."
    DEFVAL      { "" }
    ::= { sysBofInfo 39 }

sbiAutoBootClientIdType          OBJECT-TYPE
    SYNTAX      INTEGER {
        none  (1),
        ascii (2),
        hex   (3),
        mac   (4)
    }
    MAX-ACCESS  read-write
    STATUS      current
    DESCRIPTION
        "The value of sbiAutoBootClientIdType represents how the value
         of sbiAutoBootClientId is encoded:
         - 'none (1)'  : no identification has been specified
         - 'ascii(2)'  : this option contains seven-bit ASCII characters
         - 'hex  (3)'  : this option contains octets. It must be displayed in
                        hexadecimal format because it contains non-printable
                        characters.
         - 'mac  (4)'  : this type is the chassis mac in octets. It must be displayed in
                        hexadecimal format because it contains non-printable
                        characters."
    DEFVAL      { none }
    ::= { sysBofInfo 40 }

sbiAutoBootUsingMgmt             OBJECT-TYPE
    SYNTAX      TruthValue
    MAX-ACCESS  read-write
    STATUS      current
    DESCRIPTION
        "The value of sbiAutoBootUsingMgmt specifies whether or not the system
         will auto-boot using the management port."
    DEFVAL      { false }
    ::= { sysBofInfo 41 }

sbiAutoBootUsingInband           OBJECT-TYPE
    SYNTAX      TruthValue
    MAX-ACCESS  read-write
    STATUS      current
    DESCRIPTION
        "The value of sbiAutoBootUsingInband specifies whether or not the
         system will auto-boot using the inband ports."
    DEFVAL      { false }
    ::= { sysBofInfo 42 }

sbiAutoBootInbandVlan            OBJECT-TYPE
    SYNTAX      Unsigned32 (0..4094)
    MAX-ACCESS  read-write
    STATUS      current
    DESCRIPTION
        "The value of sbiAutoBootInbandVlan specifies a VLAN that the system
         will use for auto-boot on inband ports."
    DEFVAL      { 0 }
    ::= { sysBofInfo 43 }

sbiAutoBootUsingIpv4             OBJECT-TYPE
    SYNTAX      TruthValue
    MAX-ACCESS  read-write
    STATUS      current
    DESCRIPTION
        "The value of sbiAutoBootUsingIpv4 specifies whether or not the system
         will send IPv4 DHCP Discovery requests."
    DEFVAL      { false }
    ::= { sysBofInfo 44 }

sbiAutoBootUsingIpv6             OBJECT-TYPE
    SYNTAX      TruthValue
    MAX-ACCESS  read-write
    STATUS      current
    DESCRIPTION
        "The value of sbiAutoBootUsingIpv6 specifies whether or not the system
         will send IPv6 DHCP Solicit requests."
    DEFVAL      { false }
    ::= { sysBofInfo 45 }

sbiAutoBootIncludeUserClass      OBJECT-TYPE
    SYNTAX      TruthValue
    MAX-ACCESS  read-write
    STATUS      current
    DESCRIPTION
        "The value of sbiAutoBootIncludeUserClass specifies whether or not the system
         will include User Class data information in  IPv4/IPv6 DHCP requests."
    DEFVAL      { false }
    ::= { sysBofInfo 46 }

sbiAutoBootVlanDiscovery         OBJECT-TYPE
    SYNTAX      TruthValue
    MAX-ACCESS  read-write
    STATUS      current
    DESCRIPTION
        "The value of sbiAutoBootVlanDiscovery specifies whether or not the
         system will use VLAN discovery."
    DEFVAL      { false }
    ::= { sysBofInfo 47 }

sbiAutoBootMode                  OBJECT-TYPE
    SYNTAX      INTEGER {
        dhcp (1),
        ospf (2)
    }
    MAX-ACCESS  read-write
    STATUS      current
    DESCRIPTION
        "The value of sbiAutoBootMode specifies the method/mode of auto-boot.
           dhcp - Use DHCP Discovery to learn IP Address/Provisioning URL
           ospf - Use OSPF Auto-Discovery with generated NEID/NEIP"
    DEFVAL      { dhcp }
    ::= { sysBofInfo 48 }

sbiAutoBootInfo                  OBJECT IDENTIFIER ::= { sysBofInfo 49 }

sbiAutoBootTimeout               OBJECT-TYPE
    SYNTAX      Unsigned32 (30..1440)
    UNITS       "minutes"
    MAX-ACCESS  read-write
    STATUS      current
    DESCRIPTION
        "The value of sbiAutoBootTimeout specifies the timeout for auto-boot.
         The system will reboot and re-attempt auto-boot after the timeout is
         reached."
    DEFVAL      { 30 }
    ::= { sbiAutoBootInfo 1 }

sbiAutoBootPortMtu               OBJECT-TYPE
    SYNTAX      Unsigned32 (0 | 512..9800)
    UNITS       "bytes"
    MAX-ACCESS  read-write
    STATUS      current
    DESCRIPTION
        "The value of sbiAutoBootPortMtu specifies the port MTU to use for
         auto-boot. A value of '0' indicates that the default port MTU will be
         used"
    DEFVAL      { 0 }
    ::= { sbiAutoBootInfo 2 }

sbiAutoBootOspf                  OBJECT IDENTIFIER ::= { sbiAutoBootInfo 3 }

sbiAutoBootOspfNeid              OBJECT-TYPE
    SYNTAX      TmnxSysNeid
    MAX-ACCESS  read-write
    STATUS      current
    DESCRIPTION
        "The value of sbiAutoBootOspfNeid specifies the Network Element
         Identifier to use in auto-boot.

         The first 8 high-order bits indicate the subnet ID and and range from
         0x1 to 0xFE. The 16 low-order bits indicate the basic ID and ranges
         from 0x0101 to 0xFFFE."
    DEFVAL      { ''H }
    ::= { sbiAutoBootOspf 1 }

sbiAutoBootOspfVendorId          OBJECT-TYPE
    SYNTAX      Unsigned32 (1..254)
    MAX-ACCESS  read-write
    STATUS      current
    DESCRIPTION
        "The value of sbiAutoBootOspfVendorId specifies the Vendor Id to use
         for NEIP generation. The default is '140' (Nokia)"
    DEFVAL      { 140 }
    ::= { sbiAutoBootOspf 2 }

sbiAutoBootOspfNeipV4Type        OBJECT-TYPE
    SYNTAX      InetAddressType
    MAX-ACCESS  read-write
    STATUS      current
    DESCRIPTION
        "The value of sbiAutoBootOspfNeipV4Type specifies the IP address type
         of sbiAutoBootOspfNeipV4.

         The value of sbiAutoBootOspfNeipV4Type can be either of 'ipv4(1)' or
         'unknown (0)'.

         The value of 'unknown(0)' specifies no NEIP v4 address is
         auto-generated from NEID and Vendor Id."
    DEFVAL      { unknown }
    ::= { sbiAutoBootOspf 3 }

sbiAutoBootOspfNeipV4            OBJECT-TYPE
    SYNTAX      InetAddress (SIZE (0|4))
    MAX-ACCESS  read-write
    STATUS      current
    DESCRIPTION
        "The value of sbiAutoBootOspfNeipV4 indicates the IPv4 address of the
         Network Element."
    DEFVAL      { ''H }
    ::= { sbiAutoBootOspf 4 }

sbiAutoBootOspfNeipV6Type        OBJECT-TYPE
    SYNTAX      InetAddressType
    MAX-ACCESS  read-write
    STATUS      current
    DESCRIPTION
        "The value of sbiAutoBootOspfNeipV6Type specifies the IP address type
         of sbiAutoBootOspfNeipV6.

         The value of sbiAutoBootOspfNeipV6Type can be either of 'ipv6(2)' or
         'unknown (0)'.

         The value of 'unknown(0)' specifies no NEIP v6 address is
         auto-generated from NEID and Vendor Id."
    DEFVAL      { unknown }
    ::= { sbiAutoBootOspf 5 }

sbiAutoBootOspfNeipV6            OBJECT-TYPE
    SYNTAX      InetAddress (SIZE (0|16))
    MAX-ACCESS  read-write
    STATUS      current
    DESCRIPTION
        "The value of sbiAutoBootOspfNeipV6 indicates the IPv6 address of the
         Network Element."
    DEFVAL      { ''H }
    ::= { sbiAutoBootOspf 6 }

sbiAutoBootOspfMtu               OBJECT-TYPE
    SYNTAX      Unsigned32 (0 | 512..9786)
    UNITS       "bytes"
    MAX-ACCESS  read-write
    STATUS      current
    DESCRIPTION
        "The value of sbiAutoBootOspfMtu specifies the OSPF MTU to use for
         auto-boot."
    DEFVAL      { 1500 }
    ::= { sbiAutoBootOspf 7 }

sbiAutoConfigure                 OBJECT IDENTIFIER ::= { sysBofInfo 54 }

sbiAutoIpv4                      OBJECT IDENTIFIER ::= { sbiAutoConfigure 1 }

sbiAutoIpv4Dhcp                  OBJECT-TYPE
    SYNTAX      TruthValue
    MAX-ACCESS  read-write
    STATUS      current
    DESCRIPTION
        "The value of sbiAutoIpv4Dhcp specifies if the system sends IPv4 DHCP
         Discovery requests."
    DEFVAL      { false }
    ::= { sbiAutoIpv4 1 }

sbiAutoIpv4DhcpClientIdType      OBJECT-TYPE
    SYNTAX      INTEGER {
        default (1),
        ascii   (2),
        hex     (3)
    }
    MAX-ACCESS  read-write
    STATUS      current
    DESCRIPTION
        "The value of sbiAutoIpv4DhcpClientIdType specifies how the value
         of sbiAutoIpv4DhcpClientId has to be interpreted:
         - 'default (1)'  : use the chassis serial number, formatted as ASCII characters
         - 'ascii(2)'  : seven-bit ASCII characters
         - 'hex  (3)'  : octets, possibly non-printable characters."
    DEFVAL      { default }
    ::= { sbiAutoIpv4 3 }

sbiAutoIpv4DhcpClientId          OBJECT-TYPE
    SYNTAX      OCTET STRING (SIZE (0..127))
    MAX-ACCESS  read-write
    STATUS      current
    DESCRIPTION
        "The value of sbiAutoIpv4DhcpClientId specifies the client identifier."
    DEFVAL      { "" }
    ::= { sbiAutoIpv4 4 }

sbiAutoIpv4DhcpOptUserClass      OBJECT-TYPE
    SYNTAX      TruthValue
    MAX-ACCESS  read-write
    STATUS      current
    DESCRIPTION
        "The value of sbiAutoIpv4DhcpOptUserClass specifies if the system DHCP
         client sends the User Class option."
    DEFVAL      { false }
    ::= { sbiAutoIpv4 5 }

sbiAutoIpv4DhcpTimeout           OBJECT-TYPE
    SYNTAX      Unsigned32 (1..65535)
    UNITS       "seconds"
    MAX-ACCESS  read-create
    STATUS      current
    DESCRIPTION
        "The value of the object sbiAutoIpv4DhcpTimeout specifies the maximum
         time the system DHCP client waits for a DHCPOFFER message.

         While the system waits for the DHCPOFFER message, reading of the
         configuration file is suspended."
    DEFVAL      { 30 }
    ::= { sbiAutoIpv4 6 }

sbiAutoIpv6                      OBJECT IDENTIFIER ::= { sbiAutoConfigure 2 }

sbiAutoIpv6Dhcp                  OBJECT-TYPE
    SYNTAX      TruthValue
    MAX-ACCESS  read-write
    STATUS      current
    DESCRIPTION
        "The value of sbiAutoIpv6Dhcp specifies if the system sends IPv6 DHCP
         Solicit requests."
    DEFVAL      { false }
    ::= { sbiAutoIpv6 1 }

sbiAutoIpv6DhcpClientIdType      OBJECT-TYPE
    SYNTAX      INTEGER {
        default        (1),
        duidEnterprise (2),
        duidLinkLocal  (3)
    }
    MAX-ACCESS  read-write
    STATUS      current
    DESCRIPTION
        "The value of sbiAutoIpv6DhcpClientIdType specifies how the DHCPv6
         client generates the Client Identifier option.

         A value of 'default' means the DHCPv6 client uses a Client Identifier
         with the chassis serial number, formatted as ASCII characters, in the
         variable length identifier following the DUID-EN type code and
         enterprise-number."
    DEFVAL      { default }
    ::= { sbiAutoIpv6 2 }

sbiAutoIpv6DhcpClientIdDuidType  OBJECT-TYPE
    SYNTAX      INTEGER {
        none  (1),
        ascii (2),
        hex   (3)
    }
    MAX-ACCESS  read-write
    STATUS      current
    DESCRIPTION
        "The value of sbiAutoIpv6DhcpClientIdDuidType specifies how the DUID in
         the sbiAutoIpv6DhcpClientIdDuid has to be interpreted.

         When the value of sbiAutoIpv6DhcpClientIdType is equal to
         'duidEnterprise', a value other than 'none' must be specified.

         A value other than 'none' is only allowed when the value of
         sbiAutoIpv6DhcpClientIdType is equal to 'duidEnterprise'."
    DEFVAL      { none }
    ::= { sbiAutoIpv6 3 }

sbiAutoIpv6DhcpClientIdDuid      OBJECT-TYPE
    SYNTAX      OCTET STRING (SIZE (0..124))
    MAX-ACCESS  read-write
    STATUS      current
    DESCRIPTION
        "The value of sbiAutoIpv6DhcpClientIdDuid specifies the client
         identifier DHCP Unique Identifier (DUID).

         When the value of sbiAutoIpv6DhcpClientIdDuidType is not equal to
         'none', a non-empty value must be specified.

         A non-empty value is only allowed when the value of
         sbiAutoIpv6DhcpClientIdDuidType is not equal to 'none'."
    DEFVAL      { "" }
    ::= { sbiAutoIpv6 4 }

sbiAutoIpv6DhcpOptUserClass      OBJECT-TYPE
    SYNTAX      TruthValue
    MAX-ACCESS  read-write
    STATUS      current
    DESCRIPTION
        "The value of sbiAutoIpv6DhcpOptUserClass specifies if the system
         DHCPv6 client sends the User Class option."
    DEFVAL      { false }
    ::= { sbiAutoIpv6 5 }

sbiAutoIpv6DhcpTimeout           OBJECT-TYPE
    SYNTAX      Unsigned32 (1..65535)
    UNITS       "seconds"
    MAX-ACCESS  read-create
    STATUS      current
    DESCRIPTION
        "The value of the object sbiAutoIpv6DhcpTimeout specifies the maximum
         time the system DHCPv6 client waits for an ADVERTISE message.

         While the system waits for the ADVERTISE message, reading of the
         configuration file is suspended."
    DEFVAL      { 30 }
    ::= { sbiAutoIpv6 6 }

sbiStandbyAIpAddr                OBJECT-TYPE
    SYNTAX      IpAddress
    MAX-ACCESS  read-write
    STATUS      current
    DESCRIPTION
        "The value of sbiStandbyAIpAddr specifies the IP address of the
         ethernet port on CPM A if CPM A is the standby CPM."
    DEFVAL      { 0 }
    ::= { sysBofInfo 55 }

sbiStandbyAIpMask                OBJECT-TYPE
    SYNTAX      IpAddressPrefixLength
    MAX-ACCESS  read-write
    STATUS      current
    DESCRIPTION
        "The value of sbiStandbyAIpMask specifies the mask length of the subnet
         associated with the IP address of the ethernet port on CPM A if CPM A
         is the standby CPM."
    DEFVAL      { 0 }
    ::= { sysBofInfo 56 }

sbiStandbyAIPv6Addr              OBJECT-TYPE
    SYNTAX      InetAddressIPv6
    MAX-ACCESS  read-write
    STATUS      current
    DESCRIPTION
        "The value of sbiStandbyAIPv6Addr specifies the IPv6 address of the
         ethernet port on CPM A if CPM A is the standby CPM"
    DEFVAL      { '00000000000000000000000000000000'H }
    ::= { sysBofInfo 57 }

sbiStandbyAIPv6PfxLen            OBJECT-TYPE
    SYNTAX      InetAddressPrefixLength (0..128)
    MAX-ACCESS  read-write
    STATUS      current
    DESCRIPTION
        "The value of sbiStandbyAIPv6PfxLen specifies the prefix length of the
         subnet associated with the sbiStandbyAIPv6Addr address of the ethernet
         port on CPM A if CPM A is the standby CPM"
    DEFVAL      { 0 }
    ::= { sysBofInfo 58 }

sbiStandbyBIpAddr                OBJECT-TYPE
    SYNTAX      IpAddress
    MAX-ACCESS  read-write
    STATUS      current
    DESCRIPTION
        "The value of sbiStandbyBIpAddr specifies the IP address of the
         ethernet port on CPM B if CPM B is the standby CPM."
    DEFVAL      { 0 }
    ::= { sysBofInfo 59 }

sbiStandbyBIpMask                OBJECT-TYPE
    SYNTAX      IpAddressPrefixLength
    MAX-ACCESS  read-write
    STATUS      current
    DESCRIPTION
        "The value of sbiStandbyBIpMask specifies the mask length of the subnet
         associated with the IP address of the ethernet port on CPM B if CPM B
         is the standby CPM."
    DEFVAL      { 0 }
    ::= { sysBofInfo 60 }

sbiStandbyBIPv6Addr              OBJECT-TYPE
    SYNTAX      InetAddressIPv6
    MAX-ACCESS  read-write
    STATUS      current
    DESCRIPTION
        "The value of sbiStandbyBIPv6Addr specifies the IPv6 address of the
         ethernet port on CPM B if CPM B is the standby CPM"
    DEFVAL      { '00000000000000000000000000000000'H }
    ::= { sysBofInfo 61 }

sbiStandbyBIPv6PfxLen            OBJECT-TYPE
    SYNTAX      InetAddressPrefixLength (0..128)
    MAX-ACCESS  read-write
    STATUS      current
    DESCRIPTION
        "The value of sbiStandbyBIPv6PfxLen specifies the prefix length of the
         subnet associated with the sbiStandbyBIPv6Addr address of the ethernet
         port on CPM B if CPM B is the standby CPM"
    DEFVAL      { 0 }
    ::= { sysBofInfo 62 }

sbiStandbyCIpAddr                OBJECT-TYPE
    SYNTAX      IpAddress
    MAX-ACCESS  read-write
    STATUS      current
    DESCRIPTION
        "The value of sbiStandbyCIpAddr specifies the IP address of the
         ethernet port on CPM C if CPM C is the standby CPM."
    DEFVAL      { 0 }
    ::= { sysBofInfo 63 }

sbiStandbyCIpMask                OBJECT-TYPE
    SYNTAX      IpAddressPrefixLength
    MAX-ACCESS  read-write
    STATUS      current
    DESCRIPTION
        "The value of sbiStandbyCIpMask specifies the mask length of the subnet
         associated with the IP address of the ethernet port on CPM C if CPM C
         is the standby CPM."
    DEFVAL      { 0 }
    ::= { sysBofInfo 64 }

sbiStandbyCIPv6Addr              OBJECT-TYPE
    SYNTAX      InetAddressIPv6
    MAX-ACCESS  read-write
    STATUS      current
    DESCRIPTION
        "The value of sbiStandbyCIPv6Addr specifies the IPv6 address of the
         ethernet port on CPM C if CPM C is the standby CPM"
    DEFVAL      { '00000000000000000000000000000000'H }
    ::= { sysBofInfo 65 }

sbiStandbyCIPv6PfxLen            OBJECT-TYPE
    SYNTAX      InetAddressPrefixLength (0..128)
    MAX-ACCESS  read-write
    STATUS      current
    DESCRIPTION
        "The value of sbiStandbyCIPv6PfxLen specifies the prefix length of the
         subnet associated with the sbiStandbyCIPv6Addr address of the ethernet
         port on CPM C if CPM C is the standby CPM"
    DEFVAL      { 0 }
    ::= { sysBofInfo 66 }

sbiStandbyDIpAddr                OBJECT-TYPE
    SYNTAX      IpAddress
    MAX-ACCESS  read-write
    STATUS      current
    DESCRIPTION
        "The value of sbiStandbyDIpAddr specifies the IP address of the
         ethernet port on CPM D if CPM D is the standby CPM."
    DEFVAL      { 0 }
    ::= { sysBofInfo 67 }

sbiStandbyDIpMask                OBJECT-TYPE
    SYNTAX      IpAddressPrefixLength
    MAX-ACCESS  read-write
    STATUS      current
    DESCRIPTION
        "The value of sbiStandbyDIpMask specifies the mask length of the subnet
         associated with the IP address of the ethernet port on CPM D if CPM D
         is the standby CPM."
    DEFVAL      { 0 }
    ::= { sysBofInfo 68 }

sbiStandbyDIPv6Addr              OBJECT-TYPE
    SYNTAX      InetAddressIPv6
    MAX-ACCESS  read-write
    STATUS      current
    DESCRIPTION
        "The value of sbiStandbyDIPv6Addr specifies the IPv6 address of the
         ethernet port on CPM D if CPM D is the standby CPM"
    DEFVAL      { '00000000000000000000000000000000'H }
    ::= { sysBofInfo 69 }

sbiStandbyDIPv6PfxLen            OBJECT-TYPE
    SYNTAX      InetAddressPrefixLength (0..128)
    MAX-ACCESS  read-write
    STATUS      current
    DESCRIPTION
        "The value of sbiStandbyDIPv6PfxLen specifies the prefix length of the
         subnet associated with the sbiStandbyDIPv6Addr address of the ethernet
         port on CPM D if CPM D is the standby CPM"
    DEFVAL      { 0 }
    ::= { sysBofInfo 70 }

sbiMgmtIfIpMtu                   OBJECT-TYPE
    SYNTAX      Unsigned32 (0 | 512..9786)
    UNITS       "bytes"
    MAX-ACCESS  read-write
    STATUS      current
    DESCRIPTION
        "The value of sbiMgmtIfIpMtu is used to reflect configures the
         IP maximum transmit unit (packet)  for the management router
         instance. The configured IP-MTU cannot be larger than
         the calculated IP MTU based on the port MTU configuration.

         When a SNMP SET request is received with a value of zero (0), the
         agent actually sets vRtrIfMtu to the calculated default size."
    DEFVAL      { 0 }
    ::= { sysBofInfo 71 }

sysPersistenceInfo               OBJECT IDENTIFIER ::= { tmnxSysObjs 12 }

sysPersistenceDhcpL2Info         OBJECT IDENTIFIER ::= { sysPersistenceInfo 1 }

spiDhcpL2PersistenceFileLocation OBJECT-TYPE
    SYNTAX      Unsigned32 (0..32)
    MAX-ACCESS  read-write
    STATUS      obsolete
    DESCRIPTION
        "The value of spiDhcpL2PersistenceFileLocation specifies the flash
         device on a CPM card where the data for handling DHCP Layer2
         persistency is stored. The value 0 indicates that no flash device is
         specified.

         This object was made obsolete in the 5.0 release."
    DEFVAL      { 0 }
    ::= { sysPersistenceDhcpL2Info 1 }

spiDhcpL2PersistenceDescription  OBJECT-TYPE
    SYNTAX      TItemDescription
    MAX-ACCESS  read-write
    STATUS      obsolete
    DESCRIPTION
        "The value of the object spiDhcpL2PersistenceDescription specifies a
         user provided description related to DHCP Layer-2 persistency. It
         consists of any printable, seven-bit ASCII characters up to 80
         characters in length.

         This object was made obsolete in the 5.0 release."
    DEFVAL      { "" }
    ::= { sysPersistenceDhcpL2Info 2 }

sysPersistenceDhcpL3Info         OBJECT IDENTIFIER ::= { sysPersistenceInfo 2 }

spiDhcpL3PersistenceFileLocation OBJECT-TYPE
    SYNTAX      Unsigned32 (0..32)
    MAX-ACCESS  read-write
    STATUS      obsolete
    DESCRIPTION
        "The value of spiDhcpL3PersistenceFileLocation specifies the flash
         device on a CPM card where the data for handling DHCP Layer3
         persistency is stored. The value 0 indicates that no flash device is
         specified.

         This object was made obsolete in the 5.0 release."
    DEFVAL      { 0 }
    ::= { sysPersistenceDhcpL3Info 1 }

spiDhcpL3PersistenceDescription  OBJECT-TYPE
    SYNTAX      TItemDescription
    MAX-ACCESS  read-write
    STATUS      obsolete
    DESCRIPTION
        "The value of the object spiDhcpL3PersistenceDescription specifies a
         user provided description related to DHCP Layer-3 persistency. It
         consists of any printable, seven-bit ASCII characters up to 80
         characters in length.

         This object was made obsolete in the 5.0 release."
    DEFVAL      { "" }
    ::= { sysPersistenceDhcpL3Info 2 }

sysPersistenceSubMgmtInfo        OBJECT IDENTIFIER ::= { sysPersistenceInfo 3 }

spiSubMgmtPersistenceFileLocation OBJECT-TYPE
    SYNTAX      Unsigned32 (0..32)
    MAX-ACCESS  read-write
    STATUS      current
    DESCRIPTION
        "The value of spiSubMgmtPersistenceFileLocation specifies the flash
         device on a CPM card where the data for handling subscriber management
         persistency is stored. The value 0 indicates that no flash device is
         specified."
    DEFVAL      { 0 }
    ::= { sysPersistenceSubMgmtInfo 1 }

spiSubMgmtPersistenceDescription OBJECT-TYPE
    SYNTAX      TItemDescription
    MAX-ACCESS  read-write
    STATUS      current
    DESCRIPTION
        "The value of the object spiSubMgmtPersistenceDescription specifies a
         user provided description related to subscriber management
         persistency. It consists of any printable, seven-bit ASCII characters
         up to 80 characters in length."
    DEFVAL      { "" }
    ::= { sysPersistenceSubMgmtInfo 2 }

sysPersistenceDhcpSrvInfo        OBJECT IDENTIFIER ::= { sysPersistenceInfo 4 }

spiDhcpSrvPersistenceFileLoc     OBJECT-TYPE
    SYNTAX      Unsigned32 (0..32)
    MAX-ACCESS  read-write
    STATUS      current
    DESCRIPTION
        "The value of spiDhcpSrvPersistenceFileLoc specifies the flash device
         on a CPM card where the data for handling the local DHCP server
         persistency is stored. The value 0 indicates that no flash device is
         specified."
    DEFVAL      { 0 }
    ::= { sysPersistenceDhcpSrvInfo 1 }

spiDhcpSrvPersistenceDescr       OBJECT-TYPE
    SYNTAX      TItemDescription
    MAX-ACCESS  read-write
    STATUS      current
    DESCRIPTION
        "The value of the object spiDhcpSrvPersistenceDescr specifies a user
         provided description related to the local DHCP server persistency. It
         consists of any printable, seven-bit ASCII characters up to 80
         characters in length."
    DEFVAL      { "" }
    ::= { sysPersistenceDhcpSrvInfo 2 }

sysPersistenceNatInfo            OBJECT IDENTIFIER ::= { sysPersistenceInfo 5 }

spiNatFwdPersistenceFileLoc      OBJECT-TYPE
    SYNTAX      Unsigned32 (0..32)
    MAX-ACCESS  read-write
    STATUS      current
    DESCRIPTION
        "The value of spiNatFwdPersistenceFileLoc specifies the flash device on
         a CPM card where the data for handling the NAT (Network Address
         Translation) port forwarding persistence is stored.

         The value 0 indicates that no flash device is specified."
    DEFVAL      { 0 }
    ::= { sysPersistenceNatInfo 1 }

spiNatFwdPersistenceDescr        OBJECT-TYPE
    SYNTAX      TItemDescription
    MAX-ACCESS  read-write
    STATUS      current
    DESCRIPTION
        "The value of the object spiNatFwdPersistenceDescr specifies a user
         provided description related to the NAT port forwarding persistence.
         It consists of any printable, seven-bit ASCII characters up to 80
         characters in length."
    DEFVAL      { "" }
    ::= { sysPersistenceNatInfo 2 }

sysPersistenceAAInfo             OBJECT IDENTIFIER ::= { sysPersistenceInfo 6 }

spiAAPersistenceFileLoc          OBJECT-TYPE
    SYNTAX      Unsigned32 (0..32)
    MAX-ACCESS  read-write
    STATUS      current
    DESCRIPTION
        "The value of spiAAPersistenceFileLoc specifies the flash device on a
         CPM card where the data for handling the AA (Application Assurance)
         persistence is stored.

         The value 0 indicates that no flash device is specified."
    DEFVAL      { 0 }
    ::= { sysPersistenceAAInfo 1 }

spiAAPersistenceDescr            OBJECT-TYPE
    SYNTAX      TItemDescription
    MAX-ACCESS  read-write
    STATUS      current
    DESCRIPTION
        "The value of the object spiAAPersistenceDescr specifies a user
         provided description related to the AA (Application Assurance)
         persistence. It consists of any printable, seven-bit ASCII characters
         up to 80 characters in length."
    DEFVAL      { "" }
    ::= { sysPersistenceAAInfo 2 }

sysPersistenceAncpInfo           OBJECT IDENTIFIER ::= { sysPersistenceInfo 7 }

spiAncpPersistenceFileLoc        OBJECT-TYPE
    SYNTAX      Unsigned32 (0..32)
    MAX-ACCESS  read-write
    STATUS      current
    DESCRIPTION
        "The value of spiAncpPersistenceFileLoc specifies the flash device on a
         CPM card where the data for handling the Ancp persistence is stored.

         The value 0 indicates that no flash device is specified."
    DEFVAL      { 0 }
    ::= { sysPersistenceAncpInfo 1 }

spiAncpPersistenceDescr          OBJECT-TYPE
    SYNTAX      TItemDescription
    MAX-ACCESS  read-write
    STATUS      current
    DESCRIPTION
        "The value of the object spiAncpPersistenceDescr specifies a user
         provided description related to the Ancp persistence. It consists of
         any printable, seven-bit ASCII characters up to 80 characters in
         length."
    DEFVAL      { "" }
    ::= { sysPersistenceAncpInfo 2 }

sysPersistencePythonInfo         OBJECT IDENTIFIER ::= { sysPersistenceInfo 8 }

spiPythonPersistenceFileLoc      OBJECT-TYPE
    SYNTAX      Unsigned32 (0..32)
    MAX-ACCESS  read-write
    STATUS      current
    DESCRIPTION
        "The value of spiPythonPersistenceFileLoc specifies the flash device on
         a CPM card where the data for handling the python persistence is
         stored.

         The value 0 indicates that no flash device is specified."
    DEFVAL      { 0 }
    ::= { sysPersistencePythonInfo 1 }

spiPythonPersistenceDescr        OBJECT-TYPE
    SYNTAX      TItemDescription
    MAX-ACCESS  read-write
    STATUS      current
    DESCRIPTION
        "The value of the object spiPythonPersistenceDescr specifies a user
         provided description related to the Python persistence. It consists of
         any printable, seven-bit ASCII characters up to 80 characters in
         length."
    DEFVAL      { "" }
    ::= { sysPersistencePythonInfo 2 }

tmnxDhcpLeaseTimeModeThreshold   OBJECT-TYPE
    SYNTAX      Unsigned32 (0..631152000)
    UNITS       "seconds"
    MAX-ACCESS  read-create
    STATUS      current
    DESCRIPTION
        "The value of tmnxDhcpLeaseTimeModeThreshold specifies the threshold
         time for DHCP leases to be eligible for persistence in the 'lease time
         mode' of operation.

         Normally, the expiry time of a DHCP lease is stored in the persistent
         database; in 'lease time mode', however, the full lease time is
         stored; the resource usage penalty is reasonably small for leases with
         sufficiently short lease times.

         DHCP leases with a lease time greater than the value of
         tmnxDhcpLeaseTimeModeThreshold have their expiry time stored as usual.

         DHCP leases with a lease time smaller than or equal to the value of
         tmnxDhcpLeaseTimeModeThreshold have their full lease time stored."
    DEFVAL      { 0 }
    ::= { sysPersistenceInfo 20 }

sysLiInfo                        OBJECT IDENTIFIER ::= { tmnxSysObjs 13 }

sliConfigStatus                  OBJECT-TYPE
    SYNTAX      INTEGER {
        notRun  (0),
        success (1),
        fail    (2)
    }
    MAX-ACCESS  read-only
    STATUS      current
    DESCRIPTION
        "The value of sliConfigStatus indicates the results of restoring the
         Lawful Intercept (LI) configuration at boot-up time."
    ::= { sysLiInfo 1 }

sliSaveConfig                    OBJECT-TYPE
    SYNTAX      TmnxActionType
    MAX-ACCESS  read-write
    STATUS      current
    DESCRIPTION
        "The value of sliSaveConfig specifies a desired action.  Setting
         this action variable to 'doAction' causes the current Lawful
         Intercept (LI) running configuration information, to be saved to
         a file called li.cfg in the same location as the BOF file.
         If the li.cfg file already exists, it will be renamed and a
         new file is created with the current running configuration.

         An attempt to set this object to 'doAction' when the booted value of
         sbiLiLocalSave is 'false' will result in an 'inconsistentValue' error.

         Default configuration values will be included in the saved
         configuration information."
    DEFVAL      { notApplicable }
    ::= { sysLiInfo 2 }

sliSaveConfigResult              OBJECT-TYPE
    SYNTAX      INTEGER {
        none       (1),
        inProgress (2),
        success    (3),
        failed     (4)
    }
    MAX-ACCESS  read-only
    STATUS      current
    DESCRIPTION
        "The value of sliSaveConfigResult represents the result of the
         last sliSaveConfig action.
         none(1)            None of the following apply
         inProgress(2)      The action is still in progress
         success(3)         The action completed successfully
         failed(4)          The action failed"
    ::= { sysLiInfo 3 }

sliConfigLastModified            OBJECT-TYPE
    SYNTAX      DateAndTime
    MAX-ACCESS  read-only
    STATUS      current
    DESCRIPTION
        "The value of sliConfigLastModified indicates the date and time the
         Lawful Intercept (LI) running configuration was last modified. If
         sliConfigLastModified is more recent than TIMETRA-CHASSIS-MIB::
         tmnxHwSwLastBoot, the current configuration may be different than that
         in the configuration file read upon system initialization."
    ::= { sysLiInfo 4 }

sliConfigLastSaved               OBJECT-TYPE
    SYNTAX      DateAndTime
    MAX-ACCESS  read-only
    STATUS      current
    DESCRIPTION
        "The value of sliConfigLastSaved indicates the date and
         time the current Lawful Intercept (LI) configuration was
         last saved.  If sliConfigLastSaved is more recent than the
         value of TIMETRA-CHASSIS-MIB::tmnxHwSwLastBoot, the
         initial configuration is likely to be different the next
         time the system is rebooted."
    ::= { sysLiInfo 5 }

sliFilterLock                    OBJECT-TYPE
    SYNTAX      INTEGER {
        locked             (0),
        unlockedForLiUsers (1),
        unlockedForAll     (2)
    }
    MAX-ACCESS  read-write
    STATUS      current
    DESCRIPTION
        "The of sliFilterLock specifies who can modify the Lawful Intercept
         (LI) filters.

         The value:
         'locked':             no users can modify the LI filters
         'unlockedForLiUsers': only users with LI privileges can modify the
                               LI filters
         'unlockedForAll':     all users can modify the LI filters."
    DEFVAL      { locked }
    ::= { sysLiInfo 6 }

sysDNSInfo                       OBJECT IDENTIFIER ::= { tmnxSysObjs 14 }

sysDNSInfoLastChanged            OBJECT-TYPE
    SYNTAX      TimeStamp
    MAX-ACCESS  read-only
    STATUS      current
    DESCRIPTION
        "The value of sysDNSInfoLastChanged is the timestamp of the last
         configuration changes to any of the DNS global settings."
    ::= { sysDNSInfo 1 }

sysDNSAddressResolvePref         OBJECT-TYPE
    SYNTAX      INTEGER {
        ipv4Only  (1),
        ipv6First (2)
    }
    MAX-ACCESS  read-write
    STATUS      current
    DESCRIPTION
        "The value of sysDNSAddressResolvePref specifies how the DNS client
         will request for address resolution.

         ipv4-only:  The DNS client will only try to resolve a domain name
                     into an ipv4 address.

         ipv6-first: the DNS client will first try to resolve the
                     domain name in to ipv6 address. If no ipv6 address
                     is available it will try to resolve the domain name
                     into an ipv4 address."
    DEFVAL      { ipv4Only }
    ::= { sysDNSInfo 2 }

sysDNSSecAdValidation            OBJECT-TYPE
    SYNTAX      TruthValue
    MAX-ACCESS  read-write
    STATUS      current
    DESCRIPTION
        "The value of sysDNSSecAdValidation specifies whether or not the
         presence of the Authenticated Data (AD) bit in responses is validated
         from the DNS servers.

         When sysDNSSecAdValidation is set to 'true (1)', DNSSEC validation is
         enabled and a warning is reported to the SECURITY log if the AD-bit is
         not set in responses from the DNS servers. The notification
         responsible for the warning is sysDNSSecFailedAuthentication.

         When sysDNSSecAdValidation is set to 'false (2)', DNSSEC validation of
         the AD-bit is disabled."
    DEFVAL      { false }
    ::= { sysDNSInfo 3 }

sysDNSSecRespCtrl                OBJECT-TYPE
    SYNTAX      INTEGER {
        fallThrough (1),
        drop        (2)
    }
    MAX-ACCESS  read-write
    STATUS      current
    DESCRIPTION
        "The value of sysDNSSecRespCtrl specifies whether the system will
         permit or reject DNS responses that do not pass DNSSEC validation. The
         value of this object is ignored if sysDNSSecAdValidation is set to
         'false (2)'.

         When sysDNSSecRespCtrl is set to 'fallThrough (1)', the system will
         permit DNS responses that do not pass DNSSEC validation, allowing the
         resolution to complete.

         When sysDNSSecRespCtrl is set to 'drop (2)', the system will reject
         DNS responses that do not pass DNSSEC validation, and the resolution
         will appear to fail."
    DEFVAL      { drop }
    ::= { sysDNSInfo 4 }

sysIcmpVSInfo                    OBJECT IDENTIFIER ::= { tmnxSysObjs 15 }

sysIcmpVSEnhancement             OBJECT-TYPE
    SYNTAX      TmnxEnabledDisabled
    MAX-ACCESS  read-write
    STATUS      current
    DESCRIPTION
        "The value of sysIcmpVSEnhancement specifies if vendor specific
         extensions to ICMP is enabled or not."
    DEFVAL      { disabled }
    ::= { sysIcmpVSInfo 1 }

sysEthInfo                       OBJECT IDENTIFIER ::= { tmnxSysObjs 16 }

sysNewQinqUntaggedSap            OBJECT-TYPE
    SYNTAX      TruthValue
    MAX-ACCESS  read-write
    STATUS      current
    DESCRIPTION
        "The value of sysNewQinqUntaggedSap controls the forwarding of packets
         on a QinQ X.0 access SAP.

         When sysNewQinqUntaggedSap is set to true, the SAP will only accept:

         - frames with a single tag matching the SAP's outer tag or,
         - frames with double tag where the outer tag matches the SAP's outer
           tag and inner tag is set to 0.

         When sysNewQinqUntaggedSap is set to false, forwarding of packets
         remains unchanged."
    DEFVAL      { false }
    ::= { sysEthInfo 1 }

tmnxSysRollbackInfo              OBJECT IDENTIFIER ::= { tmnxSysObjs 17 }

tmnxSysRollbackIndex             OBJECT-TYPE
    SYNTAX      Unsigned32 (0..199)
    MAX-ACCESS  read-write
    STATUS      current
    DESCRIPTION
        "The value of tmnxSysRollbackIndex specifies a specific rollback
         checkpoint file to which a rollback action can be taken.

         The value of the tmnxSysRollbackIndex corresponds to a rollback
         checkpoint file with suffix .rb.index.

         The maximum checkpoint file that can be specified is determined by the
         rollback location as specified by tmnxSysRollbackLocation. If the
         location is on a compact flash, then the maximum value of
         tmnxSysRollbackIndex can be tmnxSysRollbackMaxLocalFiles minus 1. If
         the location is a remote ftp location, then the maximum value of
         tmnxSysRollbackIndex can be tmnxSysRollbackMaxRemoteFiles minus 1.

         This index is SET along with another action object, including
         tmnxSysRollbackStart to initiate a rollback revert of a file and
         tmnxSysRollbackFileDelete to delete a rollback file.

         An SNMP GET request on this object should return the last SET value."
    ::= { tmnxSysRollbackInfo 1 }

tmnxSysRollbackStart             OBJECT-TYPE
    SYNTAX      TmnxActionType
    MAX-ACCESS  read-write
    STATUS      current
    DESCRIPTION
        "The value of tmnxSysRollbackStart specifies whether to revert the
         rollback file specified by tmnxSysRollbackIndex.

         When SET to the value of 'doAction' the system will revert the
         rollback file specified by tmnxSysRollbackIndex.

         This variable must be set along with tmnxSysRollbackIndex to indicate
         the specific rollback file to revert.

         An SNMP GET request on this object should return 'notApplicable'."
    DEFVAL      { notApplicable }
    ::= { tmnxSysRollbackInfo 2 }

tmnxSysRollbackResult            OBJECT-TYPE
    SYNTAX      INTEGER {
        none        (1),
        inProgress  (2),
        success     (3),
        failed      (4),
        interrupted (5)
    }
    MAX-ACCESS  read-only
    STATUS      current
    DESCRIPTION
        "The value of tmnxSysRollbackResult indicates the result of the last
         tmnxSysRollbackStart action.

         none(1)            None of the following apply
         inProgress(2)      The action is still in progress
         success(3)         The action completed successfully
         failed(4)          The action failed
         interrupted (5)    The action was interrupted"
    ::= { tmnxSysRollbackInfo 3 }

tmnxSysRollbackSave              OBJECT-TYPE
    SYNTAX      TmnxActionType
    MAX-ACCESS  read-write
    STATUS      current
    DESCRIPTION
        "The value of tmnxSysRollbackSave specifies whether to save the
         existing configuration in a rollback checkpoint file.

         When SET to the value of 'doAction' the system will save the
         configuration in a new rollback checkpoint file, with suffix '.rb'.
         Previously saved rollback files with the same name will increment the
         filename suffix by 1 up to a maximum of 9. For example, file.rb is
         moved to file.rb.1. The higher the number, the older the file is.

         An SNMP GET request on this object should return 'notApplicable'."
    DEFVAL      { notApplicable }
    ::= { tmnxSysRollbackInfo 4 }

tmnxSysRollbackSaveResult        OBJECT-TYPE
    SYNTAX      INTEGER {
        none       (1),
        inProgress (2),
        success    (3),
        failed     (4)
    }
    MAX-ACCESS  read-only
    STATUS      current
    DESCRIPTION
        "The value of tmnxSysRollbackSaveResult indicates the result of the
         last tmnxSysRollbackSave action.

         none(1)            None of the following apply
         inProgress(2)      The action is still in progress
         success(3)         The action completed successfully
         failed(4)          The action failed"
    ::= { tmnxSysRollbackInfo 5 }

tmnxSysRollbackLocation          OBJECT-TYPE
    SYNTAX      TmnxDisplayStringURL
    MAX-ACCESS  read-write
    STATUS      current
    DESCRIPTION
        "The value of tmnxSysRollbackLocation specifies the destination filepath
         or file-URL where the current running configuration information
         will be saved when tmnxSysRollbackSave is set to 'doAction'.  If
         the value of tmnxSysRollbackLocation is an empty string the system will
         attempt to store the file in the best available location locally,
         for example compact flash 1 or 2 if either is present."
    DEFVAL      { ''H }
    ::= { tmnxSysRollbackInfo 6 }

tmnxSysRollbackRevertIndex       OBJECT-TYPE
    SYNTAX      Unsigned32 (0..199)
    MAX-ACCESS  read-only
    STATUS      current
    DESCRIPTION
        "The value of tmnxSysRollbackRevertIndex indicates the last rollback
         checkpoint file reverted on the system."
    ::= { tmnxSysRollbackInfo 7 }

tmnxSysRollbackRevertEndTime     OBJECT-TYPE
    SYNTAX      DateAndTime
    MAX-ACCESS  read-only
    STATUS      current
    DESCRIPTION
        "The value of tmnxSysRollbackRevertEndTime indicates the timestamp the
         last rollback revert on the system is completed.

         The value of tmnxSysRollbackRevertEndTime is affected by the value of
         stiPreferLocalTime."
    ::= { tmnxSysRollbackInfo 8 }

tmnxSysRollbackSavedTime         OBJECT-TYPE
    SYNTAX      DateAndTime
    MAX-ACCESS  read-only
    STATUS      current
    DESCRIPTION
        "The value of tmnxSysRollbackSavedTime indicates the timestamp the last
         rollback save on the system is completed.

         The value of tmnxSysRollbackSavedTime is affected by the value of
         stiPreferLocalTime."
    ::= { tmnxSysRollbackInfo 9 }

tmnxSysRollbackRevertStartTime   OBJECT-TYPE
    SYNTAX      DateAndTime
    MAX-ACCESS  read-only
    STATUS      current
    DESCRIPTION
        "The value of tmnxSysRollbackRevertStartTime indicates the timestamp
         the last rollback file reverted on the system is initiated.

         The value of tmnxSysRollbackRevertStartTime is affected by the value
         of stiPreferLocalTime."
    ::= { tmnxSysRollbackInfo 10 }

tmnxSysRollbackRevertUserName    OBJECT-TYPE
    SYNTAX      TNamedItemOrEmpty
    MAX-ACCESS  read-only
    STATUS      current
    DESCRIPTION
        "The value of tmnxSysRollbackRevertUserName indicates the name of a
         system user who initiated the last rollback revert."
    DEFVAL      { ''H }
    ::= { tmnxSysRollbackInfo 11 }

tmnxSysRollbackRevertFilename    OBJECT-TYPE
    SYNTAX      TmnxDisplayStringURL
    MAX-ACCESS  read-only
    STATUS      current
    DESCRIPTION
        "The value of tmnxSysRollbackRevertFilename specifies the filepath or
         file-URL of the last reverted rollback file."
    DEFVAL      { ''H }
    ::= { tmnxSysRollbackInfo 12 }

tmnxSysRollbackSaveComment       OBJECT-TYPE
    SYNTAX      DisplayString (SIZE (0..255))
    MAX-ACCESS  read-write
    STATUS      current
    DESCRIPTION
        "The value of the object tmnxSysRollbackSaveComment specifies a user
         provided comment related to the rollback checkpoint file about to be
         saved.

         It consists of any printable, seven-bit ASCII characters up to 255
         characters in length."
    DEFVAL      { ''H }
    ::= { tmnxSysRollbackInfo 13 }

tmnxSysRollbackFileDelete        OBJECT-TYPE
    SYNTAX      TmnxActionType
    MAX-ACCESS  read-write
    STATUS      current
    DESCRIPTION
        "The value of tmnxSysRollbackFileDelete specifies whether to delete the
         rollback file specified by tmnxSysRollbackIndex.

         When SET to the value of 'doAction' the system will delete the
         rollback file specified by tmnxSysRollbackIndex.

         This variable must be set along with tmnxSysRollbackIndex to specify
         the specific rollback file to delete.

         An SNMP GET request on this object should return 'notApplicable'."
    DEFVAL      { notApplicable }
    ::= { tmnxSysRollbackInfo 14 }

tmnxSysRollbackFileDeleteResult  OBJECT-TYPE
    SYNTAX      INTEGER {
        none       (1),
        inProgress (2),
        success    (3),
        failed     (4)
    }
    MAX-ACCESS  read-only
    STATUS      current
    DESCRIPTION
        "The value of tmnxSysRollbackFileDeleteResult indicates the result of
         the last tmnxSysRollbackFileDelete action.

         none(1)            None of the following apply
         inProgress(2)      The action is still in progress
         success(3)         The action completed successfully
         failed(4)          The action failed"
    ::= { tmnxSysRollbackInfo 15 }

tmnxSysRollbackAbortRevert       OBJECT-TYPE
    SYNTAX      TmnxActionType
    MAX-ACCESS  read-write
    STATUS      current
    DESCRIPTION
        "The value of tmnxSysRollbackAbortRevert specifies whether to abort the
         rollback revert that's currently in progress.

         When SET to the value of 'doAction' the system will abort the active
         rollback revert. This will leave the system in an unknown state, so it
         should be used with care.

         An SNMP GET request on this object should return 'notApplicable'."
    DEFVAL      { notApplicable }
    ::= { tmnxSysRollbackInfo 16 }

tmnxSysRollbackRescueLocation    OBJECT-TYPE
    SYNTAX      TmnxDisplayStringURL
    MAX-ACCESS  read-write
    STATUS      current
    DESCRIPTION
        "The value of tmnxSysRollbackRescueLocation specifies the destination
         file path or file-URL where the rollback rescue configuration file
         will be saved.  If the value of tmnxSysRollbackRescueLocation is
         an empty string the system will attempt to store the file in the
         best available location locally, for example compact flash 1 or 2
         if either is present."
    DEFVAL      { ''H }
    ::= { tmnxSysRollbackInfo 17 }

tmnxSysRollbackRescueRevert      OBJECT-TYPE
    SYNTAX      TmnxActionType
    MAX-ACCESS  read-write
    STATUS      current
    DESCRIPTION
        "The value of tmnxSysRollbackRescueRevert specifies whether to revert
         the rollback rescue file located in tmnxSysRollbackRescueLocation.

         When SET to the value of 'doAction' the system will revert the
         rollback rescue file.

         An SNMP GET request on this object should return 'notApplicable'."
    DEFVAL      { notApplicable }
    ::= { tmnxSysRollbackInfo 18 }

tmnxSysRollbackRescueSave        OBJECT-TYPE
    SYNTAX      TmnxActionType
    MAX-ACCESS  read-write
    STATUS      current
    DESCRIPTION
        "The value of tmnxSysRollbackRescueSave specifies whether to save the
         existing configuration in the rollback rescue file located in
         tmnxSysRollbackRescueLocation.

         When SET to the value of 'doAction' the system will save the
         configuration to the rollback rescue file.

         An SNMP GET request on this object should return 'notApplicable'."
    DEFVAL      { notApplicable }
    ::= { tmnxSysRollbackInfo 19 }

tmnxSysRollbackRescueDelete      OBJECT-TYPE
    SYNTAX      TmnxActionType
    MAX-ACCESS  read-write
    STATUS      current
    DESCRIPTION
        "The value of tmnxSysRollbackRescueDelete specifies whether to delete
         the rollback rescue file located in tmnxSysRollbackRescueLocation.

         When SET to the value of 'doAction' the system will delete the
         rollback rescue file.

         An SNMP GET request on this object should return 'notApplicable'."
    DEFVAL      { notApplicable }
    ::= { tmnxSysRollbackInfo 20 }

tmnxSysRollbackRescueSaveRes     OBJECT-TYPE
    SYNTAX      INTEGER {
        none       (1),
        inProgress (2),
        success    (3),
        failed     (4)
    }
    MAX-ACCESS  read-only
    STATUS      current
    DESCRIPTION
        "The value of tmnxSysRollbackRescueSaveRes indicates the result of the
         last tmnxSysRollbackRescueSave action.

         none(1)            None of the following apply
         inProgress(2)      The action is still in progress
         success(3)         The action completed successfully
         failed(4)          The action failed"
    ::= { tmnxSysRollbackInfo 21 }

tmnxSysRollbackRescueRevertRes   OBJECT-TYPE
    SYNTAX      INTEGER {
        none        (1),
        inProgress  (2),
        success     (3),
        failed      (4),
        interrupted (5)
    }
    MAX-ACCESS  read-only
    STATUS      current
    DESCRIPTION
        "The value of tmnxSysRollbackRescueRevertRes indicates the result of
         the last tmnxSysRollbackRescueRevert action.

         none(1)            None of the following apply
         inProgress(2)      The action is still in progress
         success(3)         The action completed successfully
         failed(4)          The action failed
         interrupted (5)    The action was interrupted"
    ::= { tmnxSysRollbackInfo 22 }

tmnxSysRollbackRescueDeleteRes   OBJECT-TYPE
    SYNTAX      INTEGER {
        none       (1),
        inProgress (2),
        success    (3),
        failed     (4)
    }
    MAX-ACCESS  read-only
    STATUS      current
    DESCRIPTION
        "The value of tmnxSysRollbackRescueDeleteRes indicates the result of
         the last tmnxSysRollbackRescueDelete action.

         none(1)            None of the following apply
         inProgress(2)      The action is still in progress
         success(3)         The action completed successfully
         failed(4)          The action failed"
    ::= { tmnxSysRollbackInfo 23 }

tmnxSysRollbackRescueSavedTime   OBJECT-TYPE
    SYNTAX      DateAndTime
    MAX-ACCESS  read-only
    STATUS      current
    DESCRIPTION
        "The value of tmnxSysRollbackRescueSavedTime indicates the timestamp
         the last rollback rescue save on the system is completed.

         The value of tmnxSysRollbackRescueSavedTime is affected by the value
         of stiPreferLocalTime."
    ::= { tmnxSysRollbackInfo 24 }

tmnxSysRollbackRescueRevStTime   OBJECT-TYPE
    SYNTAX      DateAndTime
    MAX-ACCESS  read-only
    STATUS      current
    DESCRIPTION
        "The value of tmnxSysRollbackRescueRevStTime indicates the timestamp
         the last rescue rollback file reverted on the system is initiated.

         The value of tmnxSysRollbackRescueRevStTime is affected by the value
         of stiPreferLocalTime."
    ::= { tmnxSysRollbackInfo 25 }

tmnxSysRollbackRescueRevEdTime   OBJECT-TYPE
    SYNTAX      DateAndTime
    MAX-ACCESS  read-only
    STATUS      current
    DESCRIPTION
        "The value of tmnxSysRollbackRescueRevEdTime indicates the timestamp
         the last rollback rescue revert on the system is completed.

         The value of tmnxSysRollbackRescueRevEdTime is affected by the value
         of stiPreferLocalTime."
    ::= { tmnxSysRollbackInfo 26 }

tmnxSysRollbackRescueRevUser     OBJECT-TYPE
    SYNTAX      TNamedItemOrEmpty
    MAX-ACCESS  read-only
    STATUS      current
    DESCRIPTION
        "The value of tmnxSysRollbackRescueRevUser indicates the name of a
         system user who initiated the last rollback rescue revert."
    DEFVAL      { ''H }
    ::= { tmnxSysRollbackInfo 27 }

tmnxSysRollbackRescueSaveComment OBJECT-TYPE
    SYNTAX      DisplayString (SIZE (0..255))
    MAX-ACCESS  read-write
    STATUS      current
    DESCRIPTION
        "The value of the object tmnxSysRollbackRescueSaveComment specifies a
         user provided comment related to the rollback rescue file about to be
         saved.

         It consists of any printable, seven-bit ASCII characters up to 255
         characters in length."
    DEFVAL      { ''H }
    ::= { tmnxSysRollbackInfo 28 }

tmnxSysRollbackRescueAbortRevert OBJECT-TYPE
    SYNTAX      TmnxActionType
    MAX-ACCESS  read-write
    STATUS      current
    DESCRIPTION
        "The value of tmnxSysRollbackRescueAbortRevert specifies whether to
         abort the rescue revert that's currently in progress.

         When SET to the value of 'doAction' the system will abort the active
         rollback revert. This will leave the system in an unknown state, so it
         should be used with care.

         An SNMP GET request on this object should return 'notApplicable'."
    DEFVAL      { notApplicable }
    ::= { tmnxSysRollbackInfo 29 }

tmnxSysRollbackRescueFileExists  OBJECT-TYPE
    SYNTAX      TruthValue
    MAX-ACCESS  read-only
    STATUS      current
    DESCRIPTION
        "The value of tmnxSysRollbackRescueFileExists indicates whether a
         rollback rescue file specified by tmnxSysRollbackRescueLocation and
         suffix '.rc' is present.

         A value of 'true' indicates the file is present and a value of 'false'
         indicates the file is not present."
    DEFVAL      { false }
    ::= { tmnxSysRollbackInfo 30 }

tmnxSysRollbackMaxLocalFiles     OBJECT-TYPE
    SYNTAX      Unsigned32 (1..50)
    MAX-ACCESS  read-write
    STATUS      current
    DESCRIPTION
        "The value of tmnxSysRollbackMaxLocalFiles specifies the maximum number
         of rollback checkpoint files that can be saved locally on the compact
         flash."
    DEFVAL      { 10 }
    ::= { tmnxSysRollbackInfo 31 }

tmnxSysRollbackMaxRemoteFiles    OBJECT-TYPE
    SYNTAX      Unsigned32 (1..200)
    MAX-ACCESS  read-write
    STATUS      current
    DESCRIPTION
        "The value of tmnxSysRollbackMaxRemoteFiles specifies the maximum
         number of rollback checkpoint files that can be saved at a remote ftp
         location."
    DEFVAL      { 10 }
    ::= { tmnxSysRollbackInfo 32 }

tmnxSysRollbackTableLastChanged  OBJECT-TYPE
    SYNTAX      TimeStamp
    MAX-ACCESS  read-only
    STATUS      current
    DESCRIPTION
        "The value of tmnxSysRollbackTableLastChanged indicates the timestamp
         of the last configuration changes to any of the rows in
         tmnxSysRollbackFileTable."
    ::= { tmnxSysObjs 18 }

tmnxSysRollbackFileTable         OBJECT-TYPE
    SYNTAX      SEQUENCE OF TmnxSysRollbackFileEntry
    MAX-ACCESS  not-accessible
    STATUS      current
    DESCRIPTION
        "The table tmnxSysRollbackFileTable contains information pertaining to
         an entry for each rollback checkpoint file.

         If the configured rollback location as specified by
         tmnxSysRollbackLocation is on compact flash, this table can have up to
         a maximum of tmnxSysRollbackMaxLocalFiles.

         If the configured rollback location as specified by
         tmnxSysRollbackLocation is a remote ftp location, this table can have
         up to a maximum of tmnxSysRollbackMaxRemoteFiles."
    ::= { tmnxSysObjs 19 }

tmnxSysRollbackFileEntry         OBJECT-TYPE
    SYNTAX      TmnxSysRollbackFileEntry
    MAX-ACCESS  not-accessible
    STATUS      current
    DESCRIPTION
        "Each row entry contains information about a rollback checkpoint file."
    INDEX       { tmnxSysRollbackFileIndex }
    ::= { tmnxSysRollbackFileTable 1 }

TmnxSysRollbackFileEntry         ::= SEQUENCE
{
    tmnxSysRollbackFileIndex         Unsigned32,
    tmnxSysRollbackFileCreationTime  DateAndTime,
    tmnxSysRollbackFileComment       DisplayString,
    tmnxSysRollbackFileUserName      TNamedItemOrEmpty,
    tmnxSysRollbackFileVersion       DisplayString
}

tmnxSysRollbackFileIndex         OBJECT-TYPE
    SYNTAX      Unsigned32 (0..199)
    MAX-ACCESS  not-accessible
    STATUS      current
    DESCRIPTION
        "The value of tmnxSysRollbackFileIndex specifies the index of the
         rollback checkpoint file."
    ::= { tmnxSysRollbackFileEntry 1 }

tmnxSysRollbackFileCreationTime  OBJECT-TYPE
    SYNTAX      DateAndTime
    MAX-ACCESS  read-only
    STATUS      current
    DESCRIPTION
        "The value of tmnxSysRollbackFileCreationTime indicates the timestamp
         of the creation time of this row in tmnxSysRollbackFileTable.

         The value of tmnxSysRollbackFileCreationTime is affected by the value
         of stiPreferLocalTime."
    ::= { tmnxSysRollbackFileEntry 2 }

tmnxSysRollbackFileComment       OBJECT-TYPE
    SYNTAX      DisplayString (SIZE (0..255))
    MAX-ACCESS  read-only
    STATUS      current
    DESCRIPTION
        "The value of the object tmnxSysRollbackFileComment specifies a user
         provided comment related to a rollback checkpoint file.

         It consists of any printable, seven-bit ASCII characters up to 255
         characters in length."
    ::= { tmnxSysRollbackFileEntry 3 }

tmnxSysRollbackFileUserName      OBJECT-TYPE
    SYNTAX      TNamedItemOrEmpty
    MAX-ACCESS  read-only
    STATUS      current
    DESCRIPTION
        "The value of tmnxSysRollbackFileUserName indicates the name of a
         system user who saves this rollback file."
    ::= { tmnxSysRollbackFileEntry 4 }

tmnxSysRollbackFileVersion       OBJECT-TYPE
    SYNTAX      DisplayString (SIZE (0..32))
    MAX-ACCESS  read-only
    STATUS      current
    DESCRIPTION
        "The value of tmnxSysRollbackFileVersion indicates the version number
         of the software running on the system when the rollback file is saved."
    ::= { tmnxSysRollbackFileEntry 5 }

sysBootedBofInfo                 OBJECT IDENTIFIER ::= { tmnxSysObjs 20 }

sbbiLiSeparate                   OBJECT-TYPE
    SYNTAX      TruthValue
    MAX-ACCESS  read-only
    STATUS      current
    DESCRIPTION
        "This object gives the currently active (booted) value of li-separate.
         This value specifies whether or not a non-LI user has access to Lawful
         Intercept (LI) information. When sbbiLiSeparate has a value of 'true',
         a user who does not have the TIMETRA-SECURITY-MIB:: tmnxUserAccess
         'li' bit set will not be allowed to access CLI or SNMP objects in the
         'li' context."
    ::= { sysBootedBofInfo 1 }

sbbiLiLocalSave                  OBJECT-TYPE
    SYNTAX      TruthValue
    MAX-ACCESS  read-only
    STATUS      current
    DESCRIPTION
        "This object gives the currently active (booted) value of
         li-local-save. This value specifies whether or not Lawful Intercept
         (LI) configuration is allowed to be save to a local file."
    ::= { sysBootedBofInfo 2 }

sbbiEncryptConfig                OBJECT-TYPE
    SYNTAX      TruthValue
    MAX-ACCESS  read-only
    STATUS      current
    DESCRIPTION
        "This object gives the currently active (booted) value of
         sbiEncryptConfig. This value specifies whether or not BOF
         configuration is encrypted."
    ::= { sysBootedBofInfo 3 }

sysMGMCSwitchOverInfo            OBJECT IDENTIFIER ::= { tmnxSysObjs 21 }

tmnxSysCandidateCfgInfo          OBJECT IDENTIFIER ::= { tmnxSysObjs 22 }

tmnxSysCandidateCfgState         OBJECT-TYPE
    SYNTAX      INTEGER {
        unmodified  (0),
        modified    (1),
        unconfirmed (2)
    }
    MAX-ACCESS  read-only
    STATUS      current
    DESCRIPTION
        "The value of tmnxSysCandidateCfgState indicates the current state of
         the global candidate config.

         A value of 'unmodified(0)' indicates nobody has entered the candidate
         config since boot or the last commit/discard. A value of 'modified(1)'
         indicates there are uncommitted changes in the candidate config. A
         value of 'unconfirmed(2)' indicates there are no uncommitted changes
         in the candidate config but the result of the last commit will be
         auto-reverted unless it is confirmed before the timeout expires."
    ::= { tmnxSysCandidateCfgInfo 1 }

tmnxSysCandidateCfgEditors       OBJECT-TYPE
    SYNTAX      Integer32
    MAX-ACCESS  read-only
    STATUS      current
    DESCRIPTION
        "The value of tmnxSysCandidateCfgEditors indicates the current amount
         of users that are editing or reading the candidate config."
    ::= { tmnxSysCandidateCfgInfo 2 }

tmnxSysCandidateCfgCommitState   OBJECT-TYPE
    SYNTAX      INTEGER {
        none               (0),
        in-progress        (1),
        success            (2),
        revert-pending     (3),
        failed             (4),
        revert-in-progress (5),
        reverted           (6),
        revert-failed      (7)
    }
    MAX-ACCESS  read-only
    STATUS      current
    DESCRIPTION
        "The value of tmnxSysCandidateCfgCommitState indicates the result of
         the last commit performed in the global candidate config.

          A value of 'none(0)' indicates there have been no commits since the
          last reboot of the node.
          A value of 'in-progress(1)' indicates the system is currently
          committing the candidate config.
          A value of 'success(2)' indicates the last commit finished
          successfully.
          A value of 'revert-pending(3)' indicates the last commit finished
          successfully but has not been confirmed yet, and will be auto-reverted
          if it is not confirmed before the time specified in
          tmnxSysCandidateCfgRevertTime.
          A value of 'failed(4)' indicates the last commit failed and has been
          undone.
          A value of 'revert-in-progress(5)' indicates the last commit finished
          successfully but was not confirmed in time and is currently being
          reverted.
          A value of 'reverted(6)' indicates the last commit finished
          successfully but was not confirmed in time and has been reverted.
          A value of 'revert-failed(7)' indicates the last commit finished
          successfully but was not confirmed in time and the system attempted to
          revert it but failed."
    ::= { tmnxSysCandidateCfgInfo 3 }

tmnxSysCandidateCfgCommitTime    OBJECT-TYPE
    SYNTAX      DateAndTime
    MAX-ACCESS  read-only
    STATUS      current
    DESCRIPTION
        "The value of tmnxSysCandidateCfgCommitTime indicates the date and time
         the last (attempted) commit of the candidate config was started."
    ::= { tmnxSysCandidateCfgInfo 4 }

tmnxSysCandidateCfgRevertTime    OBJECT-TYPE
    SYNTAX      DateAndTime
    MAX-ACCESS  read-only
    STATUS      current
    DESCRIPTION
        "The value of tmnxSysCandidateCfgRevertTime indicates the date and time
         the system will automatically revert the last committed candidate
         config, unless they are confirmed.

         If this date and time is in the past it indicates the candidate config
         was not confirmed and has been reverted.

         If no auto-revert was requested at the time of the commit the value of
         this field will be set to zero."
    ::= { tmnxSysCandidateCfgInfo 5 }

tmnxSysCandidateCfgChckptCreated OBJECT-TYPE
    SYNTAX      TruthValue
    MAX-ACCESS  read-only
    STATUS      current
    DESCRIPTION
        "The value of tmnxSysCandidateCfgChckptCreated indicates if a
         checkpoint was created after the last commit of the candidate config."
    ::= { tmnxSysCandidateCfgInfo 6 }

tmnxSysCandidateCfgUser          OBJECT-TYPE
    SYNTAX      TNamedItemOrEmpty
    MAX-ACCESS  read-only
    STATUS      current
    DESCRIPTION
        "The value of tmnxSysCandidateCfgUser indicates the name of a system
         user who initiated the last commit of the candidate config."
    ::= { tmnxSysCandidateCfgInfo 7 }

tmnxSysCandidateCfgExclusiveUsr  OBJECT-TYPE
    SYNTAX      TNamedItemOrEmpty
    MAX-ACCESS  read-only
    STATUS      current
    DESCRIPTION
        "The value of tmnxSysCandidateCfgExclusiveUsr indicates the name of a
         system user who is currently exclusively modifying the candidate
         config. This indicates no other user can modify the candidate config
         until this system user has finished modifying the candidate config.

         If this field is empty no user has requested to exclusively modify the
         candidate config."
    ::= { tmnxSysCandidateCfgInfo 8 }

tmnxSysNetconfInfo               OBJECT IDENTIFIER ::= { tmnxSysObjs 23 }

tmnxSysNetconfAdminStatus        OBJECT-TYPE
    SYNTAX      TmnxAdminState
    MAX-ACCESS  read-write
    STATUS      current
    DESCRIPTION
        "The value of tmnxSysNetconfAdminStatus specifies the desired
         administrative state of the NETCONF daemon. When
         tmnxSysNetconfAdminStatus is set to 'inService', the NETCONF daemon
         will begin receiving NETCONF requests from external NETCONF users.
         When tmnxSysNetconfAdminStatus is set to 'outOfService', the NETCONF
         daemon is suspended and will no longer receive NETCONF requests from
         external NETCONF users."
    DEFVAL      { outOfService }
    ::= { tmnxSysNetconfInfo 1 }

tmnxSysNetconfOperStatus         OBJECT-TYPE
    SYNTAX      TmnxOperState
    MAX-ACCESS  read-only
    STATUS      current
    DESCRIPTION
        "The value of tmnxSysNetconfOperStatus indicates the state of the
         NETCONF daemon. A value of 'inService' indicates that the NETCONF
         daemon will receive NETCONF requests from external NETCONF users. A
         value of 'outOfService' indicates that the NETCONF daemon is suspended
         and will no longer receive NETCONF requests from external NETCONF
         users."
    ::= { tmnxSysNetconfInfo 2 }

tmnxSysNetconfRequests           OBJECT-TYPE
    SYNTAX      Counter32
    MAX-ACCESS  read-only
    STATUS      current
    DESCRIPTION
        "The value of tmnxSysNetconfRequests indicates the total number of
         NETCONF requests which have been accepted and processed by the NETCONF
         server."
    ::= { tmnxSysNetconfInfo 3 }

tmnxSysNetconfGetRequests        OBJECT-TYPE
    SYNTAX      Counter32
    MAX-ACCESS  read-only
    STATUS      current
    DESCRIPTION
        "The value of tmnxSysNetconfGetRequests indicates the total number of
         get NETCONF requests which have been accepted and processed by the
         NETCONF server."
    ::= { tmnxSysNetconfInfo 4 }

tmnxSysNetconfGetConfigRequests  OBJECT-TYPE
    SYNTAX      Counter32
    MAX-ACCESS  read-only
    STATUS      current
    DESCRIPTION
        "The value of tmnxSysNetconfGetConfigRequests indicates the total
         number of get-config NETCONF requests which have been accepted and
         processed by the NETCONF server."
    ::= { tmnxSysNetconfInfo 5 }

tmnxSysNetconfEditConfigRequests OBJECT-TYPE
    SYNTAX      Counter32
    MAX-ACCESS  read-only
    STATUS      current
    DESCRIPTION
        "The value of tmnxSysNetconfEditConfigRequests indicates the total
         number of edit-config NETCONF requests which have been accepted and
         processed by the NETCONF server."
    ::= { tmnxSysNetconfInfo 6 }

tmnxSysNetconfCloseRequests      OBJECT-TYPE
    SYNTAX      Counter32
    MAX-ACCESS  read-only
    STATUS      current
    DESCRIPTION
        "The value of tmnxSysNetconfCloseRequests indicates the total number of
         close-session NETCONF requests which have been accepted and processed
         by the NETCONF server."
    ::= { tmnxSysNetconfInfo 7 }

tmnxSysNetconfKillRequests       OBJECT-TYPE
    SYNTAX      Counter32
    MAX-ACCESS  read-only
    STATUS      current
    DESCRIPTION
        "The value of tmnxSysNetconfKillRequests indicates the total number of
         kill-session NETCONF requests which have been accepted and processed
         by the NETCONF server."
    ::= { tmnxSysNetconfInfo 8 }

tmnxSysNetconfResponses          OBJECT-TYPE
    SYNTAX      Counter32
    MAX-ACCESS  read-only
    STATUS      current
    DESCRIPTION
        "The value of tmnxSysNetconfResponses indicates the total number of
         NETCONF responses which have been generated and sent by the NETCONF
         server."
    ::= { tmnxSysNetconfInfo 9 }

tmnxSysNetconfErrorResponses     OBJECT-TYPE
    SYNTAX      Counter32
    MAX-ACCESS  read-only
    STATUS      current
    DESCRIPTION
        "The value of tmnxSysNetconfErrorResponses indicates the total number
         of NETCONF error responses which have been generated and sent by the
         NETCONF server."
    ::= { tmnxSysNetconfInfo 10 }

tmnxSysNetconfCopyConfigRequests OBJECT-TYPE
    SYNTAX      Counter32
    MAX-ACCESS  read-only
    STATUS      current
    DESCRIPTION
        "The value of tmnxSysNetconfCopyConfigRequests indicates the total
         number of copy-config NETCONF requests which have been accepted and
         processed by the NETCONF server."
    ::= { tmnxSysNetconfInfo 11 }

tmnxSysNetconfDelConfigRequests  OBJECT-TYPE
    SYNTAX      Counter32
    MAX-ACCESS  read-only
    STATUS      current
    DESCRIPTION
        "The value of tmnxSysNetconfDelConfigRequests indicates the total
         number of delete-config NETCONF requests which have been accepted and
         processed by the NETCONF server."
    ::= { tmnxSysNetconfInfo 12 }

tmnxSysNetconfValidateRequests   OBJECT-TYPE
    SYNTAX      Counter32
    MAX-ACCESS  read-only
    STATUS      current
    DESCRIPTION
        "The value of tmnxSysNetconfValidateRequests indicates the total number
         of validate NETCONF requests which have been accepted and processed by
         the NETCONF server."
    ::= { tmnxSysNetconfInfo 13 }

tmnxSysNetconfFailedEditCfgReqs  OBJECT-TYPE
    SYNTAX      Counter32
    MAX-ACCESS  read-only
    STATUS      current
    DESCRIPTION
        "The value of tmnxSysNetconfFailedEditCfgReqs indicates the total
         number of edit-config NETCONF requests which have failed because of
         locks taken by other NETCONF sessions."
    ::= { tmnxSysNetconfInfo 14 }

tmnxSysNetconfFailedLockReqs     OBJECT-TYPE
    SYNTAX      Counter32
    MAX-ACCESS  read-only
    STATUS      current
    DESCRIPTION
        "The value of tmnxSysNetconfFailedLockReqs indicates the total number
         of lock NETCONF requests which have failed because of locks taken by
         other NETCONF sessions."
    ::= { tmnxSysNetconfInfo 15 }

tmnxSysNetconfLockRequests       OBJECT-TYPE
    SYNTAX      Counter32
    MAX-ACCESS  read-only
    STATUS      current
    DESCRIPTION
        "The value of tmnxSysNetconfLockRequests indicates the total number of
         lock NETCONF requests which have been accepted and processed by the
         NETCONF server."
    ::= { tmnxSysNetconfInfo 16 }

tmnxSysNetconfUnlockRequests     OBJECT-TYPE
    SYNTAX      Counter32
    MAX-ACCESS  read-only
    STATUS      current
    DESCRIPTION
        "The value of tmnxSysNetconfUnlockRequests indicates the total number
         of unlock NETCONF requests which have been accepted and processed by
         the NETCONF server."
    ::= { tmnxSysNetconfInfo 17 }

tmnxSysNetconfCommitRequests     OBJECT-TYPE
    SYNTAX      Counter32
    MAX-ACCESS  read-only
    STATUS      current
    DESCRIPTION
        "The value of tmnxSysNetconfCommitRequests indicates the total number
         of commit NETCONF requests which have been accepted and processed by
         the NETCONF server."
    ::= { tmnxSysNetconfInfo 18 }

tmnxSysNetconfDiscardRequests    OBJECT-TYPE
    SYNTAX      Counter32
    MAX-ACCESS  read-only
    STATUS      current
    DESCRIPTION
        "The value of tmnxSysNetconfDiscardRequests indicates the total number
         of discard change NETCONF requests which have been accepted and
         processed by the NETCONF server."
    ::= { tmnxSysNetconfInfo 19 }

tmnxSysNetconfCapCandidateCfg    OBJECT-TYPE
    SYNTAX      TruthValue
    MAX-ACCESS  read-write
    STATUS      current
    DESCRIPTION
        "The value of tmnxSysNetconfCapCandidateCfg specifies whether or not
         the candidate datastore is supported by the NETCONF server. When set
         to 'true', the NETCONF server allows access to the candidate
         datastore."
    DEFVAL      { true }
    ::= { tmnxSysNetconfInfo 20 }

tmnxSysNetconfCapRunningCfg      OBJECT-TYPE
    SYNTAX      TruthValue
    MAX-ACCESS  read-write
    STATUS      obsolete
    DESCRIPTION
        "The value of tmnxSysNetconfCapRunningCfg specifies whether or not the
         writable running datastore is supported by the NETCONF server. When
         set to 'true', the NETCONF server allows access to the writable
         running datastore."
    DEFVAL      { false }
    ::= { tmnxSysNetconfInfo 21 }

tmnxSysNetconfYangBaseR13        OBJECT-TYPE
    SYNTAX      TruthValue
    MAX-ACCESS  read-write
    STATUS      obsolete
    DESCRIPTION
        "The value of tmnxSysNetconfYangBaseR13 specifies whether or not the
         base release 13 Yang models are supported by the NETCONF server. When
         set to 'true', the NETCONF server allows access to base release 13
         Yang models.

         This object was made obsolete in the 15.1 release."
    DEFVAL      { true }
    ::= { tmnxSysNetconfInfo 22 }

tmnxSysNetconfYangNokia          OBJECT-TYPE
    SYNTAX      TruthValue
    MAX-ACCESS  read-write
    STATUS      obsolete
    DESCRIPTION
        "The value of tmnxSysNetconfYangNokia specifies whether or not the
         Nokia Yang models are supported by the NETCONF server. When set to
         'true', the NETCONF server allows access to the Nokia Yang models.

         This object was made obsolete in the 15.1 release."
    DEFVAL      { true }
    ::= { tmnxSysNetconfInfo 23 }

tmnxSysNetconfCreateSubRequests  OBJECT-TYPE
    SYNTAX      Counter32
    MAX-ACCESS  read-only
    STATUS      current
    DESCRIPTION
        "The value of tmnxSysNetconfCreateSubRequests indicates the total
         number of create subscription NETCONF requests which have been
         accepted and processed by the NETCONF server."
    ::= { tmnxSysNetconfInfo 24 }

tmnxSysNetconfAutoCfgSave        OBJECT-TYPE
    SYNTAX      TruthValue
    MAX-ACCESS  read-write
    STATUS      current
    DESCRIPTION
        "The value of tmnxSysNetconfAutoCfgSave specifies whether the running
         configuration is saved as part of a commit operation initiated from
         Netconf."
    DEFVAL      { true }
    ::= { tmnxSysNetconfInfo 25 }

tmnxSysNetconfPort               OBJECT-TYPE
    SYNTAX      Unsigned32 (22 | 830)
    MAX-ACCESS  read-write
    STATUS      current
    DESCRIPTION
        "The value of tmnxSysNetconfPort specifies port on which is NETCONF
         server listening for connections."
    DEFVAL      { 830 }
    ::= { tmnxSysNetconfInfo 26 }

tmnxSysNetconfGetSchemaRequests  OBJECT-TYPE
    SYNTAX      Counter32
    MAX-ACCESS  read-only
    STATUS      current
    DESCRIPTION
        "The value of tmnxSysNetconfGetSchemaRequests indicates the total
         number of get-schema NETCONF requests which have been accepted and
         processed by the NETCONF server."
    ::= { tmnxSysNetconfInfo 27 }

tmnxSysNetconfGetDataRequests    OBJECT-TYPE
    SYNTAX      Counter32
    MAX-ACCESS  read-only
    STATUS      current
    DESCRIPTION
        "The value of tmnxSysNetconfGetDataRequests indicates the total number
         of get-data NETCONF requests which have been accepted and processed by
         the NETCONF server."
    ::= { tmnxSysNetconfInfo 28 }

tmnxSysNetconfActionRequests     OBJECT-TYPE
    SYNTAX      Counter32
    MAX-ACCESS  read-only
    STATUS      current
    DESCRIPTION
        "The value of tmnxSysNetconfActionRequests indicates the total number
         of action NETCONF requests which have been accepted and processed by
         the NETCONF server."
    ::= { tmnxSysNetconfInfo 29 }

tmnxSysNetconfBadHellos          OBJECT-TYPE
    SYNTAX      Counter32
    MAX-ACCESS  read-only
    STATUS      current
    DESCRIPTION
        "The value of tmnxSysNetconfBadHellos indicates the total number of
         NETCONF bad hello messages which have been received by the NETCONF
         server."
    ::= { tmnxSysNetconfInfo 30 }

tmnxSysNetconfDroppedSessions    OBJECT-TYPE
    SYNTAX      Counter32
    MAX-ACCESS  read-only
    STATUS      current
    DESCRIPTION
        "The value of tmnxSysNetconfDroppedSessions indicates the total number
         of dropped NETCONF sessions."
    ::= { tmnxSysNetconfInfo 31 }

tmnxSysNetconfLastOperChange     OBJECT-TYPE
    SYNTAX      DateAndTime
    MAX-ACCESS  read-only
    STATUS      current
    DESCRIPTION
        "The value of tmnxSysNetconfLastOperChange indicates the time of last
         change of the operational state of NETCONF server."
    ::= { tmnxSysNetconfInfo 32 }

tmnxSysNetconfDelayOnBoot        OBJECT-TYPE
    SYNTAX      Unsigned32 (0 | 1..3600)
    UNITS       "seconds"
    MAX-ACCESS  read-write
    STATUS      current
    DESCRIPTION
        "The value of tmnxSysNetconfDelayOnBoot specifies the timeout since the
         system boots, after which NETCONF server becomes operational.

         This value only takes effect when NETCONF server is enabled in boot
         configuration file. When tmnxSysNetconfAdminStatus is set to
         'inService', the NETCONF server will begin receiving requests
         immediately."
    DEFVAL      { 0 }
    ::= { tmnxSysNetconfInfo 33 }

tmnxSysNetconfOperDownReason     OBJECT-TYPE
    SYNTAX      INTEGER {
        notApplicable     (0),
        adminDown         (1),
        noConnectedClient (2),
        activeDelayOnBoot (3)
    }
    MAX-ACCESS  read-only
    STATUS      current
    DESCRIPTION
        "The value of tmnxSysNetconfOperDownReason indicates the reason why
         NETCONF server is operationally down."
    ::= { tmnxSysNetconfInfo 34 }

tmnxDCSysObjs                    OBJECT IDENTIFIER ::= { tmnxSysObjs 24 }

tmnxSysStrmInfo                  OBJECT IDENTIFIER ::= { tmnxSysObjs 25 }

tmnxSysStrmAdminStatus           OBJECT-TYPE
    SYNTAX      TmnxAdminState
    MAX-ACCESS  read-write
    STATUS      current
    DESCRIPTION
        "The value of tmnxSysStrmAdminStatus specifies the desired
         administrative state of the proprietary protocol streaming server
         daemon.  When tmnxSysStrmAdminStatus is set to 'inService', the
         streaming server daemon accepts and processes requests from the
         Nokia 5620 Service Aware Manager (SAM) system. When
         tmnxSysStrmAdminStatus is set to 'outOfService', the streaming server
         daemon is suspended and will no longer accept requests from the SAM
         system."
    DEFVAL      { outOfService }
    ::= { tmnxSysStrmInfo 1 }

tmnxSysStrmDumpSnmpRequests      OBJECT-TYPE
    SYNTAX      Counter32
    MAX-ACCESS  read-only
    STATUS      current
    DESCRIPTION
        "The value of tmnxSysStrmDumpSnmpRequests indicates the total number of
         streaming snmp dump request PDUs which have been accepted and
         processed by the Nokia 5620 Service Aware Manager (SAM) streaming
         protocol entity."
    ::= { tmnxSysStrmInfo 2 }

tmnxSysStrmGetManyRequests       OBJECT-TYPE
    SYNTAX      Counter32
    MAX-ACCESS  read-only
    STATUS      current
    DESCRIPTION
        "The value of tmnxSysStrmGetManyRequests indicates the total number of
         streaming get many request PDUs which have been accepted and processed
         by the Nokia 5620 Service Aware Manager (SAM) streaming protocol
         entity."
    ::= { tmnxSysStrmInfo 3 }

tmnxSysStrmResponses             OBJECT-TYPE
    SYNTAX      Counter32
    MAX-ACCESS  read-only
    STATUS      current
    DESCRIPTION
        "The value of tmnxSysStrmResponses indicates the total number of
         streaming response PDUs which have been generated by the Nokia 5620
         Service Aware Manager (SAM) streaming protocol entity."
    ::= { tmnxSysStrmInfo 4 }

tmnxSysXmppInfo                  OBJECT IDENTIFIER ::= { tmnxSysObjs 26 }

tmnxSysXmppServerTable           OBJECT-TYPE
    SYNTAX      SEQUENCE OF TmnxSysXmppServerEntry
    MAX-ACCESS  not-accessible
    STATUS      obsolete
    DESCRIPTION
        "The tmnxSysXmppServerTable contains information pertaining to an entry
         for each server. Row entries are created and deleted by the agent."
    ::= { tmnxSysXmppInfo 1 }

tmnxSysXmppServerEntry           OBJECT-TYPE
    SYNTAX      TmnxSysXmppServerEntry
    MAX-ACCESS  not-accessible
    STATUS      obsolete
    DESCRIPTION
        "Each row entry contains information about a XMPP server."
    INDEX       { tmnxSysXmppServName }
    ::= { tmnxSysXmppServerTable 1 }

TmnxSysXmppServerEntry           ::= SEQUENCE
{
    tmnxSysXmppServName              DisplayString,
    tmnxSysXmppServFQDN              DisplayString,
    tmnxSysXmppServRowStatus         RowStatus,
    tmnxSysXmppServUserName          TNamedItemOrEmpty,
    tmnxSysXmppServPassword          DisplayString,
    tmnxSysXmppServLastChanged       TimeStamp,
    tmnxSysXmppServUptime            TimeStamp,
    tmnxSysXmppServIQSent            Counter64,
    tmnxSysXmppServIQRcvd            Counter64,
    tmnxSysXmppServIQError           Counter64,
    tmnxSysXmppServIQTimedOut        Counter64,
    tmnxSysXmppServIQAckRcvd         Counter64,
    tmnxSysXmppServIQMinRtt          Counter64,
    tmnxSysXmppServIQMaxRtt          Counter64,
    tmnxSysXmppServVsdUpdatesRcvd    Counter64,
    tmnxSysXmppServUpdatesRcvd       Counter64,
    tmnxSysXmppServMsgSent           Counter64,
    tmnxSysXmppServMsgRcvd           Counter64,
    tmnxSysXmppServMsgAckRcvd        Counter64,
    tmnxSysXmppServMsgError          Counter64,
    tmnxSysXmppServMsgTimedOut       Counter64,
    tmnxSysXmppServMsgMinRtt         Counter64,
    tmnxSysXmppServMsgMaxRtt         Counter64,
    tmnxSysXmppServSubSent           Counter64,
    tmnxSysXmppServUnSubSent         Counter64,
    tmnxSysXmppServState             DisplayString,
    tmnxSysXmppServAdminState        TmnxAdminState,
    tmnxSysXmppServOperUserName      TNamedItemOrEmpty,
    tmnxSysXmppServAuthType          TNamedItemOrEmpty,
    tmnxSysXmppServConnMode          INTEGER
}

tmnxSysXmppServName              OBJECT-TYPE
    SYNTAX      DisplayString (SIZE (0..32))
    MAX-ACCESS  not-accessible
    STATUS      obsolete
    DESCRIPTION
        "The value of tmnxSysXmppServName indicates the name associated with
         the XMPP Server."
    ::= { tmnxSysXmppServerEntry 1 }

tmnxSysXmppServFQDN              OBJECT-TYPE
    SYNTAX      DisplayString (SIZE (0..255))
    MAX-ACCESS  read-create
    STATUS      obsolete
    DESCRIPTION
        "The value of tmnxSysXmppServFQDN specifies the Fully Qualified Domain
         Name (FQDN) associated with the XMPP Server."
    ::= { tmnxSysXmppServerEntry 2 }

tmnxSysXmppServRowStatus         OBJECT-TYPE
    SYNTAX      RowStatus
    MAX-ACCESS  read-create
    STATUS      obsolete
    DESCRIPTION
        "The value of tmnxSysXmppServRowStatus specifies the row status. It is
         used to create and delete row entries in this table."
    ::= { tmnxSysXmppServerEntry 3 }

tmnxSysXmppServUserName          OBJECT-TYPE
    SYNTAX      TNamedItemOrEmpty
    MAX-ACCESS  read-create
    STATUS      obsolete
    DESCRIPTION
        "The value of tmnxSysXmppServUserName specifies the username that
         is used in the XMPP server access requests. When no username is
         not provided,  the chassis MAC is used as the default user name."
    ::= { tmnxSysXmppServerEntry 4 }

tmnxSysXmppServPassword          OBJECT-TYPE
    SYNTAX      DisplayString (SIZE (0..32))
    MAX-ACCESS  read-create
    STATUS      obsolete
    DESCRIPTION
        "The value of tmnxSysXmppServPassword specifies the password that is
         used in the XMPP server access requests."
    DEFVAL      { "" }
    ::= { tmnxSysXmppServerEntry 5 }

tmnxSysXmppServLastChanged       OBJECT-TYPE
    SYNTAX      TimeStamp
    MAX-ACCESS  read-only
    STATUS      obsolete
    DESCRIPTION
        "The value of tmnxSysXmppServLastChanged indicates the timestamp of
         last change to this row in tmnxSysXmppServerTable."
    ::= { tmnxSysXmppServerEntry 6 }

tmnxSysXmppServUptime            OBJECT-TYPE
    SYNTAX      TimeStamp
    MAX-ACCESS  read-only
    STATUS      obsolete
    DESCRIPTION
        "The tmnxSysXmppServUptime indicates the uptime of the XMPP server."
    ::= { tmnxSysXmppServerEntry 7 }

tmnxSysXmppServIQSent            OBJECT-TYPE
    SYNTAX      Counter64
    MAX-ACCESS  read-only
    STATUS      obsolete
    DESCRIPTION
        "The value of tmnxSysXmppServIQSent indicates the number of XMPP
         Info/Query message sent."
    ::= { tmnxSysXmppServerEntry 8 }

tmnxSysXmppServIQRcvd            OBJECT-TYPE
    SYNTAX      Counter64
    MAX-ACCESS  read-only
    STATUS      obsolete
    DESCRIPTION
        "The value of tmnxSysXmppServIQRcvd indicates the number of XMPP
         Info/Query message received."
    ::= { tmnxSysXmppServerEntry 9 }

tmnxSysXmppServIQError           OBJECT-TYPE
    SYNTAX      Counter64
    MAX-ACCESS  read-only
    STATUS      obsolete
    DESCRIPTION
        "The value of tmnxSysXmppServIQError indicates the number of XMPP
         Info/Query error messages received."
    ::= { tmnxSysXmppServerEntry 10 }

tmnxSysXmppServIQTimedOut        OBJECT-TYPE
    SYNTAX      Counter64
    MAX-ACCESS  read-only
    STATUS      obsolete
    DESCRIPTION
        "The value of tmnxSysXmppServIQTimedOut indicates the number of XMPP
         Info/Query messages timed out."
    ::= { tmnxSysXmppServerEntry 11 }

tmnxSysXmppServIQAckRcvd         OBJECT-TYPE
    SYNTAX      Counter64
    MAX-ACCESS  read-only
    STATUS      obsolete
    DESCRIPTION
        "The value of tmnxSysXmppServIQAckRcvd indicates the number of XMPP
         Info/Query acknowledgement messages received."
    ::= { tmnxSysXmppServerEntry 12 }

tmnxSysXmppServIQMinRtt          OBJECT-TYPE
    SYNTAX      Counter64
    UNITS       "milliseconds"
    MAX-ACCESS  read-only
    STATUS      obsolete
    DESCRIPTION
        "The value of tmnxSysXmppServIQMinRtt indicates the XMPP Info/Query
         minimum round trip time."
    ::= { tmnxSysXmppServerEntry 13 }

tmnxSysXmppServIQMaxRtt          OBJECT-TYPE
    SYNTAX      Counter64
    UNITS       "milliseconds"
    MAX-ACCESS  read-only
    STATUS      obsolete
    DESCRIPTION
        "The value of tmnxSysXmppServIQMaxRtt indicates the XMPP Info/Query
         maximum round trip time."
    ::= { tmnxSysXmppServerEntry 14 }

tmnxSysXmppServVsdUpdatesRcvd    OBJECT-TYPE
    SYNTAX      Counter64
    MAX-ACCESS  read-only
    STATUS      obsolete
    DESCRIPTION
        "The value of tmnxSysXmppServVsdUpdatesRcvd indicates the number of VSD
         updates received by the XMPP server."
    ::= { tmnxSysXmppServerEntry 15 }

tmnxSysXmppServUpdatesRcvd       OBJECT-TYPE
    SYNTAX      Counter64
    MAX-ACCESS  read-only
    STATUS      obsolete
    DESCRIPTION
        "The value of tmnxSysXmppServUpdatesRcvd indicates the number of nuage
         updates received by the XMPP server."
    ::= { tmnxSysXmppServerEntry 16 }

tmnxSysXmppServMsgSent           OBJECT-TYPE
    SYNTAX      Counter64
    MAX-ACCESS  read-only
    STATUS      obsolete
    DESCRIPTION
        "The value of tmnxSysXmppServMsgSent indicates the number of messages
         sent from the XMPP server."
    ::= { tmnxSysXmppServerEntry 17 }

tmnxSysXmppServMsgRcvd           OBJECT-TYPE
    SYNTAX      Counter64
    MAX-ACCESS  read-only
    STATUS      obsolete
    DESCRIPTION
        "The value of tmnxSysXmppServMsgRcvd indicates the number of messages
         received from the XMPP server."
    ::= { tmnxSysXmppServerEntry 18 }

tmnxSysXmppServMsgAckRcvd        OBJECT-TYPE
    SYNTAX      Counter64
    MAX-ACCESS  read-only
    STATUS      obsolete
    DESCRIPTION
        "The value of tmnxSysXmppServMsgAckRcvd indicates the number of message
         acknowledgements received from the XMPP server."
    ::= { tmnxSysXmppServerEntry 19 }

tmnxSysXmppServMsgError          OBJECT-TYPE
    SYNTAX      Counter64
    MAX-ACCESS  read-only
    STATUS      obsolete
    DESCRIPTION
        "The value of tmnxSysXmppServMsgError indicates the number of error
         messages received from the XMPP server."
    ::= { tmnxSysXmppServerEntry 20 }

tmnxSysXmppServMsgTimedOut       OBJECT-TYPE
    SYNTAX      Counter64
    MAX-ACCESS  read-only
    STATUS      obsolete
    DESCRIPTION
        "The value of tmnxSysXmppServMsgTimedOut indicates the number of
         timeout messages received from the XMPP server."
    ::= { tmnxSysXmppServerEntry 21 }

tmnxSysXmppServMsgMinRtt         OBJECT-TYPE
    SYNTAX      Counter64
    UNITS       "milliseconds"
    MAX-ACCESS  read-only
    STATUS      obsolete
    DESCRIPTION
        "The value of tmnxSysXmppServMsgMinRtt indicates the minimum message
         round trip time from the XMPP server."
    ::= { tmnxSysXmppServerEntry 22 }

tmnxSysXmppServMsgMaxRtt         OBJECT-TYPE
    SYNTAX      Counter64
    UNITS       "milliseconds"
    MAX-ACCESS  read-only
    STATUS      obsolete
    DESCRIPTION
        "The value of tmnxSysXmppServMsgMaxRtt indicates the maximum message
         round trip time from the XMPP server."
    ::= { tmnxSysXmppServerEntry 23 }

tmnxSysXmppServSubSent           OBJECT-TYPE
    SYNTAX      Counter64
    MAX-ACCESS  read-only
    STATUS      obsolete
    DESCRIPTION
        "The value of tmnxSysXmppServSubSent indicates the number of
         subscriptions sent from the XMPP server."
    ::= { tmnxSysXmppServerEntry 24 }

tmnxSysXmppServUnSubSent         OBJECT-TYPE
    SYNTAX      Counter64
    MAX-ACCESS  read-only
    STATUS      obsolete
    DESCRIPTION
        "The value of tmnxSysXmppServUnSubSent indicates the number of
         unsubscriptions sent from the XMPP server."
    ::= { tmnxSysXmppServerEntry 25 }

tmnxSysXmppServState             OBJECT-TYPE
    SYNTAX      DisplayString (SIZE (0..32))
    MAX-ACCESS  read-only
    STATUS      obsolete
    DESCRIPTION
        "The value of tmnxSysXmppServState indicates the state of the XMPP
         server."
    ::= { tmnxSysXmppServerEntry 26 }

tmnxSysXmppServAdminState        OBJECT-TYPE
    SYNTAX      TmnxAdminState
    MAX-ACCESS  read-create
    STATUS      obsolete
    DESCRIPTION
        "The value of tmnxSysXmppServAdminState specifies the administrative
         state of the XMPP server."
    DEFVAL      { outOfService }
    ::= { tmnxSysXmppServerEntry 27 }

tmnxSysXmppServOperUserName      OBJECT-TYPE
    SYNTAX      TNamedItemOrEmpty
    MAX-ACCESS  read-only
    STATUS      obsolete
    DESCRIPTION
        "The value of tmnxSysXmppServOperUserName indicates the operational user
         name that is used in the XMPP server access requests. When no user
         name is not provided,  the chassis MAC is used as the default user
         name."
    ::= { tmnxSysXmppServerEntry 28 }

tmnxSysXmppServAuthType          OBJECT-TYPE
    SYNTAX      TNamedItemOrEmpty
    MAX-ACCESS  read-only
    STATUS      obsolete
    DESCRIPTION
        "The value of tmnxSysXmppServAuthType indicates the authentication type
         that is used in the XMPP server access requests."
    ::= { tmnxSysXmppServerEntry 29 }

tmnxSysXmppServConnMode          OBJECT-TYPE
    SYNTAX      INTEGER {
        inBand    (1),
        outOfBand (2)
    }
    MAX-ACCESS  read-only
    STATUS      obsolete
    DESCRIPTION
        "The value of tmnxSysXmppServConnMode indicates the connection type
         that is used in the XMPP server access requests."
    ::= { tmnxSysXmppServerEntry 30 }

tmnxSysVsdServerTable            OBJECT-TYPE
    SYNTAX      SEQUENCE OF TmnxSysVsdServerEntry
    MAX-ACCESS  not-accessible
    STATUS      obsolete
    DESCRIPTION
        "The tmnxSysVsdServerTable contains information pertaining to an entry
         for each server."
    ::= { tmnxSysXmppInfo 2 }

tmnxSysVsdServerEntry            OBJECT-TYPE
    SYNTAX      TmnxSysVsdServerEntry
    MAX-ACCESS  not-accessible
    STATUS      obsolete
    DESCRIPTION
        "Each row entry contains information about a VSwitch Controller VSD
         server."
    INDEX       { tmnxSysVsdServerInstance }
    ::= { tmnxSysVsdServerTable 1 }

TmnxSysVsdServerEntry            ::= SEQUENCE
{
    tmnxSysVsdServerInstance         Unsigned32,
    tmnxSysVsdServUptime             TimeStamp,
    tmnxSysVsdServUserName           TLDisplayString,
    tmnxSysVsdServerStatus           DisplayString,
    tmnxSysVsdServMsgSent            Counter64,
    tmnxSysVsdServMsgRcvd            Counter64,
    tmnxSysVsdServMsgAckRcvd         Counter64,
    tmnxSysVsdServMsgError           Counter64,
    tmnxSysVsdServMsgTimedOut        Counter64,
    tmnxSysVsdServMsgMinRtt          Counter64,
    tmnxSysVsdServMsgMaxRtt          Counter64
}

tmnxSysVsdServerInstance         OBJECT-TYPE
    SYNTAX      Unsigned32
    MAX-ACCESS  not-accessible
    STATUS      obsolete
    DESCRIPTION
        "The value of tmnxSysVsdServerInstance specifies an instance of a
         VSwitch Controller VSD server.
         The instance Id is an internally generated number that is unique
         for a given  VSD server."
    ::= { tmnxSysVsdServerEntry 1 }

tmnxSysVsdServUptime             OBJECT-TYPE
    SYNTAX      TimeStamp
    MAX-ACCESS  read-only
    STATUS      obsolete
    DESCRIPTION
        "The value of tmnxSysVsdServUptime indicates the timestamp of the
         uptime of each VSD server entry in tmnxSysXmppServerTable."
    ::= { tmnxSysVsdServerEntry 2 }

tmnxSysVsdServUserName           OBJECT-TYPE
    SYNTAX      TLDisplayString
    MAX-ACCESS  read-only
    STATUS      obsolete
    DESCRIPTION
        "The value of tmnxSysVsdServUserName specifies the VSD username."
    ::= { tmnxSysVsdServerEntry 3 }

tmnxSysVsdServerStatus           OBJECT-TYPE
    SYNTAX      DisplayString (SIZE (0..32))
    MAX-ACCESS  read-only
    STATUS      obsolete
    DESCRIPTION
        "The value of tmnxSysVsdServerStatus indicates the status of the VSD
         server."
    ::= { tmnxSysVsdServerEntry 4 }

tmnxSysVsdServMsgSent            OBJECT-TYPE
    SYNTAX      Counter64
    MAX-ACCESS  read-only
    STATUS      obsolete
    DESCRIPTION
        "The value of tmnxSysVsdServMsgSent indicates the number of messages
         sent from the VSD server."
    ::= { tmnxSysVsdServerEntry 5 }

tmnxSysVsdServMsgRcvd            OBJECT-TYPE
    SYNTAX      Counter64
    MAX-ACCESS  read-only
    STATUS      obsolete
    DESCRIPTION
        "The value of tmnxSysVsdServMsgRcvd indicates the number of messages
         received from the VSD server."
    ::= { tmnxSysVsdServerEntry 6 }

tmnxSysVsdServMsgAckRcvd         OBJECT-TYPE
    SYNTAX      Counter64
    MAX-ACCESS  read-only
    STATUS      obsolete
    DESCRIPTION
        "The value of tmnxSysVsdServMsgAckRcvd indicates the number of message
         acknowledgements received from the VSD server."
    ::= { tmnxSysVsdServerEntry 7 }

tmnxSysVsdServMsgError           OBJECT-TYPE
    SYNTAX      Counter64
    MAX-ACCESS  read-only
    STATUS      obsolete
    DESCRIPTION
        "The value of tmnxSysVsdServMsgError indicates the number of error
         messages received from the VSD server."
    ::= { tmnxSysVsdServerEntry 8 }

tmnxSysVsdServMsgTimedOut        OBJECT-TYPE
    SYNTAX      Counter64
    MAX-ACCESS  read-only
    STATUS      obsolete
    DESCRIPTION
        "The value of tmnxSysVsdServMsgTimedOut indicates the number of timeout
         messages received from the VSD server."
    ::= { tmnxSysVsdServerEntry 9 }

tmnxSysVsdServMsgMinRtt          OBJECT-TYPE
    SYNTAX      Counter64
    UNITS       "milliseconds"
    MAX-ACCESS  read-only
    STATUS      obsolete
    DESCRIPTION
        "The value of tmnxSysVsdServMsgMinRtt indicates the minimum message
         round trip time from the VSD server."
    ::= { tmnxSysVsdServerEntry 10 }

tmnxSysVsdServMsgMaxRtt          OBJECT-TYPE
    SYNTAX      Counter64
    UNITS       "milliseconds"
    MAX-ACCESS  read-only
    STATUS      obsolete
    DESCRIPTION
        "The value of tmnxSysVsdServMsgMaxRtt indicates the maximum message
         round trip time from the VSD server."
    ::= { tmnxSysVsdServerEntry 11 }

tmnxSysResInfo                   OBJECT IDENTIFIER ::= { tmnxSysObjs 27 }

tmnxSysResCardInfo               OBJECT IDENTIFIER ::= { tmnxSysResInfo 1 }

tmnxCardCpuResMonitorTable       OBJECT-TYPE
    SYNTAX      SEQUENCE OF TmnxCardCpuResMonitorEntry
    MAX-ACCESS  not-accessible
    STATUS      current
    DESCRIPTION
        "The tmnxCardCpuResMonitorTable details the specified current card's
         CPU resources.

         The information described in this table is volatile and dependent on
         the current environmental conditions, and specified sample-time.
         Information is only displayed for online cards."
    ::= { tmnxSysResCardInfo 1 }

tmnxCardCpuResMonitorEntry       OBJECT-TYPE
    SYNTAX      TmnxCardCpuResMonitorEntry
    MAX-ACCESS  not-accessible
    STATUS      current
    DESCRIPTION
        "The tmnxCardCpuResMonitorEntry contains the card level CPU monitoring
         statistics over a specified sample-time."
    INDEX       {
        tmnxChassisIndex,
        tmnxCardResourceSlotNum,
        tmnxCardCpuResSampleTime
    }
    ::= { tmnxCardCpuResMonitorTable 1 }

TmnxCardCpuResMonitorEntry       ::= SEQUENCE
{
    tmnxCardResourceSlotNum          TmnxSlotNum,
    tmnxCardCpuResSampleTime         TmnxSysMonSampleTime,
    tmnxCardCpuResMonCpuIdle         TmnxSysMonUtilization,
    tmnxCardCpuResMonBusyCoreUtil    TmnxSysMonUtilization,
    tmnxCardCpuResMonBusyGroupName   OCTET STRING,
    tmnxCardCpuResMonBusyGroupUtil   TmnxSysMonUtilization
}

tmnxCardResourceSlotNum          OBJECT-TYPE
    SYNTAX      TmnxSlotNum
    MAX-ACCESS  not-accessible
    STATUS      current
    DESCRIPTION
        "The value of tmnxCardResourceSlotNum specifies the slot number of the
         card to which the resource information is monitored."
    ::= { tmnxCardCpuResMonitorEntry 1 }

tmnxCardCpuResSampleTime         OBJECT-TYPE
    SYNTAX      TmnxSysMonSampleTime
    MAX-ACCESS  not-accessible
    STATUS      current
    DESCRIPTION
        "The value of tmnxCardCpuResSampleTime specifies the sample-time used
         to calculate the utilization results for the row."
    ::= { tmnxCardCpuResMonitorEntry 2 }

tmnxCardCpuResMonCpuIdle         OBJECT-TYPE
    SYNTAX      TmnxSysMonUtilization
    MAX-ACCESS  read-only
    STATUS      current
    DESCRIPTION
        "The value of tmnxCardCpuResMonCpuIdle indicates the overall percentage
         of CPU idleness over the specified sample-time."
    ::= { tmnxCardCpuResMonitorEntry 3 }

tmnxCardCpuResMonBusyCoreUtil    OBJECT-TYPE
    SYNTAX      TmnxSysMonUtilization
    MAX-ACCESS  read-only
    STATUS      current
    DESCRIPTION
        "The value of tmnxCardCpuResMonBusyCoreUtil indicates the utilization
         percentage of the busiest processor core over the specified
         sample-time. On single core CPUs, this is the overall system
         utilization percentage over the specified sample-time."
    ::= { tmnxCardCpuResMonitorEntry 4 }

tmnxCardCpuResMonBusyGroupName   OBJECT-TYPE
    SYNTAX      OCTET STRING (SIZE (0..64))
    MAX-ACCESS  read-only
    STATUS      current
    DESCRIPTION
        "The value of tmnxCardCpuResMonBusyGroupName indicates the name of the
         group that is running at the highest capacity utilization.

         Capacity utilization is the CPU utilization relative to the maximum CPU
         resources available to that group.  A group is a set of related
         applications, services, tasks or protocol handlers that consumes some
         part of the system CPU resources.

         The capacity utilization of the busiest group is indicated by
         tmnxCardCpuResMonBusyGroupUtil."
    ::= { tmnxCardCpuResMonitorEntry 5 }

tmnxCardCpuResMonBusyGroupUtil   OBJECT-TYPE
    SYNTAX      TmnxSysMonUtilization
    MAX-ACCESS  read-only
    STATUS      current
    DESCRIPTION
        "The value of tmnxCardCpuResMonBusyGroupUtil indicates the capacity
         utilization of the group that is running at the highest capacity
         utilization.

         Capacity utilization is the CPU utilization relative to the maximum CPU
         resources available to that group.  A group is a set of related
         applications, services, tasks or protocol handlers that consumes some
         part of the system CPU resources.

         The name of the busiest group is indicated by
         tmnxCardCpuResMonBusyGroupName."
    ::= { tmnxCardCpuResMonitorEntry 6 }

tmnxCardMemResMonitorTable       OBJECT-TYPE
    SYNTAX      SEQUENCE OF TmnxCardMemResMonitorEntry
    MAX-ACCESS  not-accessible
    STATUS      current
    DESCRIPTION
        "The tmnxCardMemResMonitorTable details the specified current card's
         memory resources.

         The information described in this table is volatile and dependent on
         the current environmental conditions. Information is only displayed
         for online cards."
    ::= { tmnxSysResCardInfo 2 }

tmnxCardMemResMonitorEntry       OBJECT-TYPE
    SYNTAX      TmnxCardMemResMonitorEntry
    MAX-ACCESS  not-accessible
    STATUS      current
    DESCRIPTION
        "The tmnxCardMemResMonitorEntry contains the card's memory usage
         statistics."
    INDEX       {
        tmnxChassisIndex,
        tmnxCardResourceSlotNum
    }
    ::= { tmnxCardMemResMonitorTable 1 }

TmnxCardMemResMonitorEntry       ::= SEQUENCE
{
    tmnxCardMemResMemoryUsed         Gauge32,
    tmnxCardMemResMemoryAvailable    Gauge32,
    tmnxCardMemResPoolsAllocated     Gauge32
}

tmnxCardMemResMemoryUsed         OBJECT-TYPE
    SYNTAX      Gauge32
    UNITS       "kilobytes"
    MAX-ACCESS  read-only
    STATUS      current
    DESCRIPTION
        "The value of tmnxCardMemResMemoryUsed indicates the total
         pre-allocated pool memory, in kilobytes, currently in use on the card."
    ::= { tmnxCardMemResMonitorEntry 1 }

tmnxCardMemResMemoryAvailable    OBJECT-TYPE
    SYNTAX      Gauge32
    UNITS       "kilobytes"
    MAX-ACCESS  read-only
    STATUS      current
    DESCRIPTION
        "The value of tmnxCardMemResMemoryAvailable indicates the amount of
         free memory, in kilobytes, in the card that is not allocated to memory
         pools, but is available in case a memory pool needs to grow."
    ::= { tmnxCardMemResMonitorEntry 2 }

tmnxCardMemResPoolsAllocated     OBJECT-TYPE
    SYNTAX      Gauge32
    UNITS       "kilobytes"
    MAX-ACCESS  read-only
    STATUS      current
    DESCRIPTION
        "The value of tmnxCardMemResPoolsAllocated indicates the total memory,
         in kilobytes, currently allocated in memory-pools on the card.

         This memory may or may not be currently in use, but is pre-allocated
         should the software need to use it."
    ::= { tmnxCardMemResMonitorEntry 3 }

tmnxSysResEcmpProfInfo           OBJECT IDENTIFIER ::= { tmnxSysResInfo 2 }

tmnxSysResEcmpProfTable          OBJECT-TYPE
    SYNTAX      SEQUENCE OF TmnxSysResEcmpProfEntry
    MAX-ACCESS  not-accessible
    STATUS      obsolete
    DESCRIPTION
        "The tmnxSysResEcmpProfTable contains information about the system
         resource profile to be allocated for each type of the ecmp bundle.

         The table can have up to a maximum of 2 entries.

         This object is deprecated from release 23.10.  Ecmp-profile dictated
         partitioning of ECMP resources is no longer required.  IXR now supports
         Dynamic Resource Management of ECMP resources"
    ::= { tmnxSysResEcmpProfInfo 1 }

tmnxSysResEcmpProfEntry          OBJECT-TYPE
    SYNTAX      TmnxSysResEcmpProfEntry
    MAX-ACCESS  not-accessible
    STATUS      obsolete
    DESCRIPTION
        "Each row entry contains information about the resources to be created
         for each type of ecmp bundle supported.

         Entries in this table can be created and deleted via SNMP SET
         operations to tmnxSysResEcmpProfRowStatus.

         This object is deprecated from release 23.10.  Ecmp-profile dictated
         partitioning of ECMP resources is no longer required.  IXR now supports
         Dynamic Resource Management of ECMP resources"
    INDEX       { tmnxSysResEcmpProfId }
    ::= { tmnxSysResEcmpProfTable 1 }

TmnxSysResEcmpProfEntry          ::= SEQUENCE
{
    tmnxSysResEcmpProfId             Unsigned32,
    tmnxSysResEcmpProfRowStatus      RowStatus,
    tmnxSysResEcmpProfType           INTEGER,
    tmnxSysResEcmpProfLinksPerGrp    Unsigned32,
    tmnxSysResEcmpProfNumGrps        Unsigned32
}

tmnxSysResEcmpProfId             OBJECT-TYPE
    SYNTAX      Unsigned32 (1..2)
    MAX-ACCESS  not-accessible
    STATUS      obsolete
    DESCRIPTION
        "The value of tmnxSysResEcmpProfId specifies the resource profile index
         for the ecmp bundle.

         This object is deprecated from release 23.10.  Ecmp-profile dictated
         partitioning of ECMP resources is no longer required.  IXR now supports
         Dynamic Resource Management of ECMP resources"
    ::= { tmnxSysResEcmpProfEntry 1 }

tmnxSysResEcmpProfRowStatus      OBJECT-TYPE
    SYNTAX      RowStatus
    MAX-ACCESS  read-create
    STATUS      obsolete
    DESCRIPTION
        "The value of the tmnxSysResEcmpProfRowStatus specifies the status of this row.  It
         allows the creation and deletion of row entries in tmnxSysResEcmpProfTable.

         To create a row in this table, set tmnxSysResEcmpProfRowStatus to createAndGo(4).  The values of
         tmnxSysResEcmpProfType, tmnxSysResEcmpProfLinksPerGrp, and tmnxSysResEcmpProfNumGrps must also be
         set to valid values for the row creation to succeed.

         To delete a row in this table, set tmnxSysResEcmpProfRowStatus to
         destroy(6).

         This object is deprecated from release 23.10.  Ecmp-profile dictated
         partitioning of ECMP resources is no longer required.  IXR now supports
         Dynamic Resource Management of ECMP resources"
    ::= { tmnxSysResEcmpProfEntry 2 }

tmnxSysResEcmpProfType           OBJECT-TYPE
    SYNTAX      INTEGER {
        mpls (1),
        ip   (2)
    }
    MAX-ACCESS  read-create
    STATUS      obsolete
    DESCRIPTION
        "The value of tmnxSysResEcmpProfType specifies the ecmp bundle type
         applicable to this conceptual row.

         This object is deprecated from release 23.10.  Ecmp-profile dictated
         partitioning of ECMP resources is no longer required.  IXR now supports
         Dynamic Resource Management of ECMP resources"
    ::= { tmnxSysResEcmpProfEntry 3 }

tmnxSysResEcmpProfLinksPerGrp    OBJECT-TYPE
    SYNTAX      Unsigned32 (1..16)
    MAX-ACCESS  read-create
    STATUS      obsolete
    DESCRIPTION
        "The value of tmnxSysResEcmpProfLinksPerGrp specifies the maximum
         number of links per group for the ecmp bundle.

         This object is deprecated from release 23.10.  Ecmp-profile dictated
         partitioning of ECMP resources is no longer required.  IXR now supports
         Dynamic Resource Management of ECMP resources"
    ::= { tmnxSysResEcmpProfEntry 4 }

tmnxSysResEcmpProfNumGrps        OBJECT-TYPE
    SYNTAX      Unsigned32 (1..2048)
    MAX-ACCESS  read-create
    STATUS      obsolete
    DESCRIPTION
        "The value of tmnxSysResEcmpProfNumGrps specifies the maximum number of
         ecmp groups allowed for the ecmp bundle. When tmnxSysResEcmpProfType
         is 'mpls', maximum value of tmnxSysResEcmpProfNumGrps is 2047, Only
         when tmnxSysResEcmpProfType is 'ip', can the maximum value of
         tmnxSysResEcmpProfNumGrps be 2048.

         This object is deprecated from release 23.10.  Ecmp-profile dictated
         partitioning of ECMP resources is no longer required.  IXR now supports
         Dynamic Resource Management of ECMP resources"
    ::= { tmnxSysResEcmpProfEntry 5 }

tmnxSysResItCam                  OBJECT IDENTIFIER ::= { tmnxSysResInfo 3 }

tmnxSysResItCamBank              OBJECT IDENTIFIER ::= { tmnxSysResItCam 1 }

tmnxSysResItCamBankV6Multicast   OBJECT-TYPE
    SYNTAX      Unsigned32 (0..5)
    MAX-ACCESS  read-write
    STATUS      current
    DESCRIPTION
        "The value of tmnxSysResItCamBankV6Multicast specifies the maximum
         number of internal TCAM banks to support ipv6 multicast to scale"
    DEFVAL      { 0 }
    ::= { tmnxSysResItCamBank 1 }

tmnxSysFpCam                     OBJECT IDENTIFIER ::= { tmnxSysResInfo 4 }

tmnxSysFpCamAllocation           OBJECT IDENTIFIER ::= { tmnxSysFpCam 1 }

tmnxSysFpCamAllocAdmnV6Multicast OBJECT-TYPE
    SYNTAX      Unsigned32 (0..10240)
    MAX-ACCESS  read-write
    STATUS      current
    DESCRIPTION
        "The value of tmnxSysFpCamAllocAdmnV6Multicast specifies the maximum
         number of number of IPv6 multicast routes allowed to be installed in
         the system/FP"
    DEFVAL      { 0 }
    ::= { tmnxSysFpCamAllocation 1 }

tmnxSysFpCamAllocOperV6Multicast OBJECT-TYPE
    SYNTAX      Unsigned32 (0..10240)
    MAX-ACCESS  read-only
    STATUS      current
    DESCRIPTION
        "The value of tmnxSysFpCamAllocOperV6Multicast specifies the total
         number of IPv6 multicast routes installed in the system/FP"
    ::= { tmnxSysFpCamAllocation 2 }

tmnxSysFpResAlloc                OBJECT IDENTIFIER ::= { tmnxSysResInfo 5 }

tmnxSysFpResAllocation           OBJECT IDENTIFIER ::= { tmnxSysFpResAlloc 1 }

tmnxSysFpResAllocG8032Sap        OBJECT-TYPE
    SYNTAX      Unsigned32 (0..4096)
    MAX-ACCESS  read-write
    STATUS      deprecated
    DESCRIPTION
        "The tmnxSysFpResAllocG8032Sap specifies the number of G8032 saps
         resources allocated for forwarding path:
           IXR-e Small - 600 max
           IXR-e Big - 2048 max
           IXR-R6/s - 4096 max
         This value takes effect after system has rebooted.
         This is replaced with system wide paired number"
    DEFVAL      { 0 }
    ::= { tmnxSysFpResAllocation 1 }

tmnxSysFpResAllocOperG8032Sap    OBJECT-TYPE
    SYNTAX      Unsigned32 (0..4096)
    MAX-ACCESS  read-only
    STATUS      deprecated
    DESCRIPTION
        "The tmnxSysFpResAllocOperG8032Sap indicates the number of G8032 saps
         resources allocated for forwarding path. This is replaced with system
         wide paired number"
    ::= { tmnxSysFpResAllocation 2 }

tmnxSysFpResAllocFilterIpv6      OBJECT-TYPE
    SYNTAX      Unsigned32 (0 | 2 | 4 | 6 | 8 | 10)
    MAX-ACCESS  read-write
    STATUS      current
    DESCRIPTION
        "The tmnxSysFpResAllocFilterIpv6 specifies the number of ipv6 filter
         resources allocated for forwarding path. This value takes effect after
         system has rebooted."
    DEFVAL      { 4 }
    ::= { tmnxSysFpResAllocation 3 }

tmnxSysFpResAllocOperFilterIpv6  OBJECT-TYPE
    SYNTAX      Unsigned32 (0 | 2 | 4 | 6 | 8 | 10)
    MAX-ACCESS  read-only
    STATUS      current
    DESCRIPTION
        "The tmnxSysFpResAllocOperFilterIpv6 specifies the current operational
         number of ipv6 filter resources allocated for forwarding path."
    ::= { tmnxSysFpResAllocation 4 }

tmnxSysFpResAllocFecSysWdUnpd    OBJECT-TYPE
    SYNTAX      Unsigned32 (2..10240)
    MAX-ACCESS  read-write
    STATUS      current
    DESCRIPTION
        "The value of tmnxSysFpResAllocFecSysWdUnpd indicates the configured
         number of system-wide FEC space. Default value is dependent on the platform.
         Max Fec system-wide space:
         IXR-ec  - 200 max
         IXR-e Small - 800 max
         IXR-e Big - 3072 max
         IXR-6/10 - 8192 max
         IXR-X1/Xs/X3 - 8192 max
         IXR-R6/s - 8192 max
         This value takes effect after system has rebooted."
    ::= { tmnxSysFpResAllocation 5 }

tmnxSysFpResAllocFecOprSysWdUnpd OBJECT-TYPE
    SYNTAX      Unsigned32
    MAX-ACCESS  read-only
    STATUS      current
    DESCRIPTION
        "The value of tmnxSysFpResAllocFecOprSysWdUnpd indicates the
         operational number of system-wide FEC space."
    ::= { tmnxSysFpResAllocation 6 }

tmnxSysFpResAllocFecSysWdPd      OBJECT-TYPE
    SYNTAX      Unsigned32 (0..8192)
    MAX-ACCESS  read-write
    STATUS      current
    DESCRIPTION
        "The value tmnxSysFpResAllocFecSysWdPd indicates the configured number
         of paired FEC space."
    DEFVAL      { 0 }
    ::= { tmnxSysFpResAllocation 7 }

tmnxSysFpResAllocFecOprSysWdPd   OBJECT-TYPE
    SYNTAX      Unsigned32
    MAX-ACCESS  read-only
    STATUS      current
    DESCRIPTION
        "The value tmnxSysFpResAllocFecOprSysWdPd indicates the operational
         number of paired FEC space."
    ::= { tmnxSysFpResAllocation 8 }

tmnxSysFpResAlcEgrEncapRouted    OBJECT-TYPE
    SYNTAX      INTEGER {
        entries4k  (1),
        entries8k  (2),
        entries12k (3)
    }
    MAX-ACCESS  read-write
    STATUS      current
    DESCRIPTION
        "The value of tmnxSysFpResAlcEgrEncapRouted specifies the number of
         egress encapsulated routable entries that have been administratively
         provisioned for the given FP.

         This value only takes effect after the system has rebooted.

         tmnxSysFpResAlcEgrEncapOprRouted indicates the operational value."
    DEFVAL      { entries12k }
    ::= { tmnxSysFpResAllocation 9 }

tmnxSysFpResAlcEgrEncapOprRouted OBJECT-TYPE
    SYNTAX      INTEGER {
        entries4k  (1),
        entries8k  (2),
        entries12k (3)
    }
    MAX-ACCESS  read-only
    STATUS      current
    DESCRIPTION
        "The value of tmnxSysFpResAlcEgrEncapOprRouted indicates the
         operational number of egress encapsulated routable entries that have
         allocated for the given FP."
    ::= { tmnxSysFpResAllocation 10 }

tmnxSysFpRAEgrEncpPrtVlanTrns    OBJECT-TYPE
    SYNTAX      INTEGER {
        entries2k  (1),
        entries4k  (2),
        entries8k  (3),
        entries16k (4)
    }
    MAX-ACCESS  read-write
    STATUS      current
    DESCRIPTION
        "The value of tmnxSysFpRAEgrEncpPrtVlanTrns specifies the number of
         egress encapsulated port VLAN translation entries that have been
         administratively provisioned for the given FP.

         This value only takes effect after the system has rebooted.

         tmnxSysFpRAEgrEncpOprPrtVlanTrns indicates the operational value."
    ::= { tmnxSysFpResAllocation 11 }

tmnxSysFpRAEgrEncpOprPrtVlanTrns OBJECT-TYPE
    SYNTAX      INTEGER {
        entries2k  (1),
        entries4k  (2),
        entries8k  (3),
        entries16k (4)
    }
    MAX-ACCESS  read-only
    STATUS      current
    DESCRIPTION
        "The value of tmnxSysFpRAEgrEncpOprPrtVlanTrns indicates the
         operational number of egress encapsulated port VLAN translation
         entries that have been allocated for the given FP."
    ::= { tmnxSysFpResAllocation 12 }

tmnxSysFpRAPlcrStatsOvrState     OBJECT-TYPE
    SYNTAX      TmnxEnabledDisabledAdminState
    MAX-ACCESS  read-write
    STATUS      current
    DESCRIPTION
        "The value of tmnxSysFpRAPlcrStatsOvrState specifies the administrative
         state of whether policers and stats scale values will be default or
         overridden."
    DEFVAL      { disabled }
    ::= { tmnxSysFpResAllocation 13 }

tmnxSysFpRAPlcrStatsOvrOperState OBJECT-TYPE
    SYNTAX      TmnxEnabledDisabledAdminState
    MAX-ACCESS  read-only
    STATUS      current
    DESCRIPTION
        "The value of tmnxSysFpRAPlcrStatsOvrOperState specifies the
         administrative state of whether policers and stats scale values will
         be default or overridden."
    DEFVAL      { disabled }
    ::= { tmnxSysFpResAllocation 14 }

tmnxSysFpRASrv6TnlTermEntries    OBJECT-TYPE
    SYNTAX      Unsigned32 (256 | 1024 | 2048)
    MAX-ACCESS  read-write
    STATUS      current
    DESCRIPTION
        "The value of tmnxSysFpRASrv6TnlTermEntries specifies the maximum
         number of SRv6 tunnel termination TCAM entries allowed on the system.

         TCAM entries are required by SID locators, uSID uN/uA function,
         loopback address and alike.

         This value only takes effect after the system has rebooted."
    DEFVAL      { 256 }
    ::= { tmnxSysFpResAllocation 15 }

tmnxSysFpRASrv6TnlTermOprEntries OBJECT-TYPE
    SYNTAX      Unsigned32 (256 | 1024 | 2048)
    MAX-ACCESS  read-only
    STATUS      current
    DESCRIPTION
        "The value of tmnxSysFpRASrv6TnlTermOprEntries indicates the
         operational value of the maximum number of SRv6 tunnel termination
         TCAM entries on the system.

         TCAM entries are required by SID locators, uSID uN/uA function,
         loopback address and alike."
    DEFVAL      { 256 }
    ::= { tmnxSysFpResAllocation 16 }

tmnxSysFpRAStatsPolicerBanks     OBJECT-TYPE
    SYNTAX      Unsigned32 (0..4)
    MAX-ACCESS  read-write
    STATUS      current
    DESCRIPTION
        "The value of tmnxSysFpRAStatsPolicerBanks specifies the configured number of
         system-wide resources allocated for policer statistics.
         Default value is dependent on the platform.
         Max policer stats system-wide space:
         QmX (IXR-R6)         - 1 bank  max. 96k in bank.
         QmX (IXR-S)          - 2 banks max. 16k in each bank.
         Qax (IXR-Eax/IXR-R4) - 4 banks max. 4k in each bank.
         Qux(IXR-Eux/IXR-Ec)  - 4 banks max. 1 k each bank.
         This value takes effect after system has rebooted."
    ::= { tmnxSysFpResAllocation 17 }

tmnxSysFpRAStatsPolicerOperBanks OBJECT-TYPE
    SYNTAX      Unsigned32 (0..4)
    MAX-ACCESS  read-only
    STATUS      current
    DESCRIPTION
        "The tmnxSysFpRAStatsPolicerOperBanks specifies the current operational
         number of resources allocated for policer statistics."
    ::= { tmnxSysFpResAllocation 18 }

tmnxSysFpRAStatsFltrIngBanks     OBJECT-TYPE
    SYNTAX      Unsigned32
    MAX-ACCESS  read-write
    STATUS      current
    DESCRIPTION
        "The tmnxSysFpRAStatsFltrIngBanks specifies the number of  resources
         allocated for ingress filter statistics. This value takes effect after
         system has rebooted."
    DEFVAL      { 0 }
    ::= { tmnxSysFpResAllocation 19 }

tmnxSysFpRAStatsFltrOperIngBanks OBJECT-TYPE
    SYNTAX      Unsigned32
    MAX-ACCESS  read-only
    STATUS      current
    DESCRIPTION
        "The tmnxSysFpRAStatsFltrOperIngBanks specifies the current operational
          number of resources allocated for ingress filter statistics."
    ::= { tmnxSysFpResAllocation 20 }

tmnxSysFpRAStatsFltrEgrBanks     OBJECT-TYPE
    SYNTAX      Unsigned32
    MAX-ACCESS  read-write
    STATUS      current
    DESCRIPTION
        "The tmnxSysFpRAStatsFltrEgrBanks specifies the number of  resources
         allocated for egress filter statistics. This value takes effect after
         system has rebooted."
    DEFVAL      { 0 }
    ::= { tmnxSysFpResAllocation 21 }

tmnxSysFpRAStatsFltrOperEgrBanks OBJECT-TYPE
    SYNTAX      Unsigned32
    MAX-ACCESS  read-only
    STATUS      current
    DESCRIPTION
        "The tmnxSysFpRAStatsFltrOperEgrBanks specifies the current operational
          number of resources allocated for egress filter statistics."
    ::= { tmnxSysFpResAllocation 22 }

tmnxSysFpRAStatsDdctdFcPlcrs     OBJECT-TYPE
    SYNTAX      Unsigned32 (0..10816)
    MAX-ACCESS  read-write
    STATUS      current
    DESCRIPTION
        "tmnxSysFpRAStatsDdctdFcPlcrs specifies the number of stats allocated
         for dedicated fc policers. This value takes effect after a system
         reboot. Default value is dependent on the platform.
            IXR-s : 6000"
    ::= { tmnxSysFpResAllocation 23 }

tmnxSysFpRAStatsOperDdctdFcPlcrs OBJECT-TYPE
    SYNTAX      Unsigned32 (0..10816)
    MAX-ACCESS  read-only
    STATUS      current
    DESCRIPTION
        "tmnxSysFpRAStatsOperDdctdFcPlcrs specifies the current operational
         number of stats allocated for dedicated fc policers."
    ::= { tmnxSysFpResAllocation 24 }

tmnxSysFpRAEcmpBgpMplsTunnlBind  OBJECT-TYPE
    SYNTAX      TruthValue
    MAX-ACCESS  read-write
    STATUS      current
    DESCRIPTION
        "The value of the object tmnxSysFpRAEcmpBgpMplsTunnlBind specifies
         whether per flow load balancing over ECMPs for auto bind L2 and L3
         services is enabled.

         When enabled traffic is distributed over set of equal cost paths
         dedicated to a given service. The path selection is based on flows
         identified by packet fields. When disabled service id based load
         balancing is applied. This value takes effect after a system reboot."
    DEFVAL      { false }
    ::= { tmnxSysFpResAllocation 25 }

tmnxSysFpRAEcmpOperBgpMplsTBind  OBJECT-TYPE
    SYNTAX      TruthValue
    MAX-ACCESS  read-only
    STATUS      current
    DESCRIPTION
        "The value of the object tmnxSysFpRAEcmpOperBgpMplsTBind specifies the
         operation values of per flow load balancing over ECMPs for auto bind
         is enabled or not."
    ::= { tmnxSysFpResAllocation 26 }

tmnxSysFpRAEcmpPrFlwHashSdpBind  OBJECT-TYPE
    SYNTAX      TruthValue
    MAX-ACCESS  read-write
    STATUS      current
    DESCRIPTION
        "The value of the object tmnxSysFpRAEcmpPrFlwHashSdpBind specifies
         whether per flow load balancing over ECMPs for sdp manual bind L2 and
         L3 services is enabled.

         When enabled traffic is distributed over set of equal cost paths
         dedicated to a given service. The path selection is based on flows
         identified by packet fields. When disabled service id or sdp based
         load balancing is applied. This value takes effect after a system
         reboot."
    DEFVAL      { false }
    ::= { tmnxSysFpResAllocation 27 }

tmnxSysFpRAEcmpOprPrFlwHshSBind  OBJECT-TYPE
    SYNTAX      TruthValue
    MAX-ACCESS  read-only
    STATUS      current
    DESCRIPTION
        "The value of the object tmnxSysFpRAEcmpOprPrFlwHshSBind specifies the
         operation values of per flow load balancing over ECMPs for sdp manual
         bind is enabled or not."
    ::= { tmnxSysFpResAllocation 28 }

tmnxSysFpRAAdminProfile          OBJECT-TYPE
    SYNTAX      Unsigned32 (0 | 5)
    MAX-ACCESS  read-write
    STATUS      current
    DESCRIPTION
        " tmnxSysFpRAAdminProfile specifies the configured value of the
          profile option for forwarding path resource allocation.

          A system reboot is needed after changing this value."
    ::= { tmnxSysFpResAllocation 29 }

tmnxSysFpRAOperProfile           OBJECT-TYPE
    SYNTAX      Unsigned32 (0 | 5)
    MAX-ACCESS  read-only
    STATUS      current
    DESCRIPTION
        " tmnxSysFpRAOperProfile specifies the operational value of the
          profile option for forwarding path resource allocation"
    ::= { tmnxSysFpResAllocation 30 }

tmnxSysFpRAVlanQosFourQueue      OBJECT-TYPE
    SYNTAX      Unsigned32 (0..4454)
    MAX-ACCESS  read-write
    STATUS      current
    DESCRIPTION
        " tmnxSysFpRAVlanQosFourQueue specifies the configured value of the
          vlan qos queue allocation for 4-queue mode.

          A system reboot is needed after changing this value."
    DEFVAL      { 0 }
    ::= { tmnxSysFpResAllocation 31 }

tmnxSysFpRAVlanQosOprFourQueue   OBJECT-TYPE
    SYNTAX      Unsigned32 (0..4454)
    MAX-ACCESS  read-only
    STATUS      current
    DESCRIPTION
        " tmnxSysFpRAVlanQosOprFourQueue specifies the operational value of the
          vlan qos queue allocation for 4-queue mode.

          A system reboot is needed after changing this value."
    DEFVAL      { 0 }
    ::= { tmnxSysFpResAllocation 32 }

tmnxSysFpRAVlanQosStatFourQueue  OBJECT-TYPE
    SYNTAX      Unsigned32 (0..746)
    MAX-ACCESS  read-write
    STATUS      current
    DESCRIPTION
        " tmnxSysFpRAVlanQosStatFourQueue specifies the configured value of the
          vlan qos stats allocation for 4-queue mode.

          A system reboot is needed after changing this value."
    DEFVAL      { 0 }
    ::= { tmnxSysFpResAllocation 33 }

tmnxSysFpRAVlanQosOprStatFourQ   OBJECT-TYPE
    SYNTAX      Unsigned32 (0..746)
    MAX-ACCESS  read-only
    STATUS      current
    DESCRIPTION
        " tmnxSysFpRAVlanQosOprStatFourQ specifies the operational value
          of the vlan qos stats allocation for 4-queue mode.

          A system reboot is needed after changing this value."
    DEFVAL      { 0 }
    ::= { tmnxSysFpResAllocation 34 }

tmnxSysFpResAllocPoolTable       OBJECT-TYPE
    SYNTAX      SEQUENCE OF TmnxSysFpResAllocPoolEntry
    MAX-ACCESS  not-accessible
    STATUS      current
    DESCRIPTION
        "The tmnxSysFpResAllocPoolTable has an entry for every FP resource
         allocation pool in the system."
    ::= { tmnxSysFpResAlloc 2 }

tmnxSysFpResAllocPoolEntry       OBJECT-TYPE
    SYNTAX      TmnxSysFpResAllocPoolEntry
    MAX-ACCESS  not-accessible
    STATUS      current
    DESCRIPTION
        "Each row represents a specific FP resource allocation pool in the
         system.

         Entries are automatically created by the system and cannot be created
         or deleted via SNMP SET operations."
    INDEX       { tmnxSysFpRAPoolId }
    ::= { tmnxSysFpResAllocPoolTable 1 }

TmnxSysFpResAllocPoolEntry       ::= SEQUENCE
{
    tmnxSysFpRAPoolId                Unsigned32,
    tmnxSysFpRAPoolLgBndRsvMemCnt    Unsigned32,
    tmnxSysFpRAPoolOprLgBndRsvMemCnt Unsigned32
}

tmnxSysFpRAPoolId                OBJECT-TYPE
    SYNTAX      Unsigned32 (1..2)
    MAX-ACCESS  not-accessible
    STATUS      current
    DESCRIPTION
        "The value of tmnxSysFpRAPoolId specifies the FP resource allocation
         pool identifier."
    ::= { tmnxSysFpResAllocPoolEntry 1 }

tmnxSysFpRAPoolLgBndRsvMemCnt    OBJECT-TYPE
    SYNTAX      Unsigned32 (2 | 4 | 8 | 16 | 32 | 64)
    MAX-ACCESS  read-write
    STATUS      current
    DESCRIPTION
        "The value of tmnxSysFpRAPoolLgBndRsvMemCnt specifies the number of lag
         bundle members reserved for the forwarding path.

         This value takes effect after system has rebooted."
    DEFVAL      { 64 }
    ::= { tmnxSysFpResAllocPoolEntry 2 }

tmnxSysFpRAPoolOprLgBndRsvMemCnt OBJECT-TYPE
    SYNTAX      Unsigned32
    MAX-ACCESS  read-only
    STATUS      current
    DESCRIPTION
        "The value of tmnxSysFpRAPoolOprLgBndRsvMemCnt indicates the
         operational number of lag bundle members reserved for the forwarding
         path.

         This value takes effect after system has rebooted."
    ::= { tmnxSysFpResAllocPoolEntry 3 }

tmnxSySFpRAFltrObjects           OBJECT IDENTIFIER ::= { tmnxSysFpResAlloc 3 }

tmnxSySpRAFltrIngObjects         OBJECT IDENTIFIER ::= { tmnxSySFpRAFltrObjects 1 }

tmnxSysFpRAFltrIngIpMatchObjs    OBJECT IDENTIFIER ::= { tmnxSySpRAFltrIngObjects 1 }

tmnxSysFpRAFltrInIpMSrcIp        OBJECT-TYPE
    SYNTAX      TruthValue
    MAX-ACCESS  read-write
    STATUS      current
    DESCRIPTION
        "The value of the object tmnxSysFpRAFltrInIpMSrcIp specifies whether
         filter policies referenced on ingress endpoints allow configuring
         source IP address as their match criterion."
    DEFVAL      { true }
    ::= { tmnxSysFpRAFltrIngIpMatchObjs 1 }

tmnxSysFpRAFltrInIpOpMSrcIp      OBJECT-TYPE
    SYNTAX      TruthValue
    MAX-ACCESS  read-only
    STATUS      current
    DESCRIPTION
        "The value of the object tmnxSysFpRAFltrInIpOpMSrcIp indicates the
         operational of tmnxSysFpRAFltrInIpMSrcIp."
    ::= { tmnxSysFpRAFltrIngIpMatchObjs 2 }

tmnxSysFpRAFltrInIpMDstIp        OBJECT-TYPE
    SYNTAX      TruthValue
    MAX-ACCESS  read-write
    STATUS      current
    DESCRIPTION
        "The value of the object tmnxSysFpRAFltrInIpMDstIp specifies whether
         filter policies referenced on ingress endpoints allow configuring
         destination IP address as their match criterion."
    DEFVAL      { true }
    ::= { tmnxSysFpRAFltrIngIpMatchObjs 3 }

tmnxSysFpRAFltrInIpOpMDstIp      OBJECT-TYPE
    SYNTAX      TruthValue
    MAX-ACCESS  read-only
    STATUS      current
    DESCRIPTION
        "The value of the object tmnxSysFpRAFltrInIpOpMDstIp indicates the
         operational of tmnxSysFpRAFltrInIpMDstIp."
    ::= { tmnxSysFpRAFltrIngIpMatchObjs 4 }

tmnxSysFpRAFltrInIpMSrcPort      OBJECT-TYPE
    SYNTAX      TruthValue
    MAX-ACCESS  read-write
    STATUS      current
    DESCRIPTION
        "The value of the object tmnxSysFpRAFltrInIpMSrcPort specifies whether
         filter policies referenced on ingress endpoints allow configuring L4
         source port as their match criterion."
    DEFVAL      { true }
    ::= { tmnxSysFpRAFltrIngIpMatchObjs 5 }

tmnxSysFpRAFltrInIpOpMSrcPort    OBJECT-TYPE
    SYNTAX      TruthValue
    MAX-ACCESS  read-only
    STATUS      current
    DESCRIPTION
        "The value of the object tmnxSysFpRAFltrInIpOpMSrcPort indicates the
         operational of tmnxSysFpRAFltrInIpMSrcPort."
    ::= { tmnxSysFpRAFltrIngIpMatchObjs 6 }

tmnxSysFpRAFltrInIpMDstPort      OBJECT-TYPE
    SYNTAX      TruthValue
    MAX-ACCESS  read-write
    STATUS      current
    DESCRIPTION
        "The value of the object tmnxSysFpRAFltrInIpMDstPort specifies whether
         filter policies referenced on ingress endpoints allow configuring L4
         destination port as their match criterion."
    DEFVAL      { true }
    ::= { tmnxSysFpRAFltrIngIpMatchObjs 7 }

tmnxSysFpRAFltrInIpOpMDstPort    OBJECT-TYPE
    SYNTAX      TruthValue
    MAX-ACCESS  read-only
    STATUS      current
    DESCRIPTION
        "The value of the object tmnxSysFpRAFltrInIpOpMDstPort indicates the
         operational of tmnxSysFpRAFltrInIpMDstPort."
    ::= { tmnxSysFpRAFltrIngIpMatchObjs 8 }

tmnxSysFpRAFltrInIpMProt         OBJECT-TYPE
    SYNTAX      TruthValue
    MAX-ACCESS  read-write
    STATUS      current
    DESCRIPTION
        "The value of the object tmnxSysFpRAFltrInIpMProt specifies whether
         filter policies referenced on ingress endpoints allow configuring IP
         protocol as their match criterion."
    DEFVAL      { true }
    ::= { tmnxSysFpRAFltrIngIpMatchObjs 9 }

tmnxSysFpRAFltrInIpOpMProt       OBJECT-TYPE
    SYNTAX      TruthValue
    MAX-ACCESS  read-only
    STATUS      current
    DESCRIPTION
        "The value of the object tmnxSysFpRAFltrInIpOpMProt indicates the
         operational of tmnxSysFpRAFltrInIpMProt."
    ::= { tmnxSysFpRAFltrIngIpMatchObjs 10 }

tmnxSysFpRAFltrInIpMTcpFlgs      OBJECT-TYPE
    SYNTAX      TruthValue
    MAX-ACCESS  read-write
    STATUS      current
    DESCRIPTION
        "The value of the object tmnxSysFpRAFltrInIpMTcpFlgs specifies whether
         filter policies referenced on ingress endpoints allow configuring TCP
         flags as their match criterion."
    DEFVAL      { true }
    ::= { tmnxSysFpRAFltrIngIpMatchObjs 11 }

tmnxSysFpRAFltrInIpOpMTcpFlgs    OBJECT-TYPE
    SYNTAX      TruthValue
    MAX-ACCESS  read-only
    STATUS      current
    DESCRIPTION
        "The value of the object tmnxSysFpRAFltrInIpOpMTcpFlgs indicates the
         operational of tmnxSysFpRAFltrInIpMTcpFlgs."
    ::= { tmnxSysFpRAFltrIngIpMatchObjs 12 }

tmnxSysFpRAFltrInIpMDscp         OBJECT-TYPE
    SYNTAX      TruthValue
    MAX-ACCESS  read-write
    STATUS      current
    DESCRIPTION
        "The value of the object tmnxSysFpRAFltrInIpMDscp specifies whether
         filter policies referenced on ingress endpoints allow configuring DSCP
         as their match criterion."
    DEFVAL      { true }
    ::= { tmnxSysFpRAFltrIngIpMatchObjs 13 }

tmnxSysFpRAFltrInIpOpMDscp       OBJECT-TYPE
    SYNTAX      TruthValue
    MAX-ACCESS  read-only
    STATUS      current
    DESCRIPTION
        "The value of the object tmnxSysFpRAFltrInIpOpMDscp indicates the
         operational of tmnxSysFpRAFltrInIpMDscp."
    ::= { tmnxSysFpRAFltrIngIpMatchObjs 14 }

tmnxSysFpRAFltrInIpMIcmpCode     OBJECT-TYPE
    SYNTAX      TruthValue
    MAX-ACCESS  read-write
    STATUS      current
    DESCRIPTION
        "The value of the object tmnxSysFpRAFltrInIpMIcmpCode specifies whether
         filter policies referenced on ingress endpoints allow configuring ICMP
         code as their match criterion."
    DEFVAL      { false }
    ::= { tmnxSysFpRAFltrIngIpMatchObjs 15 }

tmnxSysFpRAFltrInIpOpMIcmpCode   OBJECT-TYPE
    SYNTAX      TruthValue
    MAX-ACCESS  read-only
    STATUS      current
    DESCRIPTION
        "The value of the object tmnxSysFpRAFltrInIpOpMIcmpCode indicates the
         operational of tmnxSysFpRAFltrInIpMIcmpCode."
    ::= { tmnxSysFpRAFltrIngIpMatchObjs 16 }

tmnxSysFpRAFltrInIpMIcmpType     OBJECT-TYPE
    SYNTAX      TruthValue
    MAX-ACCESS  read-write
    STATUS      current
    DESCRIPTION
        "The value of the object tmnxSysFpRAFltrInIpMIcmpType specifies whether
         filter policies referenced on ingress endpoints allow configuring ICMP
         type as their match criterion."
    DEFVAL      { false }
    ::= { tmnxSysFpRAFltrIngIpMatchObjs 17 }

tmnxSysFpRAFltrInIpOpMIcmpType   OBJECT-TYPE
    SYNTAX      TruthValue
    MAX-ACCESS  read-only
    STATUS      current
    DESCRIPTION
        "The value of the object tmnxSysFpRAFltrInIpOpMIcmpType indicates the
         operational of tmnxSysFpRAFltrInIpMIcmpType."
    ::= { tmnxSysFpRAFltrIngIpMatchObjs 18 }

tmnxSysFpRAFltrInIpMTcpFlExt     OBJECT-TYPE
    SYNTAX      TruthValue
    MAX-ACCESS  read-write
    STATUS      current
    DESCRIPTION
        "The value of the object tmnxSysFpRAFltrInIpMTcpFlExt specifies whether
         filter policies referenced on ingress endpoints allow configuring TCP
         flags for explicit congestion notification as their match criterion."
    DEFVAL      { false }
    ::= { tmnxSysFpRAFltrIngIpMatchObjs 19 }

tmnxSysFpRAFltrInIpOpMTcpFlExt   OBJECT-TYPE
    SYNTAX      TruthValue
    MAX-ACCESS  read-only
    STATUS      current
    DESCRIPTION
        "The value of the object tmnxSysFpRAFltrInIpOpMTcpFlExt indicates the
         operational of tmnxSysFpRAFltrInIpMTcpFlExt."
    ::= { tmnxSysFpRAFltrIngIpMatchObjs 20 }

tmnxSysFpRAFltrIngIpActObjs      OBJECT IDENTIFIER ::= { tmnxSySpRAFltrIngObjects 2 }

tmnxSysFpRAFltrInIpADrop         OBJECT-TYPE
    SYNTAX      TruthValue
    MAX-ACCESS  read-write
    STATUS      current
    DESCRIPTION
        "The value of the object tmnxSysFpRAFltrInIpADrop specifies whether
         filter policies referenced on ingress endpoints allow configuring
         action drop."
    DEFVAL      { true }
    ::= { tmnxSysFpRAFltrIngIpActObjs 1 }

tmnxSysFpRAFltrInIpOpADrop       OBJECT-TYPE
    SYNTAX      TruthValue
    MAX-ACCESS  read-only
    STATUS      current
    DESCRIPTION
        "The value of the object tmnxSysFpRAFltrInIpOpADrop indicates the
         operational of tmnxSysFpRAFltrInIpADrop."
    ::= { tmnxSysFpRAFltrIngIpActObjs 2 }

tmnxSysFpRAFltrInIpARedir        OBJECT-TYPE
    SYNTAX      TruthValue
    MAX-ACCESS  read-write
    STATUS      current
    DESCRIPTION
        "The value of the object tmnxSysFpRAFltrInIpARedir specifies whether
         filter policies referenced on ingress endpoints allow configuring
         actions redirecting traffic."
    DEFVAL      { true }
    ::= { tmnxSysFpRAFltrIngIpActObjs 3 }

tmnxSysFpRAFltrInIpOpARedir      OBJECT-TYPE
    SYNTAX      TruthValue
    MAX-ACCESS  read-only
    STATUS      current
    DESCRIPTION
        "The value of the object tmnxSysFpRAFltrInIpOpARedir indicates the
         operational of tmnxSysFpRAFltrInIpARedir."
    ::= { tmnxSysFpRAFltrIngIpActObjs 4 }

tmnxSysFpRAFltrInIpALog          OBJECT-TYPE
    SYNTAX      TruthValue
    MAX-ACCESS  read-write
    STATUS      current
    DESCRIPTION
        "The value of the object tmnxSysFpRAFltrInIpALog specifies whether
         filter policies referenced on ingress endpoints allow configuring
         logging for their entries."
    DEFVAL      { true }
    ::= { tmnxSysFpRAFltrIngIpActObjs 5 }

tmnxSysFpRAFltrInIpOpALog        OBJECT-TYPE
    SYNTAX      TruthValue
    MAX-ACCESS  read-only
    STATUS      current
    DESCRIPTION
        "The value of the object tmnxSysFpRAFltrInIpOpALog indicates the
         operational of tmnxSysFpRAFltrInIpALog."
    ::= { tmnxSysFpRAFltrIngIpActObjs 6 }

tmnxSysFpRAFltrInIpAMirror       OBJECT-TYPE
    SYNTAX      TruthValue
    MAX-ACCESS  read-write
    STATUS      current
    DESCRIPTION
        "The value of the object tmnxSysFpRAFltrInIpAMirror specifies whether
         filter policies referenced on ingress endpoints allow using their
         entries as mirror source."
    DEFVAL      { true }
    ::= { tmnxSysFpRAFltrIngIpActObjs 7 }

tmnxSysFpRAFltrInIpOpAMirror     OBJECT-TYPE
    SYNTAX      TruthValue
    MAX-ACCESS  read-only
    STATUS      current
    DESCRIPTION
        "The value of the object tmnxSysFpRAFltrInIpOpAMirror indicates the
         operational of tmnxSysFpRAFltrInIpAMirror."
    ::= { tmnxSysFpRAFltrIngIpActObjs 8 }

tmnxSysFpRAFltrInIpAFc           OBJECT-TYPE
    SYNTAX      TruthValue
    MAX-ACCESS  read-write
    STATUS      current
    DESCRIPTION
        "The value of the object tmnxSysFpRAFltrInIpAFc specifies whether
         filter policies referenced on ingress endpoints allow configuring
         action fc."
    DEFVAL      { true }
    ::= { tmnxSysFpRAFltrIngIpActObjs 9 }

tmnxSysFpRAFltrInIpOpAFc         OBJECT-TYPE
    SYNTAX      TruthValue
    MAX-ACCESS  read-only
    STATUS      current
    DESCRIPTION
        "The value of the object tmnxSysFpRAFltrInIpOpAFc indicates the
         operational of tmnxSysFpRAFltrInIpAFc."
    ::= { tmnxSysFpRAFltrIngIpActObjs 10 }

tmnxSysFpRAFltrInIpAStats        OBJECT-TYPE
    SYNTAX      TruthValue
    MAX-ACCESS  read-write
    STATUS      current
    DESCRIPTION
        "The value of the object tmnxSysFpRAFltrInIpAStats specifies whether
         filter policies referenced on ingress endpoints allow statistics
         collection for their entries."
    DEFVAL      { true }
    ::= { tmnxSysFpRAFltrIngIpActObjs 11 }

tmnxSysFpRAFltrInIpOpAStats      OBJECT-TYPE
    SYNTAX      TruthValue
    MAX-ACCESS  read-only
    STATUS      current
    DESCRIPTION
        "The value of the object tmnxSysFpRAFltrInIpOpAStats indicates the
         operational of tmnxSysFpRAFltrInIpAStats."
    ::= { tmnxSysFpRAFltrIngIpActObjs 12 }

tmnxSysFpRAFltrIngIpv6MatchObjs  OBJECT IDENTIFIER ::= { tmnxSySpRAFltrIngObjects 3 }

tmnxSysFpRAFltrInIpv6MSrcIpMsb   OBJECT-TYPE
    SYNTAX      TruthValue
    MAX-ACCESS  read-write
    STATUS      current
    DESCRIPTION
        "The value of the object tmnxSysFpRAFltrInIpv6MSrcIpMsb specifies
         whether filter policies referenced on ingress endpoints allow
         configuring source IP address as their match criterion."
    DEFVAL      { true }
    ::= { tmnxSysFpRAFltrIngIpv6MatchObjs 1 }

tmnxSysFpRAFltrInIpv6OpMSrcIpMsb OBJECT-TYPE
    SYNTAX      TruthValue
    MAX-ACCESS  read-only
    STATUS      current
    DESCRIPTION
        "The value of the object tmnxSysFpRAFltrInIpv6OpMSrcIpMsb indicates the
         operational of tmnxSysFpRAFltrInIpv6MSrcIpMsb."
    ::= { tmnxSysFpRAFltrIngIpv6MatchObjs 2 }

tmnxSysFpRAFltrInIpv6MSrcIpLsb   OBJECT-TYPE
    SYNTAX      TruthValue
    MAX-ACCESS  read-write
    STATUS      current
    DESCRIPTION
        "The value of the object tmnxSysFpRAFltrInIpv6MSrcIpLsb specifies
         whether filter policies referenced on ingress endpoints allow
         configuring source IP address as their match criterion."
    DEFVAL      { true }
    ::= { tmnxSysFpRAFltrIngIpv6MatchObjs 3 }

tmnxSysFpRAFltrInIpv6OpMSrcIpLsb OBJECT-TYPE
    SYNTAX      TruthValue
    MAX-ACCESS  read-only
    STATUS      current
    DESCRIPTION
        "The value of the object tmnxSysFpRAFltrInIpv6OpMSrcIpLsb indicates the
         operational of tmnxSysFpRAFltrInIpv6MSrcIpLsb."
    ::= { tmnxSysFpRAFltrIngIpv6MatchObjs 4 }

tmnxSysFpRAFltrInIpv6MDstIpMsb   OBJECT-TYPE
    SYNTAX      TruthValue
    MAX-ACCESS  read-write
    STATUS      current
    DESCRIPTION
        "The value of the object tmnxSysFpRAFltrInIpv6MDstIpMsb specifies
         whether filter policies referenced on ingress endpoints allow
         configuring destination IP address as their match criterion."
    DEFVAL      { true }
    ::= { tmnxSysFpRAFltrIngIpv6MatchObjs 5 }

tmnxSysFpRAFltrInIpv6OpMDstIpMsb OBJECT-TYPE
    SYNTAX      TruthValue
    MAX-ACCESS  read-only
    STATUS      current
    DESCRIPTION
        "The value of the object tmnxSysFpRAFltrInIpv6OpMDstIpMsb indicates the
         operational of tmnxSysFpRAFltrInIpv6MDstIpMsb."
    ::= { tmnxSysFpRAFltrIngIpv6MatchObjs 6 }

tmnxSysFpRAFltrInIpv6MDstIpLsb   OBJECT-TYPE
    SYNTAX      TruthValue
    MAX-ACCESS  read-write
    STATUS      current
    DESCRIPTION
        "The value of the object tmnxSysFpRAFltrInIpv6MDstIpLsb specifies
         whether filter policies referenced on ingress endpoints allow
         configuring destination IP address as their match criterion."
    DEFVAL      { false }
    ::= { tmnxSysFpRAFltrIngIpv6MatchObjs 7 }

tmnxSysFpRAFltrInIpv6OpMDstIpLsb OBJECT-TYPE
    SYNTAX      TruthValue
    MAX-ACCESS  read-only
    STATUS      current
    DESCRIPTION
        "The value of the object tmnxSysFpRAFltrInIpv6OpMDstIpLsb indicates the
         operational of tmnxSysFpRAFltrInIpv6MDstIpLsb."
    ::= { tmnxSysFpRAFltrIngIpv6MatchObjs 8 }

tmnxSysFpRAFltrInIpv6MSrcPort    OBJECT-TYPE
    SYNTAX      TruthValue
    MAX-ACCESS  read-write
    STATUS      current
    DESCRIPTION
        "The value of the object tmnxSysFpRAFltrInIpv6MSrcPort specifies
         whether filter policies referenced on ingress endpoints allow
         configuring L4 source port as their match criterion."
    DEFVAL      { true }
    ::= { tmnxSysFpRAFltrIngIpv6MatchObjs 9 }

tmnxSysFpRAFltrInIpv6OpMSrcPort  OBJECT-TYPE
    SYNTAX      TruthValue
    MAX-ACCESS  read-only
    STATUS      current
    DESCRIPTION
        "The value of the object tmnxSysFpRAFltrInIpv6OpMSrcPort indicates the
         operational of tmnxSysFpRAFltrInIpv6MSrcPort."
    ::= { tmnxSysFpRAFltrIngIpv6MatchObjs 10 }

tmnxSysFpRAFltrInIpv6MDstPort    OBJECT-TYPE
    SYNTAX      TruthValue
    MAX-ACCESS  read-write
    STATUS      current
    DESCRIPTION
        "The value of the object tmnxSysFpRAFltrInIpv6MDstPort specifies
         whether filter policies referenced on ingress endpoints allow
         configuring L4 destination port as their match criterion."
    DEFVAL      { true }
    ::= { tmnxSysFpRAFltrIngIpv6MatchObjs 11 }

tmnxSysFpRAFltrInIpv6OpMDstPort  OBJECT-TYPE
    SYNTAX      TruthValue
    MAX-ACCESS  read-only
    STATUS      current
    DESCRIPTION
        "The value of the object tmnxSysFpRAFltrInIpv6OpMDstPort indicates the
         operational of tmnxSysFpRAFltrInIpv6MDstPort."
    ::= { tmnxSysFpRAFltrIngIpv6MatchObjs 12 }

tmnxSysFpRAFltrInIpv6MNextHdr    OBJECT-TYPE
    SYNTAX      TruthValue
    MAX-ACCESS  read-write
    STATUS      current
    DESCRIPTION
        "The value of the object tmnxSysFpRAFltrInIpv6MNextHdr specifies
         whether filter policies referenced on ingress endpoints allow
         configuring IP protocol as their match criterion."
    DEFVAL      { true }
    ::= { tmnxSysFpRAFltrIngIpv6MatchObjs 13 }

tmnxSysFpRAFltrInIpv6OpMNextHdr  OBJECT-TYPE
    SYNTAX      TruthValue
    MAX-ACCESS  read-only
    STATUS      current
    DESCRIPTION
        "The value of the object tmnxSysFpRAFltrInIpv6OpMNextHdr indicates the
         operational of tmnxSysFpRAFltrInIpv6MNextHdr."
    ::= { tmnxSysFpRAFltrIngIpv6MatchObjs 14 }

tmnxSysFpRAFltrInIpv6MTcpFlgs    OBJECT-TYPE
    SYNTAX      TruthValue
    MAX-ACCESS  read-write
    STATUS      current
    DESCRIPTION
        "The value of the object tmnxSysFpRAFltrInIpv6MTcpFlgs specifies
         whether filter policies referenced on ingress endpoints allow
         configuring TCP flags as their match criterion."
    DEFVAL      { true }
    ::= { tmnxSysFpRAFltrIngIpv6MatchObjs 15 }

tmnxSysFpRAFltrInIpv6OpMTcpFlgs  OBJECT-TYPE
    SYNTAX      TruthValue
    MAX-ACCESS  read-only
    STATUS      current
    DESCRIPTION
        "The value of the object tmnxSysFpRAFltrInIpv6OpMTcpFlgs indicates the
         operational of tmnxSysFpRAFltrInIpv6MTcpFlgs."
    ::= { tmnxSysFpRAFltrIngIpv6MatchObjs 16 }

tmnxSysFpRAFltrInIpv6MDscp       OBJECT-TYPE
    SYNTAX      TruthValue
    MAX-ACCESS  read-write
    STATUS      current
    DESCRIPTION
        "The value of the object tmnxSysFpRAFltrInIpv6MDscp specifies whether
         filter policies referenced on ingress endpoints allow configuring DSCP
         as their match criterion."
    DEFVAL      { true }
    ::= { tmnxSysFpRAFltrIngIpv6MatchObjs 17 }

tmnxSysFpRAFltrInIpv6OpMDscp     OBJECT-TYPE
    SYNTAX      TruthValue
    MAX-ACCESS  read-only
    STATUS      current
    DESCRIPTION
        "The value of the object tmnxSysFpRAFltrInIpv6OpMDscp indicates the
         operational of tmnxSysFpRAFltrInIpv6MDscp."
    ::= { tmnxSysFpRAFltrIngIpv6MatchObjs 18 }

tmnxSysFpRAFltrInIpv6MFLabel     OBJECT-TYPE
    SYNTAX      TruthValue
    MAX-ACCESS  read-write
    STATUS      current
    DESCRIPTION
        "The value of the object tmnxSysFpRAFltrInIpv6MFLabel specifies whether
         filter policies referenced on ingress endpoints allow configuring
         flow-label as their match criterion."
    DEFVAL      { false }
    ::= { tmnxSysFpRAFltrIngIpv6MatchObjs 19 }

tmnxSysFpRAFltrInIpv6OpMFLabel   OBJECT-TYPE
    SYNTAX      TruthValue
    MAX-ACCESS  read-only
    STATUS      current
    DESCRIPTION
        "The value of the object tmnxSysFpRAFltrInIpv6OpMFLabel indicates the
         operational of tmnxSysFpRAFltrInIpv6MFLabel."
    ::= { tmnxSysFpRAFltrIngIpv6MatchObjs 20 }

tmnxSysFpRAFltrInIpv6MIcmpCode   OBJECT-TYPE
    SYNTAX      TruthValue
    MAX-ACCESS  read-write
    STATUS      current
    DESCRIPTION
        "The value of the object tmnxSysFpRAFltrInIpv6MIcmpCode specifies
         whether filter policies referenced on ingress endpoints allow
         configuring ICMP code as their match criterion."
    DEFVAL      { false }
    ::= { tmnxSysFpRAFltrIngIpv6MatchObjs 21 }

tmnxSysFpRAFltrInIpv6OpMIcmpCode OBJECT-TYPE
    SYNTAX      TruthValue
    MAX-ACCESS  read-only
    STATUS      current
    DESCRIPTION
        "The value of the object tmnxSysFpRAFltrInIpv6OpMIcmpCode indicates the
         operational of tmnxSysFpRAFltrInIpv6MIcmpCode."
    ::= { tmnxSysFpRAFltrIngIpv6MatchObjs 22 }

tmnxSysFpRAFltrInIpv6MIcmpType   OBJECT-TYPE
    SYNTAX      TruthValue
    MAX-ACCESS  read-write
    STATUS      current
    DESCRIPTION
        "The value of the object tmnxSysFpRAFltrInIpv6MIcmpType specifies
         whether filter policies referenced on ingress endpoints allow
         configuring ICMP type as their match criterion."
    DEFVAL      { false }
    ::= { tmnxSysFpRAFltrIngIpv6MatchObjs 23 }

tmnxSysFpRAFltrInIpv6OpMIcmpType OBJECT-TYPE
    SYNTAX      TruthValue
    MAX-ACCESS  read-only
    STATUS      current
    DESCRIPTION
        "The value of the object tmnxSysFpRAFltrInIpv6OpMIcmpType indicates the
         operational of tmnxSysFpRAFltrInIpv6MIcmpType."
    ::= { tmnxSysFpRAFltrIngIpv6MatchObjs 24 }

tmnxSysFpRAFltrInIpv6MTcpFlExt   OBJECT-TYPE
    SYNTAX      TruthValue
    MAX-ACCESS  read-write
    STATUS      current
    DESCRIPTION
        "The value of the object tmnxSysFpRAFltrInIpv6MTcpFlExt specifies
         whether filter policies referenced on ingress endpoints allow
         configuring TCP flags for explicit congestion notification as their
         match criterion."
    DEFVAL      { false }
    ::= { tmnxSysFpRAFltrIngIpv6MatchObjs 25 }

tmnxSysFpRAFltrInIpv6OpMTcpFlExt OBJECT-TYPE
    SYNTAX      TruthValue
    MAX-ACCESS  read-only
    STATUS      current
    DESCRIPTION
        "The value of the object tmnxSysFpRAFltrInIpv6OpMTcpFlExt indicates the
         operational of tmnxSysFpRAFltrInIpv6MTcpFlExt."
    ::= { tmnxSysFpRAFltrIngIpv6MatchObjs 26 }

tmnxSysFpRAFltrIngIpv6ActObjs    OBJECT IDENTIFIER ::= { tmnxSySpRAFltrIngObjects 4 }

tmnxSysFpRAFltrInIpv6ADrop       OBJECT-TYPE
    SYNTAX      TruthValue
    MAX-ACCESS  read-write
    STATUS      current
    DESCRIPTION
        "The value of the object tmnxSysFpRAFltrInIpv6ADrop specifies whether
         filter policies referenced on ingress endpoints allow configuring
         action drop."
    DEFVAL      { true }
    ::= { tmnxSysFpRAFltrIngIpv6ActObjs 1 }

tmnxSysFpRAFltrInIpv6OpADrop     OBJECT-TYPE
    SYNTAX      TruthValue
    MAX-ACCESS  read-only
    STATUS      current
    DESCRIPTION
        "The value of the object tmnxSysFpRAFltrInIpv6OpADrop indicates the
         operational of tmnxSysFpRAFltrInIpv6ADrop."
    ::= { tmnxSysFpRAFltrIngIpv6ActObjs 2 }

tmnxSysFpRAFltrInIpv6ARedir      OBJECT-TYPE
    SYNTAX      TruthValue
    MAX-ACCESS  read-write
    STATUS      current
    DESCRIPTION
        "The value of the object tmnxSysFpRAFltrInIpv6ARedir specifies whether
         filter policies referenced on ingress endpoints allow configuring
         actions redirecting traffic."
    DEFVAL      { true }
    ::= { tmnxSysFpRAFltrIngIpv6ActObjs 3 }

tmnxSysFpRAFltrInIpv6OpARedir    OBJECT-TYPE
    SYNTAX      TruthValue
    MAX-ACCESS  read-only
    STATUS      current
    DESCRIPTION
        "The value of the object tmnxSysFpRAFltrInIpv6OpARedir indicates the
         operational of tmnxSysFpRAFltrInIpv6ARedir."
    ::= { tmnxSysFpRAFltrIngIpv6ActObjs 4 }

tmnxSysFpRAFltrInIpv6ALog        OBJECT-TYPE
    SYNTAX      TruthValue
    MAX-ACCESS  read-write
    STATUS      current
    DESCRIPTION
        "The value of the object tmnxSysFpRAFltrInIpv6ALog specifies whether
         filter policies referenced on ingress endpoints allow configuring
         logging for their entries."
    DEFVAL      { true }
    ::= { tmnxSysFpRAFltrIngIpv6ActObjs 5 }

tmnxSysFpRAFltrInIpv6OpALog      OBJECT-TYPE
    SYNTAX      TruthValue
    MAX-ACCESS  read-only
    STATUS      current
    DESCRIPTION
        "The value of the object tmnxSysFpRAFltrInIpv6OpALog indicates the
         operational of tmnxSysFpRAFltrInIpv6ALog."
    ::= { tmnxSysFpRAFltrIngIpv6ActObjs 6 }

tmnxSysFpRAFltrInIpv6AMirror     OBJECT-TYPE
    SYNTAX      TruthValue
    MAX-ACCESS  read-write
    STATUS      current
    DESCRIPTION
        "The value of the object tmnxSysFpRAFltrInIpv6AMirror specifies whether
         filter policies referenced on ingress endpoints allow using their
         entries as mirror source."
    DEFVAL      { true }
    ::= { tmnxSysFpRAFltrIngIpv6ActObjs 7 }

tmnxSysFpRAFltrInIpv6OpAMirror   OBJECT-TYPE
    SYNTAX      TruthValue
    MAX-ACCESS  read-only
    STATUS      current
    DESCRIPTION
        "The value of the object tmnxSysFpRAFltrInIpv6OpAMirror indicates the
         operational of tmnxSysFpRAFltrInIpv6AMirror."
    ::= { tmnxSysFpRAFltrIngIpv6ActObjs 8 }

tmnxSysFpRAFltrInIpv6AFc         OBJECT-TYPE
    SYNTAX      TruthValue
    MAX-ACCESS  read-write
    STATUS      current
    DESCRIPTION
        "The value of the object tmnxSysFpRAFltrInIpv6AFc specifies whether
         filter policies referenced on ingress endpoints allow configuring
         action fc."
    DEFVAL      { true }
    ::= { tmnxSysFpRAFltrIngIpv6ActObjs 9 }

tmnxSysFpRAFltrInIpv6OpAFc       OBJECT-TYPE
    SYNTAX      TruthValue
    MAX-ACCESS  read-only
    STATUS      current
    DESCRIPTION
        "The value of the object tmnxSysFpRAFltrInIpv6OpAFc indicates the
         operational of tmnxSysFpRAFltrInIpv6AFc."
    ::= { tmnxSysFpRAFltrIngIpv6ActObjs 10 }

tmnxSysFpRAFltrInIpv6AStats      OBJECT-TYPE
    SYNTAX      TruthValue
    MAX-ACCESS  read-write
    STATUS      current
    DESCRIPTION
        "The value of the object tmnxSysFpRAFltrInIpv6AStats specifies whether
         filter policies referenced on ingress endpoints allow statistics
         collection for their entries."
    DEFVAL      { true }
    ::= { tmnxSysFpRAFltrIngIpv6ActObjs 11 }

tmnxSysFpRAFltrInIpv6OpAStats    OBJECT-TYPE
    SYNTAX      TruthValue
    MAX-ACCESS  read-only
    STATUS      current
    DESCRIPTION
        "The value of the object tmnxSysFpRAFltrInIpv6OpAStats indicates the
         operational of tmnxSysFpRAFltrInIpv6AStats."
    ::= { tmnxSysFpRAFltrIngIpv6ActObjs 12 }

tmnxSySpRAFltrEgrObjects         OBJECT IDENTIFIER ::= { tmnxSySFpRAFltrObjects 2 }

tmnxSysFpRAFltrEgrIpMatchObjs    OBJECT IDENTIFIER ::= { tmnxSySpRAFltrEgrObjects 1 }

tmnxSysFpRAFltrEgIpMSrcIp        OBJECT-TYPE
    SYNTAX      TruthValue
    MAX-ACCESS  read-write
    STATUS      current
    DESCRIPTION
        "The value of the object tmnxSysFpRAFltrEgIpMSrcIp specifies whether
         filter policies referenced on egress endpoints allow configuring
         source IP address as their match criterion."
    DEFVAL      { true }
    ::= { tmnxSysFpRAFltrEgrIpMatchObjs 1 }

tmnxSysFpRAFltrEgIpOpMSrcIp      OBJECT-TYPE
    SYNTAX      TruthValue
    MAX-ACCESS  read-only
    STATUS      current
    DESCRIPTION
        "The value of the object tmnxSysFpRAFltrEgIpOpMSrcIp indicates the
         operational state of tmnxSysFpRAFltrEgIpMSrcIp."
    ::= { tmnxSysFpRAFltrEgrIpMatchObjs 2 }

tmnxSysFpRAFltrEgIpMDstIp        OBJECT-TYPE
    SYNTAX      TruthValue
    MAX-ACCESS  read-write
    STATUS      current
    DESCRIPTION
        "The value of the object tmnxSysFpRAFltrEgIpMDstIp specifies whether
         filter policies referenced on egress endpoints allow configuring
         destination IP address as their match criterion."
    DEFVAL      { true }
    ::= { tmnxSysFpRAFltrEgrIpMatchObjs 3 }

tmnxSysFpRAFltrEgIpOpMDstIp      OBJECT-TYPE
    SYNTAX      TruthValue
    MAX-ACCESS  read-only
    STATUS      current
    DESCRIPTION
        "The value of the object tmnxSysFpRAFltrEgIpOpMDstIp indicates the
         operational state of tmnxSysFpRAFltrEgIpMDstIp."
    ::= { tmnxSysFpRAFltrEgrIpMatchObjs 4 }

tmnxSysFpRAFltrEgIpMSrcPort      OBJECT-TYPE
    SYNTAX      TruthValue
    MAX-ACCESS  read-write
    STATUS      current
    DESCRIPTION
        "The value of the object tmnxSysFpRAFltrEgIpMSrcPort specifies whether
         filter policies referenced on egress endpoints allow configuring L4
         source port as their match criterion."
    DEFVAL      { true }
    ::= { tmnxSysFpRAFltrEgrIpMatchObjs 5 }

tmnxSysFpRAFltrEgIpOpMSrcPort    OBJECT-TYPE
    SYNTAX      TruthValue
    MAX-ACCESS  read-only
    STATUS      current
    DESCRIPTION
        "The value of the object tmnxSysFpRAFltrEgIpOpMSrcPort indicates the
         operational state of tmnxSysFpRAFltrEgIpMSrcPort."
    ::= { tmnxSysFpRAFltrEgrIpMatchObjs 6 }

tmnxSysFpRAFltrEgIpMDstPort      OBJECT-TYPE
    SYNTAX      TruthValue
    MAX-ACCESS  read-write
    STATUS      current
    DESCRIPTION
        "The value of the object tmnxSysFpRAFltrEgIpMDstPort specifies whether
         filter policies referenced on egress endpoints allow configuring L4
         destination port as their match criterion."
    DEFVAL      { true }
    ::= { tmnxSysFpRAFltrEgrIpMatchObjs 7 }

tmnxSysFpRAFltrEgIpOpMDstPort    OBJECT-TYPE
    SYNTAX      TruthValue
    MAX-ACCESS  read-only
    STATUS      current
    DESCRIPTION
        "The value of the object tmnxSysFpRAFltrEgIpOpMDstPort indicates the
         operational state of tmnxSysFpRAFltrEgIpMDstPort."
    ::= { tmnxSysFpRAFltrEgrIpMatchObjs 8 }

tmnxSysFpRAFltrEgIpMProt         OBJECT-TYPE
    SYNTAX      TruthValue
    MAX-ACCESS  read-write
    STATUS      current
    DESCRIPTION
        "The value of the object tmnxSysFpRAFltrEgIpMProt specifies whether
         filter policies referenced on egress endpoints allow configuring IP
         protocol as their match criterion."
    DEFVAL      { true }
    ::= { tmnxSysFpRAFltrEgrIpMatchObjs 9 }

tmnxSysFpRAFltrEgIpOpMProt       OBJECT-TYPE
    SYNTAX      TruthValue
    MAX-ACCESS  read-only
    STATUS      current
    DESCRIPTION
        "The value of the object tmnxSysFpRAFltrEgIpOpMProt indicates the
         operational state of tmnxSysFpRAFltrEgIpMProt."
    ::= { tmnxSysFpRAFltrEgrIpMatchObjs 10 }

tmnxSysFpRAFltrEgIpMTcpFlgs      OBJECT-TYPE
    SYNTAX      TruthValue
    MAX-ACCESS  read-write
    STATUS      current
    DESCRIPTION
        "The value of the object tmnxSysFpRAFltrEgIpMTcpFlgs specifies whether
         filter policies referenced on egress endpoints allow configuring TCP
         flags as their match criterion."
    DEFVAL      { true }
    ::= { tmnxSysFpRAFltrEgrIpMatchObjs 11 }

tmnxSysFpRAFltrEgIpOpMTcpFlgs    OBJECT-TYPE
    SYNTAX      TruthValue
    MAX-ACCESS  read-only
    STATUS      current
    DESCRIPTION
        "The value of the object tmnxSysFpRAFltrEgIpOpMTcpFlgs indicates the
         operational state of tmnxSysFpRAFltrEgIpMTcpFlgs."
    ::= { tmnxSysFpRAFltrEgrIpMatchObjs 12 }

tmnxSysFpRAFltrEgIpMDscp         OBJECT-TYPE
    SYNTAX      TruthValue
    MAX-ACCESS  read-write
    STATUS      current
    DESCRIPTION
        "The value of the object tmnxSysFpRAFltrEgIpMDscp specifies whether
         filter policies referenced on egress endpoints allow configuring DSCP
         as their match criterion."
    DEFVAL      { true }
    ::= { tmnxSysFpRAFltrEgrIpMatchObjs 13 }

tmnxSysFpRAFltrEgIpOpMDscp       OBJECT-TYPE
    SYNTAX      TruthValue
    MAX-ACCESS  read-only
    STATUS      current
    DESCRIPTION
        "The value of the object tmnxSysFpRAFltrEgIpOpMDscp indicates the
         operational state of tmnxSysFpRAFltrEgIpMDscp."
    ::= { tmnxSysFpRAFltrEgrIpMatchObjs 14 }

tmnxSysFpRAFltrEgIpMIcmpCode     OBJECT-TYPE
    SYNTAX      TruthValue
    MAX-ACCESS  read-write
    STATUS      current
    DESCRIPTION
        "The value of the object tmnxSysFpRAFltrEgIpMIcmpCode specifies whether
         filter policies referenced on egress endpoints allow configuring ICMP
         code as their match criterion."
    DEFVAL      { false }
    ::= { tmnxSysFpRAFltrEgrIpMatchObjs 15 }

tmnxSysFpRAFltrEgIpOpMIcmpCode   OBJECT-TYPE
    SYNTAX      TruthValue
    MAX-ACCESS  read-only
    STATUS      current
    DESCRIPTION
        "The value of the object tmnxSysFpRAFltrEgIpOpMIcmpCode indicates the
         operational of tmnxSysFpRAFltrEgIpMIcmpCode."
    ::= { tmnxSysFpRAFltrEgrIpMatchObjs 16 }

tmnxSysFpRAFltrEgIpMIcmpType     OBJECT-TYPE
    SYNTAX      TruthValue
    MAX-ACCESS  read-write
    STATUS      current
    DESCRIPTION
        "The value of the object tmnxSysFpRAFltrEgIpMIcmpType specifies whether
         filter policies referenced on egress endpoints allow configuring ICMP
         type as their match criterion."
    DEFVAL      { false }
    ::= { tmnxSysFpRAFltrEgrIpMatchObjs 17 }

tmnxSysFpRAFltrEgIpOpMIcmpType   OBJECT-TYPE
    SYNTAX      TruthValue
    MAX-ACCESS  read-only
    STATUS      current
    DESCRIPTION
        "The value of the object tmnxSysFpRAFltrEgIpOpMIcmpType indicates the
         operational of tmnxSysFpRAFltrEgIpMIcmpType."
    ::= { tmnxSysFpRAFltrEgrIpMatchObjs 18 }

tmnxSysFpRAFltrEgIpMTcpFlExt     OBJECT-TYPE
    SYNTAX      TruthValue
    MAX-ACCESS  read-write
    STATUS      current
    DESCRIPTION
        "The value of the object tmnxSysFpRAFltrEgIpMTcpFlExt specifies whether
         filter policies referenced on egress endpoints allow configuring TCP
         flags for explicit congestion notification as their match criterion."
    DEFVAL      { false }
    ::= { tmnxSysFpRAFltrEgrIpMatchObjs 19 }

tmnxSysFpRAFltrEgIpOpMTcpFlExt   OBJECT-TYPE
    SYNTAX      TruthValue
    MAX-ACCESS  read-only
    STATUS      current
    DESCRIPTION
        "The value of the object tmnxSysFpRAFltrEgIpOpMTcpFlExt indicates the
         operational of tmnxSysFpRAFltrEgIpMTcpFlExt."
    ::= { tmnxSysFpRAFltrEgrIpMatchObjs 20 }

tmnxSysFpRAFltrEgrIpActObjs      OBJECT IDENTIFIER ::= { tmnxSySpRAFltrEgrObjects 2 }

tmnxSysFpRAFltrEgIpADrop         OBJECT-TYPE
    SYNTAX      TruthValue
    MAX-ACCESS  read-write
    STATUS      current
    DESCRIPTION
        "The value of the object tmnxSysFpRAFltrEgIpADrop specifies whether
         filter policies referenced on egress endpoints allow configuring
         action drop."
    DEFVAL      { true }
    ::= { tmnxSysFpRAFltrEgrIpActObjs 1 }

tmnxSysFpRAFltrEgIpOpADrop       OBJECT-TYPE
    SYNTAX      TruthValue
    MAX-ACCESS  read-only
    STATUS      current
    DESCRIPTION
        "The value of the object tmnxSysFpRAFltrEgIpOpADrop indicates the
         operational state of tmnxSysFpRAFltrEgIpADrop."
    ::= { tmnxSysFpRAFltrEgrIpActObjs 2 }

tmnxSysFpRAFltrEgIpAStats        OBJECT-TYPE
    SYNTAX      TruthValue
    MAX-ACCESS  read-write
    STATUS      current
    DESCRIPTION
        "The value of the object tmnxSysFpRAFltrEgIpAStats specifies whether
         filter policies referenced on egress endpoints allow statistics
         collection for their entries."
    DEFVAL      { true }
    ::= { tmnxSysFpRAFltrEgrIpActObjs 3 }

tmnxSysFpRAFltrEgIpOpAStats      OBJECT-TYPE
    SYNTAX      TruthValue
    MAX-ACCESS  read-only
    STATUS      current
    DESCRIPTION
        "The value of the object tmnxSysFpRAFltrEgIpOpAStats indicates the
         operational state of tmnxSysFpRAFltrEgIpAStats."
    ::= { tmnxSysFpRAFltrEgrIpActObjs 4 }

tmnxSysFpRAFltrEgrIpv6MatchObjs  OBJECT IDENTIFIER ::= { tmnxSySpRAFltrEgrObjects 3 }

tmnxSysFpRAFltrEgIpv6MSrcIpMsb   OBJECT-TYPE
    SYNTAX      TruthValue
    MAX-ACCESS  read-write
    STATUS      current
    DESCRIPTION
        "The value of the object tmnxSysFpRAFltrEgIpv6MSrcIpMsb specifies
         whether filter policies referenced on egress endpoints allow
         configuring source IP address as their match criterion."
    DEFVAL      { true }
    ::= { tmnxSysFpRAFltrEgrIpv6MatchObjs 1 }

tmnxSysFpRAFltrEgIpv6OpMSrcIpMsb OBJECT-TYPE
    SYNTAX      TruthValue
    MAX-ACCESS  read-only
    STATUS      current
    DESCRIPTION
        "The value of the object tmnxSysFpRAFltrEgIpv6OpMSrcIpMsb indicates the
         operational state of tmnxSysFpRAFltrEgIpv6MSrcIpMsb."
    ::= { tmnxSysFpRAFltrEgrIpv6MatchObjs 2 }

tmnxSysFpRAFltrEgIpv6MSrcIpLsb   OBJECT-TYPE
    SYNTAX      TruthValue
    MAX-ACCESS  read-write
    STATUS      current
    DESCRIPTION
        "The value of the object tmnxSysFpRAFltrEgIpv6MSrcIpLsb specifies
         whether filter policies referenced on egress endpoints allow
         configuring source IP address as their match criterion."
    DEFVAL      { true }
    ::= { tmnxSysFpRAFltrEgrIpv6MatchObjs 3 }

tmnxSysFpRAFltrEgIpv6OpMSrcIpLsb OBJECT-TYPE
    SYNTAX      TruthValue
    MAX-ACCESS  read-only
    STATUS      current
    DESCRIPTION
        "The value of the object tmnxSysFpRAFltrEgIpv6OpMSrcIpLsb indicates the
         operational state of tmnxSysFpRAFltrEgIpv6MSrcIpLsb."
    ::= { tmnxSysFpRAFltrEgrIpv6MatchObjs 4 }

tmnxSysFpRAFltrEgIpv6MDstIpMsb   OBJECT-TYPE
    SYNTAX      TruthValue
    MAX-ACCESS  read-write
    STATUS      current
    DESCRIPTION
        "The value of the object tmnxSysFpRAFltrEgIpv6MDstIpMsb specifies
         whether filter policies referenced on egress endpoints allow
         configuring destination IP address as their match criterion."
    DEFVAL      { true }
    ::= { tmnxSysFpRAFltrEgrIpv6MatchObjs 5 }

tmnxSysFpRAFltrEgIpv6OpMDstIpMsb OBJECT-TYPE
    SYNTAX      TruthValue
    MAX-ACCESS  read-only
    STATUS      current
    DESCRIPTION
        "The value of the object tmnxSysFpRAFltrEgIpv6OpMDstIpMsb indicates the
         operational state of tmnxSysFpRAFltrEgIpv6MDstIpMsb."
    ::= { tmnxSysFpRAFltrEgrIpv6MatchObjs 6 }

tmnxSysFpRAFltrEgIpv6MDstIpLsb   OBJECT-TYPE
    SYNTAX      TruthValue
    MAX-ACCESS  read-write
    STATUS      current
    DESCRIPTION
        "The value of the object tmnxSysFpRAFltrEgIpv6MDstIpLsb specifies
         whether filter policies referenced on egress endpoints allow
         configuring destination IP address as their match criterion."
    DEFVAL      { false }
    ::= { tmnxSysFpRAFltrEgrIpv6MatchObjs 7 }

tmnxSysFpRAFltrEgIpv6OpMDstIpLsb OBJECT-TYPE
    SYNTAX      TruthValue
    MAX-ACCESS  read-only
    STATUS      current
    DESCRIPTION
        "The value of the object tmnxSysFpRAFltrEgIpv6OpMDstIpLsb indicates the
         operational state of tmnxSysFpRAFltrEgIpv6MDstIpLsb."
    ::= { tmnxSysFpRAFltrEgrIpv6MatchObjs 8 }

tmnxSysFpRAFltrEgIpv6MSrcPort    OBJECT-TYPE
    SYNTAX      TruthValue
    MAX-ACCESS  read-write
    STATUS      current
    DESCRIPTION
        "The value of the object tmnxSysFpRAFltrEgIpv6MSrcPort specifies
         whether filter policies referenced on egress endpoints allow
         configuring L4 source port as their match criterion."
    DEFVAL      { true }
    ::= { tmnxSysFpRAFltrEgrIpv6MatchObjs 9 }

tmnxSysFpRAFltrEgIpv6OpMSrcPort  OBJECT-TYPE
    SYNTAX      TruthValue
    MAX-ACCESS  read-only
    STATUS      current
    DESCRIPTION
        "The value of the object tmnxSysFpRAFltrEgIpv6OpMSrcPort indicates the
         operational state of tmnxSysFpRAFltrEgIpv6MSrcPort."
    ::= { tmnxSysFpRAFltrEgrIpv6MatchObjs 10 }

tmnxSysFpRAFltrEgIpv6MDstPort    OBJECT-TYPE
    SYNTAX      TruthValue
    MAX-ACCESS  read-write
    STATUS      current
    DESCRIPTION
        "The value of the object tmnxSysFpRAFltrEgIpv6MDstPort specifies
         whether filter policies referenced on egress endpoints allow
         configuring L4 destination port as their match criterion."
    DEFVAL      { true }
    ::= { tmnxSysFpRAFltrEgrIpv6MatchObjs 11 }

tmnxSysFpRAFltrEgIpv6OpMDstPort  OBJECT-TYPE
    SYNTAX      TruthValue
    MAX-ACCESS  read-only
    STATUS      current
    DESCRIPTION
        "The value of the object tmnxSysFpRAFltrEgIpv6OpMDstPort indicates the
         operational state of tmnxSysFpRAFltrEgIpv6MDstPort."
    ::= { tmnxSysFpRAFltrEgrIpv6MatchObjs 12 }

tmnxSysFpRAFltrEgIpv6MNextHdr    OBJECT-TYPE
    SYNTAX      TruthValue
    MAX-ACCESS  read-write
    STATUS      current
    DESCRIPTION
        "The value of the object tmnxSysFpRAFltrEgIpv6MNextHdr specifies
         whether filter policies referenced on egress endpoints allow
         configuring IP protocol as their match criterion."
    DEFVAL      { true }
    ::= { tmnxSysFpRAFltrEgrIpv6MatchObjs 13 }

tmnxSysFpRAFltrEgIpv6OpMNextHdr  OBJECT-TYPE
    SYNTAX      TruthValue
    MAX-ACCESS  read-only
    STATUS      current
    DESCRIPTION
        "The value of the object tmnxSysFpRAFltrEgIpv6OpMNextHdr indicates the
         operational state of tmnxSysFpRAFltrEgIpv6MNextHdr."
    ::= { tmnxSysFpRAFltrEgrIpv6MatchObjs 14 }

tmnxSysFpRAFltrEgIpv6MTcpFlgs    OBJECT-TYPE
    SYNTAX      TruthValue
    MAX-ACCESS  read-write
    STATUS      current
    DESCRIPTION
        "The value of the object tmnxSysFpRAFltrEgIpv6MTcpFlgs specifies
         whether filter policies referenced on egress endpoints allow
         configuring TCP flags as their match criterion."
    DEFVAL      { true }
    ::= { tmnxSysFpRAFltrEgrIpv6MatchObjs 15 }

tmnxSysFpRAFltrEgIpv6OpMTcpFlgs  OBJECT-TYPE
    SYNTAX      TruthValue
    MAX-ACCESS  read-only
    STATUS      current
    DESCRIPTION
        "The value of the object tmnxSysFpRAFltrEgIpv6OpMTcpFlgs indicates the
         operational state of tmnxSysFpRAFltrEgIpv6MTcpFlgs."
    ::= { tmnxSysFpRAFltrEgrIpv6MatchObjs 16 }

tmnxSysFpRAFltrEgIpv6MDscp       OBJECT-TYPE
    SYNTAX      TruthValue
    MAX-ACCESS  read-write
    STATUS      current
    DESCRIPTION
        "The value of the object tmnxSysFpRAFltrEgIpv6MDscp specifies whether
         filter policies referenced on egress endpoints allow configuring DSCP
         as their match criterion."
    DEFVAL      { true }
    ::= { tmnxSysFpRAFltrEgrIpv6MatchObjs 17 }

tmnxSysFpRAFltrEgIpv6OpMDscp     OBJECT-TYPE
    SYNTAX      TruthValue
    MAX-ACCESS  read-only
    STATUS      current
    DESCRIPTION
        "The value of the object tmnxSysFpRAFltrEgIpv6OpMDscp indicates the
         operational state of tmnxSysFpRAFltrEgIpv6MDscp."
    ::= { tmnxSysFpRAFltrEgrIpv6MatchObjs 18 }

tmnxSysFpRAFltrEgIpv6MFLabel     OBJECT-TYPE
    SYNTAX      TruthValue
    MAX-ACCESS  read-write
    STATUS      current
    DESCRIPTION
        "The value of the object tmnxSysFpRAFltrEgIpv6MFLabel specifies whether
         filter policies referenced on egress endpoints allow configuring
         flow-label as their match criterion."
    DEFVAL      { true }
    ::= { tmnxSysFpRAFltrEgrIpv6MatchObjs 19 }

tmnxSysFpRAFltrEgIpv6OpMFLabel   OBJECT-TYPE
    SYNTAX      TruthValue
    MAX-ACCESS  read-only
    STATUS      current
    DESCRIPTION
        "The value of the object tmnxSysFpRAFltrEgIpv6OpMFLabel indicates the
         operational state of tmnxSysFpRAFltrEgIpv6MFLabel."
    ::= { tmnxSysFpRAFltrEgrIpv6MatchObjs 20 }

tmnxSysFpRAFltrEgIpv6MIcmpCode   OBJECT-TYPE
    SYNTAX      TruthValue
    MAX-ACCESS  read-write
    STATUS      current
    DESCRIPTION
        "The value of the object tmnxSysFpRAFltrEgIpv6MIcmpCode specifies
         whether filter policies referenced on egress endpoints allow
         configuring ICMP code as their match criterion."
    DEFVAL      { false }
    ::= { tmnxSysFpRAFltrEgrIpv6MatchObjs 21 }

tmnxSysFpRAFltrEgIpv6OpMIcmpCode OBJECT-TYPE
    SYNTAX      TruthValue
    MAX-ACCESS  read-only
    STATUS      current
    DESCRIPTION
        "The value of the object tmnxSysFpRAFltrEgIpv6OpMIcmpCode indicates the
         operational of tmnxSysFpRAFltrEgIpv6MIcmpCode."
    ::= { tmnxSysFpRAFltrEgrIpv6MatchObjs 22 }

tmnxSysFpRAFltrEgIpv6MIcmpType   OBJECT-TYPE
    SYNTAX      TruthValue
    MAX-ACCESS  read-write
    STATUS      current
    DESCRIPTION
        "The value of the object tmnxSysFpRAFltrEgIpv6MIcmpType specifies
         whether filter policies referenced on egress endpoints allow
         configuring ICMP type as their match criterion."
    DEFVAL      { false }
    ::= { tmnxSysFpRAFltrEgrIpv6MatchObjs 23 }

tmnxSysFpRAFltrEgIpv6OpMIcmpType OBJECT-TYPE
    SYNTAX      TruthValue
    MAX-ACCESS  read-only
    STATUS      current
    DESCRIPTION
        "The value of the object tmnxSysFpRAFltrEgIpv6OpMIcmpType indicates the
         operational of tmnxSysFpRAFltrEgIpv6MIcmpType."
    ::= { tmnxSysFpRAFltrEgrIpv6MatchObjs 24 }

tmnxSysFpRAFltrEgIpv6MTcpFlExt   OBJECT-TYPE
    SYNTAX      TruthValue
    MAX-ACCESS  read-write
    STATUS      current
    DESCRIPTION
        "The value of the object tmnxSysFpRAFltrEgIpv6MTcpFlExt specifies
         whether filter policies referenced on egress endpoints allow
         configuring TCP flags for explicit congestion notification as their
         match criterion."
    DEFVAL      { false }
    ::= { tmnxSysFpRAFltrEgrIpv6MatchObjs 25 }

tmnxSysFpRAFltrEgIpv6OpMTcpFlExt OBJECT-TYPE
    SYNTAX      TruthValue
    MAX-ACCESS  read-only
    STATUS      current
    DESCRIPTION
        "The value of the object tmnxSysFpRAFltrEgIpv6OpMTcpFlExt indicates the
         operational of tmnxSysFpRAFltrEgIpv6MTcpFlExt."
    ::= { tmnxSysFpRAFltrEgrIpv6MatchObjs 26 }

tmnxSysFpRAFltrEgrIpv6ActObjs    OBJECT IDENTIFIER ::= { tmnxSySpRAFltrEgrObjects 4 }

tmnxSysFpRAFltrEgIpv6ADrop       OBJECT-TYPE
    SYNTAX      TruthValue
    MAX-ACCESS  read-write
    STATUS      current
    DESCRIPTION
        "The value of the object tmnxSysFpRAFltrEgIpv6ADrop specifies whether
         filter policies referenced on egress endpoints allow configuring
         action drop."
    DEFVAL      { true }
    ::= { tmnxSysFpRAFltrEgrIpv6ActObjs 1 }

tmnxSysFpRAFltrEgIpv6OpADrop     OBJECT-TYPE
    SYNTAX      TruthValue
    MAX-ACCESS  read-only
    STATUS      current
    DESCRIPTION
        "The value of the object tmnxSysFpRAFltrEgIpv6OpADrop indicates the
         operational state of tmnxSysFpRAFltrEgIpv6ADrop."
    ::= { tmnxSysFpRAFltrEgrIpv6ActObjs 2 }

tmnxSysFpRAFltrEgIpv6AStats      OBJECT-TYPE
    SYNTAX      TruthValue
    MAX-ACCESS  read-write
    STATUS      current
    DESCRIPTION
        "The value of the object tmnxSysFpRAFltrEgIpv6AStats specifies whether
         filter policies referenced on egress endpoints allow statistics
         collection for their entries."
    DEFVAL      { true }
    ::= { tmnxSysFpRAFltrEgrIpv6ActObjs 3 }

tmnxSysFpRAFltrEgIpv6OpAStats    OBJECT-TYPE
    SYNTAX      TruthValue
    MAX-ACCESS  read-only
    STATUS      current
    DESCRIPTION
        "The value of the object tmnxSysFpRAFltrEgIpv6OpAStats indicates the
         operational state of tmnxSysFpRAFltrEgIpv6AStats."
    ::= { tmnxSysFpRAFltrEgrIpv6ActObjs 4 }

tSysFpRAPsAppGrpTable            OBJECT-TYPE
    SYNTAX      SEQUENCE OF TSysFpRAPsAppGrpEntry
    MAX-ACCESS  not-accessible
    STATUS      current
    DESCRIPTION
        "The tSysFpRAPsAppGrpTable has an entry for every FP resource
         allocation Application group in the system."
    ::= { tmnxSysFpResAlloc 4 }

tSysFpRAPsAppGrpEntry            OBJECT-TYPE
    SYNTAX      TSysFpRAPsAppGrpEntry
    MAX-ACCESS  not-accessible
    STATUS      current
    DESCRIPTION
        "Each row represents a specific FP resource allocation application
         group in the system.

         Entries are automatically created by the system and cannot be created
         or deleted via SNMP SET operations."
    INDEX       { tSysFpRAPsAppGrpId }
    ::= { tSysFpRAPsAppGrpTable 1 }

TSysFpRAPsAppGrpEntry            ::= SEQUENCE
{
    tSysFpRAPsAppGrpId               Unsigned32,
    tSysFpRAPsAppGrpPlcrTotalAdmin   Unsigned32,
    tSysFpRAPsAppGrpPlcrTotalOper    Unsigned32,
    tSysFpRAPsAppGrpPlcrAllocAdmin   Unsigned32,
    tSysFpRAPsAppGrpPlcrAllocOper    Unsigned32,
    tSysFpRAPsAppGrpStatsTotalAdmin  Unsigned32,
    tSysFpRAPsAppGrpStatsTotalOper   Unsigned32,
    tSysFpRAPsAppGrpStatsAllocAdmin  Unsigned32,
    tSysFpRAPsAppGrpStatsAllocOper   Unsigned32
}

tSysFpRAPsAppGrpId               OBJECT-TYPE
    SYNTAX      Unsigned32 (1..3)
    MAX-ACCESS  not-accessible
    STATUS      current
    DESCRIPTION
        "The value of tSysFpRAPsAppGrpId specifies the FP resource allocation
         application group identifier."
    ::= { tSysFpRAPsAppGrpEntry 1 }

tSysFpRAPsAppGrpPlcrTotalAdmin   OBJECT-TYPE
    SYNTAX      Unsigned32
    MAX-ACCESS  read-only
    STATUS      current
    DESCRIPTION
        "The value of tSysFpRAPsAppGrpPlcrTotalAdmin represents the admin value
         of the total number of policers in the application group on this FP."
    ::= { tSysFpRAPsAppGrpEntry 2 }

tSysFpRAPsAppGrpPlcrTotalOper    OBJECT-TYPE
    SYNTAX      Unsigned32
    MAX-ACCESS  read-only
    STATUS      current
    DESCRIPTION
        "The value of tSysFpRAPsAppGrpPlcrTotalOper represents the oper value
         of the total number of policers in the application group on this FP."
    ::= { tSysFpRAPsAppGrpEntry 3 }

tSysFpRAPsAppGrpPlcrAllocAdmin   OBJECT-TYPE
    SYNTAX      Unsigned32
    MAX-ACCESS  read-only
    STATUS      current
    DESCRIPTION
        "The value of tSysFpRAPsAppGrpPlcrAllocAdmin represents the admin value
         of the allocated number of policers in the application group on this
         FP."
    ::= { tSysFpRAPsAppGrpEntry 4 }

tSysFpRAPsAppGrpPlcrAllocOper    OBJECT-TYPE
    SYNTAX      Unsigned32
    MAX-ACCESS  read-only
    STATUS      current
    DESCRIPTION
        "The value of tSysFpRAPsAppGrpPlcrAllocOper represents the oper value
         of the allocated number of policers in the application group on this
         FP."
    ::= { tSysFpRAPsAppGrpEntry 5 }

tSysFpRAPsAppGrpStatsTotalAdmin  OBJECT-TYPE
    SYNTAX      Unsigned32
    MAX-ACCESS  read-only
    STATUS      current
    DESCRIPTION
        "The value of tSysFpRAPsAppGrpStatsTotalAdmin represents the admin
         value of the total number of stats in the application group on this
         FP."
    ::= { tSysFpRAPsAppGrpEntry 6 }

tSysFpRAPsAppGrpStatsTotalOper   OBJECT-TYPE
    SYNTAX      Unsigned32
    MAX-ACCESS  read-only
    STATUS      current
    DESCRIPTION
        "The value of tSysFpRAPsAppGrpStatsTotalOper represents the oper value
         of the total number of stats in the application group on this FP."
    ::= { tSysFpRAPsAppGrpEntry 7 }

tSysFpRAPsAppGrpStatsAllocAdmin  OBJECT-TYPE
    SYNTAX      Unsigned32
    MAX-ACCESS  read-only
    STATUS      current
    DESCRIPTION
        "The value of tSysFpRAPsAppGrpStatsAllocAdmin represents the admin
         value of the allocated number of stats in the application group on
         this FP."
    ::= { tSysFpRAPsAppGrpEntry 8 }

tSysFpRAPsAppGrpStatsAllocOper   OBJECT-TYPE
    SYNTAX      Unsigned32
    MAX-ACCESS  read-only
    STATUS      current
    DESCRIPTION
        "The value of tSysFpRAPsAppGrpStatsAllocOper represents the oper value
         of the allocated number of stats in the application group on this FP."
    ::= { tSysFpRAPsAppGrpEntry 9 }

tSysFpRAPsBankTable              OBJECT-TYPE
    SYNTAX      SEQUENCE OF TSysFpRAPsBankEntry
    MAX-ACCESS  not-accessible
    STATUS      current
    DESCRIPTION
        "The tSysFpRAPsAppGrpTable has an entry for every FP resource
         allocation bank in the system."
    ::= { tmnxSysFpResAlloc 5 }

tSysFpRAPsBankEntry              OBJECT-TYPE
    SYNTAX      TSysFpRAPsBankEntry
    MAX-ACCESS  not-accessible
    STATUS      current
    DESCRIPTION
        "Each row represents a specific FP resource allocation application bank
         in the system.

         Entries are automatically created by the system and cannot be created
         or deleted via SNMP SET operations."
    INDEX       { tSysFpRAPsBankName }
    ::= { tSysFpRAPsBankTable 1 }

TSysFpRAPsBankEntry              ::= SEQUENCE
{
    tSysFpRAPsBankName               INTEGER,
    tSysFpRAPsBankBindingAdmin       INTEGER,
    tSysFpRAPsBankBindingOper        INTEGER,
    tSysFpRAPsBankAppGrpIdAdmin      Integer32,
    tSysFpRAPsBankAppGrpIdOper       Integer32
}

tSysFpRAPsBankName               OBJECT-TYPE
    SYNTAX      INTEGER {
        dualMode16kBank1 (1),
        dualMode16kBank2 (2),
        dualMode16kBank3 (3),
        dualMode16kBank4 (4),
        dualMode16kBank5 (5),
        dualMode16kBank6 (6)
    }
    MAX-ACCESS  not-accessible
    STATUS      current
    DESCRIPTION
        "The value of tSysFpRAPsBankName specifies the FP resource allocation
         application bank identifier. The name is system generated and user
         cannot change it."
    ::= { tSysFpRAPsBankEntry 1 }

tSysFpRAPsBankBindingAdmin       OBJECT-TYPE
    SYNTAX      INTEGER {
        none       (-1),
        policer    (1),
        statistics (2)
    }
    MAX-ACCESS  read-write
    STATUS      current
    DESCRIPTION
        "The value of tSysFpRAPsBankBindingAdmin represents the admin value of
         the binding done for the bank type. Any change to this value needs the
         user to reboot the system."
    DEFVAL      { none }
    ::= { tSysFpRAPsBankEntry 2 }

tSysFpRAPsBankBindingOper        OBJECT-TYPE
    SYNTAX      INTEGER {
        none       (-1),
        policer    (1),
        statistics (2)
    }
    MAX-ACCESS  read-only
    STATUS      current
    DESCRIPTION
        "The value of tSysFpRAPsBankBindingOper represents the oper value of
         the binding done for the bank type."
    ::= { tSysFpRAPsBankEntry 3 }

tSysFpRAPsBankAppGrpIdAdmin      OBJECT-TYPE
    SYNTAX      Integer32 (-1 | 1..3)
    MAX-ACCESS  read-write
    STATUS      current
    DESCRIPTION
        "The value of tSysFpRAPsBankAppGrpIdAdmin represents the admin value of
         the Group ID configured by the user for this bank."
    DEFVAL      { -1 }
    ::= { tSysFpRAPsBankEntry 4 }

tSysFpRAPsBankAppGrpIdOper       OBJECT-TYPE
    SYNTAX      Integer32 (-1 | 1..3)
    MAX-ACCESS  read-only
    STATUS      current
    DESCRIPTION
        "The value of tSysFpRAPsBankAppGrpIdOper represents the oper value of
         the Group ID configured by the user for this bank."
    ::= { tSysFpRAPsBankEntry 5 }

tSysFpRAPsPlcrAppTable           OBJECT-TYPE
    SYNTAX      SEQUENCE OF TSysFpRAPsPlcrAppEntry
    MAX-ACCESS  not-accessible
    STATUS      current
    DESCRIPTION
        "The tSysFpRAPsPlcrAppTable has an entry for every FP resource
         allocation Application in the system."
    ::= { tmnxSysFpResAlloc 6 }

tSysFpRAPsPlcrAppEntry           OBJECT-TYPE
    SYNTAX      TSysFpRAPsPlcrAppEntry
    MAX-ACCESS  not-accessible
    STATUS      current
    DESCRIPTION
        "Each row represents a specific FP resource allocation application
         group in the system."
    INDEX       {
        tSysFpRAPsPlcrAppGroupId,
        tSysFpRAPsPlcrAppId
    }
    ::= { tSysFpRAPsPlcrAppTable 1 }

TSysFpRAPsPlcrAppEntry           ::= SEQUENCE
{
    tSysFpRAPsPlcrAppGroupId         Unsigned32,
    tSysFpRAPsPlcrAppId              TmnxSysFpRAPsAppId,
    tSysFpRAPsPlcrScaleAdmin         Integer32,
    tSysFpRAPsPlcrScaleOper          Integer32
}

tSysFpRAPsPlcrAppGroupId         OBJECT-TYPE
    SYNTAX      Unsigned32 (1..3)
    MAX-ACCESS  not-accessible
    STATUS      current
    DESCRIPTION
        "The value of tSysFpRAPsPlcrAppGroupId specifies the FP resource
         allocation application group identifier."
    ::= { tSysFpRAPsPlcrAppEntry 1 }

tSysFpRAPsPlcrAppId              OBJECT-TYPE
    SYNTAX      TmnxSysFpRAPsAppId
    MAX-ACCESS  not-accessible
    STATUS      current
    DESCRIPTION
        "The value of tSysFpRAPsPlcrAppId specifies the Application type."
    ::= { tSysFpRAPsPlcrAppEntry 2 }

tSysFpRAPsPlcrScaleAdmin         OBJECT-TYPE
    SYNTAX      Integer32 (-1 | 0..96)
    MAX-ACCESS  read-write
    STATUS      current
    DESCRIPTION
        "The value of tSysFpRAPsPlcrScaleAdmin represents the admin value of
         the scale configured by the user for this policer application."
    DEFVAL      { -1 }
    ::= { tSysFpRAPsPlcrAppEntry 3 }

tSysFpRAPsPlcrScaleOper          OBJECT-TYPE
    SYNTAX      Integer32 (-1 | 0..96)
    MAX-ACCESS  read-only
    STATUS      current
    DESCRIPTION
        "The value of tSysFpRAPsPlcrScaleOper represents the oper value of the
         scale configured by the user for this policer application."
    DEFVAL      { -1 }
    ::= { tSysFpRAPsPlcrAppEntry 4 }

tSysFpRAPsStatsAppTable          OBJECT-TYPE
    SYNTAX      SEQUENCE OF TSysFpRAPsStatsAppEntry
    MAX-ACCESS  not-accessible
    STATUS      current
    DESCRIPTION
        "tSysFpRAPsStatsAppTable has an entry for each application that
         supports user configurable stats allocation."
    ::= { tmnxSysFpResAlloc 7 }

tSysFpRAPsStatsAppEntry          OBJECT-TYPE
    SYNTAX      TSysFpRAPsStatsAppEntry
    MAX-ACCESS  not-accessible
    STATUS      current
    DESCRIPTION
        "Each row represents an application. Entries cannot be created and
         deleted via SNMP SET operations."
    INDEX       {
        tSysFpRAPsStatsAppGroupId,
        tSysFpRAPsStatsAppId
    }
    ::= { tSysFpRAPsStatsAppTable 1 }

TSysFpRAPsStatsAppEntry          ::= SEQUENCE
{
    tSysFpRAPsStatsAppGroupId        Unsigned32,
    tSysFpRAPsStatsAppId             TmnxSysFpRAPsAppId,
    tSysFpRAPsStatsScaleAdmin        Integer32,
    tSysFpRAPsStatsScaleOper         Integer32
}

tSysFpRAPsStatsAppGroupId        OBJECT-TYPE
    SYNTAX      Unsigned32 (1..3)
    MAX-ACCESS  not-accessible
    STATUS      current
    DESCRIPTION
        "The value of tSysFpRAPsStatsAppGroupId specifies the group to which
         the application belongs."
    ::= { tSysFpRAPsStatsAppEntry 1 }

tSysFpRAPsStatsAppId             OBJECT-TYPE
    SYNTAX      TmnxSysFpRAPsAppId
    MAX-ACCESS  not-accessible
    STATUS      current
    DESCRIPTION
        "The value of tSysFpRAPsStatsAppId specifies the Application Id."
    ::= { tSysFpRAPsStatsAppEntry 2 }

tSysFpRAPsStatsScaleAdmin        OBJECT-TYPE
    SYNTAX      Integer32 (-1 | 0..96)
    MAX-ACCESS  read-write
    STATUS      current
    DESCRIPTION
        "The value of tSysFpRAPsStatsScaleAdmin represents the admin value of
         the scale configured by the user for this application."
    DEFVAL      { -1 }
    ::= { tSysFpRAPsStatsAppEntry 3 }

tSysFpRAPsStatsScaleOper         OBJECT-TYPE
    SYNTAX      Integer32 (-1 | 0..96)
    MAX-ACCESS  read-only
    STATUS      current
    DESCRIPTION
        "The value of tSysFpRAPsStatsScaleOper represents the operational value
         of the scale configured by the user for this application."
    ::= { tSysFpRAPsStatsAppEntry 4 }

tmnxSysDhcp                      OBJECT IDENTIFIER ::= { tmnxSysObjs 28 }

tmnxSysDhcp6AdvNoaddrsGlobal     OBJECT-TYPE
    SYNTAX      BITS {
        esmProxy (0),
        esmRelay (1),
        relay    (2),
        server   (3)
    }
    MAX-ACCESS  read-write
    STATUS      current
    DESCRIPTION
        "The value of tmnxSysDhcp6AdvNoaddrsGlobal specifies the composition of
         DHCPv6 Advertise Messages in case a DHCP6 application in this system
         will not assign any addresses to any Identity Association (IA) in a
         subsequent Request from the client.

         DHCP6 applications in this system are Relay, Server, Enhanced
         Subscriber Management (ESM) Proxy and ESM Relay.

         By default, a DHCP6 application in this system will send an Advertise
         message to the client that includes the IA containing a Status Code
         option with status code 'NoAddrsAvail', as specified in Errata 2472.

         If the bit corresponding to a DHCP6 application is set, that
         application will send an Advertise message to the client that includes
         only a Status Code option with code 'NoAddrsAvail'.

         This system will refuse bit combinations that are not supported: the
         'esmRelay' and 'server' bits must be toggled together, and the
         'esmProxy' and 'relay' bits are read-only."
    REFERENCE
        "RFC3315 Dynamic Host Configuration Protocol for IPv6 (DHCPv6)
         section 17.2.2 Creation and Transmission of Advertise Messages

         RFC3315 errata 2472 (section 17.2)"
    DEFVAL      { {} }
    ::= { tmnxSysDhcp 1 }

tmnxSysVsdInfo                   OBJECT IDENTIFIER ::= { tmnxSysObjs 29 }

tmnxSysVsdSystemId               OBJECT-TYPE
    SYNTAX      TNamedItemOrEmpty
    MAX-ACCESS  read-write
    STATUS      obsolete
    DESCRIPTION
        "The value of tmnxSysVsdSystemId specifies the name used by this system
         as its identity when communicating with VSD."
    DEFVAL      { ''H }
    ::= { tmnxSysVsdInfo 1 }

tmnxSysVsdGwPubSubIsSubscrd      OBJECT-TYPE
    SYNTAX      TruthValue
    MAX-ACCESS  read-only
    STATUS      obsolete
    DESCRIPTION
        "The value of tmnxSysVsdGwPubSubIsSubscrd indicates whether the system
         is subscribed to the gateway publish-subscribe node."
    ::= { tmnxSysVsdInfo 2 }

tmnxSysVsdGwPubSubNodeName       OBJECT-TYPE
    SYNTAX      DisplayString
    MAX-ACCESS  read-only
    STATUS      obsolete
    DESCRIPTION
        "The value of tmnxSysVsdGwPubSubNodeName indicates the gateway
         publish-subscribe node name assigned by VSD."
    ::= { tmnxSysVsdInfo 3 }

tmnxSysVsdGwPubSubLstSubscrdTime OBJECT-TYPE
    SYNTAX      TimeStamp
    MAX-ACCESS  read-only
    STATUS      obsolete
    DESCRIPTION
        "The value of tmnxSysVsdGwPubSubLstSubscrdTime indicates the last
         subscription time to the gateway publish-subscribe node."
    ::= { tmnxSysVsdInfo 4 }

tmnxSysVsdGwLastAuditTxTime      OBJECT-TYPE
    SYNTAX      TimeStamp
    MAX-ACCESS  read-only
    STATUS      obsolete
    DESCRIPTION
        "The value of tmnxSysVsdGwLastAuditTxTime indicates the time last
         gateway audit was sent to the VSD."
    ::= { tmnxSysVsdInfo 5 }

tmnxSysLicense                   OBJECT IDENTIFIER ::= { tmnxSysObjs 30 }

tmnxSysLicenseStatus             OBJECT-TYPE
    SYNTAX      TItemDescription
    MAX-ACCESS  read-only
    STATUS      current
    DESCRIPTION
        "The value of tmnxSysLicenseStatus indicates the current status of the
         license."
    ::= { tmnxSysLicense 1 }

tmnxSysLicenseName               OBJECT-TYPE
    SYNTAX      TItemDescription
    MAX-ACCESS  read-only
    STATUS      current
    DESCRIPTION
        "The value of tmnxSysLicenseName indicates the license name."
    ::= { tmnxSysLicense 2 }

tmnxSysLicenseUuid               OBJECT-TYPE
    SYNTAX      TmnxUuid
    MAX-ACCESS  read-only
    STATUS      current
    DESCRIPTION
        "The value of tmnxSysLicenseUuid indicates the Universally Unique
         Identifier (UUID) for the license of the virtual machine (VM)."
    ::= { tmnxSysLicense 3 }

tmnxSysLicenseDescription        OBJECT-TYPE
    SYNTAX      TItemDescription
    MAX-ACCESS  read-only
    STATUS      current
    DESCRIPTION
        "The value of tmnxSysLicenseDescription indicates the license
         description."
    ::= { tmnxSysLicense 4 }

tmnxSysLicenseProduct            OBJECT-TYPE
    SYNTAX      TItemDescription
    MAX-ACCESS  read-only
    STATUS      current
    DESCRIPTION
        "The value of tmnxSysLicenseProduct indicates the product for which the
         license is valid."
    ::= { tmnxSysLicense 5 }

tmnxSysLicenseSwVersion          OBJECT-TYPE
    SYNTAX      TItemDescription
    MAX-ACCESS  read-only
    STATUS      current
    DESCRIPTION
        "The value of tmnxSysLicenseSwVersion indicates the SROS series system
         software version for which the license is valid."
    ::= { tmnxSysLicense 6 }

tmnxSysLicenseIssueDateAndTime   OBJECT-TYPE
    SYNTAX      DateAndTime
    MAX-ACCESS  read-only
    STATUS      current
    DESCRIPTION
        "The value of tmnxSysLicenseIssueDateAndTime indicates the day and time
         the license was issued."
    ::= { tmnxSysLicense 7 }

tmnxSysLicenseStartDateAndTime   OBJECT-TYPE
    SYNTAX      DateAndTime
    MAX-ACCESS  read-only
    STATUS      current
    DESCRIPTION
        "The value of tmnxSysLicenseStartDateAndTime indicates the day and time
         the license became active."
    ::= { tmnxSysLicense 8 }

tmnxSysLicenseEndDateAndTime     OBJECT-TYPE
    SYNTAX      DateAndTime
    MAX-ACCESS  read-only
    STATUS      current
    DESCRIPTION
        "The value of tmnxSysLicenseEndDateAndTime indicates the day and time
         the license expires."
    ::= { tmnxSysLicense 9 }

tmnxSysLicenseVChassisType       OBJECT-TYPE
    SYNTAX      TNamedItemOrEmpty
    MAX-ACCESS  read-only
    STATUS      current
    DESCRIPTION
        "The value of tmnxSysLicenseVChassisType indicates the virtual chassis
         type for which the license is valid.

         A value of empty string indicates that the license is not associated
         with a virtual chassis."
    ::= { tmnxSysLicense 10 }

tmnxSysLicenseMaxNumCPMs         OBJECT-TYPE
    SYNTAX      Unsigned32
    MAX-ACCESS  read-only
    STATUS      current
    DESCRIPTION
        "The value of tmnxSysLicenseMaxNumCPMs indicates the maximum number of
         CPMs allowed by the license.

         A value of 0 indicates that the number of CPMs is not restricted by
         the license."
    ::= { tmnxSysLicense 11 }

tmnxSysLicenseMaxNumIOMs         OBJECT-TYPE
    SYNTAX      Unsigned32
    MAX-ACCESS  read-only
    STATUS      current
    DESCRIPTION
        "The value of tmnxSysLicenseMaxNumIOMs indicates the maximum number of
         IOMs allowed by the license.

         A value of 0 indicates that the number of IOMs is not restricted by
         the license."
    ::= { tmnxSysLicense 12 }

tmnxSysCpmCardLicenseTable       OBJECT-TYPE
    SYNTAX      SEQUENCE OF TmnxSysCpmCardLicenseEntry
    MAX-ACCESS  not-accessible
    STATUS      current
    DESCRIPTION
        "The tmnxSysCpmCardLicenseTable has an entry for each CPM card in the
         first chassis in the system."
    ::= { tmnxSysLicense 13 }

tmnxSysCpmCardLicenseEntry       OBJECT-TYPE
    SYNTAX      TmnxSysCpmCardLicenseEntry
    MAX-ACCESS  not-accessible
    STATUS      current
    DESCRIPTION
        "Each row represents a CPM card in the first chassis in the system.
         When a tmnxChassisEntry is created, a tmnxSysCpmCardLicenseEntry is
         created for each CPM card in the first chassis. Entries cannot be
         created or deleted via SNMP SET operations."
    INDEX       {
        tmnxChassisIndex,
        tmnxCpmCardSlotNum,
        tmnxCpmCardNum
    }
    ::= { tmnxSysCpmCardLicenseTable 1 }

TmnxSysCpmCardLicenseEntry       ::= SEQUENCE
{
    tmnxSysCpmCardLicStatus          TItemDescription,
    tmnxSysCpmCardLicName            TItemDescription,
    tmnxSysCpmCardLicUuid            TmnxUuid,
    tmnxSysCpmCardLicDescription     TItemDescription,
    tmnxSysCpmCardLicProduct         TItemDescription,
    tmnxSysCpmCardLicSwVersion       TItemDescription,
    tmnxSysCpmCardLicIssueDateTime   DateAndTime,
    tmnxSysCpmCardLicStartDateTime   DateAndTime,
    tmnxSysCpmCardLicEndDateTime     DateAndTime,
    tmnxSysCpmCardLicVChassisType    TNamedItemOrEmpty,
    tmnxSysCpmCardLicMaxNumCPMs      Unsigned32,
    tmnxSysCpmCardLicMaxNumIOMs      Unsigned32
}

tmnxSysCpmCardLicStatus          OBJECT-TYPE
    SYNTAX      TItemDescription
    MAX-ACCESS  read-only
    STATUS      current
    DESCRIPTION
        "The value of tmnxSysCpmCardLicStatus indicates the current status of
         the license."
    ::= { tmnxSysCpmCardLicenseEntry 1 }

tmnxSysCpmCardLicName            OBJECT-TYPE
    SYNTAX      TItemDescription
    MAX-ACCESS  read-only
    STATUS      current
    DESCRIPTION
        "The value of tmnxSysCpmCardLicName indicates the license name."
    ::= { tmnxSysCpmCardLicenseEntry 2 }

tmnxSysCpmCardLicUuid            OBJECT-TYPE
    SYNTAX      TmnxUuid
    MAX-ACCESS  read-only
    STATUS      current
    DESCRIPTION
        "The value of tmnxSysCpmCardLicUuid indicates the Universally Unique
         Identifier (UUID) for the license of the CPM card in the virtual
         machine (VM)."
    ::= { tmnxSysCpmCardLicenseEntry 3 }

tmnxSysCpmCardLicDescription     OBJECT-TYPE
    SYNTAX      TItemDescription
    MAX-ACCESS  read-only
    STATUS      current
    DESCRIPTION
        "The value of tmnxSysCpmCardLicDescription indicates the license
         description."
    ::= { tmnxSysCpmCardLicenseEntry 4 }

tmnxSysCpmCardLicProduct         OBJECT-TYPE
    SYNTAX      TItemDescription
    MAX-ACCESS  read-only
    STATUS      current
    DESCRIPTION
        "The value of tmnxSysCpmCardLicProduct indicates the product for which
         the license is valid."
    ::= { tmnxSysCpmCardLicenseEntry 5 }

tmnxSysCpmCardLicSwVersion       OBJECT-TYPE
    SYNTAX      TItemDescription
    MAX-ACCESS  read-only
    STATUS      current
    DESCRIPTION
        "The value of tmnxSysCpmCardLicSwVersion indicates the SROS series
         system software version for which the license is valid."
    ::= { tmnxSysCpmCardLicenseEntry 6 }

tmnxSysCpmCardLicIssueDateTime   OBJECT-TYPE
    SYNTAX      DateAndTime
    MAX-ACCESS  read-only
    STATUS      current
    DESCRIPTION
        "The value of tmnxSysCpmCardLicIssueDateTime indicates the day and time
         the license was issued."
    ::= { tmnxSysCpmCardLicenseEntry 7 }

tmnxSysCpmCardLicStartDateTime   OBJECT-TYPE
    SYNTAX      DateAndTime
    MAX-ACCESS  read-only
    STATUS      current
    DESCRIPTION
        "The value of tmnxSysCpmCardLicStartDateTime indicates the day and time
         the license became active."
    ::= { tmnxSysCpmCardLicenseEntry 8 }

tmnxSysCpmCardLicEndDateTime     OBJECT-TYPE
    SYNTAX      DateAndTime
    MAX-ACCESS  read-only
    STATUS      current
    DESCRIPTION
        "The value of tmnxSysCpmCardLicEndDateTime indicates the day and time
         the license expires."
    ::= { tmnxSysCpmCardLicenseEntry 9 }

tmnxSysCpmCardLicVChassisType    OBJECT-TYPE
    SYNTAX      TNamedItemOrEmpty
    MAX-ACCESS  read-only
    STATUS      current
    DESCRIPTION
        "The value of tmnxSysCpmCardLicVChassisType indicates the virtual
         chassis type for which the license is valid.

         A value of empty string indicates that the license is not associated
         with a virtual chassis."
    ::= { tmnxSysCpmCardLicenseEntry 10 }

tmnxSysCpmCardLicMaxNumCPMs      OBJECT-TYPE
    SYNTAX      Unsigned32
    MAX-ACCESS  read-only
    STATUS      current
    DESCRIPTION
        "The value of tmnxSysCpmCardLicMaxNumCPMs indicates the maximum number
         of CPMs allowed by the license.

         A value of 0 indicates that the number of CPMs is not restricted by
         the license."
    ::= { tmnxSysCpmCardLicenseEntry 11 }

tmnxSysCpmCardLicMaxNumIOMs      OBJECT-TYPE
    SYNTAX      Unsigned32
    MAX-ACCESS  read-only
    STATUS      current
    DESCRIPTION
        "The value of tmnxSysCpmCardLicMaxNumIOMs indicates the maximum number
         of IOMs allowed by the license.

         A value of 0 indicates that the number of IOMs is not restricted by
         the license."
    ::= { tmnxSysCpmCardLicenseEntry 12 }

tmnxSysCpmCardLicFeatureTable    OBJECT-TYPE
    SYNTAX      SEQUENCE OF TmnxSysCpmCardLicFeatureEntry
    MAX-ACCESS  not-accessible
    STATUS      current
    DESCRIPTION
        "The tmnxSysCpmCardLicFeatureTable has an entry for each feature
         supported by the license installed on a CPM card in the chassis with
         TIMETRA-CHASSIS-MIB::tmnxPhysChassisClass 'routerChassis(3)' and
         TIMETRA-CHASSIS-MIB::tmnxPhysChassisNum '1'."
    ::= { tmnxSysLicense 14 }

tmnxSysCpmCardLicFeatureEntry    OBJECT-TYPE
    SYNTAX      TmnxSysCpmCardLicFeatureEntry
    MAX-ACCESS  not-accessible
    STATUS      current
    DESCRIPTION
        "When a TIMETRA-CHASSIS-MIB::tmnxCpmCardEntry is created for a CPM card
         in the chassis with TIMETRA-CHASSIS-MIB::tmnxPhysChassisClass
         'routerChassis(3)' and TIMETRA-CHASSIS-MIB::tmnxPhysChassisNum '1', a
         tmnxSysCpmCardLicFeatureEntry is created for each feature supported by
         the license installed on that CPM card.

         Entries cannot be created or deleted via SNMP SET operations."
    INDEX       {
        tmnxChassisIndex,
        tmnxCpmCardSlotNum,
        tmnxCpmCardNum,
        tmnxSysCpmCardLicFeatApplication,
        tmnxSysCpmCardLicFeatNumber
    }
    ::= { tmnxSysCpmCardLicFeatureTable 1 }

TmnxSysCpmCardLicFeatureEntry    ::= SEQUENCE
{
    tmnxSysCpmCardLicFeatApplication TNamedItem,
    tmnxSysCpmCardLicFeatNumber      Unsigned32,
    tmnxSysCpmCardLicFeatDescription TItemDescription
}

tmnxSysCpmCardLicFeatApplication OBJECT-TYPE
    SYNTAX      TNamedItem
    MAX-ACCESS  not-accessible
    STATUS      current
    DESCRIPTION
        "The value of tmnxSysCpmCardLicFeatApplication specifies the
         application supported by the license."
    ::= { tmnxSysCpmCardLicFeatureEntry 1 }

tmnxSysCpmCardLicFeatNumber      OBJECT-TYPE
    SYNTAX      Unsigned32 (1..4294967295)
    MAX-ACCESS  not-accessible
    STATUS      current
    DESCRIPTION
        "The value of tmnxSysCpmCardLicFeatNumber specifies the feature number
         associated with the feature supported by the license."
    ::= { tmnxSysCpmCardLicFeatureEntry 2 }

tmnxSysCpmCardLicFeatDescription OBJECT-TYPE
    SYNTAX      TItemDescription
    MAX-ACCESS  read-only
    STATUS      current
    DESCRIPTION
        "The value of tmnxSysCpmCardLicFeatDescription indicates the
         description of the feature supported by the license."
    ::= { tmnxSysCpmCardLicFeatureEntry 3 }

tmnxSysLicensingTable            OBJECT-TYPE
    SYNTAX      SEQUENCE OF TmnxSysLicensingEntry
    MAX-ACCESS  not-accessible
    STATUS      current
    DESCRIPTION
        "The tmnxSysLicensingTable an entry for each licensed applications for
         this system."
    ::= { tmnxSysLicense 16 }

tmnxSysLicensingEntry            OBJECT-TYPE
    SYNTAX      TmnxSysLicensingEntry
    MAX-ACCESS  not-accessible
    STATUS      current
    DESCRIPTION
        "Each row contains detailed information about each licensed
         application.

         Entries cannot be created or deleted via SNMP SET operations."
    INDEX       {
        tmnxSysLicensingGroup,
        tmnxSysLicensedAppName
    }
    ::= { tmnxSysLicensingTable 1 }

TmnxSysLicensingEntry            ::= SEQUENCE
{
    tmnxSysLicensingGroup            TmnxSysLicensingGroup,
    tmnxSysLicensedAppName           TNamedItem,
    tmnxSysAppLicenseDescription     DisplayString,
    tmnxSysAppLicenseType            INTEGER,
    tmnxSysAppLicensePoolSize        Integer32,
    tmnxSysAppLicenseAllocated       Unsigned32,
    tmnxSysAppLicensePresent         TruthValue,
    tmnxSysAppLicenseState           INTEGER,
    tmnxSysAppLicense24HrDateTime    DateAndTime,
    tmnxSysAppLicense24HrMax         Unsigned32,
    tmnxSysAppLicenseCurrentMax      Unsigned32
}

tmnxSysLicensingGroup            OBJECT-TYPE
    SYNTAX      TmnxSysLicensingGroup
    MAX-ACCESS  not-accessible
    STATUS      current
    DESCRIPTION
        "The value of tmnxSysLicensingGroup indicates the licensing group."
    ::= { tmnxSysLicensingEntry 1 }

tmnxSysLicensedAppName           OBJECT-TYPE
    SYNTAX      TNamedItem
    MAX-ACCESS  not-accessible
    STATUS      current
    DESCRIPTION
        "The value of tmnxSysLicensedAppName indicates the name of the licensed
         application."
    ::= { tmnxSysLicensingEntry 2 }

tmnxSysAppLicenseDescription     OBJECT-TYPE
    SYNTAX      DisplayString (SIZE (1..64))
    MAX-ACCESS  read-only
    STATUS      current
    DESCRIPTION
        "The value of the object tmnxSysAppLicenseDescription indicates a more
         detailed description of the application license."
    ::= { tmnxSysLicensingEntry 3 }

tmnxSysAppLicenseType            OBJECT-TYPE
    SYNTAX      INTEGER {
        unknown   (0),
        pool      (1),
        rtu       (2),
        monitored (3)
    }
    MAX-ACCESS  read-only
    STATUS      current
    DESCRIPTION
        "The value of tmnxSysAppLicenseType specifies the type
         of licensing done for this application.
         pool - A pool license grants a specified number of
                concurrent allocations of the license.
         rtu  - An RTU license grants the right to use a
                feature,
         monitored - A monitored license is audited, but not
                strictly enforced by the system."
    ::= { tmnxSysLicensingEntry 4 }

tmnxSysAppLicensePoolSize        OBJECT-TYPE
    SYNTAX      Integer32
    MAX-ACCESS  read-only
    STATUS      current
    DESCRIPTION
        "The value of tmnxSysAppLicensePoolSize indicates the size of the pool
         of licenses that can be allocated within the system. A value of (-1)
         indicates a pool size is not applicable to this application based on
         tmnxSysAppLicenseType."
    ::= { tmnxSysLicensingEntry 5 }

tmnxSysAppLicenseAllocated       OBJECT-TYPE
    SYNTAX      Unsigned32
    MAX-ACCESS  read-only
    STATUS      current
    DESCRIPTION
        "The value of tmnxSysAppLicenseAllocated indicates the the number of
         these licenses currently allocated in the system."
    ::= { tmnxSysLicensingEntry 6 }

tmnxSysAppLicensePresent         OBJECT-TYPE
    SYNTAX      TruthValue
    MAX-ACCESS  read-only
    STATUS      current
    DESCRIPTION
        "The value of tmnxSysAppLicensePresent specifies if the current system
         license grants the right to use feature on this system."
    ::= { tmnxSysLicensingEntry 7 }

tmnxSysAppLicenseState           OBJECT-TYPE
    SYNTAX      INTEGER {
        unknown   (0),
        valid     (1),
        error     (2),
        violation (3)
    }
    MAX-ACCESS  read-only
    STATUS      current
    DESCRIPTION
        "The value of tmnxSysAppLicenseState indicates the state
         of the license for this application.
         unknown   - Monitored licenses will always return this value
         valid     - No issue with application license
         error     - Insufficient licensing has been detected.
         violation - License violation has been detected."
    ::= { tmnxSysLicensingEntry 8 }

tmnxSysAppLicense24HrDateTime    OBJECT-TYPE
    SYNTAX      DateAndTime
    MAX-ACCESS  read-only
    STATUS      current
    DESCRIPTION
        "The value of tmnxSysAppLicense24HrDateTime indicates the the time that
         the last 24 hour interval ended."
    ::= { tmnxSysLicensingEntry 9 }

tmnxSysAppLicense24HrMax         OBJECT-TYPE
    SYNTAX      Unsigned32
    MAX-ACCESS  read-only
    STATUS      current
    DESCRIPTION
        "The value of tmnxSysAppLicense24HrMax indicates the the max number of
         these licenses allocated since the time indicated by
         tmnxSysAppLicense24HrStartTime (last 24 hours)."
    ::= { tmnxSysLicensingEntry 10 }

tmnxSysAppLicenseCurrentMax      OBJECT-TYPE
    SYNTAX      Unsigned32
    MAX-ACCESS  read-only
    STATUS      current
    DESCRIPTION
        "The value of tmnxSysAppLicenseCurrentMax indicates the the max number
         of these licenses allocated since the last 24 hour interval was
         recorded."
    ::= { tmnxSysLicensingEntry 11 }

tmnxSysAvailableLicensesTable    OBJECT-TYPE
    SYNTAX      SEQUENCE OF TmnxSysAvailableLicensesEntry
    MAX-ACCESS  not-accessible
    STATUS      current
    DESCRIPTION
        "The tmnxSysAvailableLicensesTable has an entry for each license
         available for this system that was matched in the license file."
    ::= { tmnxSysLicense 17 }

tmnxSysAvailableLicensesEntry    OBJECT-TYPE
    SYNTAX      TmnxSysAvailableLicensesEntry
    MAX-ACCESS  not-accessible
    STATUS      current
    DESCRIPTION
        "Each row represents a license available for this system from the last
         loaded license-file."
    INDEX       { tmnxSysAvailLicenseIndex }
    ::= { tmnxSysAvailableLicensesTable 1 }

TmnxSysAvailableLicensesEntry    ::= SEQUENCE
{
    tmnxSysAvailLicenseIndex         Unsigned32,
    tmnxSysAvailLicenseName          TItemDescription,
    tmnxSysAvailLicenseUuid          TmnxUuid,
    tmnxSysAvailLicenseDescription   TItemDescription,
    tmnxSysAvailLicenseSwVersion     TItemDescription,
    tmnxSysAvailLicIssueDateTime     DateAndTime,
    tmnxSysAvailLicStartDateTime     DateAndTime,
    tmnxSysAvailLicEndDateTime       DateAndTime,
    tmnxSysAvailLicenseProduct       TItemDescription
}

tmnxSysAvailLicenseIndex         OBJECT-TYPE
    SYNTAX      Unsigned32
    MAX-ACCESS  not-accessible
    STATUS      current
    DESCRIPTION
        "The value of tmnxSysAvailLicenseIndex indicates the index of the
         matched license."
    ::= { tmnxSysAvailableLicensesEntry 1 }

tmnxSysAvailLicenseName          OBJECT-TYPE
    SYNTAX      TItemDescription
    MAX-ACCESS  read-only
    STATUS      current
    DESCRIPTION
        "The value of tmnxSysAvailLicenseName indicates the license name."
    ::= { tmnxSysAvailableLicensesEntry 2 }

tmnxSysAvailLicenseUuid          OBJECT-TYPE
    SYNTAX      TmnxUuid
    MAX-ACCESS  read-only
    STATUS      current
    DESCRIPTION
        "The value of tmnxSysAvailLicenseUuid indicates the Universally Unique
         Identifier (UUID) for the license."
    ::= { tmnxSysAvailableLicensesEntry 3 }

tmnxSysAvailLicenseDescription   OBJECT-TYPE
    SYNTAX      TItemDescription
    MAX-ACCESS  read-only
    STATUS      current
    DESCRIPTION
        "The value of tmnxSysAvailLicenseDescription indicates the license
         description."
    ::= { tmnxSysAvailableLicensesEntry 4 }

tmnxSysAvailLicenseSwVersion     OBJECT-TYPE
    SYNTAX      TItemDescription
    MAX-ACCESS  read-only
    STATUS      current
    DESCRIPTION
        "The value of tmnxSysAvailLicenseSwVersion indicates the SROS series
         system software version for which the license is valid."
    ::= { tmnxSysAvailableLicensesEntry 5 }

tmnxSysAvailLicIssueDateTime     OBJECT-TYPE
    SYNTAX      DateAndTime
    MAX-ACCESS  read-only
    STATUS      current
    DESCRIPTION
        "The value of tmnxSysAvailLicIssueDateTime indicates the day and time
         the license was issued."
    ::= { tmnxSysAvailableLicensesEntry 6 }

tmnxSysAvailLicStartDateTime     OBJECT-TYPE
    SYNTAX      DateAndTime
    MAX-ACCESS  read-only
    STATUS      current
    DESCRIPTION
        "The value of tmnxSysAvailLicStartDateTime indicates the day and time
         the license becomes active."
    ::= { tmnxSysAvailableLicensesEntry 7 }

tmnxSysAvailLicEndDateTime       OBJECT-TYPE
    SYNTAX      DateAndTime
    MAX-ACCESS  read-only
    STATUS      current
    DESCRIPTION
        "The value of tmnxSysAvailLicEndDateTime indicates the day and time the
         license expires."
    ::= { tmnxSysAvailableLicensesEntry 8 }

tmnxSysAvailLicenseProduct       OBJECT-TYPE
    SYNTAX      TItemDescription
    MAX-ACCESS  read-only
    STATUS      current
    DESCRIPTION
        "The value of tmnxSysAvailLicenseProduct indicates the licensed
         product."
    ::= { tmnxSysAvailableLicensesEntry 9 }

tmnxSysLicensingState            OBJECT-TYPE
    SYNTAX      INTEGER {
        unlicensed      (0),
        licensed        (1),
        invalid-license (2),
        expired-license (3)
    }
    MAX-ACCESS  read-only
    STATUS      current
    DESCRIPTION
        "The value of tmnxSysLicensingState indicates the current status of the
         system licensing."
    ::= { tmnxSysLicense 18 }

tmnxSysLicensingRebootPending    OBJECT-TYPE
    SYNTAX      TruthValue
    MAX-ACCESS  read-only
    STATUS      current
    DESCRIPTION
        "The value of tmnxSysLicensingRebootPending indicates whether a system
         reboot is pending due to system licensing"
    ::= { tmnxSysLicense 19 }

tmnxSysLicenseStatistics         OBJECT IDENTIFIER ::= { tmnxSysLicense 20 }

tmnxSysAppStats24HrsTable        OBJECT-TYPE
    SYNTAX      SEQUENCE OF TmnxSysAppStats24HrsEntry
    MAX-ACCESS  not-accessible
    STATUS      current
    DESCRIPTION
        "The tmnxSysAppStats24HrsTable contains statistics about a virtual
         machine application collected periodically during the last 24 hours."
    ::= { tmnxSysLicenseStatistics 1 }

tmnxSysAppStats24HrsEntry        OBJECT-TYPE
    SYNTAX      TmnxSysAppStats24HrsEntry
    MAX-ACCESS  not-accessible
    STATUS      current
    DESCRIPTION
        "Each conceptual row contains a specific instance of a statistics value
         at a specific time."
    INDEX       {
        tmnxSysAppStats24HrsApplication,
        tmnxSysAppStats24HrsType,
        tmnxSysAppStats24HrsIndex
    }
    ::= { tmnxSysAppStats24HrsTable 1 }

TmnxSysAppStats24HrsEntry        ::= SEQUENCE
{
    tmnxSysAppStats24HrsApplication  TmnxSysLicenseApplication,
    tmnxSysAppStats24HrsType         TmnxSysLicenseAppStatsType,
    tmnxSysAppStats24HrsIndex        Unsigned32,
    tmnxSysAppStats24HrsName         DisplayString,
    tmnxSysAppStats24HrsValue        CounterBasedGauge64,
    tmnxSysAppStats24HrsTime         DateAndTime
}

tmnxSysAppStats24HrsApplication  OBJECT-TYPE
    SYNTAX      TmnxSysLicenseApplication
    MAX-ACCESS  not-accessible
    STATUS      current
    DESCRIPTION
        "The value of tmnxSysAppStats24HrsApplication indicates the
         application."
    ::= { tmnxSysAppStats24HrsEntry 1 }

tmnxSysAppStats24HrsType         OBJECT-TYPE
    SYNTAX      TmnxSysLicenseAppStatsType
    MAX-ACCESS  not-accessible
    STATUS      current
    DESCRIPTION
        "The value of tmnxSysAppStats24HrsType indicates the meaning of the
         statistics in this conceptual row."
    ::= { tmnxSysAppStats24HrsEntry 2 }

tmnxSysAppStats24HrsIndex        OBJECT-TYPE
    SYNTAX      Unsigned32
    MAX-ACCESS  not-accessible
    STATUS      current
    DESCRIPTION
        "The value of tmnxSysAppStats24HrsIndex is a numerical index value
         generated by this system."
    ::= { tmnxSysAppStats24HrsEntry 3 }

tmnxSysAppStats24HrsName         OBJECT-TYPE
    SYNTAX      DisplayString (SIZE (1..64))
    MAX-ACCESS  read-only
    STATUS      current
    DESCRIPTION
        "The value of the object tmnxSysAppStats24HrsName indicates the
         human-readable identifier of the statistics contained in this
         conceptual row."
    ::= { tmnxSysAppStats24HrsEntry 4 }

tmnxSysAppStats24HrsValue        OBJECT-TYPE
    SYNTAX      CounterBasedGauge64
    MAX-ACCESS  read-only
    STATUS      current
    DESCRIPTION
        "The value of the object tmnxSysAppStats24HrsValue indicates the value
         of the statistics contained in this conceptual row."
    ::= { tmnxSysAppStats24HrsEntry 5 }

tmnxSysAppStats24HrsTime         OBJECT-TYPE
    SYNTAX      DateAndTime (SIZE (11))
    MAX-ACCESS  read-only
    STATUS      current
    DESCRIPTION
        "The value of the object tmnxSysAppStats24HrsTime indicates the time
         the system measured the value of tmnxSysAppStats24HrsValue."
    ::= { tmnxSysAppStats24HrsEntry 6 }

tmnxSysAppStatsWeekTable         OBJECT-TYPE
    SYNTAX      SEQUENCE OF TmnxSysAppStatsWeekEntry
    MAX-ACCESS  not-accessible
    STATUS      current
    DESCRIPTION
        "The tmnxSysAppStatsWeekTable contains statistics about a virtual
         machine application collected periodically during the last week."
    ::= { tmnxSysLicenseStatistics 2 }

tmnxSysAppStatsWeekEntry         OBJECT-TYPE
    SYNTAX      TmnxSysAppStatsWeekEntry
    MAX-ACCESS  not-accessible
    STATUS      current
    DESCRIPTION
        "Each conceptual row contains a specific instance of a statistics value
         associated with a specific 24 hours period."
    INDEX       {
        tmnxSysAppStatsWeekApplication,
        tmnxSysAppStatsWeekType,
        tmnxSysAppStatsWeekIndex
    }
    ::= { tmnxSysAppStatsWeekTable 1 }

TmnxSysAppStatsWeekEntry         ::= SEQUENCE
{
    tmnxSysAppStatsWeekApplication   TmnxSysLicenseApplication,
    tmnxSysAppStatsWeekType          TmnxSysLicenseAppStatsType,
    tmnxSysAppStatsWeekIndex         Unsigned32,
    tmnxSysAppStatsWeekName          DisplayString,
    tmnxSysAppStatsWeekAverage       CounterBasedGauge64,
    tmnxSysAppStatsWeekPeak          CounterBasedGauge64,
    tmnxSysAppStatsWeekTime          DateAndTime
}

tmnxSysAppStatsWeekApplication   OBJECT-TYPE
    SYNTAX      TmnxSysLicenseApplication
    MAX-ACCESS  not-accessible
    STATUS      current
    DESCRIPTION
        "The value of tmnxSysAppStatsWeekApplication indicates the application."
    ::= { tmnxSysAppStatsWeekEntry 1 }

tmnxSysAppStatsWeekType          OBJECT-TYPE
    SYNTAX      TmnxSysLicenseAppStatsType
    MAX-ACCESS  not-accessible
    STATUS      current
    DESCRIPTION
        "The value of tmnxSysAppStatsWeekType indicates the meaning of the
         statistics in this conceptual row."
    ::= { tmnxSysAppStatsWeekEntry 2 }

tmnxSysAppStatsWeekIndex         OBJECT-TYPE
    SYNTAX      Unsigned32
    MAX-ACCESS  not-accessible
    STATUS      current
    DESCRIPTION
        "The value of tmnxSysAppStatsWeekIndex is a numerical index value
         generated by this system."
    ::= { tmnxSysAppStatsWeekEntry 3 }

tmnxSysAppStatsWeekName          OBJECT-TYPE
    SYNTAX      DisplayString (SIZE (1..64))
    MAX-ACCESS  read-only
    STATUS      current
    DESCRIPTION
        "The value of the object tmnxSysAppStatsWeekName indicates the
         human-readable identifier of the statistics contained in this
         conceptual row."
    ::= { tmnxSysAppStatsWeekEntry 4 }

tmnxSysAppStatsWeekAverage       OBJECT-TYPE
    SYNTAX      CounterBasedGauge64
    MAX-ACCESS  read-only
    STATUS      current
    DESCRIPTION
        "The value of the object tmnxSysAppStatsWeekAverage indicates the
         average value of the statistics contained in this conceptual row for
         this period of 24 hours."
    ::= { tmnxSysAppStatsWeekEntry 5 }

tmnxSysAppStatsWeekPeak          OBJECT-TYPE
    SYNTAX      CounterBasedGauge64
    MAX-ACCESS  read-only
    STATUS      current
    DESCRIPTION
        "The value of the object tmnxSysAppStatsWeekPeak indicates the peak
         value of the statistics contained in this conceptual row for this
         period of 24 hours."
    ::= { tmnxSysAppStatsWeekEntry 6 }

tmnxSysAppStatsWeekTime          OBJECT-TYPE
    SYNTAX      DateAndTime (SIZE (11))
    MAX-ACCESS  read-only
    STATUS      current
    DESCRIPTION
        "The value of the object tmnxSysAppStatsWeekTime indicates the time the
         system determined the values of tmnxSysAppStatsWeekAverage and
         tmnxSysAppStatsWeekPeak."
    ::= { tmnxSysAppStatsWeekEntry 7 }

tmnxSysAppStatsPeakTable         OBJECT-TYPE
    SYNTAX      SEQUENCE OF TmnxSysAppStatsPeakEntry
    MAX-ACCESS  not-accessible
    STATUS      current
    DESCRIPTION
        "The tmnxSysAppStatsPeakTable contains peak values of statistics about
         a virtual machine application."
    ::= { tmnxSysLicenseStatistics 3 }

tmnxSysAppStatsPeakEntry         OBJECT-TYPE
    SYNTAX      TmnxSysAppStatsPeakEntry
    MAX-ACCESS  not-accessible
    STATUS      current
    DESCRIPTION
        "Each conceptual row contains a peak value of a statistic about a
         virtual machine application."
    INDEX       {
        tmnxSysAppStatsPeakApplication,
        tmnxSysAppStatsPeakType
    }
    ::= { tmnxSysAppStatsPeakTable 1 }

TmnxSysAppStatsPeakEntry         ::= SEQUENCE
{
    tmnxSysAppStatsPeakApplication   TmnxSysLicenseApplication,
    tmnxSysAppStatsPeakType          TmnxSysLicenseAppStatsType,
    tmnxSysAppStatsPeakName          DisplayString,
    tmnxSysAppStatsPeakValue         CounterBasedGauge64,
    tmnxSysAppStatsPeakTime          DateAndTime
}

tmnxSysAppStatsPeakApplication   OBJECT-TYPE
    SYNTAX      TmnxSysLicenseApplication
    MAX-ACCESS  not-accessible
    STATUS      current
    DESCRIPTION
        "The value of tmnxSysAppStatsPeakApplication indicates the application."
    ::= { tmnxSysAppStatsPeakEntry 1 }

tmnxSysAppStatsPeakType          OBJECT-TYPE
    SYNTAX      TmnxSysLicenseAppStatsType
    MAX-ACCESS  not-accessible
    STATUS      current
    DESCRIPTION
        "The value of tmnxSysAppStatsPeakType indicates the meaning of the
         statistics in this conceptual row."
    ::= { tmnxSysAppStatsPeakEntry 2 }

tmnxSysAppStatsPeakName          OBJECT-TYPE
    SYNTAX      DisplayString (SIZE (1..64))
    MAX-ACCESS  read-only
    STATUS      current
    DESCRIPTION
        "The value of the object tmnxSysAppStatsPeakName indicates the
         human-readable identifier of the statistics contained in this
         conceptual row."
    ::= { tmnxSysAppStatsPeakEntry 3 }

tmnxSysAppStatsPeakValue         OBJECT-TYPE
    SYNTAX      CounterBasedGauge64
    MAX-ACCESS  read-only
    STATUS      current
    DESCRIPTION
        "The value of the object tmnxSysAppStatsPeakValue indicates the value
         of the statistics contained in this conceptual row."
    ::= { tmnxSysAppStatsPeakEntry 4 }

tmnxSysAppStatsPeakTime          OBJECT-TYPE
    SYNTAX      DateAndTime (SIZE (11))
    MAX-ACCESS  read-only
    STATUS      current
    DESCRIPTION
        "The value of the object tmnxSysAppStatsPeakTime indicates the time the
         system measured the value of tmnxSysAppStatsPeakValue."
    ::= { tmnxSysAppStatsPeakEntry 5 }

tmnxSysAppStats48HrsTable        OBJECT-TYPE
    SYNTAX      SEQUENCE OF TmnxSysAppStats48HrsEntry
    MAX-ACCESS  not-accessible
    STATUS      current
    DESCRIPTION
        "The tmnxSysAppStats48HrsTable contains statistics about a virtual
         machine application collected periodically 24 to 48 hours ago."
    ::= { tmnxSysLicenseStatistics 4 }

tmnxSysAppStats48HrsEntry        OBJECT-TYPE
    SYNTAX      TmnxSysAppStats48HrsEntry
    MAX-ACCESS  not-accessible
    STATUS      current
    DESCRIPTION
        "Each conceptual row contains a specific instance of a statistics value
         at a specific time."
    INDEX       {
        tmnxSysAppStats48HrsApplication,
        tmnxSysAppStats48HrsType,
        tmnxSysAppStats48HrsIndex
    }
    ::= { tmnxSysAppStats48HrsTable 1 }

TmnxSysAppStats48HrsEntry        ::= SEQUENCE
{
    tmnxSysAppStats48HrsApplication  TmnxSysLicenseApplication,
    tmnxSysAppStats48HrsType         TmnxSysLicenseAppStatsType,
    tmnxSysAppStats48HrsIndex        Unsigned32,
    tmnxSysAppStats48HrsName         DisplayString,
    tmnxSysAppStats48HrsValue        CounterBasedGauge64,
    tmnxSysAppStats48HrsTime         DateAndTime
}

tmnxSysAppStats48HrsApplication  OBJECT-TYPE
    SYNTAX      TmnxSysLicenseApplication
    MAX-ACCESS  not-accessible
    STATUS      current
    DESCRIPTION
        "The value of tmnxSysAppStats48HrsApplication indicates the
         application."
    ::= { tmnxSysAppStats48HrsEntry 1 }

tmnxSysAppStats48HrsType         OBJECT-TYPE
    SYNTAX      TmnxSysLicenseAppStatsType
    MAX-ACCESS  not-accessible
    STATUS      current
    DESCRIPTION
        "The value of tmnxSysAppStats48HrsType indicates the meaning of the
         statistics in this conceptual row."
    ::= { tmnxSysAppStats48HrsEntry 2 }

tmnxSysAppStats48HrsIndex        OBJECT-TYPE
    SYNTAX      Unsigned32
    MAX-ACCESS  not-accessible
    STATUS      current
    DESCRIPTION
        "The value of tmnxSysAppStats48HrsIndex is a numerical index value
         generated by this system."
    ::= { tmnxSysAppStats48HrsEntry 3 }

tmnxSysAppStats48HrsName         OBJECT-TYPE
    SYNTAX      DisplayString (SIZE (1..64))
    MAX-ACCESS  read-only
    STATUS      current
    DESCRIPTION
        "The value of the object tmnxSysAppStats48HrsName indicates the
         human-readable identifier of the statistics contained in this
         conceptual row."
    ::= { tmnxSysAppStats48HrsEntry 4 }

tmnxSysAppStats48HrsValue        OBJECT-TYPE
    SYNTAX      CounterBasedGauge64
    MAX-ACCESS  read-only
    STATUS      current
    DESCRIPTION
        "The value of the object tmnxSysAppStats48HrsValue indicates the value
         of the statistics contained in this conceptual row."
    ::= { tmnxSysAppStats48HrsEntry 5 }

tmnxSysAppStats48HrsTime         OBJECT-TYPE
    SYNTAX      DateAndTime (SIZE (11))
    MAX-ACCESS  read-only
    STATUS      current
    DESCRIPTION
        "The value of the object tmnxSysAppStats48HrsTime indicates the time
         the system measured the value of tmnxSysAppStats48HrsValue."
    ::= { tmnxSysAppStats48HrsEntry 6 }

tmnxSysLicensingProduct          OBJECT-TYPE
    SYNTAX      TItemDescription
    MAX-ACCESS  read-only
    STATUS      current
    DESCRIPTION
        "The value of tmnxSysLicensingProduct indicates the type of license
         expected based on the running system."
    ::= { tmnxSysLicense 21 }

tmnxSysLicensingUuid             OBJECT-TYPE
    SYNTAX      TmnxUuid
    MAX-ACCESS  read-only
    STATUS      current
    DESCRIPTION
        "The value of tmnxSysLicensingUuid indicates the Universally Unique
         Identifier (UUID) being used to match license."
    ::= { tmnxSysLicense 22 }

tmnxSysFibInfo                   OBJECT IDENTIFIER ::= { tmnxSysObjs 31 }

tmnxSysFibSelective              OBJECT-TYPE
    SYNTAX      TruthValue
    MAX-ACCESS  read-write
    STATUS      current
    DESCRIPTION
        "The value of tmnxSysFibSelective specifies whether selective FIB is
         enabled in the system.

         If the value of tmnxSysFibSelective is set to false, then all active
         routes are installed on all line cards.

         If the value of tmnxSysFibSelective is set to true, then a line card
         installs a particular IP route only if that route is relevant to the
         card based on the current configuration of interfaces and services."
    DEFVAL      { false }
    ::= { tmnxSysFibInfo 1 }

tmnxSysSnmpSrcAccessObjs         OBJECT IDENTIFIER ::= { tmnxSysObjs 32 }

tmnxSysSnmpConfigObjs            OBJECT IDENTIFIER ::= { tmnxSysSnmpSrcAccessObjs 1 }

tmnxSysSnmpSrcAccessTblLstChgd   OBJECT-TYPE
    SYNTAX      TimeStamp
    MAX-ACCESS  read-only
    STATUS      current
    DESCRIPTION
        "The value of tmnxSysSnmpSrcAccessTblLstChgd indicates the sysUpTime at
         the time of the last modification to tmnxSysSnmpSrcAccessLstTable by
         adding, deleting an entry or change to a writable object in the table.

         If no changes were made to the table since the last re-initialization
         of the local network management subsystem, then this object contains a
         zero value."
    ::= { tmnxSysSnmpConfigObjs 1 }

tmnxSysSnmpSrcAccessLstTable     OBJECT-TYPE
    SYNTAX      SEQUENCE OF TmnxSysSnmpSrcAccessLstEntry
    MAX-ACCESS  not-accessible
    STATUS      current
    DESCRIPTION
        "The tmnxSysSnmpSrcAccessLstTable contains objects for creating entries
         corresponding to source access list."
    ::= { tmnxSysSnmpConfigObjs 2 }

tmnxSysSnmpSrcAccessLstEntry     OBJECT-TYPE
    SYNTAX      TmnxSysSnmpSrcAccessLstEntry
    MAX-ACCESS  not-accessible
    STATUS      current
    DESCRIPTION
        "The tmnxSysSnmpSrcAccessLstEntry contains configuration items for
         creating src-access-list."
    INDEX       { IMPLIED tmnxSysSnmpSrcAccessLstName }
    ::= { tmnxSysSnmpSrcAccessLstTable 1 }

TmnxSysSnmpSrcAccessLstEntry     ::= SEQUENCE
{
    tmnxSysSnmpSrcAccessLstName      TNamedItem,
    tmnxSysSnmpSrcAccessLstRowStatus RowStatus,
    tmnxSysSnmpSrcAccessLstLastChg   TimeStamp
}

tmnxSysSnmpSrcAccessLstName      OBJECT-TYPE
    SYNTAX      TNamedItem
    MAX-ACCESS  not-accessible
    STATUS      current
    DESCRIPTION
        "The value of tmnxSysSnmpSrcAccessLstName specifies the name given to
         this src-access-list."
    ::= { tmnxSysSnmpSrcAccessLstEntry 1 }

tmnxSysSnmpSrcAccessLstRowStatus OBJECT-TYPE
    SYNTAX      RowStatus
    MAX-ACCESS  read-create
    STATUS      current
    DESCRIPTION
        "The value of tmnxSysSnmpSrcAccessLstRowStatus specifies the row status
         used for creation and deletion of src-access-list entries."
    ::= { tmnxSysSnmpSrcAccessLstEntry 2 }

tmnxSysSnmpSrcAccessLstLastChg   OBJECT-TYPE
    SYNTAX      TimeStamp
    MAX-ACCESS  read-only
    STATUS      current
    DESCRIPTION
        "The value of tmnxSysSnmpSrcAccessLstLastChg indicates the sysUpTime at
         the time of the last modification of this row.

         If no changes were made to the row since the last re-initialization of
         the local network management subsystem, then this object contains the
         value zero."
    ::= { tmnxSysSnmpSrcAccessLstEntry 3 }

tmnxSysSnmpStatsObjs             OBJECT IDENTIFIER ::= { tmnxSysSnmpSrcAccessObjs 2 }

tmnxSysSnmpCommunityStatsTable   OBJECT-TYPE
    SYNTAX      SEQUENCE OF TmnxSysSnmpCommunityStatsEntry
    MAX-ACCESS  not-accessible
    STATUS      current
    DESCRIPTION
        "The tmnxSysSnmpCommunityStatsTable contains statistics for SNMP
         Community."
    ::= { tmnxSysSnmpStatsObjs 1 }

tmnxSysSnmpCommunityStatsEntry   OBJECT-TYPE
    SYNTAX      TmnxSysSnmpCommunityStatsEntry
    MAX-ACCESS  not-accessible
    STATUS      current
    DESCRIPTION
        "Each row entry represents a collection of statistics for each SNMP
         Community within a virtual router.

         Entries cannot be created and deleted via SNMP SET operations."
    AUGMENTS    { snmpCommunityEntry }
    ::= { tmnxSysSnmpCommunityStatsTable 1 }

TmnxSysSnmpCommunityStatsEntry   ::= SEQUENCE
{ tmnxSysSnmpCommunityPktDropped   Gauge32 }

tmnxSysSnmpCommunityPktDropped   OBJECT-TYPE
    SYNTAX      Gauge32
    MAX-ACCESS  read-only
    STATUS      current
    DESCRIPTION
        "The value of tmnxSysSnmpCommunityPktDropped indicates the total number
         of packets dropped when a SNMP GET request has been made."
    ::= { tmnxSysSnmpCommunityStatsEntry 1 }

tmnxSysMgmtProtocolObjs          OBJECT IDENTIFIER ::= { tmnxSysObjs 33 }

tmnxSysMgmtProtocolTblLstChng    OBJECT-TYPE
    SYNTAX      TimeStamp
    MAX-ACCESS  read-only
    STATUS      current
    DESCRIPTION
        "The value of tmnxSysMgmtProtocolTblLstChng indicates the sysUpTime at
         the time of the last modification to tmnxSysMgmtProtocolTable by
         change to a writable object in the table.

         If no changes were made to the table since the last re-initialization
         of the local network management subsystem, then this object contains a
         zero value."
    ::= { tmnxSysMgmtProtocolObjs 1 }

tmnxSysMgmtProtocolTable         OBJECT-TYPE
    SYNTAX      SEQUENCE OF TmnxSysMgmtProtocolEntry
    MAX-ACCESS  not-accessible
    STATUS      current
    DESCRIPTION
        "The tmnxSysMgmtProtocolTable contains objects for managing the
         capabilities of the different network management protocols."
    ::= { tmnxSysMgmtProtocolObjs 2 }

tmnxSysMgmtProtocolEntry         OBJECT-TYPE
    SYNTAX      TmnxSysMgmtProtocolEntry
    MAX-ACCESS  not-accessible
    STATUS      current
    DESCRIPTION
        "The tmnxSysMgmtProtocolEntry contains configuration items for managing
         the different network management protocols.

         Entries in this table cannot be created or deleted."
    INDEX       { tmnxSysMgmtProtocol }
    ::= { tmnxSysMgmtProtocolTable 1 }

TmnxSysMgmtProtocolEntry         ::= SEQUENCE
{
    tmnxSysMgmtProtocol              INTEGER,
    tmnxSysMgmtProtLastChange        TimeStamp,
    tmnxSysMgmtAllowImmediateChange  TruthValue,
    tmnxSysMgmtCliEngine1            TmnxCliEngine,
    tmnxSysMgmtCliEngine2            TmnxCliEngine
}

tmnxSysMgmtProtocol              OBJECT-TYPE
    SYNTAX      INTEGER {
        cli (0)
    }
    MAX-ACCESS  not-accessible
    STATUS      current
    DESCRIPTION
        "The value of tmnxSysMgmtProtocol specifies the name of the network
         management protocol to which this row applies."
    ::= { tmnxSysMgmtProtocolEntry 1 }

tmnxSysMgmtProtLastChange        OBJECT-TYPE
    SYNTAX      TimeStamp
    MAX-ACCESS  read-only
    STATUS      current
    DESCRIPTION
        "The value of tmnxSysMgmtProtLastChange indicates the sysUpTime at the
         time of the last modification of this row.

         If no changes were made to the row since the last re-initialization of
         the local network management subsystem, then this object contains the
         value zero."
    ::= { tmnxSysMgmtProtocolEntry 2 }

tmnxSysMgmtAllowImmediateChange  OBJECT-TYPE
    SYNTAX      TruthValue
    MAX-ACCESS  read-create
    STATUS      current
    DESCRIPTION
        "The value of tmnxSysMgmtAllowImmediateChange specifies whether the
         user is allowed to make direct changes to the configuration, or
         whether all changes need to be applied through use of a candidate
         config."
    DEFVAL      { true }
    ::= { tmnxSysMgmtProtocolEntry 3 }

tmnxSysMgmtCliEngine1            OBJECT-TYPE
    SYNTAX      TmnxCliEngine
    MAX-ACCESS  read-create
    STATUS      current
    DESCRIPTION
        "The value of tmnxSysMgmtCliEngine1 specifies the CLI engine that is
         active when a user logs in.

         Value systemDerived specifies that the CLI engine is derived
         from the current value of tmnxSysMgmtIfWriteMode:
           tmnxSysMgmtIfWriteMode  ->  CLI engine
           ----------------------      ---------------------
           classic                 ->  Classic CLI
           modelDriven             ->  MD CLI
           mixed                   ->  MD CLI

         Both tmnxSysMgmtCliEngine1 and tmnxSysMgmtCliEngine2 must be present
         in the same set request."
    DEFVAL      { systemDerived }
    ::= { tmnxSysMgmtProtocolEntry 4 }

tmnxSysMgmtCliEngine2            OBJECT-TYPE
    SYNTAX      TmnxCliEngine
    MAX-ACCESS  read-create
    STATUS      current
    DESCRIPTION
        "The value of tmnxSysMgmtCliEngine2 specifies the secondary CLI engine
         that is accessible to a logged-in user.

         Value systemDerived specifies that the user does not have access to
         secondary engine (i.e.: can only access engine specified by
         tmnxSysMgmtCliEngine1).

         Values other than systemDerived are used only if tmnxSysMgmtCliEngine1
         also has value other than systemDerived and must differ from that
         value.

         Both tmnxSysMgmtCliEngine1 and tmnxSysMgmtCliEngine2 must be present
         in the same set request."
    DEFVAL      { systemDerived }
    ::= { tmnxSysMgmtProtocolEntry 5 }

tmnxSysFileTransProfObjs         OBJECT IDENTIFIER ::= { tmnxSysObjs 34 }

tmnxSysFileTransProfTableLstChgd OBJECT-TYPE
    SYNTAX      TimeStamp
    MAX-ACCESS  read-only
    STATUS      current
    DESCRIPTION
        "The value of tmnxSysFileTransProfTableLstChgd indicates the time,
         since system startup, when tmnxSysFileTransProfTable last changed
         configuration.

         A value of zero indicates that no changes were made to this table
         since the system was last initialized."
    ::= { tmnxSysFileTransProfObjs 1 }

tmnxSysFileTransProfTable        OBJECT-TYPE
    SYNTAX      SEQUENCE OF TmnxSysFileTransProfEntry
    MAX-ACCESS  not-accessible
    STATUS      current
    DESCRIPTION
        "The tmnxSysFileTransProfTable contains objects used to configure
         instances of the file transmission profile, which are used by a device
         to download files from a server (e.g. File Transfer Protocol (FTP)
         server or Hypertext Transfer Protocol(HTTP) server).

         A file transmission profile specifies 1) the local configuration for
         sending and receiving a file in an Nokia SROS device; and 2) the
         behaviours of the device when the transmission fails.

         Usage example:
             Auto Certificate Revocation List (CRL) retrieval: downloading
             CRL from a FTP or an HTTP server to an Nokia SROS device.

         Entries in this table are created and deleted via SNMP set operations
         to tmnxSysFileTransProfRowStatus."
    ::= { tmnxSysFileTransProfObjs 2 }

tmnxSysFileTransProfEntry        OBJECT-TYPE
    SYNTAX      TmnxSysFileTransProfEntry
    MAX-ACCESS  not-accessible
    STATUS      current
    DESCRIPTION
        "Each tmnxSysFileTransProfEntry contains the configuration for one file
         transmission profile."
    INDEX       { tmnxSysFileTransProfName }
    ::= { tmnxSysFileTransProfTable 1 }

TmnxSysFileTransProfEntry        ::= SEQUENCE
{
    tmnxSysFileTransProfName         TNamedItem,
    tmnxSysFileTransProfRowStatus    RowStatus,
    tmnxSysFileTransProfLastChanged  TimeStamp,
    tmnxSysFileTransProfRtrId        TmnxVRtrIDOrZero,
    tmnxSysFileTransProfSvcId        TmnxServId,
    tmnxSysFileTransProfSrcAddrV4T   InetAddressType,
    tmnxSysFileTransProfSrcAddrV4    InetAddress,
    tmnxSysFileTransProfSrcAddrV6T   InetAddressType,
    tmnxSysFileTransProfSrcAddrV6    InetAddress,
    tmnxSysFileTransProfTimeout      Unsigned32,
    tmnxSysFileTransProfRetry        Unsigned32,
    tmnxSysFileTransProfRedirection  Unsigned32,
    tmnxSysFileTransProfSvcName      TLNamedItemOrEmpty,
    tmnxSysFileTransProfHttpVersion  INTEGER
}

tmnxSysFileTransProfName         OBJECT-TYPE
    SYNTAX      TNamedItem
    MAX-ACCESS  not-accessible
    STATUS      current
    DESCRIPTION
        "The value of tmnxSysFileTransProfName uniquely specifies one file
         transmission profile configured on this system."
    ::= { tmnxSysFileTransProfEntry 1 }

tmnxSysFileTransProfRowStatus    OBJECT-TYPE
    SYNTAX      RowStatus
    MAX-ACCESS  read-create
    STATUS      current
    DESCRIPTION
        "The value of tmnxSysFileTransProfRowStatus specifies the status of
         this row. It is used to create and delete row entries in
         tmnxSysFileTransProfTable."
    ::= { tmnxSysFileTransProfEntry 2 }

tmnxSysFileTransProfLastChanged  OBJECT-TYPE
    SYNTAX      TimeStamp
    MAX-ACCESS  read-only
    STATUS      current
    DESCRIPTION
        "The value of tmnxSysFileTransProfLastChanged indicates the time, since
         system startup, that the configuration of this row was created or
         modified."
    ::= { tmnxSysFileTransProfEntry 3 }

tmnxSysFileTransProfRtrId        OBJECT-TYPE
    SYNTAX      TmnxVRtrIDOrZero
    MAX-ACCESS  read-create
    STATUS      current
    DESCRIPTION
        "The value of tmnxSysFileTransProfRtrId specifies the virtual router
         instance. The file transmission connection(s) will be established
         between the virtual router and a server (e.g. FTP or HTTP server).

         Exactly one of tmnxSysFileTransProfSvcName, tmnxSysFileTransProfSvcId
         and tmnxSysFileTransProfRtrId must be configured to a non-default
         value. For example, when the value of tmnxSysFileTransProfRtrId is
         zero, the virtual router must be specified using
         tmnxSysFileTransProfSvcId or tmnxSysFileTransProfSvcName.

         Only those IDs corresponding to the 'Base' and 'management' virtual
         routers may be set in this object. Refer to
         TIMETRA-VRTR-MIB.mib::vRtrName."
    DEFVAL      { 1 }
    ::= { tmnxSysFileTransProfEntry 4 }

tmnxSysFileTransProfSvcId        OBJECT-TYPE
    SYNTAX      TmnxServId (0..2147483647)
    MAX-ACCESS  read-create
    STATUS      current
    DESCRIPTION
        "The value of tmnxSysFileTransProfSvcId specifies the service
         identifier for a virtual router. The file transmission connection(s)
         will be established between the virtual router and a server (e.g. FTP
         or HTTP server).

         Exactly one of tmnxSysFileTransProfSvcName, tmnxSysFileTransProfSvcId
         and tmnxSysFileTransProfRtrId must be configured to a non-default
         value. For example, when the value of tmnxSysFileTransProfSvcId is
         zero, the virtual router must be specified using
         tmnxSysFileTransProfSvcName or tmnxSysFileTransProfRtrId.

         Only VPRN service IDs are allowed."
    DEFVAL      { 0 }
    ::= { tmnxSysFileTransProfEntry 5 }

tmnxSysFileTransProfSrcAddrV4T   OBJECT-TYPE
    SYNTAX      InetAddressType
    MAX-ACCESS  read-create
    STATUS      current
    DESCRIPTION
        "The value of tmnxSysFileTransProfSrcAddrV4T specifies the IP address
         type of tmnxSysFileTransProfSrcAddrV4.

         The value of tmnxSysFileTransProfSrcAddrV4T can be either of 'ipv4(1)'
         or 'unknown (0)'.

         The value of 'unknown(0)' specifies no IPv4 source address is
         configured."
    DEFVAL      { unknown }
    ::= { tmnxSysFileTransProfEntry 6 }

tmnxSysFileTransProfSrcAddrV4    OBJECT-TYPE
    SYNTAX      InetAddress (SIZE (0|4))
    MAX-ACCESS  read-create
    STATUS      current
    DESCRIPTION
        "The value of tmnxSysFileTransProfSrcAddrV4 specifies the IPv4 source
         address specified in tmnxSysFileTransProfRtrId.

         The value of an empty string specifies no IPv4 source address is
         configured."
    DEFVAL      { ''H }
    ::= { tmnxSysFileTransProfEntry 7 }

tmnxSysFileTransProfSrcAddrV6T   OBJECT-TYPE
    SYNTAX      InetAddressType
    MAX-ACCESS  read-create
    STATUS      current
    DESCRIPTION
        "The value of tmnxSysFileTransProfSrcAddrV6T specifies the IP address
         type of tmnxSysFileTransProfSrcAddrV6.

         The value of tmnxSysFileTransProfSrcAddrV6T can be either of 'ipv6(2)'
         or 'unknown (0)'.

         The value of 'unknown(0)' specifies no IPv6 source address is
         configured."
    DEFVAL      { unknown }
    ::= { tmnxSysFileTransProfEntry 8 }

tmnxSysFileTransProfSrcAddrV6    OBJECT-TYPE
    SYNTAX      InetAddress (SIZE (0|16))
    MAX-ACCESS  read-create
    STATUS      current
    DESCRIPTION
        "The value of tmnxSysFileTransProfSrcAddrV6 specifies the IPv6 source
         address specified in tmnxSysFileTransProfRtrId.

         The value of an empty string specifies no IPv6 source address is
         configured."
    DEFVAL      { ''H }
    ::= { tmnxSysFileTransProfEntry 9 }

tmnxSysFileTransProfTimeout      OBJECT-TYPE
    SYNTAX      Unsigned32 (1..3600)
    UNITS       "seconds"
    MAX-ACCESS  read-create
    STATUS      current
    DESCRIPTION
        "The value of tmnxSysFileTransProfTimeout specifies the connection
         timeout (in seconds) for the file transmission.

         The timeout is the maximum waiting time to receive any data from the
         server (e.g. FTP or HTTP server)."
    DEFVAL      { 60 }
    ::= { tmnxSysFileTransProfEntry 10 }

tmnxSysFileTransProfRetry        OBJECT-TYPE
    SYNTAX      Unsigned32 (0..256)
    MAX-ACCESS  read-create
    STATUS      current
    DESCRIPTION
        "The value of tmnxSysFileTransProfRetry specifies the number of retries
         of the file transmission profile.

         When the virtual router does not receive any data from a server (e.g.
         FTP or HTTP server) after the configured tmnxSysFileTransProfTimeout
         interval, the router may repeat the request to the server. The number
         of retries specifies the maximum number of repeated requests.

         Virtual router instances are configured using
         tmnxSysFileTransProfRtrId.

         The value of zero specifies that the request should not be resent by
         the virtual router after the configured tmnxSysFileTransProfTimeout
         interval elapsed."
    DEFVAL      { 0 }
    ::= { tmnxSysFileTransProfEntry 11 }

tmnxSysFileTransProfRedirection  OBJECT-TYPE
    SYNTAX      Unsigned32 (0..8)
    MAX-ACCESS  read-create
    STATUS      current
    DESCRIPTION
        "The value of tmnxSysFileTransProfRedirection specifies the maximum
         level of redirection of the file transmission profile.

         The virtual router may send a new request to another server if the
         requested resources are not available (e.g. temporarily available to
         another server).

         Usage example:
           When a virtual router receives an HTTP response with status code of
           redirection 3xx (e.g. 301 Moved Permanently), the router may send
           a new request to another location. The level of redirection specifies
           the maximum number of new requests that can be sent by a virtual
           router.

         For any file transmission protocols (e.g. FTP), which do not support
         redirection, the value of tmnxSysFileTransProfRedirection will be
         ignored.

         The value of zero specifies that no new request should be sent by a
         virtual router to another server."
    REFERENCE
        "RFC 2616, 'Hypertext Transfer Protocol -- HTTP/1.1', IETF, June 1999,
         section 10.3 'Redirection 3xx'."
    DEFVAL      { 0 }
    ::= { tmnxSysFileTransProfEntry 12 }

tmnxSysFileTransProfSvcName      OBJECT-TYPE
    SYNTAX      TLNamedItemOrEmpty
    MAX-ACCESS  read-create
    STATUS      current
    DESCRIPTION
        "The value of tmnxSysFileTransProfSvcName specifies the service name
         for a virtual router. The file transmission connection(s) will be
         established between the virtual router and a server (e.g. FTP or HTTP
         server).

         Exactly one of tmnxSysFileTransProfSvcName, tmnxSysFileTransProfSvcId
         and tmnxSysFileTransProfRtrId must be configured to a non-default
         value. For example, when the value of tmnxSysFileTransProfSvcName is
         an empty string, the virtual router must be specified using
         tmnxSysFileTransProfSvcId or tmnxSysFileTransProfRtrId.

         Only VPRN service names are allowed."
    DEFVAL      { ''H }
    ::= { tmnxSysFileTransProfEntry 13 }

tmnxSysFileTransProfHttpVersion  OBJECT-TYPE
    SYNTAX      INTEGER {
        v10 (1),
        v11 (2)
    }
    MAX-ACCESS  read-create
    STATUS      current
    DESCRIPTION
        "The value of tmnxSysFileTransProfHttpVersion specifies the HTTP
         version to be used by this file transmission profile."
    DEFVAL      { v11 }
    ::= { tmnxSysFileTransProfEntry 14 }

tmnxEhsExtObjs                   OBJECT IDENTIFIER ::= { tmnxSysObjs 35 }

tmnxSmLaunchExtTable             OBJECT-TYPE
    SYNTAX      SEQUENCE OF TmnxSmLaunchExtEntry
    MAX-ACCESS  not-accessible
    STATUS      current
    DESCRIPTION
        "The tmnxSmLaunchExtTable is an extension of the
         DISMAN-SCRIPT-MIB::smLaunchTable."
    ::= { tmnxEhsExtObjs 1 }

tmnxSmLaunchExtEntry             OBJECT-TYPE
    SYNTAX      TmnxSmLaunchExtEntry
    MAX-ACCESS  not-accessible
    STATUS      current
    DESCRIPTION
        "Each row entry represents contains additional attributes for the
         smLaunchEntry.

         Entries cannot be created and deleted via SNMP SET operations."
    AUGMENTS    { smLaunchEntry }
    ::= { tmnxSmLaunchExtTable 1 }

TmnxSmLaunchExtEntry             ::= SEQUENCE
{
    tmnxSmLaunchExtAuthType          TmnxScriptAuthType,
    tmnxSmLaunchExtLockOverride      TruthValue
}

tmnxSmLaunchExtAuthType          OBJECT-TYPE
    SYNTAX      TmnxScriptAuthType
    MAX-ACCESS  read-only
    STATUS      current
    DESCRIPTION
        "The value of tmnxSmLaunchExtAuthType indicates the module
         that last started a script by writing to
         DISMAN-SCRIPT-MIB::smLaunchStart.  If no script has yet
         been started the value 'none(0)' is returned."
    ::= { tmnxSmLaunchExtEntry 1 }

tmnxSmLaunchExtLockOverride      OBJECT-TYPE
    SYNTAX      TruthValue
    MAX-ACCESS  read-create
    STATUS      current
    DESCRIPTION
        "If true script run is able to override explicit lock of MD database.
         Hence giving priority to EHS/Cron script runs."
    DEFVAL      { false }
    ::= { tmnxSmLaunchExtEntry 2 }

tmnxSmRunExtTable                OBJECT-TYPE
    SYNTAX      SEQUENCE OF TmnxSmRunExtEntry
    MAX-ACCESS  not-accessible
    STATUS      current
    DESCRIPTION
        "The tmnxSmRunExtTable is an extension of the
         DISMAN-SCRIPT-MIB::smRunTable."
    ::= { tmnxEhsExtObjs 2 }

tmnxSmRunExtEntry                OBJECT-TYPE
    SYNTAX      TmnxSmRunExtEntry
    MAX-ACCESS  not-accessible
    STATUS      current
    DESCRIPTION
        "Each row entry represents contains additional attributes for the
         smRunEntry.

         Entries cannot be created and deleted via SNMP SET operations."
    AUGMENTS    { smRunEntry }
    ::= { tmnxSmRunExtTable 1 }

TmnxSmRunExtEntry                ::= SEQUENCE
{
    tmnxSmRunExtAuthType             TmnxScriptAuthType,
    tmnxSmRunExtUserName             TNamedItemOrEmpty
}

tmnxSmRunExtAuthType             OBJECT-TYPE
    SYNTAX      TmnxScriptAuthType
    MAX-ACCESS  read-only
    STATUS      current
    DESCRIPTION
        "The value of tmnxSmRunExtAuthType indicates the module
         that started this run of a script by writing to
         DISMAN-SCRIPT-MIB::smLaunchStart.  If no script has yet
         been started the value 'none(0)' is returned."
    ::= { tmnxSmRunExtEntry 1 }

tmnxSmRunExtUserName             OBJECT-TYPE
    SYNTAX      TNamedItemOrEmpty
    MAX-ACCESS  read-only
    STATUS      current
    DESCRIPTION
        "The value of tmnxSmRunExtUserName indicates the name of
         the user account used to check access to CLI commands while
         executing the script.  If no script has yet been started
         the empty string is returned."
    ::= { tmnxSmRunExtEntry 2 }

tmnxSmRunArgsTable               OBJECT-TYPE
    SYNTAX      SEQUENCE OF TmnxSmRunArgsEntry
    MAX-ACCESS  not-accessible
    STATUS      current
    DESCRIPTION
        "The tmnxSmRunArgsTable contains information pertaining to the
         arguments passed to the exec script."
    ::= { tmnxEhsExtObjs 3 }

tmnxSmRunArgsEntry               OBJECT-TYPE
    SYNTAX      TmnxSmRunArgsEntry
    MAX-ACCESS  not-accessible
    STATUS      current
    DESCRIPTION
        "The tmnxSmRunArgsEntry provides the argument information for a
         specified exec script."
    INDEX       {
        smLaunchOwner,
        smLaunchName,
        smRunIndex,
        tmnxSmRunEventArgIndex
    }
    ::= { tmnxSmRunArgsTable 1 }

TmnxSmRunArgsEntry               ::= SEQUENCE
{
    tmnxSmRunEventArgIndex           Unsigned32,
    tmnxSmRunEventArgName            TLNamedItem,
    tmnxSmRunEventArgValue           OCTET STRING
}

tmnxSmRunEventArgIndex           OBJECT-TYPE
    SYNTAX      Unsigned32
    MAX-ACCESS  not-accessible
    STATUS      current
    DESCRIPTION
        "The value of tmnxSmRunEventArgIndex specifies the argument index
         number associated with a particular tmnxSmRunArgsEntry."
    ::= { tmnxSmRunArgsEntry 1 }

tmnxSmRunEventArgName            OBJECT-TYPE
    SYNTAX      TLNamedItem
    MAX-ACCESS  read-only
    STATUS      current
    DESCRIPTION
        "The value of tmnxSmRunEventArgName indicates the name of an argument
         passed to the exec script."
    ::= { tmnxSmRunArgsEntry 2 }

tmnxSmRunEventArgValue           OBJECT-TYPE
    SYNTAX      OCTET STRING (SIZE (0..2001))
    MAX-ACCESS  read-only
    STATUS      current
    DESCRIPTION
        "The value of tmnxSmRunEventArgValue indicates the ASCII printable
         contents of the specified argument passed to the exec script."
    ::= { tmnxSmRunArgsEntry 3 }

tmnxSysSwReposObjs               OBJECT IDENTIFIER ::= { tmnxSysObjs 36 }

tmnxSysSwReposTableLastChanged   OBJECT-TYPE
    SYNTAX      TimeStamp
    MAX-ACCESS  read-only
    STATUS      current
    DESCRIPTION
        "The value of tmnxSysSwReposTableLastChanged indicates the time, since
         system startup, when tmnxSysSoftwareRepositoryTable last changed
         configuration."
    ::= { tmnxSysSwReposObjs 1 }

tmnxSysSoftwareRepositoryTable   OBJECT-TYPE
    SYNTAX      SEQUENCE OF TmnxSysSoftwareRepositoryEntry
    MAX-ACCESS  not-accessible
    STATUS      current
    DESCRIPTION
        "The tmnxSysSoftwareRepositoryTable contains configuration information
         about the system software repositories for extension chassis."
    ::= { tmnxSysSwReposObjs 2 }

tmnxSysSoftwareRepositoryEntry   OBJECT-TYPE
    SYNTAX      TmnxSysSoftwareRepositoryEntry
    MAX-ACCESS  not-accessible
    STATUS      current
    DESCRIPTION
        "The tmnxSysSoftwareRepositoryEntry consists of the configurable
         objects for the system software repositories."
    INDEX       { tmnxSysSwReposName }
    ::= { tmnxSysSoftwareRepositoryTable 1 }

TmnxSysSoftwareRepositoryEntry   ::= SEQUENCE
{
    tmnxSysSwReposName               TNamedItem,
    tmnxSysSwReposRowStatus          RowStatus,
    tmnxSysSwReposLastChanged        TimeStamp,
    tmnxSysSwReposDescription        TItemDescription,
    tmnxSysSwReposPrimaryLocation    TmnxDisplayStringURL,
    tmnxSysSwReposSecondaryLocation  TmnxDisplayStringURL,
    tmnxSysSwReposTertiaryLocation   TmnxDisplayStringURL
}

tmnxSysSwReposName               OBJECT-TYPE
    SYNTAX      TNamedItem
    MAX-ACCESS  not-accessible
    STATUS      current
    DESCRIPTION
        "The value of tmnxSysSwReposName specifies a unique name which
         identifies the system software repository."
    ::= { tmnxSysSoftwareRepositoryEntry 1 }

tmnxSysSwReposRowStatus          OBJECT-TYPE
    SYNTAX      RowStatus
    MAX-ACCESS  read-create
    STATUS      current
    DESCRIPTION
        "The value of tmnxSysSwReposRowStatus specifies the row status. It
         allows the creation and deletion of rows in
         tmnxSysSoftwareRepositoryTable."
    ::= { tmnxSysSoftwareRepositoryEntry 2 }

tmnxSysSwReposLastChanged        OBJECT-TYPE
    SYNTAX      TimeStamp
    MAX-ACCESS  read-only
    STATUS      current
    DESCRIPTION
        "The value of tmnxSysSwReposLastChanged indicates the time, since
         system startup, that the configuration of the system software
         repository was created or modified."
    ::= { tmnxSysSoftwareRepositoryEntry 3 }

tmnxSysSwReposDescription        OBJECT-TYPE
    SYNTAX      TItemDescription
    MAX-ACCESS  read-create
    STATUS      current
    DESCRIPTION
        "The value of tmnxSysSwReposDescription specifies the description of
         the system software repository.

         An empty string indicates this object has not been configured."
    DEFVAL      { ''H }
    ::= { tmnxSysSoftwareRepositoryEntry 4 }

tmnxSysSwReposPrimaryLocation    OBJECT-TYPE
    SYNTAX      TmnxDisplayStringURL
    MAX-ACCESS  read-create
    STATUS      current
    DESCRIPTION
        "The value of tmnxSysSwReposPrimaryLocation specifies the primary
         location of the directory that contains the runtime image files for
         the system software repository.

         An empty string indicates this object has not been configured."
    DEFVAL      { ''H }
    ::= { tmnxSysSoftwareRepositoryEntry 5 }

tmnxSysSwReposSecondaryLocation  OBJECT-TYPE
    SYNTAX      TmnxDisplayStringURL
    MAX-ACCESS  read-create
    STATUS      current
    DESCRIPTION
        "The value of tmnxSysSwReposSecondaryLocation specifies the secondary
         location of the directory that contains the runtime image files for
         the system software repository.

         An empty string indicates this object has not been configured."
    DEFVAL      { ''H }
    ::= { tmnxSysSoftwareRepositoryEntry 6 }

tmnxSysSwReposTertiaryLocation   OBJECT-TYPE
    SYNTAX      TmnxDisplayStringURL
    MAX-ACCESS  read-create
    STATUS      current
    DESCRIPTION
        "The value of tmnxSysSwReposTertiaryLocation specifies the tertiary
         location of the directory that contains the runtime image files for
         the system software repository.

         An empty string indicates this object has not been configured."
    DEFVAL      { ''H }
    ::= { tmnxSysSoftwareRepositoryEntry 7 }

tmnxSysNspProxyInfo              OBJECT IDENTIFIER ::= { tmnxSysObjs 37 }

tmnxLastSystemRebootSaveInfo     OBJECT IDENTIFIER ::= { tmnxSysObjs 38 }

tmnxLastSystemRebootReason       OBJECT-TYPE
    SYNTAX      INTEGER {
        admin (1),
        other (2)
    }
    MAX-ACCESS  read-only
    STATUS      current
    DESCRIPTION
        "The value of tmnxLastSystemRebootReason indicates the reason for the
         last reboot.

         Values:
             admin (1) - Indicates the last reboot was initiated by admin
             other (2) - Indicates the last reboot was initiated by other means"
    ::= { tmnxLastSystemRebootSaveInfo 1 }

tmnxLastSystemRebootTime         OBJECT-TYPE
    SYNTAX      DateAndTime
    MAX-ACCESS  read-only
    STATUS      current
    DESCRIPTION
        "The value of tmnxLastSystemRebootTime indicates the recorded date and
         time of the last reboot. This field is only valid if
         tmnxLastSystemRebootReason is 'admin (1)'"
    ::= { tmnxLastSystemRebootSaveInfo 2 }

tmnxLastSystemRebootUser         OBJECT-TYPE
    SYNTAX      DisplayString
    MAX-ACCESS  read-only
    STATUS      current
    DESCRIPTION
        "The value of tmnxLastSystemRebootUser indicates the user who initiated
         the last reboot. This field is only valid if
         tmnxLastSystemRebootReason is 'admin (1)'"
    ::= { tmnxLastSystemRebootSaveInfo 3 }

tmnxLastSystemRebootUserAddrType OBJECT-TYPE
    SYNTAX      InetAddressType
    MAX-ACCESS  read-only
    STATUS      current
    DESCRIPTION
        "The value of tmnxLastSystemRebootUserAddrType indicates the address
         type of tmnxLastSystemRebootUserAddress. This field is only valid if
         tmnxLastSystemRebootReason is 'admin (1)'"
    ::= { tmnxLastSystemRebootSaveInfo 4 }

tmnxLastSystemRebootUserAddress  OBJECT-TYPE
    SYNTAX      InetAddress (SIZE (0|4|16))
    MAX-ACCESS  read-only
    STATUS      current
    DESCRIPTION
        "The value of tmnxLastSystemRebootUserAddress indicates the IP address
         of the user who initiated the last reboot. This field is only valid if
         tmnxLastSystemRebootReason is 'admin (1)'"
    ::= { tmnxLastSystemRebootSaveInfo 5 }

tmnxLastSystemRebootRouter       OBJECT-TYPE
    SYNTAX      DisplayString
    MAX-ACCESS  read-only
    STATUS      current
    DESCRIPTION
        "The value of tmnxLastSystemRebootRouter indicates the router or
         service name of the management session which initiated the last
         reboot."
    ::= { tmnxLastSystemRebootSaveInfo 6 }

tmnxSysGrpcInfo                  OBJECT IDENTIFIER ::= { tmnxSysObjs 39 }

tmnxSysGrpcAdminState            OBJECT-TYPE
    SYNTAX      TmnxAdminState
    MAX-ACCESS  read-write
    STATUS      current
    DESCRIPTION
        "The value of tmnxSysGrpcAdminState specifies the desired
         administrative state of the gRPC server."
    DEFVAL      { outOfService }
    ::= { tmnxSysGrpcInfo 1 }

tmnxSysGrpcOperState             OBJECT-TYPE
    SYNTAX      TmnxOperState
    MAX-ACCESS  read-only
    STATUS      current
    DESCRIPTION
        "The value of tmnxSysGrpcOperState indicates the current operational
         state of gRPC server."
    ::= { tmnxSysGrpcInfo 2 }

tmnxSysGrpcTlsServerProfile      OBJECT-TYPE
    SYNTAX      TNamedItemOrEmpty
    MAX-ACCESS  read-write
    STATUS      current
    DESCRIPTION
        "The value of tmnxSysGrpcTlsServerProfile specifies the name of the TLS
         server profile to be used."
    DEFVAL      { ''H }
    ::= { tmnxSysGrpcInfo 3 }

tmnxSysGrpcMaxMsgSize            OBJECT-TYPE
    SYNTAX      Unsigned32 (1..1024)
    UNITS       "megabytes"
    MAX-ACCESS  read-write
    STATUS      current
    DESCRIPTION
        "The value of tmnxSysGrpcMaxMsgSize specifies the maximum size of the
         received decompressed serialized protobuf message without metadata."
    DEFVAL      { 512 }
    ::= { tmnxSysGrpcInfo 4 }

tmnxSysGrpcAutoCfgSave           OBJECT-TYPE
    SYNTAX      TruthValue
    MAX-ACCESS  read-write
    STATUS      current
    DESCRIPTION
        "The value of tmnxSysGrpcAutoCfgSave specifies whether the running
         configuration is saved as part of a commit operation initiated from
         gRPC."
    DEFVAL      { true }
    ::= { tmnxSysGrpcInfo 5 }

tmnxSysGrpcGnmiVersion           OBJECT-TYPE
    SYNTAX      DisplayString (SIZE (1..10))
    MAX-ACCESS  read-only
    STATUS      current
    DESCRIPTION
        "The value of tmnxSysGrpcGnmiVersion indicates the version of gNMI
         service provided by gRPC server."
    ::= { tmnxSysGrpcInfo 6 }

tmnxSysGrpcAllowUnsecure         OBJECT-TYPE
    SYNTAX      TruthValue
    MAX-ACCESS  read-write
    STATUS      current
    DESCRIPTION
        "The value of tmnxSysGrpcAllowUnsecure specifies whether gRPC server
         will run without secured transport protocol. Username and password
         will be transferred in unencrypted form with each RPC request."
    DEFVAL      { false }
    ::= { tmnxSysGrpcInfo 7 }

tmnxSysGrpcGnmiAdminState        OBJECT-TYPE
    SYNTAX      TmnxAdminState
    MAX-ACCESS  read-write
    STATUS      current
    DESCRIPTION
        "The value of tmnxSysGrpcGnmiAdminState specifies the desired
         administrative state of the gNMI service."
    DEFVAL      { inService }
    ::= { tmnxSysGrpcInfo 8 }

tmnxSysGrpcTcpKaAdminState       OBJECT-TYPE
    SYNTAX      TmnxAdminState
    MAX-ACCESS  read-write
    STATUS      current
    DESCRIPTION
        "The value of tmnxSysGrpcTcpKaAdminState specifies the administrative
         state of the TCP keepalive algorithm."
    DEFVAL      { outOfService }
    ::= { tmnxSysGrpcInfo 9 }

tmnxSysGrpcTcpKaIdle             OBJECT-TYPE
    SYNTAX      Unsigned32 (1..100000)
    UNITS       "seconds"
    MAX-ACCESS  read-write
    STATUS      current
    DESCRIPTION
        "The value of the object tmnxSysGrpcTcpKaIdle specifies the number of
         seconds until the first TCP keepalive probe is sent."
    DEFVAL      { 600 }
    ::= { tmnxSysGrpcInfo 10 }

tmnxSysGrpcTcpKaInterval         OBJECT-TYPE
    SYNTAX      Unsigned32 (1..100000)
    UNITS       "seconds"
    MAX-ACCESS  read-write
    STATUS      current
    DESCRIPTION
        "The value of the object tmnxSysGrpcTcpKaInterval specifies the number
         of seconds between two TCP keepalives probes."
    DEFVAL      { 15 }
    ::= { tmnxSysGrpcInfo 11 }

tmnxSysGrpcTcpKaCount            OBJECT-TYPE
    SYNTAX      Unsigned32 (3..100)
    UNITS       "seconds"
    MAX-ACCESS  read-write
    STATUS      current
    DESCRIPTION
        "The value of the object tmnxSysGrpcTcpKaCount specifies the number of
         missed keepalives before the TCP connection is declared down."
    DEFVAL      { 4 }
    ::= { tmnxSysGrpcInfo 12 }

tmnxSysGrpcRibApiAdminState      OBJECT-TYPE
    SYNTAX      TmnxAdminState
    MAX-ACCESS  read-write
    STATUS      current
    DESCRIPTION
        "The value of tmnxSysGrpcRibApiAdminState specifies the desired
         administrative state of the 'RibApi' service."
    DEFVAL      { outOfService }
    ::= { tmnxSysGrpcInfo 13 }

tmnxSysGrpcRibApiPurgeTimeout    OBJECT-TYPE
    SYNTAX      Unsigned32 (0..100000)
    UNITS       "seconds"
    MAX-ACCESS  read-write
    STATUS      current
    DESCRIPTION
        "The value of the object tmnxSysGrpcRibApiPurgeTimeout specifies the
         number of seconds until stale entries are purged.

         The value of zero specifies that the purge will happen immediately
         after controller disconnection is detected."
    DEFVAL      { 0 }
    ::= { tmnxSysGrpcInfo 14 }

tmnxSysGrpcRibApiVersion         OBJECT-TYPE
    SYNTAX      DisplayString (SIZE (1..10))
    MAX-ACCESS  read-only
    STATUS      current
    DESCRIPTION
        "The value of tmnxSysGrpcRibApiVersion indicates the version of RibApi
         service provided by gRPC server."
    ::= { tmnxSysGrpcInfo 15 }

tmnxSysGrpcGnoiCertMgmtAdmnState OBJECT-TYPE
    SYNTAX      TmnxAdminState
    MAX-ACCESS  read-write
    STATUS      current
    DESCRIPTION
        "The value of tmnxSysGrpcGnoiCertMgmtAdmnState specifies the desired
         administrative state of the 'gNOI CertificateManagement' service."
    DEFVAL      { outOfService }
    ::= { tmnxSysGrpcInfo 16 }

tmnxSysGrpcGnoiCertMgmtVersion   OBJECT-TYPE
    SYNTAX      DisplayString (SIZE (1..10))
    MAX-ACCESS  read-only
    STATUS      current
    DESCRIPTION
        "The value of tmnxSysGrpcGnoiCertMgmtVersion indicates the version of
         'gNOI CertificateManagement' service provided by gRPC server."
    ::= { tmnxSysGrpcInfo 17 }

tmnxSysGrpcMdCliAdminState       OBJECT-TYPE
    SYNTAX      TmnxAdminState
    MAX-ACCESS  read-write
    STATUS      current
    DESCRIPTION
        "The value of tmnxSysGrpcMdCliAdminState specifies the desired
         administrative state of the MD-CLI service."
    DEFVAL      { outOfService }
    ::= { tmnxSysGrpcInfo 18 }

tmnxSysGrpcMdCliVersion          OBJECT-TYPE
    SYNTAX      DisplayString (SIZE (1..10))
    MAX-ACCESS  read-only
    STATUS      current
    DESCRIPTION
        "The value of tmnxSysGrpcMdCliVersion indicates the version of MD-CLI
         service provided by gRPC server."
    ::= { tmnxSysGrpcInfo 19 }

tmnxSysGrpcGnoiFileAdminState    OBJECT-TYPE
    SYNTAX      TmnxAdminState
    MAX-ACCESS  read-write
    STATUS      current
    DESCRIPTION
        "The value of tmnxSysGrpcGnoiFileAdminState specifies the desired
         administrative state of the 'gNOI File' service."
    DEFVAL      { outOfService }
    ::= { tmnxSysGrpcInfo 20 }

tmnxSysGrpcGnoiFileVersion       OBJECT-TYPE
    SYNTAX      DisplayString (SIZE (1..10))
    MAX-ACCESS  read-only
    STATUS      current
    DESCRIPTION
        "The value of tmnxSysGrpcGnoiFileVersion indicates the version of 'gNOI
         File' service provided by gRPC server."
    ::= { tmnxSysGrpcInfo 21 }

tmnxSysGrpcGnoiSystemAdminState  OBJECT-TYPE
    SYNTAX      TmnxAdminState
    MAX-ACCESS  read-write
    STATUS      current
    DESCRIPTION
        "The value of tmnxSysGrpcGnoiSystemAdminState specifies the desired
         administrative state of the 'gNOI System' service."
    DEFVAL      { outOfService }
    ::= { tmnxSysGrpcInfo 22 }

tmnxSysGrpcGnoiSystemVersion     OBJECT-TYPE
    SYNTAX      DisplayString (SIZE (1..10))
    MAX-ACCESS  read-only
    STATUS      current
    DESCRIPTION
        "The value of tmnxSysGrpcGnoiSystemVersion indicates the version of
         'gNOI System' service provided by gRPC server."
    ::= { tmnxSysGrpcInfo 23 }

tmnxSysGrpcGnmiProtoVersion      OBJECT-TYPE
    SYNTAX      INTEGER {
        latest (0),
        v070   (1)
    }
    MAX-ACCESS  read-write
    STATUS      current
    DESCRIPTION
        "The value of the object tmnxSysGrpcGnmiProtoVersion specifies the
         version of gNMI service provided by gRPC server.

         Values other than 'latest' are only for backward compatibility with
         legacy collectors.

         This leaf affect also Dial-out Telemetry feature.

           'latest (0)' - Use latest supported version.
           'v070 (1)'   - Use gNMI 0.7.0 version."
    DEFVAL      { latest }
    ::= { tmnxSysGrpcInfo 24 }

tmnxSysGrpcListeningPort         OBJECT-TYPE
    SYNTAX      InetPortNumber (1024..49151 | 57400)
    MAX-ACCESS  read-write
    STATUS      current
    DESCRIPTION
        "The value of tmnxSysGrpcListeningPort specifies listening protocol TCP
         port number used by the gRPC server."
    DEFVAL      { 57400 }
    ::= { tmnxSysGrpcInfo 25 }

tmnxSysGrpcDelayOnBoot           OBJECT-TYPE
    SYNTAX      Unsigned32 (0 | 1..3600)
    UNITS       "seconds"
    MAX-ACCESS  read-write
    STATUS      current
    DESCRIPTION
        "The value of tmnxSysGrpcDelayOnBoot specifies the timeout since the
         system boots, after which gRPC server becomes operational.

         This value only takes effect when gRPC server is enabled in boot
         configuration file. When tmnxSysGrpcAdminState is set to 'inService',
         the gRPC server will begin receiving requests immediately."
    DEFVAL      { 0 }
    ::= { tmnxSysGrpcInfo 26 }

tmnxSysGrpcOperDownReason        OBJECT-TYPE
    SYNTAX      INTEGER {
        notApplicable         (0),
        adminDown             (1),
        listenPortUnavailable (2),
        activeDelayOnBoot     (3)
    }
    MAX-ACCESS  read-only
    STATUS      current
    DESCRIPTION
        "The value of tmnxSysGrpcOperDownReason indicates the reason why gRPC
         server is operationally down."
    ::= { tmnxSysGrpcInfo 27 }

tmnxSysMgmtInterfaceMDCli        OBJECT IDENTIFIER ::= { tmnxSysObjs 40 }

tmnxSysMgmtIfMDCliAutoCfgSave    OBJECT-TYPE
    SYNTAX      TruthValue
    MAX-ACCESS  read-write
    STATUS      current
    DESCRIPTION
        "The value of tmnxSysMgmtIfMDCliAutoCfgSave specifies whether the
         running configuration is saved as part of a commit operation initiated
         from MD CLI."
    DEFVAL      { true }
    ::= { tmnxSysMgmtInterfaceMDCli 1 }

tmnxSysMgmtIfMDEnvComplEnter     OBJECT-TYPE
    SYNTAX      TruthValue
    MAX-ACCESS  read-write
    STATUS      current
    DESCRIPTION
        "The value of tmnxSysMgmtIfMDEnvComplEnter specifies whether the
         command completion on enter character is allowed in MD CLI."
    DEFVAL      { true }
    ::= { tmnxSysMgmtInterfaceMDCli 2 }

tmnxSysMgmtIfMDEnvComplSpace     OBJECT-TYPE
    SYNTAX      TruthValue
    MAX-ACCESS  read-write
    STATUS      current
    DESCRIPTION
        "The value of tmnxSysMgmtIfMDEnvComplSpace specifies whether the
         command completion on space character is allowed in MD CLI."
    DEFVAL      { true }
    ::= { tmnxSysMgmtInterfaceMDCli 3 }

tmnxSysMgmtIfMDEnvComplTab       OBJECT-TYPE
    SYNTAX      TruthValue
    MAX-ACCESS  read-write
    STATUS      current
    DESCRIPTION
        "The value of tmnxSysMgmtIfMDEnvComplTab specifies whether the command
         completion on tab character is allowed in MD CLI."
    DEFVAL      { true }
    ::= { tmnxSysMgmtInterfaceMDCli 4 }

tmnxSysMgmtIfMDEnvConsLength     OBJECT-TYPE
    SYNTAX      Unsigned32 (24..512)
    MAX-ACCESS  read-write
    STATUS      current
    DESCRIPTION
        "The value of tmnxSysMgmtIfMDEnvConsLength specifies number of lines
         displayed on the console screen in MD CLI."
    DEFVAL      { 24 }
    ::= { tmnxSysMgmtInterfaceMDCli 5 }

tmnxSysMgmtIfMDEnvConsWidth      OBJECT-TYPE
    SYNTAX      Unsigned32 (80..512)
    MAX-ACCESS  read-write
    STATUS      current
    DESCRIPTION
        "The value of tmnxSysMgmtIfMDEnvConsWidth specifies number of columns
         displayed on the console screen in MD CLI."
    DEFVAL      { 80 }
    ::= { tmnxSysMgmtInterfaceMDCli 6 }

tmnxSysMgmtIfMDEnvMore           OBJECT-TYPE
    SYNTAX      TruthValue
    MAX-ACCESS  read-write
    STATUS      current
    DESCRIPTION
        "The value of tmnxSysMgmtIfMDEnvMore specifies whether paging of the
         output text in MD CLI is enabled. This applies to continuous text
         output from a single command that is capable of filling the entire
         screen."
    DEFVAL      { true }
    ::= { tmnxSysMgmtInterfaceMDCli 8 }

tmnxSysMgmtIfMDEnvPromptCtx      OBJECT-TYPE
    SYNTAX      TruthValue
    MAX-ACCESS  read-write
    STATUS      current
    DESCRIPTION
        "The value of tmnxSysMgmtIfMDEnvPromptCtx controls displaying of the
         current command context in MD CLI prompt."
    DEFVAL      { true }
    ::= { tmnxSysMgmtInterfaceMDCli 9 }

tmnxSysMgmtIfMDEnvPromptNewline  OBJECT-TYPE
    SYNTAX      TruthValue
    MAX-ACCESS  read-write
    STATUS      current
    DESCRIPTION
        "The value of tmnxSysMgmtIfMDEnvPromptNewline controls displaying of a
         newline before every prompt line in MD CLI."
    DEFVAL      { true }
    ::= { tmnxSysMgmtInterfaceMDCli 10 }

tmnxSysMgmtIfMDEnvPromptTime     OBJECT-TYPE
    SYNTAX      TruthValue
    MAX-ACCESS  read-write
    STATUS      current
    DESCRIPTION
        "The value of tmnxSysMgmtIfMDEnvPromptTime controls displaying of a
         timestamp before the first prompt line in MD CLI."
    DEFVAL      { false }
    ::= { tmnxSysMgmtInterfaceMDCli 11 }

tmnxSysMgmtIfMDEnvPromptIndic    OBJECT-TYPE
    SYNTAX      TruthValue
    MAX-ACCESS  read-write
    STATUS      current
    DESCRIPTION
        "The value of tmnxSysMgmtIfMDEnvPromptIndic controls displaying of the
         indicator of uncommitted changes in MD CLI prompt.

         The value set to true indicates that asterisk (*) is displayed in case
         of uncommitted changes are present in global configuration candidate
         datastore.

         The value set to false means that no indicator is displayed."
    DEFVAL      { true }
    ::= { tmnxSysMgmtInterfaceMDCli 12 }

tmnxSysMgmtIfMDEnvTimeDisplay    OBJECT-TYPE
    SYNTAX      INTEGER {
        local (1),
        utc   (2)
    }
    MAX-ACCESS  read-write
    STATUS      current
    DESCRIPTION
        "The value of tmnxSysMgmtIfMDEnvTimeDisplay specifies the time zone to
         be used, when displaying timestamp before prompt in MD CLI."
    DEFVAL      { local }
    ::= { tmnxSysMgmtInterfaceMDCli 13 }

tmnxSysMgmtIfMDEnvMsgCliSvrt     OBJECT-TYPE
    SYNTAX      INTEGER {
        warning (6),
        info    (7)
    }
    MAX-ACCESS  read-write
    STATUS      current
    DESCRIPTION
        "The value of tmnxSysMgmtIfMDEnvMsgCliSvrt specifies severity threshold
         for MD-CLI messages."
    DEFVAL      { info }
    ::= { tmnxSysMgmtInterfaceMDCli 14 }

tmnxSysMgmtIfMDEnvProIndAdminSt  OBJECT-TYPE
    SYNTAX      TmnxAdminStateTruthValue
    MAX-ACCESS  read-write
    STATUS      current
    DESCRIPTION
        "The value of tmnxSysMgmtIfMDEnvProIndAdminSt specifies whether
         progress indicator is active in MD-CLI."
    DEFVAL      { true }
    ::= { tmnxSysMgmtInterfaceMDCli 15 }

tmnxSysMgmtIfMDEnvProIndType     OBJECT-TYPE
    SYNTAX      INTEGER {
        dots (1)
    }
    MAX-ACCESS  read-write
    STATUS      current
    DESCRIPTION
        "Type of the progress indicator used in the MD-CLI."
    DEFVAL      { dots }
    ::= { tmnxSysMgmtInterfaceMDCli 16 }

tmnxSysMgmtIfMDEnvProIndDelay    OBJECT-TYPE
    SYNTAX      Unsigned32 (0..10000)
    MAX-ACCESS  read-write
    STATUS      current
    DESCRIPTION
        "Delay before progress indicator is displayed in MD-CLI."
    DEFVAL      { 1000 }
    ::= { tmnxSysMgmtInterfaceMDCli 17 }

tmnxSysMgmtIfMDCliCmdAccntLoad   OBJECT-TYPE
    SYNTAX      TruthValue
    MAX-ACCESS  read-write
    STATUS      obsolete
    DESCRIPTION
        "The value of tmnxSysMgmtIfMDCliCmdAccntLoad specifies whether remote
         command accounting is performed during an MD-CLI load or rollback
         operation."
    DEFVAL      { true }
    ::= { tmnxSysMgmtInterfaceMDCli 18 }

tmnxSysMgmtIfMDEnvTimeFormat     OBJECT-TYPE
    SYNTAX      INTEGER {
        iso-8601 (1),
        rfc-1123 (2),
        rfc-3339 (3)
    }
    MAX-ACCESS  read-write
    STATUS      current
    DESCRIPTION
        "The value of tmnxSysMgmtIfMDEnvTimeFormat specifies the time format to
         be used, when displaying timestamp in info command in MD CLI."
    DEFVAL      { rfc-3339 }
    ::= { tmnxSysMgmtInterfaceMDCli 19 }

tmnxSysMgmtIfMDEnvHistoryRecall  OBJECT-TYPE
    SYNTAX      TruthValue
    MAX-ACCESS  read-write
    STATUS      current
    DESCRIPTION
        "The value of tmnxSysMgmtIfMDEnvHistoryRecall controls whether Command
         history recall and search execution is allowed in MD-CLI."
    DEFVAL      { true }
    ::= { tmnxSysMgmtInterfaceMDCli 20 }

tmnxSysMgmtIfMDEnvHistorySize    OBJECT-TYPE
    SYNTAX      Unsigned32 (0..1000)
    MAX-ACCESS  read-write
    STATUS      current
    DESCRIPTION
        "The value of tmnxSysMgmtIfMDEnvHistorySize controls the size of
         Command history in MD-CLI."
    DEFVAL      { 50 }
    ::= { tmnxSysMgmtInterfaceMDCli 21 }

tmnxSysMgmtIfMDEnvCmtOptsConfirm OBJECT-TYPE
    SYNTAX      TruthValue
    MAX-ACCESS  read-write
    STATUS      current
    DESCRIPTION
        "The value of tmnxSysMgmtIfMDEnvCmtOptsConfirm controls whether Commit
         confirmed is required in MD-CLI."
    DEFVAL      { false }
    ::= { tmnxSysMgmtInterfaceMDCli 22 }

tmnxSysMgmtIfMDEnvCmtOptsComment OBJECT-TYPE
    SYNTAX      TruthValue
    MAX-ACCESS  read-write
    STATUS      current
    DESCRIPTION
        "The value of tmnxSysMgmtIfMDEnvCmtOptsComment controls whether Commit
         comment is required in MD-CLI."
    DEFVAL      { false }
    ::= { tmnxSysMgmtInterfaceMDCli 23 }

tmnxSysMgmtIfMDEnvInfoAdmState   OBJECT-TYPE
    SYNTAX      TruthValue
    MAX-ACCESS  read-write
    STATUS      current
    DESCRIPTION
        "The value of tmnxSysMgmtIfMDEnvInfoAdmState controls whether
         admin-state elements are displayed in MD-CLI."
    DEFVAL      { false }
    ::= { tmnxSysMgmtInterfaceMDCli 24 }

tmnxMGSysObjs                    OBJECT IDENTIFIER ::= { tmnxSysObjs 41 }

tmnxSysMgmtInterfaceYangModules  OBJECT IDENTIFIER ::= { tmnxSysObjs 42 }

tmnxSysMgmtIfYangBaseR13         OBJECT-TYPE
    SYNTAX      TruthValue
    MAX-ACCESS  read-write
    STATUS      obsolete
    DESCRIPTION
        "The value of tmnxSysMgmtIfYangBaseR13 specifies whether or not the
         base release 13 YANG models are supported. When set to 'true', network
         managers can access base release 13 YANG models."
    DEFVAL      { false }
    ::= { tmnxSysMgmtInterfaceYangModules 1 }

tmnxSysMgmtIfYangNokia           OBJECT-TYPE
    SYNTAX      TruthValue
    MAX-ACCESS  read-write
    STATUS      current
    DESCRIPTION
        "The value of tmnxSysMgmtIfYangNokia specifies whether or not the
         alternative submodule-based version of the Nokia YANG models are
         supported. When set to 'true', network managers can access the
         submodule-based Nokia YANG models."
    ::= { tmnxSysMgmtInterfaceYangModules 2 }

tmnxSysMgmtIfYangOpenConfig      OBJECT-TYPE
    SYNTAX      TruthValue
    MAX-ACCESS  read-write
    STATUS      current
    DESCRIPTION
        "The value of tmnxSysMgmtIfYangOpenConfig specifies whether or not the
         OpenConfig YANG models are supported. When set to 'true', network
         managers can access OpenConfig YANG models."
    DEFVAL      { false }
    ::= { tmnxSysMgmtInterfaceYangModules 3 }

tmnxSysMgmtIfYangNokiaCombined   OBJECT-TYPE
    SYNTAX      TruthValue
    MAX-ACCESS  read-write
    STATUS      current
    DESCRIPTION
        "The value of tmnxSysMgmtIfYangNokiaCombined specifies whether or not
         the combined version of the Nokia YANG models are supported. When set
         to 'true', network managers can access combined Nokia YANG models.

         tmnxSysMgmtIfYangNokiaCombined and tmnxSysMgmtIfYangNokia are mutually
         exclusive and cannot be both set to true at the same time."
    ::= { tmnxSysMgmtInterfaceYangModules 4 }

tmnxSysMgmtIfYangNmdaSupport     OBJECT-TYPE
    SYNTAX      TruthValue
    MAX-ACCESS  read-write
    STATUS      current
    DESCRIPTION
        "Enable / disable Network Management Datastores Architecture support."
    DEFVAL      { false }
    ::= { tmnxSysMgmtInterfaceYangModules 5 }

tmnxSysMgmtInterfaces            OBJECT IDENTIFIER ::= { tmnxSysObjs 43 }

tmnxSysMgmtIfWriteMode           OBJECT-TYPE
    SYNTAX      INTEGER {
        classic     (1),
        modelDriven (2),
        mixed       (3)
    }
    MAX-ACCESS  read-write
    STATUS      current
    DESCRIPTION
        "The value of tmnxSysMgmtIfWriteMode specifies the router
         configuration mode's requested provisional state.
            classic (1)     - configuration is managed by classic
                              interfaces only (e.g. classic CLI and
                              SNMP).
            modelDriven (2) - configuration is managed by
                              model-driven interfaces only
                              (e.g. MD-CLI, Netconf, and gNMI).
            mixed (3)       - configuration is managed (with
                              restrictions) with both classic and
                              model-driven interfaces.

         When the value of tmnxSysMgmtIfWriteOperMode is in 'modelDriven (2)'
         mode, SNMP Set-PDUs are rejected (ResourceUnavailable(13))). To
         re-enable SNMP access an operator MUST have write-access to CLI or a
         newer interface such as Netconf or gNMI and set the mode to either
         'classic (1)' or 'mixed (3)'."
    ::= { tmnxSysMgmtInterfaces 1 }

tmnxSysMgmtIfWriteOperMode       OBJECT-TYPE
    SYNTAX      INTEGER {
        syncing     (0),
        classic     (1),
        modelDriven (2),
        mixed       (3)
    }
    MAX-ACCESS  read-only
    STATUS      current
    DESCRIPTION
        "The value of tmnxSysMgmtIfWriteOperMode indicates the router
         configuration mode operationalized by the system.
            syncing (0)     - The system is in transition between
                              modes. Write access is restricted in
                              all interfaces.
            classic (1)     - configuration is managed by classic
                              interfaces only (e.g. classic CLI and
                              SNMP).
            modelDriven (2) - configuration is managed by
                              modelDriven interfaces only
                              (e.g. MD-CLI, Netconf, and gNMI).
            mixed (3)       - configuration is managed (with
                              restrictions) with both classic and
                              modelDriven interfaces."
    ::= { tmnxSysMgmtInterfaces 2 }

tmnxSysMgmtIfModeLastSwitchTime  OBJECT-TYPE
    SYNTAX      DateAndTime (SIZE (11))
    MAX-ACCESS  read-only
    STATUS      current
    DESCRIPTION
        "The value of tmnxSysMgmtIfModeLastSwitchTime indicates the time when a
         configuration-mode switch was last performed."
    ::= { tmnxSysMgmtInterfaces 3 }

tmnxSysMgmtIfModeSwitchDuration  OBJECT-TYPE
    SYNTAX      Counter32
    UNITS       "milliseconds"
    MAX-ACCESS  read-only
    STATUS      current
    DESCRIPTION
        "The value of tmnxSysMgmtIfModeSwitchDuration indicates the time, in
         milliseconds, that the last configuration-mode switch took to become
         active."
    ::= { tmnxSysMgmtInterfaces 4 }

tmnxSysMgmtIfDstoreLocksTable    OBJECT-TYPE
    SYNTAX      SEQUENCE OF TmnxSysMgmtIfDstoreLocksEntry
    MAX-ACCESS  not-accessible
    STATUS      current
    DESCRIPTION
        "The table tmnxSysMgmtIfDstoreLocksTable contains read-only information
         pertaining to configuration datastores' locks."
    ::= { tmnxSysMgmtInterfaces 5 }

tmnxSysMgmtIfDstoreLocksEntry    OBJECT-TYPE
    SYNTAX      TmnxSysMgmtIfDstoreLocksEntry
    MAX-ACCESS  not-accessible
    STATUS      current
    DESCRIPTION
        "Each row represents a single user session.

         Rows in the table tmnxSysMgmtIfDstoreLocksEntry are automatically
         created by the system when user acquires database connection and
         destroyed when client closes the connection."
    INDEX       { tmnxSysMgmtIfDsLocksSessionId }
    ::= { tmnxSysMgmtIfDstoreLocksTable 1 }

TmnxSysMgmtIfDstoreLocksEntry    ::= SEQUENCE
{
    tmnxSysMgmtIfDsLocksSessionId    Unsigned32,
    tmnxSysMgmtIfDsLocksRmtIpAddress InetAddress,
    tmnxSysMgmtIfDsLocksConsole      TruthValue,
    tmnxSysMgmtIfDsLocksUserName     TNamedItemOrEmpty,
    tmnxSysMgmtIfDsLocksSessionMode  INTEGER,
    tmnxSysMgmtIfDsLocksSessionType  INTEGER,
    tmnxSysMgmtIfDsLocksRegion       TNamedItem,
    tmnxSysMgmtIfDsLocksRunLock      TmnxSysMgmtIfDstoreLockState,
    tmnxSysMgmtIfDsLocksCndLock      TmnxSysMgmtIfDstoreLockState,
    tmnxSysMgmtIfDsLocksIdleTime     Unsigned32,
    tmnxSysMgmtIfDsLocksScratchCnt   Unsigned32,
    tmnxSysMgmtIfDsLocksCronEhs      TruthValue
}

tmnxSysMgmtIfDsLocksSessionId    OBJECT-TYPE
    SYNTAX      Unsigned32
    MAX-ACCESS  read-only
    STATUS      current
    DESCRIPTION
        "The value of the object tmnxSysMgmtIfDsLocksSessionId indicates the
         session ID of user session with open database connection, which can
         block other users from locking specific datastore."
    ::= { tmnxSysMgmtIfDstoreLocksEntry 1 }

tmnxSysMgmtIfDsLocksRmtIpAddress OBJECT-TYPE
    SYNTAX      InetAddress (SIZE (0|4|16))
    MAX-ACCESS  read-only
    STATUS      current
    DESCRIPTION
        "The value of the object tmnxSysMgmtIfDsLocksRmtIpAddress indicates the
         remote IP address of the user session.

         Empty address in case of console connection and
         tmnxSysMgmtIfDsLocksConsole is set to true."
    ::= { tmnxSysMgmtIfDstoreLocksEntry 2 }

tmnxSysMgmtIfDsLocksConsole      OBJECT-TYPE
    SYNTAX      TruthValue
    MAX-ACCESS  read-only
    STATUS      current
    DESCRIPTION
        "The value of tmnxSysMgmtIfDsLocksConsole indicates session session
         origin.

         Value true(1) represents for console connection and false(2) is used
         for Cron/EHS or rest of connections identified by IP address in
         tmnxSysMgmtIfDsLocksRmtIpAddress."
    DEFVAL      { false }
    ::= { tmnxSysMgmtIfDstoreLocksEntry 3 }

tmnxSysMgmtIfDsLocksUserName     OBJECT-TYPE
    SYNTAX      TNamedItemOrEmpty
    MAX-ACCESS  read-only
    STATUS      current
    DESCRIPTION
        "The value of the object tmnxSysMgmtIfDsLocksUserName indicates the
         name of the user who initiated the session."
    ::= { tmnxSysMgmtIfDstoreLocksEntry 4 }

tmnxSysMgmtIfDsLocksSessionMode  OBJECT-TYPE
    SYNTAX      INTEGER {
        global           (1),
        exclusive        (2),
        private          (3),
        privateExclusive (4),
        readOnly         (5)
    }
    MAX-ACCESS  read-only
    STATUS      current
    DESCRIPTION
        "The value of tmnxSysMgmtIfDsLocksSessionMode indicates
         the candidate datastore access session mode:
             global (1)           - write access to the global candidate datastore
                                    can be granted to multiple sessions
             exclusive (2)        - write access to the global candidate datastore
                                    and the running datastore is limited to a single session
             private (3)          - write access to a candidate datastore can be granted
                                    to multiple sessions, each with their own private
                                    candidate datastore
             privateExclusive (4) - write access to the private candidate datastore is granted,
                                    in addition, a single session is granted write access
                                    to the running datastore.
             readOnly (5)         - access to the datastore without write permissions."
    ::= { tmnxSysMgmtIfDstoreLocksEntry 5 }

tmnxSysMgmtIfDsLocksSessionType  OBJECT-TYPE
    SYNTAX      INTEGER {
        classicCli (1),
        grpc       (2),
        mdCli      (3),
        netconf    (4),
        snmp       (5),
        system     (6)
    }
    MAX-ACCESS  read-only
    STATUS      current
    DESCRIPTION
        "The value of tmnxSysMgmtIfDsLocksSessionType indicates the type of
         management interface, which was used to obtain the lock."
    ::= { tmnxSysMgmtIfDstoreLocksEntry 6 }

tmnxSysMgmtIfDsLocksRegion       OBJECT-TYPE
    SYNTAX      TNamedItem
    MAX-ACCESS  read-only
    STATUS      current
    DESCRIPTION
        "The value of the object tmnxSysMgmtIfDsLocksRegion indicates the name
         of the configuration region."
    ::= { tmnxSysMgmtIfDstoreLocksEntry 7 }

tmnxSysMgmtIfDsLocksRunLock      OBJECT-TYPE
    SYNTAX      TmnxSysMgmtIfDstoreLockState
    MAX-ACCESS  read-only
    STATUS      current
    DESCRIPTION
        "The value of tmnxSysMgmtIfDsLocksRunLock indicates running datastore
         lock state"
    ::= { tmnxSysMgmtIfDstoreLocksEntry 8 }

tmnxSysMgmtIfDsLocksCndLock      OBJECT-TYPE
    SYNTAX      TmnxSysMgmtIfDstoreLockState
    MAX-ACCESS  read-only
    STATUS      current
    DESCRIPTION
        "The value of tmnxSysMgmtIfDsLocksCndLock indicates candidate datastore
         lock state"
    ::= { tmnxSysMgmtIfDstoreLocksEntry 9 }

tmnxSysMgmtIfDsLocksIdleTime     OBJECT-TYPE
    SYNTAX      Unsigned32
    UNITS       "seconds"
    MAX-ACCESS  read-only
    STATUS      current
    DESCRIPTION
        "The value of tmnxSysMgmtIfDsLocksIdleTime indicates the idle time of
         user.

         For the CLI sessions the idle time is the period of time after last
         key pressed. For the NETCONF it is the period of time after session
         creation. For the GMI we do not track idle time."
    ::= { tmnxSysMgmtIfDstoreLocksEntry 10 }

tmnxSysMgmtIfDsLocksScratchCnt   OBJECT-TYPE
    SYNTAX      Unsigned32
    MAX-ACCESS  read-only
    STATUS      current
    DESCRIPTION
        "The value of tmnxSysMgmtIfDsLocksScratchCnt indicates the number of
         scratchpads in use for session"
    ::= { tmnxSysMgmtIfDstoreLocksEntry 11 }

tmnxSysMgmtIfDsLocksCronEhs      OBJECT-TYPE
    SYNTAX      TruthValue
    MAX-ACCESS  read-only
    STATUS      current
    DESCRIPTION
        "The value of tmnxSysMgmtIfDsLocksCronEhs indicates whether the session
         is a Cron/EHS session

         Value true(1) represents Cron/EHS session and false(2) is used for
         console or rest of connections identified by IP address in
         tmnxSysMgmtIfDsLocksRmtIpAddress."
    DEFVAL      { false }
    ::= { tmnxSysMgmtIfDstoreLocksEntry 12 }

tmnxSysMgmtIfSchemaPath          OBJECT-TYPE
    SYNTAX      TmnxDisplayStringURL
    MAX-ACCESS  read-write
    STATUS      current
    DESCRIPTION
        "The value of tmnxSysMgmtIfSchemaPath specifies the path to schema
         files used by the system."
    DEFVAL      { "" }
    ::= { tmnxSysMgmtInterfaces 6 }

tmnxSysMgmtIfWriteSwitchReason   OBJECT-TYPE
    SYNTAX      INTEGER {
        boot       (0),
        manual     (1),
        validation (2)
    }
    MAX-ACCESS  read-only
    STATUS      current
    DESCRIPTION
        "The value of tmnxSysMgmtIfWriteSwitchReason indicates the
         origin cause of the router configuration mode switch.
            boot(0)         - The system booted in the current mode.
            manual (1)      - An operator manually switched to the
                              current mode.
            validation (2)  - Validation failure was detected,
                              causing the mode switch."
    ::= { tmnxSysMgmtInterfaces 7 }

tmnxSysMgmtIfPriSchemaPathState  OBJECT-TYPE
    SYNTAX      TmnxSchemaPathState
    MAX-ACCESS  read-only
    STATUS      obsolete
    DESCRIPTION
        "The value of the object tmnxSysMgmtIfPriSchemaPathState indicates the
         state of tmnxSysMgmtIfPriSchemaPathValue.

         The value can be either 'ok', 'errConnection', 'errTooLong' or
         'errInvalid'. This object was obsoleted in release 24.3."
    ::= { tmnxSysMgmtInterfaces 8 }

tmnxSysMgmtIfPriSchemaPathValue  OBJECT-TYPE
    SYNTAX      TmnxDisplayStringURL
    MAX-ACCESS  read-only
    STATUS      obsolete
    DESCRIPTION
        "The value of the object tmnxSysMgmtIfPriSchemaPathValue indicates the
         path to schema files derived from the value of sbiPrimaryImage.

         The value of this object is valid only if the value of
         tmnxSysMgmtIfPriSchemaPathState is 'ok'. This object was obsoleted in
         release 24.3."
    ::= { tmnxSysMgmtInterfaces 9 }

tmnxSysMgmtIfSecSchemaPathState  OBJECT-TYPE
    SYNTAX      TmnxSchemaPathState
    MAX-ACCESS  read-only
    STATUS      obsolete
    DESCRIPTION
        "The value of the object tmnxSysMgmtIfSecSchemaPathState indicates the
         state of tmnxSysMgmtIfSecSchemaPathValue.

         The value can be either 'ok', 'errConnection', 'errTooLong' or
         'errInvalid'. This object was obsoleted in release 24.3."
    ::= { tmnxSysMgmtInterfaces 10 }

tmnxSysMgmtIfSecSchemaPathValue  OBJECT-TYPE
    SYNTAX      TmnxDisplayStringURL
    MAX-ACCESS  read-only
    STATUS      obsolete
    DESCRIPTION
        "The value of the object tmnxSysMgmtIfSecSchemaPathValue indicates the
         path to schema files derived from the value of sbiSecondaryImage.

         The value of this object is valid only if the value of
         tmnxSysMgmtIfSecSchemaPathState is 'ok'. This object was obsoleted in
         release 24.3."
    ::= { tmnxSysMgmtInterfaces 11 }

tmnxSysMgmtIfTerSchemaPathState  OBJECT-TYPE
    SYNTAX      TmnxSchemaPathState
    MAX-ACCESS  read-only
    STATUS      obsolete
    DESCRIPTION
        "The value of the object tmnxSysMgmtIfTerSchemaPathState indicates the
         state of tmnxSysMgmtIfTerSchemaPathValue.

         The value can be either 'ok', 'connectionEror' or 'errorTooLong'. This
         object was obsoleted in release 24.3."
    ::= { tmnxSysMgmtInterfaces 12 }

tmnxSysMgmtIfTerSchemaPathValue  OBJECT-TYPE
    SYNTAX      TmnxDisplayStringURL
    MAX-ACCESS  read-only
    STATUS      obsolete
    DESCRIPTION
        "The value of the object tmnxSysMgmtIfTerSchemaPathValue indicates the
         path to schema files derived from the value of sbiTertiaryImage.

         The value of this object is valid only if the value of
         tmnxSysMgmtIfTerSchemaPathState is 'ok'. This object was obsoleted in
         release 24.3."
    ::= { tmnxSysMgmtInterfaces 13 }

tmnxSysMgmtIfOperSchemaPathState OBJECT-TYPE
    SYNTAX      TmnxSchemaPathState
    MAX-ACCESS  read-only
    STATUS      current
    DESCRIPTION
        "The value of the object tmnxSysMgmtIfOperSchemaPathState indicates the
         state of tmnxSysMgmtIfOperSchemaPathValue.

         The value can be either 'ok', 'errConnection', 'errTooLong' or
         'errInvalid'."
    ::= { tmnxSysMgmtInterfaces 14 }

tmnxSysMgmtIfOperSchemaPathValue OBJECT-TYPE
    SYNTAX      TmnxDisplayStringURL
    MAX-ACCESS  read-only
    STATUS      current
    DESCRIPTION
        "The value of the object tmnxSysMgmtIfOperSchemaPathValue indicates the
         path to schema files used by the system.

         The value of this object is valid only if the value of
         tmnxSysMgmtIfOperSchemaPathState is 'ok'."
    ::= { tmnxSysMgmtInterfaces 15 }

tmnxSysMgmtIfCommitHistory       OBJECT-TYPE
    SYNTAX      Unsigned32 (0..200)
    MAX-ACCESS  read-write
    STATUS      current
    DESCRIPTION
        "Number of commit history IDs to store"
    DEFVAL      { 50 }
    ::= { tmnxSysMgmtInterfaces 16 }

tmnxSysGrpcConnTable             OBJECT-TYPE
    SYNTAX      SEQUENCE OF TmnxSysGrpcConnEntry
    MAX-ACCESS  not-accessible
    STATUS      current
    DESCRIPTION
        "The table tmnxSysGrpcConnTable contains read-only information
         pertaining to gRPC server connections."
    ::= { tmnxSysObjs 44 }

tmnxSysGrpcConnEntry             OBJECT-TYPE
    SYNTAX      TmnxSysGrpcConnEntry
    MAX-ACCESS  not-accessible
    STATUS      current
    DESCRIPTION
        "Each row entry represents a single TCP connection towards gRPC server.

         Rows in the table tmnxSysGrpcConnEntry are automatically created by
         the system when client connect to gRPC server and destroyed when
         client disconnect."
    INDEX       {
        tmnxSysGrpcConnSrcIpAddType,
        tmnxSysGrpcConnSrcIpAddress,
        tmnxSysGrpcConnSrcPort
    }
    ::= { tmnxSysGrpcConnTable 1 }

TmnxSysGrpcConnEntry             ::= SEQUENCE
{
    tmnxSysGrpcConnSrcIpAddType      InetAddressType,
    tmnxSysGrpcConnSrcIpAddress      InetAddress,
    tmnxSysGrpcConnSrcPort           InetPortNumber,
    tmnxSysGrpcConnStartTime         DateAndTime,
    tmnxSysGrpcConnActRpcCnt         CounterBasedGauge64,
    tmnxSysGrpcConnTotRpcCnt         Counter64,
    tmnxSysGrpcConnRxBytes           Counter64,
    tmnxSysGrpcConnTxBytes           Counter64,
    tmnxSysGrpcConnQos               TDSCPNameOrEmpty,
    tmnxSysGrpcConnSrcVRtrId         TmnxVRtrID,
    tmnxSysGrpcConnGrpcTunnel        TNamedItemOrEmpty,
    tmnxSysGrpcConnLFRpcName         TNamedItemOrEmpty,
    tmnxSysGrpcConnLFRpcServiceName  TNamedItemOrEmpty,
    tmnxSysGrpcConnLFRpcDuration     Counter64,
    tmnxSysGrpcConnLFRpcFinishTime   DateAndTime,
    tmnxSysGrpcConnLFRpcErrorStatus  OCTET STRING
}

tmnxSysGrpcConnSrcIpAddType      OBJECT-TYPE
    SYNTAX      InetAddressType
    MAX-ACCESS  not-accessible
    STATUS      current
    DESCRIPTION
        "The value of the object tmnxSysGrpcConnSrcIpAddType indicates the type
         of IP address stored in tmnxSysGrpcConnSrcIpAddress. The value can be
         either 'unknown', 'ipv4' or 'ipv6."
    ::= { tmnxSysGrpcConnEntry 1 }

tmnxSysGrpcConnSrcIpAddress      OBJECT-TYPE
    SYNTAX      InetAddress (SIZE (0|4|16))
    MAX-ACCESS  not-accessible
    STATUS      current
    DESCRIPTION
        "The value of the object tmnxSysGrpcConnSrcIpAddress indicates the
         remote IP address of the gRPC client."
    ::= { tmnxSysGrpcConnEntry 2 }

tmnxSysGrpcConnSrcPort           OBJECT-TYPE
    SYNTAX      InetPortNumber
    MAX-ACCESS  not-accessible
    STATUS      current
    DESCRIPTION
        "The value of the object tmnxSysGrpcConnSrcPort indicates the remote
         port of the gRPC client."
    ::= { tmnxSysGrpcConnEntry 3 }

tmnxSysGrpcConnStartTime         OBJECT-TYPE
    SYNTAX      DateAndTime
    MAX-ACCESS  read-only
    STATUS      current
    DESCRIPTION
        "The value of tmnxSysGrpcConnStartTime indicates the time when
         connection towards gRPC server was established."
    ::= { tmnxSysGrpcConnEntry 4 }

tmnxSysGrpcConnActRpcCnt         OBJECT-TYPE
    SYNTAX      CounterBasedGauge64
    MAX-ACCESS  read-only
    STATUS      current
    DESCRIPTION
        "The value of tmnxSysGrpcConnActRpcCnt indicates the active number of
         RPC on this connection."
    ::= { tmnxSysGrpcConnEntry 5 }

tmnxSysGrpcConnTotRpcCnt         OBJECT-TYPE
    SYNTAX      Counter64
    MAX-ACCESS  read-only
    STATUS      current
    DESCRIPTION
        "The value of tmnxSysGrpcConnTotRpcCnt indicates the total number of
         RPC on this connection since establishment time."
    ::= { tmnxSysGrpcConnEntry 6 }

tmnxSysGrpcConnRxBytes           OBJECT-TYPE
    SYNTAX      Counter64
    UNITS       "bytes"
    MAX-ACCESS  read-only
    STATUS      current
    DESCRIPTION
        "The value of tmnxSysGrpcConnRxBytes indicates the total number of
         bytes received over this connection."
    ::= { tmnxSysGrpcConnEntry 7 }

tmnxSysGrpcConnTxBytes           OBJECT-TYPE
    SYNTAX      Counter64
    UNITS       "bytes"
    MAX-ACCESS  read-only
    STATUS      current
    DESCRIPTION
        "The value of tmnxSysGrpcConnTxBytes indicates the total number of
         bytes sent over this connection."
    ::= { tmnxSysGrpcConnEntry 8 }

tmnxSysGrpcConnQos               OBJECT-TYPE
    SYNTAX      TDSCPNameOrEmpty
    MAX-ACCESS  read-only
    STATUS      current
    DESCRIPTION
        "The value of tmnxSysGrpcConnQos indicates the DSCP value of the
         connection. Only first Subscribe RPC with qos request is accepted on
         connection. DSCP value is reset to sgt-qos default after last
         Subscribe RPC on connection is terminated."
    ::= { tmnxSysGrpcConnEntry 9 }

tmnxSysGrpcConnSrcVRtrId         OBJECT-TYPE
    SYNTAX      TmnxVRtrID
    MAX-ACCESS  read-only
    STATUS      current
    DESCRIPTION
        "The value of the object tmnxSysGrpcConnSrcVRtrId indicates the virtual
         router instance ID of the gRPC client."
    ::= { tmnxSysGrpcConnEntry 10 }

tmnxSysGrpcConnGrpcTunnel        OBJECT-TYPE
    SYNTAX      TNamedItemOrEmpty
    MAX-ACCESS  read-only
    STATUS      current
    DESCRIPTION
        "The value of the object tmnxSysGrpcConnGrpcTunnel indicates the
         gRPC-Tunnel instance used as transport of a connection."
    ::= { tmnxSysGrpcConnEntry 11 }

tmnxSysGrpcConnLFRpcName         OBJECT-TYPE
    SYNTAX      TNamedItemOrEmpty
    MAX-ACCESS  read-only
    STATUS      current
    DESCRIPTION
        "The value of the object tmnxSysGrpcConnLFRpcName indicates the name of
         a last finished RPC on this connection."
    ::= { tmnxSysGrpcConnEntry 12 }

tmnxSysGrpcConnLFRpcServiceName  OBJECT-TYPE
    SYNTAX      TNamedItemOrEmpty
    MAX-ACCESS  read-only
    STATUS      current
    DESCRIPTION
        "The value of the object tmnxSysGrpcConnLFRpcServiceName indicates the
         name of a last finished RPC service on this connection."
    ::= { tmnxSysGrpcConnEntry 13 }

tmnxSysGrpcConnLFRpcDuration     OBJECT-TYPE
    SYNTAX      Counter64
    UNITS       "milliseconds"
    MAX-ACCESS  read-only
    STATUS      current
    DESCRIPTION
        "The value of the object tmnxSysGrpcConnLFRpcDuration indicates the
         duration of a last finished RPC on this connection."
    ::= { tmnxSysGrpcConnEntry 14 }

tmnxSysGrpcConnLFRpcFinishTime   OBJECT-TYPE
    SYNTAX      DateAndTime
    MAX-ACCESS  read-only
    STATUS      current
    DESCRIPTION
        "The value of tmnxSysGrpcConnLFRpcFinishTime indicates the finish time
         of a last finished RPC on this connection.

         DateAndTime.year = 0 is returned if no RPC have been finished on this
         connection."
    ::= { tmnxSysGrpcConnEntry 15 }

tmnxSysGrpcConnLFRpcErrorStatus  OBJECT-TYPE
    SYNTAX      OCTET STRING (SIZE (0..256))
    MAX-ACCESS  read-only
    STATUS      current
    DESCRIPTION
        "The value of tmnxSysGrpcConnLFRpcErrorStatus indicates the error
         status of a last finished RPC on this connection.

         Empty string is returned if no RPC have been finished on this
         connection, or if last RPC finished with OK status."
    ::= { tmnxSysGrpcConnEntry 16 }

tmnxSysHttpRdr                   OBJECT IDENTIFIER ::= { tmnxSysObjs 45 }

tmnxSysHttpRdrCpmOptimizedMode   OBJECT-TYPE
    SYNTAX      TruthValue
    MAX-ACCESS  read-write
    STATUS      current
    DESCRIPTION
        "The value of tmnxSysHttpRdrCpmOptimizedMode specifies if the CPM uses
         the optimized mode for HTTP redirect messages."
    DEFVAL      { true }
    ::= { tmnxSysHttpRdr 1 }

tmnxSysGrpcRpcTable              OBJECT-TYPE
    SYNTAX      SEQUENCE OF TmnxSysGrpcRpcEntry
    MAX-ACCESS  not-accessible
    STATUS      current
    DESCRIPTION
        "The table tmnxSysGrpcRpcTable contains read-only information
         pertaining to gRPC server RPCs."
    ::= { tmnxSysObjs 46 }

tmnxSysGrpcRpcEntry              OBJECT-TYPE
    SYNTAX      TmnxSysGrpcRpcEntry
    MAX-ACCESS  not-accessible
    STATUS      current
    DESCRIPTION
        "Each row entry represents a single RPC towards gRPC server.

         Rows in the table tmnxSysGrpcRpcEntry are automatically created by the
         system when client send RPC towards gRPC server and destroyed when RPC
         execution is finished or cancelled."
    INDEX       { tmnxSysGrpcRpcId }
    ::= { tmnxSysGrpcRpcTable 1 }

TmnxSysGrpcRpcEntry              ::= SEQUENCE
{
    tmnxSysGrpcRpcId                 Unsigned32,
    tmnxSysGrpcRpcName               TNamedItem,
    tmnxSysGrpcRpcServiceName        TNamedItem,
    tmnxSysGrpcRpcStartTime          DateAndTime,
    tmnxSysGrpcRpcSrcIpAddType       InetAddressType,
    tmnxSysGrpcRpcSrcIpAddress       InetAddress,
    tmnxSysGrpcRpcSrcPort            InetPortNumber,
    tmnxSysGrpcRpcUserName           TNamedItemOrEmpty,
    tmnxSysGrpcRpcSessionId          Unsigned32,
    tmnxSysGrpcRpcGrpcTunnel         TNamedItemOrEmpty
}

tmnxSysGrpcRpcId                 OBJECT-TYPE
    SYNTAX      Unsigned32
    MAX-ACCESS  not-accessible
    STATUS      current
    DESCRIPTION
        "The value of the object tmnxSysGrpcRpcId indicates the system
         generated unique RPC ID."
    ::= { tmnxSysGrpcRpcEntry 1 }

tmnxSysGrpcRpcName               OBJECT-TYPE
    SYNTAX      TNamedItem
    MAX-ACCESS  read-only
    STATUS      current
    DESCRIPTION
        "The value of the object tmnxSysGrpcRpcName indicates the name of a
         RPC."
    ::= { tmnxSysGrpcRpcEntry 2 }

tmnxSysGrpcRpcServiceName        OBJECT-TYPE
    SYNTAX      TNamedItem
    MAX-ACCESS  read-only
    STATUS      current
    DESCRIPTION
        "The value of the object tmnxSysGrpcRpcServiceName indicates the name
         of a RPC service."
    ::= { tmnxSysGrpcRpcEntry 3 }

tmnxSysGrpcRpcStartTime          OBJECT-TYPE
    SYNTAX      DateAndTime
    MAX-ACCESS  read-only
    STATUS      current
    DESCRIPTION
        "The value of tmnxSysGrpcRpcStartTime indicates the time of a RPC
         arrival to gRPC server."
    ::= { tmnxSysGrpcRpcEntry 4 }

tmnxSysGrpcRpcSrcIpAddType       OBJECT-TYPE
    SYNTAX      InetAddressType
    MAX-ACCESS  read-only
    STATUS      current
    DESCRIPTION
        "The value of the object tmnxSysGrpcRpcSrcIpAddType indicates the type
         of IP address stored in tmnxSysGrpcRpcSrcIpAddress. The value can be
         either 'unknown', 'ipv4' or 'ipv6."
    ::= { tmnxSysGrpcRpcEntry 5 }

tmnxSysGrpcRpcSrcIpAddress       OBJECT-TYPE
    SYNTAX      InetAddress (SIZE (0|4|16))
    MAX-ACCESS  read-only
    STATUS      current
    DESCRIPTION
        "The value of the object tmnxSysGrpcRpcSrcIpAddress indicates the
         remote IP address of gRPC client who sent a RPC."
    ::= { tmnxSysGrpcRpcEntry 6 }

tmnxSysGrpcRpcSrcPort            OBJECT-TYPE
    SYNTAX      InetPortNumber
    MAX-ACCESS  read-only
    STATUS      current
    DESCRIPTION
        "The value of the object tmnxSysGrpcRpcSrcPort indicates the remote
         port of gRPC client who sent a RPC."
    ::= { tmnxSysGrpcRpcEntry 7 }

tmnxSysGrpcRpcUserName           OBJECT-TYPE
    SYNTAX      TNamedItemOrEmpty
    MAX-ACCESS  read-only
    STATUS      current
    DESCRIPTION
        "The value of the object tmnxSysGrpcRpcUserName indicates the name of a
         system user who initiated a RPC.

         The value might be empty if client did not provide username or if a
         RPC was not yet authenticated."
    ::= { tmnxSysGrpcRpcEntry 8 }

tmnxSysGrpcRpcSessionId          OBJECT-TYPE
    SYNTAX      Unsigned32
    MAX-ACCESS  read-only
    STATUS      current
    DESCRIPTION
        "The value of the object tmnxSysGrpcRpcSessionId indicates the
         session-id of a system user who initiated a RPC.

         The value might be zero if a RPC was not yet authenticated."
    ::= { tmnxSysGrpcRpcEntry 9 }

tmnxSysGrpcRpcGrpcTunnel         OBJECT-TYPE
    SYNTAX      TNamedItemOrEmpty
    MAX-ACCESS  read-only
    STATUS      current
    DESCRIPTION
        "The value of the object tmnxSysGrpcRpcGrpcTunnel indicates the
         gRPC-Tunnel instance used as transport of a RPC."
    ::= { tmnxSysGrpcRpcEntry 10 }

tmnxSysNetworkElementObjs        OBJECT IDENTIFIER ::= { tmnxSysObjs 47 }

tmnxSysNEProfTableLstChgd        OBJECT-TYPE
    SYNTAX      TimeStamp
    MAX-ACCESS  read-only
    STATUS      current
    DESCRIPTION
        "The value of tmnxSysNEProfTableLstChgd indicates the time, since
         system startup, when tmnxSysNEProfTable last changed configuration.

         A value of zero indicates that no changes were made to this table
         since the system was last initialized."
    ::= { tmnxSysNetworkElementObjs 1 }

tmnxSysNEProfTable               OBJECT-TYPE
    SYNTAX      SEQUENCE OF TmnxSysNEProfEntry
    MAX-ACCESS  not-accessible
    STATUS      current
    DESCRIPTION
        "The tmnxSysNEProfTable contains objects used to configure instances of
         the network element profile, which are used for node discovery.

         Entries in this table are created and deleted via SNMP set operations
         to tmnxSysNEProfRowStatus."
    ::= { tmnxSysNetworkElementObjs 2 }

tmnxSysNEProfEntry               OBJECT-TYPE
    SYNTAX      TmnxSysNEProfEntry
    MAX-ACCESS  not-accessible
    STATUS      current
    DESCRIPTION
        "Each tmnxSysNEProfEntry contains the configuration for one network
         element profile."
    INDEX       { tmnxSysNEProfName }
    ::= { tmnxSysNEProfTable 1 }

TmnxSysNEProfEntry               ::= SEQUENCE
{
    tmnxSysNEProfName                TNamedItem,
    tmnxSysNEProfRowStatus           RowStatus,
    tmnxSysNEProfLastChanged         TimeStamp,
    tmnxSysNEProfNeid                TmnxSysNeid,
    tmnxSysNEProfNeipV4Type          InetAddressType,
    tmnxSysNEProfNeipV4              InetAddress,
    tmnxSysNEProfNeipV6Type          InetAddressType,
    tmnxSysNEProfNeipV6              InetAddress,
    tmnxSysNEProfSystemMac           MacAddress,
    tmnxSysNEProfPlatformType        DisplayString,
    tmnxSysNEProfVendorId            DisplayString,
    tmnxSysNEProfNeipV4AutoGenerate  TruthValue,
    tmnxSysNEProfNeipV4NeidVendorId  Unsigned32,
    tmnxSysNEProfNeipV6AutoGenerate  TruthValue,
    tmnxSysNEProfNeipV6NeidVendorId  Unsigned32
}

tmnxSysNEProfName                OBJECT-TYPE
    SYNTAX      TNamedItem
    MAX-ACCESS  not-accessible
    STATUS      current
    DESCRIPTION
        "The value of tmnxSysNEProfName uniquely specifies one network element
         profile configured on this system."
    ::= { tmnxSysNEProfEntry 1 }

tmnxSysNEProfRowStatus           OBJECT-TYPE
    SYNTAX      RowStatus
    MAX-ACCESS  read-create
    STATUS      current
    DESCRIPTION
        "The value of tmnxSysNEProfRowStatus specifies the status of this row.
         It is used to create and delete row entries in tmnxSysNEProfTable."
    ::= { tmnxSysNEProfEntry 2 }

tmnxSysNEProfLastChanged         OBJECT-TYPE
    SYNTAX      TimeStamp
    MAX-ACCESS  read-only
    STATUS      current
    DESCRIPTION
        "The value of tmnxSysNEProfLastChanged indicates the time, since system
         startup, that the configuration of this row was created or modified."
    ::= { tmnxSysNEProfEntry 3 }

tmnxSysNEProfNeid                OBJECT-TYPE
    SYNTAX      TmnxSysNeid
    MAX-ACCESS  read-create
    STATUS      current
    DESCRIPTION
        "The value of tmnxSysNEProfNeid specifies the Network Element
         Identifier.

         The first 8 high-order bits indicate the subnet ID and and range from
         0x1 to 0xFE. The 16 low-order bits indicate the basic ID and ranges
         from 0x0001 to 0xFFFE."
    DEFVAL      { ''H }
    ::= { tmnxSysNEProfEntry 4 }

tmnxSysNEProfNeipV4Type          OBJECT-TYPE
    SYNTAX      InetAddressType
    MAX-ACCESS  read-create
    STATUS      current
    DESCRIPTION
        "The value of tmnxSysNEProfNeipV4Type specifies the IP address type of
         tmnxSysNEProfNeipV4.

         The value of tmnxSysNEProfNeipV4Type can be either of 'ipv4(1)' or
         'unknown (0)'.

         The value of 'unknown(0)' specifies no NEIP v4 address is configured."
    DEFVAL      { unknown }
    ::= { tmnxSysNEProfEntry 5 }

tmnxSysNEProfNeipV4              OBJECT-TYPE
    SYNTAX      InetAddress (SIZE (0|4))
    MAX-ACCESS  read-create
    STATUS      current
    DESCRIPTION
        "The value of tmnxSysNEProfNeipV4 indicates the IPv4 address of the
         Network Element."
    DEFVAL      { ''H }
    ::= { tmnxSysNEProfEntry 6 }

tmnxSysNEProfNeipV6Type          OBJECT-TYPE
    SYNTAX      InetAddressType
    MAX-ACCESS  read-create
    STATUS      current
    DESCRIPTION
        "The value of tmnxSysNEProfNeipV6Type specifies the IP address type of
         tmnxSysNEProfNeipV6.

         The value of tmnxSysNEProfNeipV6Type can be either of 'ipv6(2)' or
         'unknown (0)'.

         The value of 'unknown(0)' specifies no NEIP v6 address is configured."
    DEFVAL      { unknown }
    ::= { tmnxSysNEProfEntry 7 }

tmnxSysNEProfNeipV6              OBJECT-TYPE
    SYNTAX      InetAddress (SIZE (0|16))
    MAX-ACCESS  read-create
    STATUS      current
    DESCRIPTION
        "The value of tmnxSysNEProfNeipV6 indicates the IPv6 address of the
         Network Element."
    DEFVAL      { ''H }
    ::= { tmnxSysNEProfEntry 8 }

tmnxSysNEProfSystemMac           OBJECT-TYPE
    SYNTAX      MacAddress
    MAX-ACCESS  read-create
    STATUS      current
    DESCRIPTION
        "The value of tmnxSysNEProfSystemMac specifies the system MAC address
         of the node.

         A value of all zeroes indicates this object is not configured, the
         chassis MAC address will be used."
    DEFVAL      { '000000000000'H }
    ::= { tmnxSysNEProfEntry 9 }

tmnxSysNEProfPlatformType        OBJECT-TYPE
    SYNTAX      DisplayString
    MAX-ACCESS  read-create
    STATUS      current
    DESCRIPTION
        "The value of tmnxSysNEProfPlatformType specifies the product
         identifier.

         An empty string indicates this object is not configured, the chassis
         name and chassis type will be used."
    DEFVAL      { ''H }
    ::= { tmnxSysNEProfEntry 10 }

tmnxSysNEProfVendorId            OBJECT-TYPE
    SYNTAX      DisplayString
    MAX-ACCESS  read-create
    STATUS      current
    DESCRIPTION
        "The value of tmnxSysNEProfVendorId specifies the vendor identifier."
    DEFVAL      { "Nokia" }
    ::= { tmnxSysNEProfEntry 11 }

tmnxSysNEProfNeipV4AutoGenerate  OBJECT-TYPE
    SYNTAX      TruthValue
    MAX-ACCESS  read-create
    STATUS      current
    DESCRIPTION
        "The value of tmnxSysNEProfNeipV4AutoGenerate specifies whether the
         Network Element (NE) IPv4 address must be auto generated.

         If the value is 'true', the NE IPv4 address will be generated based on
         tmnxSysNEProfNeipV4NeidVendorId and tmnxSysNEProfNeid."
    DEFVAL      { false }
    ::= { tmnxSysNEProfEntry 12 }

tmnxSysNEProfNeipV4NeidVendorId  OBJECT-TYPE
    SYNTAX      Unsigned32 (1..255)
    MAX-ACCESS  read-create
    STATUS      current
    DESCRIPTION
        "The value of tmnxSysNEProfNeipV4NeidVendorId specifies the vendor ID
         value to be used in combination with the NEID for the auto generated
         NE IPv4 address."
    DEFVAL      { 140 }
    ::= { tmnxSysNEProfEntry 13 }

tmnxSysNEProfNeipV6AutoGenerate  OBJECT-TYPE
    SYNTAX      TruthValue
    MAX-ACCESS  read-create
    STATUS      current
    DESCRIPTION
        "The value of tmnxSysNEProfNeipV6AutoGenerate specifies whether the
         Network Element (NE) IPv6 address must be auto generated.

         If the value is 'true', the NE IPv6 address will be generated based on
         tmnxSysNEProfNeipV6NeidVendorId and tmnxSysNEProfNeid."
    DEFVAL      { false }
    ::= { tmnxSysNEProfEntry 14 }

tmnxSysNEProfNeipV6NeidVendorId  OBJECT-TYPE
    SYNTAX      Unsigned32 (1..255)
    MAX-ACCESS  read-create
    STATUS      current
    DESCRIPTION
        "The value of tmnxSysNEProfNeipV6NeidVendorId specifies the vendor ID
         value to be used in combination with the NEID for the auto generated
         NE IPv6 address."
    DEFVAL      { 140 }
    ::= { tmnxSysNEProfEntry 15 }

tmnxSysNEDiscoveryGenerateTraps  OBJECT-TYPE
    SYNTAX      TruthValue
    MAX-ACCESS  read-write
    STATUS      current
    DESCRIPTION
        "The value of tmnxSysNEDiscoveryGenerateTraps specifies whether to
         generate Network Element Discovery notifications or not."
    DEFVAL      { false }
    ::= { tmnxSysNetworkElementObjs 3 }

tmnxSysFwdPathOptsObjs           OBJECT IDENTIFIER ::= { tmnxSysObjs 48 }

tmnxSysFpoDscpTransAdminState    OBJECT-TYPE
    SYNTAX      TmnxAdminState
    MAX-ACCESS  read-write
    STATUS      current
    DESCRIPTION
        "The value of tmnxSysFpoDscpTransAdminState specifies the
         administrative state of the DSCP transparency forwarding path option."
    DEFVAL      { inService }
    ::= { tmnxSysFwdPathOptsObjs 1 }

tmnxSysFpoDscpTransOperState     OBJECT-TYPE
    SYNTAX      TmnxOperState
    MAX-ACCESS  read-only
    STATUS      current
    DESCRIPTION
        "The value of tmnxSysFpoDscpTransOperState indicates the operational
         state of the DSCP transparency forwarding path option."
    ::= { tmnxSysFwdPathOptsObjs 2 }

tmnxSysFpoEntropyLabelAdminState OBJECT-TYPE
    SYNTAX      TmnxAdminState
    MAX-ACCESS  read-write
    STATUS      current
    DESCRIPTION
        "The value of tmnxSysFpoEntropyLabelAdminState specifies the
         administrative state of the entropy label forwarding path option."
    DEFVAL      { outOfService }
    ::= { tmnxSysFwdPathOptsObjs 3 }

tmnxSysFpoEntropyLabelOperState  OBJECT-TYPE
    SYNTAX      TmnxOperState
    MAX-ACCESS  read-only
    STATUS      current
    DESCRIPTION
        "The value of tmnxSysFpoEntropyLabelOperState indicates the operational
         state of the entropy label forwarding path option."
    ::= { tmnxSysFwdPathOptsObjs 4 }

tmnxSysFpoMacFltOutVlanPrioAdmSt OBJECT-TYPE
    SYNTAX      TmnxAdminState
    MAX-ACCESS  read-write
    STATUS      obsolete
    DESCRIPTION
        "The value of tmnxSysFpoMacFltOutVlanPrioAdmSt specifies the
         administrative state of the MAC filter outer VLAN priority forwarding
         path option. This object was obsoleted in release 22.2."
    DEFVAL      { outOfService }
    ::= { tmnxSysFwdPathOptsObjs 5 }

tmnxSysFpoMacFltOutVlanPrioOprSt OBJECT-TYPE
    SYNTAX      TmnxOperState
    MAX-ACCESS  read-only
    STATUS      obsolete
    DESCRIPTION
        "The value of tmnxSysFpoMacFltOutVlanPrioOprSt indicates the
         operational state of the MAC filter outer VLAN priority forwarding
         path option. This object was obsoleted in release 22.2."
    ::= { tmnxSysFwdPathOptsObjs 6 }

tmnxSysFpoVplsEvpnMplsAdminState OBJECT-TYPE
    SYNTAX      TmnxAdminState
    MAX-ACCESS  read-write
    STATUS      current
    DESCRIPTION
        "The value of tmnxSysFpoVplsEvpnMplsAdminState specifies the
         administrative state of the VPLS EVPN MPLS forwarding path option."
    DEFVAL      { inService }
    ::= { tmnxSysFwdPathOptsObjs 7 }

tmnxSysFpoVplsEvpnMplsOperState  OBJECT-TYPE
    SYNTAX      TmnxOperState
    MAX-ACCESS  read-only
    STATUS      current
    DESCRIPTION
        "The value of tmnxSysFpoVplsEvpnMplsOperState indicates the operational
         state of the VPLS EVPN MPLS forwarding path option."
    ::= { tmnxSysFwdPathOptsObjs 8 }

tmnxSysFpoQosFc4ProfAdminState   OBJECT-TYPE
    SYNTAX      TmnxAdminState
    MAX-ACCESS  read-write
    STATUS      current
    DESCRIPTION
        "The value of tmnxSysFpoQosFc4ProfAdminState specifies the
         administrative state of the four color mode forwarding path option."
    DEFVAL      { outOfService }
    ::= { tmnxSysFwdPathOptsObjs 9 }

tmnxSysFpoQosFc4ProfOperState    OBJECT-TYPE
    SYNTAX      TmnxOperState
    MAX-ACCESS  read-only
    STATUS      current
    DESCRIPTION
        "The value of tmnxSysFpoQosFc4ProfOperState indicates the operational
         state of the four color mode forwarding path option."
    ::= { tmnxSysFwdPathOptsObjs 10 }

tmnxSysFpoMplsFastSwOvAdminState OBJECT-TYPE
    SYNTAX      TmnxAdminState
    MAX-ACCESS  read-write
    STATUS      obsolete
    DESCRIPTION
        "The value of tmnxSysFpoMplsFastSwOvAdminState specifies the
         administrative state of the MPLS fast switchover forwarding path
         option."
    DEFVAL      { inService }
    ::= { tmnxSysFwdPathOptsObjs 11 }

tmnxSysFpoMplsFastSwOvOperState  OBJECT-TYPE
    SYNTAX      TmnxOperState
    MAX-ACCESS  read-only
    STATUS      obsolete
    DESCRIPTION
        "The value of tmnxSysFpoMplsFastSwOvOperState indicates the operational
         state of the MPLS fast switchover forwarding path option."
    ::= { tmnxSysFwdPathOptsObjs 12 }

tmnxSysFpoRouterEcmpAdminState   OBJECT-TYPE
    SYNTAX      TmnxAdminState
    MAX-ACCESS  read-write
    STATUS      obsolete
    DESCRIPTION
        "The value of tmnxSysFpoRouterEcmpAdminState specifies the
         administrative state of the router ECMP forwarding path option."
    DEFVAL      { inService }
    ::= { tmnxSysFwdPathOptsObjs 13 }

tmnxSysFpoRouterEcmpOperState    OBJECT-TYPE
    SYNTAX      TmnxOperState
    MAX-ACCESS  read-only
    STATUS      obsolete
    DESCRIPTION
        "The value of tmnxSysFpoRouterEcmpOperState indicates the operational
         state of the router ECMP forwarding path option."
    ::= { tmnxSysFwdPathOptsObjs 14 }

tmnxSysFpoQosMacCritAdminState   OBJECT-TYPE
    SYNTAX      TmnxAdminState
    MAX-ACCESS  read-write
    STATUS      current
    DESCRIPTION
        "The value of tmnxSysFpoQosMacCritAdminState specifies the
         administrative state of the MAC criteria for forwarding path option."
    DEFVAL      { outOfService }
    ::= { tmnxSysFwdPathOptsObjs 15 }

tmnxSysFpoQosMacCritOperState    OBJECT-TYPE
    SYNTAX      TmnxOperState
    MAX-ACCESS  read-only
    STATUS      current
    DESCRIPTION
        "The value of tmnxSysFpoQosMacCritOperState indicates the operational
         state of the MAC criteria for forwarding path option."
    ::= { tmnxSysFwdPathOptsObjs 16 }

tmnxSysFpoQosIpv6CritAdminState  OBJECT-TYPE
    SYNTAX      TmnxAdminState
    MAX-ACCESS  read-write
    STATUS      current
    DESCRIPTION
        "The value of tmnxSysFpoQosIpv6CritAdminState specifies the
         administrative state of the IPv6 criteria for forwarding path option."
    DEFVAL      { outOfService }
    ::= { tmnxSysFwdPathOptsObjs 17 }

tmnxSysFpoQosIpv6CritOperState   OBJECT-TYPE
    SYNTAX      TmnxOperState
    MAX-ACCESS  read-only
    STATUS      current
    DESCRIPTION
        "The value of tmnxSysFpoQosIpv6CritOperState indicates the operational
         state of the IPv6 criteria for forwarding path option."
    ::= { tmnxSysFwdPathOptsObjs 18 }

tmnxSysFpoQosBumPolAdminState    OBJECT-TYPE
    SYNTAX      TmnxAdminState
    MAX-ACCESS  read-write
    STATUS      current
    DESCRIPTION
        "The value of tmnxSysFpoQosBumPolAdminState specifies the
         administrative state of the BUM policers for forwarding path option."
    DEFVAL      { outOfService }
    ::= { tmnxSysFwdPathOptsObjs 19 }

tmnxSysFpoQosBumPolOperState     OBJECT-TYPE
    SYNTAX      TmnxOperState
    MAX-ACCESS  read-only
    STATUS      current
    DESCRIPTION
        "The value of tmnxSysFpoQosBumPolOperState indicates the operational
         state of the BUM policers for forwarding path option."
    ::= { tmnxSysFwdPathOptsObjs 20 }

tmnxSysFpoLpmAlcnScl1AdminState  OBJECT-TYPE
    SYNTAX      TmnxAdminState
    MAX-ACCESS  read-write
    STATUS      obsolete
    DESCRIPTION
        "The value of tmnxSysFpoLpmAlcnScl1AdminState specifies the
         administrative state of the LMP allocation scale option 1 for the
         forwarding path option.

         This object was obsoleted in release 22.2. It has been replaced with
         tmnxSysFpResAlcnLpmAdminState when tmnxSysFpResAlcnLpmScaleOption is
         1."
    DEFVAL      { inService }
    ::= { tmnxSysFwdPathOptsObjs 21 }

tmnxSysFpoLpmAlcnScl1OperState   OBJECT-TYPE
    SYNTAX      TmnxOperState
    MAX-ACCESS  read-only
    STATUS      obsolete
    DESCRIPTION
        "The value of tmnxSysFpoLpmAlcnScl1OperState indicates the operational
         state of the LPM allocation scale option 1 for the forwarding path
         option.

         This object was obsoleted in release 22.2. It has been replaced with
         tmnxSysFpResAlcnLpmOperState when tmnxSysFpResAlcnLpmScaleOption is 1."
    ::= { tmnxSysFwdPathOptsObjs 22 }

tmnxSysFpoLpmAlcnScl2AdminState  OBJECT-TYPE
    SYNTAX      TmnxAdminState
    MAX-ACCESS  read-write
    STATUS      obsolete
    DESCRIPTION
        "The value of tmnxSysFpoLpmAlcnScl2AdminState specifies the
         administrative state of the LMP allocation scale option 2 for the
         forwarding path option.

         This object was obsoleted in release 22.2. It has been replaced with
         tmnxSysFpResAlcnLpmAdminState when tmnxSysFpResAlcnLpmScaleOption is
         2."
    DEFVAL      { outOfService }
    ::= { tmnxSysFwdPathOptsObjs 23 }

tmnxSysFpoLpmAlcnScl2OperState   OBJECT-TYPE
    SYNTAX      TmnxOperState
    MAX-ACCESS  read-only
    STATUS      obsolete
    DESCRIPTION
        "The value of tmnxSysFpoLpmAlcnScl2OperState indicates the operational
         state of the LPM allocation scale option 2 for the forwarding path
         option.

         This object was obsoleted in release 22.2. It has been replaced with
         tmnxSysFpResAlcnLpmOperState when tmnxSysFpResAlcnLpmScaleOption is 2."
    ::= { tmnxSysFwdPathOptsObjs 24 }

tmnxSysFpoLpmAlcnScl3AdminState  OBJECT-TYPE
    SYNTAX      TmnxAdminState
    MAX-ACCESS  read-write
    STATUS      obsolete
    DESCRIPTION
        "The value of tmnxSysFpoLpmAlcnScl3AdminState specifies the
         administrative state of the LMP allocation scale option 3 for the
         forwarding path option.

         This object was obsoleted in release 22.2. It has been replaced with
         tmnxSysFpResAlcnLpmAdminState when tmnxSysFpResAlcnLpmScaleOption is
         3."
    DEFVAL      { outOfService }
    ::= { tmnxSysFwdPathOptsObjs 25 }

tmnxSysFpoLpmAlcnScl3OperState   OBJECT-TYPE
    SYNTAX      TmnxOperState
    MAX-ACCESS  read-only
    STATUS      obsolete
    DESCRIPTION
        "The value of tmnxSysFpoLpmAlcnScl3OperState indicates the operational
         state of the LPM allocation scale option 3 for the forwarding path
         option.

         This object was obsoleted in release 22.2. It has been replaced with
         tmnxSysFpResAlcnLpmOperState when tmnxSysFpResAlcnLpmScaleOption is 3."
    ::= { tmnxSysFwdPathOptsObjs 26 }

tmnxSysFpoDot1xHostAuthAdmState  OBJECT-TYPE
    SYNTAX      TmnxAdminState
    MAX-ACCESS  read-write
    STATUS      current
    DESCRIPTION
        "The value of tmnxSysFpoDot1xHostAuthAdmState specifies the
         administrative state of the Ethernet Dot1x per host authentication
         forwarding path option."
    DEFVAL      { outOfService }
    ::= { tmnxSysFwdPathOptsObjs 27 }

tmnxSysFpoDot1xHostAuthOperState OBJECT-TYPE
    SYNTAX      TmnxOperState
    MAX-ACCESS  read-only
    STATUS      current
    DESCRIPTION
        "The value of tmnxSysFpoDot1xHostAuthOperState indicates the
         operational state of the Ethernet Dot1x per host authentication
         forwarding path option."
    ::= { tmnxSysFwdPathOptsObjs 28 }

tmnxSysFpoIpv6FltrEgrAdminState  OBJECT-TYPE
    SYNTAX      TmnxAdminState
    MAX-ACCESS  read-write
    STATUS      current
    DESCRIPTION
        "The value of tmnxSysFpoIpv6FltrEgrAdminState specifies the
         administrative state of the egress ipv6 filter forwarding path option."
    DEFVAL      { inService }
    ::= { tmnxSysFwdPathOptsObjs 29 }

tmnxSysFpoIpv6FltrEgrOperState   OBJECT-TYPE
    SYNTAX      TmnxOperState
    MAX-ACCESS  read-only
    STATUS      current
    DESCRIPTION
        "The value of tmnxSysFpoIpv6FltrEgrOperState indicates the operational
         state of the egress ipv6 filter forwarding path option."
    ::= { tmnxSysFwdPathOptsObjs 30 }

tmnxSysFpoIpv6FltrNxtHdrAdmState OBJECT-TYPE
    SYNTAX      TmnxAdminState
    MAX-ACCESS  read-write
    STATUS      current
    DESCRIPTION
        "The value of tmnxSysFpoIpv6FltrNxtHdrAdmState specifies the
         administrative state of the IPv6 filter next header forwarding path
         option."
    DEFVAL      { inService }
    ::= { tmnxSysFwdPathOptsObjs 31 }

tmnxSysFpoIpv6FltrNxtHdrOprState OBJECT-TYPE
    SYNTAX      TmnxOperState
    MAX-ACCESS  read-only
    STATUS      current
    DESCRIPTION
        "The value of tmnxSysFpoIpv6FltrNxtHdrOprState indicates the
         operational state of the IPv6 filter next header forwarding path
         option."
    ::= { tmnxSysFwdPathOptsObjs 32 }

tmnxSysFpoIpv6FltrDstPrtAdmState OBJECT-TYPE
    SYNTAX      TmnxAdminState
    MAX-ACCESS  read-write
    STATUS      current
    DESCRIPTION
        "The value of tmnxSysFpoIpv6FltrDstPrtAdmState specifies the
         administrative state of the IPv6 filter destination port forwarding
         path option."
    DEFVAL      { inService }
    ::= { tmnxSysFwdPathOptsObjs 33 }

tmnxSysFpoIpv6FltrDstPrtOprState OBJECT-TYPE
    SYNTAX      TmnxOperState
    MAX-ACCESS  read-only
    STATUS      current
    DESCRIPTION
        "The value of tmnxSysFpoIpv6FltrDstPrtOprState indicates the
         operational state of the IPv6 filter destination port forwarding path
         option."
    ::= { tmnxSysFwdPathOptsObjs 34 }

tmnxSysFpoIpv6FltrSrcPrtAdmState OBJECT-TYPE
    SYNTAX      TmnxAdminState
    MAX-ACCESS  read-write
    STATUS      current
    DESCRIPTION
        "The value of tmnxSysFpoIpv6FltrSrcPrtAdmState specifies the
         administrative state of the IPv6 filter source port forwarding path
         option."
    DEFVAL      { inService }
    ::= { tmnxSysFwdPathOptsObjs 35 }

tmnxSysFpoIpv6FltrSrcPrtOprState OBJECT-TYPE
    SYNTAX      TmnxOperState
    MAX-ACCESS  read-only
    STATUS      current
    DESCRIPTION
        "The value of tmnxSysFpoIpv6FltrSrcPrtOprState indicates the
         operational state of the IPv6 filter source port forwarding path
         option."
    ::= { tmnxSysFwdPathOptsObjs 36 }

tmnxSysFpoIpv6FltrDstIpLsbAdmSt  OBJECT-TYPE
    SYNTAX      TmnxAdminState
    MAX-ACCESS  read-write
    STATUS      current
    DESCRIPTION
        "The value of tmnxSysFpoIpv6FltrDstIpLsbAdmSt specifies the
         administrative state of the IPv6 filter destination IP least
         significant bit forwarding path option."
    DEFVAL      { outOfService }
    ::= { tmnxSysFwdPathOptsObjs 37 }

tmnxSysFpoIpv6FltrDstIpLsbOprSt  OBJECT-TYPE
    SYNTAX      TmnxOperState
    MAX-ACCESS  read-only
    STATUS      current
    DESCRIPTION
        "The value of tmnxSysFpoIpv6FltrDstIpLsbOprSt indicates the operational
         state of the IPv6 filter destination IP least significant bit
         forwarding path option."
    ::= { tmnxSysFwdPathOptsObjs 38 }

tmnxSysFpoIpv6FltrTcpFlgAdmState OBJECT-TYPE
    SYNTAX      TmnxAdminState
    MAX-ACCESS  read-write
    STATUS      current
    DESCRIPTION
        "The value of tmnxSysFpoIpv6FltrTcpFlgAdmState specifies the
         administrative state of the IPv6 filter TCP flags forwarding path
         option."
    DEFVAL      { inService }
    ::= { tmnxSysFwdPathOptsObjs 39 }

tmnxSysFpoIpv6FltrTcpFlgOprState OBJECT-TYPE
    SYNTAX      TmnxOperState
    MAX-ACCESS  read-only
    STATUS      current
    DESCRIPTION
        "The value of tmnxSysFpoIpv6FltrTcpFlgOprState indicates the
         operational state of the IPv6 filter TCP flags forwarding path option."
    ::= { tmnxSysFwdPathOptsObjs 40 }

tmnxSysFpoIpv6FltStatColAdmState OBJECT-TYPE
    SYNTAX      TmnxAdminState
    MAX-ACCESS  read-write
    STATUS      current
    DESCRIPTION
        "The value of tmnxSysFpoIpv6FltStatColAdmState specifies the
         administrative state of the IPv6 filter statistics collection
         forwarding path option."
    DEFVAL      { inService }
    ::= { tmnxSysFwdPathOptsObjs 41 }

tmnxSysFpoIpv6FltStatColOprState OBJECT-TYPE
    SYNTAX      TmnxOperState
    MAX-ACCESS  read-only
    STATUS      current
    DESCRIPTION
        "The value of tmnxSysFpoIpv6FltStatColOprState indicates the
         operational state of the IPv6 filter statistics collection forwarding
         path option."
    ::= { tmnxSysFwdPathOptsObjs 42 }

tmnxSysFpoIpv4FltStatColAdmState OBJECT-TYPE
    SYNTAX      TmnxAdminState
    MAX-ACCESS  read-write
    STATUS      current
    DESCRIPTION
        "The value of tmnxSysFpoIpv4FltStatColAdmState specifies the
         administrative state of the IPv4 filter statistics collection
         forwarding path option."
    DEFVAL      { inService }
    ::= { tmnxSysFwdPathOptsObjs 43 }

tmnxSysFpoIpv4FltStatColOprState OBJECT-TYPE
    SYNTAX      TmnxOperState
    MAX-ACCESS  read-only
    STATUS      current
    DESCRIPTION
        "The value of tmnxSysFpoIpv4FltStatColOprState indicates the
         operational state of the IPv4 filter statistics collection forwarding
         path option."
    ::= { tmnxSysFwdPathOptsObjs 44 }

tmnxSysFpoIpv4FltPbrRdrtAdmState OBJECT-TYPE
    SYNTAX      TmnxAdminState
    MAX-ACCESS  read-write
    STATUS      current
    DESCRIPTION
        "The value of tmnxSysFpoIpv4FltPbrRdrtAdmState specifies the
         administrative state of the IPv4 filter Policy Based Routing (PBR)
         redirect forwarding path option."
    DEFVAL      { outOfService }
    ::= { tmnxSysFwdPathOptsObjs 45 }

tmnxSysFpoIpv4FltPbrRdrtOprState OBJECT-TYPE
    SYNTAX      TmnxOperState
    MAX-ACCESS  read-only
    STATUS      current
    DESCRIPTION
        "The value of tmnxSysFpoIpv4FltPbrRdrtOprState indicates the
         operational state of the IPv4 filter Policy Based Routing (PBR)
         redirect forwarding path option."
    ::= { tmnxSysFwdPathOptsObjs 46 }

tmnxSysFpoIpv6FltPbrRdrtAdmState OBJECT-TYPE
    SYNTAX      TmnxAdminState
    MAX-ACCESS  read-write
    STATUS      current
    DESCRIPTION
        "The value of tmnxSysFpoIpv6FltPbrRdrtAdmState specifies the
         administrative state of the IPv6 filter Policy Based Routing (PBR)
         redirect forwarding path option."
    DEFVAL      { outOfService }
    ::= { tmnxSysFwdPathOptsObjs 47 }

tmnxSysFpoIpv6FltPbrRdrtOprState OBJECT-TYPE
    SYNTAX      TmnxOperState
    MAX-ACCESS  read-only
    STATUS      current
    DESCRIPTION
        "The value of tmnxSysFpoIpv6FltPbrRdrtOprState indicates the
         operational state of the IPv6 filter Policy Based Routing (PBR)
         redirect forwarding path option."
    ::= { tmnxSysFwdPathOptsObjs 48 }

tmnxSysFpoRingApsAdminState      OBJECT-TYPE
    SYNTAX      TmnxAdminState
    MAX-ACCESS  read-write
    STATUS      current
    DESCRIPTION
        "The value of tmnxSysFpoRingApsAdminState specifies the administrative
         state of the ring aps forwarding path option."
    DEFVAL      { outOfService }
    ::= { tmnxSysFwdPathOptsObjs 49 }

tmnxSysFpoRingApsOperState       OBJECT-TYPE
    SYNTAX      TmnxOperState
    MAX-ACCESS  read-only
    STATUS      current
    DESCRIPTION
        "The value of tmnxSysFpoRingApsOperState indicates the operational
         state of the ring aps forwarding path option."
    ::= { tmnxSysFwdPathOptsObjs 50 }

tmnxSysFpoSvcCesAdminState       OBJECT-TYPE
    SYNTAX      TmnxAdminState
    MAX-ACCESS  read-write
    STATUS      current
    DESCRIPTION
        "The value of tmnxSysFpoSvcCesAdminState specifies the administrative
         state of the CES service forwarding path option.

         When the value is outOfService, 4K egress encapsulation entries
         dedicated to CES will be freed up for dynamic resource allocation."
    DEFVAL      { inService }
    ::= { tmnxSysFwdPathOptsObjs 51 }

tmnxSysFpoSvcCesOperState        OBJECT-TYPE
    SYNTAX      TmnxOperState
    MAX-ACCESS  read-only
    STATUS      current
    DESCRIPTION
        "The value of tmnxSysFpoSvcCesOperState indicates the operational state
         of the CES service forwarding path option."
    ::= { tmnxSysFwdPathOptsObjs 52 }

tmnxSysFpoIpv6FltrFlwLblAdmState OBJECT-TYPE
    SYNTAX      TmnxAdminState
    MAX-ACCESS  read-write
    STATUS      current
    DESCRIPTION
        "The value of tmnxSysFpoIpv6FltrFlwLblAdmState specifies the
         administrative state of the IPv6 filter flow-label forwarding path
         option."
    DEFVAL      { outOfService }
    ::= { tmnxSysFwdPathOptsObjs 53 }

tmnxSysFpoIpv6FltrFlwLblOprState OBJECT-TYPE
    SYNTAX      TmnxOperState
    MAX-ACCESS  read-only
    STATUS      current
    DESCRIPTION
        "The value of tmnxSysFpoIpv6FltrFlwLblOprState indicates the
         operational state of the IPv6 filter flow-label forwarding path
         option."
    ::= { tmnxSysFwdPathOptsObjs 54 }

tmnxSysFpoQosSharedPolAdminState OBJECT-TYPE
    SYNTAX      TmnxAdminState
    MAX-ACCESS  read-write
    STATUS      current
    DESCRIPTION
        "The value of tmnxSysFpoQosSharedPolAdminState indicates the
         administrative state of the QoS Shared Policer forwarding path option."
    DEFVAL      { outOfService }
    ::= { tmnxSysFwdPathOptsObjs 55 }

tmnxSysFpoQosSharedPolOperState  OBJECT-TYPE
    SYNTAX      TmnxOperState
    MAX-ACCESS  read-only
    STATUS      current
    DESCRIPTION
        "The value of tmnxSysFpoQosSharedPolOperState indicates the operational
         state of the QoS Shared Policer forwarding path option."
    ::= { tmnxSysFwdPathOptsObjs 56 }

tmnxSysFpoLagAlbAdminState       OBJECT-TYPE
    SYNTAX      TmnxAdminState
    MAX-ACCESS  read-write
    STATUS      current
    DESCRIPTION
        "The value of tmnxSysFpoLagAlbAdminState indicates the administrative
         state of the LAG adaptive load balancing forwarding path option."
    DEFVAL      { outOfService }
    ::= { tmnxSysFwdPathOptsObjs 57 }

tmnxSysFpoLagAlbOperState        OBJECT-TYPE
    SYNTAX      TmnxOperState
    MAX-ACCESS  read-only
    STATUS      current
    DESCRIPTION
        "The value of tmnxSysFpoLagAlbOperState indicates the operational state
         of the LAG adaptive load balancing forwarding path option."
    ::= { tmnxSysFwdPathOptsObjs 58 }

tmnxSysFpoMplsHierTunAdminState  OBJECT-TYPE
    SYNTAX      TmnxAdminState
    MAX-ACCESS  read-write
    STATUS      current
    DESCRIPTION
        "The value of tmnxSysFpoMplsHierTunAdminState specifies the
         administrative state of the mpls hierarchical tunnel forwarding path
         option."
    DEFVAL      { outOfService }
    ::= { tmnxSysFwdPathOptsObjs 61 }

tmnxSysFpoMplsHierTunOperState   OBJECT-TYPE
    SYNTAX      TmnxOperState
    MAX-ACCESS  read-only
    STATUS      current
    DESCRIPTION
        "The value of tmnxSysFpoMplsHierTunOperState specifies the operational
         state of the mpls hierarchical tunnel forwarding path option."
    ::= { tmnxSysFwdPathOptsObjs 62 }

tmnxSysSwitchFabricObjs          OBJECT IDENTIFIER ::= { tmnxSysObjs 49 }

tmnxSysSwFabSfmLossThresh        OBJECT-TYPE
    SYNTAX      Unsigned32 (1..7)
    MAX-ACCESS  read-write
    STATUS      current
    DESCRIPTION
        "The value of tmnxSysSwFabSfmLossThresh specifies the number of SFMs
         which are allowed to fail before the system goes into SFM overload
         state."
    ::= { tmnxSysSwitchFabricObjs 1 }

tmnxSysSwFabFailRecAdminState    OBJECT-TYPE
    SYNTAX      TmnxEnabledDisabledAdminState
    MAX-ACCESS  read-write
    STATUS      current
    DESCRIPTION
        "The value of tmnxSysSwFabFailRecAdminState specifies the
         administrative state of the automatic switch fabric recovery process."
    DEFVAL      { disabled }
    ::= { tmnxSysSwitchFabricObjs 2 }

tmnxSysSwFabFailRecOperState     OBJECT-TYPE
    SYNTAX      INTEGER {
        disabled                  (0),
        holdDown                  (1),
        ready                     (2),
        recoveryInProgress        (3),
        detectedDisabled          (4),
        detectedHoldDown          (5),
        detectedXRS40Migration    (6),
        detectedSFMUpgradePending (7)
    }
    MAX-ACCESS  read-only
    STATUS      current
    DESCRIPTION
        "The value of tmnxSysSwFabFailRecOperState specifies the operational
         state of the automatic switch fabric recovery process."
    ::= { tmnxSysSwitchFabricObjs 3 }

tmnxSysUsbTable                  OBJECT-TYPE
    SYNTAX      SEQUENCE OF TmnxSysUsbEntry
    MAX-ACCESS  not-accessible
    STATUS      current
    DESCRIPTION
        "The table tmnxSysUsbTable contains configuration information of the
         Universal Serial Bus (USB) supported by the system."
    ::= { tmnxSysObjs 50 }

tmnxSysUsbEntry                  OBJECT-TYPE
    SYNTAX      TmnxSysUsbEntry
    MAX-ACCESS  not-accessible
    STATUS      current
    DESCRIPTION
        "Each row entry represents a compact flash that can be used for a
         Universal Serial Bus (USB) port.  Rows in the table tmnxSysUsbTable
         are created only by the system at its startup and are never destroyed."
    INDEX       { tmnxSysUsbCFlashId }
    ::= { tmnxSysUsbTable 1 }

TmnxSysUsbEntry                  ::= SEQUENCE
{
    tmnxSysUsbCFlashId               INTEGER,
    tmnxSysUsbLastChgd               TimeStamp,
    tmnxSysUsbAdminState             TmnxEnabledDisabledAdminState
}

tmnxSysUsbCFlashId               OBJECT-TYPE
    SYNTAX      INTEGER {
        cf2 (2)
    }
    MAX-ACCESS  not-accessible
    STATUS      current
    DESCRIPTION
        "The value of the object tmnxSysUsbCFlashId specifies the ID of the
         compact flash."
    ::= { tmnxSysUsbEntry 1 }

tmnxSysUsbLastChgd               OBJECT-TYPE
    SYNTAX      TimeStamp
    MAX-ACCESS  read-only
    STATUS      current
    DESCRIPTION
        "The value of the object tmnxSysUsbLastChgd indicates the sysUpTime at
         the time of creation or at the last modification of this row in
         tmnxSysUsbTable."
    ::= { tmnxSysUsbEntry 2 }

tmnxSysUsbAdminState             OBJECT-TYPE
    SYNTAX      TmnxEnabledDisabledAdminState
    MAX-ACCESS  read-write
    STATUS      current
    DESCRIPTION
        "The value of tmnxSysUsbAdminState specifies the administrative state
         of the Universal Serial Bus (USB) port.

         When set to 'disabled', the USB port is powered off. When set to
         'enabled', the USB port is powered on."
    DEFVAL      { disabled }
    ::= { tmnxSysUsbEntry 3 }

tmnxSysRemoteMgmt                OBJECT IDENTIFIER ::= { tmnxSysObjs 52 }

tmnxSysRmtMgmtAdminState         OBJECT-TYPE
    SYNTAX      TmnxAdminState
    MAX-ACCESS  read-write
    STATUS      current
    DESCRIPTION
        "The value of tmnxSysRmtMgmtAdminState specifies the desired
         administrative state of the remote-management."
    DEFVAL      { outOfService }
    ::= { tmnxSysRemoteMgmt 1 }

tmnxSysRmtMgmtOperState          OBJECT-TYPE
    SYNTAX      TmnxOperState
    MAX-ACCESS  read-only
    STATUS      current
    DESCRIPTION
        "The value of tmnxSysRmtMgmtOperState indicates the current operational
         state of remote-management."
    ::= { tmnxSysRemoteMgmt 2 }

tmnxSysRmtMgmtOperDownReason     OBJECT-TYPE
    SYNTAX      INTEGER {
        unknown           (0),
        adminDown         (1),
        noManager         (2),
        activeDelayOnBoot (3)
    }
    MAX-ACCESS  read-only
    STATUS      current
    DESCRIPTION
        "The value of tmnxSysRmtMgmtOperDownReason indicates the reason why
         remote-management is operationally down."
    ::= { tmnxSysRemoteMgmt 3 }

tmnxSysRmtMgmtAllowUnsecure      OBJECT-TYPE
    SYNTAX      TruthValue
    MAX-ACCESS  read-write
    STATUS      current
    DESCRIPTION
        "The value of tmnxSysRmtMgmtAllowUnsecure specifies whether remote
         management will run without secured transport protocol."
    DEFVAL      { false }
    ::= { tmnxSysRemoteMgmt 4 }

tmnxSysRmtMgmtTlsClientProf      OBJECT-TYPE
    SYNTAX      TNamedItemOrEmpty
    MAX-ACCESS  read-write
    STATUS      current
    DESCRIPTION
        "The value of tmnxSysRmtMgmtTlsClientProf specifies the name of the TLS
         client profile to be used. The value must be valid active row in
         tTlsClntProfileTable."
    DEFVAL      { ''H }
    ::= { tmnxSysRemoteMgmt 5 }

tmnxSysRmtMgmtTimeout            OBJECT-TYPE
    SYNTAX      Unsigned32 (1..3600)
    UNITS       "seconds"
    MAX-ACCESS  read-write
    STATUS      current
    DESCRIPTION
        "The value of tmnxSysRmtMgmtTimeout specifies the remote-management
         connection timeout."
    DEFVAL      { 60 }
    ::= { tmnxSysRemoteMgmt 6 }

tmnxSysRmtMgmtVRtrId             OBJECT-TYPE
    SYNTAX      TmnxVRtrID
    MAX-ACCESS  read-write
    STATUS      current
    DESCRIPTION
        "The value of tmnxSysRmtMgmtVRtrId specifies the virtual router
         identifier used to configure this device. The value must be valid
         active row in vRtrConfTable."
    DEFVAL      { 4095 }
    ::= { tmnxSysRemoteMgmt 7 }

tmnxSysRmtMgmtSrcIpAddType       OBJECT-TYPE
    SYNTAX      InetAddressType
    MAX-ACCESS  read-write
    STATUS      current
    DESCRIPTION
        "The value of the object tmnxSysRmtMgmtSrcIpAddType indicates the type
         of IP address stored in tmnxSysRmtMgmtSrcIpAddress. The value can be
         either 'unknown', 'ipv4' or 'ipv6."
    ::= { tmnxSysRemoteMgmt 8 }

tmnxSysRmtMgmtSrcIpAddress       OBJECT-TYPE
    SYNTAX      InetAddress (SIZE (0|4|16))
    MAX-ACCESS  read-write
    STATUS      current
    DESCRIPTION
        "The value of the object tmnxSysRmtMgmtSrcIpAddress indicates the
         source IP address of this device."
    ::= { tmnxSysRemoteMgmt 9 }

tmnxSysRmtMgmtSrcPort            OBJECT-TYPE
    SYNTAX      InetPortNumber
    MAX-ACCESS  read-write
    STATUS      current
    DESCRIPTION
        "The value of the object tmnxSysRmtMgmtSrcPort indicates the source
         port of this device. Setting non-zero value overrides
         tmnxSysRmtMgmtSrcDefaultPort to 'none'."
    DEFVAL      { 0 }
    ::= { tmnxSysRemoteMgmt 10 }

tmnxSysRmtMgmtSrcDefaultPort     OBJECT-TYPE
    SYNTAX      TmnxSysRmtMgmtSrcDefaultPort
    MAX-ACCESS  read-write
    STATUS      current
    DESCRIPTION
        "The value of the object tmnxSysRmtMgmtSrcDefaultPort indicates the
         source port of this device uses default configured port. Setting value
         other than 'none' value overrides tmnxSysRmtMgmtSrcPort to zero."
    DEFVAL      { grpc }
    ::= { tmnxSysRemoteMgmt 11 }

tmnxSysRmtMgmtDeviceLabel        OBJECT-TYPE
    SYNTAX      TLNamedItemOrEmpty
    MAX-ACCESS  read-write
    STATUS      current
    DESCRIPTION
        "The value of tmnxSysRmtMgmtDeviceLabel specifies a label that helps to
         identify this device."
    DEFVAL      { ''H }
    ::= { tmnxSysRemoteMgmt 12 }

tmnxSysRmtMgmtDeviceName         OBJECT-TYPE
    SYNTAX      TLNamedItemOrEmpty
    MAX-ACCESS  read-write
    STATUS      current
    DESCRIPTION
        "The value of tmnxSysRmtMgmtDeviceName specifies the name that
         identifies this device."
    DEFVAL      { ''H }
    ::= { tmnxSysRemoteMgmt 13 }

tmnxSysRmtMgmtLastRegStatus      OBJECT-TYPE
    SYNTAX      TmnxSysRmtMgmtLastRegStatus
    MAX-ACCESS  read-only
    STATUS      current
    DESCRIPTION
        "The value of tmnxSysRmtMgmtLastRegStatus specifies a status of last
         registration."
    ::= { tmnxSysRemoteMgmt 14 }

tmnxSysRmtMgmtLastRegTime        OBJECT-TYPE
    SYNTAX      DateAndTime
    MAX-ACCESS  read-only
    STATUS      current
    DESCRIPTION
        "The value of tmnxSysRmtMgmtLastRegTime specifies a last time the
         remote-management client tried to register."
    ::= { tmnxSysRemoteMgmt 15 }

tmnxSysRmtMgmtRegsCancelled      OBJECT-TYPE
    SYNTAX      Counter64
    MAX-ACCESS  read-only
    STATUS      current
    DESCRIPTION
        "The value of tmnxSysRmtMgmtRegsCancelled specifies a number of
         cancelled registrations."
    ::= { tmnxSysRemoteMgmt 16 }

tmnxSysRmtMgmtRegsFailed         OBJECT-TYPE
    SYNTAX      Counter64
    MAX-ACCESS  read-only
    STATUS      current
    DESCRIPTION
        "The value of tmnxSysRmtMgmtRegsFailed specifies a number of failed
         registrations."
    ::= { tmnxSysRemoteMgmt 17 }

tmnxSysRmtMgmtRegsSent           OBJECT-TYPE
    SYNTAX      Counter64
    MAX-ACCESS  read-only
    STATUS      current
    DESCRIPTION
        "The value of tmnxSysRmtMgmtRegsSent specifies a number of successful
         registrations."
    ::= { tmnxSysRemoteMgmt 18 }

tmnxSysRmtMgmtHelloInterval      OBJECT-TYPE
    SYNTAX      Unsigned32 (10..3600)
    UNITS       "minutes"
    MAX-ACCESS  read-write
    STATUS      obsolete
    DESCRIPTION
        "The value of tmnxSysRmtMgmtHelloInterval specifies number of minutes
         between hello."
    DEFVAL      { 10 }
    ::= { tmnxSysRemoteMgmt 19 }

tmnxSysRmtMgmtLastHelloTime      OBJECT-TYPE
    SYNTAX      DateAndTime
    MAX-ACCESS  read-only
    STATUS      current
    DESCRIPTION
        "The value of tmnxSysRmtMgmtLastHelloTime specifies a last time the
         remote-management client successfully registered."
    ::= { tmnxSysRemoteMgmt 20 }

tmnxSysRmtMgmtManagerTable       OBJECT-TYPE
    SYNTAX      SEQUENCE OF TmnxSysRmtMgmtManagerEntry
    MAX-ACCESS  not-accessible
    STATUS      current
    DESCRIPTION
        "The tmnxSysRmtMgmtManagerTable has an entry for each configured
         manager."
    ::= { tmnxSysRemoteMgmt 21 }

tmnxSysRmtMgmtManagerEntry       OBJECT-TYPE
    SYNTAX      TmnxSysRmtMgmtManagerEntry
    MAX-ACCESS  not-accessible
    STATUS      current
    DESCRIPTION
        "Each row entry contains remote-management manager configuration."
    INDEX       { IMPLIED tmnxSysRmtMgmtMgrName }
    ::= { tmnxSysRmtMgmtManagerTable 1 }

TmnxSysRmtMgmtManagerEntry       ::= SEQUENCE
{
    tmnxSysRmtMgmtMgrName            TLNamedItem,
    tmnxSysRmtMgmtMgrRowStatus       RowStatus,
    tmnxSysRmtMgmtMgrAdminState      TmnxAdminState,
    tmnxSysRmtMgmtMgrOperState       TmnxOperState,
    tmnxSysRmtMgmtMgrOperDownReason  INTEGER,
    tmnxSysRmtMgmtMgrFQDN            DisplayString,
    tmnxSysRmtMgmtMgrIpAddType       InetAddressType,
    tmnxSysRmtMgmtMgrIpAddress       InetAddress,
    tmnxSysRmtMgmtMgrPort            InetPortNumber,
    tmnxSysRmtMgmtMgrAllowUnsecure   TruthValue,
    tmnxSysRmtMgmtMgrTlsClientProf   TNamedItemOrEmpty,
    tmnxSysRmtMgmtMgrDescription     TItemDescription,
    tmnxSysRmtMgmtMgrTimeout         Unsigned32,
    tmnxSysRmtMgmtMgrVRtrId          TmnxVRtrIDOrZero,
    tmnxSysRmtMgmtMgrSrcIpAddType    InetAddressType,
    tmnxSysRmtMgmtMgrSrcIpAddress    InetAddress,
    tmnxSysRmtMgmtMgrSrcPort         InetPortNumber,
    tmnxSysRmtMgmtMgrSrcDefaultPort  TmnxSysRmtMgmtSrcDefaultPort,
    tmnxSysRmtMgmtMgrDeviceLabel     TLNamedItemOrEmpty,
    tmnxSysRmtMgmtMgrDeviceName      TLNamedItemOrEmpty,
    tmnxSysRmtMgmtMgrLastRegStatus   TmnxSysRmtMgmtLastRegStatus,
    tmnxSysRmtMgmtMgrLastRegTime     DateAndTime,
    tmnxSysRmtMgmtMgrRegsCancelled   Counter64,
    tmnxSysRmtMgmtMgrRegsFailed      Counter64,
    tmnxSysRmtMgmtMgrRegsSent        Counter64,
    tmnxSysRmtMgmtMgrOperTlsProf     TNamedItemOrEmpty,
    tmnxSysRmtMgmtMgrOperTranspType  INTEGER,
    tmnxSysRmtMgmtMgrOperTimeout     Unsigned32,
    tmnxSysRmtMgmtMgrOperVRtrId      TmnxVRtrIDOrZero,
    tmnxSysRmtMgmtMgrOperDevName     TLNamedItemOrEmpty,
    tmnxSysRmtMgmtMgrOperDevLabel    TLNamedItemOrEmpty,
    tmnxSysRmtMgmtMgrOperSrcIpAdType InetAddressType,
    tmnxSysRmtMgmtMgrOperSrcIpAddr   InetAddress,
    tmnxSysRmtMgmtMgrOperSrcPort     InetPortNumber
}

tmnxSysRmtMgmtMgrName            OBJECT-TYPE
    SYNTAX      TLNamedItem
    MAX-ACCESS  not-accessible
    STATUS      current
    DESCRIPTION
        "The name for a remote-management manager"
    ::= { tmnxSysRmtMgmtManagerEntry 1 }

tmnxSysRmtMgmtMgrRowStatus       OBJECT-TYPE
    SYNTAX      RowStatus
    MAX-ACCESS  read-create
    STATUS      current
    DESCRIPTION
        "The row status used to create and delete rows in this table."
    ::= { tmnxSysRmtMgmtManagerEntry 2 }

tmnxSysRmtMgmtMgrAdminState      OBJECT-TYPE
    SYNTAX      TmnxAdminState
    MAX-ACCESS  read-create
    STATUS      current
    DESCRIPTION
        "The value of tmnxSysRmtMgmtMgrAdminState specifies the desired
         administrative state of the remote-management."
    DEFVAL      { outOfService }
    ::= { tmnxSysRmtMgmtManagerEntry 3 }

tmnxSysRmtMgmtMgrOperState       OBJECT-TYPE
    SYNTAX      TmnxOperState
    MAX-ACCESS  read-only
    STATUS      current
    DESCRIPTION
        "The value of tmnxSysRmtMgmtMgrOperState indicates the current
         operational state of remote-management."
    ::= { tmnxSysRmtMgmtManagerEntry 4 }

tmnxSysRmtMgmtMgrOperDownReason  OBJECT-TYPE
    SYNTAX      INTEGER {
        unknown               (0),
        adminDown             (1),
        noTransportType       (2),
        noSourceAddress       (3),
        invalidManagerAddress (4),
        registration-failed   (5),
        activeDelayOnBoot     (6)
    }
    MAX-ACCESS  read-only
    STATUS      current
    DESCRIPTION
        "The value of tmnxSysRmtMgmtMgrOperDownReason indicates the reason why
         remote-management manager is down."
    ::= { tmnxSysRmtMgmtManagerEntry 5 }

tmnxSysRmtMgmtMgrFQDN            OBJECT-TYPE
    SYNTAX      DisplayString (SIZE (0..255))
    MAX-ACCESS  read-create
    STATUS      current
    DESCRIPTION
        "The value of tmnxSysRmtMgmtMgrFQDN specifies the Fully Qualified
         Domain Name (FQDN) associated with the manager. Setting value other
         than '' resets tmnxSysRmtMgmtMgrIpAddress."
    DEFVAL      { ''H }
    ::= { tmnxSysRmtMgmtManagerEntry 6 }

tmnxSysRmtMgmtMgrIpAddType       OBJECT-TYPE
    SYNTAX      InetAddressType
    MAX-ACCESS  read-create
    STATUS      current
    DESCRIPTION
        "The value of the object tmnxSysRmtMgmtMgrIpAddType indicates the type
         of IP address stored in tmnxSysRmtMgmtMgrIpAddress. The value can be
         either 'unknown', 'ipv4' or 'ipv6."
    ::= { tmnxSysRmtMgmtManagerEntry 7 }

tmnxSysRmtMgmtMgrIpAddress       OBJECT-TYPE
    SYNTAX      InetAddress (SIZE (0|4|16))
    MAX-ACCESS  read-create
    STATUS      current
    DESCRIPTION
        "The value of the object tmnxSysRmtMgmtMgrIpAddress indicates the
         manager IP address where registrations will be sent. Setting value
         other than '' resets tmnxSysRmtMgmtMgrFQDN."
    ::= { tmnxSysRmtMgmtManagerEntry 8 }

tmnxSysRmtMgmtMgrPort            OBJECT-TYPE
    SYNTAX      InetPortNumber
    MAX-ACCESS  read-create
    STATUS      current
    DESCRIPTION
        "The value of the object tmnxSysRmtMgmtMgrPort indicates the port where
         registrations will be sent."
    DEFVAL      { 57400 }
    ::= { tmnxSysRmtMgmtManagerEntry 9 }

tmnxSysRmtMgmtMgrAllowUnsecure   OBJECT-TYPE
    SYNTAX      TruthValue
    MAX-ACCESS  read-create
    STATUS      current
    DESCRIPTION
        "The value of tmnxSysRmtMgmtMgrAllowUnsecure specifies whether remote
         management will run without secured transport protocol."
    DEFVAL      { false }
    ::= { tmnxSysRmtMgmtManagerEntry 10 }

tmnxSysRmtMgmtMgrTlsClientProf   OBJECT-TYPE
    SYNTAX      TNamedItemOrEmpty
    MAX-ACCESS  read-create
    STATUS      current
    DESCRIPTION
        "The value of tmnxSysRmtMgmtMgrTlsClientProf specifies the name of the
         TLS client profile to be used. The value must be valid active row in
         tTlsClntProfileTable."
    DEFVAL      { ''H }
    ::= { tmnxSysRmtMgmtManagerEntry 11 }

tmnxSysRmtMgmtMgrDescription     OBJECT-TYPE
    SYNTAX      TItemDescription
    MAX-ACCESS  read-create
    STATUS      current
    DESCRIPTION
        "The value of tmnxSysRmtMgmtMgrDescription specifies the
         remote-management manager description."
    DEFVAL      { ''H }
    ::= { tmnxSysRmtMgmtManagerEntry 12 }

tmnxSysRmtMgmtMgrTimeout         OBJECT-TYPE
    SYNTAX      Unsigned32 (0 | 1..3600)
    UNITS       "seconds"
    MAX-ACCESS  read-create
    STATUS      current
    DESCRIPTION
        "The value of tmnxSysRmtMgmtMgrTimeout specifies the remote-management
         connection timeout. If set to 0 the value is inherited from
         tmnxSysRmtMgmtTimeout."
    DEFVAL      { 0 }
    ::= { tmnxSysRmtMgmtManagerEntry 13 }

tmnxSysRmtMgmtMgrVRtrId          OBJECT-TYPE
    SYNTAX      TmnxVRtrIDOrZero
    MAX-ACCESS  read-create
    STATUS      current
    DESCRIPTION
        "The value of tmnxSysRmtMgmtMgrVRtrId specifies the virtual router
         identifier used to configure this device. If set the value must be
         valid active row in vRtrConfTable. Else the value is inherited from
         tmnxSysRmtMgmtVRtrId."
    DEFVAL      { 0 }
    ::= { tmnxSysRmtMgmtManagerEntry 14 }

tmnxSysRmtMgmtMgrSrcIpAddType    OBJECT-TYPE
    SYNTAX      InetAddressType
    MAX-ACCESS  read-create
    STATUS      current
    DESCRIPTION
        "The value of the object tmnxSysRmtMgmtMgrSrcIpAddType indicates the
         type of IP address stored in tmnxSysRmtMgmtMgrSrcIpAddress. The value
         can be either 'unknown', 'ipv4' or 'ipv6."
    ::= { tmnxSysRmtMgmtManagerEntry 15 }

tmnxSysRmtMgmtMgrSrcIpAddress    OBJECT-TYPE
    SYNTAX      InetAddress (SIZE (0|4|16))
    MAX-ACCESS  read-create
    STATUS      current
    DESCRIPTION
        "The value of the object tmnxSysRmtMgmtMgrSrcIpAddress indicates the
         source IP address of this device. If not set the value is inherited
         from tmnxSysRmtMgmtSrcIpAddress."
    ::= { tmnxSysRmtMgmtManagerEntry 16 }

tmnxSysRmtMgmtMgrSrcPort         OBJECT-TYPE
    SYNTAX      InetPortNumber
    MAX-ACCESS  read-create
    STATUS      current
    DESCRIPTION
        "The value of the object tmnxSysRmtMgmtMgrSrcPort indicates the source
         port of this device."
    DEFVAL      { 0 }
    ::= { tmnxSysRmtMgmtManagerEntry 17 }

tmnxSysRmtMgmtMgrSrcDefaultPort  OBJECT-TYPE
    SYNTAX      TmnxSysRmtMgmtSrcDefaultPort
    MAX-ACCESS  read-create
    STATUS      current
    DESCRIPTION
        "The value of the object tmnxSysRmtMgmtMgrSrcDefaultPort indicates the
         source port of this device uses default configured port. if
         tmnxSysRmtMgmtMgrSrcDefaultPort equals to 'none' and
         tmnxSysRmtMgmtMgrSrcPort equals to zero the configuration is inherited
         form either tmnxSysRmtMgmtSrcDefaultPort or tmnxSysRmtMgmtMgrSrcPort"
    DEFVAL      { none }
    ::= { tmnxSysRmtMgmtManagerEntry 18 }

tmnxSysRmtMgmtMgrDeviceLabel     OBJECT-TYPE
    SYNTAX      TLNamedItemOrEmpty
    MAX-ACCESS  read-create
    STATUS      current
    DESCRIPTION
        "The value of tmnxSysRmtMgmtMgrDeviceLabel specifies a label that helps
         to identify this device. If not set the value is inherited from
         tmnxSysRmtMgmtDeviceLabel."
    DEFVAL      { ''H }
    ::= { tmnxSysRmtMgmtManagerEntry 19 }

tmnxSysRmtMgmtMgrDeviceName      OBJECT-TYPE
    SYNTAX      TLNamedItemOrEmpty
    MAX-ACCESS  read-create
    STATUS      current
    DESCRIPTION
        "The value of tmnxSysRmtMgmtMgrDeviceName specifies the name that
         identifies this device. If not set the value is inherited from
         tmnxSysRmtMgmtDeviceName."
    DEFVAL      { ''H }
    ::= { tmnxSysRmtMgmtManagerEntry 20 }

tmnxSysRmtMgmtMgrLastRegStatus   OBJECT-TYPE
    SYNTAX      TmnxSysRmtMgmtLastRegStatus
    MAX-ACCESS  read-only
    STATUS      current
    DESCRIPTION
        "The value of tmnxSysRmtMgmtMgrLastRegStatus specifies a status of last
         registration."
    ::= { tmnxSysRmtMgmtManagerEntry 21 }

tmnxSysRmtMgmtMgrLastRegTime     OBJECT-TYPE
    SYNTAX      DateAndTime
    MAX-ACCESS  read-only
    STATUS      current
    DESCRIPTION
        "The value of tmnxSysRmtMgmtMgrLastRegTime specifies a last time the
         remote-management client tied to register."
    ::= { tmnxSysRmtMgmtManagerEntry 22 }

tmnxSysRmtMgmtMgrRegsCancelled   OBJECT-TYPE
    SYNTAX      Counter64
    MAX-ACCESS  read-only
    STATUS      current
    DESCRIPTION
        "The value of tmnxSysRmtMgmtMgrRegsCancelled specifies a number of
         cancelled registrations."
    ::= { tmnxSysRmtMgmtManagerEntry 23 }

tmnxSysRmtMgmtMgrRegsFailed      OBJECT-TYPE
    SYNTAX      Counter64
    MAX-ACCESS  read-only
    STATUS      current
    DESCRIPTION
        "The value of tmnxSysRmtMgmtMgrRegsFailed specifies a number of failed
         registrations."
    ::= { tmnxSysRmtMgmtManagerEntry 24 }

tmnxSysRmtMgmtMgrRegsSent        OBJECT-TYPE
    SYNTAX      Counter64
    MAX-ACCESS  read-only
    STATUS      current
    DESCRIPTION
        "The value of tmnxSysRmtMgmtMgrRegsSent specifies a number of
         successful registrations."
    ::= { tmnxSysRmtMgmtManagerEntry 25 }

tmnxSysRmtMgmtMgrOperTlsProf     OBJECT-TYPE
    SYNTAX      TNamedItemOrEmpty
    MAX-ACCESS  read-only
    STATUS      current
    DESCRIPTION
        "The value of tmnxSysRmtMgmtMgrOperTlsProf declares which client tls
         profile is in use."
    ::= { tmnxSysRmtMgmtManagerEntry 26 }

tmnxSysRmtMgmtMgrOperTranspType  OBJECT-TYPE
    SYNTAX      INTEGER {
        none      (0),
        tls       (1),
        unsecured (2)
    }
    MAX-ACCESS  read-only
    STATUS      current
    DESCRIPTION
        "The value of tmnxSysRmtMgmtMgrOperTranspType specifies whether the
         remote-management registers using tls or tcp."
    ::= { tmnxSysRmtMgmtManagerEntry 27 }

tmnxSysRmtMgmtMgrOperTimeout     OBJECT-TYPE
    SYNTAX      Unsigned32
    UNITS       "seconds"
    MAX-ACCESS  read-only
    STATUS      current
    DESCRIPTION
        "The value of tmnxSysRmtMgmtMgrOperTimeout specifies used connection
         timeout."
    ::= { tmnxSysRmtMgmtManagerEntry 28 }

tmnxSysRmtMgmtMgrOperVRtrId      OBJECT-TYPE
    SYNTAX      TmnxVRtrIDOrZero
    MAX-ACCESS  read-only
    STATUS      current
    DESCRIPTION
        "The value of tmnxSysRmtMgmtMgrOperVRtrId specifies used virtual router
         id."
    ::= { tmnxSysRmtMgmtManagerEntry 29 }

tmnxSysRmtMgmtMgrOperDevName     OBJECT-TYPE
    SYNTAX      TLNamedItemOrEmpty
    MAX-ACCESS  read-only
    STATUS      current
    DESCRIPTION
        "The value of tmnxSysRmtMgmtMgrOperDevName specifies operational name
         that identifies this device."
    ::= { tmnxSysRmtMgmtManagerEntry 30 }

tmnxSysRmtMgmtMgrOperDevLabel    OBJECT-TYPE
    SYNTAX      TLNamedItemOrEmpty
    MAX-ACCESS  read-only
    STATUS      current
    DESCRIPTION
        "The value of tmnxSysRmtMgmtMgrOperDevLabel specifies operational label
         that helps to identify this device."
    ::= { tmnxSysRmtMgmtManagerEntry 31 }

tmnxSysRmtMgmtMgrOperSrcIpAdType OBJECT-TYPE
    SYNTAX      InetAddressType
    MAX-ACCESS  read-only
    STATUS      current
    DESCRIPTION
        "The value of the object tmnxSysRmtMgmtMgrOperSrcIpAdType indicates the
         type of IP address stored in tmnxSysRmtMgmtMgrOperSrcIpAddr. The value
         can be either 'unknown', 'ipv4' or 'ipv6."
    ::= { tmnxSysRmtMgmtManagerEntry 32 }

tmnxSysRmtMgmtMgrOperSrcIpAddr   OBJECT-TYPE
    SYNTAX      InetAddress (SIZE (0|4|16))
    MAX-ACCESS  read-only
    STATUS      current
    DESCRIPTION
        "The value of the object tmnxSysRmtMgmtMgrOperSrcIpAddr indicates
         operational source IP address of this device."
    ::= { tmnxSysRmtMgmtManagerEntry 33 }

tmnxSysRmtMgmtMgrOperSrcPort     OBJECT-TYPE
    SYNTAX      InetPortNumber
    MAX-ACCESS  read-only
    STATUS      current
    DESCRIPTION
        "The value of the object tmnxSysRmtMgmtMgrOperSrcPort indicates
         operational source port of this device."
    ::= { tmnxSysRmtMgmtManagerEntry 34 }

tmnxSysRmtMgmtHelloIntervalSec   OBJECT-TYPE
    SYNTAX      Unsigned32 (10..216000)
    UNITS       "seconds"
    MAX-ACCESS  read-write
    STATUS      current
    DESCRIPTION
        "The value of tmnxSysRmtMgmtHelloIntervalSec specifies number of
         seconds between hello."
    DEFVAL      { 600 }
    ::= { tmnxSysRemoteMgmt 22 }

tmnxSysRmtMgmtDelayOnBoot        OBJECT-TYPE
    SYNTAX      Unsigned32 (0 | 1..3600)
    UNITS       "seconds"
    MAX-ACCESS  read-write
    STATUS      current
    DESCRIPTION
        "The value of tmnxSysRmtMgmtDelayOnBoot specifies the timeout since the
         system boots, after which remote-management becomes operational.

         This value only takes effect when remote-management is enabled in boot
         configuration file. When tmnxSysRmtMgmtAdminState is set to
         'inService', the remote-management will become operational
         immediately."
    DEFVAL      { 0 }
    ::= { tmnxSysRemoteMgmt 23 }

tmnxSysMgmtInterfaceOperations   OBJECT IDENTIFIER ::= { tmnxSysObjs 53 }

tmnxSysMgmtIfOpsAsyncExecTimeout OBJECT-TYPE
    SYNTAX      Unsigned32 (0..604800)
    UNITS       "seconds"
    MAX-ACCESS  read-create
    STATUS      current
    DESCRIPTION
        "The value of the object tmnxSysMgmtIfOpsAsyncExecTimeout specifies
         default timeout for asynchronous operation execution. Operations
         exceeding the timeout will be stopped. Can be overridden for specific
         operations. Value 0 indicates no timeout."
    DEFVAL      { 3600 }
    ::= { tmnxSysMgmtInterfaceOperations 1 }

tmnxSysMgmtIfOpsAsyncRetTimeout  OBJECT-TYPE
    SYNTAX      Unsigned32 (0..604800)
    UNITS       "seconds"
    MAX-ACCESS  read-create
    STATUS      current
    DESCRIPTION
        "The value of the object tmnxSysMgmtIfOpsAsyncRetTimeout default
         timeout for asynchronous operation data retention. Timer starts when
         operation finishes and operation data will be erased from the global
         operation table when it expires. Can be overridden for specific
         operations. Value 0 indicates no timeout."
    DEFVAL      { 86400 }
    ::= { tmnxSysMgmtInterfaceOperations 2 }

tmnxSysMgmtIfOpsSyncExecTimeout  OBJECT-TYPE
    SYNTAX      Unsigned32 (0..604800)
    UNITS       "seconds"
    MAX-ACCESS  read-create
    STATUS      current
    DESCRIPTION
        "The value of the object tmnxSysMgmtIfOpsSyncExecTimeout specifies
         default timeout for synchronous operation execution. Operations
         exceeding the timeout will be stopped and operation data will be
         erased from the global operation table. Can be overridden for specific
         operations. Value 0 indicates no timeout."
    DEFVAL      { 0 }
    ::= { tmnxSysMgmtInterfaceOperations 3 }

tmnxSysSwFabFailRecSfmStatsTable OBJECT-TYPE
    SYNTAX      SEQUENCE OF TmnxSysSwFabFailRecSfmStatsEntry
    MAX-ACCESS  not-accessible
    STATUS      current
    DESCRIPTION
        "The tmnxSysSwFabFailRecSfmStatsTable contains status information for
         the automatic switch fabric failure recovery process for all SFMs.
         This table is ordered based on the order in which the SFMs are to be
         reset during the recovery process."
    ::= { tmnxSysObjs 54 }

tmnxSysSwFabFailRecSfmStatsEntry OBJECT-TYPE
    SYNTAX      TmnxSysSwFabFailRecSfmStatsEntry
    MAX-ACCESS  not-accessible
    STATUS      current
    DESCRIPTION
        "Each tmnxSysSwFabFailRecSfmStatsEntry consists of status information
         for the automatic switch fabric failure recovery process for a
         specific SFM. Rows in this table are created by the system when the
         automatic recovery process starts."
    INDEX       { tmnxFabricSlotNum }
    ::= { tmnxSysSwFabFailRecSfmStatsTable 1 }

TmnxSysSwFabFailRecSfmStatsEntry ::= SEQUENCE
{
    tmnxSysSwFabFailRecSfmState      INTEGER,
    tmnxSysSwFabFailRecSfmStateTime  TimeStamp
}

tmnxSysSwFabFailRecSfmState      OBJECT-TYPE
    SYNTAX      INTEGER {
        complete   (0),
        inProgress (1),
        pending    (2),
        aborted    (3),
        failed     (4)
    }
    MAX-ACCESS  read-only
    STATUS      current
    DESCRIPTION
        "The value of tmnxSysSwFabFailRecSfmState indicates the current state
         of the SFM in the automatic switch fabric recovery process.

         Values:
             complete   - this SFM has already been reset as part of the
                          recovery process
             inProgress - this SFM is currently being reset
             pending    - this SFM has not yet been reset
             aborted    - the recovery was aborted before this SFM
                          was processed
             failed     - the SFM has not successfully completed"
    ::= { tmnxSysSwFabFailRecSfmStatsEntry 1 }

tmnxSysSwFabFailRecSfmStateTime  OBJECT-TYPE
    SYNTAX      TimeStamp
    MAX-ACCESS  read-only
    STATUS      current
    DESCRIPTION
        "The value of tmnxSysSwFabFailRecSfmStateTime indicates the time, since
         system startup, when tmnxSysSwFabFailRecSfmState changed."
    ::= { tmnxSysSwFabFailRecSfmStatsEntry 2 }

sysBofInfoExt                    OBJECT IDENTIFIER ::= { tmnxSysObjs 55 }

sbiEncryptConfig                 OBJECT-TYPE
    SYNTAX      TruthValue
    MAX-ACCESS  read-write
    STATUS      current
    DESCRIPTION
        "The value of sbiEncryptConfig indicates whether or not BOF
         configuration files saved by the SROS system will be encrypted."
    DEFVAL      { false }
    ::= { sysBofInfoExt 1 }

sbiPassword                      OBJECT-TYPE
    SYNTAX      DisplayString (SIZE (0..32))
    MAX-ACCESS  read-write
    STATUS      current
    DESCRIPTION
        "The value of sbiPassword specifies the password that must be entered
         in order to modify boot parameters in the console during the boot
         sequence.

         A get request to this object will always return an empty string.

         By default, sbiPassword will be an empty string."
    DEFVAL      { "" }
    ::= { sysBofInfoExt 2 }

sbiEncryptKey                    OBJECT-TYPE
    SYNTAX      DisplayString (SIZE (0..32))
    MAX-ACCESS  read-write
    STATUS      current
    DESCRIPTION
        "The value of sbiEncryptKey specifies the key used when decrypting
         configuration files.

         A get request to this object will always return an empty string.

         By default, sbiEncryptKey will be an empty string."
    DEFVAL      { "" }
    ::= { sysBofInfoExt 3 }

sbiFipsLevel1                    OBJECT-TYPE
    SYNTAX      TruthValue
    MAX-ACCESS  read-create
    STATUS      current
    DESCRIPTION
        "The value of sbiFipsLevel1 specifies whether or not the security level
         1 of Federal Information Processing Standards is enabled.

         A change to the value of this object does not take effect until after
         a system reboot."
    DEFVAL      { false }
    ::= { sysBofInfoExt 4 }

tmnxSysGrpcPendRebTable          OBJECT-TYPE
    SYNTAX      SEQUENCE OF TmnxSysGrpcPendRebEntry
    MAX-ACCESS  not-accessible
    STATUS      current
    DESCRIPTION
        "The table tmnxSysGrpcPendRebTable contains read-only information
         pertaining to active and canceled reboots."
    ::= { tmnxSysObjs 56 }

tmnxSysGrpcPendRebEntry          OBJECT-TYPE
    SYNTAX      TmnxSysGrpcPendRebEntry
    MAX-ACCESS  not-accessible
    STATUS      current
    DESCRIPTION
        "Each row entry represents a single requested or canceled reboot.

         Rows in the table tmnxSysGrpcPendRebEntry are automatically created by
         the system when Gnoi.System Reboot or Cancel Reboot RPC is
         successfully processed."
    INDEX       { tmnxSysGrpcPendRebComp }
    ::= { tmnxSysGrpcPendRebTable 1 }

TmnxSysGrpcPendRebEntry          ::= SEQUENCE
{
    tmnxSysGrpcPendRebComp           TLNamedItem,
    tmnxSysGrpcPendRebOperState      TmnxOperState,
    tmnxSysGrpcPendRebDelay          Unsigned32,
    tmnxSysGrpcPendRebMsg            OCTET STRING,
    tmnxSysGrpcPendRebCount          Unsigned32
}

tmnxSysGrpcPendRebComp           OBJECT-TYPE
    SYNTAX      TLNamedItem
    MAX-ACCESS  not-accessible
    STATUS      current
    DESCRIPTION
        "The value of the object tmnxSysGrpcPendRebComp indicates the object of
         Reboot or Cancel Reboot RPC."
    ::= { tmnxSysGrpcPendRebEntry 1 }

tmnxSysGrpcPendRebOperState      OBJECT-TYPE
    SYNTAX      TmnxOperState
    MAX-ACCESS  read-only
    STATUS      current
    DESCRIPTION
        "The value of tmnxSysGrpcPendRebOperState indicates the current
         operational state of reboot procedure."
    ::= { tmnxSysGrpcPendRebEntry 2 }

tmnxSysGrpcPendRebDelay          OBJECT-TYPE
    SYNTAX      Unsigned32
    UNITS       "seconds"
    MAX-ACCESS  read-only
    STATUS      current
    DESCRIPTION
        "The value of the object tmnxSysGrpcPendRebDelay indicates the time
         left until reboot."
    ::= { tmnxSysGrpcPendRebEntry 3 }

tmnxSysGrpcPendRebMsg            OBJECT-TYPE
    SYNTAX      OCTET STRING (SIZE (0..256))
    MAX-ACCESS  read-only
    STATUS      current
    DESCRIPTION
        "The value of the object tmnxSysGrpcPendRebMsg indicates reason for
         reboot or for cancellation of any outstanding reboot."
    ::= { tmnxSysGrpcPendRebEntry 4 }

tmnxSysGrpcPendRebCount          OBJECT-TYPE
    SYNTAX      Unsigned32
    MAX-ACCESS  read-only
    STATUS      current
    DESCRIPTION
        "The value of the object tmnxSysGrpcPendRebCount indicates the number
         of reboots since active."
    ::= { tmnxSysGrpcPendRebEntry 5 }

tmnxSysGrpcTunnelObjs            OBJECT IDENTIFIER ::= { tmnxSysObjs 57 }

tmnxSysGrpcTunnelLastChangedObjs OBJECT IDENTIFIER ::= { tmnxSysGrpcTunnelObjs 1 }

tmnxGTnlDestGrpTblLastChgd       OBJECT-TYPE
    SYNTAX      TimeStamp
    MAX-ACCESS  read-only
    STATUS      current
    DESCRIPTION
        "The value of tmnxGTnlDestGrpTblLastChgd indicates the time, since
         system startup, when tmnxGrpcTunnelDestGroupTable last changed
         configuration.

         A value of zero indicates that no changes were made to this table
         since the system was last initialized."
    ::= { tmnxSysGrpcTunnelLastChangedObjs 1 }

tmnxGTnlDestGrpDestTblLastChgd   OBJECT-TYPE
    SYNTAX      TimeStamp
    MAX-ACCESS  read-only
    STATUS      current
    DESCRIPTION
        "The value of tmnxGTnlDestGrpDestTblLastChgd indicates the time, since
         system startup, when tmnxGrpcTunnelDestGroupDestTable last changed
         configuration.

         A value of zero indicates that no changes were made to this table
         since the system was last initialized."
    ::= { tmnxSysGrpcTunnelLastChangedObjs 2 }

tmnxGTnlTunnelTblLastChgd        OBJECT-TYPE
    SYNTAX      TimeStamp
    MAX-ACCESS  read-only
    STATUS      current
    DESCRIPTION
        "The value of tmnxGTnlTunnelTblLastChgd indicates the time, since
         system startup, when tmnxGTnlTunnelTable last changed configuration.

         A value of zero indicates that no changes were made to this table
         since the system was last initialized."
    ::= { tmnxSysGrpcTunnelLastChangedObjs 3 }

tmnxGTnlTunnelHandlerTblLastChgd OBJECT-TYPE
    SYNTAX      TimeStamp
    MAX-ACCESS  read-only
    STATUS      current
    DESCRIPTION
        "The value of tmnxGTnlTunnelHandlerTblLastChgd indicates the time,
         since system startup, when tmnxGTnlTunnelHandlerTable last changed
         configuration.

         A value of zero indicates that no changes were made to this table
         since the system was last initialized."
    ::= { tmnxSysGrpcTunnelLastChangedObjs 4 }

tmnxGrpcTunnelDestGroupTable     OBJECT-TYPE
    SYNTAX      SEQUENCE OF TmnxGrpcTunnelDestGroupEntry
    MAX-ACCESS  not-accessible
    STATUS      current
    DESCRIPTION
        "The tmnxGrpcTunnelDestGroupTable stores configuration and status
         information related to gRPC-Tunnel destination groups."
    ::= { tmnxSysGrpcTunnelObjs 2 }

tmnxGrpcTunnelDestGroupEntry     OBJECT-TYPE
    SYNTAX      TmnxGrpcTunnelDestGroupEntry
    MAX-ACCESS  not-accessible
    STATUS      current
    DESCRIPTION
        "The tmnxGrpcTunnelDestGroupEntry is an entry (conceptual row) in the
         tmnxGrpcTunnelDestGroupTable. Each entry contains information
         pertaining to a gRPC-Tunnel destination group.

         Entries in this table can be created and deleted via SNMP SET
         operations to tmnxGTnlDestGrpRowStatus."
    INDEX       { tmnxGTnlDestGrpName }
    ::= { tmnxGrpcTunnelDestGroupTable 1 }

TmnxGrpcTunnelDestGroupEntry     ::= SEQUENCE
{
    tmnxGTnlDestGrpName              TNamedItem,
    tmnxGTnlDestGrpRowStatus         RowStatus,
    tmnxGTnlDestGrpLastChgd          TimeStamp,
    tmnxGTnlDestGrpDescription       TItemDescription,
    tmnxGTnlDestGrpTlsClientProf     TNamedItemOrEmpty,
    tmnxGTnlDestGrpAllowUnsecConn    TruthValue,
    tmnxGTnlDestGrpTcpKaAdminState   TmnxAdminState,
    tmnxGTnlDestGrpTcpKaIdle         Unsigned32,
    tmnxGTnlDestGrpTcpKaInterval     Unsigned32,
    tmnxGTnlDestGrpTcpKaCount        Unsigned32
}

tmnxGTnlDestGrpName              OBJECT-TYPE
    SYNTAX      TNamedItem
    MAX-ACCESS  not-accessible
    STATUS      current
    DESCRIPTION
        "The value of the object tmnxGTnlDestGrpName specifies a gRPC-Tunnel
         destination group name."
    ::= { tmnxGrpcTunnelDestGroupEntry 1 }

tmnxGTnlDestGrpRowStatus         OBJECT-TYPE
    SYNTAX      RowStatus
    MAX-ACCESS  read-create
    STATUS      current
    DESCRIPTION
        "The value of the object tmnxGTnlDestGrpRowStatus specifies the status
         of the conceptual row in tmnxGrpcTunnelDestGroupTable.

         Rows are created and destroyed by SNMP SET operations on this object.

         Only values 'active(1)', 'createAndGo(4)' and 'destroy(6)' are
         supported."
    ::= { tmnxGrpcTunnelDestGroupEntry 2 }

tmnxGTnlDestGrpLastChgd          OBJECT-TYPE
    SYNTAX      TimeStamp
    MAX-ACCESS  read-only
    STATUS      current
    DESCRIPTION
        "The value of tmnxGTnlDestGrpLastChgd indicates the time, since system
         startup, that the configuration of this row was created or modified."
    ::= { tmnxGrpcTunnelDestGroupEntry 3 }

tmnxGTnlDestGrpDescription       OBJECT-TYPE
    SYNTAX      TItemDescription
    MAX-ACCESS  read-create
    STATUS      current
    DESCRIPTION
        "The value of the object tmnxGTnlDestGrpDescription specifies a user
         provided description related to gRPC-Tunnel destination group. It
         consists of any printable, seven-bit ASCII characters up to 80
         characters in length."
    DEFVAL      { "" }
    ::= { tmnxGrpcTunnelDestGroupEntry 4 }

tmnxGTnlDestGrpTlsClientProf     OBJECT-TYPE
    SYNTAX      TNamedItemOrEmpty
    MAX-ACCESS  read-create
    STATUS      current
    DESCRIPTION
        "The value of tmnxGTnlDestGrpTlsClientProf specifies the name of the
         TLS client profile to be used."
    DEFVAL      { ''H }
    ::= { tmnxGrpcTunnelDestGroupEntry 5 }

tmnxGTnlDestGrpAllowUnsecConn    OBJECT-TYPE
    SYNTAX      TruthValue
    MAX-ACCESS  read-create
    STATUS      current
    DESCRIPTION
        "The value of tmnxGTnlDestGrpAllowUnsecConn specifies whether
         gRPC-Tunnel will run without secured transport protocol. All data will
         be transferred in unencrypted form."
    DEFVAL      { false }
    ::= { tmnxGrpcTunnelDestGroupEntry 6 }

tmnxGTnlDestGrpTcpKaAdminState   OBJECT-TYPE
    SYNTAX      TmnxAdminState
    MAX-ACCESS  read-create
    STATUS      current
    DESCRIPTION
        "The value of tmnxGTnlDestGrpTcpKaAdminState specifies the
         administrative state of the TCP keepalive algorithm."
    DEFVAL      { outOfService }
    ::= { tmnxGrpcTunnelDestGroupEntry 7 }

tmnxGTnlDestGrpTcpKaIdle         OBJECT-TYPE
    SYNTAX      Unsigned32 (1..100000)
    UNITS       "seconds"
    MAX-ACCESS  read-create
    STATUS      current
    DESCRIPTION
        "The value of the object tmnxGTnlDestGrpTcpKaIdle specifies the number
         of seconds until the first TCP keepalive probe is sent."
    DEFVAL      { 600 }
    ::= { tmnxGrpcTunnelDestGroupEntry 8 }

tmnxGTnlDestGrpTcpKaInterval     OBJECT-TYPE
    SYNTAX      Unsigned32 (1..100000)
    UNITS       "seconds"
    MAX-ACCESS  read-create
    STATUS      current
    DESCRIPTION
        "The value of the object tmnxGTnlDestGrpTcpKaInterval specifies the
         number of seconds between two TCP keepalives probes."
    DEFVAL      { 15 }
    ::= { tmnxGrpcTunnelDestGroupEntry 9 }

tmnxGTnlDestGrpTcpKaCount        OBJECT-TYPE
    SYNTAX      Unsigned32 (3..100)
    MAX-ACCESS  read-create
    STATUS      current
    DESCRIPTION
        "The value of the object tmnxGTnlDestGrpTcpKaCount specifies the number
         of missed keepalives before the TCP connection is declared down."
    DEFVAL      { 4 }
    ::= { tmnxGrpcTunnelDestGroupEntry 10 }

tmnxGrpcTunnelDestGroupDestTable OBJECT-TYPE
    SYNTAX      SEQUENCE OF TmnxGrpcTunnelDestGroupDestEntry
    MAX-ACCESS  not-accessible
    STATUS      current
    DESCRIPTION
        "The tmnxGrpcTunnelDestGroupDestTable stores configuration and status
         information related to gRPC-Tunnel destinations."
    ::= { tmnxSysGrpcTunnelObjs 3 }

tmnxGrpcTunnelDestGroupDestEntry OBJECT-TYPE
    SYNTAX      TmnxGrpcTunnelDestGroupDestEntry
    MAX-ACCESS  not-accessible
    STATUS      current
    DESCRIPTION
        "The tmnxGrpcTunnelDestGroupDestEntry is an entry (conceptual row) in
         the tmnxGrpcTunnelDestGroupDestTable. Each entry contains information
         pertaining to a gRPC-Tunnel destination.

         Entries in this table can be created and deleted via SNMP SET
         operations to tmnxGTnlDestGrpDestRowStatus."
    INDEX       {
        tmnxGTnlDestGrpName,
        tmnxGTnlDestGrpDestIndex
    }
    ::= { tmnxGrpcTunnelDestGroupDestTable 1 }

TmnxGrpcTunnelDestGroupDestEntry ::= SEQUENCE
{
    tmnxGTnlDestGrpDestIndex         Unsigned32,
    tmnxGTnlDestGrpDestRowStatus     RowStatus,
    tmnxGTnlDestGrpDestLastChgd      TimeStamp,
    tmnxGTnlDestGrpDestAddType       InetAddressType,
    tmnxGTnlDestGrpDestAddress       InetAddress,
    tmnxGTnlDestGrpDestPort          InetPortNumber,
    tmnxGTnlDestGrpDestVRtrId        TmnxVRtrIDOrZero,
    tmnxGTnlDestGrpDestLclSrcAddType InetAddressType,
    tmnxGTnlDestGrpDestLclSrcAddress InetAddress,
    tmnxGTnlDestGrpDestOrigQosMark   TDSCPNameOrEmpty
}

tmnxGTnlDestGrpDestIndex         OBJECT-TYPE
    SYNTAX      Unsigned32 (1..4)
    MAX-ACCESS  not-accessible
    STATUS      current
    DESCRIPTION
        "The value of the object tmnxGTnlDestGrpDestIndex indicates the index
         of the destination. Every destination group can have multiple
         destinations, therefore every destination is identified by the
         tmnxGTnlDestGrpName and tmnxGTnlDestGrpDestIndex."
    ::= { tmnxGrpcTunnelDestGroupDestEntry 1 }

tmnxGTnlDestGrpDestRowStatus     OBJECT-TYPE
    SYNTAX      RowStatus
    MAX-ACCESS  read-create
    STATUS      current
    DESCRIPTION
        "The value of the object tmnxGTnlDestGrpDestRowStatus specifies the
         status of the conceptual row in tmnxGrpcTunnelDestGroupDestTable.

         Rows are created and destroyed by SNMP SET operations on this object.

         Only values 'active(1)', 'createAndGo(4)' and 'destroy(6)' are
         supported."
    ::= { tmnxGrpcTunnelDestGroupDestEntry 2 }

tmnxGTnlDestGrpDestLastChgd      OBJECT-TYPE
    SYNTAX      TimeStamp
    MAX-ACCESS  read-only
    STATUS      current
    DESCRIPTION
        "The value of tmnxGTnlDestGrpDestLastChgd indicates the time, since
         system startup, that the configuration of this row was created or
         modified."
    ::= { tmnxGrpcTunnelDestGroupDestEntry 3 }

tmnxGTnlDestGrpDestAddType       OBJECT-TYPE
    SYNTAX      InetAddressType
    MAX-ACCESS  read-create
    STATUS      current
    DESCRIPTION
        "The value of the object tmnxGTnlDestGrpDestAddType specifies the
         context (IP address type or Fully Qualified Domain Name (FQDN)) in
         which the value of the object tmnxGTnlDestGrpDestAddress is to be
         interpreted. The value can be either 'unknown', 'ipv4', 'ipv6' or
         'dns'"
    ::= { tmnxGrpcTunnelDestGroupDestEntry 4 }

tmnxGTnlDestGrpDestAddress       OBJECT-TYPE
    SYNTAX      InetAddress (SIZE (0..255))
    MAX-ACCESS  read-create
    STATUS      current
    DESCRIPTION
        "The value of the object tmnxGTnlDestGrpDestAddress specifies the
         remote IP address or FQDN of the gRPC-Tunnel destination."
    ::= { tmnxGrpcTunnelDestGroupDestEntry 5 }

tmnxGTnlDestGrpDestPort          OBJECT-TYPE
    SYNTAX      InetPortNumber
    MAX-ACCESS  read-create
    STATUS      current
    DESCRIPTION
        "The value of the object tmnxGTnlDestGrpDestPort specifies the remote
         port of the gRPC-Tunnel destination."
    ::= { tmnxGrpcTunnelDestGroupDestEntry 6 }

tmnxGTnlDestGrpDestVRtrId        OBJECT-TYPE
    SYNTAX      TmnxVRtrIDOrZero
    MAX-ACCESS  read-create
    STATUS      current
    DESCRIPTION
        "The value of tmnxGTnlDestGrpDestVRtrId indicates the routing context
         of a connection."
    DEFVAL      { 0 }
    ::= { tmnxGrpcTunnelDestGroupDestEntry 7 }

tmnxGTnlDestGrpDestLclSrcAddType OBJECT-TYPE
    SYNTAX      InetAddressType
    MAX-ACCESS  read-create
    STATUS      current
    DESCRIPTION
        "The value of the object tmnxGTnlDestGrpDestLclSrcAddType specifies the
         type of IP address stored in tmnxGTnlDestGrpDestLclSrcAddress. The
         value can be either 'unknown', 'ipv4' or 'ipv6."
    DEFVAL      { unknown }
    ::= { tmnxGrpcTunnelDestGroupDestEntry 8 }

tmnxGTnlDestGrpDestLclSrcAddress OBJECT-TYPE
    SYNTAX      InetAddress (SIZE (0|4|16))
    MAX-ACCESS  read-create
    STATUS      current
    DESCRIPTION
        "The value of tmnxGTnlDestGrpDestLclSrcAddress specifies local IP
         address of the gRPC-Tunnel stream source."
    DEFVAL      { ''H }
    ::= { tmnxGrpcTunnelDestGroupDestEntry 9 }

tmnxGTnlDestGrpDestOrigQosMark   OBJECT-TYPE
    SYNTAX      TDSCPNameOrEmpty
    MAX-ACCESS  read-create
    STATUS      current
    DESCRIPTION
        "The value of tmnxGTnlDestGrpDestOrigQosMark specifies DSCP value of
         data stream."
    DEFVAL      { ''H }
    ::= { tmnxGrpcTunnelDestGroupDestEntry 10 }

tmnxGTnlTunnelTable              OBJECT-TYPE
    SYNTAX      SEQUENCE OF TmnxGTnlTunnelEntry
    MAX-ACCESS  not-accessible
    STATUS      current
    DESCRIPTION
        "The tmnxGTnlTunnelTable stores configuration and status information
         related to tunnel."
    ::= { tmnxSysGrpcTunnelObjs 4 }

tmnxGTnlTunnelEntry              OBJECT-TYPE
    SYNTAX      TmnxGTnlTunnelEntry
    MAX-ACCESS  not-accessible
    STATUS      current
    DESCRIPTION
        "The tmnxGTnlTunnelEntry is an entry (conceptual row) in the
         tmnxGTnlTunnelTable. Each entry contains information pertaining to a
         tunnel"
    INDEX       { tmnxGTnlTunnelName }
    ::= { tmnxGTnlTunnelTable 1 }

TmnxGTnlTunnelEntry              ::= SEQUENCE
{
    tmnxGTnlTunnelName               TNamedItem,
    tmnxGTnlTunnelRowStatus          RowStatus,
    tmnxGTnlTunnelLastChgd           TimeStamp,
    tmnxGTnlTunnelAdminState         TmnxAdminState,
    tmnxGTnlTunnelOperState          TmnxOperState,
    tmnxGTnlTunnelOperDownReason     OCTET STRING,
    tmnxGTnlTunnelDescription        TItemDescription,
    tmnxGTnlTunnelDestGrp            TNamedItemOrEmpty,
    tmnxGTnlTunnelTgtNameCustomStr   DisplayString,
    tmnxGTnlTunnelTgtNameUserAgent   TruthValue,
    tmnxGTnlTunnelTgtNameNodeName    TruthValue,
    tmnxGTnlTunnelOperTargetName     OCTET STRING
}

tmnxGTnlTunnelName               OBJECT-TYPE
    SYNTAX      TNamedItem
    MAX-ACCESS  not-accessible
    STATUS      current
    DESCRIPTION
        "The value of the object tmnxGTnlTunnelName specifies a tunnel name."
    ::= { tmnxGTnlTunnelEntry 1 }

tmnxGTnlTunnelRowStatus          OBJECT-TYPE
    SYNTAX      RowStatus
    MAX-ACCESS  read-create
    STATUS      current
    DESCRIPTION
        "The value of the object tmnxGTnlTunnelRowStatus specifies the status
         of the conceptual row in tmnxGTnlTunnelTable.

         Rows are created and destroyed by SNMP SET operations on this object.

         Only values 'active(1)', 'createAndGo(4)' and 'destroy(6)' are
         supported."
    ::= { tmnxGTnlTunnelEntry 2 }

tmnxGTnlTunnelLastChgd           OBJECT-TYPE
    SYNTAX      TimeStamp
    MAX-ACCESS  read-only
    STATUS      current
    DESCRIPTION
        "The value of tmnxGTnlTunnelLastChgd indicates the time, since system
         startup, that the configuration of this row was created or modified."
    ::= { tmnxGTnlTunnelEntry 3 }

tmnxGTnlTunnelAdminState         OBJECT-TYPE
    SYNTAX      TmnxAdminState
    MAX-ACCESS  read-create
    STATUS      current
    DESCRIPTION
        "The value of tmnxGTnlTunnelAdminState specifies the administrative
         state of the tunnel."
    DEFVAL      { outOfService }
    ::= { tmnxGTnlTunnelEntry 4 }

tmnxGTnlTunnelOperState          OBJECT-TYPE
    SYNTAX      TmnxOperState
    MAX-ACCESS  read-only
    STATUS      current
    DESCRIPTION
        "The value of tmnxGTnlTunnelOperState indicates the current operational
         state of the tunnel."
    ::= { tmnxGTnlTunnelEntry 5 }

tmnxGTnlTunnelOperDownReason     OBJECT-TYPE
    SYNTAX      OCTET STRING (SIZE (0..256))
    MAX-ACCESS  read-only
    STATUS      current
    DESCRIPTION
        "The value of tmnxGTnlTunnelOperDownReason indicates the reason due to
         which tunnel is operationally down."
    ::= { tmnxGTnlTunnelEntry 6 }

tmnxGTnlTunnelDescription        OBJECT-TYPE
    SYNTAX      TItemDescription
    MAX-ACCESS  read-create
    STATUS      current
    DESCRIPTION
        "The value of the object tmnxGTnlTunnelDescription specifies a user
         provided description related to tunnel. It consists of any printable,
         seven-bit ASCII characters up to 80 characters in length."
    DEFVAL      { "" }
    ::= { tmnxGTnlTunnelEntry 7 }

tmnxGTnlTunnelDestGrp            OBJECT-TYPE
    SYNTAX      TNamedItemOrEmpty
    MAX-ACCESS  read-create
    STATUS      current
    DESCRIPTION
        "The value of tmnxGTnlTunnelDestGrp specifies the name of the
         destination group to be used."
    DEFVAL      { ''H }
    ::= { tmnxGTnlTunnelEntry 8 }

tmnxGTnlTunnelTgtNameCustomStr   OBJECT-TYPE
    SYNTAX      DisplayString (SIZE (0..64))
    MAX-ACCESS  read-create
    STATUS      current
    DESCRIPTION
        "The value of tmnxGTnlTunnelTgtNameCustomStr specifies a user provided
         string as target in tunnel capability message."
    DEFVAL      { ''H }
    ::= { tmnxGTnlTunnelEntry 9 }

tmnxGTnlTunnelTgtNameUserAgent   OBJECT-TYPE
    SYNTAX      TruthValue
    MAX-ACCESS  read-create
    STATUS      current
    DESCRIPTION
        "The value of tmnxGTnlTunnelTgtNameUserAgent specifies whether
         automatic string in format 'node name:vendor:model:software version'
         will be used as target in tunnel capability message."
    DEFVAL      { false }
    ::= { tmnxGTnlTunnelEntry 10 }

tmnxGTnlTunnelTgtNameNodeName    OBJECT-TYPE
    SYNTAX      TruthValue
    MAX-ACCESS  read-create
    STATUS      current
    DESCRIPTION
        "The value of tmnxGTnlTunnelTgtNameNodeName specifies whether automatic
         string in format 'node name' will be used as target in tunnel
         capability message."
    DEFVAL      { false }
    ::= { tmnxGTnlTunnelEntry 11 }

tmnxGTnlTunnelOperTargetName     OBJECT-TYPE
    SYNTAX      OCTET STRING (SIZE (0..422))
    MAX-ACCESS  read-only
    STATUS      current
    DESCRIPTION
        "The value of tmnxGTnlTunnelOperTargetName indicates the operational
         target string in tunnel capability message."
    ::= { tmnxGTnlTunnelEntry 12 }

tmnxGTnlTunnelHandlerTable       OBJECT-TYPE
    SYNTAX      SEQUENCE OF TmnxGTnlTunnelHandlerEntry
    MAX-ACCESS  not-accessible
    STATUS      current
    DESCRIPTION
        "The tmnxGTnlTunnelHandlerTable stores configuration and status
         information related to target-types in tunnel."
    ::= { tmnxSysGrpcTunnelObjs 5 }

tmnxGTnlTunnelHandlerEntry       OBJECT-TYPE
    SYNTAX      TmnxGTnlTunnelHandlerEntry
    MAX-ACCESS  not-accessible
    STATUS      current
    DESCRIPTION
        "The tmnxGTnlTunnelHandlerEntry is an entry (conceptual row) in the
         tmnxGTnlTunnelHandlerTable. Each entry contains information pertaining
         to a tunnel target-type.

         Entries in this table can be created and deleted via SNMP SET
         operations to tmnxGTnlTunnelHandlerRowStatus."
    INDEX       {
        tmnxGTnlTunnelName,
        tmnxGTnlTunnelHandlerName
    }
    ::= { tmnxGTnlTunnelHandlerTable 1 }

TmnxGTnlTunnelHandlerEntry       ::= SEQUENCE
{
    tmnxGTnlTunnelHandlerName        TNamedItem,
    tmnxGTnlTunnelHandlerRowStatus   RowStatus,
    tmnxGTnlTunnelHandlerLastChgd    TimeStamp,
    tmnxGTnlTunnelHandlerAdminState  TmnxAdminState,
    tmnxGTnlTunnelHandlerPort        InetPortNumber,
    tmnxGTnlTunnelHandlerCustomType  DisplayString,
    tmnxGTnlTunnelHandlerGrpcServer  TruthValue,
    tmnxGTnlTunnelHandlerSshServer   TruthValue
}

tmnxGTnlTunnelHandlerName        OBJECT-TYPE
    SYNTAX      TNamedItem
    MAX-ACCESS  not-accessible
    STATUS      current
    DESCRIPTION
        "The value of the object tmnxGTnlTunnelHandlerName specifies a
         target-type name."
    ::= { tmnxGTnlTunnelHandlerEntry 1 }

tmnxGTnlTunnelHandlerRowStatus   OBJECT-TYPE
    SYNTAX      RowStatus
    MAX-ACCESS  read-create
    STATUS      current
    DESCRIPTION
        "The value of the object tmnxGTnlTunnelHandlerRowStatus specifies the
         status of the conceptual row in tmnxGTnlTunnelHandlerTable.

         Rows are created and destroyed by SNMP SET operations on this object.

         Only values 'active(1)', 'createAndGo(4)' and 'destroy(6)' are
         supported."
    ::= { tmnxGTnlTunnelHandlerEntry 2 }

tmnxGTnlTunnelHandlerLastChgd    OBJECT-TYPE
    SYNTAX      TimeStamp
    MAX-ACCESS  read-only
    STATUS      current
    DESCRIPTION
        "The value of tmnxGTnlTunnelHandlerLastChgd indicates the time, since
         system startup, that the configuration of this row was created or
         modified."
    ::= { tmnxGTnlTunnelHandlerEntry 3 }

tmnxGTnlTunnelHandlerAdminState  OBJECT-TYPE
    SYNTAX      TmnxAdminState
    MAX-ACCESS  read-create
    STATUS      current
    DESCRIPTION
        "The value of tmnxGTnlTunnelHandlerAdminState specifies the
         administrative state of the target-type."
    DEFVAL      { outOfService }
    ::= { tmnxGTnlTunnelHandlerEntry 4 }

tmnxGTnlTunnelHandlerPort        OBJECT-TYPE
    SYNTAX      InetPortNumber
    MAX-ACCESS  read-create
    STATUS      current
    DESCRIPTION
        "The value of the object tmnxGTnlTunnelHandlerPort specifies the
         localhost port to connect the gRPC-Tunnel session."
    DEFVAL      { 0 }
    ::= { tmnxGTnlTunnelHandlerEntry 5 }

tmnxGTnlTunnelHandlerCustomType  OBJECT-TYPE
    SYNTAX      DisplayString (SIZE (0..64))
    MAX-ACCESS  read-create
    STATUS      current
    DESCRIPTION
        "The value of tmnxGTnlTunnelHandlerCustomType specifies a user provided
         string as target-type in tunnel capability message. This string must
         be unique for a given tunnel. The target-type string should comprise
         only of uppercase letters A-Z, digits 0-9 and underscores '_'."
    DEFVAL      { ''H }
    ::= { tmnxGTnlTunnelHandlerEntry 6 }

tmnxGTnlTunnelHandlerGrpcServer  OBJECT-TYPE
    SYNTAX      TruthValue
    MAX-ACCESS  read-create
    STATUS      current
    DESCRIPTION
        "The value of tmnxGTnlTunnelHandlerGrpcServer specifies whether string
         'GNMI_GNOI' will be used as target-type in tunnel capability message."
    DEFVAL      { false }
    ::= { tmnxGTnlTunnelHandlerEntry 7 }

tmnxGTnlTunnelHandlerSshServer   OBJECT-TYPE
    SYNTAX      TruthValue
    MAX-ACCESS  read-create
    STATUS      current
    DESCRIPTION
        "The value of tmnxGTnlTunnelHandlerSshServer specifies whether string
         'SSH' will be used as target-type in tunnel capability message."
    DEFVAL      { false }
    ::= { tmnxGTnlTunnelHandlerEntry 8 }

tmnxGTnlTunnelDestTable          OBJECT-TYPE
    SYNTAX      SEQUENCE OF TmnxGTnlTunnelDestEntry
    MAX-ACCESS  not-accessible
    STATUS      current
    DESCRIPTION
        "The tmnxGTnlTunnelDestTable stores operational state of destination
         connection used in all tunnels."
    ::= { tmnxSysGrpcTunnelObjs 6 }

tmnxGTnlTunnelDestEntry          OBJECT-TYPE
    SYNTAX      TmnxGTnlTunnelDestEntry
    MAX-ACCESS  not-accessible
    STATUS      current
    DESCRIPTION
        "The tmnxGTnlTunnelDestEntry is an entry in the
         tmnxGTnlTunnelDestTable. Each entry contains information pertaining to
         a destination used in tunnel"
    INDEX       {
        tmnxGTnlTunnelName,
        tmnxGTnlTunnelDestIndex
    }
    ::= { tmnxGTnlTunnelDestTable 1 }

TmnxGTnlTunnelDestEntry          ::= SEQUENCE
{
    tmnxGTnlTunnelDestIndex          Unsigned32,
    tmnxGTnlTunnelDestAddType        InetAddressType,
    tmnxGTnlTunnelDestAddress        InetAddress,
    tmnxGTnlTunnelDestPort           InetPortNumber,
    tmnxGTnlTunnelDestOperState      TmnxOperState,
    tmnxGTnlTunnelDestOperDownReason OCTET STRING,
    tmnxGTnlTunnelDestOperVRtrId     TmnxVRtrIDOrZero,
    tmnxGTnlTunnelDestLastOperChange DateAndTime,
    tmnxGTnlTunnelDestConnAttempts   Counter64
}

tmnxGTnlTunnelDestIndex          OBJECT-TYPE
    SYNTAX      Unsigned32 (1..4)
    MAX-ACCESS  not-accessible
    STATUS      current
    DESCRIPTION
        "The value of the object tmnxGTnlTunnelDestIndex indicates the index of
         the destination used in tunnel. Every tunnel can have multiple
         destinations, therefore every destination is identified by the
         tmnxGTnlTunnelName and tmnxGTnlTunnelDestIndex."
    ::= { tmnxGTnlTunnelDestEntry 1 }

tmnxGTnlTunnelDestAddType        OBJECT-TYPE
    SYNTAX      InetAddressType
    MAX-ACCESS  read-only
    STATUS      current
    DESCRIPTION
        "The value of the object tmnxGTnlTunnelDestAddType specifies the
         context (IP address type or Fully Qualified Domain Name (FQDN)) in
         which the value of the object tmnxGTnlTunnelDestAddress is to be
         interpreted. The value can be either 'unknown', 'ipv4', 'ipv6' or
         'dns'"
    ::= { tmnxGTnlTunnelDestEntry 2 }

tmnxGTnlTunnelDestAddress        OBJECT-TYPE
    SYNTAX      InetAddress (SIZE (0..255))
    MAX-ACCESS  read-only
    STATUS      current
    DESCRIPTION
        "The value of the object tmnxGTnlTunnelDestAddress specifies the remote
         IP address or FQDN of the destination used in tunnel."
    ::= { tmnxGTnlTunnelDestEntry 3 }

tmnxGTnlTunnelDestPort           OBJECT-TYPE
    SYNTAX      InetPortNumber
    MAX-ACCESS  read-only
    STATUS      current
    DESCRIPTION
        "The value of the object tmnxGTnlTunnelDestPort specifies the remote
         port of the destination used in tunnel."
    ::= { tmnxGTnlTunnelDestEntry 4 }

tmnxGTnlTunnelDestOperState      OBJECT-TYPE
    SYNTAX      TmnxOperState
    MAX-ACCESS  read-only
    STATUS      current
    DESCRIPTION
        "The value of tmnxGTnlTunnelDestOperState indicates the current
         operational state of the destination."
    ::= { tmnxGTnlTunnelDestEntry 5 }

tmnxGTnlTunnelDestOperDownReason OBJECT-TYPE
    SYNTAX      OCTET STRING (SIZE (0..256))
    MAX-ACCESS  read-only
    STATUS      current
    DESCRIPTION
        "The value of tmnxGTnlTunnelDestOperDownReason indicates the reason due
         to which destination is operationally down."
    ::= { tmnxGTnlTunnelDestEntry 6 }

tmnxGTnlTunnelDestOperVRtrId     OBJECT-TYPE
    SYNTAX      TmnxVRtrIDOrZero
    MAX-ACCESS  read-only
    STATUS      current
    DESCRIPTION
        "The value of tmnxGTnlTunnelDestOperVRtrId indicates the operational
         routing context of a connection."
    ::= { tmnxGTnlTunnelDestEntry 7 }

tmnxGTnlTunnelDestLastOperChange OBJECT-TYPE
    SYNTAX      DateAndTime
    MAX-ACCESS  read-only
    STATUS      current
    DESCRIPTION
        "The value of tmnxGTnlTunnelDestLastOperChange indicates the time when
         the operational state of this destination last changed."
    ::= { tmnxGTnlTunnelDestEntry 8 }

tmnxGTnlTunnelDestConnAttempts   OBJECT-TYPE
    SYNTAX      Counter64
    MAX-ACCESS  read-only
    STATUS      current
    DESCRIPTION
        "The value of tmnxGTnlTunnelDestConnAttempts indicates the number of
         tried connections towards this destination."
    ::= { tmnxGTnlTunnelDestEntry 9 }

tmnxGTnlTunnelSessionTable       OBJECT-TYPE
    SYNTAX      SEQUENCE OF TmnxGTnlTunnelSessionEntry
    MAX-ACCESS  not-accessible
    STATUS      current
    DESCRIPTION
        "The tmnxGTnlTunnelSessionTable stores all sessions in all tunnels"
    ::= { tmnxSysGrpcTunnelObjs 7 }

tmnxGTnlTunnelSessionEntry       OBJECT-TYPE
    SYNTAX      TmnxGTnlTunnelSessionEntry
    MAX-ACCESS  not-accessible
    STATUS      current
    DESCRIPTION
        "The tmnxGTnlTunnelSessionEntry is an entry in the
         tmnxGTnlTunnelSessionTable. Each entry contains information pertaining
         to an active session in tunnel"
    INDEX       {
        tmnxGTnlTunnelName,
        tmnxGTnlTunnelSessionTag
    }
    ::= { tmnxGTnlTunnelSessionTable 1 }

TmnxGTnlTunnelSessionEntry       ::= SEQUENCE
{
    tmnxGTnlTunnelSessionTag         Integer32,
    tmnxGTnlTunnelSessionStartTime   DateAndTime,
    tmnxGTnlTunnelSessionTargetType  DisplayString,
    tmnxGTnlTunnelSessionLclSrcPort  InetPortNumber,
    tmnxGTnlTunnelSessionRxBytes     Counter64,
    tmnxGTnlTunnelSessionTxBytes     Counter64
}

tmnxGTnlTunnelSessionTag         OBJECT-TYPE
    SYNTAX      Integer32
    MAX-ACCESS  not-accessible
    STATUS      current
    DESCRIPTION
        "The value of the object tmnxGTnlTunnelSessionTag indicates the tag of
         the session. Every tunnel can have multiple sessions, therefore every
         session is identified by the tmnxGTnlTunnelName and
         tmnxGTnlTunnelSessionTag."
    ::= { tmnxGTnlTunnelSessionEntry 1 }

tmnxGTnlTunnelSessionStartTime   OBJECT-TYPE
    SYNTAX      DateAndTime
    MAX-ACCESS  read-only
    STATUS      current
    DESCRIPTION
        "The value of tmnxGTnlTunnelSessionStartTime indicates the time when
         session was established."
    ::= { tmnxGTnlTunnelSessionEntry 2 }

tmnxGTnlTunnelSessionTargetType  OBJECT-TYPE
    SYNTAX      DisplayString (SIZE (1..64))
    MAX-ACCESS  read-only
    STATUS      current
    DESCRIPTION
        "The value of tmnxGTnlTunnelSessionTargetType indicates requested
         target-type of the session."
    ::= { tmnxGTnlTunnelSessionEntry 3 }

tmnxGTnlTunnelSessionLclSrcPort  OBJECT-TYPE
    SYNTAX      InetPortNumber
    MAX-ACCESS  read-only
    STATUS      current
    DESCRIPTION
        "The value of the object tmnxGTnlTunnelSessionLclSrcPort indicates the
         local port of the session connection towards target application."
    ::= { tmnxGTnlTunnelSessionEntry 4 }

tmnxGTnlTunnelSessionRxBytes     OBJECT-TYPE
    SYNTAX      Counter64
    UNITS       "bytes"
    MAX-ACCESS  read-only
    STATUS      current
    DESCRIPTION
        "The value of tmnxGTnlTunnelSessionRxBytes indicates the total number
         of bytes received over this session."
    ::= { tmnxGTnlTunnelSessionEntry 5 }

tmnxGTnlTunnelSessionTxBytes     OBJECT-TYPE
    SYNTAX      Counter64
    UNITS       "bytes"
    MAX-ACCESS  read-only
    STATUS      current
    DESCRIPTION
        "The value of tmnxGTnlTunnelSessionTxBytes indicates the total number
         of bytes sent over this session."
    ::= { tmnxGTnlTunnelSessionEntry 6 }

tmnxSysGrpcTunnelGlobal          OBJECT IDENTIFIER ::= { tmnxSysGrpcTunnelObjs 8 }

tmnxSysGrpcTunnelDelayOnBoot     OBJECT-TYPE
    SYNTAX      Unsigned32 (0 | 1..3600)
    UNITS       "seconds"
    MAX-ACCESS  read-write
    STATUS      current
    DESCRIPTION
        "The value of tmnxSysGrpcTunnelDelayOnBoot specifies the timeout since
         the system boots, after which tunnel become operational.

         This value only takes effect when tunnel is enabled in boot
         configuration file. When tmnxGTnlTunnelAdminState is set to
         'inService', the tunnel will become operational immediately."
    DEFVAL      { 0 }
    ::= { tmnxSysGrpcTunnelGlobal 1 }

tmnxSysFanControl                OBJECT IDENTIFIER ::= { tmnxSysObjs 58 }

tmnxSysFanIncMinimumSpeed        OBJECT-TYPE
    SYNTAX      TruthValue
    MAX-ACCESS  read-write
    STATUS      current
    DESCRIPTION
        "The value of tmnxSysFanIncMinimumSpeed specifies whether to increase
         the minimum fan speed to a new internally determined value or to use
         its default minimum setting."
    DEFVAL      { false }
    ::= { tmnxSysFanControl 1 }

tmnxSysFanCtrlMinimumSpeed       OBJECT-TYPE
    SYNTAX      INTEGER {
        default   (-1),
        percent65 (65),
        percent90 (90)
    }
    MAX-ACCESS  read-write
    STATUS      current
    DESCRIPTION
        "The value of tmnxSysFanCtrlMinimumSpeed specifies a minimum fan speed
         which the system may reach, expressed as a percentage."
    DEFVAL      { default }
    ::= { tmnxSysFanControl 2 }

tmnxSysFanCtrlCoolingProfile     OBJECT-TYPE
    SYNTAX      INTEGER {
        default    (1),
        aggressive (2)
    }
    MAX-ACCESS  read-write
    STATUS      current
    DESCRIPTION
        "The value of tmnxSysFanCtrlCoolingProfile specifies a cooling profile
         which the system will use to determine fan speed."
    DEFVAL      { default }
    ::= { tmnxSysFanControl 3 }

tmnxSysFpResourceAllocationObjs  OBJECT IDENTIFIER ::= { tmnxSysObjs 59 }

tmnxSysFpResAlcnLpmTblLastChg    OBJECT-TYPE
    SYNTAX      TimeStamp
    MAX-ACCESS  read-only
    STATUS      current
    DESCRIPTION
        "The value of tmnxSysFpResAlcnLpmTblLastChg indicates the time, since
         system startup, when tmnxSysFpResAlcnLpmTable last changed
         configuration."
    ::= { tmnxSysFpResourceAllocationObjs 1 }

tmnxSysFpResAlcnLpmTable         OBJECT-TYPE
    SYNTAX      SEQUENCE OF TmnxSysFpResAlcnLpmEntry
    MAX-ACCESS  not-accessible
    STATUS      current
    DESCRIPTION
        "The tmnxSysFpResAlcnLpmTable contains the information for the
         forwarding path resource allocation of all the supported LPM scale
         options."
    ::= { tmnxSysFpResourceAllocationObjs 2 }

tmnxSysFpResAlcnLpmEntry         OBJECT-TYPE
    SYNTAX      TmnxSysFpResAlcnLpmEntry
    MAX-ACCESS  not-accessible
    STATUS      current
    DESCRIPTION
        "The tmnxSysFpResAlcnLpmEntry consists of the objects pertaining to
         forwarding path resource allocation for a given LPM scale option."
    INDEX       { tmnxSysFpResAlcnLpmScaleOption }
    ::= { tmnxSysFpResAlcnLpmTable 1 }

TmnxSysFpResAlcnLpmEntry         ::= SEQUENCE
{
    tmnxSysFpResAlcnLpmScaleOption   Unsigned32,
    tmnxSysFpResAlcnLpmLastChanged   TimeStamp,
    tmnxSysFpResAlcnLpmAdminState    TmnxAdminState,
    tmnxSysFpResAlcnLpmOperState     TmnxOperState
}

tmnxSysFpResAlcnLpmScaleOption   OBJECT-TYPE
    SYNTAX      Unsigned32 (1..4)
    MAX-ACCESS  not-accessible
    STATUS      current
    DESCRIPTION
        "The value of tmnxSysFpResAlcnLpmScaleOption specifies the unique scale
         option for LPM resource allocation."
    ::= { tmnxSysFpResAlcnLpmEntry 1 }

tmnxSysFpResAlcnLpmLastChanged   OBJECT-TYPE
    SYNTAX      TimeStamp
    MAX-ACCESS  read-only
    STATUS      current
    DESCRIPTION
        "The value of tmnxSysFpResAlcnLpmLastChanged indicates the time, since
         system startup, that the configuration of the forwarding path resource
         allocation for the given LPM scale option was last modified."
    ::= { tmnxSysFpResAlcnLpmEntry 2 }

tmnxSysFpResAlcnLpmAdminState    OBJECT-TYPE
    SYNTAX      TmnxAdminState
    MAX-ACCESS  read-write
    STATUS      current
    DESCRIPTION
        "The value of tmnxSysFpResAlcnLpmAdminState specifies the
         administrative state of the forwarding path resource allocation for
         the given LPM scale option."
    ::= { tmnxSysFpResAlcnLpmEntry 3 }

tmnxSysFpResAlcnLpmOperState     OBJECT-TYPE
    SYNTAX      TmnxOperState
    MAX-ACCESS  read-only
    STATUS      current
    DESCRIPTION
        "The value of tmnxSysFpResAlcnLpmOperState indicates the operational
         state of the forwarding path resource allocation for the given LPM
         scale option."
    ::= { tmnxSysFpResAlcnLpmEntry 4 }

tmnxSysSwDigitalSignatureObjs    OBJECT IDENTIFIER ::= { tmnxSysObjs 60 }

tmnxSysSwDSValidate              OBJECT-TYPE
    SYNTAX      TmnxActionType
    MAX-ACCESS  read-write
    STATUS      current
    DESCRIPTION
        "Setting this action variable to 'doAction' causes the required
         software images at the location specified by tmnxSysSwDSValidateUrl to
         be to be checked against known digital signatures of each image."
    DEFVAL      { notApplicable }
    ::= { tmnxSysSwDigitalSignatureObjs 1 }

tmnxSysSwDSValidateUrl           OBJECT-TYPE
    SYNTAX      TmnxDisplayStringURL
    MAX-ACCESS  read-write
    STATUS      current
    DESCRIPTION
        "The value of tmnxSysSwDSValidateUrl specifies the locations of the
         software images to be checked against known digital  signatures when
         tmnxSysSwDSValidate is set to 'doAction'."
    DEFVAL      { ''H }
    ::= { tmnxSysSwDigitalSignatureObjs 2 }

tmnxSysSwDSValidateResultsTable  OBJECT-TYPE
    SYNTAX      SEQUENCE OF TmnxSysSwDSValidateResultsEntry
    MAX-ACCESS  not-accessible
    STATUS      current
    DESCRIPTION
        "The tmnxSysSwDSValidateResultsTable contains the results of digital
         signature validations performed."
    ::= { tmnxSysSwDigitalSignatureObjs 3 }

tmnxSysSwDSValidateResultsEntry  OBJECT-TYPE
    SYNTAX      TmnxSysSwDSValidateResultsEntry
    MAX-ACCESS  not-accessible
    STATUS      current
    DESCRIPTION
        "The tmnxSysSwDSValidateResultsEntry consists of the objects pertaining
         to an image digital signature validation at a location."
    INDEX       { tmnxSysSwDSValidationIndex }
    ::= { tmnxSysSwDSValidateResultsTable 1 }

TmnxSysSwDSValidateResultsEntry  ::= SEQUENCE
{
    tmnxSysSwDSValidationIndex       Integer32,
    tmnxSysSwDSValidationUrl         TmnxDisplayStringURL,
    tmnxSysSwDSValidationState       INTEGER,
    tmnxSysSwDSFailureReason         DisplayString
}

tmnxSysSwDSValidationIndex       OBJECT-TYPE
    SYNTAX      Integer32 (1..3)
    MAX-ACCESS  read-only
    STATUS      current
    DESCRIPTION
        "The value of tmnxSysSwDSValidationIndex specifies the index
         of the software image validation request.  Only the three most recent
         validation requests are saved."
    ::= { tmnxSysSwDSValidateResultsEntry 1 }

tmnxSysSwDSValidationUrl         OBJECT-TYPE
    SYNTAX      TmnxDisplayStringURL
    MAX-ACCESS  read-only
    STATUS      current
    DESCRIPTION
        "The value of tmnxSysSwDSValidationUrl specifies the location of the
         software images validated against known digital  signatures."
    ::= { tmnxSysSwDSValidateResultsEntry 2 }

tmnxSysSwDSValidationState       OBJECT-TYPE
    SYNTAX      INTEGER {
        none                 (0),
        validationInProgress (1),
        validationSuccessful (2),
        validationFailed     (3)
    }
    MAX-ACCESS  read-only
    STATUS      current
    DESCRIPTION
        "The value of tmnxSysSwDSValidationState indicates the state of the
         digital signature validation."
    ::= { tmnxSysSwDSValidateResultsEntry 3 }

tmnxSysSwDSFailureReason         OBJECT-TYPE
    SYNTAX      DisplayString
    MAX-ACCESS  read-only
    STATUS      current
    DESCRIPTION
        "The value of tmnxSysSwDSFailureReason indicates the reason the digital
         signature validation failed when tmnxSysSwDSValidationState is
         'validationFailed'."
    ::= { tmnxSysSwDSValidateResultsEntry 4 }

tmnxSysConformance               OBJECT IDENTIFIER ::= { tmnxSRConfs 1 }

tmnxSysCompliances               OBJECT IDENTIFIER ::= { tmnxSysConformance 1 }

tmnxSysV4v0Compliance            MODULE-COMPLIANCE
    STATUS      obsolete
    DESCRIPTION
        "The compliance statement for management of general system capabilities
         on Nokia SROS series systems."
    MODULE
        MANDATORY-GROUPS {
            tmnxSysGeneralV3v0Group,
            tmnxSysTimeV4v0Group,
            tmnxSysConfigV3v0Group,
            tmnxSysRadiusServerGroup,
            tmnxSysTacPlusServerGroup,
            tmnxSysBofGroup,
            tmnxSysNotificationV4v0Group,
            tmnxPersistenceV4v0Group
        }
    ::= { tmnxSysCompliances 4 }

tmnxSysV5v0Compliance            MODULE-COMPLIANCE
    STATUS      obsolete
    DESCRIPTION
        "The compliance statement for management of general system capabilities
         on Nokia SROS series systems."
    MODULE
        MANDATORY-GROUPS {
            tmnxSysGeneralV3v0Group,
            tmnxSysTimeV4v0Group,
            tmnxSysConfigV3v0Group,
            tmnxSysRadiusServerV5v0Group,
            tmnxSysTacPlusServerV5v0Group,
            tmnxSysBofGroup,
            tmnxSysNotificationV5v0Group,
            tmnxPersistenceV5v0Group
        }
    ::= { tmnxSysCompliances 5 }

tmnxSysV6v0Compliance            MODULE-COMPLIANCE
    STATUS      obsolete
    DESCRIPTION
        "The compliance statement for management of general system capabilities
         on Nokia SROS series systems."
    MODULE
        MANDATORY-GROUPS {
            tmnxSysGeneralV3v0Group,
            tmnxSysTimeV4v0Group,
            tmnxSysConfigV3v0Group,
            tmnxSysRadiusServerV5v0Group,
            tmnxSysTacPlusServerV5v0Group,
            tmnxSysBofV6v0Group,
            tmnxSysNotificationV6v0Group,
            tmnxPersistenceV6v0Group,
            tmnxSysIpv6MgmtItfV6v0Group,
            tmnxSysLiV6v0Group
        }
    ::= { tmnxSysCompliances 6 }

tmnxSysV7v0Compliance            MODULE-COMPLIANCE
    STATUS      obsolete
    DESCRIPTION
        "The compliance statement for management of general system capabilities
         on Nokia SROS series systems."
    MODULE
        MANDATORY-GROUPS {
            tmnxSysGeneralV3v0Group,
            tmnxSysGeneralV7v0Group,
            tmnxSysTimeV4v0Group,
            tmnxSysConfigV3v0Group,
            tmnxSysRadiusServerV5v0Group,
            tmnxSysTacPlusServerV5v0Group,
            tmnxSysBofV6v0Group,
            tmnxSysNotificationV6v0Group,
            tmnxPersistenceV6v0Group,
            tmnxSysIpv6MgmtItfV6v0Group,
            tmnxSysLiV6v0Group,
            tmnxSystemCpuMonitorGroup
        }
    ::= { tmnxSysCompliances 7 }

tmnxSysV8v0Compliance            MODULE-COMPLIANCE
    STATUS      obsolete
    DESCRIPTION
        "The compliance statement for management of general system capabilities
         on Nokia SROS series systems."
    MODULE
        MANDATORY-GROUPS {
            tmnxSysGeneralV3v0Group,
            tmnxSysGeneralV7v0Group,
            tmnxSysTimeV4v0Group,
            tmnxSysConfigV8v0Group,
            tmnxSysLoginControlV8v0Group,
            tmnxSysRadiusServerV5v0Group,
            tmnxSysTacPlusServerV5v0Group,
            tmnxSysBofV6v0Group,
            tmnxSysNotificationV6v0Group,
            tmnxPersistenceV6v0Group,
            tmnxSysIpv6MgmtItfV6v0Group,
            tmnxSysLiV6v0Group,
            tmnxSysIcmpVSV6v1Group,
            tmnxSysEthInfoGroup,
            tmnxSystemCpuMonitorGroup
        }
    ::= { tmnxSysCompliances 8 }

tmnxSysV9v0Compliance            MODULE-COMPLIANCE
    STATUS      obsolete
    DESCRIPTION
        "The compliance statement for management of general system capabilities
         on Nokia SROS series systems."
    MODULE
        MANDATORY-GROUPS {
            tmnxPersistenceV9v0Group,
            tmnxSysBofV6v0Group,
            tmnxSysConfigV8v0Group,
            tmnxSysEthInfoGroup,
            tmnxSysGeneralV3v0Group,
            tmnxSysGeneralV7v0Group,
            tmnxSysIcmpVSV6v1Group,
            tmnxSysIpv6MgmtItfV6v0Group,
            tmnxSysLiFilterGroup,
            tmnxSysLiV6v0Group,
            tmnxSysLoginControlSecGroup,
            tmnxSysLoginControlV8v0Group,
            tmnxSysLoginControlV9v0Group,
            tmnxSysNotificationV6v0Group,
            tmnxSysNotificationV9v0Group,
            tmnxSysRadiusServerV5v0Group,
            tmnxSysRollbackV9v0Group,
            tmnxSysTacPlusServerV5v0Group,
            tmnxSysTimeV4v0Group,
            tmnxSystemCpuMonitorGroup,
            tmnxSysCertGroup,
            tmnxSysNotificationRBGroup
        }
    ::= { tmnxSysCompliances 9 }

tmnxSysBootedBofCompliance       MODULE-COMPLIANCE
    STATUS      current
    DESCRIPTION
        "The compliance statement for currently active (booted) BOF
         capabilities on Nokia SROS series systems."
    MODULE
        MANDATORY-GROUPS {
            tmnxSysBootedBofGroup
        }
    ::= { tmnxSysCompliances 10 }

tmnxSysV10v0Compliance           MODULE-COMPLIANCE
    STATUS      obsolete
    DESCRIPTION
        "The compliance statement for management of general system capabilities
         on Nokia SROS series systems."
    MODULE
        MANDATORY-GROUPS {
            tmnxPersistenceV9v0Group,
            tmnxSysBofV6v0Group,
            tmnxSysConfigV8v0Group,
            tmnxSysEthInfoGroup,
            tmnxSysGeneralV3v0Group,
            tmnxSysGeneralV7v0Group,
            tmnxSysIcmpVSV6v1Group,
            tmnxSysIpv6MgmtItfV6v0Group,
            tmnxSysLiFilterGroup,
            tmnxSysLiV6v0Group,
            tmnxSysLoginControlSecGroup,
            tmnxSysLoginControlV8v0Group,
            tmnxSysLoginControlV9v0Group,
            tmnxSysNotificationV6v0Group,
            tmnxSysNotificationV9v0Group,
            tmnxSysNotificationV10v0Group,
            tmnxSysRadiusServerV5v0Group,
            tmnxSysRollbackV9v0Group,
            tmnxSysTacPlusServerV5v0Group,
            tmnxSysTimeV4v0Group,
            tmnxSystemCpuMonitorGroup,
            tmnxSysCertGroup,
            tmnxSysRollbackRescueGroup,
            tmnxSysNotificationRBGroup
        }
    ::= { tmnxSysCompliances 11 }

tmnxSysV11v0Compliance           MODULE-COMPLIANCE
    STATUS      obsolete
    DESCRIPTION
        "The compliance statement for management of general system capabilities
         on Nokia SROS series systems."
    MODULE
        MANDATORY-GROUPS {
            tmnxPersistenceV11v0Group,
            tmnxSysBofV6v0Group,
            tmnxSysConfigV8v0Group,
            tmnxSysEthInfoGroup,
            tmnxSysGeneralV3v0Group,
            tmnxSysGeneralV7v0Group,
            tmnxSysIcmpVSV6v1Group,
            tmnxSysIpv6MgmtItfV6v0Group,
            tmnxSysLiFilterGroup,
            tmnxSysLiV6v0Group,
            tmnxSysLoginControlSecGroup,
            tmnxSysLoginControlV8v0Group,
            tmnxSysLoginControlV9v0Group,
            tmnxSysNotificationV6v0Group,
            tmnxSysNotificationV9v0Group,
            tmnxSysNotificationV10v0Group,
            tmnxSysRadiusServerV5v0Group,
            tmnxSysRollbackV9v0Group,
            tmnxSysTacPlusServerV5v0Group,
            tmnxSysTimeV4v0Group,
            tmnxSystemCpuMonitorGroup,
            tmnxSysCertGroup,
            tmnxSysRollbackRescueGroup,
            tmnxSysNotificationRBGroup,
            tmnxSysGroupingSystemGroup,
            tmnxSysCandidateCfgGroup,
            tmnxSysNetconfV11v0Group,
            tmnxSysStrmV11v0R4Group
        }
    ::= { tmnxSysCompliances 12 }

tmnxSysV12v0Compliance           MODULE-COMPLIANCE
    STATUS      obsolete
    DESCRIPTION
        "The compliance statement for management of general system capabilities
         on Nokia SROS series systems."
    MODULE
        MANDATORY-GROUPS {
            tmnxPersistenceV12v0Group,
            tmnxSysBofV6v0Group,
            tmnxSysCandidateCfgGroup,
            tmnxSysCardResourceGroup,
            tmnxSysCertGroup,
            tmnxSysConfigV8v0Group,
            tmnxSysDNSSecNotifV12v0Group,
            tmnxSysDNSSecV12v0Group,
            tmnxSysEthInfoGroup,
            tmnxSysGeneralV3v0Group,
            tmnxSysGeneralV7v0Group,
            tmnxSysGroupingSystemGroup,
            tmnxSysIcmpVSV6v1Group,
            tmnxSysIpv6MgmtItfV6v0Group,
            tmnxSysLiFilterGroup,
            tmnxSysLiV6v0Group,
            tmnxSysLoginControlSecGroup,
            tmnxSysLoginControlV8v0Group,
            tmnxSysLoginControlV9v0Group,
            tmnxSysNetconfV11v0Group,
            tmnxSysNotificationRBGroup,
            tmnxSysNotificationV10v0Group,
            tmnxSysNotificationV12v0Group,
            tmnxSysNotificationV6v0Group,
            tmnxSysNotificationV9v0Group,
            tmnxSysRadiusServerV5v0Group,
            tmnxSysRollbackRescueGroup,
            tmnxSysRollbackV9v0Group,
            tmnxSysDhcpGroup,
            tmnxSysStrmV11v0R4Group,
            tmnxSysTacPlusServerV5v0Group,
            tmnxSysTimeV4v0Group,
            tmnxSystemCpuMonitorGroup,
            tmnxSysXmppV12v4Group,
            tmnxSysBofV12v0Group,
            tmnxSysLicenseV12v0Group
        }
    ::= { tmnxSysCompliances 13 }

tmnxSysV13v0Compliance           MODULE-COMPLIANCE
    STATUS      obsolete
    DESCRIPTION
        "The compliance statement for management of general system capabilities
         on Nokia SROS series systems."
    MODULE
        MANDATORY-GROUPS {
            tmnxPersistenceV12v0Group,
            tmnxSysBofV6v0Group,
            tmnxSysCandidateCfgGroup,
            tmnxSysCardResourceGroup,
            tmnxSysCertGroup,
            tmnxSysConfigV8v0Group,
            tmnxSysDNSSecNotifV12v0Group,
            tmnxSysDNSSecV12v0Group,
            tmnxSysEthInfoGroup,
            tmnxSysGeneralV3v0Group,
            tmnxSysGeneralV7v0Group,
            tmnxSysGroupingSystemGroup,
            tmnxSysIcmpVSV6v1Group,
            tmnxSysIpv6MgmtItfV6v0Group,
            tmnxSysLiFilterGroup,
            tmnxSysLiV6v0Group,
            tmnxSysLoginControlSecGroup,
            tmnxSysLoginControlV8v0Group,
            tmnxSysLoginControlV9v0Group,
            tmnxSysNetconfV11v0Group,
            tmnxSysNotificationRBGroup,
            tmnxSysNotificationV10v0Group,
            tmnxSysNotificationV12v0Group,
            tmnxSysNotificationV6v0Group,
            tmnxSysNotificationV9v0Group,
            tmnxSysRadiusServerV5v0Group,
            tmnxSysRollbackRescueGroup,
            tmnxSysRollbackV9v0Group,
            tmnxSysDhcpGroup,
            tmnxSysStrmV11v0R4Group,
            tmnxSysTacPlusServerV5v0Group,
            tmnxSysTimeV4v0Group,
            tmnxSystemCpuMonitorGroup,
            tmnxSysXmppV12v4Group,
            tmnxSysBofV12v0Group,
            tmnxSysLicenseV12v0Group,
            tmnxSysFibV13v0Group,
            tmnxSysNetconfV13v0Group,
            tmnxSysSnmpSrcAccesLstV13v0Group,
            tmnxSysMgmtProtocolV13v0Group,
            tmnxSysFileTransProfV13v0Group,
            tmnxSysEhsV13v0Group,
            tmnxSysBofV13v0Group,
            tmnxSysLicenseV13v0Group,
            tmnxSysLicenseNotifV13v0Group,
            tmnxSysSwReposV13v0Group
        }
    ::= { tmnxSysCompliances 14 }

tmnxSysV14v0Compliance           MODULE-COMPLIANCE
    STATUS      obsolete
    DESCRIPTION
        "The compliance statement for management of general system capabilities
         on Nokia SROS series systems in release 14.0."
    MODULE
        MANDATORY-GROUPS {
            tmnxPersistenceV12v0Group,
            tmnxSysBofV6v0Group,
            tmnxSysCandidateCfgGroup,
            tmnxSysCardResourceGroup,
            tmnxSysCertGroup,
            tmnxSysConfigV8v0Group,
            tmnxSysDNSSecNotifV12v0Group,
            tmnxSysDNSSecV12v0Group,
            tmnxSysEthInfoGroup,
            tmnxSysGeneralV3v0Group,
            tmnxSysGeneralV7v0Group,
            tmnxSysGroupingSystemGroup,
            tmnxSysIcmpVSV6v1Group,
            tmnxSysIpv6MgmtItfV6v0Group,
            tmnxSysLiFilterGroup,
            tmnxSysLiV6v0Group,
            tmnxSysLoginControlSecGroup,
            tmnxSysLoginControlV8v0Group,
            tmnxSysLoginControlV9v0Group,
            tmnxSysNetconfV11v0Group,
            tmnxSysNotificationRBGroup,
            tmnxSysNotificationV10v0Group,
            tmnxSysNotificationV12v0Group,
            tmnxSysNotificationV6v0Group,
            tmnxSysNotificationV9v0Group,
            tmnxSysRadiusServerV5v0Group,
            tmnxSysRollbackRescueGroup,
            tmnxSysRollbackV9v0Group,
            tmnxSysDhcpGroup,
            tmnxSysStrmV11v0R4Group,
            tmnxSysTacPlusServerV5v0Group,
            tmnxSysTimeV4v0Group,
            tmnxSystemCpuMonitorGroup,
            tmnxSysXmppV12v4Group,
            tmnxSysBofV12v0Group,
            tmnxSysLicenseV12v0Group,
            tmnxSysFibV13v0Group,
            tmnxSysNetconfV13v0Group,
            tmnxSysSnmpSrcAccesLstV13v0Group,
            tmnxSysMgmtProtocolV13v0Group,
            tmnxSysFileTransProfV13v0Group,
            tmnxSysEhsV13v0Group,
            tmnxSysBofV13v0Group,
            tmnxSysLicenseV13v0Group,
            tmnxSysLicenseNotifV13v0Group,
            tmnxSysSwReposV13v0Group,
            tmnxSysBofV14v0Group,
            tmnxSysNotificationV14v0Group,
            tmnxPersistenceV14v0Group,
            tmnxSysEhsParameterGroup,
            tmnxSysLicenseApplicationGroup,
            tmnxSysNotifyObjsV14v0Group,
            tmnxSysTimeV14v0Group
        }
    ::= { tmnxSysCompliances 15 }

tmnxSysV15v0Compliance           MODULE-COMPLIANCE
    STATUS      obsolete
    DESCRIPTION
        "The compliance statement for management of general system capabilities
         on Nokia SROS series systems in release 15.0."
    MODULE
        MANDATORY-GROUPS {
            tmnxSysLoginControlV15v0Group,
            tmnxSysGrpcV15v0Group,
            tnmxSysRebootInfoV15v0Group,
            tmnxSysNotificationV15v0Group,
            tmnxSysLicenseApp48HrsGroup
        }
    ::= { tmnxSysCompliances 16 }

tmnxSysV15v1Compliance           MODULE-COMPLIANCE
    STATUS      current
    DESCRIPTION
        "The compliance statement for management of general system capabilities
         on Nokia SROS series systems in release 15.1."
    MODULE
        MANDATORY-GROUPS {
            tmnxSysNetconfV15v1Group,
            tmnxSysMgmtProtocolV15v1Group,
            tmnxSysConfigSaveCtrlV15v1Group,
            tmnxSysMgmtIfMdCliGroup,
            tmnxSysMgmtIfYangModulesGroup,
            tmnxSysFileTransProfV15v1Group,
            tmnxSysBofV15v1Group
        }
    ::= { tmnxSysCompliances 17 }

tmnxSysV16v0Compliance           MODULE-COMPLIANCE
    STATUS      current
    DESCRIPTION
        "The compliance statement for management of general system capabilities
         on Nokia SROS series systems in release 16.0."
    MODULE
        MANDATORY-GROUPS {
            tmnxSysHttpRdrV16v0Group,
            tmnxSysLicenseNotifV16v0Group,
            tmnxSysMgmtIfDsLocksV16v0Group,
            tmnxSysLicensingV16v0Group,
            tmnxSysMgmtInterfaceV16v0Group,
            tmnxSysMgmtIfNotifyObjsGroup,
            tmnxSysNetworkElementV16v0Group,
            tmnxSysSwitchFabricV16v0Group,
            tmnxSysSwFabNotifV16v0Group
        }
    ::= { tmnxSysCompliances 18 }

tmnxSysV19v0Compliance           MODULE-COMPLIANCE
    STATUS      obsolete
    DESCRIPTION
        "The compliance statement for management of general system capabilities
         on Nokia SROS series systems in release 19."
    MODULE
        MANDATORY-GROUPS {
            tmnxSysLicNotifyObjsV19v0Group,
            tmnxSysLicenseNotifV19v0Group,
            tmnxSysResInfoV19v0Group,
            tmnxSysBofV19v0Group,
            tmnxSysNetworkElementV19v0Group,
            tmnxSysLicensingV19v0Group,
            tmnxSysNetconfV19v0Group,
            tmnxSysEhsV19v0Group,
            tmnxSysBootConfFmtNotifyObjsGrp,
            tmnxSysFwdPathOptsV19v0Group,
            tmnxSysBootConfFmtNotifyGrp,
            tmnxSysMgmtIfMdCliCmdAccntGroup,
            tmnxSysResItCamV19v0Group,
            tmnxSysFpCamAllocV19v0Group
        }
    ::= { tmnxSysCompliances 19 }

tmnxSysV20v0Compliance           MODULE-COMPLIANCE
    STATUS      current
    DESCRIPTION
        "The compliance statement for management of general system capabilities
         on Nokia SROS series systems in release 20."
    MODULE
        MANDATORY-GROUPS {
            tmnxSysNotificationV20v0Group,
            tmnxSysNotifyObjsV20v0Group,
            tmnxSysAutoBootV20v0Group,
            tmnxSysSwitchFabricV20v0Group,
            tmnxSysUsbV20v0Group,
            tmnxSysAutoBootTimeoutV20v0Group,
            tmnxSysGeneralV20v0Group,
            tmnxSysMgmtInterfaceV20v0Group,
            tmnxSysAutoNEDV20v0Group,
            tmnxSysAutoBootOspfV20v0Group,
            tmnxSysRemoteMgmtV20v0Group,
            tmnxSysNetconfCountersExtension
        }
    ::= { tmnxSysCompliances 20 }

tmnxSysV21v0Compliance           MODULE-COMPLIANCE
    STATUS      obsolete
    DESCRIPTION
        "The compliance statement for management of general system capabilities
         on Nokia SROS series systems in release 21."
    MODULE
        MANDATORY-GROUPS {
            tmnxSysLicensingV21v0Group,
            tmnxSysMgmtIfOpsGroup,
            tmnxSysMgmtIfObsoleteGroup,
            tmnxSysLicNotifyObjsV19v0Group,
            tmnxSysLicenseNotifV19v0Group,
            tmnxSysResInfoV19v0Group,
            tmnxSysBofV19v0Group,
            tmnxSysNetworkElementV19v0Group,
            tmnxSysLicensingV19v0Group,
            tmnxSysNetconfV19v0Group,
            tmnxSysEhsV19v0Group,
            tmnxSysBootConfFmtNotifyObjsGrp,
            tmnxSysFwdPathOptsV19v0Group,
            tmnxSysFwdPathOptsV21v0Group,
            tmnxSysBootConfFmtNotifyGrp,
            tmnxSysResItCamV19v0Group,
            tmnxSysFpCamAllocV19v0Group,
            tmnxSysBofV21v0Group,
            tmnxSysFpResAllocV21v0Group,
            tmnxSysFpResAllocPoolV21v0Group,
            tmnxSysMgmtIfComHistoryV21v0Grp,
            tmnxSysFpResAllocFecV21v0Group,
            tmnxSysGrpcTunnelV21v0Group
        }
    ::= { tmnxSysCompliances 21 }

tmnxSysV22v0Compliance           MODULE-COMPLIANCE
    STATUS      current
    DESCRIPTION
        "The compliance statement for management of general system capabilities
         on Nokia SROS series systems in release 22."
    MODULE
        MANDATORY-GROUPS {
            tmnxSysFwdPathOptsV22v0Group,
            tmnxSysNotificationV22v0Group,
            tmnxSysFpLpmResAlcnV22v0Group,
            tmnxSysFanControlV22v0Group,
            tmnxSysRemoteMgmtV22v0Group,
            tmnxSysFpResAllocV22v0Group,
            tnmxSysRebootInfoV22v0Group
        }
    ::= { tmnxSysCompliances 22 }

tmnxSysV23v0Compliance           MODULE-COMPLIANCE
    STATUS      obsolete
    DESCRIPTION
        "The compliance statement for management of general system capabilities
         on Nokia SROS series systems in release 23."
    MODULE
        MANDATORY-GROUPS {
            tmnxSysBofV6v0Group,
            tmnxSysCandidateCfgGroup,
            tmnxSysCardResourceGroup,
            tmnxSysCertGroup,
            tmnxSysConfigV8v0Group,
            tmnxSysDNSSecNotifV12v0Group,
            tmnxSysDNSSecV12v0Group,
            tmnxSysEthInfoGroup,
            tmnxSysGeneralV3v0Group,
            tmnxSysGeneralV7v0Group,
            tmnxSysGroupingSystemGroup,
            tmnxSysIcmpVSV6v1Group,
            tmnxSysIpv6MgmtItfV6v0Group,
            tmnxSysLiFilterGroup,
            tmnxSysLiV6v0Group,
            tmnxSysLoginControlSecGroup,
            tmnxSysLoginControlV8v0Group,
            tmnxSysLoginControlV9v0Group,
            tmnxSysNetconfV11v0Group,
            tmnxSysNotificationRBGroup,
            tmnxSysNotificationV10v0Group,
            tmnxSysNotificationV6v0Group,
            tmnxSysNotificationV9v0Group,
            tmnxSysRadiusServerV5v0Group,
            tmnxSysRollbackRescueGroup,
            tmnxSysRollbackV9v0Group,
            tmnxSysDhcpGroup,
            tmnxSysStrmV11v0R4Group,
            tmnxSysTacPlusServerV5v0Group,
            tmnxSysTimeV4v0Group,
            tmnxSystemCpuMonitorGroup,
            tmnxSysBofV12v0Group,
            tmnxSysLicenseV12v0Group,
            tmnxSysFibV13v0Group,
            tmnxSysNetconfV13v0Group,
            tmnxSysSnmpSrcAccesLstV13v0Group,
            tmnxSysMgmtProtocolV13v0Group,
            tmnxSysFileTransProfV13v0Group,
            tmnxSysEhsV13v0Group,
            tmnxSysBofV13v0Group,
            tmnxSysLicenseV13v0Group,
            tmnxSysLicenseNotifV13v0Group,
            tmnxSysSwReposV13v0Group,
            tmnxSysBofV14v0Group,
            tmnxSysNotificationV14v0Group,
            tmnxPersistenceV14v0Group,
            tmnxSysEhsParameterGroup,
            tmnxSysLicenseApplicationGroup,
            tmnxSysNotifyObjsV14v0Group,
            tmnxSysTimeV14v0Group,
            tmnxSysLoginControlV15v0Group,
            tmnxSysGrpcV15v0Group,
            tnmxSysRebootInfoV15v0Group,
            tmnxSysNotificationV15v0Group,
            tmnxSysLicenseApp48HrsGroup,
            tmnxSysNotificationV23v0Group,
            tmnxSysConfigV23v0Group,
            tmnxSysFltrProfiles23v0Group,
            tmnxSysFileTransProfV23v0Group,
            tmnxPersistenceV23v0Group,
            tmnxPythonPersistenceV23v0Grp,
            tmnxSysFwdPathOptsV23v0Group,
            tmnxSysFltrProfFlowLabelGroup,
            tmnxSysFanControlV23v0Group,
            tmnxSysRAFlexPlcrStats23v0Group,
            tmnxSysRAFlexiblePlcr23v0Group,
            tmnxSysFanControlV23v1Group,
            tmnxSysRASrv6TunnelTermGroup,
            tmnxSysRAFlexL1Plcr23v0Group,
            tmnxSysUpTimeV23v0Group,
            tmnxSysFpResAllocV23v0Group,
            tmnxSysResEcmpProfObsoleteGroup
        }
    ::= { tmnxSysCompliances 23 }

tmnxSysV24v0Compliance           MODULE-COMPLIANCE
    STATUS      current
    DESCRIPTION
        "The compliance statement for management of general system capabilities
         on Nokia SROS series systems in release 24."
    MODULE
        MANDATORY-GROUPS {
            tmnxSysRAFlexPlcrBankBindGroup,
            tmnxSysFltrProfiles24v0Group,
            tmnxSysLicensingV21v0Group,
            tmnxSysMgmtIfOpsGroup,
            tmnxSysMgmtIfObsoleteGroup,
            tmnxSysLicNotifyObjsV19v0Group,
            tmnxSysLicenseNotifV19v0Group,
            tmnxSysBofV19v0Group,
            tmnxSysNetworkElementV19v0Group,
            tmnxSysLicensingV19v0Group,
            tmnxSysNetconfV19v0Group,
            tmnxSysEhsV19v0Group,
            tmnxSysBootConfFmtNotifyObjsGrp,
            tmnxSysFwdPathOptsV19v0Group,
            tmnxSysFwdPathOptsV21v0Group,
            tmnxSysBootConfFmtNotifyGrp,
            tmnxSysResItCamV19v0Group,
            tmnxSysFpCamAllocV19v0Group,
            tmnxSysBofV21v0Group,
            tmnxSysFpResAllocV21v0Group,
            tmnxSysFpResAllocPoolV21v0Group,
            tmnxSysMgmtIfComHistoryV21v0Grp,
            tmnxSysFpResAllocFecV21v0Group,
            tmnxSysGrpcTunnelV21v0Group,
            tmnxSysBofV6v0Group,
            tmnxSysCandidateCfgGroup,
            tmnxSysCardResourceGroup,
            tmnxSysCertGroup,
            tmnxSysConfigV8v0Group,
            tmnxSysDNSSecNotifV12v0Group,
            tmnxSysDNSSecV12v0Group,
            tmnxSysEthInfoGroup,
            tmnxSysGeneralV3v0Group,
            tmnxSysGeneralV7v0Group,
            tmnxSysGroupingSystemGroup,
            tmnxSysIcmpVSV6v1Group,
            tmnxSysIpv6MgmtItfV6v0Group,
            tmnxSysLiFilterGroup,
            tmnxSysLiV6v0Group,
            tmnxSysLoginControlSecGroup,
            tmnxSysLoginControlV8v0Group,
            tmnxSysLoginControlV9v0Group,
            tmnxSysNetconfV11v0Group,
            tmnxSysNotificationRBGroup,
            tmnxSysNotificationV10v0Group,
            tmnxSysNotificationV6v0Group,
            tmnxSysNotificationV9v0Group,
            tmnxSysRadiusServerV5v0Group,
            tmnxSysRollbackRescueGroup,
            tmnxSysRollbackV9v0Group,
            tmnxSysDhcpGroup,
            tmnxSysStrmV11v0R4Group,
            tmnxSysTacPlusServerV5v0Group,
            tmnxSysTimeV4v0Group,
            tmnxSystemCpuMonitorGroup,
            tmnxSysBofV12v0Group,
            tmnxSysLicenseV12v0Group,
            tmnxSysFibV13v0Group,
            tmnxSysNetconfV13v0Group,
            tmnxSysSnmpSrcAccesLstV13v0Group,
            tmnxSysMgmtProtocolV13v0Group,
            tmnxSysFileTransProfV13v0Group,
            tmnxSysEhsV13v0Group,
            tmnxSysBofV13v0Group,
            tmnxSysLicenseV13v0Group,
            tmnxSysLicenseNotifV13v0Group,
            tmnxSysSwReposV13v0Group,
            tmnxSysBofV14v0Group,
            tmnxSysNotificationV14v0Group,
            tmnxPersistenceV14v0Group,
            tmnxSysEhsParameterGroup,
            tmnxSysLicenseApplicationGroup,
            tmnxSysNotifyObjsV14v0Group,
            tmnxSysTimeV14v0Group,
            tmnxSysLoginControlV15v0Group,
            tmnxSysGrpcV15v0Group,
            tnmxSysRebootInfoV15v0Group,
            tmnxSysNotificationV15v0Group,
            tmnxSysLicenseApp48HrsGroup,
            tmnxSysNotificationV23v0Group,
            tmnxSysConfigV23v0Group,
            tmnxSysConfigV24v0Group,
            tmnxSysFltrProfiles23v0Group,
            tmnxSysFileTransProfV23v0Group,
            tmnxPersistenceV23v0Group,
            tmnxPythonPersistenceV23v0Grp,
            tmnxSysFwdPathOptsV23v0Group,
            tmnxSysFltrProfFlowLabelGroup,
            tmnxSysFanControlV23v0Group,
            tmnxSysRAFlexPlcrStats23v0Group,
            tmnxSysRAFlexiblePlcr23v0Group,
            tmnxSysFanControlV23v1Group,
            tmnxSysRASrv6TunnelTermGroup,
            tmnxSysRAFlexL1Plcr23v0Group,
            tmnxSysUpTimeV23v0Group,
            tmnxSysFpResAllocV23v0Group,
            tmnxSysLoginControlV24v0Group,
            tmnxSysFpResAllocV24v0Group,
            tmnxSysGeneralV24v0Group,
            tmnxSysRAFlexibleStats24v0Group,
            tmnxSysFltrProfIcmp24v0Group,
            tmnxSysFltrProfTcpFlExt24v0Group,
            tmnxSysFpRAEcmpV24v0Group,
            tmnxSysFpRAProfileV24v0Group,
            tmnxSysBofV24v0Group,
            tmnxSysFwdPathOptsV24v0Group,
            tmnxSysMgmtIfMdCliHistV24v0Group,
            tmnxSysSwDSValidateV24v0Group,
            tmnxSysSwDSValidNotifV24v0Group,
            tmnxSysMgmtIfMdCliCommitGroup,
            tmnxSysMgmtIfMdCliInfoOutGroup,
            tmnxSysFPVlanQosQModeV24v0Group,
            tmnxSysFpoMplsHierTunV24v0Group
        }
    ::= { tmnxSysCompliances 24 }

tmnxSysGroups                    OBJECT IDENTIFIER ::= { tmnxSysConformance 2 }

tmnxSysRadiusServerGroup         OBJECT-GROUP
    OBJECTS     {
        radiusOperStatus,
        radiusServerAddress,
        radiusServerOperStatus
    }
    STATUS      obsolete
    DESCRIPTION
        "The group of objects supporting management of RADIUS servers on Nokia
         SROS series systems."
    ::= { tmnxSysGroups 4 }

tmnxSysTacPlusServerGroup        OBJECT-GROUP
    OBJECTS     {
        tacplusOperStatus,
        tacplusServerAddress,
        tacplusServerOperStatus
    }
    STATUS      obsolete
    DESCRIPTION
        "The group of objects supporting management of TACACS+ servers on Nokia
         SROS series systems."
    ::= { tmnxSysGroups 5 }

tmnxSysBofGroup                  OBJECT-GROUP
    OBJECTS     {
        sbiActiveIpAddr,
        sbiActiveIpMask,
        sbiStandbyIpAddr,
        sbiStandbyIpMask,
        sbiPrimaryImage,
        sbiSecondaryImage,
        sbiTertiaryImage,
        sbiPrimaryConfigFile,
        sbiSecondaryConfigFile,
        sbiTertiaryConfigFile,
        sbiPersist,
        sbiConsoleSpeed,
        sbiAutoNegotiate,
        sbiSpeed,
        sbiDuplex,
        sbiPrimaryDns,
        sbiSecondaryDns,
        sbiTertiaryDns,
        sbiDnsDomain,
        sbiWait,
        sbiStaticRouteNextHop,
        sbiStaticRouteRowStatus
    }
    STATUS      obsolete
    DESCRIPTION
        "The group of objects supporting management of the Boot Options File
         (BOF) on Nokia SROS series systems."
    ::= { tmnxSysGroups 8 }

tmnxSysConfigV3v0Group           OBJECT-GROUP
    OBJECTS     {
        ssiSaveConfig,
        ssiSyncMode,
        ssiSyncForce,
        ssiSyncStatus,
        ssiSyncConfigLastTime,
        ssiSyncBootEnvLastTime,
        ssiConfigMaxBackupRevisions,
        ssiSaveConfigResult,
        ssiSaveBof,
        ssiSaveBofResult,
        ssiSaveConfigDest,
        ssiSaveConfigDetail,
        ssiRedFailoverTime,
        ssiRedFailoverReason,
        sbiConfigStatus,
        sbiPersistStatus,
        sbiPersistIndex,
        sbiSnmpdAdminStatus,
        sbiSnmpdOperStatus,
        sbiSnmpdMaxPktSize,
        sbiSnmpdPortNum,
        sbiBootConfigOKScript,
        sbiConfigOKScriptStatus,
        sbiBootConfigFailScript,
        sbiConfigFailScriptStatus,
        sbiRedSwitchoverScript,
        sbiRedSwitchoverScriptStatus,
        slcFtpInboundMaxSessions,
        slcTelnetInboundMaxSessions,
        slcTelnetOutboundMaxSessions,
        slcPreLoginMessage,
        slcPreLoginMessageInclName,
        slcMessageOfTheDay,
        slcMessageOfTheDayType,
        slcLoginBanner,
        sysLACPSystemPriority,
        slcLoginExponentialBackOff
    }
    STATUS      obsolete
    DESCRIPTION
        "The group of objects supporting management of boot-up configuration
         and synchronization of active and standby systems on Nokia SROS series
         systems."
    ::= { tmnxSysGroups 12 }

tmnxSysGeneralV3v0Group          OBJECT-GROUP
    OBJECTS     {
        sgiCpuUsage,
        sgiMemoryUsed,
        sgiMemoryAvailable,
        sgiMemoryPoolAllocated,
        sgiSwMajorVersion,
        sgiSwMinorVersion,
        sgiSwVersionModifier
    }
    STATUS      current
    DESCRIPTION
        "The group of objects supporting management of general system
         capabilities on Nokia SROS series systems, 3.0 Release."
    ::= { tmnxSysGroups 15 }

tmnxSysObsoleteGroup             OBJECT-GROUP
    OBJECTS     {
        stiSummerZoneStartDate,
        stiSummerZoneEndDate,
        tacplusServerAddress,
        radiusServerAddress,
        tmnxSysMgmtIfMDCliCmdAccntLoad
    }
    STATUS      obsolete
    DESCRIPTION
        "The group of objects in TIMETRA-SYSTEM-MIB which are obsoleted."
    ::= { tmnxSysGroups 17 }

tmnxPersistenceV4v0Group         OBJECT-GROUP
    OBJECTS     {
        spiDhcpL2PersistenceFileLocation,
        spiDhcpL2PersistenceDescription,
        spiDhcpL3PersistenceFileLocation,
        spiDhcpL3PersistenceDescription,
        spiSubMgmtPersistenceFileLocation,
        spiSubMgmtPersistenceDescription
    }
    STATUS      obsolete
    DESCRIPTION
        "The group of objects supporting management of persistency across
         system reboot on Nokia SROS series systems."
    ::= { tmnxSysGroups 18 }

tmnxSysTimeV4v0Group             OBJECT-GROUP
    OBJECTS     {
        stiDateAndTime,
        stiActiveZone,
        stiHoursOffset,
        stiMinutesOffset,
        stiZoneType,
        stiSummerZoneRowStatus,
        stiSummerZoneOffset,
        stiSummerZoneStartDay,
        stiSummerZoneStartWeek,
        stiSummerZoneStartMonth,
        stiSummerZoneStartHour,
        stiSummerZoneStartMinute,
        stiSummerZoneEndDay,
        stiSummerZoneEndWeek,
        stiSummerZoneEndMonth,
        stiSummerZoneEndHour,
        stiSummerZoneEndMinute,
        sntpState,
        sntpServerRowStatus,
        sntpServerVersion,
        sntpServerPreference,
        sntpServerInterval,
        sntpAdminState,
        sntpOperStatus
    }
    STATUS      current
    DESCRIPTION
        "The group of objects supporting management of time on Nokia SROS
         series systems, 4.0 Release."
    ::= { tmnxSysGroups 19 }

tmnxSysNotifyObjsR4r0Group       OBJECT-GROUP
    OBJECTS     {
        tmnxNotifyRow,
        tmnxNotifyRowAdminState,
        tmnxNotifyRowOperState,
        tmnxMemoryModule,
        tmnxModuleMallocSize,
        tmnxDroppedTrapID,
        tmnxTrapDroppedReasonCode,
        tmnxTrapDroppedEntryID,
        tmnxNotifyEntryOID,
        tmnxSnmpdErrorMsg,
        tmnxSysTimeSetBy
    }
    STATUS      obsolete
    DESCRIPTION
        "The group of objects supporting notifications for general system
         capabilities on Nokia SROS series systems."
    ::= { tmnxSysGroups 20 }

tmnxSysNotificationV4v0Group     NOTIFICATION-GROUP
    NOTIFICATIONS {
        stiDateAndTimeChanged,
        ssiSaveConfigSucceeded,
        ssiSaveConfigFailed,
        sbiBootConfig,
        sbiBootSnmpd,
        radiusServerOperStatusChange,
        radiusOperStatusChange,
        tmnxConfigModify,
        tmnxConfigCreate,
        tmnxConfigDelete,
        tmnxStateChange,
        tmnxModuleMallocFailed,
        tmnxTrapDropped,
        ssiSyncConfigOK,
        ssiSyncConfigFailed,
        ssiSyncBootEnvOK,
        ssiSyncBootEnvFailed,
        sntpTimeDiffExceedsThreshold,
        tacplusServerOperStatusChange,
        tacplusOperStatusChange,
        tmnxSnmpdError,
        tmnxSsiMismatch,
        tmnxSnmpdStateChange,
        ssiRedStandbySyncing,
        ssiRedStandbyReady,
        ssiRedStandbySyncLost,
        ssiRedSwitchover,
        ssiRedCpmActive,
        ssiRedSingleCpm,
        persistencyClosedAlarmRaised,
        persistencyClosedAlarmCleared,
        tmnxSntpOperChange,
        tmnxSysTimeSet
    }
    STATUS      obsolete
    DESCRIPTION
        "The group of notifications supporting the general system capabilities
         on Nokia SROS series systems."
    ::= { tmnxSysGroups 21 }

tmnxSysNotifyObjsV5v0Group       OBJECT-GROUP
    OBJECTS     {
        tmnxPersistencyClient,
        tmnxPersistencyFileLocator,
        tmnxPersistencyNotifyMsg,
        tmnxPersistenceAffectedCpm,
        tmnxNotifyRow,
        tmnxNotifyRowAdminState,
        tmnxNotifyRowOperState,
        tmnxMemoryModule,
        tmnxModuleMallocSize,
        tmnxDroppedTrapID,
        tmnxTrapDroppedReasonCode,
        tmnxTrapDroppedEntryID,
        tmnxNotifyEntryOID,
        tmnxSnmpdErrorMsg,
        tmnxSysTimeSetBy,
        tmnxFtpFailureMsg,
        tmnxFtpFailureDestAddressType,
        tmnxFtpFailureDestAddress
    }
    STATUS      current
    DESCRIPTION
        "The group of objects supporting notifications for general system
         capabilities on Nokia SROS series systems."
    ::= { tmnxSysGroups 22 }

tmnxSysNotificationV5v0Group     NOTIFICATION-GROUP
    NOTIFICATIONS {
        stiDateAndTimeChanged,
        ssiSaveConfigSucceeded,
        ssiSaveConfigFailed,
        sbiBootConfig,
        sbiBootSnmpd,
        radiusOperStatusChange,
        tmnxConfigModify,
        tmnxConfigCreate,
        tmnxConfigDelete,
        tmnxStateChange,
        tmnxModuleMallocFailed,
        tmnxTrapDropped,
        ssiSyncConfigOK,
        ssiSyncConfigFailed,
        ssiSyncBootEnvOK,
        ssiSyncBootEnvFailed,
        sntpTimeDiffExceedsThreshold,
        tacplusOperStatusChange,
        tmnxSnmpdError,
        tmnxSsiMismatch,
        tmnxSnmpdStateChange,
        ssiRedStandbySyncing,
        ssiRedStandbyReady,
        ssiRedStandbySyncLost,
        ssiRedSwitchover,
        ssiRedCpmActive,
        ssiRedSingleCpm,
        persistencyClosedAlarmRaised,
        persistencyClosedAlarmCleared,
        tmnxSntpOperChange,
        tmnxSysTimeSet,
        tmnxFtpClientFailure,
        tacplusInetSrvrOperStatusChange,
        radiusInetServerOperStatusChange,
        persistencyEventReport
    }
    STATUS      obsolete
    DESCRIPTION
        "The group of notifications supporting the general system capabilities
         on Nokia SROS series systems."
    ::= { tmnxSysGroups 23 }

tmnxSysObsoleteNotificationV5v0Group NOTIFICATION-GROUP
    NOTIFICATIONS {
        tacplusServerOperStatusChange,
        radiusServerOperStatusChange
    }
    STATUS      current
    DESCRIPTION
        "The group of notification objects in TIMETRA-SYSTEM-MIB which are
         obsoleted."
    ::= { tmnxSysGroups 24 }

tmnxSysTacPlusServerV5v0Group    OBJECT-GROUP
    OBJECTS     {
        tacplusOperStatus,
        tacplusServerOperStatus,
        tacPlusServerInetAddressType,
        tacPlusServerInetAddress
    }
    STATUS      current
    DESCRIPTION
        "The group of objects supporting management of TACACS+ servers on Nokia
         SROS series systems."
    ::= { tmnxSysGroups 25 }

tmnxSysRadiusServerV5v0Group     OBJECT-GROUP
    OBJECTS     {
        radiusOperStatus,
        radiusServerOperStatus,
        radiusServerInetAddressType,
        radiusServerInetAddress
    }
    STATUS      current
    DESCRIPTION
        "The group of objects supporting management of RADIUS servers on Nokia
         SROS series systems."
    ::= { tmnxSysGroups 26 }

tmnxSysObsoleteV5v0Group         OBJECT-GROUP
    OBJECTS     {
        stiSummerZoneStartDate,
        stiSummerZoneEndDate,
        tacplusServerAddress,
        radiusServerAddress,
        spiDhcpL2PersistenceFileLocation,
        spiDhcpL2PersistenceDescription,
        spiDhcpL3PersistenceFileLocation,
        spiDhcpL3PersistenceDescription
    }
    STATUS      current
    DESCRIPTION
        "The group of objects in TIMETRA-SYSTEM-MIB which are obsoleted."
    ::= { tmnxSysGroups 27 }

tmnxPersistenceV5v0Group         OBJECT-GROUP
    OBJECTS     {
        spiSubMgmtPersistenceFileLocation,
        spiSubMgmtPersistenceDescription
    }
    STATUS      obsolete
    DESCRIPTION
        "The group of objects supporting management of persistency across
         system reboot on Nokia SROS series systems."
    ::= { tmnxSysGroups 28 }

tmnxSysIpv6MgmtItfV6v0Group      OBJECT-GROUP
    OBJECTS     {
        sbiActiveIPv6Addr,
        sbiActiveIPv6PfxLen,
        sbiStandbyIPv6Addr,
        sbiStandbyIPv6PfxLen,
        sbiPrimaryDnsIPv6Addr,
        sbiSecondaryDnsIPv6Addr,
        sbiTertiaryDnsIPv6Addr,
        sbiStaticRouteIPv6NextHop,
        sbiStaticRouteIPv6RowStatus,
        sysDNSInfoLastChanged,
        sysDNSAddressResolvePref
    }
    STATUS      current
    DESCRIPTION
        "The group of objects supporting ipv6 management interface on Nokia
         SROS series systems."
    ::= { tmnxSysGroups 29 }

tmnxPersistenceV6v0Group         OBJECT-GROUP
    OBJECTS     {
        spiSubMgmtPersistenceFileLocation,
        spiSubMgmtPersistenceDescription,
        spiDhcpSrvPersistenceFileLoc,
        spiDhcpSrvPersistenceDescr
    }
    STATUS      obsolete
    DESCRIPTION
        "The group of objects supporting management of persistency across
         system reboot on Nokia SROS series systems."
    ::= { tmnxSysGroups 30 }

tmnxSysBofV6v0Group              OBJECT-GROUP
    OBJECTS     {
        sbiActiveIpAddr,
        sbiActiveIpMask,
        sbiStandbyIpAddr,
        sbiStandbyIpMask,
        sbiPrimaryImage,
        sbiSecondaryImage,
        sbiTertiaryImage,
        sbiPrimaryConfigFile,
        sbiSecondaryConfigFile,
        sbiTertiaryConfigFile,
        sbiPersist,
        sbiConsoleSpeed,
        sbiAutoNegotiate,
        sbiSpeed,
        sbiDuplex,
        sbiPrimaryDns,
        sbiSecondaryDns,
        sbiTertiaryDns,
        sbiDnsDomain,
        sbiWait,
        sbiStaticRouteNextHop,
        sbiStaticRouteRowStatus,
        sbiLiSeparate,
        sbiLiLocalSave
    }
    STATUS      current
    DESCRIPTION
        "The group of objects supporting management of the Boot Options File
         (BOF) on Nokia SROS series systems."
    ::= { tmnxSysGroups 31 }

tmnxSysNotificationV6v0Group     NOTIFICATION-GROUP
    NOTIFICATIONS {
        stiDateAndTimeChanged,
        ssiSaveConfigSucceeded,
        ssiSaveConfigFailed,
        sbiBootConfig,
        sbiBootSnmpd,
        sbiBootConfigFailFileError,
        sbiBootConfigOKFileError,
        sbiBootLiConfig,
        radiusOperStatusChange,
        tmnxConfigModify,
        tmnxConfigCreate,
        tmnxConfigDelete,
        tmnxStateChange,
        tmnxModuleMallocFailed,
        tmnxTrapDropped,
        ssiSyncConfigOK,
        ssiSyncConfigFailed,
        ssiSyncBootEnvOK,
        ssiSyncBootEnvFailed,
        sntpTimeDiffExceedsThreshold,
        tacplusOperStatusChange,
        tmnxSnmpdError,
        tmnxSsiMismatch,
        tmnxSnmpdStateChange,
        ssiRedStandbySyncing,
        ssiRedStandbyReady,
        ssiRedStandbySyncLost,
        ssiRedSwitchover,
        ssiRedCpmActive,
        ssiRedSingleCpm,
        persistencyClosedAlarmRaised,
        persistencyClosedAlarmCleared,
        tmnxSntpOperChange,
        tmnxSysTimeSet,
        tmnxFtpClientFailure,
        tacplusInetSrvrOperStatusChange,
        radiusInetServerOperStatusChange,
        persistencyEventReport,
        mdSaveCommitHistoryFailed,
        sbiBootMdReadCommitHistoryFailed
    }
    STATUS      current
    DESCRIPTION
        "The group of notifications supporting the general system capabilities
         on Nokia SROS series systems."
    ::= { tmnxSysGroups 32 }

tmnxSysLiV6v0Group               OBJECT-GROUP
    OBJECTS     {
        sliConfigStatus,
        sliSaveConfig,
        sliSaveConfigResult,
        sliConfigLastModified,
        sliConfigLastSaved
    }
    STATUS      current
    DESCRIPTION
        "The group of objects supporting management of Lawful Intercept
         configuration on Nokia SROS series systems."
    ::= { tmnxSysGroups 33 }

tmnxSysNotifyObjsV6v0Group       OBJECT-GROUP
    OBJECTS     {
        tmnxNotifyObjectName,
        tmnxSyncFailureReason
    }
    STATUS      current
    DESCRIPTION
        "The group of objects added in 6.0 release to support system
         notifications."
    ::= { tmnxSysGroups 34 }

tmnxSysGeneralV7v0Group          OBJECT-GROUP
    OBJECTS     {
        sgiSnmpInGetBulks,
        sgiKbMemoryUsed,
        sgiKbMemoryAvailable,
        sgiKbMemoryPoolAllocated
    }
    STATUS      current
    DESCRIPTION
        "The group of objects supporting management of general system
         capabilities on Nokia SROS series systems added in 7.0 Release."
    ::= { tmnxSysGroups 35 }

tmnxSysIcmpVSV6v1Group           OBJECT-GROUP
    OBJECTS     {
        sysIcmpVSEnhancement
    }
    STATUS      current
    DESCRIPTION
        "The group of objects supporting management of ICMP vendor specific
         enhancement capabilities on Nokia SROS series systems."
    ::= { tmnxSysGroups 36 }

tmnxSysConfigV8v0Group           OBJECT-GROUP
    OBJECTS     {
        ssiSaveConfig,
        ssiSyncMode,
        ssiSyncForce,
        ssiSyncStatus,
        ssiSyncConfigLastTime,
        ssiSyncBootEnvLastTime,
        ssiConfigMaxBackupRevisions,
        ssiSaveConfigResult,
        ssiSaveBof,
        ssiSaveBofResult,
        ssiSaveConfigDest,
        ssiSaveConfigDetail,
        ssiRedFailoverTime,
        ssiRedFailoverReason,
        sbiConfigStatus,
        sbiPersistStatus,
        sbiPersistIndex,
        sbiSnmpdAdminStatus,
        sbiSnmpdOperStatus,
        sbiSnmpdMaxPktSize,
        sbiSnmpdPortNum,
        sbiBootConfigOKScript,
        sbiConfigOKScriptStatus,
        sbiBootConfigFailScript,
        sbiConfigFailScriptStatus,
        sbiRedSwitchoverScript,
        sbiRedSwitchoverScriptStatus,
        sysLACPSystemPriority
    }
    STATUS      current
    DESCRIPTION
        "The group of objects supporting management of boot-up configuration
         and synchronization of active and standby systems on Nokia SROS series
         systems."
    ::= { tmnxSysGroups 37 }

tmnxSysLoginControlV8v0Group     OBJECT-GROUP
    OBJECTS     {
        slcFtpInboundMaxSessions,
        slcTelnetInboundMaxSessions,
        slcTelnetOutboundMaxSessions,
        slcPreLoginMessage,
        slcPreLoginMessageInclName,
        slcMessageOfTheDay,
        slcMessageOfTheDayType,
        slcLoginBanner,
        slcLoginExponentialBackOff,
        slcTelnetGracefulShutdown,
        slcSSHGracefulShutdown
    }
    STATUS      current
    DESCRIPTION
        "The group of objects supporting management of login control on Nokia
         SROS series systems."
    ::= { tmnxSysGroups 38 }

tmnxSysEthInfoGroup              OBJECT-GROUP
    OBJECTS     {
        sysNewQinqUntaggedSap
    }
    STATUS      current
    DESCRIPTION
        "The group of objects supporting management of Ethernet Info on Nokia
         SROS series systems."
    ::= { tmnxSysGroups 39 }

tmnxPersistenceV9v0Group         OBJECT-GROUP
    OBJECTS     {
        spiSubMgmtPersistenceFileLocation,
        spiSubMgmtPersistenceDescription,
        spiDhcpSrvPersistenceFileLoc,
        spiDhcpSrvPersistenceDescr,
        spiNatFwdPersistenceFileLoc,
        spiNatFwdPersistenceDescr,
        spiAAPersistenceFileLoc,
        spiAAPersistenceDescr
    }
    STATUS      obsolete
    DESCRIPTION
        "The group of objects supporting management of persistency across
         system reboot on Nokia SROS series systems release 9.0."
    ::= { tmnxSysGroups 40 }

tmnxSysLoginControlSecGroup      OBJECT-GROUP
    OBJECTS     {
        slcTelnetMinTTLValue,
        slcSSHMinTTLValue
    }
    STATUS      current
    DESCRIPTION
        "The group of objects supporting management of login control on Nokia
         SROS series systems."
    ::= { tmnxSysGroups 41 }

tmnxSysLiFilterGroup             OBJECT-GROUP
    OBJECTS     {
        sliFilterLock
    }
    STATUS      current
    DESCRIPTION
        "The group of objects supporting management of Lawful Intercept
         configuration on Nokia SROS series systems."
    ::= { tmnxSysGroups 42 }

tmnxSysNotificationV9v0Group     NOTIFICATION-GROUP
    NOTIFICATIONS {
        persistenceRestoreProblem,
        tmnxSysRollbackStarted,
        tmnxSysRollbackStatusChange,
        tmnxSysRollbackSaveStatusChange,
        tmnxSysRollbackFileDeleteStatus,
        ssiSyncRollbackOK,
        ssiSyncRollbackFailed,
        ssiSyncCertOK,
        ssiSyncCertFailed
    }
    STATUS      current
    DESCRIPTION
        "The group of notifications supporting the general system capabilities
         added in release 9.0 of SROS."
    ::= { tmnxSysGroups 43 }

tmnxSysRollbackV9v0Group         OBJECT-GROUP
    OBJECTS     {
        tmnxSysRollbackIndex,
        tmnxSysRollbackStart,
        tmnxSysRollbackResult,
        tmnxSysRollbackSave,
        tmnxSysRollbackSaveResult,
        tmnxSysRollbackLocation,
        tmnxSysRollbackRevertIndex,
        tmnxSysRollbackRevertEndTime,
        tmnxSysRollbackTableLastChanged,
        tmnxSysRollbackFileCreationTime,
        tmnxSysRollbackFileComment,
        tmnxSysRollbackFileUserName,
        tmnxSysRollbackSavedTime,
        ssiSyncRollbackLastTime,
        tmnxSysRollbackRevertStartTime,
        tmnxSysRollbackRevertUserName,
        tmnxSysRollbackRevertFilename,
        tmnxSysRollbackSaveComment,
        tmnxSysRollbackAbortRevert,
        tmnxSysRollbackFileVersion,
        tmnxSysRollbackFileDelete,
        tmnxSysRollbackFileDeleteResult,
        ssiSyncRollbackMode,
        ssiSyncRollbackForce,
        ssiSyncRollbackStatus
    }
    STATUS      current
    DESCRIPTION
        "The group of objects supporting management of the Rollback Files on
         Nokia SROS series systems."
    ::= { tmnxSysGroups 44 }

tmnxSysLoginControlV9v0Group     OBJECT-GROUP
    OBJECTS     {
        slcSSHInboundMaxSessions,
        slcSSHOutboundMaxSessions
    }
    STATUS      current
    DESCRIPTION
        "The group of objects supporting management of login control on Nokia
         SROS series systems, added in release 9.0."
    ::= { tmnxSysGroups 45 }

tmnxSystemCpuMonitorGroup        OBJECT-GROUP
    OBJECTS     {
        tmnxSysCpuMonCpuIdle,
        tmnxSysCpuMonBusyCoreUtil,
        tmnxSysCpuMonBusyGroupName,
        tmnxSysCpuMonBusyGroupUtil
    }
    STATUS      current
    DESCRIPTION
        "The group of objects, added in release 7.0, used for monitoring system
         CPU utilization on Nokia SROS series systems."
    ::= { tmnxSysGroups 46 }

tmnxSysCertGroup                 OBJECT-GROUP
    OBJECTS     {
        ssiSyncCertForce,
        ssiSyncCertLastTime,
        ssiSyncCertMode,
        ssiSyncCertStatus
    }
    STATUS      current
    DESCRIPTION
        "The group of objects supporting management of the synchronization of
         certificate Files on Nokia SROS series systems."
    ::= { tmnxSysGroups 47 }

tmnxSysBootedBofGroup            OBJECT-GROUP
    OBJECTS     {
        sbbiLiSeparate,
        sbbiLiLocalSave
    }
    STATUS      current
    DESCRIPTION
        "The group of objects giving the value of the currently active (booted)
         Boot Options File (BOF) parameters on Nokia SROS series systems."
    ::= { tmnxSysGroups 48 }

tmnxSysRollbackRescueGroup       OBJECT-GROUP
    OBJECTS     {
        tmnxSysRollbackRescueLocation,
        tmnxSysRollbackRescueSave,
        tmnxSysRollbackRescueRevert,
        tmnxSysRollbackRescueDelete,
        tmnxSysRollbackRescueSaveRes,
        tmnxSysRollbackRescueRevertRes,
        tmnxSysRollbackRescueDeleteRes,
        tmnxSysRollbackRescueSavedTime,
        tmnxSysRollbackRescueRevStTime,
        tmnxSysRollbackRescueRevEdTime,
        tmnxSysRollbackRescueRevUser,
        tmnxSysRollbackRescueSaveComment,
        tmnxSysRollbackRescueAbortRevert,
        tmnxSysRollbackRescueFileExists,
        tmnxSysRollbackMaxLocalFiles,
        tmnxSysRollbackMaxRemoteFiles
    }
    STATUS      current
    DESCRIPTION
        "The group of objects supporting management of the Rollback Rescue file
         on Nokia SROS series systems."
    ::= { tmnxSysGroups 49 }

tmnxSysNotificationV10v0Group    NOTIFICATION-GROUP
    NOTIFICATIONS {
        persistencyFileSysThresRaised,
        persistencyFileSysThresCleared,
        tmnxSysExecStarted,
        tmnxSysExecFinished
    }
    STATUS      current
    DESCRIPTION
        "The group of notifications supporting the general system capabilities
         added in release 10.0 of SROS."
    ::= { tmnxSysGroups 50 }

tmnxSysNotifyObjsV10v0Group      OBJECT-GROUP
    OBJECTS     {
        tmnxSysRollbackFileType,
        tmnxSysExecScript,
        tmnxSysExecResult
    }
    STATUS      current
    DESCRIPTION
        "The group of accessible-for-notify objects supporting notifications on
         Nokia SROS series systems added in SROS release 10.0."
    ::= { tmnxSysGroups 51 }

tmnxSysNotificationRBGroup       NOTIFICATION-GROUP
    NOTIFICATIONS {
        tmnxSysRollbackSaveStarted,
        tmnxSysRollbackDeleteStarted,
        tmnxSysNvsysFileError
    }
    STATUS      current
    DESCRIPTION
        "The group of notifications supporting the general system capabilities
         added in Nokia SROS series systems."
    ::= { tmnxSysGroups 52 }

tmnxSysNotifyObjsGenGroup        OBJECT-GROUP
    OBJECTS     {
        tmnxSysFileErrorType
    }
    STATUS      current
    DESCRIPTION
        "The group of accessible-for-notify objects supporting notifications on
         Nokia SROS series systems added in SROS."
    ::= { tmnxSysGroups 53 }

tmnxSysGroupingSystemGroup       OBJECT-GROUP
    OBJECTS     {
        sgiSystemGroupID,
        sgiSystemSubGroupID
    }
    STATUS      current
    DESCRIPTION
        "The group of objects supporting management of the grouping systems on
         Nokia SROS series systems."
    ::= { tmnxSysGroups 54 }

tmnxSysCandidateCfgGroup         OBJECT-GROUP
    OBJECTS     {
        tmnxSysCandidateCfgState,
        tmnxSysCandidateCfgEditors,
        tmnxSysCandidateCfgCommitState,
        tmnxSysCandidateCfgCommitTime,
        tmnxSysCandidateCfgRevertTime,
        tmnxSysCandidateCfgChckptCreated,
        tmnxSysCandidateCfgExclusiveUsr,
        tmnxSysCandidateCfgUser
    }
    STATUS      current
    DESCRIPTION
        "The group of objects supporting the candidate config on Nokia SROS
         series system added in SROS release 11.0."
    ::= { tmnxSysGroups 55 }

tmnxPersistenceV11v0Group        OBJECT-GROUP
    OBJECTS     {
        spiSubMgmtPersistenceFileLocation,
        spiSubMgmtPersistenceDescription,
        spiDhcpSrvPersistenceFileLoc,
        spiDhcpSrvPersistenceDescr,
        spiNatFwdPersistenceFileLoc,
        spiNatFwdPersistenceDescr,
        spiAAPersistenceFileLoc,
        spiAAPersistenceDescr,
        spiAncpPersistenceFileLoc,
        spiAncpPersistenceDescr
    }
    STATUS      obsolete
    DESCRIPTION
        "The group of objects supporting management of persistency across
         system reboot on Nokia SROS series systems release 11.0."
    ::= { tmnxSysGroups 56 }

tmnxSysNetconfV11v0Group         OBJECT-GROUP
    OBJECTS     {
        tmnxSysNetconfAdminStatus,
        tmnxSysNetconfOperStatus,
        tmnxSysNetconfRequests,
        tmnxSysNetconfGetRequests,
        tmnxSysNetconfGetConfigRequests,
        tmnxSysNetconfEditConfigRequests,
        tmnxSysNetconfCloseRequests,
        tmnxSysNetconfKillRequests,
        tmnxSysNetconfResponses,
        tmnxSysNetconfErrorResponses
    }
    STATUS      current
    DESCRIPTION
        "The group of objects supporting management of the NETCONF on Nokia
         SROS series system added in SROS release 11.0."
    ::= { tmnxSysGroups 57 }

tmnxSysStrmV11v0R4Group          OBJECT-GROUP
    OBJECTS     {
        tmnxSysStrmAdminStatus,
        tmnxSysStrmDumpSnmpRequests,
        tmnxSysStrmGetManyRequests,
        tmnxSysStrmResponses
    }
    STATUS      current
    DESCRIPTION
        "The group of objects supporting management of the SAM streaming on
         Nokia SROS series system added in SROS release 11.0 R4."
    ::= { tmnxSysGroups 58 }

tmnxSysNotifyObjsV11v0Group      OBJECT-GROUP
    OBJECTS     {
        tmnxTrapDroppedCount
    }
    STATUS      current
    DESCRIPTION
        "The group of objects supporting notifications for general system
         capabilities, added in Nokia SROS release 11.0."
    ::= { tmnxSysGroups 59 }

tmnxSysV12v0Groups               OBJECT IDENTIFIER ::= { tmnxSysGroups 60 }

tmnxPersistenceV12v0Group        OBJECT-GROUP
    OBJECTS     {
        spiSubMgmtPersistenceFileLocation,
        spiSubMgmtPersistenceDescription,
        spiDhcpSrvPersistenceFileLoc,
        spiDhcpSrvPersistenceDescr,
        spiNatFwdPersistenceFileLoc,
        spiNatFwdPersistenceDescr,
        spiAAPersistenceFileLoc,
        spiAAPersistenceDescr,
        spiAncpPersistenceFileLoc,
        spiAncpPersistenceDescr,
        spiPythonPersistenceFileLoc,
        spiPythonPersistenceDescr
    }
    STATUS      obsolete
    DESCRIPTION
        "The group of objects supporting management of persistency across
         system reboot on Nokia SROS series systems release 12.0."
    ::= { tmnxSysV12v0Groups 1 }

tmnxSysDNSSecV12v0Group          OBJECT-GROUP
    OBJECTS     {
        sysDNSSecAdValidation,
        sysDNSSecRespCtrl
    }
    STATUS      current
    DESCRIPTION
        "The group of objects supporting Domain Name System Security Extensions
         on Nokia SROS series systems in release 12.0."
    ::= { tmnxSysV12v0Groups 2 }

tmnxSysDNSSecNotifV12v0Group     NOTIFICATION-GROUP
    NOTIFICATIONS {
        sysDNSSecFailedAuthentication
    }
    STATUS      current
    DESCRIPTION
        "The group of notifications supporting Domain Name System Security
         Extension capabilities added in release 12.0 of SROS."
    ::= { tmnxSysV12v0Groups 3 }

tmnxSysNotificationV12v0Group    NOTIFICATION-GROUP
    NOTIFICATIONS {
        tmnxConfigConflict,
        tmnxSysLicenseInvalid,
        tmnxSysLicenseExpiresSoon,
        tmnxSysVsdServerAvailable,
        tmnxSysVsdServerUnavailable,
        tmnxSysXmppServerFunctional,
        tmnxSysXmppServerNotFunctional
    }
    STATUS      obsolete
    DESCRIPTION
        "The group of notifications supporting the general system capabilities
         added in release 12.0 of SROS."
    ::= { tmnxSysV12v0Groups 4 }

tmnxSysXmppV12v4Group            OBJECT-GROUP
    OBJECTS     {
        tmnxSysVsdSystemId,
        tmnxSysVsdGwPubSubIsSubscrd,
        tmnxSysVsdGwPubSubNodeName,
        tmnxSysVsdGwPubSubLstSubscrdTime,
        tmnxSysVsdGwLastAuditTxTime,
        tmnxSysXmppServFQDN,
        tmnxSysXmppServRowStatus,
        tmnxSysXmppServUserName,
        tmnxSysXmppServPassword,
        tmnxSysXmppServLastChanged,
        tmnxSysXmppServUptime,
        tmnxSysXmppServIQSent,
        tmnxSysXmppServIQRcvd,
        tmnxSysXmppServIQError,
        tmnxSysXmppServIQTimedOut,
        tmnxSysXmppServIQAckRcvd,
        tmnxSysXmppServIQMinRtt,
        tmnxSysXmppServIQMaxRtt,
        tmnxSysXmppServVsdUpdatesRcvd,
        tmnxSysXmppServUpdatesRcvd,
        tmnxSysXmppServMsgSent,
        tmnxSysXmppServMsgRcvd,
        tmnxSysXmppServMsgAckRcvd,
        tmnxSysXmppServMsgError,
        tmnxSysXmppServMsgTimedOut,
        tmnxSysXmppServMsgMinRtt,
        tmnxSysXmppServMsgMaxRtt,
        tmnxSysXmppServSubSent,
        tmnxSysXmppServUnSubSent,
        tmnxSysXmppServState,
        tmnxSysXmppServAdminState,
        tmnxSysVsdServUptime,
        tmnxSysVsdServUserName,
        tmnxSysVsdServerStatus,
        tmnxSysVsdServMsgSent,
        tmnxSysVsdServMsgRcvd,
        tmnxSysVsdServMsgAckRcvd,
        tmnxSysVsdServMsgError,
        tmnxSysVsdServMsgTimedOut,
        tmnxSysVsdServMsgMinRtt,
        tmnxSysVsdServMsgMaxRtt,
        tmnxSysXmppServOperUserName,
        tmnxSysXmppServAuthType,
        tmnxSysXmppServConnMode
    }
    STATUS      obsolete
    DESCRIPTION
        "The group of objects supporting XMPP server information on Nokia SROS
         series systems in release 12.0 R4."
    ::= { tmnxSysV12v0Groups 5 }

tmnxSysCardResourceGroup         OBJECT-GROUP
    OBJECTS     {
        tmnxCardCpuResMonCpuIdle,
        tmnxCardCpuResMonBusyCoreUtil,
        tmnxCardCpuResMonBusyGroupName,
        tmnxCardCpuResMonBusyGroupUtil,
        tmnxCardMemResMemoryUsed,
        tmnxCardMemResMemoryAvailable,
        tmnxCardMemResPoolsAllocated
    }
    STATUS      current
    DESCRIPTION
        "The group of objects supporting the resource monitoring of cards in
         the system on Nokia SROS series systems in release 12.0."
    ::= { tmnxSysV12v0Groups 6 }

tmnxSysNotifyObjsV12v0Group      OBJECT-GROUP
    OBJECTS     {
        tmnxSysDNSSecDomainName,
        tmnxSysNotifVsdServerName,
        tmnxSysNotifXmppServerName,
        tmnxSysLicenseErrorReason,
        tmnxSysLicenseTimeLeft
    }
    STATUS      current
    DESCRIPTION
        "The group of objects supporting notifications for general system
         capabilities, added in Nokia SROS release 12.0."
    ::= { tmnxSysV12v0Groups 7 }

tmnxSysBofV12v0Group             OBJECT-GROUP
    OBJECTS     {
        sbiLicenseFile
    }
    STATUS      current
    DESCRIPTION
        "The group of additional objects supporting bof configuration on Nokia
         SROS series systems in release 12.0."
    ::= { tmnxSysV12v0Groups 8 }

tmnxSysLicenseV12v0Group         OBJECT-GROUP
    OBJECTS     {
        tmnxSysLicenseStatus,
        tmnxSysLicenseName,
        tmnxSysLicenseUuid,
        tmnxSysLicenseDescription,
        tmnxSysLicenseProduct,
        tmnxSysLicenseSwVersion,
        tmnxSysLicenseIssueDateAndTime,
        tmnxSysLicenseStartDateAndTime,
        tmnxSysLicenseEndDateAndTime
    }
    STATUS      current
    DESCRIPTION
        "The group of objects supporting license information on Nokia SROS
         series systems in release 12.0."
    ::= { tmnxSysV12v0Groups 9 }

tmnxSysDhcpGroup                 OBJECT-GROUP
    OBJECTS     {
        tmnxSysDhcp6AdvNoaddrsGlobal
    }
    STATUS      current
    DESCRIPTION
        "The group of objects supporting the configuration of DHCP at the
         system level."
    ::= { tmnxSysGroups 61 }

tmnxSysFibV13v0Group             OBJECT-GROUP
    OBJECTS     {
        tmnxSysFibSelective
    }
    STATUS      current
    DESCRIPTION
        "The group of objects supporting the configuration of FIB at the system
         level."
    ::= { tmnxSysGroups 62 }

tmnxSysNetconfV13v0Group         OBJECT-GROUP
    OBJECTS     {
        tmnxSysNetconfCopyConfigRequests,
        tmnxSysNetconfDelConfigRequests,
        tmnxSysNetconfValidateRequests
    }
    STATUS      current
    DESCRIPTION
        "The group of objects supporting management of the NETCONF on Nokia
         SROS series system added in SROS release 13.0."
    ::= { tmnxSysGroups 63 }

tmnxSysSnmpSrcAccesLstV13v0Group OBJECT-GROUP
    OBJECTS     {
        tmnxSysSnmpSrcAccessTblLstChgd,
        tmnxSysSnmpSrcAccessLstRowStatus,
        tmnxSysSnmpSrcAccessLstLastChg,
        tmnxSysSnmpCommunityPktDropped
    }
    STATUS      current
    DESCRIPTION
        "The group of objects supporting the configuration of source access
         list on Nokia SROS series system added in SROS release 13.0."
    ::= { tmnxSysGroups 64 }

tmnxSysMgmtProtocolV13v0Group    OBJECT-GROUP
    OBJECTS     {
        tmnxSysMgmtProtocolTblLstChng,
        tmnxSysMgmtProtLastChange,
        tmnxSysMgmtAllowImmediateChange
    }
    STATUS      current
    DESCRIPTION
        "The group of objects supporting the configuration of network
         management protocols on Nokia SROS series system added in SROS release
         13.0."
    ::= { tmnxSysGroups 65 }

tmnxSysFileTransProfV13v0Group   OBJECT-GROUP
    OBJECTS     {
        tmnxSysFileTransProfTableLstChgd,
        tmnxSysFileTransProfRowStatus,
        tmnxSysFileTransProfLastChanged,
        tmnxSysFileTransProfRtrId,
        tmnxSysFileTransProfSvcId,
        tmnxSysFileTransProfSrcAddrV4T,
        tmnxSysFileTransProfSrcAddrV4,
        tmnxSysFileTransProfSrcAddrV6T,
        tmnxSysFileTransProfSrcAddrV6,
        tmnxSysFileTransProfTimeout,
        tmnxSysFileTransProfRetry,
        tmnxSysFileTransProfRedirection
    }
    STATUS      current
    DESCRIPTION
        "The group of objects supporting the configuration of file transmission
         profiles on Nokia SROS series system added in SROS release 13.0."
    ::= { tmnxSysGroups 66 }

tmnxSysEhsV13v0Group             OBJECT-GROUP
    OBJECTS     {
        tmnxSmLaunchExtAuthType,
        tmnxSmRunExtAuthType,
        tmnxSmRunExtUserName
    }
    STATUS      current
    DESCRIPTION
        "The group of objects supporting the extension of tables in
         DISMAN-SCRIPT-MIB to support the Event Handling System (EHS) feature
         added in Nokia SROS release 13.0"
    ::= { tmnxSysGroups 67 }

tmnxSysLicenseV13v0Group         OBJECT-GROUP
    OBJECTS     {
        tmnxSysLicenseVChassisType,
        tmnxSysLicenseMaxNumCPMs,
        tmnxSysLicenseMaxNumIOMs,
        tmnxSysCpmCardLicStatus,
        tmnxSysCpmCardLicName,
        tmnxSysCpmCardLicUuid,
        tmnxSysCpmCardLicDescription,
        tmnxSysCpmCardLicProduct,
        tmnxSysCpmCardLicSwVersion,
        tmnxSysCpmCardLicIssueDateTime,
        tmnxSysCpmCardLicStartDateTime,
        tmnxSysCpmCardLicEndDateTime,
        tmnxSysCpmCardLicVChassisType,
        tmnxSysCpmCardLicMaxNumCPMs,
        tmnxSysCpmCardLicMaxNumIOMs,
        tmnxSysCpmCardLicFeatDescription
    }
    STATUS      current
    DESCRIPTION
        "The group of additional objects supporting license information on
         Nokia SROS series systems in release 13.0."
    ::= { tmnxSysGroups 68 }

tmnxSysLicenseNotifV13v0Group    NOTIFICATION-GROUP
    NOTIFICATIONS {
        tmnxSysLicenseValid
    }
    STATUS      current
    DESCRIPTION
        "The group of additional notifications supporting license information
         on Nokia SROS series systems in release 13.0."
    ::= { tmnxSysGroups 69 }

tmnxSysSwReposV13v0Group         OBJECT-GROUP
    OBJECTS     {
        tmnxSysSwReposTableLastChanged,
        tmnxSysSwReposRowStatus,
        tmnxSysSwReposLastChanged,
        tmnxSysSwReposDescription,
        tmnxSysSwReposPrimaryLocation,
        tmnxSysSwReposSecondaryLocation,
        tmnxSysSwReposTertiaryLocation
    }
    STATUS      current
    DESCRIPTION
        "The group of objects maintaining configuration for system software
         repositories on Nokia SROS series systems in Release 13.0."
    ::= { tmnxSysGroups 70 }

tmnxSysBofV13v0Group             OBJECT-GROUP
    OBJECTS     {
        sbiFips1402Level1,
        sbiEssSystemType
    }
    STATUS      current
    DESCRIPTION
        "The group of additional objects supporting bof configuration on Nokia
         SROS series systems in release 13.0."
    ::= { tmnxSysGroups 71 }

tmnxSysV14v0Groups               OBJECT IDENTIFIER ::= { tmnxSysGroups 72 }

tmnxSysBofV14v0Group             OBJECT-GROUP
    OBJECTS     {
        sbiSystemBaseMacAddress
    }
    STATUS      current
    DESCRIPTION
        "The group of additional objects supporting bof configuration on Nokia
         SROS series systems in release 14.0."
    ::= { tmnxSysV14v0Groups 1 }

tmnxSysNotificationV14v0Group    NOTIFICATION-GROUP
    NOTIFICATIONS {
        tmnxSysBaseMacAddressNotSet,
        tmnxSmLaunchStartFailed,
        tmnxEhsHandlerInvoked,
        tmnxEhsDroppedByMinDelay,
        tmnxSysAppStats24HrsAvailable,
        tmnxSysAppStatsWeekAvailable
    }
    STATUS      current
    DESCRIPTION
        "The group of additional notifications supporting the general system
         capabilities on Nokia SROS series systems in release 14.0."
    ::= { tmnxSysV14v0Groups 2 }

tmnxPersistenceV14v0Group        OBJECT-GROUP
    OBJECTS     {
        tmnxDhcpLeaseTimeModeThreshold
    }
    STATUS      current
    DESCRIPTION
        "The group of objects supporting management of persistency across
         system reboot added to Nokia SROS series systems release 14.0."
    ::= { tmnxSysV14v0Groups 3 }

tmnxSysNetconfV14v0Group         OBJECT-GROUP
    OBJECTS     {
        tmnxSysNetconfFailedEditCfgReqs,
        tmnxSysNetconfFailedLockReqs,
        sgiSnmpFailedSets,
        tmnxSysNetconfLockRequests,
        tmnxSysNetconfUnlockRequests,
        tmnxSysNetconfCommitRequests,
        tmnxSysNetconfDiscardRequests,
        tmnxSysNetconfCapCandidateCfg,
        tmnxSysNetconfCapRunningCfg,
        tmnxSysNetconfYangBaseR13,
        tmnxSysNetconfYangNokia
    }
    STATUS      obsolete
    DESCRIPTION
        "The group of objects supporting management of the NETCONF on Nokia
         SROS series system added in SROS release 14.0."
    ::= { tmnxSysV14v0Groups 4 }

tmnxSysEhsParameterGroup         OBJECT-GROUP
    OBJECTS     {
        tmnxSmRunEventArgName,
        tmnxSmRunEventArgValue
    }
    STATUS      current
    DESCRIPTION
        "The group of objects extending the support of the DISMAN-SCRIPT-MIB
         for the Event Handling System (EHS) feature added in Nokia SROS
         release 14.0"
    ::= { tmnxSysV14v0Groups 5 }

tmnxSysLicenseApplicationGroup   OBJECT-GROUP
    OBJECTS     {
        tmnxSysAppStats24HrsName,
        tmnxSysAppStats24HrsValue,
        tmnxSysAppStats24HrsTime,
        tmnxSysAppStatsWeekName,
        tmnxSysAppStatsWeekAverage,
        tmnxSysAppStatsWeekPeak,
        tmnxSysAppStatsWeekTime,
        tmnxSysAppStatsPeakName,
        tmnxSysAppStatsPeakValue,
        tmnxSysAppStatsPeakTime
    }
    STATUS      current
    DESCRIPTION
        "The group of additional objects supporting license information about a
         virtual machine implementation of an application on Nokia SROS series
         systems."
    ::= { tmnxSysV14v0Groups 6 }

tmnxSysNotifyObjsV14v0Group      OBJECT-GROUP
    OBJECTS     {
        tmnxSysLicenseErrorAction,
        tmnxSysNotifAppStatsTime,
        tmnxSysNotifAppStatsApplication,
        tmnxSysNotifAppStatsType
    }
    STATUS      current
    DESCRIPTION
        "The group of objects supporting notifications for general system
         capabilities, added in Nokia SROS release 14.0."
    ::= { tmnxSysV14v0Groups 7 }

tmnxSysTimeV14v0Group            OBJECT-GROUP
    OBJECTS     {
        stiPreferLocalTime
    }
    STATUS      current
    DESCRIPTION
        "The group of objects enhancing time output on Nokia SROS series
         systems for 14.0 Release."
    ::= { tmnxSysV14v0Groups 8 }

tmnxSysLoginControlV15v0Group    OBJECT-GROUP
    OBJECTS     {
        slcIdleTimeout,
        slcLoginScriptGlobal,
        slcLoginScriptPerUserDirectory,
        slcLoginScriptPerUserFilename
    }
    STATUS      current
    DESCRIPTION
        "The group of objects enhancing system login control on Nokia SROS
         series systems for 15.0 Release."
    ::= { tmnxSysGroups 73 }

tmnxSysGrpcV15v0Group            OBJECT-GROUP
    OBJECTS     {
        tmnxSysGrpcAdminState,
        tmnxSysGrpcOperState,
        tmnxSysGrpcTlsServerProfile,
        tmnxSysGrpcMaxMsgSize,
        tmnxSysGrpcGnmiVersion,
        tmnxSysGrpcAllowUnsecure,
        tmnxSysGrpcGnmiAdminState,
        tmnxSysGrpcTcpKaAdminState,
        tmnxSysGrpcTcpKaIdle,
        tmnxSysGrpcTcpKaInterval,
        tmnxSysGrpcTcpKaCount,
        tmnxSysGrpcRibApiAdminState,
        tmnxSysGrpcRibApiPurgeTimeout,
        tmnxSysGrpcRibApiVersion,
        tmnxSysGrpcGnoiCertMgmtAdmnState,
        tmnxSysGrpcGnoiCertMgmtVersion,
        tmnxSysGrpcMdCliAdminState,
        tmnxSysGrpcMdCliVersion,
        tmnxSysGrpcGnoiFileAdminState,
        tmnxSysGrpcGnoiFileVersion,
        tmnxSysGrpcGnoiSystemAdminState,
        tmnxSysGrpcGnoiSystemVersion,
        tmnxSysGrpcGnmiProtoVersion,
        tmnxSysGrpcListeningPort,
        tmnxSysGrpcDelayOnBoot,
        tmnxSysGrpcOperDownReason,
        tmnxSysGrpcConnStartTime,
        tmnxSysGrpcConnActRpcCnt,
        tmnxSysGrpcConnTotRpcCnt,
        tmnxSysGrpcConnRxBytes,
        tmnxSysGrpcConnTxBytes,
        tmnxSysGrpcConnQos,
        tmnxSysGrpcConnSrcVRtrId,
        tmnxSysGrpcConnGrpcTunnel,
        tmnxSysGrpcConnLFRpcName,
        tmnxSysGrpcConnLFRpcServiceName,
        tmnxSysGrpcConnLFRpcDuration,
        tmnxSysGrpcConnLFRpcFinishTime,
        tmnxSysGrpcConnLFRpcErrorStatus,
        tmnxSysGrpcRpcName,
        tmnxSysGrpcRpcServiceName,
        tmnxSysGrpcRpcStartTime,
        tmnxSysGrpcRpcSrcIpAddType,
        tmnxSysGrpcRpcSrcIpAddress,
        tmnxSysGrpcRpcSrcPort,
        tmnxSysGrpcRpcUserName,
        tmnxSysGrpcRpcSessionId,
        tmnxSysGrpcRpcGrpcTunnel,
        tmnxSysGrpcPendRebOperState,
        tmnxSysGrpcPendRebDelay,
        tmnxSysGrpcPendRebMsg,
        tmnxSysGrpcPendRebCount
    }
    STATUS      current
    DESCRIPTION
        "The group of objects supporting gRPC server on Nokia SROS series
         systems for 15.0 Release."
    ::= { tmnxSysGroups 74 }

tmnxSysV15v0Groups               OBJECT IDENTIFIER ::= { tmnxSysGroups 76 }

tnmxSysRebootInfoV15v0Group      OBJECT-GROUP
    OBJECTS     {
        tmnxLastSystemRebootReason,
        tmnxLastSystemRebootTime,
        tmnxLastSystemRebootUser,
        tmnxLastSystemRebootUserAddrType,
        tmnxLastSystemRebootUserAddress
    }
    STATUS      current
    DESCRIPTION
        "The group of objects supporting logging of reboot information on Nokia
         SROS series systems for 15.0 Release."
    ::= { tmnxSysV15v0Groups 1 }

tmnxSysNotificationV15v0Group    NOTIFICATION-GROUP
    NOTIFICATIONS {
        tmnxLastSystemRebootAdmin
    }
    STATUS      current
    DESCRIPTION
        "The group of additional notifications supporting the general system
         capabilities on Nokia SROS series systems in release 15.0."
    ::= { tmnxSysV15v0Groups 2 }

tmnxSysLicenseApp48HrsGroup      OBJECT-GROUP
    OBJECTS     {
        tmnxSysAppStats48HrsName,
        tmnxSysAppStats48HrsValue,
        tmnxSysAppStats48HrsTime
    }
    STATUS      current
    DESCRIPTION
        "The group of additional objects supporting license information about a
         virtual machine implementation of an application on Nokia SROS series
         systems."
    ::= { tmnxSysV15v0Groups 3 }

tmnxSysV15v1Groups               OBJECT IDENTIFIER ::= { tmnxSysGroups 77 }

tmnxSysNetconfV15v1Group         OBJECT-GROUP
    OBJECTS     {
        tmnxSysNetconfFailedEditCfgReqs,
        tmnxSysNetconfFailedLockReqs,
        sgiSnmpFailedSets,
        tmnxSysNetconfLockRequests,
        tmnxSysNetconfUnlockRequests,
        tmnxSysNetconfCommitRequests,
        tmnxSysNetconfDiscardRequests,
        tmnxSysNetconfCapCandidateCfg,
        tmnxSysNetconfCapRunningCfg,
        tmnxSysNetconfCreateSubRequests
    }
    STATUS      current
    DESCRIPTION
        "The group of objects supporting management of the NETCONF on Nokia
         SROS series system added in SROS release 15.1."
    ::= { tmnxSysV15v1Groups 1 }

tmnxSysMgmtProtocolV15v1Group    OBJECT-GROUP
    OBJECTS     {
        tmnxSysMgmtCliEngine1,
        tmnxSysMgmtCliEngine2
    }
    STATUS      current
    DESCRIPTION
        "The group of objects supporting the configuration of network
         management protocols on Nokia SROS series system added in SROS release
         15.1."
    ::= { tmnxSysV15v1Groups 2 }

tmnxSysConfigSaveCtrlV15v1Group  OBJECT-GROUP
    OBJECTS     {
        tmnxSysMgmtIfMDCliAutoCfgSave,
        tmnxSysNetconfAutoCfgSave,
        tmnxSysGrpcAutoCfgSave
    }
    STATUS      current
    DESCRIPTION
        "The group of objects supporting the configuration of configuration
         save options on Nokia SROS series system added in SROS release 15.1."
    ::= { tmnxSysV15v1Groups 3 }

tmnxSysMgmtIfMdCliGroup          OBJECT-GROUP
    OBJECTS     {
        tmnxSysMgmtIfMDEnvComplEnter,
        tmnxSysMgmtIfMDEnvComplSpace,
        tmnxSysMgmtIfMDEnvComplTab,
        tmnxSysMgmtIfMDEnvConsLength,
        tmnxSysMgmtIfMDEnvConsWidth,
        tmnxSysMgmtIfMDEnvMore,
        tmnxSysMgmtIfMDEnvPromptCtx,
        tmnxSysMgmtIfMDEnvPromptNewline,
        tmnxSysMgmtIfMDEnvPromptTime,
        tmnxSysMgmtIfMDEnvPromptIndic,
        tmnxSysMgmtIfMDEnvTimeDisplay,
        tmnxSysMgmtIfMDEnvMsgCliSvrt,
        tmnxSysMgmtIfMDEnvProIndAdminSt,
        tmnxSysMgmtIfMDEnvProIndType,
        tmnxSysMgmtIfMDEnvProIndDelay,
        tmnxSysMgmtIfWriteMode,
        tmnxSysMgmtIfWriteOperMode,
        tmnxSysMgmtIfModeLastSwitchTime,
        tmnxSysMgmtIfModeSwitchDuration,
        tmnxSysMgmtIfMDEnvTimeFormat
    }
    STATUS      current
    DESCRIPTION
        "The group of objects supporting the configuration MD cli on Nokia SROS
         series system added in SROS release 15.1."
    ::= { tmnxSysV15v1Groups 4 }

tmnxSysMgmtIfYangModulesGroup    OBJECT-GROUP
    OBJECTS     {
        tmnxSysMgmtIfYangBaseR13,
        tmnxSysMgmtIfYangNokia,
        tmnxSysMgmtIfYangOpenConfig,
        tmnxSysMgmtIfYangNokiaCombined,
        tmnxSysMgmtIfYangNmdaSupport
    }
    STATUS      current
    DESCRIPTION
        "The group of objects supporting the configuration of YANG modules on
         Nokia SROS series system added in SROS release 15.1."
    ::= { tmnxSysV15v1Groups 5 }

tmnxSysNetconfV15v1ObsoleteGroup OBJECT-GROUP
    OBJECTS     {
        tmnxSysNetconfYangBaseR13,
        tmnxSysNetconfYangNokia
    }
    STATUS      current
    DESCRIPTION
        "The group of objects supporting management of the NETCONF on Nokia
         SROS series system which are obsoleted"
    ::= { tmnxSysV15v1Groups 6 }

tmnxSysFileTransProfV15v1Group   OBJECT-GROUP
    OBJECTS     {
        tmnxSysFileTransProfSvcName
    }
    STATUS      current
    DESCRIPTION
        "The group of objects supporting the configuration of file transmission
         profile on Nokia SROS series system added in SROS release 15.1."
    ::= { tmnxSysV15v1Groups 7 }

tmnxSysBofV15v1Group             OBJECT-GROUP
    OBJECTS     {
        sbiSystemProfile
    }
    STATUS      current
    DESCRIPTION
        "The group of objects supporting the configuration of BOF on Nokia SROS
         series system add in SROS release 15.1."
    ::= { tmnxSysV15v1Groups 8 }

tmnxSysV16v0Groups               OBJECT IDENTIFIER ::= { tmnxSysGroups 78 }

tmnxSysHttpRdrV16v0Group         OBJECT-GROUP
    OBJECTS     {
        tmnxSysHttpRdrCpmOptimizedMode
    }
    STATUS      current
    DESCRIPTION
        "The group of objects supporting HTTP redirect on Nokia SROS series
         systems for the 16.0 Release."
    ::= { tmnxSysV16v0Groups 1 }

tmnxSysLicenseNotifV16v0Group    NOTIFICATION-GROUP
    NOTIFICATIONS {
        tmnxSysLicenseActivated,
        tmnxSysStandbyLicensingError,
        tmnxSysStandbyLicensingReady,
        tmnxSysMgmtIfModeChangeStart,
        tmnxSysMgmtIfModeChangeComplete,
        tmnxSysMgmtIfModeChangeFailure
    }
    STATUS      current
    DESCRIPTION
        "The group of additional notifications supporting license information
         on Nokia SROS series systems in release 16.0."
    ::= { tmnxSysV16v0Groups 2 }

tmnxSysMgmtIfDsLocksV16v0Group   OBJECT-GROUP
    OBJECTS     {
        tmnxSysMgmtIfDsLocksSessionId,
        tmnxSysMgmtIfDsLocksRmtIpAddress,
        tmnxSysMgmtIfDsLocksConsole,
        tmnxSysMgmtIfDsLocksUserName,
        tmnxSysMgmtIfDsLocksSessionMode,
        tmnxSysMgmtIfDsLocksSessionType,
        tmnxSysMgmtIfDsLocksRegion,
        tmnxSysMgmtIfDsLocksRunLock,
        tmnxSysMgmtIfDsLocksCndLock,
        tmnxSysMgmtIfDsLocksIdleTime,
        tmnxSysMgmtIfDsLocksScratchCnt,
        tmnxSysMgmtIfDsLocksCronEhs
    }
    STATUS      current
    DESCRIPTION
        "The group of objects supporting the configuration datastore locks on
         Nokia SROS series system added in SROS release 16.0."
    ::= { tmnxSysV16v0Groups 3 }

tmnxSysLicensingV16v0Group       OBJECT-GROUP
    OBJECTS     {
        tmnxSysAppLicenseDescription,
        tmnxSysAppLicenseType,
        tmnxSysAppLicensePoolSize,
        tmnxSysAppLicenseAllocated,
        tmnxSysAppLicensePresent,
        tmnxSysAppLicenseState,
        tmnxSysAvailLicenseName,
        tmnxSysAvailLicenseUuid,
        tmnxSysAvailLicenseDescription,
        tmnxSysAvailLicenseSwVersion,
        tmnxSysAvailLicIssueDateTime,
        tmnxSysAvailLicStartDateTime,
        tmnxSysAvailLicEndDateTime,
        sbiAllowBootLicenseViolations
    }
    STATUS      current
    DESCRIPTION
        "The group of objects supporting application licensing on Nokia SROS
         series system added in SROS release 16.0."
    ::= { tmnxSysV16v0Groups 4 }

tmnxSysMgmtInterfaceV16v0Group   OBJECT-GROUP
    OBJECTS     {
        tmnxSysMgmtIfSchemaPath,
        tmnxSysMgmtIfWriteSwitchReason
    }
    STATUS      current
    DESCRIPTION
        "The group of objects supporting configuration of management interface
         on Nokia SROS series system added in SROS release 16.0."
    ::= { tmnxSysV16v0Groups 5 }

tmnxSysMgmtIfNotifyObjsGroup     OBJECT-GROUP
    OBJECTS     {
        tmnxNotifySysMgmtIfOriginalMode
    }
    STATUS      current
    DESCRIPTION
        "The group of notification objects supporting configuration of
         management interface on Nokia SROS series system added in SROS release
         16.0."
    ::= { tmnxSysV16v0Groups 6 }

tmnxSysNetworkElementV16v0Group  OBJECT-GROUP
    OBJECTS     {
        tmnxSysNEProfTableLstChgd,
        tmnxSysNEProfRowStatus,
        tmnxSysNEProfLastChanged,
        tmnxSysNEProfNeid,
        tmnxSysNEProfNeipV4Type,
        tmnxSysNEProfNeipV4,
        tmnxSysNEProfNeipV6Type,
        tmnxSysNEProfNeipV6,
        tmnxSysNEProfSystemMac,
        tmnxSysNEProfPlatformType,
        tmnxSysNEProfVendorId,
        tmnxSysNEDiscoveryGenerateTraps
    }
    STATUS      current
    DESCRIPTION
        "The group of objects supporting Network Element info on Nokia SROS
         series system added in SROS release 16.0."
    ::= { tmnxSysV16v0Groups 7 }

tmnxSysSwitchFabricV16v0Group    OBJECT-GROUP
    OBJECTS     {
        tmnxSysSwFabFailRecAdminState,
        tmnxSysSwFabFailRecOperState,
        tmnxSysSwFabFailRecSfmState,
        tmnxSysSwFabFailRecSfmStateTime
    }
    STATUS      current
    DESCRIPTION
        "The group of objects supporting management of system switch fabric
         capabilities on Nokia SROS series system added in SROS release 16."
    ::= { tmnxSysV16v0Groups 8 }

tmnxSysSwFabNotifV16v0Group      NOTIFICATION-GROUP
    NOTIFICATIONS {
        tmnxSysSwFabFailRecStarted,
        tmnxSysSwFabFailRecCompleted,
        tmnxSysSwFabFailRecAborted,
        tmnxSysSwFabFailRecDetected
    }
    STATUS      current
    DESCRIPTION
        "The group of notifications supporting system switch fabric
         capabilities on Nokia SROS series systems added in SROS release 16.0."
    ::= { tmnxSysV16v0Groups 9 }

tmnxSysV19v0Groups               OBJECT IDENTIFIER ::= { tmnxSysGroups 79 }

tmnxSysLicNotifyObjsV19v0Group   OBJECT-GROUP
    OBJECTS     {
        tmnxSysLicensingNotifyGroup,
        tmnxSysLicensedNotifyAppName
    }
    STATUS      current
    DESCRIPTION
        "The group of objects supporting notifications for licensing
         capabilities, added in Nokia SROS release 19."
    ::= { tmnxSysV19v0Groups 1 }

tmnxSysLicenseNotifV19v0Group    NOTIFICATION-GROUP
    NOTIFICATIONS {
        tmnxSysAppLicenseInsufficient,
        tmnxSysLicenseUpdateRequired
    }
    STATUS      current
    DESCRIPTION
        "The group of additional notifications supporting license information
         on Nokia SROS series systems in release 19."
    ::= { tmnxSysV19v0Groups 2 }

tmnxSysResInfoV19v0Group         OBJECT-GROUP
    OBJECTS     {
        tmnxSysResEcmpProfRowStatus,
        tmnxSysResEcmpProfType,
        tmnxSysResEcmpProfLinksPerGrp,
        tmnxSysResEcmpProfNumGrps
    }
    STATUS      obsolete
    DESCRIPTION
        "The group of objects supporting system resource info on Nokia SROS
         series system added in SROS release 19."
    ::= { tmnxSysV19v0Groups 3 }

tmnxSysBofV19v0Group             OBJECT-GROUP
    OBJECTS     {
        sbiAutoBoot,
        sbiAutoBootClientId,
        sbiAutoBootClientIdType,
        sbiAutoBootUsingMgmt,
        sbiAutoBootUsingInband,
        sbiAutoBootInbandVlan,
        sbiAutoBootUsingIpv4,
        sbiAutoBootUsingIpv6,
        sbiAutoBootIncludeUserClass,
        sbiAutoIpv4Dhcp,
        sbiAutoIpv4DhcpClientIdType,
        sbiAutoIpv4DhcpClientId,
        sbiAutoIpv4DhcpOptUserClass,
        sbiAutoIpv4DhcpTimeout,
        sbiAutoIpv6Dhcp,
        sbiAutoIpv6DhcpClientIdType,
        sbiAutoIpv6DhcpClientIdDuidType,
        sbiAutoIpv6DhcpClientIdDuid,
        sbiAutoIpv6DhcpOptUserClass,
        sbiAutoIpv6DhcpTimeout,
        sbiStandbyAIpAddr,
        sbiStandbyAIpMask,
        sbiStandbyAIPv6Addr,
        sbiStandbyAIPv6PfxLen,
        sbiStandbyBIpAddr,
        sbiStandbyBIpMask,
        sbiStandbyBIPv6Addr,
        sbiStandbyBIPv6PfxLen,
        sbiStandbyCIpAddr,
        sbiStandbyCIpMask,
        sbiStandbyCIPv6Addr,
        sbiStandbyCIPv6PfxLen,
        sbiStandbyDIpAddr,
        sbiStandbyDIpMask,
        sbiStandbyDIPv6Addr,
        sbiStandbyDIPv6PfxLen,
        sbiMgmtIfIpMtu
    }
    STATUS      current
    DESCRIPTION
        "The group of objects supporting BOF options info on Nokia SROS series
         system added in SROS release 19."
    ::= { tmnxSysV19v0Groups 4 }

tmnxSysNetworkElementV19v0Group  OBJECT-GROUP
    OBJECTS     {
        tmnxSysNEProfTableLstChgd,
        tmnxSysNEProfRowStatus,
        tmnxSysNEProfLastChanged,
        tmnxSysNEProfNeid,
        tmnxSysNEProfNeipV4Type,
        tmnxSysNEProfNeipV4,
        tmnxSysNEProfNeipV6Type,
        tmnxSysNEProfNeipV6,
        tmnxSysNEProfSystemMac,
        tmnxSysNEProfPlatformType,
        tmnxSysNEProfVendorId,
        tmnxSysNEDiscoveryGenerateTraps
    }
    STATUS      current
    DESCRIPTION
        "The group of objects supporting Network Element info on Nokia SROS
         series system added in SROS release 19."
    ::= { tmnxSysV19v0Groups 5 }

tmnxSysLicensingV19v0Group       OBJECT-GROUP
    OBJECTS     {
        tmnxSysAvailLicenseProduct,
        tmnxSysLicensingState,
        tmnxSysLicensingRebootPending,
        tmnxSysLicensingProduct,
        tmnxSysLicensingUuid
    }
    STATUS      current
    DESCRIPTION
        "The group of objects supporting Licensing info on Nokia SROS series
         system added in SROS release 19."
    ::= { tmnxSysV19v0Groups 6 }

tmnxSysNetconfV19v0Group         OBJECT-GROUP
    OBJECTS     {
        tmnxSysNetconfPort,
        tmnxSysNetconfDelayOnBoot,
        tmnxSysNetconfOperDownReason
    }
    STATUS      current
    DESCRIPTION
        "The group of objects supporting management of the NETCONF on Nokia
         SROS series system added in SROS release 19.0."
    ::= { tmnxSysV19v0Groups 7 }

tmnxSysEhsV19v0Group             OBJECT-GROUP
    OBJECTS     {
        tmnxSmLaunchExtLockOverride
    }
    STATUS      current
    DESCRIPTION
        "The group of objects supporting the extension of tables in
         DISMAN-SCRIPT-MIB to support the Event Handling System (EHS) feature
         added in Nokia SROS release 19.0"
    ::= { tmnxSysV19v0Groups 8 }

tmnxSysBootConfFmtNotifyObjsGrp  OBJECT-GROUP
    OBJECTS     {
        tmnxPrimaryConfigFileFormatType,
        tmnxLiConfigFileFormatType
    }
    STATUS      current
    DESCRIPTION
        "The group of notification objects supporting configuration of
         management interface on Nokia SROS series system added in SROS release
         19."
    ::= { tmnxSysV19v0Groups 9 }

tmnxSysBootConfFmtNotifyGrp      NOTIFICATION-GROUP
    NOTIFICATIONS {
        tmnxSysMgmtIfLiIncorrectFormat,
        tmnxSysMgmtIfLiCfgNotEncrypted
    }
    STATUS      current
    DESCRIPTION
        "The group of notification objects supporting configuration of
         management interface on Nokia SROS series system added in SROS release
         19."
    ::= { tmnxSysV19v0Groups 10 }

tmnxSysFwdPathOptsV19v0Group     OBJECT-GROUP
    OBJECTS     {
        tmnxSysFpoDscpTransAdminState,
        tmnxSysFpoDscpTransOperState,
        tmnxSysFpoEntropyLabelAdminState,
        tmnxSysFpoEntropyLabelOperState,
        tmnxSysFpoVplsEvpnMplsAdminState,
        tmnxSysFpoVplsEvpnMplsOperState,
        tmnxSysFpoQosFc4ProfAdminState,
        tmnxSysFpoQosFc4ProfOperState,
        tmnxSysFpoQosMacCritAdminState,
        tmnxSysFpoQosMacCritOperState,
        tmnxSysFpoQosIpv6CritAdminState,
        tmnxSysFpoQosIpv6CritOperState,
        tmnxSysFpoQosBumPolAdminState,
        tmnxSysFpoQosBumPolOperState
    }
    STATUS      current
    DESCRIPTION
        "The group of objects supporting management of system forwarding path
         options on Nokia SROS series system added in SROS release 19."
    ::= { tmnxSysV19v0Groups 11 }

tmnxSysMgmtIfMdCliCmdAccntGroup  OBJECT-GROUP
    OBJECTS     {
        tmnxSysMgmtIfMDCliCmdAccntLoad
    }
    STATUS      obsolete
    DESCRIPTION
        "The group of objects supporting the configuration of remote accounting
         behavior during MD-CLI load and rollback operations on Nokia SROS
         series system added in SROS release 19.10."
    ::= { tmnxSysV19v0Groups 12 }

tmnxSysResItCamV19v0Group        OBJECT-GROUP
    OBJECTS     {
        tmnxSysResItCamBankV6Multicast
    }
    STATUS      current
    DESCRIPTION
        "The group of objects supporting system internal TCAM resource info on
         Nokia SROS series system added in SROS release 19.10"
    ::= { tmnxSysV19v0Groups 13 }

tmnxSysFpCamAllocV19v0Group      OBJECT-GROUP
    OBJECTS     {
        tmnxSysFpCamAllocAdmnV6Multicast,
        tmnxSysFpCamAllocOperV6Multicast
    }
    STATUS      current
    DESCRIPTION
        "The group of objects supporting system internal TCAM resource info on
         Nokia SROS series system added in SROS release 19.10"
    ::= { tmnxSysV19v0Groups 14 }

tmnxSysV20v0Groups               OBJECT IDENTIFIER ::= { tmnxSysGroups 80 }

tmnxSysNotificationV20v0Group    NOTIFICATION-GROUP
    NOTIFICATIONS {
        tmnxEqOperStateChange,
        stiDateAndTimeChanging,
        tmnxSysHttpRdrOutOfSeqLimitExc
    }
    STATUS      current
    DESCRIPTION
        "The group of notifications supporting the general system capabilities
         on Nokia SROS series systems added in SROS release 20."
    ::= { tmnxSysV20v0Groups 1 }

tmnxSysFwdPathOptsV20v0Group     OBJECT-GROUP
    OBJECTS     {
        tmnxSysFpoMplsFastSwOvAdminState,
        tmnxSysFpoMplsFastSwOvOperState,
        tmnxSysFpoRouterEcmpAdminState,
        tmnxSysFpoRouterEcmpOperState
    }
    STATUS      obsolete
    DESCRIPTION
        "The group of objects supporting management of system forwarding path
         options on Nokia SROS series system added in SROS release 20."
    ::= { tmnxSysV20v0Groups 2 }

tmnxSysAutoBootV20v0Group        OBJECT-GROUP
    OBJECTS     {
        sbiAutoBootVlanDiscovery
    }
    STATUS      current
    DESCRIPTION
        "The group of objects supporting management of system zero touch
         provisioning on Nokia SROS series system added in SROS release 20."
    ::= { tmnxSysV20v0Groups 3 }

tmnxSysSwitchFabricV20v0Group    OBJECT-GROUP
    OBJECTS     {
        tmnxSysSwFabSfmLossThresh
    }
    STATUS      current
    DESCRIPTION
        "The group of objects supporting management of system switch fabric
         capabilities on Nokia SROS series system added in SROS release 20."
    ::= { tmnxSysV20v0Groups 4 }

tmnxSysUsbV20v0Group             OBJECT-GROUP
    OBJECTS     {
        tmnxSysUsbLastChgd,
        tmnxSysUsbAdminState
    }
    STATUS      current
    DESCRIPTION
        "The group of objects supporting management of Universal Serial Bus
         (USB) ports on Nokia SROS series systems added in SROS release 20."
    ::= { tmnxSysV20v0Groups 5 }

tmnxSysAutoBootTimeoutV20v0Group OBJECT-GROUP
    OBJECTS     {
        sbiAutoBootTimeout
    }
    STATUS      current
    DESCRIPTION
        "The group of objects supporting management of system zero touch
         provisioning on Nokia SROS series system added in SROS release 20."
    ::= { tmnxSysV20v0Groups 6 }

tmnxSysGeneralV20v0Group         OBJECT-GROUP
    OBJECTS     {
        sgiCryptoModVersion
    }
    STATUS      current
    DESCRIPTION
        "The group of objects supporting management of general system
         capabilities on Nokia SROS series system added in SROS release 20."
    ::= { tmnxSysV20v0Groups 7 }

tmnxSysNotifyObjsV20v0Group      OBJECT-GROUP
    OBJECTS     {
        tmnxSysAdditionalInfo
    }
    STATUS      current
    DESCRIPTION
        "The group of objects supporting notifications for general system
         capabilities, added in Nokia SROS release 14.0."
    ::= { tmnxSysV20v0Groups 8 }

tmnxSysMgmtInterfaceV20v0Group   OBJECT-GROUP
    OBJECTS     {
        tmnxSysMgmtIfOperSchemaPathState,
        tmnxSysMgmtIfOperSchemaPathValue
    }
    STATUS      current
    DESCRIPTION
        "The group of objects supporting configuration of management interface
         on Nokia SROS series system added in SROS release 20.0."
    ::= { tmnxSysV20v0Groups 9 }

tmnxSysFpResAllocV20v0Group      OBJECT-GROUP
    OBJECTS     {
        tmnxSysFpResAllocG8032Sap,
        tmnxSysFpResAllocOperG8032Sap
    }
    STATUS      deprecated
    DESCRIPTION
        "The group of additional FP options supporting the general system
         capabilities on Nokia SROS series systems."
    ::= { tmnxSysV20v0Groups 10 }

tmnxSysAutoNEDV20v0Group         OBJECT-GROUP
    OBJECTS     {
        tmnxSysNEProfNeipV4AutoGenerate,
        tmnxSysNEProfNeipV4NeidVendorId,
        tmnxSysNEProfNeipV6AutoGenerate,
        tmnxSysNEProfNeipV6NeidVendorId
    }
    STATUS      current
    DESCRIPTION
        "The group of objects supporting the automated node discovery on Nokia
         SROS series systems."
    ::= { tmnxSysV20v0Groups 11 }

tmnxSysAutoBootOspfV20v0Group    OBJECT-GROUP
    OBJECTS     {
        sbiAutoBootPortMtu,
        sbiAutoBootMode,
        sbiAutoBootOspfNeid,
        sbiAutoBootOspfVendorId,
        sbiAutoBootOspfNeipV4Type,
        sbiAutoBootOspfNeipV4,
        sbiAutoBootOspfNeipV6Type,
        sbiAutoBootOspfNeipV6,
        sbiAutoBootOspfMtu
    }
    STATUS      current
    DESCRIPTION
        "The group of objects supporting the Auto-Boot OSPF node discovery on
         Nokia SROS series systems."
    ::= { tmnxSysV20v0Groups 12 }

tmnxSysRemoteMgmtV20v0Group      OBJECT-GROUP
    OBJECTS     {
        tmnxSysRmtMgmtAdminState,
        tmnxSysRmtMgmtOperState,
        tmnxSysRmtMgmtAllowUnsecure,
        tmnxSysRmtMgmtDeviceLabel,
        tmnxSysRmtMgmtDeviceName,
        tmnxSysRmtMgmtHelloInterval,
        tmnxSysRmtMgmtLastHelloTime,
        tmnxSysRmtMgmtDelayOnBoot,
        tmnxSysRmtMgmtLastRegStatus,
        tmnxSysRmtMgmtLastRegTime,
        tmnxSysRmtMgmtOperDownReason,
        tmnxSysRmtMgmtRegsCancelled,
        tmnxSysRmtMgmtRegsFailed,
        tmnxSysRmtMgmtRegsSent,
        tmnxSysRmtMgmtSrcIpAddType,
        tmnxSysRmtMgmtSrcIpAddress,
        tmnxSysRmtMgmtSrcPort,
        tmnxSysRmtMgmtSrcDefaultPort,
        tmnxSysRmtMgmtTimeout,
        tmnxSysRmtMgmtTlsClientProf,
        tmnxSysRmtMgmtVRtrId,
        tmnxSysRmtMgmtMgrAdminState,
        tmnxSysRmtMgmtMgrAllowUnsecure,
        tmnxSysRmtMgmtMgrDescription,
        tmnxSysRmtMgmtMgrDeviceLabel,
        tmnxSysRmtMgmtMgrDeviceName,
        tmnxSysRmtMgmtMgrFQDN,
        tmnxSysRmtMgmtMgrIpAddType,
        tmnxSysRmtMgmtMgrPort,
        tmnxSysRmtMgmtMgrIpAddress,
        tmnxSysRmtMgmtMgrLastRegStatus,
        tmnxSysRmtMgmtMgrLastRegTime,
        tmnxSysRmtMgmtMgrOperDownReason,
        tmnxSysRmtMgmtMgrOperState,
        tmnxSysRmtMgmtMgrRegsCancelled,
        tmnxSysRmtMgmtMgrRegsFailed,
        tmnxSysRmtMgmtMgrRegsSent,
        tmnxSysRmtMgmtMgrRowStatus,
        tmnxSysRmtMgmtMgrSrcIpAddType,
        tmnxSysRmtMgmtMgrSrcIpAddress,
        tmnxSysRmtMgmtMgrSrcPort,
        tmnxSysRmtMgmtMgrSrcDefaultPort,
        tmnxSysRmtMgmtMgrTimeout,
        tmnxSysRmtMgmtMgrTlsClientProf,
        tmnxSysRmtMgmtMgrVRtrId,
        tmnxSysRmtMgmtMgrOperDevLabel,
        tmnxSysRmtMgmtMgrOperDevName,
        tmnxSysRmtMgmtMgrOperSrcIpAdType,
        tmnxSysRmtMgmtMgrOperSrcIpAddr,
        tmnxSysRmtMgmtMgrOperSrcPort,
        tmnxSysRmtMgmtMgrOperTimeout,
        tmnxSysRmtMgmtMgrOperTlsProf,
        tmnxSysRmtMgmtMgrOperVRtrId,
        tmnxSysRmtMgmtMgrOperTranspType
    }
    STATUS      current
    DESCRIPTION
        "The group of objects supporting configuration of management interface
         on Nokia SROS series system added in SROS release 20.0."
    ::= { tmnxSysV20v0Groups 13 }

tmnxSysNetconfCountersExtension  OBJECT-GROUP
    OBJECTS     {
        tmnxSysNetconfGetSchemaRequests,
        tmnxSysNetconfGetDataRequests,
        tmnxSysNetconfActionRequests,
        tmnxSysNetconfBadHellos,
        tmnxSysNetconfDroppedSessions,
        tmnxSysNetconfLastOperChange
    }
    STATUS      current
    DESCRIPTION
        "The group of objects supporting management of the NETCONF on Nokia
         SROS series system added in SROS releases 20.0 and 22.0."
    ::= { tmnxSysV20v0Groups 14 }

tmnxSysFpResAllocObsoleteGroup   OBJECT-GROUP
    OBJECTS     {
        tmnxSysFpResAllocG8032Sap,
        tmnxSysFpResAllocOperG8032Sap
    }
    STATUS      current
    DESCRIPTION
        "The group of additional FP options supporting the general system
         capabilities on Nokia SROS series systems."
    ::= { tmnxSysV20v0Groups 15 }

tmnxSysV21v0Groups               OBJECT IDENTIFIER ::= { tmnxSysGroups 81 }

tmnxSysLicensingV21v0Group       OBJECT-GROUP
    OBJECTS     {
        tmnxSysAppLicenseCurrentMax,
        tmnxSysAppLicense24HrDateTime,
        tmnxSysAppLicense24HrMax
    }
    STATUS      current
    DESCRIPTION
        "The group of objects supporting management of system licensing on
         Nokia SROS series system added in SROS release 21."
    ::= { tmnxSysV21v0Groups 2 }

tmnxSysMgmtIfOpsGroup            OBJECT-GROUP
    OBJECTS     {
        tmnxSysMgmtIfOpsAsyncExecTimeout,
        tmnxSysMgmtIfOpsAsyncRetTimeout,
        tmnxSysMgmtIfOpsSyncExecTimeout
    }
    STATUS      current
    DESCRIPTION
        "The group of objects supporting the configuration of global operations
         on Nokia SROS series system added in SROS release 21."
    ::= { tmnxSysV21v0Groups 3 }

tmnxSysMgmtIfObsoleteGroup       OBJECT-GROUP
    OBJECTS     {
        tmnxSysMgmtIfMDCliCmdAccntLoad
    }
    STATUS      current
    DESCRIPTION
        "The group of objects supporting management of the MD-CLI on Nokia SROS
         series system which are obsoleted"
    ::= { tmnxSysV21v0Groups 4 }

tmnxSysFwdPathOptsV21v0Group     OBJECT-GROUP
    OBJECTS     {
        tmnxSysFpoDot1xHostAuthAdmState,
        tmnxSysFpoDot1xHostAuthOperState,
        tmnxSysFpoIpv6FltrEgrAdminState,
        tmnxSysFpoIpv6FltrEgrOperState
    }
    STATUS      current
    DESCRIPTION
        "The group of objects supporting management of system forwarding path
         options on Nokia SROS series system added in SROS release 21."
    ::= { tmnxSysV21v0Groups 5 }

tmnxSysBofV21v0Group             OBJECT-GROUP
    OBJECTS     {
        sbiEncryptConfig,
        sbiPassword,
        sbiEncryptKey,
        sbbiEncryptConfig
    }
    STATUS      current
    DESCRIPTION
        "The group of objects supporting management of the Boot Options File
         (BOF) on Nokia SROS series system added in SROS release 21."
    ::= { tmnxSysV21v0Groups 6 }

tmnxSysFpResAllocV21v0Group      OBJECT-GROUP
    OBJECTS     {
        tmnxSysFpResAllocFilterIpv6,
        tmnxSysFpResAllocOperFilterIpv6
    }
    STATUS      current
    DESCRIPTION
        "The group of additional FP options supporting the general system
         capabilities on Nokia SROS release 21."
    ::= { tmnxSysV21v0Groups 7 }

tmnxSysFpResAllocPoolV21v0Group  OBJECT-GROUP
    OBJECTS     {
        tmnxSysFpRAPoolLgBndRsvMemCnt,
        tmnxSysFpRAPoolOprLgBndRsvMemCnt
    }
    STATUS      current
    DESCRIPTION
        "The group of objects supporting system FP resource allocation pool
         capabilities on Nokia SROS release 21."
    ::= { tmnxSysV21v0Groups 8 }

tmnxSysMgmtIfComHistoryV21v0Grp  OBJECT-GROUP
    OBJECTS     {
        tmnxSysMgmtIfCommitHistory
    }
    STATUS      current
    DESCRIPTION
        "The group of objects supporting system Commit History capability on
         Nokia SROS release 21."
    ::= { tmnxSysV21v0Groups 9 }

tmnxSysFpResAllocFecV21v0Group   OBJECT-GROUP
    OBJECTS     {
        tmnxSysFpResAllocFecSysWdUnpd,
        tmnxSysFpResAllocFecOprSysWdUnpd,
        tmnxSysFpResAllocFecSysWdPd,
        tmnxSysFpResAllocFecOprSysWdPd
    }
    STATUS      current
    DESCRIPTION
        "The group of objects supporting system FP FEC resource allocation
         capability on Nokia SROS release 21."
    ::= { tmnxSysV21v0Groups 10 }

tmnxSysGrpcTunnelV21v0Group      OBJECT-GROUP
    OBJECTS     {
        tmnxGTnlDestGrpTblLastChgd,
        tmnxGTnlDestGrpDestTblLastChgd,
        tmnxGTnlTunnelTblLastChgd,
        tmnxGTnlTunnelHandlerTblLastChgd,
        tmnxGTnlDestGrpRowStatus,
        tmnxGTnlDestGrpLastChgd,
        tmnxGTnlDestGrpDescription,
        tmnxGTnlDestGrpTlsClientProf,
        tmnxGTnlDestGrpAllowUnsecConn,
        tmnxGTnlDestGrpTcpKaAdminState,
        tmnxGTnlDestGrpTcpKaIdle,
        tmnxGTnlDestGrpTcpKaInterval,
        tmnxGTnlDestGrpTcpKaCount,
        tmnxGTnlDestGrpDestRowStatus,
        tmnxGTnlDestGrpDestLastChgd,
        tmnxGTnlDestGrpDestAddType,
        tmnxGTnlDestGrpDestAddress,
        tmnxGTnlDestGrpDestPort,
        tmnxGTnlDestGrpDestVRtrId,
        tmnxGTnlDestGrpDestLclSrcAddType,
        tmnxGTnlDestGrpDestLclSrcAddress,
        tmnxGTnlDestGrpDestOrigQosMark,
        tmnxGTnlTunnelRowStatus,
        tmnxGTnlTunnelLastChgd,
        tmnxGTnlTunnelAdminState,
        tmnxGTnlTunnelOperState,
        tmnxGTnlTunnelOperDownReason,
        tmnxGTnlTunnelDescription,
        tmnxGTnlTunnelDestGrp,
        tmnxGTnlTunnelTgtNameCustomStr,
        tmnxGTnlTunnelTgtNameUserAgent,
        tmnxGTnlTunnelTgtNameNodeName,
        tmnxGTnlTunnelOperTargetName,
        tmnxGTnlTunnelHandlerRowStatus,
        tmnxGTnlTunnelHandlerLastChgd,
        tmnxGTnlTunnelHandlerAdminState,
        tmnxGTnlTunnelHandlerPort,
        tmnxGTnlTunnelHandlerCustomType,
        tmnxGTnlTunnelHandlerGrpcServer,
        tmnxGTnlTunnelHandlerSshServer,
        tmnxGTnlTunnelDestAddType,
        tmnxGTnlTunnelDestAddress,
        tmnxGTnlTunnelDestPort,
        tmnxGTnlTunnelDestOperState,
        tmnxGTnlTunnelDestOperDownReason,
        tmnxGTnlTunnelDestOperVRtrId,
        tmnxGTnlTunnelDestLastOperChange,
        tmnxGTnlTunnelDestConnAttempts,
        tmnxGTnlTunnelSessionStartTime,
        tmnxGTnlTunnelSessionTargetType,
        tmnxGTnlTunnelSessionLclSrcPort,
        tmnxGTnlTunnelSessionRxBytes,
        tmnxGTnlTunnelSessionTxBytes,
        tmnxSysGrpcTunnelDelayOnBoot
    }
    STATUS      current
    DESCRIPTION
        "The group of objects supporting system gRPC-Tunnel capability on Nokia
         SROS release 21."
    ::= { tmnxSysV21v0Groups 11 }

tmnxSysV22v0Groups               OBJECT IDENTIFIER ::= { tmnxSysGroups 82 }

tmnxSysFwdPathOptsV22v0Group     OBJECT-GROUP
    OBJECTS     {
        tmnxSysFpoIpv6FltrNxtHdrAdmState,
        tmnxSysFpoIpv6FltrNxtHdrOprState,
        tmnxSysFpoIpv6FltrDstPrtAdmState,
        tmnxSysFpoIpv6FltrDstPrtOprState,
        tmnxSysFpoIpv6FltrSrcPrtAdmState,
        tmnxSysFpoIpv6FltrSrcPrtOprState,
        tmnxSysFpoIpv6FltrDstIpLsbAdmSt,
        tmnxSysFpoIpv6FltrDstIpLsbOprSt,
        tmnxSysFpoIpv6FltrTcpFlgAdmState,
        tmnxSysFpoIpv6FltrTcpFlgOprState,
        tmnxSysFpoIpv6FltStatColAdmState,
        tmnxSysFpoIpv6FltStatColOprState,
        tmnxSysFpoIpv4FltStatColAdmState,
        tmnxSysFpoIpv4FltStatColOprState,
        tmnxSysFpoIpv4FltPbrRdrtAdmState,
        tmnxSysFpoIpv4FltPbrRdrtOprState,
        tmnxSysFpoIpv6FltPbrRdrtAdmState,
        tmnxSysFpoIpv6FltPbrRdrtOprState,
        tmnxSysFpoRingApsAdminState,
        tmnxSysFpoRingApsOperState,
        tmnxSysFpoSvcCesAdminState,
        tmnxSysFpoSvcCesOperState
    }
    STATUS      current
    DESCRIPTION
        "The group of objects supporting management of system forwarding path
         options on Nokia SROS series system added in release 22."
    ::= { tmnxSysV22v0Groups 1 }

tmnxSysNotificationV22v0Group    NOTIFICATION-GROUP
    NOTIFICATIONS {
        tmnxSysDyingGasp
    }
    STATUS      current
    DESCRIPTION
        "The group of notifications supporting the general system capabilities
         on Nokia SROS series systems added in release 22."
    ::= { tmnxSysV22v0Groups 2 }

tmnxSysFpLpmResAlcnV22v0Group    OBJECT-GROUP
    OBJECTS     {
        tmnxSysFpResAlcnLpmTblLastChg,
        tmnxSysFpResAlcnLpmLastChanged,
        tmnxSysFpResAlcnLpmAdminState,
        tmnxSysFpResAlcnLpmOperState
    }
    STATUS      current
    DESCRIPTION
        "The group of objects supporting management of system forwarding path
         LPM resource allocation scale options on Nokia SROS series system
         added in release 22."
    ::= { tmnxSysV22v0Groups 3 }

tmnxSysFanControlV22v0Group      OBJECT-GROUP
    OBJECTS     {
        tmnxSysFanIncMinimumSpeed
    }
    STATUS      current
    DESCRIPTION
        "The group of objects supporting the system fan control added in SROS
         release 22."
    ::= { tmnxSysV22v0Groups 4 }

tmnxSysRemoteMgmtV22v0Group      OBJECT-GROUP
    OBJECTS     {
        tmnxSysRmtMgmtHelloIntervalSec
    }
    STATUS      current
    DESCRIPTION
        "The group of objects supporting configuration of management interface
         on Nokia SROS series system added in SROS release 22.0."
    ::= { tmnxSysV22v0Groups 5 }

tmnxSysRemoteMgmtObsoleteGroup   OBJECT-GROUP
    OBJECTS     {
        tmnxSysRmtMgmtHelloInterval
    }
    STATUS      current
    DESCRIPTION
        "The group of objects supporting configuration of management interface
         on Nokia SROS series system which are obsoleted"
    ::= { tmnxSysV22v0Groups 6 }

tmnxSysFpOptsV22v0ObsoleteGroup  OBJECT-GROUP
    OBJECTS     {
        tmnxSysFpoLpmAlcnScl1AdminState,
        tmnxSysFpoLpmAlcnScl1OperState,
        tmnxSysFpoLpmAlcnScl2AdminState,
        tmnxSysFpoLpmAlcnScl2OperState,
        tmnxSysFpoLpmAlcnScl3AdminState,
        tmnxSysFpoLpmAlcnScl3OperState
    }
    STATUS      current
    DESCRIPTION
        "The group of objects supporting management of system forwarding path
         options on Nokia SROS series system that were obsoleted in SROS
         release 22."
    ::= { tmnxSysV22v0Groups 7 }

tmnxSysFpResMacFltrObsoleteGroup OBJECT-GROUP
    OBJECTS     {
        tmnxSysFpoMacFltOutVlanPrioAdmSt,
        tmnxSysFpoMacFltOutVlanPrioOprSt
    }
    STATUS      current
    DESCRIPTION
        "The group of additional FP options related to mac-filter options on
         Nokia SROS series systems that were obsoleted in SROS release 22.2."
    ::= { tmnxSysV22v0Groups 8 }

tmnxSysFpResAllocV22v0Group      OBJECT-GROUP
    OBJECTS     {
        tmnxSysFpResAlcEgrEncapRouted,
        tmnxSysFpResAlcEgrEncapOprRouted,
        tmnxSysFpRAEgrEncpPrtVlanTrns,
        tmnxSysFpRAEgrEncpOprPrtVlanTrns
    }
    STATUS      current
    DESCRIPTION
        "The group of objects supporting system FP resource allocation
         capabilities on Nokia SROS release 22."
    ::= { tmnxSysV22v0Groups 10 }

tnmxSysRebootInfoV22v0Group      OBJECT-GROUP
    OBJECTS     {
        tmnxLastSystemRebootRouter
    }
    STATUS      current
    DESCRIPTION
        "The group of objects supporting management of system log last reboot
         Nokia SROS series systems in release 22.0."
    ::= { tmnxSysV22v0Groups 11 }

tmnxSysV23v0Groups               OBJECT IDENTIFIER ::= { tmnxSysGroups 83 }

tmnxSysConfigV23v0Group          OBJECT-GROUP
    OBJECTS     {
        sbiSnmpdMaxBulkDuration
    }
    STATUS      current
    DESCRIPTION
        "The group of objects supporting management of boot-up configuration
         and synchronization of active and standby systems on Nokia SROS series
         systems in release 23."
    ::= { tmnxSysV23v0Groups 1 }

tmnxSysFileTransProfV23v0Group   OBJECT-GROUP
    OBJECTS     {
        tmnxSysFileTransProfHttpVersion
    }
    STATUS      current
    DESCRIPTION
        "The group of objects supporting the configuration of file transmission
         profile on Nokia SROS series system added in SROS release 23."
    ::= { tmnxSysV23v0Groups 2 }

tmnxSysNotificationV23v0Group    NOTIFICATION-GROUP
    NOTIFICATIONS {
        tmnxConfigConflict,
        tmnxSysLicenseInvalid,
        tmnxSysLicenseExpiresSoon,
        tmnxSysLicenseCleared,
        tmnxSysLicensingStateOk
    }
    STATUS      current
    DESCRIPTION
        "The group of notifications supporting the general system capabilities
         added in release 12.0 of SROS."
    ::= { tmnxSysV23v0Groups 3 }

tmnxPersistenceV23v0Group        OBJECT-GROUP
    OBJECTS     {
        spiSubMgmtPersistenceFileLocation,
        spiSubMgmtPersistenceDescription,
        spiDhcpSrvPersistenceFileLoc,
        spiDhcpSrvPersistenceDescr,
        spiNatFwdPersistenceFileLoc,
        spiNatFwdPersistenceDescr,
        spiAAPersistenceFileLoc,
        spiAAPersistenceDescr,
        spiAncpPersistenceFileLoc,
        spiAncpPersistenceDescr
    }
    STATUS      current
    DESCRIPTION
        "The group of objects supporting management of persistency across
         system reboot on Nokia SROS series systems release 12.0."
    ::= { tmnxSysV23v0Groups 4 }

tmnxPythonPersistenceV23v0Grp    OBJECT-GROUP
    OBJECTS     {
        spiPythonPersistenceFileLoc,
        spiPythonPersistenceDescr
    }
    STATUS      current
    DESCRIPTION
        "The group of objects supporting management of persistency across
         system reboot on Nokia SROS series systems release 12.0."
    ::= { tmnxSysV23v0Groups 5 }

tmnxSysFltrProfiles23v0Group     OBJECT-GROUP
    OBJECTS     {
        tmnxSysFpRAFltrInIpMSrcIp,
        tmnxSysFpRAFltrInIpOpMSrcIp,
        tmnxSysFpRAFltrInIpMDstIp,
        tmnxSysFpRAFltrInIpOpMDstIp,
        tmnxSysFpRAFltrInIpMSrcPort,
        tmnxSysFpRAFltrInIpOpMSrcPort,
        tmnxSysFpRAFltrInIpMDstPort,
        tmnxSysFpRAFltrInIpOpMDstPort,
        tmnxSysFpRAFltrInIpMProt,
        tmnxSysFpRAFltrInIpOpMProt,
        tmnxSysFpRAFltrInIpMTcpFlgs,
        tmnxSysFpRAFltrInIpOpMTcpFlgs,
        tmnxSysFpRAFltrInIpMDscp,
        tmnxSysFpRAFltrInIpOpMDscp,
        tmnxSysFpRAFltrInIpADrop,
        tmnxSysFpRAFltrInIpOpADrop,
        tmnxSysFpRAFltrInIpARedir,
        tmnxSysFpRAFltrInIpOpARedir,
        tmnxSysFpRAFltrInIpALog,
        tmnxSysFpRAFltrInIpOpALog,
        tmnxSysFpRAFltrInIpAMirror,
        tmnxSysFpRAFltrInIpOpAMirror,
        tmnxSysFpRAFltrInIpAFc,
        tmnxSysFpRAFltrInIpOpAFc,
        tmnxSysFpRAFltrInIpAStats,
        tmnxSysFpRAFltrInIpOpAStats,
        tmnxSysFpRAFltrInIpv6MSrcIpMsb,
        tmnxSysFpRAFltrInIpv6OpMSrcIpMsb,
        tmnxSysFpRAFltrInIpv6MSrcIpLsb,
        tmnxSysFpRAFltrInIpv6OpMSrcIpLsb,
        tmnxSysFpRAFltrInIpv6MDstIpMsb,
        tmnxSysFpRAFltrInIpv6OpMDstIpMsb,
        tmnxSysFpRAFltrInIpv6MDstIpLsb,
        tmnxSysFpRAFltrInIpv6OpMDstIpLsb,
        tmnxSysFpRAFltrInIpv6MSrcPort,
        tmnxSysFpRAFltrInIpv6OpMSrcPort,
        tmnxSysFpRAFltrInIpv6MDstPort,
        tmnxSysFpRAFltrInIpv6OpMDstPort,
        tmnxSysFpRAFltrInIpv6MNextHdr,
        tmnxSysFpRAFltrInIpv6OpMNextHdr,
        tmnxSysFpRAFltrInIpv6MTcpFlgs,
        tmnxSysFpRAFltrInIpv6OpMTcpFlgs,
        tmnxSysFpRAFltrInIpv6MDscp,
        tmnxSysFpRAFltrInIpv6OpMDscp,
        tmnxSysFpRAFltrInIpv6ADrop,
        tmnxSysFpRAFltrInIpv6OpADrop,
        tmnxSysFpRAFltrInIpv6ARedir,
        tmnxSysFpRAFltrInIpv6OpARedir,
        tmnxSysFpRAFltrInIpv6ALog,
        tmnxSysFpRAFltrInIpv6OpALog,
        tmnxSysFpRAFltrInIpv6AMirror,
        tmnxSysFpRAFltrInIpv6OpAMirror,
        tmnxSysFpRAFltrInIpv6AFc,
        tmnxSysFpRAFltrInIpv6OpAFc,
        tmnxSysFpRAFltrInIpv6AStats,
        tmnxSysFpRAFltrInIpv6OpAStats
    }
    STATUS      current
    DESCRIPTION
        "The group of objects supporting user defined filter profiles
         capability on Nokia SROS release 23."
    ::= { tmnxSysV23v0Groups 6 }

tmnxSysFwdPathOptsV23v0Group     OBJECT-GROUP
    OBJECTS     {
        tmnxSysFpoIpv6FltrFlwLblAdmState,
        tmnxSysFpoIpv6FltrFlwLblOprState,
        tmnxSysFpoQosSharedPolAdminState,
        tmnxSysFpoQosSharedPolOperState
    }
    STATUS      current
    DESCRIPTION
        "The group of objects supporting management of system forwarding path
         options on Nokia SROS series system added in release 23."
    ::= { tmnxSysV23v0Groups 7 }

tmnxSysFltrProfFlowLabelGroup    OBJECT-GROUP
    OBJECTS     {
        tmnxSysFpRAFltrInIpv6MFLabel,
        tmnxSysFpRAFltrInIpv6OpMFLabel
    }
    STATUS      current
    DESCRIPTION
        "The group of objects supporting flow-label in user defined filter
         profiles capability on Nokia SROS release 23.7"
    ::= { tmnxSysV23v0Groups 8 }

tmnxSysFPOptsV23v0ObsoleteGrp    OBJECT-GROUP
    OBJECTS     {
        tmnxSysFpoMplsFastSwOvAdminState,
        tmnxSysFpoMplsFastSwOvOperState,
        tmnxSysFpoRouterEcmpAdminState,
        tmnxSysFpoRouterEcmpOperState
    }
    STATUS      current
    DESCRIPTION
        "The group of objects supporting obsoletion of system forwarding path
         options on Nokia SROS series system added in SROS release 23."
    ::= { tmnxSysV23v0Groups 9 }

tmnxSysNetconfV23vObsoleteGroup  OBJECT-GROUP
    OBJECTS     {
        tmnxSysMgmtIfYangBaseR13,
        tmnxSysNetconfCapRunningCfg
    }
    STATUS      current
    DESCRIPTION
        "The group of objects supporting management of the NETCONF on Nokia
         SROS series system which are obsoleted"
    ::= { tmnxSysV23v0Groups 10 }

tmnxSysFanControlV23v0Group      OBJECT-GROUP
    OBJECTS     {
        tmnxSysFanCtrlMinimumSpeed
    }
    STATUS      current
    DESCRIPTION
        "The group of objects supporting system fan control capability on Nokia
         SROS release 23."
    ::= { tmnxSysV23v0Groups 11 }

tmnxSysRAFlexPlcrStats23v0Group  OBJECT-GROUP
    OBJECTS     {
        tmnxSysFpRAPlcrStatsOvrState,
        tmnxSysFpRAPlcrStatsOvrOperState
    }
    STATUS      current
    DESCRIPTION
        "The group of objects supporting allocating flexible policer
         application groups capability on Nokia SROS release 23."
    ::= { tmnxSysV23v0Groups 12 }

tmnxSysRAFlexiblePlcr23v0Group   OBJECT-GROUP
    OBJECTS     {
        tSysFpRAPsAppGrpPlcrTotalAdmin,
        tSysFpRAPsAppGrpPlcrTotalOper,
        tSysFpRAPsAppGrpPlcrAllocAdmin,
        tSysFpRAPsAppGrpPlcrAllocOper,
        tSysFpRAPsPlcrScaleAdmin,
        tSysFpRAPsPlcrScaleOper
    }
    STATUS      current
    DESCRIPTION
        "The group of objects supporting allocating flexible policer
         application groups capability on Nokia SROS release 23."
    ::= { tmnxSysV23v0Groups 13 }

tmnxSysFanControlV23v1Group      OBJECT-GROUP
    OBJECTS     {
        tmnxSysFanCtrlCoolingProfile
    }
    STATUS      current
    DESCRIPTION
        "The group of objects supporting system fan control capability on Nokia
         SROS release 23.3.R3 and later."
    ::= { tmnxSysV23v0Groups 14 }

tmnxSysRASrv6TunnelTermGroup     OBJECT-GROUP
    OBJECTS     {
        tmnxSysFpRASrv6TnlTermEntries,
        tmnxSysFpRASrv6TnlTermOprEntries
    }
    STATUS      current
    DESCRIPTION
        "The group of objects supporting allocating TCAM resources for SRv6 on
         Nokia SROS."
    ::= { tmnxSysV23v0Groups 15 }

tmnxSysRAFlexL1Plcr23v0Group     OBJECT-GROUP
    OBJECTS     {
        tSysFpRAPsBankAppGrpIdAdmin,
        tSysFpRAPsBankAppGrpIdOper
    }
    STATUS      current
    DESCRIPTION
        "The group of objects supporting allocating flexible policer
         application groups capability on Nokia SROS release 23."
    ::= { tmnxSysV23v0Groups 16 }

tmnxSysUpTimeV23v0Group          OBJECT-GROUP
    OBJECTS     {
        tmnxSysUpTime
    }
    STATUS      current
    DESCRIPTION
        "The group of objects supporting the 64-bit uptime counter on Nokia
         SROS release 23."
    ::= { tmnxSysV23v0Groups 17 }

tmnxSysFpResAllocV23v0Group      OBJECT-GROUP
    OBJECTS     {
        tmnxSysFpRAStatsPolicerBanks,
        tmnxSysFpRAStatsPolicerOperBanks,
        tmnxSysFpRAStatsFltrIngBanks,
        tmnxSysFpRAStatsFltrOperIngBanks,
        tmnxSysFpRAStatsFltrEgrBanks,
        tmnxSysFpRAStatsFltrOperEgrBanks
    }
    STATUS      current
    DESCRIPTION
        "The group of additional FP objects supporting the policer and filter
         statistics resources on Nokia SROS release 23."
    ::= { tmnxSysV23v0Groups 18 }

tmnxSysResEcmpProfObsoleteGroup  OBJECT-GROUP
    OBJECTS     {
        tmnxSysResEcmpProfRowStatus,
        tmnxSysResEcmpProfType,
        tmnxSysResEcmpProfLinksPerGrp,
        tmnxSysResEcmpProfNumGrps
    }
    STATUS      current
    DESCRIPTION
        "The group of objects supporting ECMP profile deprecated  on Nokia SROS
         series system in release 23.10"
    ::= { tmnxSysV23v0Groups 19 }

tmnxSysV24v0Groups               OBJECT IDENTIFIER ::= { tmnxSysGroups 84 }

tmnxSysRAFlexPlcrBankBindGroup   OBJECT-GROUP
    OBJECTS     {
        tSysFpRAPsBankBindingAdmin,
        tSysFpRAPsBankBindingOper
    }
    STATUS      current
    DESCRIPTION
        "The group of objects supporting allocating flexible policer
         application bank binding capability on Nokia SROS release 24."
    ::= { tmnxSysV24v0Groups 1 }

tmnxSysMgmtIfV24v0ObsoleteGroup  OBJECT-GROUP
    OBJECTS     {
        tmnxSysMgmtIfPriSchemaPathState,
        tmnxSysMgmtIfPriSchemaPathValue,
        tmnxSysMgmtIfSecSchemaPathState,
        tmnxSysMgmtIfSecSchemaPathValue,
        tmnxSysMgmtIfTerSchemaPathState,
        tmnxSysMgmtIfTerSchemaPathValue
    }
    STATUS      current
    DESCRIPTION
        "The group of objects supporting configuration of management interface
         on Nokia SROS series system that were obsoleted in SROS release 24.3."
    ::= { tmnxSysV24v0Groups 2 }

tmnxSysFltrProfiles24v0Group     OBJECT-GROUP
    OBJECTS     {
        tmnxSysFpRAFltrEgIpMSrcIp,
        tmnxSysFpRAFltrEgIpOpMSrcIp,
        tmnxSysFpRAFltrEgIpMDstIp,
        tmnxSysFpRAFltrEgIpOpMDstIp,
        tmnxSysFpRAFltrEgIpMSrcPort,
        tmnxSysFpRAFltrEgIpOpMSrcPort,
        tmnxSysFpRAFltrEgIpMDstPort,
        tmnxSysFpRAFltrEgIpOpMDstPort,
        tmnxSysFpRAFltrEgIpMProt,
        tmnxSysFpRAFltrEgIpOpMProt,
        tmnxSysFpRAFltrEgIpMTcpFlgs,
        tmnxSysFpRAFltrEgIpOpMTcpFlgs,
        tmnxSysFpRAFltrEgIpMDscp,
        tmnxSysFpRAFltrEgIpOpMDscp,
        tmnxSysFpRAFltrEgIpADrop,
        tmnxSysFpRAFltrEgIpOpADrop,
        tmnxSysFpRAFltrEgIpAStats,
        tmnxSysFpRAFltrEgIpOpAStats,
        tmnxSysFpRAFltrEgIpv6MSrcIpMsb,
        tmnxSysFpRAFltrEgIpv6OpMSrcIpMsb,
        tmnxSysFpRAFltrEgIpv6MSrcIpLsb,
        tmnxSysFpRAFltrEgIpv6OpMSrcIpLsb,
        tmnxSysFpRAFltrEgIpv6MDstIpMsb,
        tmnxSysFpRAFltrEgIpv6OpMDstIpMsb,
        tmnxSysFpRAFltrEgIpv6MDstIpLsb,
        tmnxSysFpRAFltrEgIpv6OpMDstIpLsb,
        tmnxSysFpRAFltrEgIpv6MSrcPort,
        tmnxSysFpRAFltrEgIpv6OpMSrcPort,
        tmnxSysFpRAFltrEgIpv6MDstPort,
        tmnxSysFpRAFltrEgIpv6OpMDstPort,
        tmnxSysFpRAFltrEgIpv6MNextHdr,
        tmnxSysFpRAFltrEgIpv6OpMNextHdr,
        tmnxSysFpRAFltrEgIpv6MTcpFlgs,
        tmnxSysFpRAFltrEgIpv6OpMTcpFlgs,
        tmnxSysFpRAFltrEgIpv6MDscp,
        tmnxSysFpRAFltrEgIpv6OpMDscp,
        tmnxSysFpRAFltrEgIpv6MFLabel,
        tmnxSysFpRAFltrEgIpv6OpMFLabel,
        tmnxSysFpRAFltrEgIpv6ADrop,
        tmnxSysFpRAFltrEgIpv6OpADrop,
        tmnxSysFpRAFltrEgIpv6AStats,
        tmnxSysFpRAFltrEgIpv6OpAStats
    }
    STATUS      current
    DESCRIPTION
        "The group of objects supporting user defined filter profiles
         capability on Nokia SROS release 24."
    ::= { tmnxSysV24v0Groups 3 }

tmnxSysLoginControlV24v0Group    OBJECT-GROUP
    OBJECTS     {
        slcSSHMaxChannelsPerConnection
    }
    STATUS      current
    DESCRIPTION
        "The group of objects supporting management of login control on Nokia
         SROS series systems."
    ::= { tmnxSysV24v0Groups 4 }

tmnxSysFpResAllocV24v0Group      OBJECT-GROUP
    OBJECTS     {
        tmnxSysFpRAStatsDdctdFcPlcrs,
        tmnxSysFpRAStatsOperDdctdFcPlcrs
    }
    STATUS      current
    DESCRIPTION
        "The group of additional FP objects for dedicated fc policers on Nokia
         SROS release 24."
    ::= { tmnxSysV24v0Groups 5 }

tmnxSysGeneralV24v0Group         OBJECT-GROUP
    OBJECTS     {
        sgiKernelVersion,
        sgiFIPSProviderVersion,
        sgiEntropySourceVersion
    }
    STATUS      current
    DESCRIPTION
        "The group of objects supporting management of general system
         capabilities on Nokia SROS release 24."
    ::= { tmnxSysV24v0Groups 6 }

tmnxSysRAFlexibleStats24v0Group  OBJECT-GROUP
    OBJECTS     {
        tSysFpRAPsStatsScaleAdmin,
        tSysFpRAPsStatsScaleOper,
        tSysFpRAPsAppGrpStatsTotalAdmin,
        tSysFpRAPsAppGrpStatsTotalOper,
        tSysFpRAPsAppGrpStatsAllocAdmin,
        tSysFpRAPsAppGrpStatsAllocOper
    }
    STATUS      current
    DESCRIPTION
        "The group of objects supporting allocating flexible policer
         application groups capability on Nokia SROS release 24."
    ::= { tmnxSysV24v0Groups 7 }

tmnxSysFltrProfIcmp24v0Group     OBJECT-GROUP
    OBJECTS     {
        tmnxSysFpRAFltrInIpMIcmpCode,
        tmnxSysFpRAFltrInIpOpMIcmpCode,
        tmnxSysFpRAFltrInIpMIcmpType,
        tmnxSysFpRAFltrInIpOpMIcmpType,
        tmnxSysFpRAFltrInIpv6MIcmpCode,
        tmnxSysFpRAFltrInIpv6OpMIcmpCode,
        tmnxSysFpRAFltrInIpv6MIcmpType,
        tmnxSysFpRAFltrInIpv6OpMIcmpType,
        tmnxSysFpRAFltrEgIpMIcmpCode,
        tmnxSysFpRAFltrEgIpOpMIcmpCode,
        tmnxSysFpRAFltrEgIpMIcmpType,
        tmnxSysFpRAFltrEgIpOpMIcmpType,
        tmnxSysFpRAFltrEgIpv6MIcmpCode,
        tmnxSysFpRAFltrEgIpv6OpMIcmpCode,
        tmnxSysFpRAFltrEgIpv6MIcmpType,
        tmnxSysFpRAFltrEgIpv6OpMIcmpType
    }
    STATUS      current
    DESCRIPTION
        "The group of objects supporting ICMP in user defined filter profiles
         capability on Nokia SROS release 24.7"
    ::= { tmnxSysV24v0Groups 8 }

tmnxSysFltrProfTcpFlExt24v0Group OBJECT-GROUP
    OBJECTS     {
        tmnxSysFpRAFltrInIpMTcpFlExt,
        tmnxSysFpRAFltrInIpOpMTcpFlExt,
        tmnxSysFpRAFltrInIpv6MTcpFlExt,
        tmnxSysFpRAFltrInIpv6OpMTcpFlExt,
        tmnxSysFpRAFltrEgIpMTcpFlExt,
        tmnxSysFpRAFltrEgIpOpMTcpFlExt,
        tmnxSysFpRAFltrEgIpv6MTcpFlExt,
        tmnxSysFpRAFltrEgIpv6OpMTcpFlExt
    }
    STATUS      current
    DESCRIPTION
        "The group of objects supporting extended TCP flags in user defined
         filter profiles capability on Nokia SROS release 24.7"
    ::= { tmnxSysV24v0Groups 9 }

tmnxSysConfigV24v0Group          OBJECT-GROUP
    OBJECTS     {
        sbiSnmpdTransportProtocol
    }
    STATUS      current
    DESCRIPTION
        "The group of objects supporting management of boot-up configuration
         and synchronization of active and standby systems on Nokia SROS
         release 24.10"
    ::= { tmnxSysV24v0Groups 10 }

tmnxSysFpRAEcmpV24v0Group        OBJECT-GROUP
    OBJECTS     {
        tmnxSysFpRAEcmpBgpMplsTunnlBind,
        tmnxSysFpRAEcmpOperBgpMplsTBind,
        tmnxSysFpRAEcmpPrFlwHashSdpBind,
        tmnxSysFpRAEcmpOprPrFlwHshSBind
    }
    STATUS      current
    DESCRIPTION
        "The group of objects supporting management of resource allocation for
         ECMP on Nokia SROS release 24.10"
    ::= { tmnxSysV24v0Groups 11 }

tmnxSysFpRAProfileV24v0Group     OBJECT-GROUP
    OBJECTS     {
        tmnxSysFpRAAdminProfile,
        tmnxSysFpRAOperProfile
    }
    STATUS      current
    DESCRIPTION
        "The group of objects supporting management of resource allocation for
         forwarding plane profile on Nokia SROS release 24.10"
    ::= { tmnxSysV24v0Groups 12 }

tmnxSysBofV24v0Group             OBJECT-GROUP
    OBJECTS     {
        sbiFipsLevel1
    }
    STATUS      current
    DESCRIPTION
        "The group of objects supporting management of the Boot Options File
         (BOF) on Nokia SROS series system added in SROS release 24."
    ::= { tmnxSysV24v0Groups 13 }

tmnxSysFwdPathOptsV24v0Group     OBJECT-GROUP
    OBJECTS     {
        tmnxSysFpoLagAlbAdminState,
        tmnxSysFpoLagAlbOperState
    }
    STATUS      current
    DESCRIPTION
        "The group of objects supporting management of system forwarding path
         options on Nokia SROS series system added in release 24."
    ::= { tmnxSysV24v0Groups 14 }

tmnxSysMgmtIfMdCliHistV24v0Group OBJECT-GROUP
    OBJECTS     {
        tmnxSysMgmtIfMDEnvHistoryRecall,
        tmnxSysMgmtIfMDEnvHistorySize
    }
    STATUS      current
    DESCRIPTION
        "The group of objects supporting the configuration of MD cli history on
         Nokia SROS series system added in release 24."
    ::= { tmnxSysV24v0Groups 15 }

tmnxSysSwDSValidateV24v0Group    OBJECT-GROUP
    OBJECTS     {
        tmnxSysSwDSValidate,
        tmnxSysSwDSValidateUrl,
        tmnxSysSwDSValidationIndex,
        tmnxSysSwDSValidationUrl,
        tmnxSysSwDSValidationState,
        tmnxSysSwDSFailureReason
    }
    STATUS      current
    DESCRIPTION
        "The group of objects supporting management of software digital
         signature validation in release 24."
    ::= { tmnxSysV24v0Groups 16 }

tmnxSysSwDSValidNotifV24v0Group  NOTIFICATION-GROUP
    NOTIFICATIONS {
        tmnxSysSwDSValidationResult
    }
    STATUS      current
    DESCRIPTION
        "The group of notifications supporting the software digital signature
         validation for release 24."
    ::= { tmnxSysV24v0Groups 17 }

tmnxSysMgmtIfMdCliCommitGroup    OBJECT-GROUP
    OBJECTS     {
        tmnxSysMgmtIfMDEnvCmtOptsConfirm,
        tmnxSysMgmtIfMDEnvCmtOptsComment
    }
    STATUS      current
    DESCRIPTION
        "The group of objects supporting the configuration of MD cli
         commit-options on Nokia SROS series system added in release 24."
    ::= { tmnxSysV24v0Groups 18 }

tmnxSysMgmtIfMdCliInfoOutGroup   OBJECT-GROUP
    OBJECTS     {
        tmnxSysMgmtIfMDEnvInfoAdmState
    }
    STATUS      current
    DESCRIPTION
        "The group of objects supporting the configuration of MD cli
         info-output on Nokia SROS series system added in release 24."
    ::= { tmnxSysV24v0Groups 19 }

tmnxSysFPVlanQosQModeV24v0Group  OBJECT-GROUP
    OBJECTS     {
        tmnxSysFpRAVlanQosFourQueue,
        tmnxSysFpRAVlanQosOprFourQueue,
        tmnxSysFpRAVlanQosStatFourQueue,
        tmnxSysFpRAVlanQosOprStatFourQ
    }
    STATUS      current
    DESCRIPTION
        "The group of objects supporting management of resource allocation
            for vlan qos queue mode on Nokia SROS release 24.10"
    ::= { tmnxSysV24v0Groups 20 }

tmnxSysFpoMplsHierTunV24v0Group  OBJECT-GROUP
    OBJECTS     {
        tmnxSysFpoMplsHierTunAdminState,
        tmnxSysFpoMplsHierTunOperState
    }
    STATUS      current
    DESCRIPTION
        "The group of objects supporting the MPLS system forwarding path option
         to enable multi-level HW based hierarchical LSP for uniform FRR on
         Nokia SROS release 24.10"
    ::= { tmnxSysV24v0Groups 21 }

tmnxSysMGGroups                  OBJECT IDENTIFIER ::= { tmnxSysConformance 3 }

tmnxSysMGCompliances             OBJECT IDENTIFIER ::= { tmnxSysConformance 4 }

tmnxSysDCCompliance              OBJECT IDENTIFIER ::= { tmnxSysConformance 5 }

tmnxSysDCGroups                  OBJECT IDENTIFIER ::= { tmnxSysConformance 6 }

tmnxSysNspProxyCompliances       OBJECT IDENTIFIER ::= { tmnxSysConformance 7 }

tmnxSysNspProxyGroups            OBJECT IDENTIFIER ::= { tmnxSysConformance 8 }

tmnxSysVsdObsoletedGroup         OBJECT-GROUP
    OBJECTS     {
        tmnxSysVsdSystemId,
        tmnxSysVsdGwPubSubIsSubscrd,
        tmnxSysVsdGwPubSubNodeName,
        tmnxSysVsdGwPubSubLstSubscrdTime,
        tmnxSysVsdGwLastAuditTxTime,
        tmnxSysXmppServFQDN,
        tmnxSysXmppServRowStatus,
        tmnxSysXmppServUserName,
        tmnxSysXmppServPassword,
        tmnxSysXmppServLastChanged,
        tmnxSysXmppServUptime,
        tmnxSysXmppServIQSent,
        tmnxSysXmppServIQRcvd,
        tmnxSysXmppServIQError,
        tmnxSysXmppServIQTimedOut,
        tmnxSysXmppServIQAckRcvd,
        tmnxSysXmppServIQMinRtt,
        tmnxSysXmppServIQMaxRtt,
        tmnxSysXmppServVsdUpdatesRcvd,
        tmnxSysXmppServUpdatesRcvd,
        tmnxSysXmppServMsgSent,
        tmnxSysXmppServMsgRcvd,
        tmnxSysXmppServMsgAckRcvd,
        tmnxSysXmppServMsgError,
        tmnxSysXmppServMsgTimedOut,
        tmnxSysXmppServMsgMinRtt,
        tmnxSysXmppServMsgMaxRtt,
        tmnxSysXmppServSubSent,
        tmnxSysXmppServUnSubSent,
        tmnxSysXmppServState,
        tmnxSysXmppServAdminState,
        tmnxSysVsdServUptime,
        tmnxSysVsdServUserName,
        tmnxSysVsdServerStatus,
        tmnxSysVsdServMsgSent,
        tmnxSysVsdServMsgRcvd,
        tmnxSysVsdServMsgAckRcvd,
        tmnxSysVsdServMsgError,
        tmnxSysVsdServMsgTimedOut,
        tmnxSysVsdServMsgMinRtt,
        tmnxSysVsdServMsgMaxRtt,
        tmnxSysXmppServOperUserName,
        tmnxSysXmppServAuthType,
        tmnxSysXmppServConnMode
    }
    STATUS      current
    DESCRIPTION
        "The group of obsoleted objects in 23.3 supporting the general system
         Vsd and xmpp tables on Nokia SROS series systems."
    ::= { tmnxSysNspProxyGroups 3 }

tmnxSysMIBNotifyPrefix           OBJECT IDENTIFIER ::= { tmnxSRNotifyPrefix 1 }

tmnxSysNotifications             OBJECT IDENTIFIER ::= { tmnxSysMIBNotifyPrefix 0 }

stiDateAndTimeChanged            NOTIFICATION-TYPE
    OBJECTS     {
        stiDateAndTime
    }
    STATUS      current
    DESCRIPTION
        "[CAUSE] The stiDateAndTimeChanged notification is generated when the
         time on the system is explicitly set.

         [EFFECT] The time on the system is being changed.

         [RECOVERY] No recovery is necessary."
    ::= { tmnxSysNotifications 1 }

ssiSaveConfigSucceeded           NOTIFICATION-TYPE
    STATUS      current
    DESCRIPTION
        "The save config succeeded event is generated when the saving of
         configuration finishes without errors."
    ::= { tmnxSysNotifications 2 }

ssiSaveConfigFailed              NOTIFICATION-TYPE
    STATUS      current
    DESCRIPTION
        "The save config failed event is generated when the saving of
         configuration is stopped due to errors."
    ::= { tmnxSysNotifications 3 }

sbiBootConfig                    NOTIFICATION-TYPE
    OBJECTS     {
        sbiConfigStatus,
        sbiPersistStatus,
        sbiPersistIndex
    }
    STATUS      current
    DESCRIPTION
        "The sbiBootConfig notification is generated upon completion of the
         configuration phase following a system reboot."
    ::= { tmnxSysNotifications 4 }

sbiBootSnmpd                     NOTIFICATION-TYPE
    OBJECTS     {
        sbiPersistIndex,
        sbiSnmpdAdminStatus,
        sbiSnmpdOperStatus
    }
    STATUS      current
    DESCRIPTION
        "The sbiBootSnmpd notification is generated upon completion of the SNMP
         daemon initialization following a system reboot. Some system
         configuration and initialization errors may result in the SNMP daemon
         being suspended."
    ::= { tmnxSysNotifications 5 }

radiusServerOperStatusChange     NOTIFICATION-TYPE
    OBJECTS     {
        radiusServerAddress,
        radiusServerOperStatus
    }
    STATUS      obsolete
    DESCRIPTION
        "The radiusServerOperStatusChange notification is generated when the
         operational status of a RADIUS server has transitioned either from
         'up' to 'down' or from 'down' to 'up'.

         This object was made obsolete in the 5.0 release."
    ::= { tmnxSysNotifications 6 }

radiusOperStatusChange           NOTIFICATION-TYPE
    OBJECTS     {
        radiusOperStatus
    }
    STATUS      current
    DESCRIPTION
        "The radiusOperStatusChange notification is generated when the
         radiusOperStatus has transitioned either from 'up' to 'down' or from
         'down' to 'up'"
    ::= { tmnxSysNotifications 7 }

tmnxConfigModify                 NOTIFICATION-TYPE
    OBJECTS     {
        tmnxNotifyRow,
        tmnxNotifyEntryOID,
        tmnxNotifyObjectName
    }
    STATUS      current
    DESCRIPTION
        "A tmnxConfigModify notification is generated when a configuration
         attribute associated with a row entry in a MIB table is modified. It
         can be used by the NMS to trigger maintenance polls of the
         configuration information."
    ::= { tmnxSysNotifications 8 }

tmnxConfigCreate                 NOTIFICATION-TYPE
    OBJECTS     {
        tmnxNotifyRow,
        tmnxNotifyEntryOID,
        tmnxNotifyObjectName
    }
    STATUS      current
    DESCRIPTION
        "A tmnxConfigCreate notification is generated when a new row entry is
         created in one of the MIB tables. It can be used by the NMS to trigger
         maintenance polls of the configuration information."
    ::= { tmnxSysNotifications 9 }

tmnxConfigDelete                 NOTIFICATION-TYPE
    OBJECTS     {
        tmnxNotifyRow,
        tmnxNotifyEntryOID,
        tmnxNotifyObjectName
    }
    STATUS      current
    DESCRIPTION
        "A tmnxConfigDelete notification is generated when an existing row
         entry in one of the MIB tables is deleted. It can be used by the NMS
         to trigger maintenance polls of the configuration information."
    ::= { tmnxSysNotifications 10 }

tmnxStateChange                  NOTIFICATION-TYPE
    OBJECTS     {
        tmnxNotifyRow,
        tmnxNotifyRowAdminState,
        tmnxNotifyRowOperState,
        tmnxNotifyEntryOID,
        tmnxNotifyObjectName
    }
    STATUS      current
    DESCRIPTION
        "A tmnxStateChange notification is generated when there is a change in
         either the administrative or operational state of a MIB table entry."
    ::= { tmnxSysNotifications 11 }

tmnxModuleMallocFailed           NOTIFICATION-TYPE
    OBJECTS     {
        tmnxMemoryModule,
        tmnxModuleMallocSize
    }
    STATUS      current
    DESCRIPTION
        "A tmnxModuleMallocFailed notification is generated when a request to
         allocate memory from a particular module fails because the memory
         module is short on memory and cannot support the size that was
         requested."
    ::= { tmnxSysNotifications 12 }

tmnxTrapDropped                  NOTIFICATION-TYPE
    OBJECTS     {
        tmnxDroppedTrapID,
        tmnxTrapDroppedReasonCode,
        tmnxTrapDroppedEntryID,
        tmnxTrapDroppedCount
    }
    STATUS      current
    DESCRIPTION
        "A tmnxTrapDropped notification is generated when a trap is dropped for
         the reason specified by the reason code. The tmnxTrapDroppedEntryID
         identifies the table entry associated with the dropped trap.

         A nonzero value of the object tmnxTrapDroppedCount indicates the
         number of traps dropped for the current flow of traps, identified by
         the values of tmnxDroppedTrapID, tmnxTrapDroppedReasonCode and
         tmnxTrapDroppedEntryID."
    ::= { tmnxSysNotifications 13 }

ssiSyncConfigOK                  NOTIFICATION-TYPE
    STATUS      current
    DESCRIPTION
        "The ssiSyncConfigOK event is generated when the synchronization of
         configuration files between the primary and secondary CPMs finishes
         without errors."
    ::= { tmnxSysNotifications 14 }

ssiSyncConfigFailed              NOTIFICATION-TYPE
    OBJECTS     {
        tmnxSyncFailureReason
    }
    STATUS      current
    DESCRIPTION
        "The ssiSyncConfigFailed event is generated when the synchronization of
         configuration files between the primary and secondary CPMs is stopped
         due to errors. The tmnxSyncFailureReason will state reason for
         failure."
    ::= { tmnxSysNotifications 15 }

ssiSyncBootEnvOK                 NOTIFICATION-TYPE
    STATUS      current
    DESCRIPTION
        "The ssiSyncBootEnvOK event is generated when the synchronization of
         boot environment files between the primary and secondary CPMs finishes
         without errors."
    ::= { tmnxSysNotifications 16 }

ssiSyncBootEnvFailed             NOTIFICATION-TYPE
    OBJECTS     {
        tmnxSyncFailureReason
    }
    STATUS      current
    DESCRIPTION
        "The ssiSyncBootEnvFailed event is generated when the synchronization
         of boot environment files between the primary and secondary CPMs is
         stopped due to errors. The tmnxSyncFailureReason will state reason for
         failure."
    ::= { tmnxSysNotifications 17 }

sntpTimeDiffExceedsThreshold     NOTIFICATION-TYPE
    OBJECTS     {
        sntpAdminState
    }
    STATUS      current
    DESCRIPTION
        "The sntpTimeDiffExceedsThreshold event is generated when the time
         differential between the system and the SNTP server is more than 10
         seconds. In this case the system clock is not automatically adjusted."
    ::= { tmnxSysNotifications 18 }

tacplusServerOperStatusChange    NOTIFICATION-TYPE
    OBJECTS     {
        tacplusServerAddress,
        tacplusServerOperStatus
    }
    STATUS      obsolete
    DESCRIPTION
        "The tacplusServerOperStatusChange notification is generated when the
         operational status of a TACACS+ server has transitioned either from
         'up' to 'down' or from 'down' to 'up'.

         This object was made obsolete in the 5.0 release."
    ::= { tmnxSysNotifications 19 }

tacplusOperStatusChange          NOTIFICATION-TYPE
    OBJECTS     {
        tacplusOperStatus
    }
    STATUS      current
    DESCRIPTION
        "The tacplusOperStatusChange notification is generated when the
         tacplusOperStatus has transitioned either from 'up' to 'down' or from
         'down' to 'up'"
    ::= { tmnxSysNotifications 20 }

tmnxSnmpdError                   NOTIFICATION-TYPE
    OBJECTS     {
        tmnxSnmpdErrorMsg
    }
    STATUS      current
    DESCRIPTION
        "The tmnxSnmpdError notification is generated when the SNMP daemon
         detects an error condition."
    ::= { tmnxSysNotifications 21 }

tmnxSsiMismatch                  NOTIFICATION-TYPE
    OBJECTS     {
        ssiSyncMode,
        sbiPersist
    }
    STATUS      current
    DESCRIPTION
        "The tmnxSsiMismatch notification is generated by a system with
         redundant CPM cards after the processing of the bootup
         configuration has completed when ssiSyncMode has a  value of 'none'
         and sbiPersist has a value of 'true'.  This can result in SNMP
         indexes having different values following a system failover."
    ::= { tmnxSysNotifications 22 }

tmnxSnmpdStateChange             NOTIFICATION-TYPE
    OBJECTS     {
        sbiSnmpdAdminStatus,
        sbiSnmpdOperStatus
    }
    STATUS      current
    DESCRIPTION
        "The tmnxSnmpdStateChange notification is generated whenever there is a
         change in either the administrative or operational state of the SNMP
         agent."
    ::= { tmnxSysNotifications 23 }

ssiRedStandbySyncing             NOTIFICATION-TYPE
    OBJECTS     {
        tmnxChassisNotifyHwIndex,
        tmnxHwID,
        tmnxHwClass
    }
    STATUS      current
    DESCRIPTION
        "The ssiRedStandbySyncing notification is generated when
         synchronization of redundancy information onto the standby
         CPM is started.  tmnxChassisNotifyHwIndex identifies the
         standby CPM."
    ::= { tmnxSysNotifications 24 }

ssiRedStandbyReady               NOTIFICATION-TYPE
    OBJECTS     {
        tmnxChassisNotifyHwIndex,
        tmnxHwID,
        tmnxHwClass
    }
    STATUS      current
    DESCRIPTION
        "The ssiRedStandbyReady notification is generated when the
         synchronization of redundancy information onto the standby CPM
         has completed.  The standby CPM is now ready to take over
         control of the system if the active CPM fails or a manual
         switchover command is issued.  tmnxChassisNotifyHwIndex
         identifies the standby CPM."
    ::= { tmnxSysNotifications 25 }

ssiRedStandbySyncLost            NOTIFICATION-TYPE
    OBJECTS     {
        tmnxChassisNotifyHwIndex,
        tmnxHwID,
        tmnxHwClass
    }
    STATUS      current
    DESCRIPTION
        "The ssiRedStandbySyncLost notification is generated when the active
         CPM looses communication with the standby CPM.
         tmnxChassisNotifyHwIndex identifies the lost standby CPM."
    ::= { tmnxSysNotifications 26 }

ssiRedSwitchover                 NOTIFICATION-TYPE
    OBJECTS     {
        tmnxChassisNotifyHwIndex,
        tmnxHwID,
        tmnxHwClass,
        ssiRedFailoverTime,
        ssiRedFailoverReason
    }
    STATUS      current
    DESCRIPTION
        "The ssiRedSwitchover notification is generated when the standby
         CPM detects that the active CPM has failed and the standby prepares
         to take over as the new active CPM.  tmnxChassisNotifyHwIndex
         identifies the new active CPM."
    ::= { tmnxSysNotifications 27 }

ssiRedCpmActive                  NOTIFICATION-TYPE
    OBJECTS     {
        tmnxChassisNotifyHwIndex,
        tmnxHwID,
        tmnxHwClass
    }
    STATUS      current
    DESCRIPTION
        "The ssiRedCpmActive notification is generated following a
         redundancy switchover when the new active CPM has completed
         its audit and is ready to accept management commands via CLI
         or SNMP SET requests.  tmnxChassisNotifyHwIndex identifies
         the new active CPM."
    ::= { tmnxSysNotifications 28 }

ssiRedSingleCpm                  NOTIFICATION-TYPE
    OBJECTS     {
        tmnxChassisNotifyHwIndex,
        tmnxHwID,
        tmnxHwClass
    }
    STATUS      current
    DESCRIPTION
        "The ssiRedSingleCpm notification is generated by a system with
         a chassis with two CPM slots when the active CPM cannot detect a
         standby CPM in the chassis.  When the operating state of
         TIMETRA-CHASSIS-MIB::tmnxCpmCardRedundant for the active CPM card
         transitions to a value of 'singleton (1)', this notification is
         generated.  tmnxChassisNotifyHwIndex identifies the singleton CPM.

         When the active CPM later detects a standby CPM in the chassis, the
         ssiRedStandbySyncing event will be generated followed by a
         ssiRedStandbyReady event to indicate clearing of the CPM singleton
         state.  The value of tmnxCpmCardRedundant will then transition to
         'redundantActive (2)'."
    ::= { tmnxSysNotifications 29 }

persistencyClosedAlarmRaised     NOTIFICATION-TYPE
    OBJECTS     {
        tmnxPersistenceAffectedCpm,
        tmnxPersistencyClient,
        tmnxPersistencyFileLocator,
        tmnxPersistencyNotifyMsg
    }
    STATUS      current
    DESCRIPTION
        "The persistencyClosedAlarmRaised notification is generated when the
         system is unable to store persistency data (e.g. because the device is
         inaccessible, or full)."
    ::= { tmnxSysNotifications 30 }

persistencyClosedAlarmCleared    NOTIFICATION-TYPE
    OBJECTS     {
        tmnxPersistenceAffectedCpm,
        tmnxPersistencyClient,
        tmnxPersistencyFileLocator,
        tmnxPersistencyNotifyMsg
    }
    STATUS      current
    DESCRIPTION
        "The persistencyClosedAlarmCleared notification is generated when the
         output device used to store the persistence data is available for use
         again."
    ::= { tmnxSysNotifications 31 }

tmnxSntpOperChange               NOTIFICATION-TYPE
    OBJECTS     {
        sntpOperStatus
    }
    STATUS      current
    DESCRIPTION
        "The tmnxSntpOperChange notification is generated whenever there is a
         change in the operational state of SNTP."
    ::= { tmnxSysNotifications 32 }

tmnxSysTimeSet                   NOTIFICATION-TYPE
    OBJECTS     {
        stiDateAndTime,
        tmnxSysTimeSetBy
    }
    STATUS      current
    DESCRIPTION
        "The tmnxSysTimeSet notification is generated whenever system time is
         set by NTP, SNTP, SNMP, Real Time Clock(RTC) or if it was set
         manually."
    ::= { tmnxSysNotifications 33 }

tmnxFtpClientFailure             NOTIFICATION-TYPE
    OBJECTS     {
        tmnxFtpFailureMsg,
        tmnxFtpFailureDestAddressType,
        tmnxFtpFailureDestAddress
    }
    STATUS      current
    DESCRIPTION
        "The tmnxFtpClientFailure notification is generated when a file
         transfer operation initiated by the FTP client fails."
    ::= { tmnxSysNotifications 34 }

tacplusInetSrvrOperStatusChange  NOTIFICATION-TYPE
    OBJECTS     {
        tacPlusServerInetAddressType,
        tacPlusServerInetAddress,
        tacplusServerOperStatus
    }
    STATUS      current
    DESCRIPTION
        "The tacplusInetSrvrOperStatusChange notification is generated when the
         operational status of a TACACS+ server has transitioned either from
         'up' to 'down' or from 'down' to 'up'."
    ::= { tmnxSysNotifications 35 }

radiusInetServerOperStatusChange NOTIFICATION-TYPE
    OBJECTS     {
        radiusServerInetAddressType,
        radiusServerInetAddress,
        radiusServerOperStatus
    }
    STATUS      current
    DESCRIPTION
        "The radiusInetServerOperStatusChange notification is generated when
         the operational status of a Radius server has transitioned either from
         'up' to 'down' or from 'down' to 'up'."
    ::= { tmnxSysNotifications 36 }

persistencyEventReport           NOTIFICATION-TYPE
    OBJECTS     {
        tmnxPersistencyNotifyMsg
    }
    STATUS      current
    DESCRIPTION
        "The persistencyEventReport notification is generated when a
         client-specific persistence event occurs (e.g. the start and
         completion of a recover action after system startup)."
    ::= { tmnxSysNotifications 37 }

sbiBootConfigFailFileError       NOTIFICATION-TYPE
    OBJECTS     {
        sbiBootConfigFailScript
    }
    STATUS      current
    DESCRIPTION
        "The sbiBootConfigFailFileError notification is generated when
         sbiBootConfigFailScript file cannot be accessed."
    ::= { tmnxSysNotifications 38 }

sbiBootConfigOKFileError         NOTIFICATION-TYPE
    OBJECTS     {
        sbiBootConfigOKScript
    }
    STATUS      current
    DESCRIPTION
        "The sbiBootConfigOKFileError notification is generated when
         sbiBootConfigOKScript file cannot be accessed."
    ::= { tmnxSysNotifications 39 }

sbiBootLiConfig                  NOTIFICATION-TYPE
    OBJECTS     {
        sliConfigStatus,
        sbiLiSeparate,
        sbiLiLocalSave
    }
    STATUS      current
    DESCRIPTION
        "[CAUSE] The Lawful Intercept (LI) configuration phase following a
         system reboot is complete. This notification is generated
         periodically, about once an hour, and provides the status of the LI
         configuration processing at bootup time as well as the setting of the
         li-separate and li-local-save BOF flags.

         [EFFECT] LI configuration will be missing or incomplete if the LI
         configuration phase was not completed successfully.

         [RECOVERY] If the LI configuration phase was not completed
         successfully, then restore the LI configuration manually or reboot the
         router.

         This event is generated only from the LI context."
    ::= { tmnxSysNotifications 40 }

persistenceRestoreProblem        NOTIFICATION-TYPE
    OBJECTS     {
        tmnxPersistencyClient,
        tmnxPersistencyNotifyMsg
    }
    STATUS      current
    DESCRIPTION
        "The persistenceRestoreProblem notification is generated when an error
         is detected while processing a persistence record."
    ::= { tmnxSysNotifications 41 }

tmnxSysRollbackStarted           NOTIFICATION-TYPE
    OBJECTS     {
        tmnxSysRollbackIndex,
        tmnxSysRollbackFileType,
        tmnxLogExecRollbackOpIndex
    }
    STATUS      current
    DESCRIPTION
        "[CAUSE] The tmnxSysRollbackStarted notification is generated when the
         user initiates a revert of the rollback checkpoint file specified by
         tmnxSysRollbackIndex and tmnxSysRollbackFileType. The value of
         tmnxLogExecRollbackOpIndex indicates the row entry in the
         TIMETRA-LOG-MIB::tmnxLogExecRollbackOpTable for this rollback revert
         operation.

         [EFFECT] The specified file is executed and system configuration may
         change.

         [RECOVERY] There is no recovery required for this notification."
    ::= { tmnxSysNotifications 42 }

tmnxSysRollbackStatusChange      NOTIFICATION-TYPE
    OBJECTS     {
        tmnxSysRollbackIndex,
        tmnxSysRollbackResult,
        tmnxSysRollbackFileType,
        tmnxLogExecRollbackOpIndex
    }
    STATUS      current
    DESCRIPTION
        "[CAUSE] The tmnxSysRollbackStatusChange notification is
         generated upon the completion of a rollback revert as specified
         by tmnxSysRollbackIndex and tmnxSysRollbackFileType.  The value
         of tmnxLogExecRollbackOpIndex indicates the row entry in the
         TIMETRA-LOG-MIB::tmnxLogExecRollbackOpTable for this rollback
         revert operation.

         [EFFECT] The result is indicated by the value of
         tmnxSysRollbackResult.

         [RECOVERY] When the value of tmnxSysRollbackResult is none, inProgress
         or success no recovery is required. When the value is failed, the user
         should try to determine the reason for the failure. The user can
         attempt a recovery by reverting back to a known good checkpoint. The
         user may reboot the system with the bof pointing to a saved
         configuration file."
    ::= { tmnxSysNotifications 43 }

tmnxSysRollbackSaveStatusChange  NOTIFICATION-TYPE
    OBJECTS     {
        tmnxSysRollbackSaveResult,
        tmnxSysRollbackFileType
    }
    STATUS      current
    DESCRIPTION
        "[CAUSE] The tmnxSysRollbackSaveStatusChange notification is generated
         upon the completion of a rollback save as specified by
         tmnxSysRollbackFileType.

         [EFFECT] The result is indicated by value of
         tmnxSysRollbackSaveResult.

         [RECOVERY] When the value of tmnxSysRollbackSaveResult is none,
         inProgress or success no recovery is required. When the value is
         failed, the user should try to determine the reason for the failure.
         The user can attempt a recovery by attempting the rollback save again."
    ::= { tmnxSysNotifications 44 }

tmnxSysRollbackFileDeleteStatus  NOTIFICATION-TYPE
    OBJECTS     {
        tmnxSysRollbackIndex,
        tmnxSysRollbackFileDeleteResult,
        tmnxSysRollbackFileType
    }
    STATUS      current
    DESCRIPTION
        "[CAUSE] The tmnxSysRollbackFileDeleteStatus notification is generated
         upon the completion of a rollback file delete as specified by
         tmnxSysRollbackIndex and tmnxSysRollbackFileType.

         [EFFECT] The result is indicated by the value of
         tmnxSysRollbackFileDeleteResult.

         [RECOVERY] When the value of tmnxSysRollbackFileDeleteResult is none,
         inProgress or success no recovery is required. When the value is
         failed, the user should try to determine the reason for the failure.
         The user can attempt a recovery by deleting the file again."
    ::= { tmnxSysNotifications 45 }

ssiSyncRollbackOK                NOTIFICATION-TYPE
    STATUS      current
    DESCRIPTION
        "[CAUSE]  The ssiSyncRollbackOK event is generated when the
         synchronization of rollback files between the primary
         and secondary CPMs finishes without errors.

         [EFFECT] Rollback files are synchronized.

         [RECOVERY] No recovery is necessary."
    ::= { tmnxSysNotifications 46 }

ssiSyncRollbackFailed            NOTIFICATION-TYPE
    OBJECTS     {
        tmnxSyncFailureReason
    }
    STATUS      current
    DESCRIPTION
        "[CAUSE] The ssiSyncRollbackFailed event is generated when the
         synchronization of rollback files between the primary and secondary
         CPMs is stopped due to errors. The tmnxSyncFailureReason will state
         the reason for the failure.

         [EFFECT] Rollback files are not synchronized.

         [RECOVERY] The user should try to determine the cause of the failure
         and can attempt synchronizing the files again."
    ::= { tmnxSysNotifications 47 }

ssiSyncCertOK                    NOTIFICATION-TYPE
    STATUS      current
    DESCRIPTION
        "[CAUSE]  The ssiSyncCertOK event is generated when the
         synchronization of certificate files between the primary
         and secondary CPMs finishes without errors.

         [EFFECT] Certificate files are synchronized.

         [RECOVERY] No recovery is necessary."
    ::= { tmnxSysNotifications 48 }

ssiSyncCertFailed                NOTIFICATION-TYPE
    OBJECTS     {
        tmnxSyncFailureReason
    }
    STATUS      current
    DESCRIPTION
        "[CAUSE] The ssiSyncCertFailed event is generated when the
         synchronization of certificate files between the primary and secondary
         CPMs is stopped due to errors. The tmnxSyncFailureReason will state
         the reason for the failure.

         [EFFECT] Certificate files are not synchronized.

         [RECOVERY] The user should try to determine the cause of the failure
         and can attempt synchronizing the files again."
    ::= { tmnxSysNotifications 49 }

persistencyFileSysThresRaised    NOTIFICATION-TYPE
    OBJECTS     {
        tmnxPersistenceAffectedCpm,
        tmnxPersistencyClient,
        tmnxPersistencyFileLocator,
        tmnxPersistencyNotifyMsg
    }
    STATUS      current
    DESCRIPTION
        "The persistencyFileSysThresRaised notification is generated when the
         filesystem reaches 90 percent occupation."
    ::= { tmnxSysNotifications 50 }

persistencyFileSysThresCleared   NOTIFICATION-TYPE
    OBJECTS     {
        tmnxPersistenceAffectedCpm,
        tmnxPersistencyClient,
        tmnxPersistencyFileLocator,
        tmnxPersistencyNotifyMsg
    }
    STATUS      current
    DESCRIPTION
        "The persistencyFileSysThresCleared notification is generated when the
         filesystem drops below 90 percent occupation."
    ::= { tmnxSysNotifications 51 }

tmnxSysExecStarted               NOTIFICATION-TYPE
    OBJECTS     {
        tmnxSysExecScript,
        tmnxLogExecRollbackOpIndex,
        tmnxLogExecRollbackOpType
    }
    STATUS      current
    DESCRIPTION
        "[CAUSE] The tmnxSysExecStarted notification is generated when the user
         initiates a CLI 'exec' operation to process a file of SROS CLI
         commands or processing of 'vsd' configuration messages have been
         initiated.

         The value of tmnxSysExecScript indicates the command file when the
         value of tmnxLogExecRollbackOpType is 'exec' or an empty string when
         the value of tmnxLogExecRollbackOpType is 'vsd'. The value of
         tmnxLogExecRollbackOpIndex indicates the row entry in
         TIMETRA-LOG-MIB::tmnxLogExecRollbackOpTable for this CLI 'exec' or
         'vsd' operation.

         [EFFECT] All change notifications generated after the generation of
         this notification and before the tmnxSysExecFinished will be logged in
         the TIMETRA-LOG-MIB::tmnxLogExecRollbackEventEntry. Once the
         tmnxSysExecFinished notification is triggered, a Network Management
         System (NMS) is able to walk the aforementioned log table to retrieve
         the list of all objects that have been modified during this
         transaction.

         [RECOVERY] There is no recovery required for this notification."
    ::= { tmnxSysNotifications 52 }

tmnxSysExecFinished              NOTIFICATION-TYPE
    OBJECTS     {
        tmnxSysExecScript,
        tmnxSysExecResult,
        tmnxLogExecRollbackOpIndex,
        tmnxLogExecRollbackOpType
    }
    STATUS      current
    DESCRIPTION
        "[CAUSE] The tmnxSysExecFinished notification is generated upon the
         completion of the execution of a CLI command file or execution of vsd
         configuration messages is completed.

         The value of tmnxSysExecScript indicates the command file when the
         value of tmnxLogExecRollbackOpType is 'exec' or an empty string when
         the value of tmnxLogExecRollbackOpType is 'vsd'. The value of
         tmnxLogExecRollbackOpIndex indicates the row entry in
         TIMETRA-LOG-MIB::tmnxLogExecRollbackOpTable for this CLI 'exec' or
         'vsd' operation.

         [EFFECT] The effect is that the entry for the specified
         tmnxLogExecRollbackOpIndex won't be updated, and no further
         notifications will be added to the specified index in the logger.

         [RECOVERY] When the value of tmnxSysExecResult is 'none' or 'success',
         no recovery is required.

         When the value is 'fail', the system may be left in an inconsistent
         state and the user should try to determine the reason for the failure.
         The user can attempt a recovery by manually entering CLI commands to
         reverse the failed configuration.  The user can attempt a recovery by
         performing a rollback revert to a known good checkpoint. The user can
         attempt a recovery by rebooting the system with the bof pointing to a
         saved configuration file."
    ::= { tmnxSysNotifications 53 }

tmnxSysRollbackSaveStarted       NOTIFICATION-TYPE
    OBJECTS     {
        tmnxSysRollbackFileType
    }
    STATUS      current
    DESCRIPTION
        "[CAUSE] The tmnxSysRollbackSaveStarted notification is generated when
         the user initiates a rollback save as specified by
         tmnxSysRollbackFileType.

         [EFFECT] The specified configuration file is saved.

         [RECOVERY] There is no recovery required for this notification."
    ::= { tmnxSysNotifications 54 }

tmnxSysRollbackDeleteStarted     NOTIFICATION-TYPE
    OBJECTS     {
        tmnxSysRollbackIndex,
        tmnxSysRollbackFileType
    }
    STATUS      current
    DESCRIPTION
        "[CAUSE] The tmnxSysRollbackDeleteStarted notification is generated
         when the user initiates a rollback delete as specified by
         tmnxSysRollbackIndex and tmnxSysRollbackFileType.

         [EFFECT] The specified configuration file is deleted.

         [RECOVERY] There is no recovery required for this notification."
    ::= { tmnxSysNotifications 55 }

tmnxSysNvsysFileError            NOTIFICATION-TYPE
    OBJECTS     {
        tmnxSysFileErrorType
    }
    STATUS      current
    DESCRIPTION
        "[CAUSE] The tmnxSysNvsysFileError notification is generated when there
         is a failure in accessing the nvsys file as specified by
         tmnxSysFileErrorType.

         [EFFECT] The specified nvsys file operation is unsuccessful.

         [RECOVERY] The user should investigate why the failure occurred. A
         failure can indicate a problem with the compact flash."
    ::= { tmnxSysNotifications 56 }

sysDNSSecFailedAuthentication    NOTIFICATION-TYPE
    OBJECTS     {
        sysDNSSecRespCtrl,
        tmnxSysDNSSecDomainName
    }
    STATUS      current
    DESCRIPTION
        "[CAUSE] The sysDNSSecFailedAuthentication notification is generated
         when a DNS response PDU is received with an unset AD-bit and
         sysDNSSecAdValidation is set to 'true (1)'.

         [EFFECT] This notification is informational only. The message will
         vary depending on the state of sysDNSSecRespCtrl.

         [RECOVERY] There is no recovery required for this notification."
    ::= { tmnxSysNotifications 57 }

tmnxConfigConflict               NOTIFICATION-TYPE
    OBJECTS     {
        tmnxNotifyRow,
        tmnxNotifyEntryOID,
        tmnxNotifyObjectName
    }
    STATUS      current
    DESCRIPTION
        "A tmnxConfigConflict notification is generated when a configuration
         attribute associated with a row entry in a MIB table is in conflict
         with another attribute.

         It can be used by the NMS to trigger maintenance polls of the
         configuration information."
    ::= { tmnxSysNotifications 58 }

tmnxSysLicenseInvalid            NOTIFICATION-TYPE
    OBJECTS     {
        tmnxHwClass,
        tmnxSysLicenseErrorReason,
        tmnxSysLicenseTimeLeft,
        tmnxSysLicenseErrorAction
    }
    STATUS      current
    DESCRIPTION
        "[CAUSE] The tmnxSysLicenseInvalid notification is generated when the
         license becomes invalid for the reason specified in
         tmnxSysLicenseErrorReason.

         [EFFECT] The CPM or system will reboot at the end of the time
         remaining, as specified by tmnxSysLicenseTimeLeft and
         tmnxSysLicenseErrorAction.

         [RECOVERY] Configure a valid license file location and file name,
         given the value of tmnxSysLicenseErrorReason."
    ::= { tmnxSysNotifications 59 }

tmnxSysLicenseExpiresSoon        NOTIFICATION-TYPE
    OBJECTS     {
        tmnxHwClass,
        tmnxSysLicenseTimeLeft
    }
    STATUS      current
    DESCRIPTION
        "[CAUSE] The tmnxSysLicenseExpiresSoon notification is generated when
         the license is due to expire soon.

         [EFFECT] The system will reboot at the end of the time remaining, as
         specified by tmnxSysLicenseTimeLeft.

         [RECOVERY] Configure a valid license file location and file name."
    ::= { tmnxSysNotifications 60 }

tmnxSysVsdServerAvailable        NOTIFICATION-TYPE
    OBJECTS     {
        tmnxSysNotifVsdServerName
    }
    STATUS      obsolete
    DESCRIPTION
        "[CAUSE] The tmnxSysVsdServerAvailable notification is generated when
         system discover a new VSD server.

         [EFFECT] System will use this information to establish communication
         with new VSD server as needed.

         [RECOVERY] None needed."
    ::= { tmnxSysNotifications 63 }

tmnxSysVsdServerUnavailable      NOTIFICATION-TYPE
    OBJECTS     {
        tmnxSysNotifVsdServerName
    }
    STATUS      obsolete
    DESCRIPTION
        "[CAUSE] The tmnxSysVsdServerAvailable notification is generated when
         system loses connection to VSD.

         [EFFECT] System will use this information and stop communication with
         this VSD server as needed.

         [RECOVERY] None needed."
    ::= { tmnxSysNotifications 64 }

tmnxSysXmppServerFunctional      NOTIFICATION-TYPE
    OBJECTS     {
        tmnxSysNotifXmppServerName
    }
    STATUS      obsolete
    DESCRIPTION
        "[CAUSE] The tmnxSysXmppServerFunctional notification is generated when
         system discover a new XMPP server.

         [EFFECT] System will use this information to establish communication
         with new XMPP server as needed.

         [RECOVERY] None needed."
    ::= { tmnxSysNotifications 65 }

tmnxSysXmppServerNotFunctional   NOTIFICATION-TYPE
    OBJECTS     {
        tmnxSysNotifXmppServerName
    }
    STATUS      obsolete
    DESCRIPTION
        "[CAUSE] The tmnxSysXmppServerNotFunctional notification is generated
         when system can not communicate with XMPP server.

         [EFFECT] Communication with XMPP server will stop.

         [RECOVERY] Check to see why XMPP server has stopped communicating."
    ::= { tmnxSysNotifications 66 }

tmnxSysLicenseValid              NOTIFICATION-TYPE
    OBJECTS     {
        tmnxHwClass
    }
    STATUS      current
    DESCRIPTION
        "[CAUSE] The tmnxSysLicenseValid notification is generated once after
         the system boots up and the license is determined by the system to be
         valid.

         [EFFECT] The system is running with the license specified in
         tmnxSysLicenseName.

         [RECOVERY] No recovery."
    ::= { tmnxSysNotifications 67 }

tmnxSysBaseMacAddressNotSet      NOTIFICATION-TYPE
    OBJECTS     {
        tmnxChassisBaseMacAddress
    }
    STATUS      current
    DESCRIPTION
        "[CAUSE] The tmnxSysBaseMacAddressNotSet notification is generated once
         after the system boots up and the value of sbiSystemBaseMacAddress is
         all zeroes.

         [EFFECT] The system software is using the base MAC address specified
         in tmnxChassisBaseMacAddress which may not be unique.

         [RECOVERY] Configure sbiSystemBaseMacAddress to a value other than all
         zeroes."
    ::= { tmnxSysNotifications 68 }

tmnxSmLaunchStartFailed          NOTIFICATION-TYPE
    OBJECTS     {
        tmnxEhsHEntryScriptPlcyOwner,
        tmnxEhsHEntryScriptPlcyName,
        smLaunchScriptOwner,
        smLaunchScriptName,
        smLaunchError,
        tmnxSmLaunchExtAuthType,
        tmnxSmRunExtAuthType,
        tmnxSmRunExtUserName
    }
    STATUS      current
    DESCRIPTION
        "[CAUSE] The tmnxSmLaunchStartFailed notification is generated when the
         launch start fails because of one of the following reasons:
            1. The values of smLaunchScriptOwner and smLaunchScriptName don't
            have an existing entry in the smScriptTable.
            2. The value of smScriptOperStatus is not 'enabled'.
            3. The smScriptSource value is NULL.
            4. The value of smLaunchOperStatus object in smLaunchTable is not
            'enabled'.
            5. The check to see if the run Index is already in use fails.
            6. The number of currently executing scripts invoked from this
            smLaunchTable entry is greater than smLaunchMaxRunning.

          [EFFECT] The result is indicated by incrementing the value of
            tmnxEhsHEntryStatsErrLaunch.
          [RECOVERY] No recovery is necessary."
    ::= { tmnxSysNotifications 69 }

tmnxEhsHandlerInvoked            NOTIFICATION-TYPE
    OBJECTS     {
        tmnxEhsHandlerDescription,
        tmnxSmRunExtAuthType,
        tmnxSmRunExtUserName
    }
    STATUS      current
    DESCRIPTION
        "[CAUSE] The tmnxEhsHandlerInvoked notification is generated when the
         following checks pass: 1. A check to see if a event trigger is present
         for a particular log event based on the log event application-id and
         event-id/event name. 2. Evaluation of the log filter associated with
         the trigger-entry.

         [EFFECT] This may create a run entry to execute scripts.

         [RECOVERY] No recovery is necessary."
    ::= { tmnxSysNotifications 70 }

tmnxEhsDroppedByMinDelay         NOTIFICATION-TYPE
    OBJECTS     {
        tmnxEhsHEntryScriptPlcyOwner,
        tmnxEhsHEntryScriptPlcyName,
        smLaunchScriptOwner,
        smLaunchScriptName,
        tmnxEhsHEntryMinDelay,
        tmnxEhsHEntryMinDelayInterval,
        tmnxSmRunExtAuthType,
        tmnxSmRunExtUserName
    }
    STATUS      current
    DESCRIPTION
        "[CAUSE] The tmnxEhsDroppedByMinDelay is generated when two consecutive
         executions of script policy specified by the same event handler entry
         occurs within the time period specified by tmnxEhsHEntryMinDelay.

         [EFFECT] The value of tmnxEhsHEntryStatsErrMinDelay gets incremented.

         [RECOVERY] No recovery is necessary."
    ::= { tmnxSysNotifications 71 }

tmnxSysAppStats24HrsAvailable    NOTIFICATION-TYPE
    OBJECTS     {
        tmnxSysNotifAppStatsTime,
        tmnxSysNotifAppStatsApplication,
        tmnxSysNotifAppStatsType
    }
    STATUS      current
    DESCRIPTION
        "[CAUSE] The system generates the tmnxSysAppStats24HrsAvailable
         notification when new rows are available in the
         tmnxSysAppStats24HrsTable.

         The value of tmnxSysNotifAppStatsTime indicates the time the system
         collected the values in the new rows.

         A non-zero value of tmnxSysNotifAppStatsApplication indicates the
         application; a zero value of tmnxSysNotifAppStatsApplication indicates
         that new values are available for all active applications.

         A non-zero value of tmnxSysNotifAppStatsType indicates the type of
         statistics; a zero value of tmnxSysNotifAppStatsType indicates that
         new values are available for all active types.

         [EFFECT] None.

         [RECOVERY] No recovery is necessary."
    ::= { tmnxSysNotifications 72 }

tmnxSysAppStatsWeekAvailable     NOTIFICATION-TYPE
    OBJECTS     {
        tmnxSysNotifAppStatsTime
    }
    STATUS      current
    DESCRIPTION
        "[CAUSE] The system generates the tmnxSysAppStatsWeekAvailable
         notification when new rows are available in the
         tmnxSysAppStatsWeekTable.

         The value of tmnxSysNotifAppStatsTime indicates the time the system
         collected the values in the new rows.

         [EFFECT] None.

         [RECOVERY] No recovery is necessary."
    ::= { tmnxSysNotifications 73 }

tmnxLastSystemRebootAdmin        NOTIFICATION-TYPE
    OBJECTS     {
        tmnxLastSystemRebootTime,
        tmnxLastSystemRebootUser,
        tmnxLastSystemRebootUserAddrType,
        tmnxLastSystemRebootUserAddress
    }
    STATUS      current
    DESCRIPTION
        "[CAUSE] The tmnxLastSystemRebootAdmin notification is generated when
         the reason for the last system reboot (as indicated by
         tmnxLastSystemRebootReason) was 'admin (1)'.

         [EFFECT] No effect.

         [RECOVERY] No recovery is necessary."
    ::= { tmnxSysNotifications 74 }

tmnxSysLicenseActivated          NOTIFICATION-TYPE
    OBJECTS     {
        tmnxHwClass
    }
    STATUS      current
    DESCRIPTION
        "[CAUSE] The tmnxSysLicenseActivated notification is generated each
         time a license is activated by the system.

         [EFFECT] The system is running with the license specified in
         tmnxSysLicenseName.

         [RECOVERY] No recovery."
    ::= { tmnxSysNotifications 75 }

tmnxSysStandbyLicensingError     NOTIFICATION-TYPE
    OBJECTS     {
        tmnxHwClass,
        tmnxSysLicenseErrorReason
    }
    STATUS      current
    DESCRIPTION
        "[CAUSE] The tmnxSysStandbyLicensingError notification is generated
         when a licensing issue has been detected by the standby. The reason is
         specified in tmnxSysLicenseErrorReason.

         [EFFECT] The Standby CPM may not synchronized and may be put into a
         failed state depending on the failure.

         [RECOVERY] Ensure a valid license file location and file name,
         given the value of tmnxSysLicenseErrorReason.  Reset the Standby CPM or activate
         a valid license."
    ::= { tmnxSysNotifications 76 }

tmnxSysStandbyLicensingReady     NOTIFICATION-TYPE
    OBJECTS     {
        tmnxHwClass
    }
    STATUS      current
    DESCRIPTION
        "[CAUSE] The tmnxSysStandbyLicensingReady notification is generated
         when a licensing has been successfully activated by the standby.

         [EFFECT] Any licensing errors detected by the Standby CPM are cleared.

         [RECOVERY] None."
    ::= { tmnxSysNotifications 77 }

tmnxSysMgmtIfModeChangeStart     NOTIFICATION-TYPE
    OBJECTS     {
        tmnxNotifySysMgmtIfOriginalMode,
        tmnxSysMgmtIfWriteMode,
        tmnxSysMgmtIfWriteSwitchReason
    }
    STATUS      current
    DESCRIPTION
        "[CAUSE] The tmnxSysMgmtIfModeChangeStart notification is generated
         when a management interface configuration mode change request is sent.

         [EFFECT] Switching modes between any configuration mode will lock the
         configuration datastores from operator input until the mode switch has
         completed.

         [RECOVERY] None."
    ::= { tmnxSysNotifications 78 }

tmnxSysMgmtIfModeChangeComplete  NOTIFICATION-TYPE
    OBJECTS     {
        tmnxSysMgmtIfWriteMode
    }
    STATUS      current
    DESCRIPTION
        "[CAUSE] The tmnxSysMgmtIfModeChangeComplete notification is generated
         when a management interface configuration mode change request is
         complete.

         [EFFECT] Switching modes between any configuration mode will lock the
         configuration datastores from operator input until the mode switch has
         completed. Once this event is triggered the configuration datastores
         are unlocked for operator input.

         [RECOVERY] None."
    ::= { tmnxSysNotifications 79 }

tmnxSysMgmtIfModeChangeFailure   NOTIFICATION-TYPE
    OBJECTS     {
        tmnxSysMgmtIfWriteMode
    }
    STATUS      current
    DESCRIPTION
        "[CAUSE] The tmnxSysMgmtIfModeChangeFailure notification is generated
         when a management interface configuration mode change request fails to
         complete.

         [EFFECT] Switching modes between any configuration mode will lock the
         configuration datastores from operator input until the mode switch has
         completed. When this event is triggered the mode change is declared
         unsuccessful; the effective configuration mode will be indicated in
         this notification. The configuration datastores are unlocked for
         operator input.

         [RECOVERY] None."
    ::= { tmnxSysNotifications 80 }

tmnxSysAppLicenseInsufficient    NOTIFICATION-TYPE
    OBJECTS     {
        tmnxSysLicensingNotifyGroup,
        tmnxSysLicensedNotifyAppName,
        tmnxSysAppLicenseState,
        tmnxSysLicenseErrorReason
    }
    STATUS      current
    DESCRIPTION
        "[CAUSE] The tmnxSysAppLicenseInsufficient notification is generated periodically
         when licensing for an application is detected to be insufficient.  The details
         of the error is specified in tmnxSysLicenseErrorReason.
         This notification cannot be suppressed.

         [EFFECT] Notification generated periodically while the application
         remains in this condition.

         [RECOVERY] Activate a system license containing sufficient license
         entitlements for this application."
    ::= { tmnxSysNotifications 81 }

tmnxSysMgmtIfLiIncorrectFormat   NOTIFICATION-TYPE
    OBJECTS     {
        tmnxPrimaryConfigFileFormatType,
        tmnxLiConfigFileFormatType
    }
    STATUS      current
    DESCRIPTION
        "[CAUSE] The tmnxSysMgmtIfLiIncorrectFormat notification is generated
         when a format (classic or model-driven) of the Lawful Intercept (LI)
         configuration file does not match primary configuration file format.

         [EFFECT] The Lawful Intercept (LI) configuration file is not loaded
         during the boot.

         [RECOVERY] Reboot with the correct Lawful Intercept (LI) configuration
         file"
    ::= { tmnxSysNotifications 82 }

tmnxSysMgmtIfLiCfgNotEncrypted   NOTIFICATION-TYPE
    STATUS      current
    DESCRIPTION
        "[CAUSE] The tmnxSysMgmtIfLiCfgNotEncrypted notification is generated
         when the Lawful Intercept (LI) configuration file is not encrypted.

         [EFFECT] The Lawful Intercept (LI) configuration file is not loaded
         during the boot.

         [RECOVERY] Reboot with the correct Lawful Intercept (LI) configuration
         file"
    ::= { tmnxSysNotifications 83 }

tmnxSysLicenseUpdateRequired     NOTIFICATION-TYPE
    OBJECTS     {
        tmnxHwClass
    }
    STATUS      current
    DESCRIPTION
        "[CAUSE] The tmnxSysLicenseUpdateRequired notification is generated once after
         the system boots up and the license is determined by the system to be  valid, but
         requires to be updated to the correct software version.

         [EFFECT] The system will use the license until it is updated.

         [RECOVERY] Update and activate the updated license."
    ::= { tmnxSysNotifications 84 }

tmnxEqOperStateChange            NOTIFICATION-TYPE
    OBJECTS     {
        tmnxNotifyRow,
        tmnxNotifyRowOperState,
        tmnxNotifyEntryOID,
        tmnxNotifyObjectName
    }
    STATUS      current
    DESCRIPTION
        "[CAUSE] The tmnxEqOperStateChange notification is generated when a
         change occurred in the operational state on the piece of hardware.

         [EFFECT] If the state has changed to out of service, then all ports
         and services associated with the module change to out of service and
         traffic is impacted.

         [RECOVERY] Investigation is required to determine the cause of the
         change."
    ::= { tmnxSysNotifications 85 }

stiDateAndTimeChanging           NOTIFICATION-TYPE
    OBJECTS     {
        stiDateAndTime
    }
    STATUS      current
    DESCRIPTION
        "[CAUSE] The stiDateAndTimeChanging notification is generated when the
         time on the node is explicitly set. It is raised before the time is
         changed so that the time of the change can be related to the original
         timescale. It shall be followed by the stiDateAndTimeChanged
         notification.

         [EFFECT] The time on the system is being changed.

         [RECOVERY] No recovery is necessary."
    ::= { tmnxSysNotifications 86 }

tmnxSysSwFabFailRecStarted       NOTIFICATION-TYPE
    STATUS      current
    DESCRIPTION
        "[CAUSE] The tmnxSysSwFabFailRecStarted notification is generated when
         the router has initiated an automatic switch fabric recovery process
         based on detecting frequent failures to multiple IOM/XCMs. Such
         multiple failures could be caused by issues on the SFM so this process
         involves the sequential reset of the SFMs to attempt to clear the
         cause of the failures.

         [EFFECT] The router shall operate at reduced switch fabric capacity
         while each individual SFM is reset in turn.

         [RECOVERY] This process will run until all the SFMs have been
         processed. No recovery is necessary."
    ::= { tmnxSysNotifications 87 }

tmnxSysSwFabFailRecCompleted     NOTIFICATION-TYPE
    STATUS      current
    DESCRIPTION
        "[CAUSE] The tmnxSysSwFabFailRecCompleted notification is generated
         when the automatic switch fabric recovery process has completed
         successfully.

         [EFFECT] The switch fabric has been returned to normal operation.

         [RECOVERY] No recovery is necessary."
    ::= { tmnxSysNotifications 88 }

tmnxSysSwFabFailRecAborted       NOTIFICATION-TYPE
    STATUS      current
    DESCRIPTION
        "[CAUSE] The tmnxSysSwFabFailRecAborted notification is generated when
         the automatic switch fabric recovery process was aborted.

         [EFFECT] This may have been due to a problem with one of the SFMs
         resetting and may have left the router with reduced switch fabric
         capacity.

         [RECOVERY] Check to ensure all SFMs are fully operational. For any
         SFMs that are not operational, investigate manual recovery."
    ::= { tmnxSysNotifications 89 }

tmnxSysSwFabFailRecDetected      NOTIFICATION-TYPE
    STATUS      current
    DESCRIPTION
        "[CAUSE] The tmnxSysSwFabFailRecDetected notification is generated when
         a condition has been detected within the router that might be resolved
         by the running of the automatic switch fabric recovery process.

         [EFFECT] If the automatic switch fabric recovery process is enabled
         and all the required prerequisites are met, then the recovery process
         will start. If the automatic process is enabled but the recovery does
         not start, then the prerequisite conditions should be checked to
         determine what needs to be corrected to allow the process to run.

         [RECOVERY] If the automatic switch fabric recovery process is
         disabled, then contact Nokia support to determine if it should be
         enabled for this router. Otherwise, no recovery is necessary."
    ::= { tmnxSysNotifications 90 }

mdSaveCommitHistoryFailed        NOTIFICATION-TYPE
    STATUS      current
    DESCRIPTION
        "The save commit-history failed event is generated when the saving of
         commit-history is stopped due to errors."
    ::= { tmnxSysNotifications 91 }

sbiBootMdReadCommitHistoryFailed NOTIFICATION-TYPE
    STATUS      current
    DESCRIPTION
        "The sbiBootMdReadCommitHistoryFailed notification is generated when
         loading of the commit-history file failed due to errors."
    ::= { tmnxSysNotifications 92 }

tmnxSysDyingGasp                 NOTIFICATION-TYPE
    STATUS      current
    DESCRIPTION
        "[CAUSE] The tmnxSysDyingGasp notification is sent when
         the system goes down due to power loss.  The system attempts
         to send this trap using the power remaining in the
         dying gasp capacitor.

         [EFFECT] System goes down.

         [RECOVERY] Restore power at site."
    ::= { tmnxSysNotifications 93 }

tmnxSysHttpRdrOutOfSeqLimitExc   NOTIFICATION-TYPE
    OBJECTS     {
        tmnxSysAdditionalInfo
    }
    STATUS      current
    DESCRIPTION
        "[CAUSE] The notification tmnxSysHttpRdrOutOfSeqLimitExc is sent
         when the value of the object tmnxSysHttpRdrCpmOptimizedMode
         is equal to 'true' and, for any given HTTP relay TCP connection, the
         number of
         - TCP sync packets (receive direction) or
         - TCP data packets (transmit direction)
         received out-of-sequence exceeds the limit of 10.

         [EFFECT] The out-of-sequence packets received for that connection are
         dropped.

         [RECOVERY] The root cause in the network must be found and fixed."
    ::= { tmnxSysNotifications 94 }

tmnxSysLicenseCleared            NOTIFICATION-TYPE
    OBJECTS     {
        tmnxHwClass
    }
    STATUS      current
    DESCRIPTION
        "[CAUSE] The tmnxSysLicenseCleared notification is generated each time
         a license is cleared in the system.

         [EFFECT] The system is no longer running with a license.

         [RECOVERY] No recovery."
    ::= { tmnxSysNotifications 95 }

tmnxSysLicensingStateOk          NOTIFICATION-TYPE
    OBJECTS     {
        tmnxHwClass
    }
    STATUS      current
    DESCRIPTION
        "[CAUSE] The tmnxSysLicensingStateOk notification is generated when all
         violations of licensing have been cleared.

         [EFFECT] The system no longer has outstanding license violations.

         [RECOVERY] No recovery."
    ::= { tmnxSysNotifications 96 }

tmnxSysSwDSValidationResult      NOTIFICATION-TYPE
    OBJECTS     {
        tmnxSysSwDSValidationIndex,
        tmnxSysSwDSValidationUrl,
        tmnxSysSwDSValidationState
    }
    STATUS      current
    DESCRIPTION
        "[CAUSE] The tmnxSysSwDSValidationResult notification is generated each
         time a software digital signature validation has completed.

         [EFFECT] The system may use this software if the validation was
         succussful while in fips-140 mode.

         [RECOVERY] No recovery."
    ::= { tmnxSysNotifications 97 }

tmnxSysMGNotifications           OBJECT IDENTIFIER ::= { tmnxSysMIBNotifyPrefix 1 }

END
