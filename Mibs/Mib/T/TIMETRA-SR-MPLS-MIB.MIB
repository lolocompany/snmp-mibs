TIMETRA-SR-MPLS-MIB DEFINITIONS ::= BEGIN

IMPORTS
    MODULE-COMPLIANCE, NOTIFICATION-GROUP,
    OBJECT-GROUP
                                                         FROM SNMPv2-CONF
    MODULE-IDENTITY, NOTIFICATION-TYPE,
    OBJECT-TYPE, Unsigned32
                                                         FROM SNMPv2-SMI
    DisplayString, RowStatus,
    TEXTUAL-CONVENTION, TimeStamp,
    TruthValue
                                                         FROM SNMPv2-TC
    timetraSRMIBModules, tmnxSRConfs,
    tmnxSRNotifyPrefix, tmnxSRObjs
                                                         FROM TIMETRA-GLOBAL-MIB
    vRtrID, vRtrIfIndex
                                                         FROM TIMETRA-VRTR-MIB
    ;

timetraSrMplsMIBModule           MODULE-IDENTITY
    LAST-UPDATED "202402010000Z"
    ORGANIZATION "Nokia"
    CONTACT-INFO
        "Nokia SROS Support
         Web: http://www.nokia.com"
    DESCRIPTION
        "This document is the SNMP MIB module to manage and provision the
         Segment Routing extensions for the Nokia SROS device.

         Copyright 2003-2024 Nokia. All rights reserved. Reproduction of this
         document is authorized on the condition that the foregoing copyright
         notice is included.

         This SNMP MIB module (Specification) embodies Nokia's
         proprietary intellectual property.  Nokia retains
         all title and ownership in the Specification, including any
         revisions.

         Nokia grants all interested parties a non-exclusive license to use and
         distribute an unmodified copy of this Specification in connection with
         management of Nokia products, and without fee, provided this copyright
         notice and license appear on all copies.

         This Specification is supplied 'as is', and Nokia makes no warranty,
         either express or implied, as to the use, operation, condition, or
         performance of the Specification."

    REVISION    "202402010000Z"
    DESCRIPTION
        "Rev 24.0               01 Feb 2024 00:00
         24.0 release of the TIMETRA-SR-MPLS-MIB."

    REVISION    "202102010000Z"
    DESCRIPTION
        "Rev 21.0               1 Feb 2021 00:00
         21.0 release of the TIMETRA-SR-MPLS-MIB."

    ::= { timetraSRMIBModules 130 }

TmnxSrSidOperState               ::= TEXTUAL-CONVENTION
    STATUS      current
    DESCRIPTION
        "TmnxSrSidOperState is an enumerated integer that indicates  the
         operational state of a prefix SID for an interface.

         enabled(1)   - operational up
         adminDown(2) - admin state down (i.e. no sid configured)
         failed(3)    - operational down due to failure (e.g. resource allocation failure)
         notPref(4)   - tunnel programmed, but not preferred
         ifDown(5)    - interface down
         ifFailed(6)  - interface configuration failure (e.g. interface is not a loopback)"
    SYNTAX      INTEGER {
        enabled   (1),
        adminDown (2),
        failed    (3),
        notPref   (4),
        ifDown    (5),
        ifFailed  (6)
    }

tmnxSrMplsObjs                   OBJECT IDENTIFIER ::= { tmnxSRObjs 130 }

tmnxSrMplsConfigTimeStamps       OBJECT IDENTIFIER ::= { tmnxSrMplsObjs 1 }

tmnxSrMplsPrefixSidTblLstChg     OBJECT-TYPE
    SYNTAX      TimeStamp
    MAX-ACCESS  read-only
    STATUS      current
    DESCRIPTION
        "The value of tmnxSrMplsPrefixSidTblLstChg indicates the sysUpTime at
         the time of the last modification of an entry in the
         tmnxSrMplsPrefixSidTable."
    ::= { tmnxSrMplsConfigTimeStamps 1 }

tmnxSrMplsConfigObjs             OBJECT IDENTIFIER ::= { tmnxSrMplsObjs 2 }

tmnxSrMplsPrefixSidTable         OBJECT-TYPE
    SYNTAX      SEQUENCE OF TmnxSrMplsPrefixSidEntry
    MAX-ACCESS  not-accessible
    STATUS      current
    DESCRIPTION
        "The table tmnxSrMplsPrefixSidTable contains the information pertaining
         to Segment Routing MPLS (SR-MPLS) prefix SIDs."
    ::= { tmnxSrMplsConfigObjs 1 }

tmnxSrMplsPrefixSidEntry         OBJECT-TYPE
    SYNTAX      TmnxSrMplsPrefixSidEntry
    MAX-ACCESS  not-accessible
    STATUS      current
    DESCRIPTION
        "Each conceptual row represents a SR-MPLS prefix SID for an interface
         on the virtual router in the system.

         Rows in table tmnxSrMplsPrefixSidTable are created and destroyed by
         SNMP Set operations on the object tmnxSrMplsPfxSidRowStatus"
    INDEX       {
        vRtrID,
        vRtrIfIndex
    }
    ::= { tmnxSrMplsPrefixSidTable 1 }

TmnxSrMplsPrefixSidEntry         ::= SEQUENCE
{
    tmnxSrMplsPfxSidRowStatus        RowStatus,
    tmnxSrMplsPfxSidLastChanged      TimeStamp,
    tmnxSrMplsPfxSidIpv4SidType      INTEGER,
    tmnxSrMplsPfxSidIpv4SidValue     Unsigned32,
    tmnxSrMplsPfxSidIpv6SidType      INTEGER,
    tmnxSrMplsPfxSidIpv6SidValue     Unsigned32,
    tmnxSrMplsPfxSidNodeSid          TruthValue
}

tmnxSrMplsPfxSidRowStatus        OBJECT-TYPE
    SYNTAX      RowStatus
    MAX-ACCESS  read-create
    STATUS      current
    DESCRIPTION
        "The value of the object tmnxSrMplsPfxSidRowStatus specifies the row
         status used for creation, deletion, or control of
         tmnxSrMplsPrefixSidTable entries."
    ::= { tmnxSrMplsPrefixSidEntry 1 }

tmnxSrMplsPfxSidLastChanged      OBJECT-TYPE
    SYNTAX      TimeStamp
    MAX-ACCESS  read-only
    STATUS      current
    DESCRIPTION
        "The value of the object tmnxSrMplsPfxSidLastChanged indicates the
         sysUpTime when this row was last modified."
    ::= { tmnxSrMplsPrefixSidEntry 2 }

tmnxSrMplsPfxSidIpv4SidType      OBJECT-TYPE
    SYNTAX      INTEGER {
        none  (0),
        index (1),
        label (2)
    }
    MAX-ACCESS  read-create
    STATUS      current
    DESCRIPTION
        "The value of tmnxSrMplsPfxSidIpv4SidType specifies how the value of
         tmnxSrMplsPfxSidIpv4SidValue shall be interpreted."
    DEFVAL      { none }
    ::= { tmnxSrMplsPrefixSidEntry 3 }

tmnxSrMplsPfxSidIpv4SidValue     OBJECT-TYPE
    SYNTAX      Unsigned32
    MAX-ACCESS  read-create
    STATUS      current
    DESCRIPTION
        "The value of the object tmnxSrMplsPfxSidIpv4SidValue specifies the
         IPv4 node SID label or index for the interface.

         When tmnxSrMplsPfxSidIpv4SidType is set to 'label', the label value
         must be within the range defined by
         TIMETRA-MPLS-MIB::vRtrMplsLabelSegRouteStartLabel and
         TIMETRA-MPLS-MIB::vRtrMplsLabelSegRouteEndLabel."
    DEFVAL      { 0 }
    ::= { tmnxSrMplsPrefixSidEntry 4 }

tmnxSrMplsPfxSidIpv6SidType      OBJECT-TYPE
    SYNTAX      INTEGER {
        none  (0),
        index (1),
        label (2)
    }
    MAX-ACCESS  read-create
    STATUS      current
    DESCRIPTION
        "The value of tmnxSrMplsPfxSidIpv6SidType specifies how the value of
         tmnxSrMplsPfxSidIpv6SidValue shall be interpreted."
    DEFVAL      { none }
    ::= { tmnxSrMplsPrefixSidEntry 5 }

tmnxSrMplsPfxSidIpv6SidValue     OBJECT-TYPE
    SYNTAX      Unsigned32
    MAX-ACCESS  read-create
    STATUS      current
    DESCRIPTION
        "The value of the object tmnxSrMplsPfxSidIpv6SidValue specifies the
         IPv6 node SID label or index for the interface.

         When tmnxSrMplsPfxSidIpv6SidType is set to 'label', the label value
         must be within the range defined by
         TIMETRA-MPLS-MIB::vRtrMplsLabelSegRouteStartLabel and
         TIMETRA-MPLS-MIB::vRtrMplsLabelSegRouteEndLabel."
    DEFVAL      { 0 }
    ::= { tmnxSrMplsPrefixSidEntry 6 }

tmnxSrMplsPfxSidNodeSid          OBJECT-TYPE
    SYNTAX      TruthValue
    MAX-ACCESS  read-create
    STATUS      current
    DESCRIPTION
        "The value of the object tmnxSrMplsPfxSidNodeSid specifies whether
         node-sid flag (N-flag) should be set in the prefix SID sub-TLV for the
         interface.

         When the value of tmnxSrMplsPfxSidNodeSid is true, the prefix SID
         sub-TLV for the prefix of a loopback interface is tagged as a node SID
         meaning that it belongs to this node only.

         When the value of tmnxSrMplsPfxSidNodeSid is false, the same prefix
         SID sub-TLV may be advertised by multiple nodes."
    DEFVAL      { true }
    ::= { tmnxSrMplsPrefixSidEntry 7 }

tmnxSrMplsStatsObjs              OBJECT IDENTIFIER ::= { tmnxSrMplsObjs 3 }

tmnxSrMplsPrefixSidStatusTable   OBJECT-TYPE
    SYNTAX      SEQUENCE OF TmnxSrMplsPrefixSidStatusEntry
    MAX-ACCESS  not-accessible
    STATUS      current
    DESCRIPTION
        "The table tmnxSrMplsPrefixSidStatusTable provides an extension of the
         tmnxSrMplsPrefixSidTable for SR-MPLS prefix SID statuses."
    ::= { tmnxSrMplsStatsObjs 1 }

tmnxSrMplsPrefixSidStatusEntry   OBJECT-TYPE
    SYNTAX      TmnxSrMplsPrefixSidStatusEntry
    MAX-ACCESS  not-accessible
    STATUS      current
    DESCRIPTION
        "Each conceptual row represents additional columns for status objects
         for a SR-MPLS prefix SID on an interface.

         The system automatically creates and destroys rows in this table when
         rows in the tmnxSrMplsPrefixSidTable are created and destroyed."
    AUGMENTS    { tmnxSrMplsPrefixSidEntry }
    ::= { tmnxSrMplsPrefixSidStatusTable 1 }

TmnxSrMplsPrefixSidStatusEntry   ::= SEQUENCE
{
    tmnxSrMplsPfxSidIpv4SidOperState TmnxSrSidOperState,
    tmnxSrMplsPfxSidIpv6SidOperState TmnxSrSidOperState
}

tmnxSrMplsPfxSidIpv4SidOperState OBJECT-TYPE
    SYNTAX      TmnxSrSidOperState
    MAX-ACCESS  read-only
    STATUS      current
    DESCRIPTION
        "The value of tmnxSrMplsPfxSidIpv4SidOperState indicates the
         operational state of the IPv4 SID prefix for the interface."
    ::= { tmnxSrMplsPrefixSidStatusEntry 1 }

tmnxSrMplsPfxSidIpv6SidOperState OBJECT-TYPE
    SYNTAX      TmnxSrSidOperState
    MAX-ACCESS  read-only
    STATUS      current
    DESCRIPTION
        "The value of tmnxSrMplsPfxSidIpv6SidOperState indicates the
         operational state of the IPv6 SID prefix for the interface."
    ::= { tmnxSrMplsPrefixSidStatusEntry 2 }

tmnxSrMplsNotificationObjs       OBJECT IDENTIFIER ::= { tmnxSrMplsObjs 4 }

tmnxSrMplsNotifyDescription      OBJECT-TYPE
    SYNTAX      DisplayString
    MAX-ACCESS  accessible-for-notify
    STATUS      current
    DESCRIPTION
        "The object tmnxSrMplsNotifyDescription is a printable character
         string."
    ::= { tmnxSrMplsNotificationObjs 1 }

tmnxSrMplsConformance            OBJECT IDENTIFIER ::= { tmnxSRConfs 130 }

tmnxSrMplsCompliances            OBJECT IDENTIFIER ::= { tmnxSrMplsConformance 1 }

tmnxSrMplsCompliance             MODULE-COMPLIANCE
    STATUS      current
    DESCRIPTION
        "The compliance statement for management of segment routing (SR) MPLS
         on Nokia SROS series systems 21.0 Release."
    MODULE
        MANDATORY-GROUPS {
            tmnxSrMplsGroup
        }
    ::= { tmnxSrMplsCompliances 1 }

tmnxSrMplsNotifyCompliance       MODULE-COMPLIANCE
    STATUS      current
    DESCRIPTION
        "The compliance statement for management of segment routing (SR) MPLS
         notifications on Nokia SROS series systems."
    MODULE
        MANDATORY-GROUPS {
            tmnxSrMplsNotificationGroup
        }
    ::= { tmnxSrMplsCompliances 2 }

tmnxSrMplsGroups                 OBJECT IDENTIFIER ::= { tmnxSrMplsConformance 2 }

tmnxSrMplsGroup                  OBJECT-GROUP
    OBJECTS     {
        tmnxSrMplsPrefixSidTblLstChg,
        tmnxSrMplsPfxSidRowStatus,
        tmnxSrMplsPfxSidLastChanged,
        tmnxSrMplsPfxSidIpv4SidType,
        tmnxSrMplsPfxSidIpv4SidValue,
        tmnxSrMplsPfxSidIpv6SidType,
        tmnxSrMplsPfxSidIpv6SidValue,
        tmnxSrMplsPfxSidNodeSid,
        tmnxSrMplsPfxSidIpv4SidOperState,
        tmnxSrMplsPfxSidIpv6SidOperState
    }
    STATUS      current
    DESCRIPTION
        "The group of objects in segment routing system  for MPLS on Nokia SROS
         series systems."
    ::= { tmnxSrMplsGroups 1 }

tmnxSrMplsNotifyObjsGroup        OBJECT-GROUP
    OBJECTS     {
        tmnxSrMplsNotifyDescription
    }
    STATUS      current
    DESCRIPTION
        "The group of notify objects supporting management of  segment routing
         MPLS on Nokia SROS series systems."
    ::= { tmnxSrMplsGroups 2 }

tmnxSrMplsNotificationGroup      NOTIFICATION-GROUP
    NOTIFICATIONS {
        tmnxSrMplsPfxSidFailure
    }
    STATUS      current
    DESCRIPTION
        "The group of objects supporting segment routing MPLS notifications on
         Nokia SROS series systems."
    ::= { tmnxSrMplsGroups 3 }

tmnxSrMplsNotifyPrefix           OBJECT IDENTIFIER ::= { tmnxSRNotifyPrefix 130 }

tmnxSrNotifications              OBJECT IDENTIFIER ::= { tmnxSrMplsNotifyPrefix 0 }

tmnxSrMplsPfxSidFailure          NOTIFICATION-TYPE
    OBJECTS     {
        tmnxSrMplsPfxSidLastChanged,
        tmnxSrMplsNotifyDescription
    }
    STATUS      current
    DESCRIPTION
        "[CAUSE] This notification is generated when the system cannot program
         the prefix SID due to conflicting configuration of the interface, a
         duplicate SID or system exhaustion.

         [EFFECT] The Segment Routing tunnel will not be programmed and will
         not be advertised by other protocols

         [RECOVERY] In case of system exhaustion, the system will periodically
         retry. In case of interface configuration conflict or duplicate, the
         parameters need to be corrected."
    ::= { tmnxSrNotifications 1 }

END
