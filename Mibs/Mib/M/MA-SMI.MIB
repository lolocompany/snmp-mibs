-- --------------------------------------------------------------------------
-- STRUCTURE OF MANAGEMENT INFORMATION (SMI)
-- --------------------------------------------------------------------------
--
-- Document Number:
-- 1/207 14-BYN 101 Oen
--
-- Revision:
-- A
--
-- Date:
-- 2002-07-22
--
-- Author:
-- Jonas Andersson 
--
-- Approved:
-- Lars Kari 
--
-- Document Class:
-- Restricted External
--
-- Document Type:
-- MANAGEMENT INFO BASE
--
-- Abstract: 
-- This document defines the top level of the managed objects in MIBs for 
-- MobileArts products.
--
-- Revision Information:
-- This is the first issue of STRUCTURE OF MANAGEMENT INFORMATION (SMI)
-- --------------------------------------------------------------------------

MA-SMI DEFINITIONS ::= BEGIN


IMPORTS
    enterprises           FROM RFC1155-SMI
    ;

mobilearts           OBJECT IDENTIFIER ::= { enterprises 11264 }


END
