OneAccess-R1646v2-4676-LacpB DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1646Rootv2 MODULE-IDENTITY
   LAST-UPDATED "202107151728Z"
   ORGANIZATION "OneAccess"
   CONTACT-INFO "http://www.oneaccess-net.com/telindus/"
   DESCRIPTION
      "..."
   ::= {telindus 1132}




r1646v2LacpB OBJECT IDENTIFIER ::= {r1646Rootv2 4676}

r1646v2LacpBMOProp OBJECT-TYPE
   SYNTAX      SEQUENCE OF R1646v2LacpBMOPropEntry
   MAX-ACCESS  not-accessible
   STATUS      current
   DESCRIPTION
      ""
   ::= {r1646v2LacpB 1}

r1646v2LacpBMOPropEntry OBJECT-TYPE
   SYNTAX      R1646v2LacpBMOPropEntry
   MAX-ACCESS  not-accessible
   STATUS      current
   DESCRIPTION
      ""
   INDEX      { r1646v2LacpBMOPropGlobalIx }
   ::= {r1646v2LacpBMOProp 1}

R1646v2LacpBMOPropEntry ::=
   SEQUENCE
      {
      r1646v2LacpBMOPropPath
         ContainmentPath,
      r1646v2LacpBMOPropRev
         ObjectRevision,
      r1646v2LacpBMOPropGlobalIx
         GlobalIndex
      }

r1646v2LacpBMOPropPath OBJECT-TYPE
   SYNTAX      ContainmentPath
   MAX-ACCESS  read-only
   STATUS      current
   DESCRIPTION
      "Textual description of the containment tree from the instance of
       the root object down to the instance of the current object."
   ::= {r1646v2LacpBMOPropEntry 3}

r1646v2LacpBMOPropRev OBJECT-TYPE
   SYNTAX      ObjectRevision
   MAX-ACCESS  read-only
   STATUS      current
   DESCRIPTION
      "This value corresponds with the revision of the MANAGED OBJECT."
   ::= {r1646v2LacpBMOPropEntry 4}

r1646v2LacpBMOPropGlobalIx OBJECT-TYPE
   SYNTAX      GlobalIndex
   MAX-ACCESS  read-only
   STATUS      current
   DESCRIPTION
      "The value of the tlsCntTreeGlobalIndex of the MANAGED OBJECT."
   ::= {r1646v2LacpBMOPropEntry 10}



er1646v2LacpB OBJECT IDENTIFIER ::= {r1646v2LacpB 11}


er1646v2LacpBRemark OBJECT IDENTIFIER ::= {er1646v2LacpB 321}

er1646v2LacpBRemarkTable OBJECT-TYPE
   SYNTAX      SEQUENCE OF Er1646v2LacpBRemarkEntry
   MAX-ACCESS  not-accessible
   STATUS      current
   DESCRIPTION
      "intfRemark"
   ::= {er1646v2LacpBRemark 1}

er1646v2LacpBRemarkEntry OBJECT-TYPE
   SYNTAX      Er1646v2LacpBRemarkEntry
   MAX-ACCESS  not-accessible
   STATUS      current
   DESCRIPTION
      ""
   INDEX      { er1646v2LacpBRemarkGlobalIx }
   ::= {er1646v2LacpBRemarkTable 1}

Er1646v2LacpBRemarkEntry ::=
   SEQUENCE
      {
      er1646v2LacpBRemarkGlobalIx
         GlobalIndex,
      er1646v2LacpBRemarkValue
         DisplayString
      }

er1646v2LacpBRemarkGlobalIx OBJECT-TYPE
   SYNTAX      GlobalIndex
   MAX-ACCESS  not-accessible
   STATUS      current
   DESCRIPTION
      "The value of the tlsCntTreeGlobalIndex of the MANAGED OBJECT."
   ::= {er1646v2LacpBRemarkEntry 10}

er1646v2LacpBRemarkValue OBJECT-TYPE
   SYNTAX      DisplayString
   MAX-ACCESS  read-write
   STATUS      current
   DESCRIPTION
      "Path: lacpBundle.editConf.remark"
   ::= {er1646v2LacpBRemarkEntry 2147483648}


er1646v2LacpBArp OBJECT IDENTIFIER ::= {er1646v2LacpB 19}

er1646v2LacpBArpSSCTable OBJECT-TYPE
   SYNTAX      SEQUENCE OF Er1646v2LacpBArpEntry
   MAX-ACCESS  not-accessible
   STATUS      current
   DESCRIPTION
      "ethernet related config parameters"
   ::= {er1646v2LacpBArp 1}

er1646v2LacpBArpEntry OBJECT-TYPE
   SYNTAX      Er1646v2LacpBArpEntry
   MAX-ACCESS  not-accessible
   STATUS      current
   DESCRIPTION
      ""
   INDEX      { er1646v2LacpBArpGlobalIx }
   ::= {er1646v2LacpBArpSSCTable 1}

Er1646v2LacpBArpEntry ::=
   SEQUENCE
      {
      er1646v2LacpBArpGlobalIx
         GlobalIndex,
      er1646v2LacpBArpTimeOut
         TimeTicks,
      er1646v2LacpBArpProxyArp
         INTEGER
      }

er1646v2LacpBArpGlobalIx OBJECT-TYPE
   SYNTAX      GlobalIndex
   MAX-ACCESS  not-accessible
   STATUS      current
   DESCRIPTION
      "The value of the tlsCntTreeGlobalIndex of the MANAGED OBJECT."
   ::= {er1646v2LacpBArpEntry 10}

er1646v2LacpBArpTimeOut OBJECT-TYPE
   SYNTAX      TimeTicks
   MAX-ACCESS  read-write
   STATUS      current
   DESCRIPTION
      "Path: lacpBundle.editConf.arp.timeOut

       Time in centi-second."
   ::= {er1646v2LacpBArpEntry 201326592}

er1646v2LacpBArpProxyArp OBJECT-TYPE
   SYNTAX      INTEGER
               {
               disabled (0),
               enabled (1)
               }
   MAX-ACCESS  read-write
   STATUS      current
   DESCRIPTION
      "Path: lacpBundle.editConf.arp.proxyArp

       Possibilities:
               disabled   (0)
               enabled   (1)"
   ::= {er1646v2LacpBArpEntry 838860800}

er1646v2LacpBArpStaticArp OBJECT-TYPE
   SYNTAX      SEQUENCE OF Er1646v2LacpBArpStaticArpEntry
   MAX-ACCESS  not-accessible
   STATUS      current
   DESCRIPTION
      ""
   ::= {er1646v2LacpBArp 50331648}

er1646v2LacpBArpStaticArpEntry OBJECT-TYPE
   SYNTAX      Er1646v2LacpBArpStaticArpEntry
   MAX-ACCESS  not-accessible
   STATUS      current
   DESCRIPTION
      ""
   INDEX      { er1646v2LacpBArpStaticArpGlobalIx,
                er1646v2LacpBArpStaticArpTableIx }
   ::= {er1646v2LacpBArpStaticArp 1}

Er1646v2LacpBArpStaticArpEntry ::=
   SEQUENCE
      {
      er1646v2LacpBArpStaticArpActions
         VariableLengthTableActions,
      er1646v2LacpBArpStaticArpGlobalIx
         GlobalIndex,
      er1646v2LacpBArpStaticArpTableIx
         TableIndex,
      er1646v2LacpBArpStaticArpMacAddress
         OCTET STRING,
      er1646v2LacpBArpStaticArpIpAddress
         IpAddress
      }

er1646v2LacpBArpStaticArpActions OBJECT-TYPE
   SYNTAX      VariableLengthTableActions
   MAX-ACCESS  read-write
   STATUS      current
   DESCRIPTION
      "By way of this field, some manipulations
       on this table may be performed."
   ::= {er1646v2LacpBArpStaticArpEntry 2}

er1646v2LacpBArpStaticArpGlobalIx OBJECT-TYPE
   SYNTAX      GlobalIndex
   MAX-ACCESS  not-accessible
   STATUS      current
   DESCRIPTION
      "The value of the tlsCntTreeGlobalIndex of the MANAGED OBJECT."
   ::= {er1646v2LacpBArpStaticArpEntry 10}

er1646v2LacpBArpStaticArpTableIx OBJECT-TYPE
   SYNTAX      TableIndex
   MAX-ACCESS  not-accessible
   STATUS      current
   DESCRIPTION
      ""
   ::= {er1646v2LacpBArpStaticArpEntry 11}

er1646v2LacpBArpStaticArpMacAddress OBJECT-TYPE
   SYNTAX      OCTET STRING
   MAX-ACCESS  read-write
   STATUS      current
   DESCRIPTION
      "Path: lacpBundle.editConf.arp.staticArp.macAddress

       MAC address."
   ::= {er1646v2LacpBArpStaticArpEntry 16777216}

er1646v2LacpBArpStaticArpIpAddress OBJECT-TYPE
   SYNTAX      IpAddress
   MAX-ACCESS  read-write
   STATUS      current
   DESCRIPTION
      "Path: lacpBundle.editConf.arp.staticArp.ipAddress"
   ::= {er1646v2LacpBArpStaticArpEntry 33554432}


er1646v2LacpBBrC OBJECT IDENTIFIER ::= {er1646v2LacpB 27}

er1646v2LacpBBrCSSCTable OBJECT-TYPE
   SYNTAX      SEQUENCE OF Er1646v2LacpBBrCEntry
   MAX-ACCESS  not-accessible
   STATUS      current
   DESCRIPTION
      "Set bridging parameters"
   ::= {er1646v2LacpBBrC 1}

er1646v2LacpBBrCEntry OBJECT-TYPE
   SYNTAX      Er1646v2LacpBBrCEntry
   MAX-ACCESS  not-accessible
   STATUS      current
   DESCRIPTION
      ""
   INDEX      { er1646v2LacpBBrCGlobalIx }
   ::= {er1646v2LacpBBrCSSCTable 1}

Er1646v2LacpBBrCEntry ::=
   SEQUENCE
      {
      er1646v2LacpBBrCGlobalIx
         GlobalIndex,
      er1646v2LacpBBrCAccessList
         DisplayString,
      er1646v2LacpBBrCInAccessList
         DisplayString,
      er1646v2LacpBBrCTp
         DisplayString,
      er1646v2LacpBBrCBridgeGroup
         DisplayString,
      er1646v2LacpBBrCLimBC
         INTEGER,
      er1646v2LacpBBrCPrivateMode
         INTEGER,
      er1646v2LacpBBrCLearning
         INTEGER,
      er1646v2LacpBBrCMaxCacheSize
         INTEGER,
      er1646v2LacpBBrCRelearnDropOnRelearn
         INTEGER,
      er1646v2LacpBBrCRelearnShutdownThreshold
         Integer32,
      er1646v2LacpBBrCRelearnShutdownTime
         TimeTicks,
      er1646v2LacpBBrCRelearnLoopDetection
         INTEGER,
      er1646v2LacpBBrCRelearnLoopDetectionInterval
         TimeTicks,
      er1646v2LacpBBrCVlanMemberShip
         INTEGER,
      er1646v2LacpBBrCDot1adType
         INTEGER,
      er1646v2LacpBBrCPriority
         Integer32,
      er1646v2LacpBBrCPathCost
         Integer32,
      er1646v2LacpBBrCInternalPathCost
         Integer32,
      er1646v2LacpBBrCTCD
         INTEGER,
      er1646v2LacpBBrCRestrictedRole
         INTEGER,
      er1646v2LacpBBrCAdminEdge
         INTEGER,
      er1646v2LacpBBrCMgmtInline
         INTEGER,
      er1646v2LacpBBrCL2ptMode
         INTEGER,
      er1646v2LacpBBrCL2ptProtocols
         Integer32,
      er1646v2LacpBBrCL2ptDestMac
         OCTET STRING,
      er1646v2LacpBBrCL2ptCos
         INTEGER,
      er1646v2LacpBBrCL2ptDropThrStp
         INTEGER,
      er1646v2LacpBBrCL2ptDropThrLldp
         INTEGER,
      er1646v2LacpBBrCL2ptDropThrOam
         INTEGER,
      er1646v2LacpBBrCL2ptDropThrCdp
         INTEGER,
      er1646v2LacpBBrCL2ptDropThrVtp
         INTEGER,
      er1646v2LacpBBrCL2ptDropThrLacp
         INTEGER,
      er1646v2LacpBBrCL2ptDropThrEfmOam
         INTEGER,
      er1646v2LacpBBrCL2ptDropThrPvst
         INTEGER,
      er1646v2LacpBBrCL2ptDropThrMmrp
         INTEGER,
      er1646v2LacpBBrCL2ptDropThrMvrp
         INTEGER,
      er1646v2LacpBBrCL2ptDropThrGvrp
         INTEGER,
      er1646v2LacpBBrCL2ptDropThrGmrp
         INTEGER,
      er1646v2LacpBBrCL2ptDropThrDtp
         INTEGER,
      er1646v2LacpBBrCL2ptDropThrPagp
         INTEGER,
      er1646v2LacpBBrCL2ptDropThrUdld
         INTEGER
      }

er1646v2LacpBBrCGlobalIx OBJECT-TYPE
   SYNTAX      GlobalIndex
   MAX-ACCESS  not-accessible
   STATUS      current
   DESCRIPTION
      "The value of the tlsCntTreeGlobalIndex of the MANAGED OBJECT."
   ::= {er1646v2LacpBBrCEntry 10}

er1646v2LacpBBrCAccessList OBJECT-TYPE
   SYNTAX      DisplayString
   MAX-ACCESS  read-write
   STATUS      current
   DESCRIPTION
      "Path: lacpBundle.editConf.bridging.accessList"
   ::= {er1646v2LacpBBrCEntry 83886080}

er1646v2LacpBBrCInAccessList OBJECT-TYPE
   SYNTAX      DisplayString
   MAX-ACCESS  read-write
   STATUS      current
   DESCRIPTION
      "Path: lacpBundle.editConf.bridging.inAccessList"
   ::= {er1646v2LacpBBrCEntry 251658240}

er1646v2LacpBBrCTp OBJECT-TYPE
   SYNTAX      DisplayString
   MAX-ACCESS  read-write
   STATUS      current
   DESCRIPTION
      "Path: lacpBundle.editConf.bridging.trafficPolicy"
   ::= {er1646v2LacpBBrCEntry 100663296}

er1646v2LacpBBrCBridgeGroup OBJECT-TYPE
   SYNTAX      DisplayString
   MAX-ACCESS  read-write
   STATUS      current
   DESCRIPTION
      "Path: lacpBundle.editConf.bridging.bridgeGroup"
   ::= {er1646v2LacpBBrCEntry 117440512}

er1646v2LacpBBrCLimBC OBJECT-TYPE
   SYNTAX      INTEGER
               {
               disabled (0),
               enabled (1)
               }
   MAX-ACCESS  read-write
   STATUS      current
   DESCRIPTION
      "Path: lacpBundle.editConf.bridging.limitBroadcasts

       Possibilities:
               disabled   (0)
               enabled   (1)"
   ::= {er1646v2LacpBBrCEntry 134217728}

er1646v2LacpBBrCPrivateMode OBJECT-TYPE
   SYNTAX      INTEGER
               {
               disabled (0),
               enabled (1)
               }
   MAX-ACCESS  read-write
   STATUS      current
   DESCRIPTION
      "Path: lacpBundle.editConf.bridging.privateMode

       Possibilities:
               disabled   (0)
               enabled   (1)"
   ::= {er1646v2LacpBBrCEntry 419430400}

er1646v2LacpBBrCLearning OBJECT-TYPE
   SYNTAX      INTEGER
               {
               disabled (0),
               enabled (1)
               }
   MAX-ACCESS  read-write
   STATUS      current
   DESCRIPTION
      "Path: lacpBundle.editConf.bridging.learning

       Possibilities:
               disabled   (0)
               enabled   (1)"
   ::= {er1646v2LacpBBrCEntry 201326592}

er1646v2LacpBBrCMaxCacheSize OBJECT-TYPE
   SYNTAX      INTEGER
               {
               unlimited (0)
               }
   MAX-ACCESS  read-write
   STATUS      current
   DESCRIPTION
      "Path: lacpBundle.editConf.bridging.maxCacheSize

       Possibilities:
               unlimited   (0)"
   ::= {er1646v2LacpBBrCEntry 218103808}

er1646v2LacpBBrCRelearnDropOnRelearn OBJECT-TYPE
   SYNTAX      INTEGER
               {
               disabled (0),
               enabled (1)
               }
   MAX-ACCESS  read-write
   STATUS      current
   DESCRIPTION
      "Path: lacpBundle.editConf.bridging.relearn.dropOnRelearn

       Possibilities:
               disabled   (0)
               enabled   (1)"
   ::= {er1646v2LacpBBrCEntry 234946560}

er1646v2LacpBBrCRelearnShutdownThreshold OBJECT-TYPE
   SYNTAX      Integer32
   MAX-ACCESS  read-write
   STATUS      current
   DESCRIPTION
      "Path: lacpBundle.editConf.bridging.relearn.shutdownThreshold"
   ::= {er1646v2LacpBBrCEntry 235012096}

er1646v2LacpBBrCRelearnShutdownTime OBJECT-TYPE
   SYNTAX      TimeTicks
   MAX-ACCESS  read-write
   STATUS      current
   DESCRIPTION
      "Path: lacpBundle.editConf.bridging.relearn.shutdownTime

       Time in centi-second."
   ::= {er1646v2LacpBBrCEntry 235077632}

er1646v2LacpBBrCRelearnLoopDetection OBJECT-TYPE
   SYNTAX      INTEGER
               {
               disabled (0),
               passive (1),
               active (2)
               }
   MAX-ACCESS  read-write
   STATUS      current
   DESCRIPTION
      "Path: lacpBundle.editConf.bridging.relearn.loopDetection

       Possibilities:
               disabled   (0)
               passive   (1)
               active   (2)"
   ::= {er1646v2LacpBBrCEntry 235143168}

er1646v2LacpBBrCRelearnLoopDetectionInterval OBJECT-TYPE
   SYNTAX      TimeTicks
   MAX-ACCESS  read-write
   STATUS      current
   DESCRIPTION
      "Path: lacpBundle.editConf.bridging.relearn.loopDetectionInterval

       Time in centi-second."
   ::= {er1646v2LacpBBrCEntry 235208704}

er1646v2LacpBBrCVlanMemberShip OBJECT-TYPE
   SYNTAX      INTEGER
               {
               all (0),
               none (1),
               grouped (2)
               }
   MAX-ACCESS  read-write
   STATUS      current
   DESCRIPTION
      "Path: lacpBundle.editConf.bridging.vlanMemberShip

       Possibilities:
               all   (0)
               none   (1)
               grouped   (2)"
   ::= {er1646v2LacpBBrCEntry 318767104}

er1646v2LacpBBrCDot1adType OBJECT-TYPE
   SYNTAX      INTEGER
               {
               slOPTg (0),
               cPort (4),
               sPort (1),
               nni (2)
               }
   MAX-ACCESS  read-write
   STATUS      current
   DESCRIPTION
      "Path: lacpBundle.editConf.bridging.dot1ad.type

       Possibilities:
               <OPT>   (0)
               cPort   (4)
               sPort   (1)
               nni   (2)"
   ::= {er1646v2LacpBBrCEntry 503382016}

er1646v2LacpBBrCPriority OBJECT-TYPE
   SYNTAX      Integer32
   MAX-ACCESS  read-write
   STATUS      current
   DESCRIPTION
      "Path: lacpBundle.editConf.bridging.priority"
   ::= {er1646v2LacpBBrCEntry 33554432}

er1646v2LacpBBrCPathCost OBJECT-TYPE
   SYNTAX      Integer32
   MAX-ACCESS  read-write
   STATUS      current
   DESCRIPTION
      "Path: lacpBundle.editConf.bridging.pathCost"
   ::= {er1646v2LacpBBrCEntry 50331648}

er1646v2LacpBBrCInternalPathCost OBJECT-TYPE
   SYNTAX      Integer32
   MAX-ACCESS  read-write
   STATUS      current
   DESCRIPTION
      "Path: lacpBundle.editConf.bridging.internalPathCost"
   ::= {er1646v2LacpBBrCEntry 301989888}

er1646v2LacpBBrCTCD OBJECT-TYPE
   SYNTAX      INTEGER
               {
               disabled (0),
               enabled (1)
               }
   MAX-ACCESS  read-write
   STATUS      current
   DESCRIPTION
      "Path: lacpBundle.editConf.bridging.topologyChangeDetection

       Possibilities:
               disabled   (0)
               enabled   (1)"
   ::= {er1646v2LacpBBrCEntry 67108864}

er1646v2LacpBBrCRestrictedRole OBJECT-TYPE
   SYNTAX      INTEGER
               {
               disabled (0),
               enabled (1)
               }
   MAX-ACCESS  read-write
   STATUS      current
   DESCRIPTION
      "Path: lacpBundle.editConf.bridging.restrictedRole

       Possibilities:
               disabled   (0)
               enabled   (1)"
   ::= {er1646v2LacpBBrCEntry 335544320}

er1646v2LacpBBrCAdminEdge OBJECT-TYPE
   SYNTAX      INTEGER
               {
               disabled (0),
               enabled (1)
               }
   MAX-ACCESS  read-write
   STATUS      current
   DESCRIPTION
      "Path: lacpBundle.editConf.bridging.adminEdge

       Possibilities:
               disabled   (0)
               enabled   (1)"
   ::= {er1646v2LacpBBrCEntry 268435456}

er1646v2LacpBBrCMgmtInline OBJECT-TYPE
   SYNTAX      INTEGER
               {
               disabled (0),
               enabled (1)
               }
   MAX-ACCESS  read-write
   STATUS      current
   DESCRIPTION
      "Path: lacpBundle.editConf.bridging.mgmtInline

       Possibilities:
               disabled   (0)
               enabled   (1)"
   ::= {er1646v2LacpBBrCEntry 369098752}

er1646v2LacpBBrCL2ptMode OBJECT-TYPE
   SYNTAX      INTEGER
               {
               disabled (0),
               enabled (1)
               }
   MAX-ACCESS  read-write
   STATUS      current
   DESCRIPTION
      "Path: lacpBundle.editConf.bridging.l2ProtTunnel.mode

       Possibilities:
               disabled   (0)
               enabled   (1)"
   ::= {er1646v2LacpBBrCEntry 403701760}

er1646v2LacpBBrCL2ptProtocols OBJECT-TYPE
   SYNTAX      Integer32
   MAX-ACCESS  read-write
   STATUS      current
   DESCRIPTION
      "Path: lacpBundle.editConf.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1646v2LacpBBrCEntry 404750336}

er1646v2LacpBBrCL2ptDestMac OBJECT-TYPE
   SYNTAX      OCTET STRING
   MAX-ACCESS  read-write
   STATUS      current
   DESCRIPTION
      "Path: lacpBundle.editConf.bridging.l2ProtTunnel.destinationMac

       MAC address."
   ::= {er1646v2LacpBBrCEntry 405798912}

er1646v2LacpBBrCL2ptCos OBJECT-TYPE
   SYNTAX      INTEGER
               {
               unchanged (255)
               }
   MAX-ACCESS  read-write
   STATUS      current
   DESCRIPTION
      "Path: lacpBundle.editConf.bridging.l2ProtTunnel.cos

       Possibilities:
               unchanged   (255)"
   ::= {er1646v2LacpBBrCEntry 406847488}

er1646v2LacpBBrCL2ptDropThrStp OBJECT-TYPE
   SYNTAX      INTEGER
               {
               unlimited (0)
               }
   UNITS       "packets/sec"
   MAX-ACCESS  read-write
   STATUS      current
   DESCRIPTION
      "Path: lacpBundle.editConf.bridging.l2ProtTunnel.dropThresholds.stp

       unit name = packets/sec

       Possibilities:
               unlimited   (0)"
   ::= {er1646v2LacpBBrCEntry 407900160}

er1646v2LacpBBrCL2ptDropThrLldp OBJECT-TYPE
   SYNTAX      INTEGER
               {
               unlimited (0)
               }
   UNITS       "packets/sec"
   MAX-ACCESS  read-write
   STATUS      current
   DESCRIPTION
      "Path: lacpBundle.editConf.bridging.l2ProtTunnel.dropThresholds.lldp

       unit name = packets/sec

       Possibilities:
               unlimited   (0)"
   ::= {er1646v2LacpBBrCEntry 407904256}

er1646v2LacpBBrCL2ptDropThrOam OBJECT-TYPE
   SYNTAX      INTEGER
               {
               unlimited (0)
               }
   UNITS       "packets/sec"
   MAX-ACCESS  read-write
   STATUS      current
   DESCRIPTION
      "Path: lacpBundle.editConf.bridging.l2ProtTunnel.dropThresholds.oam

       unit name = packets/sec

       Possibilities:
               unlimited   (0)"
   ::= {er1646v2LacpBBrCEntry 407908352}

er1646v2LacpBBrCL2ptDropThrCdp OBJECT-TYPE
   SYNTAX      INTEGER
               {
               unlimited (0)
               }
   UNITS       "packets/sec"
   MAX-ACCESS  read-write
   STATUS      current
   DESCRIPTION
      "Path: lacpBundle.editConf.bridging.l2ProtTunnel.dropThresholds.cdp

       unit name = packets/sec

       Possibilities:
               unlimited   (0)"
   ::= {er1646v2LacpBBrCEntry 407912448}

er1646v2LacpBBrCL2ptDropThrVtp OBJECT-TYPE
   SYNTAX      INTEGER
               {
               unlimited (0)
               }
   UNITS       "packets/sec"
   MAX-ACCESS  read-write
   STATUS      current
   DESCRIPTION
      "Path: lacpBundle.editConf.bridging.l2ProtTunnel.dropThresholds.vtp

       unit name = packets/sec

       Possibilities:
               unlimited   (0)"
   ::= {er1646v2LacpBBrCEntry 407916544}

er1646v2LacpBBrCL2ptDropThrLacp OBJECT-TYPE
   SYNTAX      INTEGER
               {
               unlimited (0)
               }
   UNITS       "packets/sec"
   MAX-ACCESS  read-write
   STATUS      current
   DESCRIPTION
      "Path: lacpBundle.editConf.bridging.l2ProtTunnel.dropThresholds.lacp

       unit name = packets/sec

       Possibilities:
               unlimited   (0)"
   ::= {er1646v2LacpBBrCEntry 407920640}

er1646v2LacpBBrCL2ptDropThrEfmOam OBJECT-TYPE
   SYNTAX      INTEGER
               {
               unlimited (0)
               }
   UNITS       "packets/sec"
   MAX-ACCESS  read-write
   STATUS      current
   DESCRIPTION
      "Path: lacpBundle.editConf.bridging.l2ProtTunnel.dropThresholds.efmOam

       unit name = packets/sec

       Possibilities:
               unlimited   (0)"
   ::= {er1646v2LacpBBrCEntry 407924736}

er1646v2LacpBBrCL2ptDropThrPvst OBJECT-TYPE
   SYNTAX      INTEGER
               {
               unlimited (0)
               }
   UNITS       "packets/sec"
   MAX-ACCESS  read-write
   STATUS      current
   DESCRIPTION
      "Path: lacpBundle.editConf.bridging.l2ProtTunnel.dropThresholds.pvst

       unit name = packets/sec

       Possibilities:
               unlimited   (0)"
   ::= {er1646v2LacpBBrCEntry 407928832}

er1646v2LacpBBrCL2ptDropThrMmrp OBJECT-TYPE
   SYNTAX      INTEGER
               {
               unlimited (0)
               }
   UNITS       "packets/sec"
   MAX-ACCESS  read-write
   STATUS      current
   DESCRIPTION
      "Path: lacpBundle.editConf.bridging.l2ProtTunnel.dropThresholds.mmrp

       unit name = packets/sec

       Possibilities:
               unlimited   (0)"
   ::= {er1646v2LacpBBrCEntry 407932928}

er1646v2LacpBBrCL2ptDropThrMvrp OBJECT-TYPE
   SYNTAX      INTEGER
               {
               unlimited (0)
               }
   UNITS       "packets/sec"
   MAX-ACCESS  read-write
   STATUS      current
   DESCRIPTION
      "Path: lacpBundle.editConf.bridging.l2ProtTunnel.dropThresholds.mvrp

       unit name = packets/sec

       Possibilities:
               unlimited   (0)"
   ::= {er1646v2LacpBBrCEntry 407937024}

er1646v2LacpBBrCL2ptDropThrGvrp OBJECT-TYPE
   SYNTAX      INTEGER
               {
               unlimited (0)
               }
   UNITS       "packets/sec"
   MAX-ACCESS  read-write
   STATUS      current
   DESCRIPTION
      "Path: lacpBundle.editConf.bridging.l2ProtTunnel.dropThresholds.gvrp

       unit name = packets/sec

       Possibilities:
               unlimited   (0)"
   ::= {er1646v2LacpBBrCEntry 407941120}

er1646v2LacpBBrCL2ptDropThrGmrp OBJECT-TYPE
   SYNTAX      INTEGER
               {
               unlimited (0)
               }
   UNITS       "packets/sec"
   MAX-ACCESS  read-write
   STATUS      current
   DESCRIPTION
      "Path: lacpBundle.editConf.bridging.l2ProtTunnel.dropThresholds.gmrp

       unit name = packets/sec

       Possibilities:
               unlimited   (0)"
   ::= {er1646v2LacpBBrCEntry 407945216}

er1646v2LacpBBrCL2ptDropThrDtp OBJECT-TYPE
   SYNTAX      INTEGER
               {
               unlimited (0)
               }
   UNITS       "packets/sec"
   MAX-ACCESS  read-write
   STATUS      current
   DESCRIPTION
      "Path: lacpBundle.editConf.bridging.l2ProtTunnel.dropThresholds.dtp

       unit name = packets/sec

       Possibilities:
               unlimited   (0)"
   ::= {er1646v2LacpBBrCEntry 407949312}

er1646v2LacpBBrCL2ptDropThrPagp OBJECT-TYPE
   SYNTAX      INTEGER
               {
               unlimited (0)
               }
   UNITS       "packets/sec"
   MAX-ACCESS  read-write
   STATUS      current
   DESCRIPTION
      "Path: lacpBundle.editConf.bridging.l2ProtTunnel.dropThresholds.pagp

       unit name = packets/sec

       Possibilities:
               unlimited   (0)"
   ::= {er1646v2LacpBBrCEntry 407953408}

er1646v2LacpBBrCL2ptDropThrUdld OBJECT-TYPE
   SYNTAX      INTEGER
               {
               unlimited (0)
               }
   UNITS       "packets/sec"
   MAX-ACCESS  read-write
   STATUS      current
   DESCRIPTION
      "Path: lacpBundle.editConf.bridging.l2ProtTunnel.dropThresholds.udld

       unit name = packets/sec

       Possibilities:
               unlimited   (0)"
   ::= {er1646v2LacpBBrCEntry 407957504}


er1646v2LacpBVlanTagging OBJECT IDENTIFIER ::= {er1646v2LacpB 14}

er1646v2LacpBVlanTaggingSSCTable OBJECT-TYPE
   SYNTAX      SEQUENCE OF Er1646v2LacpBVlanTaggingEntry
   MAX-ACCESS  not-accessible
   STATUS      current
   DESCRIPTION
      "vlan tagging config"
   ::= {er1646v2LacpBVlanTagging 1}

er1646v2LacpBVlanTaggingEntry OBJECT-TYPE
   SYNTAX      Er1646v2LacpBVlanTaggingEntry
   MAX-ACCESS  not-accessible
   STATUS      current
   DESCRIPTION
      ""
   INDEX      { er1646v2LacpBVlanTaggingGlobalIx }
   ::= {er1646v2LacpBVlanTaggingSSCTable 1}

Er1646v2LacpBVlanTaggingEntry ::=
   SEQUENCE
      {
      er1646v2LacpBVlanTaggingGlobalIx
         GlobalIndex,
      er1646v2LacpBVlanTaggingUntaggedAction
         INTEGER,
      er1646v2LacpBVlanTaggingUntaggedTagInfoTpid
         INTEGER,
      er1646v2LacpBVlanTaggingUntaggedTagInfoVid
         Integer32,
      er1646v2LacpBVlanTaggingUnknownVlansAction
         INTEGER,
      er1646v2LacpBVlanTaggingUnknownVlansTagInfoTpid
         INTEGER,
      er1646v2LacpBVlanTaggingUnknownVlansTagInfoVid
         Integer32
      }

er1646v2LacpBVlanTaggingGlobalIx OBJECT-TYPE
   SYNTAX      GlobalIndex
   MAX-ACCESS  not-accessible
   STATUS      current
   DESCRIPTION
      "The value of the tlsCntTreeGlobalIndex of the MANAGED OBJECT."
   ::= {er1646v2LacpBVlanTaggingEntry 10}

er1646v2LacpBVlanTaggingUntaggedAction OBJECT-TYPE
   SYNTAX      INTEGER
               {
               discard (0),
               accept (1),
               tag (2)
               }
   MAX-ACCESS  read-write
   STATUS      current
   DESCRIPTION
      "Path: lacpBundle.editConf.vlanTagging.untagged.action

       Possibilities:
               discard   (0)
               accept   (1)
               tag   (2)"
   ::= {er1646v2LacpBVlanTaggingEntry 671088640}

er1646v2LacpBVlanTaggingUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: lacpBundle.editConf.vlanTagging.untagged.tagInfo.tpid

       Possibilities:
               dot1Q   (33024)
               dot1ad   (34984)
               0x9100   (37120)
               0x9200   (37376)
               0x9300   (37632)"
   ::= {er1646v2LacpBVlanTaggingEntry 746586112}

er1646v2LacpBVlanTaggingUntaggedTagInfoVid OBJECT-TYPE
   SYNTAX      Integer32
   MAX-ACCESS  read-write
   STATUS      current
   DESCRIPTION
      "Path: lacpBundle.editConf.vlanTagging.untagged.tagInfo.vid"
   ::= {er1646v2LacpBVlanTaggingEntry 754974720}

er1646v2LacpBVlanTaggingUnknownVlansAction OBJECT-TYPE
   SYNTAX      INTEGER
               {
               discard (0),
               accept (1),
               tag (2)
               }
   MAX-ACCESS  read-write
   STATUS      current
   DESCRIPTION
      "Path: lacpBundle.editConf.vlanTagging.unknownVlans.action

       Possibilities:
               discard   (0)
               accept   (1)
               tag   (2)"
   ::= {er1646v2LacpBVlanTaggingEntry 1744830464}

er1646v2LacpBVlanTaggingUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: lacpBundle.editConf.vlanTagging.unknownVlans.tagInfo.tpid

       Possibilities:
               dot1Q   (33024)
               dot1ad   (34984)
               0x9100   (37120)
               0x9200   (37376)
               0x9300   (37632)"
   ::= {er1646v2LacpBVlanTaggingEntry 1820327936}

er1646v2LacpBVlanTaggingUnknownVlansTagInfoVid OBJECT-TYPE
   SYNTAX      Integer32
   MAX-ACCESS  read-write
   STATUS      current
   DESCRIPTION
      "Path: lacpBundle.editConf.vlanTagging.unknownVlans.tagInfo.vid"
   ::= {er1646v2LacpBVlanTaggingEntry 1828716544}

er1646v2LacpBVlanTaggingVlans OBJECT-TYPE
   SYNTAX      SEQUENCE OF Er1646v2LacpBVlanTaggingVlansEntry
   MAX-ACCESS  not-accessible
   STATUS      current
   DESCRIPTION
      ""
   ::= {er1646v2LacpBVlanTagging 1073741824}

er1646v2LacpBVlanTaggingVlansEntry OBJECT-TYPE
   SYNTAX      Er1646v2LacpBVlanTaggingVlansEntry
   MAX-ACCESS  not-accessible
   STATUS      current
   DESCRIPTION
      ""
   INDEX      { er1646v2LacpBVlanTaggingVlansGlobalIx,
                er1646v2LacpBVlanTaggingVlansTableIx }
   ::= {er1646v2LacpBVlanTaggingVlans 1}

Er1646v2LacpBVlanTaggingVlansEntry ::=
   SEQUENCE
      {
      er1646v2LacpBVlanTaggingVlansActions
         VariableLengthTableActions,
      er1646v2LacpBVlanTaggingVlansGlobalIx
         GlobalIndex,
      er1646v2LacpBVlanTaggingVlansTableIx
         TableIndex,
      er1646v2LacpBVlanTaggingVlansVid
         Integer32,
      er1646v2LacpBVlanTaggingVlansEndVid
         Integer32,
      er1646v2LacpBVlanTaggingVlansAction
         INTEGER,
      er1646v2LacpBVlanTaggingVlansTagInfoTpid
         INTEGER,
      er1646v2LacpBVlanTaggingVlansTagInfoVid
         Integer32
      }

er1646v2LacpBVlanTaggingVlansActions OBJECT-TYPE
   SYNTAX      VariableLengthTableActions
   MAX-ACCESS  read-write
   STATUS      current
   DESCRIPTION
      "By way of this field, some manipulations
       on this table may be performed."
   ::= {er1646v2LacpBVlanTaggingVlansEntry 2}

er1646v2LacpBVlanTaggingVlansGlobalIx OBJECT-TYPE
   SYNTAX      GlobalIndex
   MAX-ACCESS  not-accessible
   STATUS      current
   DESCRIPTION
      "The value of the tlsCntTreeGlobalIndex of the MANAGED OBJECT."
   ::= {er1646v2LacpBVlanTaggingVlansEntry 10}

er1646v2LacpBVlanTaggingVlansTableIx OBJECT-TYPE
   SYNTAX      TableIndex
   MAX-ACCESS  not-accessible
   STATUS      current
   DESCRIPTION
      ""
   ::= {er1646v2LacpBVlanTaggingVlansEntry 11}

er1646v2LacpBVlanTaggingVlansVid OBJECT-TYPE
   SYNTAX      Integer32
   MAX-ACCESS  read-write
   STATUS      current
   DESCRIPTION
      "Path: lacpBundle.editConf.vlanTagging.vlans.vid"
   ::= {er1646v2LacpBVlanTaggingVlansEntry 536870912}

er1646v2LacpBVlanTaggingVlansEndVid OBJECT-TYPE
   SYNTAX      Integer32
   MAX-ACCESS  read-write
   STATUS      current
   DESCRIPTION
      "Path: lacpBundle.editConf.vlanTagging.vlans.endVid"
   ::= {er1646v2LacpBVlanTaggingVlansEntry 2147483648}

er1646v2LacpBVlanTaggingVlansAction OBJECT-TYPE
   SYNTAX      INTEGER
               {
               discard (0),
               accept (1),
               tag (2)
               }
   MAX-ACCESS  read-write
   STATUS      current
   DESCRIPTION
      "Path: lacpBundle.editConf.vlanTagging.vlans.action

       Possibilities:
               discard   (0)
               accept   (1)
               tag   (2)"
   ::= {er1646v2LacpBVlanTaggingVlansEntry 1073741824}

er1646v2LacpBVlanTaggingVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: lacpBundle.editConf.vlanTagging.vlans.tagInfo.tpid

       Possibilities:
               dot1Q   (33024)
               dot1ad   (34984)
               0x9100   (37120)
               0x9200   (37376)
               0x9300   (37632)"
   ::= {er1646v2LacpBVlanTaggingVlansEntry 1677721600}

er1646v2LacpBVlanTaggingVlansTagInfoVid OBJECT-TYPE
   SYNTAX      Integer32
   MAX-ACCESS  read-write
   STATUS      current
   DESCRIPTION
      "Path: lacpBundle.editConf.vlanTagging.vlans.tagInfo.vid"
   ::= {er1646v2LacpBVlanTaggingVlansEntry 1744830464}


er1646v2LacpBIp OBJECT IDENTIFIER ::= {er1646v2LacpB 1}

er1646v2LacpBIpSSCTable OBJECT-TYPE
   SYNTAX      SEQUENCE OF Er1646v2LacpBIpEntry
   MAX-ACCESS  not-accessible
   STATUS      current
   DESCRIPTION
      "ip interface config parameters"
   ::= {er1646v2LacpBIp 1}

er1646v2LacpBIpEntry OBJECT-TYPE
   SYNTAX      Er1646v2LacpBIpEntry
   MAX-ACCESS  not-accessible
   STATUS      current
   DESCRIPTION
      ""
   INDEX      { er1646v2LacpBIpGlobalIx }
   ::= {er1646v2LacpBIpSSCTable 1}

Er1646v2LacpBIpEntry ::=
   SEQUENCE
      {
      er1646v2LacpBIpGlobalIx
         GlobalIndex,
      er1646v2LacpBIpVrfRouter
         DisplayString,
      er1646v2LacpBIpAdr
         IpAddress,
      er1646v2LacpBIpNetm
         IpAddress,
      er1646v2LacpBIpSNetName
         INTEGER,
      er1646v2LacpBIpSNetCust
         DisplayString,
      er1646v2LacpBIpDhcpC
         INTEGER,
      er1646v2LacpBIpDhcpGatewayPreference
         Integer32,
      er1646v2LacpBIpDhcpRoutePreference
         Integer32,
      er1646v2LacpBIpDhcpDnsPreference
         Integer32,
      er1646v2LacpBIpMtu
         Integer32,
      er1646v2LacpBIpMssAdjust
         INTEGER,
      er1646v2LacpBIpRipMetric
         Integer32,
      er1646v2LacpBIpRipMetricOut
         Integer32,
      er1646v2LacpBIpRipMode
         INTEGER,
      er1646v2LacpBIpRipTxVer
         INTEGER,
      er1646v2LacpBIpRipRxVer
         INTEGER,
      er1646v2LacpBIpRipSplitH
         INTEGER,
      er1646v2LacpBIpRipAuth
         INTEGER,
      er1646v2LacpBIpRipFilter
         DisplayString,
      er1646v2LacpBIpRipFilterIn
         DisplayString,
      er1646v2LacpBIpRipClearNextHop
         INTEGER,
      er1646v2LacpBIpAccPol
         DisplayString,
      er1646v2LacpBIpAB
         DisplayString,
      er1646v2LacpBIpMA
         INTEGER,
      er1646v2LacpBIpMF
         Integer32,
      er1646v2LacpBIpDB
         INTEGER,
      er1646v2LacpBIpIR
         INTEGER,
      er1646v2LacpBIpIgmp
         INTEGER,
      er1646v2LacpBIpNN
         DisplayString,
      er1646v2LacpBIpVrrp
         INTEGER,
      er1646v2LacpBIpPimMode
         INTEGER,
      er1646v2LacpBIpPimDrPriority
         Counter32,
      er1646v2LacpBIpPimHelloTime
         TimeTicks,
      er1646v2LacpBIpPimPropagationDelay
         TimeTicks,
      er1646v2LacpBIpPimOverrideInterval
         TimeTicks,
      er1646v2LacpBIpPimBsrBorder
         INTEGER,
      er1646v2LacpBIpPimTtlThreshold
         Integer32,
      er1646v2LacpBIpIMNetworkUnreachable
         INTEGER,
      er1646v2LacpBIpIMHostUnreachable
         INTEGER,
      er1646v2LacpBIpIMProtocolUnreachable
         INTEGER,
      er1646v2LacpBIpIMPortUnreachable
         INTEGER,
      er1646v2LacpBIpIMMtuExceeded
         INTEGER,
      er1646v2LacpBIpIMAdminProhibited
         INTEGER,
      er1646v2LacpBIpIMTtlExceeded
         INTEGER,
      er1646v2LacpBIpIMRedirect
         INTEGER
      }

er1646v2LacpBIpGlobalIx OBJECT-TYPE
   SYNTAX      GlobalIndex
   MAX-ACCESS  not-accessible
   STATUS      current
   DESCRIPTION
      "The value of the tlsCntTreeGlobalIndex of the MANAGED OBJECT."
   ::= {er1646v2LacpBIpEntry 10}

er1646v2LacpBIpVrfRouter OBJECT-TYPE
   SYNTAX      DisplayString
   MAX-ACCESS  read-write
   STATUS      current
   DESCRIPTION
      "Path: lacpBundle.editConf.ip.vrfRouter"
   ::= {er1646v2LacpBIpEntry 738197504}

er1646v2LacpBIpAdr OBJECT-TYPE
   SYNTAX      IpAddress
   MAX-ACCESS  read-write
   STATUS      current
   DESCRIPTION
      "Path: lacpBundle.editConf.ip.address"
   ::= {er1646v2LacpBIpEntry 2030043136}

er1646v2LacpBIpNetm OBJECT-TYPE
   SYNTAX      IpAddress
   MAX-ACCESS  read-write
   STATUS      current
   DESCRIPTION
      "Path: lacpBundle.editConf.ip.netMask"
   ::= {er1646v2LacpBIpEntry 2063597568}

er1646v2LacpBIpSNetName OBJECT-TYPE
   SYNTAX      INTEGER
               {
               slOPTg (0),
               corp (2),
               dmz (3),
               internet (1)
               }
   MAX-ACCESS  read-write
   STATUS      current
   DESCRIPTION
      "Path: lacpBundle.editConf.ip.sNet.name

       Possibilities:
               <OPT>   (0)
               corp   (2)
               dmz   (3)
               internet   (1)"
   ::= {er1646v2LacpBIpEntry 855703552}

er1646v2LacpBIpSNetCust OBJECT-TYPE
   SYNTAX      DisplayString
   MAX-ACCESS  read-write
   STATUS      current
   DESCRIPTION
      "Path: lacpBundle.editConf.ip.sNet.custom"
   ::= {er1646v2LacpBIpEntry 855769088}

er1646v2LacpBIpDhcpC OBJECT-TYPE
   SYNTAX      INTEGER
               {
               disabled (0),
               enabled (1)
               }
   MAX-ACCESS  read-write
   STATUS      current
   DESCRIPTION
      "Path: lacpBundle.editConf.ip.dhcpClient

       Possibilities:
               disabled   (0)
               enabled   (1)"
   ::= {er1646v2LacpBIpEntry 838860800}

er1646v2LacpBIpDhcpGatewayPreference OBJECT-TYPE
   SYNTAX      Integer32
   MAX-ACCESS  read-write
   STATUS      current
   DESCRIPTION
      "Path: lacpBundle.editConf.ip.dhcp.gatewayPreference"
   ::= {er1646v2LacpBIpEntry 872480768}

er1646v2LacpBIpDhcpRoutePreference OBJECT-TYPE
   SYNTAX      Integer32
   MAX-ACCESS  read-write
   STATUS      current
   DESCRIPTION
      "Path: lacpBundle.editConf.ip.dhcp.routePreference"
   ::= {er1646v2LacpBIpEntry 872546304}

er1646v2LacpBIpDhcpDnsPreference OBJECT-TYPE
   SYNTAX      Integer32
   MAX-ACCESS  read-write
   STATUS      current
   DESCRIPTION
      "Path: lacpBundle.editConf.ip.dhcp.dnsPreference"
   ::= {er1646v2LacpBIpEntry 872611840}

er1646v2LacpBIpMtu OBJECT-TYPE
   SYNTAX      Integer32
   MAX-ACCESS  read-write
   STATUS      current
   DESCRIPTION
      "Path: lacpBundle.editConf.ip.mtu"
   ::= {er1646v2LacpBIpEntry 671088640}

er1646v2LacpBIpMssAdjust OBJECT-TYPE
   SYNTAX      INTEGER
               {
               disabled (0),
               auto (65536)
               }
   MAX-ACCESS  read-write
   STATUS      current
   DESCRIPTION
      "Path: lacpBundle.editConf.ip.mssAdjust

       Possibilities:
               disabled   (0)
               auto   (65536)"
   ::= {er1646v2LacpBIpEntry 754974720}

er1646v2LacpBIpRipMetric OBJECT-TYPE
   SYNTAX      Integer32
   MAX-ACCESS  read-write
   STATUS      current
   DESCRIPTION
      "Path: lacpBundle.editConf.ip.rip.metric"
   ::= {er1646v2LacpBIpEntry 353566720}

er1646v2LacpBIpRipMetricOut OBJECT-TYPE
   SYNTAX      Integer32
   MAX-ACCESS  read-write
   STATUS      current
   DESCRIPTION
      "Path: lacpBundle.editConf.ip.rip.metricOut"
   ::= {er1646v2LacpBIpEntry 353632256}

er1646v2LacpBIpRipMode OBJECT-TYPE
   SYNTAX      INTEGER
               {
               disabled (0),
               passive (1),
               active (2)
               }
   MAX-ACCESS  read-write
   STATUS      current
   DESCRIPTION
      "Path: lacpBundle.editConf.ip.rip.mode

       Possibilities:
               disabled   (0)
               passive   (1)
               active   (2)"
   ::= {er1646v2LacpBIpEntry 353697792}

er1646v2LacpBIpRipTxVer OBJECT-TYPE
   SYNTAX      INTEGER
               {
               rip1 (0),
               rip2 (1),
               rip1mcompatible (2)
               }
   MAX-ACCESS  read-write
   STATUS      current
   DESCRIPTION
      "Path: lacpBundle.editConf.ip.rip.txVersion

       Possibilities:
               rip1   (0)
               rip2   (1)
               rip1-compatible   (2)"
   ::= {er1646v2LacpBIpEntry 354615296}

er1646v2LacpBIpRipRxVer OBJECT-TYPE
   SYNTAX      INTEGER
               {
               rip1only (0),
               rip2only (1),
               rip12 (2)
               }
   MAX-ACCESS  read-write
   STATUS      current
   DESCRIPTION
      "Path: lacpBundle.editConf.ip.rip.rxVersion

       Possibilities:
               rip1only   (0)
               rip2only   (1)
               rip1&2   (2)"
   ::= {er1646v2LacpBIpEntry 354680832}

er1646v2LacpBIpRipSplitH OBJECT-TYPE
   SYNTAX      INTEGER
               {
               disabled (0),
               enabled (1),
               poisonedReverse (2)
               }
   MAX-ACCESS  read-write
   STATUS      current
   DESCRIPTION
      "Path: lacpBundle.editConf.ip.rip.splitHorizon

       Possibilities:
               disabled   (0)
               enabled   (1)
               poisonedReverse   (2)"
   ::= {er1646v2LacpBIpEntry 353828864}

er1646v2LacpBIpRipAuth OBJECT-TYPE
   SYNTAX      INTEGER
               {
               disabled (0),
               texts (1),
               md5 (2)
               }
   MAX-ACCESS  read-write
   STATUS      current
   DESCRIPTION
      "Path: lacpBundle.editConf.ip.rip.authentication

       Possibilities:
               disabled   (0)
               text    (1)
               md5   (2)"
   ::= {er1646v2LacpBIpEntry 353501184}

er1646v2LacpBIpRipFilter OBJECT-TYPE
   SYNTAX      DisplayString
   MAX-ACCESS  read-write
   STATUS      current
   DESCRIPTION
      "Path: lacpBundle.editConf.ip.rip.filter"
   ::= {er1646v2LacpBIpEntry 354418688}

er1646v2LacpBIpRipFilterIn OBJECT-TYPE
   SYNTAX      DisplayString
   MAX-ACCESS  read-write
   STATUS      current
   DESCRIPTION
      "Path: lacpBundle.editConf.ip.rip.filterIn"
   ::= {er1646v2LacpBIpEntry 354484224}

er1646v2LacpBIpRipClearNextHop OBJECT-TYPE
   SYNTAX      INTEGER
               {
               disabled (0),
               enabled (1)
               }
   MAX-ACCESS  read-write
   STATUS      current
   DESCRIPTION
      "Path: lacpBundle.editConf.ip.rip.clearNextHop

       Possibilities:
               disabled   (0)
               enabled   (1)"
   ::= {er1646v2LacpBIpEntry 352452608}

er1646v2LacpBIpAccPol OBJECT-TYPE
   SYNTAX      DisplayString
   MAX-ACCESS  read-write
   STATUS      current
   DESCRIPTION
      "Path: lacpBundle.editConf.ip.accessPolicy"
   ::= {er1646v2LacpBIpEntry 704643072}

er1646v2LacpBIpAB OBJECT-TYPE
   SYNTAX      DisplayString
   MAX-ACCESS  read-write
   STATUS      current
   DESCRIPTION
      "Path: lacpBundle.editConf.ip.trafficPolicy"
   ::= {er1646v2LacpBIpEntry 234881024}

er1646v2LacpBIpMA OBJECT-TYPE
   SYNTAX      INTEGER
               {
               disabled (0),
               enabled (1)
               }
   MAX-ACCESS  read-write
   STATUS      current
   DESCRIPTION
      "Path: lacpBundle.editConf.ip.mgmtAccess

       Possibilities:
               disabled   (0)
               enabled   (1)"
   ::= {er1646v2LacpBIpEntry 268435456}

er1646v2LacpBIpMF OBJECT-TYPE
   SYNTAX      Integer32
   MAX-ACCESS  read-write
   STATUS      current
   DESCRIPTION
      "Path: lacpBundle.editConf.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1646v2LacpBIpEntry 285212672}

er1646v2LacpBIpDB OBJECT-TYPE
   SYNTAX      INTEGER
               {
               disabled (0),
               enabled (1)
               }
   MAX-ACCESS  read-write
   STATUS      current
   DESCRIPTION
      "Path: lacpBundle.editConf.ip.directedBroadcasts

       Possibilities:
               disabled   (0)
               enabled   (1)"
   ::= {er1646v2LacpBIpEntry 369098752}

er1646v2LacpBIpIR OBJECT-TYPE
   SYNTAX      INTEGER
               {
               disabled (0),
               enabled (1)
               }
   MAX-ACCESS  read-write
   STATUS      current
   DESCRIPTION
      "Path: lacpBundle.editConf.ip.icmpRedirects

       Possibilities:
               disabled   (0)
               enabled   (1)"
   ::= {er1646v2LacpBIpEntry 436207616}

er1646v2LacpBIpIgmp OBJECT-TYPE
   SYNTAX      INTEGER
               {
               disabled (0),
               proxy (1),
               router (2),
               v3Router (5)
               }
   MAX-ACCESS  read-write
   STATUS      current
   DESCRIPTION
      "Path: lacpBundle.editConf.ip.igmp

       Possibilities:
               disabled   (0)
               proxy   (1)
               router   (2)
               v3Router   (5)"
   ::= {er1646v2LacpBIpEntry 536870912}

er1646v2LacpBIpNN OBJECT-TYPE
   SYNTAX      DisplayString
   MAX-ACCESS  read-write
   STATUS      current
   DESCRIPTION
      "Path: lacpBundle.editConf.ip.nat"
   ::= {er1646v2LacpBIpEntry 452984832}

er1646v2LacpBIpVrrp OBJECT-TYPE
   SYNTAX      INTEGER
               {
               disabled (0),
               enabled (1)
               }
   MAX-ACCESS  read-write
   STATUS      current
   DESCRIPTION
      "Path: lacpBundle.editConf.ip.vrrp

       Possibilities:
               disabled   (0)
               enabled   (1)"
   ::= {er1646v2LacpBIpEntry 721420288}

er1646v2LacpBIpPimMode OBJECT-TYPE
   SYNTAX      INTEGER
               {
               disabled (0),
               sparse (1),
               passive (2)
               }
   MAX-ACCESS  read-write
   STATUS      current
   DESCRIPTION
      "Path: lacpBundle.editConf.ip.pim.mode

       Possibilities:
               disabled   (0)
               sparse   (1)
               passive   (2)"
   ::= {er1646v2LacpBIpEntry 771817472}

er1646v2LacpBIpPimDrPriority OBJECT-TYPE
   SYNTAX      Counter32
   MAX-ACCESS  read-write
   STATUS      current
   DESCRIPTION
      "Path: lacpBundle.editConf.ip.pim.drPriority

       32 bit unsigned wrappable counter."
   ::= {er1646v2LacpBIpEntry 771883008}

er1646v2LacpBIpPimHelloTime OBJECT-TYPE
   SYNTAX      TimeTicks
   MAX-ACCESS  read-write
   STATUS      current
   DESCRIPTION
      "Path: lacpBundle.editConf.ip.pim.helloTime

       Time in centi-second."
   ::= {er1646v2LacpBIpEntry 771948544}

er1646v2LacpBIpPimPropagationDelay OBJECT-TYPE
   SYNTAX      TimeTicks
   MAX-ACCESS  read-write
   STATUS      current
   DESCRIPTION
      "Path: lacpBundle.editConf.ip.pim.propagationDelay

       Time in centi-second."
   ::= {er1646v2LacpBIpEntry 772014080}

er1646v2LacpBIpPimOverrideInterval OBJECT-TYPE
   SYNTAX      TimeTicks
   MAX-ACCESS  read-write
   STATUS      current
   DESCRIPTION
      "Path: lacpBundle.editConf.ip.pim.overrideInterval

       Time in centi-second."
   ::= {er1646v2LacpBIpEntry 772079616}

er1646v2LacpBIpPimBsrBorder OBJECT-TYPE
   SYNTAX      INTEGER
               {
               disabled (0),
               enabled (1)
               }
   MAX-ACCESS  read-write
   STATUS      current
   DESCRIPTION
      "Path: lacpBundle.editConf.ip.pim.bsrBorder

       Possibilities:
               disabled   (0)
               enabled   (1)"
   ::= {er1646v2LacpBIpEntry 772145152}

er1646v2LacpBIpPimTtlThreshold OBJECT-TYPE
   SYNTAX      Integer32
   MAX-ACCESS  read-write
   STATUS      current
   DESCRIPTION
      "Path: lacpBundle.editConf.ip.pim.ttlThreshold"
   ::= {er1646v2LacpBIpEntry 772210688}

er1646v2LacpBIpIMNetworkUnreachable OBJECT-TYPE
   SYNTAX      INTEGER
               {
               disabled (0),
               enabled (1)
               }
   MAX-ACCESS  read-write
   STATUS      current
   DESCRIPTION
      "Path: lacpBundle.editConf.ip.icmpMessages.networkUnreachable

       Possibilities:
               disabled   (0)
               enabled   (1)"
   ::= {er1646v2LacpBIpEntry 788594688}

er1646v2LacpBIpIMHostUnreachable OBJECT-TYPE
   SYNTAX      INTEGER
               {
               disabled (0),
               enabled (1)
               }
   MAX-ACCESS  read-write
   STATUS      current
   DESCRIPTION
      "Path: lacpBundle.editConf.ip.icmpMessages.hostUnreachable

       Possibilities:
               disabled   (0)
               enabled   (1)"
   ::= {er1646v2LacpBIpEntry 788660224}

er1646v2LacpBIpIMProtocolUnreachable OBJECT-TYPE
   SYNTAX      INTEGER
               {
               disabled (0),
               enabled (1)
               }
   MAX-ACCESS  read-write
   STATUS      current
   DESCRIPTION
      "Path: lacpBundle.editConf.ip.icmpMessages.protocolUnreachable

       Possibilities:
               disabled   (0)
               enabled   (1)"
   ::= {er1646v2LacpBIpEntry 788725760}

er1646v2LacpBIpIMPortUnreachable OBJECT-TYPE
   SYNTAX      INTEGER
               {
               disabled (0),
               enabled (1)
               }
   MAX-ACCESS  read-write
   STATUS      current
   DESCRIPTION
      "Path: lacpBundle.editConf.ip.icmpMessages.portUnreachable

       Possibilities:
               disabled   (0)
               enabled   (1)"
   ::= {er1646v2LacpBIpEntry 788791296}

er1646v2LacpBIpIMMtuExceeded OBJECT-TYPE
   SYNTAX      INTEGER
               {
               disabled (0),
               enabled (1)
               }
   MAX-ACCESS  read-write
   STATUS      current
   DESCRIPTION
      "Path: lacpBundle.editConf.ip.icmpMessages.mtuExceeded

       Possibilities:
               disabled   (0)
               enabled   (1)"
   ::= {er1646v2LacpBIpEntry 788856832}

er1646v2LacpBIpIMAdminProhibited OBJECT-TYPE
   SYNTAX      INTEGER
               {
               disabled (0),
               enabled (1)
               }
   MAX-ACCESS  read-write
   STATUS      current
   DESCRIPTION
      "Path: lacpBundle.editConf.ip.icmpMessages.adminProhibited

       Possibilities:
               disabled   (0)
               enabled   (1)"
   ::= {er1646v2LacpBIpEntry 788922368}

er1646v2LacpBIpIMTtlExceeded OBJECT-TYPE
   SYNTAX      INTEGER
               {
               disabled (0),
               enabled (1)
               }
   MAX-ACCESS  read-write
   STATUS      current
   DESCRIPTION
      "Path: lacpBundle.editConf.ip.icmpMessages.ttlExceeded

       Possibilities:
               disabled   (0)
               enabled   (1)"
   ::= {er1646v2LacpBIpEntry 788987904}

er1646v2LacpBIpIMRedirect OBJECT-TYPE
   SYNTAX      INTEGER
               {
               disabled (0),
               enabled (1)
               }
   MAX-ACCESS  read-write
   STATUS      current
   DESCRIPTION
      "Path: lacpBundle.editConf.ip.icmpMessages.redirect

       Possibilities:
               disabled   (0)
               enabled   (1)"
   ::= {er1646v2LacpBIpEntry 789053440}

er1646v2LacpBIpSaddr OBJECT-TYPE
   SYNTAX      SEQUENCE OF Er1646v2LacpBIpSaddrEntry
   MAX-ACCESS  not-accessible
   STATUS      current
   DESCRIPTION
      ""
   ::= {er1646v2LacpBIp 385875968}

er1646v2LacpBIpSaddrEntry OBJECT-TYPE
   SYNTAX      Er1646v2LacpBIpSaddrEntry
   MAX-ACCESS  not-accessible
   STATUS      current
   DESCRIPTION
      ""
   INDEX      { er1646v2LacpBIpSaddrGlobalIx,
                er1646v2LacpBIpSaddrTableIx }
   ::= {er1646v2LacpBIpSaddr 1}

Er1646v2LacpBIpSaddrEntry ::=
   SEQUENCE
      {
      er1646v2LacpBIpSaddrActions
         VariableLengthTableActions,
      er1646v2LacpBIpSaddrGlobalIx
         GlobalIndex,
      er1646v2LacpBIpSaddrTableIx
         TableIndex,
      er1646v2LacpBIpSaddrAddress
         IpAddress,
      er1646v2LacpBIpSaddrNetMask
         IpAddress
      }

er1646v2LacpBIpSaddrActions OBJECT-TYPE
   SYNTAX      VariableLengthTableActions
   MAX-ACCESS  read-write
   STATUS      current
   DESCRIPTION
      "By way of this field, some manipulations
       on this table may be performed."
   ::= {er1646v2LacpBIpSaddrEntry 2}

er1646v2LacpBIpSaddrGlobalIx OBJECT-TYPE
   SYNTAX      GlobalIndex
   MAX-ACCESS  not-accessible
   STATUS      current
   DESCRIPTION
      "The value of the tlsCntTreeGlobalIndex of the MANAGED OBJECT."
   ::= {er1646v2LacpBIpSaddrEntry 10}

er1646v2LacpBIpSaddrTableIx OBJECT-TYPE
   SYNTAX      TableIndex
   MAX-ACCESS  not-accessible
   STATUS      current
   DESCRIPTION
      ""
   ::= {er1646v2LacpBIpSaddrEntry 11}

er1646v2LacpBIpSaddrAddress OBJECT-TYPE
   SYNTAX      IpAddress
   MAX-ACCESS  read-write
   STATUS      current
   DESCRIPTION
      "Path: lacpBundle.editConf.ip.secondaryIp.address"
   ::= {er1646v2LacpBIpSaddrEntry 2030043136}

er1646v2LacpBIpSaddrNetMask OBJECT-TYPE
   SYNTAX      IpAddress
   MAX-ACCESS  read-write
   STATUS      current
   DESCRIPTION
      "Path: lacpBundle.editConf.ip.secondaryIp.netMask"
   ::= {er1646v2LacpBIpSaddrEntry 2063597568}

er1646v2LacpBIpH OBJECT-TYPE
   SYNTAX      SEQUENCE OF Er1646v2LacpBIpHEntry
   MAX-ACCESS  not-accessible
   STATUS      current
   DESCRIPTION
      ""
   ::= {er1646v2LacpBIp 251658240}

er1646v2LacpBIpHEntry OBJECT-TYPE
   SYNTAX      Er1646v2LacpBIpHEntry
   MAX-ACCESS  not-accessible
   STATUS      current
   DESCRIPTION
      ""
   INDEX      { er1646v2LacpBIpHGlobalIx,
                er1646v2LacpBIpHTableIx }
   ::= {er1646v2LacpBIpH 1}

Er1646v2LacpBIpHEntry ::=
   SEQUENCE
      {
      er1646v2LacpBIpHActions
         VariableLengthTableActions,
      er1646v2LacpBIpHGlobalIx
         GlobalIndex,
      er1646v2LacpBIpHTableIx
         TableIndex,
      er1646v2LacpBIpHAddress
         IpAddress,
      er1646v2LacpBIpHDhcpRelayOptionSubscriberId
         DisplayString
      }

er1646v2LacpBIpHActions OBJECT-TYPE
   SYNTAX      VariableLengthTableActions
   MAX-ACCESS  read-write
   STATUS      current
   DESCRIPTION
      "By way of this field, some manipulations
       on this table may be performed."
   ::= {er1646v2LacpBIpHEntry 2}

er1646v2LacpBIpHGlobalIx OBJECT-TYPE
   SYNTAX      GlobalIndex
   MAX-ACCESS  not-accessible
   STATUS      current
   DESCRIPTION
      "The value of the tlsCntTreeGlobalIndex of the MANAGED OBJECT."
   ::= {er1646v2LacpBIpHEntry 10}

er1646v2LacpBIpHTableIx OBJECT-TYPE
   SYNTAX      TableIndex
   MAX-ACCESS  not-accessible
   STATUS      current
   DESCRIPTION
      ""
   ::= {er1646v2LacpBIpHEntry 11}

er1646v2LacpBIpHAddress OBJECT-TYPE
   SYNTAX      IpAddress
   MAX-ACCESS  read-write
   STATUS      current
   DESCRIPTION
      "Path: lacpBundle.editConf.ip.helpers.address"
   ::= {er1646v2LacpBIpHEntry 16777216}

er1646v2LacpBIpHDhcpRelayOptionSubscriberId OBJECT-TYPE
   SYNTAX      DisplayString
   MAX-ACCESS  read-write
   STATUS      current
   DESCRIPTION
      "Path: lacpBundle.editConf.ip.helpers.dhcpRelayOption.subscriberId"
   ::= {er1646v2LacpBIpHEntry 33947648}


er1646v2LacpBVlan OBJECT IDENTIFIER ::= {er1646v2LacpB 33}

er1646v2LacpBVlanSSCTable OBJECT-TYPE
   SYNTAX      SEQUENCE OF Er1646v2LacpBVlanEntry
   MAX-ACCESS  not-accessible
   STATUS      current
   DESCRIPTION
      ""
   ::= {er1646v2LacpBVlan 1}

er1646v2LacpBVlanEntry OBJECT-TYPE
   SYNTAX      Er1646v2LacpBVlanEntry
   MAX-ACCESS  not-accessible
   STATUS      current
   DESCRIPTION
      ""
   INDEX      { er1646v2LacpBVlanGlobalIx,
                er1646v2LacpBVlanTableIx }
   ::= {er1646v2LacpBVlanSSCTable 1}

Er1646v2LacpBVlanEntry ::=
   SEQUENCE
      {
      er1646v2LacpBVlanActions
         VariableLengthTableActions,
      er1646v2LacpBVlanGlobalIx
         GlobalIndex,
      er1646v2LacpBVlanTableIx
         TableIndex,
      er1646v2LacpBVlanName
         DisplayString,
      er1646v2LacpBVlanRemark
         DisplayString,
      er1646v2LacpBVlanAdminStatus
         INTEGER,
      er1646v2LacpBVlanMode
         INTEGER,
      er1646v2LacpBVlanPriorityPolicy
         DisplayString,
      er1646v2LacpBVlanIpVrfRouter
         DisplayString,
      er1646v2LacpBVlanIpAdr
         IpAddress,
      er1646v2LacpBVlanIpNetm
         IpAddress,
      er1646v2LacpBVlanIpSNetName
         INTEGER,
      er1646v2LacpBVlanIpSNetCust
         DisplayString,
      er1646v2LacpBVlanIpDhcpC
         INTEGER,
      er1646v2LacpBVlanIpDhcpGatewayPreference
         Integer32,
      er1646v2LacpBVlanIpDhcpRoutePreference
         Integer32,
      er1646v2LacpBVlanIpDhcpDnsPreference
         Integer32,
      er1646v2LacpBVlanIpMtu
         Integer32,
      er1646v2LacpBVlanIpMssAdjust
         INTEGER,
      er1646v2LacpBVlanIpRipMetric
         Integer32,
      er1646v2LacpBVlanIpRipMetricOut
         Integer32,
      er1646v2LacpBVlanIpRipMode
         INTEGER,
      er1646v2LacpBVlanIpRipTxVer
         INTEGER,
      er1646v2LacpBVlanIpRipRxVer
         INTEGER,
      er1646v2LacpBVlanIpRipSplitH
         INTEGER,
      er1646v2LacpBVlanIpRipAuth
         INTEGER,
      er1646v2LacpBVlanIpRipFilter
         DisplayString,
      er1646v2LacpBVlanIpRipFilterIn
         DisplayString,
      er1646v2LacpBVlanIpRipClearNextHop
         INTEGER,
      er1646v2LacpBVlanIpAccPol
         DisplayString,
      er1646v2LacpBVlanIpAB
         DisplayString,
      er1646v2LacpBVlanIpMA
         INTEGER,
      er1646v2LacpBVlanIpMF
         Integer32,
      er1646v2LacpBVlanIpDB
         INTEGER,
      er1646v2LacpBVlanIpIR
         INTEGER,
      er1646v2LacpBVlanIpIgmp
         INTEGER,
      er1646v2LacpBVlanIpNN
         DisplayString,
      er1646v2LacpBVlanIpVrrp
         INTEGER,
      er1646v2LacpBVlanIpPimMode
         INTEGER,
      er1646v2LacpBVlanIpPimDrPriority
         Counter32,
      er1646v2LacpBVlanIpPimHelloTime
         TimeTicks,
      er1646v2LacpBVlanIpPimPropagationDelay
         TimeTicks,
      er1646v2LacpBVlanIpPimOverrideInterval
         TimeTicks,
      er1646v2LacpBVlanIpPimBsrBorder
         INTEGER,
      er1646v2LacpBVlanIpPimTtlThreshold
         Integer32,
      er1646v2LacpBVlanIpIMNetworkUnreachable
         INTEGER,
      er1646v2LacpBVlanIpIMHostUnreachable
         INTEGER,
      er1646v2LacpBVlanIpIMProtocolUnreachable
         INTEGER,
      er1646v2LacpBVlanIpIMPortUnreachable
         INTEGER,
      er1646v2LacpBVlanIpIMMtuExceeded
         INTEGER,
      er1646v2LacpBVlanIpIMAdminProhibited
         INTEGER,
      er1646v2LacpBVlanIpIMTtlExceeded
         INTEGER,
      er1646v2LacpBVlanIpIMRedirect
         INTEGER,
      er1646v2LacpBVlanIpV6VrfRouter
         DisplayString,
      er1646v2LacpBVlanIpV6AddrAutoConfigNrDupAddrDetects
         Integer32,
      er1646v2LacpBVlanIpV6AddrAutoConfigAcceptRa
         INTEGER,
      er1646v2LacpBVlanIpV6AddrAutoConfigAcceptRaRdnss
         INTEGER,
      er1646v2LacpBVlanIpV6AddrAutoConfigAcceptRaDnssl
         INTEGER,
      er1646v2LacpBVlanIpV6DefaultRoute
         INTEGER,
      er1646v2LacpBVlanIpV6RaSend
         INTEGER,
      er1646v2LacpBVlanIpV6RaMinInterval
         TimeTicks,
      er1646v2LacpBVlanIpV6RaMaxInterval
         TimeTicks,
      er1646v2LacpBVlanIpV6RaManagedFlag
         INTEGER,
      er1646v2LacpBVlanIpV6RaOtherConfFlag
         INTEGER,
      er1646v2LacpBVlanIpV6RaLinkMtu
         Integer32,
      er1646v2LacpBVlanIpV6RaReachableTime
         TimeTicks,
      er1646v2LacpBVlanIpV6RaRetransmitTime
         TimeTicks,
      er1646v2LacpBVlanIpV6RaHopLimit
         Integer32,
      er1646v2LacpBVlanIpV6RaDefaultLifeTime
         TimeTicks,
      er1646v2LacpBVlanIpV6RaDnsOptionsRdnssLifeTime
         TimeTicks,
      er1646v2LacpBVlanIpV6RaDnsOptionsRdnssImportServers
         INTEGER,
      er1646v2LacpBVlanIpV6RaDnsOptionsDnsslLifeTime
         TimeTicks,
      er1646v2LacpBVlanIpV6RaDnsOptionsDnsslImportDomains
         INTEGER,
      er1646v2LacpBVlanIpV6RsSend
         INTEGER,
      er1646v2LacpBVlanIpV6RsMaxRandomDelay
         TimeTicks,
      er1646v2LacpBVlanIpV6RsInterval
         TimeTicks,
      er1646v2LacpBVlanIpV6RsMaxSolicitations
         Integer32,
      er1646v2LacpBVlanIpV6TrafficPolicyInbound
         DisplayString,
      er1646v2LacpBVlanIpV6TrafficPolicyOutbound
         DisplayString,
      er1646v2LacpBVlanIpV6FirewallZone
         DisplayString,
      er1646v2LacpBVlanIpV6DhcpClientAddrAC
         INTEGER,
      er1646v2LacpBVlanIpV6DhcpClientPrDelMode
         INTEGER,
      er1646v2LacpBVlanIpV6DhcpClientPrDelPool
         DisplayString,
      er1646v2LacpBVlanIpV6DhcpClientPrDelPdExclOpt
         INTEGER,
      er1646v2LacpBVlanIpV6DhcpClientDnsServerPref
         Integer32,
      er1646v2LacpBVlanIpV6DhcpClientRapidCommit
         INTEGER,
      er1646v2LacpBVlanIpV6DhcpClientTimersSolTimeOut
         TimeTicks,
      er1646v2LacpBVlanIpV6DhcpClientTimersSolMaxRt
         TimeTicks,
      er1646v2LacpBVlanIpV6DhcpClientTimersInfoRefresh
         TimeTicks,
      er1646v2LacpBVlanIpV6DhcpServerMode
         INTEGER,
      er1646v2LacpBVlanIpV6DhcpServerPreference
         Integer32,
      er1646v2LacpBVlanIpV6DhcpServerPool
         DisplayString,
      er1646v2LacpBVlanIpV6DhcpServerRapidCommit
         INTEGER,
      er1646v2LacpBVlanIpV6DhcpServerTimersInfoRefresh
         TimeTicks,
      er1646v2LacpBVlanIpV6DhcpRelayMode
         INTEGER,
      er1646v2LacpBVlanIpV6SendRedirect
         INTEGER,
      er1646v2LacpBVlanIpV6LinkMtu
         Integer32,
      er1646v2LacpBVlanIpV6InterfaceId
         OCTET STRING,
      er1646v2LacpBVlanIpV6MF
         Integer32,
      er1646v2LacpBVlanIpV6IcmpMessagesNoRoute
         INTEGER,
      er1646v2LacpBVlanIpV6IcmpMessagesBeyondScope
         INTEGER,
      er1646v2LacpBVlanIpV6IcmpMessagesAddressUnreachable
         INTEGER,
      er1646v2LacpBVlanIpV6IcmpMessagesPortUnreachable
         INTEGER,
      er1646v2LacpBVlanIpV6IcmpMessagesPacketTooBig
         INTEGER,
      er1646v2LacpBVlanIpV6IcmpMessagesHopLimitExceeded
         INTEGER,
      er1646v2LacpBVlanIpV6IcmpMessagesFragTimeExceeded
         INTEGER,
      er1646v2LacpBVlanIpV6IcmpMessagesHeaderFieldErr
         INTEGER,
      er1646v2LacpBVlanIpV6IcmpMessagesOptionUnrecognized
         INTEGER,
      er1646v2LacpBVlanIpV6IcmpMessagesRedirect
         INTEGER,
      er1646v2LacpBVlanBridgingAccList
         DisplayString,
      er1646v2LacpBVlanBridgingInACL
         DisplayString,
      er1646v2LacpBVlanBridgingTp
         DisplayString,
      er1646v2LacpBVlanBridgingBrGrp
         DisplayString,
      er1646v2LacpBVlanBridgingLimBC
         INTEGER,
      er1646v2LacpBVlanBridgingPrivateMode
         INTEGER,
      er1646v2LacpBVlanBridgingLearning
         INTEGER,
      er1646v2LacpBVlanBridgingMaxCacheSize
         INTEGER,
      er1646v2LacpBVlanBridgingRelearnDropOnRelearn
         INTEGER,
      er1646v2LacpBVlanBridgingRelearnShutdownThreshold
         Integer32,
      er1646v2LacpBVlanBridgingRelearnShutdownTime
         TimeTicks,
      er1646v2LacpBVlanBridgingRelearnLoopDetection
         INTEGER,
      er1646v2LacpBVlanBridgingRelearnLoopDetectionInterval
         TimeTicks,
      er1646v2LacpBVlanBridgingVlanMemberShip
         INTEGER,
      er1646v2LacpBVlanBridgingVlTUntaggedAction
         INTEGER,
      er1646v2LacpBVlanBridgingVlTUntaggedTagInfoTpid
         INTEGER,
      er1646v2LacpBVlanBridgingVlTUntaggedTagInfoVid
         Integer32,
      er1646v2LacpBVlanBridgingVlTUnknownVlansAction
         INTEGER,
      er1646v2LacpBVlanBridgingVlTUnknownVlansTagInfoTpid
         INTEGER,
      er1646v2LacpBVlanBridgingVlTUnknownVlansTagInfoVid
         Integer32,
      er1646v2LacpBVlanBridgingDot1adType
         INTEGER,
      er1646v2LacpBVlanBridgingPriority
         Integer32,
      er1646v2LacpBVlanBridgingPathCost
         Integer32,
      er1646v2LacpBVlanBridgingInternalPathCost
         Integer32,
      er1646v2LacpBVlanBridgingTCD
         INTEGER,
      er1646v2LacpBVlanBridgingRestrictedRole
         INTEGER,
      er1646v2LacpBVlanBridgingAdminEdge
         INTEGER,
      er1646v2LacpBVlanBridgingOamMacDeviceMac
         DisplayString,
      er1646v2LacpBVlanBridgingOamMacUserMac
         OCTET STRING,
      er1646v2LacpBVlanBridgingOamMacBridgeMac
         DisplayString,
      er1646v2LacpBVlanBridgingMgmtInline
         INTEGER,
      er1646v2LacpBVlanBridgingL2ptMode
         INTEGER,
      er1646v2LacpBVlanBridgingL2ptProtocols
         Integer32,
      er1646v2LacpBVlanBridgingL2ptDestMac
         OCTET STRING,
      er1646v2LacpBVlanBridgingL2ptCos
         INTEGER,
      er1646v2LacpBVlanBridgingL2ptDropThrStp
         INTEGER,
      er1646v2LacpBVlanBridgingL2ptDropThrLldp
         INTEGER,
      er1646v2LacpBVlanBridgingL2ptDropThrOam
         INTEGER,
      er1646v2LacpBVlanBridgingL2ptDropThrCdp
         INTEGER,
      er1646v2LacpBVlanBridgingL2ptDropThrVtp
         INTEGER,
      er1646v2LacpBVlanBridgingL2ptDropThrLacp
         INTEGER,
      er1646v2LacpBVlanBridgingL2ptDropThrEfmOam
         INTEGER,
      er1646v2LacpBVlanBridgingL2ptDropThrPvst
         INTEGER,
      er1646v2LacpBVlanBridgingL2ptDropThrMmrp
         INTEGER,
      er1646v2LacpBVlanBridgingL2ptDropThrMvrp
         INTEGER,
      er1646v2LacpBVlanBridgingL2ptDropThrGvrp
         INTEGER,
      er1646v2LacpBVlanBridgingL2ptDropThrGmrp
         INTEGER,
      er1646v2LacpBVlanBridgingL2ptDropThrDtp
         INTEGER,
      er1646v2LacpBVlanBridgingL2ptDropThrPagp
         INTEGER,
      er1646v2LacpBVlanBridgingL2ptDropThrUdld
         INTEGER,
      er1646v2LacpBVlanVlanVid
         INTEGER,
      er1646v2LacpBVlanVlanVidExtensionSingle
         OCTET STRING,
      er1646v2LacpBVlanVlanVidExtensionEndVid
         Integer32,
      er1646v2LacpBVlanVlanTpid
         INTEGER,
      er1646v2LacpBVlanVlanTagSign
         INTEGER,
      er1646v2LacpBVlanVlanChTos
         INTEGER,
      er1646v2LacpBVlanVlanCTMapP0
         INTEGER,
      er1646v2LacpBVlanVlanCTMapP1
         INTEGER,
      er1646v2LacpBVlanVlanCTMapP2
         INTEGER,
      er1646v2LacpBVlanVlanCTMapP3
         INTEGER,
      er1646v2LacpBVlanVlanCTMapP4
         INTEGER,
      er1646v2LacpBVlanVlanCTMapP5
         INTEGER,
      er1646v2LacpBVlanVlanCTMapP6
         INTEGER,
      er1646v2LacpBVlanVlanCTMapP7
         INTEGER,
      er1646v2LacpBVlanVlanTxCos
         INTEGER,
      er1646v2LacpBVlanVlanCCMapP0
         Integer32,
      er1646v2LacpBVlanVlanCCMapP1
         Integer32,
      er1646v2LacpBVlanVlanCCMapP2
         Integer32,
      er1646v2LacpBVlanVlanCCMapP3
         Integer32,
      er1646v2LacpBVlanVlanCCMapP4
         Integer32,
      er1646v2LacpBVlanVlanCCMapP5
         Integer32,
      er1646v2LacpBVlanVlanCCMapP6
         Integer32,
      er1646v2LacpBVlanVlanCCMapP7
         Integer32,
      er1646v2LacpBVlanVlanQCMapQueue1
         Integer32,
      er1646v2LacpBVlanVlanQCMapQueue2
         Integer32,
      er1646v2LacpBVlanVlanQCMapQueue3
         Integer32,
      er1646v2LacpBVlanVlanQCMapQueue4
         Integer32,
      er1646v2LacpBVlanVlanQCMapQueue5
         Integer32,
      er1646v2LacpBVlanVlanQCMapLowDelayQueue
         Integer32,
      er1646v2LacpBVlanVlanQCMapLowDelay2Queue
         Integer32,
      er1646v2LacpBVlanVlanQCMapSystemQueue
         Integer32,
      er1646v2LacpBVlanVlanQinQSVid
         Integer32,
      er1646v2LacpBVlanVlanQinQSTpid
         INTEGER,
      er1646v2LacpBVlanVlanArpTimeOut
         TimeTicks,
      er1646v2LacpBVlanVlanArpProxyArp
         INTEGER,
      er1646v2LacpBVlanBandwidthMode
         INTEGER,
      er1646v2LacpBVlanBandwidthCir
         Integer32,
      er1646v2LacpBVlanBandwidthEir
         Integer32,
      er1646v2LacpBVlanBandwidthUnit
         INTEGER,
      er1646v2LacpBVlanBandwidthTc
         INTEGER,
      er1646v2LacpBVlanBandwidthTcFactor
         INTEGER,
      er1646v2LacpBVlanBandwidthCorrType
         INTEGER,
      er1646v2LacpBVlanBandwidthCorrPredefEncapsFrameRelay
         DisplayString,
      er1646v2LacpBVlanBandwidthCorrPredefEncapsPpp
         DisplayString,
      er1646v2LacpBVlanBandwidthCorrPredefEncapsAtmHl
         INTEGER,
      er1646v2LacpBVlanBandwidthCorrPredefEncapsAtmMp
         INTEGER,
      er1646v2LacpBVlanBandwidthCorrPredefEncapsHdlc
         DisplayString,
      er1646v2LacpBVlanBandwidthCorrPredefEncapsEfmFs
         Integer32,
      er1646v2LacpBVlanBandwidthCorrPredefEncapsEfmIb
         Integer32,
      er1646v2LacpBVlanBandwidthCorrPredefMode
         INTEGER,
      er1646v2LacpBVlanBandwidthCorrManualOverhead
         Integer32,
      er1646v2LacpBVlanBandwidthCorrManualFrameData
         Counter32,
      er1646v2LacpBVlanBandwidthCorrManualFrameHeader
         Counter32,
      er1646v2LacpBVlanBandwidthMaxFifoQLen
         Integer32,
      er1646v2LacpBVlanBandwidthDeFlagCir
         INTEGER,
      er1646v2LacpBVlanBandwidthDeFlagEir
         INTEGER,
      er1646v2LacpBVlanBandwidthDeFlagViolate
         INTEGER,
      er1646v2LacpBVlanBandwidthActCirActNone
         OCTET STRING,
      er1646v2LacpBVlanBandwidthActCirActEthCos1
         INTEGER,
      er1646v2LacpBVlanBandwidthActCirActEthDei1
         INTEGER,
      er1646v2LacpBVlanBandwidthActCirActEthCos2
         INTEGER,
      er1646v2LacpBVlanBandwidthActCirActEthDei2
         INTEGER,
      er1646v2LacpBVlanBandwidthActCirActEthCos3
         INTEGER,
      er1646v2LacpBVlanBandwidthActCirActEthDei3
         INTEGER,
      er1646v2LacpBVlanBandwidthActCirActEthCos4
         INTEGER,
      er1646v2LacpBVlanBandwidthActCirActEthDei4
         INTEGER,
      er1646v2LacpBVlanBandwidthActCirActEthCos5
         INTEGER,
      er1646v2LacpBVlanBandwidthActCirActEthDei5
         INTEGER,
      er1646v2LacpBVlanBandwidthActCirActEthCos6
         INTEGER,
      er1646v2LacpBVlanBandwidthActCirActEthDei6
         INTEGER,
      er1646v2LacpBVlanBandwidthActCirActEthCos7
         INTEGER,
      er1646v2LacpBVlanBandwidthActCirActEthDei7
         INTEGER,
      er1646v2LacpBVlanBandwidthActCirActEthCos8
         INTEGER,
      er1646v2LacpBVlanBandwidthActCirActEthDei8
         INTEGER,
      er1646v2LacpBVlanBandwidthActCirActEthTos
         INTEGER,
      er1646v2LacpBVlanBandwidthActCirActEthQueue
         INTEGER,
      er1646v2LacpBVlanBandwidthActCirActEthDrpLev
         INTEGER,
      er1646v2LacpBVlanBandwidthActCirActEthDeFlag
         INTEGER,
      er1646v2LacpBVlanBandwidthActCirActIpTos
         INTEGER,
      er1646v2LacpBVlanBandwidthActCirActIpQueue
         INTEGER,
      er1646v2LacpBVlanBandwidthActCirActIpDrpLev
         INTEGER,
      er1646v2LacpBVlanBandwidthActCirActIpDeFlag
         INTEGER,
      er1646v2LacpBVlanBandwidthActEirActNone
         OCTET STRING,
      er1646v2LacpBVlanBandwidthActEirActEthCos1
         INTEGER,
      er1646v2LacpBVlanBandwidthActEirActEthDei1
         INTEGER,
      er1646v2LacpBVlanBandwidthActEirActEthCos2
         INTEGER,
      er1646v2LacpBVlanBandwidthActEirActEthDei2
         INTEGER,
      er1646v2LacpBVlanBandwidthActEirActEthCos3
         INTEGER,
      er1646v2LacpBVlanBandwidthActEirActEthDei3
         INTEGER,
      er1646v2LacpBVlanBandwidthActEirActEthCos4
         INTEGER,
      er1646v2LacpBVlanBandwidthActEirActEthDei4
         INTEGER,
      er1646v2LacpBVlanBandwidthActEirActEthCos5
         INTEGER,
      er1646v2LacpBVlanBandwidthActEirActEthDei5
         INTEGER,
      er1646v2LacpBVlanBandwidthActEirActEthCos6
         INTEGER,
      er1646v2LacpBVlanBandwidthActEirActEthDei6
         INTEGER,
      er1646v2LacpBVlanBandwidthActEirActEthCos7
         INTEGER,
      er1646v2LacpBVlanBandwidthActEirActEthDei7
         INTEGER,
      er1646v2LacpBVlanBandwidthActEirActEthCos8
         INTEGER,
      er1646v2LacpBVlanBandwidthActEirActEthDei8
         INTEGER,
      er1646v2LacpBVlanBandwidthActEirActEthTos
         INTEGER,
      er1646v2LacpBVlanBandwidthActEirActEthQueue
         INTEGER,
      er1646v2LacpBVlanBandwidthActEirActEthDrpLev
         INTEGER,
      er1646v2LacpBVlanBandwidthActEirActEthDeFlag
         INTEGER,
      er1646v2LacpBVlanBandwidthActEirActIpTos
         INTEGER,
      er1646v2LacpBVlanBandwidthActEirActIpQueue
         INTEGER,
      er1646v2LacpBVlanBandwidthActEirActIpDrpLev
         INTEGER,
      er1646v2LacpBVlanBandwidthActEirActIpDeFlag
         INTEGER,
      er1646v2LacpBVlanBandwidthActViolActNone
         OCTET STRING,
      er1646v2LacpBVlanBandwidthActViolActDrop
         OCTET STRING,
      er1646v2LacpBVlanBandwidthActViolActEthCos1
         INTEGER,
      er1646v2LacpBVlanBandwidthActViolActEthDei1
         INTEGER,
      er1646v2LacpBVlanBandwidthActViolActEthCos2
         INTEGER,
      er1646v2LacpBVlanBandwidthActViolActEthDei2
         INTEGER,
      er1646v2LacpBVlanBandwidthActViolActEthCos3
         INTEGER,
      er1646v2LacpBVlanBandwidthActViolActEthDei3
         INTEGER,
      er1646v2LacpBVlanBandwidthActViolActEthCos4
         INTEGER,
      er1646v2LacpBVlanBandwidthActViolActEthDei4
         INTEGER,
      er1646v2LacpBVlanBandwidthActViolActEthCos5
         INTEGER,
      er1646v2LacpBVlanBandwidthActViolActEthDei5
         INTEGER,
      er1646v2LacpBVlanBandwidthActViolActEthCos6
         INTEGER,
      er1646v2LacpBVlanBandwidthActViolActEthDei6
         INTEGER,
      er1646v2LacpBVlanBandwidthActViolActEthCos7
         INTEGER,
      er1646v2LacpBVlanBandwidthActViolActEthDei7
         INTEGER,
      er1646v2LacpBVlanBandwidthActViolActEthCos8
         INTEGER,
      er1646v2LacpBVlanBandwidthActViolActEthDei8
         INTEGER,
      er1646v2LacpBVlanBandwidthActViolActEthTos
         INTEGER,
      er1646v2LacpBVlanBandwidthActViolActEthQueue
         INTEGER,
      er1646v2LacpBVlanBandwidthActViolActEthDrpLev
         INTEGER,
      er1646v2LacpBVlanBandwidthActViolActEthDeFlag
         INTEGER,
      er1646v2LacpBVlanBandwidthActViolActIpTos
         INTEGER,
      er1646v2LacpBVlanBandwidthActViolActIpQueue
         INTEGER,
      er1646v2LacpBVlanBandwidthActViolActIpDrpLev
         INTEGER,
      er1646v2LacpBVlanBandwidthActViolActIpDeFlag
         INTEGER,
      er1646v2LacpBVlanInbBwMode
         INTEGER,
      er1646v2LacpBVlanInbBwCir
         Integer32,
      er1646v2LacpBVlanInbBwEir
         Integer32,
      er1646v2LacpBVlanInbBwUnit
         INTEGER,
      er1646v2LacpBVlanInbBwTc
         INTEGER,
      er1646v2LacpBVlanInbBwTcFactor
         INTEGER,
      er1646v2LacpBVlanInbBwCorrType
         INTEGER,
      er1646v2LacpBVlanInbBwCorrPredefEncapsFrameRelay
         DisplayString,
      er1646v2LacpBVlanInbBwCorrPredefEncapsPpp
         DisplayString,
      er1646v2LacpBVlanInbBwCorrPredefEncapsAtmHl
         INTEGER,
      er1646v2LacpBVlanInbBwCorrPredefEncapsAtmMp
         INTEGER,
      er1646v2LacpBVlanInbBwCorrPredefEncapsHdlc
         DisplayString,
      er1646v2LacpBVlanInbBwCorrPredefEncapsEfmFs
         Integer32,
      er1646v2LacpBVlanInbBwCorrPredefEncapsEfmIb
         Integer32,
      er1646v2LacpBVlanInbBwCorrPredefMode
         INTEGER,
      er1646v2LacpBVlanInbBwCorrManualOverhead
         Integer32,
      er1646v2LacpBVlanInbBwCorrManualFrameData
         Counter32,
      er1646v2LacpBVlanInbBwCorrManualFrameHeader
         Counter32,
      er1646v2LacpBVlanInbBwMaxFifoQLen
         Integer32,
      er1646v2LacpBVlanInbBwPriorityPolicy
         DisplayString,
      er1646v2LacpBVlanInbBwDeFlagCir
         INTEGER,
      er1646v2LacpBVlanInbBwDeFlagEir
         INTEGER,
      er1646v2LacpBVlanInbBwDeFlagViolate
         INTEGER,
      er1646v2LacpBVlanInbBwActCirActNone
         OCTET STRING,
      er1646v2LacpBVlanInbBwActCirActEthCos1
         INTEGER,
      er1646v2LacpBVlanInbBwActCirActEthDei1
         INTEGER,
      er1646v2LacpBVlanInbBwActCirActEthCos2
         INTEGER,
      er1646v2LacpBVlanInbBwActCirActEthDei2
         INTEGER,
      er1646v2LacpBVlanInbBwActCirActEthCos3
         INTEGER,
      er1646v2LacpBVlanInbBwActCirActEthDei3
         INTEGER,
      er1646v2LacpBVlanInbBwActCirActEthCos4
         INTEGER,
      er1646v2LacpBVlanInbBwActCirActEthDei4
         INTEGER,
      er1646v2LacpBVlanInbBwActCirActEthCos5
         INTEGER,
      er1646v2LacpBVlanInbBwActCirActEthDei5
         INTEGER,
      er1646v2LacpBVlanInbBwActCirActEthCos6
         INTEGER,
      er1646v2LacpBVlanInbBwActCirActEthDei6
         INTEGER,
      er1646v2LacpBVlanInbBwActCirActEthCos7
         INTEGER,
      er1646v2LacpBVlanInbBwActCirActEthDei7
         INTEGER,
      er1646v2LacpBVlanInbBwActCirActEthCos8
         INTEGER,
      er1646v2LacpBVlanInbBwActCirActEthDei8
         INTEGER,
      er1646v2LacpBVlanInbBwActCirActEthTos
         INTEGER,
      er1646v2LacpBVlanInbBwActCirActEthQueue
         INTEGER,
      er1646v2LacpBVlanInbBwActCirActEthDrpLev
         INTEGER,
      er1646v2LacpBVlanInbBwActCirActEthDeFlag
         INTEGER,
      er1646v2LacpBVlanInbBwActCirActIpTos
         INTEGER,
      er1646v2LacpBVlanInbBwActCirActIpQueue
         INTEGER,
      er1646v2LacpBVlanInbBwActCirActIpDrpLev
         INTEGER,
      er1646v2LacpBVlanInbBwActCirActIpDeFlag
         INTEGER,
      er1646v2LacpBVlanInbBwActEirActNone
         OCTET STRING,
      er1646v2LacpBVlanInbBwActEirActEthCos1
         INTEGER,
      er1646v2LacpBVlanInbBwActEirActEthDei1
         INTEGER,
      er1646v2LacpBVlanInbBwActEirActEthCos2
         INTEGER,
      er1646v2LacpBVlanInbBwActEirActEthDei2
         INTEGER,
      er1646v2LacpBVlanInbBwActEirActEthCos3
         INTEGER,
      er1646v2LacpBVlanInbBwActEirActEthDei3
         INTEGER,
      er1646v2LacpBVlanInbBwActEirActEthCos4
         INTEGER,
      er1646v2LacpBVlanInbBwActEirActEthDei4
         INTEGER,
      er1646v2LacpBVlanInbBwActEirActEthCos5
         INTEGER,
      er1646v2LacpBVlanInbBwActEirActEthDei5
         INTEGER,
      er1646v2LacpBVlanInbBwActEirActEthCos6
         INTEGER,
      er1646v2LacpBVlanInbBwActEirActEthDei6
         INTEGER,
      er1646v2LacpBVlanInbBwActEirActEthCos7
         INTEGER,
      er1646v2LacpBVlanInbBwActEirActEthDei7
         INTEGER,
      er1646v2LacpBVlanInbBwActEirActEthCos8
         INTEGER,
      er1646v2LacpBVlanInbBwActEirActEthDei8
         INTEGER,
      er1646v2LacpBVlanInbBwActEirActEthTos
         INTEGER,
      er1646v2LacpBVlanInbBwActEirActEthQueue
         INTEGER,
      er1646v2LacpBVlanInbBwActEirActEthDrpLev
         INTEGER,
      er1646v2LacpBVlanInbBwActEirActEthDeFlag
         INTEGER,
      er1646v2LacpBVlanInbBwActEirActIpTos
         INTEGER,
      er1646v2LacpBVlanInbBwActEirActIpQueue
         INTEGER,
      er1646v2LacpBVlanInbBwActEirActIpDrpLev
         INTEGER,
      er1646v2LacpBVlanInbBwActEirActIpDeFlag
         INTEGER,
      er1646v2LacpBVlanInbBwActViolActNone
         OCTET STRING,
      er1646v2LacpBVlanInbBwActViolActDrop
         OCTET STRING,
      er1646v2LacpBVlanInbBwActViolActEthCos1
         INTEGER,
      er1646v2LacpBVlanInbBwActViolActEthDei1
         INTEGER,
      er1646v2LacpBVlanInbBwActViolActEthCos2
         INTEGER,
      er1646v2LacpBVlanInbBwActViolActEthDei2
         INTEGER,
      er1646v2LacpBVlanInbBwActViolActEthCos3
         INTEGER,
      er1646v2LacpBVlanInbBwActViolActEthDei3
         INTEGER,
      er1646v2LacpBVlanInbBwActViolActEthCos4
         INTEGER,
      er1646v2LacpBVlanInbBwActViolActEthDei4
         INTEGER,
      er1646v2LacpBVlanInbBwActViolActEthCos5
         INTEGER,
      er1646v2LacpBVlanInbBwActViolActEthDei5
         INTEGER,
      er1646v2LacpBVlanInbBwActViolActEthCos6
         INTEGER,
      er1646v2LacpBVlanInbBwActViolActEthDei6
         INTEGER,
      er1646v2LacpBVlanInbBwActViolActEthCos7
         INTEGER,
      er1646v2LacpBVlanInbBwActViolActEthDei7
         INTEGER,
      er1646v2LacpBVlanInbBwActViolActEthCos8
         INTEGER,
      er1646v2LacpBVlanInbBwActViolActEthDei8
         INTEGER,
      er1646v2LacpBVlanInbBwActViolActEthTos
         INTEGER,
      er1646v2LacpBVlanInbBwActViolActEthQueue
         INTEGER,
      er1646v2LacpBVlanInbBwActViolActEthDrpLev
         INTEGER,
      er1646v2LacpBVlanInbBwActViolActEthDeFlag
         INTEGER,
      er1646v2LacpBVlanInbBwActViolActIpTos
         INTEGER,
      er1646v2LacpBVlanInbBwActViolActIpQueue
         INTEGER,
      er1646v2LacpBVlanInbBwActViolActIpDrpLev
         INTEGER,
      er1646v2LacpBVlanInbBwActViolActIpDeFlag
         INTEGER,
      er1646v2LacpBVlanPppoE
         INTEGER,
      er1646v2LacpBVlanPppLnkMOperation
         INTEGER,
      er1646v2LacpBVlanPppLnkMInterval
         TimeTicks,
      er1646v2LacpBVlanPppLnkMRepTimeOut
         TimeTicks,
      er1646v2LacpBVlanPppLnkMFailsPrmt
         Integer32,
      er1646v2LacpBVlanPppAuthentication
         INTEGER,
      er1646v2LacpBVlanPppAuthenPeriod
         TimeTicks,
      er1646v2LacpBVlanPppSessionName
         DisplayString,
      er1646v2LacpBVlanPppSessionSecret
         DisplayString,
      er1646v2LacpBVlanPppEncModeSessionSecret
         INTEGER,
      er1646v2LacpBVlanPppEncSessionSecret
         DisplayString,
      er1646v2LacpBVlanPppServiceName
         DisplayString,
      er1646v2LacpBVlanPbbMode
         INTEGER,
      er1646v2LacpBVlanPbbTxCos
         Integer32,
      er1646v2LacpBVlanPbbIsid
         Integer32,
      er1646v2LacpBVlanPbbDestMac
         OCTET STRING,
      er1646v2LacpBVlanPbbCustomGroupMac
         OCTET STRING
      }

er1646v2LacpBVlanActions OBJECT-TYPE
   SYNTAX      VariableLengthTableActions
   MAX-ACCESS  read-write
   STATUS      current
   DESCRIPTION
      "By way of this field, some manipulations
       on this table may be performed."
   ::= {er1646v2LacpBVlanEntry 2}

er1646v2LacpBVlanGlobalIx OBJECT-TYPE
   SYNTAX      GlobalIndex
   MAX-ACCESS  not-accessible
   STATUS      current
   DESCRIPTION
      "The value of the tlsCntTreeGlobalIndex of the MANAGED OBJECT."
   ::= {er1646v2LacpBVlanEntry 10}

er1646v2LacpBVlanTableIx OBJECT-TYPE
   SYNTAX      TableIndex
   MAX-ACCESS  not-accessible
   STATUS      current
   DESCRIPTION
      ""
   ::= {er1646v2LacpBVlanEntry 11}

er1646v2LacpBVlanName OBJECT-TYPE
   SYNTAX      DisplayString
   MAX-ACCESS  read-write
   STATUS      current
   DESCRIPTION
      "Path: lacpBundle.editConf.vlan.name"
   ::= {er1646v2LacpBVlanEntry 16777216}

er1646v2LacpBVlanRemark OBJECT-TYPE
   SYNTAX      DisplayString
   MAX-ACCESS  read-write
   STATUS      current
   DESCRIPTION
      "Path: lacpBundle.editConf.vlan.remark"
   ::= {er1646v2LacpBVlanEntry 1157627904}

er1646v2LacpBVlanAdminStatus OBJECT-TYPE
   SYNTAX      INTEGER
               {
               up (1),
               down (2)
               }
   MAX-ACCESS  read-write
   STATUS      current
   DESCRIPTION
      "Path: lacpBundle.editConf.vlan.adminStatus

       Possibilities:
               up   (1)
               down   (2)"
   ::= {er1646v2LacpBVlanEntry 33554432}

er1646v2LacpBVlanMode OBJECT-TYPE
   SYNTAX      INTEGER
               {
               routing (1),
               bridging (2),
               ipV6 (16),
               ipV6ipV4 (17),
               multilink (8)
               }
   MAX-ACCESS  read-write
   STATUS      current
   DESCRIPTION
      "Path: lacpBundle.editConf.vlan.mode

       Possibilities:
               routing   (1)
               bridging   (2)
               ipV6   (16)
               ipV6/ipV4   (17)
               multilink   (8)"
   ::= {er1646v2LacpBVlanEntry 67108864}

er1646v2LacpBVlanPriorityPolicy OBJECT-TYPE
   SYNTAX      DisplayString
   MAX-ACCESS  read-write
   STATUS      current
   DESCRIPTION
      "Path: lacpBundle.editConf.vlan.priorityPolicy"
   ::= {er1646v2LacpBVlanEntry 83886080}

er1646v2LacpBVlanIpVrfRouter OBJECT-TYPE
   SYNTAX      DisplayString
   MAX-ACCESS  read-write
   STATUS      current
   DESCRIPTION
      "Path: lacpBundle.editConf.vlan.ip.vrfRouter"
   ::= {er1646v2LacpBVlanEntry 53215232}

er1646v2LacpBVlanIpAdr OBJECT-TYPE
   SYNTAX      IpAddress
   MAX-ACCESS  read-write
   STATUS      current
   DESCRIPTION
      "Path: lacpBundle.editConf.vlan.ip.address"
   ::= {er1646v2LacpBVlanEntry 58261504}

er1646v2LacpBVlanIpNetm OBJECT-TYPE
   SYNTAX      IpAddress
   MAX-ACCESS  read-write
   STATUS      current
   DESCRIPTION
      "Path: lacpBundle.editConf.vlan.ip.netMask"
   ::= {er1646v2LacpBVlanEntry 58392576}

er1646v2LacpBVlanIpSNetName OBJECT-TYPE
   SYNTAX      INTEGER
               {
               slOPTg (0),
               corp (2),
               dmz (3),
               internet (1)
               }
   MAX-ACCESS  read-write
   STATUS      current
   DESCRIPTION
      "Path: lacpBundle.editConf.vlan.ip.sNet.name

       Possibilities:
               <OPT>   (0)
               corp   (2)
               dmz   (3)
               internet   (1)"
   ::= {er1646v2LacpBVlanEntry 53674240}

er1646v2LacpBVlanIpSNetCust OBJECT-TYPE
   SYNTAX      DisplayString
   MAX-ACCESS  read-write
   STATUS      current
   DESCRIPTION
      "Path: lacpBundle.editConf.vlan.ip.sNet.custom"
   ::= {er1646v2LacpBVlanEntry 53674496}

er1646v2LacpBVlanIpDhcpC OBJECT-TYPE
   SYNTAX      INTEGER
               {
               disabled (0),
               enabled (1)
               }
   MAX-ACCESS  read-write
   STATUS      current
   DESCRIPTION
      "Path: lacpBundle.editConf.vlan.ip.dhcpClient

       Possibilities:
               disabled   (0)
               enabled   (1)"
   ::= {er1646v2LacpBVlanEntry 53608448}

er1646v2LacpBVlanIpDhcpGatewayPreference OBJECT-TYPE
   SYNTAX      Integer32
   MAX-ACCESS  read-write
   STATUS      current
   DESCRIPTION
      "Path: lacpBundle.editConf.vlan.ip.dhcp.gatewayPreference"
   ::= {er1646v2LacpBVlanEntry 53739776}

er1646v2LacpBVlanIpDhcpRoutePreference OBJECT-TYPE
   SYNTAX      Integer32
   MAX-ACCESS  read-write
   STATUS      current
   DESCRIPTION
      "Path: lacpBundle.editConf.vlan.ip.dhcp.routePreference"
   ::= {er1646v2LacpBVlanEntry 53740032}

er1646v2LacpBVlanIpDhcpDnsPreference OBJECT-TYPE
   SYNTAX      Integer32
   MAX-ACCESS  read-write
   STATUS      current
   DESCRIPTION
      "Path: lacpBundle.editConf.vlan.ip.dhcp.dnsPreference"
   ::= {er1646v2LacpBVlanEntry 53740288}

er1646v2LacpBVlanIpMtu OBJECT-TYPE
   SYNTAX      Integer32
   MAX-ACCESS  read-write
   STATUS      current
   DESCRIPTION
      "Path: lacpBundle.editConf.vlan.ip.mtu"
   ::= {er1646v2LacpBVlanEntry 52953088}

er1646v2LacpBVlanIpMssAdjust OBJECT-TYPE
   SYNTAX      INTEGER
               {
               disabled (0),
               auto (65536)
               }
   MAX-ACCESS  read-write
   STATUS      current
   DESCRIPTION
      "Path: lacpBundle.editConf.vlan.ip.mssAdjust

       Possibilities:
               disabled   (0)
               auto   (65536)"
   ::= {er1646v2LacpBVlanEntry 53280768}

er1646v2LacpBVlanIpRipMetric OBJECT-TYPE
   SYNTAX      Integer32
   MAX-ACCESS  read-write
   STATUS      current
   DESCRIPTION
      "Path: lacpBundle.editConf.vlan.ip.rip.metric"
   ::= {er1646v2LacpBVlanEntry 51712768}

er1646v2LacpBVlanIpRipMetricOut OBJECT-TYPE
   SYNTAX      Integer32
   MAX-ACCESS  read-write
   STATUS      current
   DESCRIPTION
      "Path: lacpBundle.editConf.vlan.ip.rip.metricOut"
   ::= {er1646v2LacpBVlanEntry 51713024}

er1646v2LacpBVlanIpRipMode OBJECT-TYPE
   SYNTAX      INTEGER
               {
               disabled (0),
               passive (1),
               active (2)
               }
   MAX-ACCESS  read-write
   STATUS      current
   DESCRIPTION
      "Path: lacpBundle.editConf.vlan.ip.rip.mode

       Possibilities:
               disabled   (0)
               passive   (1)
               active   (2)"
   ::= {er1646v2LacpBVlanEntry 51713280}

er1646v2LacpBVlanIpRipTxVer OBJECT-TYPE
   SYNTAX      INTEGER
               {
               rip1 (0),
               rip2 (1),
               rip1mcompatible (2)
               }
   MAX-ACCESS  read-write
   STATUS      current
   DESCRIPTION
      "Path: lacpBundle.editConf.vlan.ip.rip.txVersion

       Possibilities:
               rip1   (0)
               rip2   (1)
               rip1-compatible   (2)"
   ::= {er1646v2LacpBVlanEntry 51716864}

er1646v2LacpBVlanIpRipRxVer OBJECT-TYPE
   SYNTAX      INTEGER
               {
               rip1only (0),
               rip2only (1),
               rip12 (2)
               }
   MAX-ACCESS  read-write
   STATUS      current
   DESCRIPTION
      "Path: lacpBundle.editConf.vlan.ip.rip.rxVersion

       Possibilities:
               rip1only   (0)
               rip2only   (1)
               rip1&2   (2)"
   ::= {er1646v2LacpBVlanEntry 51717120}

er1646v2LacpBVlanIpRipSplitH OBJECT-TYPE
   SYNTAX      INTEGER
               {
               disabled (0),
               enabled (1),
               poisonedReverse (2)
               }
   MAX-ACCESS  read-write
   STATUS      current
   DESCRIPTION
      "Path: lacpBundle.editConf.vlan.ip.rip.splitHorizon

       Possibilities:
               disabled   (0)
               enabled   (1)
               poisonedReverse   (2)"
   ::= {er1646v2LacpBVlanEntry 51713792}

er1646v2LacpBVlanIpRipAuth OBJECT-TYPE
   SYNTAX      INTEGER
               {
               disabled (0),
               texts (1),
               md5 (2)
               }
   MAX-ACCESS  read-write
   STATUS      current
   DESCRIPTION
      "Path: lacpBundle.editConf.vlan.ip.rip.authentication

       Possibilities:
               disabled   (0)
               text    (1)
               md5   (2)"
   ::= {er1646v2LacpBVlanEntry 51712512}

er1646v2LacpBVlanIpRipFilter OBJECT-TYPE
   SYNTAX      DisplayString
   MAX-ACCESS  read-write
   STATUS      current
   DESCRIPTION
      "Path: lacpBundle.editConf.vlan.ip.rip.filter"
   ::= {er1646v2LacpBVlanEntry 51716096}

er1646v2LacpBVlanIpRipFilterIn OBJECT-TYPE
   SYNTAX      DisplayString
   MAX-ACCESS  read-write
   STATUS      current
   DESCRIPTION
      "Path: lacpBundle.editConf.vlan.ip.rip.filterIn"
   ::= {er1646v2LacpBVlanEntry 51716352}

er1646v2LacpBVlanIpRipClearNextHop OBJECT-TYPE
   SYNTAX      INTEGER
               {
               disabled (0),
               enabled (1)
               }
   MAX-ACCESS  read-write
   STATUS      current
   DESCRIPTION
      "Path: lacpBundle.editConf.vlan.ip.rip.clearNextHop

       Possibilities:
               disabled   (0)
               enabled   (1)"
   ::= {er1646v2LacpBVlanEntry 51708416}

er1646v2LacpBVlanIpAccPol OBJECT-TYPE
   SYNTAX      DisplayString
   MAX-ACCESS  read-write
   STATUS      current
   DESCRIPTION
      "Path: lacpBundle.editConf.vlan.ip.accessPolicy"
   ::= {er1646v2LacpBVlanEntry 53084160}

er1646v2LacpBVlanIpAB OBJECT-TYPE
   SYNTAX      DisplayString
   MAX-ACCESS  read-write
   STATUS      current
   DESCRIPTION
      "Path: lacpBundle.editConf.vlan.ip.trafficPolicy"
   ::= {er1646v2LacpBVlanEntry 51249152}

er1646v2LacpBVlanIpMA OBJECT-TYPE
   SYNTAX      INTEGER
               {
               disabled (0),
               enabled (1)
               }
   MAX-ACCESS  read-write
   STATUS      current
   DESCRIPTION
      "Path: lacpBundle.editConf.vlan.ip.mgmtAccess

       Possibilities:
               disabled   (0)
               enabled   (1)"
   ::= {er1646v2LacpBVlanEntry 51380224}

er1646v2LacpBVlanIpMF OBJECT-TYPE
   SYNTAX      Integer32
   MAX-ACCESS  read-write
   STATUS      current
   DESCRIPTION
      "Path: lacpBundle.editConf.vlan.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1646v2LacpBVlanEntry 51445760}

er1646v2LacpBVlanIpDB OBJECT-TYPE
   SYNTAX      INTEGER
               {
               disabled (0),
               enabled (1)
               }
   MAX-ACCESS  read-write
   STATUS      current
   DESCRIPTION
      "Path: lacpBundle.editConf.vlan.ip.directedBroadcasts

       Possibilities:
               disabled   (0)
               enabled   (1)"
   ::= {er1646v2LacpBVlanEntry 51773440}

er1646v2LacpBVlanIpIR OBJECT-TYPE
   SYNTAX      INTEGER
               {
               disabled (0),
               enabled (1)
               }
   MAX-ACCESS  read-write
   STATUS      current
   DESCRIPTION
      "Path: lacpBundle.editConf.vlan.ip.icmpRedirects

       Possibilities:
               disabled   (0)
               enabled   (1)"
   ::= {er1646v2LacpBVlanEntry 52035584}

er1646v2LacpBVlanIpIgmp OBJECT-TYPE
   SYNTAX      INTEGER
               {
               disabled (0),
               proxy (1),
               router (2),
               v3Router (5)
               }
   MAX-ACCESS  read-write
   STATUS      current
   DESCRIPTION
      "Path: lacpBundle.editConf.vlan.ip.igmp

       Possibilities:
               disabled   (0)
               proxy   (1)
               router   (2)
               v3Router   (5)"
   ::= {er1646v2LacpBVlanEntry 52428800}

er1646v2LacpBVlanIpNN OBJECT-TYPE
   SYNTAX      DisplayString
   MAX-ACCESS  read-write
   STATUS      current
   DESCRIPTION
      "Path: lacpBundle.editConf.vlan.ip.nat"
   ::= {er1646v2LacpBVlanEntry 52101120}

er1646v2LacpBVlanIpVrrp OBJECT-TYPE
   SYNTAX      INTEGER
               {
               disabled (0),
               enabled (1)
               }
   MAX-ACCESS  read-write
   STATUS      current
   DESCRIPTION
      "Path: lacpBundle.editConf.vlan.ip.vrrp

       Possibilities:
               disabled   (0)
               enabled   (1)"
   ::= {er1646v2LacpBVlanEntry 53149696}

er1646v2LacpBVlanIpPimMode OBJECT-TYPE
   SYNTAX      INTEGER
               {
               disabled (0),
               sparse (1),
               passive (2)
               }
   MAX-ACCESS  read-write
   STATUS      current
   DESCRIPTION
      "Path: lacpBundle.editConf.vlan.ip.pim.mode

       Possibilities:
               disabled   (0)
               sparse   (1)
               passive   (2)"
   ::= {er1646v2LacpBVlanEntry 53346560}

er1646v2LacpBVlanIpPimDrPriority OBJECT-TYPE
   SYNTAX      Counter32
   MAX-ACCESS  read-write
   STATUS      current
   DESCRIPTION
      "Path: lacpBundle.editConf.vlan.ip.pim.drPriority

       32 bit unsigned wrappable counter."
   ::= {er1646v2LacpBVlanEntry 53346816}

er1646v2LacpBVlanIpPimHelloTime OBJECT-TYPE
   SYNTAX      TimeTicks
   MAX-ACCESS  read-write
   STATUS      current
   DESCRIPTION
      "Path: lacpBundle.editConf.vlan.ip.pim.helloTime

       Time in centi-second."
   ::= {er1646v2LacpBVlanEntry 53347072}

er1646v2LacpBVlanIpPimPropagationDelay OBJECT-TYPE
   SYNTAX      TimeTicks
   MAX-ACCESS  read-write
   STATUS      current
   DESCRIPTION
      "Path: lacpBundle.editConf.vlan.ip.pim.propagationDelay

       Time in centi-second."
   ::= {er1646v2LacpBVlanEntry 53347328}

er1646v2LacpBVlanIpPimOverrideInterval OBJECT-TYPE
   SYNTAX      TimeTicks
   MAX-ACCESS  read-write
   STATUS      current
   DESCRIPTION
      "Path: lacpBundle.editConf.vlan.ip.pim.overrideInterval

       Time in centi-second."
   ::= {er1646v2LacpBVlanEntry 53347584}

er1646v2LacpBVlanIpPimBsrBorder OBJECT-TYPE
   SYNTAX      INTEGER
               {
               disabled (0),
               enabled (1)
               }
   MAX-ACCESS  read-write
   STATUS      current
   DESCRIPTION
      "Path: lacpBundle.editConf.vlan.ip.pim.bsrBorder

       Possibilities:
               disabled   (0)
               enabled   (1)"
   ::= {er1646v2LacpBVlanEntry 53347840}

er1646v2LacpBVlanIpPimTtlThreshold OBJECT-TYPE
   SYNTAX      Integer32
   MAX-ACCESS  read-write
   STATUS      current
   DESCRIPTION
      "Path: lacpBundle.editConf.vlan.ip.pim.ttlThreshold"
   ::= {er1646v2LacpBVlanEntry 53348096}

er1646v2LacpBVlanIpIMNetworkUnreachable OBJECT-TYPE
   SYNTAX      INTEGER
               {
               disabled (0),
               enabled (1)
               }
   MAX-ACCESS  read-write
   STATUS      current
   DESCRIPTION
      "Path: lacpBundle.editConf.vlan.ip.icmpMessages.networkUnreachable

       Possibilities:
               disabled   (0)
               enabled   (1)"
   ::= {er1646v2LacpBVlanEntry 53412096}

er1646v2LacpBVlanIpIMHostUnreachable OBJECT-TYPE
   SYNTAX      INTEGER
               {
               disabled (0),
               enabled (1)
               }
   MAX-ACCESS  read-write
   STATUS      current
   DESCRIPTION
      "Path: lacpBundle.editConf.vlan.ip.icmpMessages.hostUnreachable

       Possibilities:
               disabled   (0)
               enabled   (1)"
   ::= {er1646v2LacpBVlanEntry 53412352}

er1646v2LacpBVlanIpIMProtocolUnreachable OBJECT-TYPE
   SYNTAX      INTEGER
               {
               disabled (0),
               enabled (1)
               }
   MAX-ACCESS  read-write
   STATUS      current
   DESCRIPTION
      "Path: lacpBundle.editConf.vlan.ip.icmpMessages.protocolUnreachable

       Possibilities:
               disabled   (0)
               enabled   (1)"
   ::= {er1646v2LacpBVlanEntry 53412608}

er1646v2LacpBVlanIpIMPortUnreachable OBJECT-TYPE
   SYNTAX      INTEGER
               {
               disabled (0),
               enabled (1)
               }
   MAX-ACCESS  read-write
   STATUS      current
   DESCRIPTION
      "Path: lacpBundle.editConf.vlan.ip.icmpMessages.portUnreachable

       Possibilities:
               disabled   (0)
               enabled   (1)"
   ::= {er1646v2LacpBVlanEntry 53412864}

er1646v2LacpBVlanIpIMMtuExceeded OBJECT-TYPE
   SYNTAX      INTEGER
               {
               disabled (0),
               enabled (1)
               }
   MAX-ACCESS  read-write
   STATUS      current
   DESCRIPTION
      "Path: lacpBundle.editConf.vlan.ip.icmpMessages.mtuExceeded

       Possibilities:
               disabled   (0)
               enabled   (1)"
   ::= {er1646v2LacpBVlanEntry 53413120}

er1646v2LacpBVlanIpIMAdminProhibited OBJECT-TYPE
   SYNTAX      INTEGER
               {
               disabled (0),
               enabled (1)
               }
   MAX-ACCESS  read-write
   STATUS      current
   DESCRIPTION
      "Path: lacpBundle.editConf.vlan.ip.icmpMessages.adminProhibited

       Possibilities:
               disabled   (0)
               enabled   (1)"
   ::= {er1646v2LacpBVlanEntry 53413376}

er1646v2LacpBVlanIpIMTtlExceeded OBJECT-TYPE
   SYNTAX      INTEGER
               {
               disabled (0),
               enabled (1)
               }
   MAX-ACCESS  read-write
   STATUS      current
   DESCRIPTION
      "Path: lacpBundle.editConf.vlan.ip.icmpMessages.ttlExceeded

       Possibilities:
               disabled   (0)
               enabled   (1)"
   ::= {er1646v2LacpBVlanEntry 53413632}

er1646v2LacpBVlanIpIMRedirect OBJECT-TYPE
   SYNTAX      INTEGER
               {
               disabled (0),
               enabled (1)
               }
   MAX-ACCESS  read-write
   STATUS      current
   DESCRIPTION
      "Path: lacpBundle.editConf.vlan.ip.icmpMessages.redirect

       Possibilities:
               disabled   (0)
               enabled   (1)"
   ::= {er1646v2LacpBVlanEntry 53413888}

er1646v2LacpBVlanIpV6VrfRouter OBJECT-TYPE
   SYNTAX      DisplayString
   MAX-ACCESS  read-write
   STATUS      current
   DESCRIPTION
      "Path: lacpBundle.editConf.vlan.ipV6.vrfRouter"
   ::= {er1646v2LacpBVlanEntry 704708608}

er1646v2LacpBVlanIpV6AddrAutoConfigNrDupAddrDetects OBJECT-TYPE
   SYNTAX      Integer32
   MAX-ACCESS  read-write
   STATUS      current
   DESCRIPTION
      "Path: lacpBundle.editConf.vlan.ipV6.addrAutoConfig.nrDupAddrDetects"
   ::= {er1646v2LacpBVlanEntry 704905472}

er1646v2LacpBVlanIpV6AddrAutoConfigAcceptRa OBJECT-TYPE
   SYNTAX      INTEGER
               {
               disabled (0),
               enabled (1)
               }
   MAX-ACCESS  read-write
   STATUS      current
   DESCRIPTION
      "Path: lacpBundle.editConf.vlan.ipV6.addrAutoConfig.acceptRa

       Possibilities:
               disabled   (0)
               enabled   (1)"
   ::= {er1646v2LacpBVlanEntry 704905728}

er1646v2LacpBVlanIpV6AddrAutoConfigAcceptRaRdnss OBJECT-TYPE
   SYNTAX      INTEGER
               {
               disabled (0),
               enabled (1)
               }
   MAX-ACCESS  read-write
   STATUS      current
   DESCRIPTION
      "Path: lacpBundle.editConf.vlan.ipV6.addrAutoConfig.acceptRaRdnss

       Possibilities:
               disabled   (0)
               enabled   (1)"
   ::= {er1646v2LacpBVlanEntry 704905984}

er1646v2LacpBVlanIpV6AddrAutoConfigAcceptRaDnssl OBJECT-TYPE
   SYNTAX      INTEGER
               {
               disabled (0),
               enabled (1)
               }
   MAX-ACCESS  read-write
   STATUS      current
   DESCRIPTION
      "Path: lacpBundle.editConf.vlan.ipV6.addrAutoConfig.acceptRaDnssl

       Possibilities:
               disabled   (0)
               enabled   (1)"
   ::= {er1646v2LacpBVlanEntry 704906240}

er1646v2LacpBVlanIpV6DefaultRoute OBJECT-TYPE
   SYNTAX      INTEGER
               {
               disabled (0),
               enabled (1)
               }
   MAX-ACCESS  read-write
   STATUS      current
   DESCRIPTION
      "Path: lacpBundle.editConf.vlan.ipV6.defaultRoute

       Possibilities:
               disabled   (0)
               enabled   (1)"
   ::= {er1646v2LacpBVlanEntry 704970752}

er1646v2LacpBVlanIpV6RaSend OBJECT-TYPE
   SYNTAX      INTEGER
               {
               disabled (0),
               enabled (1)
               }
   MAX-ACCESS  read-write
   STATUS      current
   DESCRIPTION
      "Path: lacpBundle.editConf.vlan.ipV6.ra.send

       Possibilities:
               disabled   (0)
               enabled   (1)"
   ::= {er1646v2LacpBVlanEntry 705036544}

er1646v2LacpBVlanIpV6RaMinInterval OBJECT-TYPE
   SYNTAX      TimeTicks
   MAX-ACCESS  read-write
   STATUS      current
   DESCRIPTION
      "Path: lacpBundle.editConf.vlan.ipV6.ra.minInterval

       Time in centi-second."
   ::= {er1646v2LacpBVlanEntry 705036800}

er1646v2LacpBVlanIpV6RaMaxInterval OBJECT-TYPE
   SYNTAX      TimeTicks
   MAX-ACCESS  read-write
   STATUS      current
   DESCRIPTION
      "Path: lacpBundle.editConf.vlan.ipV6.ra.maxInterval

       Time in centi-second."
   ::= {er1646v2LacpBVlanEntry 705037056}

er1646v2LacpBVlanIpV6RaManagedFlag OBJECT-TYPE
   SYNTAX      INTEGER
               {
               disabled (0),
               enabled (1)
               }
   MAX-ACCESS  read-write
   STATUS      current
   DESCRIPTION
      "Path: lacpBundle.editConf.vlan.ipV6.ra.managedFlag

       Possibilities:
               disabled   (0)
               enabled   (1)"
   ::= {er1646v2LacpBVlanEntry 705037312}

er1646v2LacpBVlanIpV6RaOtherConfFlag OBJECT-TYPE
   SYNTAX      INTEGER
               {
               disabled (0),
               enabled (1)
               }
   MAX-ACCESS  read-write
   STATUS      current
   DESCRIPTION
      "Path: lacpBundle.editConf.vlan.ipV6.ra.otherConfFlag

       Possibilities:
               disabled   (0)
               enabled   (1)"
   ::= {er1646v2LacpBVlanEntry 705037568}

er1646v2LacpBVlanIpV6RaLinkMtu OBJECT-TYPE
   SYNTAX      Integer32
   MAX-ACCESS  read-write
   STATUS      current
   DESCRIPTION
      "Path: lacpBundle.editConf.vlan.ipV6.ra.linkMtu"
   ::= {er1646v2LacpBVlanEntry 705037824}

er1646v2LacpBVlanIpV6RaReachableTime OBJECT-TYPE
   SYNTAX      TimeTicks
   MAX-ACCESS  read-write
   STATUS      current
   DESCRIPTION
      "Path: lacpBundle.editConf.vlan.ipV6.ra.reachableTime

       Time in centi-second."
   ::= {er1646v2LacpBVlanEntry 705038080}

er1646v2LacpBVlanIpV6RaRetransmitTime OBJECT-TYPE
   SYNTAX      TimeTicks
   MAX-ACCESS  read-write
   STATUS      current
   DESCRIPTION
      "Path: lacpBundle.editConf.vlan.ipV6.ra.retransmitTime

       Time in centi-second."
   ::= {er1646v2LacpBVlanEntry 705038336}

er1646v2LacpBVlanIpV6RaHopLimit OBJECT-TYPE
   SYNTAX      Integer32
   MAX-ACCESS  read-write
   STATUS      current
   DESCRIPTION
      "Path: lacpBundle.editConf.vlan.ipV6.ra.hopLimit"
   ::= {er1646v2LacpBVlanEntry 705038592}

er1646v2LacpBVlanIpV6RaDefaultLifeTime OBJECT-TYPE
   SYNTAX      TimeTicks
   MAX-ACCESS  read-write
   STATUS      current
   DESCRIPTION
      "Path: lacpBundle.editConf.vlan.ipV6.ra.defaultLifeTime

       Time in centi-second."
   ::= {er1646v2LacpBVlanEntry 705038848}

er1646v2LacpBVlanIpV6RaDnsOptionsRdnssLifeTime OBJECT-TYPE
   SYNTAX      TimeTicks
   MAX-ACCESS  read-write
   STATUS      current
   DESCRIPTION
      "Path: lacpBundle.editConf.vlan.ipV6.ra.dnsOptions.rdnss.lifeTime

       Time in centi-second."
   ::= {er1646v2LacpBVlanEntry 705039140}

er1646v2LacpBVlanIpV6RaDnsOptionsRdnssImportServers OBJECT-TYPE
   SYNTAX      INTEGER
               {
               disabled (0),
               enabled (1)
               }
   MAX-ACCESS  read-write
   STATUS      current
   DESCRIPTION
      "Path: lacpBundle.editConf.vlan.ipV6.ra.dnsOptions.rdnss.importServers

       Possibilities:
               disabled   (0)
               enabled   (1)"
   ::= {er1646v2LacpBVlanEntry 705039148}

er1646v2LacpBVlanIpV6RaDnsOptionsDnsslLifeTime OBJECT-TYPE
   SYNTAX      TimeTicks
   MAX-ACCESS  read-write
   STATUS      current
   DESCRIPTION
      "Path: lacpBundle.editConf.vlan.ipV6.ra.dnsOptions.dnssl.lifeTime

       Time in centi-second."
   ::= {er1646v2LacpBVlanEntry 705039172}

er1646v2LacpBVlanIpV6RaDnsOptionsDnsslImportDomains OBJECT-TYPE
   SYNTAX      INTEGER
               {
               disabled (0),
               enabled (1)
               }
   MAX-ACCESS  read-write
   STATUS      current
   DESCRIPTION
      "Path: lacpBundle.editConf.vlan.ipV6.ra.dnsOptions.dnssl.importDomains

       Possibilities:
               disabled   (0)
               enabled   (1)"
   ::= {er1646v2LacpBVlanEntry 705039180}

er1646v2LacpBVlanIpV6RsSend OBJECT-TYPE
   SYNTAX      INTEGER
               {
               disabled (0),
               enabled (1)
               }
   MAX-ACCESS  read-write
   STATUS      current
   DESCRIPTION
      "Path: lacpBundle.editConf.vlan.ipV6.rs.send

       Possibilities:
               disabled   (0)
               enabled   (1)"
   ::= {er1646v2LacpBVlanEntry 705954048}

er1646v2LacpBVlanIpV6RsMaxRandomDelay OBJECT-TYPE
   SYNTAX      TimeTicks
   MAX-ACCESS  read-write
   STATUS      current
   DESCRIPTION
      "Path: lacpBundle.editConf.vlan.ipV6.rs.maxRandomDelay

       Time in centi-second."
   ::= {er1646v2LacpBVlanEntry 705954304}

er1646v2LacpBVlanIpV6RsInterval OBJECT-TYPE
   SYNTAX      TimeTicks
   MAX-ACCESS  read-write
   STATUS      current
   DESCRIPTION
      "Path: lacpBundle.editConf.vlan.ipV6.rs.interval

       Time in centi-second."
   ::= {er1646v2LacpBVlanEntry 705954560}

er1646v2LacpBVlanIpV6RsMaxSolicitations OBJECT-TYPE
   SYNTAX      Integer32
   MAX-ACCESS  read-write
   STATUS      current
   DESCRIPTION
      "Path: lacpBundle.editConf.vlan.ipV6.rs.maxSolicitations"
   ::= {er1646v2LacpBVlanEntry 705954816}

er1646v2LacpBVlanIpV6TrafficPolicyInbound OBJECT-TYPE
   SYNTAX      DisplayString
   MAX-ACCESS  read-write
   STATUS      current
   DESCRIPTION
      "Path: lacpBundle.editConf.vlan.ipV6.trafficPolicy.inbound"
   ::= {er1646v2LacpBVlanEntry 705364224}

er1646v2LacpBVlanIpV6TrafficPolicyOutbound OBJECT-TYPE
   SYNTAX      DisplayString
   MAX-ACCESS  read-write
   STATUS      current
   DESCRIPTION
      "Path: lacpBundle.editConf.vlan.ipV6.trafficPolicy.outbound"
   ::= {er1646v2LacpBVlanEntry 705364480}

er1646v2LacpBVlanIpV6FirewallZone OBJECT-TYPE
   SYNTAX      DisplayString
   MAX-ACCESS  read-write
   STATUS      current
   DESCRIPTION
      "Path: lacpBundle.editConf.vlan.ipV6.firewall.zone"
   ::= {er1646v2LacpBVlanEntry 705429760}

er1646v2LacpBVlanIpV6DhcpClientAddrAC OBJECT-TYPE
   SYNTAX      INTEGER
               {
               disabled (0),
               enabled (1)
               }
   MAX-ACCESS  read-write
   STATUS      current
   DESCRIPTION
      "Path: lacpBundle.editConf.vlan.ipV6.dhcp.client.addrAutoConfig

       Possibilities:
               disabled   (0)
               enabled   (1)"
   ::= {er1646v2LacpBVlanEntry 705307648}

er1646v2LacpBVlanIpV6DhcpClientPrDelMode OBJECT-TYPE
   SYNTAX      INTEGER
               {
               disabled (0),
               enabled (1)
               }
   MAX-ACCESS  read-write
   STATUS      current
   DESCRIPTION
      "Path: lacpBundle.editConf.vlan.ipV6.dhcp.client.pd.mode

       Possibilities:
               disabled   (0)
               enabled   (1)"
   ::= {er1646v2LacpBVlanEntry 705308676}

er1646v2LacpBVlanIpV6DhcpClientPrDelPool OBJECT-TYPE
   SYNTAX      DisplayString
   MAX-ACCESS  read-write
   STATUS      current
   DESCRIPTION
      "Path: lacpBundle.editConf.vlan.ipV6.dhcp.client.pd.pool"
   ::= {er1646v2LacpBVlanEntry 705308680}

er1646v2LacpBVlanIpV6DhcpClientPrDelPdExclOpt OBJECT-TYPE
   SYNTAX      INTEGER
               {
               disabled (0),
               enabled (1)
               }
   MAX-ACCESS  read-write
   STATUS      current
   DESCRIPTION
      "Path: lacpBundle.editConf.vlan.ipV6.dhcp.client.pd.pdExclOpt

       Possibilities:
               disabled   (0)
               enabled   (1)"
   ::= {er1646v2LacpBVlanEntry 705308684}

er1646v2LacpBVlanIpV6DhcpClientDnsServerPref OBJECT-TYPE
   SYNTAX      Integer32
   MAX-ACCESS  read-write
   STATUS      current
   DESCRIPTION
      "Path: lacpBundle.editConf.vlan.ipV6.dhcp.client.dns.serverPref"
   ::= {er1646v2LacpBVlanEntry 705310724}

er1646v2LacpBVlanIpV6DhcpClientRapidCommit OBJECT-TYPE
   SYNTAX      INTEGER
               {
               disabled (0),
               enabled (1)
               }
   MAX-ACCESS  read-write
   STATUS      current
   DESCRIPTION
      "Path: lacpBundle.editConf.vlan.ipV6.dhcp.client.rapidCommit

       Possibilities:
               disabled   (0)
               enabled   (1)"
   ::= {er1646v2LacpBVlanEntry 705309696}

er1646v2LacpBVlanIpV6DhcpClientTimersSolTimeOut OBJECT-TYPE
   SYNTAX      TimeTicks
   MAX-ACCESS  read-write
   STATUS      current
   DESCRIPTION
      "Path: lacpBundle.editConf.vlan.ipV6.dhcp.client.timers.solTimeOut

       Time in centi-second."
   ::= {er1646v2LacpBVlanEntry 705311748}

er1646v2LacpBVlanIpV6DhcpClientTimersSolMaxRt OBJECT-TYPE
   SYNTAX      TimeTicks
   MAX-ACCESS  read-write
   STATUS      current
   DESCRIPTION
      "Path: lacpBundle.editConf.vlan.ipV6.dhcp.client.timers.solMaxRt

       Time in centi-second."
   ::= {er1646v2LacpBVlanEntry 705311752}

er1646v2LacpBVlanIpV6DhcpClientTimersInfoRefresh OBJECT-TYPE
   SYNTAX      TimeTicks
   MAX-ACCESS  read-write
   STATUS      current
   DESCRIPTION
      "Path: lacpBundle.editConf.vlan.ipV6.dhcp.client.timers.infoRefresh

       Time in centi-second."
   ::= {er1646v2LacpBVlanEntry 705311756}

er1646v2LacpBVlanIpV6DhcpServerMode OBJECT-TYPE
   SYNTAX      INTEGER
               {
               disabled (0),
               enabled (1)
               }
   MAX-ACCESS  read-write
   STATUS      current
   DESCRIPTION
      "Path: lacpBundle.editConf.vlan.ipV6.dhcp.server.mode

       Possibilities:
               disabled   (0)
               enabled   (1)"
   ::= {er1646v2LacpBVlanEntry 705315840}

er1646v2LacpBVlanIpV6DhcpServerPreference OBJECT-TYPE
   SYNTAX      Integer32
   MAX-ACCESS  read-write
   STATUS      current
   DESCRIPTION
      "Path: lacpBundle.editConf.vlan.ipV6.dhcp.server.preference"
   ::= {er1646v2LacpBVlanEntry 705316864}

er1646v2LacpBVlanIpV6DhcpServerPool OBJECT-TYPE
   SYNTAX      DisplayString
   MAX-ACCESS  read-write
   STATUS      current
   DESCRIPTION
      "Path: lacpBundle.editConf.vlan.ipV6.dhcp.server.pool"
   ::= {er1646v2LacpBVlanEntry 705317888}

er1646v2LacpBVlanIpV6DhcpServerRapidCommit OBJECT-TYPE
   SYNTAX      INTEGER
               {
               disabled (0),
               enabled (1)
               }
   MAX-ACCESS  read-write
   STATUS      current
   DESCRIPTION
      "Path: lacpBundle.editConf.vlan.ipV6.dhcp.server.rapidCommit

       Possibilities:
               disabled   (0)
               enabled   (1)"
   ::= {er1646v2LacpBVlanEntry 705318912}

er1646v2LacpBVlanIpV6DhcpServerTimersInfoRefresh OBJECT-TYPE
   SYNTAX      TimeTicks
   MAX-ACCESS  read-write
   STATUS      current
   DESCRIPTION
      "Path: lacpBundle.editConf.vlan.ipV6.dhcp.server.timers.infoRefresh

       Time in centi-second."
   ::= {er1646v2LacpBVlanEntry 705319940}

er1646v2LacpBVlanIpV6DhcpRelayMode OBJECT-TYPE
   SYNTAX      INTEGER
               {
               disabled (0),
               enabled (1)
               }
   MAX-ACCESS  read-write
   STATUS      current
   DESCRIPTION
      "Path: lacpBundle.editConf.vlan.ipV6.dhcp.relay.mode

       Possibilities:
               disabled   (0)
               enabled   (1)"
   ::= {er1646v2LacpBVlanEntry 705323040}

er1646v2LacpBVlanIpV6SendRedirect OBJECT-TYPE
   SYNTAX      INTEGER
               {
               disabled (0),
               enabled (1)
               }
   MAX-ACCESS  read-write
   STATUS      current
   DESCRIPTION
      "Path: lacpBundle.editConf.vlan.ipV6.sendRedirect

       Possibilities:
               disabled   (0)
               enabled   (1)"
   ::= {er1646v2LacpBVlanEntry 705101824}

er1646v2LacpBVlanIpV6LinkMtu OBJECT-TYPE
   SYNTAX      Integer32
   MAX-ACCESS  read-write
   STATUS      current
   DESCRIPTION
      "Path: lacpBundle.editConf.vlan.ipV6.linkMtu"
   ::= {er1646v2LacpBVlanEntry 705167360}

er1646v2LacpBVlanIpV6InterfaceId OBJECT-TYPE
   SYNTAX      OCTET STRING
   MAX-ACCESS  read-write
   STATUS      current
   DESCRIPTION
      "Path: lacpBundle.editConf.vlan.ipV6.interfaceId"
   ::= {er1646v2LacpBVlanEntry 705232896}

er1646v2LacpBVlanIpV6MF OBJECT-TYPE
   SYNTAX      Integer32
   MAX-ACCESS  read-write
   STATUS      current
   DESCRIPTION
      "Path: lacpBundle.editConf.vlan.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1646v2LacpBVlanEntry 705757184}

er1646v2LacpBVlanIpV6IcmpMessagesNoRoute OBJECT-TYPE
   SYNTAX      INTEGER
               {
               disabled (0),
               enabled (1)
               }
   MAX-ACCESS  read-write
   STATUS      current
   DESCRIPTION
      "Path: lacpBundle.editConf.vlan.ipV6.icmpMessages.noRoute

       Possibilities:
               disabled   (0)
               enabled   (1)"
   ::= {er1646v2LacpBVlanEntry 705822976}

er1646v2LacpBVlanIpV6IcmpMessagesBeyondScope OBJECT-TYPE
   SYNTAX      INTEGER
               {
               disabled (0),
               enabled (1)
               }
   MAX-ACCESS  read-write
   STATUS      current
   DESCRIPTION
      "Path: lacpBundle.editConf.vlan.ipV6.icmpMessages.beyondScope

       Possibilities:
               disabled   (0)
               enabled   (1)"
   ::= {er1646v2LacpBVlanEntry 705823488}

er1646v2LacpBVlanIpV6IcmpMessagesAddressUnreachable OBJECT-TYPE
   SYNTAX      INTEGER
               {
               disabled (0),
               enabled (1)
               }
   MAX-ACCESS  read-write
   STATUS      current
   DESCRIPTION
      "Path: lacpBundle.editConf.vlan.ipV6.icmpMessages.addressUnreachable

       Possibilities:
               disabled   (0)
               enabled   (1)"
   ::= {er1646v2LacpBVlanEntry 705823744}

er1646v2LacpBVlanIpV6IcmpMessagesPortUnreachable OBJECT-TYPE
   SYNTAX      INTEGER
               {
               disabled (0),
               enabled (1)
               }
   MAX-ACCESS  read-write
   STATUS      current
   DESCRIPTION
      "Path: lacpBundle.editConf.vlan.ipV6.icmpMessages.portUnreachable

       Possibilities:
               disabled   (0)
               enabled   (1)"
   ::= {er1646v2LacpBVlanEntry 705824000}

er1646v2LacpBVlanIpV6IcmpMessagesPacketTooBig OBJECT-TYPE
   SYNTAX      INTEGER
               {
               disabled (0),
               enabled (1)
               }
   MAX-ACCESS  read-write
   STATUS      current
   DESCRIPTION
      "Path: lacpBundle.editConf.vlan.ipV6.icmpMessages.packetTooBig

       Possibilities:
               disabled   (0)
               enabled   (1)"
   ::= {er1646v2LacpBVlanEntry 705825280}

er1646v2LacpBVlanIpV6IcmpMessagesHopLimitExceeded OBJECT-TYPE
   SYNTAX      INTEGER
               {
               disabled (0),
               enabled (1)
               }
   MAX-ACCESS  read-write
   STATUS      current
   DESCRIPTION
      "Path: lacpBundle.editConf.vlan.ipV6.icmpMessages.hopLimitExceeded

       Possibilities:
               disabled   (0)
               enabled   (1)"
   ::= {er1646v2LacpBVlanEntry 705827840}

er1646v2LacpBVlanIpV6IcmpMessagesFragTimeExceeded OBJECT-TYPE
   SYNTAX      INTEGER
               {
               disabled (0),
               enabled (1)
               }
   MAX-ACCESS  read-write
   STATUS      current
   DESCRIPTION
      "Path: lacpBundle.editConf.vlan.ipV6.icmpMessages.fragTimeExceeded

       Possibilities:
               disabled   (0)
               enabled   (1)"
   ::= {er1646v2LacpBVlanEntry 705828096}

er1646v2LacpBVlanIpV6IcmpMessagesHeaderFieldErr OBJECT-TYPE
   SYNTAX      INTEGER
               {
               disabled (0),
               enabled (1)
               }
   MAX-ACCESS  read-write
   STATUS      current
   DESCRIPTION
      "Path: lacpBundle.editConf.vlan.ipV6.icmpMessages.headerFieldErr

       Possibilities:
               disabled   (0)
               enabled   (1)"
   ::= {er1646v2LacpBVlanEntry 705830400}

er1646v2LacpBVlanIpV6IcmpMessagesOptionUnrecognized OBJECT-TYPE
   SYNTAX      INTEGER
               {
               disabled (0),
               enabled (1)
               }
   MAX-ACCESS  read-write
   STATUS      current
   DESCRIPTION
      "Path: lacpBundle.editConf.vlan.ipV6.icmpMessages.optionUnrecognized

       Possibilities:
               disabled   (0)
               enabled   (1)"
   ::= {er1646v2LacpBVlanEntry 705830912}

er1646v2LacpBVlanIpV6IcmpMessagesRedirect OBJECT-TYPE
   SYNTAX      INTEGER
               {
               disabled (0),
               enabled (1)
               }
   MAX-ACCESS  read-write
   STATUS      current
   DESCRIPTION
      "Path: lacpBundle.editConf.vlan.ipV6.icmpMessages.redirect

       Possibilities:
               disabled   (0)
               enabled   (1)"
   ::= {er1646v2LacpBVlanEntry 705832960}

er1646v2LacpBVlanBridgingAccList OBJECT-TYPE
   SYNTAX      DisplayString
   MAX-ACCESS  read-write
   STATUS      current
   DESCRIPTION
      "Path: lacpBundle.editConf.vlan.bridging.accessList"
   ::= {er1646v2LacpBVlanEntry 453246976}

er1646v2LacpBVlanBridgingInACL OBJECT-TYPE
   SYNTAX      DisplayString
   MAX-ACCESS  read-write
   STATUS      current
   DESCRIPTION
      "Path: lacpBundle.editConf.vlan.bridging.inAccessList"
   ::= {er1646v2LacpBVlanEntry 456916992}

er1646v2LacpBVlanBridgingTp OBJECT-TYPE
   SYNTAX      DisplayString
   MAX-ACCESS  read-write
   STATUS      current
   DESCRIPTION
      "Path: lacpBundle.editConf.vlan.bridging.trafficPolicy"
   ::= {er1646v2LacpBVlanEntry 454295552}

er1646v2LacpBVlanBridgingBrGrp OBJECT-TYPE
   SYNTAX      DisplayString
   MAX-ACCESS  read-write
   STATUS      current
   DESCRIPTION
      "Path: lacpBundle.editConf.vlan.bridging.bridgeGroup"
   ::= {er1646v2LacpBVlanEntry 454819840}

er1646v2LacpBVlanBridgingLimBC OBJECT-TYPE
   SYNTAX      INTEGER
               {
               disabled (0),
               enabled (1)
               }
   MAX-ACCESS  read-write
   STATUS      current
   DESCRIPTION
      "Path: lacpBundle.editConf.vlan.bridging.limitBroadcasts

       Possibilities:
               disabled   (0)
               enabled   (1)"
   ::= {er1646v2LacpBVlanEntry 455081984}

er1646v2LacpBVlanBridgingPrivateMode OBJECT-TYPE
   SYNTAX      INTEGER
               {
               disabled (0),
               enabled (1)
               }
   MAX-ACCESS  read-write
   STATUS      current
   DESCRIPTION
      "Path: lacpBundle.editConf.vlan.bridging.privateMode

       Possibilities:
               disabled   (0)
               enabled   (1)"
   ::= {er1646v2LacpBVlanEntry 459538432}

er1646v2LacpBVlanBridgingLearning OBJECT-TYPE
   SYNTAX      INTEGER
               {
               disabled (0),
               enabled (1)
               }
   MAX-ACCESS  read-write
   STATUS      current
   DESCRIPTION
      "Path: lacpBundle.editConf.vlan.bridging.learning

       Possibilities:
               disabled   (0)
               enabled   (1)"
   ::= {er1646v2LacpBVlanEntry 456130560}

er1646v2LacpBVlanBridgingMaxCacheSize OBJECT-TYPE
   SYNTAX      INTEGER
               {
               unlimited (0)
               }
   MAX-ACCESS  read-write
   STATUS      current
   DESCRIPTION
      "Path: lacpBundle.editConf.vlan.bridging.maxCacheSize

       Possibilities:
               unlimited   (0)"
   ::= {er1646v2LacpBVlanEntry 456392704}

er1646v2LacpBVlanBridgingRelearnDropOnRelearn OBJECT-TYPE
   SYNTAX      INTEGER
               {
               disabled (0),
               enabled (1)
               }
   MAX-ACCESS  read-write
   STATUS      current
   DESCRIPTION
      "Path: lacpBundle.editConf.vlan.bridging.relearn.dropOnRelearn

       Possibilities:
               disabled   (0)
               enabled   (1)"
   ::= {er1646v2LacpBVlanEntry 456655872}

er1646v2LacpBVlanBridgingRelearnShutdownThreshold OBJECT-TYPE
   SYNTAX      Integer32
   MAX-ACCESS  read-write
   STATUS      current
   DESCRIPTION
      "Path: lacpBundle.editConf.vlan.bridging.relearn.shutdownThreshold"
   ::= {er1646v2LacpBVlanEntry 456656896}

er1646v2LacpBVlanBridgingRelearnShutdownTime OBJECT-TYPE
   SYNTAX      TimeTicks
   MAX-ACCESS  read-write
   STATUS      current
   DESCRIPTION
      "Path: lacpBundle.editConf.vlan.bridging.relearn.shutdownTime

       Time in centi-second."
   ::= {er1646v2LacpBVlanEntry 456657920}

er1646v2LacpBVlanBridgingRelearnLoopDetection OBJECT-TYPE
   SYNTAX      INTEGER
               {
               disabled (0),
               passive (1),
               active (2)
               }
   MAX-ACCESS  read-write
   STATUS      current
   DESCRIPTION
      "Path: lacpBundle.editConf.vlan.bridging.relearn.loopDetection

       Possibilities:
               disabled   (0)
               passive   (1)
               active   (2)"
   ::= {er1646v2LacpBVlanEntry 456658944}

er1646v2LacpBVlanBridgingRelearnLoopDetectionInterval OBJECT-TYPE
   SYNTAX      TimeTicks
   MAX-ACCESS  read-write
   STATUS      current
   DESCRIPTION
      "Path: lacpBundle.editConf.vlan.bridging.relearn.loopDetectionInterval

       Time in centi-second."
   ::= {er1646v2LacpBVlanEntry 456659968}

er1646v2LacpBVlanBridgingVlanMemberShip OBJECT-TYPE
   SYNTAX      INTEGER
               {
               all (0),
               none (1),
               grouped (2)
               }
   MAX-ACCESS  read-write
   STATUS      current
   DESCRIPTION
      "Path: lacpBundle.editConf.vlan.bridging.vlanMemberShip

       Possibilities:
               all   (0)
               none   (1)
               grouped   (2)"
   ::= {er1646v2LacpBVlanEntry 457965568}

er1646v2LacpBVlanBridgingVlTUntaggedAction OBJECT-TYPE
   SYNTAX      INTEGER
               {
               discard (0),
               accept (1),
               tag (2)
               }
   MAX-ACCESS  read-write
   STATUS      current
   DESCRIPTION
      "Path: lacpBundle.editConf.vlan.bridging.vlanTagging.untagged.action

       Possibilities:
               discard   (0)
               accept   (1)
               tag   (2)"
   ::= {er1646v2LacpBVlanEntry 459055104}

er1646v2LacpBVlanBridgingVlTUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: lacpBundle.editConf.vlan.bridging.vlanTagging.untagged.tagInfo.tpid

       Possibilities:
               dot1Q   (33024)
               dot1ad   (34984)
               0x9100   (37120)
               0x9200   (37376)
               0x9300   (37632)"
   ::= {er1646v2LacpBVlanEntry 459059712}

er1646v2LacpBVlanBridgingVlTUntaggedTagInfoVid OBJECT-TYPE
   SYNTAX      Integer32
   MAX-ACCESS  read-write
   STATUS      current
   DESCRIPTION
      "Path: lacpBundle.editConf.vlan.bridging.vlanTagging.untagged.tagInfo.vid"
   ::= {er1646v2LacpBVlanEntry 459060224}

er1646v2LacpBVlanBridgingVlTUnknownVlansAction OBJECT-TYPE
   SYNTAX      INTEGER
               {
               discard (0),
               accept (1),
               tag (2)
               }
   MAX-ACCESS  read-write
   STATUS      current
   DESCRIPTION
      "Path: lacpBundle.editConf.vlan.bridging.vlanTagging.unknownVlans.action

       Possibilities:
               discard   (0)
               accept   (1)
               tag   (2)"
   ::= {er1646v2LacpBVlanEntry 459120640}

er1646v2LacpBVlanBridgingVlTUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: lacpBundle.editConf.vlan.bridging.vlanTagging.unknownVlans.tagInfo.tpid

       Possibilities:
               dot1Q   (33024)
               dot1ad   (34984)
               0x9100   (37120)
               0x9200   (37376)
               0x9300   (37632)"
   ::= {er1646v2LacpBVlanEntry 459125248}

er1646v2LacpBVlanBridgingVlTUnknownVlansTagInfoVid OBJECT-TYPE
   SYNTAX      Integer32
   MAX-ACCESS  read-write
   STATUS      current
   DESCRIPTION
      "Path: lacpBundle.editConf.vlan.bridging.vlanTagging.unknownVlans.tagInfo.vid"
   ::= {er1646v2LacpBVlanEntry 459125760}

er1646v2LacpBVlanBridgingDot1adType OBJECT-TYPE
   SYNTAX      INTEGER
               {
               slOPTg (0),
               cPort (4),
               sPort (1),
               nni (2)
               }
   MAX-ACCESS  read-write
   STATUS      current
   DESCRIPTION
      "Path: lacpBundle.editConf.vlan.bridging.dot1ad.type

       Possibilities:
               <OPT>   (0)
               cPort   (4)
               sPort   (1)
               nni   (2)"
   ::= {er1646v2LacpBVlanEntry 460850176}

er1646v2LacpBVlanBridgingPriority OBJECT-TYPE
   SYNTAX      Integer32
   MAX-ACCESS  read-write
   STATUS      current
   DESCRIPTION
      "Path: lacpBundle.editConf.vlan.bridging.priority"
   ::= {er1646v2LacpBVlanEntry 453509120}

er1646v2LacpBVlanBridgingPathCost OBJECT-TYPE
   SYNTAX      Integer32
   MAX-ACCESS  read-write
   STATUS      current
   DESCRIPTION
      "Path: lacpBundle.editConf.vlan.bridging.pathCost"
   ::= {er1646v2LacpBVlanEntry 453771264}

er1646v2LacpBVlanBridgingInternalPathCost OBJECT-TYPE
   SYNTAX      Integer32
   MAX-ACCESS  read-write
   STATUS      current
   DESCRIPTION
      "Path: lacpBundle.editConf.vlan.bridging.internalPathCost"
   ::= {er1646v2LacpBVlanEntry 457703424}

er1646v2LacpBVlanBridgingTCD OBJECT-TYPE
   SYNTAX      INTEGER
               {
               disabled (0),
               enabled (1)
               }
   MAX-ACCESS  read-write
   STATUS      current
   DESCRIPTION
      "Path: lacpBundle.editConf.vlan.bridging.topologyChangeDetection

       Possibilities:
               disabled   (0)
               enabled   (1)"
   ::= {er1646v2LacpBVlanEntry 454033408}

er1646v2LacpBVlanBridgingRestrictedRole OBJECT-TYPE
   SYNTAX      INTEGER
               {
               disabled (0),
               enabled (1)
               }
   MAX-ACCESS  read-write
   STATUS      current
   DESCRIPTION
      "Path: lacpBundle.editConf.vlan.bridging.restrictedRole

       Possibilities:
               disabled   (0)
               enabled   (1)"
   ::= {er1646v2LacpBVlanEntry 458227712}

er1646v2LacpBVlanBridgingAdminEdge OBJECT-TYPE
   SYNTAX      INTEGER
               {
               disabled (0),
               enabled (1)
               }
   MAX-ACCESS  read-write
   STATUS      current
   DESCRIPTION
      "Path: lacpBundle.editConf.vlan.bridging.adminEdge

       Possibilities:
               disabled   (0)
               enabled   (1)"
   ::= {er1646v2LacpBVlanEntry 457179136}

er1646v2LacpBVlanBridgingOamMacDeviceMac OBJECT-TYPE
   SYNTAX      DisplayString
   MAX-ACCESS  read-write
   STATUS      current
   DESCRIPTION
      "Path: lacpBundle.editConf.vlan.bridging.ethOam.macAddress.deviceMac"
   ::= {er1646v2LacpBVlanEntry 458506496}

er1646v2LacpBVlanBridgingOamMacUserMac OBJECT-TYPE
   SYNTAX      OCTET STRING
   MAX-ACCESS  read-write
   STATUS      current
   DESCRIPTION
      "Path: lacpBundle.editConf.vlan.bridging.ethOam.macAddress.userMac

       MAC address."
   ::= {er1646v2LacpBVlanEntry 458506368}

er1646v2LacpBVlanBridgingOamMacBridgeMac OBJECT-TYPE
   SYNTAX      DisplayString
   MAX-ACCESS  read-write
   STATUS      current
   DESCRIPTION
      "Path: lacpBundle.editConf.vlan.bridging.ethOam.macAddress.bridgeMac"
   ::= {er1646v2LacpBVlanEntry 458506432}

er1646v2LacpBVlanBridgingMgmtInline OBJECT-TYPE
   SYNTAX      INTEGER
               {
               disabled (0),
               enabled (1)
               }
   MAX-ACCESS  read-write
   STATUS      current
   DESCRIPTION
      "Path: lacpBundle.editConf.vlan.bridging.mgmtInline

       Possibilities:
               disabled   (0)
               enabled   (1)"
   ::= {er1646v2LacpBVlanEntry 458752000}

er1646v2LacpBVlanBridgingL2ptMode OBJECT-TYPE
   SYNTAX      INTEGER
               {
               disabled (0),
               enabled (1)
               }
   MAX-ACCESS  read-write
   STATUS      current
   DESCRIPTION
      "Path: lacpBundle.editConf.vlan.bridging.l2ProtTunnel.mode

       Possibilities:
               disabled   (0)
               enabled   (1)"
   ::= {er1646v2LacpBVlanEntry 459292672}

er1646v2LacpBVlanBridgingL2ptProtocols OBJECT-TYPE
   SYNTAX      Integer32
   MAX-ACCESS  read-write
   STATUS      current
   DESCRIPTION
      "Path: lacpBundle.editConf.vlan.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1646v2LacpBVlanEntry 459309056}

er1646v2LacpBVlanBridgingL2ptDestMac OBJECT-TYPE
   SYNTAX      OCTET STRING
   MAX-ACCESS  read-write
   STATUS      current
   DESCRIPTION
      "Path: lacpBundle.editConf.vlan.bridging.l2ProtTunnel.destinationMac

       MAC address."
   ::= {er1646v2LacpBVlanEntry 459325440}

er1646v2LacpBVlanBridgingL2ptCos OBJECT-TYPE
   SYNTAX      INTEGER
               {
               unchanged (255)
               }
   MAX-ACCESS  read-write
   STATUS      current
   DESCRIPTION
      "Path: lacpBundle.editConf.vlan.bridging.l2ProtTunnel.cos

       Possibilities:
               unchanged   (255)"
   ::= {er1646v2LacpBVlanEntry 459341824}

er1646v2LacpBVlanBridgingL2ptDropThrStp OBJECT-TYPE
   SYNTAX      INTEGER
               {
               unlimited (0)
               }
   UNITS       "packets/sec"
   MAX-ACCESS  read-write
   STATUS      current
   DESCRIPTION
      "Path: lacpBundle.editConf.vlan.bridging.l2ProtTunnel.dropThresholds.stp

       unit name = packets/sec

       Possibilities:
               unlimited   (0)"
   ::= {er1646v2LacpBVlanEntry 459358272}

er1646v2LacpBVlanBridgingL2ptDropThrLldp OBJECT-TYPE
   SYNTAX      INTEGER
               {
               unlimited (0)
               }
   UNITS       "packets/sec"
   MAX-ACCESS  read-write
   STATUS      current
   DESCRIPTION
      "Path: lacpBundle.editConf.vlan.bridging.l2ProtTunnel.dropThresholds.lldp

       unit name = packets/sec

       Possibilities:
               unlimited   (0)"
   ::= {er1646v2LacpBVlanEntry 459358336}

er1646v2LacpBVlanBridgingL2ptDropThrOam OBJECT-TYPE
   SYNTAX      INTEGER
               {
               unlimited (0)
               }
   UNITS       "packets/sec"
   MAX-ACCESS  read-write
   STATUS      current
   DESCRIPTION
      "Path: lacpBundle.editConf.vlan.bridging.l2ProtTunnel.dropThresholds.oam

       unit name = packets/sec

       Possibilities:
               unlimited   (0)"
   ::= {er1646v2LacpBVlanEntry 459358400}

er1646v2LacpBVlanBridgingL2ptDropThrCdp OBJECT-TYPE
   SYNTAX      INTEGER
               {
               unlimited (0)
               }
   UNITS       "packets/sec"
   MAX-ACCESS  read-write
   STATUS      current
   DESCRIPTION
      "Path: lacpBundle.editConf.vlan.bridging.l2ProtTunnel.dropThresholds.cdp

       unit name = packets/sec

       Possibilities:
               unlimited   (0)"
   ::= {er1646v2LacpBVlanEntry 459358464}

er1646v2LacpBVlanBridgingL2ptDropThrVtp OBJECT-TYPE
   SYNTAX      INTEGER
               {
               unlimited (0)
               }
   UNITS       "packets/sec"
   MAX-ACCESS  read-write
   STATUS      current
   DESCRIPTION
      "Path: lacpBundle.editConf.vlan.bridging.l2ProtTunnel.dropThresholds.vtp

       unit name = packets/sec

       Possibilities:
               unlimited   (0)"
   ::= {er1646v2LacpBVlanEntry 459358528}

er1646v2LacpBVlanBridgingL2ptDropThrLacp OBJECT-TYPE
   SYNTAX      INTEGER
               {
               unlimited (0)
               }
   UNITS       "packets/sec"
   MAX-ACCESS  read-write
   STATUS      current
   DESCRIPTION
      "Path: lacpBundle.editConf.vlan.bridging.l2ProtTunnel.dropThresholds.lacp

       unit name = packets/sec

       Possibilities:
               unlimited   (0)"
   ::= {er1646v2LacpBVlanEntry 459358592}

er1646v2LacpBVlanBridgingL2ptDropThrEfmOam OBJECT-TYPE
   SYNTAX      INTEGER
               {
               unlimited (0)
               }
   UNITS       "packets/sec"
   MAX-ACCESS  read-write
   STATUS      current
   DESCRIPTION
      "Path: lacpBundle.editConf.vlan.bridging.l2ProtTunnel.dropThresholds.efmOam

       unit name = packets/sec

       Possibilities:
               unlimited   (0)"
   ::= {er1646v2LacpBVlanEntry 459358656}

er1646v2LacpBVlanBridgingL2ptDropThrPvst OBJECT-TYPE
   SYNTAX      INTEGER
               {
               unlimited (0)
               }
   UNITS       "packets/sec"
   MAX-ACCESS  read-write
   STATUS      current
   DESCRIPTION
      "Path: lacpBundle.editConf.vlan.bridging.l2ProtTunnel.dropThresholds.pvst

       unit name = packets/sec

       Possibilities:
               unlimited   (0)"
   ::= {er1646v2LacpBVlanEntry 459358720}

er1646v2LacpBVlanBridgingL2ptDropThrMmrp OBJECT-TYPE
   SYNTAX      INTEGER
               {
               unlimited (0)
               }
   UNITS       "packets/sec"
   MAX-ACCESS  read-write
   STATUS      current
   DESCRIPTION
      "Path: lacpBundle.editConf.vlan.bridging.l2ProtTunnel.dropThresholds.mmrp

       unit name = packets/sec

       Possibilities:
               unlimited   (0)"
   ::= {er1646v2LacpBVlanEntry 459358784}

er1646v2LacpBVlanBridgingL2ptDropThrMvrp OBJECT-TYPE
   SYNTAX      INTEGER
               {
               unlimited (0)
               }
   UNITS       "packets/sec"
   MAX-ACCESS  read-write
   STATUS      current
   DESCRIPTION
      "Path: lacpBundle.editConf.vlan.bridging.l2ProtTunnel.dropThresholds.mvrp

       unit name = packets/sec

       Possibilities:
               unlimited   (0)"
   ::= {er1646v2LacpBVlanEntry 459358848}

er1646v2LacpBVlanBridgingL2ptDropThrGvrp OBJECT-TYPE
   SYNTAX      INTEGER
               {
               unlimited (0)
               }
   UNITS       "packets/sec"
   MAX-ACCESS  read-write
   STATUS      current
   DESCRIPTION
      "Path: lacpBundle.editConf.vlan.bridging.l2ProtTunnel.dropThresholds.gvrp

       unit name = packets/sec

       Possibilities:
               unlimited   (0)"
   ::= {er1646v2LacpBVlanEntry 459358912}

er1646v2LacpBVlanBridgingL2ptDropThrGmrp OBJECT-TYPE
   SYNTAX      INTEGER
               {
               unlimited (0)
               }
   UNITS       "packets/sec"
   MAX-ACCESS  read-write
   STATUS      current
   DESCRIPTION
      "Path: lacpBundle.editConf.vlan.bridging.l2ProtTunnel.dropThresholds.gmrp

       unit name = packets/sec

       Possibilities:
               unlimited   (0)"
   ::= {er1646v2LacpBVlanEntry 459358976}

er1646v2LacpBVlanBridgingL2ptDropThrDtp OBJECT-TYPE
   SYNTAX      INTEGER
               {
               unlimited (0)
               }
   UNITS       "packets/sec"
   MAX-ACCESS  read-write
   STATUS      current
   DESCRIPTION
      "Path: lacpBundle.editConf.vlan.bridging.l2ProtTunnel.dropThresholds.dtp

       unit name = packets/sec

       Possibilities:
               unlimited   (0)"
   ::= {er1646v2LacpBVlanEntry 459359040}

er1646v2LacpBVlanBridgingL2ptDropThrPagp OBJECT-TYPE
   SYNTAX      INTEGER
               {
               unlimited (0)
               }
   UNITS       "packets/sec"
   MAX-ACCESS  read-write
   STATUS      current
   DESCRIPTION
      "Path: lacpBundle.editConf.vlan.bridging.l2ProtTunnel.dropThresholds.pagp

       unit name = packets/sec

       Possibilities:
               unlimited   (0)"
   ::= {er1646v2LacpBVlanEntry 459359104}

er1646v2LacpBVlanBridgingL2ptDropThrUdld OBJECT-TYPE
   SYNTAX      INTEGER
               {
               unlimited (0)
               }
   UNITS       "packets/sec"
   MAX-ACCESS  read-write
   STATUS      current
   DESCRIPTION
      "Path: lacpBundle.editConf.vlan.bridging.l2ProtTunnel.dropThresholds.udld

       unit name = packets/sec

       Possibilities:
               unlimited   (0)"
   ::= {er1646v2LacpBVlanEntry 459359168}

er1646v2LacpBVlanVlanVid OBJECT-TYPE
   SYNTAX      INTEGER
               {
               untagged (0),
               prioTagged (4096),
               notUsed (4097)
               }
   MAX-ACCESS  read-write
   STATUS      current
   DESCRIPTION
      "Path: lacpBundle.editConf.vlan.vlan.vid

       Possibilities:
               untagged   (0)
               prioTagged   (4096)
               notUsed   (4097)"
   ::= {er1646v2LacpBVlanEntry 234946560}

er1646v2LacpBVlanVlanVidExtensionSingle OBJECT-TYPE
   SYNTAX      OCTET STRING
   MAX-ACCESS  read-write
   STATUS      current
   DESCRIPTION
      "Path: lacpBundle.editConf.vlan.vlan.vidExtension.single"
   ::= {er1646v2LacpBVlanEntry 235340032}

er1646v2LacpBVlanVlanVidExtensionEndVid OBJECT-TYPE
   SYNTAX      Integer32
   MAX-ACCESS  read-write
   STATUS      current
   DESCRIPTION
      "Path: lacpBundle.editConf.vlan.vlan.vidExtension.endVid"
   ::= {er1646v2LacpBVlanEntry 235340288}

er1646v2LacpBVlanVlanTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: lacpBundle.editConf.vlan.vlan.tpid

       Possibilities:
               dot1Q   (33024)
               dot1ad   (34984)
               0x9100   (37120)
               0x9200   (37376)
               0x9300   (37632)"
   ::= {er1646v2LacpBVlanEntry 241238016}

er1646v2LacpBVlanVlanTagSign OBJECT-TYPE
   SYNTAX      INTEGER
               {
               global (0),
               local (1),
               sVlan (2),
               sVlanGlobal (6),
               cVlan (3),
               scVlan (5),
               cVlanLocal (4)
               }
   MAX-ACCESS  read-write
   STATUS      current
   DESCRIPTION
      "Path: lacpBundle.editConf.vlan.vlan.tagSignificance

       Possibilities:
               global   (0)
               local   (1)
               sVlan   (2)
               sVlanGlobal   (6)
               cVlan   (3)
               scVlan   (5)
               cVlanLocal   (4)"
   ::= {er1646v2LacpBVlanEntry 235012096}

er1646v2LacpBVlanVlanChTos OBJECT-TYPE
   SYNTAX      INTEGER
               {
               disabled (0),
               enabled (1)
               }
   MAX-ACCESS  read-write
   STATUS      current
   DESCRIPTION
      "Path: lacpBundle.editConf.vlan.vlan.changeTos

       Possibilities:
               disabled   (0)
               enabled   (1)"
   ::= {er1646v2LacpBVlanEntry 235208704}

er1646v2LacpBVlanVlanCTMapP0 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: lacpBundle.editConf.vlan.vlan.cosTosMap.p0

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2LacpBVlanEntry 235143424}

er1646v2LacpBVlanVlanCTMapP1 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: lacpBundle.editConf.vlan.vlan.cosTosMap.p1

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2LacpBVlanEntry 235143680}

er1646v2LacpBVlanVlanCTMapP2 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: lacpBundle.editConf.vlan.vlan.cosTosMap.p2

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2LacpBVlanEntry 235143936}

er1646v2LacpBVlanVlanCTMapP3 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: lacpBundle.editConf.vlan.vlan.cosTosMap.p3

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2LacpBVlanEntry 235144192}

er1646v2LacpBVlanVlanCTMapP4 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: lacpBundle.editConf.vlan.vlan.cosTosMap.p4

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2LacpBVlanEntry 235144448}

er1646v2LacpBVlanVlanCTMapP5 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: lacpBundle.editConf.vlan.vlan.cosTosMap.p5

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2LacpBVlanEntry 235144704}

er1646v2LacpBVlanVlanCTMapP6 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: lacpBundle.editConf.vlan.vlan.cosTosMap.p6

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2LacpBVlanEntry 235144960}

er1646v2LacpBVlanVlanCTMapP7 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: lacpBundle.editConf.vlan.vlan.cosTosMap.p7

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2LacpBVlanEntry 235145216}

er1646v2LacpBVlanVlanTxCos OBJECT-TYPE
   SYNTAX      INTEGER
               {
               tosCosMap (8),
               queueCosMap (16)
               }
   MAX-ACCESS  read-write
   STATUS      current
   DESCRIPTION
      "Path: lacpBundle.editConf.vlan.vlan.txCos

       Possibilities:
               tosCosMap   (8)
               queueCosMap   (16)"
   ::= {er1646v2LacpBVlanEntry 235077632}

er1646v2LacpBVlanVlanCCMapP0 OBJECT-TYPE
   SYNTAX      Integer32
   MAX-ACCESS  read-write
   STATUS      current
   DESCRIPTION
      "Path: lacpBundle.editConf.vlan.vlan.cosCosMap.p0"
   ::= {er1646v2LacpBVlanEntry 241303808}

er1646v2LacpBVlanVlanCCMapP1 OBJECT-TYPE
   SYNTAX      Integer32
   MAX-ACCESS  read-write
   STATUS      current
   DESCRIPTION
      "Path: lacpBundle.editConf.vlan.vlan.cosCosMap.p1"
   ::= {er1646v2LacpBVlanEntry 241304064}

er1646v2LacpBVlanVlanCCMapP2 OBJECT-TYPE
   SYNTAX      Integer32
   MAX-ACCESS  read-write
   STATUS      current
   DESCRIPTION
      "Path: lacpBundle.editConf.vlan.vlan.cosCosMap.p2"
   ::= {er1646v2LacpBVlanEntry 241304320}

er1646v2LacpBVlanVlanCCMapP3 OBJECT-TYPE
   SYNTAX      Integer32
   MAX-ACCESS  read-write
   STATUS      current
   DESCRIPTION
      "Path: lacpBundle.editConf.vlan.vlan.cosCosMap.p3"
   ::= {er1646v2LacpBVlanEntry 241304576}

er1646v2LacpBVlanVlanCCMapP4 OBJECT-TYPE
   SYNTAX      Integer32
   MAX-ACCESS  read-write
   STATUS      current
   DESCRIPTION
      "Path: lacpBundle.editConf.vlan.vlan.cosCosMap.p4"
   ::= {er1646v2LacpBVlanEntry 241304832}

er1646v2LacpBVlanVlanCCMapP5 OBJECT-TYPE
   SYNTAX      Integer32
   MAX-ACCESS  read-write
   STATUS      current
   DESCRIPTION
      "Path: lacpBundle.editConf.vlan.vlan.cosCosMap.p5"
   ::= {er1646v2LacpBVlanEntry 241305088}

er1646v2LacpBVlanVlanCCMapP6 OBJECT-TYPE
   SYNTAX      Integer32
   MAX-ACCESS  read-write
   STATUS      current
   DESCRIPTION
      "Path: lacpBundle.editConf.vlan.vlan.cosCosMap.p6"
   ::= {er1646v2LacpBVlanEntry 241305344}

er1646v2LacpBVlanVlanCCMapP7 OBJECT-TYPE
   SYNTAX      Integer32
   MAX-ACCESS  read-write
   STATUS      current
   DESCRIPTION
      "Path: lacpBundle.editConf.vlan.vlan.cosCosMap.p7"
   ::= {er1646v2LacpBVlanEntry 241305600}

er1646v2LacpBVlanVlanQCMapQueue1 OBJECT-TYPE
   SYNTAX      Integer32
   MAX-ACCESS  read-write
   STATUS      current
   DESCRIPTION
      "Path: lacpBundle.editConf.vlan.vlan.queueCosMap.queue1"
   ::= {er1646v2LacpBVlanEntry 241434880}

er1646v2LacpBVlanVlanQCMapQueue2 OBJECT-TYPE
   SYNTAX      Integer32
   MAX-ACCESS  read-write
   STATUS      current
   DESCRIPTION
      "Path: lacpBundle.editConf.vlan.vlan.queueCosMap.queue2"
   ::= {er1646v2LacpBVlanEntry 241435136}

er1646v2LacpBVlanVlanQCMapQueue3 OBJECT-TYPE
   SYNTAX      Integer32
   MAX-ACCESS  read-write
   STATUS      current
   DESCRIPTION
      "Path: lacpBundle.editConf.vlan.vlan.queueCosMap.queue3"
   ::= {er1646v2LacpBVlanEntry 241435392}

er1646v2LacpBVlanVlanQCMapQueue4 OBJECT-TYPE
   SYNTAX      Integer32
   MAX-ACCESS  read-write
   STATUS      current
   DESCRIPTION
      "Path: lacpBundle.editConf.vlan.vlan.queueCosMap.queue4"
   ::= {er1646v2LacpBVlanEntry 241435648}

er1646v2LacpBVlanVlanQCMapQueue5 OBJECT-TYPE
   SYNTAX      Integer32
   MAX-ACCESS  read-write
   STATUS      current
   DESCRIPTION
      "Path: lacpBundle.editConf.vlan.vlan.queueCosMap.queue5"
   ::= {er1646v2LacpBVlanEntry 241435904}

er1646v2LacpBVlanVlanQCMapLowDelayQueue OBJECT-TYPE
   SYNTAX      Integer32
   MAX-ACCESS  read-write
   STATUS      current
   DESCRIPTION
      "Path: lacpBundle.editConf.vlan.vlan.queueCosMap.lowDelayQueue"
   ::= {er1646v2LacpBVlanEntry 241436160}

er1646v2LacpBVlanVlanQCMapLowDelay2Queue OBJECT-TYPE
   SYNTAX      Integer32
   MAX-ACCESS  read-write
   STATUS      current
   DESCRIPTION
      "Path: lacpBundle.editConf.vlan.vlan.queueCosMap.lowDelay2Queue"
   ::= {er1646v2LacpBVlanEntry 241436416}

er1646v2LacpBVlanVlanQCMapSystemQueue OBJECT-TYPE
   SYNTAX      Integer32
   MAX-ACCESS  read-write
   STATUS      current
   DESCRIPTION
      "Path: lacpBundle.editConf.vlan.vlan.queueCosMap.systemQueue"
   ::= {er1646v2LacpBVlanEntry 241436672}

er1646v2LacpBVlanVlanQinQSVid OBJECT-TYPE
   SYNTAX      Integer32
   MAX-ACCESS  read-write
   STATUS      current
   DESCRIPTION
      "Path: lacpBundle.editConf.vlan.vlan.tunnel.sVid"
   ::= {er1646v2LacpBVlanEntry 241172736}

er1646v2LacpBVlanVlanQinQSTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: lacpBundle.editConf.vlan.vlan.tunnel.sTpid

       Possibilities:
               dot1Q   (33024)
               dot1ad   (34984)
               0x9100   (37120)
               0x9200   (37376)
               0x9300   (37632)"
   ::= {er1646v2LacpBVlanEntry 241172992}

er1646v2LacpBVlanVlanArpTimeOut OBJECT-TYPE
   SYNTAX      TimeTicks
   MAX-ACCESS  read-write
   STATUS      current
   DESCRIPTION
      "Path: lacpBundle.editConf.vlan.vlan.arp.timeOut

       Time in centi-second."
   ::= {er1646v2LacpBVlanEntry 235277312}

er1646v2LacpBVlanVlanArpProxyArp OBJECT-TYPE
   SYNTAX      INTEGER
               {
               disabled (0),
               enabled (1)
               }
   MAX-ACCESS  read-write
   STATUS      current
   DESCRIPTION
      "Path: lacpBundle.editConf.vlan.vlan.arp.proxyArp

       Possibilities:
               disabled   (0)
               enabled   (1)"
   ::= {er1646v2LacpBVlanEntry 235287040}

er1646v2LacpBVlanBandwidthMode OBJECT-TYPE
   SYNTAX      INTEGER
               {
               reshaping (1),
               policing (2),
               policingReshape (3)
               }
   MAX-ACCESS  read-write
   STATUS      current
   DESCRIPTION
      "Path: lacpBundle.editConf.vlan.bandwidth.mode

       Possibilities:
               reshaping   (1)
               policing   (2)
               policingReshape   (3)"
   ::= {er1646v2LacpBVlanEntry 148897792}

er1646v2LacpBVlanBandwidthCir OBJECT-TYPE
   SYNTAX      Integer32
   MAX-ACCESS  read-write
   STATUS      current
   DESCRIPTION
      "Path: lacpBundle.editConf.vlan.bandwidth.cir"
   ::= {er1646v2LacpBVlanEntry 135266304}

er1646v2LacpBVlanBandwidthEir OBJECT-TYPE
   SYNTAX      Integer32
   MAX-ACCESS  read-write
   STATUS      current
   DESCRIPTION
      "Path: lacpBundle.editConf.vlan.bandwidth.eir"
   ::= {er1646v2LacpBVlanEntry 141557760}

er1646v2LacpBVlanBandwidthUnit OBJECT-TYPE
   SYNTAX      INTEGER
               {
               bitssec (1),
               percent (2)
               }
   MAX-ACCESS  read-write
   STATUS      current
   DESCRIPTION
      "Path: lacpBundle.editConf.vlan.bandwidth.unit

       Possibilities:
               bits/sec   (1)
               percent   (2)"
   ::= {er1646v2LacpBVlanEntry 139460608}

er1646v2LacpBVlanBandwidthTc OBJECT-TYPE
   SYNTAX      INTEGER
               {
               auto (0)
               }
   MAX-ACCESS  read-write
   STATUS      current
   DESCRIPTION
      "Path: lacpBundle.editConf.vlan.bandwidth.tc

       Possibilities:
               auto   (0)"
   ::= {er1646v2LacpBVlanEntry 140509184}

er1646v2LacpBVlanBandwidthTcFactor OBJECT-TYPE
   SYNTAX      INTEGER
               {
               ms (10),
               s100us (1)
               }
   MAX-ACCESS  read-write
   STATUS      current
   DESCRIPTION
      "Path: lacpBundle.editConf.vlan.bandwidth.tcFactor

       Possibilities:
               ms   (10)
               *100us   (1)"
   ::= {er1646v2LacpBVlanEntry 142606336}

er1646v2LacpBVlanBandwidthCorrType OBJECT-TYPE
   SYNTAX      INTEGER
               {
               noCorrection (0),
               predefined (1),
               manual (2)
               }
   MAX-ACCESS  read-write
   STATUS      current
   DESCRIPTION
      "Path: lacpBundle.editConf.vlan.bandwidth.correction.type

       Possibilities:
               noCorrection   (0)
               predefined   (1)
               manual   (2)"
   ::= {er1646v2LacpBVlanEntry 136445952}

er1646v2LacpBVlanBandwidthCorrPredefEncapsFrameRelay OBJECT-TYPE
   SYNTAX      DisplayString
   MAX-ACCESS  read-write
   STATUS      current
   DESCRIPTION
      "Path: lacpBundle.editConf.vlan.bandwidth.correction.predefined.encapsulation.frameRelay"
   ::= {er1646v2LacpBVlanEntry 136594432}

er1646v2LacpBVlanBandwidthCorrPredefEncapsPpp OBJECT-TYPE
   SYNTAX      DisplayString
   MAX-ACCESS  read-write
   STATUS      current
   DESCRIPTION
      "Path: lacpBundle.editConf.vlan.bandwidth.correction.predefined.encapsulation.ppp"
   ::= {er1646v2LacpBVlanEntry 136595456}

er1646v2LacpBVlanBandwidthCorrPredefEncapsAtmHl OBJECT-TYPE
   SYNTAX      INTEGER
               {
               rfc2684 (0),
               ppp (1),
               pppOverEthernet (2)
               }
   MAX-ACCESS  read-write
   STATUS      current
   DESCRIPTION
      "Path: lacpBundle.editConf.vlan.bandwidth.correction.predefined.encapsulation.atm.higherLayer

       Possibilities:
               rfc2684   (0)
               ppp   (1)
               pppOverEthernet   (2)"
   ::= {er1646v2LacpBVlanEntry 136596608}

er1646v2LacpBVlanBandwidthCorrPredefEncapsAtmMp OBJECT-TYPE
   SYNTAX      INTEGER
               {
               llcEncapsulation (0),
               vcMultiplexing (1)
               }
   MAX-ACCESS  read-write
   STATUS      current
   DESCRIPTION
      "Path: lacpBundle.editConf.vlan.bandwidth.correction.predefined.encapsulation.atm.multiProtocol

       Possibilities:
               llcEncapsulation   (0)
               vcMultiplexing   (1)"
   ::= {er1646v2LacpBVlanEntry 136596736}

er1646v2LacpBVlanBandwidthCorrPredefEncapsHdlc OBJECT-TYPE
   SYNTAX      DisplayString
   MAX-ACCESS  read-write
   STATUS      current
   DESCRIPTION
      "Path: lacpBundle.editConf.vlan.bandwidth.correction.predefined.encapsulation.hdlc"
   ::= {er1646v2LacpBVlanEntry 136597504}

er1646v2LacpBVlanBandwidthCorrPredefEncapsEfmFs OBJECT-TYPE
   SYNTAX      Integer32
   MAX-ACCESS  read-write
   STATUS      current
   DESCRIPTION
      "Path: lacpBundle.editConf.vlan.bandwidth.correction.predefined.encapsulation.efm.fragmentSize"
   ::= {er1646v2LacpBVlanEntry 136598656}

er1646v2LacpBVlanBandwidthCorrPredefEncapsEfmIb OBJECT-TYPE
   SYNTAX      Integer32
   MAX-ACCESS  read-write
   STATUS      current
   DESCRIPTION
      "Path: lacpBundle.editConf.vlan.bandwidth.correction.predefined.encapsulation.efm.idleBytes"
   ::= {er1646v2LacpBVlanEntry 136598784}

er1646v2LacpBVlanBandwidthCorrPredefMode OBJECT-TYPE
   SYNTAX      INTEGER
               {
               routing (0),
               bridging (1)
               }
   MAX-ACCESS  read-write
   STATUS      current
   DESCRIPTION
      "Path: lacpBundle.editConf.vlan.bandwidth.correction.predefined.mode

       Possibilities:
               routing   (0)
               bridging   (1)"
   ::= {er1646v2LacpBVlanEntry 136609792}

er1646v2LacpBVlanBandwidthCorrManualOverhead OBJECT-TYPE
   SYNTAX      Integer32
   MAX-ACCESS  read-write
   STATUS      current
   DESCRIPTION
      "Path: lacpBundle.editConf.vlan.bandwidth.correction.manual.overhead"
   ::= {er1646v2LacpBVlanEntry 136708608}

er1646v2LacpBVlanBandwidthCorrManualFrameData OBJECT-TYPE
   SYNTAX      Counter32
   MAX-ACCESS  read-write
   STATUS      current
   DESCRIPTION
      "Path: lacpBundle.editConf.vlan.bandwidth.correction.manual.frameData

       32 bit unsigned wrappable counter."
   ::= {er1646v2LacpBVlanEntry 136709120}

er1646v2LacpBVlanBandwidthCorrManualFrameHeader OBJECT-TYPE
   SYNTAX      Counter32
   MAX-ACCESS  read-write
   STATUS      current
   DESCRIPTION
      "Path: lacpBundle.editConf.vlan.bandwidth.correction.manual.frameHeader

       32 bit unsigned wrappable counter."
   ::= {er1646v2LacpBVlanEntry 136709632}

er1646v2LacpBVlanBandwidthMaxFifoQLen OBJECT-TYPE
   SYNTAX      Integer32
   MAX-ACCESS  read-write
   STATUS      current
   DESCRIPTION
      "Path: lacpBundle.editConf.vlan.bandwidth.maxFifoQLen"
   ::= {er1646v2LacpBVlanEntry 137363456}

er1646v2LacpBVlanBandwidthDeFlagCir OBJECT-TYPE
   SYNTAX      INTEGER
               {
               allowed (1),
               notAllowed (2)
               }
   MAX-ACCESS  read-write
   STATUS      current
   DESCRIPTION
      "Path: lacpBundle.editConf.vlan.bandwidth.deFlag.cir

       Possibilities:
               allowed   (1)
               notAllowed   (2)"
   ::= {er1646v2LacpBVlanEntry 147853312}

er1646v2LacpBVlanBandwidthDeFlagEir OBJECT-TYPE
   SYNTAX      INTEGER
               {
               allowed (1),
               notAllowed (2)
               }
   MAX-ACCESS  read-write
   STATUS      current
   DESCRIPTION
      "Path: lacpBundle.editConf.vlan.bandwidth.deFlag.eir

       Possibilities:
               allowed   (1)
               notAllowed   (2)"
   ::= {er1646v2LacpBVlanEntry 147857408}

er1646v2LacpBVlanBandwidthDeFlagViolate OBJECT-TYPE
   SYNTAX      INTEGER
               {
               allowed (1),
               notAllowed (2)
               }
   MAX-ACCESS  read-write
   STATUS      current
   DESCRIPTION
      "Path: lacpBundle.editConf.vlan.bandwidth.deFlag.violate

       Possibilities:
               allowed   (1)
               notAllowed   (2)"
   ::= {er1646v2LacpBVlanEntry 147861504}

er1646v2LacpBVlanBandwidthActCirActNone OBJECT-TYPE
   SYNTAX      OCTET STRING
   MAX-ACCESS  read-write
   STATUS      current
   DESCRIPTION
      "Path: lacpBundle.editConf.vlan.bandwidth.action.cirAction.none"
   ::= {er1646v2LacpBVlanEntry 150085632}

er1646v2LacpBVlanBandwidthActCirActEthCos1 OBJECT-TYPE
   SYNTAX      INTEGER
               {
               unchanged (256)
               }
   MAX-ACCESS  read-write
   STATUS      current
   DESCRIPTION
      "Path: lacpBundle.editConf.vlan.bandwidth.action.cirAction.ethernet.cosDepth1

       Possibilities:
               unchanged   (256)"
   ::= {er1646v2LacpBVlanEntry 150094080}

er1646v2LacpBVlanBandwidthActCirActEthDei1 OBJECT-TYPE
   SYNTAX      INTEGER
               {
               unchanged (255),
               clear (0),
               set (1)
               }
   MAX-ACCESS  read-write
   STATUS      current
   DESCRIPTION
      "Path: lacpBundle.editConf.vlan.bandwidth.action.cirAction.ethernet.deiDepth1

       Possibilities:
               unchanged   (255)
               clear   (0)
               set   (1)"
   ::= {er1646v2LacpBVlanEntry 150099200}

er1646v2LacpBVlanBandwidthActCirActEthCos2 OBJECT-TYPE
   SYNTAX      INTEGER
               {
               unchanged (256)
               }
   MAX-ACCESS  read-write
   STATUS      current
   DESCRIPTION
      "Path: lacpBundle.editConf.vlan.bandwidth.action.cirAction.ethernet.cosDepth2

       Possibilities:
               unchanged   (256)"
   ::= {er1646v2LacpBVlanEntry 150094336}

er1646v2LacpBVlanBandwidthActCirActEthDei2 OBJECT-TYPE
   SYNTAX      INTEGER
               {
               unchanged (255),
               clear (0),
               set (1)
               }
   MAX-ACCESS  read-write
   STATUS      current
   DESCRIPTION
      "Path: lacpBundle.editConf.vlan.bandwidth.action.cirAction.ethernet.deiDepth2

       Possibilities:
               unchanged   (255)
               clear   (0)
               set   (1)"
   ::= {er1646v2LacpBVlanEntry 150099456}

er1646v2LacpBVlanBandwidthActCirActEthCos3 OBJECT-TYPE
   SYNTAX      INTEGER
               {
               unchanged (256)
               }
   MAX-ACCESS  read-write
   STATUS      current
   DESCRIPTION
      "Path: lacpBundle.editConf.vlan.bandwidth.action.cirAction.ethernet.cosDepth3

       Possibilities:
               unchanged   (256)"
   ::= {er1646v2LacpBVlanEntry 150094592}

er1646v2LacpBVlanBandwidthActCirActEthDei3 OBJECT-TYPE
   SYNTAX      INTEGER
               {
               unchanged (255),
               clear (0),
               set (1)
               }
   MAX-ACCESS  read-write
   STATUS      current
   DESCRIPTION
      "Path: lacpBundle.editConf.vlan.bandwidth.action.cirAction.ethernet.deiDepth3

       Possibilities:
               unchanged   (255)
               clear   (0)
               set   (1)"
   ::= {er1646v2LacpBVlanEntry 150099712}

er1646v2LacpBVlanBandwidthActCirActEthCos4 OBJECT-TYPE
   SYNTAX      INTEGER
               {
               unchanged (256)
               }
   MAX-ACCESS  read-write
   STATUS      current
   DESCRIPTION
      "Path: lacpBundle.editConf.vlan.bandwidth.action.cirAction.ethernet.cosDepth4

       Possibilities:
               unchanged   (256)"
   ::= {er1646v2LacpBVlanEntry 150094848}

er1646v2LacpBVlanBandwidthActCirActEthDei4 OBJECT-TYPE
   SYNTAX      INTEGER
               {
               unchanged (255),
               clear (0),
               set (1)
               }
   MAX-ACCESS  read-write
   STATUS      current
   DESCRIPTION
      "Path: lacpBundle.editConf.vlan.bandwidth.action.cirAction.ethernet.deiDepth4

       Possibilities:
               unchanged   (255)
               clear   (0)
               set   (1)"
   ::= {er1646v2LacpBVlanEntry 150099968}

er1646v2LacpBVlanBandwidthActCirActEthCos5 OBJECT-TYPE
   SYNTAX      INTEGER
               {
               unchanged (256)
               }
   MAX-ACCESS  read-write
   STATUS      current
   DESCRIPTION
      "Path: lacpBundle.editConf.vlan.bandwidth.action.cirAction.ethernet.cosDepth5

       Possibilities:
               unchanged   (256)"
   ::= {er1646v2LacpBVlanEntry 150095104}

er1646v2LacpBVlanBandwidthActCirActEthDei5 OBJECT-TYPE
   SYNTAX      INTEGER
               {
               unchanged (255),
               clear (0),
               set (1)
               }
   MAX-ACCESS  read-write
   STATUS      current
   DESCRIPTION
      "Path: lacpBundle.editConf.vlan.bandwidth.action.cirAction.ethernet.deiDepth5

       Possibilities:
               unchanged   (255)
               clear   (0)
               set   (1)"
   ::= {er1646v2LacpBVlanEntry 150100224}

er1646v2LacpBVlanBandwidthActCirActEthCos6 OBJECT-TYPE
   SYNTAX      INTEGER
               {
               unchanged (256)
               }
   MAX-ACCESS  read-write
   STATUS      current
   DESCRIPTION
      "Path: lacpBundle.editConf.vlan.bandwidth.action.cirAction.ethernet.cosDepth6

       Possibilities:
               unchanged   (256)"
   ::= {er1646v2LacpBVlanEntry 150095360}

er1646v2LacpBVlanBandwidthActCirActEthDei6 OBJECT-TYPE
   SYNTAX      INTEGER
               {
               unchanged (255),
               clear (0),
               set (1)
               }
   MAX-ACCESS  read-write
   STATUS      current
   DESCRIPTION
      "Path: lacpBundle.editConf.vlan.bandwidth.action.cirAction.ethernet.deiDepth6

       Possibilities:
               unchanged   (255)
               clear   (0)
               set   (1)"
   ::= {er1646v2LacpBVlanEntry 150100480}

er1646v2LacpBVlanBandwidthActCirActEthCos7 OBJECT-TYPE
   SYNTAX      INTEGER
               {
               unchanged (256)
               }
   MAX-ACCESS  read-write
   STATUS      current
   DESCRIPTION
      "Path: lacpBundle.editConf.vlan.bandwidth.action.cirAction.ethernet.cosDepth7

       Possibilities:
               unchanged   (256)"
   ::= {er1646v2LacpBVlanEntry 150095616}

er1646v2LacpBVlanBandwidthActCirActEthDei7 OBJECT-TYPE
   SYNTAX      INTEGER
               {
               unchanged (255),
               clear (0),
               set (1)
               }
   MAX-ACCESS  read-write
   STATUS      current
   DESCRIPTION
      "Path: lacpBundle.editConf.vlan.bandwidth.action.cirAction.ethernet.deiDepth7

       Possibilities:
               unchanged   (255)
               clear   (0)
               set   (1)"
   ::= {er1646v2LacpBVlanEntry 150100736}

er1646v2LacpBVlanBandwidthActCirActEthCos8 OBJECT-TYPE
   SYNTAX      INTEGER
               {
               unchanged (256)
               }
   MAX-ACCESS  read-write
   STATUS      current
   DESCRIPTION
      "Path: lacpBundle.editConf.vlan.bandwidth.action.cirAction.ethernet.cosDepth8

       Possibilities:
               unchanged   (256)"
   ::= {er1646v2LacpBVlanEntry 150095872}

er1646v2LacpBVlanBandwidthActCirActEthDei8 OBJECT-TYPE
   SYNTAX      INTEGER
               {
               unchanged (255),
               clear (0),
               set (1)
               }
   MAX-ACCESS  read-write
   STATUS      current
   DESCRIPTION
      "Path: lacpBundle.editConf.vlan.bandwidth.action.cirAction.ethernet.deiDepth8

       Possibilities:
               unchanged   (255)
               clear   (0)
               set   (1)"
   ::= {er1646v2LacpBVlanEntry 150100992}

er1646v2LacpBVlanBandwidthActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: lacpBundle.editConf.vlan.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2LacpBVlanEntry 150096128}

er1646v2LacpBVlanBandwidthActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: lacpBundle.editConf.vlan.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2LacpBVlanEntry 150096384}

er1646v2LacpBVlanBandwidthActCirActEthDrpLev OBJECT-TYPE
   SYNTAX      INTEGER
               {
               unchanged (0)
               }
   MAX-ACCESS  read-write
   STATUS      current
   DESCRIPTION
      "Path: lacpBundle.editConf.vlan.bandwidth.action.cirAction.ethernet.dropLevel

       Possibilities:
               unchanged   (0)"
   ::= {er1646v2LacpBVlanEntry 150096640}

er1646v2LacpBVlanBandwidthActCirActEthDeFlag OBJECT-TYPE
   SYNTAX      INTEGER
               {
               unchanged (255),
               clear (0),
               set (1)
               }
   MAX-ACCESS  read-write
   STATUS      current
   DESCRIPTION
      "Path: lacpBundle.editConf.vlan.bandwidth.action.cirAction.ethernet.deFlag

       Possibilities:
               unchanged   (255)
               clear   (0)
               set   (1)"
   ::= {er1646v2LacpBVlanEntry 150097408}

er1646v2LacpBVlanBandwidthActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: lacpBundle.editConf.vlan.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2LacpBVlanEntry 150120704}

er1646v2LacpBVlanBandwidthActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: lacpBundle.editConf.vlan.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2LacpBVlanEntry 150120960}

er1646v2LacpBVlanBandwidthActCirActIpDrpLev OBJECT-TYPE
   SYNTAX      INTEGER
               {
               unchanged (0)
               }
   MAX-ACCESS  read-write
   STATUS      current
   DESCRIPTION
      "Path: lacpBundle.editConf.vlan.bandwidth.action.cirAction.ip.dropLevel

       Possibilities:
               unchanged   (0)"
   ::= {er1646v2LacpBVlanEntry 150121216}

er1646v2LacpBVlanBandwidthActCirActIpDeFlag OBJECT-TYPE
   SYNTAX      INTEGER
               {
               unchanged (255),
               clear (0),
               set (1)
               }
   MAX-ACCESS  read-write
   STATUS      current
   DESCRIPTION
      "Path: lacpBundle.editConf.vlan.bandwidth.action.cirAction.ip.deFlag

       Possibilities:
               unchanged   (255)
               clear   (0)
               set   (1)"
   ::= {er1646v2LacpBVlanEntry 150121984}

er1646v2LacpBVlanBandwidthActEirActNone OBJECT-TYPE
   SYNTAX      OCTET STRING
   MAX-ACCESS  read-write
   STATUS      current
   DESCRIPTION
      "Path: lacpBundle.editConf.vlan.bandwidth.action.eirAction.none"
   ::= {er1646v2LacpBVlanEntry 150216704}

er1646v2LacpBVlanBandwidthActEirActEthCos1 OBJECT-TYPE
   SYNTAX      INTEGER
               {
               unchanged (256)
               }
   MAX-ACCESS  read-write
   STATUS      current
   DESCRIPTION
      "Path: lacpBundle.editConf.vlan.bandwidth.action.eirAction.ethernet.cosDepth1

       Possibilities:
               unchanged   (256)"
   ::= {er1646v2LacpBVlanEntry 150225152}

er1646v2LacpBVlanBandwidthActEirActEthDei1 OBJECT-TYPE
   SYNTAX      INTEGER
               {
               unchanged (255),
               clear (0),
               set (1)
               }
   MAX-ACCESS  read-write
   STATUS      current
   DESCRIPTION
      "Path: lacpBundle.editConf.vlan.bandwidth.action.eirAction.ethernet.deiDepth1

       Possibilities:
               unchanged   (255)
               clear   (0)
               set   (1)"
   ::= {er1646v2LacpBVlanEntry 150230272}

er1646v2LacpBVlanBandwidthActEirActEthCos2 OBJECT-TYPE
   SYNTAX      INTEGER
               {
               unchanged (256)
               }
   MAX-ACCESS  read-write
   STATUS      current
   DESCRIPTION
      "Path: lacpBundle.editConf.vlan.bandwidth.action.eirAction.ethernet.cosDepth2

       Possibilities:
               unchanged   (256)"
   ::= {er1646v2LacpBVlanEntry 150225408}

er1646v2LacpBVlanBandwidthActEirActEthDei2 OBJECT-TYPE
   SYNTAX      INTEGER
               {
               unchanged (255),
               clear (0),
               set (1)
               }
   MAX-ACCESS  read-write
   STATUS      current
   DESCRIPTION
      "Path: lacpBundle.editConf.vlan.bandwidth.action.eirAction.ethernet.deiDepth2

       Possibilities:
               unchanged   (255)
               clear   (0)
               set   (1)"
   ::= {er1646v2LacpBVlanEntry 150230528}

er1646v2LacpBVlanBandwidthActEirActEthCos3 OBJECT-TYPE
   SYNTAX      INTEGER
               {
               unchanged (256)
               }
   MAX-ACCESS  read-write
   STATUS      current
   DESCRIPTION
      "Path: lacpBundle.editConf.vlan.bandwidth.action.eirAction.ethernet.cosDepth3

       Possibilities:
               unchanged   (256)"
   ::= {er1646v2LacpBVlanEntry 150225664}

er1646v2LacpBVlanBandwidthActEirActEthDei3 OBJECT-TYPE
   SYNTAX      INTEGER
               {
               unchanged (255),
               clear (0),
               set (1)
               }
   MAX-ACCESS  read-write
   STATUS      current
   DESCRIPTION
      "Path: lacpBundle.editConf.vlan.bandwidth.action.eirAction.ethernet.deiDepth3

       Possibilities:
               unchanged   (255)
               clear   (0)
               set   (1)"
   ::= {er1646v2LacpBVlanEntry 150230784}

er1646v2LacpBVlanBandwidthActEirActEthCos4 OBJECT-TYPE
   SYNTAX      INTEGER
               {
               unchanged (256)
               }
   MAX-ACCESS  read-write
   STATUS      current
   DESCRIPTION
      "Path: lacpBundle.editConf.vlan.bandwidth.action.eirAction.ethernet.cosDepth4

       Possibilities:
               unchanged   (256)"
   ::= {er1646v2LacpBVlanEntry 150225920}

er1646v2LacpBVlanBandwidthActEirActEthDei4 OBJECT-TYPE
   SYNTAX      INTEGER
               {
               unchanged (255),
               clear (0),
               set (1)
               }
   MAX-ACCESS  read-write
   STATUS      current
   DESCRIPTION
      "Path: lacpBundle.editConf.vlan.bandwidth.action.eirAction.ethernet.deiDepth4

       Possibilities:
               unchanged   (255)
               clear   (0)
               set   (1)"
   ::= {er1646v2LacpBVlanEntry 150231040}

er1646v2LacpBVlanBandwidthActEirActEthCos5 OBJECT-TYPE
   SYNTAX      INTEGER
               {
               unchanged (256)
               }
   MAX-ACCESS  read-write
   STATUS      current
   DESCRIPTION
      "Path: lacpBundle.editConf.vlan.bandwidth.action.eirAction.ethernet.cosDepth5

       Possibilities:
               unchanged   (256)"
   ::= {er1646v2LacpBVlanEntry 150226176}

er1646v2LacpBVlanBandwidthActEirActEthDei5 OBJECT-TYPE
   SYNTAX      INTEGER
               {
               unchanged (255),
               clear (0),
               set (1)
               }
   MAX-ACCESS  read-write
   STATUS      current
   DESCRIPTION
      "Path: lacpBundle.editConf.vlan.bandwidth.action.eirAction.ethernet.deiDepth5

       Possibilities:
               unchanged   (255)
               clear   (0)
               set   (1)"
   ::= {er1646v2LacpBVlanEntry 150231296}

er1646v2LacpBVlanBandwidthActEirActEthCos6 OBJECT-TYPE
   SYNTAX      INTEGER
               {
               unchanged (256)
               }
   MAX-ACCESS  read-write
   STATUS      current
   DESCRIPTION
      "Path: lacpBundle.editConf.vlan.bandwidth.action.eirAction.ethernet.cosDepth6

       Possibilities:
               unchanged   (256)"
   ::= {er1646v2LacpBVlanEntry 150226432}

er1646v2LacpBVlanBandwidthActEirActEthDei6 OBJECT-TYPE
   SYNTAX      INTEGER
               {
               unchanged (255),
               clear (0),
               set (1)
               }
   MAX-ACCESS  read-write
   STATUS      current
   DESCRIPTION
      "Path: lacpBundle.editConf.vlan.bandwidth.action.eirAction.ethernet.deiDepth6

       Possibilities:
               unchanged   (255)
               clear   (0)
               set   (1)"
   ::= {er1646v2LacpBVlanEntry 150231552}

er1646v2LacpBVlanBandwidthActEirActEthCos7 OBJECT-TYPE
   SYNTAX      INTEGER
               {
               unchanged (256)
               }
   MAX-ACCESS  read-write
   STATUS      current
   DESCRIPTION
      "Path: lacpBundle.editConf.vlan.bandwidth.action.eirAction.ethernet.cosDepth7

       Possibilities:
               unchanged   (256)"
   ::= {er1646v2LacpBVlanEntry 150226688}

er1646v2LacpBVlanBandwidthActEirActEthDei7 OBJECT-TYPE
   SYNTAX      INTEGER
               {
               unchanged (255),
               clear (0),
               set (1)
               }
   MAX-ACCESS  read-write
   STATUS      current
   DESCRIPTION
      "Path: lacpBundle.editConf.vlan.bandwidth.action.eirAction.ethernet.deiDepth7

       Possibilities:
               unchanged   (255)
               clear   (0)
               set   (1)"
   ::= {er1646v2LacpBVlanEntry 150231808}

er1646v2LacpBVlanBandwidthActEirActEthCos8 OBJECT-TYPE
   SYNTAX      INTEGER
               {
               unchanged (256)
               }
   MAX-ACCESS  read-write
   STATUS      current
   DESCRIPTION
      "Path: lacpBundle.editConf.vlan.bandwidth.action.eirAction.ethernet.cosDepth8

       Possibilities:
               unchanged   (256)"
   ::= {er1646v2LacpBVlanEntry 150226944}

er1646v2LacpBVlanBandwidthActEirActEthDei8 OBJECT-TYPE
   SYNTAX      INTEGER
               {
               unchanged (255),
               clear (0),
               set (1)
               }
   MAX-ACCESS  read-write
   STATUS      current
   DESCRIPTION
      "Path: lacpBundle.editConf.vlan.bandwidth.action.eirAction.ethernet.deiDepth8

       Possibilities:
               unchanged   (255)
               clear   (0)
               set   (1)"
   ::= {er1646v2LacpBVlanEntry 150232064}

er1646v2LacpBVlanBandwidthActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: lacpBundle.editConf.vlan.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2LacpBVlanEntry 150227200}

er1646v2LacpBVlanBandwidthActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: lacpBundle.editConf.vlan.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2LacpBVlanEntry 150227456}

er1646v2LacpBVlanBandwidthActEirActEthDrpLev OBJECT-TYPE
   SYNTAX      INTEGER
               {
               unchanged (0)
               }
   MAX-ACCESS  read-write
   STATUS      current
   DESCRIPTION
      "Path: lacpBundle.editConf.vlan.bandwidth.action.eirAction.ethernet.dropLevel

       Possibilities:
               unchanged   (0)"
   ::= {er1646v2LacpBVlanEntry 150227712}

er1646v2LacpBVlanBandwidthActEirActEthDeFlag OBJECT-TYPE
   SYNTAX      INTEGER
               {
               unchanged (255),
               clear (0),
               set (1)
               }
   MAX-ACCESS  read-write
   STATUS      current
   DESCRIPTION
      "Path: lacpBundle.editConf.vlan.bandwidth.action.eirAction.ethernet.deFlag

       Possibilities:
               unchanged   (255)
               clear   (0)
               set   (1)"
   ::= {er1646v2LacpBVlanEntry 150228480}

er1646v2LacpBVlanBandwidthActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: lacpBundle.editConf.vlan.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2LacpBVlanEntry 150251776}

er1646v2LacpBVlanBandwidthActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: lacpBundle.editConf.vlan.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2LacpBVlanEntry 150252032}

er1646v2LacpBVlanBandwidthActEirActIpDrpLev OBJECT-TYPE
   SYNTAX      INTEGER
               {
               unchanged (0)
               }
   MAX-ACCESS  read-write
   STATUS      current
   DESCRIPTION
      "Path: lacpBundle.editConf.vlan.bandwidth.action.eirAction.ip.dropLevel

       Possibilities:
               unchanged   (0)"
   ::= {er1646v2LacpBVlanEntry 150252288}

er1646v2LacpBVlanBandwidthActEirActIpDeFlag OBJECT-TYPE
   SYNTAX      INTEGER
               {
               unchanged (255),
               clear (0),
               set (1)
               }
   MAX-ACCESS  read-write
   STATUS      current
   DESCRIPTION
      "Path: lacpBundle.editConf.vlan.bandwidth.action.eirAction.ip.deFlag

       Possibilities:
               unchanged   (255)
               clear   (0)
               set   (1)"
   ::= {er1646v2LacpBVlanEntry 150253056}

er1646v2LacpBVlanBandwidthActViolActNone OBJECT-TYPE
   SYNTAX      OCTET STRING
   MAX-ACCESS  read-write
   STATUS      current
   DESCRIPTION
      "Path: lacpBundle.editConf.vlan.bandwidth.action.violateAction.none"
   ::= {er1646v2LacpBVlanEntry 150347776}

er1646v2LacpBVlanBandwidthActViolActDrop OBJECT-TYPE
   SYNTAX      OCTET STRING
   MAX-ACCESS  read-write
   STATUS      current
   DESCRIPTION
      "Path: lacpBundle.editConf.vlan.bandwidth.action.violateAction.drop"
   ::= {er1646v2LacpBVlanEntry 150364160}

er1646v2LacpBVlanBandwidthActViolActEthCos1 OBJECT-TYPE
   SYNTAX      INTEGER
               {
               unchanged (256)
               }
   MAX-ACCESS  read-write
   STATUS      current
   DESCRIPTION
      "Path: lacpBundle.editConf.vlan.bandwidth.action.violateAction.ethernet.cosDepth1

       Possibilities:
               unchanged   (256)"
   ::= {er1646v2LacpBVlanEntry 150356224}

er1646v2LacpBVlanBandwidthActViolActEthDei1 OBJECT-TYPE
   SYNTAX      INTEGER
               {
               unchanged (255),
               clear (0),
               set (1)
               }
   MAX-ACCESS  read-write
   STATUS      current
   DESCRIPTION
      "Path: lacpBundle.editConf.vlan.bandwidth.action.violateAction.ethernet.deiDepth1

       Possibilities:
               unchanged   (255)
               clear   (0)
               set   (1)"
   ::= {er1646v2LacpBVlanEntry 150361344}

er1646v2LacpBVlanBandwidthActViolActEthCos2 OBJECT-TYPE
   SYNTAX      INTEGER
               {
               unchanged (256)
               }
   MAX-ACCESS  read-write
   STATUS      current
   DESCRIPTION
      "Path: lacpBundle.editConf.vlan.bandwidth.action.violateAction.ethernet.cosDepth2

       Possibilities:
               unchanged   (256)"
   ::= {er1646v2LacpBVlanEntry 150356480}

er1646v2LacpBVlanBandwidthActViolActEthDei2 OBJECT-TYPE
   SYNTAX      INTEGER
               {
               unchanged (255),
               clear (0),
               set (1)
               }
   MAX-ACCESS  read-write
   STATUS      current
   DESCRIPTION
      "Path: lacpBundle.editConf.vlan.bandwidth.action.violateAction.ethernet.deiDepth2

       Possibilities:
               unchanged   (255)
               clear   (0)
               set   (1)"
   ::= {er1646v2LacpBVlanEntry 150361600}

er1646v2LacpBVlanBandwidthActViolActEthCos3 OBJECT-TYPE
   SYNTAX      INTEGER
               {
               unchanged (256)
               }
   MAX-ACCESS  read-write
   STATUS      current
   DESCRIPTION
      "Path: lacpBundle.editConf.vlan.bandwidth.action.violateAction.ethernet.cosDepth3

       Possibilities:
               unchanged   (256)"
   ::= {er1646v2LacpBVlanEntry 150356736}

er1646v2LacpBVlanBandwidthActViolActEthDei3 OBJECT-TYPE
   SYNTAX      INTEGER
               {
               unchanged (255),
               clear (0),
               set (1)
               }
   MAX-ACCESS  read-write
   STATUS      current
   DESCRIPTION
      "Path: lacpBundle.editConf.vlan.bandwidth.action.violateAction.ethernet.deiDepth3

       Possibilities:
               unchanged   (255)
               clear   (0)
               set   (1)"
   ::= {er1646v2LacpBVlanEntry 150361856}

er1646v2LacpBVlanBandwidthActViolActEthCos4 OBJECT-TYPE
   SYNTAX      INTEGER
               {
               unchanged (256)
               }
   MAX-ACCESS  read-write
   STATUS      current
   DESCRIPTION
      "Path: lacpBundle.editConf.vlan.bandwidth.action.violateAction.ethernet.cosDepth4

       Possibilities:
               unchanged   (256)"
   ::= {er1646v2LacpBVlanEntry 150356992}

er1646v2LacpBVlanBandwidthActViolActEthDei4 OBJECT-TYPE
   SYNTAX      INTEGER
               {
               unchanged (255),
               clear (0),
               set (1)
               }
   MAX-ACCESS  read-write
   STATUS      current
   DESCRIPTION
      "Path: lacpBundle.editConf.vlan.bandwidth.action.violateAction.ethernet.deiDepth4

       Possibilities:
               unchanged   (255)
               clear   (0)
               set   (1)"
   ::= {er1646v2LacpBVlanEntry 150362112}

er1646v2LacpBVlanBandwidthActViolActEthCos5 OBJECT-TYPE
   SYNTAX      INTEGER
               {
               unchanged (256)
               }
   MAX-ACCESS  read-write
   STATUS      current
   DESCRIPTION
      "Path: lacpBundle.editConf.vlan.bandwidth.action.violateAction.ethernet.cosDepth5

       Possibilities:
               unchanged   (256)"
   ::= {er1646v2LacpBVlanEntry 150357248}

er1646v2LacpBVlanBandwidthActViolActEthDei5 OBJECT-TYPE
   SYNTAX      INTEGER
               {
               unchanged (255),
               clear (0),
               set (1)
               }
   MAX-ACCESS  read-write
   STATUS      current
   DESCRIPTION
      "Path: lacpBundle.editConf.vlan.bandwidth.action.violateAction.ethernet.deiDepth5

       Possibilities:
               unchanged   (255)
               clear   (0)
               set   (1)"
   ::= {er1646v2LacpBVlanEntry 150362368}

er1646v2LacpBVlanBandwidthActViolActEthCos6 OBJECT-TYPE
   SYNTAX      INTEGER
               {
               unchanged (256)
               }
   MAX-ACCESS  read-write
   STATUS      current
   DESCRIPTION
      "Path: lacpBundle.editConf.vlan.bandwidth.action.violateAction.ethernet.cosDepth6

       Possibilities:
               unchanged   (256)"
   ::= {er1646v2LacpBVlanEntry 150357504}

er1646v2LacpBVlanBandwidthActViolActEthDei6 OBJECT-TYPE
   SYNTAX      INTEGER
               {
               unchanged (255),
               clear (0),
               set (1)
               }
   MAX-ACCESS  read-write
   STATUS      current
   DESCRIPTION
      "Path: lacpBundle.editConf.vlan.bandwidth.action.violateAction.ethernet.deiDepth6

       Possibilities:
               unchanged   (255)
               clear   (0)
               set   (1)"
   ::= {er1646v2LacpBVlanEntry 150362624}

er1646v2LacpBVlanBandwidthActViolActEthCos7 OBJECT-TYPE
   SYNTAX      INTEGER
               {
               unchanged (256)
               }
   MAX-ACCESS  read-write
   STATUS      current
   DESCRIPTION
      "Path: lacpBundle.editConf.vlan.bandwidth.action.violateAction.ethernet.cosDepth7

       Possibilities:
               unchanged   (256)"
   ::= {er1646v2LacpBVlanEntry 150357760}

er1646v2LacpBVlanBandwidthActViolActEthDei7 OBJECT-TYPE
   SYNTAX      INTEGER
               {
               unchanged (255),
               clear (0),
               set (1)
               }
   MAX-ACCESS  read-write
   STATUS      current
   DESCRIPTION
      "Path: lacpBundle.editConf.vlan.bandwidth.action.violateAction.ethernet.deiDepth7

       Possibilities:
               unchanged   (255)
               clear   (0)
               set   (1)"
   ::= {er1646v2LacpBVlanEntry 150362880}

er1646v2LacpBVlanBandwidthActViolActEthCos8 OBJECT-TYPE
   SYNTAX      INTEGER
               {
               unchanged (256)
               }
   MAX-ACCESS  read-write
   STATUS      current
   DESCRIPTION
      "Path: lacpBundle.editConf.vlan.bandwidth.action.violateAction.ethernet.cosDepth8

       Possibilities:
               unchanged   (256)"
   ::= {er1646v2LacpBVlanEntry 150358016}

er1646v2LacpBVlanBandwidthActViolActEthDei8 OBJECT-TYPE
   SYNTAX      INTEGER
               {
               unchanged (255),
               clear (0),
               set (1)
               }
   MAX-ACCESS  read-write
   STATUS      current
   DESCRIPTION
      "Path: lacpBundle.editConf.vlan.bandwidth.action.violateAction.ethernet.deiDepth8

       Possibilities:
               unchanged   (255)
               clear   (0)
               set   (1)"
   ::= {er1646v2LacpBVlanEntry 150363136}

er1646v2LacpBVlanBandwidthActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: lacpBundle.editConf.vlan.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2LacpBVlanEntry 150358272}

er1646v2LacpBVlanBandwidthActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: lacpBundle.editConf.vlan.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2LacpBVlanEntry 150358528}

er1646v2LacpBVlanBandwidthActViolActEthDrpLev OBJECT-TYPE
   SYNTAX      INTEGER
               {
               unchanged (0)
               }
   MAX-ACCESS  read-write
   STATUS      current
   DESCRIPTION
      "Path: lacpBundle.editConf.vlan.bandwidth.action.violateAction.ethernet.dropLevel

       Possibilities:
               unchanged   (0)"
   ::= {er1646v2LacpBVlanEntry 150358784}

er1646v2LacpBVlanBandwidthActViolActEthDeFlag OBJECT-TYPE
   SYNTAX      INTEGER
               {
               unchanged (255),
               clear (0),
               set (1)
               }
   MAX-ACCESS  read-write
   STATUS      current
   DESCRIPTION
      "Path: lacpBundle.editConf.vlan.bandwidth.action.violateAction.ethernet.deFlag

       Possibilities:
               unchanged   (255)
               clear   (0)
               set   (1)"
   ::= {er1646v2LacpBVlanEntry 150359552}

er1646v2LacpBVlanBandwidthActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: lacpBundle.editConf.vlan.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2LacpBVlanEntry 150382848}

er1646v2LacpBVlanBandwidthActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: lacpBundle.editConf.vlan.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1646v2LacpBVlanEntry 150383104}

er1646v2LacpBVlanBandwidthActViolActIpDrpLev OBJECT-TYPE
   SYNTAX      INTEGER
               {
               unchanged (0)
               }
   MAX-ACCESS  read-write
   STATUS      current
   DESCRIPTION
      "Path: lacpBundle.editConf.vlan.bandwidth.action.violateAction.ip.dropLevel

       Possibilities:
               unchanged   (0)"
   ::= {er1646v2LacpBVlanEntry 150383360}

er1646v2LacpBVlanBandwidthActViolActIpDeFlag OBJECT-TYPE
   SYNTAX      INTEGER
               {
               unchanged (255),
               clear (0),
               set (1)
               }
   MAX-ACCESS  read-write
   STATUS      current
   DESCRIPTION
      "Path: lacpBundle.editConf.vlan.bandwidth.action.violateAction.ip.deFlag

       Possibilities:
               unchanged   (255)
               clear   (0)
               set   (1)"
   ::= {er1646v2LacpBVlanEntry 150384128}

er1646v2LacpBVlanInbBwMode OBJECT-TYPE
   SYNTAX      INTEGER
               {
               reshaping (1),
               policing (2)
               }
   MAX-ACCESS  read-write
   STATUS      current
   DESCRIPTION
      "Path: lacpBundle.editConf.vlan.inboundBandwidth.mode

       Possibilities:
               reshaping   (1)
               policing   (2)"
   ::= {er1646v2LacpBVlanEntry 132120576}

er1646v2LacpBVlanInbBwCir OBJECT-TYPE
   SYNTAX      Integer32
   MAX-ACCESS  read-write
   STATUS      current
   DESCRIPTION
      "Path: lacpBundle.editConf.vlan.inboundBandwidth.cir"
   ::= {er1646v2LacpBVlanEntry 118489088}

er1646v2LacpBVlanInbBwEir OBJECT-TYPE
   SYNTAX      Integer32
   MAX-ACCESS  read-write
   STATUS      current
   DESCRIPTION
      "Path: lacpBundle.editConf.vlan.inboundBandwidth.eir"
   ::= {er1646v2LacpBVlanEntry 124780544}

er1646v2LacpBVlanInbBwUnit OBJECT-TYPE
   SYNTAX      INTEGER
               {
               bitssec (1),
               percent (2)
               }
   MAX-ACCESS  read-write
   STATUS      current
   DESCRIPTION
      "Path: lacpBundle.editConf.vlan.inboundBandwidth.unit

       Possibilities:
               bits/sec   (1)
               percent   (2)"
   ::= {er1646v2LacpBVlanEntry 122683392}

er1646v2LacpBVlanInbBwTc OBJECT-TYPE
   SYNTAX      INTEGER
               {
               auto (0)
               }
   MAX-ACCESS  read-write
   STATUS      current
   DESCRIPTION
      "Path: lacpBundle.editConf.vlan.inboundBandwidth.tc

       Possibilities:
               auto   (0)"
   ::= {er1646v2LacpBVlanEntry 123731968}

er1646v2LacpBVlanInbBwTcFactor OBJECT-TYPE
   SYNTAX      INTEGER
               {
               ms (10),
               s100us (1)
               }
   MAX-ACCESS  read-write
   STATUS      current
   DESCRIPTION
      "Path: lacpBundle.editConf.vlan.inboundBandwidth.tcFactor

       Possibilities:
               ms   (10)
               *100us   (1)"
   ::= {er1646v2LacpBVlanEntry 125829120}

er1646v2LacpBVlanInbBwCorrType OBJECT-TYPE
   SYNTAX      INTEGER
               {
               noCorrection (0),
               predefined (1),
               manual (2)
               }
   MAX-ACCESS  read-write
   STATUS      current
   DESCRIPTION
      "Path: lacpBundle.editConf.vlan.inboundBandwidth.correction.type

       Possibilities:
               noCorrection   (0)
               predefined   (1)
               manual   (2)"
   ::= {er1646v2LacpBVlanEntry 119668736}

er1646v2LacpBVlanInbBwCorrPredefEncapsFrameRelay OBJECT-TYPE
   SYNTAX      DisplayString
   MAX-ACCESS  read-write
   STATUS      current
   DESCRIPTION
      "Path: lacpBundle.editConf.vlan.inboundBandwidth.correction.predefined.encapsulation.frameRelay"
   ::= {er1646v2LacpBVlanEntry 119817216}

er1646v2LacpBVlanInbBwCorrPredefEncapsPpp OBJECT-TYPE
   SYNTAX      DisplayString
   MAX-ACCESS  read-write
   STATUS      current
   DESCRIPTION
      "Path: lacpBundle.editConf.vlan.inboundBandwidth.correction.predefined.encapsulation.ppp"
   ::= {er1646v2LacpBVlanEntry 119818240}

er1646v2LacpBVlanInbBwCorrPredefEncapsAtmHl OBJECT-TYPE
   SYNTAX      INTEGER
               {
               rfc2684 (0),
               ppp (1),
               pppOverEthernet (2)
               }
   MAX-ACCESS  read-write
   STATUS      current
   DESCRIPTION
      "Path: lacpBundle.editConf.vlan.inboundBandwidth.correction.predefined.encapsulation.atm.higherLayer

       Possibilities:
               rfc2684   (0)
               ppp   (1)
               pppOverEthernet   (2)"
   ::= {er1646v2LacpBVlanEntry 119819392}

er1646v2LacpBVlanInbBwCorrPredefEncapsAtmMp OBJECT-TYPE
   SYNTAX      INTEGER
               {
               llcEncapsulation (0),
               vcMultiplexing (1)
               }
   MAX-ACCESS  read-write
   STATUS      current
   DESCRIPTION
      "Path: lacpBundle.editConf.vlan.inboundBandwidth.correction.predefined.encapsulation.atm.multiProtocol

       Possibilities:
               llcEncapsulation   (0)
               vcMultiplexing   (1)"
   ::= {er1646v2LacpBVlanEntry 119819520}

er1646v2LacpBVlanInbBwCorrPredefEncapsHdlc OBJECT-TYPE
   SYNTAX      DisplayString
   MAX-ACCESS  read-write
   STATUS      current
   DESCRIPTION
      "Path: lacpBundle.editConf.vlan.inboundBandwidth.correction.predefined.encapsulation.hdlc"
   ::= {er1646v2LacpBVlanEntry 119820288}

er1646v2LacpBVlanInbBwCorrPredefEncapsEfmFs OBJECT-TYPE
   SYNTAX      Integer32
   MAX-ACCESS  read-write
   STATUS      current
   DESCRIPTION
      "Path: lacpBundle.editConf.vlan.inboundBandwidth.correction.predefined.encapsulation.efm.fragmentSize"
   ::= {er1646v2LacpBVlanEntry 119821440}

er1646v2LacpBVlanInbBwCorrPredefEncapsEfmIb OBJECT-TYPE
   SYNTAX      Integer32
   MAX-ACCESS  read-write
   STATUS      current
   DESCRIPTION
      "Path: lacpBundle.editConf.vlan.inboundBandwidth.correction.predefined.encapsulation.efm.idleBytes"
   ::= {er1646v2LacpBVlanEntry 119821568}

er1646v2LacpBVlanInbBwCorrPredefMode OBJECT-TYPE
   SYNTAX      INTEGER
               {
               routing (0),
               bridging (1)
               }
   MAX-ACCESS  read-write
   STATUS      current
   DESCRIPTION
      "Path: lacpBundle.editConf.vlan.inboundBandwidth.correction.predefined.mode

       Possibilities:
               routing   (0)
               bridging   (1)"
   ::= {er1646v2LacpBVlanEntry 119832576}

er1646v2LacpBVlanInbBwCorrManualOverhead OBJECT-TYPE
   SYNTAX      Integer32
   MAX-ACCESS  read-write
   STATUS      current
   DESCRIPTION
      "Path: lacpBundle.editConf.vlan.inboundBandwidth.correction.manual.overhead"
   ::= {er1646v2LacpBVlanEntry 119931392}

er1646v2LacpBVlanInbBwCorrManualFrameData OBJECT-TYPE
   SYNTAX      Counter32
   MAX-ACCESS  read-write
   STATUS      current
   DESCRIPTION
      "Path: lacpBundle.editConf.vlan.inboundBandwidth.correction.manual.frameData

       32 bit unsigned wrappable counter."
   ::= {er1646v2LacpBVlanEntry 119931904}

er1646v2LacpBVlanInbBwCorrManualFrameHeader OBJECT-TYPE
   SYNTAX      Counter32
   MAX-ACCESS  read-write
   STATUS      current
   DESCRIPTION
      "Path: lacpBundle.editConf.vlan.inboundBandwidth.correction.manual.frameHeader

       32 bit unsigned wrappable counter."
   ::= {er1646v2LacpBVlanEntry 119932416}

er1646v2LacpBVlanInbBwMaxFifoQLen OBJECT-TYPE
   SYNTAX      Integer32
   MAX-ACCESS  read-write
   STATUS      current
   DESCRIPTION
      "Path: lacpBundle.editConf.vlan.inboundBandwidth.maxFifoQLen"
   ::= {er1646v2LacpBVlanEntry 120586240}

er1646v2LacpBVlanInbBwPriorityPolicy OBJECT-TYPE
   SYNTAX      DisplayString
   MAX-ACCESS  read-write
   STATUS      current
   DESCRIPTION
      "Path: lacpBundle.editConf.vlan.inboundBandwidth.priorityPolicy"
   ::= {er1646v2LacpBVlanEntry 121634816}

er1646v2LacpBVlanInbBwDeFlagCir OBJECT-TYPE
   SYNTAX      INTEGER
               {
               allowed (1),
               notAllowed (2)
               }
   MAX-ACCESS  read-write
   STATUS      current
   DESCRIPTION
      "Path: lacpBundle.editConf.vlan.inboundBandwidth.deFlag.cir

       Possibilities:
               allowed   (1)
               notAllowed   (2)"
   ::= {er1646v2LacpBVlanEntry 131076096}

er1646v2LacpBVlanInbBwDeFlagEir OBJECT-TYPE
   SYNTAX      INTEGER
               {
               allowed (1),
               notAllowed (2)
               }
   MAX-ACCESS  read-write
   STATUS      current
   DESCRIPTION
      "Path: lacpBundle.editConf.vlan.inboundBandwidth.deFlag.eir

       Possibilities:
               allowed   (1)
               notAllowed   (2)"
   ::= {er1646v2LacpBVlanEntry 131080192}

er1646v2LacpBVlanInbBwDeFlagViolate OBJECT-TYPE
   SYNTAX      INTEGER
               {
               allowed (1),
               notAllowed (2)
               }
   MAX-ACCESS  read-write
   STATUS      current
   DESCRIPTION
      "Path: lacpBundle.editConf.vlan.inboundBandwidth.deFlag.violate

       Possibilities:
               allowed   (1)
               notAllowed   (2)"
   ::= {er1646v2LacpBVlanEntry 131084288}

er1646v2LacpBVlanInbBwActCirActNone OBJECT-TYPE
   SYNTAX      OCTET STRING
   MAX-ACCESS  read-write
   STATUS      current
   DESCRIPTION
      "Path: lacpBundle.editConf.vlan.inboundBandwidth.action.cirAction.none"
   ::= {er1646v2LacpBVlanEntry 133308416}

er1646v2LacpBVlanInbBwActCirActEthCos1 OBJECT-TYPE
   SYNTAX      INTEGER
               {
               unchanged (256)
               }
   MAX-ACCESS  read-write
   STATUS      current
   DESCRIPTION
      "Path: lacpBundle.editConf.vlan.inboundBandwidth.action.cirAction.ethernet.cosDepth1

       Possibilities:
               unchanged   (256)"
   ::= {er1646v2LacpBVlanEntry 133316864}

er1646v2LacpBVlanInbBwActCirActEthDei1 OBJECT-TYPE
   SYNTAX      INTEGER
               {
               unchanged (255),
               clear (0),
               set (1)
               }
   MAX-ACCESS  read-write
   STATUS      current
   DESCRIPTION
      "Path: lacpBundle.editConf.vlan.inboundBandwidth.action.cirAction.ethernet.deiDepth1

       Possibilities:
               unchanged   (255)
               clear   (0)
               set   (1)"
   ::= {er1646v2LacpBVlanEntry 133321984}

er1646v2LacpBVlanInbBwActCirActEthCos2 OBJECT-TYPE
   SYNTAX      INTEGER
               {
               unchanged (256)
               }
   MAX-ACCESS  read-write
   STATUS      current
   DESCRIPTION
      "Path: lacpBundle.editConf.vlan.inboundBandwidth.action.cirAction.ethernet.cosDepth2

       Possibilities:
               unchanged   (256)"
   ::= {er1646v2LacpBVlanEntry 133317120}

er1646v2LacpBVlanInbBwActCirActEthDei2 OBJECT-TYPE
   SYNTAX      INTEGER
               {
               unchanged (255),
               clear (0),
               set (1)
               }
   MAX-ACCESS  read-write
   STATUS      current
   DESCRIPTION
      "Path: lacpBundle.editConf.vlan.inboundBandwidth.action.cirAction.ethernet.deiDepth2

       Possibilities:
               unchanged   (255)
               clear   (0)
               set   (1)"
   ::= {er1646v2LacpBVlanEntry 133322240}

er1646v2LacpBVlanInbBwActCirActEthCos3 OBJECT-TYPE
   SYNTAX      INTEGER
               {
               unchanged (256)
               }
   MAX-ACCESS  read-write
   STATUS      current
   DESCRIPTION
      "Path: lacpBundle.editConf.vlan.inboundBandwidth.action.cirAction.ethernet.cosDepth3

       Possibilities:
               unchanged   (256)"
   ::= {er1646v2LacpBVlanEntry 133317376}

er1646v2LacpBVlanInbBwActCirActEthDei3 OBJECT-TYPE
   SYNTAX      INTEGER
               {
               unchanged (255),
               clear (0),
               set (1)
               }
   MAX-ACCESS  read-write
   STATUS      current
   DESCRIPTION
      "Path: lacpBundle.editConf.vlan.inboundBandwidth.action.cirAction.ethernet.deiDepth3

       Possibilities:
               unchanged   (255)
               clear   (0)
               set   (1)"
   ::= {er1646v2LacpBVlanEntry 133322496}

er1646v2LacpBVlanInbBwActCirActEthCos4 OBJECT-TYPE
   SYNTAX      INTEGER
               {
               unchanged (256)
               }
   MAX-ACCESS  read-write
   STATUS      current
   DESCRIPTION
      "Path: lacpBundle.editConf.vlan.inboundBandwidth.action.cirAction.ethernet.cosDepth4

       Possibilities:
               unchanged   (256)"
   ::= {er1646v2LacpBVlanEntry 133317632}

er1646v2LacpBVlanInbBwActCirActEthDei4 OBJECT-TYPE
   SYNTAX      INTEGER
               {
               unchanged (255),
               clear (0),
               set (1)
               }
   MAX-ACCESS  read-write
   STATUS      current
   DESCRIPTION
      "Path: lacpBundle.editConf.vlan.inboundBandwidth.action.cirAction.ethernet.deiDepth4

       Possibilities:
               unchanged   (255)
               clear   (0)
               set   (1)"
   ::= {er1646v2LacpBVlanEntry 133322752}

er1646v2LacpBVlanInbBwActCirActEthCos5 OBJECT-TYPE
   SYNTAX      INTEGER
               {
               unchanged (256)
               }
   MAX-ACCESS  read-write
   STATUS      current
   DESCRIPTION
      "Path: lacpBundle.editConf.vlan.inboundBandwidth.action.cirAction.ethernet.cosDepth5

       Possibilities:
               unchanged   (256)"
   ::= {er1646v2LacpBVlanEntry 133317888}

er1646v2LacpBVlanInbBwActCirActEthDei5 OBJECT-TYPE
   SYNTAX      INTEGER
               {
               unchanged (255),
               clear (0),
               set (1)
               }
   MAX-ACCESS  read-write
   STATUS      current
   DESCRIPTION
      "Path: lacpBundle.editConf.vlan.inboundBandwidth.action.cirAction.ethernet.deiDepth5

       Possibilities:
               unchanged   (255)
               clear   (0)
               set   (1)"
   ::= {er1646v2LacpBVlanEntry 133323008}

er1646v2LacpBVlanInbBwActCirActEthCos6 OBJECT-TYPE
   SYNTAX      INTEGER
               {
               unchanged (256)
               }
   MAX-ACCESS  read-write
   STATUS      current
   DESCRIPTION
      "Path: lacpBundle.editConf.vlan.inboundBandwidth.action.cirAction.ethernet.cosDepth6

       Possibilities:
               unchanged   (256)"
   ::= {er1646v2LacpBVlanEntry 133318144}

er1646v2LacpBVlanInbBwActCirActEthDei6 OBJECT-TYPE
   SYNTAX      INTEGER
               {
               unchanged (255),
               clear (0),
               set (1)
               }
   MAX-ACCESS  read-write
   STATUS      current
   DESCRIPTION
      "Path: lacpBundle.editConf.vlan.inboundBandwidth.action.cirAction.ethernet.deiDepth6

       Possibilities:
               unchanged   (255)
               clear   (0)
               set   (1)"
   ::= {er1646v2LacpBVlanEntry 133323264}

er1646v2LacpBVlanInbBwActCirActEthCos7 OBJECT-TYPE
   SYNTAX      INTEGER
               {
               unchanged (256)
               }
   MAX-ACCESS  read-write
   STATUS      current
   DESCRIPTION
      "Path: lacpBundle.editConf.vlan.inboundBandwidth.action.cirAction.ethernet.cosDepth7

       Possibilities:
               unchanged   (256)"
   ::= {er1646v2LacpBVlanEntry 133318400}

er1646v2LacpBVlanInbBwActCirActEthDei7 OBJECT-TYPE
   SYNTAX      INTEGER
               {
               unchanged (255),
               clear (0),
               set (1)
               }
   MAX-ACCESS  read-write
   STATUS      current
   DESCRIPTION
      "Path: lacpBundle.editConf.vlan.inboundBandwidth.action.cirAction.ethernet.deiDepth7

       Possibilities:
               unchanged   (255)
               clear   (0)
               set   (1)"
   ::= {er1646v2LacpBVlanEntry 133323520}

er1646v2LacpBVlanInbBwActCirActEthCos8 OBJECT-TYPE
   SYNTAX      INTEGER
               {
               unchanged (256)
               }
   MAX-ACCESS  read-write
   STATUS      current
   DESCRIPTION
      "Path: lacpBundle.editConf.vlan.inboundBandwidth.action.cirAction.ethernet.cosDepth8

       Possibilities:
               unchanged   (256)"
   ::= {er1646v2LacpBVlanEntry 133318656}

er1646v2LacpBVlanInbBwActCirActEthDei8 OBJECT-TYPE
   SYNTAX      INTEGER
               {
               unchanged (255),
               clear (0),
               set (1)
               }
   MAX-ACCESS  read-write
   STATUS      current
   DESCRIPTION
      "Path: lacpBundle.editConf.vlan.inboundBandwidth.action.cirAction.ethernet.deiDepth8

       Possibilities:
               unchanged   (255)
               clear   (0)
               set   (1)"
   ::= {er1646v2LacpBVlanEntry 133323776}

er1646v2LacpBVlanInbBwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: lacpBundle.editConf.vlan.inboundBandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2LacpBVlanEntry 133318912}

er1646v2LacpBVlanInbBwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: lacpBundle.editConf.vlan.inboundBandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2LacpBVlanEntry 133319168}

er1646v2LacpBVlanInbBwActCirActEthDrpLev OBJECT-TYPE
   SYNTAX      INTEGER
               {
               unchanged (0)
               }
   MAX-ACCESS  read-write
   STATUS      current
   DESCRIPTION
      "Path: lacpBundle.editConf.vlan.inboundBandwidth.action.cirAction.ethernet.dropLevel

       Possibilities:
               unchanged   (0)"
   ::= {er1646v2LacpBVlanEntry 133319424}

er1646v2LacpBVlanInbBwActCirActEthDeFlag OBJECT-TYPE
   SYNTAX      INTEGER
               {
               unchanged (255),
               clear (0),
               set (1)
               }
   MAX-ACCESS  read-write
   STATUS      current
   DESCRIPTION
      "Path: lacpBundle.editConf.vlan.inboundBandwidth.action.cirAction.ethernet.deFlag

       Possibilities:
               unchanged   (255)
               clear   (0)
               set   (1)"
   ::= {er1646v2LacpBVlanEntry 133320192}

er1646v2LacpBVlanInbBwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: lacpBundle.editConf.vlan.inboundBandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2LacpBVlanEntry 133343488}

er1646v2LacpBVlanInbBwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: lacpBundle.editConf.vlan.inboundBandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2LacpBVlanEntry 133343744}

er1646v2LacpBVlanInbBwActCirActIpDrpLev OBJECT-TYPE
   SYNTAX      INTEGER
               {
               unchanged (0)
               }
   MAX-ACCESS  read-write
   STATUS      current
   DESCRIPTION
      "Path: lacpBundle.editConf.vlan.inboundBandwidth.action.cirAction.ip.dropLevel

       Possibilities:
               unchanged   (0)"
   ::= {er1646v2LacpBVlanEntry 133344000}

er1646v2LacpBVlanInbBwActCirActIpDeFlag OBJECT-TYPE
   SYNTAX      INTEGER
               {
               unchanged (255),
               clear (0),
               set (1)
               }
   MAX-ACCESS  read-write
   STATUS      current
   DESCRIPTION
      "Path: lacpBundle.editConf.vlan.inboundBandwidth.action.cirAction.ip.deFlag

       Possibilities:
               unchanged   (255)
               clear   (0)
               set   (1)"
   ::= {er1646v2LacpBVlanEntry 133344768}

er1646v2LacpBVlanInbBwActEirActNone OBJECT-TYPE
   SYNTAX      OCTET STRING
   MAX-ACCESS  read-write
   STATUS      current
   DESCRIPTION
      "Path: lacpBundle.editConf.vlan.inboundBandwidth.action.eirAction.none"
   ::= {er1646v2LacpBVlanEntry 133439488}

er1646v2LacpBVlanInbBwActEirActEthCos1 OBJECT-TYPE
   SYNTAX      INTEGER
               {
               unchanged (256)
               }
   MAX-ACCESS  read-write
   STATUS      current
   DESCRIPTION
      "Path: lacpBundle.editConf.vlan.inboundBandwidth.action.eirAction.ethernet.cosDepth1

       Possibilities:
               unchanged   (256)"
   ::= {er1646v2LacpBVlanEntry 133447936}

er1646v2LacpBVlanInbBwActEirActEthDei1 OBJECT-TYPE
   SYNTAX      INTEGER
               {
               unchanged (255),
               clear (0),
               set (1)
               }
   MAX-ACCESS  read-write
   STATUS      current
   DESCRIPTION
      "Path: lacpBundle.editConf.vlan.inboundBandwidth.action.eirAction.ethernet.deiDepth1

       Possibilities:
               unchanged   (255)
               clear   (0)
               set   (1)"
   ::= {er1646v2LacpBVlanEntry 133453056}

er1646v2LacpBVlanInbBwActEirActEthCos2 OBJECT-TYPE
   SYNTAX      INTEGER
               {
               unchanged (256)
               }
   MAX-ACCESS  read-write
   STATUS      current
   DESCRIPTION
      "Path: lacpBundle.editConf.vlan.inboundBandwidth.action.eirAction.ethernet.cosDepth2

       Possibilities:
               unchanged   (256)"
   ::= {er1646v2LacpBVlanEntry 133448192}

er1646v2LacpBVlanInbBwActEirActEthDei2 OBJECT-TYPE
   SYNTAX      INTEGER
               {
               unchanged (255),
               clear (0),
               set (1)
               }
   MAX-ACCESS  read-write
   STATUS      current
   DESCRIPTION
      "Path: lacpBundle.editConf.vlan.inboundBandwidth.action.eirAction.ethernet.deiDepth2

       Possibilities:
               unchanged   (255)
               clear   (0)
               set   (1)"
   ::= {er1646v2LacpBVlanEntry 133453312}

er1646v2LacpBVlanInbBwActEirActEthCos3 OBJECT-TYPE
   SYNTAX      INTEGER
               {
               unchanged (256)
               }
   MAX-ACCESS  read-write
   STATUS      current
   DESCRIPTION
      "Path: lacpBundle.editConf.vlan.inboundBandwidth.action.eirAction.ethernet.cosDepth3

       Possibilities:
               unchanged   (256)"
   ::= {er1646v2LacpBVlanEntry 133448448}

er1646v2LacpBVlanInbBwActEirActEthDei3 OBJECT-TYPE
   SYNTAX      INTEGER
               {
               unchanged (255),
               clear (0),
               set (1)
               }
   MAX-ACCESS  read-write
   STATUS      current
   DESCRIPTION
      "Path: lacpBundle.editConf.vlan.inboundBandwidth.action.eirAction.ethernet.deiDepth3

       Possibilities:
               unchanged   (255)
               clear   (0)
               set   (1)"
   ::= {er1646v2LacpBVlanEntry 133453568}

er1646v2LacpBVlanInbBwActEirActEthCos4 OBJECT-TYPE
   SYNTAX      INTEGER
               {
               unchanged (256)
               }
   MAX-ACCESS  read-write
   STATUS      current
   DESCRIPTION
      "Path: lacpBundle.editConf.vlan.inboundBandwidth.action.eirAction.ethernet.cosDepth4

       Possibilities:
               unchanged   (256)"
   ::= {er1646v2LacpBVlanEntry 133448704}

er1646v2LacpBVlanInbBwActEirActEthDei4 OBJECT-TYPE
   SYNTAX      INTEGER
               {
               unchanged (255),
               clear (0),
               set (1)
               }
   MAX-ACCESS  read-write
   STATUS      current
   DESCRIPTION
      "Path: lacpBundle.editConf.vlan.inboundBandwidth.action.eirAction.ethernet.deiDepth4

       Possibilities:
               unchanged   (255)
               clear   (0)
               set   (1)"
   ::= {er1646v2LacpBVlanEntry 133453824}

er1646v2LacpBVlanInbBwActEirActEthCos5 OBJECT-TYPE
   SYNTAX      INTEGER
               {
               unchanged (256)
               }
   MAX-ACCESS  read-write
   STATUS      current
   DESCRIPTION
      "Path: lacpBundle.editConf.vlan.inboundBandwidth.action.eirAction.ethernet.cosDepth5

       Possibilities:
               unchanged   (256)"
   ::= {er1646v2LacpBVlanEntry 133448960}

er1646v2LacpBVlanInbBwActEirActEthDei5 OBJECT-TYPE
   SYNTAX      INTEGER
               {
               unchanged (255),
               clear (0),
               set (1)
               }
   MAX-ACCESS  read-write
   STATUS      current
   DESCRIPTION
      "Path: lacpBundle.editConf.vlan.inboundBandwidth.action.eirAction.ethernet.deiDepth5

       Possibilities:
               unchanged   (255)
               clear   (0)
               set   (1)"
   ::= {er1646v2LacpBVlanEntry 133454080}

er1646v2LacpBVlanInbBwActEirActEthCos6 OBJECT-TYPE
   SYNTAX      INTEGER
               {
               unchanged (256)
               }
   MAX-ACCESS  read-write
   STATUS      current
   DESCRIPTION
      "Path: lacpBundle.editConf.vlan.inboundBandwidth.action.eirAction.ethernet.cosDepth6

       Possibilities:
               unchanged   (256)"
   ::= {er1646v2LacpBVlanEntry 133449216}

er1646v2LacpBVlanInbBwActEirActEthDei6 OBJECT-TYPE
   SYNTAX      INTEGER
               {
               unchanged (255),
               clear (0),
               set (1)
               }
   MAX-ACCESS  read-write
   STATUS      current
   DESCRIPTION
      "Path: lacpBundle.editConf.vlan.inboundBandwidth.action.eirAction.ethernet.deiDepth6

       Possibilities:
               unchanged   (255)
               clear   (0)
               set   (1)"
   ::= {er1646v2LacpBVlanEntry 133454336}

er1646v2LacpBVlanInbBwActEirActEthCos7 OBJECT-TYPE
   SYNTAX      INTEGER
               {
               unchanged (256)
               }
   MAX-ACCESS  read-write
   STATUS      current
   DESCRIPTION
      "Path: lacpBundle.editConf.vlan.inboundBandwidth.action.eirAction.ethernet.cosDepth7

       Possibilities:
               unchanged   (256)"
   ::= {er1646v2LacpBVlanEntry 133449472}

er1646v2LacpBVlanInbBwActEirActEthDei7 OBJECT-TYPE
   SYNTAX      INTEGER
               {
               unchanged (255),
               clear (0),
               set (1)
               }
   MAX-ACCESS  read-write
   STATUS      current
   DESCRIPTION
      "Path: lacpBundle.editConf.vlan.inboundBandwidth.action.eirAction.ethernet.deiDepth7

       Possibilities:
               unchanged   (255)
               clear   (0)
               set   (1)"
   ::= {er1646v2LacpBVlanEntry 133454592}

er1646v2LacpBVlanInbBwActEirActEthCos8 OBJECT-TYPE
   SYNTAX      INTEGER
               {
               unchanged (256)
               }
   MAX-ACCESS  read-write
   STATUS      current
   DESCRIPTION
      "Path: lacpBundle.editConf.vlan.inboundBandwidth.action.eirAction.ethernet.cosDepth8

       Possibilities:
               unchanged   (256)"
   ::= {er1646v2LacpBVlanEntry 133449728}

er1646v2LacpBVlanInbBwActEirActEthDei8 OBJECT-TYPE
   SYNTAX      INTEGER
               {
               unchanged (255),
               clear (0),
               set (1)
               }
   MAX-ACCESS  read-write
   STATUS      current
   DESCRIPTION
      "Path: lacpBundle.editConf.vlan.inboundBandwidth.action.eirAction.ethernet.deiDepth8

       Possibilities:
               unchanged   (255)
               clear   (0)
               set   (1)"
   ::= {er1646v2LacpBVlanEntry 133454848}

er1646v2LacpBVlanInbBwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: lacpBundle.editConf.vlan.inboundBandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2LacpBVlanEntry 133449984}

er1646v2LacpBVlanInbBwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: lacpBundle.editConf.vlan.inboundBandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2LacpBVlanEntry 133450240}

er1646v2LacpBVlanInbBwActEirActEthDrpLev OBJECT-TYPE
   SYNTAX      INTEGER
               {
               unchanged (0)
               }
   MAX-ACCESS  read-write
   STATUS      current
   DESCRIPTION
      "Path: lacpBundle.editConf.vlan.inboundBandwidth.action.eirAction.ethernet.dropLevel

       Possibilities:
               unchanged   (0)"
   ::= {er1646v2LacpBVlanEntry 133450496}

er1646v2LacpBVlanInbBwActEirActEthDeFlag OBJECT-TYPE
   SYNTAX      INTEGER
               {
               unchanged (255),
               clear (0),
               set (1)
               }
   MAX-ACCESS  read-write
   STATUS      current
   DESCRIPTION
      "Path: lacpBundle.editConf.vlan.inboundBandwidth.action.eirAction.ethernet.deFlag

       Possibilities:
               unchanged   (255)
               clear   (0)
               set   (1)"
   ::= {er1646v2LacpBVlanEntry 133451264}

er1646v2LacpBVlanInbBwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: lacpBundle.editConf.vlan.inboundBandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2LacpBVlanEntry 133474560}

er1646v2LacpBVlanInbBwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: lacpBundle.editConf.vlan.inboundBandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2LacpBVlanEntry 133474816}

er1646v2LacpBVlanInbBwActEirActIpDrpLev OBJECT-TYPE
   SYNTAX      INTEGER
               {
               unchanged (0)
               }
   MAX-ACCESS  read-write
   STATUS      current
   DESCRIPTION
      "Path: lacpBundle.editConf.vlan.inboundBandwidth.action.eirAction.ip.dropLevel

       Possibilities:
               unchanged   (0)"
   ::= {er1646v2LacpBVlanEntry 133475072}

er1646v2LacpBVlanInbBwActEirActIpDeFlag OBJECT-TYPE
   SYNTAX      INTEGER
               {
               unchanged (255),
               clear (0),
               set (1)
               }
   MAX-ACCESS  read-write
   STATUS      current
   DESCRIPTION
      "Path: lacpBundle.editConf.vlan.inboundBandwidth.action.eirAction.ip.deFlag

       Possibilities:
               unchanged   (255)
               clear   (0)
               set   (1)"
   ::= {er1646v2LacpBVlanEntry 133475840}

er1646v2LacpBVlanInbBwActViolActNone OBJECT-TYPE
   SYNTAX      OCTET STRING
   MAX-ACCESS  read-write
   STATUS      current
   DESCRIPTION
      "Path: lacpBundle.editConf.vlan.inboundBandwidth.action.violateAction.none"
   ::= {er1646v2LacpBVlanEntry 133570560}

er1646v2LacpBVlanInbBwActViolActDrop OBJECT-TYPE
   SYNTAX      OCTET STRING
   MAX-ACCESS  read-write
   STATUS      current
   DESCRIPTION
      "Path: lacpBundle.editConf.vlan.inboundBandwidth.action.violateAction.drop"
   ::= {er1646v2LacpBVlanEntry 133586944}

er1646v2LacpBVlanInbBwActViolActEthCos1 OBJECT-TYPE
   SYNTAX      INTEGER
               {
               unchanged (256)
               }
   MAX-ACCESS  read-write
   STATUS      current
   DESCRIPTION
      "Path: lacpBundle.editConf.vlan.inboundBandwidth.action.violateAction.ethernet.cosDepth1

       Possibilities:
               unchanged   (256)"
   ::= {er1646v2LacpBVlanEntry 133579008}

er1646v2LacpBVlanInbBwActViolActEthDei1 OBJECT-TYPE
   SYNTAX      INTEGER
               {
               unchanged (255),
               clear (0),
               set (1)
               }
   MAX-ACCESS  read-write
   STATUS      current
   DESCRIPTION
      "Path: lacpBundle.editConf.vlan.inboundBandwidth.action.violateAction.ethernet.deiDepth1

       Possibilities:
               unchanged   (255)
               clear   (0)
               set   (1)"
   ::= {er1646v2LacpBVlanEntry 133584128}

er1646v2LacpBVlanInbBwActViolActEthCos2 OBJECT-TYPE
   SYNTAX      INTEGER
               {
               unchanged (256)
               }
   MAX-ACCESS  read-write
   STATUS      current
   DESCRIPTION
      "Path: lacpBundle.editConf.vlan.inboundBandwidth.action.violateAction.ethernet.cosDepth2

       Possibilities:
               unchanged   (256)"
   ::= {er1646v2LacpBVlanEntry 133579264}

er1646v2LacpBVlanInbBwActViolActEthDei2 OBJECT-TYPE
   SYNTAX      INTEGER
               {
               unchanged (255),
               clear (0),
               set (1)
               }
   MAX-ACCESS  read-write
   STATUS      current
   DESCRIPTION
      "Path: lacpBundle.editConf.vlan.inboundBandwidth.action.violateAction.ethernet.deiDepth2

       Possibilities:
               unchanged   (255)
               clear   (0)
               set   (1)"
   ::= {er1646v2LacpBVlanEntry 133584384}

er1646v2LacpBVlanInbBwActViolActEthCos3 OBJECT-TYPE
   SYNTAX      INTEGER
               {
               unchanged (256)
               }
   MAX-ACCESS  read-write
   STATUS      current
   DESCRIPTION
      "Path: lacpBundle.editConf.vlan.inboundBandwidth.action.violateAction.ethernet.cosDepth3

       Possibilities:
               unchanged   (256)"
   ::= {er1646v2LacpBVlanEntry 133579520}

er1646v2LacpBVlanInbBwActViolActEthDei3 OBJECT-TYPE
   SYNTAX      INTEGER
               {
               unchanged (255),
               clear (0),
               set (1)
               }
   MAX-ACCESS  read-write
   STATUS      current
   DESCRIPTION
      "Path: lacpBundle.editConf.vlan.inboundBandwidth.action.violateAction.ethernet.deiDepth3

       Possibilities:
               unchanged   (255)
               clear   (0)
               set   (1)"
   ::= {er1646v2LacpBVlanEntry 133584640}

er1646v2LacpBVlanInbBwActViolActEthCos4 OBJECT-TYPE
   SYNTAX      INTEGER
               {
               unchanged (256)
               }
   MAX-ACCESS  read-write
   STATUS      current
   DESCRIPTION
      "Path: lacpBundle.editConf.vlan.inboundBandwidth.action.violateAction.ethernet.cosDepth4

       Possibilities:
               unchanged   (256)"
   ::= {er1646v2LacpBVlanEntry 133579776}

er1646v2LacpBVlanInbBwActViolActEthDei4 OBJECT-TYPE
   SYNTAX      INTEGER
               {
               unchanged (255),
               clear (0),
               set (1)
               }
   MAX-ACCESS  read-write
   STATUS      current
   DESCRIPTION
      "Path: lacpBundle.editConf.vlan.inboundBandwidth.action.violateAction.ethernet.deiDepth4

       Possibilities:
               unchanged   (255)
               clear   (0)
               set   (1)"
   ::= {er1646v2LacpBVlanEntry 133584896}

er1646v2LacpBVlanInbBwActViolActEthCos5 OBJECT-TYPE
   SYNTAX      INTEGER
               {
               unchanged (256)
               }
   MAX-ACCESS  read-write
   STATUS      current
   DESCRIPTION
      "Path: lacpBundle.editConf.vlan.inboundBandwidth.action.violateAction.ethernet.cosDepth5

       Possibilities:
               unchanged   (256)"
   ::= {er1646v2LacpBVlanEntry 133580032}

er1646v2LacpBVlanInbBwActViolActEthDei5 OBJECT-TYPE
   SYNTAX      INTEGER
               {
               unchanged (255),
               clear (0),
               set (1)
               }
   MAX-ACCESS  read-write
   STATUS      current
   DESCRIPTION
      "Path: lacpBundle.editConf.vlan.inboundBandwidth.action.violateAction.ethernet.deiDepth5

       Possibilities:
               unchanged   (255)
               clear   (0)
               set   (1)"
   ::= {er1646v2LacpBVlanEntry 133585152}

er1646v2LacpBVlanInbBwActViolActEthCos6 OBJECT-TYPE
   SYNTAX      INTEGER
               {
               unchanged (256)
               }
   MAX-ACCESS  read-write
   STATUS      current
   DESCRIPTION
      "Path: lacpBundle.editConf.vlan.inboundBandwidth.action.violateAction.ethernet.cosDepth6

       Possibilities:
               unchanged   (256)"
   ::= {er1646v2LacpBVlanEntry 133580288}

er1646v2LacpBVlanInbBwActViolActEthDei6 OBJECT-TYPE
   SYNTAX      INTEGER
               {
               unchanged (255),
               clear (0),
               set (1)
               }
   MAX-ACCESS  read-write
   STATUS      current
   DESCRIPTION
      "Path: lacpBundle.editConf.vlan.inboundBandwidth.action.violateAction.ethernet.deiDepth6

       Possibilities:
               unchanged   (255)
               clear   (0)
               set   (1)"
   ::= {er1646v2LacpBVlanEntry 133585408}

er1646v2LacpBVlanInbBwActViolActEthCos7 OBJECT-TYPE
   SYNTAX      INTEGER
               {
               unchanged (256)
               }
   MAX-ACCESS  read-write
   STATUS      current
   DESCRIPTION
      "Path: lacpBundle.editConf.vlan.inboundBandwidth.action.violateAction.ethernet.cosDepth7

       Possibilities:
               unchanged   (256)"
   ::= {er1646v2LacpBVlanEntry 133580544}

er1646v2LacpBVlanInbBwActViolActEthDei7 OBJECT-TYPE
   SYNTAX      INTEGER
               {
               unchanged (255),
               clear (0),
               set (1)
               }
   MAX-ACCESS  read-write
   STATUS      current
   DESCRIPTION
      "Path: lacpBundle.editConf.vlan.inboundBandwidth.action.violateAction.ethernet.deiDepth7

       Possibilities:
               unchanged   (255)
               clear   (0)
               set   (1)"
   ::= {er1646v2LacpBVlanEntry 133585664}

er1646v2LacpBVlanInbBwActViolActEthCos8 OBJECT-TYPE
   SYNTAX      INTEGER
               {
               unchanged (256)
               }
   MAX-ACCESS  read-write
   STATUS      current
   DESCRIPTION
      "Path: lacpBundle.editConf.vlan.inboundBandwidth.action.violateAction.ethernet.cosDepth8

       Possibilities:
               unchanged   (256)"
   ::= {er1646v2LacpBVlanEntry 133580800}

er1646v2LacpBVlanInbBwActViolActEthDei8 OBJECT-TYPE
   SYNTAX      INTEGER
               {
               unchanged (255),
               clear (0),
               set (1)
               }
   MAX-ACCESS  read-write
   STATUS      current
   DESCRIPTION
      "Path: lacpBundle.editConf.vlan.inboundBandwidth.action.violateAction.ethernet.deiDepth8

       Possibilities:
               unchanged   (255)
               clear   (0)
               set   (1)"
   ::= {er1646v2LacpBVlanEntry 133585920}

er1646v2LacpBVlanInbBwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: lacpBundle.editConf.vlan.inboundBandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2LacpBVlanEntry 133581056}

er1646v2LacpBVlanInbBwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: lacpBundle.editConf.vlan.inboundBandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2LacpBVlanEntry 133581312}

er1646v2LacpBVlanInbBwActViolActEthDrpLev OBJECT-TYPE
   SYNTAX      INTEGER
               {
               unchanged (0)
               }
   MAX-ACCESS  read-write
   STATUS      current
   DESCRIPTION
      "Path: lacpBundle.editConf.vlan.inboundBandwidth.action.violateAction.ethernet.dropLevel

       Possibilities:
               unchanged   (0)"
   ::= {er1646v2LacpBVlanEntry 133581568}

er1646v2LacpBVlanInbBwActViolActEthDeFlag OBJECT-TYPE
   SYNTAX      INTEGER
               {
               unchanged (255),
               clear (0),
               set (1)
               }
   MAX-ACCESS  read-write
   STATUS      current
   DESCRIPTION
      "Path: lacpBundle.editConf.vlan.inboundBandwidth.action.violateAction.ethernet.deFlag

       Possibilities:
               unchanged   (255)
               clear   (0)
               set   (1)"
   ::= {er1646v2LacpBVlanEntry 133582336}

er1646v2LacpBVlanInbBwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: lacpBundle.editConf.vlan.inboundBandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2LacpBVlanEntry 133605632}

er1646v2LacpBVlanInbBwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: lacpBundle.editConf.vlan.inboundBandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1646v2LacpBVlanEntry 133605888}

er1646v2LacpBVlanInbBwActViolActIpDrpLev OBJECT-TYPE
   SYNTAX      INTEGER
               {
               unchanged (0)
               }
   MAX-ACCESS  read-write
   STATUS      current
   DESCRIPTION
      "Path: lacpBundle.editConf.vlan.inboundBandwidth.action.violateAction.ip.dropLevel

       Possibilities:
               unchanged   (0)"
   ::= {er1646v2LacpBVlanEntry 133606144}

er1646v2LacpBVlanInbBwActViolActIpDeFlag OBJECT-TYPE
   SYNTAX      INTEGER
               {
               unchanged (255),
               clear (0),
               set (1)
               }
   MAX-ACCESS  read-write
   STATUS      current
   DESCRIPTION
      "Path: lacpBundle.editConf.vlan.inboundBandwidth.action.violateAction.ip.deFlag

       Possibilities:
               unchanged   (255)
               clear   (0)
               set   (1)"
   ::= {er1646v2LacpBVlanEntry 133606912}

er1646v2LacpBVlanPppoE OBJECT-TYPE
   SYNTAX      INTEGER
               {
               disabled (0),
               enabled (1)
               }
   MAX-ACCESS  read-write
   STATUS      current
   DESCRIPTION
      "Path: lacpBundle.editConf.vlan.pppoE

       Possibilities:
               disabled   (0)
               enabled   (1)"
   ::= {er1646v2LacpBVlanEntry 838860800}

er1646v2LacpBVlanPppLnkMOperation OBJECT-TYPE
   SYNTAX      INTEGER
               {
               disabled (0),
               enabled (1)
               }
   MAX-ACCESS  read-write
   STATUS      current
   DESCRIPTION
      "Path: lacpBundle.editConf.vlan.ppp.linkMonitoring.operation

       Possibilities:
               disabled   (0)
               enabled   (1)"
   ::= {er1646v2LacpBVlanEntry 251724032}

er1646v2LacpBVlanPppLnkMInterval OBJECT-TYPE
   SYNTAX      TimeTicks
   MAX-ACCESS  read-write
   STATUS      current
   DESCRIPTION
      "Path: lacpBundle.editConf.vlan.ppp.linkMonitoring.interval

       Time in centi-second."
   ::= {er1646v2LacpBVlanEntry 251724288}

er1646v2LacpBVlanPppLnkMRepTimeOut OBJECT-TYPE
   SYNTAX      TimeTicks
   MAX-ACCESS  read-write
   STATUS      current
   DESCRIPTION
      "Path: lacpBundle.editConf.vlan.ppp.linkMonitoring.replyTimeOut

       Time in centi-second."
   ::= {er1646v2LacpBVlanEntry 251724544}

er1646v2LacpBVlanPppLnkMFailsPrmt OBJECT-TYPE
   SYNTAX      Integer32
   MAX-ACCESS  read-write
   STATUS      current
   DESCRIPTION
      "Path: lacpBundle.editConf.vlan.ppp.linkMonitoring.failsPermitted"
   ::= {er1646v2LacpBVlanEntry 251724800}

er1646v2LacpBVlanPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: lacpBundle.editConf.vlan.ppp.authentication

       Possibilities:
               disabled   (0)
               chap   (1)
               pap   (2)
               chapOrPap   (3)
               msChap   (4)
               msChapV2   (5)"
   ::= {er1646v2LacpBVlanEntry 251789312}

er1646v2LacpBVlanPppAuthenPeriod OBJECT-TYPE
   SYNTAX      TimeTicks
   MAX-ACCESS  read-write
   STATUS      current
   DESCRIPTION
      "Path: lacpBundle.editConf.vlan.ppp.authenPeriod

       Time in centi-second."
   ::= {er1646v2LacpBVlanEntry 251854848}

er1646v2LacpBVlanPppSessionName OBJECT-TYPE
   SYNTAX      DisplayString
   MAX-ACCESS  read-write
   STATUS      current
   DESCRIPTION
      "Path: lacpBundle.editConf.vlan.ppp.sessionName"
   ::= {er1646v2LacpBVlanEntry 251985920}

er1646v2LacpBVlanPppSessionSecret OBJECT-TYPE
   SYNTAX      DisplayString
   MAX-ACCESS  read-write
   STATUS      current
   DESCRIPTION
      "Path: lacpBundle.editConf.vlan.ppp.sessionSecret"
   ::= {er1646v2LacpBVlanEntry 252051456}

er1646v2LacpBVlanPppEncModeSessionSecret OBJECT-TYPE
   SYNTAX      INTEGER
               {
               none (1),
               encrypt (2),
               encType1 (3),
               invalid (128)
               }
   MAX-ACCESS  read-write
   STATUS      current
   DESCRIPTION
      "Path: lacpBundle.editConf.vlan.ppp.encModeSessionSecret

       Possibilities:
               none   (1)
               encrypt   (2)
               encType1   (3)
               invalid   (128)"
   ::= {er1646v2LacpBVlanEntry 252182528}

er1646v2LacpBVlanPppEncSessionSecret OBJECT-TYPE
   SYNTAX      DisplayString
   MAX-ACCESS  read-write
   STATUS      current
   DESCRIPTION
      "Path: lacpBundle.editConf.vlan.ppp.encSessionSecret"
   ::= {er1646v2LacpBVlanEntry 252248064}

er1646v2LacpBVlanPppServiceName OBJECT-TYPE
   SYNTAX      DisplayString
   MAX-ACCESS  read-write
   STATUS      current
   DESCRIPTION
      "Path: lacpBundle.editConf.vlan.ppp.serviceName"
   ::= {er1646v2LacpBVlanEntry 252116992}

er1646v2LacpBVlanPbbMode OBJECT-TYPE
   SYNTAX      INTEGER
               {
               disabled (0),
               static (1),
               dynamicPtp (2),
               dynamicPtmp (3)
               }
   MAX-ACCESS  read-write
   STATUS      current
   DESCRIPTION
      "Path: lacpBundle.editConf.vlan.pbb.mode

       Possibilities:
               disabled   (0)
               static   (1)
               dynamicPtp   (2)
               dynamicPtmp   (3)"
   ::= {er1646v2LacpBVlanEntry 1174667264}

er1646v2LacpBVlanPbbTxCos OBJECT-TYPE
   SYNTAX      Integer32
   MAX-ACCESS  read-write
   STATUS      current
   DESCRIPTION
      "Path: lacpBundle.editConf.vlan.pbb.txCos"
   ::= {er1646v2LacpBVlanEntry 1175191552}

er1646v2LacpBVlanPbbIsid OBJECT-TYPE
   SYNTAX      Integer32
   MAX-ACCESS  read-write
   STATUS      current
   DESCRIPTION
      "Path: lacpBundle.editConf.vlan.pbb.isid"
   ::= {er1646v2LacpBVlanEntry 1175453696}

er1646v2LacpBVlanPbbDestMac OBJECT-TYPE
   SYNTAX      OCTET STRING
   MAX-ACCESS  read-write
   STATUS      current
   DESCRIPTION
      "Path: lacpBundle.editConf.vlan.pbb.destMac

       MAC address."
   ::= {er1646v2LacpBVlanEntry 1175715840}

er1646v2LacpBVlanPbbCustomGroupMac OBJECT-TYPE
   SYNTAX      OCTET STRING
   MAX-ACCESS  read-write
   STATUS      current
   DESCRIPTION
      "Path: lacpBundle.editConf.vlan.pbb.customGroupMac

       MAC address."
   ::= {er1646v2LacpBVlanEntry 1175977984}

er1646v2LacpBVlanIpSaddr OBJECT-TYPE
   SYNTAX      SEQUENCE OF Er1646v2LacpBVlanIpSaddrEntry
   MAX-ACCESS  not-accessible
   STATUS      current
   DESCRIPTION
      ""
   ::= {er1646v2LacpBVlan 51838976}

er1646v2LacpBVlanIpSaddrEntry OBJECT-TYPE
   SYNTAX      Er1646v2LacpBVlanIpSaddrEntry
   MAX-ACCESS  not-accessible
   STATUS      current
   DESCRIPTION
      ""
   INDEX      { er1646v2LacpBVlanIpSaddrGlobalIx,
                er1646v2LacpBVlanTableIx,
                er1646v2LacpBVlanIpSaddrTableIx }
   ::= {er1646v2LacpBVlanIpSaddr 1}

Er1646v2LacpBVlanIpSaddrEntry ::=
   SEQUENCE
      {
      er1646v2LacpBVlanIpSaddrActions
         VariableLengthTableActions,
      er1646v2LacpBVlanIpSaddrGlobalIx
         GlobalIndex,
      er1646v2LacpBVlanIpSaddrTableIx
         TableIndex,
      er1646v2LacpBVlanIpSaddrAddress
         IpAddress,
      er1646v2LacpBVlanIpSaddrNetMask
         IpAddress
      }

er1646v2LacpBVlanIpSaddrActions OBJECT-TYPE
   SYNTAX      VariableLengthTableActions
   MAX-ACCESS  read-write
   STATUS      current
   DESCRIPTION
      "By way of this field, some manipulations
       on this table may be performed."
   ::= {er1646v2LacpBVlanIpSaddrEntry 2}

er1646v2LacpBVlanIpSaddrGlobalIx OBJECT-TYPE
   SYNTAX      GlobalIndex
   MAX-ACCESS  not-accessible
   STATUS      current
   DESCRIPTION
      "The value of the tlsCntTreeGlobalIndex of the MANAGED OBJECT."
   ::= {er1646v2LacpBVlanIpSaddrEntry 10}

er1646v2LacpBVlanIpSaddrTableIx OBJECT-TYPE
   SYNTAX      TableIndex
   MAX-ACCESS  not-accessible
   STATUS      current
   DESCRIPTION
      ""
   ::= {er1646v2LacpBVlanIpSaddrEntry 11}

er1646v2LacpBVlanIpSaddrAddress OBJECT-TYPE
   SYNTAX      IpAddress
   MAX-ACCESS  read-write
   STATUS      current
   DESCRIPTION
      "Path: lacpBundle.editConf.vlan.ip.secondaryIp.address"
   ::= {er1646v2LacpBVlanIpSaddrEntry 2030043136}

er1646v2LacpBVlanIpSaddrNetMask OBJECT-TYPE
   SYNTAX      IpAddress
   MAX-ACCESS  read-write
   STATUS      current
   DESCRIPTION
      "Path: lacpBundle.editConf.vlan.ip.secondaryIp.netMask"
   ::= {er1646v2LacpBVlanIpSaddrEntry 2063597568}

er1646v2LacpBVlanIpH OBJECT-TYPE
   SYNTAX      SEQUENCE OF Er1646v2LacpBVlanIpHEntry
   MAX-ACCESS  not-accessible
   STATUS      current
   DESCRIPTION
      ""
   ::= {er1646v2LacpBVlan 51314688}

er1646v2LacpBVlanIpHEntry OBJECT-TYPE
   SYNTAX      Er1646v2LacpBVlanIpHEntry
   MAX-ACCESS  not-accessible
   STATUS      current
   DESCRIPTION
      ""
   INDEX      { er1646v2LacpBVlanIpHGlobalIx,
                er1646v2LacpBVlanTableIx,
                er1646v2LacpBVlanIpHTableIx }
   ::= {er1646v2LacpBVlanIpH 1}

Er1646v2LacpBVlanIpHEntry ::=
   SEQUENCE
      {
      er1646v2LacpBVlanIpHActions
         VariableLengthTableActions,
      er1646v2LacpBVlanIpHGlobalIx
         GlobalIndex,
      er1646v2LacpBVlanIpHTableIx
         TableIndex,
      er1646v2LacpBVlanIpHAddress
         IpAddress,
      er1646v2LacpBVlanIpHDhcpRelayOptionSubscriberId
         DisplayString
      }

er1646v2LacpBVlanIpHActions OBJECT-TYPE
   SYNTAX      VariableLengthTableActions
   MAX-ACCESS  read-write
   STATUS      current
   DESCRIPTION
      "By way of this field, some manipulations
       on this table may be performed."
   ::= {er1646v2LacpBVlanIpHEntry 2}

er1646v2LacpBVlanIpHGlobalIx OBJECT-TYPE
   SYNTAX      GlobalIndex
   MAX-ACCESS  not-accessible
   STATUS      current
   DESCRIPTION
      "The value of the tlsCntTreeGlobalIndex of the MANAGED OBJECT."
   ::= {er1646v2LacpBVlanIpHEntry 10}

er1646v2LacpBVlanIpHTableIx OBJECT-TYPE
   SYNTAX      TableIndex
   MAX-ACCESS  not-accessible
   STATUS      current
   DESCRIPTION
      ""
   ::= {er1646v2LacpBVlanIpHEntry 11}

er1646v2LacpBVlanIpHAddress OBJECT-TYPE
   SYNTAX      IpAddress
   MAX-ACCESS  read-write
   STATUS      current
   DESCRIPTION
      "Path: lacpBundle.editConf.vlan.ip.helpers.address"
   ::= {er1646v2LacpBVlanIpHEntry 16777216}

er1646v2LacpBVlanIpHDhcpRelayOptionSubscriberId OBJECT-TYPE
   SYNTAX      DisplayString
   MAX-ACCESS  read-write
   STATUS      current
   DESCRIPTION
      "Path: lacpBundle.editConf.vlan.ip.helpers.dhcpRelayOption.subscriberId"
   ::= {er1646v2LacpBVlanIpHEntry 33947648}

er1646v2LacpBVlanIpV6Addresses OBJECT-TYPE
   SYNTAX      SEQUENCE OF Er1646v2LacpBVlanIpV6AddressesEntry
   MAX-ACCESS  not-accessible
   STATUS      current
   DESCRIPTION
      ""
   ::= {er1646v2LacpBVlan 704839680}

er1646v2LacpBVlanIpV6AddressesEntry OBJECT-TYPE
   SYNTAX      Er1646v2LacpBVlanIpV6AddressesEntry
   MAX-ACCESS  not-accessible
   STATUS      current
   DESCRIPTION
      ""
   INDEX      { er1646v2LacpBVlanIpV6AddressesGlobalIx,
                er1646v2LacpBVlanTableIx,
                er1646v2LacpBVlanIpV6AddressesTableIx }
   ::= {er1646v2LacpBVlanIpV6Addresses 1}

Er1646v2LacpBVlanIpV6AddressesEntry ::=
   SEQUENCE
      {
      er1646v2LacpBVlanIpV6AddressesActions
         VariableLengthTableActions,
      er1646v2LacpBVlanIpV6AddressesGlobalIx
         GlobalIndex,
      er1646v2LacpBVlanIpV6AddressesTableIx
         TableIndex,
      er1646v2LacpBVlanIpV6AddressesType
         INTEGER,
      er1646v2LacpBVlanIpV6AddressesAddress
         Ipv6Address,
      er1646v2LacpBVlanIpV6AddressesPrefixLength
         Integer32,
      er1646v2LacpBVlanIpV6AddressesGeneralPrefix
         DisplayString,
      er1646v2LacpBVlanIpV6AddressesRaSend
         INTEGER,
      er1646v2LacpBVlanIpV6AddressesRaOnLinkFlag
         INTEGER,
      er1646v2LacpBVlanIpV6AddressesRaAutoFlag
         INTEGER,
      er1646v2LacpBVlanIpV6AddressesRaValidLifeTime
         TimeTicks,
      er1646v2LacpBVlanIpV6AddressesRaValidLTMode
         INTEGER,
      er1646v2LacpBVlanIpV6AddressesRaPrefLifeTime
         TimeTicks,
      er1646v2LacpBVlanIpV6AddressesRaPrefLTMode
         INTEGER
      }

er1646v2LacpBVlanIpV6AddressesActions OBJECT-TYPE
   SYNTAX      VariableLengthTableActions
   MAX-ACCESS  read-write
   STATUS      current
   DESCRIPTION
      "By way of this field, some manipulations
       on this table may be performed."
   ::= {er1646v2LacpBVlanIpV6AddressesEntry 2}

er1646v2LacpBVlanIpV6AddressesGlobalIx OBJECT-TYPE
   SYNTAX      GlobalIndex
   MAX-ACCESS  not-accessible
   STATUS      current
   DESCRIPTION
      "The value of the tlsCntTreeGlobalIndex of the MANAGED OBJECT."
   ::= {er1646v2LacpBVlanIpV6AddressesEntry 10}

er1646v2LacpBVlanIpV6AddressesTableIx OBJECT-TYPE
   SYNTAX      TableIndex
   MAX-ACCESS  not-accessible
   STATUS      current
   DESCRIPTION
      ""
   ::= {er1646v2LacpBVlanIpV6AddressesEntry 11}

er1646v2LacpBVlanIpV6AddressesType OBJECT-TYPE
   SYNTAX      INTEGER
               {
               unicast (0),
               eui64 (1),
               anycast (2),
               linkLocal (3),
               generalPrefix (4)
               }
   MAX-ACCESS  read-write
   STATUS      current
   DESCRIPTION
      "Path: lacpBundle.editConf.vlan.ipV6.addresses.type

       Possibilities:
               unicast   (0)
               eui64   (1)
               anycast   (2)
               linkLocal   (3)
               generalPrefix   (4)"
   ::= {er1646v2LacpBVlanIpV6AddressesEntry 50331648}

er1646v2LacpBVlanIpV6AddressesAddress OBJECT-TYPE
   SYNTAX      Ipv6Address
   MAX-ACCESS  read-write
   STATUS      current
   DESCRIPTION
      "Path: lacpBundle.editConf.vlan.ipV6.addresses.address

       ipv6 address"
   ::= {er1646v2LacpBVlanIpV6AddressesEntry 16777216}

er1646v2LacpBVlanIpV6AddressesPrefixLength OBJECT-TYPE
   SYNTAX      Integer32
   MAX-ACCESS  read-write
   STATUS      current
   DESCRIPTION
      "Path: lacpBundle.editConf.vlan.ipV6.addresses.prefixLength"
   ::= {er1646v2LacpBVlanIpV6AddressesEntry 33554432}

er1646v2LacpBVlanIpV6AddressesGeneralPrefix OBJECT-TYPE
   SYNTAX      DisplayString
   MAX-ACCESS  read-write
   STATUS      current
   DESCRIPTION
      "Path: lacpBundle.editConf.vlan.ipV6.addresses.generalPrefix"
   ::= {er1646v2LacpBVlanIpV6AddressesEntry 83886080}

er1646v2LacpBVlanIpV6AddressesRaSend OBJECT-TYPE
   SYNTAX      INTEGER
               {
               disabled (0),
               enabled (1)
               }
   MAX-ACCESS  read-write
   STATUS      current
   DESCRIPTION
      "Path: lacpBundle.editConf.vlan.ipV6.addresses.ra.send

       Possibilities:
               disabled   (0)
               enabled   (1)"
   ::= {er1646v2LacpBVlanIpV6AddressesEntry 67174400}

er1646v2LacpBVlanIpV6AddressesRaOnLinkFlag OBJECT-TYPE
   SYNTAX      INTEGER
               {
               disabled (0),
               enabled (1)
               }
   MAX-ACCESS  read-write
   STATUS      current
   DESCRIPTION
      "Path: lacpBundle.editConf.vlan.ipV6.addresses.ra.onLinkFlag

       Possibilities:
               disabled   (0)
               enabled   (1)"
   ::= {er1646v2LacpBVlanIpV6AddressesEntry 67371008}

er1646v2LacpBVlanIpV6AddressesRaAutoFlag OBJECT-TYPE
   SYNTAX      INTEGER
               {
               disabled (0),
               enabled (1)
               }
   MAX-ACCESS  read-write
   STATUS      current
   DESCRIPTION
      "Path: lacpBundle.editConf.vlan.ipV6.addresses.ra.autonomousFlag

       Possibilities:
               disabled   (0)
               enabled   (1)"
   ::= {er1646v2LacpBVlanIpV6AddressesEntry 67567616}

er1646v2LacpBVlanIpV6AddressesRaValidLifeTime OBJECT-TYPE
   SYNTAX      TimeTicks
   MAX-ACCESS  read-write
   STATUS      current
   DESCRIPTION
      "Path: lacpBundle.editConf.vlan.ipV6.addresses.ra.validLifeTime

       Time in centi-second."
   ::= {er1646v2LacpBVlanIpV6AddressesEntry 67239936}

er1646v2LacpBVlanIpV6AddressesRaValidLTMode OBJECT-TYPE
   SYNTAX      INTEGER
               {
               fixed (0),
               infinite (2)
               }
   MAX-ACCESS  read-write
   STATUS      current
   DESCRIPTION
      "Path: lacpBundle.editConf.vlan.ipV6.addresses.ra.validLifeTimeMode

       Possibilities:
               fixed   (0)
               infinite   (2)"
   ::= {er1646v2LacpBVlanIpV6AddressesEntry 67305472}

er1646v2LacpBVlanIpV6AddressesRaPrefLifeTime OBJECT-TYPE
   SYNTAX      TimeTicks
   MAX-ACCESS  read-write
   STATUS      current
   DESCRIPTION
      "Path: lacpBundle.editConf.vlan.ipV6.addresses.ra.prefLifeTime

       Time in centi-second."
   ::= {er1646v2LacpBVlanIpV6AddressesEntry 67436544}

er1646v2LacpBVlanIpV6AddressesRaPrefLTMode OBJECT-TYPE
   SYNTAX      INTEGER
               {
               fixed (0),
               infinite (2)
               }
   MAX-ACCESS  read-write
   STATUS      current
   DESCRIPTION
      "Path: lacpBundle.editConf.vlan.ipV6.addresses.ra.prefLifeTimeMode

       Possibilities:
               fixed   (0)
               infinite   (2)"
   ::= {er1646v2LacpBVlanIpV6AddressesEntry 67502080}

er1646v2LacpBVlanIpV6RaDnsOptionsRdnssServers OBJECT-TYPE
   SYNTAX      SEQUENCE OF Er1646v2LacpBVlanIpV6RaDnsOptionsRdnssServersEntry
   MAX-ACCESS  not-accessible
   STATUS      current
   DESCRIPTION
      ""
   ::= {er1646v2LacpBVlan 705039144}

er1646v2LacpBVlanIpV6RaDnsOptionsRdnssServersEntry OBJECT-TYPE
   SYNTAX      Er1646v2LacpBVlanIpV6RaDnsOptionsRdnssServersEntry
   MAX-ACCESS  not-accessible
   STATUS      current
   DESCRIPTION
      ""
   INDEX      { er1646v2LacpBVlanIpV6RaDnsOptionsRdnssServersGlobalIx,
                er1646v2LacpBVlanTableIx,
                er1646v2LacpBVlanIpV6RaDnsOptionsRdnssServersTableIx }
   ::= {er1646v2LacpBVlanIpV6RaDnsOptionsRdnssServers 1}

Er1646v2LacpBVlanIpV6RaDnsOptionsRdnssServersEntry ::=
   SEQUENCE
      {
      er1646v2LacpBVlanIpV6RaDnsOptionsRdnssServersActions
         VariableLengthTableActions,
      er1646v2LacpBVlanIpV6RaDnsOptionsRdnssServersGlobalIx
         GlobalIndex,
      er1646v2LacpBVlanIpV6RaDnsOptionsRdnssServersTableIx
         TableIndex,
      er1646v2LacpBVlanIpV6RaDnsOptionsRdnssServersAddress
         Ipv6Address
      }

er1646v2LacpBVlanIpV6RaDnsOptionsRdnssServersActions OBJECT-TYPE
   SYNTAX      VariableLengthTableActions
   MAX-ACCESS  read-write
   STATUS      current
   DESCRIPTION
      "By way of this field, some manipulations
       on this table may be performed."
   ::= {er1646v2LacpBVlanIpV6RaDnsOptionsRdnssServersEntry 2}

er1646v2LacpBVlanIpV6RaDnsOptionsRdnssServersGlobalIx OBJECT-TYPE
   SYNTAX      GlobalIndex
   MAX-ACCESS  not-accessible
   STATUS      current
   DESCRIPTION
      "The value of the tlsCntTreeGlobalIndex of the MANAGED OBJECT."
   ::= {er1646v2LacpBVlanIpV6RaDnsOptionsRdnssServersEntry 10}

er1646v2LacpBVlanIpV6RaDnsOptionsRdnssServersTableIx OBJECT-TYPE
   SYNTAX      TableIndex
   MAX-ACCESS  not-accessible
   STATUS      current
   DESCRIPTION
      ""
   ::= {er1646v2LacpBVlanIpV6RaDnsOptionsRdnssServersEntry 11}

er1646v2LacpBVlanIpV6RaDnsOptionsRdnssServersAddress OBJECT-TYPE
   SYNTAX      Ipv6Address
   MAX-ACCESS  read-write
   STATUS      current
   DESCRIPTION
      "Path: lacpBundle.editConf.vlan.ipV6.ra.dnsOptions.rdnss.servers.address

       ipv6 address"
   ::= {er1646v2LacpBVlanIpV6RaDnsOptionsRdnssServersEntry 16777216}

er1646v2LacpBVlanIpV6RaDnsOptionsDnsslDomains OBJECT-TYPE
   SYNTAX      SEQUENCE OF Er1646v2LacpBVlanIpV6RaDnsOptionsDnsslDomainsEntry
   MAX-ACCESS  not-accessible
   STATUS      current
   DESCRIPTION
      ""
   ::= {er1646v2LacpBVlan 705039176}

er1646v2LacpBVlanIpV6RaDnsOptionsDnsslDomainsEntry OBJECT-TYPE
   SYNTAX      Er1646v2LacpBVlanIpV6RaDnsOptionsDnsslDomainsEntry
   MAX-ACCESS  not-accessible
   STATUS      current
   DESCRIPTION
      ""
   INDEX      { er1646v2LacpBVlanIpV6RaDnsOptionsDnsslDomainsGlobalIx,
                er1646v2LacpBVlanTableIx,
                er1646v2LacpBVlanIpV6RaDnsOptionsDnsslDomainsTableIx }
   ::= {er1646v2LacpBVlanIpV6RaDnsOptionsDnsslDomains 1}

Er1646v2LacpBVlanIpV6RaDnsOptionsDnsslDomainsEntry ::=
   SEQUENCE
      {
      er1646v2LacpBVlanIpV6RaDnsOptionsDnsslDomainsActions
         VariableLengthTableActions,
      er1646v2LacpBVlanIpV6RaDnsOptionsDnsslDomainsGlobalIx
         GlobalIndex,
      er1646v2LacpBVlanIpV6RaDnsOptionsDnsslDomainsTableIx
         TableIndex,
      er1646v2LacpBVlanIpV6RaDnsOptionsDnsslDomainsName
         DisplayString
      }

er1646v2LacpBVlanIpV6RaDnsOptionsDnsslDomainsActions OBJECT-TYPE
   SYNTAX      VariableLengthTableActions
   MAX-ACCESS  read-write
   STATUS      current
   DESCRIPTION
      "By way of this field, some manipulations
       on this table may be performed."
   ::= {er1646v2LacpBVlanIpV6RaDnsOptionsDnsslDomainsEntry 2}

er1646v2LacpBVlanIpV6RaDnsOptionsDnsslDomainsGlobalIx OBJECT-TYPE
   SYNTAX      GlobalIndex
   MAX-ACCESS  not-accessible
   STATUS      current
   DESCRIPTION
      "The value of the tlsCntTreeGlobalIndex of the MANAGED OBJECT."
   ::= {er1646v2LacpBVlanIpV6RaDnsOptionsDnsslDomainsEntry 10}

er1646v2LacpBVlanIpV6RaDnsOptionsDnsslDomainsTableIx OBJECT-TYPE
   SYNTAX      TableIndex
   MAX-ACCESS  not-accessible
   STATUS      current
   DESCRIPTION
      ""
   ::= {er1646v2LacpBVlanIpV6RaDnsOptionsDnsslDomainsEntry 11}

er1646v2LacpBVlanIpV6RaDnsOptionsDnsslDomainsName OBJECT-TYPE
   SYNTAX      DisplayString
   MAX-ACCESS  read-write
   STATUS      current
   DESCRIPTION
      "Path: lacpBundle.editConf.vlan.ipV6.ra.dnsOptions.dnssl.domains.name"
   ::= {er1646v2LacpBVlanIpV6RaDnsOptionsDnsslDomainsEntry 16777216}

er1646v2LacpBVlanIpV6DhcpClientUserClassOpt OBJECT-TYPE
   SYNTAX      SEQUENCE OF Er1646v2LacpBVlanIpV6DhcpClientUserClassOptEntry
   MAX-ACCESS  not-accessible
   STATUS      current
   DESCRIPTION
      ""
   ::= {er1646v2LacpBVlan 705312768}

er1646v2LacpBVlanIpV6DhcpClientUserClassOptEntry OBJECT-TYPE
   SYNTAX      Er1646v2LacpBVlanIpV6DhcpClientUserClassOptEntry
   MAX-ACCESS  not-accessible
   STATUS      current
   DESCRIPTION
      ""
   INDEX      { er1646v2LacpBVlanIpV6DhcpClientUserClassOptGlobalIx,
                er1646v2LacpBVlanTableIx,
                er1646v2LacpBVlanIpV6DhcpClientUserClassOptTableIx }
   ::= {er1646v2LacpBVlanIpV6DhcpClientUserClassOpt 1}

Er1646v2LacpBVlanIpV6DhcpClientUserClassOptEntry ::=
   SEQUENCE
      {
      er1646v2LacpBVlanIpV6DhcpClientUserClassOptActions
         VariableLengthTableActions,
      er1646v2LacpBVlanIpV6DhcpClientUserClassOptGlobalIx
         GlobalIndex,
      er1646v2LacpBVlanIpV6DhcpClientUserClassOptTableIx
         TableIndex,
      er1646v2LacpBVlanIpV6DhcpClientUserClassOptValueAscii
         DisplayString,
      er1646v2LacpBVlanIpV6DhcpClientUserClassOptValueDecimal
         Integer32,
      er1646v2LacpBVlanIpV6DhcpClientUserClassOptValueHexData
         OCTET STRING
      }

er1646v2LacpBVlanIpV6DhcpClientUserClassOptActions OBJECT-TYPE
   SYNTAX      VariableLengthTableActions
   MAX-ACCESS  read-write
   STATUS      current
   DESCRIPTION
      "By way of this field, some manipulations
       on this table may be performed."
   ::= {er1646v2LacpBVlanIpV6DhcpClientUserClassOptEntry 2}

er1646v2LacpBVlanIpV6DhcpClientUserClassOptGlobalIx OBJECT-TYPE
   SYNTAX      GlobalIndex
   MAX-ACCESS  not-accessible
   STATUS      current
   DESCRIPTION
      "The value of the tlsCntTreeGlobalIndex of the MANAGED OBJECT."
   ::= {er1646v2LacpBVlanIpV6DhcpClientUserClassOptEntry 10}

er1646v2LacpBVlanIpV6DhcpClientUserClassOptTableIx OBJECT-TYPE
   SYNTAX      TableIndex
   MAX-ACCESS  not-accessible
   STATUS      current
   DESCRIPTION
      ""
   ::= {er1646v2LacpBVlanIpV6DhcpClientUserClassOptEntry 11}

er1646v2LacpBVlanIpV6DhcpClientUserClassOptValueAscii OBJECT-TYPE
   SYNTAX      DisplayString
   MAX-ACCESS  read-write
   STATUS      current
   DESCRIPTION
      "Path: lacpBundle.editConf.vlan.ipV6.dhcp.client.userClassOpt.value.ascii"
   ::= {er1646v2LacpBVlanIpV6DhcpClientUserClassOptEntry 16842752}

er1646v2LacpBVlanIpV6DhcpClientUserClassOptValueDecimal OBJECT-TYPE
   SYNTAX      Integer32
   MAX-ACCESS  read-write
   STATUS      current
   DESCRIPTION
      "Path: lacpBundle.editConf.vlan.ipV6.dhcp.client.userClassOpt.value.decimal"
   ::= {er1646v2LacpBVlanIpV6DhcpClientUserClassOptEntry 16908288}

er1646v2LacpBVlanIpV6DhcpClientUserClassOptValueHexData OBJECT-TYPE
   SYNTAX      OCTET STRING
   MAX-ACCESS  read-write
   STATUS      current
   DESCRIPTION
      "Path: lacpBundle.editConf.vlan.ipV6.dhcp.client.userClassOpt.value.hexData"
   ::= {er1646v2LacpBVlanIpV6DhcpClientUserClassOptEntry 16973824}

er1646v2LacpBVlanIpV6DhcpClientVendorCl OBJECT-TYPE
   SYNTAX      SEQUENCE OF Er1646v2LacpBVlanIpV6DhcpClientVendorClEntry
   MAX-ACCESS  not-accessible
   STATUS      current
   DESCRIPTION
      ""
   ::= {er1646v2LacpBVlan 705313792}

er1646v2LacpBVlanIpV6DhcpClientVendorClEntry OBJECT-TYPE
   SYNTAX      Er1646v2LacpBVlanIpV6DhcpClientVendorClEntry
   MAX-ACCESS  not-accessible
   STATUS      current
   DESCRIPTION
      ""
   INDEX      { er1646v2LacpBVlanIpV6DhcpClientVendorClGlobalIx,
                er1646v2LacpBVlanTableIx,
                er1646v2LacpBVlanIpV6DhcpClientVendorClTableIx }
   ::= {er1646v2LacpBVlanIpV6DhcpClientVendorCl 1}

Er1646v2LacpBVlanIpV6DhcpClientVendorClEntry ::=
   SEQUENCE
      {
      er1646v2LacpBVlanIpV6DhcpClientVendorClActions
         VariableLengthTableActions,
      er1646v2LacpBVlanIpV6DhcpClientVendorClGlobalIx
         GlobalIndex,
      er1646v2LacpBVlanIpV6DhcpClientVendorClTableIx
         TableIndex,
      er1646v2LacpBVlanIpV6DhcpClientVendorClValueAscii
         DisplayString,
      er1646v2LacpBVlanIpV6DhcpClientVendorClValueDecimal
         Integer32,
      er1646v2LacpBVlanIpV6DhcpClientVendorClValueHexData
         OCTET STRING
      }

er1646v2LacpBVlanIpV6DhcpClientVendorClActions OBJECT-TYPE
   SYNTAX      VariableLengthTableActions
   MAX-ACCESS  read-write
   STATUS      current
   DESCRIPTION
      "By way of this field, some manipulations
       on this table may be performed."
   ::= {er1646v2LacpBVlanIpV6DhcpClientVendorClEntry 2}

er1646v2LacpBVlanIpV6DhcpClientVendorClGlobalIx OBJECT-TYPE
   SYNTAX      GlobalIndex
   MAX-ACCESS  not-accessible
   STATUS      current
   DESCRIPTION
      "The value of the tlsCntTreeGlobalIndex of the MANAGED OBJECT."
   ::= {er1646v2LacpBVlanIpV6DhcpClientVendorClEntry 10}

er1646v2LacpBVlanIpV6DhcpClientVendorClTableIx OBJECT-TYPE
   SYNTAX      TableIndex
   MAX-ACCESS  not-accessible
   STATUS      current
   DESCRIPTION
      ""
   ::= {er1646v2LacpBVlanIpV6DhcpClientVendorClEntry 11}

er1646v2LacpBVlanIpV6DhcpClientVendorClValueAscii OBJECT-TYPE
   SYNTAX      DisplayString
   MAX-ACCESS  read-write
   STATUS      current
   DESCRIPTION
      "Path: lacpBundle.editConf.vlan.ipV6.dhcp.client.vendorClassOpt.value.ascii"
   ::= {er1646v2LacpBVlanIpV6DhcpClientVendorClEntry 16842752}

er1646v2LacpBVlanIpV6DhcpClientVendorClValueDecimal OBJECT-TYPE
   SYNTAX      Integer32
   MAX-ACCESS  read-write
   STATUS      current
   DESCRIPTION
      "Path: lacpBundle.editConf.vlan.ipV6.dhcp.client.vendorClassOpt.value.decimal"
   ::= {er1646v2LacpBVlanIpV6DhcpClientVendorClEntry 16908288}

er1646v2LacpBVlanIpV6DhcpClientVendorClValueHexData OBJECT-TYPE
   SYNTAX      OCTET STRING
   MAX-ACCESS  read-write
   STATUS      current
   DESCRIPTION
      "Path: lacpBundle.editConf.vlan.ipV6.dhcp.client.vendorClassOpt.value.hexData"
   ::= {er1646v2LacpBVlanIpV6DhcpClientVendorClEntry 16973824}

er1646v2LacpBVlanIpV6DhcpRelayDestinations OBJECT-TYPE
   SYNTAX      SEQUENCE OF Er1646v2LacpBVlanIpV6DhcpRelayDestinationsEntry
   MAX-ACCESS  not-accessible
   STATUS      current
   DESCRIPTION
      ""
   ::= {er1646v2LacpBVlan 705323072}

er1646v2LacpBVlanIpV6DhcpRelayDestinationsEntry OBJECT-TYPE
   SYNTAX      Er1646v2LacpBVlanIpV6DhcpRelayDestinationsEntry
   MAX-ACCESS  not-accessible
   STATUS      current
   DESCRIPTION
      ""
   INDEX      { er1646v2LacpBVlanIpV6DhcpRelayDestinationsGlobalIx,
                er1646v2LacpBVlanTableIx,
                er1646v2LacpBVlanIpV6DhcpRelayDestinationsTableIx }
   ::= {er1646v2LacpBVlanIpV6DhcpRelayDestinations 1}

Er1646v2LacpBVlanIpV6DhcpRelayDestinationsEntry ::=
   SEQUENCE
      {
      er1646v2LacpBVlanIpV6DhcpRelayDestinationsActions
         VariableLengthTableActions,
      er1646v2LacpBVlanIpV6DhcpRelayDestinationsGlobalIx
         GlobalIndex,
      er1646v2LacpBVlanIpV6DhcpRelayDestinationsTableIx
         TableIndex,
      er1646v2LacpBVlanIpV6DhcpRelayDestinationsAddress
         Ipv6Address,
      er1646v2LacpBVlanIpV6DhcpRelayDestinationsInterface
         DisplayString
      }

er1646v2LacpBVlanIpV6DhcpRelayDestinationsActions OBJECT-TYPE
   SYNTAX      VariableLengthTableActions
   MAX-ACCESS  read-write
   STATUS      current
   DESCRIPTION
      "By way of this field, some manipulations
       on this table may be performed."
   ::= {er1646v2LacpBVlanIpV6DhcpRelayDestinationsEntry 2}

er1646v2LacpBVlanIpV6DhcpRelayDestinationsGlobalIx OBJECT-TYPE
   SYNTAX      GlobalIndex
   MAX-ACCESS  not-accessible
   STATUS      current
   DESCRIPTION
      "The value of the tlsCntTreeGlobalIndex of the MANAGED OBJECT."
   ::= {er1646v2LacpBVlanIpV6DhcpRelayDestinationsEntry 10}

er1646v2LacpBVlanIpV6DhcpRelayDestinationsTableIx OBJECT-TYPE
   SYNTAX      TableIndex
   MAX-ACCESS  not-accessible
   STATUS      current
   DESCRIPTION
      ""
   ::= {er1646v2LacpBVlanIpV6DhcpRelayDestinationsEntry 11}

er1646v2LacpBVlanIpV6DhcpRelayDestinationsAddress OBJECT-TYPE
   SYNTAX      Ipv6Address
   MAX-ACCESS  read-write
   STATUS      current
   DESCRIPTION
      "Path: lacpBundle.editConf.vlan.ipV6.dhcp.relay.destinations.address

       ipv6 address"
   ::= {er1646v2LacpBVlanIpV6DhcpRelayDestinationsEntry 16777216}

er1646v2LacpBVlanIpV6DhcpRelayDestinationsInterface OBJECT-TYPE
   SYNTAX      DisplayString
   MAX-ACCESS  read-write
   STATUS      current
   DESCRIPTION
      "Path: lacpBundle.editConf.vlan.ipV6.dhcp.relay.destinations.interface"
   ::= {er1646v2LacpBVlanIpV6DhcpRelayDestinationsEntry 33554432}

er1646v2LacpBVlanBridgingVlTVlans OBJECT-TYPE
   SYNTAX      SEQUENCE OF Er1646v2LacpBVlanBridgingVlTVlansEntry
   MAX-ACCESS  not-accessible
   STATUS      current
   DESCRIPTION
      ""
   ::= {er1646v2LacpBVlan 459079680}

er1646v2LacpBVlanBridgingVlTVlansEntry OBJECT-TYPE
   SYNTAX      Er1646v2LacpBVlanBridgingVlTVlansEntry
   MAX-ACCESS  not-accessible
   STATUS      current
   DESCRIPTION
      ""
   INDEX      { er1646v2LacpBVlanBridgingVlTVlansGlobalIx,
                er1646v2LacpBVlanTableIx,
                er1646v2LacpBVlanBridgingVlTVlansTableIx }
   ::= {er1646v2LacpBVlanBridgingVlTVlans 1}

Er1646v2LacpBVlanBridgingVlTVlansEntry ::=
   SEQUENCE
      {
      er1646v2LacpBVlanBridgingVlTVlansActions
         VariableLengthTableActions,
      er1646v2LacpBVlanBridgingVlTVlansGlobalIx
         GlobalIndex,
      er1646v2LacpBVlanBridgingVlTVlansTableIx
         TableIndex,
      er1646v2LacpBVlanBridgingVlTVlansVid
         Integer32,
      er1646v2LacpBVlanBridgingVlTVlansEndVid
         Integer32,
      er1646v2LacpBVlanBridgingVlTVlansAction
         INTEGER,
      er1646v2LacpBVlanBridgingVlTVlansTagInfoTpid
         INTEGER,
      er1646v2LacpBVlanBridgingVlTVlansTagInfoVid
         Integer32
      }

er1646v2LacpBVlanBridgingVlTVlansActions OBJECT-TYPE
   SYNTAX      VariableLengthTableActions
   MAX-ACCESS  read-write
   STATUS      current
   DESCRIPTION
      "By way of this field, some manipulations
       on this table may be performed."
   ::= {er1646v2LacpBVlanBridgingVlTVlansEntry 2}

er1646v2LacpBVlanBridgingVlTVlansGlobalIx OBJECT-TYPE
   SYNTAX      GlobalIndex
   MAX-ACCESS  not-accessible
   STATUS      current
   DESCRIPTION
      "The value of the tlsCntTreeGlobalIndex of the MANAGED OBJECT."
   ::= {er1646v2LacpBVlanBridgingVlTVlansEntry 10}

er1646v2LacpBVlanBridgingVlTVlansTableIx OBJECT-TYPE
   SYNTAX      TableIndex
   MAX-ACCESS  not-accessible
   STATUS      current
   DESCRIPTION
      ""
   ::= {er1646v2LacpBVlanBridgingVlTVlansEntry 11}

er1646v2LacpBVlanBridgingVlTVlansVid OBJECT-TYPE
   SYNTAX      Integer32
   MAX-ACCESS  read-write
   STATUS      current
   DESCRIPTION
      "Path: lacpBundle.editConf.vlan.bridging.vlanTagging.vlans.vid"
   ::= {er1646v2LacpBVlanBridgingVlTVlansEntry 536870912}

er1646v2LacpBVlanBridgingVlTVlansEndVid OBJECT-TYPE
   SYNTAX      Integer32
   MAX-ACCESS  read-write
   STATUS      current
   DESCRIPTION
      "Path: lacpBundle.editConf.vlan.bridging.vlanTagging.vlans.endVid"
   ::= {er1646v2LacpBVlanBridgingVlTVlansEntry 2147483648}

er1646v2LacpBVlanBridgingVlTVlansAction OBJECT-TYPE
   SYNTAX      INTEGER
               {
               discard (0),
               accept (1),
               tag (2)
               }
   MAX-ACCESS  read-write
   STATUS      current
   DESCRIPTION
      "Path: lacpBundle.editConf.vlan.bridging.vlanTagging.vlans.action

       Possibilities:
               discard   (0)
               accept   (1)
               tag   (2)"
   ::= {er1646v2LacpBVlanBridgingVlTVlansEntry 1073741824}

er1646v2LacpBVlanBridgingVlTVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: lacpBundle.editConf.vlan.bridging.vlanTagging.vlans.tagInfo.tpid

       Possibilities:
               dot1Q   (33024)
               dot1ad   (34984)
               0x9100   (37120)
               0x9200   (37376)
               0x9300   (37632)"
   ::= {er1646v2LacpBVlanBridgingVlTVlansEntry 1677721600}

er1646v2LacpBVlanBridgingVlTVlansTagInfoVid OBJECT-TYPE
   SYNTAX      Integer32
   MAX-ACCESS  read-write
   STATUS      current
   DESCRIPTION
      "Path: lacpBundle.editConf.vlan.bridging.vlanTagging.vlans.tagInfo.vid"
   ::= {er1646v2LacpBVlanBridgingVlTVlansEntry 1744830464}

er1646v2LacpBVlanVlanVidExtensionTable OBJECT-TYPE
   SYNTAX      SEQUENCE OF Er1646v2LacpBVlanVlanVidExtensionTableEntry
   MAX-ACCESS  not-accessible
   STATUS      current
   DESCRIPTION
      ""
   ::= {er1646v2LacpBVlan 235340544}

er1646v2LacpBVlanVlanVidExtensionTableEntry OBJECT-TYPE
   SYNTAX      Er1646v2LacpBVlanVlanVidExtensionTableEntry
   MAX-ACCESS  not-accessible
   STATUS      current
   DESCRIPTION
      ""
   INDEX      { er1646v2LacpBVlanVlanVidExtensionTableGlobalIx,
                er1646v2LacpBVlanTableIx,
                er1646v2LacpBVlanVlanVidExtensionTableTableIx }
   ::= {er1646v2LacpBVlanVlanVidExtensionTable 1}

Er1646v2LacpBVlanVlanVidExtensionTableEntry ::=
   SEQUENCE
      {
      er1646v2LacpBVlanVlanVidExtensionTableActions
         VariableLengthTableActions,
      er1646v2LacpBVlanVlanVidExtensionTableGlobalIx
         GlobalIndex,
      er1646v2LacpBVlanVlanVidExtensionTableTableIx
         TableIndex,
      er1646v2LacpBVlanVlanVidExtensionTableTpid
         INTEGER,
      er1646v2LacpBVlanVlanVidExtensionTableVid
         Integer32,
      er1646v2LacpBVlanVlanVidExtensionTableEndVid
         Integer32
      }

er1646v2LacpBVlanVlanVidExtensionTableActions OBJECT-TYPE
   SYNTAX      VariableLengthTableActions
   MAX-ACCESS  read-write
   STATUS      current
   DESCRIPTION
      "By way of this field, some manipulations
       on this table may be performed."
   ::= {er1646v2LacpBVlanVlanVidExtensionTableEntry 2}

er1646v2LacpBVlanVlanVidExtensionTableGlobalIx OBJECT-TYPE
   SYNTAX      GlobalIndex
   MAX-ACCESS  not-accessible
   STATUS      current
   DESCRIPTION
      "The value of the tlsCntTreeGlobalIndex of the MANAGED OBJECT."
   ::= {er1646v2LacpBVlanVlanVidExtensionTableEntry 10}

er1646v2LacpBVlanVlanVidExtensionTableTableIx OBJECT-TYPE
   SYNTAX      TableIndex
   MAX-ACCESS  not-accessible
   STATUS      current
   DESCRIPTION
      ""
   ::= {er1646v2LacpBVlanVlanVidExtensionTableEntry 11}

er1646v2LacpBVlanVlanVidExtensionTableTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: lacpBundle.editConf.vlan.vlan.vidExtension.table.tpid

       Possibilities:
               dot1Q   (33024)
               dot1ad   (34984)
               0x9100   (37120)
               0x9200   (37376)
               0x9300   (37632)"
   ::= {er1646v2LacpBVlanVlanVidExtensionTableEntry 16777216}

er1646v2LacpBVlanVlanVidExtensionTableVid OBJECT-TYPE
   SYNTAX      Integer32
   MAX-ACCESS  read-write
   STATUS      current
   DESCRIPTION
      "Path: lacpBundle.editConf.vlan.vlan.vidExtension.table.vid"
   ::= {er1646v2LacpBVlanVlanVidExtensionTableEntry 33554432}

er1646v2LacpBVlanVlanVidExtensionTableEndVid OBJECT-TYPE
   SYNTAX      Integer32
   MAX-ACCESS  read-write
   STATUS      current
   DESCRIPTION
      "Path: lacpBundle.editConf.vlan.vlan.vidExtension.table.endVid"
   ::= {er1646v2LacpBVlanVlanVidExtensionTableEntry 50331648}

er1646v2LacpBVlanVlanCSMap OBJECT-TYPE
   SYNTAX      SEQUENCE OF Er1646v2LacpBVlanVlanCSMapEntry
   MAX-ACCESS  not-accessible
   STATUS      current
   DESCRIPTION
      ""
   ::= {er1646v2LacpBVlan 235405312}

er1646v2LacpBVlanVlanCSMapEntry OBJECT-TYPE
   SYNTAX      Er1646v2LacpBVlanVlanCSMapEntry
   MAX-ACCESS  not-accessible
   STATUS      current
   DESCRIPTION
      ""
   INDEX      { er1646v2LacpBVlanVlanCSMapGlobalIx,
                er1646v2LacpBVlanTableIx,
                er1646v2LacpBVlanVlanCSMapTableIx }
   ::= {er1646v2LacpBVlanVlanCSMap 1}

Er1646v2LacpBVlanVlanCSMapEntry ::=
   SEQUENCE
      {
      er1646v2LacpBVlanVlanCSMapActions
         VariableLengthTableActions,
      er1646v2LacpBVlanVlanCSMapGlobalIx
         GlobalIndex,
      er1646v2LacpBVlanVlanCSMapTableIx
         TableIndex,
      er1646v2LacpBVlanVlanCSMapCos
         INTEGER,
      er1646v2LacpBVlanVlanCSMapDei
         INTEGER,
      er1646v2LacpBVlanVlanCSMapTos
         INTEGER,
      er1646v2LacpBVlanVlanCSMapQueue
         INTEGER,
      er1646v2LacpBVlanVlanCSMapDropLevel
         INTEGER,
      er1646v2LacpBVlanVlanCSMapDeFlag
         INTEGER
      }

er1646v2LacpBVlanVlanCSMapActions OBJECT-TYPE
   SYNTAX      VariableLengthTableActions
   MAX-ACCESS  read-write
   STATUS      current
   DESCRIPTION
      "By way of this field, some manipulations
       on this table may be performed."
   ::= {er1646v2LacpBVlanVlanCSMapEntry 2}

er1646v2LacpBVlanVlanCSMapGlobalIx OBJECT-TYPE
   SYNTAX      GlobalIndex
   MAX-ACCESS  not-accessible
   STATUS      current
   DESCRIPTION
      "The value of the tlsCntTreeGlobalIndex of the MANAGED OBJECT."
   ::= {er1646v2LacpBVlanVlanCSMapEntry 10}

er1646v2LacpBVlanVlanCSMapTableIx OBJECT-TYPE
   SYNTAX      TableIndex
   MAX-ACCESS  not-accessible
   STATUS      current
   DESCRIPTION
      ""
   ::= {er1646v2LacpBVlanVlanCSMapEntry 11}

er1646v2LacpBVlanVlanCSMapCos OBJECT-TYPE
   SYNTAX      INTEGER
               {
               any (8)
               }
   MAX-ACCESS  read-write
   STATUS      current
   DESCRIPTION
      "Path: lacpBundle.editConf.vlan.vlan.cosMap.cos

       Possibilities:
               any   (8)"
   ::= {er1646v2LacpBVlanVlanCSMapEntry 16777216}

er1646v2LacpBVlanVlanCSMapDei OBJECT-TYPE
   SYNTAX      INTEGER
               {
               clear (0),
               set (1),
               any (2)
               }
   MAX-ACCESS  read-write
   STATUS      current
   DESCRIPTION
      "Path: lacpBundle.editConf.vlan.vlan.cosMap.dei

       Possibilities:
               clear   (0)
               set   (1)
               any   (2)"
   ::= {er1646v2LacpBVlanVlanCSMapEntry 33554432}

er1646v2LacpBVlanVlanCSMapTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: lacpBundle.editConf.vlan.vlan.cosMap.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2LacpBVlanVlanCSMapEntry 50331648}

er1646v2LacpBVlanVlanCSMapQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: lacpBundle.editConf.vlan.vlan.cosMap.queue

       Possibilities:
               unchanged   (-1)
               queue1   (0)
               queue2   (1)
               queue3   (2)
               queue4   (3)
               queue5   (4)
               lowDelayQueue   (5)
               lowDelay2Queue   (6)
               systemQueue   (7)"
   ::= {er1646v2LacpBVlanVlanCSMapEntry 67108864}

er1646v2LacpBVlanVlanCSMapDropLevel OBJECT-TYPE
   SYNTAX      INTEGER
               {
               unchanged (-1),
               dropOnQueue (0)
               }
   MAX-ACCESS  read-write
   STATUS      current
   DESCRIPTION
      "Path: lacpBundle.editConf.vlan.vlan.cosMap.dropLevel

       Possibilities:
               unchanged   (-1)
               dropOnQueue   (0)"
   ::= {er1646v2LacpBVlanVlanCSMapEntry 83886080}

er1646v2LacpBVlanVlanCSMapDeFlag OBJECT-TYPE
   SYNTAX      INTEGER
               {
               unchanged (255),
               clear (0),
               set (1)
               }
   MAX-ACCESS  read-write
   STATUS      current
   DESCRIPTION
      "Path: lacpBundle.editConf.vlan.vlan.cosMap.deFlag

       Possibilities:
               unchanged   (255)
               clear   (0)
               set   (1)"
   ::= {er1646v2LacpBVlanVlanCSMapEntry 117440512}

er1646v2LacpBVlanVlanTCMap OBJECT-TYPE
   SYNTAX      SEQUENCE OF Er1646v2LacpBVlanVlanTCMapEntry
   MAX-ACCESS  not-accessible
   STATUS      current
   DESCRIPTION
      ""
   ::= {er1646v2LacpBVlan 241369088}

er1646v2LacpBVlanVlanTCMapEntry OBJECT-TYPE
   SYNTAX      Er1646v2LacpBVlanVlanTCMapEntry
   MAX-ACCESS  not-accessible
   STATUS      current
   DESCRIPTION
      ""
   INDEX      { er1646v2LacpBVlanVlanTCMapGlobalIx,
                er1646v2LacpBVlanTableIx,
                er1646v2LacpBVlanVlanTCMapTableIx }
   ::= {er1646v2LacpBVlanVlanTCMap 1}

Er1646v2LacpBVlanVlanTCMapEntry ::=
   SEQUENCE
      {
      er1646v2LacpBVlanVlanTCMapActions
         VariableLengthTableActions,
      er1646v2LacpBVlanVlanTCMapGlobalIx
         GlobalIndex,
      er1646v2LacpBVlanVlanTCMapTableIx
         TableIndex,
      er1646v2LacpBVlanVlanTCMapStartTos
         INTEGER,
      er1646v2LacpBVlanVlanTCMapEndTos
         INTEGER,
      er1646v2LacpBVlanVlanTCMapCos
         INTEGER
      }

er1646v2LacpBVlanVlanTCMapActions OBJECT-TYPE
   SYNTAX      VariableLengthTableActions
   MAX-ACCESS  read-write
   STATUS      current
   DESCRIPTION
      "By way of this field, some manipulations
       on this table may be performed."
   ::= {er1646v2LacpBVlanVlanTCMapEntry 2}

er1646v2LacpBVlanVlanTCMapGlobalIx OBJECT-TYPE
   SYNTAX      GlobalIndex
   MAX-ACCESS  not-accessible
   STATUS      current
   DESCRIPTION
      "The value of the tlsCntTreeGlobalIndex of the MANAGED OBJECT."
   ::= {er1646v2LacpBVlanVlanTCMapEntry 10}

er1646v2LacpBVlanVlanTCMapTableIx OBJECT-TYPE
   SYNTAX      TableIndex
   MAX-ACCESS  not-accessible
   STATUS      current
   DESCRIPTION
      ""
   ::= {er1646v2LacpBVlanVlanTCMapEntry 11}

er1646v2LacpBVlanVlanTCMapStartTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: lacpBundle.editConf.vlan.vlan.tosCosMap.startTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1646v2LacpBVlanVlanTCMapEntry 16777216}

er1646v2LacpBVlanVlanTCMapEndTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: lacpBundle.editConf.vlan.vlan.tosCosMap.endTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1646v2LacpBVlanVlanTCMapEntry 33554432}

er1646v2LacpBVlanVlanTCMapCos OBJECT-TYPE
   SYNTAX      INTEGER
               {
               queueCosMap (8)
               }
   MAX-ACCESS  read-write
   STATUS      current
   DESCRIPTION
      "Path: lacpBundle.editConf.vlan.vlan.tosCosMap.cos

       Possibilities:
               queueCosMap   (8)"
   ::= {er1646v2LacpBVlanVlanTCMapEntry 50331648}

er1646v2LacpBVlanVlanArpStaticArp OBJECT-TYPE
   SYNTAX      SEQUENCE OF Er1646v2LacpBVlanVlanArpStaticArpEntry
   MAX-ACCESS  not-accessible
   STATUS      current
   DESCRIPTION
      ""
   ::= {er1646v2LacpBVlan 235275008}

er1646v2LacpBVlanVlanArpStaticArpEntry OBJECT-TYPE
   SYNTAX      Er1646v2LacpBVlanVlanArpStaticArpEntry
   MAX-ACCESS  not-accessible
   STATUS      current
   DESCRIPTION
      ""
   INDEX      { er1646v2LacpBVlanVlanArpStaticArpGlobalIx,
                er1646v2LacpBVlanTableIx,
                er1646v2LacpBVlanVlanArpStaticArpTableIx }
   ::= {er1646v2LacpBVlanVlanArpStaticArp 1}

Er1646v2LacpBVlanVlanArpStaticArpEntry ::=
   SEQUENCE
      {
      er1646v2LacpBVlanVlanArpStaticArpActions
         VariableLengthTableActions,
      er1646v2LacpBVlanVlanArpStaticArpGlobalIx
         GlobalIndex,
      er1646v2LacpBVlanVlanArpStaticArpTableIx
         TableIndex,
      er1646v2LacpBVlanVlanArpStaticArpMacAddress
         OCTET STRING,
      er1646v2LacpBVlanVlanArpStaticArpIpAddress
         IpAddress
      }

er1646v2LacpBVlanVlanArpStaticArpActions OBJECT-TYPE
   SYNTAX      VariableLengthTableActions
   MAX-ACCESS  read-write
   STATUS      current
   DESCRIPTION
      "By way of this field, some manipulations
       on this table may be performed."
   ::= {er1646v2LacpBVlanVlanArpStaticArpEntry 2}

er1646v2LacpBVlanVlanArpStaticArpGlobalIx OBJECT-TYPE
   SYNTAX      GlobalIndex
   MAX-ACCESS  not-accessible
   STATUS      current
   DESCRIPTION
      "The value of the tlsCntTreeGlobalIndex of the MANAGED OBJECT."
   ::= {er1646v2LacpBVlanVlanArpStaticArpEntry 10}

er1646v2LacpBVlanVlanArpStaticArpTableIx OBJECT-TYPE
   SYNTAX      TableIndex
   MAX-ACCESS  not-accessible
   STATUS      current
   DESCRIPTION
      ""
   ::= {er1646v2LacpBVlanVlanArpStaticArpEntry 11}

er1646v2LacpBVlanVlanArpStaticArpMacAddress OBJECT-TYPE
   SYNTAX      OCTET STRING
   MAX-ACCESS  read-write
   STATUS      current
   DESCRIPTION
      "Path: lacpBundle.editConf.vlan.vlan.arp.staticArp.macAddress

       MAC address."
   ::= {er1646v2LacpBVlanVlanArpStaticArpEntry 16777216}

er1646v2LacpBVlanVlanArpStaticArpIpAddress OBJECT-TYPE
   SYNTAX      IpAddress
   MAX-ACCESS  read-write
   STATUS      current
   DESCRIPTION
      "Path: lacpBundle.editConf.vlan.vlan.arp.staticArp.ipAddress"
   ::= {er1646v2LacpBVlanVlanArpStaticArpEntry 33554432}


er1646v2LacpBPppOE OBJECT IDENTIFIER ::= {er1646v2LacpB 35}

er1646v2LacpBPppOESSCTable OBJECT-TYPE
   SYNTAX      SEQUENCE OF Er1646v2LacpBPppOEEntry
   MAX-ACCESS  not-accessible
   STATUS      current
   DESCRIPTION
      ""
   ::= {er1646v2LacpBPppOE 1}

er1646v2LacpBPppOEEntry OBJECT-TYPE
   SYNTAX      Er1646v2LacpBPppOEEntry
   MAX-ACCESS  not-accessible
   STATUS      current
   DESCRIPTION
      ""
   INDEX      { er1646v2LacpBPppOEGlobalIx,
                er1646v2LacpBPppOETableIx }
   ::= {er1646v2LacpBPppOESSCTable 1}

Er1646v2LacpBPppOEEntry ::=
   SEQUENCE
      {
      er1646v2LacpBPppOEActions
         VariableLengthTableActions,
      er1646v2LacpBPppOEGlobalIx
         GlobalIndex,
      er1646v2LacpBPppOETableIx
         TableIndex,
      er1646v2LacpBPppOEName
         DisplayString,
      er1646v2LacpBPppOERemark
         DisplayString,
      er1646v2LacpBPppOEAdminStatus
         INTEGER,
      er1646v2LacpBPppOEMode
         INTEGER,
      er1646v2LacpBPppOEIpVrfRouter
         DisplayString,
      er1646v2LacpBPppOEIpAdr
         IpAddress,
      er1646v2LacpBPppOEIpNetm
         IpAddress,
      er1646v2LacpBPppOEIpSNetName
         INTEGER,
      er1646v2LacpBPppOEIpSNetCust
         DisplayString,
      er1646v2LacpBPppOEIpRem
         IpAddress,
      er1646v2LacpBPppOEIpUnnumbered
         DisplayString,
      er1646v2LacpBPppOEIpGwPref
         Integer32,
      er1646v2LacpBPppOEIpRsn
         INTEGER,
      er1646v2LacpBPppOEIpMtu
         Integer32,
      er1646v2LacpBPppOEIpMssAdjust
         INTEGER,
      er1646v2LacpBPppOEIpRipMetric
         Integer32,
      er1646v2LacpBPppOEIpRipMetricOut
         Integer32,
      er1646v2LacpBPppOEIpRipMode
         INTEGER,
      er1646v2LacpBPppOEIpRipTxVer
         INTEGER,
      er1646v2LacpBPppOEIpRipRxVer
         INTEGER,
      er1646v2LacpBPppOEIpRipSplitH
         INTEGER,
      er1646v2LacpBPppOEIpRipAuth
         INTEGER,
      er1646v2LacpBPppOEIpRipFilter
         DisplayString,
      er1646v2LacpBPppOEIpRipFilterIn
         DisplayString,
      er1646v2LacpBPppOEIpRipClearNextHop
         INTEGER,
      er1646v2LacpBPppOEIpAccPol
         DisplayString,
      er1646v2LacpBPppOEIpAB
         DisplayString,
      er1646v2LacpBPppOEIpMA
         INTEGER,
      er1646v2LacpBPppOEIpMF
         Integer32,
      er1646v2LacpBPppOEIpDB
         INTEGER,
      er1646v2LacpBPppOEIpIR
         INTEGER,
      er1646v2LacpBPppOEIpIgmp
         INTEGER,
      er1646v2LacpBPppOEIpNN
         DisplayString,
      er1646v2LacpBPppOEIpPimMode
         INTEGER,
      er1646v2LacpBPppOEIpPimDrPriority
         Counter32,
      er1646v2LacpBPppOEIpPimHelloTime
         TimeTicks,
      er1646v2LacpBPppOEIpPimPropagationDelay
         TimeTicks,
      er1646v2LacpBPppOEIpPimOverrideInterval
         TimeTicks,
      er1646v2LacpBPppOEIpPimBsrBorder
         INTEGER,
      er1646v2LacpBPppOEIpPimTtlThreshold
         Integer32,
      er1646v2LacpBPppOEIpIMNetworkUnreachable
         INTEGER,
      er1646v2LacpBPppOEIpIMHostUnreachable
         INTEGER,
      er1646v2LacpBPppOEIpIMProtocolUnreachable
         INTEGER,
      er1646v2LacpBPppOEIpIMPortUnreachable
         INTEGER,
      er1646v2LacpBPppOEIpIMMtuExceeded
         INTEGER,
      er1646v2LacpBPppOEIpIMAdminProhibited
         INTEGER,
      er1646v2LacpBPppOEIpIMTtlExceeded
         INTEGER,
      er1646v2LacpBPppOEIpIMRedirect
         INTEGER,
      er1646v2LacpBPppOEIpV6VrfRouter
         DisplayString,
      er1646v2LacpBPppOEIpV6AddrAutoConfigNrDupAddrDetects
         Integer32,
      er1646v2LacpBPppOEIpV6AddrAutoConfigAcceptRa
         INTEGER,
      er1646v2LacpBPppOEIpV6AddrAutoConfigAcceptRaRdnss
         INTEGER,
      er1646v2LacpBPppOEIpV6AddrAutoConfigAcceptRaDnssl
         INTEGER,
      er1646v2LacpBPppOEIpV6DefaultRoute
         INTEGER,
      er1646v2LacpBPppOEIpV6RaSend
         INTEGER,
      er1646v2LacpBPppOEIpV6RaMinInterval
         TimeTicks,
      er1646v2LacpBPppOEIpV6RaMaxInterval
         TimeTicks,
      er1646v2LacpBPppOEIpV6RaManagedFlag
         INTEGER,
      er1646v2LacpBPppOEIpV6RaOtherConfFlag
         INTEGER,
      er1646v2LacpBPppOEIpV6RaLinkMtu
         Integer32,
      er1646v2LacpBPppOEIpV6RaReachableTime
         TimeTicks,
      er1646v2LacpBPppOEIpV6RaRetransmitTime
         TimeTicks,
      er1646v2LacpBPppOEIpV6RaHopLimit
         Integer32,
      er1646v2LacpBPppOEIpV6RaDefaultLifeTime
         TimeTicks,
      er1646v2LacpBPppOEIpV6RaDnsOptionsRdnssLifeTime
         TimeTicks,
      er1646v2LacpBPppOEIpV6RaDnsOptionsRdnssImportServers
         INTEGER,
      er1646v2LacpBPppOEIpV6RaDnsOptionsDnsslLifeTime
         TimeTicks,
      er1646v2LacpBPppOEIpV6RaDnsOptionsDnsslImportDomains
         INTEGER,
      er1646v2LacpBPppOEIpV6RsSend
         INTEGER,
      er1646v2LacpBPppOEIpV6RsMaxRandomDelay
         TimeTicks,
      er1646v2LacpBPppOEIpV6RsInterval
         TimeTicks,
      er1646v2LacpBPppOEIpV6RsMaxSolicitations
         Integer32,
      er1646v2LacpBPppOEIpV6TrafficPolicyInbound
         DisplayString,
      er1646v2LacpBPppOEIpV6TrafficPolicyOutbound
         DisplayString,
      er1646v2LacpBPppOEIpV6FirewallZone
         DisplayString,
      er1646v2LacpBPppOEIpV6DhcpClientAddrAC
         INTEGER,
      er1646v2LacpBPppOEIpV6DhcpClientPrDelMode
         INTEGER,
      er1646v2LacpBPppOEIpV6DhcpClientPrDelPool
         DisplayString,
      er1646v2LacpBPppOEIpV6DhcpClientPrDelPdExclOpt
         INTEGER,
      er1646v2LacpBPppOEIpV6DhcpClientDnsServerPref
         Integer32,
      er1646v2LacpBPppOEIpV6DhcpClientRapidCommit
         INTEGER,
      er1646v2LacpBPppOEIpV6DhcpClientTimersSolTimeOut
         TimeTicks,
      er1646v2LacpBPppOEIpV6DhcpClientTimersSolMaxRt
         TimeTicks,
      er1646v2LacpBPppOEIpV6DhcpClientTimersInfoRefresh
         TimeTicks,
      er1646v2LacpBPppOEIpV6DhcpServerMode
         INTEGER,
      er1646v2LacpBPppOEIpV6DhcpServerPreference
         Integer32,
      er1646v2LacpBPppOEIpV6DhcpServerPool
         DisplayString,
      er1646v2LacpBPppOEIpV6DhcpServerRapidCommit
         INTEGER,
      er1646v2LacpBPppOEIpV6DhcpServerTimersInfoRefresh
         TimeTicks,
      er1646v2LacpBPppOEIpV6DhcpRelayMode
         INTEGER,
      er1646v2LacpBPppOEIpV6SendRedirect
         INTEGER,
      er1646v2LacpBPppOEIpV6LinkMtu
         Integer32,
      er1646v2LacpBPppOEIpV6InterfaceId
         OCTET STRING,
      er1646v2LacpBPppOEIpV6MF
         Integer32,
      er1646v2LacpBPppOEIpV6IcmpMessagesNoRoute
         INTEGER,
      er1646v2LacpBPppOEIpV6IcmpMessagesBeyondScope
         INTEGER,
      er1646v2LacpBPppOEIpV6IcmpMessagesAddressUnreachable
         INTEGER,
      er1646v2LacpBPppOEIpV6IcmpMessagesPortUnreachable
         INTEGER,
      er1646v2LacpBPppOEIpV6IcmpMessagesPacketTooBig
         INTEGER,
      er1646v2LacpBPppOEIpV6IcmpMessagesHopLimitExceeded
         INTEGER,
      er1646v2LacpBPppOEIpV6IcmpMessagesFragTimeExceeded
         INTEGER,
      er1646v2LacpBPppOEIpV6IcmpMessagesHeaderFieldErr
         INTEGER,
      er1646v2LacpBPppOEIpV6IcmpMessagesOptionUnrecognized
         INTEGER,
      er1646v2LacpBPppOEIpV6IcmpMessagesRedirect
         INTEGER,
      er1646v2LacpBPppOEPppLnkMOperation
         INTEGER,
      er1646v2LacpBPppOEPppLnkMInterval
         TimeTicks,
      er1646v2LacpBPppOEPppLnkMRepTimeOut
         TimeTicks,
      er1646v2LacpBPppOEPppLnkMFailsPrmt
         Integer32,
      er1646v2LacpBPppOEPppAuthentication
         INTEGER,
      er1646v2LacpBPppOEPppAuthenPeriod
         TimeTicks,
      er1646v2LacpBPppOEPppSessionName
         DisplayString,
      er1646v2LacpBPppOEPppSessionSecret
         DisplayString,
      er1646v2LacpBPppOEPppEncModeSessionSecret
         INTEGER,
      er1646v2LacpBPppOEPppEncSessionSecret
         DisplayString,
      er1646v2LacpBPppOEPppServiceName
         DisplayString
      }

er1646v2LacpBPppOEActions OBJECT-TYPE
   SYNTAX      VariableLengthTableActions
   MAX-ACCESS  read-write
   STATUS      current
   DESCRIPTION
      "By way of this field, some manipulations
       on this table may be performed."
   ::= {er1646v2LacpBPppOEEntry 2}

er1646v2LacpBPppOEGlobalIx OBJECT-TYPE
   SYNTAX      GlobalIndex
   MAX-ACCESS  not-accessible
   STATUS      current
   DESCRIPTION
      "The value of the tlsCntTreeGlobalIndex of the MANAGED OBJECT."
   ::= {er1646v2LacpBPppOEEntry 10}

er1646v2LacpBPppOETableIx OBJECT-TYPE
   SYNTAX      TableIndex
   MAX-ACCESS  not-accessible
   STATUS      current
   DESCRIPTION
      ""
   ::= {er1646v2LacpBPppOEEntry 11}

er1646v2LacpBPppOEName OBJECT-TYPE
   SYNTAX      DisplayString
   MAX-ACCESS  read-write
   STATUS      current
   DESCRIPTION
      "Path: lacpBundle.editConf.pppoEClient.name"
   ::= {er1646v2LacpBPppOEEntry 16777216}

er1646v2LacpBPppOERemark OBJECT-TYPE
   SYNTAX      DisplayString
   MAX-ACCESS  read-write
   STATUS      current
   DESCRIPTION
      "Path: lacpBundle.editConf.pppoEClient.remark"
   ::= {er1646v2LacpBPppOEEntry 1157627904}

er1646v2LacpBPppOEAdminStatus OBJECT-TYPE
   SYNTAX      INTEGER
               {
               up (1),
               down (2)
               }
   MAX-ACCESS  read-write
   STATUS      current
   DESCRIPTION
      "Path: lacpBundle.editConf.pppoEClient.adminStatus

       Possibilities:
               up   (1)
               down   (2)"
   ::= {er1646v2LacpBPppOEEntry 33554432}

er1646v2LacpBPppOEMode OBJECT-TYPE
   SYNTAX      INTEGER
               {
               routing (1),
               multilink (8),
               ipV6 (16),
               ipV6ipV4 (17)
               }
   MAX-ACCESS  read-write
   STATUS      current
   DESCRIPTION
      "Path: lacpBundle.editConf.pppoEClient.mode

       Possibilities:
               routing   (1)
               multilink   (8)
               ipV6   (16)
               ipV6/ipV4   (17)"
   ::= {er1646v2LacpBPppOEEntry 67108864}

er1646v2LacpBPppOEIpVrfRouter OBJECT-TYPE
   SYNTAX      DisplayString
   MAX-ACCESS  read-write
   STATUS      current
   DESCRIPTION
      "Path: lacpBundle.editConf.pppoEClient.ip.vrfRouter"
   ::= {er1646v2LacpBPppOEEntry 53215232}

er1646v2LacpBPppOEIpAdr OBJECT-TYPE
   SYNTAX      IpAddress
   MAX-ACCESS  read-write
   STATUS      current
   DESCRIPTION
      "Path: lacpBundle.editConf.pppoEClient.ip.address"
   ::= {er1646v2LacpBPppOEEntry 58261504}

er1646v2LacpBPppOEIpNetm OBJECT-TYPE
   SYNTAX      IpAddress
   MAX-ACCESS  read-write
   STATUS      current
   DESCRIPTION
      "Path: lacpBundle.editConf.pppoEClient.ip.netMask"
   ::= {er1646v2LacpBPppOEEntry 58392576}

er1646v2LacpBPppOEIpSNetName OBJECT-TYPE
   SYNTAX      INTEGER
               {
               slOPTg (0),
               corp (2),
               dmz (3),
               internet (1)
               }
   MAX-ACCESS  read-write
   STATUS      current
   DESCRIPTION
      "Path: lacpBundle.editConf.pppoEClient.ip.sNet.name

       Possibilities:
               <OPT>   (0)
               corp   (2)
               dmz   (3)
               internet   (1)"
   ::= {er1646v2LacpBPppOEEntry 53674240}

er1646v2LacpBPppOEIpSNetCust OBJECT-TYPE
   SYNTAX      DisplayString
   MAX-ACCESS  read-write
   STATUS      current
   DESCRIPTION
      "Path: lacpBundle.editConf.pppoEClient.ip.sNet.custom"
   ::= {er1646v2LacpBPppOEEntry 53674496}

er1646v2LacpBPppOEIpRem OBJECT-TYPE
   SYNTAX      IpAddress
   MAX-ACCESS  read-write
   STATUS      current
   DESCRIPTION
      "Path: lacpBundle.editConf.pppoEClient.ip.remote"
   ::= {er1646v2LacpBPppOEEntry 58458112}

er1646v2LacpBPppOEIpUnnumbered OBJECT-TYPE
   SYNTAX      DisplayString
   MAX-ACCESS  read-write
   STATUS      current
   DESCRIPTION
      "Path: lacpBundle.editConf.pppoEClient.ip.unnumbered"
   ::= {er1646v2LacpBPppOEEntry 52625408}

er1646v2LacpBPppOEIpGwPref OBJECT-TYPE
   SYNTAX      Integer32
   MAX-ACCESS  read-write
   STATUS      current
   DESCRIPTION
      "Path: lacpBundle.editConf.pppoEClient.ip.gatewayPreference"
   ::= {er1646v2LacpBPppOEEntry 52690944}

er1646v2LacpBPppOEIpRsn OBJECT-TYPE
   SYNTAX      INTEGER
               {
               disabled (0),
               enabled (1)
               }
   MAX-ACCESS  read-write
   STATUS      current
   DESCRIPTION
      "Path: lacpBundle.editConf.pppoEClient.ip.requestSubnet

       Possibilities:
               disabled   (0)
               enabled   (1)"
   ::= {er1646v2LacpBPppOEEntry 56688640}

er1646v2LacpBPppOEIpMtu OBJECT-TYPE
   SYNTAX      Integer32
   MAX-ACCESS  read-write
   STATUS      current
   DESCRIPTION
      "Path: lacpBundle.editConf.pppoEClient.ip.mtu"
   ::= {er1646v2LacpBPppOEEntry 52953088}

er1646v2LacpBPppOEIpMssAdjust OBJECT-TYPE
   SYNTAX      INTEGER
               {
               disabled (0),
               auto (65536)
               }
   MAX-ACCESS  read-write
   STATUS      current
   DESCRIPTION
      "Path: lacpBundle.editConf.pppoEClient.ip.mssAdjust

       Possibilities:
               disabled   (0)
               auto   (65536)"
   ::= {er1646v2LacpBPppOEEntry 53280768}

er1646v2LacpBPppOEIpRipMetric OBJECT-TYPE
   SYNTAX      Integer32
   MAX-ACCESS  read-write
   STATUS      current
   DESCRIPTION
      "Path: lacpBundle.editConf.pppoEClient.ip.rip.metric"
   ::= {er1646v2LacpBPppOEEntry 51712768}

er1646v2LacpBPppOEIpRipMetricOut OBJECT-TYPE
   SYNTAX      Integer32
   MAX-ACCESS  read-write
   STATUS      current
   DESCRIPTION
      "Path: lacpBundle.editConf.pppoEClient.ip.rip.metricOut"
   ::= {er1646v2LacpBPppOEEntry 51713024}

er1646v2LacpBPppOEIpRipMode OBJECT-TYPE
   SYNTAX      INTEGER
               {
               disabled (0),
               passive (1),
               active (2)
               }
   MAX-ACCESS  read-write
   STATUS      current
   DESCRIPTION
      "Path: lacpBundle.editConf.pppoEClient.ip.rip.mode

       Possibilities:
               disabled   (0)
               passive   (1)
               active   (2)"
   ::= {er1646v2LacpBPppOEEntry 51713280}

er1646v2LacpBPppOEIpRipTxVer OBJECT-TYPE
   SYNTAX      INTEGER
               {
               rip1 (0),
               rip2 (1),
               rip1mcompatible (2)
               }
   MAX-ACCESS  read-write
   STATUS      current
   DESCRIPTION
      "Path: lacpBundle.editConf.pppoEClient.ip.rip.txVersion

       Possibilities:
               rip1   (0)
               rip2   (1)
               rip1-compatible   (2)"
   ::= {er1646v2LacpBPppOEEntry 51716864}

er1646v2LacpBPppOEIpRipRxVer OBJECT-TYPE
   SYNTAX      INTEGER
               {
               rip1only (0),
               rip2only (1),
               rip12 (2)
               }
   MAX-ACCESS  read-write
   STATUS      current
   DESCRIPTION
      "Path: lacpBundle.editConf.pppoEClient.ip.rip.rxVersion

       Possibilities:
               rip1only   (0)
               rip2only   (1)
               rip1&2   (2)"
   ::= {er1646v2LacpBPppOEEntry 51717120}

er1646v2LacpBPppOEIpRipSplitH OBJECT-TYPE
   SYNTAX      INTEGER
               {
               disabled (0),
               enabled (1),
               poisonedReverse (2)
               }
   MAX-ACCESS  read-write
   STATUS      current
   DESCRIPTION
      "Path: lacpBundle.editConf.pppoEClient.ip.rip.splitHorizon

       Possibilities:
               disabled   (0)
               enabled   (1)
               poisonedReverse   (2)"
   ::= {er1646v2LacpBPppOEEntry 51713792}

er1646v2LacpBPppOEIpRipAuth OBJECT-TYPE
   SYNTAX      INTEGER
               {
               disabled (0),
               texts (1),
               md5 (2)
               }
   MAX-ACCESS  read-write
   STATUS      current
   DESCRIPTION
      "Path: lacpBundle.editConf.pppoEClient.ip.rip.authentication

       Possibilities:
               disabled   (0)
               text    (1)
               md5   (2)"
   ::= {er1646v2LacpBPppOEEntry 51712512}

er1646v2LacpBPppOEIpRipFilter OBJECT-TYPE
   SYNTAX      DisplayString
   MAX-ACCESS  read-write
   STATUS      current
   DESCRIPTION
      "Path: lacpBundle.editConf.pppoEClient.ip.rip.filter"
   ::= {er1646v2LacpBPppOEEntry 51716096}

er1646v2LacpBPppOEIpRipFilterIn OBJECT-TYPE
   SYNTAX      DisplayString
   MAX-ACCESS  read-write
   STATUS      current
   DESCRIPTION
      "Path: lacpBundle.editConf.pppoEClient.ip.rip.filterIn"
   ::= {er1646v2LacpBPppOEEntry 51716352}

er1646v2LacpBPppOEIpRipClearNextHop OBJECT-TYPE
   SYNTAX      INTEGER
               {
               disabled (0),
               enabled (1)
               }
   MAX-ACCESS  read-write
   STATUS      current
   DESCRIPTION
      "Path: lacpBundle.editConf.pppoEClient.ip.rip.clearNextHop

       Possibilities:
               disabled   (0)
               enabled   (1)"
   ::= {er1646v2LacpBPppOEEntry 51708416}

er1646v2LacpBPppOEIpAccPol OBJECT-TYPE
   SYNTAX      DisplayString
   MAX-ACCESS  read-write
   STATUS      current
   DESCRIPTION
      "Path: lacpBundle.editConf.pppoEClient.ip.accessPolicy"
   ::= {er1646v2LacpBPppOEEntry 53084160}

er1646v2LacpBPppOEIpAB OBJECT-TYPE
   SYNTAX      DisplayString
   MAX-ACCESS  read-write
   STATUS      current
   DESCRIPTION
      "Path: lacpBundle.editConf.pppoEClient.ip.trafficPolicy"
   ::= {er1646v2LacpBPppOEEntry 51249152}

er1646v2LacpBPppOEIpMA OBJECT-TYPE
   SYNTAX      INTEGER
               {
               disabled (0),
               enabled (1)
               }
   MAX-ACCESS  read-write
   STATUS      current
   DESCRIPTION
      "Path: lacpBundle.editConf.pppoEClient.ip.mgmtAccess

       Possibilities:
               disabled   (0)
               enabled   (1)"
   ::= {er1646v2LacpBPppOEEntry 51380224}

er1646v2LacpBPppOEIpMF OBJECT-TYPE
   SYNTAX      Integer32
   MAX-ACCESS  read-write
   STATUS      current
   DESCRIPTION
      "Path: lacpBundle.editConf.pppoEClient.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1646v2LacpBPppOEEntry 51445760}

er1646v2LacpBPppOEIpDB OBJECT-TYPE
   SYNTAX      INTEGER
               {
               disabled (0),
               enabled (1)
               }
   MAX-ACCESS  read-write
   STATUS      current
   DESCRIPTION
      "Path: lacpBundle.editConf.pppoEClient.ip.directedBroadcasts

       Possibilities:
               disabled   (0)
               enabled   (1)"
   ::= {er1646v2LacpBPppOEEntry 51773440}

er1646v2LacpBPppOEIpIR OBJECT-TYPE
   SYNTAX      INTEGER
               {
               disabled (0),
               enabled (1)
               }
   MAX-ACCESS  read-write
   STATUS      current
   DESCRIPTION
      "Path: lacpBundle.editConf.pppoEClient.ip.icmpRedirects

       Possibilities:
               disabled   (0)
               enabled   (1)"
   ::= {er1646v2LacpBPppOEEntry 52035584}

er1646v2LacpBPppOEIpIgmp OBJECT-TYPE
   SYNTAX      INTEGER
               {
               disabled (0),
               proxy (1),
               router (2),
               v3Router (5)
               }
   MAX-ACCESS  read-write
   STATUS      current
   DESCRIPTION
      "Path: lacpBundle.editConf.pppoEClient.ip.igmp

       Possibilities:
               disabled   (0)
               proxy   (1)
               router   (2)
               v3Router   (5)"
   ::= {er1646v2LacpBPppOEEntry 52428800}

er1646v2LacpBPppOEIpNN OBJECT-TYPE
   SYNTAX      DisplayString
   MAX-ACCESS  read-write
   STATUS      current
   DESCRIPTION
      "Path: lacpBundle.editConf.pppoEClient.ip.nat"
   ::= {er1646v2LacpBPppOEEntry 52101120}

er1646v2LacpBPppOEIpPimMode OBJECT-TYPE
   SYNTAX      INTEGER
               {
               disabled (0),
               sparse (1),
               passive (2)
               }
   MAX-ACCESS  read-write
   STATUS      current
   DESCRIPTION
      "Path: lacpBundle.editConf.pppoEClient.ip.pim.mode

       Possibilities:
               disabled   (0)
               sparse   (1)
               passive   (2)"
   ::= {er1646v2LacpBPppOEEntry 53346560}

er1646v2LacpBPppOEIpPimDrPriority OBJECT-TYPE
   SYNTAX      Counter32
   MAX-ACCESS  read-write
   STATUS      current
   DESCRIPTION
      "Path: lacpBundle.editConf.pppoEClient.ip.pim.drPriority

       32 bit unsigned wrappable counter."
   ::= {er1646v2LacpBPppOEEntry 53346816}

er1646v2LacpBPppOEIpPimHelloTime OBJECT-TYPE
   SYNTAX      TimeTicks
   MAX-ACCESS  read-write
   STATUS      current
   DESCRIPTION
      "Path: lacpBundle.editConf.pppoEClient.ip.pim.helloTime

       Time in centi-second."
   ::= {er1646v2LacpBPppOEEntry 53347072}

er1646v2LacpBPppOEIpPimPropagationDelay OBJECT-TYPE
   SYNTAX      TimeTicks
   MAX-ACCESS  read-write
   STATUS      current
   DESCRIPTION
      "Path: lacpBundle.editConf.pppoEClient.ip.pim.propagationDelay

       Time in centi-second."
   ::= {er1646v2LacpBPppOEEntry 53347328}

er1646v2LacpBPppOEIpPimOverrideInterval OBJECT-TYPE
   SYNTAX      TimeTicks
   MAX-ACCESS  read-write
   STATUS      current
   DESCRIPTION
      "Path: lacpBundle.editConf.pppoEClient.ip.pim.overrideInterval

       Time in centi-second."
   ::= {er1646v2LacpBPppOEEntry 53347584}

er1646v2LacpBPppOEIpPimBsrBorder OBJECT-TYPE
   SYNTAX      INTEGER
               {
               disabled (0),
               enabled (1)
               }
   MAX-ACCESS  read-write
   STATUS      current
   DESCRIPTION
      "Path: lacpBundle.editConf.pppoEClient.ip.pim.bsrBorder

       Possibilities:
               disabled   (0)
               enabled   (1)"
   ::= {er1646v2LacpBPppOEEntry 53347840}

er1646v2LacpBPppOEIpPimTtlThreshold OBJECT-TYPE
   SYNTAX      Integer32
   MAX-ACCESS  read-write
   STATUS      current
   DESCRIPTION
      "Path: lacpBundle.editConf.pppoEClient.ip.pim.ttlThreshold"
   ::= {er1646v2LacpBPppOEEntry 53348096}

er1646v2LacpBPppOEIpIMNetworkUnreachable OBJECT-TYPE
   SYNTAX      INTEGER
               {
               disabled (0),
               enabled (1)
               }
   MAX-ACCESS  read-write
   STATUS      current
   DESCRIPTION
      "Path: lacpBundle.editConf.pppoEClient.ip.icmpMessages.networkUnreachable

       Possibilities:
               disabled   (0)
               enabled   (1)"
   ::= {er1646v2LacpBPppOEEntry 53412096}

er1646v2LacpBPppOEIpIMHostUnreachable OBJECT-TYPE
   SYNTAX      INTEGER
               {
               disabled (0),
               enabled (1)
               }
   MAX-ACCESS  read-write
   STATUS      current
   DESCRIPTION
      "Path: lacpBundle.editConf.pppoEClient.ip.icmpMessages.hostUnreachable

       Possibilities:
               disabled   (0)
               enabled   (1)"
   ::= {er1646v2LacpBPppOEEntry 53412352}

er1646v2LacpBPppOEIpIMProtocolUnreachable OBJECT-TYPE
   SYNTAX      INTEGER
               {
               disabled (0),
               enabled (1)
               }
   MAX-ACCESS  read-write
   STATUS      current
   DESCRIPTION
      "Path: lacpBundle.editConf.pppoEClient.ip.icmpMessages.protocolUnreachable

       Possibilities:
               disabled   (0)
               enabled   (1)"
   ::= {er1646v2LacpBPppOEEntry 53412608}

er1646v2LacpBPppOEIpIMPortUnreachable OBJECT-TYPE
   SYNTAX      INTEGER
               {
               disabled (0),
               enabled (1)
               }
   MAX-ACCESS  read-write
   STATUS      current
   DESCRIPTION
      "Path: lacpBundle.editConf.pppoEClient.ip.icmpMessages.portUnreachable

       Possibilities:
               disabled   (0)
               enabled   (1)"
   ::= {er1646v2LacpBPppOEEntry 53412864}

er1646v2LacpBPppOEIpIMMtuExceeded OBJECT-TYPE
   SYNTAX      INTEGER
               {
               disabled (0),
               enabled (1)
               }
   MAX-ACCESS  read-write
   STATUS      current
   DESCRIPTION
      "Path: lacpBundle.editConf.pppoEClient.ip.icmpMessages.mtuExceeded

       Possibilities:
               disabled   (0)
               enabled   (1)"
   ::= {er1646v2LacpBPppOEEntry 53413120}

er1646v2LacpBPppOEIpIMAdminProhibited OBJECT-TYPE
   SYNTAX      INTEGER
               {
               disabled (0),
               enabled (1)
               }
   MAX-ACCESS  read-write
   STATUS      current
   DESCRIPTION
      "Path: lacpBundle.editConf.pppoEClient.ip.icmpMessages.adminProhibited

       Possibilities:
               disabled   (0)
               enabled   (1)"
   ::= {er1646v2LacpBPppOEEntry 53413376}

er1646v2LacpBPppOEIpIMTtlExceeded OBJECT-TYPE
   SYNTAX      INTEGER
               {
               disabled (0),
               enabled (1)
               }
   MAX-ACCESS  read-write
   STATUS      current
   DESCRIPTION
      "Path: lacpBundle.editConf.pppoEClient.ip.icmpMessages.ttlExceeded

       Possibilities:
               disabled   (0)
               enabled   (1)"
   ::= {er1646v2LacpBPppOEEntry 53413632}

er1646v2LacpBPppOEIpIMRedirect OBJECT-TYPE
   SYNTAX      INTEGER
               {
               disabled (0),
               enabled (1)
               }
   MAX-ACCESS  read-write
   STATUS      current
   DESCRIPTION
      "Path: lacpBundle.editConf.pppoEClient.ip.icmpMessages.redirect

       Possibilities:
               disabled   (0)
               enabled   (1)"
   ::= {er1646v2LacpBPppOEEntry 53413888}

er1646v2LacpBPppOEIpV6VrfRouter OBJECT-TYPE
   SYNTAX      DisplayString
   MAX-ACCESS  read-write
   STATUS      current
   DESCRIPTION
      "Path: lacpBundle.editConf.pppoEClient.ipV6.vrfRouter"
   ::= {er1646v2LacpBPppOEEntry 704708608}

er1646v2LacpBPppOEIpV6AddrAutoConfigNrDupAddrDetects OBJECT-TYPE
   SYNTAX      Integer32
   MAX-ACCESS  read-write
   STATUS      current
   DESCRIPTION
      "Path: lacpBundle.editConf.pppoEClient.ipV6.addrAutoConfig.nrDupAddrDetects"
   ::= {er1646v2LacpBPppOEEntry 704905472}

er1646v2LacpBPppOEIpV6AddrAutoConfigAcceptRa OBJECT-TYPE
   SYNTAX      INTEGER
               {
               disabled (0),
               enabled (1)
               }
   MAX-ACCESS  read-write
   STATUS      current
   DESCRIPTION
      "Path: lacpBundle.editConf.pppoEClient.ipV6.addrAutoConfig.acceptRa

       Possibilities:
               disabled   (0)
               enabled   (1)"
   ::= {er1646v2LacpBPppOEEntry 704905728}

er1646v2LacpBPppOEIpV6AddrAutoConfigAcceptRaRdnss OBJECT-TYPE
   SYNTAX      INTEGER
               {
               disabled (0),
               enabled (1)
               }
   MAX-ACCESS  read-write
   STATUS      current
   DESCRIPTION
      "Path: lacpBundle.editConf.pppoEClient.ipV6.addrAutoConfig.acceptRaRdnss

       Possibilities:
               disabled   (0)
               enabled   (1)"
   ::= {er1646v2LacpBPppOEEntry 704905984}

er1646v2LacpBPppOEIpV6AddrAutoConfigAcceptRaDnssl OBJECT-TYPE
   SYNTAX      INTEGER
               {
               disabled (0),
               enabled (1)
               }
   MAX-ACCESS  read-write
   STATUS      current
   DESCRIPTION
      "Path: lacpBundle.editConf.pppoEClient.ipV6.addrAutoConfig.acceptRaDnssl

       Possibilities:
               disabled   (0)
               enabled   (1)"
   ::= {er1646v2LacpBPppOEEntry 704906240}

er1646v2LacpBPppOEIpV6DefaultRoute OBJECT-TYPE
   SYNTAX      INTEGER
               {
               disabled (0),
               enabled (1)
               }
   MAX-ACCESS  read-write
   STATUS      current
   DESCRIPTION
      "Path: lacpBundle.editConf.pppoEClient.ipV6.defaultRoute

       Possibilities:
               disabled   (0)
               enabled   (1)"
   ::= {er1646v2LacpBPppOEEntry 704970752}

er1646v2LacpBPppOEIpV6RaSend OBJECT-TYPE
   SYNTAX      INTEGER
               {
               disabled (0),
               enabled (1)
               }
   MAX-ACCESS  read-write
   STATUS      current
   DESCRIPTION
      "Path: lacpBundle.editConf.pppoEClient.ipV6.ra.send

       Possibilities:
               disabled   (0)
               enabled   (1)"
   ::= {er1646v2LacpBPppOEEntry 705036544}

er1646v2LacpBPppOEIpV6RaMinInterval OBJECT-TYPE
   SYNTAX      TimeTicks
   MAX-ACCESS  read-write
   STATUS      current
   DESCRIPTION
      "Path: lacpBundle.editConf.pppoEClient.ipV6.ra.minInterval

       Time in centi-second."
   ::= {er1646v2LacpBPppOEEntry 705036800}

er1646v2LacpBPppOEIpV6RaMaxInterval OBJECT-TYPE
   SYNTAX      TimeTicks
   MAX-ACCESS  read-write
   STATUS      current
   DESCRIPTION
      "Path: lacpBundle.editConf.pppoEClient.ipV6.ra.maxInterval

       Time in centi-second."
   ::= {er1646v2LacpBPppOEEntry 705037056}

er1646v2LacpBPppOEIpV6RaManagedFlag OBJECT-TYPE
   SYNTAX      INTEGER
               {
               disabled (0),
               enabled (1)
               }
   MAX-ACCESS  read-write
   STATUS      current
   DESCRIPTION
      "Path: lacpBundle.editConf.pppoEClient.ipV6.ra.managedFlag

       Possibilities:
               disabled   (0)
               enabled   (1)"
   ::= {er1646v2LacpBPppOEEntry 705037312}

er1646v2LacpBPppOEIpV6RaOtherConfFlag OBJECT-TYPE
   SYNTAX      INTEGER
               {
               disabled (0),
               enabled (1)
               }
   MAX-ACCESS  read-write
   STATUS      current
   DESCRIPTION
      "Path: lacpBundle.editConf.pppoEClient.ipV6.ra.otherConfFlag

       Possibilities:
               disabled   (0)
               enabled   (1)"
   ::= {er1646v2LacpBPppOEEntry 705037568}

er1646v2LacpBPppOEIpV6RaLinkMtu OBJECT-TYPE
   SYNTAX      Integer32
   MAX-ACCESS  read-write
   STATUS      current
   DESCRIPTION
      "Path: lacpBundle.editConf.pppoEClient.ipV6.ra.linkMtu"
   ::= {er1646v2LacpBPppOEEntry 705037824}

er1646v2LacpBPppOEIpV6RaReachableTime OBJECT-TYPE
   SYNTAX      TimeTicks
   MAX-ACCESS  read-write
   STATUS      current
   DESCRIPTION
      "Path: lacpBundle.editConf.pppoEClient.ipV6.ra.reachableTime

       Time in centi-second."
   ::= {er1646v2LacpBPppOEEntry 705038080}

er1646v2LacpBPppOEIpV6RaRetransmitTime OBJECT-TYPE
   SYNTAX      TimeTicks
   MAX-ACCESS  read-write
   STATUS      current
   DESCRIPTION
      "Path: lacpBundle.editConf.pppoEClient.ipV6.ra.retransmitTime

       Time in centi-second."
   ::= {er1646v2LacpBPppOEEntry 705038336}

er1646v2LacpBPppOEIpV6RaHopLimit OBJECT-TYPE
   SYNTAX      Integer32
   MAX-ACCESS  read-write
   STATUS      current
   DESCRIPTION
      "Path: lacpBundle.editConf.pppoEClient.ipV6.ra.hopLimit"
   ::= {er1646v2LacpBPppOEEntry 705038592}

er1646v2LacpBPppOEIpV6RaDefaultLifeTime OBJECT-TYPE
   SYNTAX      TimeTicks
   MAX-ACCESS  read-write
   STATUS      current
   DESCRIPTION
      "Path: lacpBundle.editConf.pppoEClient.ipV6.ra.defaultLifeTime

       Time in centi-second."
   ::= {er1646v2LacpBPppOEEntry 705038848}

er1646v2LacpBPppOEIpV6RaDnsOptionsRdnssLifeTime OBJECT-TYPE
   SYNTAX      TimeTicks
   MAX-ACCESS  read-write
   STATUS      current
   DESCRIPTION
      "Path: lacpBundle.editConf.pppoEClient.ipV6.ra.dnsOptions.rdnss.lifeTime

       Time in centi-second."
   ::= {er1646v2LacpBPppOEEntry 705039140}

er1646v2LacpBPppOEIpV6RaDnsOptionsRdnssImportServers OBJECT-TYPE
   SYNTAX      INTEGER
               {
               disabled (0),
               enabled (1)
               }
   MAX-ACCESS  read-write
   STATUS      current
   DESCRIPTION
      "Path: lacpBundle.editConf.pppoEClient.ipV6.ra.dnsOptions.rdnss.importServers

       Possibilities:
               disabled   (0)
               enabled   (1)"
   ::= {er1646v2LacpBPppOEEntry 705039148}

er1646v2LacpBPppOEIpV6RaDnsOptionsDnsslLifeTime OBJECT-TYPE
   SYNTAX      TimeTicks
   MAX-ACCESS  read-write
   STATUS      current
   DESCRIPTION
      "Path: lacpBundle.editConf.pppoEClient.ipV6.ra.dnsOptions.dnssl.lifeTime

       Time in centi-second."
   ::= {er1646v2LacpBPppOEEntry 705039172}

er1646v2LacpBPppOEIpV6RaDnsOptionsDnsslImportDomains OBJECT-TYPE
   SYNTAX      INTEGER
               {
               disabled (0),
               enabled (1)
               }
   MAX-ACCESS  read-write
   STATUS      current
   DESCRIPTION
      "Path: lacpBundle.editConf.pppoEClient.ipV6.ra.dnsOptions.dnssl.importDomains

       Possibilities:
               disabled   (0)
               enabled   (1)"
   ::= {er1646v2LacpBPppOEEntry 705039180}

er1646v2LacpBPppOEIpV6RsSend OBJECT-TYPE
   SYNTAX      INTEGER
               {
               disabled (0),
               enabled (1)
               }
   MAX-ACCESS  read-write
   STATUS      current
   DESCRIPTION
      "Path: lacpBundle.editConf.pppoEClient.ipV6.rs.send

       Possibilities:
               disabled   (0)
               enabled   (1)"
   ::= {er1646v2LacpBPppOEEntry 705954048}

er1646v2LacpBPppOEIpV6RsMaxRandomDelay OBJECT-TYPE
   SYNTAX      TimeTicks
   MAX-ACCESS  read-write
   STATUS      current
   DESCRIPTION
      "Path: lacpBundle.editConf.pppoEClient.ipV6.rs.maxRandomDelay

       Time in centi-second."
   ::= {er1646v2LacpBPppOEEntry 705954304}

er1646v2LacpBPppOEIpV6RsInterval OBJECT-TYPE
   SYNTAX      TimeTicks
   MAX-ACCESS  read-write
   STATUS      current
   DESCRIPTION
      "Path: lacpBundle.editConf.pppoEClient.ipV6.rs.interval

       Time in centi-second."
   ::= {er1646v2LacpBPppOEEntry 705954560}

er1646v2LacpBPppOEIpV6RsMaxSolicitations OBJECT-TYPE
   SYNTAX      Integer32
   MAX-ACCESS  read-write
   STATUS      current
   DESCRIPTION
      "Path: lacpBundle.editConf.pppoEClient.ipV6.rs.maxSolicitations"
   ::= {er1646v2LacpBPppOEEntry 705954816}

er1646v2LacpBPppOEIpV6TrafficPolicyInbound OBJECT-TYPE
   SYNTAX      DisplayString
   MAX-ACCESS  read-write
   STATUS      current
   DESCRIPTION
      "Path: lacpBundle.editConf.pppoEClient.ipV6.trafficPolicy.inbound"
   ::= {er1646v2LacpBPppOEEntry 705364224}

er1646v2LacpBPppOEIpV6TrafficPolicyOutbound OBJECT-TYPE
   SYNTAX      DisplayString
   MAX-ACCESS  read-write
   STATUS      current
   DESCRIPTION
      "Path: lacpBundle.editConf.pppoEClient.ipV6.trafficPolicy.outbound"
   ::= {er1646v2LacpBPppOEEntry 705364480}

er1646v2LacpBPppOEIpV6FirewallZone OBJECT-TYPE
   SYNTAX      DisplayString
   MAX-ACCESS  read-write
   STATUS      current
   DESCRIPTION
      "Path: lacpBundle.editConf.pppoEClient.ipV6.firewall.zone"
   ::= {er1646v2LacpBPppOEEntry 705429760}

er1646v2LacpBPppOEIpV6DhcpClientAddrAC OBJECT-TYPE
   SYNTAX      INTEGER
               {
               disabled (0),
               enabled (1)
               }
   MAX-ACCESS  read-write
   STATUS      current
   DESCRIPTION
      "Path: lacpBundle.editConf.pppoEClient.ipV6.dhcp.client.addrAutoConfig

       Possibilities:
               disabled   (0)
               enabled   (1)"
   ::= {er1646v2LacpBPppOEEntry 705307648}

er1646v2LacpBPppOEIpV6DhcpClientPrDelMode OBJECT-TYPE
   SYNTAX      INTEGER
               {
               disabled (0),
               enabled (1)
               }
   MAX-ACCESS  read-write
   STATUS      current
   DESCRIPTION
      "Path: lacpBundle.editConf.pppoEClient.ipV6.dhcp.client.pd.mode

       Possibilities:
               disabled   (0)
               enabled   (1)"
   ::= {er1646v2LacpBPppOEEntry 705308676}

er1646v2LacpBPppOEIpV6DhcpClientPrDelPool OBJECT-TYPE
   SYNTAX      DisplayString
   MAX-ACCESS  read-write
   STATUS      current
   DESCRIPTION
      "Path: lacpBundle.editConf.pppoEClient.ipV6.dhcp.client.pd.pool"
   ::= {er1646v2LacpBPppOEEntry 705308680}

er1646v2LacpBPppOEIpV6DhcpClientPrDelPdExclOpt OBJECT-TYPE
   SYNTAX      INTEGER
               {
               disabled (0),
               enabled (1)
               }
   MAX-ACCESS  read-write
   STATUS      current
   DESCRIPTION
      "Path: lacpBundle.editConf.pppoEClient.ipV6.dhcp.client.pd.pdExclOpt

       Possibilities:
               disabled   (0)
               enabled   (1)"
   ::= {er1646v2LacpBPppOEEntry 705308684}

er1646v2LacpBPppOEIpV6DhcpClientDnsServerPref OBJECT-TYPE
   SYNTAX      Integer32
   MAX-ACCESS  read-write
   STATUS      current
   DESCRIPTION
      "Path: lacpBundle.editConf.pppoEClient.ipV6.dhcp.client.dns.serverPref"
   ::= {er1646v2LacpBPppOEEntry 705310724}

er1646v2LacpBPppOEIpV6DhcpClientRapidCommit OBJECT-TYPE
   SYNTAX      INTEGER
               {
               disabled (0),
               enabled (1)
               }
   MAX-ACCESS  read-write
   STATUS      current
   DESCRIPTION
      "Path: lacpBundle.editConf.pppoEClient.ipV6.dhcp.client.rapidCommit

       Possibilities:
               disabled   (0)
               enabled   (1)"
   ::= {er1646v2LacpBPppOEEntry 705309696}

er1646v2LacpBPppOEIpV6DhcpClientTimersSolTimeOut OBJECT-TYPE
   SYNTAX      TimeTicks
   MAX-ACCESS  read-write
   STATUS      current
   DESCRIPTION
      "Path: lacpBundle.editConf.pppoEClient.ipV6.dhcp.client.timers.solTimeOut

       Time in centi-second."
   ::= {er1646v2LacpBPppOEEntry 705311748}

er1646v2LacpBPppOEIpV6DhcpClientTimersSolMaxRt OBJECT-TYPE
   SYNTAX      TimeTicks
   MAX-ACCESS  read-write
   STATUS      current
   DESCRIPTION
      "Path: lacpBundle.editConf.pppoEClient.ipV6.dhcp.client.timers.solMaxRt

       Time in centi-second."
   ::= {er1646v2LacpBPppOEEntry 705311752}

er1646v2LacpBPppOEIpV6DhcpClientTimersInfoRefresh OBJECT-TYPE
   SYNTAX      TimeTicks
   MAX-ACCESS  read-write
   STATUS      current
   DESCRIPTION
      "Path: lacpBundle.editConf.pppoEClient.ipV6.dhcp.client.timers.infoRefresh

       Time in centi-second."
   ::= {er1646v2LacpBPppOEEntry 705311756}

er1646v2LacpBPppOEIpV6DhcpServerMode OBJECT-TYPE
   SYNTAX      INTEGER
               {
               disabled (0),
               enabled (1)
               }
   MAX-ACCESS  read-write
   STATUS      current
   DESCRIPTION
      "Path: lacpBundle.editConf.pppoEClient.ipV6.dhcp.server.mode

       Possibilities:
               disabled   (0)
               enabled   (1)"
   ::= {er1646v2LacpBPppOEEntry 705315840}

er1646v2LacpBPppOEIpV6DhcpServerPreference OBJECT-TYPE
   SYNTAX      Integer32
   MAX-ACCESS  read-write
   STATUS      current
   DESCRIPTION
      "Path: lacpBundle.editConf.pppoEClient.ipV6.dhcp.server.preference"
   ::= {er1646v2LacpBPppOEEntry 705316864}

er1646v2LacpBPppOEIpV6DhcpServerPool OBJECT-TYPE
   SYNTAX      DisplayString
   MAX-ACCESS  read-write
   STATUS      current
   DESCRIPTION
      "Path: lacpBundle.editConf.pppoEClient.ipV6.dhcp.server.pool"
   ::= {er1646v2LacpBPppOEEntry 705317888}

er1646v2LacpBPppOEIpV6DhcpServerRapidCommit OBJECT-TYPE
   SYNTAX      INTEGER
               {
               disabled (0),
               enabled (1)
               }
   MAX-ACCESS  read-write
   STATUS      current
   DESCRIPTION
      "Path: lacpBundle.editConf.pppoEClient.ipV6.dhcp.server.rapidCommit

       Possibilities:
               disabled   (0)
               enabled   (1)"
   ::= {er1646v2LacpBPppOEEntry 705318912}

er1646v2LacpBPppOEIpV6DhcpServerTimersInfoRefresh OBJECT-TYPE
   SYNTAX      TimeTicks
   MAX-ACCESS  read-write
   STATUS      current
   DESCRIPTION
      "Path: lacpBundle.editConf.pppoEClient.ipV6.dhcp.server.timers.infoRefresh

       Time in centi-second."
   ::= {er1646v2LacpBPppOEEntry 705319940}

er1646v2LacpBPppOEIpV6DhcpRelayMode OBJECT-TYPE
   SYNTAX      INTEGER
               {
               disabled (0),
               enabled (1)
               }
   MAX-ACCESS  read-write
   STATUS      current
   DESCRIPTION
      "Path: lacpBundle.editConf.pppoEClient.ipV6.dhcp.relay.mode

       Possibilities:
               disabled   (0)
               enabled   (1)"
   ::= {er1646v2LacpBPppOEEntry 705323040}

er1646v2LacpBPppOEIpV6SendRedirect OBJECT-TYPE
   SYNTAX      INTEGER
               {
               disabled (0),
               enabled (1)
               }
   MAX-ACCESS  read-write
   STATUS      current
   DESCRIPTION
      "Path: lacpBundle.editConf.pppoEClient.ipV6.sendRedirect

       Possibilities:
               disabled   (0)
               enabled   (1)"
   ::= {er1646v2LacpBPppOEEntry 705101824}

er1646v2LacpBPppOEIpV6LinkMtu OBJECT-TYPE
   SYNTAX      Integer32
   MAX-ACCESS  read-write
   STATUS      current
   DESCRIPTION
      "Path: lacpBundle.editConf.pppoEClient.ipV6.linkMtu"
   ::= {er1646v2LacpBPppOEEntry 705167360}

er1646v2LacpBPppOEIpV6InterfaceId OBJECT-TYPE
   SYNTAX      OCTET STRING
   MAX-ACCESS  read-write
   STATUS      current
   DESCRIPTION
      "Path: lacpBundle.editConf.pppoEClient.ipV6.interfaceId"
   ::= {er1646v2LacpBPppOEEntry 705232896}

er1646v2LacpBPppOEIpV6MF OBJECT-TYPE
   SYNTAX      Integer32
   MAX-ACCESS  read-write
   STATUS      current
   DESCRIPTION
      "Path: lacpBundle.editConf.pppoEClient.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1646v2LacpBPppOEEntry 705757184}

er1646v2LacpBPppOEIpV6IcmpMessagesNoRoute OBJECT-TYPE
   SYNTAX      INTEGER
               {
               disabled (0),
               enabled (1)
               }
   MAX-ACCESS  read-write
   STATUS      current
   DESCRIPTION
      "Path: lacpBundle.editConf.pppoEClient.ipV6.icmpMessages.noRoute

       Possibilities:
               disabled   (0)
               enabled   (1)"
   ::= {er1646v2LacpBPppOEEntry 705822976}

er1646v2LacpBPppOEIpV6IcmpMessagesBeyondScope OBJECT-TYPE
   SYNTAX      INTEGER
               {
               disabled (0),
               enabled (1)
               }
   MAX-ACCESS  read-write
   STATUS      current
   DESCRIPTION
      "Path: lacpBundle.editConf.pppoEClient.ipV6.icmpMessages.beyondScope

       Possibilities:
               disabled   (0)
               enabled   (1)"
   ::= {er1646v2LacpBPppOEEntry 705823488}

er1646v2LacpBPppOEIpV6IcmpMessagesAddressUnreachable OBJECT-TYPE
   SYNTAX      INTEGER
               {
               disabled (0),
               enabled (1)
               }
   MAX-ACCESS  read-write
   STATUS      current
   DESCRIPTION
      "Path: lacpBundle.editConf.pppoEClient.ipV6.icmpMessages.addressUnreachable

       Possibilities:
               disabled   (0)
               enabled   (1)"
   ::= {er1646v2LacpBPppOEEntry 705823744}

er1646v2LacpBPppOEIpV6IcmpMessagesPortUnreachable OBJECT-TYPE
   SYNTAX      INTEGER
               {
               disabled (0),
               enabled (1)
               }
   MAX-ACCESS  read-write
   STATUS      current
   DESCRIPTION
      "Path: lacpBundle.editConf.pppoEClient.ipV6.icmpMessages.portUnreachable

       Possibilities:
               disabled   (0)
               enabled   (1)"
   ::= {er1646v2LacpBPppOEEntry 705824000}

er1646v2LacpBPppOEIpV6IcmpMessagesPacketTooBig OBJECT-TYPE
   SYNTAX      INTEGER
               {
               disabled (0),
               enabled (1)
               }
   MAX-ACCESS  read-write
   STATUS      current
   DESCRIPTION
      "Path: lacpBundle.editConf.pppoEClient.ipV6.icmpMessages.packetTooBig

       Possibilities:
               disabled   (0)
               enabled   (1)"
   ::= {er1646v2LacpBPppOEEntry 705825280}

er1646v2LacpBPppOEIpV6IcmpMessagesHopLimitExceeded OBJECT-TYPE
   SYNTAX      INTEGER
               {
               disabled (0),
               enabled (1)
               }
   MAX-ACCESS  read-write
   STATUS      current
   DESCRIPTION
      "Path: lacpBundle.editConf.pppoEClient.ipV6.icmpMessages.hopLimitExceeded

       Possibilities:
               disabled   (0)
               enabled   (1)"
   ::= {er1646v2LacpBPppOEEntry 705827840}

er1646v2LacpBPppOEIpV6IcmpMessagesFragTimeExceeded OBJECT-TYPE
   SYNTAX      INTEGER
               {
               disabled (0),
               enabled (1)
               }
   MAX-ACCESS  read-write
   STATUS      current
   DESCRIPTION
      "Path: lacpBundle.editConf.pppoEClient.ipV6.icmpMessages.fragTimeExceeded

       Possibilities:
               disabled   (0)
               enabled   (1)"
   ::= {er1646v2LacpBPppOEEntry 705828096}

er1646v2LacpBPppOEIpV6IcmpMessagesHeaderFieldErr OBJECT-TYPE
   SYNTAX      INTEGER
               {
               disabled (0),
               enabled (1)
               }
   MAX-ACCESS  read-write
   STATUS      current
   DESCRIPTION
      "Path: lacpBundle.editConf.pppoEClient.ipV6.icmpMessages.headerFieldErr

       Possibilities:
               disabled   (0)
               enabled   (1)"
   ::= {er1646v2LacpBPppOEEntry 705830400}

er1646v2LacpBPppOEIpV6IcmpMessagesOptionUnrecognized OBJECT-TYPE
   SYNTAX      INTEGER
               {
               disabled (0),
               enabled (1)
               }
   MAX-ACCESS  read-write
   STATUS      current
   DESCRIPTION
      "Path: lacpBundle.editConf.pppoEClient.ipV6.icmpMessages.optionUnrecognized

       Possibilities:
               disabled   (0)
               enabled   (1)"
   ::= {er1646v2LacpBPppOEEntry 705830912}

er1646v2LacpBPppOEIpV6IcmpMessagesRedirect OBJECT-TYPE
   SYNTAX      INTEGER
               {
               disabled (0),
               enabled (1)
               }
   MAX-ACCESS  read-write
   STATUS      current
   DESCRIPTION
      "Path: lacpBundle.editConf.pppoEClient.ipV6.icmpMessages.redirect

       Possibilities:
               disabled   (0)
               enabled   (1)"
   ::= {er1646v2LacpBPppOEEntry 705832960}

er1646v2LacpBPppOEPppLnkMOperation OBJECT-TYPE
   SYNTAX      INTEGER
               {
               disabled (0),
               enabled (1)
               }
   MAX-ACCESS  read-write
   STATUS      current
   DESCRIPTION
      "Path: lacpBundle.editConf.pppoEClient.ppp.linkMonitoring.operation

       Possibilities:
               disabled   (0)
               enabled   (1)"
   ::= {er1646v2LacpBPppOEEntry 251724032}

er1646v2LacpBPppOEPppLnkMInterval OBJECT-TYPE
   SYNTAX      TimeTicks
   MAX-ACCESS  read-write
   STATUS      current
   DESCRIPTION
      "Path: lacpBundle.editConf.pppoEClient.ppp.linkMonitoring.interval

       Time in centi-second."
   ::= {er1646v2LacpBPppOEEntry 251724288}

er1646v2LacpBPppOEPppLnkMRepTimeOut OBJECT-TYPE
   SYNTAX      TimeTicks
   MAX-ACCESS  read-write
   STATUS      current
   DESCRIPTION
      "Path: lacpBundle.editConf.pppoEClient.ppp.linkMonitoring.replyTimeOut

       Time in centi-second."
   ::= {er1646v2LacpBPppOEEntry 251724544}

er1646v2LacpBPppOEPppLnkMFailsPrmt OBJECT-TYPE
   SYNTAX      Integer32
   MAX-ACCESS  read-write
   STATUS      current
   DESCRIPTION
      "Path: lacpBundle.editConf.pppoEClient.ppp.linkMonitoring.failsPermitted"
   ::= {er1646v2LacpBPppOEEntry 251724800}

er1646v2LacpBPppOEPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: lacpBundle.editConf.pppoEClient.ppp.authentication

       Possibilities:
               disabled   (0)
               chap   (1)
               pap   (2)
               chapOrPap   (3)
               msChap   (4)
               msChapV2   (5)"
   ::= {er1646v2LacpBPppOEEntry 251789312}

er1646v2LacpBPppOEPppAuthenPeriod OBJECT-TYPE
   SYNTAX      TimeTicks
   MAX-ACCESS  read-write
   STATUS      current
   DESCRIPTION
      "Path: lacpBundle.editConf.pppoEClient.ppp.authenPeriod

       Time in centi-second."
   ::= {er1646v2LacpBPppOEEntry 251854848}

er1646v2LacpBPppOEPppSessionName OBJECT-TYPE
   SYNTAX      DisplayString
   MAX-ACCESS  read-write
   STATUS      current
   DESCRIPTION
      "Path: lacpBundle.editConf.pppoEClient.ppp.sessionName"
   ::= {er1646v2LacpBPppOEEntry 251985920}

er1646v2LacpBPppOEPppSessionSecret OBJECT-TYPE
   SYNTAX      DisplayString
   MAX-ACCESS  read-write
   STATUS      current
   DESCRIPTION
      "Path: lacpBundle.editConf.pppoEClient.ppp.sessionSecret"
   ::= {er1646v2LacpBPppOEEntry 252051456}

er1646v2LacpBPppOEPppEncModeSessionSecret OBJECT-TYPE
   SYNTAX      INTEGER
               {
               none (1),
               encrypt (2),
               encType1 (3),
               invalid (128)
               }
   MAX-ACCESS  read-write
   STATUS      current
   DESCRIPTION
      "Path: lacpBundle.editConf.pppoEClient.ppp.encModeSessionSecret

       Possibilities:
               none   (1)
               encrypt   (2)
               encType1   (3)
               invalid   (128)"
   ::= {er1646v2LacpBPppOEEntry 252182528}

er1646v2LacpBPppOEPppEncSessionSecret OBJECT-TYPE
   SYNTAX      DisplayString
   MAX-ACCESS  read-write
   STATUS      current
   DESCRIPTION
      "Path: lacpBundle.editConf.pppoEClient.ppp.encSessionSecret"
   ::= {er1646v2LacpBPppOEEntry 252248064}

er1646v2LacpBPppOEPppServiceName OBJECT-TYPE
   SYNTAX      DisplayString
   MAX-ACCESS  read-write
   STATUS      current
   DESCRIPTION
      "Path: lacpBundle.editConf.pppoEClient.ppp.serviceName"
   ::= {er1646v2LacpBPppOEEntry 252116992}

er1646v2LacpBPppOEIpH OBJECT-TYPE
   SYNTAX      SEQUENCE OF Er1646v2LacpBPppOEIpHEntry
   MAX-ACCESS  not-accessible
   STATUS      current
   DESCRIPTION
      ""
   ::= {er1646v2LacpBPppOE 51314688}

er1646v2LacpBPppOEIpHEntry OBJECT-TYPE
   SYNTAX      Er1646v2LacpBPppOEIpHEntry
   MAX-ACCESS  not-accessible
   STATUS      current
   DESCRIPTION
      ""
   INDEX      { er1646v2LacpBPppOEIpHGlobalIx,
                er1646v2LacpBPppOETableIx,
                er1646v2LacpBPppOEIpHTableIx }
   ::= {er1646v2LacpBPppOEIpH 1}

Er1646v2LacpBPppOEIpHEntry ::=
   SEQUENCE
      {
      er1646v2LacpBPppOEIpHActions
         VariableLengthTableActions,
      er1646v2LacpBPppOEIpHGlobalIx
         GlobalIndex,
      er1646v2LacpBPppOEIpHTableIx
         TableIndex,
      er1646v2LacpBPppOEIpHAddress
         IpAddress,
      er1646v2LacpBPppOEIpHDhcpRelayOptionSubscriberId
         DisplayString
      }

er1646v2LacpBPppOEIpHActions OBJECT-TYPE
   SYNTAX      VariableLengthTableActions
   MAX-ACCESS  read-write
   STATUS      current
   DESCRIPTION
      "By way of this field, some manipulations
       on this table may be performed."
   ::= {er1646v2LacpBPppOEIpHEntry 2}

er1646v2LacpBPppOEIpHGlobalIx OBJECT-TYPE
   SYNTAX      GlobalIndex
   MAX-ACCESS  not-accessible
   STATUS      current
   DESCRIPTION
      "The value of the tlsCntTreeGlobalIndex of the MANAGED OBJECT."
   ::= {er1646v2LacpBPppOEIpHEntry 10}

er1646v2LacpBPppOEIpHTableIx OBJECT-TYPE
   SYNTAX      TableIndex
   MAX-ACCESS  not-accessible
   STATUS      current
   DESCRIPTION
      ""
   ::= {er1646v2LacpBPppOEIpHEntry 11}

er1646v2LacpBPppOEIpHAddress OBJECT-TYPE
   SYNTAX      IpAddress
   MAX-ACCESS  read-write
   STATUS      current
   DESCRIPTION
      "Path: lacpBundle.editConf.pppoEClient.ip.helpers.address"
   ::= {er1646v2LacpBPppOEIpHEntry 16777216}

er1646v2LacpBPppOEIpHDhcpRelayOptionSubscriberId OBJECT-TYPE
   SYNTAX      DisplayString
   MAX-ACCESS  read-write
   STATUS      current
   DESCRIPTION
      "Path: lacpBundle.editConf.pppoEClient.ip.helpers.dhcpRelayOption.subscriberId"
   ::= {er1646v2LacpBPppOEIpHEntry 33947648}

er1646v2LacpBPppOEIpV6Addresses OBJECT-TYPE
   SYNTAX      SEQUENCE OF Er1646v2LacpBPppOEIpV6AddressesEntry
   MAX-ACCESS  not-accessible
   STATUS      current
   DESCRIPTION
      ""
   ::= {er1646v2LacpBPppOE 704839680}

er1646v2LacpBPppOEIpV6AddressesEntry OBJECT-TYPE
   SYNTAX      Er1646v2LacpBPppOEIpV6AddressesEntry
   MAX-ACCESS  not-accessible
   STATUS      current
   DESCRIPTION
      ""
   INDEX      { er1646v2LacpBPppOEIpV6AddressesGlobalIx,
                er1646v2LacpBPppOETableIx,
                er1646v2LacpBPppOEIpV6AddressesTableIx }
   ::= {er1646v2LacpBPppOEIpV6Addresses 1}

Er1646v2LacpBPppOEIpV6AddressesEntry ::=
   SEQUENCE
      {
      er1646v2LacpBPppOEIpV6AddressesActions
         VariableLengthTableActions,
      er1646v2LacpBPppOEIpV6AddressesGlobalIx
         GlobalIndex,
      er1646v2LacpBPppOEIpV6AddressesTableIx
         TableIndex,
      er1646v2LacpBPppOEIpV6AddressesType
         INTEGER,
      er1646v2LacpBPppOEIpV6AddressesAddress
         Ipv6Address,
      er1646v2LacpBPppOEIpV6AddressesPrefixLength
         Integer32,
      er1646v2LacpBPppOEIpV6AddressesGeneralPrefix
         DisplayString,
      er1646v2LacpBPppOEIpV6AddressesRaSend
         INTEGER,
      er1646v2LacpBPppOEIpV6AddressesRaOnLinkFlag
         INTEGER,
      er1646v2LacpBPppOEIpV6AddressesRaAutoFlag
         INTEGER,
      er1646v2LacpBPppOEIpV6AddressesRaValidLifeTime
         TimeTicks,
      er1646v2LacpBPppOEIpV6AddressesRaValidLTMode
         INTEGER,
      er1646v2LacpBPppOEIpV6AddressesRaPrefLifeTime
         TimeTicks,
      er1646v2LacpBPppOEIpV6AddressesRaPrefLTMode
         INTEGER
      }

er1646v2LacpBPppOEIpV6AddressesActions OBJECT-TYPE
   SYNTAX      VariableLengthTableActions
   MAX-ACCESS  read-write
   STATUS      current
   DESCRIPTION
      "By way of this field, some manipulations
       on this table may be performed."
   ::= {er1646v2LacpBPppOEIpV6AddressesEntry 2}

er1646v2LacpBPppOEIpV6AddressesGlobalIx OBJECT-TYPE
   SYNTAX      GlobalIndex
   MAX-ACCESS  not-accessible
   STATUS      current
   DESCRIPTION
      "The value of the tlsCntTreeGlobalIndex of the MANAGED OBJECT."
   ::= {er1646v2LacpBPppOEIpV6AddressesEntry 10}

er1646v2LacpBPppOEIpV6AddressesTableIx OBJECT-TYPE
   SYNTAX      TableIndex
   MAX-ACCESS  not-accessible
   STATUS      current
   DESCRIPTION
      ""
   ::= {er1646v2LacpBPppOEIpV6AddressesEntry 11}

er1646v2LacpBPppOEIpV6AddressesType OBJECT-TYPE
   SYNTAX      INTEGER
               {
               unicast (0),
               eui64 (1),
               anycast (2),
               linkLocal (3),
               generalPrefix (4)
               }
   MAX-ACCESS  read-write
   STATUS      current
   DESCRIPTION
      "Path: lacpBundle.editConf.pppoEClient.ipV6.addresses.type

       Possibilities:
               unicast   (0)
               eui64   (1)
               anycast   (2)
               linkLocal   (3)
               generalPrefix   (4)"
   ::= {er1646v2LacpBPppOEIpV6AddressesEntry 50331648}

er1646v2LacpBPppOEIpV6AddressesAddress OBJECT-TYPE
   SYNTAX      Ipv6Address
   MAX-ACCESS  read-write
   STATUS      current
   DESCRIPTION
      "Path: lacpBundle.editConf.pppoEClient.ipV6.addresses.address

       ipv6 address"
   ::= {er1646v2LacpBPppOEIpV6AddressesEntry 16777216}

er1646v2LacpBPppOEIpV6AddressesPrefixLength OBJECT-TYPE
   SYNTAX      Integer32
   MAX-ACCESS  read-write
   STATUS      current
   DESCRIPTION
      "Path: lacpBundle.editConf.pppoEClient.ipV6.addresses.prefixLength"
   ::= {er1646v2LacpBPppOEIpV6AddressesEntry 33554432}

er1646v2LacpBPppOEIpV6AddressesGeneralPrefix OBJECT-TYPE
   SYNTAX      DisplayString
   MAX-ACCESS  read-write
   STATUS      current
   DESCRIPTION
      "Path: lacpBundle.editConf.pppoEClient.ipV6.addresses.generalPrefix"
   ::= {er1646v2LacpBPppOEIpV6AddressesEntry 83886080}

er1646v2LacpBPppOEIpV6AddressesRaSend OBJECT-TYPE
   SYNTAX      INTEGER
               {
               disabled (0),
               enabled (1)
               }
   MAX-ACCESS  read-write
   STATUS      current
   DESCRIPTION
      "Path: lacpBundle.editConf.pppoEClient.ipV6.addresses.ra.send

       Possibilities:
               disabled   (0)
               enabled   (1)"
   ::= {er1646v2LacpBPppOEIpV6AddressesEntry 67174400}

er1646v2LacpBPppOEIpV6AddressesRaOnLinkFlag OBJECT-TYPE
   SYNTAX      INTEGER
               {
               disabled (0),
               enabled (1)
               }
   MAX-ACCESS  read-write
   STATUS      current
   DESCRIPTION
      "Path: lacpBundle.editConf.pppoEClient.ipV6.addresses.ra.onLinkFlag

       Possibilities:
               disabled   (0)
               enabled   (1)"
   ::= {er1646v2LacpBPppOEIpV6AddressesEntry 67371008}

er1646v2LacpBPppOEIpV6AddressesRaAutoFlag OBJECT-TYPE
   SYNTAX      INTEGER
               {
               disabled (0),
               enabled (1)
               }
   MAX-ACCESS  read-write
   STATUS      current
   DESCRIPTION
      "Path: lacpBundle.editConf.pppoEClient.ipV6.addresses.ra.autonomousFlag

       Possibilities:
               disabled   (0)
               enabled   (1)"
   ::= {er1646v2LacpBPppOEIpV6AddressesEntry 67567616}

er1646v2LacpBPppOEIpV6AddressesRaValidLifeTime OBJECT-TYPE
   SYNTAX      TimeTicks
   MAX-ACCESS  read-write
   STATUS      current
   DESCRIPTION
      "Path: lacpBundle.editConf.pppoEClient.ipV6.addresses.ra.validLifeTime

       Time in centi-second."
   ::= {er1646v2LacpBPppOEIpV6AddressesEntry 67239936}

er1646v2LacpBPppOEIpV6AddressesRaValidLTMode OBJECT-TYPE
   SYNTAX      INTEGER
               {
               fixed (0),
               infinite (2)
               }
   MAX-ACCESS  read-write
   STATUS      current
   DESCRIPTION
      "Path: lacpBundle.editConf.pppoEClient.ipV6.addresses.ra.validLifeTimeMode

       Possibilities:
               fixed   (0)
               infinite   (2)"
   ::= {er1646v2LacpBPppOEIpV6AddressesEntry 67305472}

er1646v2LacpBPppOEIpV6AddressesRaPrefLifeTime OBJECT-TYPE
   SYNTAX      TimeTicks
   MAX-ACCESS  read-write
   STATUS      current
   DESCRIPTION
      "Path: lacpBundle.editConf.pppoEClient.ipV6.addresses.ra.prefLifeTime

       Time in centi-second."
   ::= {er1646v2LacpBPppOEIpV6AddressesEntry 67436544}

er1646v2LacpBPppOEIpV6AddressesRaPrefLTMode OBJECT-TYPE
   SYNTAX      INTEGER
               {
               fixed (0),
               infinite (2)
               }
   MAX-ACCESS  read-write
   STATUS      current
   DESCRIPTION
      "Path: lacpBundle.editConf.pppoEClient.ipV6.addresses.ra.prefLifeTimeMode

       Possibilities:
               fixed   (0)
               infinite   (2)"
   ::= {er1646v2LacpBPppOEIpV6AddressesEntry 67502080}

er1646v2LacpBPppOEIpV6RaDnsOptionsRdnssServers OBJECT-TYPE
   SYNTAX      SEQUENCE OF Er1646v2LacpBPppOEIpV6RaDnsOptionsRdnssServersEntry
   MAX-ACCESS  not-accessible
   STATUS      current
   DESCRIPTION
      ""
   ::= {er1646v2LacpBPppOE 705039144}

er1646v2LacpBPppOEIpV6RaDnsOptionsRdnssServersEntry OBJECT-TYPE
   SYNTAX      Er1646v2LacpBPppOEIpV6RaDnsOptionsRdnssServersEntry
   MAX-ACCESS  not-accessible
   STATUS      current
   DESCRIPTION
      ""
   INDEX      { er1646v2LacpBPppOEIpV6RaDnsOptionsRdnssServersGlobalIx,
                er1646v2LacpBPppOETableIx,
                er1646v2LacpBPppOEIpV6RaDnsOptionsRdnssServersTableIx }
   ::= {er1646v2LacpBPppOEIpV6RaDnsOptionsRdnssServers 1}

Er1646v2LacpBPppOEIpV6RaDnsOptionsRdnssServersEntry ::=
   SEQUENCE
      {
      er1646v2LacpBPppOEIpV6RaDnsOptionsRdnssServersActions
         VariableLengthTableActions,
      er1646v2LacpBPppOEIpV6RaDnsOptionsRdnssServersGlobalIx
         GlobalIndex,
      er1646v2LacpBPppOEIpV6RaDnsOptionsRdnssServersTableIx
         TableIndex,
      er1646v2LacpBPppOEIpV6RaDnsOptionsRdnssServersAddress
         Ipv6Address
      }

er1646v2LacpBPppOEIpV6RaDnsOptionsRdnssServersActions OBJECT-TYPE
   SYNTAX      VariableLengthTableActions
   MAX-ACCESS  read-write
   STATUS      current
   DESCRIPTION
      "By way of this field, some manipulations
       on this table may be performed."
   ::= {er1646v2LacpBPppOEIpV6RaDnsOptionsRdnssServersEntry 2}

er1646v2LacpBPppOEIpV6RaDnsOptionsRdnssServersGlobalIx OBJECT-TYPE
   SYNTAX      GlobalIndex
   MAX-ACCESS  not-accessible
   STATUS      current
   DESCRIPTION
      "The value of the tlsCntTreeGlobalIndex of the MANAGED OBJECT."
   ::= {er1646v2LacpBPppOEIpV6RaDnsOptionsRdnssServersEntry 10}

er1646v2LacpBPppOEIpV6RaDnsOptionsRdnssServersTableIx OBJECT-TYPE
   SYNTAX      TableIndex
   MAX-ACCESS  not-accessible
   STATUS      current
   DESCRIPTION
      ""
   ::= {er1646v2LacpBPppOEIpV6RaDnsOptionsRdnssServersEntry 11}

er1646v2LacpBPppOEIpV6RaDnsOptionsRdnssServersAddress OBJECT-TYPE
   SYNTAX      Ipv6Address
   MAX-ACCESS  read-write
   STATUS      current
   DESCRIPTION
      "Path: lacpBundle.editConf.pppoEClient.ipV6.ra.dnsOptions.rdnss.servers.address

       ipv6 address"
   ::= {er1646v2LacpBPppOEIpV6RaDnsOptionsRdnssServersEntry 16777216}

er1646v2LacpBPppOEIpV6RaDnsOptionsDnsslDomains OBJECT-TYPE
   SYNTAX      SEQUENCE OF Er1646v2LacpBPppOEIpV6RaDnsOptionsDnsslDomainsEntry
   MAX-ACCESS  not-accessible
   STATUS      current
   DESCRIPTION
      ""
   ::= {er1646v2LacpBPppOE 705039176}

er1646v2LacpBPppOEIpV6RaDnsOptionsDnsslDomainsEntry OBJECT-TYPE
   SYNTAX      Er1646v2LacpBPppOEIpV6RaDnsOptionsDnsslDomainsEntry
   MAX-ACCESS  not-accessible
   STATUS      current
   DESCRIPTION
      ""
   INDEX      { er1646v2LacpBPppOEIpV6RaDnsOptionsDnsslDomainsGlobalIx,
                er1646v2LacpBPppOETableIx,
                er1646v2LacpBPppOEIpV6RaDnsOptionsDnsslDomainsTableIx }
   ::= {er1646v2LacpBPppOEIpV6RaDnsOptionsDnsslDomains 1}

Er1646v2LacpBPppOEIpV6RaDnsOptionsDnsslDomainsEntry ::=
   SEQUENCE
      {
      er1646v2LacpBPppOEIpV6RaDnsOptionsDnsslDomainsActions
         VariableLengthTableActions,
      er1646v2LacpBPppOEIpV6RaDnsOptionsDnsslDomainsGlobalIx
         GlobalIndex,
      er1646v2LacpBPppOEIpV6RaDnsOptionsDnsslDomainsTableIx
         TableIndex,
      er1646v2LacpBPppOEIpV6RaDnsOptionsDnsslDomainsName
         DisplayString
      }

er1646v2LacpBPppOEIpV6RaDnsOptionsDnsslDomainsActions OBJECT-TYPE
   SYNTAX      VariableLengthTableActions
   MAX-ACCESS  read-write
   STATUS      current
   DESCRIPTION
      "By way of this field, some manipulations
       on this table may be performed."
   ::= {er1646v2LacpBPppOEIpV6RaDnsOptionsDnsslDomainsEntry 2}

er1646v2LacpBPppOEIpV6RaDnsOptionsDnsslDomainsGlobalIx OBJECT-TYPE
   SYNTAX      GlobalIndex
   MAX-ACCESS  not-accessible
   STATUS      current
   DESCRIPTION
      "The value of the tlsCntTreeGlobalIndex of the MANAGED OBJECT."
   ::= {er1646v2LacpBPppOEIpV6RaDnsOptionsDnsslDomainsEntry 10}

er1646v2LacpBPppOEIpV6RaDnsOptionsDnsslDomainsTableIx OBJECT-TYPE
   SYNTAX      TableIndex
   MAX-ACCESS  not-accessible
   STATUS      current
   DESCRIPTION
      ""
   ::= {er1646v2LacpBPppOEIpV6RaDnsOptionsDnsslDomainsEntry 11}

er1646v2LacpBPppOEIpV6RaDnsOptionsDnsslDomainsName OBJECT-TYPE
   SYNTAX      DisplayString
   MAX-ACCESS  read-write
   STATUS      current
   DESCRIPTION
      "Path: lacpBundle.editConf.pppoEClient.ipV6.ra.dnsOptions.dnssl.domains.name"
   ::= {er1646v2LacpBPppOEIpV6RaDnsOptionsDnsslDomainsEntry 16777216}

er1646v2LacpBPppOEIpV6DhcpClientUserClassOpt OBJECT-TYPE
   SYNTAX      SEQUENCE OF Er1646v2LacpBPppOEIpV6DhcpClientUserClassOptEntry
   MAX-ACCESS  not-accessible
   STATUS      current
   DESCRIPTION
      ""
   ::= {er1646v2LacpBPppOE 705312768}

er1646v2LacpBPppOEIpV6DhcpClientUserClassOptEntry OBJECT-TYPE
   SYNTAX      Er1646v2LacpBPppOEIpV6DhcpClientUserClassOptEntry
   MAX-ACCESS  not-accessible
   STATUS      current
   DESCRIPTION
      ""
   INDEX      { er1646v2LacpBPppOEIpV6DhcpClientUserClassOptGlobalIx,
                er1646v2LacpBPppOETableIx,
                er1646v2LacpBPppOEIpV6DhcpClientUserClassOptTableIx }
   ::= {er1646v2LacpBPppOEIpV6DhcpClientUserClassOpt 1}

Er1646v2LacpBPppOEIpV6DhcpClientUserClassOptEntry ::=
   SEQUENCE
      {
      er1646v2LacpBPppOEIpV6DhcpClientUserClassOptActions
         VariableLengthTableActions,
      er1646v2LacpBPppOEIpV6DhcpClientUserClassOptGlobalIx
         GlobalIndex,
      er1646v2LacpBPppOEIpV6DhcpClientUserClassOptTableIx
         TableIndex,
      er1646v2LacpBPppOEIpV6DhcpClientUserClassOptValueAscii
         DisplayString,
      er1646v2LacpBPppOEIpV6DhcpClientUserClassOptValueDecimal
         Integer32,
      er1646v2LacpBPppOEIpV6DhcpClientUserClassOptValueHexData
         OCTET STRING
      }

er1646v2LacpBPppOEIpV6DhcpClientUserClassOptActions OBJECT-TYPE
   SYNTAX      VariableLengthTableActions
   MAX-ACCESS  read-write
   STATUS      current
   DESCRIPTION
      "By way of this field, some manipulations
       on this table may be performed."
   ::= {er1646v2LacpBPppOEIpV6DhcpClientUserClassOptEntry 2}

er1646v2LacpBPppOEIpV6DhcpClientUserClassOptGlobalIx OBJECT-TYPE
   SYNTAX      GlobalIndex
   MAX-ACCESS  not-accessible
   STATUS      current
   DESCRIPTION
      "The value of the tlsCntTreeGlobalIndex of the MANAGED OBJECT."
   ::= {er1646v2LacpBPppOEIpV6DhcpClientUserClassOptEntry 10}

er1646v2LacpBPppOEIpV6DhcpClientUserClassOptTableIx OBJECT-TYPE
   SYNTAX      TableIndex
   MAX-ACCESS  not-accessible
   STATUS      current
   DESCRIPTION
      ""
   ::= {er1646v2LacpBPppOEIpV6DhcpClientUserClassOptEntry 11}

er1646v2LacpBPppOEIpV6DhcpClientUserClassOptValueAscii OBJECT-TYPE
   SYNTAX      DisplayString
   MAX-ACCESS  read-write
   STATUS      current
   DESCRIPTION
      "Path: lacpBundle.editConf.pppoEClient.ipV6.dhcp.client.userClassOpt.value.ascii"
   ::= {er1646v2LacpBPppOEIpV6DhcpClientUserClassOptEntry 16842752}

er1646v2LacpBPppOEIpV6DhcpClientUserClassOptValueDecimal OBJECT-TYPE
   SYNTAX      Integer32
   MAX-ACCESS  read-write
   STATUS      current
   DESCRIPTION
      "Path: lacpBundle.editConf.pppoEClient.ipV6.dhcp.client.userClassOpt.value.decimal"
   ::= {er1646v2LacpBPppOEIpV6DhcpClientUserClassOptEntry 16908288}

er1646v2LacpBPppOEIpV6DhcpClientUserClassOptValueHexData OBJECT-TYPE
   SYNTAX      OCTET STRING
   MAX-ACCESS  read-write
   STATUS      current
   DESCRIPTION
      "Path: lacpBundle.editConf.pppoEClient.ipV6.dhcp.client.userClassOpt.value.hexData"
   ::= {er1646v2LacpBPppOEIpV6DhcpClientUserClassOptEntry 16973824}

er1646v2LacpBPppOEIpV6DhcpClientVendorCl OBJECT-TYPE
   SYNTAX      SEQUENCE OF Er1646v2LacpBPppOEIpV6DhcpClientVendorClEntry
   MAX-ACCESS  not-accessible
   STATUS      current
   DESCRIPTION
      ""
   ::= {er1646v2LacpBPppOE 705313792}

er1646v2LacpBPppOEIpV6DhcpClientVendorClEntry OBJECT-TYPE
   SYNTAX      Er1646v2LacpBPppOEIpV6DhcpClientVendorClEntry
   MAX-ACCESS  not-accessible
   STATUS      current
   DESCRIPTION
      ""
   INDEX      { er1646v2LacpBPppOEIpV6DhcpClientVendorClGlobalIx,
                er1646v2LacpBPppOETableIx,
                er1646v2LacpBPppOEIpV6DhcpClientVendorClTableIx }
   ::= {er1646v2LacpBPppOEIpV6DhcpClientVendorCl 1}

Er1646v2LacpBPppOEIpV6DhcpClientVendorClEntry ::=
   SEQUENCE
      {
      er1646v2LacpBPppOEIpV6DhcpClientVendorClActions
         VariableLengthTableActions,
      er1646v2LacpBPppOEIpV6DhcpClientVendorClGlobalIx
         GlobalIndex,
      er1646v2LacpBPppOEIpV6DhcpClientVendorClTableIx
         TableIndex,
      er1646v2LacpBPppOEIpV6DhcpClientVendorClValueAscii
         DisplayString,
      er1646v2LacpBPppOEIpV6DhcpClientVendorClValueDecimal
         Integer32,
      er1646v2LacpBPppOEIpV6DhcpClientVendorClValueHexData
         OCTET STRING
      }

er1646v2LacpBPppOEIpV6DhcpClientVendorClActions OBJECT-TYPE
   SYNTAX      VariableLengthTableActions
   MAX-ACCESS  read-write
   STATUS      current
   DESCRIPTION
      "By way of this field, some manipulations
       on this table may be performed."
   ::= {er1646v2LacpBPppOEIpV6DhcpClientVendorClEntry 2}

er1646v2LacpBPppOEIpV6DhcpClientVendorClGlobalIx OBJECT-TYPE
   SYNTAX      GlobalIndex
   MAX-ACCESS  not-accessible
   STATUS      current
   DESCRIPTION
      "The value of the tlsCntTreeGlobalIndex of the MANAGED OBJECT."
   ::= {er1646v2LacpBPppOEIpV6DhcpClientVendorClEntry 10}

er1646v2LacpBPppOEIpV6DhcpClientVendorClTableIx OBJECT-TYPE
   SYNTAX      TableIndex
   MAX-ACCESS  not-accessible
   STATUS      current
   DESCRIPTION
      ""
   ::= {er1646v2LacpBPppOEIpV6DhcpClientVendorClEntry 11}

er1646v2LacpBPppOEIpV6DhcpClientVendorClValueAscii OBJECT-TYPE
   SYNTAX      DisplayString
   MAX-ACCESS  read-write
   STATUS      current
   DESCRIPTION
      "Path: lacpBundle.editConf.pppoEClient.ipV6.dhcp.client.vendorClassOpt.value.ascii"
   ::= {er1646v2LacpBPppOEIpV6DhcpClientVendorClEntry 16842752}

er1646v2LacpBPppOEIpV6DhcpClientVendorClValueDecimal OBJECT-TYPE
   SYNTAX      Integer32
   MAX-ACCESS  read-write
   STATUS      current
   DESCRIPTION
      "Path: lacpBundle.editConf.pppoEClient.ipV6.dhcp.client.vendorClassOpt.value.decimal"
   ::= {er1646v2LacpBPppOEIpV6DhcpClientVendorClEntry 16908288}

er1646v2LacpBPppOEIpV6DhcpClientVendorClValueHexData OBJECT-TYPE
   SYNTAX      OCTET STRING
   MAX-ACCESS  read-write
   STATUS      current
   DESCRIPTION
      "Path: lacpBundle.editConf.pppoEClient.ipV6.dhcp.client.vendorClassOpt.value.hexData"
   ::= {er1646v2LacpBPppOEIpV6DhcpClientVendorClEntry 16973824}

er1646v2LacpBPppOEIpV6DhcpRelayDestinations OBJECT-TYPE
   SYNTAX      SEQUENCE OF Er1646v2LacpBPppOEIpV6DhcpRelayDestinationsEntry
   MAX-ACCESS  not-accessible
   STATUS      current
   DESCRIPTION
      ""
   ::= {er1646v2LacpBPppOE 705323072}

er1646v2LacpBPppOEIpV6DhcpRelayDestinationsEntry OBJECT-TYPE
   SYNTAX      Er1646v2LacpBPppOEIpV6DhcpRelayDestinationsEntry
   MAX-ACCESS  not-accessible
   STATUS      current
   DESCRIPTION
      ""
   INDEX      { er1646v2LacpBPppOEIpV6DhcpRelayDestinationsGlobalIx,
                er1646v2LacpBPppOETableIx,
                er1646v2LacpBPppOEIpV6DhcpRelayDestinationsTableIx }
   ::= {er1646v2LacpBPppOEIpV6DhcpRelayDestinations 1}

Er1646v2LacpBPppOEIpV6DhcpRelayDestinationsEntry ::=
   SEQUENCE
      {
      er1646v2LacpBPppOEIpV6DhcpRelayDestinationsActions
         VariableLengthTableActions,
      er1646v2LacpBPppOEIpV6DhcpRelayDestinationsGlobalIx
         GlobalIndex,
      er1646v2LacpBPppOEIpV6DhcpRelayDestinationsTableIx
         TableIndex,
      er1646v2LacpBPppOEIpV6DhcpRelayDestinationsAddress
         Ipv6Address,
      er1646v2LacpBPppOEIpV6DhcpRelayDestinationsInterface
         DisplayString
      }

er1646v2LacpBPppOEIpV6DhcpRelayDestinationsActions OBJECT-TYPE
   SYNTAX      VariableLengthTableActions
   MAX-ACCESS  read-write
   STATUS      current
   DESCRIPTION
      "By way of this field, some manipulations
       on this table may be performed."
   ::= {er1646v2LacpBPppOEIpV6DhcpRelayDestinationsEntry 2}

er1646v2LacpBPppOEIpV6DhcpRelayDestinationsGlobalIx OBJECT-TYPE
   SYNTAX      GlobalIndex
   MAX-ACCESS  not-accessible
   STATUS      current
   DESCRIPTION
      "The value of the tlsCntTreeGlobalIndex of the MANAGED OBJECT."
   ::= {er1646v2LacpBPppOEIpV6DhcpRelayDestinationsEntry 10}

er1646v2LacpBPppOEIpV6DhcpRelayDestinationsTableIx OBJECT-TYPE
   SYNTAX      TableIndex
   MAX-ACCESS  not-accessible
   STATUS      current
   DESCRIPTION
      ""
   ::= {er1646v2LacpBPppOEIpV6DhcpRelayDestinationsEntry 11}

er1646v2LacpBPppOEIpV6DhcpRelayDestinationsAddress OBJECT-TYPE
   SYNTAX      Ipv6Address
   MAX-ACCESS  read-write
   STATUS      current
   DESCRIPTION
      "Path: lacpBundle.editConf.pppoEClient.ipV6.dhcp.relay.destinations.address

       ipv6 address"
   ::= {er1646v2LacpBPppOEIpV6DhcpRelayDestinationsEntry 16777216}

er1646v2LacpBPppOEIpV6DhcpRelayDestinationsInterface OBJECT-TYPE
   SYNTAX      DisplayString
   MAX-ACCESS  read-write
   STATUS      current
   DESCRIPTION
      "Path: lacpBundle.editConf.pppoEClient.ipV6.dhcp.relay.destinations.interface"
   ::= {er1646v2LacpBPppOEIpV6DhcpRelayDestinationsEntry 33554432}


er1646v2LacpBDot1x OBJECT IDENTIFIER ::= {er1646v2LacpB 191}

er1646v2LacpBDot1xSSCTable OBJECT-TYPE
   SYNTAX      SEQUENCE OF Er1646v2LacpBDot1xEntry
   MAX-ACCESS  not-accessible
   STATUS      current
   DESCRIPTION
      "ppp server name on interface"
   ::= {er1646v2LacpBDot1x 1}

er1646v2LacpBDot1xEntry OBJECT-TYPE
   SYNTAX      Er1646v2LacpBDot1xEntry
   MAX-ACCESS  not-accessible
   STATUS      current
   DESCRIPTION
      ""
   INDEX      { er1646v2LacpBDot1xGlobalIx }
   ::= {er1646v2LacpBDot1xSSCTable 1}

Er1646v2LacpBDot1xEntry ::=
   SEQUENCE
      {
      er1646v2LacpBDot1xGlobalIx
         GlobalIndex,
      er1646v2LacpBDot1xMode
         INTEGER,
      er1646v2LacpBDot1xMaxHosts
         Integer32,
      er1646v2LacpBDot1xReAuthentication
         INTEGER,
      er1646v2LacpBDot1xReAuthPeriod
         TimeTicks,
      er1646v2LacpBDot1xQuietPeriod
         TimeTicks,
      er1646v2LacpBDot1xSupplTimeout
         TimeTicks,
      er1646v2LacpBDot1xServerTimeout
         TimeTicks,
      er1646v2LacpBDot1xMaxReqCount
         Integer32
      }

er1646v2LacpBDot1xGlobalIx OBJECT-TYPE
   SYNTAX      GlobalIndex
   MAX-ACCESS  not-accessible
   STATUS      current
   DESCRIPTION
      "The value of the tlsCntTreeGlobalIndex of the MANAGED OBJECT."
   ::= {er1646v2LacpBDot1xEntry 10}

er1646v2LacpBDot1xMode OBJECT-TYPE
   SYNTAX      INTEGER
               {
               inactive (0),
               auto (1)
               }
   MAX-ACCESS  read-write
   STATUS      current
   DESCRIPTION
      "Path: lacpBundle.editConf.dot1x.mode

       Possibilities:
               inactive   (0)
               auto   (1)"
   ::= {er1646v2LacpBDot1xEntry 16777216}

er1646v2LacpBDot1xMaxHosts OBJECT-TYPE
   SYNTAX      Integer32
   MAX-ACCESS  read-write
   STATUS      current
   DESCRIPTION
      "Path: lacpBundle.editConf.dot1x.maxHosts"
   ::= {er1646v2LacpBDot1xEntry 33554432}

er1646v2LacpBDot1xReAuthentication OBJECT-TYPE
   SYNTAX      INTEGER
               {
               disabled (0),
               enabled (1)
               }
   MAX-ACCESS  read-write
   STATUS      current
   DESCRIPTION
      "Path: lacpBundle.editConf.dot1x.reAuthentication

       Possibilities:
               disabled   (0)
               enabled   (1)"
   ::= {er1646v2LacpBDot1xEntry 50331648}

er1646v2LacpBDot1xReAuthPeriod OBJECT-TYPE
   SYNTAX      TimeTicks
   MAX-ACCESS  read-write
   STATUS      current
   DESCRIPTION
      "Path: lacpBundle.editConf.dot1x.reAuthPeriod

       Time in centi-second."
   ::= {er1646v2LacpBDot1xEntry 67108864}

er1646v2LacpBDot1xQuietPeriod OBJECT-TYPE
   SYNTAX      TimeTicks
   MAX-ACCESS  read-write
   STATUS      current
   DESCRIPTION
      "Path: lacpBundle.editConf.dot1x.quietPeriod

       Time in centi-second."
   ::= {er1646v2LacpBDot1xEntry 83886080}

er1646v2LacpBDot1xSupplTimeout OBJECT-TYPE
   SYNTAX      TimeTicks
   MAX-ACCESS  read-write
   STATUS      current
   DESCRIPTION
      "Path: lacpBundle.editConf.dot1x.supplTimeout

       Time in centi-second."
   ::= {er1646v2LacpBDot1xEntry 100663296}

er1646v2LacpBDot1xServerTimeout OBJECT-TYPE
   SYNTAX      TimeTicks
   MAX-ACCESS  read-write
   STATUS      current
   DESCRIPTION
      "Path: lacpBundle.editConf.dot1x.serverTimeout

       Time in centi-second."
   ::= {er1646v2LacpBDot1xEntry 117440512}

er1646v2LacpBDot1xMaxReqCount OBJECT-TYPE
   SYNTAX      Integer32
   MAX-ACCESS  read-write
   STATUS      current
   DESCRIPTION
      "Path: lacpBundle.editConf.dot1x.maxReqCount"
   ::= {er1646v2LacpBDot1xEntry 134217728}


er1646v2LacpBMode OBJECT IDENTIFIER ::= {er1646v2LacpB 29}

er1646v2LacpBModeTable OBJECT-TYPE
   SYNTAX      SEQUENCE OF Er1646v2LacpBModeEntry
   MAX-ACCESS  not-accessible
   STATUS      current
   DESCRIPTION
      "routing and/or bridging or ipV6 selection"
   ::= {er1646v2LacpBMode 1}

er1646v2LacpBModeEntry OBJECT-TYPE
   SYNTAX      Er1646v2LacpBModeEntry
   MAX-ACCESS  not-accessible
   STATUS      current
   DESCRIPTION
      ""
   INDEX      { er1646v2LacpBModeGlobalIx }
   ::= {er1646v2LacpBModeTable 1}

Er1646v2LacpBModeEntry ::=
   SEQUENCE
      {
      er1646v2LacpBModeGlobalIx
         GlobalIndex,
      er1646v2LacpBModeValue
         INTEGER
      }

er1646v2LacpBModeGlobalIx OBJECT-TYPE
   SYNTAX      GlobalIndex
   MAX-ACCESS  not-accessible
   STATUS      current
   DESCRIPTION
      "The value of the tlsCntTreeGlobalIndex of the MANAGED OBJECT."
   ::= {er1646v2LacpBModeEntry 10}

er1646v2LacpBModeValue OBJECT-TYPE
   SYNTAX      INTEGER
               {
               bridging (0),
               routing (1),
               routingAndBridging (2),
               ipV6 (3),
               ipV6ipV4 (4)
               }
   MAX-ACCESS  read-write
   STATUS      current
   DESCRIPTION
      "Path: lacpBundle.editConf.mode

       Possibilities:
               bridging   (0)
               routing   (1)
               routingAndBridging   (2)
               ipV6   (3)
               ipV6/ipV4   (4)"
   ::= {er1646v2LacpBModeEntry 2147483648}


er1646v2LacpBIpV6 OBJECT IDENTIFIER ::= {er1646v2LacpB 15}

er1646v2LacpBIpV6SSCTable OBJECT-TYPE
   SYNTAX      SEQUENCE OF Er1646v2LacpBIpV6Entry
   MAX-ACCESS  not-accessible
   STATUS      current
   DESCRIPTION
      "IPv6 interface config parameters"
   ::= {er1646v2LacpBIpV6 1}

er1646v2LacpBIpV6Entry OBJECT-TYPE
   SYNTAX      Er1646v2LacpBIpV6Entry
   MAX-ACCESS  not-accessible
   STATUS      current
   DESCRIPTION
      ""
   INDEX      { er1646v2LacpBIpV6GlobalIx }
   ::= {er1646v2LacpBIpV6SSCTable 1}

Er1646v2LacpBIpV6Entry ::=
   SEQUENCE
      {
      er1646v2LacpBIpV6GlobalIx
         GlobalIndex,
      er1646v2LacpBIpV6VrfRouter
         DisplayString,
      er1646v2LacpBIpV6AddrAutoConfigNrDupAddrDetects
         Integer32,
      er1646v2LacpBIpV6AddrAutoConfigAcceptRa
         INTEGER,
      er1646v2LacpBIpV6AddrAutoConfigAcceptRaRdnss
         INTEGER,
      er1646v2LacpBIpV6AddrAutoConfigAcceptRaDnssl
         INTEGER,
      er1646v2LacpBIpV6DefaultRoute
         INTEGER,
      er1646v2LacpBIpV6RaSend
         INTEGER,
      er1646v2LacpBIpV6RaMinInterval
         TimeTicks,
      er1646v2LacpBIpV6RaMaxInterval
         TimeTicks,
      er1646v2LacpBIpV6RaManagedFlag
         INTEGER,
      er1646v2LacpBIpV6RaOtherConfFlag
         INTEGER,
      er1646v2LacpBIpV6RaLinkMtu
         Integer32,
      er1646v2LacpBIpV6RaReachableTime
         TimeTicks,
      er1646v2LacpBIpV6RaRetransmitTime
         TimeTicks,
      er1646v2LacpBIpV6RaHopLimit
         Integer32,
      er1646v2LacpBIpV6RaDefaultLifeTime
         TimeTicks,
      er1646v2LacpBIpV6RaDnsOptionsRdnssLifeTime
         TimeTicks,
      er1646v2LacpBIpV6RaDnsOptionsRdnssImportServers
         INTEGER,
      er1646v2LacpBIpV6RaDnsOptionsDnsslLifeTime
         TimeTicks,
      er1646v2LacpBIpV6RaDnsOptionsDnsslImportDomains
         INTEGER,
      er1646v2LacpBIpV6RsSend
         INTEGER,
      er1646v2LacpBIpV6RsMaxRandomDelay
         TimeTicks,
      er1646v2LacpBIpV6RsInterval
         TimeTicks,
      er1646v2LacpBIpV6RsMaxSolicitations
         Integer32,
      er1646v2LacpBIpV6TrafficPolicyInbound
         DisplayString,
      er1646v2LacpBIpV6TrafficPolicyOutbound
         DisplayString,
      er1646v2LacpBIpV6FirewallZone
         DisplayString,
      er1646v2LacpBIpV6DhcpClientAddrAC
         INTEGER,
      er1646v2LacpBIpV6DhcpClientPrDelMode
         INTEGER,
      er1646v2LacpBIpV6DhcpClientPrDelPool
         DisplayString,
      er1646v2LacpBIpV6DhcpClientPrDelPdExclOpt
         INTEGER,
      er1646v2LacpBIpV6DhcpClientDnsServerPref
         Integer32,
      er1646v2LacpBIpV6DhcpClientRapidCommit
         INTEGER,
      er1646v2LacpBIpV6DhcpClientTimersSolTimeOut
         TimeTicks,
      er1646v2LacpBIpV6DhcpClientTimersSolMaxRt
         TimeTicks,
      er1646v2LacpBIpV6DhcpClientTimersInfoRefresh
         TimeTicks,
      er1646v2LacpBIpV6DhcpServerMode
         INTEGER,
      er1646v2LacpBIpV6DhcpServerPreference
         Integer32,
      er1646v2LacpBIpV6DhcpServerPool
         DisplayString,
      er1646v2LacpBIpV6DhcpServerRapidCommit
         INTEGER,
      er1646v2LacpBIpV6DhcpServerTimersInfoRefresh
         TimeTicks,
      er1646v2LacpBIpV6DhcpRelayMode
         INTEGER,
      er1646v2LacpBIpV6SendRedirect
         INTEGER,
      er1646v2LacpBIpV6LinkMtu
         Integer32,
      er1646v2LacpBIpV6InterfaceId
         OCTET STRING,
      er1646v2LacpBIpV6MF
         Integer32,
      er1646v2LacpBIpV6IcmpMessagesNoRoute
         INTEGER,
      er1646v2LacpBIpV6IcmpMessagesBeyondScope
         INTEGER,
      er1646v2LacpBIpV6IcmpMessagesAddressUnreachable
         INTEGER,
      er1646v2LacpBIpV6IcmpMessagesPortUnreachable
         INTEGER,
      er1646v2LacpBIpV6IcmpMessagesPacketTooBig
         INTEGER,
      er1646v2LacpBIpV6IcmpMessagesHopLimitExceeded
         INTEGER,
      er1646v2LacpBIpV6IcmpMessagesFragTimeExceeded
         INTEGER,
      er1646v2LacpBIpV6IcmpMessagesHeaderFieldErr
         INTEGER,
      er1646v2LacpBIpV6IcmpMessagesOptionUnrecognized
         INTEGER,
      er1646v2LacpBIpV6IcmpMessagesRedirect
         INTEGER
      }

er1646v2LacpBIpV6GlobalIx OBJECT-TYPE
   SYNTAX      GlobalIndex
   MAX-ACCESS  not-accessible
   STATUS      current
   DESCRIPTION
      "The value of the tlsCntTreeGlobalIndex of the MANAGED OBJECT."
   ::= {er1646v2LacpBIpV6Entry 10}

er1646v2LacpBIpV6VrfRouter OBJECT-TYPE
   SYNTAX      DisplayString
   MAX-ACCESS  read-write
   STATUS      current
   DESCRIPTION
      "Path: lacpBundle.editConf.ipV6.vrfRouter"
   ::= {er1646v2LacpBIpV6Entry 16777216}

er1646v2LacpBIpV6AddrAutoConfigNrDupAddrDetects OBJECT-TYPE
   SYNTAX      Integer32
   MAX-ACCESS  read-write
   STATUS      current
   DESCRIPTION
      "Path: lacpBundle.editConf.ipV6.addrAutoConfig.nrDupAddrDetects"
   ::= {er1646v2LacpBIpV6Entry 67174400}

er1646v2LacpBIpV6AddrAutoConfigAcceptRa OBJECT-TYPE
   SYNTAX      INTEGER
               {
               disabled (0),
               enabled (1)
               }
   MAX-ACCESS  read-write
   STATUS      current
   DESCRIPTION
      "Path: lacpBundle.editConf.ipV6.addrAutoConfig.acceptRa

       Possibilities:
               disabled   (0)
               enabled   (1)"
   ::= {er1646v2LacpBIpV6Entry 67239936}

er1646v2LacpBIpV6AddrAutoConfigAcceptRaRdnss OBJECT-TYPE
   SYNTAX      INTEGER
               {
               disabled (0),
               enabled (1)
               }
   MAX-ACCESS  read-write
   STATUS      current
   DESCRIPTION
      "Path: lacpBundle.editConf.ipV6.addrAutoConfig.acceptRaRdnss

       Possibilities:
               disabled   (0)
               enabled   (1)"
   ::= {er1646v2LacpBIpV6Entry 67305472}

er1646v2LacpBIpV6AddrAutoConfigAcceptRaDnssl OBJECT-TYPE
   SYNTAX      INTEGER
               {
               disabled (0),
               enabled (1)
               }
   MAX-ACCESS  read-write
   STATUS      current
   DESCRIPTION
      "Path: lacpBundle.editConf.ipV6.addrAutoConfig.acceptRaDnssl

       Possibilities:
               disabled   (0)
               enabled   (1)"
   ::= {er1646v2LacpBIpV6Entry 67371008}

er1646v2LacpBIpV6DefaultRoute OBJECT-TYPE
   SYNTAX      INTEGER
               {
               disabled (0),
               enabled (1)
               }
   MAX-ACCESS  read-write
   STATUS      current
   DESCRIPTION
      "Path: lacpBundle.editConf.ipV6.defaultRoute

       Possibilities:
               disabled   (0)
               enabled   (1)"
   ::= {er1646v2LacpBIpV6Entry 83886080}

er1646v2LacpBIpV6RaSend OBJECT-TYPE
   SYNTAX      INTEGER
               {
               disabled (0),
               enabled (1)
               }
   MAX-ACCESS  read-write
   STATUS      current
   DESCRIPTION
      "Path: lacpBundle.editConf.ipV6.ra.send

       Possibilities:
               disabled   (0)
               enabled   (1)"
   ::= {er1646v2LacpBIpV6Entry 100728832}

er1646v2LacpBIpV6RaMinInterval OBJECT-TYPE
   SYNTAX      TimeTicks
   MAX-ACCESS  read-write
   STATUS      current
   DESCRIPTION
      "Path: lacpBundle.editConf.ipV6.ra.minInterval

       Time in centi-second."
   ::= {er1646v2LacpBIpV6Entry 100794368}

er1646v2LacpBIpV6RaMaxInterval OBJECT-TYPE
   SYNTAX      TimeTicks
   MAX-ACCESS  read-write
   STATUS      current
   DESCRIPTION
      "Path: lacpBundle.editConf.ipV6.ra.maxInterval

       Time in centi-second."
   ::= {er1646v2LacpBIpV6Entry 100859904}

er1646v2LacpBIpV6RaManagedFlag OBJECT-TYPE
   SYNTAX      INTEGER
               {
               disabled (0),
               enabled (1)
               }
   MAX-ACCESS  read-write
   STATUS      current
   DESCRIPTION
      "Path: lacpBundle.editConf.ipV6.ra.managedFlag

       Possibilities:
               disabled   (0)
               enabled   (1)"
   ::= {er1646v2LacpBIpV6Entry 100925440}

er1646v2LacpBIpV6RaOtherConfFlag OBJECT-TYPE
   SYNTAX      INTEGER
               {
               disabled (0),
               enabled (1)
               }
   MAX-ACCESS  read-write
   STATUS      current
   DESCRIPTION
      "Path: lacpBundle.editConf.ipV6.ra.otherConfFlag

       Possibilities:
               disabled   (0)
               enabled   (1)"
   ::= {er1646v2LacpBIpV6Entry 100990976}

er1646v2LacpBIpV6RaLinkMtu OBJECT-TYPE
   SYNTAX      Integer32
   MAX-ACCESS  read-write
   STATUS      current
   DESCRIPTION
      "Path: lacpBundle.editConf.ipV6.ra.linkMtu"
   ::= {er1646v2LacpBIpV6Entry 101056512}

er1646v2LacpBIpV6RaReachableTime OBJECT-TYPE
   SYNTAX      TimeTicks
   MAX-ACCESS  read-write
   STATUS      current
   DESCRIPTION
      "Path: lacpBundle.editConf.ipV6.ra.reachableTime

       Time in centi-second."
   ::= {er1646v2LacpBIpV6Entry 101122048}

er1646v2LacpBIpV6RaRetransmitTime OBJECT-TYPE
   SYNTAX      TimeTicks
   MAX-ACCESS  read-write
   STATUS      current
   DESCRIPTION
      "Path: lacpBundle.editConf.ipV6.ra.retransmitTime

       Time in centi-second."
   ::= {er1646v2LacpBIpV6Entry 101187584}

er1646v2LacpBIpV6RaHopLimit OBJECT-TYPE
   SYNTAX      Integer32
   MAX-ACCESS  read-write
   STATUS      current
   DESCRIPTION
      "Path: lacpBundle.editConf.ipV6.ra.hopLimit"
   ::= {er1646v2LacpBIpV6Entry 101253120}

er1646v2LacpBIpV6RaDefaultLifeTime OBJECT-TYPE
   SYNTAX      TimeTicks
   MAX-ACCESS  read-write
   STATUS      current
   DESCRIPTION
      "Path: lacpBundle.editConf.ipV6.ra.defaultLifeTime

       Time in centi-second."
   ::= {er1646v2LacpBIpV6Entry 101318656}

er1646v2LacpBIpV6RaDnsOptionsRdnssLifeTime OBJECT-TYPE
   SYNTAX      TimeTicks
   MAX-ACCESS  read-write
   STATUS      current
   DESCRIPTION
      "Path: lacpBundle.editConf.ipV6.ra.dnsOptions.rdnss.lifeTime

       Time in centi-second."
   ::= {er1646v2LacpBIpV6Entry 101393408}

er1646v2LacpBIpV6RaDnsOptionsRdnssImportServers OBJECT-TYPE
   SYNTAX      INTEGER
               {
               disabled (0),
               enabled (1)
               }
   MAX-ACCESS  read-write
   STATUS      current
   DESCRIPTION
      "Path: lacpBundle.editConf.ipV6.ra.dnsOptions.rdnss.importServers

       Possibilities:
               disabled   (0)
               enabled   (1)"
   ::= {er1646v2LacpBIpV6Entry 101395456}

er1646v2LacpBIpV6RaDnsOptionsDnsslLifeTime OBJECT-TYPE
   SYNTAX      TimeTicks
   MAX-ACCESS  read-write
   STATUS      current
   DESCRIPTION
      "Path: lacpBundle.editConf.ipV6.ra.dnsOptions.dnssl.lifeTime

       Time in centi-second."
   ::= {er1646v2LacpBIpV6Entry 101401600}

er1646v2LacpBIpV6RaDnsOptionsDnsslImportDomains OBJECT-TYPE
   SYNTAX      INTEGER
               {
               disabled (0),
               enabled (1)
               }
   MAX-ACCESS  read-write
   STATUS      current
   DESCRIPTION
      "Path: lacpBundle.editConf.ipV6.ra.dnsOptions.dnssl.importDomains

       Possibilities:
               disabled   (0)
               enabled   (1)"
   ::= {er1646v2LacpBIpV6Entry 101403648}

er1646v2LacpBIpV6RsSend OBJECT-TYPE
   SYNTAX      INTEGER
               {
               disabled (0),
               enabled (1)
               }
   MAX-ACCESS  read-write
   STATUS      current
   DESCRIPTION
      "Path: lacpBundle.editConf.ipV6.rs.send

       Possibilities:
               disabled   (0)
               enabled   (1)"
   ::= {er1646v2LacpBIpV6Entry 335609856}

er1646v2LacpBIpV6RsMaxRandomDelay OBJECT-TYPE
   SYNTAX      TimeTicks
   MAX-ACCESS  read-write
   STATUS      current
   DESCRIPTION
      "Path: lacpBundle.editConf.ipV6.rs.maxRandomDelay

       Time in centi-second."
   ::= {er1646v2LacpBIpV6Entry 335675392}

er1646v2LacpBIpV6RsInterval OBJECT-TYPE
   SYNTAX      TimeTicks
   MAX-ACCESS  read-write
   STATUS      current
   DESCRIPTION
      "Path: lacpBundle.editConf.ipV6.rs.interval

       Time in centi-second."
   ::= {er1646v2LacpBIpV6Entry 335740928}

er1646v2LacpBIpV6RsMaxSolicitations OBJECT-TYPE
   SYNTAX      Integer32
   MAX-ACCESS  read-write
   STATUS      current
   DESCRIPTION
      "Path: lacpBundle.editConf.ipV6.rs.maxSolicitations"
   ::= {er1646v2LacpBIpV6Entry 335806464}

er1646v2LacpBIpV6TrafficPolicyInbound OBJECT-TYPE
   SYNTAX      DisplayString
   MAX-ACCESS  read-write
   STATUS      current
   DESCRIPTION
      "Path: lacpBundle.editConf.ipV6.trafficPolicy.inbound"
   ::= {er1646v2LacpBIpV6Entry 184614912}

er1646v2LacpBIpV6TrafficPolicyOutbound OBJECT-TYPE
   SYNTAX      DisplayString
   MAX-ACCESS  read-write
   STATUS      current
   DESCRIPTION
      "Path: lacpBundle.editConf.ipV6.trafficPolicy.outbound"
   ::= {er1646v2LacpBIpV6Entry 184680448}

er1646v2LacpBIpV6FirewallZone OBJECT-TYPE
   SYNTAX      DisplayString
   MAX-ACCESS  read-write
   STATUS      current
   DESCRIPTION
      "Path: lacpBundle.editConf.ipV6.firewall.zone"
   ::= {er1646v2LacpBIpV6Entry 201392128}

er1646v2LacpBIpV6DhcpClientAddrAC OBJECT-TYPE
   SYNTAX      INTEGER
               {
               disabled (0),
               enabled (1)
               }
   MAX-ACCESS  read-write
   STATUS      current
   DESCRIPTION
      "Path: lacpBundle.editConf.ipV6.dhcp.client.addrAutoConfig

       Possibilities:
               disabled   (0)
               enabled   (1)"
   ::= {er1646v2LacpBIpV6Entry 170131456}

er1646v2LacpBIpV6DhcpClientPrDelMode OBJECT-TYPE
   SYNTAX      INTEGER
               {
               disabled (0),
               enabled (1)
               }
   MAX-ACCESS  read-write
   STATUS      current
   DESCRIPTION
      "Path: lacpBundle.editConf.ipV6.dhcp.client.pd.mode

       Possibilities:
               disabled   (0)
               enabled   (1)"
   ::= {er1646v2LacpBIpV6Entry 170394624}

er1646v2LacpBIpV6DhcpClientPrDelPool OBJECT-TYPE
   SYNTAX      DisplayString
   MAX-ACCESS  read-write
   STATUS      current
   DESCRIPTION
      "Path: lacpBundle.editConf.ipV6.dhcp.client.pd.pool"
   ::= {er1646v2LacpBIpV6Entry 170395648}

er1646v2LacpBIpV6DhcpClientPrDelPdExclOpt OBJECT-TYPE
   SYNTAX      INTEGER
               {
               disabled (0),
               enabled (1)
               }
   MAX-ACCESS  read-write
   STATUS      current
   DESCRIPTION
      "Path: lacpBundle.editConf.ipV6.dhcp.client.pd.pdExclOpt

       Possibilities:
               disabled   (0)
               enabled   (1)"
   ::= {er1646v2LacpBIpV6Entry 170396672}

er1646v2LacpBIpV6DhcpClientDnsServerPref OBJECT-TYPE
   SYNTAX      Integer32
   MAX-ACCESS  read-write
   STATUS      current
   DESCRIPTION
      "Path: lacpBundle.editConf.ipV6.dhcp.client.dns.serverPref"
   ::= {er1646v2LacpBIpV6Entry 170918912}

er1646v2LacpBIpV6DhcpClientRapidCommit OBJECT-TYPE
   SYNTAX      INTEGER
               {
               disabled (0),
               enabled (1)
               }
   MAX-ACCESS  read-write
   STATUS      current
   DESCRIPTION
      "Path: lacpBundle.editConf.ipV6.dhcp.client.rapidCommit

       Possibilities:
               disabled   (0)
               enabled   (1)"
   ::= {er1646v2LacpBIpV6Entry 170655744}

er1646v2LacpBIpV6DhcpClientTimersSolTimeOut OBJECT-TYPE
   SYNTAX      TimeTicks
   MAX-ACCESS  read-write
   STATUS      current
   DESCRIPTION
      "Path: lacpBundle.editConf.ipV6.dhcp.client.timers.solTimeOut

       Time in centi-second."
   ::= {er1646v2LacpBIpV6Entry 171181056}

er1646v2LacpBIpV6DhcpClientTimersSolMaxRt OBJECT-TYPE
   SYNTAX      TimeTicks
   MAX-ACCESS  read-write
   STATUS      current
   DESCRIPTION
      "Path: lacpBundle.editConf.ipV6.dhcp.client.timers.solMaxRt

       Time in centi-second."
   ::= {er1646v2LacpBIpV6Entry 171182080}

er1646v2LacpBIpV6DhcpClientTimersInfoRefresh OBJECT-TYPE
   SYNTAX      TimeTicks
   MAX-ACCESS  read-write
   STATUS      current
   DESCRIPTION
      "Path: lacpBundle.editConf.ipV6.dhcp.client.timers.infoRefresh

       Time in centi-second."
   ::= {er1646v2LacpBIpV6Entry 171183104}

er1646v2LacpBIpV6DhcpServerMode OBJECT-TYPE
   SYNTAX      INTEGER
               {
               disabled (0),
               enabled (1)
               }
   MAX-ACCESS  read-write
   STATUS      current
   DESCRIPTION
      "Path: lacpBundle.editConf.ipV6.dhcp.server.mode

       Possibilities:
               disabled   (0)
               enabled   (1)"
   ::= {er1646v2LacpBIpV6Entry 172228608}

er1646v2LacpBIpV6DhcpServerPreference OBJECT-TYPE
   SYNTAX      Integer32
   MAX-ACCESS  read-write
   STATUS      current
   DESCRIPTION
      "Path: lacpBundle.editConf.ipV6.dhcp.server.preference"
   ::= {er1646v2LacpBIpV6Entry 172490752}

er1646v2LacpBIpV6DhcpServerPool OBJECT-TYPE
   SYNTAX      DisplayString
   MAX-ACCESS  read-write
   STATUS      current
   DESCRIPTION
      "Path: lacpBundle.editConf.ipV6.dhcp.server.pool"
   ::= {er1646v2LacpBIpV6Entry 172752896}

er1646v2LacpBIpV6DhcpServerRapidCommit OBJECT-TYPE
   SYNTAX      INTEGER
               {
               disabled (0),
               enabled (1)
               }
   MAX-ACCESS  read-write
   STATUS      current
   DESCRIPTION
      "Path: lacpBundle.editConf.ipV6.dhcp.server.rapidCommit

       Possibilities:
               disabled   (0)
               enabled   (1)"
   ::= {er1646v2LacpBIpV6Entry 173015040}

er1646v2LacpBIpV6DhcpServerTimersInfoRefresh OBJECT-TYPE
   SYNTAX      TimeTicks
   MAX-ACCESS  read-write
   STATUS      current
   DESCRIPTION
      "Path: lacpBundle.editConf.ipV6.dhcp.server.timers.infoRefresh

       Time in centi-second."
   ::= {er1646v2LacpBIpV6Entry 173278208}

er1646v2LacpBIpV6DhcpRelayMode OBJECT-TYPE
   SYNTAX      INTEGER
               {
               disabled (0),
               enabled (1)
               }
   MAX-ACCESS  read-write
   STATUS      current
   DESCRIPTION
      "Path: lacpBundle.editConf.ipV6.dhcp.relay.mode

       Possibilities:
               disabled   (0)
               enabled   (1)"
   ::= {er1646v2LacpBIpV6Entry 174071808}

er1646v2LacpBIpV6SendRedirect OBJECT-TYPE
   SYNTAX      INTEGER
               {
               disabled (0),
               enabled (1)
               }
   MAX-ACCESS  read-write
   STATUS      current
   DESCRIPTION
      "Path: lacpBundle.editConf.ipV6.sendRedirect

       Possibilities:
               disabled   (0)
               enabled   (1)"
   ::= {er1646v2LacpBIpV6Entry 117440512}

er1646v2LacpBIpV6LinkMtu OBJECT-TYPE
   SYNTAX      Integer32
   MAX-ACCESS  read-write
   STATUS      current
   DESCRIPTION
      "Path: lacpBundle.editConf.ipV6.linkMtu"
   ::= {er1646v2LacpBIpV6Entry 134217728}

er1646v2LacpBIpV6InterfaceId OBJECT-TYPE
   SYNTAX      OCTET STRING
   MAX-ACCESS  read-write
   STATUS      current
   DESCRIPTION
      "Path: lacpBundle.editConf.ipV6.interfaceId"
   ::= {er1646v2LacpBIpV6Entry 150994944}

er1646v2LacpBIpV6MF OBJECT-TYPE
   SYNTAX      Integer32
   MAX-ACCESS  read-write
   STATUS      current
   DESCRIPTION
      "Path: lacpBundle.editConf.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1646v2LacpBIpV6Entry 285212672}

er1646v2LacpBIpV6IcmpMessagesNoRoute OBJECT-TYPE
   SYNTAX      INTEGER
               {
               disabled (0),
               enabled (1)
               }
   MAX-ACCESS  read-write
   STATUS      current
   DESCRIPTION
      "Path: lacpBundle.editConf.ipV6.icmpMessages.noRoute

       Possibilities:
               disabled   (0)
               enabled   (1)"
   ::= {er1646v2LacpBIpV6Entry 302055424}

er1646v2LacpBIpV6IcmpMessagesBeyondScope OBJECT-TYPE
   SYNTAX      INTEGER
               {
               disabled (0),
               enabled (1)
               }
   MAX-ACCESS  read-write
   STATUS      current
   DESCRIPTION
      "Path: lacpBundle.editConf.ipV6.icmpMessages.beyondScope

       Possibilities:
               disabled   (0)
               enabled   (1)"
   ::= {er1646v2LacpBIpV6Entry 302186496}

er1646v2LacpBIpV6IcmpMessagesAddressUnreachable OBJECT-TYPE
   SYNTAX      INTEGER
               {
               disabled (0),
               enabled (1)
               }
   MAX-ACCESS  read-write
   STATUS      current
   DESCRIPTION
      "Path: lacpBundle.editConf.ipV6.icmpMessages.addressUnreachable

       Possibilities:
               disabled   (0)
               enabled   (1)"
   ::= {er1646v2LacpBIpV6Entry 302252032}

er1646v2LacpBIpV6IcmpMessagesPortUnreachable OBJECT-TYPE
   SYNTAX      INTEGER
               {
               disabled (0),
               enabled (1)
               }
   MAX-ACCESS  read-write
   STATUS      current
   DESCRIPTION
      "Path: lacpBundle.editConf.ipV6.icmpMessages.portUnreachable

       Possibilities:
               disabled   (0)
               enabled   (1)"
   ::= {er1646v2LacpBIpV6Entry 302317568}

er1646v2LacpBIpV6IcmpMessagesPacketTooBig OBJECT-TYPE
   SYNTAX      INTEGER
               {
               disabled (0),
               enabled (1)
               }
   MAX-ACCESS  read-write
   STATUS      current
   DESCRIPTION
      "Path: lacpBundle.editConf.ipV6.icmpMessages.packetTooBig

       Possibilities:
               disabled   (0)
               enabled   (1)"
   ::= {er1646v2LacpBIpV6Entry 302645248}

er1646v2LacpBIpV6IcmpMessagesHopLimitExceeded OBJECT-TYPE
   SYNTAX      INTEGER
               {
               disabled (0),
               enabled (1)
               }
   MAX-ACCESS  read-write
   STATUS      current
   DESCRIPTION
      "Path: lacpBundle.editConf.ipV6.icmpMessages.hopLimitExceeded

       Possibilities:
               disabled   (0)
               enabled   (1)"
   ::= {er1646v2LacpBIpV6Entry 303300608}

er1646v2LacpBIpV6IcmpMessagesFragTimeExceeded OBJECT-TYPE
   SYNTAX      INTEGER
               {
               disabled (0),
               enabled (1)
               }
   MAX-ACCESS  read-write
   STATUS      current
   DESCRIPTION
      "Path: lacpBundle.editConf.ipV6.icmpMessages.fragTimeExceeded

       Possibilities:
               disabled   (0)
               enabled   (1)"
   ::= {er1646v2LacpBIpV6Entry 303366144}

er1646v2LacpBIpV6IcmpMessagesHeaderFieldErr OBJECT-TYPE
   SYNTAX      INTEGER
               {
               disabled (0),
               enabled (1)
               }
   MAX-ACCESS  read-write
   STATUS      current
   DESCRIPTION
      "Path: lacpBundle.editConf.ipV6.icmpMessages.headerFieldErr

       Possibilities:
               disabled   (0)
               enabled   (1)"
   ::= {er1646v2LacpBIpV6Entry 303955968}

er1646v2LacpBIpV6IcmpMessagesOptionUnrecognized OBJECT-TYPE
   SYNTAX      INTEGER
               {
               disabled (0),
               enabled (1)
               }
   MAX-ACCESS  read-write
   STATUS      current
   DESCRIPTION
      "Path: lacpBundle.editConf.ipV6.icmpMessages.optionUnrecognized

       Possibilities:
               disabled   (0)
               enabled   (1)"
   ::= {er1646v2LacpBIpV6Entry 304087040}

er1646v2LacpBIpV6IcmpMessagesRedirect OBJECT-TYPE
   SYNTAX      INTEGER
               {
               disabled (0),
               enabled (1)
               }
   MAX-ACCESS  read-write
   STATUS      current
   DESCRIPTION
      "Path: lacpBundle.editConf.ipV6.icmpMessages.redirect

       Possibilities:
               disabled   (0)
               enabled   (1)"
   ::= {er1646v2LacpBIpV6Entry 304611328}

er1646v2LacpBIpV6Addresses OBJECT-TYPE
   SYNTAX      SEQUENCE OF Er1646v2LacpBIpV6AddressesEntry
   MAX-ACCESS  not-accessible
   STATUS      current
   DESCRIPTION
      ""
   ::= {er1646v2LacpBIpV6 50331648}

er1646v2LacpBIpV6AddressesEntry OBJECT-TYPE
   SYNTAX      Er1646v2LacpBIpV6AddressesEntry
   MAX-ACCESS  not-accessible
   STATUS      current
   DESCRIPTION
      ""
   INDEX      { er1646v2LacpBIpV6AddressesGlobalIx,
                er1646v2LacpBIpV6AddressesTableIx }
   ::= {er1646v2LacpBIpV6Addresses 1}

Er1646v2LacpBIpV6AddressesEntry ::=
   SEQUENCE
      {
      er1646v2LacpBIpV6AddressesActions
         VariableLengthTableActions,
      er1646v2LacpBIpV6AddressesGlobalIx
         GlobalIndex,
      er1646v2LacpBIpV6AddressesTableIx
         TableIndex,
      er1646v2LacpBIpV6AddressesType
         INTEGER,
      er1646v2LacpBIpV6AddressesAddress
         Ipv6Address,
      er1646v2LacpBIpV6AddressesPrefixLength
         Integer32,
      er1646v2LacpBIpV6AddressesGeneralPrefix
         DisplayString,
      er1646v2LacpBIpV6AddressesRaSend
         INTEGER,
      er1646v2LacpBIpV6AddressesRaOnLinkFlag
         INTEGER,
      er1646v2LacpBIpV6AddressesRaAutoFlag
         INTEGER,
      er1646v2LacpBIpV6AddressesRaValidLifeTime
         TimeTicks,
      er1646v2LacpBIpV6AddressesRaValidLTMode
         INTEGER,
      er1646v2LacpBIpV6AddressesRaPrefLifeTime
         TimeTicks,
      er1646v2LacpBIpV6AddressesRaPrefLTMode
         INTEGER
      }

er1646v2LacpBIpV6AddressesActions OBJECT-TYPE
   SYNTAX      VariableLengthTableActions
   MAX-ACCESS  read-write
   STATUS      current
   DESCRIPTION
      "By way of this field, some manipulations
       on this table may be performed."
   ::= {er1646v2LacpBIpV6AddressesEntry 2}

er1646v2LacpBIpV6AddressesGlobalIx OBJECT-TYPE
   SYNTAX      GlobalIndex
   MAX-ACCESS  not-accessible
   STATUS      current
   DESCRIPTION
      "The value of the tlsCntTreeGlobalIndex of the MANAGED OBJECT."
   ::= {er1646v2LacpBIpV6AddressesEntry 10}

er1646v2LacpBIpV6AddressesTableIx OBJECT-TYPE
   SYNTAX      TableIndex
   MAX-ACCESS  not-accessible
   STATUS      current
   DESCRIPTION
      ""
   ::= {er1646v2LacpBIpV6AddressesEntry 11}

er1646v2LacpBIpV6AddressesType OBJECT-TYPE
   SYNTAX      INTEGER
               {
               unicast (0),
               eui64 (1),
               anycast (2),
               linkLocal (3),
               generalPrefix (4)
               }
   MAX-ACCESS  read-write
   STATUS      current
   DESCRIPTION
      "Path: lacpBundle.editConf.ipV6.addresses.type

       Possibilities:
               unicast   (0)
               eui64   (1)
               anycast   (2)
               linkLocal   (3)
               generalPrefix   (4)"
   ::= {er1646v2LacpBIpV6AddressesEntry 50331648}

er1646v2LacpBIpV6AddressesAddress OBJECT-TYPE
   SYNTAX      Ipv6Address
   MAX-ACCESS  read-write
   STATUS      current
   DESCRIPTION
      "Path: lacpBundle.editConf.ipV6.addresses.address

       ipv6 address"
   ::= {er1646v2LacpBIpV6AddressesEntry 16777216}

er1646v2LacpBIpV6AddressesPrefixLength OBJECT-TYPE
   SYNTAX      Integer32
   MAX-ACCESS  read-write
   STATUS      current
   DESCRIPTION
      "Path: lacpBundle.editConf.ipV6.addresses.prefixLength"
   ::= {er1646v2LacpBIpV6AddressesEntry 33554432}

er1646v2LacpBIpV6AddressesGeneralPrefix OBJECT-TYPE
   SYNTAX      DisplayString
   MAX-ACCESS  read-write
   STATUS      current
   DESCRIPTION
      "Path: lacpBundle.editConf.ipV6.addresses.generalPrefix"
   ::= {er1646v2LacpBIpV6AddressesEntry 83886080}

er1646v2LacpBIpV6AddressesRaSend OBJECT-TYPE
   SYNTAX      INTEGER
               {
               disabled (0),
               enabled (1)
               }
   MAX-ACCESS  read-write
   STATUS      current
   DESCRIPTION
      "Path: lacpBundle.editConf.ipV6.addresses.ra.send

       Possibilities:
               disabled   (0)
               enabled   (1)"
   ::= {er1646v2LacpBIpV6AddressesEntry 67174400}

er1646v2LacpBIpV6AddressesRaOnLinkFlag OBJECT-TYPE
   SYNTAX      INTEGER
               {
               disabled (0),
               enabled (1)
               }
   MAX-ACCESS  read-write
   STATUS      current
   DESCRIPTION
      "Path: lacpBundle.editConf.ipV6.addresses.ra.onLinkFlag

       Possibilities:
               disabled   (0)
               enabled   (1)"
   ::= {er1646v2LacpBIpV6AddressesEntry 67371008}

er1646v2LacpBIpV6AddressesRaAutoFlag OBJECT-TYPE
   SYNTAX      INTEGER
               {
               disabled (0),
               enabled (1)
               }
   MAX-ACCESS  read-write
   STATUS      current
   DESCRIPTION
      "Path: lacpBundle.editConf.ipV6.addresses.ra.autonomousFlag

       Possibilities:
               disabled   (0)
               enabled   (1)"
   ::= {er1646v2LacpBIpV6AddressesEntry 67567616}

er1646v2LacpBIpV6AddressesRaValidLifeTime OBJECT-TYPE
   SYNTAX      TimeTicks
   MAX-ACCESS  read-write
   STATUS      current
   DESCRIPTION
      "Path: lacpBundle.editConf.ipV6.addresses.ra.validLifeTime

       Time in centi-second."
   ::= {er1646v2LacpBIpV6AddressesEntry 67239936}

er1646v2LacpBIpV6AddressesRaValidLTMode OBJECT-TYPE
   SYNTAX      INTEGER
               {
               fixed (0),
               infinite (2)
               }
   MAX-ACCESS  read-write
   STATUS      current
   DESCRIPTION
      "Path: lacpBundle.editConf.ipV6.addresses.ra.validLifeTimeMode

       Possibilities:
               fixed   (0)
               infinite   (2)"
   ::= {er1646v2LacpBIpV6AddressesEntry 67305472}

er1646v2LacpBIpV6AddressesRaPrefLifeTime OBJECT-TYPE
   SYNTAX      TimeTicks
   MAX-ACCESS  read-write
   STATUS      current
   DESCRIPTION
      "Path: lacpBundle.editConf.ipV6.addresses.ra.prefLifeTime

       Time in centi-second."
   ::= {er1646v2LacpBIpV6AddressesEntry 67436544}

er1646v2LacpBIpV6AddressesRaPrefLTMode OBJECT-TYPE
   SYNTAX      INTEGER
               {
               fixed (0),
               infinite (2)
               }
   MAX-ACCESS  read-write
   STATUS      current
   DESCRIPTION
      "Path: lacpBundle.editConf.ipV6.addresses.ra.prefLifeTimeMode

       Possibilities:
               fixed   (0)
               infinite   (2)"
   ::= {er1646v2LacpBIpV6AddressesEntry 67502080}

er1646v2LacpBIpV6RaDnsOptionsRdnssServers OBJECT-TYPE
   SYNTAX      SEQUENCE OF Er1646v2LacpBIpV6RaDnsOptionsRdnssServersEntry
   MAX-ACCESS  not-accessible
   STATUS      current
   DESCRIPTION
      ""
   ::= {er1646v2LacpBIpV6 101394432}

er1646v2LacpBIpV6RaDnsOptionsRdnssServersEntry OBJECT-TYPE
   SYNTAX      Er1646v2LacpBIpV6RaDnsOptionsRdnssServersEntry
   MAX-ACCESS  not-accessible
   STATUS      current
   DESCRIPTION
      ""
   INDEX      { er1646v2LacpBIpV6RaDnsOptionsRdnssServersGlobalIx,
                er1646v2LacpBIpV6RaDnsOptionsRdnssServersTableIx }
   ::= {er1646v2LacpBIpV6RaDnsOptionsRdnssServers 1}

Er1646v2LacpBIpV6RaDnsOptionsRdnssServersEntry ::=
   SEQUENCE
      {
      er1646v2LacpBIpV6RaDnsOptionsRdnssServersActions
         VariableLengthTableActions,
      er1646v2LacpBIpV6RaDnsOptionsRdnssServersGlobalIx
         GlobalIndex,
      er1646v2LacpBIpV6RaDnsOptionsRdnssServersTableIx
         TableIndex,
      er1646v2LacpBIpV6RaDnsOptionsRdnssServersAddress
         Ipv6Address
      }

er1646v2LacpBIpV6RaDnsOptionsRdnssServersActions OBJECT-TYPE
   SYNTAX      VariableLengthTableActions
   MAX-ACCESS  read-write
   STATUS      current
   DESCRIPTION
      "By way of this field, some manipulations
       on this table may be performed."
   ::= {er1646v2LacpBIpV6RaDnsOptionsRdnssServersEntry 2}

er1646v2LacpBIpV6RaDnsOptionsRdnssServersGlobalIx OBJECT-TYPE
   SYNTAX      GlobalIndex
   MAX-ACCESS  not-accessible
   STATUS      current
   DESCRIPTION
      "The value of the tlsCntTreeGlobalIndex of the MANAGED OBJECT."
   ::= {er1646v2LacpBIpV6RaDnsOptionsRdnssServersEntry 10}

er1646v2LacpBIpV6RaDnsOptionsRdnssServersTableIx OBJECT-TYPE
   SYNTAX      TableIndex
   MAX-ACCESS  not-accessible
   STATUS      current
   DESCRIPTION
      ""
   ::= {er1646v2LacpBIpV6RaDnsOptionsRdnssServersEntry 11}

er1646v2LacpBIpV6RaDnsOptionsRdnssServersAddress OBJECT-TYPE
   SYNTAX      Ipv6Address
   MAX-ACCESS  read-write
   STATUS      current
   DESCRIPTION
      "Path: lacpBundle.editConf.ipV6.ra.dnsOptions.rdnss.servers.address

       ipv6 address"
   ::= {er1646v2LacpBIpV6RaDnsOptionsRdnssServersEntry 16777216}

er1646v2LacpBIpV6RaDnsOptionsDnsslDomains OBJECT-TYPE
   SYNTAX      SEQUENCE OF Er1646v2LacpBIpV6RaDnsOptionsDnsslDomainsEntry
   MAX-ACCESS  not-accessible
   STATUS      current
   DESCRIPTION
      ""
   ::= {er1646v2LacpBIpV6 101402624}

er1646v2LacpBIpV6RaDnsOptionsDnsslDomainsEntry OBJECT-TYPE
   SYNTAX      Er1646v2LacpBIpV6RaDnsOptionsDnsslDomainsEntry
   MAX-ACCESS  not-accessible
   STATUS      current
   DESCRIPTION
      ""
   INDEX      { er1646v2LacpBIpV6RaDnsOptionsDnsslDomainsGlobalIx,
                er1646v2LacpBIpV6RaDnsOptionsDnsslDomainsTableIx }
   ::= {er1646v2LacpBIpV6RaDnsOptionsDnsslDomains 1}

Er1646v2LacpBIpV6RaDnsOptionsDnsslDomainsEntry ::=
   SEQUENCE
      {
      er1646v2LacpBIpV6RaDnsOptionsDnsslDomainsActions
         VariableLengthTableActions,
      er1646v2LacpBIpV6RaDnsOptionsDnsslDomainsGlobalIx
         GlobalIndex,
      er1646v2LacpBIpV6RaDnsOptionsDnsslDomainsTableIx
         TableIndex,
      er1646v2LacpBIpV6RaDnsOptionsDnsslDomainsName
         DisplayString
      }

er1646v2LacpBIpV6RaDnsOptionsDnsslDomainsActions OBJECT-TYPE
   SYNTAX      VariableLengthTableActions
   MAX-ACCESS  read-write
   STATUS      current
   DESCRIPTION
      "By way of this field, some manipulations
       on this table may be performed."
   ::= {er1646v2LacpBIpV6RaDnsOptionsDnsslDomainsEntry 2}

er1646v2LacpBIpV6RaDnsOptionsDnsslDomainsGlobalIx OBJECT-TYPE
   SYNTAX      GlobalIndex
   MAX-ACCESS  not-accessible
   STATUS      current
   DESCRIPTION
      "The value of the tlsCntTreeGlobalIndex of the MANAGED OBJECT."
   ::= {er1646v2LacpBIpV6RaDnsOptionsDnsslDomainsEntry 10}

er1646v2LacpBIpV6RaDnsOptionsDnsslDomainsTableIx OBJECT-TYPE
   SYNTAX      TableIndex
   MAX-ACCESS  not-accessible
   STATUS      current
   DESCRIPTION
      ""
   ::= {er1646v2LacpBIpV6RaDnsOptionsDnsslDomainsEntry 11}

er1646v2LacpBIpV6RaDnsOptionsDnsslDomainsName OBJECT-TYPE
   SYNTAX      DisplayString
   MAX-ACCESS  read-write
   STATUS      current
   DESCRIPTION
      "Path: lacpBundle.editConf.ipV6.ra.dnsOptions.dnssl.domains.name"
   ::= {er1646v2LacpBIpV6RaDnsOptionsDnsslDomainsEntry 16777216}

er1646v2LacpBIpV6DhcpClientUserClassOpt OBJECT-TYPE
   SYNTAX      SEQUENCE OF Er1646v2LacpBIpV6DhcpClientUserClassOptEntry
   MAX-ACCESS  not-accessible
   STATUS      current
   DESCRIPTION
      ""
   ::= {er1646v2LacpBIpV6 171442176}

er1646v2LacpBIpV6DhcpClientUserClassOptEntry OBJECT-TYPE
   SYNTAX      Er1646v2LacpBIpV6DhcpClientUserClassOptEntry
   MAX-ACCESS  not-accessible
   STATUS      current
   DESCRIPTION
      ""
   INDEX      { er1646v2LacpBIpV6DhcpClientUserClassOptGlobalIx,
                er1646v2LacpBIpV6DhcpClientUserClassOptTableIx }
   ::= {er1646v2LacpBIpV6DhcpClientUserClassOpt 1}

Er1646v2LacpBIpV6DhcpClientUserClassOptEntry ::=
   SEQUENCE
      {
      er1646v2LacpBIpV6DhcpClientUserClassOptActions
         VariableLengthTableActions,
      er1646v2LacpBIpV6DhcpClientUserClassOptGlobalIx
         GlobalIndex,
      er1646v2LacpBIpV6DhcpClientUserClassOptTableIx
         TableIndex,
      er1646v2LacpBIpV6DhcpClientUserClassOptValueAscii
         DisplayString,
      er1646v2LacpBIpV6DhcpClientUserClassOptValueDecimal
         Integer32,
      er1646v2LacpBIpV6DhcpClientUserClassOptValueHexData
         OCTET STRING
      }

er1646v2LacpBIpV6DhcpClientUserClassOptActions OBJECT-TYPE
   SYNTAX      VariableLengthTableActions
   MAX-ACCESS  read-write
   STATUS      current
   DESCRIPTION
      "By way of this field, some manipulations
       on this table may be performed."
   ::= {er1646v2LacpBIpV6DhcpClientUserClassOptEntry 2}

er1646v2LacpBIpV6DhcpClientUserClassOptGlobalIx OBJECT-TYPE
   SYNTAX      GlobalIndex
   MAX-ACCESS  not-accessible
   STATUS      current
   DESCRIPTION
      "The value of the tlsCntTreeGlobalIndex of the MANAGED OBJECT."
   ::= {er1646v2LacpBIpV6DhcpClientUserClassOptEntry 10}

er1646v2LacpBIpV6DhcpClientUserClassOptTableIx OBJECT-TYPE
   SYNTAX      TableIndex
   MAX-ACCESS  not-accessible
   STATUS      current
   DESCRIPTION
      ""
   ::= {er1646v2LacpBIpV6DhcpClientUserClassOptEntry 11}

er1646v2LacpBIpV6DhcpClientUserClassOptValueAscii OBJECT-TYPE
   SYNTAX      DisplayString
   MAX-ACCESS  read-write
   STATUS      current
   DESCRIPTION
      "Path: lacpBundle.editConf.ipV6.dhcp.client.userClassOpt.value.ascii"
   ::= {er1646v2LacpBIpV6DhcpClientUserClassOptEntry 16842752}

er1646v2LacpBIpV6DhcpClientUserClassOptValueDecimal OBJECT-TYPE
   SYNTAX      Integer32
   MAX-ACCESS  read-write
   STATUS      current
   DESCRIPTION
      "Path: lacpBundle.editConf.ipV6.dhcp.client.userClassOpt.value.decimal"
   ::= {er1646v2LacpBIpV6DhcpClientUserClassOptEntry 16908288}

er1646v2LacpBIpV6DhcpClientUserClassOptValueHexData OBJECT-TYPE
   SYNTAX      OCTET STRING
   MAX-ACCESS  read-write
   STATUS      current
   DESCRIPTION
      "Path: lacpBundle.editConf.ipV6.dhcp.client.userClassOpt.value.hexData"
   ::= {er1646v2LacpBIpV6DhcpClientUserClassOptEntry 16973824}

er1646v2LacpBIpV6DhcpClientVendorCl OBJECT-TYPE
   SYNTAX      SEQUENCE OF Er1646v2LacpBIpV6DhcpClientVendorClEntry
   MAX-ACCESS  not-accessible
   STATUS      current
   DESCRIPTION
      ""
   ::= {er1646v2LacpBIpV6 171704320}

er1646v2LacpBIpV6DhcpClientVendorClEntry OBJECT-TYPE
   SYNTAX      Er1646v2LacpBIpV6DhcpClientVendorClEntry
   MAX-ACCESS  not-accessible
   STATUS      current
   DESCRIPTION
      ""
   INDEX      { er1646v2LacpBIpV6DhcpClientVendorClGlobalIx,
                er1646v2LacpBIpV6DhcpClientVendorClTableIx }
   ::= {er1646v2LacpBIpV6DhcpClientVendorCl 1}

Er1646v2LacpBIpV6DhcpClientVendorClEntry ::=
   SEQUENCE
      {
      er1646v2LacpBIpV6DhcpClientVendorClActions
         VariableLengthTableActions,
      er1646v2LacpBIpV6DhcpClientVendorClGlobalIx
         GlobalIndex,
      er1646v2LacpBIpV6DhcpClientVendorClTableIx
         TableIndex,
      er1646v2LacpBIpV6DhcpClientVendorClValueAscii
         DisplayString,
      er1646v2LacpBIpV6DhcpClientVendorClValueDecimal
         Integer32,
      er1646v2LacpBIpV6DhcpClientVendorClValueHexData
         OCTET STRING
      }

er1646v2LacpBIpV6DhcpClientVendorClActions OBJECT-TYPE
   SYNTAX      VariableLengthTableActions
   MAX-ACCESS  read-write
   STATUS      current
   DESCRIPTION
      "By way of this field, some manipulations
       on this table may be performed."
   ::= {er1646v2LacpBIpV6DhcpClientVendorClEntry 2}

er1646v2LacpBIpV6DhcpClientVendorClGlobalIx OBJECT-TYPE
   SYNTAX      GlobalIndex
   MAX-ACCESS  not-accessible
   STATUS      current
   DESCRIPTION
      "The value of the tlsCntTreeGlobalIndex of the MANAGED OBJECT."
   ::= {er1646v2LacpBIpV6DhcpClientVendorClEntry 10}

er1646v2LacpBIpV6DhcpClientVendorClTableIx OBJECT-TYPE
   SYNTAX      TableIndex
   MAX-ACCESS  not-accessible
   STATUS      current
   DESCRIPTION
      ""
   ::= {er1646v2LacpBIpV6DhcpClientVendorClEntry 11}

er1646v2LacpBIpV6DhcpClientVendorClValueAscii OBJECT-TYPE
   SYNTAX      DisplayString
   MAX-ACCESS  read-write
   STATUS      current
   DESCRIPTION
      "Path: lacpBundle.editConf.ipV6.dhcp.client.vendorClassOpt.value.ascii"
   ::= {er1646v2LacpBIpV6DhcpClientVendorClEntry 16842752}

er1646v2LacpBIpV6DhcpClientVendorClValueDecimal OBJECT-TYPE
   SYNTAX      Integer32
   MAX-ACCESS  read-write
   STATUS      current
   DESCRIPTION
      "Path: lacpBundle.editConf.ipV6.dhcp.client.vendorClassOpt.value.decimal"
   ::= {er1646v2LacpBIpV6DhcpClientVendorClEntry 16908288}

er1646v2LacpBIpV6DhcpClientVendorClValueHexData OBJECT-TYPE
   SYNTAX      OCTET STRING
   MAX-ACCESS  read-write
   STATUS      current
   DESCRIPTION
      "Path: lacpBundle.editConf.ipV6.dhcp.client.vendorClassOpt.value.hexData"
   ::= {er1646v2LacpBIpV6DhcpClientVendorClEntry 16973824}

er1646v2LacpBIpV6DhcpRelayDestinations OBJECT-TYPE
   SYNTAX      SEQUENCE OF Er1646v2LacpBIpV6DhcpRelayDestinationsEntry
   MAX-ACCESS  not-accessible
   STATUS      current
   DESCRIPTION
      ""
   ::= {er1646v2LacpBIpV6 174080000}

er1646v2LacpBIpV6DhcpRelayDestinationsEntry OBJECT-TYPE
   SYNTAX      Er1646v2LacpBIpV6DhcpRelayDestinationsEntry
   MAX-ACCESS  not-accessible
   STATUS      current
   DESCRIPTION
      ""
   INDEX      { er1646v2LacpBIpV6DhcpRelayDestinationsGlobalIx,
                er1646v2LacpBIpV6DhcpRelayDestinationsTableIx }
   ::= {er1646v2LacpBIpV6DhcpRelayDestinations 1}

Er1646v2LacpBIpV6DhcpRelayDestinationsEntry ::=
   SEQUENCE
      {
      er1646v2LacpBIpV6DhcpRelayDestinationsActions
         VariableLengthTableActions,
      er1646v2LacpBIpV6DhcpRelayDestinationsGlobalIx
         GlobalIndex,
      er1646v2LacpBIpV6DhcpRelayDestinationsTableIx
         TableIndex,
      er1646v2LacpBIpV6DhcpRelayDestinationsAddress
         Ipv6Address,
      er1646v2LacpBIpV6DhcpRelayDestinationsInterface
         DisplayString
      }

er1646v2LacpBIpV6DhcpRelayDestinationsActions OBJECT-TYPE
   SYNTAX      VariableLengthTableActions
   MAX-ACCESS  read-write
   STATUS      current
   DESCRIPTION
      "By way of this field, some manipulations
       on this table may be performed."
   ::= {er1646v2LacpBIpV6DhcpRelayDestinationsEntry 2}

er1646v2LacpBIpV6DhcpRelayDestinationsGlobalIx OBJECT-TYPE
   SYNTAX      GlobalIndex
   MAX-ACCESS  not-accessible
   STATUS      current
   DESCRIPTION
      "The value of the tlsCntTreeGlobalIndex of the MANAGED OBJECT."
   ::= {er1646v2LacpBIpV6DhcpRelayDestinationsEntry 10}

er1646v2LacpBIpV6DhcpRelayDestinationsTableIx OBJECT-TYPE
   SYNTAX      TableIndex
   MAX-ACCESS  not-accessible
   STATUS      current
   DESCRIPTION
      ""
   ::= {er1646v2LacpBIpV6DhcpRelayDestinationsEntry 11}

er1646v2LacpBIpV6DhcpRelayDestinationsAddress OBJECT-TYPE
   SYNTAX      Ipv6Address
   MAX-ACCESS  read-write
   STATUS      current
   DESCRIPTION
      "Path: lacpBundle.editConf.ipV6.dhcp.relay.destinations.address

       ipv6 address"
   ::= {er1646v2LacpBIpV6DhcpRelayDestinationsEntry 16777216}

er1646v2LacpBIpV6DhcpRelayDestinationsInterface OBJECT-TYPE
   SYNTAX      DisplayString
   MAX-ACCESS  read-write
   STATUS      current
   DESCRIPTION
      "Path: lacpBundle.editConf.ipV6.dhcp.relay.destinations.interface"
   ::= {er1646v2LacpBIpV6DhcpRelayDestinationsEntry 33554432}


er1646v2LacpBSnmpIndexOffset OBJECT IDENTIFIER ::= {er1646v2LacpB 268}

er1646v2LacpBSnmpIndexOffsetTable OBJECT-TYPE
   SYNTAX      SEQUENCE OF Er1646v2LacpBSnmpIndexOffsetEntry
   MAX-ACCESS  not-accessible
   STATUS      current
   DESCRIPTION
      "Preferred offset in the range of SNMP indices for this SWinst, 0 means automatic"
   ::= {er1646v2LacpBSnmpIndexOffset 1}

er1646v2LacpBSnmpIndexOffsetEntry OBJECT-TYPE
   SYNTAX      Er1646v2LacpBSnmpIndexOffsetEntry
   MAX-ACCESS  not-accessible
   STATUS      current
   DESCRIPTION
      ""
   INDEX      { er1646v2LacpBSnmpIndexOffsetGlobalIx }
   ::= {er1646v2LacpBSnmpIndexOffsetTable 1}

Er1646v2LacpBSnmpIndexOffsetEntry ::=
   SEQUENCE
      {
      er1646v2LacpBSnmpIndexOffsetGlobalIx
         GlobalIndex,
      er1646v2LacpBSnmpIndexOffsetValue
         Integer32
      }

er1646v2LacpBSnmpIndexOffsetGlobalIx OBJECT-TYPE
   SYNTAX      GlobalIndex
   MAX-ACCESS  not-accessible
   STATUS      current
   DESCRIPTION
      "The value of the tlsCntTreeGlobalIndex of the MANAGED OBJECT."
   ::= {er1646v2LacpBSnmpIndexOffsetEntry 10}

er1646v2LacpBSnmpIndexOffsetValue OBJECT-TYPE
   SYNTAX      Integer32
   MAX-ACCESS  read-write
   STATUS      current
   DESCRIPTION
      "Path: lacpBundle.editConf.snmpIndexOffset"
   ::= {er1646v2LacpBSnmpIndexOffsetEntry 2147483648}


er1646v2LacpBBw OBJECT IDENTIFIER ::= {er1646v2LacpB 5}

er1646v2LacpBBwSSCTable OBJECT-TYPE
   SYNTAX      SEQUENCE OF Er1646v2LacpBBwEntry
   MAX-ACCESS  not-accessible
   STATUS      current
   DESCRIPTION
      ""
   ::= {er1646v2LacpBBw 1}

er1646v2LacpBBwEntry OBJECT-TYPE
   SYNTAX      Er1646v2LacpBBwEntry
   MAX-ACCESS  not-accessible
   STATUS      current
   DESCRIPTION
      ""
   INDEX      { er1646v2LacpBBwGlobalIx }
   ::= {er1646v2LacpBBwSSCTable 1}

Er1646v2LacpBBwEntry ::=
   SEQUENCE
      {
      er1646v2LacpBBwGlobalIx
         GlobalIndex,
      er1646v2LacpBBwMode
         INTEGER,
      er1646v2LacpBBwCir
         Integer32,
      er1646v2LacpBBwEir
         Integer32,
      er1646v2LacpBBwUnit
         INTEGER,
      er1646v2LacpBBwTc
         INTEGER,
      er1646v2LacpBBwTcFactor
         INTEGER,
      er1646v2LacpBBwCorrType
         INTEGER,
      er1646v2LacpBBwCorrPredefEncapsFrameRelay
         DisplayString,
      er1646v2LacpBBwCorrPredefEncapsPpp
         DisplayString,
      er1646v2LacpBBwCorrPredefEncapsAtmHl
         INTEGER,
      er1646v2LacpBBwCorrPredefEncapsAtmMp
         INTEGER,
      er1646v2LacpBBwCorrPredefEncapsHdlc
         DisplayString,
      er1646v2LacpBBwCorrPredefEncapsEfmFs
         Integer32,
      er1646v2LacpBBwCorrPredefEncapsEfmIb
         Integer32,
      er1646v2LacpBBwCorrPredefMode
         INTEGER,
      er1646v2LacpBBwCorrManualOverhead
         Integer32,
      er1646v2LacpBBwCorrManualFrameData
         Counter32,
      er1646v2LacpBBwCorrManualFrameHeader
         Counter32,
      er1646v2LacpBBwMaxFifoQLen
         Integer32,
      er1646v2LacpBBwDeFlagCir
         INTEGER,
      er1646v2LacpBBwDeFlagEir
         INTEGER,
      er1646v2LacpBBwDeFlagViolate
         INTEGER,
      er1646v2LacpBBwActCirActNone
         OCTET STRING,
      er1646v2LacpBBwActCirActEthCos1
         INTEGER,
      er1646v2LacpBBwActCirActEthDei1
         INTEGER,
      er1646v2LacpBBwActCirActEthCos2
         INTEGER,
      er1646v2LacpBBwActCirActEthDei2
         INTEGER,
      er1646v2LacpBBwActCirActEthCos3
         INTEGER,
      er1646v2LacpBBwActCirActEthDei3
         INTEGER,
      er1646v2LacpBBwActCirActEthCos4
         INTEGER,
      er1646v2LacpBBwActCirActEthDei4
         INTEGER,
      er1646v2LacpBBwActCirActEthCos5
         INTEGER,
      er1646v2LacpBBwActCirActEthDei5
         INTEGER,
      er1646v2LacpBBwActCirActEthCos6
         INTEGER,
      er1646v2LacpBBwActCirActEthDei6
         INTEGER,
      er1646v2LacpBBwActCirActEthCos7
         INTEGER,
      er1646v2LacpBBwActCirActEthDei7
         INTEGER,
      er1646v2LacpBBwActCirActEthCos8
         INTEGER,
      er1646v2LacpBBwActCirActEthDei8
         INTEGER,
      er1646v2LacpBBwActCirActEthTos
         INTEGER,
      er1646v2LacpBBwActCirActEthQueue
         INTEGER,
      er1646v2LacpBBwActCirActEthDrpLev
         INTEGER,
      er1646v2LacpBBwActCirActEthDeFlag
         INTEGER,
      er1646v2LacpBBwActCirActIpTos
         INTEGER,
      er1646v2LacpBBwActCirActIpQueue
         INTEGER,
      er1646v2LacpBBwActCirActIpDrpLev
         INTEGER,
      er1646v2LacpBBwActCirActIpDeFlag
         INTEGER,
      er1646v2LacpBBwActEirActNone
         OCTET STRING,
      er1646v2LacpBBwActEirActEthCos1
         INTEGER,
      er1646v2LacpBBwActEirActEthDei1
         INTEGER,
      er1646v2LacpBBwActEirActEthCos2
         INTEGER,
      er1646v2LacpBBwActEirActEthDei2
         INTEGER,
      er1646v2LacpBBwActEirActEthCos3
         INTEGER,
      er1646v2LacpBBwActEirActEthDei3
         INTEGER,
      er1646v2LacpBBwActEirActEthCos4
         INTEGER,
      er1646v2LacpBBwActEirActEthDei4
         INTEGER,
      er1646v2LacpBBwActEirActEthCos5
         INTEGER,
      er1646v2LacpBBwActEirActEthDei5
         INTEGER,
      er1646v2LacpBBwActEirActEthCos6
         INTEGER,
      er1646v2LacpBBwActEirActEthDei6
         INTEGER,
      er1646v2LacpBBwActEirActEthCos7
         INTEGER,
      er1646v2LacpBBwActEirActEthDei7
         INTEGER,
      er1646v2LacpBBwActEirActEthCos8
         INTEGER,
      er1646v2LacpBBwActEirActEthDei8
         INTEGER,
      er1646v2LacpBBwActEirActEthTos
         INTEGER,
      er1646v2LacpBBwActEirActEthQueue
         INTEGER,
      er1646v2LacpBBwActEirActEthDrpLev
         INTEGER,
      er1646v2LacpBBwActEirActEthDeFlag
         INTEGER,
      er1646v2LacpBBwActEirActIpTos
         INTEGER,
      er1646v2LacpBBwActEirActIpQueue
         INTEGER,
      er1646v2LacpBBwActEirActIpDrpLev
         INTEGER,
      er1646v2LacpBBwActEirActIpDeFlag
         INTEGER,
      er1646v2LacpBBwActViolActNone
         OCTET STRING,
      er1646v2LacpBBwActViolActDrop
         OCTET STRING,
      er1646v2LacpBBwActViolActEthCos1
         INTEGER,
      er1646v2LacpBBwActViolActEthDei1
         INTEGER,
      er1646v2LacpBBwActViolActEthCos2
         INTEGER,
      er1646v2LacpBBwActViolActEthDei2
         INTEGER,
      er1646v2LacpBBwActViolActEthCos3
         INTEGER,
      er1646v2LacpBBwActViolActEthDei3
         INTEGER,
      er1646v2LacpBBwActViolActEthCos4
         INTEGER,
      er1646v2LacpBBwActViolActEthDei4
         INTEGER,
      er1646v2LacpBBwActViolActEthCos5
         INTEGER,
      er1646v2LacpBBwActViolActEthDei5
         INTEGER,
      er1646v2LacpBBwActViolActEthCos6
         INTEGER,
      er1646v2LacpBBwActViolActEthDei6
         INTEGER,
      er1646v2LacpBBwActViolActEthCos7
         INTEGER,
      er1646v2LacpBBwActViolActEthDei7
         INTEGER,
      er1646v2LacpBBwActViolActEthCos8
         INTEGER,
      er1646v2LacpBBwActViolActEthDei8
         INTEGER,
      er1646v2LacpBBwActViolActEthTos
         INTEGER,
      er1646v2LacpBBwActViolActEthQueue
         INTEGER,
      er1646v2LacpBBwActViolActEthDrpLev
         INTEGER,
      er1646v2LacpBBwActViolActEthDeFlag
         INTEGER,
      er1646v2LacpBBwActViolActIpTos
         INTEGER,
      er1646v2LacpBBwActViolActIpQueue
         INTEGER,
      er1646v2LacpBBwActViolActIpDrpLev
         INTEGER,
      er1646v2LacpBBwActViolActIpDeFlag
         INTEGER
      }

er1646v2LacpBBwGlobalIx OBJECT-TYPE
   SYNTAX      GlobalIndex
   MAX-ACCESS  not-accessible
   STATUS      current
   DESCRIPTION
      "The value of the tlsCntTreeGlobalIndex of the MANAGED OBJECT."
   ::= {er1646v2LacpBBwEntry 10}

er1646v2LacpBBwMode OBJECT-TYPE
   SYNTAX      INTEGER
               {
               reshaping (1),
               policing (2),
               policingReshape (3)
               }
   MAX-ACCESS  read-write
   STATUS      current
   DESCRIPTION
      "Path: lacpBundle.editConf.bandwidth.mode

       Possibilities:
               reshaping   (1)
               policing   (2)
               policingReshape   (3)"
   ::= {er1646v2LacpBBwEntry 3758096384}

er1646v2LacpBBwCir OBJECT-TYPE
   SYNTAX      Integer32
   MAX-ACCESS  read-write
   STATUS      current
   DESCRIPTION
      "Path: lacpBundle.editConf.bandwidth.cir"
   ::= {er1646v2LacpBBwEntry 268435456}

er1646v2LacpBBwEir OBJECT-TYPE
   SYNTAX      Integer32
   MAX-ACCESS  read-write
   STATUS      current
   DESCRIPTION
      "Path: lacpBundle.editConf.bandwidth.eir"
   ::= {er1646v2LacpBBwEntry 1879048192}

er1646v2LacpBBwUnit OBJECT-TYPE
   SYNTAX      INTEGER
               {
               bitssec (1),
               percent (2)
               }
   MAX-ACCESS  read-write
   STATUS      current
   DESCRIPTION
      "Path: lacpBundle.editConf.bandwidth.unit

       Possibilities:
               bits/sec   (1)
               percent   (2)"
   ::= {er1646v2LacpBBwEntry 1342177280}

er1646v2LacpBBwTc OBJECT-TYPE
   SYNTAX      INTEGER
               {
               auto (0)
               }
   MAX-ACCESS  read-write
   STATUS      current
   DESCRIPTION
      "Path: lacpBundle.editConf.bandwidth.tc

       Possibilities:
               auto   (0)"
   ::= {er1646v2LacpBBwEntry 1610612736}

er1646v2LacpBBwTcFactor OBJECT-TYPE
   SYNTAX      INTEGER
               {
               ms (10),
               s100us (1)
               }
   MAX-ACCESS  read-write
   STATUS      current
   DESCRIPTION
      "Path: lacpBundle.editConf.bandwidth.tcFactor

       Possibilities:
               ms   (10)
               *100us   (1)"
   ::= {er1646v2LacpBBwEntry 2147483648}

er1646v2LacpBBwCorrType OBJECT-TYPE
   SYNTAX      INTEGER
               {
               noCorrection (0),
               predefined (1),
               manual (2)
               }
   MAX-ACCESS  read-write
   STATUS      current
   DESCRIPTION
      "Path: lacpBundle.editConf.bandwidth.correction.type

       Possibilities:
               noCorrection   (0)
               predefined   (1)
               manual   (2)"
   ::= {er1646v2LacpBBwEntry 570425344}

er1646v2LacpBBwCorrPredefEncapsFrameRelay OBJECT-TYPE
   SYNTAX      DisplayString
   MAX-ACCESS  read-write
   STATUS      current
   DESCRIPTION
      "Path: lacpBundle.editConf.bandwidth.correction.predefined.encapsulation.frameRelay"
   ::= {er1646v2LacpBBwEntry 608436224}

er1646v2LacpBBwCorrPredefEncapsPpp OBJECT-TYPE
   SYNTAX      DisplayString
   MAX-ACCESS  read-write
   STATUS      current
   DESCRIPTION
      "Path: lacpBundle.editConf.bandwidth.correction.predefined.encapsulation.ppp"
   ::= {er1646v2LacpBBwEntry 608698368}

er1646v2LacpBBwCorrPredefEncapsAtmHl OBJECT-TYPE
   SYNTAX      INTEGER
               {
               rfc2684 (0),
               ppp (1),
               pppOverEthernet (2)
               }
   MAX-ACCESS  read-write
   STATUS      current
   DESCRIPTION
      "Path: lacpBundle.editConf.bandwidth.correction.predefined.encapsulation.atm.higherLayer

       Possibilities:
               rfc2684   (0)
               ppp   (1)
               pppOverEthernet   (2)"
   ::= {er1646v2LacpBBwEntry 608993280}

er1646v2LacpBBwCorrPredefEncapsAtmMp OBJECT-TYPE
   SYNTAX      INTEGER
               {
               llcEncapsulation (0),
               vcMultiplexing (1)
               }
   MAX-ACCESS  read-write
   STATUS      current
   DESCRIPTION
      "Path: lacpBundle.editConf.bandwidth.correction.predefined.encapsulation.atm.multiProtocol

       Possibilities:
               llcEncapsulation   (0)
               vcMultiplexing   (1)"
   ::= {er1646v2LacpBBwEntry 609026048}

er1646v2LacpBBwCorrPredefEncapsHdlc OBJECT-TYPE
   SYNTAX      DisplayString
   MAX-ACCESS  read-write
   STATUS      current
   DESCRIPTION
      "Path: lacpBundle.editConf.bandwidth.correction.predefined.encapsulation.hdlc"
   ::= {er1646v2LacpBBwEntry 609222656}

er1646v2LacpBBwCorrPredefEncapsEfmFs OBJECT-TYPE
   SYNTAX      Integer32
   MAX-ACCESS  read-write
   STATUS      current
   DESCRIPTION
      "Path: lacpBundle.editConf.bandwidth.correction.predefined.encapsulation.efm.fragmentSize"
   ::= {er1646v2LacpBBwEntry 609517568}

er1646v2LacpBBwCorrPredefEncapsEfmIb OBJECT-TYPE
   SYNTAX      Integer32
   MAX-ACCESS  read-write
   STATUS      current
   DESCRIPTION
      "Path: lacpBundle.editConf.bandwidth.correction.predefined.encapsulation.efm.idleBytes"
   ::= {er1646v2LacpBBwEntry 609550336}

er1646v2LacpBBwCorrPredefMode OBJECT-TYPE
   SYNTAX      INTEGER
               {
               routing (0),
               bridging (1)
               }
   MAX-ACCESS  read-write
   STATUS      current
   DESCRIPTION
      "Path: lacpBundle.editConf.bandwidth.correction.predefined.mode

       Possibilities:
               routing   (0)
               bridging   (1)"
   ::= {er1646v2LacpBBwEntry 612368384}

er1646v2LacpBBwCorrManualOverhead OBJECT-TYPE
   SYNTAX      Integer32
   MAX-ACCESS  read-write
   STATUS      current
   DESCRIPTION
      "Path: lacpBundle.editConf.bandwidth.correction.manual.overhead"
   ::= {er1646v2LacpBBwEntry 637665280}

er1646v2LacpBBwCorrManualFrameData OBJECT-TYPE
   SYNTAX      Counter32
   MAX-ACCESS  read-write
   STATUS      current
   DESCRIPTION
      "Path: lacpBundle.editConf.bandwidth.correction.manual.frameData

       32 bit unsigned wrappable counter."
   ::= {er1646v2LacpBBwEntry 637796352}

er1646v2LacpBBwCorrManualFrameHeader OBJECT-TYPE
   SYNTAX      Counter32
   MAX-ACCESS  read-write
   STATUS      current
   DESCRIPTION
      "Path: lacpBundle.editConf.bandwidth.correction.manual.frameHeader

       32 bit unsigned wrappable counter."
   ::= {er1646v2LacpBBwEntry 637927424}

er1646v2LacpBBwMaxFifoQLen OBJECT-TYPE
   SYNTAX      Integer32
   MAX-ACCESS  read-write
   STATUS      current
   DESCRIPTION
      "Path: lacpBundle.editConf.bandwidth.maxFifoQLen"
   ::= {er1646v2LacpBBwEntry 805306368}

er1646v2LacpBBwDeFlagCir OBJECT-TYPE
   SYNTAX      INTEGER
               {
               allowed (1),
               notAllowed (2)
               }
   MAX-ACCESS  read-write
   STATUS      current
   DESCRIPTION
      "Path: lacpBundle.editConf.bandwidth.deFlag.cir

       Possibilities:
               allowed   (1)
               notAllowed   (2)"
   ::= {er1646v2LacpBBwEntry 3490709504}

er1646v2LacpBBwDeFlagEir OBJECT-TYPE
   SYNTAX      INTEGER
               {
               allowed (1),
               notAllowed (2)
               }
   MAX-ACCESS  read-write
   STATUS      current
   DESCRIPTION
      "Path: lacpBundle.editConf.bandwidth.deFlag.eir

       Possibilities:
               allowed   (1)
               notAllowed   (2)"
   ::= {er1646v2LacpBBwEntry 3491758080}

er1646v2LacpBBwDeFlagViolate OBJECT-TYPE
   SYNTAX      INTEGER
               {
               allowed (1),
               notAllowed (2)
               }
   MAX-ACCESS  read-write
   STATUS      current
   DESCRIPTION
      "Path: lacpBundle.editConf.bandwidth.deFlag.violate

       Possibilities:
               allowed   (1)
               notAllowed   (2)"
   ::= {er1646v2LacpBBwEntry 3492806656}

er1646v2LacpBBwActCirActNone OBJECT-TYPE
   SYNTAX      OCTET STRING
   MAX-ACCESS  read-write
   STATUS      current
   DESCRIPTION
      "Path: lacpBundle.editConf.bandwidth.action.cirAction.none"
   ::= {er1646v2LacpBBwEntry 4062183424}

er1646v2LacpBBwActCirActEthCos1 OBJECT-TYPE
   SYNTAX      INTEGER
               {
               unchanged (256)
               }
   MAX-ACCESS  read-write
   STATUS      current
   DESCRIPTION
      "Path: lacpBundle.editConf.bandwidth.action.cirAction.ethernet.cosDepth1

       Possibilities:
               unchanged   (256)"
   ::= {er1646v2LacpBBwEntry 4064346112}

er1646v2LacpBBwActCirActEthDei1 OBJECT-TYPE
   SYNTAX      INTEGER
               {
               unchanged (255),
               clear (0),
               set (1)
               }
   MAX-ACCESS  read-write
   STATUS      current
   DESCRIPTION
      "Path: lacpBundle.editConf.bandwidth.action.cirAction.ethernet.deiDepth1

       Possibilities:
               unchanged   (255)
               clear   (0)
               set   (1)"
   ::= {er1646v2LacpBBwEntry 4065656832}

er1646v2LacpBBwActCirActEthCos2 OBJECT-TYPE
   SYNTAX      INTEGER
               {
               unchanged (256)
               }
   MAX-ACCESS  read-write
   STATUS      current
   DESCRIPTION
      "Path: lacpBundle.editConf.bandwidth.action.cirAction.ethernet.cosDepth2

       Possibilities:
               unchanged   (256)"
   ::= {er1646v2LacpBBwEntry 4064411648}

er1646v2LacpBBwActCirActEthDei2 OBJECT-TYPE
   SYNTAX      INTEGER
               {
               unchanged (255),
               clear (0),
               set (1)
               }
   MAX-ACCESS  read-write
   STATUS      current
   DESCRIPTION
      "Path: lacpBundle.editConf.bandwidth.action.cirAction.ethernet.deiDepth2

       Possibilities:
               unchanged   (255)
               clear   (0)
               set   (1)"
   ::= {er1646v2LacpBBwEntry 4065722368}

er1646v2LacpBBwActCirActEthCos3 OBJECT-TYPE
   SYNTAX      INTEGER
               {
               unchanged (256)
               }
   MAX-ACCESS  read-write
   STATUS      current
   DESCRIPTION
      "Path: lacpBundle.editConf.bandwidth.action.cirAction.ethernet.cosDepth3

       Possibilities:
               unchanged   (256)"
   ::= {er1646v2LacpBBwEntry 4064477184}

er1646v2LacpBBwActCirActEthDei3 OBJECT-TYPE
   SYNTAX      INTEGER
               {
               unchanged (255),
               clear (0),
               set (1)
               }
   MAX-ACCESS  read-write
   STATUS      current
   DESCRIPTION
      "Path: lacpBundle.editConf.bandwidth.action.cirAction.ethernet.deiDepth3

       Possibilities:
               unchanged   (255)
               clear   (0)
               set   (1)"
   ::= {er1646v2LacpBBwEntry 4065787904}

er1646v2LacpBBwActCirActEthCos4 OBJECT-TYPE
   SYNTAX      INTEGER
               {
               unchanged (256)
               }
   MAX-ACCESS  read-write
   STATUS      current
   DESCRIPTION
      "Path: lacpBundle.editConf.bandwidth.action.cirAction.ethernet.cosDepth4

       Possibilities:
               unchanged   (256)"
   ::= {er1646v2LacpBBwEntry 4064542720}

er1646v2LacpBBwActCirActEthDei4 OBJECT-TYPE
   SYNTAX      INTEGER
               {
               unchanged (255),
               clear (0),
               set (1)
               }
   MAX-ACCESS  read-write
   STATUS      current
   DESCRIPTION
      "Path: lacpBundle.editConf.bandwidth.action.cirAction.ethernet.deiDepth4

       Possibilities:
               unchanged   (255)
               clear   (0)
               set   (1)"
   ::= {er1646v2LacpBBwEntry 4065853440}

er1646v2LacpBBwActCirActEthCos5 OBJECT-TYPE
   SYNTAX      INTEGER
               {
               unchanged (256)
               }
   MAX-ACCESS  read-write
   STATUS      current
   DESCRIPTION
      "Path: lacpBundle.editConf.bandwidth.action.cirAction.ethernet.cosDepth5

       Possibilities:
               unchanged   (256)"
   ::= {er1646v2LacpBBwEntry 4064608256}

er1646v2LacpBBwActCirActEthDei5 OBJECT-TYPE
   SYNTAX      INTEGER
               {
               unchanged (255),
               clear (0),
               set (1)
               }
   MAX-ACCESS  read-write
   STATUS      current
   DESCRIPTION
      "Path: lacpBundle.editConf.bandwidth.action.cirAction.ethernet.deiDepth5

       Possibilities:
               unchanged   (255)
               clear   (0)
               set   (1)"
   ::= {er1646v2LacpBBwEntry 4065918976}

er1646v2LacpBBwActCirActEthCos6 OBJECT-TYPE
   SYNTAX      INTEGER
               {
               unchanged (256)
               }
   MAX-ACCESS  read-write
   STATUS      current
   DESCRIPTION
      "Path: lacpBundle.editConf.bandwidth.action.cirAction.ethernet.cosDepth6

       Possibilities:
               unchanged   (256)"
   ::= {er1646v2LacpBBwEntry 4064673792}

er1646v2LacpBBwActCirActEthDei6 OBJECT-TYPE
   SYNTAX      INTEGER
               {
               unchanged (255),
               clear (0),
               set (1)
               }
   MAX-ACCESS  read-write
   STATUS      current
   DESCRIPTION
      "Path: lacpBundle.editConf.bandwidth.action.cirAction.ethernet.deiDepth6

       Possibilities:
               unchanged   (255)
               clear   (0)
               set   (1)"
   ::= {er1646v2LacpBBwEntry 4065984512}

er1646v2LacpBBwActCirActEthCos7 OBJECT-TYPE
   SYNTAX      INTEGER
               {
               unchanged (256)
               }
   MAX-ACCESS  read-write
   STATUS      current
   DESCRIPTION
      "Path: lacpBundle.editConf.bandwidth.action.cirAction.ethernet.cosDepth7

       Possibilities:
               unchanged   (256)"
   ::= {er1646v2LacpBBwEntry 4064739328}

er1646v2LacpBBwActCirActEthDei7 OBJECT-TYPE
   SYNTAX      INTEGER
               {
               unchanged (255),
               clear (0),
               set (1)
               }
   MAX-ACCESS  read-write
   STATUS      current
   DESCRIPTION
      "Path: lacpBundle.editConf.bandwidth.action.cirAction.ethernet.deiDepth7

       Possibilities:
               unchanged   (255)
               clear   (0)
               set   (1)"
   ::= {er1646v2LacpBBwEntry 4066050048}

er1646v2LacpBBwActCirActEthCos8 OBJECT-TYPE
   SYNTAX      INTEGER
               {
               unchanged (256)
               }
   MAX-ACCESS  read-write
   STATUS      current
   DESCRIPTION
      "Path: lacpBundle.editConf.bandwidth.action.cirAction.ethernet.cosDepth8

       Possibilities:
               unchanged   (256)"
   ::= {er1646v2LacpBBwEntry 4064804864}

er1646v2LacpBBwActCirActEthDei8 OBJECT-TYPE
   SYNTAX      INTEGER
               {
               unchanged (255),
               clear (0),
               set (1)
               }
   MAX-ACCESS  read-write
   STATUS      current
   DESCRIPTION
      "Path: lacpBundle.editConf.bandwidth.action.cirAction.ethernet.deiDepth8

       Possibilities:
               unchanged   (255)
               clear   (0)
               set   (1)"
   ::= {er1646v2LacpBBwEntry 4066115584}

er1646v2LacpBBwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: lacpBundle.editConf.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2LacpBBwEntry 4064870400}

er1646v2LacpBBwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: lacpBundle.editConf.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2LacpBBwEntry 4064935936}

er1646v2LacpBBwActCirActEthDrpLev OBJECT-TYPE
   SYNTAX      INTEGER
               {
               unchanged (0)
               }
   MAX-ACCESS  read-write
   STATUS      current
   DESCRIPTION
      "Path: lacpBundle.editConf.bandwidth.action.cirAction.ethernet.dropLevel

       Possibilities:
               unchanged   (0)"
   ::= {er1646v2LacpBBwEntry 4065001472}

er1646v2LacpBBwActCirActEthDeFlag OBJECT-TYPE
   SYNTAX      INTEGER
               {
               unchanged (255),
               clear (0),
               set (1)
               }
   MAX-ACCESS  read-write
   STATUS      current
   DESCRIPTION
      "Path: lacpBundle.editConf.bandwidth.action.cirAction.ethernet.deFlag

       Possibilities:
               unchanged   (255)
               clear   (0)
               set   (1)"
   ::= {er1646v2LacpBBwEntry 4065198080}

er1646v2LacpBBwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: lacpBundle.editConf.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2LacpBBwEntry 4071161856}

er1646v2LacpBBwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: lacpBundle.editConf.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2LacpBBwEntry 4071227392}

er1646v2LacpBBwActCirActIpDrpLev OBJECT-TYPE
   SYNTAX      INTEGER
               {
               unchanged (0)
               }
   MAX-ACCESS  read-write
   STATUS      current
   DESCRIPTION
      "Path: lacpBundle.editConf.bandwidth.action.cirAction.ip.dropLevel

       Possibilities:
               unchanged   (0)"
   ::= {er1646v2LacpBBwEntry 4071292928}

er1646v2LacpBBwActCirActIpDeFlag OBJECT-TYPE
   SYNTAX      INTEGER
               {
               unchanged (255),
               clear (0),
               set (1)
               }
   MAX-ACCESS  read-write
   STATUS      current
   DESCRIPTION
      "Path: lacpBundle.editConf.bandwidth.action.cirAction.ip.deFlag

       Possibilities:
               unchanged   (255)
               clear   (0)
               set   (1)"
   ::= {er1646v2LacpBBwEntry 4071489536}

er1646v2LacpBBwActEirActNone OBJECT-TYPE
   SYNTAX      OCTET STRING
   MAX-ACCESS  read-write
   STATUS      current
   DESCRIPTION
      "Path: lacpBundle.editConf.bandwidth.action.eirAction.none"
   ::= {er1646v2LacpBBwEntry 4095737856}

er1646v2LacpBBwActEirActEthCos1 OBJECT-TYPE
   SYNTAX      INTEGER
               {
               unchanged (256)
               }
   MAX-ACCESS  read-write
   STATUS      current
   DESCRIPTION
      "Path: lacpBundle.editConf.bandwidth.action.eirAction.ethernet.cosDepth1

       Possibilities:
               unchanged   (256)"
   ::= {er1646v2LacpBBwEntry 4097900544}

er1646v2LacpBBwActEirActEthDei1 OBJECT-TYPE
   SYNTAX      INTEGER
               {
               unchanged (255),
               clear (0),
               set (1)
               }
   MAX-ACCESS  read-write
   STATUS      current
   DESCRIPTION
      "Path: lacpBundle.editConf.bandwidth.action.eirAction.ethernet.deiDepth1

       Possibilities:
               unchanged   (255)
               clear   (0)
               set   (1)"
   ::= {er1646v2LacpBBwEntry 4099211264}

er1646v2LacpBBwActEirActEthCos2 OBJECT-TYPE
   SYNTAX      INTEGER
               {
               unchanged (256)
               }
   MAX-ACCESS  read-write
   STATUS      current
   DESCRIPTION
      "Path: lacpBundle.editConf.bandwidth.action.eirAction.ethernet.cosDepth2

       Possibilities:
               unchanged   (256)"
   ::= {er1646v2LacpBBwEntry 4097966080}

er1646v2LacpBBwActEirActEthDei2 OBJECT-TYPE
   SYNTAX      INTEGER
               {
               unchanged (255),
               clear (0),
               set (1)
               }
   MAX-ACCESS  read-write
   STATUS      current
   DESCRIPTION
      "Path: lacpBundle.editConf.bandwidth.action.eirAction.ethernet.deiDepth2

       Possibilities:
               unchanged   (255)
               clear   (0)
               set   (1)"
   ::= {er1646v2LacpBBwEntry 4099276800}

er1646v2LacpBBwActEirActEthCos3 OBJECT-TYPE
   SYNTAX      INTEGER
               {
               unchanged (256)
               }
   MAX-ACCESS  read-write
   STATUS      current
   DESCRIPTION
      "Path: lacpBundle.editConf.bandwidth.action.eirAction.ethernet.cosDepth3

       Possibilities:
               unchanged   (256)"
   ::= {er1646v2LacpBBwEntry 4098031616}

er1646v2LacpBBwActEirActEthDei3 OBJECT-TYPE
   SYNTAX      INTEGER
               {
               unchanged (255),
               clear (0),
               set (1)
               }
   MAX-ACCESS  read-write
   STATUS      current
   DESCRIPTION
      "Path: lacpBundle.editConf.bandwidth.action.eirAction.ethernet.deiDepth3

       Possibilities:
               unchanged   (255)
               clear   (0)
               set   (1)"
   ::= {er1646v2LacpBBwEntry 4099342336}

er1646v2LacpBBwActEirActEthCos4 OBJECT-TYPE
   SYNTAX      INTEGER
               {
               unchanged (256)
               }
   MAX-ACCESS  read-write
   STATUS      current
   DESCRIPTION
      "Path: lacpBundle.editConf.bandwidth.action.eirAction.ethernet.cosDepth4

       Possibilities:
               unchanged   (256)"
   ::= {er1646v2LacpBBwEntry 4098097152}

er1646v2LacpBBwActEirActEthDei4 OBJECT-TYPE
   SYNTAX      INTEGER
               {
               unchanged (255),
               clear (0),
               set (1)
               }
   MAX-ACCESS  read-write
   STATUS      current
   DESCRIPTION
      "Path: lacpBundle.editConf.bandwidth.action.eirAction.ethernet.deiDepth4

       Possibilities:
               unchanged   (255)
               clear   (0)
               set   (1)"
   ::= {er1646v2LacpBBwEntry 4099407872}

er1646v2LacpBBwActEirActEthCos5 OBJECT-TYPE
   SYNTAX      INTEGER
               {
               unchanged (256)
               }
   MAX-ACCESS  read-write
   STATUS      current
   DESCRIPTION
      "Path: lacpBundle.editConf.bandwidth.action.eirAction.ethernet.cosDepth5

       Possibilities:
               unchanged   (256)"
   ::= {er1646v2LacpBBwEntry 4098162688}

er1646v2LacpBBwActEirActEthDei5 OBJECT-TYPE
   SYNTAX      INTEGER
               {
               unchanged (255),
               clear (0),
               set (1)
               }
   MAX-ACCESS  read-write
   STATUS      current
   DESCRIPTION
      "Path: lacpBundle.editConf.bandwidth.action.eirAction.ethernet.deiDepth5

       Possibilities:
               unchanged   (255)
               clear   (0)
               set   (1)"
   ::= {er1646v2LacpBBwEntry 4099473408}

er1646v2LacpBBwActEirActEthCos6 OBJECT-TYPE
   SYNTAX      INTEGER
               {
               unchanged (256)
               }
   MAX-ACCESS  read-write
   STATUS      current
   DESCRIPTION
      "Path: lacpBundle.editConf.bandwidth.action.eirAction.ethernet.cosDepth6

       Possibilities:
               unchanged   (256)"
   ::= {er1646v2LacpBBwEntry 4098228224}

er1646v2LacpBBwActEirActEthDei6 OBJECT-TYPE
   SYNTAX      INTEGER
               {
               unchanged (255),
               clear (0),
               set (1)
               }
   MAX-ACCESS  read-write
   STATUS      current
   DESCRIPTION
      "Path: lacpBundle.editConf.bandwidth.action.eirAction.ethernet.deiDepth6

       Possibilities:
               unchanged   (255)
               clear   (0)
               set   (1)"
   ::= {er1646v2LacpBBwEntry 4099538944}

er1646v2LacpBBwActEirActEthCos7 OBJECT-TYPE
   SYNTAX      INTEGER
               {
               unchanged (256)
               }
   MAX-ACCESS  read-write
   STATUS      current
   DESCRIPTION
      "Path: lacpBundle.editConf.bandwidth.action.eirAction.ethernet.cosDepth7

       Possibilities:
               unchanged   (256)"
   ::= {er1646v2LacpBBwEntry 4098293760}

er1646v2LacpBBwActEirActEthDei7 OBJECT-TYPE
   SYNTAX      INTEGER
               {
               unchanged (255),
               clear (0),
               set (1)
               }
   MAX-ACCESS  read-write
   STATUS      current
   DESCRIPTION
      "Path: lacpBundle.editConf.bandwidth.action.eirAction.ethernet.deiDepth7

       Possibilities:
               unchanged   (255)
               clear   (0)
               set   (1)"
   ::= {er1646v2LacpBBwEntry 4099604480}

er1646v2LacpBBwActEirActEthCos8 OBJECT-TYPE
   SYNTAX      INTEGER
               {
               unchanged (256)
               }
   MAX-ACCESS  read-write
   STATUS      current
   DESCRIPTION
      "Path: lacpBundle.editConf.bandwidth.action.eirAction.ethernet.cosDepth8

       Possibilities:
               unchanged   (256)"
   ::= {er1646v2LacpBBwEntry 4098359296}

er1646v2LacpBBwActEirActEthDei8 OBJECT-TYPE
   SYNTAX      INTEGER
               {
               unchanged (255),
               clear (0),
               set (1)
               }
   MAX-ACCESS  read-write
   STATUS      current
   DESCRIPTION
      "Path: lacpBundle.editConf.bandwidth.action.eirAction.ethernet.deiDepth8

       Possibilities:
               unchanged   (255)
               clear   (0)
               set   (1)"
   ::= {er1646v2LacpBBwEntry 4099670016}

er1646v2LacpBBwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: lacpBundle.editConf.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2LacpBBwEntry 4098424832}

er1646v2LacpBBwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: lacpBundle.editConf.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2LacpBBwEntry 4098490368}

er1646v2LacpBBwActEirActEthDrpLev OBJECT-TYPE
   SYNTAX      INTEGER
               {
               unchanged (0)
               }
   MAX-ACCESS  read-write
   STATUS      current
   DESCRIPTION
      "Path: lacpBundle.editConf.bandwidth.action.eirAction.ethernet.dropLevel

       Possibilities:
               unchanged   (0)"
   ::= {er1646v2LacpBBwEntry 4098555904}

er1646v2LacpBBwActEirActEthDeFlag OBJECT-TYPE
   SYNTAX      INTEGER
               {
               unchanged (255),
               clear (0),
               set (1)
               }
   MAX-ACCESS  read-write
   STATUS      current
   DESCRIPTION
      "Path: lacpBundle.editConf.bandwidth.action.eirAction.ethernet.deFlag

       Possibilities:
               unchanged   (255)
               clear   (0)
               set   (1)"
   ::= {er1646v2LacpBBwEntry 4098752512}

er1646v2LacpBBwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: lacpBundle.editConf.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2LacpBBwEntry 4104716288}

er1646v2LacpBBwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: lacpBundle.editConf.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2LacpBBwEntry 4104781824}

er1646v2LacpBBwActEirActIpDrpLev OBJECT-TYPE
   SYNTAX      INTEGER
               {
               unchanged (0)
               }
   MAX-ACCESS  read-write
   STATUS      current
   DESCRIPTION
      "Path: lacpBundle.editConf.bandwidth.action.eirAction.ip.dropLevel

       Possibilities:
               unchanged   (0)"
   ::= {er1646v2LacpBBwEntry 4104847360}

er1646v2LacpBBwActEirActIpDeFlag OBJECT-TYPE
   SYNTAX      INTEGER
               {
               unchanged (255),
               clear (0),
               set (1)
               }
   MAX-ACCESS  read-write
   STATUS      current
   DESCRIPTION
      "Path: lacpBundle.editConf.bandwidth.action.eirAction.ip.deFlag

       Possibilities:
               unchanged   (255)
               clear   (0)
               set   (1)"
   ::= {er1646v2LacpBBwEntry 4105043968}

er1646v2LacpBBwActViolActNone OBJECT-TYPE
   SYNTAX      OCTET STRING
   MAX-ACCESS  read-write
   STATUS      current
   DESCRIPTION
      "Path: lacpBundle.editConf.bandwidth.action.violateAction.none"
   ::= {er1646v2LacpBBwEntry 4129292288}

er1646v2LacpBBwActViolActDrop OBJECT-TYPE
   SYNTAX      OCTET STRING
   MAX-ACCESS  read-write
   STATUS      current
   DESCRIPTION
      "Path: lacpBundle.editConf.bandwidth.action.violateAction.drop"
   ::= {er1646v2LacpBBwEntry 4133486592}

er1646v2LacpBBwActViolActEthCos1 OBJECT-TYPE
   SYNTAX      INTEGER
               {
               unchanged (256)
               }
   MAX-ACCESS  read-write
   STATUS      current
   DESCRIPTION
      "Path: lacpBundle.editConf.bandwidth.action.violateAction.ethernet.cosDepth1

       Possibilities:
               unchanged   (256)"
   ::= {er1646v2LacpBBwEntry 4131454976}

er1646v2LacpBBwActViolActEthDei1 OBJECT-TYPE
   SYNTAX      INTEGER
               {
               unchanged (255),
               clear (0),
               set (1)
               }
   MAX-ACCESS  read-write
   STATUS      current
   DESCRIPTION
      "Path: lacpBundle.editConf.bandwidth.action.violateAction.ethernet.deiDepth1

       Possibilities:
               unchanged   (255)
               clear   (0)
               set   (1)"
   ::= {er1646v2LacpBBwEntry 4132765696}

er1646v2LacpBBwActViolActEthCos2 OBJECT-TYPE
   SYNTAX      INTEGER
               {
               unchanged (256)
               }
   MAX-ACCESS  read-write
   STATUS      current
   DESCRIPTION
      "Path: lacpBundle.editConf.bandwidth.action.violateAction.ethernet.cosDepth2

       Possibilities:
               unchanged   (256)"
   ::= {er1646v2LacpBBwEntry 4131520512}

er1646v2LacpBBwActViolActEthDei2 OBJECT-TYPE
   SYNTAX      INTEGER
               {
               unchanged (255),
               clear (0),
               set (1)
               }
   MAX-ACCESS  read-write
   STATUS      current
   DESCRIPTION
      "Path: lacpBundle.editConf.bandwidth.action.violateAction.ethernet.deiDepth2

       Possibilities:
               unchanged   (255)
               clear   (0)
               set   (1)"
   ::= {er1646v2LacpBBwEntry 4132831232}

er1646v2LacpBBwActViolActEthCos3 OBJECT-TYPE
   SYNTAX      INTEGER
               {
               unchanged (256)
               }
   MAX-ACCESS  read-write
   STATUS      current
   DESCRIPTION
      "Path: lacpBundle.editConf.bandwidth.action.violateAction.ethernet.cosDepth3

       Possibilities:
               unchanged   (256)"
   ::= {er1646v2LacpBBwEntry 4131586048}

er1646v2LacpBBwActViolActEthDei3 OBJECT-TYPE
   SYNTAX      INTEGER
               {
               unchanged (255),
               clear (0),
               set (1)
               }
   MAX-ACCESS  read-write
   STATUS      current
   DESCRIPTION
      "Path: lacpBundle.editConf.bandwidth.action.violateAction.ethernet.deiDepth3

       Possibilities:
               unchanged   (255)
               clear   (0)
               set   (1)"
   ::= {er1646v2LacpBBwEntry 4132896768}

er1646v2LacpBBwActViolActEthCos4 OBJECT-TYPE
   SYNTAX      INTEGER
               {
               unchanged (256)
               }
   MAX-ACCESS  read-write
   STATUS      current
   DESCRIPTION
      "Path: lacpBundle.editConf.bandwidth.action.violateAction.ethernet.cosDepth4

       Possibilities:
               unchanged   (256)"
   ::= {er1646v2LacpBBwEntry 4131651584}

er1646v2LacpBBwActViolActEthDei4 OBJECT-TYPE
   SYNTAX      INTEGER
               {
               unchanged (255),
               clear (0),
               set (1)
               }
   MAX-ACCESS  read-write
   STATUS      current
   DESCRIPTION
      "Path: lacpBundle.editConf.bandwidth.action.violateAction.ethernet.deiDepth4

       Possibilities:
               unchanged   (255)
               clear   (0)
               set   (1)"
   ::= {er1646v2LacpBBwEntry 4132962304}

er1646v2LacpBBwActViolActEthCos5 OBJECT-TYPE
   SYNTAX      INTEGER
               {
               unchanged (256)
               }
   MAX-ACCESS  read-write
   STATUS      current
   DESCRIPTION
      "Path: lacpBundle.editConf.bandwidth.action.violateAction.ethernet.cosDepth5

       Possibilities:
               unchanged   (256)"
   ::= {er1646v2LacpBBwEntry 4131717120}

er1646v2LacpBBwActViolActEthDei5 OBJECT-TYPE
   SYNTAX      INTEGER
               {
               unchanged (255),
               clear (0),
               set (1)
               }
   MAX-ACCESS  read-write
   STATUS      current
   DESCRIPTION
      "Path: lacpBundle.editConf.bandwidth.action.violateAction.ethernet.deiDepth5

       Possibilities:
               unchanged   (255)
               clear   (0)
               set   (1)"
   ::= {er1646v2LacpBBwEntry 4133027840}

er1646v2LacpBBwActViolActEthCos6 OBJECT-TYPE
   SYNTAX      INTEGER
               {
               unchanged (256)
               }
   MAX-ACCESS  read-write
   STATUS      current
   DESCRIPTION
      "Path: lacpBundle.editConf.bandwidth.action.violateAction.ethernet.cosDepth6

       Possibilities:
               unchanged   (256)"
   ::= {er1646v2LacpBBwEntry 4131782656}

er1646v2LacpBBwActViolActEthDei6 OBJECT-TYPE
   SYNTAX      INTEGER
               {
               unchanged (255),
               clear (0),
               set (1)
               }
   MAX-ACCESS  read-write
   STATUS      current
   DESCRIPTION
      "Path: lacpBundle.editConf.bandwidth.action.violateAction.ethernet.deiDepth6

       Possibilities:
               unchanged   (255)
               clear   (0)
               set   (1)"
   ::= {er1646v2LacpBBwEntry 4133093376}

er1646v2LacpBBwActViolActEthCos7 OBJECT-TYPE
   SYNTAX      INTEGER
               {
               unchanged (256)
               }
   MAX-ACCESS  read-write
   STATUS      current
   DESCRIPTION
      "Path: lacpBundle.editConf.bandwidth.action.violateAction.ethernet.cosDepth7

       Possibilities:
               unchanged   (256)"
   ::= {er1646v2LacpBBwEntry 4131848192}

er1646v2LacpBBwActViolActEthDei7 OBJECT-TYPE
   SYNTAX      INTEGER
               {
               unchanged (255),
               clear (0),
               set (1)
               }
   MAX-ACCESS  read-write
   STATUS      current
   DESCRIPTION
      "Path: lacpBundle.editConf.bandwidth.action.violateAction.ethernet.deiDepth7

       Possibilities:
               unchanged   (255)
               clear   (0)
               set   (1)"
   ::= {er1646v2LacpBBwEntry 4133158912}

er1646v2LacpBBwActViolActEthCos8 OBJECT-TYPE
   SYNTAX      INTEGER
               {
               unchanged (256)
               }
   MAX-ACCESS  read-write
   STATUS      current
   DESCRIPTION
      "Path: lacpBundle.editConf.bandwidth.action.violateAction.ethernet.cosDepth8

       Possibilities:
               unchanged   (256)"
   ::= {er1646v2LacpBBwEntry 4131913728}

er1646v2LacpBBwActViolActEthDei8 OBJECT-TYPE
   SYNTAX      INTEGER
               {
               unchanged (255),
               clear (0),
               set (1)
               }
   MAX-ACCESS  read-write
   STATUS      current
   DESCRIPTION
      "Path: lacpBundle.editConf.bandwidth.action.violateAction.ethernet.deiDepth8

       Possibilities:
               unchanged   (255)
               clear   (0)
               set   (1)"
   ::= {er1646v2LacpBBwEntry 4133224448}

er1646v2LacpBBwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: lacpBundle.editConf.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2LacpBBwEntry 4131979264}

er1646v2LacpBBwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: lacpBundle.editConf.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2LacpBBwEntry 4132044800}

er1646v2LacpBBwActViolActEthDrpLev OBJECT-TYPE
   SYNTAX      INTEGER
               {
               unchanged (0)
               }
   MAX-ACCESS  read-write
   STATUS      current
   DESCRIPTION
      "Path: lacpBundle.editConf.bandwidth.action.violateAction.ethernet.dropLevel

       Possibilities:
               unchanged   (0)"
   ::= {er1646v2LacpBBwEntry 4132110336}

er1646v2LacpBBwActViolActEthDeFlag OBJECT-TYPE
   SYNTAX      INTEGER
               {
               unchanged (255),
               clear (0),
               set (1)
               }
   MAX-ACCESS  read-write
   STATUS      current
   DESCRIPTION
      "Path: lacpBundle.editConf.bandwidth.action.violateAction.ethernet.deFlag

       Possibilities:
               unchanged   (255)
               clear   (0)
               set   (1)"
   ::= {er1646v2LacpBBwEntry 4132306944}

er1646v2LacpBBwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: lacpBundle.editConf.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2LacpBBwEntry 4138270720}

er1646v2LacpBBwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: lacpBundle.editConf.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1646v2LacpBBwEntry 4138336256}

er1646v2LacpBBwActViolActIpDrpLev OBJECT-TYPE
   SYNTAX      INTEGER
               {
               unchanged (0)
               }
   MAX-ACCESS  read-write
   STATUS      current
   DESCRIPTION
      "Path: lacpBundle.editConf.bandwidth.action.violateAction.ip.dropLevel

       Possibilities:
               unchanged   (0)"
   ::= {er1646v2LacpBBwEntry 4138401792}

er1646v2LacpBBwActViolActIpDeFlag OBJECT-TYPE
   SYNTAX      INTEGER
               {
               unchanged (255),
               clear (0),
               set (1)
               }
   MAX-ACCESS  read-write
   STATUS      current
   DESCRIPTION
      "Path: lacpBundle.editConf.bandwidth.action.violateAction.ip.deFlag

       Possibilities:
               unchanged   (255)
               clear   (0)
               set   (1)"
   ::= {er1646v2LacpBBwEntry 4138598400}


er1646v2LacpBIbw OBJECT IDENTIFIER ::= {er1646v2LacpB 13}

er1646v2LacpBIbwSSCTable OBJECT-TYPE
   SYNTAX      SEQUENCE OF Er1646v2LacpBIbwEntry
   MAX-ACCESS  not-accessible
   STATUS      current
   DESCRIPTION
      ""
   ::= {er1646v2LacpBIbw 1}

er1646v2LacpBIbwEntry OBJECT-TYPE
   SYNTAX      Er1646v2LacpBIbwEntry
   MAX-ACCESS  not-accessible
   STATUS      current
   DESCRIPTION
      ""
   INDEX      { er1646v2LacpBIbwGlobalIx }
   ::= {er1646v2LacpBIbwSSCTable 1}

Er1646v2LacpBIbwEntry ::=
   SEQUENCE
      {
      er1646v2LacpBIbwGlobalIx
         GlobalIndex,
      er1646v2LacpBIbwMode
         INTEGER,
      er1646v2LacpBIbwCir
         Integer32,
      er1646v2LacpBIbwEir
         Integer32,
      er1646v2LacpBIbwUnit
         INTEGER,
      er1646v2LacpBIbwTc
         INTEGER,
      er1646v2LacpBIbwTcFactor
         INTEGER,
      er1646v2LacpBIbwCorrType
         INTEGER,
      er1646v2LacpBIbwCorrPredefEncapsFrameRelay
         DisplayString,
      er1646v2LacpBIbwCorrPredefEncapsPpp
         DisplayString,
      er1646v2LacpBIbwCorrPredefEncapsAtmHl
         INTEGER,
      er1646v2LacpBIbwCorrPredefEncapsAtmMp
         INTEGER,
      er1646v2LacpBIbwCorrPredefEncapsHdlc
         DisplayString,
      er1646v2LacpBIbwCorrPredefEncapsEfmFs
         Integer32,
      er1646v2LacpBIbwCorrPredefEncapsEfmIb
         Integer32,
      er1646v2LacpBIbwCorrPredefMode
         INTEGER,
      er1646v2LacpBIbwCorrManualOverhead
         Integer32,
      er1646v2LacpBIbwCorrManualFrameData
         Counter32,
      er1646v2LacpBIbwCorrManualFrameHeader
         Counter32,
      er1646v2LacpBIbwMaxFifoQLen
         Integer32,
      er1646v2LacpBIbwPriorityPolicy
         DisplayString,
      er1646v2LacpBIbwDeFlagCir
         INTEGER,
      er1646v2LacpBIbwDeFlagEir
         INTEGER,
      er1646v2LacpBIbwDeFlagViolate
         INTEGER,
      er1646v2LacpBIbwActCirActNone
         OCTET STRING,
      er1646v2LacpBIbwActCirActEthCos1
         INTEGER,
      er1646v2LacpBIbwActCirActEthDei1
         INTEGER,
      er1646v2LacpBIbwActCirActEthCos2
         INTEGER,
      er1646v2LacpBIbwActCirActEthDei2
         INTEGER,
      er1646v2LacpBIbwActCirActEthCos3
         INTEGER,
      er1646v2LacpBIbwActCirActEthDei3
         INTEGER,
      er1646v2LacpBIbwActCirActEthCos4
         INTEGER,
      er1646v2LacpBIbwActCirActEthDei4
         INTEGER,
      er1646v2LacpBIbwActCirActEthCos5
         INTEGER,
      er1646v2LacpBIbwActCirActEthDei5
         INTEGER,
      er1646v2LacpBIbwActCirActEthCos6
         INTEGER,
      er1646v2LacpBIbwActCirActEthDei6
         INTEGER,
      er1646v2LacpBIbwActCirActEthCos7
         INTEGER,
      er1646v2LacpBIbwActCirActEthDei7
         INTEGER,
      er1646v2LacpBIbwActCirActEthCos8
         INTEGER,
      er1646v2LacpBIbwActCirActEthDei8
         INTEGER,
      er1646v2LacpBIbwActCirActEthTos
         INTEGER,
      er1646v2LacpBIbwActCirActEthQueue
         INTEGER,
      er1646v2LacpBIbwActCirActEthDrpLev
         INTEGER,
      er1646v2LacpBIbwActCirActEthDeFlag
         INTEGER,
      er1646v2LacpBIbwActCirActIpTos
         INTEGER,
      er1646v2LacpBIbwActCirActIpQueue
         INTEGER,
      er1646v2LacpBIbwActCirActIpDrpLev
         INTEGER,
      er1646v2LacpBIbwActCirActIpDeFlag
         INTEGER,
      er1646v2LacpBIbwActEirActNone
         OCTET STRING,
      er1646v2LacpBIbwActEirActEthCos1
         INTEGER,
      er1646v2LacpBIbwActEirActEthDei1
         INTEGER,
      er1646v2LacpBIbwActEirActEthCos2
         INTEGER,
      er1646v2LacpBIbwActEirActEthDei2
         INTEGER,
      er1646v2LacpBIbwActEirActEthCos3
         INTEGER,
      er1646v2LacpBIbwActEirActEthDei3
         INTEGER,
      er1646v2LacpBIbwActEirActEthCos4
         INTEGER,
      er1646v2LacpBIbwActEirActEthDei4
         INTEGER,
      er1646v2LacpBIbwActEirActEthCos5
         INTEGER,
      er1646v2LacpBIbwActEirActEthDei5
         INTEGER,
      er1646v2LacpBIbwActEirActEthCos6
         INTEGER,
      er1646v2LacpBIbwActEirActEthDei6
         INTEGER,
      er1646v2LacpBIbwActEirActEthCos7
         INTEGER,
      er1646v2LacpBIbwActEirActEthDei7
         INTEGER,
      er1646v2LacpBIbwActEirActEthCos8
         INTEGER,
      er1646v2LacpBIbwActEirActEthDei8
         INTEGER,
      er1646v2LacpBIbwActEirActEthTos
         INTEGER,
      er1646v2LacpBIbwActEirActEthQueue
         INTEGER,
      er1646v2LacpBIbwActEirActEthDrpLev
         INTEGER,
      er1646v2LacpBIbwActEirActEthDeFlag
         INTEGER,
      er1646v2LacpBIbwActEirActIpTos
         INTEGER,
      er1646v2LacpBIbwActEirActIpQueue
         INTEGER,
      er1646v2LacpBIbwActEirActIpDrpLev
         INTEGER,
      er1646v2LacpBIbwActEirActIpDeFlag
         INTEGER,
      er1646v2LacpBIbwActViolActNone
         OCTET STRING,
      er1646v2LacpBIbwActViolActDrop
         OCTET STRING,
      er1646v2LacpBIbwActViolActEthCos1
         INTEGER,
      er1646v2LacpBIbwActViolActEthDei1
         INTEGER,
      er1646v2LacpBIbwActViolActEthCos2
         INTEGER,
      er1646v2LacpBIbwActViolActEthDei2
         INTEGER,
      er1646v2LacpBIbwActViolActEthCos3
         INTEGER,
      er1646v2LacpBIbwActViolActEthDei3
         INTEGER,
      er1646v2LacpBIbwActViolActEthCos4
         INTEGER,
      er1646v2LacpBIbwActViolActEthDei4
         INTEGER,
      er1646v2LacpBIbwActViolActEthCos5
         INTEGER,
      er1646v2LacpBIbwActViolActEthDei5
         INTEGER,
      er1646v2LacpBIbwActViolActEthCos6
         INTEGER,
      er1646v2LacpBIbwActViolActEthDei6
         INTEGER,
      er1646v2LacpBIbwActViolActEthCos7
         INTEGER,
      er1646v2LacpBIbwActViolActEthDei7
         INTEGER,
      er1646v2LacpBIbwActViolActEthCos8
         INTEGER,
      er1646v2LacpBIbwActViolActEthDei8
         INTEGER,
      er1646v2LacpBIbwActViolActEthTos
         INTEGER,
      er1646v2LacpBIbwActViolActEthQueue
         INTEGER,
      er1646v2LacpBIbwActViolActEthDrpLev
         INTEGER,
      er1646v2LacpBIbwActViolActEthDeFlag
         INTEGER,
      er1646v2LacpBIbwActViolActIpTos
         INTEGER,
      er1646v2LacpBIbwActViolActIpQueue
         INTEGER,
      er1646v2LacpBIbwActViolActIpDrpLev
         INTEGER,
      er1646v2LacpBIbwActViolActIpDeFlag
         INTEGER
      }

er1646v2LacpBIbwGlobalIx OBJECT-TYPE
   SYNTAX      GlobalIndex
   MAX-ACCESS  not-accessible
   STATUS      current
   DESCRIPTION
      "The value of the tlsCntTreeGlobalIndex of the MANAGED OBJECT."
   ::= {er1646v2LacpBIbwEntry 10}

er1646v2LacpBIbwMode OBJECT-TYPE
   SYNTAX      INTEGER
               {
               reshaping (1),
               policing (2)
               }
   MAX-ACCESS  read-write
   STATUS      current
   DESCRIPTION
      "Path: lacpBundle.editConf.inboundBandwidth.mode

       Possibilities:
               reshaping   (1)
               policing   (2)"
   ::= {er1646v2LacpBIbwEntry 3758096384}

er1646v2LacpBIbwCir OBJECT-TYPE
   SYNTAX      Integer32
   MAX-ACCESS  read-write
   STATUS      current
   DESCRIPTION
      "Path: lacpBundle.editConf.inboundBandwidth.cir"
   ::= {er1646v2LacpBIbwEntry 268435456}

er1646v2LacpBIbwEir OBJECT-TYPE
   SYNTAX      Integer32
   MAX-ACCESS  read-write
   STATUS      current
   DESCRIPTION
      "Path: lacpBundle.editConf.inboundBandwidth.eir"
   ::= {er1646v2LacpBIbwEntry 1879048192}

er1646v2LacpBIbwUnit OBJECT-TYPE
   SYNTAX      INTEGER
               {
               bitssec (1),
               percent (2)
               }
   MAX-ACCESS  read-write
   STATUS      current
   DESCRIPTION
      "Path: lacpBundle.editConf.inboundBandwidth.unit

       Possibilities:
               bits/sec   (1)
               percent   (2)"
   ::= {er1646v2LacpBIbwEntry 1342177280}

er1646v2LacpBIbwTc OBJECT-TYPE
   SYNTAX      INTEGER
               {
               auto (0)
               }
   MAX-ACCESS  read-write
   STATUS      current
   DESCRIPTION
      "Path: lacpBundle.editConf.inboundBandwidth.tc

       Possibilities:
               auto   (0)"
   ::= {er1646v2LacpBIbwEntry 1610612736}

er1646v2LacpBIbwTcFactor OBJECT-TYPE
   SYNTAX      INTEGER
               {
               ms (10),
               s100us (1)
               }
   MAX-ACCESS  read-write
   STATUS      current
   DESCRIPTION
      "Path: lacpBundle.editConf.inboundBandwidth.tcFactor

       Possibilities:
               ms   (10)
               *100us   (1)"
   ::= {er1646v2LacpBIbwEntry 2147483648}

er1646v2LacpBIbwCorrType OBJECT-TYPE
   SYNTAX      INTEGER
               {
               noCorrection (0),
               predefined (1),
               manual (2)
               }
   MAX-ACCESS  read-write
   STATUS      current
   DESCRIPTION
      "Path: lacpBundle.editConf.inboundBandwidth.correction.type

       Possibilities:
               noCorrection   (0)
               predefined   (1)
               manual   (2)"
   ::= {er1646v2LacpBIbwEntry 570425344}

er1646v2LacpBIbwCorrPredefEncapsFrameRelay OBJECT-TYPE
   SYNTAX      DisplayString
   MAX-ACCESS  read-write
   STATUS      current
   DESCRIPTION
      "Path: lacpBundle.editConf.inboundBandwidth.correction.predefined.encapsulation.frameRelay"
   ::= {er1646v2LacpBIbwEntry 608436224}

er1646v2LacpBIbwCorrPredefEncapsPpp OBJECT-TYPE
   SYNTAX      DisplayString
   MAX-ACCESS  read-write
   STATUS      current
   DESCRIPTION
      "Path: lacpBundle.editConf.inboundBandwidth.correction.predefined.encapsulation.ppp"
   ::= {er1646v2LacpBIbwEntry 608698368}

er1646v2LacpBIbwCorrPredefEncapsAtmHl OBJECT-TYPE
   SYNTAX      INTEGER
               {
               rfc2684 (0),
               ppp (1),
               pppOverEthernet (2)
               }
   MAX-ACCESS  read-write
   STATUS      current
   DESCRIPTION
      "Path: lacpBundle.editConf.inboundBandwidth.correction.predefined.encapsulation.atm.higherLayer

       Possibilities:
               rfc2684   (0)
               ppp   (1)
               pppOverEthernet   (2)"
   ::= {er1646v2LacpBIbwEntry 608993280}

er1646v2LacpBIbwCorrPredefEncapsAtmMp OBJECT-TYPE
   SYNTAX      INTEGER
               {
               llcEncapsulation (0),
               vcMultiplexing (1)
               }
   MAX-ACCESS  read-write
   STATUS      current
   DESCRIPTION
      "Path: lacpBundle.editConf.inboundBandwidth.correction.predefined.encapsulation.atm.multiProtocol

       Possibilities:
               llcEncapsulation   (0)
               vcMultiplexing   (1)"
   ::= {er1646v2LacpBIbwEntry 609026048}

er1646v2LacpBIbwCorrPredefEncapsHdlc OBJECT-TYPE
   SYNTAX      DisplayString
   MAX-ACCESS  read-write
   STATUS      current
   DESCRIPTION
      "Path: lacpBundle.editConf.inboundBandwidth.correction.predefined.encapsulation.hdlc"
   ::= {er1646v2LacpBIbwEntry 609222656}

er1646v2LacpBIbwCorrPredefEncapsEfmFs OBJECT-TYPE
   SYNTAX      Integer32
   MAX-ACCESS  read-write
   STATUS      current
   DESCRIPTION
      "Path: lacpBundle.editConf.inboundBandwidth.correction.predefined.encapsulation.efm.fragmentSize"
   ::= {er1646v2LacpBIbwEntry 609517568}

er1646v2LacpBIbwCorrPredefEncapsEfmIb OBJECT-TYPE
   SYNTAX      Integer32
   MAX-ACCESS  read-write
   STATUS      current
   DESCRIPTION
      "Path: lacpBundle.editConf.inboundBandwidth.correction.predefined.encapsulation.efm.idleBytes"
   ::= {er1646v2LacpBIbwEntry 609550336}

er1646v2LacpBIbwCorrPredefMode OBJECT-TYPE
   SYNTAX      INTEGER
               {
               routing (0),
               bridging (1)
               }
   MAX-ACCESS  read-write
   STATUS      current
   DESCRIPTION
      "Path: lacpBundle.editConf.inboundBandwidth.correction.predefined.mode

       Possibilities:
               routing   (0)
               bridging   (1)"
   ::= {er1646v2LacpBIbwEntry 612368384}

er1646v2LacpBIbwCorrManualOverhead OBJECT-TYPE
   SYNTAX      Integer32
   MAX-ACCESS  read-write
   STATUS      current
   DESCRIPTION
      "Path: lacpBundle.editConf.inboundBandwidth.correction.manual.overhead"
   ::= {er1646v2LacpBIbwEntry 637665280}

er1646v2LacpBIbwCorrManualFrameData OBJECT-TYPE
   SYNTAX      Counter32
   MAX-ACCESS  read-write
   STATUS      current
   DESCRIPTION
      "Path: lacpBundle.editConf.inboundBandwidth.correction.manual.frameData

       32 bit unsigned wrappable counter."
   ::= {er1646v2LacpBIbwEntry 637796352}

er1646v2LacpBIbwCorrManualFrameHeader OBJECT-TYPE
   SYNTAX      Counter32
   MAX-ACCESS  read-write
   STATUS      current
   DESCRIPTION
      "Path: lacpBundle.editConf.inboundBandwidth.correction.manual.frameHeader

       32 bit unsigned wrappable counter."
   ::= {er1646v2LacpBIbwEntry 637927424}

er1646v2LacpBIbwMaxFifoQLen OBJECT-TYPE
   SYNTAX      Integer32
   MAX-ACCESS  read-write
   STATUS      current
   DESCRIPTION
      "Path: lacpBundle.editConf.inboundBandwidth.maxFifoQLen"
   ::= {er1646v2LacpBIbwEntry 805306368}

er1646v2LacpBIbwPriorityPolicy OBJECT-TYPE
   SYNTAX      DisplayString
   MAX-ACCESS  read-write
   STATUS      current
   DESCRIPTION
      "Path: lacpBundle.editConf.inboundBandwidth.priorityPolicy"
   ::= {er1646v2LacpBIbwEntry 1073741824}

er1646v2LacpBIbwDeFlagCir OBJECT-TYPE
   SYNTAX      INTEGER
               {
               allowed (1),
               notAllowed (2)
               }
   MAX-ACCESS  read-write
   STATUS      current
   DESCRIPTION
      "Path: lacpBundle.editConf.inboundBandwidth.deFlag.cir

       Possibilities:
               allowed   (1)
               notAllowed   (2)"
   ::= {er1646v2LacpBIbwEntry 3490709504}

er1646v2LacpBIbwDeFlagEir OBJECT-TYPE
   SYNTAX      INTEGER
               {
               allowed (1),
               notAllowed (2)
               }
   MAX-ACCESS  read-write
   STATUS      current
   DESCRIPTION
      "Path: lacpBundle.editConf.inboundBandwidth.deFlag.eir

       Possibilities:
               allowed   (1)
               notAllowed   (2)"
   ::= {er1646v2LacpBIbwEntry 3491758080}

er1646v2LacpBIbwDeFlagViolate OBJECT-TYPE
   SYNTAX      INTEGER
               {
               allowed (1),
               notAllowed (2)
               }
   MAX-ACCESS  read-write
   STATUS      current
   DESCRIPTION
      "Path: lacpBundle.editConf.inboundBandwidth.deFlag.violate

       Possibilities:
               allowed   (1)
               notAllowed   (2)"
   ::= {er1646v2LacpBIbwEntry 3492806656}

er1646v2LacpBIbwActCirActNone OBJECT-TYPE
   SYNTAX      OCTET STRING
   MAX-ACCESS  read-write
   STATUS      current
   DESCRIPTION
      "Path: lacpBundle.editConf.inboundBandwidth.action.cirAction.none"
   ::= {er1646v2LacpBIbwEntry 4062183424}

er1646v2LacpBIbwActCirActEthCos1 OBJECT-TYPE
   SYNTAX      INTEGER
               {
               unchanged (256)
               }
   MAX-ACCESS  read-write
   STATUS      current
   DESCRIPTION
      "Path: lacpBundle.editConf.inboundBandwidth.action.cirAction.ethernet.cosDepth1

       Possibilities:
               unchanged   (256)"
   ::= {er1646v2LacpBIbwEntry 4064346112}

er1646v2LacpBIbwActCirActEthDei1 OBJECT-TYPE
   SYNTAX      INTEGER
               {
               unchanged (255),
               clear (0),
               set (1)
               }
   MAX-ACCESS  read-write
   STATUS      current
   DESCRIPTION
      "Path: lacpBundle.editConf.inboundBandwidth.action.cirAction.ethernet.deiDepth1

       Possibilities:
               unchanged   (255)
               clear   (0)
               set   (1)"
   ::= {er1646v2LacpBIbwEntry 4065656832}

er1646v2LacpBIbwActCirActEthCos2 OBJECT-TYPE
   SYNTAX      INTEGER
               {
               unchanged (256)
               }
   MAX-ACCESS  read-write
   STATUS      current
   DESCRIPTION
      "Path: lacpBundle.editConf.inboundBandwidth.action.cirAction.ethernet.cosDepth2

       Possibilities:
               unchanged   (256)"
   ::= {er1646v2LacpBIbwEntry 4064411648}

er1646v2LacpBIbwActCirActEthDei2 OBJECT-TYPE
   SYNTAX      INTEGER
               {
               unchanged (255),
               clear (0),
               set (1)
               }
   MAX-ACCESS  read-write
   STATUS      current
   DESCRIPTION
      "Path: lacpBundle.editConf.inboundBandwidth.action.cirAction.ethernet.deiDepth2

       Possibilities:
               unchanged   (255)
               clear   (0)
               set   (1)"
   ::= {er1646v2LacpBIbwEntry 4065722368}

er1646v2LacpBIbwActCirActEthCos3 OBJECT-TYPE
   SYNTAX      INTEGER
               {
               unchanged (256)
               }
   MAX-ACCESS  read-write
   STATUS      current
   DESCRIPTION
      "Path: lacpBundle.editConf.inboundBandwidth.action.cirAction.ethernet.cosDepth3

       Possibilities:
               unchanged   (256)"
   ::= {er1646v2LacpBIbwEntry 4064477184}

er1646v2LacpBIbwActCirActEthDei3 OBJECT-TYPE
   SYNTAX      INTEGER
               {
               unchanged (255),
               clear (0),
               set (1)
               }
   MAX-ACCESS  read-write
   STATUS      current
   DESCRIPTION
      "Path: lacpBundle.editConf.inboundBandwidth.action.cirAction.ethernet.deiDepth3

       Possibilities:
               unchanged   (255)
               clear   (0)
               set   (1)"
   ::= {er1646v2LacpBIbwEntry 4065787904}

er1646v2LacpBIbwActCirActEthCos4 OBJECT-TYPE
   SYNTAX      INTEGER
               {
               unchanged (256)
               }
   MAX-ACCESS  read-write
   STATUS      current
   DESCRIPTION
      "Path: lacpBundle.editConf.inboundBandwidth.action.cirAction.ethernet.cosDepth4

       Possibilities:
               unchanged   (256)"
   ::= {er1646v2LacpBIbwEntry 4064542720}

er1646v2LacpBIbwActCirActEthDei4 OBJECT-TYPE
   SYNTAX      INTEGER
               {
               unchanged (255),
               clear (0),
               set (1)
               }
   MAX-ACCESS  read-write
   STATUS      current
   DESCRIPTION
      "Path: lacpBundle.editConf.inboundBandwidth.action.cirAction.ethernet.deiDepth4

       Possibilities:
               unchanged   (255)
               clear   (0)
               set   (1)"
   ::= {er1646v2LacpBIbwEntry 4065853440}

er1646v2LacpBIbwActCirActEthCos5 OBJECT-TYPE
   SYNTAX      INTEGER
               {
               unchanged (256)
               }
   MAX-ACCESS  read-write
   STATUS      current
   DESCRIPTION
      "Path: lacpBundle.editConf.inboundBandwidth.action.cirAction.ethernet.cosDepth5

       Possibilities:
               unchanged   (256)"
   ::= {er1646v2LacpBIbwEntry 4064608256}

er1646v2LacpBIbwActCirActEthDei5 OBJECT-TYPE
   SYNTAX      INTEGER
               {
               unchanged (255),
               clear (0),
               set (1)
               }
   MAX-ACCESS  read-write
   STATUS      current
   DESCRIPTION
      "Path: lacpBundle.editConf.inboundBandwidth.action.cirAction.ethernet.deiDepth5

       Possibilities:
               unchanged   (255)
               clear   (0)
               set   (1)"
   ::= {er1646v2LacpBIbwEntry 4065918976}

er1646v2LacpBIbwActCirActEthCos6 OBJECT-TYPE
   SYNTAX      INTEGER
               {
               unchanged (256)
               }
   MAX-ACCESS  read-write
   STATUS      current
   DESCRIPTION
      "Path: lacpBundle.editConf.inboundBandwidth.action.cirAction.ethernet.cosDepth6

       Possibilities:
               unchanged   (256)"
   ::= {er1646v2LacpBIbwEntry 4064673792}

er1646v2LacpBIbwActCirActEthDei6 OBJECT-TYPE
   SYNTAX      INTEGER
               {
               unchanged (255),
               clear (0),
               set (1)
               }
   MAX-ACCESS  read-write
   STATUS      current
   DESCRIPTION
      "Path: lacpBundle.editConf.inboundBandwidth.action.cirAction.ethernet.deiDepth6

       Possibilities:
               unchanged   (255)
               clear   (0)
               set   (1)"
   ::= {er1646v2LacpBIbwEntry 4065984512}

er1646v2LacpBIbwActCirActEthCos7 OBJECT-TYPE
   SYNTAX      INTEGER
               {
               unchanged (256)
               }
   MAX-ACCESS  read-write
   STATUS      current
   DESCRIPTION
      "Path: lacpBundle.editConf.inboundBandwidth.action.cirAction.ethernet.cosDepth7

       Possibilities:
               unchanged   (256)"
   ::= {er1646v2LacpBIbwEntry 4064739328}

er1646v2LacpBIbwActCirActEthDei7 OBJECT-TYPE
   SYNTAX      INTEGER
               {
               unchanged (255),
               clear (0),
               set (1)
               }
   MAX-ACCESS  read-write
   STATUS      current
   DESCRIPTION
      "Path: lacpBundle.editConf.inboundBandwidth.action.cirAction.ethernet.deiDepth7

       Possibilities:
               unchanged   (255)
               clear   (0)
               set   (1)"
   ::= {er1646v2LacpBIbwEntry 4066050048}

er1646v2LacpBIbwActCirActEthCos8 OBJECT-TYPE
   SYNTAX      INTEGER
               {
               unchanged (256)
               }
   MAX-ACCESS  read-write
   STATUS      current
   DESCRIPTION
      "Path: lacpBundle.editConf.inboundBandwidth.action.cirAction.ethernet.cosDepth8

       Possibilities:
               unchanged   (256)"
   ::= {er1646v2LacpBIbwEntry 4064804864}

er1646v2LacpBIbwActCirActEthDei8 OBJECT-TYPE
   SYNTAX      INTEGER
               {
               unchanged (255),
               clear (0),
               set (1)
               }
   MAX-ACCESS  read-write
   STATUS      current
   DESCRIPTION
      "Path: lacpBundle.editConf.inboundBandwidth.action.cirAction.ethernet.deiDepth8

       Possibilities:
               unchanged   (255)
               clear   (0)
               set   (1)"
   ::= {er1646v2LacpBIbwEntry 4066115584}

er1646v2LacpBIbwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: lacpBundle.editConf.inboundBandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2LacpBIbwEntry 4064870400}

er1646v2LacpBIbwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: lacpBundle.editConf.inboundBandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2LacpBIbwEntry 4064935936}

er1646v2LacpBIbwActCirActEthDrpLev OBJECT-TYPE
   SYNTAX      INTEGER
               {
               unchanged (0)
               }
   MAX-ACCESS  read-write
   STATUS      current
   DESCRIPTION
      "Path: lacpBundle.editConf.inboundBandwidth.action.cirAction.ethernet.dropLevel

       Possibilities:
               unchanged   (0)"
   ::= {er1646v2LacpBIbwEntry 4065001472}

er1646v2LacpBIbwActCirActEthDeFlag OBJECT-TYPE
   SYNTAX      INTEGER
               {
               unchanged (255),
               clear (0),
               set (1)
               }
   MAX-ACCESS  read-write
   STATUS      current
   DESCRIPTION
      "Path: lacpBundle.editConf.inboundBandwidth.action.cirAction.ethernet.deFlag

       Possibilities:
               unchanged   (255)
               clear   (0)
               set   (1)"
   ::= {er1646v2LacpBIbwEntry 4065198080}

er1646v2LacpBIbwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: lacpBundle.editConf.inboundBandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2LacpBIbwEntry 4071161856}

er1646v2LacpBIbwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: lacpBundle.editConf.inboundBandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2LacpBIbwEntry 4071227392}

er1646v2LacpBIbwActCirActIpDrpLev OBJECT-TYPE
   SYNTAX      INTEGER
               {
               unchanged (0)
               }
   MAX-ACCESS  read-write
   STATUS      current
   DESCRIPTION
      "Path: lacpBundle.editConf.inboundBandwidth.action.cirAction.ip.dropLevel

       Possibilities:
               unchanged   (0)"
   ::= {er1646v2LacpBIbwEntry 4071292928}

er1646v2LacpBIbwActCirActIpDeFlag OBJECT-TYPE
   SYNTAX      INTEGER
               {
               unchanged (255),
               clear (0),
               set (1)
               }
   MAX-ACCESS  read-write
   STATUS      current
   DESCRIPTION
      "Path: lacpBundle.editConf.inboundBandwidth.action.cirAction.ip.deFlag

       Possibilities:
               unchanged   (255)
               clear   (0)
               set   (1)"
   ::= {er1646v2LacpBIbwEntry 4071489536}

er1646v2LacpBIbwActEirActNone OBJECT-TYPE
   SYNTAX      OCTET STRING
   MAX-ACCESS  read-write
   STATUS      current
   DESCRIPTION
      "Path: lacpBundle.editConf.inboundBandwidth.action.eirAction.none"
   ::= {er1646v2LacpBIbwEntry 4095737856}

er1646v2LacpBIbwActEirActEthCos1 OBJECT-TYPE
   SYNTAX      INTEGER
               {
               unchanged (256)
               }
   MAX-ACCESS  read-write
   STATUS      current
   DESCRIPTION
      "Path: lacpBundle.editConf.inboundBandwidth.action.eirAction.ethernet.cosDepth1

       Possibilities:
               unchanged   (256)"
   ::= {er1646v2LacpBIbwEntry 4097900544}

er1646v2LacpBIbwActEirActEthDei1 OBJECT-TYPE
   SYNTAX      INTEGER
               {
               unchanged (255),
               clear (0),
               set (1)
               }
   MAX-ACCESS  read-write
   STATUS      current
   DESCRIPTION
      "Path: lacpBundle.editConf.inboundBandwidth.action.eirAction.ethernet.deiDepth1

       Possibilities:
               unchanged   (255)
               clear   (0)
               set   (1)"
   ::= {er1646v2LacpBIbwEntry 4099211264}

er1646v2LacpBIbwActEirActEthCos2 OBJECT-TYPE
   SYNTAX      INTEGER
               {
               unchanged (256)
               }
   MAX-ACCESS  read-write
   STATUS      current
   DESCRIPTION
      "Path: lacpBundle.editConf.inboundBandwidth.action.eirAction.ethernet.cosDepth2

       Possibilities:
               unchanged   (256)"
   ::= {er1646v2LacpBIbwEntry 4097966080}

er1646v2LacpBIbwActEirActEthDei2 OBJECT-TYPE
   SYNTAX      INTEGER
               {
               unchanged (255),
               clear (0),
               set (1)
               }
   MAX-ACCESS  read-write
   STATUS      current
   DESCRIPTION
      "Path: lacpBundle.editConf.inboundBandwidth.action.eirAction.ethernet.deiDepth2

       Possibilities:
               unchanged   (255)
               clear   (0)
               set   (1)"
   ::= {er1646v2LacpBIbwEntry 4099276800}

er1646v2LacpBIbwActEirActEthCos3 OBJECT-TYPE
   SYNTAX      INTEGER
               {
               unchanged (256)
               }
   MAX-ACCESS  read-write
   STATUS      current
   DESCRIPTION
      "Path: lacpBundle.editConf.inboundBandwidth.action.eirAction.ethernet.cosDepth3

       Possibilities:
               unchanged   (256)"
   ::= {er1646v2LacpBIbwEntry 4098031616}

er1646v2LacpBIbwActEirActEthDei3 OBJECT-TYPE
   SYNTAX      INTEGER
               {
               unchanged (255),
               clear (0),
               set (1)
               }
   MAX-ACCESS  read-write
   STATUS      current
   DESCRIPTION
      "Path: lacpBundle.editConf.inboundBandwidth.action.eirAction.ethernet.deiDepth3

       Possibilities:
               unchanged   (255)
               clear   (0)
               set   (1)"
   ::= {er1646v2LacpBIbwEntry 4099342336}

er1646v2LacpBIbwActEirActEthCos4 OBJECT-TYPE
   SYNTAX      INTEGER
               {
               unchanged (256)
               }
   MAX-ACCESS  read-write
   STATUS      current
   DESCRIPTION
      "Path: lacpBundle.editConf.inboundBandwidth.action.eirAction.ethernet.cosDepth4

       Possibilities:
               unchanged   (256)"
   ::= {er1646v2LacpBIbwEntry 4098097152}

er1646v2LacpBIbwActEirActEthDei4 OBJECT-TYPE
   SYNTAX      INTEGER
               {
               unchanged (255),
               clear (0),
               set (1)
               }
   MAX-ACCESS  read-write
   STATUS      current
   DESCRIPTION
      "Path: lacpBundle.editConf.inboundBandwidth.action.eirAction.ethernet.deiDepth4

       Possibilities:
               unchanged   (255)
               clear   (0)
               set   (1)"
   ::= {er1646v2LacpBIbwEntry 4099407872}

er1646v2LacpBIbwActEirActEthCos5 OBJECT-TYPE
   SYNTAX      INTEGER
               {
               unchanged (256)
               }
   MAX-ACCESS  read-write
   STATUS      current
   DESCRIPTION
      "Path: lacpBundle.editConf.inboundBandwidth.action.eirAction.ethernet.cosDepth5

       Possibilities:
               unchanged   (256)"
   ::= {er1646v2LacpBIbwEntry 4098162688}

er1646v2LacpBIbwActEirActEthDei5 OBJECT-TYPE
   SYNTAX      INTEGER
               {
               unchanged (255),
               clear (0),
               set (1)
               }
   MAX-ACCESS  read-write
   STATUS      current
   DESCRIPTION
      "Path: lacpBundle.editConf.inboundBandwidth.action.eirAction.ethernet.deiDepth5

       Possibilities:
               unchanged   (255)
               clear   (0)
               set   (1)"
   ::= {er1646v2LacpBIbwEntry 4099473408}

er1646v2LacpBIbwActEirActEthCos6 OBJECT-TYPE
   SYNTAX      INTEGER
               {
               unchanged (256)
               }
   MAX-ACCESS  read-write
   STATUS      current
   DESCRIPTION
      "Path: lacpBundle.editConf.inboundBandwidth.action.eirAction.ethernet.cosDepth6

       Possibilities:
               unchanged   (256)"
   ::= {er1646v2LacpBIbwEntry 4098228224}

er1646v2LacpBIbwActEirActEthDei6 OBJECT-TYPE
   SYNTAX      INTEGER
               {
               unchanged (255),
               clear (0),
               set (1)
               }
   MAX-ACCESS  read-write
   STATUS      current
   DESCRIPTION
      "Path: lacpBundle.editConf.inboundBandwidth.action.eirAction.ethernet.deiDepth6

       Possibilities:
               unchanged   (255)
               clear   (0)
               set   (1)"
   ::= {er1646v2LacpBIbwEntry 4099538944}

er1646v2LacpBIbwActEirActEthCos7 OBJECT-TYPE
   SYNTAX      INTEGER
               {
               unchanged (256)
               }
   MAX-ACCESS  read-write
   STATUS      current
   DESCRIPTION
      "Path: lacpBundle.editConf.inboundBandwidth.action.eirAction.ethernet.cosDepth7

       Possibilities:
               unchanged   (256)"
   ::= {er1646v2LacpBIbwEntry 4098293760}

er1646v2LacpBIbwActEirActEthDei7 OBJECT-TYPE
   SYNTAX      INTEGER
               {
               unchanged (255),
               clear (0),
               set (1)
               }
   MAX-ACCESS  read-write
   STATUS      current
   DESCRIPTION
      "Path: lacpBundle.editConf.inboundBandwidth.action.eirAction.ethernet.deiDepth7

       Possibilities:
               unchanged   (255)
               clear   (0)
               set   (1)"
   ::= {er1646v2LacpBIbwEntry 4099604480}

er1646v2LacpBIbwActEirActEthCos8 OBJECT-TYPE
   SYNTAX      INTEGER
               {
               unchanged (256)
               }
   MAX-ACCESS  read-write
   STATUS      current
   DESCRIPTION
      "Path: lacpBundle.editConf.inboundBandwidth.action.eirAction.ethernet.cosDepth8

       Possibilities:
               unchanged   (256)"
   ::= {er1646v2LacpBIbwEntry 4098359296}

er1646v2LacpBIbwActEirActEthDei8 OBJECT-TYPE
   SYNTAX      INTEGER
               {
               unchanged (255),
               clear (0),
               set (1)
               }
   MAX-ACCESS  read-write
   STATUS      current
   DESCRIPTION
      "Path: lacpBundle.editConf.inboundBandwidth.action.eirAction.ethernet.deiDepth8

       Possibilities:
               unchanged   (255)
               clear   (0)
               set   (1)"
   ::= {er1646v2LacpBIbwEntry 4099670016}

er1646v2LacpBIbwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: lacpBundle.editConf.inboundBandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2LacpBIbwEntry 4098424832}

er1646v2LacpBIbwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: lacpBundle.editConf.inboundBandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2LacpBIbwEntry 4098490368}

er1646v2LacpBIbwActEirActEthDrpLev OBJECT-TYPE
   SYNTAX      INTEGER
               {
               unchanged (0)
               }
   MAX-ACCESS  read-write
   STATUS      current
   DESCRIPTION
      "Path: lacpBundle.editConf.inboundBandwidth.action.eirAction.ethernet.dropLevel

       Possibilities:
               unchanged   (0)"
   ::= {er1646v2LacpBIbwEntry 4098555904}

er1646v2LacpBIbwActEirActEthDeFlag OBJECT-TYPE
   SYNTAX      INTEGER
               {
               unchanged (255),
               clear (0),
               set (1)
               }
   MAX-ACCESS  read-write
   STATUS      current
   DESCRIPTION
      "Path: lacpBundle.editConf.inboundBandwidth.action.eirAction.ethernet.deFlag

       Possibilities:
               unchanged   (255)
               clear   (0)
               set   (1)"
   ::= {er1646v2LacpBIbwEntry 4098752512}

er1646v2LacpBIbwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: lacpBundle.editConf.inboundBandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2LacpBIbwEntry 4104716288}

er1646v2LacpBIbwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: lacpBundle.editConf.inboundBandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2LacpBIbwEntry 4104781824}

er1646v2LacpBIbwActEirActIpDrpLev OBJECT-TYPE
   SYNTAX      INTEGER
               {
               unchanged (0)
               }
   MAX-ACCESS  read-write
   STATUS      current
   DESCRIPTION
      "Path: lacpBundle.editConf.inboundBandwidth.action.eirAction.ip.dropLevel

       Possibilities:
               unchanged   (0)"
   ::= {er1646v2LacpBIbwEntry 4104847360}

er1646v2LacpBIbwActEirActIpDeFlag OBJECT-TYPE
   SYNTAX      INTEGER
               {
               unchanged (255),
               clear (0),
               set (1)
               }
   MAX-ACCESS  read-write
   STATUS      current
   DESCRIPTION
      "Path: lacpBundle.editConf.inboundBandwidth.action.eirAction.ip.deFlag

       Possibilities:
               unchanged   (255)
               clear   (0)
               set   (1)"
   ::= {er1646v2LacpBIbwEntry 4105043968}

er1646v2LacpBIbwActViolActNone OBJECT-TYPE
   SYNTAX      OCTET STRING
   MAX-ACCESS  read-write
   STATUS      current
   DESCRIPTION
      "Path: lacpBundle.editConf.inboundBandwidth.action.violateAction.none"
   ::= {er1646v2LacpBIbwEntry 4129292288}

er1646v2LacpBIbwActViolActDrop OBJECT-TYPE
   SYNTAX      OCTET STRING
   MAX-ACCESS  read-write
   STATUS      current
   DESCRIPTION
      "Path: lacpBundle.editConf.inboundBandwidth.action.violateAction.drop"
   ::= {er1646v2LacpBIbwEntry 4133486592}

er1646v2LacpBIbwActViolActEthCos1 OBJECT-TYPE
   SYNTAX      INTEGER
               {
               unchanged (256)
               }
   MAX-ACCESS  read-write
   STATUS      current
   DESCRIPTION
      "Path: lacpBundle.editConf.inboundBandwidth.action.violateAction.ethernet.cosDepth1

       Possibilities:
               unchanged   (256)"
   ::= {er1646v2LacpBIbwEntry 4131454976}

er1646v2LacpBIbwActViolActEthDei1 OBJECT-TYPE
   SYNTAX      INTEGER
               {
               unchanged (255),
               clear (0),
               set (1)
               }
   MAX-ACCESS  read-write
   STATUS      current
   DESCRIPTION
      "Path: lacpBundle.editConf.inboundBandwidth.action.violateAction.ethernet.deiDepth1

       Possibilities:
               unchanged   (255)
               clear   (0)
               set   (1)"
   ::= {er1646v2LacpBIbwEntry 4132765696}

er1646v2LacpBIbwActViolActEthCos2 OBJECT-TYPE
   SYNTAX      INTEGER
               {
               unchanged (256)
               }
   MAX-ACCESS  read-write
   STATUS      current
   DESCRIPTION
      "Path: lacpBundle.editConf.inboundBandwidth.action.violateAction.ethernet.cosDepth2

       Possibilities:
               unchanged   (256)"
   ::= {er1646v2LacpBIbwEntry 4131520512}

er1646v2LacpBIbwActViolActEthDei2 OBJECT-TYPE
   SYNTAX      INTEGER
               {
               unchanged (255),
               clear (0),
               set (1)
               }
   MAX-ACCESS  read-write
   STATUS      current
   DESCRIPTION
      "Path: lacpBundle.editConf.inboundBandwidth.action.violateAction.ethernet.deiDepth2

       Possibilities:
               unchanged   (255)
               clear   (0)
               set   (1)"
   ::= {er1646v2LacpBIbwEntry 4132831232}

er1646v2LacpBIbwActViolActEthCos3 OBJECT-TYPE
   SYNTAX      INTEGER
               {
               unchanged (256)
               }
   MAX-ACCESS  read-write
   STATUS      current
   DESCRIPTION
      "Path: lacpBundle.editConf.inboundBandwidth.action.violateAction.ethernet.cosDepth3

       Possibilities:
               unchanged   (256)"
   ::= {er1646v2LacpBIbwEntry 4131586048}

er1646v2LacpBIbwActViolActEthDei3 OBJECT-TYPE
   SYNTAX      INTEGER
               {
               unchanged (255),
               clear (0),
               set (1)
               }
   MAX-ACCESS  read-write
   STATUS      current
   DESCRIPTION
      "Path: lacpBundle.editConf.inboundBandwidth.action.violateAction.ethernet.deiDepth3

       Possibilities:
               unchanged   (255)
               clear   (0)
               set   (1)"
   ::= {er1646v2LacpBIbwEntry 4132896768}

er1646v2LacpBIbwActViolActEthCos4 OBJECT-TYPE
   SYNTAX      INTEGER
               {
               unchanged (256)
               }
   MAX-ACCESS  read-write
   STATUS      current
   DESCRIPTION
      "Path: lacpBundle.editConf.inboundBandwidth.action.violateAction.ethernet.cosDepth4

       Possibilities:
               unchanged   (256)"
   ::= {er1646v2LacpBIbwEntry 4131651584}

er1646v2LacpBIbwActViolActEthDei4 OBJECT-TYPE
   SYNTAX      INTEGER
               {
               unchanged (255),
               clear (0),
               set (1)
               }
   MAX-ACCESS  read-write
   STATUS      current
   DESCRIPTION
      "Path: lacpBundle.editConf.inboundBandwidth.action.violateAction.ethernet.deiDepth4

       Possibilities:
               unchanged   (255)
               clear   (0)
               set   (1)"
   ::= {er1646v2LacpBIbwEntry 4132962304}

er1646v2LacpBIbwActViolActEthCos5 OBJECT-TYPE
   SYNTAX      INTEGER
               {
               unchanged (256)
               }
   MAX-ACCESS  read-write
   STATUS      current
   DESCRIPTION
      "Path: lacpBundle.editConf.inboundBandwidth.action.violateAction.ethernet.cosDepth5

       Possibilities:
               unchanged   (256)"
   ::= {er1646v2LacpBIbwEntry 4131717120}

er1646v2LacpBIbwActViolActEthDei5 OBJECT-TYPE
   SYNTAX      INTEGER
               {
               unchanged (255),
               clear (0),
               set (1)
               }
   MAX-ACCESS  read-write
   STATUS      current
   DESCRIPTION
      "Path: lacpBundle.editConf.inboundBandwidth.action.violateAction.ethernet.deiDepth5

       Possibilities:
               unchanged   (255)
               clear   (0)
               set   (1)"
   ::= {er1646v2LacpBIbwEntry 4133027840}

er1646v2LacpBIbwActViolActEthCos6 OBJECT-TYPE
   SYNTAX      INTEGER
               {
               unchanged (256)
               }
   MAX-ACCESS  read-write
   STATUS      current
   DESCRIPTION
      "Path: lacpBundle.editConf.inboundBandwidth.action.violateAction.ethernet.cosDepth6

       Possibilities:
               unchanged   (256)"
   ::= {er1646v2LacpBIbwEntry 4131782656}

er1646v2LacpBIbwActViolActEthDei6 OBJECT-TYPE
   SYNTAX      INTEGER
               {
               unchanged (255),
               clear (0),
               set (1)
               }
   MAX-ACCESS  read-write
   STATUS      current
   DESCRIPTION
      "Path: lacpBundle.editConf.inboundBandwidth.action.violateAction.ethernet.deiDepth6

       Possibilities:
               unchanged   (255)
               clear   (0)
               set   (1)"
   ::= {er1646v2LacpBIbwEntry 4133093376}

er1646v2LacpBIbwActViolActEthCos7 OBJECT-TYPE
   SYNTAX      INTEGER
               {
               unchanged (256)
               }
   MAX-ACCESS  read-write
   STATUS      current
   DESCRIPTION
      "Path: lacpBundle.editConf.inboundBandwidth.action.violateAction.ethernet.cosDepth7

       Possibilities:
               unchanged   (256)"
   ::= {er1646v2LacpBIbwEntry 4131848192}

er1646v2LacpBIbwActViolActEthDei7 OBJECT-TYPE
   SYNTAX      INTEGER
               {
               unchanged (255),
               clear (0),
               set (1)
               }
   MAX-ACCESS  read-write
   STATUS      current
   DESCRIPTION
      "Path: lacpBundle.editConf.inboundBandwidth.action.violateAction.ethernet.deiDepth7

       Possibilities:
               unchanged   (255)
               clear   (0)
               set   (1)"
   ::= {er1646v2LacpBIbwEntry 4133158912}

er1646v2LacpBIbwActViolActEthCos8 OBJECT-TYPE
   SYNTAX      INTEGER
               {
               unchanged (256)
               }
   MAX-ACCESS  read-write
   STATUS      current
   DESCRIPTION
      "Path: lacpBundle.editConf.inboundBandwidth.action.violateAction.ethernet.cosDepth8

       Possibilities:
               unchanged   (256)"
   ::= {er1646v2LacpBIbwEntry 4131913728}

er1646v2LacpBIbwActViolActEthDei8 OBJECT-TYPE
   SYNTAX      INTEGER
               {
               unchanged (255),
               clear (0),
               set (1)
               }
   MAX-ACCESS  read-write
   STATUS      current
   DESCRIPTION
      "Path: lacpBundle.editConf.inboundBandwidth.action.violateAction.ethernet.deiDepth8

       Possibilities:
               unchanged   (255)
               clear   (0)
               set   (1)"
   ::= {er1646v2LacpBIbwEntry 4133224448}

er1646v2LacpBIbwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: lacpBundle.editConf.inboundBandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2LacpBIbwEntry 4131979264}

er1646v2LacpBIbwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: lacpBundle.editConf.inboundBandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2LacpBIbwEntry 4132044800}

er1646v2LacpBIbwActViolActEthDrpLev OBJECT-TYPE
   SYNTAX      INTEGER
               {
               unchanged (0)
               }
   MAX-ACCESS  read-write
   STATUS      current
   DESCRIPTION
      "Path: lacpBundle.editConf.inboundBandwidth.action.violateAction.ethernet.dropLevel

       Possibilities:
               unchanged   (0)"
   ::= {er1646v2LacpBIbwEntry 4132110336}

er1646v2LacpBIbwActViolActEthDeFlag OBJECT-TYPE
   SYNTAX      INTEGER
               {
               unchanged (255),
               clear (0),
               set (1)
               }
   MAX-ACCESS  read-write
   STATUS      current
   DESCRIPTION
      "Path: lacpBundle.editConf.inboundBandwidth.action.violateAction.ethernet.deFlag

       Possibilities:
               unchanged   (255)
               clear   (0)
               set   (1)"
   ::= {er1646v2LacpBIbwEntry 4132306944}

er1646v2LacpBIbwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: lacpBundle.editConf.inboundBandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2LacpBIbwEntry 4138270720}

er1646v2LacpBIbwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: lacpBundle.editConf.inboundBandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1646v2LacpBIbwEntry 4138336256}

er1646v2LacpBIbwActViolActIpDrpLev OBJECT-TYPE
   SYNTAX      INTEGER
               {
               unchanged (0)
               }
   MAX-ACCESS  read-write
   STATUS      current
   DESCRIPTION
      "Path: lacpBundle.editConf.inboundBandwidth.action.violateAction.ip.dropLevel

       Possibilities:
               unchanged   (0)"
   ::= {er1646v2LacpBIbwEntry 4138401792}

er1646v2LacpBIbwActViolActIpDeFlag OBJECT-TYPE
   SYNTAX      INTEGER
               {
               unchanged (255),
               clear (0),
               set (1)
               }
   MAX-ACCESS  read-write
   STATUS      current
   DESCRIPTION
      "Path: lacpBundle.editConf.inboundBandwidth.action.violateAction.ip.deFlag

       Possibilities:
               unchanged   (255)
               clear   (0)
               set   (1)"
   ::= {er1646v2LacpBIbwEntry 4138598400}


er1646v2LacpBAdminStatus OBJECT IDENTIFIER ::= {er1646v2LacpB 106}

er1646v2LacpBAdminStatusTable OBJECT-TYPE
   SYNTAX      SEQUENCE OF Er1646v2LacpBAdminStatusEntry
   MAX-ACCESS  not-accessible
   STATUS      current
   DESCRIPTION
      "ifAdminStatus"
   ::= {er1646v2LacpBAdminStatus 1}

er1646v2LacpBAdminStatusEntry OBJECT-TYPE
   SYNTAX      Er1646v2LacpBAdminStatusEntry
   MAX-ACCESS  not-accessible
   STATUS      current
   DESCRIPTION
      ""
   INDEX      { er1646v2LacpBAdminStatusGlobalIx }
   ::= {er1646v2LacpBAdminStatusTable 1}

Er1646v2LacpBAdminStatusEntry ::=
   SEQUENCE
      {
      er1646v2LacpBAdminStatusGlobalIx
         GlobalIndex,
      er1646v2LacpBAdminStatusValue
         INTEGER
      }

er1646v2LacpBAdminStatusGlobalIx OBJECT-TYPE
   SYNTAX      GlobalIndex
   MAX-ACCESS  not-accessible
   STATUS      current
   DESCRIPTION
      "The value of the tlsCntTreeGlobalIndex of the MANAGED OBJECT."
   ::= {er1646v2LacpBAdminStatusEntry 10}

er1646v2LacpBAdminStatusValue OBJECT-TYPE
   SYNTAX      INTEGER
               {
               up (1),
               down (2)
               }
   MAX-ACCESS  read-write
   STATUS      current
   DESCRIPTION
      "Path: lacpBundle.editConf.adminStatus

       Possibilities:
               up   (1)
               down   (2)"
   ::= {er1646v2LacpBAdminStatusEntry 2147483648}


er1646v2LacpBAlarmMask OBJECT IDENTIFIER ::= {er1646v2LacpB 135}

er1646v2LacpBAlarmMaskTable OBJECT-TYPE
   SYNTAX      SEQUENCE OF Er1646v2LacpBAlarmMaskEntry
   MAX-ACCESS  not-accessible
   STATUS      current
   DESCRIPTION
      "ifAlarmMask"
   ::= {er1646v2LacpBAlarmMask 1}

er1646v2LacpBAlarmMaskEntry OBJECT-TYPE
   SYNTAX      Er1646v2LacpBAlarmMaskEntry
   MAX-ACCESS  not-accessible
   STATUS      current
   DESCRIPTION
      ""
   INDEX      { er1646v2LacpBAlarmMaskGlobalIx }
   ::= {er1646v2LacpBAlarmMaskTable 1}

Er1646v2LacpBAlarmMaskEntry ::=
   SEQUENCE
      {
      er1646v2LacpBAlarmMaskGlobalIx
         GlobalIndex,
      er1646v2LacpBAlarmMaskValue
         Integer32
      }

er1646v2LacpBAlarmMaskGlobalIx OBJECT-TYPE
   SYNTAX      GlobalIndex
   MAX-ACCESS  not-accessible
   STATUS      current
   DESCRIPTION
      "The value of the tlsCntTreeGlobalIndex of the MANAGED OBJECT."
   ::= {er1646v2LacpBAlarmMaskEntry 10}

er1646v2LacpBAlarmMaskValue OBJECT-TYPE
   SYNTAX      Integer32
   MAX-ACCESS  read-write
   STATUS      current
   DESCRIPTION
      "Path: lacpBundle.editConf.alarmMask

       Bit meanings:
               bit 0 = linkDown,
               bit 9 = pppoEDown"
   ::= {er1646v2LacpBAlarmMaskEntry 2147483648}


er1646v2LacpBAlarmLev OBJECT IDENTIFIER ::= {er1646v2LacpB 170}

er1646v2LacpBAlarmLevSSCTable OBJECT-TYPE
   SYNTAX      SEQUENCE OF Er1646v2LacpBAlarmLevEntry
   MAX-ACCESS  not-accessible
   STATUS      current
   DESCRIPTION
      "IfAlarmLevels"
   ::= {er1646v2LacpBAlarmLev 1}

er1646v2LacpBAlarmLevEntry OBJECT-TYPE
   SYNTAX      Er1646v2LacpBAlarmLevEntry
   MAX-ACCESS  not-accessible
   STATUS      current
   DESCRIPTION
      ""
   INDEX      { er1646v2LacpBAlarmLevGlobalIx }
   ::= {er1646v2LacpBAlarmLevSSCTable 1}

Er1646v2LacpBAlarmLevEntry ::=
   SEQUENCE
      {
      er1646v2LacpBAlarmLevGlobalIx
         GlobalIndex,
      er1646v2LacpBAlarmLevLinkDown
         Integer32,
      er1646v2LacpBAlarmLevPppoEDown
         Integer32
      }

er1646v2LacpBAlarmLevGlobalIx OBJECT-TYPE
   SYNTAX      GlobalIndex
   MAX-ACCESS  not-accessible
   STATUS      current
   DESCRIPTION
      "The value of the tlsCntTreeGlobalIndex of the MANAGED OBJECT."
   ::= {er1646v2LacpBAlarmLevEntry 10}

er1646v2LacpBAlarmLevLinkDown OBJECT-TYPE
   SYNTAX      Integer32
   MAX-ACCESS  read-write
   STATUS      current
   DESCRIPTION
      "Path: lacpBundle.editConf.alarmLevel.linkDown"
   ::= {er1646v2LacpBAlarmLevEntry 16777216}

er1646v2LacpBAlarmLevPppoEDown OBJECT-TYPE
   SYNTAX      Integer32
   MAX-ACCESS  read-write
   STATUS      current
   DESCRIPTION
      "Path: lacpBundle.editConf.alarmLevel.pppoEDown"
   ::= {er1646v2LacpBAlarmLevEntry 167772160}


er1646v2LacpBPriorityPolicy OBJECT IDENTIFIER ::= {er1646v2LacpB 39}

er1646v2LacpBPriorityPolicyTable OBJECT-TYPE
   SYNTAX      SEQUENCE OF Er1646v2LacpBPriorityPolicyEntry
   MAX-ACCESS  not-accessible
   STATUS      current
   DESCRIPTION
      "Preferred Policy"
   ::= {er1646v2LacpBPriorityPolicy 1}

er1646v2LacpBPriorityPolicyEntry OBJECT-TYPE
   SYNTAX      Er1646v2LacpBPriorityPolicyEntry
   MAX-ACCESS  not-accessible
   STATUS      current
   DESCRIPTION
      ""
   INDEX      { er1646v2LacpBPriorityPolicyGlobalIx }
   ::= {er1646v2LacpBPriorityPolicyTable 1}

Er1646v2LacpBPriorityPolicyEntry ::=
   SEQUENCE
      {
      er1646v2LacpBPriorityPolicyGlobalIx
         GlobalIndex,
      er1646v2LacpBPriorityPolicyValue
         DisplayString
      }

er1646v2LacpBPriorityPolicyGlobalIx OBJECT-TYPE
   SYNTAX      GlobalIndex
   MAX-ACCESS  not-accessible
   STATUS      current
   DESCRIPTION
      "The value of the tlsCntTreeGlobalIndex of the MANAGED OBJECT."
   ::= {er1646v2LacpBPriorityPolicyEntry 10}

er1646v2LacpBPriorityPolicyValue OBJECT-TYPE
   SYNTAX      DisplayString
   MAX-ACCESS  read-write
   STATUS      current
   DESCRIPTION
      "Path: lacpBundle.editConf.priorityPolicy"
   ::= {er1646v2LacpBPriorityPolicyEntry 2147483648}


er1646v2LacpBMinActiveLinks OBJECT IDENTIFIER ::= {er1646v2LacpB 87}

er1646v2LacpBMinActiveLinksTable OBJECT-TYPE
   SYNTAX      SEQUENCE OF Er1646v2LacpBMinActiveLinksEntry
   MAX-ACCESS  not-accessible
   STATUS      current
   DESCRIPTION
      "minimum number of active links in the LACP bundle"
   ::= {er1646v2LacpBMinActiveLinks 1}

er1646v2LacpBMinActiveLinksEntry OBJECT-TYPE
   SYNTAX      Er1646v2LacpBMinActiveLinksEntry
   MAX-ACCESS  not-accessible
   STATUS      current
   DESCRIPTION
      ""
   INDEX      { er1646v2LacpBMinActiveLinksGlobalIx }
   ::= {er1646v2LacpBMinActiveLinksTable 1}

Er1646v2LacpBMinActiveLinksEntry ::=
   SEQUENCE
      {
      er1646v2LacpBMinActiveLinksGlobalIx
         GlobalIndex,
      er1646v2LacpBMinActiveLinksValue
         Integer32
      }

er1646v2LacpBMinActiveLinksGlobalIx OBJECT-TYPE
   SYNTAX      GlobalIndex
   MAX-ACCESS  not-accessible
   STATUS      current
   DESCRIPTION
      "The value of the tlsCntTreeGlobalIndex of the MANAGED OBJECT."
   ::= {er1646v2LacpBMinActiveLinksEntry 10}

er1646v2LacpBMinActiveLinksValue OBJECT-TYPE
   SYNTAX      Integer32
   MAX-ACCESS  read-write
   STATUS      current
   DESCRIPTION
      "Path: lacpBundle.editConf.minActiveLinks"
   ::= {er1646v2LacpBMinActiveLinksEntry 2147483648}


er1646v2LacpBMaxActiveLinks OBJECT IDENTIFIER ::= {er1646v2LacpB 88}

er1646v2LacpBMaxActiveLinksTable OBJECT-TYPE
   SYNTAX      SEQUENCE OF Er1646v2LacpBMaxActiveLinksEntry
   MAX-ACCESS  not-accessible
   STATUS      current
   DESCRIPTION
      "maximum number of active links in the LACP bundle"
   ::= {er1646v2LacpBMaxActiveLinks 1}

er1646v2LacpBMaxActiveLinksEntry OBJECT-TYPE
   SYNTAX      Er1646v2LacpBMaxActiveLinksEntry
   MAX-ACCESS  not-accessible
   STATUS      current
   DESCRIPTION
      ""
   INDEX      { er1646v2LacpBMaxActiveLinksGlobalIx }
   ::= {er1646v2LacpBMaxActiveLinksTable 1}

Er1646v2LacpBMaxActiveLinksEntry ::=
   SEQUENCE
      {
      er1646v2LacpBMaxActiveLinksGlobalIx
         GlobalIndex,
      er1646v2LacpBMaxActiveLinksValue
         INTEGER
      }

er1646v2LacpBMaxActiveLinksGlobalIx OBJECT-TYPE
   SYNTAX      GlobalIndex
   MAX-ACCESS  not-accessible
   STATUS      current
   DESCRIPTION
      "The value of the tlsCntTreeGlobalIndex of the MANAGED OBJECT."
   ::= {er1646v2LacpBMaxActiveLinksEntry 10}

er1646v2LacpBMaxActiveLinksValue OBJECT-TYPE
   SYNTAX      INTEGER
               {
               noLimit (0)
               }
   MAX-ACCESS  read-write
   STATUS      current
   DESCRIPTION
      "Path: lacpBundle.editConf.maxActiveLinks

       Possibilities:
               noLimit   (0)"
   ::= {er1646v2LacpBMaxActiveLinksEntry 2147483648}


er1646v2LacpBDistributionAlgorithm OBJECT IDENTIFIER ::= {er1646v2LacpB 89}

er1646v2LacpBDistributionAlgorithmTable OBJECT-TYPE
   SYNTAX      SEQUENCE OF Er1646v2LacpBDistributionAlgorithmEntry
   MAX-ACCESS  not-accessible
   STATUS      current
   DESCRIPTION
      "distribution algorithm"
   ::= {er1646v2LacpBDistributionAlgorithm 1}

er1646v2LacpBDistributionAlgorithmEntry OBJECT-TYPE
   SYNTAX      Er1646v2LacpBDistributionAlgorithmEntry
   MAX-ACCESS  not-accessible
   STATUS      current
   DESCRIPTION
      ""
   INDEX      { er1646v2LacpBDistributionAlgorithmGlobalIx }
   ::= {er1646v2LacpBDistributionAlgorithmTable 1}

Er1646v2LacpBDistributionAlgorithmEntry ::=
   SEQUENCE
      {
      er1646v2LacpBDistributionAlgorithmGlobalIx
         GlobalIndex,
      er1646v2LacpBDistributionAlgorithmValue
         INTEGER
      }

er1646v2LacpBDistributionAlgorithmGlobalIx OBJECT-TYPE
   SYNTAX      GlobalIndex
   MAX-ACCESS  not-accessible
   STATUS      current
   DESCRIPTION
      "The value of the tlsCntTreeGlobalIndex of the MANAGED OBJECT."
   ::= {er1646v2LacpBDistributionAlgorithmEntry 10}

er1646v2LacpBDistributionAlgorithmValue OBJECT-TYPE
   SYNTAX      INTEGER
               {
               macAddresses (2),
               ipAddresses (3),
               portNumbers (4)
               }
   MAX-ACCESS  read-write
   STATUS      current
   DESCRIPTION
      "Path: lacpBundle.editConf.distributionAlgorithm

       Possibilities:
               macAddresses   (2)
               ipAddresses   (3)
               portNumbers   (4)"
   ::= {er1646v2LacpBDistributionAlgorithmEntry 2147483648}


er1646v2LacpBMemberSelection OBJECT IDENTIFIER ::= {er1646v2LacpB 91}

er1646v2LacpBMemberSelectionTable OBJECT-TYPE
   SYNTAX      SEQUENCE OF Er1646v2LacpBMemberSelectionEntry
   MAX-ACCESS  not-accessible
   STATUS      current
   DESCRIPTION
      "distribution algorithm"
   ::= {er1646v2LacpBMemberSelection 1}

er1646v2LacpBMemberSelectionEntry OBJECT-TYPE
   SYNTAX      Er1646v2LacpBMemberSelectionEntry
   MAX-ACCESS  not-accessible
   STATUS      current
   DESCRIPTION
      ""
   INDEX      { er1646v2LacpBMemberSelectionGlobalIx }
   ::= {er1646v2LacpBMemberSelectionTable 1}

Er1646v2LacpBMemberSelectionEntry ::=
   SEQUENCE
      {
      er1646v2LacpBMemberSelectionGlobalIx
         GlobalIndex,
      er1646v2LacpBMemberSelectionValue
         INTEGER
      }

er1646v2LacpBMemberSelectionGlobalIx OBJECT-TYPE
   SYNTAX      GlobalIndex
   MAX-ACCESS  not-accessible
   STATUS      current
   DESCRIPTION
      "The value of the tlsCntTreeGlobalIndex of the MANAGED OBJECT."
   ::= {er1646v2LacpBMemberSelectionEntry 10}

er1646v2LacpBMemberSelectionValue OBJECT-TYPE
   SYNTAX      INTEGER
               {
               sessionAndTimeOut (1),
               hash (2)
               }
   MAX-ACCESS  read-write
   STATUS      current
   DESCRIPTION
      "Path: lacpBundle.editConf.memberSelection

       Possibilities:
               sessionAndTimeOut   (1)
               hash   (2)"
   ::= {er1646v2LacpBMemberSelectionEntry 2147483648}


er1646v2LacpBMembers OBJECT IDENTIFIER ::= {er1646v2LacpB 90}

er1646v2LacpBMembersSSCTable OBJECT-TYPE
   SYNTAX      SEQUENCE OF Er1646v2LacpBMembersEntry
   MAX-ACCESS  not-accessible
   STATUS      current
   DESCRIPTION
      "LACP bundle member list"
   ::= {er1646v2LacpBMembers 1}

er1646v2LacpBMembersEntry OBJECT-TYPE
   SYNTAX      Er1646v2LacpBMembersEntry
   MAX-ACCESS  not-accessible
   STATUS      current
   DESCRIPTION
      ""
   INDEX      { er1646v2LacpBMembersGlobalIx,
                er1646v2LacpBMembersTableIx }
   ::= {er1646v2LacpBMembersSSCTable 1}

Er1646v2LacpBMembersEntry ::=
   SEQUENCE
      {
      er1646v2LacpBMembersActions
         VariableLengthTableActions,
      er1646v2LacpBMembersGlobalIx
         GlobalIndex,
      er1646v2LacpBMembersTableIx
         TableIndex,
      er1646v2LacpBMembersInterface
         DisplayString,
      er1646v2LacpBMembersPortPriority
         Integer32,
      er1646v2LacpBMembersActivity
         INTEGER,
      er1646v2LacpBMembersTimeout
         INTEGER
      }

er1646v2LacpBMembersActions OBJECT-TYPE
   SYNTAX      VariableLengthTableActions
   MAX-ACCESS  read-write
   STATUS      current
   DESCRIPTION
      "By way of this field, some manipulations
       on this table may be performed."
   ::= {er1646v2LacpBMembersEntry 2}

er1646v2LacpBMembersGlobalIx OBJECT-TYPE
   SYNTAX      GlobalIndex
   MAX-ACCESS  not-accessible
   STATUS      current
   DESCRIPTION
      "The value of the tlsCntTreeGlobalIndex of the MANAGED OBJECT."
   ::= {er1646v2LacpBMembersEntry 10}

er1646v2LacpBMembersTableIx OBJECT-TYPE
   SYNTAX      TableIndex
   MAX-ACCESS  not-accessible
   STATUS      current
   DESCRIPTION
      ""
   ::= {er1646v2LacpBMembersEntry 11}

er1646v2LacpBMembersInterface OBJECT-TYPE
   SYNTAX      DisplayString
   MAX-ACCESS  read-write
   STATUS      current
   DESCRIPTION
      "Path: lacpBundle.editConf.members.interface"
   ::= {er1646v2LacpBMembersEntry 16777216}

er1646v2LacpBMembersPortPriority OBJECT-TYPE
   SYNTAX      Integer32
   MAX-ACCESS  read-write
   STATUS      current
   DESCRIPTION
      "Path: lacpBundle.editConf.members.portPriority"
   ::= {er1646v2LacpBMembersEntry 33554432}

er1646v2LacpBMembersActivity OBJECT-TYPE
   SYNTAX      INTEGER
               {
               passive (0),
               active (1)
               }
   MAX-ACCESS  read-write
   STATUS      current
   DESCRIPTION
      "Path: lacpBundle.editConf.members.activity

       Possibilities:
               passive   (0)
               active   (1)"
   ::= {er1646v2LacpBMembersEntry 50331648}

er1646v2LacpBMembersTimeout OBJECT-TYPE
   SYNTAX      INTEGER
               {
               long (0),
               short (1)
               }
   MAX-ACCESS  read-write
   STATUS      current
   DESCRIPTION
      "Path: lacpBundle.editConf.members.timeout

       Possibilities:
               long   (0)
               short   (1)"
   ::= {er1646v2LacpBMembersEntry 67108864}


er1646v2LacpBMacAddress OBJECT IDENTIFIER ::= {er1646v2LacpB 201}

er1646v2LacpBMacAddressSSCTable OBJECT-TYPE
   SYNTAX      SEQUENCE OF Er1646v2LacpBMacAddressEntry
   MAX-ACCESS  not-accessible
   STATUS      current
   DESCRIPTION
      "Configurable MAC address of LACP bundle"
   ::= {er1646v2LacpBMacAddress 1}

er1646v2LacpBMacAddressEntry OBJECT-TYPE
   SYNTAX      Er1646v2LacpBMacAddressEntry
   MAX-ACCESS  not-accessible
   STATUS      current
   DESCRIPTION
      ""
   INDEX      { er1646v2LacpBMacAddressGlobalIx }
   ::= {er1646v2LacpBMacAddressSSCTable 1}

Er1646v2LacpBMacAddressEntry ::=
   SEQUENCE
      {
      er1646v2LacpBMacAddressGlobalIx
         GlobalIndex,
      er1646v2LacpBMacAddressFirstMember
         Integer32,
      er1646v2LacpBMacAddressDeviceMac
         DisplayString,
      er1646v2LacpBMacAddressUserMac
         OCTET STRING,
      er1646v2LacpBMacAddressRandomMac
         Integer32
      }

er1646v2LacpBMacAddressGlobalIx OBJECT-TYPE
   SYNTAX      GlobalIndex
   MAX-ACCESS  not-accessible
   STATUS      current
   DESCRIPTION
      "The value of the tlsCntTreeGlobalIndex of the MANAGED OBJECT."
   ::= {er1646v2LacpBMacAddressEntry 10}

er1646v2LacpBMacAddressFirstMember OBJECT-TYPE
   SYNTAX      Integer32
   MAX-ACCESS  read-write
   STATUS      current
   DESCRIPTION
      "Path: lacpBundle.editConf.macAddress.firstMember"
   ::= {er1646v2LacpBMacAddressEntry 83886080}

er1646v2LacpBMacAddressDeviceMac OBJECT-TYPE
   SYNTAX      DisplayString
   MAX-ACCESS  read-write
   STATUS      current
   DESCRIPTION
      "Path: lacpBundle.editConf.macAddress.deviceMac"
   ::= {er1646v2LacpBMacAddressEntry 50331648}

er1646v2LacpBMacAddressUserMac OBJECT-TYPE
   SYNTAX      OCTET STRING
   MAX-ACCESS  read-write
   STATUS      current
   DESCRIPTION
      "Path: lacpBundle.editConf.macAddress.userMac

       MAC address."
   ::= {er1646v2LacpBMacAddressEntry 33554432}

er1646v2LacpBMacAddressRandomMac OBJECT-TYPE
   SYNTAX      Integer32
   MAX-ACCESS  read-write
   STATUS      current
   DESCRIPTION
      "Path: lacpBundle.editConf.macAddress.randomMac"
   ::= {er1646v2LacpBMacAddressEntry 67108864}



sr1646v2LacpB OBJECT IDENTIFIER ::= {r1646v2LacpB 14}


sr1646v2LacpBDescr OBJECT IDENTIFIER ::= {sr1646v2LacpB 101}

sr1646v2LacpBDescrTable OBJECT-TYPE
   SYNTAX      SEQUENCE OF Sr1646v2LacpBDescrEntry
   MAX-ACCESS  not-accessible
   STATUS      current
   DESCRIPTION
      "ifDescr"
   ::= {sr1646v2LacpBDescr 1}

sr1646v2LacpBDescrEntry OBJECT-TYPE
   SYNTAX      Sr1646v2LacpBDescrEntry
   MAX-ACCESS  not-accessible
   STATUS      current
   DESCRIPTION
      ""
   INDEX      { sr1646v2LacpBDescrGlobalIx }
   ::= {sr1646v2LacpBDescrTable 1}

Sr1646v2LacpBDescrEntry ::=
   SEQUENCE
      {
      sr1646v2LacpBDescrGlobalIx
         GlobalIndex,
      sr1646v2LacpBDescrValue
         DisplayString
      }

sr1646v2LacpBDescrGlobalIx OBJECT-TYPE
   SYNTAX      GlobalIndex
   MAX-ACCESS  not-accessible
   STATUS      current
   DESCRIPTION
      "The value of the tlsCntTreeGlobalIndex of the MANAGED OBJECT."
   ::= {sr1646v2LacpBDescrEntry 10}

sr1646v2LacpBDescrValue OBJECT-TYPE
   SYNTAX      DisplayString
   MAX-ACCESS  read-only
   STATUS      current
   DESCRIPTION
      "Path: lacpBundle.status.ifDescr"
   ::= {sr1646v2LacpBDescrEntry 2147483648}


sr1646v2LacpBType OBJECT IDENTIFIER ::= {sr1646v2LacpB 102}

sr1646v2LacpBTypeTable OBJECT-TYPE
   SYNTAX      SEQUENCE OF Sr1646v2LacpBTypeEntry
   MAX-ACCESS  not-accessible
   STATUS      current
   DESCRIPTION
      "ifType"
   ::= {sr1646v2LacpBType 1}

sr1646v2LacpBTypeEntry OBJECT-TYPE
   SYNTAX      Sr1646v2LacpBTypeEntry
   MAX-ACCESS  not-accessible
   STATUS      current
   DESCRIPTION
      ""
   INDEX      { sr1646v2LacpBTypeGlobalIx }
   ::= {sr1646v2LacpBTypeTable 1}

Sr1646v2LacpBTypeEntry ::=
   SEQUENCE
      {
      sr1646v2LacpBTypeGlobalIx
         GlobalIndex,
      sr1646v2LacpBTypeValue
         INTEGER
      }

sr1646v2LacpBTypeGlobalIx OBJECT-TYPE
   SYNTAX      GlobalIndex
   MAX-ACCESS  not-accessible
   STATUS      current
   DESCRIPTION
      "The value of the tlsCntTreeGlobalIndex of the MANAGED OBJECT."
   ::= {sr1646v2LacpBTypeEntry 10}

sr1646v2LacpBTypeValue OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: lacpBundle.status.ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1646v2LacpBTypeEntry 2147483648}


sr1646v2LacpBMtu OBJECT IDENTIFIER ::= {sr1646v2LacpB 103}

sr1646v2LacpBMtuTable OBJECT-TYPE
   SYNTAX      SEQUENCE OF Sr1646v2LacpBMtuEntry
   MAX-ACCESS  not-accessible
   STATUS      current
   DESCRIPTION
      "ifMtu"
   ::= {sr1646v2LacpBMtu 1}

sr1646v2LacpBMtuEntry OBJECT-TYPE
   SYNTAX      Sr1646v2LacpBMtuEntry
   MAX-ACCESS  not-accessible
   STATUS      current
   DESCRIPTION
      ""
   INDEX      { sr1646v2LacpBMtuGlobalIx }
   ::= {sr1646v2LacpBMtuTable 1}

Sr1646v2LacpBMtuEntry ::=
   SEQUENCE
      {
      sr1646v2LacpBMtuGlobalIx
         GlobalIndex,
      sr1646v2LacpBMtuValue
         Integer32
      }

sr1646v2LacpBMtuGlobalIx OBJECT-TYPE
   SYNTAX      GlobalIndex
   MAX-ACCESS  not-accessible
   STATUS      current
   DESCRIPTION
      "The value of the tlsCntTreeGlobalIndex of the MANAGED OBJECT."
   ::= {sr1646v2LacpBMtuEntry 10}

sr1646v2LacpBMtuValue OBJECT-TYPE
   SYNTAX      Integer32
   MAX-ACCESS  read-only
   STATUS      current
   DESCRIPTION
      "Path: lacpBundle.status.ifMtu"
   ::= {sr1646v2LacpBMtuEntry 2147483648}


sr1646v2LacpBOperStatus OBJECT IDENTIFIER ::= {sr1646v2LacpB 107}

sr1646v2LacpBOperStatusTable OBJECT-TYPE
   SYNTAX      SEQUENCE OF Sr1646v2LacpBOperStatusEntry
   MAX-ACCESS  not-accessible
   STATUS      current
   DESCRIPTION
      "ifOperStatus"
   ::= {sr1646v2LacpBOperStatus 1}

sr1646v2LacpBOperStatusEntry OBJECT-TYPE
   SYNTAX      Sr1646v2LacpBOperStatusEntry
   MAX-ACCESS  not-accessible
   STATUS      current
   DESCRIPTION
      ""
   INDEX      { sr1646v2LacpBOperStatusGlobalIx }
   ::= {sr1646v2LacpBOperStatusTable 1}

Sr1646v2LacpBOperStatusEntry ::=
   SEQUENCE
      {
      sr1646v2LacpBOperStatusGlobalIx
         GlobalIndex,
      sr1646v2LacpBOperStatusValue
         INTEGER
      }

sr1646v2LacpBOperStatusGlobalIx OBJECT-TYPE
   SYNTAX      GlobalIndex
   MAX-ACCESS  not-accessible
   STATUS      current
   DESCRIPTION
      "The value of the tlsCntTreeGlobalIndex of the MANAGED OBJECT."
   ::= {sr1646v2LacpBOperStatusEntry 10}

sr1646v2LacpBOperStatusValue OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: lacpBundle.status.ifOperStatus

       Possibilities:
               up   (1)
               down   (2)
               testing   (3)
               unknown   (4)
               dormant   (5)
               notPresent   (6)
               lowerLayerDown   (7)"
   ::= {sr1646v2LacpBOperStatusEntry 2147483648}


sr1646v2LacpBLastChange OBJECT IDENTIFIER ::= {sr1646v2LacpB 108}

sr1646v2LacpBLastChangeTable OBJECT-TYPE
   SYNTAX      SEQUENCE OF Sr1646v2LacpBLastChangeEntry
   MAX-ACCESS  not-accessible
   STATUS      current
   DESCRIPTION
      "ifLastChange"
   ::= {sr1646v2LacpBLastChange 1}

sr1646v2LacpBLastChangeEntry OBJECT-TYPE
   SYNTAX      Sr1646v2LacpBLastChangeEntry
   MAX-ACCESS  not-accessible
   STATUS      current
   DESCRIPTION
      ""
   INDEX      { sr1646v2LacpBLastChangeGlobalIx }
   ::= {sr1646v2LacpBLastChangeTable 1}

Sr1646v2LacpBLastChangeEntry ::=
   SEQUENCE
      {
      sr1646v2LacpBLastChangeGlobalIx
         GlobalIndex,
      sr1646v2LacpBLastChangeValue
         TimeTicks
      }

sr1646v2LacpBLastChangeGlobalIx OBJECT-TYPE
   SYNTAX      GlobalIndex
   MAX-ACCESS  not-accessible
   STATUS      current
   DESCRIPTION
      "The value of the tlsCntTreeGlobalIndex of the MANAGED OBJECT."
   ::= {sr1646v2LacpBLastChangeEntry 10}

sr1646v2LacpBLastChangeValue OBJECT-TYPE
   SYNTAX      TimeTicks
   MAX-ACCESS  read-only
   STATUS      current
   DESCRIPTION
      "Path: lacpBundle.status.ifLastChange

       Time in centi-second."
   ::= {sr1646v2LacpBLastChangeEntry 2147483648}


sr1646v2LacpBLastChangeD OBJECT IDENTIFIER ::= {sr1646v2LacpB 183}

sr1646v2LacpBLastChangeDTable OBJECT-TYPE
   SYNTAX      SEQUENCE OF Sr1646v2LacpBLastChangeDEntry
   MAX-ACCESS  not-accessible
   STATUS      current
   DESCRIPTION
      "ifLastChangeDate"
   ::= {sr1646v2LacpBLastChangeD 1}

sr1646v2LacpBLastChangeDEntry OBJECT-TYPE
   SYNTAX      Sr1646v2LacpBLastChangeDEntry
   MAX-ACCESS  not-accessible
   STATUS      current
   DESCRIPTION
      ""
   INDEX      { sr1646v2LacpBLastChangeDGlobalIx }
   ::= {sr1646v2LacpBLastChangeDTable 1}

Sr1646v2LacpBLastChangeDEntry ::=
   SEQUENCE
      {
      sr1646v2LacpBLastChangeDGlobalIx
         GlobalIndex,
      sr1646v2LacpBLastChangeDValue
         DisplayString
      }

sr1646v2LacpBLastChangeDGlobalIx OBJECT-TYPE
   SYNTAX      GlobalIndex
   MAX-ACCESS  not-accessible
   STATUS      current
   DESCRIPTION
      "The value of the tlsCntTreeGlobalIndex of the MANAGED OBJECT."
   ::= {sr1646v2LacpBLastChangeDEntry 10}

sr1646v2LacpBLastChangeDValue OBJECT-TYPE
   SYNTAX      DisplayString
   MAX-ACCESS  read-only
   STATUS      current
   DESCRIPTION
      "Path: lacpBundle.status.ifLastChangeDate"
   ::= {sr1646v2LacpBLastChangeDEntry 2147483648}


sr1646v2LacpBSpeed OBJECT IDENTIFIER ::= {sr1646v2LacpB 104}

sr1646v2LacpBSpeedTable OBJECT-TYPE
   SYNTAX      SEQUENCE OF Sr1646v2LacpBSpeedEntry
   MAX-ACCESS  not-accessible
   STATUS      current
   DESCRIPTION
      "ifSpeed"
   ::= {sr1646v2LacpBSpeed 1}

sr1646v2LacpBSpeedEntry OBJECT-TYPE
   SYNTAX      Sr1646v2LacpBSpeedEntry
   MAX-ACCESS  not-accessible
   STATUS      current
   DESCRIPTION
      ""
   INDEX      { sr1646v2LacpBSpeedGlobalIx }
   ::= {sr1646v2LacpBSpeedTable 1}

Sr1646v2LacpBSpeedEntry ::=
   SEQUENCE
      {
      sr1646v2LacpBSpeedGlobalIx
         GlobalIndex,
      sr1646v2LacpBSpeedValue
         Gauge32
      }

sr1646v2LacpBSpeedGlobalIx OBJECT-TYPE
   SYNTAX      GlobalIndex
   MAX-ACCESS  not-accessible
   STATUS      current
   DESCRIPTION
      "The value of the tlsCntTreeGlobalIndex of the MANAGED OBJECT."
   ::= {sr1646v2LacpBSpeedEntry 10}

sr1646v2LacpBSpeedValue OBJECT-TYPE
   SYNTAX      Gauge32
   MAX-ACCESS  read-only
   STATUS      current
   DESCRIPTION
      "Path: lacpBundle.status.ifSpeed

       32 bit unsigned gauge value."
   ::= {sr1646v2LacpBSpeedEntry 2147483648}


sr1646v2LacpBIp OBJECT IDENTIFIER ::= {sr1646v2LacpB 16}

sr1646v2LacpBIpSSCTable OBJECT-TYPE
   SYNTAX      SEQUENCE OF Sr1646v2LacpBIpEntry
   MAX-ACCESS  not-accessible
   STATUS      current
   DESCRIPTION
      "ip interface status parameters"
   ::= {sr1646v2LacpBIp 1}

sr1646v2LacpBIpEntry OBJECT-TYPE
   SYNTAX      Sr1646v2LacpBIpEntry
   MAX-ACCESS  not-accessible
   STATUS      current
   DESCRIPTION
      ""
   INDEX      { sr1646v2LacpBIpGlobalIx }
   ::= {sr1646v2LacpBIpSSCTable 1}

Sr1646v2LacpBIpEntry ::=
   SEQUENCE
      {
      sr1646v2LacpBIpGlobalIx
         GlobalIndex,
      sr1646v2LacpBIpStatus
         INTEGER,
      sr1646v2LacpBIpAddress
         IpAddress,
      sr1646v2LacpBIpNetMask
         IpAddress,
      sr1646v2LacpBIpDhcpStatus
         INTEGER,
      sr1646v2LacpBIpDhcpLeaseTime
         TimeTicks
      }

sr1646v2LacpBIpGlobalIx OBJECT-TYPE
   SYNTAX      GlobalIndex
   MAX-ACCESS  not-accessible
   STATUS      current
   DESCRIPTION
      "The value of the tlsCntTreeGlobalIndex of the MANAGED OBJECT."
   ::= {sr1646v2LacpBIpEntry 10}

sr1646v2LacpBIpStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: lacpBundle.status.ip.status

       Possibilities:
               up   (1)
               down   (2)
               testing   (3)
               unknown   (4)
               dormant   (5)
               notPresent   (6)
               lowerLayerDown   (7)"
   ::= {sr1646v2LacpBIpEntry 1795162112}

sr1646v2LacpBIpAddress OBJECT-TYPE
   SYNTAX      IpAddress
   MAX-ACCESS  read-only
   STATUS      current
   DESCRIPTION
      "Path: lacpBundle.status.ip.address"
   ::= {sr1646v2LacpBIpEntry 2030043136}

sr1646v2LacpBIpNetMask OBJECT-TYPE
   SYNTAX      IpAddress
   MAX-ACCESS  read-only
   STATUS      current
   DESCRIPTION
      "Path: lacpBundle.status.ip.netMask"
   ::= {sr1646v2LacpBIpEntry 2063597568}

sr1646v2LacpBIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: lacpBundle.status.ip.dhcp.status

       Possibilities:
               none   (0)
               selecting   (1)
               requesting   (2)
               rebinding   (3)
               bound   (4)
               renewing   (5)
               rebooting   (6)
               initreboot   (7)"
   ::= {sr1646v2LacpBIpEntry 402718720}

sr1646v2LacpBIpDhcpLeaseTime OBJECT-TYPE
   SYNTAX      TimeTicks
   MAX-ACCESS  read-only
   STATUS      current
   DESCRIPTION
      "Path: lacpBundle.status.ip.dhcp.leaseTime

       Time in centi-second."
   ::= {sr1646v2LacpBIpEntry 402784256}

sr1646v2LacpBIpSecondaryIp OBJECT-TYPE
   SYNTAX      SEQUENCE OF Sr1646v2LacpBIpSecondaryIpEntry
   MAX-ACCESS  not-accessible
   STATUS      current
   DESCRIPTION
      ""
   ::= {sr1646v2LacpBIp 385875968}

sr1646v2LacpBIpSecondaryIpEntry OBJECT-TYPE
   SYNTAX      Sr1646v2LacpBIpSecondaryIpEntry
   MAX-ACCESS  not-accessible
   STATUS      current
   DESCRIPTION
      ""
   INDEX      { sr1646v2LacpBIpSecondaryIpGlobalIx,
                sr1646v2LacpBIpSecondaryIpTableIx }
   ::= {sr1646v2LacpBIpSecondaryIp 1}

Sr1646v2LacpBIpSecondaryIpEntry ::=
   SEQUENCE
      {
      sr1646v2LacpBIpSecondaryIpGlobalIx
         GlobalIndex,
      sr1646v2LacpBIpSecondaryIpTableIx
         TableIndex,
      sr1646v2LacpBIpSecondaryIpAddress
         IpAddress,
      sr1646v2LacpBIpSecondaryIpNetMask
         IpAddress
      }

sr1646v2LacpBIpSecondaryIpGlobalIx OBJECT-TYPE
   SYNTAX      GlobalIndex
   MAX-ACCESS  not-accessible
   STATUS      current
   DESCRIPTION
      "The value of the tlsCntTreeGlobalIndex of the MANAGED OBJECT."
   ::= {sr1646v2LacpBIpSecondaryIpEntry 10}

sr1646v2LacpBIpSecondaryIpTableIx OBJECT-TYPE
   SYNTAX      TableIndex
   MAX-ACCESS  not-accessible
   STATUS      current
   DESCRIPTION
      ""
   ::= {sr1646v2LacpBIpSecondaryIpEntry 11}

sr1646v2LacpBIpSecondaryIpAddress OBJECT-TYPE
   SYNTAX      IpAddress
   MAX-ACCESS  read-only
   STATUS      current
   DESCRIPTION
      "Path: lacpBundle.status.ip.secondaryIp.address"
   ::= {sr1646v2LacpBIpSecondaryIpEntry 2030043136}

sr1646v2LacpBIpSecondaryIpNetMask OBJECT-TYPE
   SYNTAX      IpAddress
   MAX-ACCESS  read-only
   STATUS      current
   DESCRIPTION
      "Path: lacpBundle.status.ip.secondaryIp.netMask"
   ::= {sr1646v2LacpBIpSecondaryIpEntry 2063597568}


sr1646v2LacpBArpCache OBJECT IDENTIFIER ::= {sr1646v2LacpB 11}

sr1646v2LacpBArpCacheSSCTable OBJECT-TYPE
   SYNTAX      SEQUENCE OF Sr1646v2LacpBArpCacheEntry
   MAX-ACCESS  not-accessible
   STATUS      current
   DESCRIPTION
      "arp cache of ethernet interface"
   ::= {sr1646v2LacpBArpCache 1}

sr1646v2LacpBArpCacheEntry OBJECT-TYPE
   SYNTAX      Sr1646v2LacpBArpCacheEntry
   MAX-ACCESS  not-accessible
   STATUS      current
   DESCRIPTION
      ""
   INDEX      { sr1646v2LacpBArpCacheGlobalIx,
                sr1646v2LacpBArpCacheTableIx }
   ::= {sr1646v2LacpBArpCacheSSCTable 1}

Sr1646v2LacpBArpCacheEntry ::=
   SEQUENCE
      {
      sr1646v2LacpBArpCacheGlobalIx
         GlobalIndex,
      sr1646v2LacpBArpCacheTableIx
         TableIndex,
      sr1646v2LacpBArpCacheMacAddress
         OCTET STRING,
      sr1646v2LacpBArpCacheIpAddress
         IpAddress,
      sr1646v2LacpBArpCacheType
         INTEGER,
      sr1646v2LacpBArpCacheTimeOut
         TimeTicks
      }

sr1646v2LacpBArpCacheGlobalIx OBJECT-TYPE
   SYNTAX      GlobalIndex
   MAX-ACCESS  not-accessible
   STATUS      current
   DESCRIPTION
      "The value of the tlsCntTreeGlobalIndex of the MANAGED OBJECT."
   ::= {sr1646v2LacpBArpCacheEntry 10}

sr1646v2LacpBArpCacheTableIx OBJECT-TYPE
   SYNTAX      TableIndex
   MAX-ACCESS  not-accessible
   STATUS      current
   DESCRIPTION
      ""
   ::= {sr1646v2LacpBArpCacheEntry 11}

sr1646v2LacpBArpCacheMacAddress OBJECT-TYPE
   SYNTAX      OCTET STRING
   MAX-ACCESS  read-only
   STATUS      current
   DESCRIPTION
      "Path: lacpBundle.status.arpCache.macAddress

       MAC address."
   ::= {sr1646v2LacpBArpCacheEntry 16777216}

sr1646v2LacpBArpCacheIpAddress OBJECT-TYPE
   SYNTAX      IpAddress
   MAX-ACCESS  read-only
   STATUS      current
   DESCRIPTION
      "Path: lacpBundle.status.arpCache.ipAddress"
   ::= {sr1646v2LacpBArpCacheEntry 33554432}

sr1646v2LacpBArpCacheType OBJECT-TYPE
   SYNTAX      INTEGER
               {
               static (0),
               dynamic (1)
               }
   MAX-ACCESS  read-only
   STATUS      current
   DESCRIPTION
      "Path: lacpBundle.status.arpCache.type

       Possibilities:
               static   (0)
               dynamic   (1)"
   ::= {sr1646v2LacpBArpCacheEntry 50331648}

sr1646v2LacpBArpCacheTimeOut OBJECT-TYPE
   SYNTAX      TimeTicks
   MAX-ACCESS  read-only
   STATUS      current
   DESCRIPTION
      "Path: lacpBundle.status.arpCache.timeOut

       Time in centi-second."
   ::= {sr1646v2LacpBArpCacheEntry 67108864}


sr1646v2LacpBBrS OBJECT IDENTIFIER ::= {sr1646v2LacpB 28}

sr1646v2LacpBBrSSSCTable OBJECT-TYPE
   SYNTAX      SEQUENCE OF Sr1646v2LacpBBrSEntry
   MAX-ACCESS  not-accessible
   STATUS      current
   DESCRIPTION
      "spanning tree status ethernet interface"
   ::= {sr1646v2LacpBBrS 1}

sr1646v2LacpBBrSEntry OBJECT-TYPE
   SYNTAX      Sr1646v2LacpBBrSEntry
   MAX-ACCESS  not-accessible
   STATUS      current
   DESCRIPTION
      ""
   INDEX      { sr1646v2LacpBBrSGlobalIx }
   ::= {sr1646v2LacpBBrSSSCTable 1}

Sr1646v2LacpBBrSEntry ::=
   SEQUENCE
      {
      sr1646v2LacpBBrSGlobalIx
         GlobalIndex,
      sr1646v2LacpBBrSStatus
         INTEGER,
      sr1646v2LacpBBrSStPortRole
         INTEGER,
      sr1646v2LacpBBrSStPortId
         Integer32,
      sr1646v2LacpBBrSStPpCostExtPathCost
         Integer32,
      sr1646v2LacpBBrSStPpCostIntPathCost
         Integer32,
      sr1646v2LacpBBrSStExtRpCost
         Integer32,
      sr1646v2LacpBBrSStIntRpCost
         Integer32,
      sr1646v2LacpBBrSStDesBrIdPriority
         Integer32,
      sr1646v2LacpBBrSStDesBrIdMacAddress
         OCTET STRING,
      sr1646v2LacpBBrSStDesPrtId
         Integer32,
      sr1646v2LacpBBrSStDesInt
         INTEGER,
      sr1646v2LacpBBrSStEdgeDetection
         INTEGER
      }

sr1646v2LacpBBrSGlobalIx OBJECT-TYPE
   SYNTAX      GlobalIndex
   MAX-ACCESS  not-accessible
   STATUS      current
   DESCRIPTION
      "The value of the tlsCntTreeGlobalIndex of the MANAGED OBJECT."
   ::= {sr1646v2LacpBBrSEntry 10}

sr1646v2LacpBBrSStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: lacpBundle.status.bridging.status

       Possibilities:
               disabled   (0)
               discarding   (1)
               learning   (2)
               forwarding   (3)
               backupBlockedIntfDown   (256)
               backupBlockedIntfUp   (259)
               shutdown   (255)"
   ::= {sr1646v2LacpBBrSEntry 16777216}

sr1646v2LacpBBrSStPortRole OBJECT-TYPE
   SYNTAX      INTEGER
               {
               none (0),
               root (1),
               designated (2),
               alternate (3),
               backup (4),
               disabled (5),
               master (6)
               }
   MAX-ACCESS  read-only
   STATUS      current
   DESCRIPTION
      "Path: lacpBundle.status.bridging.spanningTree.portRole

       Possibilities:
               none   (0)
               root   (1)
               designated   (2)
               alternate   (3)
               backup   (4)
               disabled   (5)
               master   (6)"
   ::= {sr1646v2LacpBBrSEntry 33619968}

sr1646v2LacpBBrSStPortId OBJECT-TYPE
   SYNTAX      Integer32
   MAX-ACCESS  read-only
   STATUS      current
   DESCRIPTION
      "Path: lacpBundle.status.bridging.spanningTree.portId"
   ::= {sr1646v2LacpBBrSEntry 33685504}

sr1646v2LacpBBrSStPpCostExtPathCost OBJECT-TYPE
   SYNTAX      Integer32
   MAX-ACCESS  read-only
   STATUS      current
   DESCRIPTION
      "Path: lacpBundle.status.bridging.spanningTree.portPathCosts.extPathCost"
   ::= {sr1646v2LacpBBrSEntry 33751296}

sr1646v2LacpBBrSStPpCostIntPathCost OBJECT-TYPE
   SYNTAX      Integer32
   MAX-ACCESS  read-only
   STATUS      current
   DESCRIPTION
      "Path: lacpBundle.status.bridging.spanningTree.portPathCosts.intPathCost"
   ::= {sr1646v2LacpBBrSEntry 33751552}

sr1646v2LacpBBrSStExtRpCost OBJECT-TYPE
   SYNTAX      Integer32
   MAX-ACCESS  read-only
   STATUS      current
   DESCRIPTION
      "Path: lacpBundle.status.bridging.spanningTree.extRootPathCost"
   ::= {sr1646v2LacpBBrSEntry 33816576}

sr1646v2LacpBBrSStIntRpCost OBJECT-TYPE
   SYNTAX      Integer32
   MAX-ACCESS  read-only
   STATUS      current
   DESCRIPTION
      "Path: lacpBundle.status.bridging.spanningTree.intRootPathCost"
   ::= {sr1646v2LacpBBrSEntry 33882112}

sr1646v2LacpBBrSStDesBrIdPriority OBJECT-TYPE
   SYNTAX      Integer32
   MAX-ACCESS  read-only
   STATUS      current
   DESCRIPTION
      "Path: lacpBundle.status.bridging.spanningTree.designatedBridgeId.priority"
   ::= {sr1646v2LacpBBrSEntry 33947904}

sr1646v2LacpBBrSStDesBrIdMacAddress OBJECT-TYPE
   SYNTAX      OCTET STRING
   MAX-ACCESS  read-only
   STATUS      current
   DESCRIPTION
      "Path: lacpBundle.status.bridging.spanningTree.designatedBridgeId.macAddress

       MAC address."
   ::= {sr1646v2LacpBBrSEntry 33948160}

sr1646v2LacpBBrSStDesPrtId OBJECT-TYPE
   SYNTAX      Integer32
   MAX-ACCESS  read-only
   STATUS      current
   DESCRIPTION
      "Path: lacpBundle.status.bridging.spanningTree.designatedPortId"
   ::= {sr1646v2LacpBBrSEntry 34013184}

sr1646v2LacpBBrSStDesInt OBJECT-TYPE
   SYNTAX      INTEGER
               {
               no (0),
               yes (1)
               }
   MAX-ACCESS  read-only
   STATUS      current
   DESCRIPTION
      "Path: lacpBundle.status.bridging.spanningTree.designatedOrInternal

       Possibilities:
               no   (0)
               yes   (1)"
   ::= {sr1646v2LacpBBrSEntry 34078720}

sr1646v2LacpBBrSStEdgeDetection OBJECT-TYPE
   SYNTAX      INTEGER
               {
               none (0),
               edge (1),
               notEdge (2)
               }
   MAX-ACCESS  read-only
   STATUS      current
   DESCRIPTION
      "Path: lacpBundle.status.bridging.spanningTree.edgeDetection

       Possibilities:
               none   (0)
               edge   (1)
               notEdge   (2)"
   ::= {sr1646v2LacpBBrSEntry 34144256}


sr1646v2LacpBMacAddress OBJECT IDENTIFIER ::= {sr1646v2LacpB 105}

sr1646v2LacpBMacAddressTable OBJECT-TYPE
   SYNTAX      SEQUENCE OF Sr1646v2LacpBMacAddressEntry
   MAX-ACCESS  not-accessible
   STATUS      current
   DESCRIPTION
      "ifPhysAddress"
   ::= {sr1646v2LacpBMacAddress 1}

sr1646v2LacpBMacAddressEntry OBJECT-TYPE
   SYNTAX      Sr1646v2LacpBMacAddressEntry
   MAX-ACCESS  not-accessible
   STATUS      current
   DESCRIPTION
      ""
   INDEX      { sr1646v2LacpBMacAddressGlobalIx }
   ::= {sr1646v2LacpBMacAddressTable 1}

Sr1646v2LacpBMacAddressEntry ::=
   SEQUENCE
      {
      sr1646v2LacpBMacAddressGlobalIx
         GlobalIndex,
      sr1646v2LacpBMacAddressValue
         OCTET STRING
      }

sr1646v2LacpBMacAddressGlobalIx OBJECT-TYPE
   SYNTAX      GlobalIndex
   MAX-ACCESS  not-accessible
   STATUS      current
   DESCRIPTION
      "The value of the tlsCntTreeGlobalIndex of the MANAGED OBJECT."
   ::= {sr1646v2LacpBMacAddressEntry 10}

sr1646v2LacpBMacAddressValue OBJECT-TYPE
   SYNTAX      OCTET STRING
   MAX-ACCESS  read-only
   STATUS      current
   DESCRIPTION
      "Path: lacpBundle.status.macAddress

       MAC address."
   ::= {sr1646v2LacpBMacAddressEntry 2147483648}


sr1646v2LacpBIpAdEntBcastAddr OBJECT IDENTIFIER ::= {sr1646v2LacpB 124}

sr1646v2LacpBIpAdEntBcastAddrTable OBJECT-TYPE
   SYNTAX      SEQUENCE OF Sr1646v2LacpBIpAdEntBcastAddrEntry
   MAX-ACCESS  not-accessible
   STATUS      current
   DESCRIPTION
      "ipAdEntBcastAddr"
   ::= {sr1646v2LacpBIpAdEntBcastAddr 1}

sr1646v2LacpBIpAdEntBcastAddrEntry OBJECT-TYPE
   SYNTAX      Sr1646v2LacpBIpAdEntBcastAddrEntry
   MAX-ACCESS  not-accessible
   STATUS      current
   DESCRIPTION
      ""
   INDEX      { sr1646v2LacpBIpAdEntBcastAddrGlobalIx }
   ::= {sr1646v2LacpBIpAdEntBcastAddrTable 1}

Sr1646v2LacpBIpAdEntBcastAddrEntry ::=
   SEQUENCE
      {
      sr1646v2LacpBIpAdEntBcastAddrGlobalIx
         GlobalIndex,
      sr1646v2LacpBIpAdEntBcastAddrValue
         Integer32
      }

sr1646v2LacpBIpAdEntBcastAddrGlobalIx OBJECT-TYPE
   SYNTAX      GlobalIndex
   MAX-ACCESS  not-accessible
   STATUS      current
   DESCRIPTION
      "The value of the tlsCntTreeGlobalIndex of the MANAGED OBJECT."
   ::= {sr1646v2LacpBIpAdEntBcastAddrEntry 10}

sr1646v2LacpBIpAdEntBcastAddrValue OBJECT-TYPE
   SYNTAX      Integer32
   MAX-ACCESS  read-only
   STATUS      current
   DESCRIPTION
      "Path: lacpBundle.status.ipAdEntBcastAddr"
   ::= {sr1646v2LacpBIpAdEntBcastAddrEntry 2147483648}


sr1646v2LacpBIpAdEntReasmMaxSize OBJECT IDENTIFIER ::= {sr1646v2LacpB 125}

sr1646v2LacpBIpAdEntReasmMaxSizeTable OBJECT-TYPE
   SYNTAX      SEQUENCE OF Sr1646v2LacpBIpAdEntReasmMaxSizeEntry
   MAX-ACCESS  not-accessible
   STATUS      current
   DESCRIPTION
      "ipAdEntReasmMaxSize"
   ::= {sr1646v2LacpBIpAdEntReasmMaxSize 1}

sr1646v2LacpBIpAdEntReasmMaxSizeEntry OBJECT-TYPE
   SYNTAX      Sr1646v2LacpBIpAdEntReasmMaxSizeEntry
   MAX-ACCESS  not-accessible
   STATUS      current
   DESCRIPTION
      ""
   INDEX      { sr1646v2LacpBIpAdEntReasmMaxSizeGlobalIx }
   ::= {sr1646v2LacpBIpAdEntReasmMaxSizeTable 1}

Sr1646v2LacpBIpAdEntReasmMaxSizeEntry ::=
   SEQUENCE
      {
      sr1646v2LacpBIpAdEntReasmMaxSizeGlobalIx
         GlobalIndex,
      sr1646v2LacpBIpAdEntReasmMaxSizeValue
         Integer32
      }

sr1646v2LacpBIpAdEntReasmMaxSizeGlobalIx OBJECT-TYPE
   SYNTAX      GlobalIndex
   MAX-ACCESS  not-accessible
   STATUS      current
   DESCRIPTION
      "The value of the tlsCntTreeGlobalIndex of the MANAGED OBJECT."
   ::= {sr1646v2LacpBIpAdEntReasmMaxSizeEntry 10}

sr1646v2LacpBIpAdEntReasmMaxSizeValue OBJECT-TYPE
   SYNTAX      Integer32
   MAX-ACCESS  read-only
   STATUS      current
   DESCRIPTION
      "Path: lacpBundle.status.ipAdEntReasmMaxSize"
   ::= {sr1646v2LacpBIpAdEntReasmMaxSizeEntry 2147483648}


sr1646v2LacpBVlan OBJECT IDENTIFIER ::= {sr1646v2LacpB 34}

sr1646v2LacpBVlanSSCTable OBJECT-TYPE
   SYNTAX      SEQUENCE OF Sr1646v2LacpBVlanEntry
   MAX-ACCESS  not-accessible
   STATUS      current
   DESCRIPTION
      ""
   ::= {sr1646v2LacpBVlan 1}

sr1646v2LacpBVlanEntry OBJECT-TYPE
   SYNTAX      Sr1646v2LacpBVlanEntry
   MAX-ACCESS  not-accessible
   STATUS      current
   DESCRIPTION
      ""
   INDEX      { sr1646v2LacpBVlanGlobalIx,
                sr1646v2LacpBVlanTableIx }
   ::= {sr1646v2LacpBVlanSSCTable 1}

Sr1646v2LacpBVlanEntry ::=
   SEQUENCE
      {
      sr1646v2LacpBVlanGlobalIx
         GlobalIndex,
      sr1646v2LacpBVlanTableIx
         TableIndex,
      sr1646v2LacpBVlanName
         DisplayString,
      sr1646v2LacpBVlanMode
         INTEGER,
      sr1646v2LacpBVlanIfOperStatus
         INTEGER,
      sr1646v2LacpBVlanIfLastChange
         TimeTicks,
      sr1646v2LacpBVlanIfLastChangeDate
         DisplayString,
      sr1646v2LacpBVlanIpAddress
         IpAddress,
      sr1646v2LacpBVlanIpNetMask
         IpAddress,
      sr1646v2LacpBVlanIpRemote
         IpAddress,
      sr1646v2LacpBVlanIpDhcpStatus
         INTEGER,
      sr1646v2LacpBVlanIpDhcpLeaseTime
         TimeTicks,
      sr1646v2LacpBVlanIpV6State
         INTEGER,
      sr1646v2LacpBVlanIpV6InterfaceId
         OCTET STRING,
      sr1646v2LacpBVlanIpV6LinkMtu
         Integer32,
      sr1646v2LacpBVlanIpV6HopLimit
         Integer32,
      sr1646v2LacpBVlanIpV6DhcpIaid
         Counter32,
      sr1646v2LacpBVlanIpV6RaRcvOption
         Integer32,
      sr1646v2LacpBVlanBridgingStatus
         INTEGER,
      sr1646v2LacpBVlanBridgingSpanningTreePortRole
         INTEGER,
      sr1646v2LacpBVlanBridgingSpanningTreePortId
         Integer32,
      sr1646v2LacpBVlanBridgingSpanningTreePpCostExtPathCost
         Integer32,
      sr1646v2LacpBVlanBridgingSpanningTreePpCostIntPathCost
         Integer32,
      sr1646v2LacpBVlanBridgingSpanningTreeExtRpCost
         Integer32,
      sr1646v2LacpBVlanBridgingSpanningTreeIntRpCost
         Integer32,
      sr1646v2LacpBVlanBridgingSpanningTreeDesBrIdPriority
         Integer32,
      sr1646v2LacpBVlanBridgingSpanningTreeDesBrIdMacAddress
         OCTET STRING,
      sr1646v2LacpBVlanBridgingSpanningTreeDesPrtId
         Integer32,
      sr1646v2LacpBVlanBridgingSpanningTreeDesInt
         INTEGER,
      sr1646v2LacpBVlanBridgingSpanningTreeEdgeDetection
         INTEGER,
      sr1646v2LacpBVlanVlanVid
         Integer32,
      sr1646v2LacpBVlanPppOEthDiscState
         INTEGER,
      sr1646v2LacpBVlanPppOEthPeerMac
         OCTET STRING,
      sr1646v2LacpBVlanPppOEthServiceName
         DisplayString,
      sr1646v2LacpBVlanPppLcpState
         INTEGER,
      sr1646v2LacpBVlanPppIpcpState
         INTEGER,
      sr1646v2LacpBVlanPppIp6cpState
         INTEGER,
      sr1646v2LacpBVlanPppMyAutSt
         INTEGER,
      sr1646v2LacpBVlanPppHisAutSt
         INTEGER,
      sr1646v2LacpBVlanPppMru
         Integer32
      }

sr1646v2LacpBVlanGlobalIx OBJECT-TYPE
   SYNTAX      GlobalIndex
   MAX-ACCESS  not-accessible
   STATUS      current
   DESCRIPTION
      "The value of the tlsCntTreeGlobalIndex of the MANAGED OBJECT."
   ::= {sr1646v2LacpBVlanEntry 10}

sr1646v2LacpBVlanTableIx OBJECT-TYPE
   SYNTAX      TableIndex
   MAX-ACCESS  not-accessible
   STATUS      current
   DESCRIPTION
      ""
   ::= {sr1646v2LacpBVlanEntry 11}

sr1646v2LacpBVlanName OBJECT-TYPE
   SYNTAX      DisplayString
   MAX-ACCESS  read-only
   STATUS      current
   DESCRIPTION
      "Path: lacpBundle.status.vlan.name"
   ::= {sr1646v2LacpBVlanEntry 16777216}

sr1646v2LacpBVlanMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: lacpBundle.status.vlan.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1646v2LacpBVlanEntry 335544320}

sr1646v2LacpBVlanIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: lacpBundle.status.vlan.ifOperStatus

       Possibilities:
               up   (1)
               down   (2)
               testing   (3)
               unknown   (4)
               dormant   (5)
               notPresent   (6)
               lowerLayerDown   (7)"
   ::= {sr1646v2LacpBVlanEntry 1795162112}

sr1646v2LacpBVlanIfLastChange OBJECT-TYPE
   SYNTAX      TimeTicks
   MAX-ACCESS  read-only
   STATUS      current
   DESCRIPTION
      "Path: lacpBundle.status.vlan.ifLastChange

       Time in centi-second."
   ::= {sr1646v2LacpBVlanEntry 1811939328}

sr1646v2LacpBVlanIfLastChangeDate OBJECT-TYPE
   SYNTAX      DisplayString
   MAX-ACCESS  read-only
   STATUS      current
   DESCRIPTION
      "Path: lacpBundle.status.vlan.ifLastChangeDate"
   ::= {sr1646v2LacpBVlanEntry 3070230528}

sr1646v2LacpBVlanIpAddress OBJECT-TYPE
   SYNTAX      IpAddress
   MAX-ACCESS  read-only
   STATUS      current
   DESCRIPTION
      "Path: lacpBundle.status.vlan.ip.address"
   ::= {sr1646v2LacpBVlanEntry 51380224}

sr1646v2LacpBVlanIpNetMask OBJECT-TYPE
   SYNTAX      IpAddress
   MAX-ACCESS  read-only
   STATUS      current
   DESCRIPTION
      "Path: lacpBundle.status.vlan.ip.netMask"
   ::= {sr1646v2LacpBVlanEntry 51445760}

sr1646v2LacpBVlanIpRemote OBJECT-TYPE
   SYNTAX      IpAddress
   MAX-ACCESS  read-only
   STATUS      current
   DESCRIPTION
      "Path: lacpBundle.status.vlan.ip.remote"
   ::= {sr1646v2LacpBVlanEntry 51511296}

sr1646v2LacpBVlanIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: lacpBundle.status.vlan.ip.dhcp.status

       Possibilities:
               none   (0)
               selecting   (1)
               requesting   (2)
               rebinding   (3)
               bound   (4)
               renewing   (5)
               rebooting   (6)
               initreboot   (7)"
   ::= {sr1646v2LacpBVlanEntry 51904768}

sr1646v2LacpBVlanIpDhcpLeaseTime OBJECT-TYPE
   SYNTAX      TimeTicks
   MAX-ACCESS  read-only
   STATUS      current
   DESCRIPTION
      "Path: lacpBundle.status.vlan.ip.dhcp.leaseTime

       Time in centi-second."
   ::= {sr1646v2LacpBVlanEntry 51905024}

sr1646v2LacpBVlanIpV6State OBJECT-TYPE
   SYNTAX      INTEGER
               {
               disabled (0),
               enabled (1)
               }
   MAX-ACCESS  read-only
   STATUS      current
   DESCRIPTION
      "Path: lacpBundle.status.vlan.ipV6.state

       Possibilities:
               disabled   (0)
               enabled   (1)"
   ::= {sr1646v2LacpBVlanEntry 100728832}

sr1646v2LacpBVlanIpV6InterfaceId OBJECT-TYPE
   SYNTAX      OCTET STRING
   MAX-ACCESS  read-only
   STATUS      current
   DESCRIPTION
      "Path: lacpBundle.status.vlan.ipV6.interfaceId"
   ::= {sr1646v2LacpBVlanEntry 100794368}

sr1646v2LacpBVlanIpV6LinkMtu OBJECT-TYPE
   SYNTAX      Integer32
   MAX-ACCESS  read-only
   STATUS      current
   DESCRIPTION
      "Path: lacpBundle.status.vlan.ipV6.linkMtu"
   ::= {sr1646v2LacpBVlanEntry 100925440}

sr1646v2LacpBVlanIpV6HopLimit OBJECT-TYPE
   SYNTAX      Integer32
   MAX-ACCESS  read-only
   STATUS      current
   DESCRIPTION
      "Path: lacpBundle.status.vlan.ipV6.hopLimit"
   ::= {sr1646v2LacpBVlanEntry 100990976}

sr1646v2LacpBVlanIpV6DhcpIaid OBJECT-TYPE
   SYNTAX      Counter32
   MAX-ACCESS  read-only
   STATUS      current
   DESCRIPTION
      "Path: lacpBundle.status.vlan.ipV6.dhcp.iaid

       32 bit unsigned wrappable counter."
   ::= {sr1646v2LacpBVlanEntry 101056768}

sr1646v2LacpBVlanIpV6RaRcvOption OBJECT-TYPE
   SYNTAX      Integer32
   MAX-ACCESS  read-only
   STATUS      current
   DESCRIPTION
      "Path: lacpBundle.status.vlan.ipV6.raRcvOption

       Bit meanings:
               bit 0 = linkMtu,
               bit 1 = srcLinkLayer,
               bit 2 = prefixInfo,
               bit 3 = rdnss,
               bit 4 = dnssl"
   ::= {sr1646v2LacpBVlanEntry 101122048}

sr1646v2LacpBVlanBridgingStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: lacpBundle.status.vlan.bridging.status

       Possibilities:
               disabled   (0)
               discarding   (1)
               learning   (2)
               forwarding   (3)
               backupBlockedIntfDown   (256)
               backupBlockedIntfUp   (259)
               shutdown   (255)"
   ::= {sr1646v2LacpBVlanEntry 453050368}

sr1646v2LacpBVlanBridgingSpanningTreePortRole OBJECT-TYPE
   SYNTAX      INTEGER
               {
               none (0),
               root (1),
               designated (2),
               alternate (3),
               backup (4),
               disabled (5),
               master (6)
               }
   MAX-ACCESS  read-only
   STATUS      current
   DESCRIPTION
      "Path: lacpBundle.status.vlan.bridging.spanningTree.portRole

       Possibilities:
               none   (0)
               root   (1)
               designated   (2)
               alternate   (3)
               backup   (4)
               disabled   (5)
               master   (6)"
   ::= {sr1646v2LacpBVlanEntry 453116160}

sr1646v2LacpBVlanBridgingSpanningTreePortId OBJECT-TYPE
   SYNTAX      Integer32
   MAX-ACCESS  read-only
   STATUS      current
   DESCRIPTION
      "Path: lacpBundle.status.vlan.bridging.spanningTree.portId"
   ::= {sr1646v2LacpBVlanEntry 453116416}

sr1646v2LacpBVlanBridgingSpanningTreePpCostExtPathCost OBJECT-TYPE
   SYNTAX      Integer32
   MAX-ACCESS  read-only
   STATUS      current
   DESCRIPTION
      "Path: lacpBundle.status.vlan.bridging.spanningTree.portPathCosts.extPathCost"
   ::= {sr1646v2LacpBVlanEntry 453116673}

sr1646v2LacpBVlanBridgingSpanningTreePpCostIntPathCost OBJECT-TYPE
   SYNTAX      Integer32
   MAX-ACCESS  read-only
   STATUS      current
   DESCRIPTION
      "Path: lacpBundle.status.vlan.bridging.spanningTree.portPathCosts.intPathCost"
   ::= {sr1646v2LacpBVlanEntry 453116674}

sr1646v2LacpBVlanBridgingSpanningTreeExtRpCost OBJECT-TYPE
   SYNTAX      Integer32
   MAX-ACCESS  read-only
   STATUS      current
   DESCRIPTION
      "Path: lacpBundle.status.vlan.bridging.spanningTree.extRootPathCost"
   ::= {sr1646v2LacpBVlanEntry 453116928}

sr1646v2LacpBVlanBridgingSpanningTreeIntRpCost OBJECT-TYPE
   SYNTAX      Integer32
   MAX-ACCESS  read-only
   STATUS      current
   DESCRIPTION
      "Path: lacpBundle.status.vlan.bridging.spanningTree.intRootPathCost"
   ::= {sr1646v2LacpBVlanEntry 453117184}

sr1646v2LacpBVlanBridgingSpanningTreeDesBrIdPriority OBJECT-TYPE
   SYNTAX      Integer32
   MAX-ACCESS  read-only
   STATUS      current
   DESCRIPTION
      "Path: lacpBundle.status.vlan.bridging.spanningTree.designatedBridgeId.priority"
   ::= {sr1646v2LacpBVlanEntry 453117441}

sr1646v2LacpBVlanBridgingSpanningTreeDesBrIdMacAddress OBJECT-TYPE
   SYNTAX      OCTET STRING
   MAX-ACCESS  read-only
   STATUS      current
   DESCRIPTION
      "Path: lacpBundle.status.vlan.bridging.spanningTree.designatedBridgeId.macAddress

       MAC address."
   ::= {sr1646v2LacpBVlanEntry 453117442}

sr1646v2LacpBVlanBridgingSpanningTreeDesPrtId OBJECT-TYPE
   SYNTAX      Integer32
   MAX-ACCESS  read-only
   STATUS      current
   DESCRIPTION
      "Path: lacpBundle.status.vlan.bridging.spanningTree.designatedPortId"
   ::= {sr1646v2LacpBVlanEntry 453117696}

sr1646v2LacpBVlanBridgingSpanningTreeDesInt OBJECT-TYPE
   SYNTAX      INTEGER
               {
               no (0),
               yes (1)
               }
   MAX-ACCESS  read-only
   STATUS      current
   DESCRIPTION
      "Path: lacpBundle.status.vlan.bridging.spanningTree.designatedOrInternal

       Possibilities:
               no   (0)
               yes   (1)"
   ::= {sr1646v2LacpBVlanEntry 453117952}

sr1646v2LacpBVlanBridgingSpanningTreeEdgeDetection OBJECT-TYPE
   SYNTAX      INTEGER
               {
               none (0),
               edge (1),
               notEdge (2)
               }
   MAX-ACCESS  read-only
   STATUS      current
   DESCRIPTION
      "Path: lacpBundle.status.vlan.bridging.spanningTree.edgeDetection

       Possibilities:
               none   (0)
               edge   (1)
               notEdge   (2)"
   ::= {sr1646v2LacpBVlanEntry 453118208}

sr1646v2LacpBVlanVlanVid OBJECT-TYPE
   SYNTAX      Integer32
   MAX-ACCESS  read-only
   STATUS      current
   DESCRIPTION
      "Path: lacpBundle.status.vlan.vlan.vid"
   ::= {sr1646v2LacpBVlanEntry 234946560}

sr1646v2LacpBVlanPppOEthDiscState OBJECT-TYPE
   SYNTAX      INTEGER
               {
               idle (0),
               waitForPADO (1),
               waitForPADS (2),
               established (3)
               }
   MAX-ACCESS  read-only
   STATUS      current
   DESCRIPTION
      "Path: lacpBundle.status.vlan.pppOverEth.discState

       Possibilities:
               idle   (0)
               waitForPADO   (1)
               waitForPADS   (2)
               established   (3)"
   ::= {sr1646v2LacpBVlanEntry 67174400}

sr1646v2LacpBVlanPppOEthPeerMac OBJECT-TYPE
   SYNTAX      OCTET STRING
   MAX-ACCESS  read-only
   STATUS      current
   DESCRIPTION
      "Path: lacpBundle.status.vlan.pppOverEth.remoteMacAddress

       MAC address."
   ::= {sr1646v2LacpBVlanEntry 67239936}

sr1646v2LacpBVlanPppOEthServiceName OBJECT-TYPE
   SYNTAX      DisplayString
   MAX-ACCESS  read-only
   STATUS      current
   DESCRIPTION
      "Path: lacpBundle.status.vlan.pppOverEth.serviceName"
   ::= {sr1646v2LacpBVlanEntry 67305472}

sr1646v2LacpBVlanPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: lacpBundle.status.vlan.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2LacpBVlanEntry 83951616}

sr1646v2LacpBVlanPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: lacpBundle.status.vlan.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2LacpBVlanEntry 84017152}

sr1646v2LacpBVlanPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: lacpBundle.status.vlan.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2LacpBVlanEntry 84869120}

sr1646v2LacpBVlanPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: lacpBundle.status.vlan.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1646v2LacpBVlanEntry 84541440}

sr1646v2LacpBVlanPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: lacpBundle.status.vlan.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1646v2LacpBVlanEntry 84606976}

sr1646v2LacpBVlanPppMru OBJECT-TYPE
   SYNTAX      Integer32
   MAX-ACCESS  read-only
   STATUS      current
   DESCRIPTION
      "Path: lacpBundle.status.vlan.ppp.mru"
   ::= {sr1646v2LacpBVlanEntry 84934656}

sr1646v2LacpBVlanIpSecondaryIp OBJECT-TYPE
   SYNTAX      SEQUENCE OF Sr1646v2LacpBVlanIpSecondaryIpEntry
   MAX-ACCESS  not-accessible
   STATUS      current
   DESCRIPTION
      ""
   ::= {sr1646v2LacpBVlan 51838976}

sr1646v2LacpBVlanIpSecondaryIpEntry OBJECT-TYPE
   SYNTAX      Sr1646v2LacpBVlanIpSecondaryIpEntry
   MAX-ACCESS  not-accessible
   STATUS      current
   DESCRIPTION
      ""
   INDEX      { sr1646v2LacpBVlanIpSecondaryIpGlobalIx,
                sr1646v2LacpBVlanTableIx,
                sr1646v2LacpBVlanIpSecondaryIpTableIx }
   ::= {sr1646v2LacpBVlanIpSecondaryIp 1}

Sr1646v2LacpBVlanIpSecondaryIpEntry ::=
   SEQUENCE
      {
      sr1646v2LacpBVlanIpSecondaryIpGlobalIx
         GlobalIndex,
      sr1646v2LacpBVlanIpSecondaryIpTableIx
         TableIndex,
      sr1646v2LacpBVlanIpSecondaryIpAddress
         IpAddress,
      sr1646v2LacpBVlanIpSecondaryIpNetMask
         IpAddress
      }

sr1646v2LacpBVlanIpSecondaryIpGlobalIx OBJECT-TYPE
   SYNTAX      GlobalIndex
   MAX-ACCESS  not-accessible
   STATUS      current
   DESCRIPTION
      "The value of the tlsCntTreeGlobalIndex of the MANAGED OBJECT."
   ::= {sr1646v2LacpBVlanIpSecondaryIpEntry 10}

sr1646v2LacpBVlanIpSecondaryIpTableIx OBJECT-TYPE
   SYNTAX      TableIndex
   MAX-ACCESS  not-accessible
   STATUS      current
   DESCRIPTION
      ""
   ::= {sr1646v2LacpBVlanIpSecondaryIpEntry 11}

sr1646v2LacpBVlanIpSecondaryIpAddress OBJECT-TYPE
   SYNTAX      IpAddress
   MAX-ACCESS  read-only
   STATUS      current
   DESCRIPTION
      "Path: lacpBundle.status.vlan.ip.secondaryIp.address"
   ::= {sr1646v2LacpBVlanIpSecondaryIpEntry 2030043136}

sr1646v2LacpBVlanIpSecondaryIpNetMask OBJECT-TYPE
   SYNTAX      IpAddress
   MAX-ACCESS  read-only
   STATUS      current
   DESCRIPTION
      "Path: lacpBundle.status.vlan.ip.secondaryIp.netMask"
   ::= {sr1646v2LacpBVlanIpSecondaryIpEntry 2063597568}

sr1646v2LacpBVlanIpV6Addresses OBJECT-TYPE
   SYNTAX      SEQUENCE OF Sr1646v2LacpBVlanIpV6AddressesEntry
   MAX-ACCESS  not-accessible
   STATUS      current
   DESCRIPTION
      ""
   ::= {sr1646v2LacpBVlan 100859904}

sr1646v2LacpBVlanIpV6AddressesEntry OBJECT-TYPE
   SYNTAX      Sr1646v2LacpBVlanIpV6AddressesEntry
   MAX-ACCESS  not-accessible
   STATUS      current
   DESCRIPTION
      ""
   INDEX      { sr1646v2LacpBVlanIpV6AddressesGlobalIx,
                sr1646v2LacpBVlanTableIx,
                sr1646v2LacpBVlanIpV6AddressesTableIx }
   ::= {sr1646v2LacpBVlanIpV6Addresses 1}

Sr1646v2LacpBVlanIpV6AddressesEntry ::=
   SEQUENCE
      {
      sr1646v2LacpBVlanIpV6AddressesGlobalIx
         GlobalIndex,
      sr1646v2LacpBVlanIpV6AddressesTableIx
         TableIndex,
      sr1646v2LacpBVlanIpV6AddressesAddress
         Ipv6Address,
      sr1646v2LacpBVlanIpV6AddressesPrefixLength
         Integer32,
      sr1646v2LacpBVlanIpV6AddressesStatus
         INTEGER,
      sr1646v2LacpBVlanIpV6AddressesOrigin
         INTEGER,
      sr1646v2LacpBVlanIpV6AddressesFlagsInterfaceId
         INTEGER,
      sr1646v2LacpBVlanIpV6AddressesFlagsAnycast
         INTEGER,
      sr1646v2LacpBVlanIpV6AddressesTimersValidLifeTime
         TimeTicks,
      sr1646v2LacpBVlanIpV6AddressesTimersPrefLifeTime
         TimeTicks
      }

sr1646v2LacpBVlanIpV6AddressesGlobalIx OBJECT-TYPE
   SYNTAX      GlobalIndex
   MAX-ACCESS  not-accessible
   STATUS      current
   DESCRIPTION
      "The value of the tlsCntTreeGlobalIndex of the MANAGED OBJECT."
   ::= {sr1646v2LacpBVlanIpV6AddressesEntry 10}

sr1646v2LacpBVlanIpV6AddressesTableIx OBJECT-TYPE
   SYNTAX      TableIndex
   MAX-ACCESS  not-accessible
   STATUS      current
   DESCRIPTION
      ""
   ::= {sr1646v2LacpBVlanIpV6AddressesEntry 11}

sr1646v2LacpBVlanIpV6AddressesAddress OBJECT-TYPE
   SYNTAX      Ipv6Address
   MAX-ACCESS  read-only
   STATUS      current
   DESCRIPTION
      "Path: lacpBundle.status.vlan.ipV6.addresses.address

       ipv6 address"
   ::= {sr1646v2LacpBVlanIpV6AddressesEntry 16777216}

sr1646v2LacpBVlanIpV6AddressesPrefixLength OBJECT-TYPE
   SYNTAX      Integer32
   MAX-ACCESS  read-only
   STATUS      current
   DESCRIPTION
      "Path: lacpBundle.status.vlan.ipV6.addresses.prefixLength"
   ::= {sr1646v2LacpBVlanIpV6AddressesEntry 33554432}

sr1646v2LacpBVlanIpV6AddressesStatus OBJECT-TYPE
   SYNTAX      INTEGER
               {
               invalid (0),
               tentative (1),
               deprecated (2),
               preferred (3)
               }
   MAX-ACCESS  read-only
   STATUS      current
   DESCRIPTION
      "Path: lacpBundle.status.vlan.ipV6.addresses.status

       Possibilities:
               invalid   (0)
               tentative   (1)
               deprecated   (2)
               preferred   (3)"
   ::= {sr1646v2LacpBVlanIpV6AddressesEntry 50331648}

sr1646v2LacpBVlanIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: lacpBundle.status.vlan.ipV6.addresses.origin

       Possibilities:
               unknown   (0)
               manual   (1)
               generalPrefix   (2)
               statelessAuto   (3)
               statefullAuto   (4)"
   ::= {sr1646v2LacpBVlanIpV6AddressesEntry 67108864}

sr1646v2LacpBVlanIpV6AddressesFlagsInterfaceId OBJECT-TYPE
   SYNTAX      INTEGER
               {
               no (0),
               yes (1)
               }
   MAX-ACCESS  read-only
   STATUS      current
   DESCRIPTION
      "Path: lacpBundle.status.vlan.ipV6.addresses.flags.interfaceId

       Possibilities:
               no   (0)
               yes   (1)"
   ::= {sr1646v2LacpBVlanIpV6AddressesEntry 83951616}

sr1646v2LacpBVlanIpV6AddressesFlagsAnycast OBJECT-TYPE
   SYNTAX      INTEGER
               {
               no (0),
               yes (1)
               }
   MAX-ACCESS  read-only
   STATUS      current
   DESCRIPTION
      "Path: lacpBundle.status.vlan.ipV6.addresses.flags.anycast

       Possibilities:
               no   (0)
               yes   (1)"
   ::= {sr1646v2LacpBVlanIpV6AddressesEntry 84017152}

sr1646v2LacpBVlanIpV6AddressesTimersValidLifeTime OBJECT-TYPE
   SYNTAX      TimeTicks
   MAX-ACCESS  read-only
   STATUS      current
   DESCRIPTION
      "Path: lacpBundle.status.vlan.ipV6.addresses.timers.validLifeTime

       Time in centi-second."
   ::= {sr1646v2LacpBVlanIpV6AddressesEntry 100794368}

sr1646v2LacpBVlanIpV6AddressesTimersPrefLifeTime OBJECT-TYPE
   SYNTAX      TimeTicks
   MAX-ACCESS  read-only
   STATUS      current
   DESCRIPTION
      "Path: lacpBundle.status.vlan.ipV6.addresses.timers.prefLifeTime

       Time in centi-second."
   ::= {sr1646v2LacpBVlanIpV6AddressesEntry 100728832}

sr1646v2LacpBVlanVlanArpCache OBJECT-TYPE
   SYNTAX      SEQUENCE OF Sr1646v2LacpBVlanVlanArpCacheEntry
   MAX-ACCESS  not-accessible
   STATUS      current
   DESCRIPTION
      ""
   ::= {sr1646v2LacpBVlan 235601920}

sr1646v2LacpBVlanVlanArpCacheEntry OBJECT-TYPE
   SYNTAX      Sr1646v2LacpBVlanVlanArpCacheEntry
   MAX-ACCESS  not-accessible
   STATUS      current
   DESCRIPTION
      ""
   INDEX      { sr1646v2LacpBVlanVlanArpCacheGlobalIx,
                sr1646v2LacpBVlanTableIx,
                sr1646v2LacpBVlanVlanArpCacheTableIx }
   ::= {sr1646v2LacpBVlanVlanArpCache 1}

Sr1646v2LacpBVlanVlanArpCacheEntry ::=
   SEQUENCE
      {
      sr1646v2LacpBVlanVlanArpCacheGlobalIx
         GlobalIndex,
      sr1646v2LacpBVlanVlanArpCacheTableIx
         TableIndex,
      sr1646v2LacpBVlanVlanArpCacheMacAddress
         OCTET STRING,
      sr1646v2LacpBVlanVlanArpCacheIpAddress
         IpAddress,
      sr1646v2LacpBVlanVlanArpCacheType
         INTEGER,
      sr1646v2LacpBVlanVlanArpCacheTimeOut
         TimeTicks
      }

sr1646v2LacpBVlanVlanArpCacheGlobalIx OBJECT-TYPE
   SYNTAX      GlobalIndex
   MAX-ACCESS  not-accessible
   STATUS      current
   DESCRIPTION
      "The value of the tlsCntTreeGlobalIndex of the MANAGED OBJECT."
   ::= {sr1646v2LacpBVlanVlanArpCacheEntry 10}

sr1646v2LacpBVlanVlanArpCacheTableIx OBJECT-TYPE
   SYNTAX      TableIndex
   MAX-ACCESS  not-accessible
   STATUS      current
   DESCRIPTION
      ""
   ::= {sr1646v2LacpBVlanVlanArpCacheEntry 11}

sr1646v2LacpBVlanVlanArpCacheMacAddress OBJECT-TYPE
   SYNTAX      OCTET STRING
   MAX-ACCESS  read-only
   STATUS      current
   DESCRIPTION
      "Path: lacpBundle.status.vlan.vlan.arpCache.macAddress

       MAC address."
   ::= {sr1646v2LacpBVlanVlanArpCacheEntry 16777216}

sr1646v2LacpBVlanVlanArpCacheIpAddress OBJECT-TYPE
   SYNTAX      IpAddress
   MAX-ACCESS  read-only
   STATUS      current
   DESCRIPTION
      "Path: lacpBundle.status.vlan.vlan.arpCache.ipAddress"
   ::= {sr1646v2LacpBVlanVlanArpCacheEntry 33554432}

sr1646v2LacpBVlanVlanArpCacheType OBJECT-TYPE
   SYNTAX      INTEGER
               {
               static (0),
               dynamic (1)
               }
   MAX-ACCESS  read-only
   STATUS      current
   DESCRIPTION
      "Path: lacpBundle.status.vlan.vlan.arpCache.type

       Possibilities:
               static   (0)
               dynamic   (1)"
   ::= {sr1646v2LacpBVlanVlanArpCacheEntry 50331648}

sr1646v2LacpBVlanVlanArpCacheTimeOut OBJECT-TYPE
   SYNTAX      TimeTicks
   MAX-ACCESS  read-only
   STATUS      current
   DESCRIPTION
      "Path: lacpBundle.status.vlan.vlan.arpCache.timeOut

       Time in centi-second."
   ::= {sr1646v2LacpBVlanVlanArpCacheEntry 67108864}


sr1646v2LacpBPppOE OBJECT IDENTIFIER ::= {sr1646v2LacpB 36}

sr1646v2LacpBPppOESSCTable OBJECT-TYPE
   SYNTAX      SEQUENCE OF Sr1646v2LacpBPppOEEntry
   MAX-ACCESS  not-accessible
   STATUS      current
   DESCRIPTION
      ""
   ::= {sr1646v2LacpBPppOE 1}

sr1646v2LacpBPppOEEntry OBJECT-TYPE
   SYNTAX      Sr1646v2LacpBPppOEEntry
   MAX-ACCESS  not-accessible
   STATUS      current
   DESCRIPTION
      ""
   INDEX      { sr1646v2LacpBPppOEGlobalIx,
                sr1646v2LacpBPppOETableIx }
   ::= {sr1646v2LacpBPppOESSCTable 1}

Sr1646v2LacpBPppOEEntry ::=
   SEQUENCE
      {
      sr1646v2LacpBPppOEGlobalIx
         GlobalIndex,
      sr1646v2LacpBPppOETableIx
         TableIndex,
      sr1646v2LacpBPppOEName
         DisplayString,
      sr1646v2LacpBPppOEMode
         INTEGER,
      sr1646v2LacpBPppOEIfOperStatus
         INTEGER,
      sr1646v2LacpBPppOEIfLastChange
         TimeTicks,
      sr1646v2LacpBPppOEIfLastChangeDate
         DisplayString,
      sr1646v2LacpBPppOEIpAddress
         IpAddress,
      sr1646v2LacpBPppOEIpNetMask
         IpAddress,
      sr1646v2LacpBPppOEIpRemote
         IpAddress,
      sr1646v2LacpBPppOEPppOEthDiscState
         INTEGER,
      sr1646v2LacpBPppOEPppOEthPeerMac
         OCTET STRING,
      sr1646v2LacpBPppOEPppOEthServiceName
         DisplayString,
      sr1646v2LacpBPppOEPppLcpState
         INTEGER,
      sr1646v2LacpBPppOEPppIpcpState
         INTEGER,
      sr1646v2LacpBPppOEPppIp6cpState
         INTEGER,
      sr1646v2LacpBPppOEPppMyAutSt
         INTEGER,
      sr1646v2LacpBPppOEPppHisAutSt
         INTEGER,
      sr1646v2LacpBPppOEPppMru
         Integer32,
      sr1646v2LacpBPppOEIpV6State
         INTEGER,
      sr1646v2LacpBPppOEIpV6InterfaceId
         OCTET STRING,
      sr1646v2LacpBPppOEIpV6LinkMtu
         Integer32,
      sr1646v2LacpBPppOEIpV6HopLimit
         Integer32,
      sr1646v2LacpBPppOEIpV6DhcpIaid
         Counter32,
      sr1646v2LacpBPppOEIpV6RaRcvOption
         Integer32
      }

sr1646v2LacpBPppOEGlobalIx OBJECT-TYPE
   SYNTAX      GlobalIndex
   MAX-ACCESS  not-accessible
   STATUS      current
   DESCRIPTION
      "The value of the tlsCntTreeGlobalIndex of the MANAGED OBJECT."
   ::= {sr1646v2LacpBPppOEEntry 10}

sr1646v2LacpBPppOETableIx OBJECT-TYPE
   SYNTAX      TableIndex
   MAX-ACCESS  not-accessible
   STATUS      current
   DESCRIPTION
      ""
   ::= {sr1646v2LacpBPppOEEntry 11}

sr1646v2LacpBPppOEName OBJECT-TYPE
   SYNTAX      DisplayString
   MAX-ACCESS  read-only
   STATUS      current
   DESCRIPTION
      "Path: lacpBundle.status.pppoEClient.name"
   ::= {sr1646v2LacpBPppOEEntry 16777216}

sr1646v2LacpBPppOEMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: lacpBundle.status.pppoEClient.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1646v2LacpBPppOEEntry 335544320}

sr1646v2LacpBPppOEIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: lacpBundle.status.pppoEClient.ifOperStatus

       Possibilities:
               up   (1)
               down   (2)
               testing   (3)
               unknown   (4)
               dormant   (5)
               notPresent   (6)
               lowerLayerDown   (7)"
   ::= {sr1646v2LacpBPppOEEntry 1795162112}

sr1646v2LacpBPppOEIfLastChange OBJECT-TYPE
   SYNTAX      TimeTicks
   MAX-ACCESS  read-only
   STATUS      current
   DESCRIPTION
      "Path: lacpBundle.status.pppoEClient.ifLastChange

       Time in centi-second."
   ::= {sr1646v2LacpBPppOEEntry 1811939328}

sr1646v2LacpBPppOEIfLastChangeDate OBJECT-TYPE
   SYNTAX      DisplayString
   MAX-ACCESS  read-only
   STATUS      current
   DESCRIPTION
      "Path: lacpBundle.status.pppoEClient.ifLastChangeDate"
   ::= {sr1646v2LacpBPppOEEntry 3070230528}

sr1646v2LacpBPppOEIpAddress OBJECT-TYPE
   SYNTAX      IpAddress
   MAX-ACCESS  read-only
   STATUS      current
   DESCRIPTION
      "Path: lacpBundle.status.pppoEClient.ip.address"
   ::= {sr1646v2LacpBPppOEEntry 51380224}

sr1646v2LacpBPppOEIpNetMask OBJECT-TYPE
   SYNTAX      IpAddress
   MAX-ACCESS  read-only
   STATUS      current
   DESCRIPTION
      "Path: lacpBundle.status.pppoEClient.ip.netMask"
   ::= {sr1646v2LacpBPppOEEntry 51445760}

sr1646v2LacpBPppOEIpRemote OBJECT-TYPE
   SYNTAX      IpAddress
   MAX-ACCESS  read-only
   STATUS      current
   DESCRIPTION
      "Path: lacpBundle.status.pppoEClient.ip.remote"
   ::= {sr1646v2LacpBPppOEEntry 51511296}

sr1646v2LacpBPppOEPppOEthDiscState OBJECT-TYPE
   SYNTAX      INTEGER
               {
               idle (0),
               waitForPADO (1),
               waitForPADS (2),
               established (3)
               }
   MAX-ACCESS  read-only
   STATUS      current
   DESCRIPTION
      "Path: lacpBundle.status.pppoEClient.pppOverEth.discState

       Possibilities:
               idle   (0)
               waitForPADO   (1)
               waitForPADS   (2)
               established   (3)"
   ::= {sr1646v2LacpBPppOEEntry 67174400}

sr1646v2LacpBPppOEPppOEthPeerMac OBJECT-TYPE
   SYNTAX      OCTET STRING
   MAX-ACCESS  read-only
   STATUS      current
   DESCRIPTION
      "Path: lacpBundle.status.pppoEClient.pppOverEth.remoteMacAddress

       MAC address."
   ::= {sr1646v2LacpBPppOEEntry 67239936}

sr1646v2LacpBPppOEPppOEthServiceName OBJECT-TYPE
   SYNTAX      DisplayString
   MAX-ACCESS  read-only
   STATUS      current
   DESCRIPTION
      "Path: lacpBundle.status.pppoEClient.pppOverEth.serviceName"
   ::= {sr1646v2LacpBPppOEEntry 67305472}

sr1646v2LacpBPppOEPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: lacpBundle.status.pppoEClient.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2LacpBPppOEEntry 83951616}

sr1646v2LacpBPppOEPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: lacpBundle.status.pppoEClient.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2LacpBPppOEEntry 84017152}

sr1646v2LacpBPppOEPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: lacpBundle.status.pppoEClient.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2LacpBPppOEEntry 84869120}

sr1646v2LacpBPppOEPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: lacpBundle.status.pppoEClient.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1646v2LacpBPppOEEntry 84541440}

sr1646v2LacpBPppOEPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: lacpBundle.status.pppoEClient.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1646v2LacpBPppOEEntry 84606976}

sr1646v2LacpBPppOEPppMru OBJECT-TYPE
   SYNTAX      Integer32
   MAX-ACCESS  read-only
   STATUS      current
   DESCRIPTION
      "Path: lacpBundle.status.pppoEClient.ppp.mru"
   ::= {sr1646v2LacpBPppOEEntry 84934656}

sr1646v2LacpBPppOEIpV6State OBJECT-TYPE
   SYNTAX      INTEGER
               {
               disabled (0),
               enabled (1)
               }
   MAX-ACCESS  read-only
   STATUS      current
   DESCRIPTION
      "Path: lacpBundle.status.pppoEClient.ipV6.state

       Possibilities:
               disabled   (0)
               enabled   (1)"
   ::= {sr1646v2LacpBPppOEEntry 100728832}

sr1646v2LacpBPppOEIpV6InterfaceId OBJECT-TYPE
   SYNTAX      OCTET STRING
   MAX-ACCESS  read-only
   STATUS      current
   DESCRIPTION
      "Path: lacpBundle.status.pppoEClient.ipV6.interfaceId"
   ::= {sr1646v2LacpBPppOEEntry 100794368}

sr1646v2LacpBPppOEIpV6LinkMtu OBJECT-TYPE
   SYNTAX      Integer32
   MAX-ACCESS  read-only
   STATUS      current
   DESCRIPTION
      "Path: lacpBundle.status.pppoEClient.ipV6.linkMtu"
   ::= {sr1646v2LacpBPppOEEntry 100925440}

sr1646v2LacpBPppOEIpV6HopLimit OBJECT-TYPE
   SYNTAX      Integer32
   MAX-ACCESS  read-only
   STATUS      current
   DESCRIPTION
      "Path: lacpBundle.status.pppoEClient.ipV6.hopLimit"
   ::= {sr1646v2LacpBPppOEEntry 100990976}

sr1646v2LacpBPppOEIpV6DhcpIaid OBJECT-TYPE
   SYNTAX      Counter32
   MAX-ACCESS  read-only
   STATUS      current
   DESCRIPTION
      "Path: lacpBundle.status.pppoEClient.ipV6.dhcp.iaid

       32 bit unsigned wrappable counter."
   ::= {sr1646v2LacpBPppOEEntry 101056768}

sr1646v2LacpBPppOEIpV6RaRcvOption OBJECT-TYPE
   SYNTAX      Integer32
   MAX-ACCESS  read-only
   STATUS      current
   DESCRIPTION
      "Path: lacpBundle.status.pppoEClient.ipV6.raRcvOption

       Bit meanings:
               bit 0 = linkMtu,
               bit 1 = srcLinkLayer,
               bit 2 = prefixInfo,
               bit 3 = rdnss,
               bit 4 = dnssl"
   ::= {sr1646v2LacpBPppOEEntry 101122048}

sr1646v2LacpBPppOEIpV6Addresses OBJECT-TYPE
   SYNTAX      SEQUENCE OF Sr1646v2LacpBPppOEIpV6AddressesEntry
   MAX-ACCESS  not-accessible
   STATUS      current
   DESCRIPTION
      ""
   ::= {sr1646v2LacpBPppOE 100859904}

sr1646v2LacpBPppOEIpV6AddressesEntry OBJECT-TYPE
   SYNTAX      Sr1646v2LacpBPppOEIpV6AddressesEntry
   MAX-ACCESS  not-accessible
   STATUS      current
   DESCRIPTION
      ""
   INDEX      { sr1646v2LacpBPppOEIpV6AddressesGlobalIx,
                sr1646v2LacpBPppOETableIx,
                sr1646v2LacpBPppOEIpV6AddressesTableIx }
   ::= {sr1646v2LacpBPppOEIpV6Addresses 1}

Sr1646v2LacpBPppOEIpV6AddressesEntry ::=
   SEQUENCE
      {
      sr1646v2LacpBPppOEIpV6AddressesGlobalIx
         GlobalIndex,
      sr1646v2LacpBPppOEIpV6AddressesTableIx
         TableIndex,
      sr1646v2LacpBPppOEIpV6AddressesAddress
         Ipv6Address,
      sr1646v2LacpBPppOEIpV6AddressesPrefixLength
         Integer32,
      sr1646v2LacpBPppOEIpV6AddressesStatus
         INTEGER,
      sr1646v2LacpBPppOEIpV6AddressesOrigin
         INTEGER,
      sr1646v2LacpBPppOEIpV6AddressesFlagsInterfaceId
         INTEGER,
      sr1646v2LacpBPppOEIpV6AddressesFlagsAnycast
         INTEGER,
      sr1646v2LacpBPppOEIpV6AddressesTimersValidLifeTime
         TimeTicks,
      sr1646v2LacpBPppOEIpV6AddressesTimersPrefLifeTime
         TimeTicks
      }

sr1646v2LacpBPppOEIpV6AddressesGlobalIx OBJECT-TYPE
   SYNTAX      GlobalIndex
   MAX-ACCESS  not-accessible
   STATUS      current
   DESCRIPTION
      "The value of the tlsCntTreeGlobalIndex of the MANAGED OBJECT."
   ::= {sr1646v2LacpBPppOEIpV6AddressesEntry 10}

sr1646v2LacpBPppOEIpV6AddressesTableIx OBJECT-TYPE
   SYNTAX      TableIndex
   MAX-ACCESS  not-accessible
   STATUS      current
   DESCRIPTION
      ""
   ::= {sr1646v2LacpBPppOEIpV6AddressesEntry 11}

sr1646v2LacpBPppOEIpV6AddressesAddress OBJECT-TYPE
   SYNTAX      Ipv6Address
   MAX-ACCESS  read-only
   STATUS      current
   DESCRIPTION
      "Path: lacpBundle.status.pppoEClient.ipV6.addresses.address

       ipv6 address"
   ::= {sr1646v2LacpBPppOEIpV6AddressesEntry 16777216}

sr1646v2LacpBPppOEIpV6AddressesPrefixLength OBJECT-TYPE
   SYNTAX      Integer32
   MAX-ACCESS  read-only
   STATUS      current
   DESCRIPTION
      "Path: lacpBundle.status.pppoEClient.ipV6.addresses.prefixLength"
   ::= {sr1646v2LacpBPppOEIpV6AddressesEntry 33554432}

sr1646v2LacpBPppOEIpV6AddressesStatus OBJECT-TYPE
   SYNTAX      INTEGER
               {
               invalid (0),
               tentative (1),
               deprecated (2),
               preferred (3)
               }
   MAX-ACCESS  read-only
   STATUS      current
   DESCRIPTION
      "Path: lacpBundle.status.pppoEClient.ipV6.addresses.status

       Possibilities:
               invalid   (0)
               tentative   (1)
               deprecated   (2)
               preferred   (3)"
   ::= {sr1646v2LacpBPppOEIpV6AddressesEntry 50331648}

sr1646v2LacpBPppOEIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: lacpBundle.status.pppoEClient.ipV6.addresses.origin

       Possibilities:
               unknown   (0)
               manual   (1)
               generalPrefix   (2)
               statelessAuto   (3)
               statefullAuto   (4)"
   ::= {sr1646v2LacpBPppOEIpV6AddressesEntry 67108864}

sr1646v2LacpBPppOEIpV6AddressesFlagsInterfaceId OBJECT-TYPE
   SYNTAX      INTEGER
               {
               no (0),
               yes (1)
               }
   MAX-ACCESS  read-only
   STATUS      current
   DESCRIPTION
      "Path: lacpBundle.status.pppoEClient.ipV6.addresses.flags.interfaceId

       Possibilities:
               no   (0)
               yes   (1)"
   ::= {sr1646v2LacpBPppOEIpV6AddressesEntry 83951616}

sr1646v2LacpBPppOEIpV6AddressesFlagsAnycast OBJECT-TYPE
   SYNTAX      INTEGER
               {
               no (0),
               yes (1)
               }
   MAX-ACCESS  read-only
   STATUS      current
   DESCRIPTION
      "Path: lacpBundle.status.pppoEClient.ipV6.addresses.flags.anycast

       Possibilities:
               no   (0)
               yes   (1)"
   ::= {sr1646v2LacpBPppOEIpV6AddressesEntry 84017152}

sr1646v2LacpBPppOEIpV6AddressesTimersValidLifeTime OBJECT-TYPE
   SYNTAX      TimeTicks
   MAX-ACCESS  read-only
   STATUS      current
   DESCRIPTION
      "Path: lacpBundle.status.pppoEClient.ipV6.addresses.timers.validLifeTime

       Time in centi-second."
   ::= {sr1646v2LacpBPppOEIpV6AddressesEntry 100794368}

sr1646v2LacpBPppOEIpV6AddressesTimersPrefLifeTime OBJECT-TYPE
   SYNTAX      TimeTicks
   MAX-ACCESS  read-only
   STATUS      current
   DESCRIPTION
      "Path: lacpBundle.status.pppoEClient.ipV6.addresses.timers.prefLifeTime

       Time in centi-second."
   ::= {sr1646v2LacpBPppOEIpV6AddressesEntry 100728832}


sr1646v2LacpBDot1x OBJECT IDENTIFIER ::= {sr1646v2LacpB 190}

sr1646v2LacpBDot1xSSCTable OBJECT-TYPE
   SYNTAX      SEQUENCE OF Sr1646v2LacpBDot1xEntry
   MAX-ACCESS  not-accessible
   STATUS      current
   DESCRIPTION
      "Ethernet Switch VLAN Table"
   ::= {sr1646v2LacpBDot1x 1}

sr1646v2LacpBDot1xEntry OBJECT-TYPE
   SYNTAX      Sr1646v2LacpBDot1xEntry
   MAX-ACCESS  not-accessible
   STATUS      current
   DESCRIPTION
      ""
   INDEX      { sr1646v2LacpBDot1xGlobalIx,
                sr1646v2LacpBDot1xTableIx }
   ::= {sr1646v2LacpBDot1xSSCTable 1}

Sr1646v2LacpBDot1xEntry ::=
   SEQUENCE
      {
      sr1646v2LacpBDot1xGlobalIx
         GlobalIndex,
      sr1646v2LacpBDot1xTableIx
         TableIndex,
      sr1646v2LacpBDot1xRemote
         OCTET STRING,
      sr1646v2LacpBDot1xAuthorized
         INTEGER,
      sr1646v2LacpBDot1xAuthenticator
         INTEGER,
      sr1646v2LacpBDot1xBackEnd
         INTEGER,
      sr1646v2LacpBDot1xRetries
         Integer32,
      sr1646v2LacpBDot1xReAuthTime
         TimeTicks,
      sr1646v2LacpBDot1xHoldTime
         TimeTicks
      }

sr1646v2LacpBDot1xGlobalIx OBJECT-TYPE
   SYNTAX      GlobalIndex
   MAX-ACCESS  not-accessible
   STATUS      current
   DESCRIPTION
      "The value of the tlsCntTreeGlobalIndex of the MANAGED OBJECT."
   ::= {sr1646v2LacpBDot1xEntry 10}

sr1646v2LacpBDot1xTableIx OBJECT-TYPE
   SYNTAX      TableIndex
   MAX-ACCESS  not-accessible
   STATUS      current
   DESCRIPTION
      ""
   ::= {sr1646v2LacpBDot1xEntry 11}

sr1646v2LacpBDot1xRemote OBJECT-TYPE
   SYNTAX      OCTET STRING
   MAX-ACCESS  read-only
   STATUS      current
   DESCRIPTION
      "Path: lacpBundle.status.dot1x.remote

       MAC address."
   ::= {sr1646v2LacpBDot1xEntry 16777216}

sr1646v2LacpBDot1xAuthorized OBJECT-TYPE
   SYNTAX      INTEGER
               {
               no (0),
               yes (1)
               }
   MAX-ACCESS  read-only
   STATUS      current
   DESCRIPTION
      "Path: lacpBundle.status.dot1x.authorized

       Possibilities:
               no   (0)
               yes   (1)"
   ::= {sr1646v2LacpBDot1xEntry 33554432}

sr1646v2LacpBDot1xAuthenticator OBJECT-TYPE
   SYNTAX      INTEGER
               {
               preInit (0),
               initialize (1),
               disconnected (2),
               restart (3),
               connecting (4),
               authenticating (5),
               authenticated (6),
               aborting (7),
               held (8),
               forceAuth (9),
               forceUnauth (10)
               }
   MAX-ACCESS  read-only
   STATUS      current
   DESCRIPTION
      "Path: lacpBundle.status.dot1x.authenticator

       Possibilities:
               preInit   (0)
               initialize   (1)
               disconnected   (2)
               restart   (3)
               connecting   (4)
               authenticating   (5)
               authenticated   (6)
               aborting   (7)
               held   (8)
               forceAuth   (9)
               forceUnauth   (10)"
   ::= {sr1646v2LacpBDot1xEntry 50331648}

sr1646v2LacpBDot1xBackEnd OBJECT-TYPE
   SYNTAX      INTEGER
               {
               preInit (0),
               initialize (1),
               idle (2),
               request (3),
               response (4),
               success (5),
               failure (6),
               radiusTimeout (7),
               timeout (8)
               }
   MAX-ACCESS  read-only
   STATUS      current
   DESCRIPTION
      "Path: lacpBundle.status.dot1x.backEnd

       Possibilities:
               preInit   (0)
               initialize   (1)
               idle   (2)
               request   (3)
               response   (4)
               success   (5)
               failure   (6)
               radiusTimeout   (7)
               timeout   (8)"
   ::= {sr1646v2LacpBDot1xEntry 67108864}

sr1646v2LacpBDot1xRetries OBJECT-TYPE
   SYNTAX      Integer32
   MAX-ACCESS  read-only
   STATUS      current
   DESCRIPTION
      "Path: lacpBundle.status.dot1x.retries"
   ::= {sr1646v2LacpBDot1xEntry 83886080}

sr1646v2LacpBDot1xReAuthTime OBJECT-TYPE
   SYNTAX      TimeTicks
   MAX-ACCESS  read-only
   STATUS      current
   DESCRIPTION
      "Path: lacpBundle.status.dot1x.reAuthTime

       Time in centi-second."
   ::= {sr1646v2LacpBDot1xEntry 100663296}

sr1646v2LacpBDot1xHoldTime OBJECT-TYPE
   SYNTAX      TimeTicks
   MAX-ACCESS  read-only
   STATUS      current
   DESCRIPTION
      "Path: lacpBundle.status.dot1x.holdTime

       Time in centi-second."
   ::= {sr1646v2LacpBDot1xEntry 117440512}


sr1646v2LacpBIpV6 OBJECT IDENTIFIER ::= {sr1646v2LacpB 17}

sr1646v2LacpBIpV6SSCTable OBJECT-TYPE
   SYNTAX      SEQUENCE OF Sr1646v2LacpBIpV6Entry
   MAX-ACCESS  not-accessible
   STATUS      current
   DESCRIPTION
      "IPv6 interface config parameters"
   ::= {sr1646v2LacpBIpV6 1}

sr1646v2LacpBIpV6Entry OBJECT-TYPE
   SYNTAX      Sr1646v2LacpBIpV6Entry
   MAX-ACCESS  not-accessible
   STATUS      current
   DESCRIPTION
      ""
   INDEX      { sr1646v2LacpBIpV6GlobalIx }
   ::= {sr1646v2LacpBIpV6SSCTable 1}

Sr1646v2LacpBIpV6Entry ::=
   SEQUENCE
      {
      sr1646v2LacpBIpV6GlobalIx
         GlobalIndex,
      sr1646v2LacpBIpV6State
         INTEGER,
      sr1646v2LacpBIpV6InterfaceId
         OCTET STRING,
      sr1646v2LacpBIpV6LinkMtu
         Integer32,
      sr1646v2LacpBIpV6HopLimit
         Integer32,
      sr1646v2LacpBIpV6DhcpIaid
         Counter32,
      sr1646v2LacpBIpV6RaRcvOption
         Integer32
      }

sr1646v2LacpBIpV6GlobalIx OBJECT-TYPE
   SYNTAX      GlobalIndex
   MAX-ACCESS  not-accessible
   STATUS      current
   DESCRIPTION
      "The value of the tlsCntTreeGlobalIndex of the MANAGED OBJECT."
   ::= {sr1646v2LacpBIpV6Entry 10}

sr1646v2LacpBIpV6State OBJECT-TYPE
   SYNTAX      INTEGER
               {
               disabled (0),
               enabled (1)
               }
   MAX-ACCESS  read-only
   STATUS      current
   DESCRIPTION
      "Path: lacpBundle.status.ipV6.state

       Possibilities:
               disabled   (0)
               enabled   (1)"
   ::= {sr1646v2LacpBIpV6Entry 16777216}

sr1646v2LacpBIpV6InterfaceId OBJECT-TYPE
   SYNTAX      OCTET STRING
   MAX-ACCESS  read-only
   STATUS      current
   DESCRIPTION
      "Path: lacpBundle.status.ipV6.interfaceId"
   ::= {sr1646v2LacpBIpV6Entry 33554432}

sr1646v2LacpBIpV6LinkMtu OBJECT-TYPE
   SYNTAX      Integer32
   MAX-ACCESS  read-only
   STATUS      current
   DESCRIPTION
      "Path: lacpBundle.status.ipV6.linkMtu"
   ::= {sr1646v2LacpBIpV6Entry 67108864}

sr1646v2LacpBIpV6HopLimit OBJECT-TYPE
   SYNTAX      Integer32
   MAX-ACCESS  read-only
   STATUS      current
   DESCRIPTION
      "Path: lacpBundle.status.ipV6.hopLimit"
   ::= {sr1646v2LacpBIpV6Entry 83886080}

sr1646v2LacpBIpV6DhcpIaid OBJECT-TYPE
   SYNTAX      Counter32
   MAX-ACCESS  read-only
   STATUS      current
   DESCRIPTION
      "Path: lacpBundle.status.ipV6.dhcp.iaid

       32 bit unsigned wrappable counter."
   ::= {sr1646v2LacpBIpV6Entry 100728832}

sr1646v2LacpBIpV6RaRcvOption OBJECT-TYPE
   SYNTAX      Integer32
   MAX-ACCESS  read-only
   STATUS      current
   DESCRIPTION
      "Path: lacpBundle.status.ipV6.raRcvOption

       Bit meanings:
               bit 0 = linkMtu,
               bit 1 = srcLinkLayer,
               bit 2 = prefixInfo,
               bit 3 = rdnss,
               bit 4 = dnssl"
   ::= {sr1646v2LacpBIpV6Entry 117440512}

sr1646v2LacpBIpV6Addresses OBJECT-TYPE
   SYNTAX      SEQUENCE OF Sr1646v2LacpBIpV6AddressesEntry
   MAX-ACCESS  not-accessible
   STATUS      current
   DESCRIPTION
      ""
   ::= {sr1646v2LacpBIpV6 50331648}

sr1646v2LacpBIpV6AddressesEntry OBJECT-TYPE
   SYNTAX      Sr1646v2LacpBIpV6AddressesEntry
   MAX-ACCESS  not-accessible
   STATUS      current
   DESCRIPTION
      ""
   INDEX      { sr1646v2LacpBIpV6AddressesGlobalIx,
                sr1646v2LacpBIpV6AddressesTableIx }
   ::= {sr1646v2LacpBIpV6Addresses 1}

Sr1646v2LacpBIpV6AddressesEntry ::=
   SEQUENCE
      {
      sr1646v2LacpBIpV6AddressesGlobalIx
         GlobalIndex,
      sr1646v2LacpBIpV6AddressesTableIx
         TableIndex,
      sr1646v2LacpBIpV6AddressesAddress
         Ipv6Address,
      sr1646v2LacpBIpV6AddressesPrefixLength
         Integer32,
      sr1646v2LacpBIpV6AddressesStatus
         INTEGER,
      sr1646v2LacpBIpV6AddressesOrigin
         INTEGER,
      sr1646v2LacpBIpV6AddressesFlagsInterfaceId
         INTEGER,
      sr1646v2LacpBIpV6AddressesFlagsAnycast
         INTEGER,
      sr1646v2LacpBIpV6AddressesTimersValidLifeTime
         TimeTicks,
      sr1646v2LacpBIpV6AddressesTimersPrefLifeTime
         TimeTicks
      }

sr1646v2LacpBIpV6AddressesGlobalIx OBJECT-TYPE
   SYNTAX      GlobalIndex
   MAX-ACCESS  not-accessible
   STATUS      current
   DESCRIPTION
      "The value of the tlsCntTreeGlobalIndex of the MANAGED OBJECT."
   ::= {sr1646v2LacpBIpV6AddressesEntry 10}

sr1646v2LacpBIpV6AddressesTableIx OBJECT-TYPE
   SYNTAX      TableIndex
   MAX-ACCESS  not-accessible
   STATUS      current
   DESCRIPTION
      ""
   ::= {sr1646v2LacpBIpV6AddressesEntry 11}

sr1646v2LacpBIpV6AddressesAddress OBJECT-TYPE
   SYNTAX      Ipv6Address
   MAX-ACCESS  read-only
   STATUS      current
   DESCRIPTION
      "Path: lacpBundle.status.ipV6.addresses.address

       ipv6 address"
   ::= {sr1646v2LacpBIpV6AddressesEntry 16777216}

sr1646v2LacpBIpV6AddressesPrefixLength OBJECT-TYPE
   SYNTAX      Integer32
   MAX-ACCESS  read-only
   STATUS      current
   DESCRIPTION
      "Path: lacpBundle.status.ipV6.addresses.prefixLength"
   ::= {sr1646v2LacpBIpV6AddressesEntry 33554432}

sr1646v2LacpBIpV6AddressesStatus OBJECT-TYPE
   SYNTAX      INTEGER
               {
               invalid (0),
               tentative (1),
               deprecated (2),
               preferred (3)
               }
   MAX-ACCESS  read-only
   STATUS      current
   DESCRIPTION
      "Path: lacpBundle.status.ipV6.addresses.status

       Possibilities:
               invalid   (0)
               tentative   (1)
               deprecated   (2)
               preferred   (3)"
   ::= {sr1646v2LacpBIpV6AddressesEntry 50331648}

sr1646v2LacpBIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: lacpBundle.status.ipV6.addresses.origin

       Possibilities:
               unknown   (0)
               manual   (1)
               generalPrefix   (2)
               statelessAuto   (3)
               statefullAuto   (4)"
   ::= {sr1646v2LacpBIpV6AddressesEntry 67108864}

sr1646v2LacpBIpV6AddressesFlagsInterfaceId OBJECT-TYPE
   SYNTAX      INTEGER
               {
               no (0),
               yes (1)
               }
   MAX-ACCESS  read-only
   STATUS      current
   DESCRIPTION
      "Path: lacpBundle.status.ipV6.addresses.flags.interfaceId

       Possibilities:
               no   (0)
               yes   (1)"
   ::= {sr1646v2LacpBIpV6AddressesEntry 83951616}

sr1646v2LacpBIpV6AddressesFlagsAnycast OBJECT-TYPE
   SYNTAX      INTEGER
               {
               no (0),
               yes (1)
               }
   MAX-ACCESS  read-only
   STATUS      current
   DESCRIPTION
      "Path: lacpBundle.status.ipV6.addresses.flags.anycast

       Possibilities:
               no   (0)
               yes   (1)"
   ::= {sr1646v2LacpBIpV6AddressesEntry 84017152}

sr1646v2LacpBIpV6AddressesTimersValidLifeTime OBJECT-TYPE
   SYNTAX      TimeTicks
   MAX-ACCESS  read-only
   STATUS      current
   DESCRIPTION
      "Path: lacpBundle.status.ipV6.addresses.timers.validLifeTime

       Time in centi-second."
   ::= {sr1646v2LacpBIpV6AddressesEntry 100794368}

sr1646v2LacpBIpV6AddressesTimersPrefLifeTime OBJECT-TYPE
   SYNTAX      TimeTicks
   MAX-ACCESS  read-only
   STATUS      current
   DESCRIPTION
      "Path: lacpBundle.status.ipV6.addresses.timers.prefLifeTime

       Time in centi-second."
   ::= {sr1646v2LacpBIpV6AddressesEntry 100728832}


sr1646v2LacpBSnmpIndex OBJECT IDENTIFIER ::= {sr1646v2LacpB 269}

sr1646v2LacpBSnmpIndexTable OBJECT-TYPE
   SYNTAX      SEQUENCE OF Sr1646v2LacpBSnmpIndexEntry
   MAX-ACCESS  not-accessible
   STATUS      current
   DESCRIPTION
      "SNMP index assigned to this object"
   ::= {sr1646v2LacpBSnmpIndex 1}

sr1646v2LacpBSnmpIndexEntry OBJECT-TYPE
   SYNTAX      Sr1646v2LacpBSnmpIndexEntry
   MAX-ACCESS  not-accessible
   STATUS      current
   DESCRIPTION
      ""
   INDEX      { sr1646v2LacpBSnmpIndexGlobalIx }
   ::= {sr1646v2LacpBSnmpIndexTable 1}

Sr1646v2LacpBSnmpIndexEntry ::=
   SEQUENCE
      {
      sr1646v2LacpBSnmpIndexGlobalIx
         GlobalIndex,
      sr1646v2LacpBSnmpIndexValue
         Integer32
      }

sr1646v2LacpBSnmpIndexGlobalIx OBJECT-TYPE
   SYNTAX      GlobalIndex
   MAX-ACCESS  not-accessible
   STATUS      current
   DESCRIPTION
      "The value of the tlsCntTreeGlobalIndex of the MANAGED OBJECT."
   ::= {sr1646v2LacpBSnmpIndexEntry 10}

sr1646v2LacpBSnmpIndexValue OBJECT-TYPE
   SYNTAX      Integer32
   MAX-ACCESS  read-only
   STATUS      current
   DESCRIPTION
      "Path: lacpBundle.status.snmpIndex"
   ::= {sr1646v2LacpBSnmpIndexEntry 2147483648}


sr1646v2LacpBAggregator OBJECT IDENTIFIER ::= {sr1646v2LacpB 84}

sr1646v2LacpBAggregatorSSCTable OBJECT-TYPE
   SYNTAX      SEQUENCE OF Sr1646v2LacpBAggregatorEntry
   MAX-ACCESS  not-accessible
   STATUS      current
   DESCRIPTION
      "status of the aggregator"
   ::= {sr1646v2LacpBAggregator 1}

sr1646v2LacpBAggregatorEntry OBJECT-TYPE
   SYNTAX      Sr1646v2LacpBAggregatorEntry
   MAX-ACCESS  not-accessible
   STATUS      current
   DESCRIPTION
      ""
   INDEX      { sr1646v2LacpBAggregatorGlobalIx }
   ::= {sr1646v2LacpBAggregatorSSCTable 1}

Sr1646v2LacpBAggregatorEntry ::=
   SEQUENCE
      {
      sr1646v2LacpBAggregatorGlobalIx
         GlobalIndex,
      sr1646v2LacpBAggregatorId
         Integer32,
      sr1646v2LacpBAggregatorActorMacAddress
         OCTET STRING,
      sr1646v2LacpBAggregatorActorSystemPriority
         Integer32,
      sr1646v2LacpBAggregatorActorAdministrativeKey
         OCTET STRING,
      sr1646v2LacpBAggregatorActorOperationalKey
         OCTET STRING,
      sr1646v2LacpBAggregatorPartnerMacAddress
         OCTET STRING,
      sr1646v2LacpBAggregatorPartnerSystemPriority
         Integer32,
      sr1646v2LacpBAggregatorPartnerOperationalKey
         OCTET STRING
      }

sr1646v2LacpBAggregatorGlobalIx OBJECT-TYPE
   SYNTAX      GlobalIndex
   MAX-ACCESS  not-accessible
   STATUS      current
   DESCRIPTION
      "The value of the tlsCntTreeGlobalIndex of the MANAGED OBJECT."
   ::= {sr1646v2LacpBAggregatorEntry 10}

sr1646v2LacpBAggregatorId OBJECT-TYPE
   SYNTAX      Integer32
   MAX-ACCESS  read-only
   STATUS      current
   DESCRIPTION
      "Path: lacpBundle.status.aggregator.id"
   ::= {sr1646v2LacpBAggregatorEntry 16777216}

sr1646v2LacpBAggregatorActorMacAddress OBJECT-TYPE
   SYNTAX      OCTET STRING
   MAX-ACCESS  read-only
   STATUS      current
   DESCRIPTION
      "Path: lacpBundle.status.aggregator.actor.macAddress

       MAC address."
   ::= {sr1646v2LacpBAggregatorEntry 33619968}

sr1646v2LacpBAggregatorActorSystemPriority OBJECT-TYPE
   SYNTAX      Integer32
   MAX-ACCESS  read-only
   STATUS      current
   DESCRIPTION
      "Path: lacpBundle.status.aggregator.actor.systemPriority"
   ::= {sr1646v2LacpBAggregatorEntry 33685504}

sr1646v2LacpBAggregatorActorAdministrativeKey OBJECT-TYPE
   SYNTAX      OCTET STRING
   MAX-ACCESS  read-only
   STATUS      current
   DESCRIPTION
      "Path: lacpBundle.status.aggregator.actor.administrativeKey"
   ::= {sr1646v2LacpBAggregatorEntry 33751040}

sr1646v2LacpBAggregatorActorOperationalKey OBJECT-TYPE
   SYNTAX      OCTET STRING
   MAX-ACCESS  read-only
   STATUS      current
   DESCRIPTION
      "Path: lacpBundle.status.aggregator.actor.operationalKey"
   ::= {sr1646v2LacpBAggregatorEntry 33816576}

sr1646v2LacpBAggregatorPartnerMacAddress OBJECT-TYPE
   SYNTAX      OCTET STRING
   MAX-ACCESS  read-only
   STATUS      current
   DESCRIPTION
      "Path: lacpBundle.status.aggregator.partner.macAddress

       MAC address."
   ::= {sr1646v2LacpBAggregatorEntry 50397184}

sr1646v2LacpBAggregatorPartnerSystemPriority OBJECT-TYPE
   SYNTAX      Integer32
   MAX-ACCESS  read-only
   STATUS      current
   DESCRIPTION
      "Path: lacpBundle.status.aggregator.partner.systemPriority"
   ::= {sr1646v2LacpBAggregatorEntry 50462720}

sr1646v2LacpBAggregatorPartnerOperationalKey OBJECT-TYPE
   SYNTAX      OCTET STRING
   MAX-ACCESS  read-only
   STATUS      current
   DESCRIPTION
      "Path: lacpBundle.status.aggregator.partner.operationalKey"
   ::= {sr1646v2LacpBAggregatorEntry 50528256}


sr1646v2LacpBMembers OBJECT IDENTIFIER ::= {sr1646v2LacpB 85}

sr1646v2LacpBMembersSSCTable OBJECT-TYPE
   SYNTAX      SEQUENCE OF Sr1646v2LacpBMembersEntry
   MAX-ACCESS  not-accessible
   STATUS      current
   DESCRIPTION
      "status of the aggregation links"
   ::= {sr1646v2LacpBMembers 1}

sr1646v2LacpBMembersEntry OBJECT-TYPE
   SYNTAX      Sr1646v2LacpBMembersEntry
   MAX-ACCESS  not-accessible
   STATUS      current
   DESCRIPTION
      ""
   INDEX      { sr1646v2LacpBMembersGlobalIx,
                sr1646v2LacpBMembersTableIx }
   ::= {sr1646v2LacpBMembersSSCTable 1}

Sr1646v2LacpBMembersEntry ::=
   SEQUENCE
      {
      sr1646v2LacpBMembersGlobalIx
         GlobalIndex,
      sr1646v2LacpBMembersTableIx
         TableIndex,
      sr1646v2LacpBMembersIfDescr
         DisplayString,
      sr1646v2LacpBMembersMemberStatus
         INTEGER,
      sr1646v2LacpBMembersIfLastChange
         TimeTicks,
      sr1646v2LacpBMembersIfLastChangeDate
         DisplayString,
      sr1646v2LacpBMembersReceiveState
         INTEGER,
      sr1646v2LacpBMembersTransmitState
         INTEGER,
      sr1646v2LacpBMembersMuxState
         INTEGER,
      sr1646v2LacpBMembersActorPortPriority
         Integer32,
      sr1646v2LacpBMembersActorPortNumber
         Integer32,
      sr1646v2LacpBMembersActorStateActivity
         INTEGER,
      sr1646v2LacpBMembersActorStateTimeout
         INTEGER,
      sr1646v2LacpBMembersActorStateAggregation
         INTEGER,
      sr1646v2LacpBMembersActorStateSynchronization
         INTEGER,
      sr1646v2LacpBMembersActorStateCollecting
         INTEGER,
      sr1646v2LacpBMembersActorStateDistributing
         INTEGER,
      sr1646v2LacpBMembersActorStateDefaulted
         INTEGER,
      sr1646v2LacpBMembersActorStateExpired
         INTEGER,
      sr1646v2LacpBMembersActorAdministrativeKey
         OCTET STRING,
      sr1646v2LacpBMembersActorOperationalKey
         OCTET STRING,
      sr1646v2LacpBMembersPartnerPortPriority
         Integer32,
      sr1646v2LacpBMembersPartnerPortNumber
         Integer32,
      sr1646v2LacpBMembersPartnerStateActivity
         INTEGER,
      sr1646v2LacpBMembersPartnerStateTimeout
         INTEGER,
      sr1646v2LacpBMembersPartnerStateAggregation
         INTEGER,
      sr1646v2LacpBMembersPartnerStateSynchronization
         INTEGER,
      sr1646v2LacpBMembersPartnerStateCollecting
         INTEGER,
      sr1646v2LacpBMembersPartnerStateDistributing
         INTEGER,
      sr1646v2LacpBMembersPartnerStateDefaulted
         INTEGER,
      sr1646v2LacpBMembersPartnerStateExpired
         INTEGER,
      sr1646v2LacpBMembersPartnerOperationalKey
         OCTET STRING
      }

sr1646v2LacpBMembersGlobalIx OBJECT-TYPE
   SYNTAX      GlobalIndex
   MAX-ACCESS  not-accessible
   STATUS      current
   DESCRIPTION
      "The value of the tlsCntTreeGlobalIndex of the MANAGED OBJECT."
   ::= {sr1646v2LacpBMembersEntry 10}

sr1646v2LacpBMembersTableIx OBJECT-TYPE
   SYNTAX      TableIndex
   MAX-ACCESS  not-accessible
   STATUS      current
   DESCRIPTION
      ""
   ::= {sr1646v2LacpBMembersEntry 11}

sr1646v2LacpBMembersIfDescr OBJECT-TYPE
   SYNTAX      DisplayString
   MAX-ACCESS  read-only
   STATUS      current
   DESCRIPTION
      "Path: lacpBundle.status.members.ifDescr"
   ::= {sr1646v2LacpBMembersEntry 1694498816}

sr1646v2LacpBMembersMemberStatus OBJECT-TYPE
   SYNTAX      INTEGER
               {
               notFound (0),
               joined (1),
               notJoined (2),
               standby (3)
               }
   MAX-ACCESS  read-only
   STATUS      current
   DESCRIPTION
      "Path: lacpBundle.status.members.memberStatus

       Possibilities:
               notFound   (0)
               joined   (1)
               notJoined   (2)
               standby   (3)"
   ::= {sr1646v2LacpBMembersEntry 1795162112}

sr1646v2LacpBMembersIfLastChange OBJECT-TYPE
   SYNTAX      TimeTicks
   MAX-ACCESS  read-only
   STATUS      current
   DESCRIPTION
      "Path: lacpBundle.status.members.ifLastChange

       Time in centi-second."
   ::= {sr1646v2LacpBMembersEntry 1811939328}

sr1646v2LacpBMembersIfLastChangeDate OBJECT-TYPE
   SYNTAX      DisplayString
   MAX-ACCESS  read-only
   STATUS      current
   DESCRIPTION
      "Path: lacpBundle.status.members.ifLastChangeDate"
   ::= {sr1646v2LacpBMembersEntry 3070230528}

sr1646v2LacpBMembersReceiveState OBJECT-TYPE
   SYNTAX      INTEGER
               {
               unknown (0),
               initialize (1),
               portDisabled (2),
               expired (3),
               lacpDisabled (4),
               defaulted (5),
               current (6)
               }
   MAX-ACCESS  read-only
   STATUS      current
   DESCRIPTION
      "Path: lacpBundle.status.members.receiveState

       Possibilities:
               unknown   (0)
               initialize   (1)
               portDisabled   (2)
               expired   (3)
               lacpDisabled   (4)
               defaulted   (5)
               current   (6)"
   ::= {sr1646v2LacpBMembersEntry 67108864}

sr1646v2LacpBMembersTransmitState OBJECT-TYPE
   SYNTAX      INTEGER
               {
               unknown (0),
               noPeriodic (1),
               fastPeriodic (2),
               slowPeriodic (3),
               periodicTx (4)
               }
   MAX-ACCESS  read-only
   STATUS      current
   DESCRIPTION
      "Path: lacpBundle.status.members.transmitState

       Possibilities:
               unknown   (0)
               noPeriodic   (1)
               fastPeriodic   (2)
               slowPeriodic   (3)
               periodicTx   (4)"
   ::= {sr1646v2LacpBMembersEntry 134217728}

sr1646v2LacpBMembersMuxState OBJECT-TYPE
   SYNTAX      INTEGER
               {
               unknown (0),
               detached (1),
               waiting (2),
               attached (3),
               collecting (4),
               distributing (5)
               }
   MAX-ACCESS  read-only
   STATUS      current
   DESCRIPTION
      "Path: lacpBundle.status.members.muxState

       Possibilities:
               unknown   (0)
               detached   (1)
               waiting   (2)
               attached   (3)
               collecting   (4)
               distributing   (5)"
   ::= {sr1646v2LacpBMembersEntry 83886080}

sr1646v2LacpBMembersActorPortPriority OBJECT-TYPE
   SYNTAX      Integer32
   MAX-ACCESS  read-only
   STATUS      current
   DESCRIPTION
      "Path: lacpBundle.status.members.actor.portPriority"
   ::= {sr1646v2LacpBMembersEntry 100728832}

sr1646v2LacpBMembersActorPortNumber OBJECT-TYPE
   SYNTAX      Integer32
   MAX-ACCESS  read-only
   STATUS      current
   DESCRIPTION
      "Path: lacpBundle.status.members.actor.portNumber"
   ::= {sr1646v2LacpBMembersEntry 100794368}

sr1646v2LacpBMembersActorStateActivity OBJECT-TYPE
   SYNTAX      INTEGER
               {
               passive (0),
               active (1)
               }
   MAX-ACCESS  read-only
   STATUS      current
   DESCRIPTION
      "Path: lacpBundle.status.members.actor.state.activity

       Possibilities:
               passive   (0)
               active   (1)"
   ::= {sr1646v2LacpBMembersEntry 100860160}

sr1646v2LacpBMembersActorStateTimeout OBJECT-TYPE
   SYNTAX      INTEGER
               {
               long (0),
               short (1)
               }
   MAX-ACCESS  read-only
   STATUS      current
   DESCRIPTION
      "Path: lacpBundle.status.members.actor.state.timeout

       Possibilities:
               long   (0)
               short   (1)"
   ::= {sr1646v2LacpBMembersEntry 100860416}

sr1646v2LacpBMembersActorStateAggregation OBJECT-TYPE
   SYNTAX      INTEGER
               {
               false (0),
               true (1)
               }
   MAX-ACCESS  read-only
   STATUS      current
   DESCRIPTION
      "Path: lacpBundle.status.members.actor.state.aggregation

       Possibilities:
               false   (0)
               true   (1)"
   ::= {sr1646v2LacpBMembersEntry 100860672}

sr1646v2LacpBMembersActorStateSynchronization OBJECT-TYPE
   SYNTAX      INTEGER
               {
               false (0),
               true (1)
               }
   MAX-ACCESS  read-only
   STATUS      current
   DESCRIPTION
      "Path: lacpBundle.status.members.actor.state.synchronization

       Possibilities:
               false   (0)
               true   (1)"
   ::= {sr1646v2LacpBMembersEntry 100860928}

sr1646v2LacpBMembersActorStateCollecting OBJECT-TYPE
   SYNTAX      INTEGER
               {
               false (0),
               true (1)
               }
   MAX-ACCESS  read-only
   STATUS      current
   DESCRIPTION
      "Path: lacpBundle.status.members.actor.state.collecting

       Possibilities:
               false   (0)
               true   (1)"
   ::= {sr1646v2LacpBMembersEntry 100861184}

sr1646v2LacpBMembersActorStateDistributing OBJECT-TYPE
   SYNTAX      INTEGER
               {
               false (0),
               true (1)
               }
   MAX-ACCESS  read-only
   STATUS      current
   DESCRIPTION
      "Path: lacpBundle.status.members.actor.state.distributing

       Possibilities:
               false   (0)
               true   (1)"
   ::= {sr1646v2LacpBMembersEntry 100861440}

sr1646v2LacpBMembersActorStateDefaulted OBJECT-TYPE
   SYNTAX      INTEGER
               {
               false (0),
               true (1)
               }
   MAX-ACCESS  read-only
   STATUS      current
   DESCRIPTION
      "Path: lacpBundle.status.members.actor.state.defaulted

       Possibilities:
               false   (0)
               true   (1)"
   ::= {sr1646v2LacpBMembersEntry 100861696}

sr1646v2LacpBMembersActorStateExpired OBJECT-TYPE
   SYNTAX      INTEGER
               {
               false (0),
               true (1)
               }
   MAX-ACCESS  read-only
   STATUS      current
   DESCRIPTION
      "Path: lacpBundle.status.members.actor.state.expired

       Possibilities:
               false   (0)
               true   (1)"
   ::= {sr1646v2LacpBMembersEntry 100861952}

sr1646v2LacpBMembersActorAdministrativeKey OBJECT-TYPE
   SYNTAX      OCTET STRING
   MAX-ACCESS  read-only
   STATUS      current
   DESCRIPTION
      "Path: lacpBundle.status.members.actor.administrativeKey"
   ::= {sr1646v2LacpBMembersEntry 100925440}

sr1646v2LacpBMembersActorOperationalKey OBJECT-TYPE
   SYNTAX      OCTET STRING
   MAX-ACCESS  read-only
   STATUS      current
   DESCRIPTION
      "Path: lacpBundle.status.members.actor.operationalKey"
   ::= {sr1646v2LacpBMembersEntry 100990976}

sr1646v2LacpBMembersPartnerPortPriority OBJECT-TYPE
   SYNTAX      Integer32
   MAX-ACCESS  read-only
   STATUS      current
   DESCRIPTION
      "Path: lacpBundle.status.members.partner.portPriority"
   ::= {sr1646v2LacpBMembersEntry 117506048}

sr1646v2LacpBMembersPartnerPortNumber OBJECT-TYPE
   SYNTAX      Integer32
   MAX-ACCESS  read-only
   STATUS      current
   DESCRIPTION
      "Path: lacpBundle.status.members.partner.portNumber"
   ::= {sr1646v2LacpBMembersEntry 117571584}

sr1646v2LacpBMembersPartnerStateActivity OBJECT-TYPE
   SYNTAX      INTEGER
               {
               passive (0),
               active (1)
               }
   MAX-ACCESS  read-only
   STATUS      current
   DESCRIPTION
      "Path: lacpBundle.status.members.partner.state.activity

       Possibilities:
               passive   (0)
               active   (1)"
   ::= {sr1646v2LacpBMembersEntry 117637376}

sr1646v2LacpBMembersPartnerStateTimeout OBJECT-TYPE
   SYNTAX      INTEGER
               {
               long (0),
               short (1)
               }
   MAX-ACCESS  read-only
   STATUS      current
   DESCRIPTION
      "Path: lacpBundle.status.members.partner.state.timeout

       Possibilities:
               long   (0)
               short   (1)"
   ::= {sr1646v2LacpBMembersEntry 117637632}

sr1646v2LacpBMembersPartnerStateAggregation OBJECT-TYPE
   SYNTAX      INTEGER
               {
               false (0),
               true (1)
               }
   MAX-ACCESS  read-only
   STATUS      current
   DESCRIPTION
      "Path: lacpBundle.status.members.partner.state.aggregation

       Possibilities:
               false   (0)
               true   (1)"
   ::= {sr1646v2LacpBMembersEntry 117637888}

sr1646v2LacpBMembersPartnerStateSynchronization OBJECT-TYPE
   SYNTAX      INTEGER
               {
               false (0),
               true (1)
               }
   MAX-ACCESS  read-only
   STATUS      current
   DESCRIPTION
      "Path: lacpBundle.status.members.partner.state.synchronization

       Possibilities:
               false   (0)
               true   (1)"
   ::= {sr1646v2LacpBMembersEntry 117638144}

sr1646v2LacpBMembersPartnerStateCollecting OBJECT-TYPE
   SYNTAX      INTEGER
               {
               false (0),
               true (1)
               }
   MAX-ACCESS  read-only
   STATUS      current
   DESCRIPTION
      "Path: lacpBundle.status.members.partner.state.collecting

       Possibilities:
               false   (0)
               true   (1)"
   ::= {sr1646v2LacpBMembersEntry 117638400}

sr1646v2LacpBMembersPartnerStateDistributing OBJECT-TYPE
   SYNTAX      INTEGER
               {
               false (0),
               true (1)
               }
   MAX-ACCESS  read-only
   STATUS      current
   DESCRIPTION
      "Path: lacpBundle.status.members.partner.state.distributing

       Possibilities:
               false   (0)
               true   (1)"
   ::= {sr1646v2LacpBMembersEntry 117638656}

sr1646v2LacpBMembersPartnerStateDefaulted OBJECT-TYPE
   SYNTAX      INTEGER
               {
               false (0),
               true (1)
               }
   MAX-ACCESS  read-only
   STATUS      current
   DESCRIPTION
      "Path: lacpBundle.status.members.partner.state.defaulted

       Possibilities:
               false   (0)
               true   (1)"
   ::= {sr1646v2LacpBMembersEntry 117638912}

sr1646v2LacpBMembersPartnerStateExpired OBJECT-TYPE
   SYNTAX      INTEGER
               {
               false (0),
               true (1)
               }
   MAX-ACCESS  read-only
   STATUS      current
   DESCRIPTION
      "Path: lacpBundle.status.members.partner.state.expired

       Possibilities:
               false   (0)
               true   (1)"
   ::= {sr1646v2LacpBMembersEntry 117639168}

sr1646v2LacpBMembersPartnerOperationalKey OBJECT-TYPE
   SYNTAX      OCTET STRING
   MAX-ACCESS  read-only
   STATUS      current
   DESCRIPTION
      "Path: lacpBundle.status.members.partner.operationalKey"
   ::= {sr1646v2LacpBMembersEntry 117702656}



pr1646v2LacpB OBJECT IDENTIFIER ::= {r1646v2LacpB 12}


pr1646v2LacpBInOctets OBJECT IDENTIFIER ::= {pr1646v2LacpB 109}

pr1646v2LacpBInOctetsTable OBJECT-TYPE
   SYNTAX      SEQUENCE OF Pr1646v2LacpBInOctetsEntry
   MAX-ACCESS  not-accessible
   STATUS      current
   DESCRIPTION
      "ifInOctets"
   ::= {pr1646v2LacpBInOctets 1}

pr1646v2LacpBInOctetsEntry OBJECT-TYPE
   SYNTAX      Pr1646v2LacpBInOctetsEntry
   MAX-ACCESS  not-accessible
   STATUS      current
   DESCRIPTION
      ""
   INDEX      { pr1646v2LacpBInOctetsGlobalIx }
   ::= {pr1646v2LacpBInOctetsTable 1}

Pr1646v2LacpBInOctetsEntry ::=
   SEQUENCE
      {
      pr1646v2LacpBInOctetsGlobalIx
         GlobalIndex,
      pr1646v2LacpBInOctetsValue
         Counter64
      }

pr1646v2LacpBInOctetsGlobalIx OBJECT-TYPE
   SYNTAX      GlobalIndex
   MAX-ACCESS  not-accessible
   STATUS      current
   DESCRIPTION
      "The value of the tlsCntTreeGlobalIndex of the MANAGED OBJECT."
   ::= {pr1646v2LacpBInOctetsEntry 10}

pr1646v2LacpBInOctetsValue OBJECT-TYPE
   SYNTAX      Counter64
   MAX-ACCESS  read-only
   STATUS      current
   DESCRIPTION
      "Path: lacpBundle.performance.ifInOctets

       64 bit unsigned wrappable counter."
   ::= {pr1646v2LacpBInOctetsEntry 2147483648}


pr1646v2LacpBInUcast OBJECT IDENTIFIER ::= {pr1646v2LacpB 110}

pr1646v2LacpBInUcastTable OBJECT-TYPE
   SYNTAX      SEQUENCE OF Pr1646v2LacpBInUcastEntry
   MAX-ACCESS  not-accessible
   STATUS      current
   DESCRIPTION
      "ifInUcastPkts"
   ::= {pr1646v2LacpBInUcast 1}

pr1646v2LacpBInUcastEntry OBJECT-TYPE
   SYNTAX      Pr1646v2LacpBInUcastEntry
   MAX-ACCESS  not-accessible
   STATUS      current
   DESCRIPTION
      ""
   INDEX      { pr1646v2LacpBInUcastGlobalIx }
   ::= {pr1646v2LacpBInUcastTable 1}

Pr1646v2LacpBInUcastEntry ::=
   SEQUENCE
      {
      pr1646v2LacpBInUcastGlobalIx
         GlobalIndex,
      pr1646v2LacpBInUcastValue
         Counter64
      }

pr1646v2LacpBInUcastGlobalIx OBJECT-TYPE
   SYNTAX      GlobalIndex
   MAX-ACCESS  not-accessible
   STATUS      current
   DESCRIPTION
      "The value of the tlsCntTreeGlobalIndex of the MANAGED OBJECT."
   ::= {pr1646v2LacpBInUcastEntry 10}

pr1646v2LacpBInUcastValue OBJECT-TYPE
   SYNTAX      Counter64
   MAX-ACCESS  read-only
   STATUS      current
   DESCRIPTION
      "Path: lacpBundle.performance.ifInUcastPkts

       64 bit unsigned wrappable counter."
   ::= {pr1646v2LacpBInUcastEntry 2147483648}


pr1646v2LacpBInNUcastPkts OBJECT IDENTIFIER ::= {pr1646v2LacpB 111}

pr1646v2LacpBInNUcastPktsTable OBJECT-TYPE
   SYNTAX      SEQUENCE OF Pr1646v2LacpBInNUcastPktsEntry
   MAX-ACCESS  not-accessible
   STATUS      current
   DESCRIPTION
      "ifInNUcastPkts"
   ::= {pr1646v2LacpBInNUcastPkts 1}

pr1646v2LacpBInNUcastPktsEntry OBJECT-TYPE
   SYNTAX      Pr1646v2LacpBInNUcastPktsEntry
   MAX-ACCESS  not-accessible
   STATUS      current
   DESCRIPTION
      ""
   INDEX      { pr1646v2LacpBInNUcastPktsGlobalIx }
   ::= {pr1646v2LacpBInNUcastPktsTable 1}

Pr1646v2LacpBInNUcastPktsEntry ::=
   SEQUENCE
      {
      pr1646v2LacpBInNUcastPktsGlobalIx
         GlobalIndex,
      pr1646v2LacpBInNUcastPktsValue
         Counter64
      }

pr1646v2LacpBInNUcastPktsGlobalIx OBJECT-TYPE
   SYNTAX      GlobalIndex
   MAX-ACCESS  not-accessible
   STATUS      current
   DESCRIPTION
      "The value of the tlsCntTreeGlobalIndex of the MANAGED OBJECT."
   ::= {pr1646v2LacpBInNUcastPktsEntry 10}

pr1646v2LacpBInNUcastPktsValue OBJECT-TYPE
   SYNTAX      Counter64
   MAX-ACCESS  read-only
   STATUS      current
   DESCRIPTION
      "Path: lacpBundle.performance.ifInNUcastPkts

       64 bit unsigned wrappable counter."
   ::= {pr1646v2LacpBInNUcastPktsEntry 2147483648}


pr1646v2LacpBInBcastPkts OBJECT IDENTIFIER ::= {pr1646v2LacpB 211}

pr1646v2LacpBInBcastPktsTable OBJECT-TYPE
   SYNTAX      SEQUENCE OF Pr1646v2LacpBInBcastPktsEntry
   MAX-ACCESS  not-accessible
   STATUS      current
   DESCRIPTION
      "ifInBcastPkts"
   ::= {pr1646v2LacpBInBcastPkts 1}

pr1646v2LacpBInBcastPktsEntry OBJECT-TYPE
   SYNTAX      Pr1646v2LacpBInBcastPktsEntry
   MAX-ACCESS  not-accessible
   STATUS      current
   DESCRIPTION
      ""
   INDEX      { pr1646v2LacpBInBcastPktsGlobalIx }
   ::= {pr1646v2LacpBInBcastPktsTable 1}

Pr1646v2LacpBInBcastPktsEntry ::=
   SEQUENCE
      {
      pr1646v2LacpBInBcastPktsGlobalIx
         GlobalIndex,
      pr1646v2LacpBInBcastPktsValue
         Counter64
      }

pr1646v2LacpBInBcastPktsGlobalIx OBJECT-TYPE
   SYNTAX      GlobalIndex
   MAX-ACCESS  not-accessible
   STATUS      current
   DESCRIPTION
      "The value of the tlsCntTreeGlobalIndex of the MANAGED OBJECT."
   ::= {pr1646v2LacpBInBcastPktsEntry 10}

pr1646v2LacpBInBcastPktsValue OBJECT-TYPE
   SYNTAX      Counter64
   MAX-ACCESS  read-only
   STATUS      current
   DESCRIPTION
      "Path: lacpBundle.performance.ifInBcastPkts

       64 bit unsigned wrappable counter."
   ::= {pr1646v2LacpBInBcastPktsEntry 2147483648}


pr1646v2LacpBInMcastPkts OBJECT IDENTIFIER ::= {pr1646v2LacpB 221}

pr1646v2LacpBInMcastPktsTable OBJECT-TYPE
   SYNTAX      SEQUENCE OF Pr1646v2LacpBInMcastPktsEntry
   MAX-ACCESS  not-accessible
   STATUS      current
   DESCRIPTION
      "ifInNUcastPkts"
   ::= {pr1646v2LacpBInMcastPkts 1}

pr1646v2LacpBInMcastPktsEntry OBJECT-TYPE
   SYNTAX      Pr1646v2LacpBInMcastPktsEntry
   MAX-ACCESS  not-accessible
   STATUS      current
   DESCRIPTION
      ""
   INDEX      { pr1646v2LacpBInMcastPktsGlobalIx }
   ::= {pr1646v2LacpBInMcastPktsTable 1}

Pr1646v2LacpBInMcastPktsEntry ::=
   SEQUENCE
      {
      pr1646v2LacpBInMcastPktsGlobalIx
         GlobalIndex,
      pr1646v2LacpBInMcastPktsValue
         Counter64
      }

pr1646v2LacpBInMcastPktsGlobalIx OBJECT-TYPE
   SYNTAX      GlobalIndex
   MAX-ACCESS  not-accessible
   STATUS      current
   DESCRIPTION
      "The value of the tlsCntTreeGlobalIndex of the MANAGED OBJECT."
   ::= {pr1646v2LacpBInMcastPktsEntry 10}

pr1646v2LacpBInMcastPktsValue OBJECT-TYPE
   SYNTAX      Counter64
   MAX-ACCESS  read-only
   STATUS      current
   DESCRIPTION
      "Path: lacpBundle.performance.ifInMcastPkts

       64 bit unsigned wrappable counter."
   ::= {pr1646v2LacpBInMcastPktsEntry 2147483648}


pr1646v2LacpBInDiscards OBJECT IDENTIFIER ::= {pr1646v2LacpB 112}

pr1646v2LacpBInDiscardsTable OBJECT-TYPE
   SYNTAX      SEQUENCE OF Pr1646v2LacpBInDiscardsEntry
   MAX-ACCESS  not-accessible
   STATUS      current
   DESCRIPTION
      "ifInDiscards"
   ::= {pr1646v2LacpBInDiscards 1}

pr1646v2LacpBInDiscardsEntry OBJECT-TYPE
   SYNTAX      Pr1646v2LacpBInDiscardsEntry
   MAX-ACCESS  not-accessible
   STATUS      current
   DESCRIPTION
      ""
   INDEX      { pr1646v2LacpBInDiscardsGlobalIx }
   ::= {pr1646v2LacpBInDiscardsTable 1}

Pr1646v2LacpBInDiscardsEntry ::=
   SEQUENCE
      {
      pr1646v2LacpBInDiscardsGlobalIx
         GlobalIndex,
      pr1646v2LacpBInDiscardsValue
         Counter64
      }

pr1646v2LacpBInDiscardsGlobalIx OBJECT-TYPE
   SYNTAX      GlobalIndex
   MAX-ACCESS  not-accessible
   STATUS      current
   DESCRIPTION
      "The value of the tlsCntTreeGlobalIndex of the MANAGED OBJECT."
   ::= {pr1646v2LacpBInDiscardsEntry 10}

pr1646v2LacpBInDiscardsValue OBJECT-TYPE
   SYNTAX      Counter64
   MAX-ACCESS  read-only
   STATUS      current
   DESCRIPTION
      "Path: lacpBundle.performance.ifInDiscards

       64 bit unsigned wrappable counter."
   ::= {pr1646v2LacpBInDiscardsEntry 2147483648}


pr1646v2LacpBInErrors OBJECT IDENTIFIER ::= {pr1646v2LacpB 113}

pr1646v2LacpBInErrorsTable OBJECT-TYPE
   SYNTAX      SEQUENCE OF Pr1646v2LacpBInErrorsEntry
   MAX-ACCESS  not-accessible
   STATUS      current
   DESCRIPTION
      "ifInErrors"
   ::= {pr1646v2LacpBInErrors 1}

pr1646v2LacpBInErrorsEntry OBJECT-TYPE
   SYNTAX      Pr1646v2LacpBInErrorsEntry
   MAX-ACCESS  not-accessible
   STATUS      current
   DESCRIPTION
      ""
   INDEX      { pr1646v2LacpBInErrorsGlobalIx }
   ::= {pr1646v2LacpBInErrorsTable 1}

Pr1646v2LacpBInErrorsEntry ::=
   SEQUENCE
      {
      pr1646v2LacpBInErrorsGlobalIx
         GlobalIndex,
      pr1646v2LacpBInErrorsValue
         Counter64
      }

pr1646v2LacpBInErrorsGlobalIx OBJECT-TYPE
   SYNTAX      GlobalIndex
   MAX-ACCESS  not-accessible
   STATUS      current
   DESCRIPTION
      "The value of the tlsCntTreeGlobalIndex of the MANAGED OBJECT."
   ::= {pr1646v2LacpBInErrorsEntry 10}

pr1646v2LacpBInErrorsValue OBJECT-TYPE
   SYNTAX      Counter64
   MAX-ACCESS  read-only
   STATUS      current
   DESCRIPTION
      "Path: lacpBundle.performance.ifInErrors

       64 bit unsigned wrappable counter."
   ::= {pr1646v2LacpBInErrorsEntry 2147483648}


pr1646v2LacpBInUnknownProtos OBJECT IDENTIFIER ::= {pr1646v2LacpB 114}

pr1646v2LacpBInUnknownProtosTable OBJECT-TYPE
   SYNTAX      SEQUENCE OF Pr1646v2LacpBInUnknownProtosEntry
   MAX-ACCESS  not-accessible
   STATUS      current
   DESCRIPTION
      "ifInUnknownprotos"
   ::= {pr1646v2LacpBInUnknownProtos 1}

pr1646v2LacpBInUnknownProtosEntry OBJECT-TYPE
   SYNTAX      Pr1646v2LacpBInUnknownProtosEntry
   MAX-ACCESS  not-accessible
   STATUS      current
   DESCRIPTION
      ""
   INDEX      { pr1646v2LacpBInUnknownProtosGlobalIx }
   ::= {pr1646v2LacpBInUnknownProtosTable 1}

Pr1646v2LacpBInUnknownProtosEntry ::=
   SEQUENCE
      {
      pr1646v2LacpBInUnknownProtosGlobalIx
         GlobalIndex,
      pr1646v2LacpBInUnknownProtosValue
         Counter64
      }

pr1646v2LacpBInUnknownProtosGlobalIx OBJECT-TYPE
   SYNTAX      GlobalIndex
   MAX-ACCESS  not-accessible
   STATUS      current
   DESCRIPTION
      "The value of the tlsCntTreeGlobalIndex of the MANAGED OBJECT."
   ::= {pr1646v2LacpBInUnknownProtosEntry 10}

pr1646v2LacpBInUnknownProtosValue OBJECT-TYPE
   SYNTAX      Counter64
   MAX-ACCESS  read-only
   STATUS      current
   DESCRIPTION
      "Path: lacpBundle.performance.ifInUnknownProtos

       64 bit unsigned wrappable counter."
   ::= {pr1646v2LacpBInUnknownProtosEntry 2147483648}


pr1646v2LacpBInQLen OBJECT IDENTIFIER ::= {pr1646v2LacpB 128}

pr1646v2LacpBInQLenTable OBJECT-TYPE
   SYNTAX      SEQUENCE OF Pr1646v2LacpBInQLenEntry
   MAX-ACCESS  not-accessible
   STATUS      current
   DESCRIPTION
      "ifInQLen"
   ::= {pr1646v2LacpBInQLen 1}

pr1646v2LacpBInQLenEntry OBJECT-TYPE
   SYNTAX      Pr1646v2LacpBInQLenEntry
   MAX-ACCESS  not-accessible
   STATUS      current
   DESCRIPTION
      ""
   INDEX      { pr1646v2LacpBInQLenGlobalIx }
   ::= {pr1646v2LacpBInQLenTable 1}

Pr1646v2LacpBInQLenEntry ::=
   SEQUENCE
      {
      pr1646v2LacpBInQLenGlobalIx
         GlobalIndex,
      pr1646v2LacpBInQLenValue
         Gauge32
      }

pr1646v2LacpBInQLenGlobalIx OBJECT-TYPE
   SYNTAX      GlobalIndex
   MAX-ACCESS  not-accessible
   STATUS      current
   DESCRIPTION
      "The value of the tlsCntTreeGlobalIndex of the MANAGED OBJECT."
   ::= {pr1646v2LacpBInQLenEntry 10}

pr1646v2LacpBInQLenValue OBJECT-TYPE
   SYNTAX      Gauge32
   MAX-ACCESS  read-only
   STATUS      current
   DESCRIPTION
      "Path: lacpBundle.performance.ifInQLen

       32 bit unsigned gauge value."
   ::= {pr1646v2LacpBInQLenEntry 2147483648}


pr1646v2LacpBInDropEx OBJECT IDENTIFIER ::= {pr1646v2LacpB 130}

pr1646v2LacpBInDropExTable OBJECT-TYPE
   SYNTAX      SEQUENCE OF Pr1646v2LacpBInDropExEntry
   MAX-ACCESS  not-accessible
   STATUS      current
   DESCRIPTION
      "ifInDiscards"
   ::= {pr1646v2LacpBInDropEx 1}

pr1646v2LacpBInDropExEntry OBJECT-TYPE
   SYNTAX      Pr1646v2LacpBInDropExEntry
   MAX-ACCESS  not-accessible
   STATUS      current
   DESCRIPTION
      ""
   INDEX      { pr1646v2LacpBInDropExGlobalIx }
   ::= {pr1646v2LacpBInDropExTable 1}

Pr1646v2LacpBInDropExEntry ::=
   SEQUENCE
      {
      pr1646v2LacpBInDropExGlobalIx
         GlobalIndex,
      pr1646v2LacpBInDropExValue
         Counter64
      }

pr1646v2LacpBInDropExGlobalIx OBJECT-TYPE
   SYNTAX      GlobalIndex
   MAX-ACCESS  not-accessible
   STATUS      current
   DESCRIPTION
      "The value of the tlsCntTreeGlobalIndex of the MANAGED OBJECT."
   ::= {pr1646v2LacpBInDropExEntry 10}

pr1646v2LacpBInDropExValue OBJECT-TYPE
   SYNTAX      Counter64
   MAX-ACCESS  read-only
   STATUS      current
   DESCRIPTION
      "Path: lacpBundle.performance.ifInDropLevelExceeded

       64 bit unsigned wrappable counter."
   ::= {pr1646v2LacpBInDropExEntry 2147483648}


pr1646v2LacpBInDropNoMac OBJECT IDENTIFIER ::= {pr1646v2LacpB 133}

pr1646v2LacpBInDropNoMacTable OBJECT-TYPE
   SYNTAX      SEQUENCE OF Pr1646v2LacpBInDropNoMacEntry
   MAX-ACCESS  not-accessible
   STATUS      current
   DESCRIPTION
      "ifInDiscards"
   ::= {pr1646v2LacpBInDropNoMac 1}

pr1646v2LacpBInDropNoMacEntry OBJECT-TYPE
   SYNTAX      Pr1646v2LacpBInDropNoMacEntry
   MAX-ACCESS  not-accessible
   STATUS      current
   DESCRIPTION
      ""
   INDEX      { pr1646v2LacpBInDropNoMacGlobalIx }
   ::= {pr1646v2LacpBInDropNoMacTable 1}

Pr1646v2LacpBInDropNoMacEntry ::=
   SEQUENCE
      {
      pr1646v2LacpBInDropNoMacGlobalIx
         GlobalIndex,
      pr1646v2LacpBInDropNoMacValue
         Counter64
      }

pr1646v2LacpBInDropNoMacGlobalIx OBJECT-TYPE
   SYNTAX      GlobalIndex
   MAX-ACCESS  not-accessible
   STATUS      current
   DESCRIPTION
      "The value of the tlsCntTreeGlobalIndex of the MANAGED OBJECT."
   ::= {pr1646v2LacpBInDropNoMacEntry 10}

pr1646v2LacpBInDropNoMacValue OBJECT-TYPE
   SYNTAX      Counter64
   MAX-ACCESS  read-only
   STATUS      current
   DESCRIPTION
      "Path: lacpBundle.performance.ifInDiscardsNoMacFit

       64 bit unsigned wrappable counter."
   ::= {pr1646v2LacpBInDropNoMacEntry 2147483648}


pr1646v2LacpBInDropNUCast OBJECT IDENTIFIER ::= {pr1646v2LacpB 136}

pr1646v2LacpBInDropNUCastTable OBJECT-TYPE
   SYNTAX      SEQUENCE OF Pr1646v2LacpBInDropNUCastEntry
   MAX-ACCESS  not-accessible
   STATUS      current
   DESCRIPTION
      "ifInDiscards"
   ::= {pr1646v2LacpBInDropNUCast 1}

pr1646v2LacpBInDropNUCastEntry OBJECT-TYPE
   SYNTAX      Pr1646v2LacpBInDropNUCastEntry
   MAX-ACCESS  not-accessible
   STATUS      current
   DESCRIPTION
      ""
   INDEX      { pr1646v2LacpBInDropNUCastGlobalIx }
   ::= {pr1646v2LacpBInDropNUCastTable 1}

Pr1646v2LacpBInDropNUCastEntry ::=
   SEQUENCE
      {
      pr1646v2LacpBInDropNUCastGlobalIx
         GlobalIndex,
      pr1646v2LacpBInDropNUCastValue
         Counter64
      }

pr1646v2LacpBInDropNUCastGlobalIx OBJECT-TYPE
   SYNTAX      GlobalIndex
   MAX-ACCESS  not-accessible
   STATUS      current
   DESCRIPTION
      "The value of the tlsCntTreeGlobalIndex of the MANAGED OBJECT."
   ::= {pr1646v2LacpBInDropNUCastEntry 10}

pr1646v2LacpBInDropNUCastValue OBJECT-TYPE
   SYNTAX      Counter64
   MAX-ACCESS  read-only
   STATUS      current
   DESCRIPTION
      "Path: lacpBundle.performance.ifInDiscardsNUCast

       64 bit unsigned wrappable counter."
   ::= {pr1646v2LacpBInDropNUCastEntry 2147483648}


pr1646v2LacpBInDropFilter OBJECT IDENTIFIER ::= {pr1646v2LacpB 137}

pr1646v2LacpBInDropFilterTable OBJECT-TYPE
   SYNTAX      SEQUENCE OF Pr1646v2LacpBInDropFilterEntry
   MAX-ACCESS  not-accessible
   STATUS      current
   DESCRIPTION
      "ifInDiscards"
   ::= {pr1646v2LacpBInDropFilter 1}

pr1646v2LacpBInDropFilterEntry OBJECT-TYPE
   SYNTAX      Pr1646v2LacpBInDropFilterEntry
   MAX-ACCESS  not-accessible
   STATUS      current
   DESCRIPTION
      ""
   INDEX      { pr1646v2LacpBInDropFilterGlobalIx }
   ::= {pr1646v2LacpBInDropFilterTable 1}

Pr1646v2LacpBInDropFilterEntry ::=
   SEQUENCE
      {
      pr1646v2LacpBInDropFilterGlobalIx
         GlobalIndex,
      pr1646v2LacpBInDropFilterValue
         Counter64
      }

pr1646v2LacpBInDropFilterGlobalIx OBJECT-TYPE
   SYNTAX      GlobalIndex
   MAX-ACCESS  not-accessible
   STATUS      current
   DESCRIPTION
      "The value of the tlsCntTreeGlobalIndex of the MANAGED OBJECT."
   ::= {pr1646v2LacpBInDropFilterEntry 10}

pr1646v2LacpBInDropFilterValue OBJECT-TYPE
   SYNTAX      Counter64
   MAX-ACCESS  read-only
   STATUS      current
   DESCRIPTION
      "Path: lacpBundle.performance.ifInDiscardsFilter

       64 bit unsigned wrappable counter."
   ::= {pr1646v2LacpBInDropFilterEntry 2147483648}


pr1646v2LacpBInQueues OBJECT IDENTIFIER ::= {pr1646v2LacpB 131}

pr1646v2LacpBInQueuesSSCTable OBJECT-TYPE
   SYNTAX      SEQUENCE OF Pr1646v2LacpBInQueuesEntry
   MAX-ACCESS  not-accessible
   STATUS      current
   DESCRIPTION
      "Queue Lengths"
   ::= {pr1646v2LacpBInQueues 1}

pr1646v2LacpBInQueuesEntry OBJECT-TYPE
   SYNTAX      Pr1646v2LacpBInQueuesEntry
   MAX-ACCESS  not-accessible
   STATUS      current
   DESCRIPTION
      ""
   INDEX      { pr1646v2LacpBInQueuesGlobalIx,
                pr1646v2LacpBInQueuesTableIx }
   ::= {pr1646v2LacpBInQueuesSSCTable 1}

Pr1646v2LacpBInQueuesEntry ::=
   SEQUENCE
      {
      pr1646v2LacpBInQueuesGlobalIx
         GlobalIndex,
      pr1646v2LacpBInQueuesTableIx
         TableIndex,
      pr1646v2LacpBInQueuesName
         INTEGER,
      pr1646v2LacpBInQueuesLength
         Integer32,
      pr1646v2LacpBInQueuesOctetLength
         Integer32,
      pr1646v2LacpBInQueuesRedLength
         Integer32,
      pr1646v2LacpBInQueuesPacketsTotal
         Counter64,
      pr1646v2LacpBInQueuesPacketsDirectTx
         Counter64,
      pr1646v2LacpBInQueuesPacketsQueued
         Counter64,
      pr1646v2LacpBInQueuesPacketsDropped
         Counter64,
      pr1646v2LacpBInQueuesPacketsRedDropped
         Counter64,
      pr1646v2LacpBInQueuesPacketsCirTx
         Counter64,
      pr1646v2LacpBInQueuesPacketsEirTx
         Counter64,
      pr1646v2LacpBInQueuesPacketsViolateTx
         Counter64,
      pr1646v2LacpBInQueuesOctetsTotal
         Counter64,
      pr1646v2LacpBInQueuesOctetsDirectTx
         Counter64,
      pr1646v2LacpBInQueuesOctetsQueued
         Counter64,
      pr1646v2LacpBInQueuesOctetsDropped
         Counter64,
      pr1646v2LacpBInQueuesOctetsRedDropped
         Counter64,
      pr1646v2LacpBInQueuesOctetsCirTx
         Counter64,
      pr1646v2LacpBInQueuesOctetsEirTx
         Counter64,
      pr1646v2LacpBInQueuesOctetsViolateTx
         Counter64,
      pr1646v2LacpBInQueuesOctetsBandwidth15sec
         Integer32,
      pr1646v2LacpBInQueuesOctetsBandwidth30sec
         Integer32,
      pr1646v2LacpBInQueuesOctetsBandwidth1min
         Integer32,
      pr1646v2LacpBInQueuesOctetsBandwidth2min
         Integer32,
      pr1646v2LacpBInQueuesOctetsBandwidth5min
         Integer32
      }

pr1646v2LacpBInQueuesGlobalIx OBJECT-TYPE
   SYNTAX      GlobalIndex
   MAX-ACCESS  not-accessible
   STATUS      current
   DESCRIPTION
      "The value of the tlsCntTreeGlobalIndex of the MANAGED OBJECT."
   ::= {pr1646v2LacpBInQueuesEntry 10}

pr1646v2LacpBInQueuesTableIx OBJECT-TYPE
   SYNTAX      TableIndex
   MAX-ACCESS  not-accessible
   STATUS      current
   DESCRIPTION
      ""
   ::= {pr1646v2LacpBInQueuesEntry 11}

pr1646v2LacpBInQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: lacpBundle.performance.ifInPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2LacpBInQueuesEntry 16777216}

pr1646v2LacpBInQueuesLength OBJECT-TYPE
   SYNTAX      Integer32
   MAX-ACCESS  read-only
   STATUS      current
   DESCRIPTION
      "Path: lacpBundle.performance.ifInPriorityQueues.length"
   ::= {pr1646v2LacpBInQueuesEntry 33554432}

pr1646v2LacpBInQueuesOctetLength OBJECT-TYPE
   SYNTAX      Integer32
   MAX-ACCESS  read-only
   STATUS      current
   DESCRIPTION
      "Path: lacpBundle.performance.ifInPriorityQueues.octetLength"
   ::= {pr1646v2LacpBInQueuesEntry 150994944}

pr1646v2LacpBInQueuesRedLength OBJECT-TYPE
   SYNTAX      Integer32
   MAX-ACCESS  read-only
   STATUS      current
   DESCRIPTION
      "Path: lacpBundle.performance.ifInPriorityQueues.redLength"
   ::= {pr1646v2LacpBInQueuesEntry 134217728}

pr1646v2LacpBInQueuesPacketsTotal OBJECT-TYPE
   SYNTAX      Counter64
   MAX-ACCESS  read-only
   STATUS      current
   DESCRIPTION
      "Path: lacpBundle.performance.ifInPriorityQueues.packets.total

       64 bit unsigned wrappable counter."
   ::= {pr1646v2LacpBInQueuesEntry 50790400}

pr1646v2LacpBInQueuesPacketsDirectTx OBJECT-TYPE
   SYNTAX      Counter64
   MAX-ACCESS  read-only
   STATUS      current
   DESCRIPTION
      "Path: lacpBundle.performance.ifInPriorityQueues.packets.directTx

       64 bit unsigned wrappable counter."
   ::= {pr1646v2LacpBInQueuesEntry 50397184}

pr1646v2LacpBInQueuesPacketsQueued OBJECT-TYPE
   SYNTAX      Counter64
   MAX-ACCESS  read-only
   STATUS      current
   DESCRIPTION
      "Path: lacpBundle.performance.ifInPriorityQueues.packets.queued

       64 bit unsigned wrappable counter."
   ::= {pr1646v2LacpBInQueuesEntry 50462720}

pr1646v2LacpBInQueuesPacketsDropped OBJECT-TYPE
   SYNTAX      Counter64
   MAX-ACCESS  read-only
   STATUS      current
   DESCRIPTION
      "Path: lacpBundle.performance.ifInPriorityQueues.packets.dropped

       64 bit unsigned wrappable counter."
   ::= {pr1646v2LacpBInQueuesEntry 50528256}

pr1646v2LacpBInQueuesPacketsRedDropped OBJECT-TYPE
   SYNTAX      Counter64
   MAX-ACCESS  read-only
   STATUS      current
   DESCRIPTION
      "Path: lacpBundle.performance.ifInPriorityQueues.packets.redDropped

       64 bit unsigned wrappable counter."
   ::= {pr1646v2LacpBInQueuesEntry 50724864}

pr1646v2LacpBInQueuesPacketsCirTx OBJECT-TYPE
   SYNTAX      Counter64
   MAX-ACCESS  read-only
   STATUS      current
   DESCRIPTION
      "Path: lacpBundle.performance.ifInPriorityQueues.packets.cirTx

       64 bit unsigned wrappable counter."
   ::= {pr1646v2LacpBInQueuesEntry 50593792}

pr1646v2LacpBInQueuesPacketsEirTx OBJECT-TYPE
   SYNTAX      Counter64
   MAX-ACCESS  read-only
   STATUS      current
   DESCRIPTION
      "Path: lacpBundle.performance.ifInPriorityQueues.packets.eirTx

       64 bit unsigned wrappable counter."
   ::= {pr1646v2LacpBInQueuesEntry 50659328}

pr1646v2LacpBInQueuesPacketsViolateTx OBJECT-TYPE
   SYNTAX      Counter64
   MAX-ACCESS  read-only
   STATUS      current
   DESCRIPTION
      "Path: lacpBundle.performance.ifInPriorityQueues.packets.violateTx

       64 bit unsigned wrappable counter."
   ::= {pr1646v2LacpBInQueuesEntry 50855936}

pr1646v2LacpBInQueuesOctetsTotal OBJECT-TYPE
   SYNTAX      Counter64
   MAX-ACCESS  read-only
   STATUS      current
   DESCRIPTION
      "Path: lacpBundle.performance.ifInPriorityQueues.octets.total

       64 bit unsigned wrappable counter."
   ::= {pr1646v2LacpBInQueuesEntry 67567616}

pr1646v2LacpBInQueuesOctetsDirectTx OBJECT-TYPE
   SYNTAX      Counter64
   MAX-ACCESS  read-only
   STATUS      current
   DESCRIPTION
      "Path: lacpBundle.performance.ifInPriorityQueues.octets.directTx

       64 bit unsigned wrappable counter."
   ::= {pr1646v2LacpBInQueuesEntry 67174400}

pr1646v2LacpBInQueuesOctetsQueued OBJECT-TYPE
   SYNTAX      Counter64
   MAX-ACCESS  read-only
   STATUS      current
   DESCRIPTION
      "Path: lacpBundle.performance.ifInPriorityQueues.octets.queued

       64 bit unsigned wrappable counter."
   ::= {pr1646v2LacpBInQueuesEntry 67239936}

pr1646v2LacpBInQueuesOctetsDropped OBJECT-TYPE
   SYNTAX      Counter64
   MAX-ACCESS  read-only
   STATUS      current
   DESCRIPTION
      "Path: lacpBundle.performance.ifInPriorityQueues.octets.dropped

       64 bit unsigned wrappable counter."
   ::= {pr1646v2LacpBInQueuesEntry 67305472}

pr1646v2LacpBInQueuesOctetsRedDropped OBJECT-TYPE
   SYNTAX      Counter64
   MAX-ACCESS  read-only
   STATUS      current
   DESCRIPTION
      "Path: lacpBundle.performance.ifInPriorityQueues.octets.redDropped

       64 bit unsigned wrappable counter."
   ::= {pr1646v2LacpBInQueuesEntry 67502080}

pr1646v2LacpBInQueuesOctetsCirTx OBJECT-TYPE
   SYNTAX      Counter64
   MAX-ACCESS  read-only
   STATUS      current
   DESCRIPTION
      "Path: lacpBundle.performance.ifInPriorityQueues.octets.cirTx

       64 bit unsigned wrappable counter."
   ::= {pr1646v2LacpBInQueuesEntry 67371008}

pr1646v2LacpBInQueuesOctetsEirTx OBJECT-TYPE
   SYNTAX      Counter64
   MAX-ACCESS  read-only
   STATUS      current
   DESCRIPTION
      "Path: lacpBundle.performance.ifInPriorityQueues.octets.eirTx

       64 bit unsigned wrappable counter."
   ::= {pr1646v2LacpBInQueuesEntry 67436544}

pr1646v2LacpBInQueuesOctetsViolateTx OBJECT-TYPE
   SYNTAX      Counter64
   MAX-ACCESS  read-only
   STATUS      current
   DESCRIPTION
      "Path: lacpBundle.performance.ifInPriorityQueues.octets.violateTx

       64 bit unsigned wrappable counter."
   ::= {pr1646v2LacpBInQueuesEntry 67633152}

pr1646v2LacpBInQueuesOctetsBandwidth15sec OBJECT-TYPE
   SYNTAX      Integer32
   MAX-ACCESS  read-only
   STATUS      current
   DESCRIPTION
      "Path: lacpBundle.performance.ifInPriorityQueues.octets.bandwidth.15sec

       unit name = bps
       formula = 8 * ; 8 /"
   ::= {pr1646v2LacpBInQueuesEntry 70386944}

pr1646v2LacpBInQueuesOctetsBandwidth30sec OBJECT-TYPE
   SYNTAX      Integer32
   MAX-ACCESS  read-only
   STATUS      current
   DESCRIPTION
      "Path: lacpBundle.performance.ifInPriorityQueues.octets.bandwidth.30sec

       unit name = bps
       formula = 8 * ; 8 /"
   ::= {pr1646v2LacpBInQueuesEntry 70388224}

pr1646v2LacpBInQueuesOctetsBandwidth1min OBJECT-TYPE
   SYNTAX      Integer32
   MAX-ACCESS  read-only
   STATUS      current
   DESCRIPTION
      "Path: lacpBundle.performance.ifInPriorityQueues.octets.bandwidth.1min

       unit name = bps
       formula = 8 * ; 8 /"
   ::= {pr1646v2LacpBInQueuesEntry 70390784}

pr1646v2LacpBInQueuesOctetsBandwidth2min OBJECT-TYPE
   SYNTAX      Integer32
   MAX-ACCESS  read-only
   STATUS      current
   DESCRIPTION
      "Path: lacpBundle.performance.ifInPriorityQueues.octets.bandwidth.2min

       unit name = bps
       formula = 8 * ; 8 /"
   ::= {pr1646v2LacpBInQueuesEntry 70395904}

pr1646v2LacpBInQueuesOctetsBandwidth5min OBJECT-TYPE
   SYNTAX      Integer32
   MAX-ACCESS  read-only
   STATUS      current
   DESCRIPTION
      "Path: lacpBundle.performance.ifInPriorityQueues.octets.bandwidth.5min

       unit name = bps
       formula = 8 * ; 8 /"
   ::= {pr1646v2LacpBInQueuesEntry 70411264}

pr1646v2LacpBInQueuesH2Performance OBJECT-TYPE
   SYNTAX      SEQUENCE OF Pr1646v2LacpBInQueuesH2PerformanceEntry
   MAX-ACCESS  not-accessible
   STATUS      current
   DESCRIPTION
      ""
   ::= {pr1646v2LacpBInQueues 83886080}

pr1646v2LacpBInQueuesH2PerformanceEntry OBJECT-TYPE
   SYNTAX      Pr1646v2LacpBInQueuesH2PerformanceEntry
   MAX-ACCESS  not-accessible
   STATUS      current
   DESCRIPTION
      ""
   INDEX      { pr1646v2LacpBInQueuesH2PerformanceGlobalIx,
                pr1646v2LacpBInQueuesTableIx,
                pr1646v2LacpBInQueuesH2PerformanceTableIx }
   ::= {pr1646v2LacpBInQueuesH2Performance 1}

Pr1646v2LacpBInQueuesH2PerformanceEntry ::=
   SEQUENCE
      {
      pr1646v2LacpBInQueuesH2PerformanceGlobalIx
         GlobalIndex,
      pr1646v2LacpBInQueuesH2PerformanceTableIx
         TableIndex,
      pr1646v2LacpBInQueuesH2PerformanceSysUpTime
         TimeTicks,
      pr1646v2LacpBInQueuesH2PerformanceTotPkts
         Counter64,
      pr1646v2LacpBInQueuesH2PerformanceDirTxPkts
         Counter64,
      pr1646v2LacpBInQueuesH2PerformanceQdPkts
         Counter64,
      pr1646v2LacpBInQueuesH2PerformanceDropPkts
         Counter64,
      pr1646v2LacpBInQueuesH2PerformanceRDropPkts
         Counter64,
      pr1646v2LacpBInQueuesH2PerformanceCirTxPkts
         Counter64,
      pr1646v2LacpBInQueuesH2PerformanceEirTxPkts
         Counter64,
      pr1646v2LacpBInQueuesH2PerformanceViolTxPkts
         Counter64,
      pr1646v2LacpBInQueuesH2PerformanceTotOcts
         Counter64,
      pr1646v2LacpBInQueuesH2PerformanceDirTxOcts
         Counter64,
      pr1646v2LacpBInQueuesH2PerformanceQdOcts
         Counter64,
      pr1646v2LacpBInQueuesH2PerformanceDropOcts
         Counter64,
      pr1646v2LacpBInQueuesH2PerformanceRDropOcts
         Counter64,
      pr1646v2LacpBInQueuesH2PerformanceCirTxOcts
         Counter64,
      pr1646v2LacpBInQueuesH2PerformanceEirTxOcts
         Counter64,
      pr1646v2LacpBInQueuesH2PerformanceViolTxOcts
         Counter64,
      pr1646v2LacpBInQueuesH2PerformanceBandwidth
         Integer32
      }

pr1646v2LacpBInQueuesH2PerformanceGlobalIx OBJECT-TYPE
   SYNTAX      GlobalIndex
   MAX-ACCESS  not-accessible
   STATUS      current
   DESCRIPTION
      "The value of the tlsCntTreeGlobalIndex of the MANAGED OBJECT."
   ::= {pr1646v2LacpBInQueuesH2PerformanceEntry 10}

pr1646v2LacpBInQueuesH2PerformanceTableIx OBJECT-TYPE
   SYNTAX      TableIndex
   MAX-ACCESS  not-accessible
   STATUS      current
   DESCRIPTION
      ""
   ::= {pr1646v2LacpBInQueuesH2PerformanceEntry 11}

pr1646v2LacpBInQueuesH2PerformanceSysUpTime OBJECT-TYPE
   SYNTAX      TimeTicks
   MAX-ACCESS  read-only
   STATUS      current
   DESCRIPTION
      "Path: lacpBundle.performance.ifInPriorityQueues.h2Performance.sysUpTime

       Time in centi-second."
   ::= {pr1646v2LacpBInQueuesH2PerformanceEntry 16777216}

pr1646v2LacpBInQueuesH2PerformanceTotPkts OBJECT-TYPE
   SYNTAX      Counter64
   MAX-ACCESS  read-only
   STATUS      current
   DESCRIPTION
      "Path: lacpBundle.performance.ifInPriorityQueues.h2Performance.totalPkts

       64 bit unsigned wrappable counter."
   ::= {pr1646v2LacpBInQueuesH2PerformanceEntry 234881024}

pr1646v2LacpBInQueuesH2PerformanceDirTxPkts OBJECT-TYPE
   SYNTAX      Counter64
   MAX-ACCESS  read-only
   STATUS      current
   DESCRIPTION
      "Path: lacpBundle.performance.ifInPriorityQueues.h2Performance.directTxPkts

       64 bit unsigned wrappable counter."
   ::= {pr1646v2LacpBInQueuesH2PerformanceEntry 33554432}

pr1646v2LacpBInQueuesH2PerformanceQdPkts OBJECT-TYPE
   SYNTAX      Counter64
   MAX-ACCESS  read-only
   STATUS      current
   DESCRIPTION
      "Path: lacpBundle.performance.ifInPriorityQueues.h2Performance.queuedPkts

       64 bit unsigned wrappable counter."
   ::= {pr1646v2LacpBInQueuesH2PerformanceEntry 50331648}

pr1646v2LacpBInQueuesH2PerformanceDropPkts OBJECT-TYPE
   SYNTAX      Counter64
   MAX-ACCESS  read-only
   STATUS      current
   DESCRIPTION
      "Path: lacpBundle.performance.ifInPriorityQueues.h2Performance.droppedPkts

       64 bit unsigned wrappable counter."
   ::= {pr1646v2LacpBInQueuesH2PerformanceEntry 67108864}

pr1646v2LacpBInQueuesH2PerformanceRDropPkts OBJECT-TYPE
   SYNTAX      Counter64
   MAX-ACCESS  read-only
   STATUS      current
   DESCRIPTION
      "Path: lacpBundle.performance.ifInPriorityQueues.h2Performance.redDroppedPkts

       64 bit unsigned wrappable counter."
   ::= {pr1646v2LacpBInQueuesH2PerformanceEntry 201326592}

pr1646v2LacpBInQueuesH2PerformanceCirTxPkts OBJECT-TYPE
   SYNTAX      Counter64
   MAX-ACCESS  read-only
   STATUS      current
   DESCRIPTION
      "Path: lacpBundle.performance.ifInPriorityQueues.h2Performance.cirTxPkts

       64 bit unsigned wrappable counter."
   ::= {pr1646v2LacpBInQueuesH2PerformanceEntry 83886080}

pr1646v2LacpBInQueuesH2PerformanceEirTxPkts OBJECT-TYPE
   SYNTAX      Counter64
   MAX-ACCESS  read-only
   STATUS      current
   DESCRIPTION
      "Path: lacpBundle.performance.ifInPriorityQueues.h2Performance.eirTxPkts

       64 bit unsigned wrappable counter."
   ::= {pr1646v2LacpBInQueuesH2PerformanceEntry 100663296}

pr1646v2LacpBInQueuesH2PerformanceViolTxPkts OBJECT-TYPE
   SYNTAX      Counter64
   MAX-ACCESS  read-only
   STATUS      current
   DESCRIPTION
      "Path: lacpBundle.performance.ifInPriorityQueues.h2Performance.violateTxPkts

       64 bit unsigned wrappable counter."
   ::= {pr1646v2LacpBInQueuesH2PerformanceEntry 301989888}

pr1646v2LacpBInQueuesH2PerformanceTotOcts OBJECT-TYPE
   SYNTAX      Counter64
   MAX-ACCESS  read-only
   STATUS      current
   DESCRIPTION
      "Path: lacpBundle.performance.ifInPriorityQueues.h2Performance.totalOctets

       64 bit unsigned wrappable counter."
   ::= {pr1646v2LacpBInQueuesH2PerformanceEntry 251658240}

pr1646v2LacpBInQueuesH2PerformanceDirTxOcts OBJECT-TYPE
   SYNTAX      Counter64
   MAX-ACCESS  read-only
   STATUS      current
   DESCRIPTION
      "Path: lacpBundle.performance.ifInPriorityQueues.h2Performance.directTxOctets

       64 bit unsigned wrappable counter."
   ::= {pr1646v2LacpBInQueuesH2PerformanceEntry 117440512}

pr1646v2LacpBInQueuesH2PerformanceQdOcts OBJECT-TYPE
   SYNTAX      Counter64
   MAX-ACCESS  read-only
   STATUS      current
   DESCRIPTION
      "Path: lacpBundle.performance.ifInPriorityQueues.h2Performance.queuedOctets

       64 bit unsigned wrappable counter."
   ::= {pr1646v2LacpBInQueuesH2PerformanceEntry 134217728}

pr1646v2LacpBInQueuesH2PerformanceDropOcts OBJECT-TYPE
   SYNTAX      Counter64
   MAX-ACCESS  read-only
   STATUS      current
   DESCRIPTION
      "Path: lacpBundle.performance.ifInPriorityQueues.h2Performance.droppedOctets

       64 bit unsigned wrappable counter."
   ::= {pr1646v2LacpBInQueuesH2PerformanceEntry 150994944}

pr1646v2LacpBInQueuesH2PerformanceRDropOcts OBJECT-TYPE
   SYNTAX      Counter64
   MAX-ACCESS  read-only
   STATUS      current
   DESCRIPTION
      "Path: lacpBundle.performance.ifInPriorityQueues.h2Performance.redDroppedOctets

       64 bit unsigned wrappable counter."
   ::= {pr1646v2LacpBInQueuesH2PerformanceEntry 218103808}

pr1646v2LacpBInQueuesH2PerformanceCirTxOcts OBJECT-TYPE
   SYNTAX      Counter64
   MAX-ACCESS  read-only
   STATUS      current
   DESCRIPTION
      "Path: lacpBundle.performance.ifInPriorityQueues.h2Performance.cirTxOctets

       64 bit unsigned wrappable counter."
   ::= {pr1646v2LacpBInQueuesH2PerformanceEntry 167772160}

pr1646v2LacpBInQueuesH2PerformanceEirTxOcts OBJECT-TYPE
   SYNTAX      Counter64
   MAX-ACCESS  read-only
   STATUS      current
   DESCRIPTION
      "Path: lacpBundle.performance.ifInPriorityQueues.h2Performance.eirTxOctets

       64 bit unsigned wrappable counter."
   ::= {pr1646v2LacpBInQueuesH2PerformanceEntry 184549376}

pr1646v2LacpBInQueuesH2PerformanceViolTxOcts OBJECT-TYPE
   SYNTAX      Counter64
   MAX-ACCESS  read-only
   STATUS      current
   DESCRIPTION
      "Path: lacpBundle.performance.ifInPriorityQueues.h2Performance.violateTxOctets

       64 bit unsigned wrappable counter."
   ::= {pr1646v2LacpBInQueuesH2PerformanceEntry 318767104}

pr1646v2LacpBInQueuesH2PerformanceBandwidth OBJECT-TYPE
   SYNTAX      Integer32
   MAX-ACCESS  read-only
   STATUS      current
   DESCRIPTION
      "Path: lacpBundle.performance.ifInPriorityQueues.h2Performance.bandwidth

       unit name = bps
       formula = 8 * ; 8 /"
   ::= {pr1646v2LacpBInQueuesH2PerformanceEntry 268435456}

pr1646v2LacpBInQueuesH24Performance OBJECT-TYPE
   SYNTAX      SEQUENCE OF Pr1646v2LacpBInQueuesH24PerformanceEntry
   MAX-ACCESS  not-accessible
   STATUS      current
   DESCRIPTION
      ""
   ::= {pr1646v2LacpBInQueues 100663296}

pr1646v2LacpBInQueuesH24PerformanceEntry OBJECT-TYPE
   SYNTAX      Pr1646v2LacpBInQueuesH24PerformanceEntry
   MAX-ACCESS  not-accessible
   STATUS      current
   DESCRIPTION
      ""
   INDEX      { pr1646v2LacpBInQueuesH24PerformanceGlobalIx,
                pr1646v2LacpBInQueuesTableIx,
                pr1646v2LacpBInQueuesH24PerformanceTableIx }
   ::= {pr1646v2LacpBInQueuesH24Performance 1}

Pr1646v2LacpBInQueuesH24PerformanceEntry ::=
   SEQUENCE
      {
      pr1646v2LacpBInQueuesH24PerformanceGlobalIx
         GlobalIndex,
      pr1646v2LacpBInQueuesH24PerformanceTableIx
         TableIndex,
      pr1646v2LacpBInQueuesH24PerformanceSysUpTime
         TimeTicks,
      pr1646v2LacpBInQueuesH24PerformanceTotPkts
         Counter64,
      pr1646v2LacpBInQueuesH24PerformanceDirTxPkts
         Counter64,
      pr1646v2LacpBInQueuesH24PerformanceQdPkts
         Counter64,
      pr1646v2LacpBInQueuesH24PerformanceDropPkts
         Counter64,
      pr1646v2LacpBInQueuesH24PerformanceRDropPkts
         Counter64,
      pr1646v2LacpBInQueuesH24PerformanceCirTxPkts
         Counter64,
      pr1646v2LacpBInQueuesH24PerformanceEirTxPkts
         Counter64,
      pr1646v2LacpBInQueuesH24PerformanceViolTxPkts
         Counter64,
      pr1646v2LacpBInQueuesH24PerformanceTotOcts
         Counter64,
      pr1646v2LacpBInQueuesH24PerformanceDirTxOcts
         Counter64,
      pr1646v2LacpBInQueuesH24PerformanceQdOcts
         Counter64,
      pr1646v2LacpBInQueuesH24PerformanceDropOcts
         Counter64,
      pr1646v2LacpBInQueuesH24PerformanceRDropOcts
         Counter64,
      pr1646v2LacpBInQueuesH24PerformanceCirTxOcts
         Counter64,
      pr1646v2LacpBInQueuesH24PerformanceEirTxOcts
         Counter64,
      pr1646v2LacpBInQueuesH24PerformanceViolTxOcts
         Counter64,
      pr1646v2LacpBInQueuesH24PerformanceBandwidth
         Integer32
      }

pr1646v2LacpBInQueuesH24PerformanceGlobalIx OBJECT-TYPE
   SYNTAX      GlobalIndex
   MAX-ACCESS  not-accessible
   STATUS      current
   DESCRIPTION
      "The value of the tlsCntTreeGlobalIndex of the MANAGED OBJECT."
   ::= {pr1646v2LacpBInQueuesH24PerformanceEntry 10}

pr1646v2LacpBInQueuesH24PerformanceTableIx OBJECT-TYPE
   SYNTAX      TableIndex
   MAX-ACCESS  not-accessible
   STATUS      current
   DESCRIPTION
      ""
   ::= {pr1646v2LacpBInQueuesH24PerformanceEntry 11}

pr1646v2LacpBInQueuesH24PerformanceSysUpTime OBJECT-TYPE
   SYNTAX      TimeTicks
   MAX-ACCESS  read-only
   STATUS      current
   DESCRIPTION
      "Path: lacpBundle.performance.ifInPriorityQueues.h24Performance.sysUpTime

       Time in centi-second."
   ::= {pr1646v2LacpBInQueuesH24PerformanceEntry 16777216}

pr1646v2LacpBInQueuesH24PerformanceTotPkts OBJECT-TYPE
   SYNTAX      Counter64
   MAX-ACCESS  read-only
   STATUS      current
   DESCRIPTION
      "Path: lacpBundle.performance.ifInPriorityQueues.h24Performance.totalPkts

       64 bit unsigned wrappable counter."
   ::= {pr1646v2LacpBInQueuesH24PerformanceEntry 234881024}

pr1646v2LacpBInQueuesH24PerformanceDirTxPkts OBJECT-TYPE
   SYNTAX      Counter64
   MAX-ACCESS  read-only
   STATUS      current
   DESCRIPTION
      "Path: lacpBundle.performance.ifInPriorityQueues.h24Performance.directTxPkts

       64 bit unsigned wrappable counter."
   ::= {pr1646v2LacpBInQueuesH24PerformanceEntry 33554432}

pr1646v2LacpBInQueuesH24PerformanceQdPkts OBJECT-TYPE
   SYNTAX      Counter64
   MAX-ACCESS  read-only
   STATUS      current
   DESCRIPTION
      "Path: lacpBundle.performance.ifInPriorityQueues.h24Performance.queuedPkts

       64 bit unsigned wrappable counter."
   ::= {pr1646v2LacpBInQueuesH24PerformanceEntry 50331648}

pr1646v2LacpBInQueuesH24PerformanceDropPkts OBJECT-TYPE
   SYNTAX      Counter64
   MAX-ACCESS  read-only
   STATUS      current
   DESCRIPTION
      "Path: lacpBundle.performance.ifInPriorityQueues.h24Performance.droppedPkts

       64 bit unsigned wrappable counter."
   ::= {pr1646v2LacpBInQueuesH24PerformanceEntry 67108864}

pr1646v2LacpBInQueuesH24PerformanceRDropPkts OBJECT-TYPE
   SYNTAX      Counter64
   MAX-ACCESS  read-only
   STATUS      current
   DESCRIPTION
      "Path: lacpBundle.performance.ifInPriorityQueues.h24Performance.redDroppedPkts

       64 bit unsigned wrappable counter."
   ::= {pr1646v2LacpBInQueuesH24PerformanceEntry 201326592}

pr1646v2LacpBInQueuesH24PerformanceCirTxPkts OBJECT-TYPE
   SYNTAX      Counter64
   MAX-ACCESS  read-only
   STATUS      current
   DESCRIPTION
      "Path: lacpBundle.performance.ifInPriorityQueues.h24Performance.cirTxPkts

       64 bit unsigned wrappable counter."
   ::= {pr1646v2LacpBInQueuesH24PerformanceEntry 83886080}

pr1646v2LacpBInQueuesH24PerformanceEirTxPkts OBJECT-TYPE
   SYNTAX      Counter64
   MAX-ACCESS  read-only
   STATUS      current
   DESCRIPTION
      "Path: lacpBundle.performance.ifInPriorityQueues.h24Performance.eirTxPkts

       64 bit unsigned wrappable counter."
   ::= {pr1646v2LacpBInQueuesH24PerformanceEntry 100663296}

pr1646v2LacpBInQueuesH24PerformanceViolTxPkts OBJECT-TYPE
   SYNTAX      Counter64
   MAX-ACCESS  read-only
   STATUS      current
   DESCRIPTION
      "Path: lacpBundle.performance.ifInPriorityQueues.h24Performance.violateTxPkts

       64 bit unsigned wrappable counter."
   ::= {pr1646v2LacpBInQueuesH24PerformanceEntry 301989888}

pr1646v2LacpBInQueuesH24PerformanceTotOcts OBJECT-TYPE
   SYNTAX      Counter64
   MAX-ACCESS  read-only
   STATUS      current
   DESCRIPTION
      "Path: lacpBundle.performance.ifInPriorityQueues.h24Performance.totalOctets

       64 bit unsigned wrappable counter."
   ::= {pr1646v2LacpBInQueuesH24PerformanceEntry 251658240}

pr1646v2LacpBInQueuesH24PerformanceDirTxOcts OBJECT-TYPE
   SYNTAX      Counter64
   MAX-ACCESS  read-only
   STATUS      current
   DESCRIPTION
      "Path: lacpBundle.performance.ifInPriorityQueues.h24Performance.directTxOctets

       64 bit unsigned wrappable counter."
   ::= {pr1646v2LacpBInQueuesH24PerformanceEntry 117440512}

pr1646v2LacpBInQueuesH24PerformanceQdOcts OBJECT-TYPE
   SYNTAX      Counter64
   MAX-ACCESS  read-only
   STATUS      current
   DESCRIPTION
      "Path: lacpBundle.performance.ifInPriorityQueues.h24Performance.queuedOctets

       64 bit unsigned wrappable counter."
   ::= {pr1646v2LacpBInQueuesH24PerformanceEntry 134217728}

pr1646v2LacpBInQueuesH24PerformanceDropOcts OBJECT-TYPE
   SYNTAX      Counter64
   MAX-ACCESS  read-only
   STATUS      current
   DESCRIPTION
      "Path: lacpBundle.performance.ifInPriorityQueues.h24Performance.droppedOctets

       64 bit unsigned wrappable counter."
   ::= {pr1646v2LacpBInQueuesH24PerformanceEntry 150994944}

pr1646v2LacpBInQueuesH24PerformanceRDropOcts OBJECT-TYPE
   SYNTAX      Counter64
   MAX-ACCESS  read-only
   STATUS      current
   DESCRIPTION
      "Path: lacpBundle.performance.ifInPriorityQueues.h24Performance.redDroppedOctets

       64 bit unsigned wrappable counter."
   ::= {pr1646v2LacpBInQueuesH24PerformanceEntry 218103808}

pr1646v2LacpBInQueuesH24PerformanceCirTxOcts OBJECT-TYPE
   SYNTAX      Counter64
   MAX-ACCESS  read-only
   STATUS      current
   DESCRIPTION
      "Path: lacpBundle.performance.ifInPriorityQueues.h24Performance.cirTxOctets

       64 bit unsigned wrappable counter."
   ::= {pr1646v2LacpBInQueuesH24PerformanceEntry 167772160}

pr1646v2LacpBInQueuesH24PerformanceEirTxOcts OBJECT-TYPE
   SYNTAX      Counter64
   MAX-ACCESS  read-only
   STATUS      current
   DESCRIPTION
      "Path: lacpBundle.performance.ifInPriorityQueues.h24Performance.eirTxOctets

       64 bit unsigned wrappable counter."
   ::= {pr1646v2LacpBInQueuesH24PerformanceEntry 184549376}

pr1646v2LacpBInQueuesH24PerformanceViolTxOcts OBJECT-TYPE
   SYNTAX      Counter64
   MAX-ACCESS  read-only
   STATUS      current
   DESCRIPTION
      "Path: lacpBundle.performance.ifInPriorityQueues.h24Performance.violateTxOctets

       64 bit unsigned wrappable counter."
   ::= {pr1646v2LacpBInQueuesH24PerformanceEntry 318767104}

pr1646v2LacpBInQueuesH24PerformanceBandwidth OBJECT-TYPE
   SYNTAX      Integer32
   MAX-ACCESS  read-only
   STATUS      current
   DESCRIPTION
      "Path: lacpBundle.performance.ifInPriorityQueues.h24Performance.bandwidth

       unit name = bps
       formula = 8 * ; 8 /"
   ::= {pr1646v2LacpBInQueuesH24PerformanceEntry 268435456}

pr1646v2LacpBInQueuesD7Performance OBJECT-TYPE
   SYNTAX      SEQUENCE OF Pr1646v2LacpBInQueuesD7PerformanceEntry
   MAX-ACCESS  not-accessible
   STATUS      current
   DESCRIPTION
      ""
   ::= {pr1646v2LacpBInQueues 117440512}

pr1646v2LacpBInQueuesD7PerformanceEntry OBJECT-TYPE
   SYNTAX      Pr1646v2LacpBInQueuesD7PerformanceEntry
   MAX-ACCESS  not-accessible
   STATUS      current
   DESCRIPTION
      ""
   INDEX      { pr1646v2LacpBInQueuesD7PerformanceGlobalIx,
                pr1646v2LacpBInQueuesTableIx,
                pr1646v2LacpBInQueuesD7PerformanceTableIx }
   ::= {pr1646v2LacpBInQueuesD7Performance 1}

Pr1646v2LacpBInQueuesD7PerformanceEntry ::=
   SEQUENCE
      {
      pr1646v2LacpBInQueuesD7PerformanceGlobalIx
         GlobalIndex,
      pr1646v2LacpBInQueuesD7PerformanceTableIx
         TableIndex,
      pr1646v2LacpBInQueuesD7PerformanceSysUpTime
         TimeTicks,
      pr1646v2LacpBInQueuesD7PerformanceTotPkts
         Counter64,
      pr1646v2LacpBInQueuesD7PerformanceDirTxPkts
         Counter64,
      pr1646v2LacpBInQueuesD7PerformanceQdPkts
         Counter64,
      pr1646v2LacpBInQueuesD7PerformanceDropPkts
         Counter64,
      pr1646v2LacpBInQueuesD7PerformanceRDropPkts
         Counter64,
      pr1646v2LacpBInQueuesD7PerformanceCirTxPkts
         Counter64,
      pr1646v2LacpBInQueuesD7PerformanceEirTxPkts
         Counter64,
      pr1646v2LacpBInQueuesD7PerformanceViolTxPkts
         Counter64,
      pr1646v2LacpBInQueuesD7PerformanceTotOcts
         Counter64,
      pr1646v2LacpBInQueuesD7PerformanceDirTxOcts
         Counter64,
      pr1646v2LacpBInQueuesD7PerformanceQdOcts
         Counter64,
      pr1646v2LacpBInQueuesD7PerformanceDropOcts
         Counter64,
      pr1646v2LacpBInQueuesD7PerformanceRDropOcts
         Counter64,
      pr1646v2LacpBInQueuesD7PerformanceCirTxOcts
         Counter64,
      pr1646v2LacpBInQueuesD7PerformanceEirTxOcts
         Counter64,
      pr1646v2LacpBInQueuesD7PerformanceViolTxOcts
         Counter64,
      pr1646v2LacpBInQueuesD7PerformanceBandwidth
         Integer32
      }

pr1646v2LacpBInQueuesD7PerformanceGlobalIx OBJECT-TYPE
   SYNTAX      GlobalIndex
   MAX-ACCESS  not-accessible
   STATUS      current
   DESCRIPTION
      "The value of the tlsCntTreeGlobalIndex of the MANAGED OBJECT."
   ::= {pr1646v2LacpBInQueuesD7PerformanceEntry 10}

pr1646v2LacpBInQueuesD7PerformanceTableIx OBJECT-TYPE
   SYNTAX      TableIndex
   MAX-ACCESS  not-accessible
   STATUS      current
   DESCRIPTION
      ""
   ::= {pr1646v2LacpBInQueuesD7PerformanceEntry 11}

pr1646v2LacpBInQueuesD7PerformanceSysUpTime OBJECT-TYPE
   SYNTAX      TimeTicks
   MAX-ACCESS  read-only
   STATUS      current
   DESCRIPTION
      "Path: lacpBundle.performance.ifInPriorityQueues.d7Performance.sysUpTime

       Time in centi-second."
   ::= {pr1646v2LacpBInQueuesD7PerformanceEntry 16777216}

pr1646v2LacpBInQueuesD7PerformanceTotPkts OBJECT-TYPE
   SYNTAX      Counter64
   MAX-ACCESS  read-only
   STATUS      current
   DESCRIPTION
      "Path: lacpBundle.performance.ifInPriorityQueues.d7Performance.totalPkts

       64 bit unsigned wrappable counter."
   ::= {pr1646v2LacpBInQueuesD7PerformanceEntry 234881024}

pr1646v2LacpBInQueuesD7PerformanceDirTxPkts OBJECT-TYPE
   SYNTAX      Counter64
   MAX-ACCESS  read-only
   STATUS      current
   DESCRIPTION
      "Path: lacpBundle.performance.ifInPriorityQueues.d7Performance.directTxPkts

       64 bit unsigned wrappable counter."
   ::= {pr1646v2LacpBInQueuesD7PerformanceEntry 33554432}

pr1646v2LacpBInQueuesD7PerformanceQdPkts OBJECT-TYPE
   SYNTAX      Counter64
   MAX-ACCESS  read-only
   STATUS      current
   DESCRIPTION
      "Path: lacpBundle.performance.ifInPriorityQueues.d7Performance.queuedPkts

       64 bit unsigned wrappable counter."
   ::= {pr1646v2LacpBInQueuesD7PerformanceEntry 50331648}

pr1646v2LacpBInQueuesD7PerformanceDropPkts OBJECT-TYPE
   SYNTAX      Counter64
   MAX-ACCESS  read-only
   STATUS      current
   DESCRIPTION
      "Path: lacpBundle.performance.ifInPriorityQueues.d7Performance.droppedPkts

       64 bit unsigned wrappable counter."
   ::= {pr1646v2LacpBInQueuesD7PerformanceEntry 67108864}

pr1646v2LacpBInQueuesD7PerformanceRDropPkts OBJECT-TYPE
   SYNTAX      Counter64
   MAX-ACCESS  read-only
   STATUS      current
   DESCRIPTION
      "Path: lacpBundle.performance.ifInPriorityQueues.d7Performance.redDroppedPkts

       64 bit unsigned wrappable counter."
   ::= {pr1646v2LacpBInQueuesD7PerformanceEntry 201326592}

pr1646v2LacpBInQueuesD7PerformanceCirTxPkts OBJECT-TYPE
   SYNTAX      Counter64
   MAX-ACCESS  read-only
   STATUS      current
   DESCRIPTION
      "Path: lacpBundle.performance.ifInPriorityQueues.d7Performance.cirTxPkts

       64 bit unsigned wrappable counter."
   ::= {pr1646v2LacpBInQueuesD7PerformanceEntry 83886080}

pr1646v2LacpBInQueuesD7PerformanceEirTxPkts OBJECT-TYPE
   SYNTAX      Counter64
   MAX-ACCESS  read-only
   STATUS      current
   DESCRIPTION
      "Path: lacpBundle.performance.ifInPriorityQueues.d7Performance.eirTxPkts

       64 bit unsigned wrappable counter."
   ::= {pr1646v2LacpBInQueuesD7PerformanceEntry 100663296}

pr1646v2LacpBInQueuesD7PerformanceViolTxPkts OBJECT-TYPE
   SYNTAX      Counter64
   MAX-ACCESS  read-only
   STATUS      current
   DESCRIPTION
      "Path: lacpBundle.performance.ifInPriorityQueues.d7Performance.violateTxPkts

       64 bit unsigned wrappable counter."
   ::= {pr1646v2LacpBInQueuesD7PerformanceEntry 301989888}

pr1646v2LacpBInQueuesD7PerformanceTotOcts OBJECT-TYPE
   SYNTAX      Counter64
   MAX-ACCESS  read-only
   STATUS      current
   DESCRIPTION
      "Path: lacpBundle.performance.ifInPriorityQueues.d7Performance.totalOctets

       64 bit unsigned wrappable counter."
   ::= {pr1646v2LacpBInQueuesD7PerformanceEntry 251658240}

pr1646v2LacpBInQueuesD7PerformanceDirTxOcts OBJECT-TYPE
   SYNTAX      Counter64
   MAX-ACCESS  read-only
   STATUS      current
   DESCRIPTION
      "Path: lacpBundle.performance.ifInPriorityQueues.d7Performance.directTxOctets

       64 bit unsigned wrappable counter."
   ::= {pr1646v2LacpBInQueuesD7PerformanceEntry 117440512}

pr1646v2LacpBInQueuesD7PerformanceQdOcts OBJECT-TYPE
   SYNTAX      Counter64
   MAX-ACCESS  read-only
   STATUS      current
   DESCRIPTION
      "Path: lacpBundle.performance.ifInPriorityQueues.d7Performance.queuedOctets

       64 bit unsigned wrappable counter."
   ::= {pr1646v2LacpBInQueuesD7PerformanceEntry 134217728}

pr1646v2LacpBInQueuesD7PerformanceDropOcts OBJECT-TYPE
   SYNTAX      Counter64
   MAX-ACCESS  read-only
   STATUS      current
   DESCRIPTION
      "Path: lacpBundle.performance.ifInPriorityQueues.d7Performance.droppedOctets

       64 bit unsigned wrappable counter."
   ::= {pr1646v2LacpBInQueuesD7PerformanceEntry 150994944}

pr1646v2LacpBInQueuesD7PerformanceRDropOcts OBJECT-TYPE
   SYNTAX      Counter64
   MAX-ACCESS  read-only
   STATUS      current
   DESCRIPTION
      "Path: lacpBundle.performance.ifInPriorityQueues.d7Performance.redDroppedOctets

       64 bit unsigned wrappable counter."
   ::= {pr1646v2LacpBInQueuesD7PerformanceEntry 218103808}

pr1646v2LacpBInQueuesD7PerformanceCirTxOcts OBJECT-TYPE
   SYNTAX      Counter64
   MAX-ACCESS  read-only
   STATUS      current
   DESCRIPTION
      "Path: lacpBundle.performance.ifInPriorityQueues.d7Performance.cirTxOctets

       64 bit unsigned wrappable counter."
   ::= {pr1646v2LacpBInQueuesD7PerformanceEntry 167772160}

pr1646v2LacpBInQueuesD7PerformanceEirTxOcts OBJECT-TYPE
   SYNTAX      Counter64
   MAX-ACCESS  read-only
   STATUS      current
   DESCRIPTION
      "Path: lacpBundle.performance.ifInPriorityQueues.d7Performance.eirTxOctets

       64 bit unsigned wrappable counter."
   ::= {pr1646v2LacpBInQueuesD7PerformanceEntry 184549376}

pr1646v2LacpBInQueuesD7PerformanceViolTxOcts OBJECT-TYPE
   SYNTAX      Counter64
   MAX-ACCESS  read-only
   STATUS      current
   DESCRIPTION
      "Path: lacpBundle.performance.ifInPriorityQueues.d7Performance.violateTxOctets

       64 bit unsigned wrappable counter."
   ::= {pr1646v2LacpBInQueuesD7PerformanceEntry 318767104}

pr1646v2LacpBInQueuesD7PerformanceBandwidth OBJECT-TYPE
   SYNTAX      Integer32
   MAX-ACCESS  read-only
   STATUS      current
   DESCRIPTION
      "Path: lacpBundle.performance.ifInPriorityQueues.d7Performance.bandwidth

       unit name = bps
       formula = 8 * ; 8 /"
   ::= {pr1646v2LacpBInQueuesD7PerformanceEntry 268435456}


pr1646v2LacpBInBandwidth OBJECT IDENTIFIER ::= {pr1646v2LacpB 181}

pr1646v2LacpBInBandwidthSSCTable OBJECT-TYPE
   SYNTAX      SEQUENCE OF Pr1646v2LacpBInBandwidthEntry
   MAX-ACCESS  not-accessible
   STATUS      current
   DESCRIPTION
      "bandwidth"
   ::= {pr1646v2LacpBInBandwidth 1}

pr1646v2LacpBInBandwidthEntry OBJECT-TYPE
   SYNTAX      Pr1646v2LacpBInBandwidthEntry
   MAX-ACCESS  not-accessible
   STATUS      current
   DESCRIPTION
      ""
   INDEX      { pr1646v2LacpBInBandwidthGlobalIx }
   ::= {pr1646v2LacpBInBandwidthSSCTable 1}

Pr1646v2LacpBInBandwidthEntry ::=
   SEQUENCE
      {
      pr1646v2LacpBInBandwidthGlobalIx
         GlobalIndex,
      pr1646v2LacpBInBandwidth15sec
         Integer32,
      pr1646v2LacpBInBandwidth30sec
         Integer32,
      pr1646v2LacpBInBandwidth1min
         Integer32,
      pr1646v2LacpBInBandwidth2min
         Integer32,
      pr1646v2LacpBInBandwidth5min
         Integer32
      }

pr1646v2LacpBInBandwidthGlobalIx OBJECT-TYPE
   SYNTAX      GlobalIndex
   MAX-ACCESS  not-accessible
   STATUS      current
   DESCRIPTION
      "The value of the tlsCntTreeGlobalIndex of the MANAGED OBJECT."
   ::= {pr1646v2LacpBInBandwidthEntry 10}

pr1646v2LacpBInBandwidth15sec OBJECT-TYPE
   SYNTAX      Integer32
   MAX-ACCESS  read-only
   STATUS      current
   DESCRIPTION
      "Path: lacpBundle.performance.ifInBandwidth.15sec

       unit name = bps
       formula = 8 * ; 8 /"
   ::= {pr1646v2LacpBInBandwidthEntry 83886080}

pr1646v2LacpBInBandwidth30sec OBJECT-TYPE
   SYNTAX      Integer32
   MAX-ACCESS  read-only
   STATUS      current
   DESCRIPTION
      "Path: lacpBundle.performance.ifInBandwidth.30sec

       unit name = bps
       formula = 8 * ; 8 /"
   ::= {pr1646v2LacpBInBandwidthEntry 167772160}

pr1646v2LacpBInBandwidth1min OBJECT-TYPE
   SYNTAX      Integer32
   MAX-ACCESS  read-only
   STATUS      current
   DESCRIPTION
      "Path: lacpBundle.performance.ifInBandwidth.1min

       unit name = bps
       formula = 8 * ; 8 /"
   ::= {pr1646v2LacpBInBandwidthEntry 335544320}

pr1646v2LacpBInBandwidth2min OBJECT-TYPE
   SYNTAX      Integer32
   MAX-ACCESS  read-only
   STATUS      current
   DESCRIPTION
      "Path: lacpBundle.performance.ifInBandwidth.2min

       unit name = bps
       formula = 8 * ; 8 /"
   ::= {pr1646v2LacpBInBandwidthEntry 671088640}

pr1646v2LacpBInBandwidth5min OBJECT-TYPE
   SYNTAX      Integer32
   MAX-ACCESS  read-only
   STATUS      current
   DESCRIPTION
      "Path: lacpBundle.performance.ifInBandwidth.5min

       unit name = bps
       formula = 8 * ; 8 /"
   ::= {pr1646v2LacpBInBandwidthEntry 1677721600}


pr1646v2LacpBOutOctets OBJECT IDENTIFIER ::= {pr1646v2LacpB 115}

pr1646v2LacpBOutOctetsTable OBJECT-TYPE
   SYNTAX      SEQUENCE OF Pr1646v2LacpBOutOctetsEntry
   MAX-ACCESS  not-accessible
   STATUS      current
   DESCRIPTION
      "ifOutOctets"
   ::= {pr1646v2LacpBOutOctets 1}

pr1646v2LacpBOutOctetsEntry OBJECT-TYPE
   SYNTAX      Pr1646v2LacpBOutOctetsEntry
   MAX-ACCESS  not-accessible
   STATUS      current
   DESCRIPTION
      ""
   INDEX      { pr1646v2LacpBOutOctetsGlobalIx }
   ::= {pr1646v2LacpBOutOctetsTable 1}

Pr1646v2LacpBOutOctetsEntry ::=
   SEQUENCE
      {
      pr1646v2LacpBOutOctetsGlobalIx
         GlobalIndex,
      pr1646v2LacpBOutOctetsValue
         Counter64
      }

pr1646v2LacpBOutOctetsGlobalIx OBJECT-TYPE
   SYNTAX      GlobalIndex
   MAX-ACCESS  not-accessible
   STATUS      current
   DESCRIPTION
      "The value of the tlsCntTreeGlobalIndex of the MANAGED OBJECT."
   ::= {pr1646v2LacpBOutOctetsEntry 10}

pr1646v2LacpBOutOctetsValue OBJECT-TYPE
   SYNTAX      Counter64
   MAX-ACCESS  read-only
   STATUS      current
   DESCRIPTION
      "Path: lacpBundle.performance.ifOutOctets

       64 bit unsigned wrappable counter."
   ::= {pr1646v2LacpBOutOctetsEntry 2147483648}


pr1646v2LacpBOutUcastPkts OBJECT IDENTIFIER ::= {pr1646v2LacpB 116}

pr1646v2LacpBOutUcastPktsTable OBJECT-TYPE
   SYNTAX      SEQUENCE OF Pr1646v2LacpBOutUcastPktsEntry
   MAX-ACCESS  not-accessible
   STATUS      current
   DESCRIPTION
      "ifOutUcastPkts"
   ::= {pr1646v2LacpBOutUcastPkts 1}

pr1646v2LacpBOutUcastPktsEntry OBJECT-TYPE
   SYNTAX      Pr1646v2LacpBOutUcastPktsEntry
   MAX-ACCESS  not-accessible
   STATUS      current
   DESCRIPTION
      ""
   INDEX      { pr1646v2LacpBOutUcastPktsGlobalIx }
   ::= {pr1646v2LacpBOutUcastPktsTable 1}

Pr1646v2LacpBOutUcastPktsEntry ::=
   SEQUENCE
      {
      pr1646v2LacpBOutUcastPktsGlobalIx
         GlobalIndex,
      pr1646v2LacpBOutUcastPktsValue
         Counter64
      }

pr1646v2LacpBOutUcastPktsGlobalIx OBJECT-TYPE
   SYNTAX      GlobalIndex
   MAX-ACCESS  not-accessible
   STATUS      current
   DESCRIPTION
      "The value of the tlsCntTreeGlobalIndex of the MANAGED OBJECT."
   ::= {pr1646v2LacpBOutUcastPktsEntry 10}

pr1646v2LacpBOutUcastPktsValue OBJECT-TYPE
   SYNTAX      Counter64
   MAX-ACCESS  read-only
   STATUS      current
   DESCRIPTION
      "Path: lacpBundle.performance.ifOutUcastPkts

       64 bit unsigned wrappable counter."
   ::= {pr1646v2LacpBOutUcastPktsEntry 2147483648}


pr1646v2LacpBOutNUcastPkts OBJECT IDENTIFIER ::= {pr1646v2LacpB 117}

pr1646v2LacpBOutNUcastPktsTable OBJECT-TYPE
   SYNTAX      SEQUENCE OF Pr1646v2LacpBOutNUcastPktsEntry
   MAX-ACCESS  not-accessible
   STATUS      current
   DESCRIPTION
      "ifOutNUcastPkts"
   ::= {pr1646v2LacpBOutNUcastPkts 1}

pr1646v2LacpBOutNUcastPktsEntry OBJECT-TYPE
   SYNTAX      Pr1646v2LacpBOutNUcastPktsEntry
   MAX-ACCESS  not-accessible
   STATUS      current
   DESCRIPTION
      ""
   INDEX      { pr1646v2LacpBOutNUcastPktsGlobalIx }
   ::= {pr1646v2LacpBOutNUcastPktsTable 1}

Pr1646v2LacpBOutNUcastPktsEntry ::=
   SEQUENCE
      {
      pr1646v2LacpBOutNUcastPktsGlobalIx
         GlobalIndex,
      pr1646v2LacpBOutNUcastPktsValue
         Counter64
      }

pr1646v2LacpBOutNUcastPktsGlobalIx OBJECT-TYPE
   SYNTAX      GlobalIndex
   MAX-ACCESS  not-accessible
   STATUS      current
   DESCRIPTION
      "The value of the tlsCntTreeGlobalIndex of the MANAGED OBJECT."
   ::= {pr1646v2LacpBOutNUcastPktsEntry 10}

pr1646v2LacpBOutNUcastPktsValue OBJECT-TYPE
   SYNTAX      Counter64
   MAX-ACCESS  read-only
   STATUS      current
   DESCRIPTION
      "Path: lacpBundle.performance.ifOutNUcastPkts

       64 bit unsigned wrappable counter."
   ::= {pr1646v2LacpBOutNUcastPktsEntry 2147483648}


pr1646v2LacpBOutBcastPkts OBJECT IDENTIFIER ::= {pr1646v2LacpB 217}

pr1646v2LacpBOutBcastPktsTable OBJECT-TYPE
   SYNTAX      SEQUENCE OF Pr1646v2LacpBOutBcastPktsEntry
   MAX-ACCESS  not-accessible
   STATUS      current
   DESCRIPTION
      "ifOutBcastPkts"
   ::= {pr1646v2LacpBOutBcastPkts 1}

pr1646v2LacpBOutBcastPktsEntry OBJECT-TYPE
   SYNTAX      Pr1646v2LacpBOutBcastPktsEntry
   MAX-ACCESS  not-accessible
   STATUS      current
   DESCRIPTION
      ""
   INDEX      { pr1646v2LacpBOutBcastPktsGlobalIx }
   ::= {pr1646v2LacpBOutBcastPktsTable 1}

Pr1646v2LacpBOutBcastPktsEntry ::=
   SEQUENCE
      {
      pr1646v2LacpBOutBcastPktsGlobalIx
         GlobalIndex,
      pr1646v2LacpBOutBcastPktsValue
         Counter64
      }

pr1646v2LacpBOutBcastPktsGlobalIx OBJECT-TYPE
   SYNTAX      GlobalIndex
   MAX-ACCESS  not-accessible
   STATUS      current
   DESCRIPTION
      "The value of the tlsCntTreeGlobalIndex of the MANAGED OBJECT."
   ::= {pr1646v2LacpBOutBcastPktsEntry 10}

pr1646v2LacpBOutBcastPktsValue OBJECT-TYPE
   SYNTAX      Counter64
   MAX-ACCESS  read-only
   STATUS      current
   DESCRIPTION
      "Path: lacpBundle.performance.ifOutBcastPkts

       64 bit unsigned wrappable counter."
   ::= {pr1646v2LacpBOutBcastPktsEntry 2147483648}


pr1646v2LacpBOutMcastPkts OBJECT IDENTIFIER ::= {pr1646v2LacpB 227}

pr1646v2LacpBOutMcastPktsTable OBJECT-TYPE
   SYNTAX      SEQUENCE OF Pr1646v2LacpBOutMcastPktsEntry
   MAX-ACCESS  not-accessible
   STATUS      current
   DESCRIPTION
      "ifOutMcastPkts"
   ::= {pr1646v2LacpBOutMcastPkts 1}

pr1646v2LacpBOutMcastPktsEntry OBJECT-TYPE
   SYNTAX      Pr1646v2LacpBOutMcastPktsEntry
   MAX-ACCESS  not-accessible
   STATUS      current
   DESCRIPTION
      ""
   INDEX      { pr1646v2LacpBOutMcastPktsGlobalIx }
   ::= {pr1646v2LacpBOutMcastPktsTable 1}

Pr1646v2LacpBOutMcastPktsEntry ::=
   SEQUENCE
      {
      pr1646v2LacpBOutMcastPktsGlobalIx
         GlobalIndex,
      pr1646v2LacpBOutMcastPktsValue
         Counter64
      }

pr1646v2LacpBOutMcastPktsGlobalIx OBJECT-TYPE
   SYNTAX      GlobalIndex
   MAX-ACCESS  not-accessible
   STATUS      current
   DESCRIPTION
      "The value of the tlsCntTreeGlobalIndex of the MANAGED OBJECT."
   ::= {pr1646v2LacpBOutMcastPktsEntry 10}

pr1646v2LacpBOutMcastPktsValue OBJECT-TYPE
   SYNTAX      Counter64
   MAX-ACCESS  read-only
   STATUS      current
   DESCRIPTION
      "Path: lacpBundle.performance.ifOutMcastPkts

       64 bit unsigned wrappable counter."
   ::= {pr1646v2LacpBOutMcastPktsEntry 2147483648}


pr1646v2LacpBOutDiscards OBJECT IDENTIFIER ::= {pr1646v2LacpB 118}

pr1646v2LacpBOutDiscardsTable OBJECT-TYPE
   SYNTAX      SEQUENCE OF Pr1646v2LacpBOutDiscardsEntry
   MAX-ACCESS  not-accessible
   STATUS      current
   DESCRIPTION
      "ifOutDiscards"
   ::= {pr1646v2LacpBOutDiscards 1}

pr1646v2LacpBOutDiscardsEntry OBJECT-TYPE
   SYNTAX      Pr1646v2LacpBOutDiscardsEntry
   MAX-ACCESS  not-accessible
   STATUS      current
   DESCRIPTION
      ""
   INDEX      { pr1646v2LacpBOutDiscardsGlobalIx }
   ::= {pr1646v2LacpBOutDiscardsTable 1}

Pr1646v2LacpBOutDiscardsEntry ::=
   SEQUENCE
      {
      pr1646v2LacpBOutDiscardsGlobalIx
         GlobalIndex,
      pr1646v2LacpBOutDiscardsValue
         Counter64
      }

pr1646v2LacpBOutDiscardsGlobalIx OBJECT-TYPE
   SYNTAX      GlobalIndex
   MAX-ACCESS  not-accessible
   STATUS      current
   DESCRIPTION
      "The value of the tlsCntTreeGlobalIndex of the MANAGED OBJECT."
   ::= {pr1646v2LacpBOutDiscardsEntry 10}

pr1646v2LacpBOutDiscardsValue OBJECT-TYPE
   SYNTAX      Counter64
   MAX-ACCESS  read-only
   STATUS      current
   DESCRIPTION
      "Path: lacpBundle.performance.ifOutDiscards

       64 bit unsigned wrappable counter."
   ::= {pr1646v2LacpBOutDiscardsEntry 2147483648}


pr1646v2LacpBOutErrors OBJECT IDENTIFIER ::= {pr1646v2LacpB 119}

pr1646v2LacpBOutErrorsTable OBJECT-TYPE
   SYNTAX      SEQUENCE OF Pr1646v2LacpBOutErrorsEntry
   MAX-ACCESS  not-accessible
   STATUS      current
   DESCRIPTION
      "ifOutErrors"
   ::= {pr1646v2LacpBOutErrors 1}

pr1646v2LacpBOutErrorsEntry OBJECT-TYPE
   SYNTAX      Pr1646v2LacpBOutErrorsEntry
   MAX-ACCESS  not-accessible
   STATUS      current
   DESCRIPTION
      ""
   INDEX      { pr1646v2LacpBOutErrorsGlobalIx }
   ::= {pr1646v2LacpBOutErrorsTable 1}

Pr1646v2LacpBOutErrorsEntry ::=
   SEQUENCE
      {
      pr1646v2LacpBOutErrorsGlobalIx
         GlobalIndex,
      pr1646v2LacpBOutErrorsValue
         Counter64
      }

pr1646v2LacpBOutErrorsGlobalIx OBJECT-TYPE
   SYNTAX      GlobalIndex
   MAX-ACCESS  not-accessible
   STATUS      current
   DESCRIPTION
      "The value of the tlsCntTreeGlobalIndex of the MANAGED OBJECT."
   ::= {pr1646v2LacpBOutErrorsEntry 10}

pr1646v2LacpBOutErrorsValue OBJECT-TYPE
   SYNTAX      Counter64
   MAX-ACCESS  read-only
   STATUS      current
   DESCRIPTION
      "Path: lacpBundle.performance.ifOutErrors

       64 bit unsigned wrappable counter."
   ::= {pr1646v2LacpBOutErrorsEntry 2147483648}


pr1646v2LacpBOutQLen OBJECT IDENTIFIER ::= {pr1646v2LacpB 120}

pr1646v2LacpBOutQLenTable OBJECT-TYPE
   SYNTAX      SEQUENCE OF Pr1646v2LacpBOutQLenEntry
   MAX-ACCESS  not-accessible
   STATUS      current
   DESCRIPTION
      "ifOutQLen"
   ::= {pr1646v2LacpBOutQLen 1}

pr1646v2LacpBOutQLenEntry OBJECT-TYPE
   SYNTAX      Pr1646v2LacpBOutQLenEntry
   MAX-ACCESS  not-accessible
   STATUS      current
   DESCRIPTION
      ""
   INDEX      { pr1646v2LacpBOutQLenGlobalIx }
   ::= {pr1646v2LacpBOutQLenTable 1}

Pr1646v2LacpBOutQLenEntry ::=
   SEQUENCE
      {
      pr1646v2LacpBOutQLenGlobalIx
         GlobalIndex,
      pr1646v2LacpBOutQLenValue
         Gauge32
      }

pr1646v2LacpBOutQLenGlobalIx OBJECT-TYPE
   SYNTAX      GlobalIndex
   MAX-ACCESS  not-accessible
   STATUS      current
   DESCRIPTION
      "The value of the tlsCntTreeGlobalIndex of the MANAGED OBJECT."
   ::= {pr1646v2LacpBOutQLenEntry 10}

pr1646v2LacpBOutQLenValue OBJECT-TYPE
   SYNTAX      Gauge32
   MAX-ACCESS  read-only
   STATUS      current
   DESCRIPTION
      "Path: lacpBundle.performance.ifOutQLen

       32 bit unsigned gauge value."
   ::= {pr1646v2LacpBOutQLenEntry 2147483648}


pr1646v2LacpBOutDropEx OBJECT IDENTIFIER ::= {pr1646v2LacpB 127}

pr1646v2LacpBOutDropExTable OBJECT-TYPE
   SYNTAX      SEQUENCE OF Pr1646v2LacpBOutDropExEntry
   MAX-ACCESS  not-accessible
   STATUS      current
   DESCRIPTION
      "ifOutDiscards"
   ::= {pr1646v2LacpBOutDropEx 1}

pr1646v2LacpBOutDropExEntry OBJECT-TYPE
   SYNTAX      Pr1646v2LacpBOutDropExEntry
   MAX-ACCESS  not-accessible
   STATUS      current
   DESCRIPTION
      ""
   INDEX      { pr1646v2LacpBOutDropExGlobalIx }
   ::= {pr1646v2LacpBOutDropExTable 1}

Pr1646v2LacpBOutDropExEntry ::=
   SEQUENCE
      {
      pr1646v2LacpBOutDropExGlobalIx
         GlobalIndex,
      pr1646v2LacpBOutDropExValue
         Counter64
      }

pr1646v2LacpBOutDropExGlobalIx OBJECT-TYPE
   SYNTAX      GlobalIndex
   MAX-ACCESS  not-accessible
   STATUS      current
   DESCRIPTION
      "The value of the tlsCntTreeGlobalIndex of the MANAGED OBJECT."
   ::= {pr1646v2LacpBOutDropExEntry 10}

pr1646v2LacpBOutDropExValue OBJECT-TYPE
   SYNTAX      Counter64
   MAX-ACCESS  read-only
   STATUS      current
   DESCRIPTION
      "Path: lacpBundle.performance.ifOutDropLevelExceeded

       64 bit unsigned wrappable counter."
   ::= {pr1646v2LacpBOutDropExEntry 2147483648}


pr1646v2LacpBOutDropNoArp OBJECT IDENTIFIER ::= {pr1646v2LacpB 134}

pr1646v2LacpBOutDropNoArpTable OBJECT-TYPE
   SYNTAX      SEQUENCE OF Pr1646v2LacpBOutDropNoArpEntry
   MAX-ACCESS  not-accessible
   STATUS      current
   DESCRIPTION
      "ifOutDiscards"
   ::= {pr1646v2LacpBOutDropNoArp 1}

pr1646v2LacpBOutDropNoArpEntry OBJECT-TYPE
   SYNTAX      Pr1646v2LacpBOutDropNoArpEntry
   MAX-ACCESS  not-accessible
   STATUS      current
   DESCRIPTION
      ""
   INDEX      { pr1646v2LacpBOutDropNoArpGlobalIx }
   ::= {pr1646v2LacpBOutDropNoArpTable 1}

Pr1646v2LacpBOutDropNoArpEntry ::=
   SEQUENCE
      {
      pr1646v2LacpBOutDropNoArpGlobalIx
         GlobalIndex,
      pr1646v2LacpBOutDropNoArpValue
         Counter64
      }

pr1646v2LacpBOutDropNoArpGlobalIx OBJECT-TYPE
   SYNTAX      GlobalIndex
   MAX-ACCESS  not-accessible
   STATUS      current
   DESCRIPTION
      "The value of the tlsCntTreeGlobalIndex of the MANAGED OBJECT."
   ::= {pr1646v2LacpBOutDropNoArpEntry 10}

pr1646v2LacpBOutDropNoArpValue OBJECT-TYPE
   SYNTAX      Counter64
   MAX-ACCESS  read-only
   STATUS      current
   DESCRIPTION
      "Path: lacpBundle.performance.ifOutDiscardsNoArp

       64 bit unsigned wrappable counter."
   ::= {pr1646v2LacpBOutDropNoArpEntry 2147483648}


pr1646v2LacpBOutDropFilter OBJECT IDENTIFIER ::= {pr1646v2LacpB 138}

pr1646v2LacpBOutDropFilterTable OBJECT-TYPE
   SYNTAX      SEQUENCE OF Pr1646v2LacpBOutDropFilterEntry
   MAX-ACCESS  not-accessible
   STATUS      current
   DESCRIPTION
      "ifOutDiscards"
   ::= {pr1646v2LacpBOutDropFilter 1}

pr1646v2LacpBOutDropFilterEntry OBJECT-TYPE
   SYNTAX      Pr1646v2LacpBOutDropFilterEntry
   MAX-ACCESS  not-accessible
   STATUS      current
   DESCRIPTION
      ""
   INDEX      { pr1646v2LacpBOutDropFilterGlobalIx }
   ::= {pr1646v2LacpBOutDropFilterTable 1}

Pr1646v2LacpBOutDropFilterEntry ::=
   SEQUENCE
      {
      pr1646v2LacpBOutDropFilterGlobalIx
         GlobalIndex,
      pr1646v2LacpBOutDropFilterValue
         Counter64
      }

pr1646v2LacpBOutDropFilterGlobalIx OBJECT-TYPE
   SYNTAX      GlobalIndex
   MAX-ACCESS  not-accessible
   STATUS      current
   DESCRIPTION
      "The value of the tlsCntTreeGlobalIndex of the MANAGED OBJECT."
   ::= {pr1646v2LacpBOutDropFilterEntry 10}

pr1646v2LacpBOutDropFilterValue OBJECT-TYPE
   SYNTAX      Counter64
   MAX-ACCESS  read-only
   STATUS      current
   DESCRIPTION
      "Path: lacpBundle.performance.ifOutDiscardsFilter

       64 bit unsigned wrappable counter."
   ::= {pr1646v2LacpBOutDropFilterEntry 2147483648}


pr1646v2LacpBOutQueues OBJECT IDENTIFIER ::= {pr1646v2LacpB 129}

pr1646v2LacpBOutQueuesSSCTable OBJECT-TYPE
   SYNTAX      SEQUENCE OF Pr1646v2LacpBOutQueuesEntry
   MAX-ACCESS  not-accessible
   STATUS      current
   DESCRIPTION
      "Queue Lengths"
   ::= {pr1646v2LacpBOutQueues 1}

pr1646v2LacpBOutQueuesEntry OBJECT-TYPE
   SYNTAX      Pr1646v2LacpBOutQueuesEntry
   MAX-ACCESS  not-accessible
   STATUS      current
   DESCRIPTION
      ""
   INDEX      { pr1646v2LacpBOutQueuesGlobalIx,
                pr1646v2LacpBOutQueuesTableIx }
   ::= {pr1646v2LacpBOutQueuesSSCTable 1}

Pr1646v2LacpBOutQueuesEntry ::=
   SEQUENCE
      {
      pr1646v2LacpBOutQueuesGlobalIx
         GlobalIndex,
      pr1646v2LacpBOutQueuesTableIx
         TableIndex,
      pr1646v2LacpBOutQueuesName
         INTEGER,
      pr1646v2LacpBOutQueuesLength
         Integer32,
      pr1646v2LacpBOutQueuesOctetLength
         Integer32,
      pr1646v2LacpBOutQueuesRedLength
         Integer32,
      pr1646v2LacpBOutQueuesPacketsTotal
         Counter64,
      pr1646v2LacpBOutQueuesPacketsDirectTx
         Counter64,
      pr1646v2LacpBOutQueuesPacketsQueued
         Counter64,
      pr1646v2LacpBOutQueuesPacketsDropped
         Counter64,
      pr1646v2LacpBOutQueuesPacketsRedDropped
         Counter64,
      pr1646v2LacpBOutQueuesPacketsCirTx
         Counter64,
      pr1646v2LacpBOutQueuesPacketsEirTx
         Counter64,
      pr1646v2LacpBOutQueuesPacketsViolateTx
         Counter64,
      pr1646v2LacpBOutQueuesOctetsTotal
         Counter64,
      pr1646v2LacpBOutQueuesOctetsDirectTx
         Counter64,
      pr1646v2LacpBOutQueuesOctetsQueued
         Counter64,
      pr1646v2LacpBOutQueuesOctetsDropped
         Counter64,
      pr1646v2LacpBOutQueuesOctetsRedDropped
         Counter64,
      pr1646v2LacpBOutQueuesOctetsCirTx
         Counter64,
      pr1646v2LacpBOutQueuesOctetsEirTx
         Counter64,
      pr1646v2LacpBOutQueuesOctetsViolateTx
         Counter64,
      pr1646v2LacpBOutQueuesOctetsBandwidth15sec
         Integer32,
      pr1646v2LacpBOutQueuesOctetsBandwidth30sec
         Integer32,
      pr1646v2LacpBOutQueuesOctetsBandwidth1min
         Integer32,
      pr1646v2LacpBOutQueuesOctetsBandwidth2min
         Integer32,
      pr1646v2LacpBOutQueuesOctetsBandwidth5min
         Integer32
      }

pr1646v2LacpBOutQueuesGlobalIx OBJECT-TYPE
   SYNTAX      GlobalIndex
   MAX-ACCESS  not-accessible
   STATUS      current
   DESCRIPTION
      "The value of the tlsCntTreeGlobalIndex of the MANAGED OBJECT."
   ::= {pr1646v2LacpBOutQueuesEntry 10}

pr1646v2LacpBOutQueuesTableIx OBJECT-TYPE
   SYNTAX      TableIndex
   MAX-ACCESS  not-accessible
   STATUS      current
   DESCRIPTION
      ""
   ::= {pr1646v2LacpBOutQueuesEntry 11}

pr1646v2LacpBOutQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: lacpBundle.performance.ifOutPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2LacpBOutQueuesEntry 16777216}

pr1646v2LacpBOutQueuesLength OBJECT-TYPE
   SYNTAX      Integer32
   MAX-ACCESS  read-only
   STATUS      current
   DESCRIPTION
      "Path: lacpBundle.performance.ifOutPriorityQueues.length"
   ::= {pr1646v2LacpBOutQueuesEntry 33554432}

pr1646v2LacpBOutQueuesOctetLength OBJECT-TYPE
   SYNTAX      Integer32
   MAX-ACCESS  read-only
   STATUS      current
   DESCRIPTION
      "Path: lacpBundle.performance.ifOutPriorityQueues.octetLength"
   ::= {pr1646v2LacpBOutQueuesEntry 150994944}

pr1646v2LacpBOutQueuesRedLength OBJECT-TYPE
   SYNTAX      Integer32
   MAX-ACCESS  read-only
   STATUS      current
   DESCRIPTION
      "Path: lacpBundle.performance.ifOutPriorityQueues.redLength"
   ::= {pr1646v2LacpBOutQueuesEntry 134217728}

pr1646v2LacpBOutQueuesPacketsTotal OBJECT-TYPE
   SYNTAX      Counter64
   MAX-ACCESS  read-only
   STATUS      current
   DESCRIPTION
      "Path: lacpBundle.performance.ifOutPriorityQueues.packets.total

       64 bit unsigned wrappable counter."
   ::= {pr1646v2LacpBOutQueuesEntry 50790400}

pr1646v2LacpBOutQueuesPacketsDirectTx OBJECT-TYPE
   SYNTAX      Counter64
   MAX-ACCESS  read-only
   STATUS      current
   DESCRIPTION
      "Path: lacpBundle.performance.ifOutPriorityQueues.packets.directTx

       64 bit unsigned wrappable counter."
   ::= {pr1646v2LacpBOutQueuesEntry 50397184}

pr1646v2LacpBOutQueuesPacketsQueued OBJECT-TYPE
   SYNTAX      Counter64
   MAX-ACCESS  read-only
   STATUS      current
   DESCRIPTION
      "Path: lacpBundle.performance.ifOutPriorityQueues.packets.queued

       64 bit unsigned wrappable counter."
   ::= {pr1646v2LacpBOutQueuesEntry 50462720}

pr1646v2LacpBOutQueuesPacketsDropped OBJECT-TYPE
   SYNTAX      Counter64
   MAX-ACCESS  read-only
   STATUS      current
   DESCRIPTION
      "Path: lacpBundle.performance.ifOutPriorityQueues.packets.dropped

       64 bit unsigned wrappable counter."
   ::= {pr1646v2LacpBOutQueuesEntry 50528256}

pr1646v2LacpBOutQueuesPacketsRedDropped OBJECT-TYPE
   SYNTAX      Counter64
   MAX-ACCESS  read-only
   STATUS      current
   DESCRIPTION
      "Path: lacpBundle.performance.ifOutPriorityQueues.packets.redDropped

       64 bit unsigned wrappable counter."
   ::= {pr1646v2LacpBOutQueuesEntry 50724864}

pr1646v2LacpBOutQueuesPacketsCirTx OBJECT-TYPE
   SYNTAX      Counter64
   MAX-ACCESS  read-only
   STATUS      current
   DESCRIPTION
      "Path: lacpBundle.performance.ifOutPriorityQueues.packets.cirTx

       64 bit unsigned wrappable counter."
   ::= {pr1646v2LacpBOutQueuesEntry 50593792}

pr1646v2LacpBOutQueuesPacketsEirTx OBJECT-TYPE
   SYNTAX      Counter64
   MAX-ACCESS  read-only
   STATUS      current
   DESCRIPTION
      "Path: lacpBundle.performance.ifOutPriorityQueues.packets.eirTx

       64 bit unsigned wrappable counter."
   ::= {pr1646v2LacpBOutQueuesEntry 50659328}

pr1646v2LacpBOutQueuesPacketsViolateTx OBJECT-TYPE
   SYNTAX      Counter64
   MAX-ACCESS  read-only
   STATUS      current
   DESCRIPTION
      "Path: lacpBundle.performance.ifOutPriorityQueues.packets.violateTx

       64 bit unsigned wrappable counter."
   ::= {pr1646v2LacpBOutQueuesEntry 50855936}

pr1646v2LacpBOutQueuesOctetsTotal OBJECT-TYPE
   SYNTAX      Counter64
   MAX-ACCESS  read-only
   STATUS      current
   DESCRIPTION
      "Path: lacpBundle.performance.ifOutPriorityQueues.octets.total

       64 bit unsigned wrappable counter."
   ::= {pr1646v2LacpBOutQueuesEntry 67567616}

pr1646v2LacpBOutQueuesOctetsDirectTx OBJECT-TYPE
   SYNTAX      Counter64
   MAX-ACCESS  read-only
   STATUS      current
   DESCRIPTION
      "Path: lacpBundle.performance.ifOutPriorityQueues.octets.directTx

       64 bit unsigned wrappable counter."
   ::= {pr1646v2LacpBOutQueuesEntry 67174400}

pr1646v2LacpBOutQueuesOctetsQueued OBJECT-TYPE
   SYNTAX      Counter64
   MAX-ACCESS  read-only
   STATUS      current
   DESCRIPTION
      "Path: lacpBundle.performance.ifOutPriorityQueues.octets.queued

       64 bit unsigned wrappable counter."
   ::= {pr1646v2LacpBOutQueuesEntry 67239936}

pr1646v2LacpBOutQueuesOctetsDropped OBJECT-TYPE
   SYNTAX      Counter64
   MAX-ACCESS  read-only
   STATUS      current
   DESCRIPTION
      "Path: lacpBundle.performance.ifOutPriorityQueues.octets.dropped

       64 bit unsigned wrappable counter."
   ::= {pr1646v2LacpBOutQueuesEntry 67305472}

pr1646v2LacpBOutQueuesOctetsRedDropped OBJECT-TYPE
   SYNTAX      Counter64
   MAX-ACCESS  read-only
   STATUS      current
   DESCRIPTION
      "Path: lacpBundle.performance.ifOutPriorityQueues.octets.redDropped

       64 bit unsigned wrappable counter."
   ::= {pr1646v2LacpBOutQueuesEntry 67502080}

pr1646v2LacpBOutQueuesOctetsCirTx OBJECT-TYPE
   SYNTAX      Counter64
   MAX-ACCESS  read-only
   STATUS      current
   DESCRIPTION
      "Path: lacpBundle.performance.ifOutPriorityQueues.octets.cirTx

       64 bit unsigned wrappable counter."
   ::= {pr1646v2LacpBOutQueuesEntry 67371008}

pr1646v2LacpBOutQueuesOctetsEirTx OBJECT-TYPE
   SYNTAX      Counter64
   MAX-ACCESS  read-only
   STATUS      current
   DESCRIPTION
      "Path: lacpBundle.performance.ifOutPriorityQueues.octets.eirTx

       64 bit unsigned wrappable counter."
   ::= {pr1646v2LacpBOutQueuesEntry 67436544}

pr1646v2LacpBOutQueuesOctetsViolateTx OBJECT-TYPE
   SYNTAX      Counter64
   MAX-ACCESS  read-only
   STATUS      current
   DESCRIPTION
      "Path: lacpBundle.performance.ifOutPriorityQueues.octets.violateTx

       64 bit unsigned wrappable counter."
   ::= {pr1646v2LacpBOutQueuesEntry 67633152}

pr1646v2LacpBOutQueuesOctetsBandwidth15sec OBJECT-TYPE
   SYNTAX      Integer32
   MAX-ACCESS  read-only
   STATUS      current
   DESCRIPTION
      "Path: lacpBundle.performance.ifOutPriorityQueues.octets.bandwidth.15sec

       unit name = bps
       formula = 8 * ; 8 /"
   ::= {pr1646v2LacpBOutQueuesEntry 70386944}

pr1646v2LacpBOutQueuesOctetsBandwidth30sec OBJECT-TYPE
   SYNTAX      Integer32
   MAX-ACCESS  read-only
   STATUS      current
   DESCRIPTION
      "Path: lacpBundle.performance.ifOutPriorityQueues.octets.bandwidth.30sec

       unit name = bps
       formula = 8 * ; 8 /"
   ::= {pr1646v2LacpBOutQueuesEntry 70388224}

pr1646v2LacpBOutQueuesOctetsBandwidth1min OBJECT-TYPE
   SYNTAX      Integer32
   MAX-ACCESS  read-only
   STATUS      current
   DESCRIPTION
      "Path: lacpBundle.performance.ifOutPriorityQueues.octets.bandwidth.1min

       unit name = bps
       formula = 8 * ; 8 /"
   ::= {pr1646v2LacpBOutQueuesEntry 70390784}

pr1646v2LacpBOutQueuesOctetsBandwidth2min OBJECT-TYPE
   SYNTAX      Integer32
   MAX-ACCESS  read-only
   STATUS      current
   DESCRIPTION
      "Path: lacpBundle.performance.ifOutPriorityQueues.octets.bandwidth.2min

       unit name = bps
       formula = 8 * ; 8 /"
   ::= {pr1646v2LacpBOutQueuesEntry 70395904}

pr1646v2LacpBOutQueuesOctetsBandwidth5min OBJECT-TYPE
   SYNTAX      Integer32
   MAX-ACCESS  read-only
   STATUS      current
   DESCRIPTION
      "Path: lacpBundle.performance.ifOutPriorityQueues.octets.bandwidth.5min

       unit name = bps
       formula = 8 * ; 8 /"
   ::= {pr1646v2LacpBOutQueuesEntry 70411264}

pr1646v2LacpBOutQueuesH2Performance OBJECT-TYPE
   SYNTAX      SEQUENCE OF Pr1646v2LacpBOutQueuesH2PerformanceEntry
   MAX-ACCESS  not-accessible
   STATUS      current
   DESCRIPTION
      ""
   ::= {pr1646v2LacpBOutQueues 83886080}

pr1646v2LacpBOutQueuesH2PerformanceEntry OBJECT-TYPE
   SYNTAX      Pr1646v2LacpBOutQueuesH2PerformanceEntry
   MAX-ACCESS  not-accessible
   STATUS      current
   DESCRIPTION
      ""
   INDEX      { pr1646v2LacpBOutQueuesH2PerformanceGlobalIx,
                pr1646v2LacpBOutQueuesTableIx,
                pr1646v2LacpBOutQueuesH2PerformanceTableIx }
   ::= {pr1646v2LacpBOutQueuesH2Performance 1}

Pr1646v2LacpBOutQueuesH2PerformanceEntry ::=
   SEQUENCE
      {
      pr1646v2LacpBOutQueuesH2PerformanceGlobalIx
         GlobalIndex,
      pr1646v2LacpBOutQueuesH2PerformanceTableIx
         TableIndex,
      pr1646v2LacpBOutQueuesH2PerformanceSysUpTime
         TimeTicks,
      pr1646v2LacpBOutQueuesH2PerformanceTotPkts
         Counter64,
      pr1646v2LacpBOutQueuesH2PerformanceDirTxPkts
         Counter64,
      pr1646v2LacpBOutQueuesH2PerformanceQdPkts
         Counter64,
      pr1646v2LacpBOutQueuesH2PerformanceDropPkts
         Counter64,
      pr1646v2LacpBOutQueuesH2PerformanceRDropPkts
         Counter64,
      pr1646v2LacpBOutQueuesH2PerformanceCirTxPkts
         Counter64,
      pr1646v2LacpBOutQueuesH2PerformanceEirTxPkts
         Counter64,
      pr1646v2LacpBOutQueuesH2PerformanceViolTxPkts
         Counter64,
      pr1646v2LacpBOutQueuesH2PerformanceTotOcts
         Counter64,
      pr1646v2LacpBOutQueuesH2PerformanceDirTxOcts
         Counter64,
      pr1646v2LacpBOutQueuesH2PerformanceQdOcts
         Counter64,
      pr1646v2LacpBOutQueuesH2PerformanceDropOcts
         Counter64,
      pr1646v2LacpBOutQueuesH2PerformanceRDropOcts
         Counter64,
      pr1646v2LacpBOutQueuesH2PerformanceCirTxOcts
         Counter64,
      pr1646v2LacpBOutQueuesH2PerformanceEirTxOcts
         Counter64,
      pr1646v2LacpBOutQueuesH2PerformanceViolTxOcts
         Counter64,
      pr1646v2LacpBOutQueuesH2PerformanceBandwidth
         Integer32
      }

pr1646v2LacpBOutQueuesH2PerformanceGlobalIx OBJECT-TYPE
   SYNTAX      GlobalIndex
   MAX-ACCESS  not-accessible
   STATUS      current
   DESCRIPTION
      "The value of the tlsCntTreeGlobalIndex of the MANAGED OBJECT."
   ::= {pr1646v2LacpBOutQueuesH2PerformanceEntry 10}

pr1646v2LacpBOutQueuesH2PerformanceTableIx OBJECT-TYPE
   SYNTAX      TableIndex
   MAX-ACCESS  not-accessible
   STATUS      current
   DESCRIPTION
      ""
   ::= {pr1646v2LacpBOutQueuesH2PerformanceEntry 11}

pr1646v2LacpBOutQueuesH2PerformanceSysUpTime OBJECT-TYPE
   SYNTAX      TimeTicks
   MAX-ACCESS  read-only
   STATUS      current
   DESCRIPTION
      "Path: lacpBundle.performance.ifOutPriorityQueues.h2Performance.sysUpTime

       Time in centi-second."
   ::= {pr1646v2LacpBOutQueuesH2PerformanceEntry 16777216}

pr1646v2LacpBOutQueuesH2PerformanceTotPkts OBJECT-TYPE
   SYNTAX      Counter64
   MAX-ACCESS  read-only
   STATUS      current
   DESCRIPTION
      "Path: lacpBundle.performance.ifOutPriorityQueues.h2Performance.totalPkts

       64 bit unsigned wrappable counter."
   ::= {pr1646v2LacpBOutQueuesH2PerformanceEntry 234881024}

pr1646v2LacpBOutQueuesH2PerformanceDirTxPkts OBJECT-TYPE
   SYNTAX      Counter64
   MAX-ACCESS  read-only
   STATUS      current
   DESCRIPTION
      "Path: lacpBundle.performance.ifOutPriorityQueues.h2Performance.directTxPkts

       64 bit unsigned wrappable counter."
   ::= {pr1646v2LacpBOutQueuesH2PerformanceEntry 33554432}

pr1646v2LacpBOutQueuesH2PerformanceQdPkts OBJECT-TYPE
   SYNTAX      Counter64
   MAX-ACCESS  read-only
   STATUS      current
   DESCRIPTION
      "Path: lacpBundle.performance.ifOutPriorityQueues.h2Performance.queuedPkts

       64 bit unsigned wrappable counter."
   ::= {pr1646v2LacpBOutQueuesH2PerformanceEntry 50331648}

pr1646v2LacpBOutQueuesH2PerformanceDropPkts OBJECT-TYPE
   SYNTAX      Counter64
   MAX-ACCESS  read-only
   STATUS      current
   DESCRIPTION
      "Path: lacpBundle.performance.ifOutPriorityQueues.h2Performance.droppedPkts

       64 bit unsigned wrappable counter."
   ::= {pr1646v2LacpBOutQueuesH2PerformanceEntry 67108864}

pr1646v2LacpBOutQueuesH2PerformanceRDropPkts OBJECT-TYPE
   SYNTAX      Counter64
   MAX-ACCESS  read-only
   STATUS      current
   DESCRIPTION
      "Path: lacpBundle.performance.ifOutPriorityQueues.h2Performance.redDroppedPkts

       64 bit unsigned wrappable counter."
   ::= {pr1646v2LacpBOutQueuesH2PerformanceEntry 201326592}

pr1646v2LacpBOutQueuesH2PerformanceCirTxPkts OBJECT-TYPE
   SYNTAX      Counter64
   MAX-ACCESS  read-only
   STATUS      current
   DESCRIPTION
      "Path: lacpBundle.performance.ifOutPriorityQueues.h2Performance.cirTxPkts

       64 bit unsigned wrappable counter."
   ::= {pr1646v2LacpBOutQueuesH2PerformanceEntry 83886080}

pr1646v2LacpBOutQueuesH2PerformanceEirTxPkts OBJECT-TYPE
   SYNTAX      Counter64
   MAX-ACCESS  read-only
   STATUS      current
   DESCRIPTION
      "Path: lacpBundle.performance.ifOutPriorityQueues.h2Performance.eirTxPkts

       64 bit unsigned wrappable counter."
   ::= {pr1646v2LacpBOutQueuesH2PerformanceEntry 100663296}

pr1646v2LacpBOutQueuesH2PerformanceViolTxPkts OBJECT-TYPE
   SYNTAX      Counter64
   MAX-ACCESS  read-only
   STATUS      current
   DESCRIPTION
      "Path: lacpBundle.performance.ifOutPriorityQueues.h2Performance.violateTxPkts

       64 bit unsigned wrappable counter."
   ::= {pr1646v2LacpBOutQueuesH2PerformanceEntry 301989888}

pr1646v2LacpBOutQueuesH2PerformanceTotOcts OBJECT-TYPE
   SYNTAX      Counter64
   MAX-ACCESS  read-only
   STATUS      current
   DESCRIPTION
      "Path: lacpBundle.performance.ifOutPriorityQueues.h2Performance.totalOctets

       64 bit unsigned wrappable counter."
   ::= {pr1646v2LacpBOutQueuesH2PerformanceEntry 251658240}

pr1646v2LacpBOutQueuesH2PerformanceDirTxOcts OBJECT-TYPE
   SYNTAX      Counter64
   MAX-ACCESS  read-only
   STATUS      current
   DESCRIPTION
      "Path: lacpBundle.performance.ifOutPriorityQueues.h2Performance.directTxOctets

       64 bit unsigned wrappable counter."
   ::= {pr1646v2LacpBOutQueuesH2PerformanceEntry 117440512}

pr1646v2LacpBOutQueuesH2PerformanceQdOcts OBJECT-TYPE
   SYNTAX      Counter64
   MAX-ACCESS  read-only
   STATUS      current
   DESCRIPTION
      "Path: lacpBundle.performance.ifOutPriorityQueues.h2Performance.queuedOctets

       64 bit unsigned wrappable counter."
   ::= {pr1646v2LacpBOutQueuesH2PerformanceEntry 134217728}

pr1646v2LacpBOutQueuesH2PerformanceDropOcts OBJECT-TYPE
   SYNTAX      Counter64
   MAX-ACCESS  read-only
   STATUS      current
   DESCRIPTION
      "Path: lacpBundle.performance.ifOutPriorityQueues.h2Performance.droppedOctets

       64 bit unsigned wrappable counter."
   ::= {pr1646v2LacpBOutQueuesH2PerformanceEntry 150994944}

pr1646v2LacpBOutQueuesH2PerformanceRDropOcts OBJECT-TYPE
   SYNTAX      Counter64
   MAX-ACCESS  read-only
   STATUS      current
   DESCRIPTION
      "Path: lacpBundle.performance.ifOutPriorityQueues.h2Performance.redDroppedOctets

       64 bit unsigned wrappable counter."
   ::= {pr1646v2LacpBOutQueuesH2PerformanceEntry 218103808}

pr1646v2LacpBOutQueuesH2PerformanceCirTxOcts OBJECT-TYPE
   SYNTAX      Counter64
   MAX-ACCESS  read-only
   STATUS      current
   DESCRIPTION
      "Path: lacpBundle.performance.ifOutPriorityQueues.h2Performance.cirTxOctets

       64 bit unsigned wrappable counter."
   ::= {pr1646v2LacpBOutQueuesH2PerformanceEntry 167772160}

pr1646v2LacpBOutQueuesH2PerformanceEirTxOcts OBJECT-TYPE
   SYNTAX      Counter64
   MAX-ACCESS  read-only
   STATUS      current
   DESCRIPTION
      "Path: lacpBundle.performance.ifOutPriorityQueues.h2Performance.eirTxOctets

       64 bit unsigned wrappable counter."
   ::= {pr1646v2LacpBOutQueuesH2PerformanceEntry 184549376}

pr1646v2LacpBOutQueuesH2PerformanceViolTxOcts OBJECT-TYPE
   SYNTAX      Counter64
   MAX-ACCESS  read-only
   STATUS      current
   DESCRIPTION
      "Path: lacpBundle.performance.ifOutPriorityQueues.h2Performance.violateTxOctets

       64 bit unsigned wrappable counter."
   ::= {pr1646v2LacpBOutQueuesH2PerformanceEntry 318767104}

pr1646v2LacpBOutQueuesH2PerformanceBandwidth OBJECT-TYPE
   SYNTAX      Integer32
   MAX-ACCESS  read-only
   STATUS      current
   DESCRIPTION
      "Path: lacpBundle.performance.ifOutPriorityQueues.h2Performance.bandwidth

       unit name = bps
       formula = 8 * ; 8 /"
   ::= {pr1646v2LacpBOutQueuesH2PerformanceEntry 268435456}

pr1646v2LacpBOutQueuesH24Performance OBJECT-TYPE
   SYNTAX      SEQUENCE OF Pr1646v2LacpBOutQueuesH24PerformanceEntry
   MAX-ACCESS  not-accessible
   STATUS      current
   DESCRIPTION
      ""
   ::= {pr1646v2LacpBOutQueues 100663296}

pr1646v2LacpBOutQueuesH24PerformanceEntry OBJECT-TYPE
   SYNTAX      Pr1646v2LacpBOutQueuesH24PerformanceEntry
   MAX-ACCESS  not-accessible
   STATUS      current
   DESCRIPTION
      ""
   INDEX      { pr1646v2LacpBOutQueuesH24PerformanceGlobalIx,
                pr1646v2LacpBOutQueuesTableIx,
                pr1646v2LacpBOutQueuesH24PerformanceTableIx }
   ::= {pr1646v2LacpBOutQueuesH24Performance 1}

Pr1646v2LacpBOutQueuesH24PerformanceEntry ::=
   SEQUENCE
      {
      pr1646v2LacpBOutQueuesH24PerformanceGlobalIx
         GlobalIndex,
      pr1646v2LacpBOutQueuesH24PerformanceTableIx
         TableIndex,
      pr1646v2LacpBOutQueuesH24PerformanceSysUpTime
         TimeTicks,
      pr1646v2LacpBOutQueuesH24PerformanceTotPkts
         Counter64,
      pr1646v2LacpBOutQueuesH24PerformanceDirTxPkts
         Counter64,
      pr1646v2LacpBOutQueuesH24PerformanceQdPkts
         Counter64,
      pr1646v2LacpBOutQueuesH24PerformanceDropPkts
         Counter64,
      pr1646v2LacpBOutQueuesH24PerformanceRDropPkts
         Counter64,
      pr1646v2LacpBOutQueuesH24PerformanceCirTxPkts
         Counter64,
      pr1646v2LacpBOutQueuesH24PerformanceEirTxPkts
         Counter64,
      pr1646v2LacpBOutQueuesH24PerformanceViolTxPkts
         Counter64,
      pr1646v2LacpBOutQueuesH24PerformanceTotOcts
         Counter64,
      pr1646v2LacpBOutQueuesH24PerformanceDirTxOcts
         Counter64,
      pr1646v2LacpBOutQueuesH24PerformanceQdOcts
         Counter64,
      pr1646v2LacpBOutQueuesH24PerformanceDropOcts
         Counter64,
      pr1646v2LacpBOutQueuesH24PerformanceRDropOcts
         Counter64,
      pr1646v2LacpBOutQueuesH24PerformanceCirTxOcts
         Counter64,
      pr1646v2LacpBOutQueuesH24PerformanceEirTxOcts
         Counter64,
      pr1646v2LacpBOutQueuesH24PerformanceViolTxOcts
         Counter64,
      pr1646v2LacpBOutQueuesH24PerformanceBandwidth
         Integer32
      }

pr1646v2LacpBOutQueuesH24PerformanceGlobalIx OBJECT-TYPE
   SYNTAX      GlobalIndex
   MAX-ACCESS  not-accessible
   STATUS      current
   DESCRIPTION
      "The value of the tlsCntTreeGlobalIndex of the MANAGED OBJECT."
   ::= {pr1646v2LacpBOutQueuesH24PerformanceEntry 10}

pr1646v2LacpBOutQueuesH24PerformanceTableIx OBJECT-TYPE
   SYNTAX      TableIndex
   MAX-ACCESS  not-accessible
   STATUS      current
   DESCRIPTION
      ""
   ::= {pr1646v2LacpBOutQueuesH24PerformanceEntry 11}

pr1646v2LacpBOutQueuesH24PerformanceSysUpTime OBJECT-TYPE
   SYNTAX      TimeTicks
   MAX-ACCESS  read-only
   STATUS      current
   DESCRIPTION
      "Path: lacpBundle.performance.ifOutPriorityQueues.h24Performance.sysUpTime

       Time in centi-second."
   ::= {pr1646v2LacpBOutQueuesH24PerformanceEntry 16777216}

pr1646v2LacpBOutQueuesH24PerformanceTotPkts OBJECT-TYPE
   SYNTAX      Counter64
   MAX-ACCESS  read-only
   STATUS      current
   DESCRIPTION
      "Path: lacpBundle.performance.ifOutPriorityQueues.h24Performance.totalPkts

       64 bit unsigned wrappable counter."
   ::= {pr1646v2LacpBOutQueuesH24PerformanceEntry 234881024}

pr1646v2LacpBOutQueuesH24PerformanceDirTxPkts OBJECT-TYPE
   SYNTAX      Counter64
   MAX-ACCESS  read-only
   STATUS      current
   DESCRIPTION
      "Path: lacpBundle.performance.ifOutPriorityQueues.h24Performance.directTxPkts

       64 bit unsigned wrappable counter."
   ::= {pr1646v2LacpBOutQueuesH24PerformanceEntry 33554432}

pr1646v2LacpBOutQueuesH24PerformanceQdPkts OBJECT-TYPE
   SYNTAX      Counter64
   MAX-ACCESS  read-only
   STATUS      current
   DESCRIPTION
      "Path: lacpBundle.performance.ifOutPriorityQueues.h24Performance.queuedPkts

       64 bit unsigned wrappable counter."
   ::= {pr1646v2LacpBOutQueuesH24PerformanceEntry 50331648}

pr1646v2LacpBOutQueuesH24PerformanceDropPkts OBJECT-TYPE
   SYNTAX      Counter64
   MAX-ACCESS  read-only
   STATUS      current
   DESCRIPTION
      "Path: lacpBundle.performance.ifOutPriorityQueues.h24Performance.droppedPkts

       64 bit unsigned wrappable counter."
   ::= {pr1646v2LacpBOutQueuesH24PerformanceEntry 67108864}

pr1646v2LacpBOutQueuesH24PerformanceRDropPkts OBJECT-TYPE
   SYNTAX      Counter64
   MAX-ACCESS  read-only
   STATUS      current
   DESCRIPTION
      "Path: lacpBundle.performance.ifOutPriorityQueues.h24Performance.redDroppedPkts

       64 bit unsigned wrappable counter."
   ::= {pr1646v2LacpBOutQueuesH24PerformanceEntry 201326592}

pr1646v2LacpBOutQueuesH24PerformanceCirTxPkts OBJECT-TYPE
   SYNTAX      Counter64
   MAX-ACCESS  read-only
   STATUS      current
   DESCRIPTION
      "Path: lacpBundle.performance.ifOutPriorityQueues.h24Performance.cirTxPkts

       64 bit unsigned wrappable counter."
   ::= {pr1646v2LacpBOutQueuesH24PerformanceEntry 83886080}

pr1646v2LacpBOutQueuesH24PerformanceEirTxPkts OBJECT-TYPE
   SYNTAX      Counter64
   MAX-ACCESS  read-only
   STATUS      current
   DESCRIPTION
      "Path: lacpBundle.performance.ifOutPriorityQueues.h24Performance.eirTxPkts

       64 bit unsigned wrappable counter."
   ::= {pr1646v2LacpBOutQueuesH24PerformanceEntry 100663296}

pr1646v2LacpBOutQueuesH24PerformanceViolTxPkts OBJECT-TYPE
   SYNTAX      Counter64
   MAX-ACCESS  read-only
   STATUS      current
   DESCRIPTION
      "Path: lacpBundle.performance.ifOutPriorityQueues.h24Performance.violateTxPkts

       64 bit unsigned wrappable counter."
   ::= {pr1646v2LacpBOutQueuesH24PerformanceEntry 301989888}

pr1646v2LacpBOutQueuesH24PerformanceTotOcts OBJECT-TYPE
   SYNTAX      Counter64
   MAX-ACCESS  read-only
   STATUS      current
   DESCRIPTION
      "Path: lacpBundle.performance.ifOutPriorityQueues.h24Performance.totalOctets

       64 bit unsigned wrappable counter."
   ::= {pr1646v2LacpBOutQueuesH24PerformanceEntry 251658240}

pr1646v2LacpBOutQueuesH24PerformanceDirTxOcts OBJECT-TYPE
   SYNTAX      Counter64
   MAX-ACCESS  read-only
   STATUS      current
   DESCRIPTION
      "Path: lacpBundle.performance.ifOutPriorityQueues.h24Performance.directTxOctets

       64 bit unsigned wrappable counter."
   ::= {pr1646v2LacpBOutQueuesH24PerformanceEntry 117440512}

pr1646v2LacpBOutQueuesH24PerformanceQdOcts OBJECT-TYPE
   SYNTAX      Counter64
   MAX-ACCESS  read-only
   STATUS      current
   DESCRIPTION
      "Path: lacpBundle.performance.ifOutPriorityQueues.h24Performance.queuedOctets

       64 bit unsigned wrappable counter."
   ::= {pr1646v2LacpBOutQueuesH24PerformanceEntry 134217728}

pr1646v2LacpBOutQueuesH24PerformanceDropOcts OBJECT-TYPE
   SYNTAX      Counter64
   MAX-ACCESS  read-only
   STATUS      current
   DESCRIPTION
      "Path: lacpBundle.performance.ifOutPriorityQueues.h24Performance.droppedOctets

       64 bit unsigned wrappable counter."
   ::= {pr1646v2LacpBOutQueuesH24PerformanceEntry 150994944}

pr1646v2LacpBOutQueuesH24PerformanceRDropOcts OBJECT-TYPE
   SYNTAX      Counter64
   MAX-ACCESS  read-only
   STATUS      current
   DESCRIPTION
      "Path: lacpBundle.performance.ifOutPriorityQueues.h24Performance.redDroppedOctets

       64 bit unsigned wrappable counter."
   ::= {pr1646v2LacpBOutQueuesH24PerformanceEntry 218103808}

pr1646v2LacpBOutQueuesH24PerformanceCirTxOcts OBJECT-TYPE
   SYNTAX      Counter64
   MAX-ACCESS  read-only
   STATUS      current
   DESCRIPTION
      "Path: lacpBundle.performance.ifOutPriorityQueues.h24Performance.cirTxOctets

       64 bit unsigned wrappable counter."
   ::= {pr1646v2LacpBOutQueuesH24PerformanceEntry 167772160}

pr1646v2LacpBOutQueuesH24PerformanceEirTxOcts OBJECT-TYPE
   SYNTAX      Counter64
   MAX-ACCESS  read-only
   STATUS      current
   DESCRIPTION
      "Path: lacpBundle.performance.ifOutPriorityQueues.h24Performance.eirTxOctets

       64 bit unsigned wrappable counter."
   ::= {pr1646v2LacpBOutQueuesH24PerformanceEntry 184549376}

pr1646v2LacpBOutQueuesH24PerformanceViolTxOcts OBJECT-TYPE
   SYNTAX      Counter64
   MAX-ACCESS  read-only
   STATUS      current
   DESCRIPTION
      "Path: lacpBundle.performance.ifOutPriorityQueues.h24Performance.violateTxOctets

       64 bit unsigned wrappable counter."
   ::= {pr1646v2LacpBOutQueuesH24PerformanceEntry 318767104}

pr1646v2LacpBOutQueuesH24PerformanceBandwidth OBJECT-TYPE
   SYNTAX      Integer32
   MAX-ACCESS  read-only
   STATUS      current
   DESCRIPTION
      "Path: lacpBundle.performance.ifOutPriorityQueues.h24Performance.bandwidth

       unit name = bps
       formula = 8 * ; 8 /"
   ::= {pr1646v2LacpBOutQueuesH24PerformanceEntry 268435456}

pr1646v2LacpBOutQueuesD7Performance OBJECT-TYPE
   SYNTAX      SEQUENCE OF Pr1646v2LacpBOutQueuesD7PerformanceEntry
   MAX-ACCESS  not-accessible
   STATUS      current
   DESCRIPTION
      ""
   ::= {pr1646v2LacpBOutQueues 117440512}

pr1646v2LacpBOutQueuesD7PerformanceEntry OBJECT-TYPE
   SYNTAX      Pr1646v2LacpBOutQueuesD7PerformanceEntry
   MAX-ACCESS  not-accessible
   STATUS      current
   DESCRIPTION
      ""
   INDEX      { pr1646v2LacpBOutQueuesD7PerformanceGlobalIx,
                pr1646v2LacpBOutQueuesTableIx,
                pr1646v2LacpBOutQueuesD7PerformanceTableIx }
   ::= {pr1646v2LacpBOutQueuesD7Performance 1}

Pr1646v2LacpBOutQueuesD7PerformanceEntry ::=
   SEQUENCE
      {
      pr1646v2LacpBOutQueuesD7PerformanceGlobalIx
         GlobalIndex,
      pr1646v2LacpBOutQueuesD7PerformanceTableIx
         TableIndex,
      pr1646v2LacpBOutQueuesD7PerformanceSysUpTime
         TimeTicks,
      pr1646v2LacpBOutQueuesD7PerformanceTotPkts
         Counter64,
      pr1646v2LacpBOutQueuesD7PerformanceDirTxPkts
         Counter64,
      pr1646v2LacpBOutQueuesD7PerformanceQdPkts
         Counter64,
      pr1646v2LacpBOutQueuesD7PerformanceDropPkts
         Counter64,
      pr1646v2LacpBOutQueuesD7PerformanceRDropPkts
         Counter64,
      pr1646v2LacpBOutQueuesD7PerformanceCirTxPkts
         Counter64,
      pr1646v2LacpBOutQueuesD7PerformanceEirTxPkts
         Counter64,
      pr1646v2LacpBOutQueuesD7PerformanceViolTxPkts
         Counter64,
      pr1646v2LacpBOutQueuesD7PerformanceTotOcts
         Counter64,
      pr1646v2LacpBOutQueuesD7PerformanceDirTxOcts
         Counter64,
      pr1646v2LacpBOutQueuesD7PerformanceQdOcts
         Counter64,
      pr1646v2LacpBOutQueuesD7PerformanceDropOcts
         Counter64,
      pr1646v2LacpBOutQueuesD7PerformanceRDropOcts
         Counter64,
      pr1646v2LacpBOutQueuesD7PerformanceCirTxOcts
         Counter64,
      pr1646v2LacpBOutQueuesD7PerformanceEirTxOcts
         Counter64,
      pr1646v2LacpBOutQueuesD7PerformanceViolTxOcts
         Counter64,
      pr1646v2LacpBOutQueuesD7PerformanceBandwidth
         Integer32
      }

pr1646v2LacpBOutQueuesD7PerformanceGlobalIx OBJECT-TYPE
   SYNTAX      GlobalIndex
   MAX-ACCESS  not-accessible
   STATUS      current
   DESCRIPTION
      "The value of the tlsCntTreeGlobalIndex of the MANAGED OBJECT."
   ::= {pr1646v2LacpBOutQueuesD7PerformanceEntry 10}

pr1646v2LacpBOutQueuesD7PerformanceTableIx OBJECT-TYPE
   SYNTAX      TableIndex
   MAX-ACCESS  not-accessible
   STATUS      current
   DESCRIPTION
      ""
   ::= {pr1646v2LacpBOutQueuesD7PerformanceEntry 11}

pr1646v2LacpBOutQueuesD7PerformanceSysUpTime OBJECT-TYPE
   SYNTAX      TimeTicks
   MAX-ACCESS  read-only
   STATUS      current
   DESCRIPTION
      "Path: lacpBundle.performance.ifOutPriorityQueues.d7Performance.sysUpTime

       Time in centi-second."
   ::= {pr1646v2LacpBOutQueuesD7PerformanceEntry 16777216}

pr1646v2LacpBOutQueuesD7PerformanceTotPkts OBJECT-TYPE
   SYNTAX      Counter64
   MAX-ACCESS  read-only
   STATUS      current
   DESCRIPTION
      "Path: lacpBundle.performance.ifOutPriorityQueues.d7Performance.totalPkts

       64 bit unsigned wrappable counter."
   ::= {pr1646v2LacpBOutQueuesD7PerformanceEntry 234881024}

pr1646v2LacpBOutQueuesD7PerformanceDirTxPkts OBJECT-TYPE
   SYNTAX      Counter64
   MAX-ACCESS  read-only
   STATUS      current
   DESCRIPTION
      "Path: lacpBundle.performance.ifOutPriorityQueues.d7Performance.directTxPkts

       64 bit unsigned wrappable counter."
   ::= {pr1646v2LacpBOutQueuesD7PerformanceEntry 33554432}

pr1646v2LacpBOutQueuesD7PerformanceQdPkts OBJECT-TYPE
   SYNTAX      Counter64
   MAX-ACCESS  read-only
   STATUS      current
   DESCRIPTION
      "Path: lacpBundle.performance.ifOutPriorityQueues.d7Performance.queuedPkts

       64 bit unsigned wrappable counter."
   ::= {pr1646v2LacpBOutQueuesD7PerformanceEntry 50331648}

pr1646v2LacpBOutQueuesD7PerformanceDropPkts OBJECT-TYPE
   SYNTAX      Counter64
   MAX-ACCESS  read-only
   STATUS      current
   DESCRIPTION
      "Path: lacpBundle.performance.ifOutPriorityQueues.d7Performance.droppedPkts

       64 bit unsigned wrappable counter."
   ::= {pr1646v2LacpBOutQueuesD7PerformanceEntry 67108864}

pr1646v2LacpBOutQueuesD7PerformanceRDropPkts OBJECT-TYPE
   SYNTAX      Counter64
   MAX-ACCESS  read-only
   STATUS      current
   DESCRIPTION
      "Path: lacpBundle.performance.ifOutPriorityQueues.d7Performance.redDroppedPkts

       64 bit unsigned wrappable counter."
   ::= {pr1646v2LacpBOutQueuesD7PerformanceEntry 201326592}

pr1646v2LacpBOutQueuesD7PerformanceCirTxPkts OBJECT-TYPE
   SYNTAX      Counter64
   MAX-ACCESS  read-only
   STATUS      current
   DESCRIPTION
      "Path: lacpBundle.performance.ifOutPriorityQueues.d7Performance.cirTxPkts

       64 bit unsigned wrappable counter."
   ::= {pr1646v2LacpBOutQueuesD7PerformanceEntry 83886080}

pr1646v2LacpBOutQueuesD7PerformanceEirTxPkts OBJECT-TYPE
   SYNTAX      Counter64
   MAX-ACCESS  read-only
   STATUS      current
   DESCRIPTION
      "Path: lacpBundle.performance.ifOutPriorityQueues.d7Performance.eirTxPkts

       64 bit unsigned wrappable counter."
   ::= {pr1646v2LacpBOutQueuesD7PerformanceEntry 100663296}

pr1646v2LacpBOutQueuesD7PerformanceViolTxPkts OBJECT-TYPE
   SYNTAX      Counter64
   MAX-ACCESS  read-only
   STATUS      current
   DESCRIPTION
      "Path: lacpBundle.performance.ifOutPriorityQueues.d7Performance.violateTxPkts

       64 bit unsigned wrappable counter."
   ::= {pr1646v2LacpBOutQueuesD7PerformanceEntry 301989888}

pr1646v2LacpBOutQueuesD7PerformanceTotOcts OBJECT-TYPE
   SYNTAX      Counter64
   MAX-ACCESS  read-only
   STATUS      current
   DESCRIPTION
      "Path: lacpBundle.performance.ifOutPriorityQueues.d7Performance.totalOctets

       64 bit unsigned wrappable counter."
   ::= {pr1646v2LacpBOutQueuesD7PerformanceEntry 251658240}

pr1646v2LacpBOutQueuesD7PerformanceDirTxOcts OBJECT-TYPE
   SYNTAX      Counter64
   MAX-ACCESS  read-only
   STATUS      current
   DESCRIPTION
      "Path: lacpBundle.performance.ifOutPriorityQueues.d7Performance.directTxOctets

       64 bit unsigned wrappable counter."
   ::= {pr1646v2LacpBOutQueuesD7PerformanceEntry 117440512}

pr1646v2LacpBOutQueuesD7PerformanceQdOcts OBJECT-TYPE
   SYNTAX      Counter64
   MAX-ACCESS  read-only
   STATUS      current
   DESCRIPTION
      "Path: lacpBundle.performance.ifOutPriorityQueues.d7Performance.queuedOctets

       64 bit unsigned wrappable counter."
   ::= {pr1646v2LacpBOutQueuesD7PerformanceEntry 134217728}

pr1646v2LacpBOutQueuesD7PerformanceDropOcts OBJECT-TYPE
   SYNTAX      Counter64
   MAX-ACCESS  read-only
   STATUS      current
   DESCRIPTION
      "Path: lacpBundle.performance.ifOutPriorityQueues.d7Performance.droppedOctets

       64 bit unsigned wrappable counter."
   ::= {pr1646v2LacpBOutQueuesD7PerformanceEntry 150994944}

pr1646v2LacpBOutQueuesD7PerformanceRDropOcts OBJECT-TYPE
   SYNTAX      Counter64
   MAX-ACCESS  read-only
   STATUS      current
   DESCRIPTION
      "Path: lacpBundle.performance.ifOutPriorityQueues.d7Performance.redDroppedOctets

       64 bit unsigned wrappable counter."
   ::= {pr1646v2LacpBOutQueuesD7PerformanceEntry 218103808}

pr1646v2LacpBOutQueuesD7PerformanceCirTxOcts OBJECT-TYPE
   SYNTAX      Counter64
   MAX-ACCESS  read-only
   STATUS      current
   DESCRIPTION
      "Path: lacpBundle.performance.ifOutPriorityQueues.d7Performance.cirTxOctets

       64 bit unsigned wrappable counter."
   ::= {pr1646v2LacpBOutQueuesD7PerformanceEntry 167772160}

pr1646v2LacpBOutQueuesD7PerformanceEirTxOcts OBJECT-TYPE
   SYNTAX      Counter64
   MAX-ACCESS  read-only
   STATUS      current
   DESCRIPTION
      "Path: lacpBundle.performance.ifOutPriorityQueues.d7Performance.eirTxOctets

       64 bit unsigned wrappable counter."
   ::= {pr1646v2LacpBOutQueuesD7PerformanceEntry 184549376}

pr1646v2LacpBOutQueuesD7PerformanceViolTxOcts OBJECT-TYPE
   SYNTAX      Counter64
   MAX-ACCESS  read-only
   STATUS      current
   DESCRIPTION
      "Path: lacpBundle.performance.ifOutPriorityQueues.d7Performance.violateTxOctets

       64 bit unsigned wrappable counter."
   ::= {pr1646v2LacpBOutQueuesD7PerformanceEntry 318767104}

pr1646v2LacpBOutQueuesD7PerformanceBandwidth OBJECT-TYPE
   SYNTAX      Integer32
   MAX-ACCESS  read-only
   STATUS      current
   DESCRIPTION
      "Path: lacpBundle.performance.ifOutPriorityQueues.d7Performance.bandwidth

       unit name = bps
       formula = 8 * ; 8 /"
   ::= {pr1646v2LacpBOutQueuesD7PerformanceEntry 268435456}


pr1646v2LacpBOutBandwidth OBJECT IDENTIFIER ::= {pr1646v2LacpB 182}

pr1646v2LacpBOutBandwidthSSCTable OBJECT-TYPE
   SYNTAX      SEQUENCE OF Pr1646v2LacpBOutBandwidthEntry
   MAX-ACCESS  not-accessible
   STATUS      current
   DESCRIPTION
      "bandwidth"
   ::= {pr1646v2LacpBOutBandwidth 1}

pr1646v2LacpBOutBandwidthEntry OBJECT-TYPE
   SYNTAX      Pr1646v2LacpBOutBandwidthEntry
   MAX-ACCESS  not-accessible
   STATUS      current
   DESCRIPTION
      ""
   INDEX      { pr1646v2LacpBOutBandwidthGlobalIx }
   ::= {pr1646v2LacpBOutBandwidthSSCTable 1}

Pr1646v2LacpBOutBandwidthEntry ::=
   SEQUENCE
      {
      pr1646v2LacpBOutBandwidthGlobalIx
         GlobalIndex,
      pr1646v2LacpBOutBandwidth15sec
         Integer32,
      pr1646v2LacpBOutBandwidth30sec
         Integer32,
      pr1646v2LacpBOutBandwidth1min
         Integer32,
      pr1646v2LacpBOutBandwidth2min
         Integer32,
      pr1646v2LacpBOutBandwidth5min
         Integer32
      }

pr1646v2LacpBOutBandwidthGlobalIx OBJECT-TYPE
   SYNTAX      GlobalIndex
   MAX-ACCESS  not-accessible
   STATUS      current
   DESCRIPTION
      "The value of the tlsCntTreeGlobalIndex of the MANAGED OBJECT."
   ::= {pr1646v2LacpBOutBandwidthEntry 10}

pr1646v2LacpBOutBandwidth15sec OBJECT-TYPE
   SYNTAX      Integer32
   MAX-ACCESS  read-only
   STATUS      current
   DESCRIPTION
      "Path: lacpBundle.performance.ifOutBandwidth.15sec

       unit name = bps
       formula = 8 * ; 8 /"
   ::= {pr1646v2LacpBOutBandwidthEntry 83886080}

pr1646v2LacpBOutBandwidth30sec OBJECT-TYPE
   SYNTAX      Integer32
   MAX-ACCESS  read-only
   STATUS      current
   DESCRIPTION
      "Path: lacpBundle.performance.ifOutBandwidth.30sec

       unit name = bps
       formula = 8 * ; 8 /"
   ::= {pr1646v2LacpBOutBandwidthEntry 167772160}

pr1646v2LacpBOutBandwidth1min OBJECT-TYPE
   SYNTAX      Integer32
   MAX-ACCESS  read-only
   STATUS      current
   DESCRIPTION
      "Path: lacpBundle.performance.ifOutBandwidth.1min

       unit name = bps
       formula = 8 * ; 8 /"
   ::= {pr1646v2LacpBOutBandwidthEntry 335544320}

pr1646v2LacpBOutBandwidth2min OBJECT-TYPE
   SYNTAX      Integer32
   MAX-ACCESS  read-only
   STATUS      current
   DESCRIPTION
      "Path: lacpBundle.performance.ifOutBandwidth.2min

       unit name = bps
       formula = 8 * ; 8 /"
   ::= {pr1646v2LacpBOutBandwidthEntry 671088640}

pr1646v2LacpBOutBandwidth5min OBJECT-TYPE
   SYNTAX      Integer32
   MAX-ACCESS  read-only
   STATUS      current
   DESCRIPTION
      "Path: lacpBundle.performance.ifOutBandwidth.5min

       unit name = bps
       formula = 8 * ; 8 /"
   ::= {pr1646v2LacpBOutBandwidthEntry 1677721600}


pr1646v2LacpBInP OBJECT IDENTIFIER ::= {pr1646v2LacpB 307}

pr1646v2LacpBInPSSCTable OBJECT-TYPE
   SYNTAX      SEQUENCE OF Pr1646v2LacpBInPEntry
   MAX-ACCESS  not-accessible
   STATUS      current
   DESCRIPTION
      "h2IfInPerformance"
   ::= {pr1646v2LacpBInP 1}

pr1646v2LacpBInPEntry OBJECT-TYPE
   SYNTAX      Pr1646v2LacpBInPEntry
   MAX-ACCESS  not-accessible
   STATUS      current
   DESCRIPTION
      ""
   INDEX      { pr1646v2LacpBInPGlobalIx,
                pr1646v2LacpBInPTableIx }
   ::= {pr1646v2LacpBInPSSCTable 1}

Pr1646v2LacpBInPEntry ::=
   SEQUENCE
      {
      pr1646v2LacpBInPGlobalIx
         GlobalIndex,
      pr1646v2LacpBInPTableIx
         TableIndex,
      pr1646v2LacpBInPSysUpTime
         TimeTicks,
      pr1646v2LacpBInPIfUpTime
         TimeTicks,
      pr1646v2LacpBInPIfStatChanges
         Counter32,
      pr1646v2LacpBInPIfInOctets
         Counter64,
      pr1646v2LacpBInPIfInUCPkts
         Counter64,
      pr1646v2LacpBInPIfInNUCPkts
         Counter64,
      pr1646v2LacpBInPIfInBCPkts
         Counter64,
      pr1646v2LacpBInPIfInMCPkts
         Counter64,
      pr1646v2LacpBInPIfInDiscards
         Counter64,
      pr1646v2LacpBInPIfInErrors
         Counter64,
      pr1646v2LacpBInPIfInUnkwn
         Counter64,
      pr1646v2LacpBInPInDropEx
         Counter64,
      pr1646v2LacpBInPInDropNoMac
         Counter64,
      pr1646v2LacpBInPInDropNUCast
         Counter64,
      pr1646v2LacpBInPInDropFilter
         Counter64,
      pr1646v2LacpBInPIfInBandwidth
         Integer32,
      pr1646v2LacpBInPIfOutOctets
         Counter64,
      pr1646v2LacpBInPIfOutUCPkts
         Counter64,
      pr1646v2LacpBInPIfOutNUCPkts
         Counter64,
      pr1646v2LacpBInPIfOutBCPkts
         Counter64,
      pr1646v2LacpBInPIfOutMCPkts
         Counter64,
      pr1646v2LacpBInPIfOutDiscards
         Counter64,
      pr1646v2LacpBInPIfOutErrors
         Counter64,
      pr1646v2LacpBInPOutDropEx
         Counter64,
      pr1646v2LacpBInPOutDropNoArp
         Counter64,
      pr1646v2LacpBInPOutDropFilter
         Counter64,
      pr1646v2LacpBInPIfOutBandwidth
         Integer32,
      pr1646v2LacpBInPIfErrSec
         Counter32
      }

pr1646v2LacpBInPGlobalIx OBJECT-TYPE
   SYNTAX      GlobalIndex
   MAX-ACCESS  not-accessible
   STATUS      current
   DESCRIPTION
      "The value of the tlsCntTreeGlobalIndex of the MANAGED OBJECT."
   ::= {pr1646v2LacpBInPEntry 10}

pr1646v2LacpBInPTableIx OBJECT-TYPE
   SYNTAX      TableIndex
   MAX-ACCESS  not-accessible
   STATUS      current
   DESCRIPTION
      ""
   ::= {pr1646v2LacpBInPEntry 11}

pr1646v2LacpBInPSysUpTime OBJECT-TYPE
   SYNTAX      TimeTicks
   MAX-ACCESS  read-only
   STATUS      current
   DESCRIPTION
      "Path: lacpBundle.performance.h2Performance.sysUpTime

       Time in centi-second."
   ::= {pr1646v2LacpBInPEntry 16777216}

pr1646v2LacpBInPIfUpTime OBJECT-TYPE
   SYNTAX      TimeTicks
   MAX-ACCESS  read-only
   STATUS      current
   DESCRIPTION
      "Path: lacpBundle.performance.h2Performance.ifUpTime

       Time in centi-second."
   ::= {pr1646v2LacpBInPEntry 33554432}

pr1646v2LacpBInPIfStatChanges OBJECT-TYPE
   SYNTAX      Counter32
   MAX-ACCESS  read-only
   STATUS      current
   DESCRIPTION
      "Path: lacpBundle.performance.h2Performance.ifStatusChanges

       32 bit unsigned wrappable counter."
   ::= {pr1646v2LacpBInPEntry 50331648}

pr1646v2LacpBInPIfInOctets OBJECT-TYPE
   SYNTAX      Counter64
   MAX-ACCESS  read-only
   STATUS      current
   DESCRIPTION
      "Path: lacpBundle.performance.h2Performance.ifInOctets

       64 bit unsigned wrappable counter."
   ::= {pr1646v2LacpBInPEntry 67108864}

pr1646v2LacpBInPIfInUCPkts OBJECT-TYPE
   SYNTAX      Counter64
   MAX-ACCESS  read-only
   STATUS      current
   DESCRIPTION
      "Path: lacpBundle.performance.h2Performance.ifInUcastPkts

       64 bit unsigned wrappable counter."
   ::= {pr1646v2LacpBInPEntry 83886080}

pr1646v2LacpBInPIfInNUCPkts OBJECT-TYPE
   SYNTAX      Counter64
   MAX-ACCESS  read-only
   STATUS      current
   DESCRIPTION
      "Path: lacpBundle.performance.h2Performance.ifInNUcastPkts

       64 bit unsigned wrappable counter."
   ::= {pr1646v2LacpBInPEntry 100663296}

pr1646v2LacpBInPIfInBCPkts OBJECT-TYPE
   SYNTAX      Counter64
   MAX-ACCESS  read-only
   STATUS      current
   DESCRIPTION
      "Path: lacpBundle.performance.h2Performance.ifInBcastPkts

       64 bit unsigned wrappable counter."
   ::= {pr1646v2LacpBInPEntry 419430400}

pr1646v2LacpBInPIfInMCPkts OBJECT-TYPE
   SYNTAX      Counter64
   MAX-ACCESS  read-only
   STATUS      current
   DESCRIPTION
      "Path: lacpBundle.performance.h2Performance.ifInMcastPkts

       64 bit unsigned wrappable counter."
   ::= {pr1646v2LacpBInPEntry 436207616}

pr1646v2LacpBInPIfInDiscards OBJECT-TYPE
   SYNTAX      Counter64
   MAX-ACCESS  read-only
   STATUS      current
   DESCRIPTION
      "Path: lacpBundle.performance.h2Performance.ifInDiscards

       64 bit unsigned wrappable counter."
   ::= {pr1646v2LacpBInPEntry 117440512}

pr1646v2LacpBInPIfInErrors OBJECT-TYPE
   SYNTAX      Counter64
   MAX-ACCESS  read-only
   STATUS      current
   DESCRIPTION
      "Path: lacpBundle.performance.h2Performance.ifInErrors

       64 bit unsigned wrappable counter."
   ::= {pr1646v2LacpBInPEntry 134217728}

pr1646v2LacpBInPIfInUnkwn OBJECT-TYPE
   SYNTAX      Counter64
   MAX-ACCESS  read-only
   STATUS      current
   DESCRIPTION
      "Path: lacpBundle.performance.h2Performance.ifInUnknownProtos

       64 bit unsigned wrappable counter."
   ::= {pr1646v2LacpBInPEntry 150994944}

pr1646v2LacpBInPInDropEx OBJECT-TYPE
   SYNTAX      Counter64
   MAX-ACCESS  read-only
   STATUS      current
   DESCRIPTION
      "Path: lacpBundle.performance.h2Performance.ifInDropLevelExceeded

       64 bit unsigned wrappable counter."
   ::= {pr1646v2LacpBInPEntry 335544320}

pr1646v2LacpBInPInDropNoMac OBJECT-TYPE
   SYNTAX      Counter64
   MAX-ACCESS  read-only
   STATUS      current
   DESCRIPTION
      "Path: lacpBundle.performance.h2Performance.fInDiscardsNoMacFit

       64 bit unsigned wrappable counter."
   ::= {pr1646v2LacpBInPEntry 301989888}

pr1646v2LacpBInPInDropNUCast OBJECT-TYPE
   SYNTAX      Counter64
   MAX-ACCESS  read-only
   STATUS      current
   DESCRIPTION
      "Path: lacpBundle.performance.h2Performance.fInDiscardsNUCast

       64 bit unsigned wrappable counter."
   ::= {pr1646v2LacpBInPEntry 318767104}

pr1646v2LacpBInPInDropFilter OBJECT-TYPE
   SYNTAX      Counter64
   MAX-ACCESS  read-only
   STATUS      current
   DESCRIPTION
      "Path: lacpBundle.performance.h2Performance.fInDiscardsFilter

       64 bit unsigned wrappable counter."
   ::= {pr1646v2LacpBInPEntry 385875968}

pr1646v2LacpBInPIfInBandwidth OBJECT-TYPE
   SYNTAX      Integer32
   MAX-ACCESS  read-only
   STATUS      current
   DESCRIPTION
      "Path: lacpBundle.performance.h2Performance.ifInBandwidth

       unit name = bps
       formula = 8 * ; 8 /"
   ::= {pr1646v2LacpBInPEntry 268435456}

pr1646v2LacpBInPIfOutOctets OBJECT-TYPE
   SYNTAX      Counter64
   MAX-ACCESS  read-only
   STATUS      current
   DESCRIPTION
      "Path: lacpBundle.performance.h2Performance.ifOutOctets

       64 bit unsigned wrappable counter."
   ::= {pr1646v2LacpBInPEntry 167772160}

pr1646v2LacpBInPIfOutUCPkts OBJECT-TYPE
   SYNTAX      Counter64
   MAX-ACCESS  read-only
   STATUS      current
   DESCRIPTION
      "Path: lacpBundle.performance.h2Performance.ifOutUcastPkts

       64 bit unsigned wrappable counter."
   ::= {pr1646v2LacpBInPEntry 184549376}

pr1646v2LacpBInPIfOutNUCPkts OBJECT-TYPE
   SYNTAX      Counter64
   MAX-ACCESS  read-only
   STATUS      current
   DESCRIPTION
      "Path: lacpBundle.performance.h2Performance.ifOutNUcastPkts

       64 bit unsigned wrappable counter."
   ::= {pr1646v2LacpBInPEntry 201326592}

pr1646v2LacpBInPIfOutBCPkts OBJECT-TYPE
   SYNTAX      Counter64
   MAX-ACCESS  read-only
   STATUS      current
   DESCRIPTION
      "Path: lacpBundle.performance.h2Performance.ifOutBcastPkts

       64 bit unsigned wrappable counter."
   ::= {pr1646v2LacpBInPEntry 452984832}

pr1646v2LacpBInPIfOutMCPkts OBJECT-TYPE
   SYNTAX      Counter64
   MAX-ACCESS  read-only
   STATUS      current
   DESCRIPTION
      "Path: lacpBundle.performance.h2Performance.ifOutMcastPkts

       64 bit unsigned wrappable counter."
   ::= {pr1646v2LacpBInPEntry 469762048}

pr1646v2LacpBInPIfOutDiscards OBJECT-TYPE
   SYNTAX      Counter64
   MAX-ACCESS  read-only
   STATUS      current
   DESCRIPTION
      "Path: lacpBundle.performance.h2Performance.ifOutDiscards

       64 bit unsigned wrappable counter."
   ::= {pr1646v2LacpBInPEntry 218103808}

pr1646v2LacpBInPIfOutErrors OBJECT-TYPE
   SYNTAX      Counter64
   MAX-ACCESS  read-only
   STATUS      current
   DESCRIPTION
      "Path: lacpBundle.performance.h2Performance.ifOutErrors

       64 bit unsigned wrappable counter."
   ::= {pr1646v2LacpBInPEntry 234881024}

pr1646v2LacpBInPOutDropEx OBJECT-TYPE
   SYNTAX      Counter64
   MAX-ACCESS  read-only
   STATUS      current
   DESCRIPTION
      "Path: lacpBundle.performance.h2Performance.ifOutDropLevelExceeded

       64 bit unsigned wrappable counter."
   ::= {pr1646v2LacpBInPEntry 352321536}

pr1646v2LacpBInPOutDropNoArp OBJECT-TYPE
   SYNTAX      Counter64
   MAX-ACCESS  read-only
   STATUS      current
   DESCRIPTION
      "Path: lacpBundle.performance.h2Performance.ifOutDiscardsNoArp

       64 bit unsigned wrappable counter."
   ::= {pr1646v2LacpBInPEntry 369098752}

pr1646v2LacpBInPOutDropFilter OBJECT-TYPE
   SYNTAX      Counter64
   MAX-ACCESS  read-only
   STATUS      current
   DESCRIPTION
      "Path: lacpBundle.performance.h2Performance.ifOutDiscardsFilter

       64 bit unsigned wrappable counter."
   ::= {pr1646v2LacpBInPEntry 402653184}

pr1646v2LacpBInPIfOutBandwidth OBJECT-TYPE
   SYNTAX      Integer32
   MAX-ACCESS  read-only
   STATUS      current
   DESCRIPTION
      "Path: lacpBundle.performance.h2Performance.ifOutBandwidth

       unit name = bps
       formula = 8 * ; 8 /"
   ::= {pr1646v2LacpBInPEntry 285212672}

pr1646v2LacpBInPIfErrSec OBJECT-TYPE
   SYNTAX      Counter32
   MAX-ACCESS  read-only
   STATUS      current
   DESCRIPTION
      "Path: lacpBundle.performance.h2Performance.ifErrSec

       32 bit unsigned wrappable counter."
   ::= {pr1646v2LacpBInPEntry 251658240}


pr1646v2LacpBH24InP OBJECT IDENTIFIER ::= {pr1646v2LacpB 308}

pr1646v2LacpBH24InPSSCTable OBJECT-TYPE
   SYNTAX      SEQUENCE OF Pr1646v2LacpBH24InPEntry
   MAX-ACCESS  not-accessible
   STATUS      current
   DESCRIPTION
      "h24IfInPerformance"
   ::= {pr1646v2LacpBH24InP 1}

pr1646v2LacpBH24InPEntry OBJECT-TYPE
   SYNTAX      Pr1646v2LacpBH24InPEntry
   MAX-ACCESS  not-accessible
   STATUS      current
   DESCRIPTION
      ""
   INDEX      { pr1646v2LacpBH24InPGlobalIx,
                pr1646v2LacpBH24InPTableIx }
   ::= {pr1646v2LacpBH24InPSSCTable 1}

Pr1646v2LacpBH24InPEntry ::=
   SEQUENCE
      {
      pr1646v2LacpBH24InPGlobalIx
         GlobalIndex,
      pr1646v2LacpBH24InPTableIx
         TableIndex,
      pr1646v2LacpBH24InPSysUpTime
         TimeTicks,
      pr1646v2LacpBH24InPIfUpTime
         TimeTicks,
      pr1646v2LacpBH24InPIfStatChanges
         Counter32,
      pr1646v2LacpBH24InPIfInOctets
         Counter64,
      pr1646v2LacpBH24InPIfInUCPkts
         Counter64,
      pr1646v2LacpBH24InPIfInNUCPkts
         Counter64,
      pr1646v2LacpBH24InPIfInBCPkts
         Counter64,
      pr1646v2LacpBH24InPIfInMCPkts
         Counter64,
      pr1646v2LacpBH24InPIfInDiscards
         Counter64,
      pr1646v2LacpBH24InPIfInErrors
         Counter64,
      pr1646v2LacpBH24InPIfInUnkwn
         Counter64,
      pr1646v2LacpBH24InPInDropEx
         Counter64,
      pr1646v2LacpBH24InPInDropNoMac
         Counter64,
      pr1646v2LacpBH24InPInDropNUCast
         Counter64,
      pr1646v2LacpBH24InPInDropFilter
         Counter64,
      pr1646v2LacpBH24InPIfInBandwidth
         Integer32,
      pr1646v2LacpBH24InPIfOutOctets
         Counter64,
      pr1646v2LacpBH24InPIfOutUCPkts
         Counter64,
      pr1646v2LacpBH24InPIfOutNUCPkts
         Counter64,
      pr1646v2LacpBH24InPIfOutBCPkts
         Counter64,
      pr1646v2LacpBH24InPIfOutMCPkts
         Counter64,
      pr1646v2LacpBH24InPIfOutDiscards
         Counter64,
      pr1646v2LacpBH24InPIfOutErrors
         Counter64,
      pr1646v2LacpBH24InPOutDropEx
         Counter64,
      pr1646v2LacpBH24InPOutDropNoArp
         Counter64,
      pr1646v2LacpBH24InPOutDropFilter
         Counter64,
      pr1646v2LacpBH24InPIfOutBandwidth
         Integer32,
      pr1646v2LacpBH24InPIfErrSec
         Counter32
      }

pr1646v2LacpBH24InPGlobalIx OBJECT-TYPE
   SYNTAX      GlobalIndex
   MAX-ACCESS  not-accessible
   STATUS      current
   DESCRIPTION
      "The value of the tlsCntTreeGlobalIndex of the MANAGED OBJECT."
   ::= {pr1646v2LacpBH24InPEntry 10}

pr1646v2LacpBH24InPTableIx OBJECT-TYPE
   SYNTAX      TableIndex
   MAX-ACCESS  not-accessible
   STATUS      current
   DESCRIPTION
      ""
   ::= {pr1646v2LacpBH24InPEntry 11}

pr1646v2LacpBH24InPSysUpTime OBJECT-TYPE
   SYNTAX      TimeTicks
   MAX-ACCESS  read-only
   STATUS      current
   DESCRIPTION
      "Path: lacpBundle.performance.h24Performance.sysUpTime

       Time in centi-second."
   ::= {pr1646v2LacpBH24InPEntry 16777216}

pr1646v2LacpBH24InPIfUpTime OBJECT-TYPE
   SYNTAX      TimeTicks
   MAX-ACCESS  read-only
   STATUS      current
   DESCRIPTION
      "Path: lacpBundle.performance.h24Performance.ifUpTime

       Time in centi-second."
   ::= {pr1646v2LacpBH24InPEntry 33554432}

pr1646v2LacpBH24InPIfStatChanges OBJECT-TYPE
   SYNTAX      Counter32
   MAX-ACCESS  read-only
   STATUS      current
   DESCRIPTION
      "Path: lacpBundle.performance.h24Performance.ifStatusChanges

       32 bit unsigned wrappable counter."
   ::= {pr1646v2LacpBH24InPEntry 50331648}

pr1646v2LacpBH24InPIfInOctets OBJECT-TYPE
   SYNTAX      Counter64
   MAX-ACCESS  read-only
   STATUS      current
   DESCRIPTION
      "Path: lacpBundle.performance.h24Performance.ifInOctets

       64 bit unsigned wrappable counter."
   ::= {pr1646v2LacpBH24InPEntry 67108864}

pr1646v2LacpBH24InPIfInUCPkts OBJECT-TYPE
   SYNTAX      Counter64
   MAX-ACCESS  read-only
   STATUS      current
   DESCRIPTION
      "Path: lacpBundle.performance.h24Performance.ifInUcastPkts

       64 bit unsigned wrappable counter."
   ::= {pr1646v2LacpBH24InPEntry 83886080}

pr1646v2LacpBH24InPIfInNUCPkts OBJECT-TYPE
   SYNTAX      Counter64
   MAX-ACCESS  read-only
   STATUS      current
   DESCRIPTION
      "Path: lacpBundle.performance.h24Performance.ifInNUcastPkts

       64 bit unsigned wrappable counter."
   ::= {pr1646v2LacpBH24InPEntry 100663296}

pr1646v2LacpBH24InPIfInBCPkts OBJECT-TYPE
   SYNTAX      Counter64
   MAX-ACCESS  read-only
   STATUS      current
   DESCRIPTION
      "Path: lacpBundle.performance.h24Performance.ifInBcastPkts

       64 bit unsigned wrappable counter."
   ::= {pr1646v2LacpBH24InPEntry 419430400}

pr1646v2LacpBH24InPIfInMCPkts OBJECT-TYPE
   SYNTAX      Counter64
   MAX-ACCESS  read-only
   STATUS      current
   DESCRIPTION
      "Path: lacpBundle.performance.h24Performance.ifInMcastPkts

       64 bit unsigned wrappable counter."
   ::= {pr1646v2LacpBH24InPEntry 436207616}

pr1646v2LacpBH24InPIfInDiscards OBJECT-TYPE
   SYNTAX      Counter64
   MAX-ACCESS  read-only
   STATUS      current
   DESCRIPTION
      "Path: lacpBundle.performance.h24Performance.ifInDiscards

       64 bit unsigned wrappable counter."
   ::= {pr1646v2LacpBH24InPEntry 117440512}

pr1646v2LacpBH24InPIfInErrors OBJECT-TYPE
   SYNTAX      Counter64
   MAX-ACCESS  read-only
   STATUS      current
   DESCRIPTION
      "Path: lacpBundle.performance.h24Performance.ifInErrors

       64 bit unsigned wrappable counter."
   ::= {pr1646v2LacpBH24InPEntry 134217728}

pr1646v2LacpBH24InPIfInUnkwn OBJECT-TYPE
   SYNTAX      Counter64
   MAX-ACCESS  read-only
   STATUS      current
   DESCRIPTION
      "Path: lacpBundle.performance.h24Performance.ifInUnknownProtos

       64 bit unsigned wrappable counter."
   ::= {pr1646v2LacpBH24InPEntry 150994944}

pr1646v2LacpBH24InPInDropEx OBJECT-TYPE
   SYNTAX      Counter64
   MAX-ACCESS  read-only
   STATUS      current
   DESCRIPTION
      "Path: lacpBundle.performance.h24Performance.ifInDropLevelExceeded

       64 bit unsigned wrappable counter."
   ::= {pr1646v2LacpBH24InPEntry 335544320}

pr1646v2LacpBH24InPInDropNoMac OBJECT-TYPE
   SYNTAX      Counter64
   MAX-ACCESS  read-only
   STATUS      current
   DESCRIPTION
      "Path: lacpBundle.performance.h24Performance.fInDiscardsNoMacFit

       64 bit unsigned wrappable counter."
   ::= {pr1646v2LacpBH24InPEntry 301989888}

pr1646v2LacpBH24InPInDropNUCast OBJECT-TYPE
   SYNTAX      Counter64
   MAX-ACCESS  read-only
   STATUS      current
   DESCRIPTION
      "Path: lacpBundle.performance.h24Performance.fInDiscardsNUCast

       64 bit unsigned wrappable counter."
   ::= {pr1646v2LacpBH24InPEntry 318767104}

pr1646v2LacpBH24InPInDropFilter OBJECT-TYPE
   SYNTAX      Counter64
   MAX-ACCESS  read-only
   STATUS      current
   DESCRIPTION
      "Path: lacpBundle.performance.h24Performance.fInDiscardsFilter

       64 bit unsigned wrappable counter."
   ::= {pr1646v2LacpBH24InPEntry 385875968}

pr1646v2LacpBH24InPIfInBandwidth OBJECT-TYPE
   SYNTAX      Integer32
   MAX-ACCESS  read-only
   STATUS      current
   DESCRIPTION
      "Path: lacpBundle.performance.h24Performance.ifInBandwidth

       unit name = bps
       formula = 8 * ; 8 /"
   ::= {pr1646v2LacpBH24InPEntry 268435456}

pr1646v2LacpBH24InPIfOutOctets OBJECT-TYPE
   SYNTAX      Counter64
   MAX-ACCESS  read-only
   STATUS      current
   DESCRIPTION
      "Path: lacpBundle.performance.h24Performance.ifOutOctets

       64 bit unsigned wrappable counter."
   ::= {pr1646v2LacpBH24InPEntry 167772160}

pr1646v2LacpBH24InPIfOutUCPkts OBJECT-TYPE
   SYNTAX      Counter64
   MAX-ACCESS  read-only
   STATUS      current
   DESCRIPTION
      "Path: lacpBundle.performance.h24Performance.ifOutUcastPkts

       64 bit unsigned wrappable counter."
   ::= {pr1646v2LacpBH24InPEntry 184549376}

pr1646v2LacpBH24InPIfOutNUCPkts OBJECT-TYPE
   SYNTAX      Counter64
   MAX-ACCESS  read-only
   STATUS      current
   DESCRIPTION
      "Path: lacpBundle.performance.h24Performance.ifOutNUcastPkts

       64 bit unsigned wrappable counter."
   ::= {pr1646v2LacpBH24InPEntry 201326592}

pr1646v2LacpBH24InPIfOutBCPkts OBJECT-TYPE
   SYNTAX      Counter64
   MAX-ACCESS  read-only
   STATUS      current
   DESCRIPTION
      "Path: lacpBundle.performance.h24Performance.ifOutBcastPkts

       64 bit unsigned wrappable counter."
   ::= {pr1646v2LacpBH24InPEntry 452984832}

pr1646v2LacpBH24InPIfOutMCPkts OBJECT-TYPE
   SYNTAX      Counter64
   MAX-ACCESS  read-only
   STATUS      current
   DESCRIPTION
      "Path: lacpBundle.performance.h24Performance.ifOutMcastPkts

       64 bit unsigned wrappable counter."
   ::= {pr1646v2LacpBH24InPEntry 469762048}

pr1646v2LacpBH24InPIfOutDiscards OBJECT-TYPE
   SYNTAX      Counter64
   MAX-ACCESS  read-only
   STATUS      current
   DESCRIPTION
      "Path: lacpBundle.performance.h24Performance.ifOutDiscards

       64 bit unsigned wrappable counter."
   ::= {pr1646v2LacpBH24InPEntry 218103808}

pr1646v2LacpBH24InPIfOutErrors OBJECT-TYPE
   SYNTAX      Counter64
   MAX-ACCESS  read-only
   STATUS      current
   DESCRIPTION
      "Path: lacpBundle.performance.h24Performance.ifOutErrors

       64 bit unsigned wrappable counter."
   ::= {pr1646v2LacpBH24InPEntry 234881024}

pr1646v2LacpBH24InPOutDropEx OBJECT-TYPE
   SYNTAX      Counter64
   MAX-ACCESS  read-only
   STATUS      current
   DESCRIPTION
      "Path: lacpBundle.performance.h24Performance.ifOutDropLevelExceeded

       64 bit unsigned wrappable counter."
   ::= {pr1646v2LacpBH24InPEntry 352321536}

pr1646v2LacpBH24InPOutDropNoArp OBJECT-TYPE
   SYNTAX      Counter64
   MAX-ACCESS  read-only
   STATUS      current
   DESCRIPTION
      "Path: lacpBundle.performance.h24Performance.ifOutDiscardsNoArp

       64 bit unsigned wrappable counter."
   ::= {pr1646v2LacpBH24InPEntry 369098752}

pr1646v2LacpBH24InPOutDropFilter OBJECT-TYPE
   SYNTAX      Counter64
   MAX-ACCESS  read-only
   STATUS      current
   DESCRIPTION
      "Path: lacpBundle.performance.h24Performance.ifOutDiscardsFilter

       64 bit unsigned wrappable counter."
   ::= {pr1646v2LacpBH24InPEntry 402653184}

pr1646v2LacpBH24InPIfOutBandwidth OBJECT-TYPE
   SYNTAX      Integer32
   MAX-ACCESS  read-only
   STATUS      current
   DESCRIPTION
      "Path: lacpBundle.performance.h24Performance.ifOutBandwidth

       unit name = bps
       formula = 8 * ; 8 /"
   ::= {pr1646v2LacpBH24InPEntry 285212672}

pr1646v2LacpBH24InPIfErrSec OBJECT-TYPE
   SYNTAX      Counter32
   MAX-ACCESS  read-only
   STATUS      current
   DESCRIPTION
      "Path: lacpBundle.performance.h24Performance.ifErrSec

       32 bit unsigned wrappable counter."
   ::= {pr1646v2LacpBH24InPEntry 251658240}


pr1646v2LacpBD7InP OBJECT IDENTIFIER ::= {pr1646v2LacpB 309}

pr1646v2LacpBD7InPSSCTable OBJECT-TYPE
   SYNTAX      SEQUENCE OF Pr1646v2LacpBD7InPEntry
   MAX-ACCESS  not-accessible
   STATUS      current
   DESCRIPTION
      "d7IfInPerformance"
   ::= {pr1646v2LacpBD7InP 1}

pr1646v2LacpBD7InPEntry OBJECT-TYPE
   SYNTAX      Pr1646v2LacpBD7InPEntry
   MAX-ACCESS  not-accessible
   STATUS      current
   DESCRIPTION
      ""
   INDEX      { pr1646v2LacpBD7InPGlobalIx,
                pr1646v2LacpBD7InPTableIx }
   ::= {pr1646v2LacpBD7InPSSCTable 1}

Pr1646v2LacpBD7InPEntry ::=
   SEQUENCE
      {
      pr1646v2LacpBD7InPGlobalIx
         GlobalIndex,
      pr1646v2LacpBD7InPTableIx
         TableIndex,
      pr1646v2LacpBD7InPSysUpTime
         TimeTicks,
      pr1646v2LacpBD7InPIfUpTime
         TimeTicks,
      pr1646v2LacpBD7InPIfStatChanges
         Counter32,
      pr1646v2LacpBD7InPIfInOctets
         Counter64,
      pr1646v2LacpBD7InPIfInUCPkts
         Counter64,
      pr1646v2LacpBD7InPIfInNUCPkts
         Counter64,
      pr1646v2LacpBD7InPIfInBCPkts
         Counter64,
      pr1646v2LacpBD7InPIfInMCPkts
         Counter64,
      pr1646v2LacpBD7InPIfInDiscards
         Counter64,
      pr1646v2LacpBD7InPIfInErrors
         Counter64,
      pr1646v2LacpBD7InPIfInUnkwn
         Counter64,
      pr1646v2LacpBD7InPInDropEx
         Counter64,
      pr1646v2LacpBD7InPInDropNoMac
         Counter64,
      pr1646v2LacpBD7InPInDropNUCast
         Counter64,
      pr1646v2LacpBD7InPInDropFilter
         Counter64,
      pr1646v2LacpBD7InPIfInBandwidth
         Integer32,
      pr1646v2LacpBD7InPIfOutOctets
         Counter64,
      pr1646v2LacpBD7InPIfOutUCPkts
         Counter64,
      pr1646v2LacpBD7InPIfOutNUCPkts
         Counter64,
      pr1646v2LacpBD7InPIfOutBCPkts
         Counter64,
      pr1646v2LacpBD7InPIfOutMCPkts
         Counter64,
      pr1646v2LacpBD7InPIfOutDiscards
         Counter64,
      pr1646v2LacpBD7InPIfOutErrors
         Counter64,
      pr1646v2LacpBD7InPOutDropEx
         Counter64,
      pr1646v2LacpBD7InPOutDropNoArp
         Counter64,
      pr1646v2LacpBD7InPOutDropFilter
         Counter64,
      pr1646v2LacpBD7InPIfOutBandwidth
         Integer32,
      pr1646v2LacpBD7InPIfErrSec
         Counter32
      }

pr1646v2LacpBD7InPGlobalIx OBJECT-TYPE
   SYNTAX      GlobalIndex
   MAX-ACCESS  not-accessible
   STATUS      current
   DESCRIPTION
      "The value of the tlsCntTreeGlobalIndex of the MANAGED OBJECT."
   ::= {pr1646v2LacpBD7InPEntry 10}

pr1646v2LacpBD7InPTableIx OBJECT-TYPE
   SYNTAX      TableIndex
   MAX-ACCESS  not-accessible
   STATUS      current
   DESCRIPTION
      ""
   ::= {pr1646v2LacpBD7InPEntry 11}

pr1646v2LacpBD7InPSysUpTime OBJECT-TYPE
   SYNTAX      TimeTicks
   MAX-ACCESS  read-only
   STATUS      current
   DESCRIPTION
      "Path: lacpBundle.performance.d7Performance.sysUpTime

       Time in centi-second."
   ::= {pr1646v2LacpBD7InPEntry 16777216}

pr1646v2LacpBD7InPIfUpTime OBJECT-TYPE
   SYNTAX      TimeTicks
   MAX-ACCESS  read-only
   STATUS      current
   DESCRIPTION
      "Path: lacpBundle.performance.d7Performance.ifUpTime

       Time in centi-second."
   ::= {pr1646v2LacpBD7InPEntry 33554432}

pr1646v2LacpBD7InPIfStatChanges OBJECT-TYPE
   SYNTAX      Counter32
   MAX-ACCESS  read-only
   STATUS      current
   DESCRIPTION
      "Path: lacpBundle.performance.d7Performance.ifStatusChanges

       32 bit unsigned wrappable counter."
   ::= {pr1646v2LacpBD7InPEntry 50331648}

pr1646v2LacpBD7InPIfInOctets OBJECT-TYPE
   SYNTAX      Counter64
   MAX-ACCESS  read-only
   STATUS      current
   DESCRIPTION
      "Path: lacpBundle.performance.d7Performance.ifInOctets

       64 bit unsigned wrappable counter."
   ::= {pr1646v2LacpBD7InPEntry 67108864}

pr1646v2LacpBD7InPIfInUCPkts OBJECT-TYPE
   SYNTAX      Counter64
   MAX-ACCESS  read-only
   STATUS      current
   DESCRIPTION
      "Path: lacpBundle.performance.d7Performance.ifInUcastPkts

       64 bit unsigned wrappable counter."
   ::= {pr1646v2LacpBD7InPEntry 83886080}

pr1646v2LacpBD7InPIfInNUCPkts OBJECT-TYPE
   SYNTAX      Counter64
   MAX-ACCESS  read-only
   STATUS      current
   DESCRIPTION
      "Path: lacpBundle.performance.d7Performance.ifInNUcastPkts

       64 bit unsigned wrappable counter."
   ::= {pr1646v2LacpBD7InPEntry 100663296}

pr1646v2LacpBD7InPIfInBCPkts OBJECT-TYPE
   SYNTAX      Counter64
   MAX-ACCESS  read-only
   STATUS      current
   DESCRIPTION
      "Path: lacpBundle.performance.d7Performance.ifInBcastPkts

       64 bit unsigned wrappable counter."
   ::= {pr1646v2LacpBD7InPEntry 419430400}

pr1646v2LacpBD7InPIfInMCPkts OBJECT-TYPE
   SYNTAX      Counter64
   MAX-ACCESS  read-only
   STATUS      current
   DESCRIPTION
      "Path: lacpBundle.performance.d7Performance.ifInMcastPkts

       64 bit unsigned wrappable counter."
   ::= {pr1646v2LacpBD7InPEntry 436207616}

pr1646v2LacpBD7InPIfInDiscards OBJECT-TYPE
   SYNTAX      Counter64
   MAX-ACCESS  read-only
   STATUS      current
   DESCRIPTION
      "Path: lacpBundle.performance.d7Performance.ifInDiscards

       64 bit unsigned wrappable counter."
   ::= {pr1646v2LacpBD7InPEntry 117440512}

pr1646v2LacpBD7InPIfInErrors OBJECT-TYPE
   SYNTAX      Counter64
   MAX-ACCESS  read-only
   STATUS      current
   DESCRIPTION
      "Path: lacpBundle.performance.d7Performance.ifInErrors

       64 bit unsigned wrappable counter."
   ::= {pr1646v2LacpBD7InPEntry 134217728}

pr1646v2LacpBD7InPIfInUnkwn OBJECT-TYPE
   SYNTAX      Counter64
   MAX-ACCESS  read-only
   STATUS      current
   DESCRIPTION
      "Path: lacpBundle.performance.d7Performance.ifInUnknownProtos

       64 bit unsigned wrappable counter."
   ::= {pr1646v2LacpBD7InPEntry 150994944}

pr1646v2LacpBD7InPInDropEx OBJECT-TYPE
   SYNTAX      Counter64
   MAX-ACCESS  read-only
   STATUS      current
   DESCRIPTION
      "Path: lacpBundle.performance.d7Performance.ifInDropLevelExceeded

       64 bit unsigned wrappable counter."
   ::= {pr1646v2LacpBD7InPEntry 335544320}

pr1646v2LacpBD7InPInDropNoMac OBJECT-TYPE
   SYNTAX      Counter64
   MAX-ACCESS  read-only
   STATUS      current
   DESCRIPTION
      "Path: lacpBundle.performance.d7Performance.fInDiscardsNoMacFit

       64 bit unsigned wrappable counter."
   ::= {pr1646v2LacpBD7InPEntry 301989888}

pr1646v2LacpBD7InPInDropNUCast OBJECT-TYPE
   SYNTAX      Counter64
   MAX-ACCESS  read-only
   STATUS      current
   DESCRIPTION
      "Path: lacpBundle.performance.d7Performance.fInDiscardsNUCast

       64 bit unsigned wrappable counter."
   ::= {pr1646v2LacpBD7InPEntry 318767104}

pr1646v2LacpBD7InPInDropFilter OBJECT-TYPE
   SYNTAX      Counter64
   MAX-ACCESS  read-only
   STATUS      current
   DESCRIPTION
      "Path: lacpBundle.performance.d7Performance.fInDiscardsFilter

       64 bit unsigned wrappable counter."
   ::= {pr1646v2LacpBD7InPEntry 385875968}

pr1646v2LacpBD7InPIfInBandwidth OBJECT-TYPE
   SYNTAX      Integer32
   MAX-ACCESS  read-only
   STATUS      current
   DESCRIPTION
      "Path: lacpBundle.performance.d7Performance.ifInBandwidth

       unit name = bps
       formula = 8 * ; 8 /"
   ::= {pr1646v2LacpBD7InPEntry 268435456}

pr1646v2LacpBD7InPIfOutOctets OBJECT-TYPE
   SYNTAX      Counter64
   MAX-ACCESS  read-only
   STATUS      current
   DESCRIPTION
      "Path: lacpBundle.performance.d7Performance.ifOutOctets

       64 bit unsigned wrappable counter."
   ::= {pr1646v2LacpBD7InPEntry 167772160}

pr1646v2LacpBD7InPIfOutUCPkts OBJECT-TYPE
   SYNTAX      Counter64
   MAX-ACCESS  read-only
   STATUS      current
   DESCRIPTION
      "Path: lacpBundle.performance.d7Performance.ifOutUcastPkts

       64 bit unsigned wrappable counter."
   ::= {pr1646v2LacpBD7InPEntry 184549376}

pr1646v2LacpBD7InPIfOutNUCPkts OBJECT-TYPE
   SYNTAX      Counter64
   MAX-ACCESS  read-only
   STATUS      current
   DESCRIPTION
      "Path: lacpBundle.performance.d7Performance.ifOutNUcastPkts

       64 bit unsigned wrappable counter."
   ::= {pr1646v2LacpBD7InPEntry 201326592}

pr1646v2LacpBD7InPIfOutBCPkts OBJECT-TYPE
   SYNTAX      Counter64
   MAX-ACCESS  read-only
   STATUS      current
   DESCRIPTION
      "Path: lacpBundle.performance.d7Performance.ifOutBcastPkts

       64 bit unsigned wrappable counter."
   ::= {pr1646v2LacpBD7InPEntry 452984832}

pr1646v2LacpBD7InPIfOutMCPkts OBJECT-TYPE
   SYNTAX      Counter64
   MAX-ACCESS  read-only
   STATUS      current
   DESCRIPTION
      "Path: lacpBundle.performance.d7Performance.ifOutMcastPkts

       64 bit unsigned wrappable counter."
   ::= {pr1646v2LacpBD7InPEntry 469762048}

pr1646v2LacpBD7InPIfOutDiscards OBJECT-TYPE
   SYNTAX      Counter64
   MAX-ACCESS  read-only
   STATUS      current
   DESCRIPTION
      "Path: lacpBundle.performance.d7Performance.ifOutDiscards

       64 bit unsigned wrappable counter."
   ::= {pr1646v2LacpBD7InPEntry 218103808}

pr1646v2LacpBD7InPIfOutErrors OBJECT-TYPE
   SYNTAX      Counter64
   MAX-ACCESS  read-only
   STATUS      current
   DESCRIPTION
      "Path: lacpBundle.performance.d7Performance.ifOutErrors

       64 bit unsigned wrappable counter."
   ::= {pr1646v2LacpBD7InPEntry 234881024}

pr1646v2LacpBD7InPOutDropEx OBJECT-TYPE
   SYNTAX      Counter64
   MAX-ACCESS  read-only
   STATUS      current
   DESCRIPTION
      "Path: lacpBundle.performance.d7Performance.ifOutDropLevelExceeded

       64 bit unsigned wrappable counter."
   ::= {pr1646v2LacpBD7InPEntry 352321536}

pr1646v2LacpBD7InPOutDropNoArp OBJECT-TYPE
   SYNTAX      Counter64
   MAX-ACCESS  read-only
   STATUS      current
   DESCRIPTION
      "Path: lacpBundle.performance.d7Performance.ifOutDiscardsNoArp

       64 bit unsigned wrappable counter."
   ::= {pr1646v2LacpBD7InPEntry 369098752}

pr1646v2LacpBD7InPOutDropFilter OBJECT-TYPE
   SYNTAX      Counter64
   MAX-ACCESS  read-only
   STATUS      current
   DESCRIPTION
      "Path: lacpBundle.performance.d7Performance.ifOutDiscardsFilter

       64 bit unsigned wrappable counter."
   ::= {pr1646v2LacpBD7InPEntry 402653184}

pr1646v2LacpBD7InPIfOutBandwidth OBJECT-TYPE
   SYNTAX      Integer32
   MAX-ACCESS  read-only
   STATUS      current
   DESCRIPTION
      "Path: lacpBundle.performance.d7Performance.ifOutBandwidth

       unit name = bps
       formula = 8 * ; 8 /"
   ::= {pr1646v2LacpBD7InPEntry 285212672}

pr1646v2LacpBD7InPIfErrSec OBJECT-TYPE
   SYNTAX      Counter32
   MAX-ACCESS  read-only
   STATUS      current
   DESCRIPTION
      "Path: lacpBundle.performance.d7Performance.ifErrSec

       32 bit unsigned wrappable counter."
   ::= {pr1646v2LacpBD7InPEntry 251658240}


pr1646v2LacpBVlan OBJECT IDENTIFIER ::= {pr1646v2LacpB 310}

pr1646v2LacpBVlanSSCTable OBJECT-TYPE
   SYNTAX      SEQUENCE OF Pr1646v2LacpBVlanEntry
   MAX-ACCESS  not-accessible
   STATUS      current
   DESCRIPTION
      ""
   ::= {pr1646v2LacpBVlan 1}

pr1646v2LacpBVlanEntry OBJECT-TYPE
   SYNTAX      Pr1646v2LacpBVlanEntry
   MAX-ACCESS  not-accessible
   STATUS      current
   DESCRIPTION
      ""
   INDEX      { pr1646v2LacpBVlanGlobalIx,
                pr1646v2LacpBVlanTableIx }
   ::= {pr1646v2LacpBVlanSSCTable 1}

Pr1646v2LacpBVlanEntry ::=
   SEQUENCE
      {
      pr1646v2LacpBVlanGlobalIx
         GlobalIndex,
      pr1646v2LacpBVlanTableIx
         TableIndex,
      pr1646v2LacpBVlanName
         DisplayString,
      pr1646v2LacpBVlanMCInOctets
         Counter64,
      pr1646v2LacpBVlanMCInUcast
         Counter64,
      pr1646v2LacpBVlanMCInNUcastPkts
         Counter64,
      pr1646v2LacpBVlanMCInBcastPkts
         Counter64,
      pr1646v2LacpBVlanMCInMcastPkts
         Counter64,
      pr1646v2LacpBVlanMCInDiscards
         Counter64,
      pr1646v2LacpBVlanMCInErrors
         Counter64,
      pr1646v2LacpBVlanMCInUnknownProtos
         Counter64,
      pr1646v2LacpBVlanMCInDropEx
         Counter64,
      pr1646v2LacpBVlanMCInDropNoMac
         Counter64,
      pr1646v2LacpBVlanMCInDropNUCast
         Counter64,
      pr1646v2LacpBVlanMCInDropFilter
         Counter64,
      pr1646v2LacpBVlanMCInBandwidth15sec
         Integer32,
      pr1646v2LacpBVlanMCInBandwidth30sec
         Integer32,
      pr1646v2LacpBVlanMCInBandwidth1min
         Integer32,
      pr1646v2LacpBVlanMCInBandwidth2min
         Integer32,
      pr1646v2LacpBVlanMCInBandwidth5min
         Integer32,
      pr1646v2LacpBVlanMCOutOctets
         Counter64,
      pr1646v2LacpBVlanMCOutUcastPkts
         Counter64,
      pr1646v2LacpBVlanMCOutNUcastPkts
         Counter64,
      pr1646v2LacpBVlanMCOutBcastPkts
         Counter64,
      pr1646v2LacpBVlanMCOutMcastPkts
         Counter64,
      pr1646v2LacpBVlanMCOutDiscards
         Counter64,
      pr1646v2LacpBVlanMCOutErrors
         Counter64,
      pr1646v2LacpBVlanMCOutQLen
         Counter32,
      pr1646v2LacpBVlanMCOutDropEx
         Counter64,
      pr1646v2LacpBVlanMCOutDropNoArp
         Counter64,
      pr1646v2LacpBVlanMCOutDropFilter
         Counter64,
      pr1646v2LacpBVlanMCOutBandwidth15sec
         Integer32,
      pr1646v2LacpBVlanMCOutBandwidth30sec
         Integer32,
      pr1646v2LacpBVlanMCOutBandwidth1min
         Integer32,
      pr1646v2LacpBVlanMCOutBandwidth2min
         Integer32,
      pr1646v2LacpBVlanMCOutBandwidth5min
         Integer32,
      pr1646v2LacpBVlanVlanVid
         Integer32,
      pr1646v2LacpBVlanPppLinkMonitoringRequestsSent
         Gauge32,
      pr1646v2LacpBVlanPppLinkMonitoringRepliesRcvd
         Gauge32,
      pr1646v2LacpBVlanPppLinkMonitoringRequestsRcvd
         Gauge32,
      pr1646v2LacpBVlanPppLinkMonitoringRepliesSent
         Gauge32
      }

pr1646v2LacpBVlanGlobalIx OBJECT-TYPE
   SYNTAX      GlobalIndex
   MAX-ACCESS  not-accessible
   STATUS      current
   DESCRIPTION
      "The value of the tlsCntTreeGlobalIndex of the MANAGED OBJECT."
   ::= {pr1646v2LacpBVlanEntry 10}

pr1646v2LacpBVlanTableIx OBJECT-TYPE
   SYNTAX      TableIndex
   MAX-ACCESS  not-accessible
   STATUS      current
   DESCRIPTION
      ""
   ::= {pr1646v2LacpBVlanEntry 11}

pr1646v2LacpBVlanName OBJECT-TYPE
   SYNTAX      DisplayString
   MAX-ACCESS  read-only
   STATUS      current
   DESCRIPTION
      "Path: lacpBundle.performance.vlan.name"
   ::= {pr1646v2LacpBVlanEntry 16777216}

pr1646v2LacpBVlanMCInOctets OBJECT-TYPE
   SYNTAX      Counter64
   MAX-ACCESS  read-only
   STATUS      current
   DESCRIPTION
      "Path: lacpBundle.performance.vlan.mibCounters.ifInOctets

       64 bit unsigned wrappable counter."
   ::= {pr1646v2LacpBVlanEntry 40697856}

pr1646v2LacpBVlanMCInUcast OBJECT-TYPE
   SYNTAX      Counter64
   MAX-ACCESS  read-only
   STATUS      current
   DESCRIPTION
      "Path: lacpBundle.performance.vlan.mibCounters.ifInUcastPkts

       64 bit unsigned wrappable counter."
   ::= {pr1646v2LacpBVlanEntry 40763392}

pr1646v2LacpBVlanMCInNUcastPkts OBJECT-TYPE
   SYNTAX      Counter64
   MAX-ACCESS  read-only
   STATUS      current
   DESCRIPTION
      "Path: lacpBundle.performance.vlan.mibCounters.ifInNUcastPkts

       64 bit unsigned wrappable counter."
   ::= {pr1646v2LacpBVlanEntry 40828928}

pr1646v2LacpBVlanMCInBcastPkts OBJECT-TYPE
   SYNTAX      Counter64
   MAX-ACCESS  read-only
   STATUS      current
   DESCRIPTION
      "Path: lacpBundle.performance.vlan.mibCounters.ifInBcastPkts

       64 bit unsigned wrappable counter."
   ::= {pr1646v2LacpBVlanEntry 47382528}

pr1646v2LacpBVlanMCInMcastPkts OBJECT-TYPE
   SYNTAX      Counter64
   MAX-ACCESS  read-only
   STATUS      current
   DESCRIPTION
      "Path: lacpBundle.performance.vlan.mibCounters.ifInMcastPkts

       64 bit unsigned wrappable counter."
   ::= {pr1646v2LacpBVlanEntry 48037888}

pr1646v2LacpBVlanMCInDiscards OBJECT-TYPE
   SYNTAX      Counter64
   MAX-ACCESS  read-only
   STATUS      current
   DESCRIPTION
      "Path: lacpBundle.performance.vlan.mibCounters.ifInDiscards

       64 bit unsigned wrappable counter."
   ::= {pr1646v2LacpBVlanEntry 40894464}

pr1646v2LacpBVlanMCInErrors OBJECT-TYPE
   SYNTAX      Counter64
   MAX-ACCESS  read-only
   STATUS      current
   DESCRIPTION
      "Path: lacpBundle.performance.vlan.mibCounters.ifInErrors

       64 bit unsigned wrappable counter."
   ::= {pr1646v2LacpBVlanEntry 40960000}

pr1646v2LacpBVlanMCInUnknownProtos OBJECT-TYPE
   SYNTAX      Counter64
   MAX-ACCESS  read-only
   STATUS      current
   DESCRIPTION
      "Path: lacpBundle.performance.vlan.mibCounters.ifInUnknownProtos

       64 bit unsigned wrappable counter."
   ::= {pr1646v2LacpBVlanEntry 41025536}

pr1646v2LacpBVlanMCInDropEx OBJECT-TYPE
   SYNTAX      Counter64
   MAX-ACCESS  read-only
   STATUS      current
   DESCRIPTION
      "Path: lacpBundle.performance.vlan.mibCounters.ifInDropLevelExceeded

       64 bit unsigned wrappable counter."
   ::= {pr1646v2LacpBVlanEntry 42074112}

pr1646v2LacpBVlanMCInDropNoMac OBJECT-TYPE
   SYNTAX      Counter64
   MAX-ACCESS  read-only
   STATUS      current
   DESCRIPTION
      "Path: lacpBundle.performance.vlan.mibCounters.ifInDiscardsNoMacFit

       64 bit unsigned wrappable counter."
   ::= {pr1646v2LacpBVlanEntry 42270720}

pr1646v2LacpBVlanMCInDropNUCast OBJECT-TYPE
   SYNTAX      Counter64
   MAX-ACCESS  read-only
   STATUS      current
   DESCRIPTION
      "Path: lacpBundle.performance.vlan.mibCounters.ifInDiscardsNUCast

       64 bit unsigned wrappable counter."
   ::= {pr1646v2LacpBVlanEntry 42467328}

pr1646v2LacpBVlanMCInDropFilter OBJECT-TYPE
   SYNTAX      Counter64
   MAX-ACCESS  read-only
   STATUS      current
   DESCRIPTION
      "Path: lacpBundle.performance.vlan.mibCounters.ifInDiscardsFilter

       64 bit unsigned wrappable counter."
   ::= {pr1646v2LacpBVlanEntry 42532864}

pr1646v2LacpBVlanMCInBandwidth15sec OBJECT-TYPE
   SYNTAX      Integer32
   MAX-ACCESS  read-only
   STATUS      current
   DESCRIPTION
      "Path: lacpBundle.performance.vlan.mibCounters.ifInBandwidth.15sec

       unit name = bps
       formula = 8 * ; 8 /"
   ::= {pr1646v2LacpBVlanEntry 45417728}

pr1646v2LacpBVlanMCInBandwidth30sec OBJECT-TYPE
   SYNTAX      Integer32
   MAX-ACCESS  read-only
   STATUS      current
   DESCRIPTION
      "Path: lacpBundle.performance.vlan.mibCounters.ifInBandwidth.30sec

       unit name = bps
       formula = 8 * ; 8 /"
   ::= {pr1646v2LacpBVlanEntry 45419008}

pr1646v2LacpBVlanMCInBandwidth1min OBJECT-TYPE
   SYNTAX      Integer32
   MAX-ACCESS  read-only
   STATUS      current
   DESCRIPTION
      "Path: lacpBundle.performance.vlan.mibCounters.ifInBandwidth.1min

       unit name = bps
       formula = 8 * ; 8 /"
   ::= {pr1646v2LacpBVlanEntry 45421568}

pr1646v2LacpBVlanMCInBandwidth2min OBJECT-TYPE
   SYNTAX      Integer32
   MAX-ACCESS  read-only
   STATUS      current
   DESCRIPTION
      "Path: lacpBundle.performance.vlan.mibCounters.ifInBandwidth.2min

       unit name = bps
       formula = 8 * ; 8 /"
   ::= {pr1646v2LacpBVlanEntry 45426688}

pr1646v2LacpBVlanMCInBandwidth5min OBJECT-TYPE
   SYNTAX      Integer32
   MAX-ACCESS  read-only
   STATUS      current
   DESCRIPTION
      "Path: lacpBundle.performance.vlan.mibCounters.ifInBandwidth.5min

       unit name = bps
       formula = 8 * ; 8 /"
   ::= {pr1646v2LacpBVlanEntry 45442048}

pr1646v2LacpBVlanMCOutOctets OBJECT-TYPE
   SYNTAX      Counter64
   MAX-ACCESS  read-only
   STATUS      current
   DESCRIPTION
      "Path: lacpBundle.performance.vlan.mibCounters.ifOutOctets

       64 bit unsigned wrappable counter."
   ::= {pr1646v2LacpBVlanEntry 41091072}

pr1646v2LacpBVlanMCOutUcastPkts OBJECT-TYPE
   SYNTAX      Counter64
   MAX-ACCESS  read-only
   STATUS      current
   DESCRIPTION
      "Path: lacpBundle.performance.vlan.mibCounters.ifOutUcastPkts

       64 bit unsigned wrappable counter."
   ::= {pr1646v2LacpBVlanEntry 41156608}

pr1646v2LacpBVlanMCOutNUcastPkts OBJECT-TYPE
   SYNTAX      Counter64
   MAX-ACCESS  read-only
   STATUS      current
   DESCRIPTION
      "Path: lacpBundle.performance.vlan.mibCounters.ifOutNUcastPkts

       64 bit unsigned wrappable counter."
   ::= {pr1646v2LacpBVlanEntry 41222144}

pr1646v2LacpBVlanMCOutBcastPkts OBJECT-TYPE
   SYNTAX      Counter64
   MAX-ACCESS  read-only
   STATUS      current
   DESCRIPTION
      "Path: lacpBundle.performance.vlan.mibCounters.ifOutBcastPkts

       64 bit unsigned wrappable counter."
   ::= {pr1646v2LacpBVlanEntry 47775744}

pr1646v2LacpBVlanMCOutMcastPkts OBJECT-TYPE
   SYNTAX      Counter64
   MAX-ACCESS  read-only
   STATUS      current
   DESCRIPTION
      "Path: lacpBundle.performance.vlan.mibCounters.ifOutMcastPkts

       64 bit unsigned wrappable counter."
   ::= {pr1646v2LacpBVlanEntry 48431104}

pr1646v2LacpBVlanMCOutDiscards OBJECT-TYPE
   SYNTAX      Counter64
   MAX-ACCESS  read-only
   STATUS      current
   DESCRIPTION
      "Path: lacpBundle.performance.vlan.mibCounters.ifOutDiscards

       64 bit unsigned wrappable counter."
   ::= {pr1646v2LacpBVlanEntry 41287680}

pr1646v2LacpBVlanMCOutErrors OBJECT-TYPE
   SYNTAX      Counter64
   MAX-ACCESS  read-only
   STATUS      current
   DESCRIPTION
      "Path: lacpBundle.performance.vlan.mibCounters.ifOutErrors

       64 bit unsigned wrappable counter."
   ::= {pr1646v2LacpBVlanEntry 41353216}

pr1646v2LacpBVlanMCOutQLen OBJECT-TYPE
   SYNTAX      Counter32
   MAX-ACCESS  read-only
   STATUS      current
   DESCRIPTION
      "Path: lacpBundle.performance.vlan.mibCounters.ifOutQLen

       32 bit unsigned wrappable counter."
   ::= {pr1646v2LacpBVlanEntry 41418752}

pr1646v2LacpBVlanMCOutDropEx OBJECT-TYPE
   SYNTAX      Counter64
   MAX-ACCESS  read-only
   STATUS      current
   DESCRIPTION
      "Path: lacpBundle.performance.vlan.mibCounters.ifOutDropLevelExceeded

       64 bit unsigned wrappable counter."
   ::= {pr1646v2LacpBVlanEntry 41484288}

pr1646v2LacpBVlanMCOutDropNoArp OBJECT-TYPE
   SYNTAX      Counter64
   MAX-ACCESS  read-only
   STATUS      current
   DESCRIPTION
      "Path: lacpBundle.performance.vlan.mibCounters.ifOutDiscardsNoArp

       64 bit unsigned wrappable counter."
   ::= {pr1646v2LacpBVlanEntry 42336256}

pr1646v2LacpBVlanMCOutDropFilter OBJECT-TYPE
   SYNTAX      Counter64
   MAX-ACCESS  read-only
   STATUS      current
   DESCRIPTION
      "Path: lacpBundle.performance.vlan.mibCounters.ifOutDiscardsFilter

       64 bit unsigned wrappable counter."
   ::= {pr1646v2LacpBVlanEntry 42598400}

pr1646v2LacpBVlanMCOutBandwidth15sec OBJECT-TYPE
   SYNTAX      Integer32
   MAX-ACCESS  read-only
   STATUS      current
   DESCRIPTION
      "Path: lacpBundle.performance.vlan.mibCounters.ifOutBandwidth.15sec

       unit name = bps
       formula = 8 * ; 8 /"
   ::= {pr1646v2LacpBVlanEntry 45483264}

pr1646v2LacpBVlanMCOutBandwidth30sec OBJECT-TYPE
   SYNTAX      Integer32
   MAX-ACCESS  read-only
   STATUS      current
   DESCRIPTION
      "Path: lacpBundle.performance.vlan.mibCounters.ifOutBandwidth.30sec

       unit name = bps
       formula = 8 * ; 8 /"
   ::= {pr1646v2LacpBVlanEntry 45484544}

pr1646v2LacpBVlanMCOutBandwidth1min OBJECT-TYPE
   SYNTAX      Integer32
   MAX-ACCESS  read-only
   STATUS      current
   DESCRIPTION
      "Path: lacpBundle.performance.vlan.mibCounters.ifOutBandwidth.1min

       unit name = bps
       formula = 8 * ; 8 /"
   ::= {pr1646v2LacpBVlanEntry 45487104}

pr1646v2LacpBVlanMCOutBandwidth2min OBJECT-TYPE
   SYNTAX      Integer32
   MAX-ACCESS  read-only
   STATUS      current
   DESCRIPTION
      "Path: lacpBundle.performance.vlan.mibCounters.ifOutBandwidth.2min

       unit name = bps
       formula = 8 * ; 8 /"
   ::= {pr1646v2LacpBVlanEntry 45492224}

pr1646v2LacpBVlanMCOutBandwidth5min OBJECT-TYPE
   SYNTAX      Integer32
   MAX-ACCESS  read-only
   STATUS      current
   DESCRIPTION
      "Path: lacpBundle.performance.vlan.mibCounters.ifOutBandwidth.5min

       unit name = bps
       formula = 8 * ; 8 /"
   ::= {pr1646v2LacpBVlanEntry 45507584}

pr1646v2LacpBVlanVlanVid OBJECT-TYPE
   SYNTAX      Integer32
   MAX-ACCESS  read-only
   STATUS      current
   DESCRIPTION
      "Path: lacpBundle.performance.vlan.vlan.vid"
   ::= {pr1646v2LacpBVlanEntry 234946560}

pr1646v2LacpBVlanPppLinkMonitoringRequestsSent OBJECT-TYPE
   SYNTAX      Gauge32
   MAX-ACCESS  read-only
   STATUS      current
   DESCRIPTION
      "Path: lacpBundle.performance.vlan.ppp.linkMonitoring.requestsSent

       32 bit unsigned gauge value."
   ::= {pr1646v2LacpBVlanEntry 50397440}

pr1646v2LacpBVlanPppLinkMonitoringRepliesRcvd OBJECT-TYPE
   SYNTAX      Gauge32
   MAX-ACCESS  read-only
   STATUS      current
   DESCRIPTION
      "Path: lacpBundle.performance.vlan.ppp.linkMonitoring.repliesRcvd

       32 bit unsigned gauge value."
   ::= {pr1646v2LacpBVlanEntry 50397696}

pr1646v2LacpBVlanPppLinkMonitoringRequestsRcvd OBJECT-TYPE
   SYNTAX      Gauge32
   MAX-ACCESS  read-only
   STATUS      current
   DESCRIPTION
      "Path: lacpBundle.performance.vlan.ppp.linkMonitoring.requestsRcvd

       32 bit unsigned gauge value."
   ::= {pr1646v2LacpBVlanEntry 50397952}

pr1646v2LacpBVlanPppLinkMonitoringRepliesSent OBJECT-TYPE
   SYNTAX      Gauge32
   MAX-ACCESS  read-only
   STATUS      current
   DESCRIPTION
      "Path: lacpBundle.performance.vlan.ppp.linkMonitoring.repliesSent

       32 bit unsigned gauge value."
   ::= {pr1646v2LacpBVlanEntry 50398208}

pr1646v2LacpBVlanMCH2P OBJECT-TYPE
   SYNTAX      SEQUENCE OF Pr1646v2LacpBVlanMCH2PEntry
   MAX-ACCESS  not-accessible
   STATUS      current
   DESCRIPTION
      ""
   ::= {pr1646v2LacpBVlan 41549824}

pr1646v2LacpBVlanMCH2PEntry OBJECT-TYPE
   SYNTAX      Pr1646v2LacpBVlanMCH2PEntry
   MAX-ACCESS  not-accessible
   STATUS      current
   DESCRIPTION
      ""
   INDEX      { pr1646v2LacpBVlanMCH2PGlobalIx,
                pr1646v2LacpBVlanTableIx,
                pr1646v2LacpBVlanMCH2PTableIx }
   ::= {pr1646v2LacpBVlanMCH2P 1}

Pr1646v2LacpBVlanMCH2PEntry ::=
   SEQUENCE
      {
      pr1646v2LacpBVlanMCH2PGlobalIx
         GlobalIndex,
      pr1646v2LacpBVlanMCH2PTableIx
         TableIndex,
      pr1646v2LacpBVlanMCH2PSysUpTime
         TimeTicks,
      pr1646v2LacpBVlanMCH2PIfUpTime
         TimeTicks,
      pr1646v2LacpBVlanMCH2PIfStatChanges
         Counter32,
      pr1646v2LacpBVlanMCH2PIfInOctets
         Counter64,
      pr1646v2LacpBVlanMCH2PIfInUCPkts
         Counter64,
      pr1646v2LacpBVlanMCH2PIfInNUCPkts
         Counter64,
      pr1646v2LacpBVlanMCH2PIfInBCPkts
         Counter64,
      pr1646v2LacpBVlanMCH2PIfInMCPkts
         Counter64,
      pr1646v2LacpBVlanMCH2PIfInDiscards
         Counter64,
      pr1646v2LacpBVlanMCH2PIfInErrors
         Counter64,
      pr1646v2LacpBVlanMCH2PIfInUnkwn
         Counter64,
      pr1646v2LacpBVlanMCH2PInDropEx
         Counter64,
      pr1646v2LacpBVlanMCH2PInDropNoMac
         Counter64,
      pr1646v2LacpBVlanMCH2PInDropNUCast
         Counter64,
      pr1646v2LacpBVlanMCH2PInDropFilter
         Counter64,
      pr1646v2LacpBVlanMCH2PIfInBandwidth
         Integer32,
      pr1646v2LacpBVlanMCH2PIfOutOctets
         Counter64,
      pr1646v2LacpBVlanMCH2PIfOutUCPkts
         Counter64,
      pr1646v2LacpBVlanMCH2PIfOutNUCPkts
         Counter64,
      pr1646v2LacpBVlanMCH2PIfOutBCPkts
         Counter64,
      pr1646v2LacpBVlanMCH2PIfOutMCPkts
         Counter64,
      pr1646v2LacpBVlanMCH2PIfOutDiscards
         Counter64,
      pr1646v2LacpBVlanMCH2PIfOutErrors
         Counter64,
      pr1646v2LacpBVlanMCH2POutDropEx
         Counter64,
      pr1646v2LacpBVlanMCH2POutDropNoArp
         Counter64,
      pr1646v2LacpBVlanMCH2POutDropFilter
         Counter64,
      pr1646v2LacpBVlanMCH2PIfOutBandwidth
         Integer32,
      pr1646v2LacpBVlanMCH2PIfErrSec
         Counter32
      }

pr1646v2LacpBVlanMCH2PGlobalIx OBJECT-TYPE
   SYNTAX      GlobalIndex
   MAX-ACCESS  not-accessible
   STATUS      current
   DESCRIPTION
      "The value of the tlsCntTreeGlobalIndex of the MANAGED OBJECT."
   ::= {pr1646v2LacpBVlanMCH2PEntry 10}

pr1646v2LacpBVlanMCH2PTableIx OBJECT-TYPE
   SYNTAX      TableIndex
   MAX-ACCESS  not-accessible
   STATUS      current
   DESCRIPTION
      ""
   ::= {pr1646v2LacpBVlanMCH2PEntry 11}

pr1646v2LacpBVlanMCH2PSysUpTime OBJECT-TYPE
   SYNTAX      TimeTicks
   MAX-ACCESS  read-only
   STATUS      current
   DESCRIPTION
      "Path: lacpBundle.performance.vlan.mibCounters.h2Performance.sysUpTime

       Time in centi-second."
   ::= {pr1646v2LacpBVlanMCH2PEntry 16777216}

pr1646v2LacpBVlanMCH2PIfUpTime OBJECT-TYPE
   SYNTAX      TimeTicks
   MAX-ACCESS  read-only
   STATUS      current
   DESCRIPTION
      "Path: lacpBundle.performance.vlan.mibCounters.h2Performance.ifUpTime

       Time in centi-second."
   ::= {pr1646v2LacpBVlanMCH2PEntry 33554432}

pr1646v2LacpBVlanMCH2PIfStatChanges OBJECT-TYPE
   SYNTAX      Counter32
   MAX-ACCESS  read-only
   STATUS      current
   DESCRIPTION
      "Path: lacpBundle.performance.vlan.mibCounters.h2Performance.ifStatusChanges

       32 bit unsigned wrappable counter."
   ::= {pr1646v2LacpBVlanMCH2PEntry 50331648}

pr1646v2LacpBVlanMCH2PIfInOctets OBJECT-TYPE
   SYNTAX      Counter64
   MAX-ACCESS  read-only
   STATUS      current
   DESCRIPTION
      "Path: lacpBundle.performance.vlan.mibCounters.h2Performance.ifInOctets

       64 bit unsigned wrappable counter."
   ::= {pr1646v2LacpBVlanMCH2PEntry 67108864}

pr1646v2LacpBVlanMCH2PIfInUCPkts OBJECT-TYPE
   SYNTAX      Counter64
   MAX-ACCESS  read-only
   STATUS      current
   DESCRIPTION
      "Path: lacpBundle.performance.vlan.mibCounters.h2Performance.ifInUcastPkts

       64 bit unsigned wrappable counter."
   ::= {pr1646v2LacpBVlanMCH2PEntry 83886080}

pr1646v2LacpBVlanMCH2PIfInNUCPkts OBJECT-TYPE
   SYNTAX      Counter64
   MAX-ACCESS  read-only
   STATUS      current
   DESCRIPTION
      "Path: lacpBundle.performance.vlan.mibCounters.h2Performance.ifInNUcastPkts

       64 bit unsigned wrappable counter."
   ::= {pr1646v2LacpBVlanMCH2PEntry 100663296}

pr1646v2LacpBVlanMCH2PIfInBCPkts OBJECT-TYPE
   SYNTAX      Counter64
   MAX-ACCESS  read-only
   STATUS      current
   DESCRIPTION
      "Path: lacpBundle.performance.vlan.mibCounters.h2Performance.ifInBcastPkts

       64 bit unsigned wrappable counter."
   ::= {pr1646v2LacpBVlanMCH2PEntry 419430400}

pr1646v2LacpBVlanMCH2PIfInMCPkts OBJECT-TYPE
   SYNTAX      Counter64
   MAX-ACCESS  read-only
   STATUS      current
   DESCRIPTION
      "Path: lacpBundle.performance.vlan.mibCounters.h2Performance.ifInMcastPkts

       64 bit unsigned wrappable counter."
   ::= {pr1646v2LacpBVlanMCH2PEntry 436207616}

pr1646v2LacpBVlanMCH2PIfInDiscards OBJECT-TYPE
   SYNTAX      Counter64
   MAX-ACCESS  read-only
   STATUS      current
   DESCRIPTION
      "Path: lacpBundle.performance.vlan.mibCounters.h2Performance.ifInDiscards

       64 bit unsigned wrappable counter."
   ::= {pr1646v2LacpBVlanMCH2PEntry 117440512}

pr1646v2LacpBVlanMCH2PIfInErrors OBJECT-TYPE
   SYNTAX      Counter64
   MAX-ACCESS  read-only
   STATUS      current
   DESCRIPTION
      "Path: lacpBundle.performance.vlan.mibCounters.h2Performance.ifInErrors

       64 bit unsigned wrappable counter."
   ::= {pr1646v2LacpBVlanMCH2PEntry 134217728}

pr1646v2LacpBVlanMCH2PIfInUnkwn OBJECT-TYPE
   SYNTAX      Counter64
   MAX-ACCESS  read-only
   STATUS      current
   DESCRIPTION
      "Path: lacpBundle.performance.vlan.mibCounters.h2Performance.ifInUnknownProtos

       64 bit unsigned wrappable counter."
   ::= {pr1646v2LacpBVlanMCH2PEntry 150994944}

pr1646v2LacpBVlanMCH2PInDropEx OBJECT-TYPE
   SYNTAX      Counter64
   MAX-ACCESS  read-only
   STATUS      current
   DESCRIPTION
      "Path: lacpBundle.performance.vlan.mibCounters.h2Performance.ifInDropLevelExceeded

       64 bit unsigned wrappable counter."
   ::= {pr1646v2LacpBVlanMCH2PEntry 335544320}

pr1646v2LacpBVlanMCH2PInDropNoMac OBJECT-TYPE
   SYNTAX      Counter64
   MAX-ACCESS  read-only
   STATUS      current
   DESCRIPTION
      "Path: lacpBundle.performance.vlan.mibCounters.h2Performance.fInDiscardsNoMacFit

       64 bit unsigned wrappable counter."
   ::= {pr1646v2LacpBVlanMCH2PEntry 301989888}

pr1646v2LacpBVlanMCH2PInDropNUCast OBJECT-TYPE
   SYNTAX      Counter64
   MAX-ACCESS  read-only
   STATUS      current
   DESCRIPTION
      "Path: lacpBundle.performance.vlan.mibCounters.h2Performance.fInDiscardsNUCast

       64 bit unsigned wrappable counter."
   ::= {pr1646v2LacpBVlanMCH2PEntry 318767104}

pr1646v2LacpBVlanMCH2PInDropFilter OBJECT-TYPE
   SYNTAX      Counter64
   MAX-ACCESS  read-only
   STATUS      current
   DESCRIPTION
      "Path: lacpBundle.performance.vlan.mibCounters.h2Performance.fInDiscardsFilter

       64 bit unsigned wrappable counter."
   ::= {pr1646v2LacpBVlanMCH2PEntry 385875968}

pr1646v2LacpBVlanMCH2PIfInBandwidth OBJECT-TYPE
   SYNTAX      Integer32
   MAX-ACCESS  read-only
   STATUS      current
   DESCRIPTION
      "Path: lacpBundle.performance.vlan.mibCounters.h2Performance.ifInBandwidth

       unit name = bps
       formula = 8 * ; 8 /"
   ::= {pr1646v2LacpBVlanMCH2PEntry 268435456}

pr1646v2LacpBVlanMCH2PIfOutOctets OBJECT-TYPE
   SYNTAX      Counter64
   MAX-ACCESS  read-only
   STATUS      current
   DESCRIPTION
      "Path: lacpBundle.performance.vlan.mibCounters.h2Performance.ifOutOctets

       64 bit unsigned wrappable counter."
   ::= {pr1646v2LacpBVlanMCH2PEntry 167772160}

pr1646v2LacpBVlanMCH2PIfOutUCPkts OBJECT-TYPE
   SYNTAX      Counter64
   MAX-ACCESS  read-only
   STATUS      current
   DESCRIPTION
      "Path: lacpBundle.performance.vlan.mibCounters.h2Performance.ifOutUcastPkts

       64 bit unsigned wrappable counter."
   ::= {pr1646v2LacpBVlanMCH2PEntry 184549376}

pr1646v2LacpBVlanMCH2PIfOutNUCPkts OBJECT-TYPE
   SYNTAX      Counter64
   MAX-ACCESS  read-only
   STATUS      current
   DESCRIPTION
      "Path: lacpBundle.performance.vlan.mibCounters.h2Performance.ifOutNUcastPkts

       64 bit unsigned wrappable counter."
   ::= {pr1646v2LacpBVlanMCH2PEntry 201326592}

pr1646v2LacpBVlanMCH2PIfOutBCPkts OBJECT-TYPE
   SYNTAX      Counter64
   MAX-ACCESS  read-only
   STATUS      current
   DESCRIPTION
      "Path: lacpBundle.performance.vlan.mibCounters.h2Performance.ifOutBcastPkts

       64 bit unsigned wrappable counter."
   ::= {pr1646v2LacpBVlanMCH2PEntry 452984832}

pr1646v2LacpBVlanMCH2PIfOutMCPkts OBJECT-TYPE
   SYNTAX      Counter64
   MAX-ACCESS  read-only
   STATUS      current
   DESCRIPTION
      "Path: lacpBundle.performance.vlan.mibCounters.h2Performance.ifOutMcastPkts

       64 bit unsigned wrappable counter."
   ::= {pr1646v2LacpBVlanMCH2PEntry 469762048}

pr1646v2LacpBVlanMCH2PIfOutDiscards OBJECT-TYPE
   SYNTAX      Counter64
   MAX-ACCESS  read-only
   STATUS      current
   DESCRIPTION
      "Path: lacpBundle.performance.vlan.mibCounters.h2Performance.ifOutDiscards

       64 bit unsigned wrappable counter."
   ::= {pr1646v2LacpBVlanMCH2PEntry 218103808}

pr1646v2LacpBVlanMCH2PIfOutErrors OBJECT-TYPE
   SYNTAX      Counter64
   MAX-ACCESS  read-only
   STATUS      current
   DESCRIPTION
      "Path: lacpBundle.performance.vlan.mibCounters.h2Performance.ifOutErrors

       64 bit unsigned wrappable counter."
   ::= {pr1646v2LacpBVlanMCH2PEntry 234881024}

pr1646v2LacpBVlanMCH2POutDropEx OBJECT-TYPE
   SYNTAX      Counter64
   MAX-ACCESS  read-only
   STATUS      current
   DESCRIPTION
      "Path: lacpBundle.performance.vlan.mibCounters.h2Performance.ifOutDropLevelExceeded

       64 bit unsigned wrappable counter."
   ::= {pr1646v2LacpBVlanMCH2PEntry 352321536}

pr1646v2LacpBVlanMCH2POutDropNoArp OBJECT-TYPE
   SYNTAX      Counter64
   MAX-ACCESS  read-only
   STATUS      current
   DESCRIPTION
      "Path: lacpBundle.performance.vlan.mibCounters.h2Performance.ifOutDiscardsNoArp

       64 bit unsigned wrappable counter."
   ::= {pr1646v2LacpBVlanMCH2PEntry 369098752}

pr1646v2LacpBVlanMCH2POutDropFilter OBJECT-TYPE
   SYNTAX      Counter64
   MAX-ACCESS  read-only
   STATUS      current
   DESCRIPTION
      "Path: lacpBundle.performance.vlan.mibCounters.h2Performance.ifOutDiscardsFilter

       64 bit unsigned wrappable counter."
   ::= {pr1646v2LacpBVlanMCH2PEntry 402653184}

pr1646v2LacpBVlanMCH2PIfOutBandwidth OBJECT-TYPE
   SYNTAX      Integer32
   MAX-ACCESS  read-only
   STATUS      current
   DESCRIPTION
      "Path: lacpBundle.performance.vlan.mibCounters.h2Performance.ifOutBandwidth

       unit name = bps
       formula = 8 * ; 8 /"
   ::= {pr1646v2LacpBVlanMCH2PEntry 285212672}

pr1646v2LacpBVlanMCH2PIfErrSec OBJECT-TYPE
   SYNTAX      Counter32
   MAX-ACCESS  read-only
   STATUS      current
   DESCRIPTION
      "Path: lacpBundle.performance.vlan.mibCounters.h2Performance.ifErrSec

       32 bit unsigned wrappable counter."
   ::= {pr1646v2LacpBVlanMCH2PEntry 251658240}

pr1646v2LacpBVlanMCH24P OBJECT-TYPE
   SYNTAX      SEQUENCE OF Pr1646v2LacpBVlanMCH24PEntry
   MAX-ACCESS  not-accessible
   STATUS      current
   DESCRIPTION
      ""
   ::= {pr1646v2LacpBVlan 41615360}

pr1646v2LacpBVlanMCH24PEntry OBJECT-TYPE
   SYNTAX      Pr1646v2LacpBVlanMCH24PEntry
   MAX-ACCESS  not-accessible
   STATUS      current
   DESCRIPTION
      ""
   INDEX      { pr1646v2LacpBVlanMCH24PGlobalIx,
                pr1646v2LacpBVlanTableIx,
                pr1646v2LacpBVlanMCH24PTableIx }
   ::= {pr1646v2LacpBVlanMCH24P 1}

Pr1646v2LacpBVlanMCH24PEntry ::=
   SEQUENCE
      {
      pr1646v2LacpBVlanMCH24PGlobalIx
         GlobalIndex,
      pr1646v2LacpBVlanMCH24PTableIx
         TableIndex,
      pr1646v2LacpBVlanMCH24PSysUpTime
         TimeTicks,
      pr1646v2LacpBVlanMCH24PIfUpTime
         TimeTicks,
      pr1646v2LacpBVlanMCH24PIfStatChanges
         Counter32,
      pr1646v2LacpBVlanMCH24PIfInOctets
         Counter64,
      pr1646v2LacpBVlanMCH24PIfInUCPkts
         Counter64,
      pr1646v2LacpBVlanMCH24PIfInNUCPkts
         Counter64,
      pr1646v2LacpBVlanMCH24PIfInBCPkts
         Counter64,
      pr1646v2LacpBVlanMCH24PIfInMCPkts
         Counter64,
      pr1646v2LacpBVlanMCH24PIfInDiscards
         Counter64,
      pr1646v2LacpBVlanMCH24PIfInErrors
         Counter64,
      pr1646v2LacpBVlanMCH24PIfInUnkwn
         Counter64,
      pr1646v2LacpBVlanMCH24PInDropEx
         Counter64,
      pr1646v2LacpBVlanMCH24PInDropNoMac
         Counter64,
      pr1646v2LacpBVlanMCH24PInDropNUCast
         Counter64,
      pr1646v2LacpBVlanMCH24PInDropFilter
         Counter64,
      pr1646v2LacpBVlanMCH24PIfInBandwidth
         Integer32,
      pr1646v2LacpBVlanMCH24PIfOutOctets
         Counter64,
      pr1646v2LacpBVlanMCH24PIfOutUCPkts
         Counter64,
      pr1646v2LacpBVlanMCH24PIfOutNUCPkts
         Counter64,
      pr1646v2LacpBVlanMCH24PIfOutBCPkts
         Counter64,
      pr1646v2LacpBVlanMCH24PIfOutMCPkts
         Counter64,
      pr1646v2LacpBVlanMCH24PIfOutDiscards
         Counter64,
      pr1646v2LacpBVlanMCH24PIfOutErrors
         Counter64,
      pr1646v2LacpBVlanMCH24POutDropEx
         Counter64,
      pr1646v2LacpBVlanMCH24POutDropNoArp
         Counter64,
      pr1646v2LacpBVlanMCH24POutDropFilter
         Counter64,
      pr1646v2LacpBVlanMCH24PIfOutBandwidth
         Integer32,
      pr1646v2LacpBVlanMCH24PIfErrSec
         Counter32
      }

pr1646v2LacpBVlanMCH24PGlobalIx OBJECT-TYPE
   SYNTAX      GlobalIndex
   MAX-ACCESS  not-accessible
   STATUS      current
   DESCRIPTION
      "The value of the tlsCntTreeGlobalIndex of the MANAGED OBJECT."
   ::= {pr1646v2LacpBVlanMCH24PEntry 10}

pr1646v2LacpBVlanMCH24PTableIx OBJECT-TYPE
   SYNTAX      TableIndex
   MAX-ACCESS  not-accessible
   STATUS      current
   DESCRIPTION
      ""
   ::= {pr1646v2LacpBVlanMCH24PEntry 11}

pr1646v2LacpBVlanMCH24PSysUpTime OBJECT-TYPE
   SYNTAX      TimeTicks
   MAX-ACCESS  read-only
   STATUS      current
   DESCRIPTION
      "Path: lacpBundle.performance.vlan.mibCounters.h24Performance.sysUpTime

       Time in centi-second."
   ::= {pr1646v2LacpBVlanMCH24PEntry 16777216}

pr1646v2LacpBVlanMCH24PIfUpTime OBJECT-TYPE
   SYNTAX      TimeTicks
   MAX-ACCESS  read-only
   STATUS      current
   DESCRIPTION
      "Path: lacpBundle.performance.vlan.mibCounters.h24Performance.ifUpTime

       Time in centi-second."
   ::= {pr1646v2LacpBVlanMCH24PEntry 33554432}

pr1646v2LacpBVlanMCH24PIfStatChanges OBJECT-TYPE
   SYNTAX      Counter32
   MAX-ACCESS  read-only
   STATUS      current
   DESCRIPTION
      "Path: lacpBundle.performance.vlan.mibCounters.h24Performance.ifStatusChanges

       32 bit unsigned wrappable counter."
   ::= {pr1646v2LacpBVlanMCH24PEntry 50331648}

pr1646v2LacpBVlanMCH24PIfInOctets OBJECT-TYPE
   SYNTAX      Counter64
   MAX-ACCESS  read-only
   STATUS      current
   DESCRIPTION
      "Path: lacpBundle.performance.vlan.mibCounters.h24Performance.ifInOctets

       64 bit unsigned wrappable counter."
   ::= {pr1646v2LacpBVlanMCH24PEntry 67108864}

pr1646v2LacpBVlanMCH24PIfInUCPkts OBJECT-TYPE
   SYNTAX      Counter64
   MAX-ACCESS  read-only
   STATUS      current
   DESCRIPTION
      "Path: lacpBundle.performance.vlan.mibCounters.h24Performance.ifInUcastPkts

       64 bit unsigned wrappable counter."
   ::= {pr1646v2LacpBVlanMCH24PEntry 83886080}

pr1646v2LacpBVlanMCH24PIfInNUCPkts OBJECT-TYPE
   SYNTAX      Counter64
   MAX-ACCESS  read-only
   STATUS      current
   DESCRIPTION
      "Path: lacpBundle.performance.vlan.mibCounters.h24Performance.ifInNUcastPkts

       64 bit unsigned wrappable counter."
   ::= {pr1646v2LacpBVlanMCH24PEntry 100663296}

pr1646v2LacpBVlanMCH24PIfInBCPkts OBJECT-TYPE
   SYNTAX      Counter64
   MAX-ACCESS  read-only
   STATUS      current
   DESCRIPTION
      "Path: lacpBundle.performance.vlan.mibCounters.h24Performance.ifInBcastPkts

       64 bit unsigned wrappable counter."
   ::= {pr1646v2LacpBVlanMCH24PEntry 419430400}

pr1646v2LacpBVlanMCH24PIfInMCPkts OBJECT-TYPE
   SYNTAX      Counter64
   MAX-ACCESS  read-only
   STATUS      current
   DESCRIPTION
      "Path: lacpBundle.performance.vlan.mibCounters.h24Performance.ifInMcastPkts

       64 bit unsigned wrappable counter."
   ::= {pr1646v2LacpBVlanMCH24PEntry 436207616}

pr1646v2LacpBVlanMCH24PIfInDiscards OBJECT-TYPE
   SYNTAX      Counter64
   MAX-ACCESS  read-only
   STATUS      current
   DESCRIPTION
      "Path: lacpBundle.performance.vlan.mibCounters.h24Performance.ifInDiscards

       64 bit unsigned wrappable counter."
   ::= {pr1646v2LacpBVlanMCH24PEntry 117440512}

pr1646v2LacpBVlanMCH24PIfInErrors OBJECT-TYPE
   SYNTAX      Counter64
   MAX-ACCESS  read-only
   STATUS      current
   DESCRIPTION
      "Path: lacpBundle.performance.vlan.mibCounters.h24Performance.ifInErrors

       64 bit unsigned wrappable counter."
   ::= {pr1646v2LacpBVlanMCH24PEntry 134217728}

pr1646v2LacpBVlanMCH24PIfInUnkwn OBJECT-TYPE
   SYNTAX      Counter64
   MAX-ACCESS  read-only
   STATUS      current
   DESCRIPTION
      "Path: lacpBundle.performance.vlan.mibCounters.h24Performance.ifInUnknownProtos

       64 bit unsigned wrappable counter."
   ::= {pr1646v2LacpBVlanMCH24PEntry 150994944}

pr1646v2LacpBVlanMCH24PInDropEx OBJECT-TYPE
   SYNTAX      Counter64
   MAX-ACCESS  read-only
   STATUS      current
   DESCRIPTION
      "Path: lacpBundle.performance.vlan.mibCounters.h24Performance.ifInDropLevelExceeded

       64 bit unsigned wrappable counter."
   ::= {pr1646v2LacpBVlanMCH24PEntry 335544320}

pr1646v2LacpBVlanMCH24PInDropNoMac OBJECT-TYPE
   SYNTAX      Counter64
   MAX-ACCESS  read-only
   STATUS      current
   DESCRIPTION
      "Path: lacpBundle.performance.vlan.mibCounters.h24Performance.fInDiscardsNoMacFit

       64 bit unsigned wrappable counter."
   ::= {pr1646v2LacpBVlanMCH24PEntry 301989888}

pr1646v2LacpBVlanMCH24PInDropNUCast OBJECT-TYPE
   SYNTAX      Counter64
   MAX-ACCESS  read-only
   STATUS      current
   DESCRIPTION
      "Path: lacpBundle.performance.vlan.mibCounters.h24Performance.fInDiscardsNUCast

       64 bit unsigned wrappable counter."
   ::= {pr1646v2LacpBVlanMCH24PEntry 318767104}

pr1646v2LacpBVlanMCH24PInDropFilter OBJECT-TYPE
   SYNTAX      Counter64
   MAX-ACCESS  read-only
   STATUS      current
   DESCRIPTION
      "Path: lacpBundle.performance.vlan.mibCounters.h24Performance.fInDiscardsFilter

       64 bit unsigned wrappable counter."
   ::= {pr1646v2LacpBVlanMCH24PEntry 385875968}

pr1646v2LacpBVlanMCH24PIfInBandwidth OBJECT-TYPE
   SYNTAX      Integer32
   MAX-ACCESS  read-only
   STATUS      current
   DESCRIPTION
      "Path: lacpBundle.performance.vlan.mibCounters.h24Performance.ifInBandwidth

       unit name = bps
       formula = 8 * ; 8 /"
   ::= {pr1646v2LacpBVlanMCH24PEntry 268435456}

pr1646v2LacpBVlanMCH24PIfOutOctets OBJECT-TYPE
   SYNTAX      Counter64
   MAX-ACCESS  read-only
   STATUS      current
   DESCRIPTION
      "Path: lacpBundle.performance.vlan.mibCounters.h24Performance.ifOutOctets

       64 bit unsigned wrappable counter."
   ::= {pr1646v2LacpBVlanMCH24PEntry 167772160}

pr1646v2LacpBVlanMCH24PIfOutUCPkts OBJECT-TYPE
   SYNTAX      Counter64
   MAX-ACCESS  read-only
   STATUS      current
   DESCRIPTION
      "Path: lacpBundle.performance.vlan.mibCounters.h24Performance.ifOutUcastPkts

       64 bit unsigned wrappable counter."
   ::= {pr1646v2LacpBVlanMCH24PEntry 184549376}

pr1646v2LacpBVlanMCH24PIfOutNUCPkts OBJECT-TYPE
   SYNTAX      Counter64
   MAX-ACCESS  read-only
   STATUS      current
   DESCRIPTION
      "Path: lacpBundle.performance.vlan.mibCounters.h24Performance.ifOutNUcastPkts

       64 bit unsigned wrappable counter."
   ::= {pr1646v2LacpBVlanMCH24PEntry 201326592}

pr1646v2LacpBVlanMCH24PIfOutBCPkts OBJECT-TYPE
   SYNTAX      Counter64
   MAX-ACCESS  read-only
   STATUS      current
   DESCRIPTION
      "Path: lacpBundle.performance.vlan.mibCounters.h24Performance.ifOutBcastPkts

       64 bit unsigned wrappable counter."
   ::= {pr1646v2LacpBVlanMCH24PEntry 452984832}

pr1646v2LacpBVlanMCH24PIfOutMCPkts OBJECT-TYPE
   SYNTAX      Counter64
   MAX-ACCESS  read-only
   STATUS      current
   DESCRIPTION
      "Path: lacpBundle.performance.vlan.mibCounters.h24Performance.ifOutMcastPkts

       64 bit unsigned wrappable counter."
   ::= {pr1646v2LacpBVlanMCH24PEntry 469762048}

pr1646v2LacpBVlanMCH24PIfOutDiscards OBJECT-TYPE
   SYNTAX      Counter64
   MAX-ACCESS  read-only
   STATUS      current
   DESCRIPTION
      "Path: lacpBundle.performance.vlan.mibCounters.h24Performance.ifOutDiscards

       64 bit unsigned wrappable counter."
   ::= {pr1646v2LacpBVlanMCH24PEntry 218103808}

pr1646v2LacpBVlanMCH24PIfOutErrors OBJECT-TYPE
   SYNTAX      Counter64
   MAX-ACCESS  read-only
   STATUS      current
   DESCRIPTION
      "Path: lacpBundle.performance.vlan.mibCounters.h24Performance.ifOutErrors

       64 bit unsigned wrappable counter."
   ::= {pr1646v2LacpBVlanMCH24PEntry 234881024}

pr1646v2LacpBVlanMCH24POutDropEx OBJECT-TYPE
   SYNTAX      Counter64
   MAX-ACCESS  read-only
   STATUS      current
   DESCRIPTION
      "Path: lacpBundle.performance.vlan.mibCounters.h24Performance.ifOutDropLevelExceeded

       64 bit unsigned wrappable counter."
   ::= {pr1646v2LacpBVlanMCH24PEntry 352321536}

pr1646v2LacpBVlanMCH24POutDropNoArp OBJECT-TYPE
   SYNTAX      Counter64
   MAX-ACCESS  read-only
   STATUS      current
   DESCRIPTION
      "Path: lacpBundle.performance.vlan.mibCounters.h24Performance.ifOutDiscardsNoArp

       64 bit unsigned wrappable counter."
   ::= {pr1646v2LacpBVlanMCH24PEntry 369098752}

pr1646v2LacpBVlanMCH24POutDropFilter OBJECT-TYPE
   SYNTAX      Counter64
   MAX-ACCESS  read-only
   STATUS      current
   DESCRIPTION
      "Path: lacpBundle.performance.vlan.mibCounters.h24Performance.ifOutDiscardsFilter

       64 bit unsigned wrappable counter."
   ::= {pr1646v2LacpBVlanMCH24PEntry 402653184}

pr1646v2LacpBVlanMCH24PIfOutBandwidth OBJECT-TYPE
   SYNTAX      Integer32
   MAX-ACCESS  read-only
   STATUS      current
   DESCRIPTION
      "Path: lacpBundle.performance.vlan.mibCounters.h24Performance.ifOutBandwidth

       unit name = bps
       formula = 8 * ; 8 /"
   ::= {pr1646v2LacpBVlanMCH24PEntry 285212672}

pr1646v2LacpBVlanMCH24PIfErrSec OBJECT-TYPE
   SYNTAX      Counter32
   MAX-ACCESS  read-only
   STATUS      current
   DESCRIPTION
      "Path: lacpBundle.performance.vlan.mibCounters.h24Performance.ifErrSec

       32 bit unsigned wrappable counter."
   ::= {pr1646v2LacpBVlanMCH24PEntry 251658240}

pr1646v2LacpBVlanMCD7P OBJECT-TYPE
   SYNTAX      SEQUENCE OF Pr1646v2LacpBVlanMCD7PEntry
   MAX-ACCESS  not-accessible
   STATUS      current
   DESCRIPTION
      ""
   ::= {pr1646v2LacpBVlan 41680896}

pr1646v2LacpBVlanMCD7PEntry OBJECT-TYPE
   SYNTAX      Pr1646v2LacpBVlanMCD7PEntry
   MAX-ACCESS  not-accessible
   STATUS      current
   DESCRIPTION
      ""
   INDEX      { pr1646v2LacpBVlanMCD7PGlobalIx,
                pr1646v2LacpBVlanTableIx,
                pr1646v2LacpBVlanMCD7PTableIx }
   ::= {pr1646v2LacpBVlanMCD7P 1}

Pr1646v2LacpBVlanMCD7PEntry ::=
   SEQUENCE
      {
      pr1646v2LacpBVlanMCD7PGlobalIx
         GlobalIndex,
      pr1646v2LacpBVlanMCD7PTableIx
         TableIndex,
      pr1646v2LacpBVlanMCD7PSysUpTime
         TimeTicks,
      pr1646v2LacpBVlanMCD7PIfUpTime
         TimeTicks,
      pr1646v2LacpBVlanMCD7PIfStatChanges
         Counter32,
      pr1646v2LacpBVlanMCD7PIfInOctets
         Counter64,
      pr1646v2LacpBVlanMCD7PIfInUCPkts
         Counter64,
      pr1646v2LacpBVlanMCD7PIfInNUCPkts
         Counter64,
      pr1646v2LacpBVlanMCD7PIfInBCPkts
         Counter64,
      pr1646v2LacpBVlanMCD7PIfInMCPkts
         Counter64,
      pr1646v2LacpBVlanMCD7PIfInDiscards
         Counter64,
      pr1646v2LacpBVlanMCD7PIfInErrors
         Counter64,
      pr1646v2LacpBVlanMCD7PIfInUnkwn
         Counter64,
      pr1646v2LacpBVlanMCD7PInDropEx
         Counter64,
      pr1646v2LacpBVlanMCD7PInDropNoMac
         Counter64,
      pr1646v2LacpBVlanMCD7PInDropNUCast
         Counter64,
      pr1646v2LacpBVlanMCD7PInDropFilter
         Counter64,
      pr1646v2LacpBVlanMCD7PIfInBandwidth
         Integer32,
      pr1646v2LacpBVlanMCD7PIfOutOctets
         Counter64,
      pr1646v2LacpBVlanMCD7PIfOutUCPkts
         Counter64,
      pr1646v2LacpBVlanMCD7PIfOutNUCPkts
         Counter64,
      pr1646v2LacpBVlanMCD7PIfOutBCPkts
         Counter64,
      pr1646v2LacpBVlanMCD7PIfOutMCPkts
         Counter64,
      pr1646v2LacpBVlanMCD7PIfOutDiscards
         Counter64,
      pr1646v2LacpBVlanMCD7PIfOutErrors
         Counter64,
      pr1646v2LacpBVlanMCD7POutDropEx
         Counter64,
      pr1646v2LacpBVlanMCD7POutDropNoArp
         Counter64,
      pr1646v2LacpBVlanMCD7POutDropFilter
         Counter64,
      pr1646v2LacpBVlanMCD7PIfOutBandwidth
         Integer32,
      pr1646v2LacpBVlanMCD7PIfErrSec
         Counter32
      }

pr1646v2LacpBVlanMCD7PGlobalIx OBJECT-TYPE
   SYNTAX      GlobalIndex
   MAX-ACCESS  not-accessible
   STATUS      current
   DESCRIPTION
      "The value of the tlsCntTreeGlobalIndex of the MANAGED OBJECT."
   ::= {pr1646v2LacpBVlanMCD7PEntry 10}

pr1646v2LacpBVlanMCD7PTableIx OBJECT-TYPE
   SYNTAX      TableIndex
   MAX-ACCESS  not-accessible
   STATUS      current
   DESCRIPTION
      ""
   ::= {pr1646v2LacpBVlanMCD7PEntry 11}

pr1646v2LacpBVlanMCD7PSysUpTime OBJECT-TYPE
   SYNTAX      TimeTicks
   MAX-ACCESS  read-only
   STATUS      current
   DESCRIPTION
      "Path: lacpBundle.performance.vlan.mibCounters.d7Performance.sysUpTime

       Time in centi-second."
   ::= {pr1646v2LacpBVlanMCD7PEntry 16777216}

pr1646v2LacpBVlanMCD7PIfUpTime OBJECT-TYPE
   SYNTAX      TimeTicks
   MAX-ACCESS  read-only
   STATUS      current
   DESCRIPTION
      "Path: lacpBundle.performance.vlan.mibCounters.d7Performance.ifUpTime

       Time in centi-second."
   ::= {pr1646v2LacpBVlanMCD7PEntry 33554432}

pr1646v2LacpBVlanMCD7PIfStatChanges OBJECT-TYPE
   SYNTAX      Counter32
   MAX-ACCESS  read-only
   STATUS      current
   DESCRIPTION
      "Path: lacpBundle.performance.vlan.mibCounters.d7Performance.ifStatusChanges

       32 bit unsigned wrappable counter."
   ::= {pr1646v2LacpBVlanMCD7PEntry 50331648}

pr1646v2LacpBVlanMCD7PIfInOctets OBJECT-TYPE
   SYNTAX      Counter64
   MAX-ACCESS  read-only
   STATUS      current
   DESCRIPTION
      "Path: lacpBundle.performance.vlan.mibCounters.d7Performance.ifInOctets

       64 bit unsigned wrappable counter."
   ::= {pr1646v2LacpBVlanMCD7PEntry 67108864}

pr1646v2LacpBVlanMCD7PIfInUCPkts OBJECT-TYPE
   SYNTAX      Counter64
   MAX-ACCESS  read-only
   STATUS      current
   DESCRIPTION
      "Path: lacpBundle.performance.vlan.mibCounters.d7Performance.ifInUcastPkts

       64 bit unsigned wrappable counter."
   ::= {pr1646v2LacpBVlanMCD7PEntry 83886080}

pr1646v2LacpBVlanMCD7PIfInNUCPkts OBJECT-TYPE
   SYNTAX      Counter64
   MAX-ACCESS  read-only
   STATUS      current
   DESCRIPTION
      "Path: lacpBundle.performance.vlan.mibCounters.d7Performance.ifInNUcastPkts

       64 bit unsigned wrappable counter."
   ::= {pr1646v2LacpBVlanMCD7PEntry 100663296}

pr1646v2LacpBVlanMCD7PIfInBCPkts OBJECT-TYPE
   SYNTAX      Counter64
   MAX-ACCESS  read-only
   STATUS      current
   DESCRIPTION
      "Path: lacpBundle.performance.vlan.mibCounters.d7Performance.ifInBcastPkts

       64 bit unsigned wrappable counter."
   ::= {pr1646v2LacpBVlanMCD7PEntry 419430400}

pr1646v2LacpBVlanMCD7PIfInMCPkts OBJECT-TYPE
   SYNTAX      Counter64
   MAX-ACCESS  read-only
   STATUS      current
   DESCRIPTION
      "Path: lacpBundle.performance.vlan.mibCounters.d7Performance.ifInMcastPkts

       64 bit unsigned wrappable counter."
   ::= {pr1646v2LacpBVlanMCD7PEntry 436207616}

pr1646v2LacpBVlanMCD7PIfInDiscards OBJECT-TYPE
   SYNTAX      Counter64
   MAX-ACCESS  read-only
   STATUS      current
   DESCRIPTION
      "Path: lacpBundle.performance.vlan.mibCounters.d7Performance.ifInDiscards

       64 bit unsigned wrappable counter."
   ::= {pr1646v2LacpBVlanMCD7PEntry 117440512}

pr1646v2LacpBVlanMCD7PIfInErrors OBJECT-TYPE
   SYNTAX      Counter64
   MAX-ACCESS  read-only
   STATUS      current
   DESCRIPTION
      "Path: lacpBundle.performance.vlan.mibCounters.d7Performance.ifInErrors

       64 bit unsigned wrappable counter."
   ::= {pr1646v2LacpBVlanMCD7PEntry 134217728}

pr1646v2LacpBVlanMCD7PIfInUnkwn OBJECT-TYPE
   SYNTAX      Counter64
   MAX-ACCESS  read-only
   STATUS      current
   DESCRIPTION
      "Path: lacpBundle.performance.vlan.mibCounters.d7Performance.ifInUnknownProtos

       64 bit unsigned wrappable counter."
   ::= {pr1646v2LacpBVlanMCD7PEntry 150994944}

pr1646v2LacpBVlanMCD7PInDropEx OBJECT-TYPE
   SYNTAX      Counter64
   MAX-ACCESS  read-only
   STATUS      current
   DESCRIPTION
      "Path: lacpBundle.performance.vlan.mibCounters.d7Performance.ifInDropLevelExceeded

       64 bit unsigned wrappable counter."
   ::= {pr1646v2LacpBVlanMCD7PEntry 335544320}

pr1646v2LacpBVlanMCD7PInDropNoMac OBJECT-TYPE
   SYNTAX      Counter64
   MAX-ACCESS  read-only
   STATUS      current
   DESCRIPTION
      "Path: lacpBundle.performance.vlan.mibCounters.d7Performance.fInDiscardsNoMacFit

       64 bit unsigned wrappable counter."
   ::= {pr1646v2LacpBVlanMCD7PEntry 301989888}

pr1646v2LacpBVlanMCD7PInDropNUCast OBJECT-TYPE
   SYNTAX      Counter64
   MAX-ACCESS  read-only
   STATUS      current
   DESCRIPTION
      "Path: lacpBundle.performance.vlan.mibCounters.d7Performance.fInDiscardsNUCast

       64 bit unsigned wrappable counter."
   ::= {pr1646v2LacpBVlanMCD7PEntry 318767104}

pr1646v2LacpBVlanMCD7PInDropFilter OBJECT-TYPE
   SYNTAX      Counter64
   MAX-ACCESS  read-only
   STATUS      current
   DESCRIPTION
      "Path: lacpBundle.performance.vlan.mibCounters.d7Performance.fInDiscardsFilter

       64 bit unsigned wrappable counter."
   ::= {pr1646v2LacpBVlanMCD7PEntry 385875968}

pr1646v2LacpBVlanMCD7PIfInBandwidth OBJECT-TYPE
   SYNTAX      Integer32
   MAX-ACCESS  read-only
   STATUS      current
   DESCRIPTION
      "Path: lacpBundle.performance.vlan.mibCounters.d7Performance.ifInBandwidth

       unit name = bps
       formula = 8 * ; 8 /"
   ::= {pr1646v2LacpBVlanMCD7PEntry 268435456}

pr1646v2LacpBVlanMCD7PIfOutOctets OBJECT-TYPE
   SYNTAX      Counter64
   MAX-ACCESS  read-only
   STATUS      current
   DESCRIPTION
      "Path: lacpBundle.performance.vlan.mibCounters.d7Performance.ifOutOctets

       64 bit unsigned wrappable counter."
   ::= {pr1646v2LacpBVlanMCD7PEntry 167772160}

pr1646v2LacpBVlanMCD7PIfOutUCPkts OBJECT-TYPE
   SYNTAX      Counter64
   MAX-ACCESS  read-only
   STATUS      current
   DESCRIPTION
      "Path: lacpBundle.performance.vlan.mibCounters.d7Performance.ifOutUcastPkts

       64 bit unsigned wrappable counter."
   ::= {pr1646v2LacpBVlanMCD7PEntry 184549376}

pr1646v2LacpBVlanMCD7PIfOutNUCPkts OBJECT-TYPE
   SYNTAX      Counter64
   MAX-ACCESS  read-only
   STATUS      current
   DESCRIPTION
      "Path: lacpBundle.performance.vlan.mibCounters.d7Performance.ifOutNUcastPkts

       64 bit unsigned wrappable counter."
   ::= {pr1646v2LacpBVlanMCD7PEntry 201326592}

pr1646v2LacpBVlanMCD7PIfOutBCPkts OBJECT-TYPE
   SYNTAX      Counter64
   MAX-ACCESS  read-only
   STATUS      current
   DESCRIPTION
      "Path: lacpBundle.performance.vlan.mibCounters.d7Performance.ifOutBcastPkts

       64 bit unsigned wrappable counter."
   ::= {pr1646v2LacpBVlanMCD7PEntry 452984832}

pr1646v2LacpBVlanMCD7PIfOutMCPkts OBJECT-TYPE
   SYNTAX      Counter64
   MAX-ACCESS  read-only
   STATUS      current
   DESCRIPTION
      "Path: lacpBundle.performance.vlan.mibCounters.d7Performance.ifOutMcastPkts

       64 bit unsigned wrappable counter."
   ::= {pr1646v2LacpBVlanMCD7PEntry 469762048}

pr1646v2LacpBVlanMCD7PIfOutDiscards OBJECT-TYPE
   SYNTAX      Counter64
   MAX-ACCESS  read-only
   STATUS      current
   DESCRIPTION
      "Path: lacpBundle.performance.vlan.mibCounters.d7Performance.ifOutDiscards

       64 bit unsigned wrappable counter."
   ::= {pr1646v2LacpBVlanMCD7PEntry 218103808}

pr1646v2LacpBVlanMCD7PIfOutErrors OBJECT-TYPE
   SYNTAX      Counter64
   MAX-ACCESS  read-only
   STATUS      current
   DESCRIPTION
      "Path: lacpBundle.performance.vlan.mibCounters.d7Performance.ifOutErrors

       64 bit unsigned wrappable counter."
   ::= {pr1646v2LacpBVlanMCD7PEntry 234881024}

pr1646v2LacpBVlanMCD7POutDropEx OBJECT-TYPE
   SYNTAX      Counter64
   MAX-ACCESS  read-only
   STATUS      current
   DESCRIPTION
      "Path: lacpBundle.performance.vlan.mibCounters.d7Performance.ifOutDropLevelExceeded

       64 bit unsigned wrappable counter."
   ::= {pr1646v2LacpBVlanMCD7PEntry 352321536}

pr1646v2LacpBVlanMCD7POutDropNoArp OBJECT-TYPE
   SYNTAX      Counter64
   MAX-ACCESS  read-only
   STATUS      current
   DESCRIPTION
      "Path: lacpBundle.performance.vlan.mibCounters.d7Performance.ifOutDiscardsNoArp

       64 bit unsigned wrappable counter."
   ::= {pr1646v2LacpBVlanMCD7PEntry 369098752}

pr1646v2LacpBVlanMCD7POutDropFilter OBJECT-TYPE
   SYNTAX      Counter64
   MAX-ACCESS  read-only
   STATUS      current
   DESCRIPTION
      "Path: lacpBundle.performance.vlan.mibCounters.d7Performance.ifOutDiscardsFilter

       64 bit unsigned wrappable counter."
   ::= {pr1646v2LacpBVlanMCD7PEntry 402653184}

pr1646v2LacpBVlanMCD7PIfOutBandwidth OBJECT-TYPE
   SYNTAX      Integer32
   MAX-ACCESS  read-only
   STATUS      current
   DESCRIPTION
      "Path: lacpBundle.performance.vlan.mibCounters.d7Performance.ifOutBandwidth

       unit name = bps
       formula = 8 * ; 8 /"
   ::= {pr1646v2LacpBVlanMCD7PEntry 285212672}

pr1646v2LacpBVlanMCD7PIfErrSec OBJECT-TYPE
   SYNTAX      Counter32
   MAX-ACCESS  read-only
   STATUS      current
   DESCRIPTION
      "Path: lacpBundle.performance.vlan.mibCounters.d7Performance.ifErrSec

       32 bit unsigned wrappable counter."
   ::= {pr1646v2LacpBVlanMCD7PEntry 251658240}

pr1646v2LacpBVlanInPQs OBJECT-TYPE
   SYNTAX      SEQUENCE OF Pr1646v2LacpBVlanInPQsEntry
   MAX-ACCESS  not-accessible
   STATUS      current
   DESCRIPTION
      ""
   ::= {pr1646v2LacpBVlan 100663296}

pr1646v2LacpBVlanInPQsEntry OBJECT-TYPE
   SYNTAX      Pr1646v2LacpBVlanInPQsEntry
   MAX-ACCESS  not-accessible
   STATUS      current
   DESCRIPTION
      ""
   INDEX      { pr1646v2LacpBVlanInPQsGlobalIx,
                pr1646v2LacpBVlanTableIx,
                pr1646v2LacpBVlanInPQsTableIx }
   ::= {pr1646v2LacpBVlanInPQs 1}

Pr1646v2LacpBVlanInPQsEntry ::=
   SEQUENCE
      {
      pr1646v2LacpBVlanInPQsGlobalIx
         GlobalIndex,
      pr1646v2LacpBVlanInPQsTableIx
         TableIndex,
      pr1646v2LacpBVlanInPQsName
         INTEGER,
      pr1646v2LacpBVlanInPQsLength
         Integer32,
      pr1646v2LacpBVlanInPQsOctetLength
         Integer32,
      pr1646v2LacpBVlanInPQsRedLength
         Integer32,
      pr1646v2LacpBVlanInPQsPacketsTotal
         Counter64,
      pr1646v2LacpBVlanInPQsPacketsDirectTx
         Counter64,
      pr1646v2LacpBVlanInPQsPacketsQueued
         Counter64,
      pr1646v2LacpBVlanInPQsPacketsDropped
         Counter64,
      pr1646v2LacpBVlanInPQsPacketsRedDropped
         Counter64,
      pr1646v2LacpBVlanInPQsPacketsCirTx
         Counter64,
      pr1646v2LacpBVlanInPQsPacketsEirTx
         Counter64,
      pr1646v2LacpBVlanInPQsPacketsViolateTx
         Counter64,
      pr1646v2LacpBVlanInPQsOctetsTotal
         Counter64,
      pr1646v2LacpBVlanInPQsOctetsDirectTx
         Counter64,
      pr1646v2LacpBVlanInPQsOctetsQueued
         Counter64,
      pr1646v2LacpBVlanInPQsOctetsDropped
         Counter64,
      pr1646v2LacpBVlanInPQsOctetsRedDropped
         Counter64,
      pr1646v2LacpBVlanInPQsOctetsCirTx
         Counter64,
      pr1646v2LacpBVlanInPQsOctetsEirTx
         Counter64,
      pr1646v2LacpBVlanInPQsOctetsViolateTx
         Counter64,
      pr1646v2LacpBVlanInPQsOctetsBandwidth15sec
         Integer32,
      pr1646v2LacpBVlanInPQsOctetsBandwidth30sec
         Integer32,
      pr1646v2LacpBVlanInPQsOctetsBandwidth1min
         Integer32,
      pr1646v2LacpBVlanInPQsOctetsBandwidth2min
         Integer32,
      pr1646v2LacpBVlanInPQsOctetsBandwidth5min
         Integer32
      }

pr1646v2LacpBVlanInPQsGlobalIx OBJECT-TYPE
   SYNTAX      GlobalIndex
   MAX-ACCESS  not-accessible
   STATUS      current
   DESCRIPTION
      "The value of the tlsCntTreeGlobalIndex of the MANAGED OBJECT."
   ::= {pr1646v2LacpBVlanInPQsEntry 10}

pr1646v2LacpBVlanInPQsTableIx OBJECT-TYPE
   SYNTAX      TableIndex
   MAX-ACCESS  not-accessible
   STATUS      current
   DESCRIPTION
      ""
   ::= {pr1646v2LacpBVlanInPQsEntry 11}

pr1646v2LacpBVlanInPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: lacpBundle.performance.vlan.inPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2LacpBVlanInPQsEntry 16777216}

pr1646v2LacpBVlanInPQsLength OBJECT-TYPE
   SYNTAX      Integer32
   MAX-ACCESS  read-only
   STATUS      current
   DESCRIPTION
      "Path: lacpBundle.performance.vlan.inPriorityQueues.length"
   ::= {pr1646v2LacpBVlanInPQsEntry 33554432}

pr1646v2LacpBVlanInPQsOctetLength OBJECT-TYPE
   SYNTAX      Integer32
   MAX-ACCESS  read-only
   STATUS      current
   DESCRIPTION
      "Path: lacpBundle.performance.vlan.inPriorityQueues.octetLength"
   ::= {pr1646v2LacpBVlanInPQsEntry 150994944}

pr1646v2LacpBVlanInPQsRedLength OBJECT-TYPE
   SYNTAX      Integer32
   MAX-ACCESS  read-only
   STATUS      current
   DESCRIPTION
      "Path: lacpBundle.performance.vlan.inPriorityQueues.redLength"
   ::= {pr1646v2LacpBVlanInPQsEntry 134217728}

pr1646v2LacpBVlanInPQsPacketsTotal OBJECT-TYPE
   SYNTAX      Counter64
   MAX-ACCESS  read-only
   STATUS      current
   DESCRIPTION
      "Path: lacpBundle.performance.vlan.inPriorityQueues.packets.total

       64 bit unsigned wrappable counter."
   ::= {pr1646v2LacpBVlanInPQsEntry 50790400}

pr1646v2LacpBVlanInPQsPacketsDirectTx OBJECT-TYPE
   SYNTAX      Counter64
   MAX-ACCESS  read-only
   STATUS      current
   DESCRIPTION
      "Path: lacpBundle.performance.vlan.inPriorityQueues.packets.directTx

       64 bit unsigned wrappable counter."
   ::= {pr1646v2LacpBVlanInPQsEntry 50397184}

pr1646v2LacpBVlanInPQsPacketsQueued OBJECT-TYPE
   SYNTAX      Counter64
   MAX-ACCESS  read-only
   STATUS      current
   DESCRIPTION
      "Path: lacpBundle.performance.vlan.inPriorityQueues.packets.queued

       64 bit unsigned wrappable counter."
   ::= {pr1646v2LacpBVlanInPQsEntry 50462720}

pr1646v2LacpBVlanInPQsPacketsDropped OBJECT-TYPE
   SYNTAX      Counter64
   MAX-ACCESS  read-only
   STATUS      current
   DESCRIPTION
      "Path: lacpBundle.performance.vlan.inPriorityQueues.packets.dropped

       64 bit unsigned wrappable counter."
   ::= {pr1646v2LacpBVlanInPQsEntry 50528256}

pr1646v2LacpBVlanInPQsPacketsRedDropped OBJECT-TYPE
   SYNTAX      Counter64
   MAX-ACCESS  read-only
   STATUS      current
   DESCRIPTION
      "Path: lacpBundle.performance.vlan.inPriorityQueues.packets.redDropped

       64 bit unsigned wrappable counter."
   ::= {pr1646v2LacpBVlanInPQsEntry 50724864}

pr1646v2LacpBVlanInPQsPacketsCirTx OBJECT-TYPE
   SYNTAX      Counter64
   MAX-ACCESS  read-only
   STATUS      current
   DESCRIPTION
      "Path: lacpBundle.performance.vlan.inPriorityQueues.packets.cirTx

       64 bit unsigned wrappable counter."
   ::= {pr1646v2LacpBVlanInPQsEntry 50593792}

pr1646v2LacpBVlanInPQsPacketsEirTx OBJECT-TYPE
   SYNTAX      Counter64
   MAX-ACCESS  read-only
   STATUS      current
   DESCRIPTION
      "Path: lacpBundle.performance.vlan.inPriorityQueues.packets.eirTx

       64 bit unsigned wrappable counter."
   ::= {pr1646v2LacpBVlanInPQsEntry 50659328}

pr1646v2LacpBVlanInPQsPacketsViolateTx OBJECT-TYPE
   SYNTAX      Counter64
   MAX-ACCESS  read-only
   STATUS      current
   DESCRIPTION
      "Path: lacpBundle.performance.vlan.inPriorityQueues.packets.violateTx

       64 bit unsigned wrappable counter."
   ::= {pr1646v2LacpBVlanInPQsEntry 50855936}

pr1646v2LacpBVlanInPQsOctetsTotal OBJECT-TYPE
   SYNTAX      Counter64
   MAX-ACCESS  read-only
   STATUS      current
   DESCRIPTION
      "Path: lacpBundle.performance.vlan.inPriorityQueues.octets.total

       64 bit unsigned wrappable counter."
   ::= {pr1646v2LacpBVlanInPQsEntry 67567616}

pr1646v2LacpBVlanInPQsOctetsDirectTx OBJECT-TYPE
   SYNTAX      Counter64
   MAX-ACCESS  read-only
   STATUS      current
   DESCRIPTION
      "Path: lacpBundle.performance.vlan.inPriorityQueues.octets.directTx

       64 bit unsigned wrappable counter."
   ::= {pr1646v2LacpBVlanInPQsEntry 67174400}

pr1646v2LacpBVlanInPQsOctetsQueued OBJECT-TYPE
   SYNTAX      Counter64
   MAX-ACCESS  read-only
   STATUS      current
   DESCRIPTION
      "Path: lacpBundle.performance.vlan.inPriorityQueues.octets.queued

       64 bit unsigned wrappable counter."
   ::= {pr1646v2LacpBVlanInPQsEntry 67239936}

pr1646v2LacpBVlanInPQsOctetsDropped OBJECT-TYPE
   SYNTAX      Counter64
   MAX-ACCESS  read-only
   STATUS      current
   DESCRIPTION
      "Path: lacpBundle.performance.vlan.inPriorityQueues.octets.dropped

       64 bit unsigned wrappable counter."
   ::= {pr1646v2LacpBVlanInPQsEntry 67305472}

pr1646v2LacpBVlanInPQsOctetsRedDropped OBJECT-TYPE
   SYNTAX      Counter64
   MAX-ACCESS  read-only
   STATUS      current
   DESCRIPTION
      "Path: lacpBundle.performance.vlan.inPriorityQueues.octets.redDropped

       64 bit unsigned wrappable counter."
   ::= {pr1646v2LacpBVlanInPQsEntry 67502080}

pr1646v2LacpBVlanInPQsOctetsCirTx OBJECT-TYPE
   SYNTAX      Counter64
   MAX-ACCESS  read-only
   STATUS      current
   DESCRIPTION
      "Path: lacpBundle.performance.vlan.inPriorityQueues.octets.cirTx

       64 bit unsigned wrappable counter."
   ::= {pr1646v2LacpBVlanInPQsEntry 67371008}

pr1646v2LacpBVlanInPQsOctetsEirTx OBJECT-TYPE
   SYNTAX      Counter64
   MAX-ACCESS  read-only
   STATUS      current
   DESCRIPTION
      "Path: lacpBundle.performance.vlan.inPriorityQueues.octets.eirTx

       64 bit unsigned wrappable counter."
   ::= {pr1646v2LacpBVlanInPQsEntry 67436544}

pr1646v2LacpBVlanInPQsOctetsViolateTx OBJECT-TYPE
   SYNTAX      Counter64
   MAX-ACCESS  read-only
   STATUS      current
   DESCRIPTION
      "Path: lacpBundle.performance.vlan.inPriorityQueues.octets.violateTx

       64 bit unsigned wrappable counter."
   ::= {pr1646v2LacpBVlanInPQsEntry 67633152}

pr1646v2LacpBVlanInPQsOctetsBandwidth15sec OBJECT-TYPE
   SYNTAX      Integer32
   MAX-ACCESS  read-only
   STATUS      current
   DESCRIPTION
      "Path: lacpBundle.performance.vlan.inPriorityQueues.octets.bandwidth.15sec

       unit name = bps
       formula = 8 * ; 8 /"
   ::= {pr1646v2LacpBVlanInPQsEntry 70386944}

pr1646v2LacpBVlanInPQsOctetsBandwidth30sec OBJECT-TYPE
   SYNTAX      Integer32
   MAX-ACCESS  read-only
   STATUS      current
   DESCRIPTION
      "Path: lacpBundle.performance.vlan.inPriorityQueues.octets.bandwidth.30sec

       unit name = bps
       formula = 8 * ; 8 /"
   ::= {pr1646v2LacpBVlanInPQsEntry 70388224}

pr1646v2LacpBVlanInPQsOctetsBandwidth1min OBJECT-TYPE
   SYNTAX      Integer32
   MAX-ACCESS  read-only
   STATUS      current
   DESCRIPTION
      "Path: lacpBundle.performance.vlan.inPriorityQueues.octets.bandwidth.1min

       unit name = bps
       formula = 8 * ; 8 /"
   ::= {pr1646v2LacpBVlanInPQsEntry 70390784}

pr1646v2LacpBVlanInPQsOctetsBandwidth2min OBJECT-TYPE
   SYNTAX      Integer32
   MAX-ACCESS  read-only
   STATUS      current
   DESCRIPTION
      "Path: lacpBundle.performance.vlan.inPriorityQueues.octets.bandwidth.2min

       unit name = bps
       formula = 8 * ; 8 /"
   ::= {pr1646v2LacpBVlanInPQsEntry 70395904}

pr1646v2LacpBVlanInPQsOctetsBandwidth5min OBJECT-TYPE
   SYNTAX      Integer32
   MAX-ACCESS  read-only
   STATUS      current
   DESCRIPTION
      "Path: lacpBundle.performance.vlan.inPriorityQueues.octets.bandwidth.5min

       unit name = bps
       formula = 8 * ; 8 /"
   ::= {pr1646v2LacpBVlanInPQsEntry 70411264}

pr1646v2LacpBVlanInPQsH2Performance OBJECT-TYPE
   SYNTAX      SEQUENCE OF Pr1646v2LacpBVlanInPQsH2PerformanceEntry
   MAX-ACCESS  not-accessible
   STATUS      current
   DESCRIPTION
      ""
   ::= {pr1646v2LacpBVlan 100990976}

pr1646v2LacpBVlanInPQsH2PerformanceEntry OBJECT-TYPE
   SYNTAX      Pr1646v2LacpBVlanInPQsH2PerformanceEntry
   MAX-ACCESS  not-accessible
   STATUS      current
   DESCRIPTION
      ""
   INDEX      { pr1646v2LacpBVlanInPQsH2PerformanceGlobalIx,
                pr1646v2LacpBVlanTableIx,
                pr1646v2LacpBVlanInPQsTableIx,
                pr1646v2LacpBVlanInPQsH2PerformanceTableIx }
   ::= {pr1646v2LacpBVlanInPQsH2Performance 1}

Pr1646v2LacpBVlanInPQsH2PerformanceEntry ::=
   SEQUENCE
      {
      pr1646v2LacpBVlanInPQsH2PerformanceGlobalIx
         GlobalIndex,
      pr1646v2LacpBVlanInPQsH2PerformanceTableIx
         TableIndex,
      pr1646v2LacpBVlanInPQsH2PerformanceSysUpTime
         TimeTicks,
      pr1646v2LacpBVlanInPQsH2PerformanceTotPkts
         Counter64,
      pr1646v2LacpBVlanInPQsH2PerformanceDirTxPkts
         Counter64,
      pr1646v2LacpBVlanInPQsH2PerformanceQdPkts
         Counter64,
      pr1646v2LacpBVlanInPQsH2PerformanceDropPkts
         Counter64,
      pr1646v2LacpBVlanInPQsH2PerformanceRDropPkts
         Counter64,
      pr1646v2LacpBVlanInPQsH2PerformanceCirTxPkts
         Counter64,
      pr1646v2LacpBVlanInPQsH2PerformanceEirTxPkts
         Counter64,
      pr1646v2LacpBVlanInPQsH2PerformanceViolTxPkts
         Counter64,
      pr1646v2LacpBVlanInPQsH2PerformanceTotOcts
         Counter64,
      pr1646v2LacpBVlanInPQsH2PerformanceDirTxOcts
         Counter64,
      pr1646v2LacpBVlanInPQsH2PerformanceQdOcts
         Counter64,
      pr1646v2LacpBVlanInPQsH2PerformanceDropOcts
         Counter64,
      pr1646v2LacpBVlanInPQsH2PerformanceRDropOcts
         Counter64,
      pr1646v2LacpBVlanInPQsH2PerformanceCirTxOcts
         Counter64,
      pr1646v2LacpBVlanInPQsH2PerformanceEirTxOcts
         Counter64,
      pr1646v2LacpBVlanInPQsH2PerformanceViolTxOcts
         Counter64,
      pr1646v2LacpBVlanInPQsH2PerformanceBandwidth
         Integer32
      }

pr1646v2LacpBVlanInPQsH2PerformanceGlobalIx OBJECT-TYPE
   SYNTAX      GlobalIndex
   MAX-ACCESS  not-accessible
   STATUS      current
   DESCRIPTION
      "The value of the tlsCntTreeGlobalIndex of the MANAGED OBJECT."
   ::= {pr1646v2LacpBVlanInPQsH2PerformanceEntry 10}

pr1646v2LacpBVlanInPQsH2PerformanceTableIx OBJECT-TYPE
   SYNTAX      TableIndex
   MAX-ACCESS  not-accessible
   STATUS      current
   DESCRIPTION
      ""
   ::= {pr1646v2LacpBVlanInPQsH2PerformanceEntry 11}

pr1646v2LacpBVlanInPQsH2PerformanceSysUpTime OBJECT-TYPE
   SYNTAX      TimeTicks
   MAX-ACCESS  read-only
   STATUS      current
   DESCRIPTION
      "Path: lacpBundle.performance.vlan.inPriorityQueues.h2Performance.sysUpTime

       Time in centi-second."
   ::= {pr1646v2LacpBVlanInPQsH2PerformanceEntry 16777216}

pr1646v2LacpBVlanInPQsH2PerformanceTotPkts OBJECT-TYPE
   SYNTAX      Counter64
   MAX-ACCESS  read-only
   STATUS      current
   DESCRIPTION
      "Path: lacpBundle.performance.vlan.inPriorityQueues.h2Performance.totalPkts

       64 bit unsigned wrappable counter."
   ::= {pr1646v2LacpBVlanInPQsH2PerformanceEntry 234881024}

pr1646v2LacpBVlanInPQsH2PerformanceDirTxPkts OBJECT-TYPE
   SYNTAX      Counter64
   MAX-ACCESS  read-only
   STATUS      current
   DESCRIPTION
      "Path: lacpBundle.performance.vlan.inPriorityQueues.h2Performance.directTxPkts

       64 bit unsigned wrappable counter."
   ::= {pr1646v2LacpBVlanInPQsH2PerformanceEntry 33554432}

pr1646v2LacpBVlanInPQsH2PerformanceQdPkts OBJECT-TYPE
   SYNTAX      Counter64
   MAX-ACCESS  read-only
   STATUS      current
   DESCRIPTION
      "Path: lacpBundle.performance.vlan.inPriorityQueues.h2Performance.queuedPkts

       64 bit unsigned wrappable counter."
   ::= {pr1646v2LacpBVlanInPQsH2PerformanceEntry 50331648}

pr1646v2LacpBVlanInPQsH2PerformanceDropPkts OBJECT-TYPE
   SYNTAX      Counter64
   MAX-ACCESS  read-only
   STATUS      current
   DESCRIPTION
      "Path: lacpBundle.performance.vlan.inPriorityQueues.h2Performance.droppedPkts

       64 bit unsigned wrappable counter."
   ::= {pr1646v2LacpBVlanInPQsH2PerformanceEntry 67108864}

pr1646v2LacpBVlanInPQsH2PerformanceRDropPkts OBJECT-TYPE
   SYNTAX      Counter64
   MAX-ACCESS  read-only
   STATUS      current
   DESCRIPTION
      "Path: lacpBundle.performance.vlan.inPriorityQueues.h2Performance.redDroppedPkts

       64 bit unsigned wrappable counter."
   ::= {pr1646v2LacpBVlanInPQsH2PerformanceEntry 201326592}

pr1646v2LacpBVlanInPQsH2PerformanceCirTxPkts OBJECT-TYPE
   SYNTAX      Counter64
   MAX-ACCESS  read-only
   STATUS      current
   DESCRIPTION
      "Path: lacpBundle.performance.vlan.inPriorityQueues.h2Performance.cirTxPkts

       64 bit unsigned wrappable counter."
   ::= {pr1646v2LacpBVlanInPQsH2PerformanceEntry 83886080}

pr1646v2LacpBVlanInPQsH2PerformanceEirTxPkts OBJECT-TYPE
   SYNTAX      Counter64
   MAX-ACCESS  read-only
   STATUS      current
   DESCRIPTION
      "Path: lacpBundle.performance.vlan.inPriorityQueues.h2Performance.eirTxPkts

       64 bit unsigned wrappable counter."
   ::= {pr1646v2LacpBVlanInPQsH2PerformanceEntry 100663296}

pr1646v2LacpBVlanInPQsH2PerformanceViolTxPkts OBJECT-TYPE
   SYNTAX      Counter64
   MAX-ACCESS  read-only
   STATUS      current
   DESCRIPTION
      "Path: lacpBundle.performance.vlan.inPriorityQueues.h2Performance.violateTxPkts

       64 bit unsigned wrappable counter."
   ::= {pr1646v2LacpBVlanInPQsH2PerformanceEntry 301989888}

pr1646v2LacpBVlanInPQsH2PerformanceTotOcts OBJECT-TYPE
   SYNTAX      Counter64
   MAX-ACCESS  read-only
   STATUS      current
   DESCRIPTION
      "Path: lacpBundle.performance.vlan.inPriorityQueues.h2Performance.totalOctets

       64 bit unsigned wrappable counter."
   ::= {pr1646v2LacpBVlanInPQsH2PerformanceEntry 251658240}

pr1646v2LacpBVlanInPQsH2PerformanceDirTxOcts OBJECT-TYPE
   SYNTAX      Counter64
   MAX-ACCESS  read-only
   STATUS      current
   DESCRIPTION
      "Path: lacpBundle.performance.vlan.inPriorityQueues.h2Performance.directTxOctets

       64 bit unsigned wrappable counter."
   ::= {pr1646v2LacpBVlanInPQsH2PerformanceEntry 117440512}

pr1646v2LacpBVlanInPQsH2PerformanceQdOcts OBJECT-TYPE
   SYNTAX      Counter64
   MAX-ACCESS  read-only
   STATUS      current
   DESCRIPTION
      "Path: lacpBundle.performance.vlan.inPriorityQueues.h2Performance.queuedOctets

       64 bit unsigned wrappable counter."
   ::= {pr1646v2LacpBVlanInPQsH2PerformanceEntry 134217728}

pr1646v2LacpBVlanInPQsH2PerformanceDropOcts OBJECT-TYPE
   SYNTAX      Counter64
   MAX-ACCESS  read-only
   STATUS      current
   DESCRIPTION
      "Path: lacpBundle.performance.vlan.inPriorityQueues.h2Performance.droppedOctets

       64 bit unsigned wrappable counter."
   ::= {pr1646v2LacpBVlanInPQsH2PerformanceEntry 150994944}

pr1646v2LacpBVlanInPQsH2PerformanceRDropOcts OBJECT-TYPE
   SYNTAX      Counter64
   MAX-ACCESS  read-only
   STATUS      current
   DESCRIPTION
      "Path: lacpBundle.performance.vlan.inPriorityQueues.h2Performance.redDroppedOctets

       64 bit unsigned wrappable counter."
   ::= {pr1646v2LacpBVlanInPQsH2PerformanceEntry 218103808}

pr1646v2LacpBVlanInPQsH2PerformanceCirTxOcts OBJECT-TYPE
   SYNTAX      Counter64
   MAX-ACCESS  read-only
   STATUS      current
   DESCRIPTION
      "Path: lacpBundle.performance.vlan.inPriorityQueues.h2Performance.cirTxOctets

       64 bit unsigned wrappable counter."
   ::= {pr1646v2LacpBVlanInPQsH2PerformanceEntry 167772160}

pr1646v2LacpBVlanInPQsH2PerformanceEirTxOcts OBJECT-TYPE
   SYNTAX      Counter64
   MAX-ACCESS  read-only
   STATUS      current
   DESCRIPTION
      "Path: lacpBundle.performance.vlan.inPriorityQueues.h2Performance.eirTxOctets

       64 bit unsigned wrappable counter."
   ::= {pr1646v2LacpBVlanInPQsH2PerformanceEntry 184549376}

pr1646v2LacpBVlanInPQsH2PerformanceViolTxOcts OBJECT-TYPE
   SYNTAX      Counter64
   MAX-ACCESS  read-only
   STATUS      current
   DESCRIPTION
      "Path: lacpBundle.performance.vlan.inPriorityQueues.h2Performance.violateTxOctets

       64 bit unsigned wrappable counter."
   ::= {pr1646v2LacpBVlanInPQsH2PerformanceEntry 318767104}

pr1646v2LacpBVlanInPQsH2PerformanceBandwidth OBJECT-TYPE
   SYNTAX      Integer32
   MAX-ACCESS  read-only
   STATUS      current
   DESCRIPTION
      "Path: lacpBundle.performance.vlan.inPriorityQueues.h2Performance.bandwidth

       unit name = bps
       formula = 8 * ; 8 /"
   ::= {pr1646v2LacpBVlanInPQsH2PerformanceEntry 268435456}

pr1646v2LacpBVlanInPQsH24Performance OBJECT-TYPE
   SYNTAX      SEQUENCE OF Pr1646v2LacpBVlanInPQsH24PerformanceEntry
   MAX-ACCESS  not-accessible
   STATUS      current
   DESCRIPTION
      ""
   ::= {pr1646v2LacpBVlan 101056512}

pr1646v2LacpBVlanInPQsH24PerformanceEntry OBJECT-TYPE
   SYNTAX      Pr1646v2LacpBVlanInPQsH24PerformanceEntry
   MAX-ACCESS  not-accessible
   STATUS      current
   DESCRIPTION
      ""
   INDEX      { pr1646v2LacpBVlanInPQsH24PerformanceGlobalIx,
                pr1646v2LacpBVlanTableIx,
                pr1646v2LacpBVlanInPQsTableIx,
                pr1646v2LacpBVlanInPQsH24PerformanceTableIx }
   ::= {pr1646v2LacpBVlanInPQsH24Performance 1}

Pr1646v2LacpBVlanInPQsH24PerformanceEntry ::=
   SEQUENCE
      {
      pr1646v2LacpBVlanInPQsH24PerformanceGlobalIx
         GlobalIndex,
      pr1646v2LacpBVlanInPQsH24PerformanceTableIx
         TableIndex,
      pr1646v2LacpBVlanInPQsH24PerformanceSysUpTime
         TimeTicks,
      pr1646v2LacpBVlanInPQsH24PerformanceTotPkts
         Counter64,
      pr1646v2LacpBVlanInPQsH24PerformanceDirTxPkts
         Counter64,
      pr1646v2LacpBVlanInPQsH24PerformanceQdPkts
         Counter64,
      pr1646v2LacpBVlanInPQsH24PerformanceDropPkts
         Counter64,
      pr1646v2LacpBVlanInPQsH24PerformanceRDropPkts
         Counter64,
      pr1646v2LacpBVlanInPQsH24PerformanceCirTxPkts
         Counter64,
      pr1646v2LacpBVlanInPQsH24PerformanceEirTxPkts
         Counter64,
      pr1646v2LacpBVlanInPQsH24PerformanceViolTxPkts
         Counter64,
      pr1646v2LacpBVlanInPQsH24PerformanceTotOcts
         Counter64,
      pr1646v2LacpBVlanInPQsH24PerformanceDirTxOcts
         Counter64,
      pr1646v2LacpBVlanInPQsH24PerformanceQdOcts
         Counter64,
      pr1646v2LacpBVlanInPQsH24PerformanceDropOcts
         Counter64,
      pr1646v2LacpBVlanInPQsH24PerformanceRDropOcts
         Counter64,
      pr1646v2LacpBVlanInPQsH24PerformanceCirTxOcts
         Counter64,
      pr1646v2LacpBVlanInPQsH24PerformanceEirTxOcts
         Counter64,
      pr1646v2LacpBVlanInPQsH24PerformanceViolTxOcts
         Counter64,
      pr1646v2LacpBVlanInPQsH24PerformanceBandwidth
         Integer32
      }

pr1646v2LacpBVlanInPQsH24PerformanceGlobalIx OBJECT-TYPE
   SYNTAX      GlobalIndex
   MAX-ACCESS  not-accessible
   STATUS      current
   DESCRIPTION
      "The value of the tlsCntTreeGlobalIndex of the MANAGED OBJECT."
   ::= {pr1646v2LacpBVlanInPQsH24PerformanceEntry 10}

pr1646v2LacpBVlanInPQsH24PerformanceTableIx OBJECT-TYPE
   SYNTAX      TableIndex
   MAX-ACCESS  not-accessible
   STATUS      current
   DESCRIPTION
      ""
   ::= {pr1646v2LacpBVlanInPQsH24PerformanceEntry 11}

pr1646v2LacpBVlanInPQsH24PerformanceSysUpTime OBJECT-TYPE
   SYNTAX      TimeTicks
   MAX-ACCESS  read-only
   STATUS      current
   DESCRIPTION
      "Path: lacpBundle.performance.vlan.inPriorityQueues.h24Performance.sysUpTime

       Time in centi-second."
   ::= {pr1646v2LacpBVlanInPQsH24PerformanceEntry 16777216}

pr1646v2LacpBVlanInPQsH24PerformanceTotPkts OBJECT-TYPE
   SYNTAX      Counter64
   MAX-ACCESS  read-only
   STATUS      current
   DESCRIPTION
      "Path: lacpBundle.performance.vlan.inPriorityQueues.h24Performance.totalPkts

       64 bit unsigned wrappable counter."
   ::= {pr1646v2LacpBVlanInPQsH24PerformanceEntry 234881024}

pr1646v2LacpBVlanInPQsH24PerformanceDirTxPkts OBJECT-TYPE
   SYNTAX      Counter64
   MAX-ACCESS  read-only
   STATUS      current
   DESCRIPTION
      "Path: lacpBundle.performance.vlan.inPriorityQueues.h24Performance.directTxPkts

       64 bit unsigned wrappable counter."
   ::= {pr1646v2LacpBVlanInPQsH24PerformanceEntry 33554432}

pr1646v2LacpBVlanInPQsH24PerformanceQdPkts OBJECT-TYPE
   SYNTAX      Counter64
   MAX-ACCESS  read-only
   STATUS      current
   DESCRIPTION
      "Path: lacpBundle.performance.vlan.inPriorityQueues.h24Performance.queuedPkts

       64 bit unsigned wrappable counter."
   ::= {pr1646v2LacpBVlanInPQsH24PerformanceEntry 50331648}

pr1646v2LacpBVlanInPQsH24PerformanceDropPkts OBJECT-TYPE
   SYNTAX      Counter64
   MAX-ACCESS  read-only
   STATUS      current
   DESCRIPTION
      "Path: lacpBundle.performance.vlan.inPriorityQueues.h24Performance.droppedPkts

       64 bit unsigned wrappable counter."
   ::= {pr1646v2LacpBVlanInPQsH24PerformanceEntry 67108864}

pr1646v2LacpBVlanInPQsH24PerformanceRDropPkts OBJECT-TYPE
   SYNTAX      Counter64
   MAX-ACCESS  read-only
   STATUS      current
   DESCRIPTION
      "Path: lacpBundle.performance.vlan.inPriorityQueues.h24Performance.redDroppedPkts

       64 bit unsigned wrappable counter."
   ::= {pr1646v2LacpBVlanInPQsH24PerformanceEntry 201326592}

pr1646v2LacpBVlanInPQsH24PerformanceCirTxPkts OBJECT-TYPE
   SYNTAX      Counter64
   MAX-ACCESS  read-only
   STATUS      current
   DESCRIPTION
      "Path: lacpBundle.performance.vlan.inPriorityQueues.h24Performance.cirTxPkts

       64 bit unsigned wrappable counter."
   ::= {pr1646v2LacpBVlanInPQsH24PerformanceEntry 83886080}

pr1646v2LacpBVlanInPQsH24PerformanceEirTxPkts OBJECT-TYPE
   SYNTAX      Counter64
   MAX-ACCESS  read-only
   STATUS      current
   DESCRIPTION
      "Path: lacpBundle.performance.vlan.inPriorityQueues.h24Performance.eirTxPkts

       64 bit unsigned wrappable counter."
   ::= {pr1646v2LacpBVlanInPQsH24PerformanceEntry 100663296}

pr1646v2LacpBVlanInPQsH24PerformanceViolTxPkts OBJECT-TYPE
   SYNTAX      Counter64
   MAX-ACCESS  read-only
   STATUS      current
   DESCRIPTION
      "Path: lacpBundle.performance.vlan.inPriorityQueues.h24Performance.violateTxPkts

       64 bit unsigned wrappable counter."
   ::= {pr1646v2LacpBVlanInPQsH24PerformanceEntry 301989888}

pr1646v2LacpBVlanInPQsH24PerformanceTotOcts OBJECT-TYPE
   SYNTAX      Counter64
   MAX-ACCESS  read-only
   STATUS      current
   DESCRIPTION
      "Path: lacpBundle.performance.vlan.inPriorityQueues.h24Performance.totalOctets

       64 bit unsigned wrappable counter."
   ::= {pr1646v2LacpBVlanInPQsH24PerformanceEntry 251658240}

pr1646v2LacpBVlanInPQsH24PerformanceDirTxOcts OBJECT-TYPE
   SYNTAX      Counter64
   MAX-ACCESS  read-only
   STATUS      current
   DESCRIPTION
      "Path: lacpBundle.performance.vlan.inPriorityQueues.h24Performance.directTxOctets

       64 bit unsigned wrappable counter."
   ::= {pr1646v2LacpBVlanInPQsH24PerformanceEntry 117440512}

pr1646v2LacpBVlanInPQsH24PerformanceQdOcts OBJECT-TYPE
   SYNTAX      Counter64
   MAX-ACCESS  read-only
   STATUS      current
   DESCRIPTION
      "Path: lacpBundle.performance.vlan.inPriorityQueues.h24Performance.queuedOctets

       64 bit unsigned wrappable counter."
   ::= {pr1646v2LacpBVlanInPQsH24PerformanceEntry 134217728}

pr1646v2LacpBVlanInPQsH24PerformanceDropOcts OBJECT-TYPE
   SYNTAX      Counter64
   MAX-ACCESS  read-only
   STATUS      current
   DESCRIPTION
      "Path: lacpBundle.performance.vlan.inPriorityQueues.h24Performance.droppedOctets

       64 bit unsigned wrappable counter."
   ::= {pr1646v2LacpBVlanInPQsH24PerformanceEntry 150994944}

pr1646v2LacpBVlanInPQsH24PerformanceRDropOcts OBJECT-TYPE
   SYNTAX      Counter64
   MAX-ACCESS  read-only
   STATUS      current
   DESCRIPTION
      "Path: lacpBundle.performance.vlan.inPriorityQueues.h24Performance.redDroppedOctets

       64 bit unsigned wrappable counter."
   ::= {pr1646v2LacpBVlanInPQsH24PerformanceEntry 218103808}

pr1646v2LacpBVlanInPQsH24PerformanceCirTxOcts OBJECT-TYPE
   SYNTAX      Counter64
   MAX-ACCESS  read-only
   STATUS      current
   DESCRIPTION
      "Path: lacpBundle.performance.vlan.inPriorityQueues.h24Performance.cirTxOctets

       64 bit unsigned wrappable counter."
   ::= {pr1646v2LacpBVlanInPQsH24PerformanceEntry 167772160}

pr1646v2LacpBVlanInPQsH24PerformanceEirTxOcts OBJECT-TYPE
   SYNTAX      Counter64
   MAX-ACCESS  read-only
   STATUS      current
   DESCRIPTION
      "Path: lacpBundle.performance.vlan.inPriorityQueues.h24Performance.eirTxOctets

       64 bit unsigned wrappable counter."
   ::= {pr1646v2LacpBVlanInPQsH24PerformanceEntry 184549376}

pr1646v2LacpBVlanInPQsH24PerformanceViolTxOcts OBJECT-TYPE
   SYNTAX      Counter64
   MAX-ACCESS  read-only
   STATUS      current
   DESCRIPTION
      "Path: lacpBundle.performance.vlan.inPriorityQueues.h24Performance.violateTxOctets

       64 bit unsigned wrappable counter."
   ::= {pr1646v2LacpBVlanInPQsH24PerformanceEntry 318767104}

pr1646v2LacpBVlanInPQsH24PerformanceBandwidth OBJECT-TYPE
   SYNTAX      Integer32
   MAX-ACCESS  read-only
   STATUS      current
   DESCRIPTION
      "Path: lacpBundle.performance.vlan.inPriorityQueues.h24Performance.bandwidth

       unit name = bps
       formula = 8 * ; 8 /"
   ::= {pr1646v2LacpBVlanInPQsH24PerformanceEntry 268435456}

pr1646v2LacpBVlanInPQsD7Performance OBJECT-TYPE
   SYNTAX      SEQUENCE OF Pr1646v2LacpBVlanInPQsD7PerformanceEntry
   MAX-ACCESS  not-accessible
   STATUS      current
   DESCRIPTION
      ""
   ::= {pr1646v2LacpBVlan 101122048}

pr1646v2LacpBVlanInPQsD7PerformanceEntry OBJECT-TYPE
   SYNTAX      Pr1646v2LacpBVlanInPQsD7PerformanceEntry
   MAX-ACCESS  not-accessible
   STATUS      current
   DESCRIPTION
      ""
   INDEX      { pr1646v2LacpBVlanInPQsD7PerformanceGlobalIx,
                pr1646v2LacpBVlanTableIx,
                pr1646v2LacpBVlanInPQsTableIx,
                pr1646v2LacpBVlanInPQsD7PerformanceTableIx }
   ::= {pr1646v2LacpBVlanInPQsD7Performance 1}

Pr1646v2LacpBVlanInPQsD7PerformanceEntry ::=
   SEQUENCE
      {
      pr1646v2LacpBVlanInPQsD7PerformanceGlobalIx
         GlobalIndex,
      pr1646v2LacpBVlanInPQsD7PerformanceTableIx
         TableIndex,
      pr1646v2LacpBVlanInPQsD7PerformanceSysUpTime
         TimeTicks,
      pr1646v2LacpBVlanInPQsD7PerformanceTotPkts
         Counter64,
      pr1646v2LacpBVlanInPQsD7PerformanceDirTxPkts
         Counter64,
      pr1646v2LacpBVlanInPQsD7PerformanceQdPkts
         Counter64,
      pr1646v2LacpBVlanInPQsD7PerformanceDropPkts
         Counter64,
      pr1646v2LacpBVlanInPQsD7PerformanceRDropPkts
         Counter64,
      pr1646v2LacpBVlanInPQsD7PerformanceCirTxPkts
         Counter64,
      pr1646v2LacpBVlanInPQsD7PerformanceEirTxPkts
         Counter64,
      pr1646v2LacpBVlanInPQsD7PerformanceViolTxPkts
         Counter64,
      pr1646v2LacpBVlanInPQsD7PerformanceTotOcts
         Counter64,
      pr1646v2LacpBVlanInPQsD7PerformanceDirTxOcts
         Counter64,
      pr1646v2LacpBVlanInPQsD7PerformanceQdOcts
         Counter64,
      pr1646v2LacpBVlanInPQsD7PerformanceDropOcts
         Counter64,
      pr1646v2LacpBVlanInPQsD7PerformanceRDropOcts
         Counter64,
      pr1646v2LacpBVlanInPQsD7PerformanceCirTxOcts
         Counter64,
      pr1646v2LacpBVlanInPQsD7PerformanceEirTxOcts
         Counter64,
      pr1646v2LacpBVlanInPQsD7PerformanceViolTxOcts
         Counter64,
      pr1646v2LacpBVlanInPQsD7PerformanceBandwidth
         Integer32
      }

pr1646v2LacpBVlanInPQsD7PerformanceGlobalIx OBJECT-TYPE
   SYNTAX      GlobalIndex
   MAX-ACCESS  not-accessible
   STATUS      current
   DESCRIPTION
      "The value of the tlsCntTreeGlobalIndex of the MANAGED OBJECT."
   ::= {pr1646v2LacpBVlanInPQsD7PerformanceEntry 10}

pr1646v2LacpBVlanInPQsD7PerformanceTableIx OBJECT-TYPE
   SYNTAX      TableIndex
   MAX-ACCESS  not-accessible
   STATUS      current
   DESCRIPTION
      ""
   ::= {pr1646v2LacpBVlanInPQsD7PerformanceEntry 11}

pr1646v2LacpBVlanInPQsD7PerformanceSysUpTime OBJECT-TYPE
   SYNTAX      TimeTicks
   MAX-ACCESS  read-only
   STATUS      current
   DESCRIPTION
      "Path: lacpBundle.performance.vlan.inPriorityQueues.d7Performance.sysUpTime

       Time in centi-second."
   ::= {pr1646v2LacpBVlanInPQsD7PerformanceEntry 16777216}

pr1646v2LacpBVlanInPQsD7PerformanceTotPkts OBJECT-TYPE
   SYNTAX      Counter64
   MAX-ACCESS  read-only
   STATUS      current
   DESCRIPTION
      "Path: lacpBundle.performance.vlan.inPriorityQueues.d7Performance.totalPkts

       64 bit unsigned wrappable counter."
   ::= {pr1646v2LacpBVlanInPQsD7PerformanceEntry 234881024}

pr1646v2LacpBVlanInPQsD7PerformanceDirTxPkts OBJECT-TYPE
   SYNTAX      Counter64
   MAX-ACCESS  read-only
   STATUS      current
   DESCRIPTION
      "Path: lacpBundle.performance.vlan.inPriorityQueues.d7Performance.directTxPkts

       64 bit unsigned wrappable counter."
   ::= {pr1646v2LacpBVlanInPQsD7PerformanceEntry 33554432}

pr1646v2LacpBVlanInPQsD7PerformanceQdPkts OBJECT-TYPE
   SYNTAX      Counter64
   MAX-ACCESS  read-only
   STATUS      current
   DESCRIPTION
      "Path: lacpBundle.performance.vlan.inPriorityQueues.d7Performance.queuedPkts

       64 bit unsigned wrappable counter."
   ::= {pr1646v2LacpBVlanInPQsD7PerformanceEntry 50331648}

pr1646v2LacpBVlanInPQsD7PerformanceDropPkts OBJECT-TYPE
   SYNTAX      Counter64
   MAX-ACCESS  read-only
   STATUS      current
   DESCRIPTION
      "Path: lacpBundle.performance.vlan.inPriorityQueues.d7Performance.droppedPkts

       64 bit unsigned wrappable counter."
   ::= {pr1646v2LacpBVlanInPQsD7PerformanceEntry 67108864}

pr1646v2LacpBVlanInPQsD7PerformanceRDropPkts OBJECT-TYPE
   SYNTAX      Counter64
   MAX-ACCESS  read-only
   STATUS      current
   DESCRIPTION
      "Path: lacpBundle.performance.vlan.inPriorityQueues.d7Performance.redDroppedPkts

       64 bit unsigned wrappable counter."
   ::= {pr1646v2LacpBVlanInPQsD7PerformanceEntry 201326592}

pr1646v2LacpBVlanInPQsD7PerformanceCirTxPkts OBJECT-TYPE
   SYNTAX      Counter64
   MAX-ACCESS  read-only
   STATUS      current
   DESCRIPTION
      "Path: lacpBundle.performance.vlan.inPriorityQueues.d7Performance.cirTxPkts

       64 bit unsigned wrappable counter."
   ::= {pr1646v2LacpBVlanInPQsD7PerformanceEntry 83886080}

pr1646v2LacpBVlanInPQsD7PerformanceEirTxPkts OBJECT-TYPE
   SYNTAX      Counter64
   MAX-ACCESS  read-only
   STATUS      current
   DESCRIPTION
      "Path: lacpBundle.performance.vlan.inPriorityQueues.d7Performance.eirTxPkts

       64 bit unsigned wrappable counter."
   ::= {pr1646v2LacpBVlanInPQsD7PerformanceEntry 100663296}

pr1646v2LacpBVlanInPQsD7PerformanceViolTxPkts OBJECT-TYPE
   SYNTAX      Counter64
   MAX-ACCESS  read-only
   STATUS      current
   DESCRIPTION
      "Path: lacpBundle.performance.vlan.inPriorityQueues.d7Performance.violateTxPkts

       64 bit unsigned wrappable counter."
   ::= {pr1646v2LacpBVlanInPQsD7PerformanceEntry 301989888}

pr1646v2LacpBVlanInPQsD7PerformanceTotOcts OBJECT-TYPE
   SYNTAX      Counter64
   MAX-ACCESS  read-only
   STATUS      current
   DESCRIPTION
      "Path: lacpBundle.performance.vlan.inPriorityQueues.d7Performance.totalOctets

       64 bit unsigned wrappable counter."
   ::= {pr1646v2LacpBVlanInPQsD7PerformanceEntry 251658240}

pr1646v2LacpBVlanInPQsD7PerformanceDirTxOcts OBJECT-TYPE
   SYNTAX      Counter64
   MAX-ACCESS  read-only
   STATUS      current
   DESCRIPTION
      "Path: lacpBundle.performance.vlan.inPriorityQueues.d7Performance.directTxOctets

       64 bit unsigned wrappable counter."
   ::= {pr1646v2LacpBVlanInPQsD7PerformanceEntry 117440512}

pr1646v2LacpBVlanInPQsD7PerformanceQdOcts OBJECT-TYPE
   SYNTAX      Counter64
   MAX-ACCESS  read-only
   STATUS      current
   DESCRIPTION
      "Path: lacpBundle.performance.vlan.inPriorityQueues.d7Performance.queuedOctets

       64 bit unsigned wrappable counter."
   ::= {pr1646v2LacpBVlanInPQsD7PerformanceEntry 134217728}

pr1646v2LacpBVlanInPQsD7PerformanceDropOcts OBJECT-TYPE
   SYNTAX      Counter64
   MAX-ACCESS  read-only
   STATUS      current
   DESCRIPTION
      "Path: lacpBundle.performance.vlan.inPriorityQueues.d7Performance.droppedOctets

       64 bit unsigned wrappable counter."
   ::= {pr1646v2LacpBVlanInPQsD7PerformanceEntry 150994944}

pr1646v2LacpBVlanInPQsD7PerformanceRDropOcts OBJECT-TYPE
   SYNTAX      Counter64
   MAX-ACCESS  read-only
   STATUS      current
   DESCRIPTION
      "Path: lacpBundle.performance.vlan.inPriorityQueues.d7Performance.redDroppedOctets

       64 bit unsigned wrappable counter."
   ::= {pr1646v2LacpBVlanInPQsD7PerformanceEntry 218103808}

pr1646v2LacpBVlanInPQsD7PerformanceCirTxOcts OBJECT-TYPE
   SYNTAX      Counter64
   MAX-ACCESS  read-only
   STATUS      current
   DESCRIPTION
      "Path: lacpBundle.performance.vlan.inPriorityQueues.d7Performance.cirTxOctets

       64 bit unsigned wrappable counter."
   ::= {pr1646v2LacpBVlanInPQsD7PerformanceEntry 167772160}

pr1646v2LacpBVlanInPQsD7PerformanceEirTxOcts OBJECT-TYPE
   SYNTAX      Counter64
   MAX-ACCESS  read-only
   STATUS      current
   DESCRIPTION
      "Path: lacpBundle.performance.vlan.inPriorityQueues.d7Performance.eirTxOctets

       64 bit unsigned wrappable counter."
   ::= {pr1646v2LacpBVlanInPQsD7PerformanceEntry 184549376}

pr1646v2LacpBVlanInPQsD7PerformanceViolTxOcts OBJECT-TYPE
   SYNTAX      Counter64
   MAX-ACCESS  read-only
   STATUS      current
   DESCRIPTION
      "Path: lacpBundle.performance.vlan.inPriorityQueues.d7Performance.violateTxOctets

       64 bit unsigned wrappable counter."
   ::= {pr1646v2LacpBVlanInPQsD7PerformanceEntry 318767104}

pr1646v2LacpBVlanInPQsD7PerformanceBandwidth OBJECT-TYPE
   SYNTAX      Integer32
   MAX-ACCESS  read-only
   STATUS      current
   DESCRIPTION
      "Path: lacpBundle.performance.vlan.inPriorityQueues.d7Performance.bandwidth

       unit name = bps
       formula = 8 * ; 8 /"
   ::= {pr1646v2LacpBVlanInPQsD7PerformanceEntry 268435456}

pr1646v2LacpBVlanOutPQs OBJECT-TYPE
   SYNTAX      SEQUENCE OF Pr1646v2LacpBVlanOutPQsEntry
   MAX-ACCESS  not-accessible
   STATUS      current
   DESCRIPTION
      ""
   ::= {pr1646v2LacpBVlan 83886080}

pr1646v2LacpBVlanOutPQsEntry OBJECT-TYPE
   SYNTAX      Pr1646v2LacpBVlanOutPQsEntry
   MAX-ACCESS  not-accessible
   STATUS      current
   DESCRIPTION
      ""
   INDEX      { pr1646v2LacpBVlanOutPQsGlobalIx,
                pr1646v2LacpBVlanTableIx,
                pr1646v2LacpBVlanOutPQsTableIx }
   ::= {pr1646v2LacpBVlanOutPQs 1}

Pr1646v2LacpBVlanOutPQsEntry ::=
   SEQUENCE
      {
      pr1646v2LacpBVlanOutPQsGlobalIx
         GlobalIndex,
      pr1646v2LacpBVlanOutPQsTableIx
         TableIndex,
      pr1646v2LacpBVlanOutPQsName
         INTEGER,
      pr1646v2LacpBVlanOutPQsLength
         Integer32,
      pr1646v2LacpBVlanOutPQsOctetLength
         Integer32,
      pr1646v2LacpBVlanOutPQsRedLength
         Integer32,
      pr1646v2LacpBVlanOutPQsPacketsTotal
         Counter64,
      pr1646v2LacpBVlanOutPQsPacketsDirectTx
         Counter64,
      pr1646v2LacpBVlanOutPQsPacketsQueued
         Counter64,
      pr1646v2LacpBVlanOutPQsPacketsDropped
         Counter64,
      pr1646v2LacpBVlanOutPQsPacketsRedDropped
         Counter64,
      pr1646v2LacpBVlanOutPQsPacketsCirTx
         Counter64,
      pr1646v2LacpBVlanOutPQsPacketsEirTx
         Counter64,
      pr1646v2LacpBVlanOutPQsPacketsViolateTx
         Counter64,
      pr1646v2LacpBVlanOutPQsOctetsTotal
         Counter64,
      pr1646v2LacpBVlanOutPQsOctetsDirectTx
         Counter64,
      pr1646v2LacpBVlanOutPQsOctetsQueued
         Counter64,
      pr1646v2LacpBVlanOutPQsOctetsDropped
         Counter64,
      pr1646v2LacpBVlanOutPQsOctetsRedDropped
         Counter64,
      pr1646v2LacpBVlanOutPQsOctetsCirTx
         Counter64,
      pr1646v2LacpBVlanOutPQsOctetsEirTx
         Counter64,
      pr1646v2LacpBVlanOutPQsOctetsViolateTx
         Counter64,
      pr1646v2LacpBVlanOutPQsOctetsBandwidth15sec
         Integer32,
      pr1646v2LacpBVlanOutPQsOctetsBandwidth30sec
         Integer32,
      pr1646v2LacpBVlanOutPQsOctetsBandwidth1min
         Integer32,
      pr1646v2LacpBVlanOutPQsOctetsBandwidth2min
         Integer32,
      pr1646v2LacpBVlanOutPQsOctetsBandwidth5min
         Integer32
      }

pr1646v2LacpBVlanOutPQsGlobalIx OBJECT-TYPE
   SYNTAX      GlobalIndex
   MAX-ACCESS  not-accessible
   STATUS      current
   DESCRIPTION
      "The value of the tlsCntTreeGlobalIndex of the MANAGED OBJECT."
   ::= {pr1646v2LacpBVlanOutPQsEntry 10}

pr1646v2LacpBVlanOutPQsTableIx OBJECT-TYPE
   SYNTAX      TableIndex
   MAX-ACCESS  not-accessible
   STATUS      current
   DESCRIPTION
      ""
   ::= {pr1646v2LacpBVlanOutPQsEntry 11}

pr1646v2LacpBVlanOutPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: lacpBundle.performance.vlan.outPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2LacpBVlanOutPQsEntry 16777216}

pr1646v2LacpBVlanOutPQsLength OBJECT-TYPE
   SYNTAX      Integer32
   MAX-ACCESS  read-only
   STATUS      current
   DESCRIPTION
      "Path: lacpBundle.performance.vlan.outPriorityQueues.length"
   ::= {pr1646v2LacpBVlanOutPQsEntry 33554432}

pr1646v2LacpBVlanOutPQsOctetLength OBJECT-TYPE
   SYNTAX      Integer32
   MAX-ACCESS  read-only
   STATUS      current
   DESCRIPTION
      "Path: lacpBundle.performance.vlan.outPriorityQueues.octetLength"
   ::= {pr1646v2LacpBVlanOutPQsEntry 150994944}

pr1646v2LacpBVlanOutPQsRedLength OBJECT-TYPE
   SYNTAX      Integer32
   MAX-ACCESS  read-only
   STATUS      current
   DESCRIPTION
      "Path: lacpBundle.performance.vlan.outPriorityQueues.redLength"
   ::= {pr1646v2LacpBVlanOutPQsEntry 134217728}

pr1646v2LacpBVlanOutPQsPacketsTotal OBJECT-TYPE
   SYNTAX      Counter64
   MAX-ACCESS  read-only
   STATUS      current
   DESCRIPTION
      "Path: lacpBundle.performance.vlan.outPriorityQueues.packets.total

       64 bit unsigned wrappable counter."
   ::= {pr1646v2LacpBVlanOutPQsEntry 50790400}

pr1646v2LacpBVlanOutPQsPacketsDirectTx OBJECT-TYPE
   SYNTAX      Counter64
   MAX-ACCESS  read-only
   STATUS      current
   DESCRIPTION
      "Path: lacpBundle.performance.vlan.outPriorityQueues.packets.directTx

       64 bit unsigned wrappable counter."
   ::= {pr1646v2LacpBVlanOutPQsEntry 50397184}

pr1646v2LacpBVlanOutPQsPacketsQueued OBJECT-TYPE
   SYNTAX      Counter64
   MAX-ACCESS  read-only
   STATUS      current
   DESCRIPTION
      "Path: lacpBundle.performance.vlan.outPriorityQueues.packets.queued

       64 bit unsigned wrappable counter."
   ::= {pr1646v2LacpBVlanOutPQsEntry 50462720}

pr1646v2LacpBVlanOutPQsPacketsDropped OBJECT-TYPE
   SYNTAX      Counter64
   MAX-ACCESS  read-only
   STATUS      current
   DESCRIPTION
      "Path: lacpBundle.performance.vlan.outPriorityQueues.packets.dropped

       64 bit unsigned wrappable counter."
   ::= {pr1646v2LacpBVlanOutPQsEntry 50528256}

pr1646v2LacpBVlanOutPQsPacketsRedDropped OBJECT-TYPE
   SYNTAX      Counter64
   MAX-ACCESS  read-only
   STATUS      current
   DESCRIPTION
      "Path: lacpBundle.performance.vlan.outPriorityQueues.packets.redDropped

       64 bit unsigned wrappable counter."
   ::= {pr1646v2LacpBVlanOutPQsEntry 50724864}

pr1646v2LacpBVlanOutPQsPacketsCirTx OBJECT-TYPE
   SYNTAX      Counter64
   MAX-ACCESS  read-only
   STATUS      current
   DESCRIPTION
      "Path: lacpBundle.performance.vlan.outPriorityQueues.packets.cirTx

       64 bit unsigned wrappable counter."
   ::= {pr1646v2LacpBVlanOutPQsEntry 50593792}

pr1646v2LacpBVlanOutPQsPacketsEirTx OBJECT-TYPE
   SYNTAX      Counter64
   MAX-ACCESS  read-only
   STATUS      current
   DESCRIPTION
      "Path: lacpBundle.performance.vlan.outPriorityQueues.packets.eirTx

       64 bit unsigned wrappable counter."
   ::= {pr1646v2LacpBVlanOutPQsEntry 50659328}

pr1646v2LacpBVlanOutPQsPacketsViolateTx OBJECT-TYPE
   SYNTAX      Counter64
   MAX-ACCESS  read-only
   STATUS      current
   DESCRIPTION
      "Path: lacpBundle.performance.vlan.outPriorityQueues.packets.violateTx

       64 bit unsigned wrappable counter."
   ::= {pr1646v2LacpBVlanOutPQsEntry 50855936}

pr1646v2LacpBVlanOutPQsOctetsTotal OBJECT-TYPE
   SYNTAX      Counter64
   MAX-ACCESS  read-only
   STATUS      current
   DESCRIPTION
      "Path: lacpBundle.performance.vlan.outPriorityQueues.octets.total

       64 bit unsigned wrappable counter."
   ::= {pr1646v2LacpBVlanOutPQsEntry 67567616}

pr1646v2LacpBVlanOutPQsOctetsDirectTx OBJECT-TYPE
   SYNTAX      Counter64
   MAX-ACCESS  read-only
   STATUS      current
   DESCRIPTION
      "Path: lacpBundle.performance.vlan.outPriorityQueues.octets.directTx

       64 bit unsigned wrappable counter."
   ::= {pr1646v2LacpBVlanOutPQsEntry 67174400}

pr1646v2LacpBVlanOutPQsOctetsQueued OBJECT-TYPE
   SYNTAX      Counter64
   MAX-ACCESS  read-only
   STATUS      current
   DESCRIPTION
      "Path: lacpBundle.performance.vlan.outPriorityQueues.octets.queued

       64 bit unsigned wrappable counter."
   ::= {pr1646v2LacpBVlanOutPQsEntry 67239936}

pr1646v2LacpBVlanOutPQsOctetsDropped OBJECT-TYPE
   SYNTAX      Counter64
   MAX-ACCESS  read-only
   STATUS      current
   DESCRIPTION
      "Path: lacpBundle.performance.vlan.outPriorityQueues.octets.dropped

       64 bit unsigned wrappable counter."
   ::= {pr1646v2LacpBVlanOutPQsEntry 67305472}

pr1646v2LacpBVlanOutPQsOctetsRedDropped OBJECT-TYPE
   SYNTAX      Counter64
   MAX-ACCESS  read-only
   STATUS      current
   DESCRIPTION
      "Path: lacpBundle.performance.vlan.outPriorityQueues.octets.redDropped

       64 bit unsigned wrappable counter."
   ::= {pr1646v2LacpBVlanOutPQsEntry 67502080}

pr1646v2LacpBVlanOutPQsOctetsCirTx OBJECT-TYPE
   SYNTAX      Counter64
   MAX-ACCESS  read-only
   STATUS      current
   DESCRIPTION
      "Path: lacpBundle.performance.vlan.outPriorityQueues.octets.cirTx

       64 bit unsigned wrappable counter."
   ::= {pr1646v2LacpBVlanOutPQsEntry 67371008}

pr1646v2LacpBVlanOutPQsOctetsEirTx OBJECT-TYPE
   SYNTAX      Counter64
   MAX-ACCESS  read-only
   STATUS      current
   DESCRIPTION
      "Path: lacpBundle.performance.vlan.outPriorityQueues.octets.eirTx

       64 bit unsigned wrappable counter."
   ::= {pr1646v2LacpBVlanOutPQsEntry 67436544}

pr1646v2LacpBVlanOutPQsOctetsViolateTx OBJECT-TYPE
   SYNTAX      Counter64
   MAX-ACCESS  read-only
   STATUS      current
   DESCRIPTION
      "Path: lacpBundle.performance.vlan.outPriorityQueues.octets.violateTx

       64 bit unsigned wrappable counter."
   ::= {pr1646v2LacpBVlanOutPQsEntry 67633152}

pr1646v2LacpBVlanOutPQsOctetsBandwidth15sec OBJECT-TYPE
   SYNTAX      Integer32
   MAX-ACCESS  read-only
   STATUS      current
   DESCRIPTION
      "Path: lacpBundle.performance.vlan.outPriorityQueues.octets.bandwidth.15sec

       unit name = bps
       formula = 8 * ; 8 /"
   ::= {pr1646v2LacpBVlanOutPQsEntry 70386944}

pr1646v2LacpBVlanOutPQsOctetsBandwidth30sec OBJECT-TYPE
   SYNTAX      Integer32
   MAX-ACCESS  read-only
   STATUS      current
   DESCRIPTION
      "Path: lacpBundle.performance.vlan.outPriorityQueues.octets.bandwidth.30sec

       unit name = bps
       formula = 8 * ; 8 /"
   ::= {pr1646v2LacpBVlanOutPQsEntry 70388224}

pr1646v2LacpBVlanOutPQsOctetsBandwidth1min OBJECT-TYPE
   SYNTAX      Integer32
   MAX-ACCESS  read-only
   STATUS      current
   DESCRIPTION
      "Path: lacpBundle.performance.vlan.outPriorityQueues.octets.bandwidth.1min

       unit name = bps
       formula = 8 * ; 8 /"
   ::= {pr1646v2LacpBVlanOutPQsEntry 70390784}

pr1646v2LacpBVlanOutPQsOctetsBandwidth2min OBJECT-TYPE
   SYNTAX      Integer32
   MAX-ACCESS  read-only
   STATUS      current
   DESCRIPTION
      "Path: lacpBundle.performance.vlan.outPriorityQueues.octets.bandwidth.2min

       unit name = bps
       formula = 8 * ; 8 /"
   ::= {pr1646v2LacpBVlanOutPQsEntry 70395904}

pr1646v2LacpBVlanOutPQsOctetsBandwidth5min OBJECT-TYPE
   SYNTAX      Integer32
   MAX-ACCESS  read-only
   STATUS      current
   DESCRIPTION
      "Path: lacpBundle.performance.vlan.outPriorityQueues.octets.bandwidth.5min

       unit name = bps
       formula = 8 * ; 8 /"
   ::= {pr1646v2LacpBVlanOutPQsEntry 70411264}

pr1646v2LacpBVlanOutPQsH2Performance OBJECT-TYPE
   SYNTAX      SEQUENCE OF Pr1646v2LacpBVlanOutPQsH2PerformanceEntry
   MAX-ACCESS  not-accessible
   STATUS      current
   DESCRIPTION
      ""
   ::= {pr1646v2LacpBVlan 84213760}

pr1646v2LacpBVlanOutPQsH2PerformanceEntry OBJECT-TYPE
   SYNTAX      Pr1646v2LacpBVlanOutPQsH2PerformanceEntry
   MAX-ACCESS  not-accessible
   STATUS      current
   DESCRIPTION
      ""
   INDEX      { pr1646v2LacpBVlanOutPQsH2PerformanceGlobalIx,
                pr1646v2LacpBVlanTableIx,
                pr1646v2LacpBVlanOutPQsTableIx,
                pr1646v2LacpBVlanOutPQsH2PerformanceTableIx }
   ::= {pr1646v2LacpBVlanOutPQsH2Performance 1}

Pr1646v2LacpBVlanOutPQsH2PerformanceEntry ::=
   SEQUENCE
      {
      pr1646v2LacpBVlanOutPQsH2PerformanceGlobalIx
         GlobalIndex,
      pr1646v2LacpBVlanOutPQsH2PerformanceTableIx
         TableIndex,
      pr1646v2LacpBVlanOutPQsH2PerformanceSysUpTime
         TimeTicks,
      pr1646v2LacpBVlanOutPQsH2PerformanceTotPkts
         Counter64,
      pr1646v2LacpBVlanOutPQsH2PerformanceDirTxPkts
         Counter64,
      pr1646v2LacpBVlanOutPQsH2PerformanceQdPkts
         Counter64,
      pr1646v2LacpBVlanOutPQsH2PerformanceDropPkts
         Counter64,
      pr1646v2LacpBVlanOutPQsH2PerformanceRDropPkts
         Counter64,
      pr1646v2LacpBVlanOutPQsH2PerformanceCirTxPkts
         Counter64,
      pr1646v2LacpBVlanOutPQsH2PerformanceEirTxPkts
         Counter64,
      pr1646v2LacpBVlanOutPQsH2PerformanceViolTxPkts
         Counter64,
      pr1646v2LacpBVlanOutPQsH2PerformanceTotOcts
         Counter64,
      pr1646v2LacpBVlanOutPQsH2PerformanceDirTxOcts
         Counter64,
      pr1646v2LacpBVlanOutPQsH2PerformanceQdOcts
         Counter64,
      pr1646v2LacpBVlanOutPQsH2PerformanceDropOcts
         Counter64,
      pr1646v2LacpBVlanOutPQsH2PerformanceRDropOcts
         Counter64,
      pr1646v2LacpBVlanOutPQsH2PerformanceCirTxOcts
         Counter64,
      pr1646v2LacpBVlanOutPQsH2PerformanceEirTxOcts
         Counter64,
      pr1646v2LacpBVlanOutPQsH2PerformanceViolTxOcts
         Counter64,
      pr1646v2LacpBVlanOutPQsH2PerformanceBandwidth
         Integer32
      }

pr1646v2LacpBVlanOutPQsH2PerformanceGlobalIx OBJECT-TYPE
   SYNTAX      GlobalIndex
   MAX-ACCESS  not-accessible
   STATUS      current
   DESCRIPTION
      "The value of the tlsCntTreeGlobalIndex of the MANAGED OBJECT."
   ::= {pr1646v2LacpBVlanOutPQsH2PerformanceEntry 10}

pr1646v2LacpBVlanOutPQsH2PerformanceTableIx OBJECT-TYPE
   SYNTAX      TableIndex
   MAX-ACCESS  not-accessible
   STATUS      current
   DESCRIPTION
      ""
   ::= {pr1646v2LacpBVlanOutPQsH2PerformanceEntry 11}

pr1646v2LacpBVlanOutPQsH2PerformanceSysUpTime OBJECT-TYPE
   SYNTAX      TimeTicks
   MAX-ACCESS  read-only
   STATUS      current
   DESCRIPTION
      "Path: lacpBundle.performance.vlan.outPriorityQueues.h2Performance.sysUpTime

       Time in centi-second."
   ::= {pr1646v2LacpBVlanOutPQsH2PerformanceEntry 16777216}

pr1646v2LacpBVlanOutPQsH2PerformanceTotPkts OBJECT-TYPE
   SYNTAX      Counter64
   MAX-ACCESS  read-only
   STATUS      current
   DESCRIPTION
      "Path: lacpBundle.performance.vlan.outPriorityQueues.h2Performance.totalPkts

       64 bit unsigned wrappable counter."
   ::= {pr1646v2LacpBVlanOutPQsH2PerformanceEntry 234881024}

pr1646v2LacpBVlanOutPQsH2PerformanceDirTxPkts OBJECT-TYPE
   SYNTAX      Counter64
   MAX-ACCESS  read-only
   STATUS      current
   DESCRIPTION
      "Path: lacpBundle.performance.vlan.outPriorityQueues.h2Performance.directTxPkts

       64 bit unsigned wrappable counter."
   ::= {pr1646v2LacpBVlanOutPQsH2PerformanceEntry 33554432}

pr1646v2LacpBVlanOutPQsH2PerformanceQdPkts OBJECT-TYPE
   SYNTAX      Counter64
   MAX-ACCESS  read-only
   STATUS      current
   DESCRIPTION
      "Path: lacpBundle.performance.vlan.outPriorityQueues.h2Performance.queuedPkts

       64 bit unsigned wrappable counter."
   ::= {pr1646v2LacpBVlanOutPQsH2PerformanceEntry 50331648}

pr1646v2LacpBVlanOutPQsH2PerformanceDropPkts OBJECT-TYPE
   SYNTAX      Counter64
   MAX-ACCESS  read-only
   STATUS      current
   DESCRIPTION
      "Path: lacpBundle.performance.vlan.outPriorityQueues.h2Performance.droppedPkts

       64 bit unsigned wrappable counter."
   ::= {pr1646v2LacpBVlanOutPQsH2PerformanceEntry 67108864}

pr1646v2LacpBVlanOutPQsH2PerformanceRDropPkts OBJECT-TYPE
   SYNTAX      Counter64
   MAX-ACCESS  read-only
   STATUS      current
   DESCRIPTION
      "Path: lacpBundle.performance.vlan.outPriorityQueues.h2Performance.redDroppedPkts

       64 bit unsigned wrappable counter."
   ::= {pr1646v2LacpBVlanOutPQsH2PerformanceEntry 201326592}

pr1646v2LacpBVlanOutPQsH2PerformanceCirTxPkts OBJECT-TYPE
   SYNTAX      Counter64
   MAX-ACCESS  read-only
   STATUS      current
   DESCRIPTION
      "Path: lacpBundle.performance.vlan.outPriorityQueues.h2Performance.cirTxPkts

       64 bit unsigned wrappable counter."
   ::= {pr1646v2LacpBVlanOutPQsH2PerformanceEntry 83886080}

pr1646v2LacpBVlanOutPQsH2PerformanceEirTxPkts OBJECT-TYPE
   SYNTAX      Counter64
   MAX-ACCESS  read-only
   STATUS      current
   DESCRIPTION
      "Path: lacpBundle.performance.vlan.outPriorityQueues.h2Performance.eirTxPkts

       64 bit unsigned wrappable counter."
   ::= {pr1646v2LacpBVlanOutPQsH2PerformanceEntry 100663296}

pr1646v2LacpBVlanOutPQsH2PerformanceViolTxPkts OBJECT-TYPE
   SYNTAX      Counter64
   MAX-ACCESS  read-only
   STATUS      current
   DESCRIPTION
      "Path: lacpBundle.performance.vlan.outPriorityQueues.h2Performance.violateTxPkts

       64 bit unsigned wrappable counter."
   ::= {pr1646v2LacpBVlanOutPQsH2PerformanceEntry 301989888}

pr1646v2LacpBVlanOutPQsH2PerformanceTotOcts OBJECT-TYPE
   SYNTAX      Counter64
   MAX-ACCESS  read-only
   STATUS      current
   DESCRIPTION
      "Path: lacpBundle.performance.vlan.outPriorityQueues.h2Performance.totalOctets

       64 bit unsigned wrappable counter."
   ::= {pr1646v2LacpBVlanOutPQsH2PerformanceEntry 251658240}

pr1646v2LacpBVlanOutPQsH2PerformanceDirTxOcts OBJECT-TYPE
   SYNTAX      Counter64
   MAX-ACCESS  read-only
   STATUS      current
   DESCRIPTION
      "Path: lacpBundle.performance.vlan.outPriorityQueues.h2Performance.directTxOctets

       64 bit unsigned wrappable counter."
   ::= {pr1646v2LacpBVlanOutPQsH2PerformanceEntry 117440512}

pr1646v2LacpBVlanOutPQsH2PerformanceQdOcts OBJECT-TYPE
   SYNTAX      Counter64
   MAX-ACCESS  read-only
   STATUS      current
   DESCRIPTION
      "Path: lacpBundle.performance.vlan.outPriorityQueues.h2Performance.queuedOctets

       64 bit unsigned wrappable counter."
   ::= {pr1646v2LacpBVlanOutPQsH2PerformanceEntry 134217728}

pr1646v2LacpBVlanOutPQsH2PerformanceDropOcts OBJECT-TYPE
   SYNTAX      Counter64
   MAX-ACCESS  read-only
   STATUS      current
   DESCRIPTION
      "Path: lacpBundle.performance.vlan.outPriorityQueues.h2Performance.droppedOctets

       64 bit unsigned wrappable counter."
   ::= {pr1646v2LacpBVlanOutPQsH2PerformanceEntry 150994944}

pr1646v2LacpBVlanOutPQsH2PerformanceRDropOcts OBJECT-TYPE
   SYNTAX      Counter64
   MAX-ACCESS  read-only
   STATUS      current
   DESCRIPTION
      "Path: lacpBundle.performance.vlan.outPriorityQueues.h2Performance.redDroppedOctets

       64 bit unsigned wrappable counter."
   ::= {pr1646v2LacpBVlanOutPQsH2PerformanceEntry 218103808}

pr1646v2LacpBVlanOutPQsH2PerformanceCirTxOcts OBJECT-TYPE
   SYNTAX      Counter64
   MAX-ACCESS  read-only
   STATUS      current
   DESCRIPTION
      "Path: lacpBundle.performance.vlan.outPriorityQueues.h2Performance.cirTxOctets

       64 bit unsigned wrappable counter."
   ::= {pr1646v2LacpBVlanOutPQsH2PerformanceEntry 167772160}

pr1646v2LacpBVlanOutPQsH2PerformanceEirTxOcts OBJECT-TYPE
   SYNTAX      Counter64
   MAX-ACCESS  read-only
   STATUS      current
   DESCRIPTION
      "Path: lacpBundle.performance.vlan.outPriorityQueues.h2Performance.eirTxOctets

       64 bit unsigned wrappable counter."
   ::= {pr1646v2LacpBVlanOutPQsH2PerformanceEntry 184549376}

pr1646v2LacpBVlanOutPQsH2PerformanceViolTxOcts OBJECT-TYPE
   SYNTAX      Counter64
   MAX-ACCESS  read-only
   STATUS      current
   DESCRIPTION
      "Path: lacpBundle.performance.vlan.outPriorityQueues.h2Performance.violateTxOctets

       64 bit unsigned wrappable counter."
   ::= {pr1646v2LacpBVlanOutPQsH2PerformanceEntry 318767104}

pr1646v2LacpBVlanOutPQsH2PerformanceBandwidth OBJECT-TYPE
   SYNTAX      Integer32
   MAX-ACCESS  read-only
   STATUS      current
   DESCRIPTION
      "Path: lacpBundle.performance.vlan.outPriorityQueues.h2Performance.bandwidth

       unit name = bps
       formula = 8 * ; 8 /"
   ::= {pr1646v2LacpBVlanOutPQsH2PerformanceEntry 268435456}

pr1646v2LacpBVlanOutPQsH24Performance OBJECT-TYPE
   SYNTAX      SEQUENCE OF Pr1646v2LacpBVlanOutPQsH24PerformanceEntry
   MAX-ACCESS  not-accessible
   STATUS      current
   DESCRIPTION
      ""
   ::= {pr1646v2LacpBVlan 84279296}

pr1646v2LacpBVlanOutPQsH24PerformanceEntry OBJECT-TYPE
   SYNTAX      Pr1646v2LacpBVlanOutPQsH24PerformanceEntry
   MAX-ACCESS  not-accessible
   STATUS      current
   DESCRIPTION
      ""
   INDEX      { pr1646v2LacpBVlanOutPQsH24PerformanceGlobalIx,
                pr1646v2LacpBVlanTableIx,
                pr1646v2LacpBVlanOutPQsTableIx,
                pr1646v2LacpBVlanOutPQsH24PerformanceTableIx }
   ::= {pr1646v2LacpBVlanOutPQsH24Performance 1}

Pr1646v2LacpBVlanOutPQsH24PerformanceEntry ::=
   SEQUENCE
      {
      pr1646v2LacpBVlanOutPQsH24PerformanceGlobalIx
         GlobalIndex,
      pr1646v2LacpBVlanOutPQsH24PerformanceTableIx
         TableIndex,
      pr1646v2LacpBVlanOutPQsH24PerformanceSysUpTime
         TimeTicks,
      pr1646v2LacpBVlanOutPQsH24PerformanceTotPkts
         Counter64,
      pr1646v2LacpBVlanOutPQsH24PerformanceDirTxPkts
         Counter64,
      pr1646v2LacpBVlanOutPQsH24PerformanceQdPkts
         Counter64,
      pr1646v2LacpBVlanOutPQsH24PerformanceDropPkts
         Counter64,
      pr1646v2LacpBVlanOutPQsH24PerformanceRDropPkts
         Counter64,
      pr1646v2LacpBVlanOutPQsH24PerformanceCirTxPkts
         Counter64,
      pr1646v2LacpBVlanOutPQsH24PerformanceEirTxPkts
         Counter64,
      pr1646v2LacpBVlanOutPQsH24PerformanceViolTxPkts
         Counter64,
      pr1646v2LacpBVlanOutPQsH24PerformanceTotOcts
         Counter64,
      pr1646v2LacpBVlanOutPQsH24PerformanceDirTxOcts
         Counter64,
      pr1646v2LacpBVlanOutPQsH24PerformanceQdOcts
         Counter64,
      pr1646v2LacpBVlanOutPQsH24PerformanceDropOcts
         Counter64,
      pr1646v2LacpBVlanOutPQsH24PerformanceRDropOcts
         Counter64,
      pr1646v2LacpBVlanOutPQsH24PerformanceCirTxOcts
         Counter64,
      pr1646v2LacpBVlanOutPQsH24PerformanceEirTxOcts
         Counter64,
      pr1646v2LacpBVlanOutPQsH24PerformanceViolTxOcts
         Counter64,
      pr1646v2LacpBVlanOutPQsH24PerformanceBandwidth
         Integer32
      }

pr1646v2LacpBVlanOutPQsH24PerformanceGlobalIx OBJECT-TYPE
   SYNTAX      GlobalIndex
   MAX-ACCESS  not-accessible
   STATUS      current
   DESCRIPTION
      "The value of the tlsCntTreeGlobalIndex of the MANAGED OBJECT."
   ::= {pr1646v2LacpBVlanOutPQsH24PerformanceEntry 10}

pr1646v2LacpBVlanOutPQsH24PerformanceTableIx OBJECT-TYPE
   SYNTAX      TableIndex
   MAX-ACCESS  not-accessible
   STATUS      current
   DESCRIPTION
      ""
   ::= {pr1646v2LacpBVlanOutPQsH24PerformanceEntry 11}

pr1646v2LacpBVlanOutPQsH24PerformanceSysUpTime OBJECT-TYPE
   SYNTAX      TimeTicks
   MAX-ACCESS  read-only
   STATUS      current
   DESCRIPTION
      "Path: lacpBundle.performance.vlan.outPriorityQueues.h24Performance.sysUpTime

       Time in centi-second."
   ::= {pr1646v2LacpBVlanOutPQsH24PerformanceEntry 16777216}

pr1646v2LacpBVlanOutPQsH24PerformanceTotPkts OBJECT-TYPE
   SYNTAX      Counter64
   MAX-ACCESS  read-only
   STATUS      current
   DESCRIPTION
      "Path: lacpBundle.performance.vlan.outPriorityQueues.h24Performance.totalPkts

       64 bit unsigned wrappable counter."
   ::= {pr1646v2LacpBVlanOutPQsH24PerformanceEntry 234881024}

pr1646v2LacpBVlanOutPQsH24PerformanceDirTxPkts OBJECT-TYPE
   SYNTAX      Counter64
   MAX-ACCESS  read-only
   STATUS      current
   DESCRIPTION
      "Path: lacpBundle.performance.vlan.outPriorityQueues.h24Performance.directTxPkts

       64 bit unsigned wrappable counter."
   ::= {pr1646v2LacpBVlanOutPQsH24PerformanceEntry 33554432}

pr1646v2LacpBVlanOutPQsH24PerformanceQdPkts OBJECT-TYPE
   SYNTAX      Counter64
   MAX-ACCESS  read-only
   STATUS      current
   DESCRIPTION
      "Path: lacpBundle.performance.vlan.outPriorityQueues.h24Performance.queuedPkts

       64 bit unsigned wrappable counter."
   ::= {pr1646v2LacpBVlanOutPQsH24PerformanceEntry 50331648}

pr1646v2LacpBVlanOutPQsH24PerformanceDropPkts OBJECT-TYPE
   SYNTAX      Counter64
   MAX-ACCESS  read-only
   STATUS      current
   DESCRIPTION
      "Path: lacpBundle.performance.vlan.outPriorityQueues.h24Performance.droppedPkts

       64 bit unsigned wrappable counter."
   ::= {pr1646v2LacpBVlanOutPQsH24PerformanceEntry 67108864}

pr1646v2LacpBVlanOutPQsH24PerformanceRDropPkts OBJECT-TYPE
   SYNTAX      Counter64
   MAX-ACCESS  read-only
   STATUS      current
   DESCRIPTION
      "Path: lacpBundle.performance.vlan.outPriorityQueues.h24Performance.redDroppedPkts

       64 bit unsigned wrappable counter."
   ::= {pr1646v2LacpBVlanOutPQsH24PerformanceEntry 201326592}

pr1646v2LacpBVlanOutPQsH24PerformanceCirTxPkts OBJECT-TYPE
   SYNTAX      Counter64
   MAX-ACCESS  read-only
   STATUS      current
   DESCRIPTION
      "Path: lacpBundle.performance.vlan.outPriorityQueues.h24Performance.cirTxPkts

       64 bit unsigned wrappable counter."
   ::= {pr1646v2LacpBVlanOutPQsH24PerformanceEntry 83886080}

pr1646v2LacpBVlanOutPQsH24PerformanceEirTxPkts OBJECT-TYPE
   SYNTAX      Counter64
   MAX-ACCESS  read-only
   STATUS      current
   DESCRIPTION
      "Path: lacpBundle.performance.vlan.outPriorityQueues.h24Performance.eirTxPkts

       64 bit unsigned wrappable counter."
   ::= {pr1646v2LacpBVlanOutPQsH24PerformanceEntry 100663296}

pr1646v2LacpBVlanOutPQsH24PerformanceViolTxPkts OBJECT-TYPE
   SYNTAX      Counter64
   MAX-ACCESS  read-only
   STATUS      current
   DESCRIPTION
      "Path: lacpBundle.performance.vlan.outPriorityQueues.h24Performance.violateTxPkts

       64 bit unsigned wrappable counter."
   ::= {pr1646v2LacpBVlanOutPQsH24PerformanceEntry 301989888}

pr1646v2LacpBVlanOutPQsH24PerformanceTotOcts OBJECT-TYPE
   SYNTAX      Counter64
   MAX-ACCESS  read-only
   STATUS      current
   DESCRIPTION
      "Path: lacpBundle.performance.vlan.outPriorityQueues.h24Performance.totalOctets

       64 bit unsigned wrappable counter."
   ::= {pr1646v2LacpBVlanOutPQsH24PerformanceEntry 251658240}

pr1646v2LacpBVlanOutPQsH24PerformanceDirTxOcts OBJECT-TYPE
   SYNTAX      Counter64
   MAX-ACCESS  read-only
   STATUS      current
   DESCRIPTION
      "Path: lacpBundle.performance.vlan.outPriorityQueues.h24Performance.directTxOctets

       64 bit unsigned wrappable counter."
   ::= {pr1646v2LacpBVlanOutPQsH24PerformanceEntry 117440512}

pr1646v2LacpBVlanOutPQsH24PerformanceQdOcts OBJECT-TYPE
   SYNTAX      Counter64
   MAX-ACCESS  read-only
   STATUS      current
   DESCRIPTION
      "Path: lacpBundle.performance.vlan.outPriorityQueues.h24Performance.queuedOctets

       64 bit unsigned wrappable counter."
   ::= {pr1646v2LacpBVlanOutPQsH24PerformanceEntry 134217728}

pr1646v2LacpBVlanOutPQsH24PerformanceDropOcts OBJECT-TYPE
   SYNTAX      Counter64
   MAX-ACCESS  read-only
   STATUS      current
   DESCRIPTION
      "Path: lacpBundle.performance.vlan.outPriorityQueues.h24Performance.droppedOctets

       64 bit unsigned wrappable counter."
   ::= {pr1646v2LacpBVlanOutPQsH24PerformanceEntry 150994944}

pr1646v2LacpBVlanOutPQsH24PerformanceRDropOcts OBJECT-TYPE
   SYNTAX      Counter64
   MAX-ACCESS  read-only
   STATUS      current
   DESCRIPTION
      "Path: lacpBundle.performance.vlan.outPriorityQueues.h24Performance.redDroppedOctets

       64 bit unsigned wrappable counter."
   ::= {pr1646v2LacpBVlanOutPQsH24PerformanceEntry 218103808}

pr1646v2LacpBVlanOutPQsH24PerformanceCirTxOcts OBJECT-TYPE
   SYNTAX      Counter64
   MAX-ACCESS  read-only
   STATUS      current
   DESCRIPTION
      "Path: lacpBundle.performance.vlan.outPriorityQueues.h24Performance.cirTxOctets

       64 bit unsigned wrappable counter."
   ::= {pr1646v2LacpBVlanOutPQsH24PerformanceEntry 167772160}

pr1646v2LacpBVlanOutPQsH24PerformanceEirTxOcts OBJECT-TYPE
   SYNTAX      Counter64
   MAX-ACCESS  read-only
   STATUS      current
   DESCRIPTION
      "Path: lacpBundle.performance.vlan.outPriorityQueues.h24Performance.eirTxOctets

       64 bit unsigned wrappable counter."
   ::= {pr1646v2LacpBVlanOutPQsH24PerformanceEntry 184549376}

pr1646v2LacpBVlanOutPQsH24PerformanceViolTxOcts OBJECT-TYPE
   SYNTAX      Counter64
   MAX-ACCESS  read-only
   STATUS      current
   DESCRIPTION
      "Path: lacpBundle.performance.vlan.outPriorityQueues.h24Performance.violateTxOctets

       64 bit unsigned wrappable counter."
   ::= {pr1646v2LacpBVlanOutPQsH24PerformanceEntry 318767104}

pr1646v2LacpBVlanOutPQsH24PerformanceBandwidth OBJECT-TYPE
   SYNTAX      Integer32
   MAX-ACCESS  read-only
   STATUS      current
   DESCRIPTION
      "Path: lacpBundle.performance.vlan.outPriorityQueues.h24Performance.bandwidth

       unit name = bps
       formula = 8 * ; 8 /"
   ::= {pr1646v2LacpBVlanOutPQsH24PerformanceEntry 268435456}

pr1646v2LacpBVlanOutPQsD7Performance OBJECT-TYPE
   SYNTAX      SEQUENCE OF Pr1646v2LacpBVlanOutPQsD7PerformanceEntry
   MAX-ACCESS  not-accessible
   STATUS      current
   DESCRIPTION
      ""
   ::= {pr1646v2LacpBVlan 84344832}

pr1646v2LacpBVlanOutPQsD7PerformanceEntry OBJECT-TYPE
   SYNTAX      Pr1646v2LacpBVlanOutPQsD7PerformanceEntry
   MAX-ACCESS  not-accessible
   STATUS      current
   DESCRIPTION
      ""
   INDEX      { pr1646v2LacpBVlanOutPQsD7PerformanceGlobalIx,
                pr1646v2LacpBVlanTableIx,
                pr1646v2LacpBVlanOutPQsTableIx,
                pr1646v2LacpBVlanOutPQsD7PerformanceTableIx }
   ::= {pr1646v2LacpBVlanOutPQsD7Performance 1}

Pr1646v2LacpBVlanOutPQsD7PerformanceEntry ::=
   SEQUENCE
      {
      pr1646v2LacpBVlanOutPQsD7PerformanceGlobalIx
         GlobalIndex,
      pr1646v2LacpBVlanOutPQsD7PerformanceTableIx
         TableIndex,
      pr1646v2LacpBVlanOutPQsD7PerformanceSysUpTime
         TimeTicks,
      pr1646v2LacpBVlanOutPQsD7PerformanceTotPkts
         Counter64,
      pr1646v2LacpBVlanOutPQsD7PerformanceDirTxPkts
         Counter64,
      pr1646v2LacpBVlanOutPQsD7PerformanceQdPkts
         Counter64,
      pr1646v2LacpBVlanOutPQsD7PerformanceDropPkts
         Counter64,
      pr1646v2LacpBVlanOutPQsD7PerformanceRDropPkts
         Counter64,
      pr1646v2LacpBVlanOutPQsD7PerformanceCirTxPkts
         Counter64,
      pr1646v2LacpBVlanOutPQsD7PerformanceEirTxPkts
         Counter64,
      pr1646v2LacpBVlanOutPQsD7PerformanceViolTxPkts
         Counter64,
      pr1646v2LacpBVlanOutPQsD7PerformanceTotOcts
         Counter64,
      pr1646v2LacpBVlanOutPQsD7PerformanceDirTxOcts
         Counter64,
      pr1646v2LacpBVlanOutPQsD7PerformanceQdOcts
         Counter64,
      pr1646v2LacpBVlanOutPQsD7PerformanceDropOcts
         Counter64,
      pr1646v2LacpBVlanOutPQsD7PerformanceRDropOcts
         Counter64,
      pr1646v2LacpBVlanOutPQsD7PerformanceCirTxOcts
         Counter64,
      pr1646v2LacpBVlanOutPQsD7PerformanceEirTxOcts
         Counter64,
      pr1646v2LacpBVlanOutPQsD7PerformanceViolTxOcts
         Counter64,
      pr1646v2LacpBVlanOutPQsD7PerformanceBandwidth
         Integer32
      }

pr1646v2LacpBVlanOutPQsD7PerformanceGlobalIx OBJECT-TYPE
   SYNTAX      GlobalIndex
   MAX-ACCESS  not-accessible
   STATUS      current
   DESCRIPTION
      "The value of the tlsCntTreeGlobalIndex of the MANAGED OBJECT."
   ::= {pr1646v2LacpBVlanOutPQsD7PerformanceEntry 10}

pr1646v2LacpBVlanOutPQsD7PerformanceTableIx OBJECT-TYPE
   SYNTAX      TableIndex
   MAX-ACCESS  not-accessible
   STATUS      current
   DESCRIPTION
      ""
   ::= {pr1646v2LacpBVlanOutPQsD7PerformanceEntry 11}

pr1646v2LacpBVlanOutPQsD7PerformanceSysUpTime OBJECT-TYPE
   SYNTAX      TimeTicks
   MAX-ACCESS  read-only
   STATUS      current
   DESCRIPTION
      "Path: lacpBundle.performance.vlan.outPriorityQueues.d7Performance.sysUpTime

       Time in centi-second."
   ::= {pr1646v2LacpBVlanOutPQsD7PerformanceEntry 16777216}

pr1646v2LacpBVlanOutPQsD7PerformanceTotPkts OBJECT-TYPE
   SYNTAX      Counter64
   MAX-ACCESS  read-only
   STATUS      current
   DESCRIPTION
      "Path: lacpBundle.performance.vlan.outPriorityQueues.d7Performance.totalPkts

       64 bit unsigned wrappable counter."
   ::= {pr1646v2LacpBVlanOutPQsD7PerformanceEntry 234881024}

pr1646v2LacpBVlanOutPQsD7PerformanceDirTxPkts OBJECT-TYPE
   SYNTAX      Counter64
   MAX-ACCESS  read-only
   STATUS      current
   DESCRIPTION
      "Path: lacpBundle.performance.vlan.outPriorityQueues.d7Performance.directTxPkts

       64 bit unsigned wrappable counter."
   ::= {pr1646v2LacpBVlanOutPQsD7PerformanceEntry 33554432}

pr1646v2LacpBVlanOutPQsD7PerformanceQdPkts OBJECT-TYPE
   SYNTAX      Counter64
   MAX-ACCESS  read-only
   STATUS      current
   DESCRIPTION
      "Path: lacpBundle.performance.vlan.outPriorityQueues.d7Performance.queuedPkts

       64 bit unsigned wrappable counter."
   ::= {pr1646v2LacpBVlanOutPQsD7PerformanceEntry 50331648}

pr1646v2LacpBVlanOutPQsD7PerformanceDropPkts OBJECT-TYPE
   SYNTAX      Counter64
   MAX-ACCESS  read-only
   STATUS      current
   DESCRIPTION
      "Path: lacpBundle.performance.vlan.outPriorityQueues.d7Performance.droppedPkts

       64 bit unsigned wrappable counter."
   ::= {pr1646v2LacpBVlanOutPQsD7PerformanceEntry 67108864}

pr1646v2LacpBVlanOutPQsD7PerformanceRDropPkts OBJECT-TYPE
   SYNTAX      Counter64
   MAX-ACCESS  read-only
   STATUS      current
   DESCRIPTION
      "Path: lacpBundle.performance.vlan.outPriorityQueues.d7Performance.redDroppedPkts

       64 bit unsigned wrappable counter."
   ::= {pr1646v2LacpBVlanOutPQsD7PerformanceEntry 201326592}

pr1646v2LacpBVlanOutPQsD7PerformanceCirTxPkts OBJECT-TYPE
   SYNTAX      Counter64
   MAX-ACCESS  read-only
   STATUS      current
   DESCRIPTION
      "Path: lacpBundle.performance.vlan.outPriorityQueues.d7Performance.cirTxPkts

       64 bit unsigned wrappable counter."
   ::= {pr1646v2LacpBVlanOutPQsD7PerformanceEntry 83886080}

pr1646v2LacpBVlanOutPQsD7PerformanceEirTxPkts OBJECT-TYPE
   SYNTAX      Counter64
   MAX-ACCESS  read-only
   STATUS      current
   DESCRIPTION
      "Path: lacpBundle.performance.vlan.outPriorityQueues.d7Performance.eirTxPkts

       64 bit unsigned wrappable counter."
   ::= {pr1646v2LacpBVlanOutPQsD7PerformanceEntry 100663296}

pr1646v2LacpBVlanOutPQsD7PerformanceViolTxPkts OBJECT-TYPE
   SYNTAX      Counter64
   MAX-ACCESS  read-only
   STATUS      current
   DESCRIPTION
      "Path: lacpBundle.performance.vlan.outPriorityQueues.d7Performance.violateTxPkts

       64 bit unsigned wrappable counter."
   ::= {pr1646v2LacpBVlanOutPQsD7PerformanceEntry 301989888}

pr1646v2LacpBVlanOutPQsD7PerformanceTotOcts OBJECT-TYPE
   SYNTAX      Counter64
   MAX-ACCESS  read-only
   STATUS      current
   DESCRIPTION
      "Path: lacpBundle.performance.vlan.outPriorityQueues.d7Performance.totalOctets

       64 bit unsigned wrappable counter."
   ::= {pr1646v2LacpBVlanOutPQsD7PerformanceEntry 251658240}

pr1646v2LacpBVlanOutPQsD7PerformanceDirTxOcts OBJECT-TYPE
   SYNTAX      Counter64
   MAX-ACCESS  read-only
   STATUS      current
   DESCRIPTION
      "Path: lacpBundle.performance.vlan.outPriorityQueues.d7Performance.directTxOctets

       64 bit unsigned wrappable counter."
   ::= {pr1646v2LacpBVlanOutPQsD7PerformanceEntry 117440512}

pr1646v2LacpBVlanOutPQsD7PerformanceQdOcts OBJECT-TYPE
   SYNTAX      Counter64
   MAX-ACCESS  read-only
   STATUS      current
   DESCRIPTION
      "Path: lacpBundle.performance.vlan.outPriorityQueues.d7Performance.queuedOctets

       64 bit unsigned wrappable counter."
   ::= {pr1646v2LacpBVlanOutPQsD7PerformanceEntry 134217728}

pr1646v2LacpBVlanOutPQsD7PerformanceDropOcts OBJECT-TYPE
   SYNTAX      Counter64
   MAX-ACCESS  read-only
   STATUS      current
   DESCRIPTION
      "Path: lacpBundle.performance.vlan.outPriorityQueues.d7Performance.droppedOctets

       64 bit unsigned wrappable counter."
   ::= {pr1646v2LacpBVlanOutPQsD7PerformanceEntry 150994944}

pr1646v2LacpBVlanOutPQsD7PerformanceRDropOcts OBJECT-TYPE
   SYNTAX      Counter64
   MAX-ACCESS  read-only
   STATUS      current
   DESCRIPTION
      "Path: lacpBundle.performance.vlan.outPriorityQueues.d7Performance.redDroppedOctets

       64 bit unsigned wrappable counter."
   ::= {pr1646v2LacpBVlanOutPQsD7PerformanceEntry 218103808}

pr1646v2LacpBVlanOutPQsD7PerformanceCirTxOcts OBJECT-TYPE
   SYNTAX      Counter64
   MAX-ACCESS  read-only
   STATUS      current
   DESCRIPTION
      "Path: lacpBundle.performance.vlan.outPriorityQueues.d7Performance.cirTxOctets

       64 bit unsigned wrappable counter."
   ::= {pr1646v2LacpBVlanOutPQsD7PerformanceEntry 167772160}

pr1646v2LacpBVlanOutPQsD7PerformanceEirTxOcts OBJECT-TYPE
   SYNTAX      Counter64
   MAX-ACCESS  read-only
   STATUS      current
   DESCRIPTION
      "Path: lacpBundle.performance.vlan.outPriorityQueues.d7Performance.eirTxOctets

       64 bit unsigned wrappable counter."
   ::= {pr1646v2LacpBVlanOutPQsD7PerformanceEntry 184549376}

pr1646v2LacpBVlanOutPQsD7PerformanceViolTxOcts OBJECT-TYPE
   SYNTAX      Counter64
   MAX-ACCESS  read-only
   STATUS      current
   DESCRIPTION
      "Path: lacpBundle.performance.vlan.outPriorityQueues.d7Performance.violateTxOctets

       64 bit unsigned wrappable counter."
   ::= {pr1646v2LacpBVlanOutPQsD7PerformanceEntry 318767104}

pr1646v2LacpBVlanOutPQsD7PerformanceBandwidth OBJECT-TYPE
   SYNTAX      Integer32
   MAX-ACCESS  read-only
   STATUS      current
   DESCRIPTION
      "Path: lacpBundle.performance.vlan.outPriorityQueues.d7Performance.bandwidth

       unit name = bps
       formula = 8 * ; 8 /"
   ::= {pr1646v2LacpBVlanOutPQsD7PerformanceEntry 268435456}


pr1646v2LacpBPPPoE OBJECT IDENTIFIER ::= {pr1646v2LacpB 53}

pr1646v2LacpBPPPoESSCTable OBJECT-TYPE
   SYNTAX      SEQUENCE OF Pr1646v2LacpBPPPoEEntry
   MAX-ACCESS  not-accessible
   STATUS      current
   DESCRIPTION
      ""
   ::= {pr1646v2LacpBPPPoE 1}

pr1646v2LacpBPPPoEEntry OBJECT-TYPE
   SYNTAX      Pr1646v2LacpBPPPoEEntry
   MAX-ACCESS  not-accessible
   STATUS      current
   DESCRIPTION
      ""
   INDEX      { pr1646v2LacpBPPPoEGlobalIx,
                pr1646v2LacpBPPPoETableIx }
   ::= {pr1646v2LacpBPPPoESSCTable 1}

Pr1646v2LacpBPPPoEEntry ::=
   SEQUENCE
      {
      pr1646v2LacpBPPPoEGlobalIx
         GlobalIndex,
      pr1646v2LacpBPPPoETableIx
         TableIndex,
      pr1646v2LacpBPPPoEName
         DisplayString,
      pr1646v2LacpBPPPoEMCInOctets
         Counter64,
      pr1646v2LacpBPPPoEMCInUcast
         Counter64,
      pr1646v2LacpBPPPoEMCInNUcastPkts
         Counter64,
      pr1646v2LacpBPPPoEMCInBcastPkts
         Counter64,
      pr1646v2LacpBPPPoEMCInMcastPkts
         Counter64,
      pr1646v2LacpBPPPoEMCInDiscards
         Counter64,
      pr1646v2LacpBPPPoEMCInErrors
         Counter64,
      pr1646v2LacpBPPPoEMCInUnknownProtos
         Counter64,
      pr1646v2LacpBPPPoEMCInDropEx
         Counter64,
      pr1646v2LacpBPPPoEMCInDropNoMac
         Counter64,
      pr1646v2LacpBPPPoEMCInDropNUCast
         Counter64,
      pr1646v2LacpBPPPoEMCInDropFilter
         Counter64,
      pr1646v2LacpBPPPoEMCInBandwidth15sec
         Integer32,
      pr1646v2LacpBPPPoEMCInBandwidth30sec
         Integer32,
      pr1646v2LacpBPPPoEMCInBandwidth1min
         Integer32,
      pr1646v2LacpBPPPoEMCInBandwidth2min
         Integer32,
      pr1646v2LacpBPPPoEMCInBandwidth5min
         Integer32,
      pr1646v2LacpBPPPoEMCOutOctets
         Counter64,
      pr1646v2LacpBPPPoEMCOutUcastPkts
         Counter64,
      pr1646v2LacpBPPPoEMCOutNUcastPkts
         Counter64,
      pr1646v2LacpBPPPoEMCOutBcastPkts
         Counter64,
      pr1646v2LacpBPPPoEMCOutMcastPkts
         Counter64,
      pr1646v2LacpBPPPoEMCOutDiscards
         Counter64,
      pr1646v2LacpBPPPoEMCOutErrors
         Counter64,
      pr1646v2LacpBPPPoEMCOutQLen
         Counter32,
      pr1646v2LacpBPPPoEMCOutDropEx
         Counter64,
      pr1646v2LacpBPPPoEMCOutDropNoArp
         Counter64,
      pr1646v2LacpBPPPoEMCOutDropFilter
         Counter64,
      pr1646v2LacpBPPPoEMCOutBandwidth15sec
         Integer32,
      pr1646v2LacpBPPPoEMCOutBandwidth30sec
         Integer32,
      pr1646v2LacpBPPPoEMCOutBandwidth1min
         Integer32,
      pr1646v2LacpBPPPoEMCOutBandwidth2min
         Integer32,
      pr1646v2LacpBPPPoEMCOutBandwidth5min
         Integer32,
      pr1646v2LacpBPPPoEPppLinkMonitoringRequestsSent
         Gauge32,
      pr1646v2LacpBPPPoEPppLinkMonitoringRepliesRcvd
         Gauge32,
      pr1646v2LacpBPPPoEPppLinkMonitoringRequestsRcvd
         Gauge32,
      pr1646v2LacpBPPPoEPppLinkMonitoringRepliesSent
         Gauge32
      }

pr1646v2LacpBPPPoEGlobalIx OBJECT-TYPE
   SYNTAX      GlobalIndex
   MAX-ACCESS  not-accessible
   STATUS      current
   DESCRIPTION
      "The value of the tlsCntTreeGlobalIndex of the MANAGED OBJECT."
   ::= {pr1646v2LacpBPPPoEEntry 10}

pr1646v2LacpBPPPoETableIx OBJECT-TYPE
   SYNTAX      TableIndex
   MAX-ACCESS  not-accessible
   STATUS      current
   DESCRIPTION
      ""
   ::= {pr1646v2LacpBPPPoEEntry 11}

pr1646v2LacpBPPPoEName OBJECT-TYPE
   SYNTAX      DisplayString
   MAX-ACCESS  read-only
   STATUS      current
   DESCRIPTION
      "Path: lacpBundle.performance.pppoEClient.name"
   ::= {pr1646v2LacpBPPPoEEntry 16777216}

pr1646v2LacpBPPPoEMCInOctets OBJECT-TYPE
   SYNTAX      Counter64
   MAX-ACCESS  read-only
   STATUS      current
   DESCRIPTION
      "Path: lacpBundle.performance.pppoEClient.mibCounters.ifInOctets

       64 bit unsigned wrappable counter."
   ::= {pr1646v2LacpBPPPoEEntry 40697856}

pr1646v2LacpBPPPoEMCInUcast OBJECT-TYPE
   SYNTAX      Counter64
   MAX-ACCESS  read-only
   STATUS      current
   DESCRIPTION
      "Path: lacpBundle.performance.pppoEClient.mibCounters.ifInUcastPkts

       64 bit unsigned wrappable counter."
   ::= {pr1646v2LacpBPPPoEEntry 40763392}

pr1646v2LacpBPPPoEMCInNUcastPkts OBJECT-TYPE
   SYNTAX      Counter64
   MAX-ACCESS  read-only
   STATUS      current
   DESCRIPTION
      "Path: lacpBundle.performance.pppoEClient.mibCounters.ifInNUcastPkts

       64 bit unsigned wrappable counter."
   ::= {pr1646v2LacpBPPPoEEntry 40828928}

pr1646v2LacpBPPPoEMCInBcastPkts OBJECT-TYPE
   SYNTAX      Counter64
   MAX-ACCESS  read-only
   STATUS      current
   DESCRIPTION
      "Path: lacpBundle.performance.pppoEClient.mibCounters.ifInBcastPkts

       64 bit unsigned wrappable counter."
   ::= {pr1646v2LacpBPPPoEEntry 47382528}

pr1646v2LacpBPPPoEMCInMcastPkts OBJECT-TYPE
   SYNTAX      Counter64
   MAX-ACCESS  read-only
   STATUS      current
   DESCRIPTION
      "Path: lacpBundle.performance.pppoEClient.mibCounters.ifInMcastPkts

       64 bit unsigned wrappable counter."
   ::= {pr1646v2LacpBPPPoEEntry 48037888}

pr1646v2LacpBPPPoEMCInDiscards OBJECT-TYPE
   SYNTAX      Counter64
   MAX-ACCESS  read-only
   STATUS      current
   DESCRIPTION
      "Path: lacpBundle.performance.pppoEClient.mibCounters.ifInDiscards

       64 bit unsigned wrappable counter."
   ::= {pr1646v2LacpBPPPoEEntry 40894464}

pr1646v2LacpBPPPoEMCInErrors OBJECT-TYPE
   SYNTAX      Counter64
   MAX-ACCESS  read-only
   STATUS      current
   DESCRIPTION
      "Path: lacpBundle.performance.pppoEClient.mibCounters.ifInErrors

       64 bit unsigned wrappable counter."
   ::= {pr1646v2LacpBPPPoEEntry 40960000}

pr1646v2LacpBPPPoEMCInUnknownProtos OBJECT-TYPE
   SYNTAX      Counter64
   MAX-ACCESS  read-only
   STATUS      current
   DESCRIPTION
      "Path: lacpBundle.performance.pppoEClient.mibCounters.ifInUnknownProtos

       64 bit unsigned wrappable counter."
   ::= {pr1646v2LacpBPPPoEEntry 41025536}

pr1646v2LacpBPPPoEMCInDropEx OBJECT-TYPE
   SYNTAX      Counter64
   MAX-ACCESS  read-only
   STATUS      current
   DESCRIPTION
      "Path: lacpBundle.performance.pppoEClient.mibCounters.ifInDropLevelExceeded

       64 bit unsigned wrappable counter."
   ::= {pr1646v2LacpBPPPoEEntry 42074112}

pr1646v2LacpBPPPoEMCInDropNoMac OBJECT-TYPE
   SYNTAX      Counter64
   MAX-ACCESS  read-only
   STATUS      current
   DESCRIPTION
      "Path: lacpBundle.performance.pppoEClient.mibCounters.ifInDiscardsNoMacFit

       64 bit unsigned wrappable counter."
   ::= {pr1646v2LacpBPPPoEEntry 42270720}

pr1646v2LacpBPPPoEMCInDropNUCast OBJECT-TYPE
   SYNTAX      Counter64
   MAX-ACCESS  read-only
   STATUS      current
   DESCRIPTION
      "Path: lacpBundle.performance.pppoEClient.mibCounters.ifInDiscardsNUCast

       64 bit unsigned wrappable counter."
   ::= {pr1646v2LacpBPPPoEEntry 42467328}

pr1646v2LacpBPPPoEMCInDropFilter OBJECT-TYPE
   SYNTAX      Counter64
   MAX-ACCESS  read-only
   STATUS      current
   DESCRIPTION
      "Path: lacpBundle.performance.pppoEClient.mibCounters.ifInDiscardsFilter

       64 bit unsigned wrappable counter."
   ::= {pr1646v2LacpBPPPoEEntry 42532864}

pr1646v2LacpBPPPoEMCInBandwidth15sec OBJECT-TYPE
   SYNTAX      Integer32
   MAX-ACCESS  read-only
   STATUS      current
   DESCRIPTION
      "Path: lacpBundle.performance.pppoEClient.mibCounters.ifInBandwidth.15sec

       unit name = bps
       formula = 8 * ; 8 /"
   ::= {pr1646v2LacpBPPPoEEntry 45417728}

pr1646v2LacpBPPPoEMCInBandwidth30sec OBJECT-TYPE
   SYNTAX      Integer32
   MAX-ACCESS  read-only
   STATUS      current
   DESCRIPTION
      "Path: lacpBundle.performance.pppoEClient.mibCounters.ifInBandwidth.30sec

       unit name = bps
       formula = 8 * ; 8 /"
   ::= {pr1646v2LacpBPPPoEEntry 45419008}

pr1646v2LacpBPPPoEMCInBandwidth1min OBJECT-TYPE
   SYNTAX      Integer32
   MAX-ACCESS  read-only
   STATUS      current
   DESCRIPTION
      "Path: lacpBundle.performance.pppoEClient.mibCounters.ifInBandwidth.1min

       unit name = bps
       formula = 8 * ; 8 /"
   ::= {pr1646v2LacpBPPPoEEntry 45421568}

pr1646v2LacpBPPPoEMCInBandwidth2min OBJECT-TYPE
   SYNTAX      Integer32
   MAX-ACCESS  read-only
   STATUS      current
   DESCRIPTION
      "Path: lacpBundle.performance.pppoEClient.mibCounters.ifInBandwidth.2min

       unit name = bps
       formula = 8 * ; 8 /"
   ::= {pr1646v2LacpBPPPoEEntry 45426688}

pr1646v2LacpBPPPoEMCInBandwidth5min OBJECT-TYPE
   SYNTAX      Integer32
   MAX-ACCESS  read-only
   STATUS      current
   DESCRIPTION
      "Path: lacpBundle.performance.pppoEClient.mibCounters.ifInBandwidth.5min

       unit name = bps
       formula = 8 * ; 8 /"
   ::= {pr1646v2LacpBPPPoEEntry 45442048}

pr1646v2LacpBPPPoEMCOutOctets OBJECT-TYPE
   SYNTAX      Counter64
   MAX-ACCESS  read-only
   STATUS      current
   DESCRIPTION
      "Path: lacpBundle.performance.pppoEClient.mibCounters.ifOutOctets

       64 bit unsigned wrappable counter."
   ::= {pr1646v2LacpBPPPoEEntry 41091072}

pr1646v2LacpBPPPoEMCOutUcastPkts OBJECT-TYPE
   SYNTAX      Counter64
   MAX-ACCESS  read-only
   STATUS      current
   DESCRIPTION
      "Path: lacpBundle.performance.pppoEClient.mibCounters.ifOutUcastPkts

       64 bit unsigned wrappable counter."
   ::= {pr1646v2LacpBPPPoEEntry 41156608}

pr1646v2LacpBPPPoEMCOutNUcastPkts OBJECT-TYPE
   SYNTAX      Counter64
   MAX-ACCESS  read-only
   STATUS      current
   DESCRIPTION
      "Path: lacpBundle.performance.pppoEClient.mibCounters.ifOutNUcastPkts

       64 bit unsigned wrappable counter."
   ::= {pr1646v2LacpBPPPoEEntry 41222144}

pr1646v2LacpBPPPoEMCOutBcastPkts OBJECT-TYPE
   SYNTAX      Counter64
   MAX-ACCESS  read-only
   STATUS      current
   DESCRIPTION
      "Path: lacpBundle.performance.pppoEClient.mibCounters.ifOutBcastPkts

       64 bit unsigned wrappable counter."
   ::= {pr1646v2LacpBPPPoEEntry 47775744}

pr1646v2LacpBPPPoEMCOutMcastPkts OBJECT-TYPE
   SYNTAX      Counter64
   MAX-ACCESS  read-only
   STATUS      current
   DESCRIPTION
      "Path: lacpBundle.performance.pppoEClient.mibCounters.ifOutMcastPkts

       64 bit unsigned wrappable counter."
   ::= {pr1646v2LacpBPPPoEEntry 48431104}

pr1646v2LacpBPPPoEMCOutDiscards OBJECT-TYPE
   SYNTAX      Counter64
   MAX-ACCESS  read-only
   STATUS      current
   DESCRIPTION
      "Path: lacpBundle.performance.pppoEClient.mibCounters.ifOutDiscards

       64 bit unsigned wrappable counter."
   ::= {pr1646v2LacpBPPPoEEntry 41287680}

pr1646v2LacpBPPPoEMCOutErrors OBJECT-TYPE
   SYNTAX      Counter64
   MAX-ACCESS  read-only
   STATUS      current
   DESCRIPTION
      "Path: lacpBundle.performance.pppoEClient.mibCounters.ifOutErrors

       64 bit unsigned wrappable counter."
   ::= {pr1646v2LacpBPPPoEEntry 41353216}

pr1646v2LacpBPPPoEMCOutQLen OBJECT-TYPE
   SYNTAX      Counter32
   MAX-ACCESS  read-only
   STATUS      current
   DESCRIPTION
      "Path: lacpBundle.performance.pppoEClient.mibCounters.ifOutQLen

       32 bit unsigned wrappable counter."
   ::= {pr1646v2LacpBPPPoEEntry 41418752}

pr1646v2LacpBPPPoEMCOutDropEx OBJECT-TYPE
   SYNTAX      Counter64
   MAX-ACCESS  read-only
   STATUS      current
   DESCRIPTION
      "Path: lacpBundle.performance.pppoEClient.mibCounters.ifOutDropLevelExceeded

       64 bit unsigned wrappable counter."
   ::= {pr1646v2LacpBPPPoEEntry 41484288}

pr1646v2LacpBPPPoEMCOutDropNoArp OBJECT-TYPE
   SYNTAX      Counter64
   MAX-ACCESS  read-only
   STATUS      current
   DESCRIPTION
      "Path: lacpBundle.performance.pppoEClient.mibCounters.ifOutDiscardsNoArp

       64 bit unsigned wrappable counter."
   ::= {pr1646v2LacpBPPPoEEntry 42336256}

pr1646v2LacpBPPPoEMCOutDropFilter OBJECT-TYPE
   SYNTAX      Counter64
   MAX-ACCESS  read-only
   STATUS      current
   DESCRIPTION
      "Path: lacpBundle.performance.pppoEClient.mibCounters.ifOutDiscardsFilter

       64 bit unsigned wrappable counter."
   ::= {pr1646v2LacpBPPPoEEntry 42598400}

pr1646v2LacpBPPPoEMCOutBandwidth15sec OBJECT-TYPE
   SYNTAX      Integer32
   MAX-ACCESS  read-only
   STATUS      current
   DESCRIPTION
      "Path: lacpBundle.performance.pppoEClient.mibCounters.ifOutBandwidth.15sec

       unit name = bps
       formula = 8 * ; 8 /"
   ::= {pr1646v2LacpBPPPoEEntry 45483264}

pr1646v2LacpBPPPoEMCOutBandwidth30sec OBJECT-TYPE
   SYNTAX      Integer32
   MAX-ACCESS  read-only
   STATUS      current
   DESCRIPTION
      "Path: lacpBundle.performance.pppoEClient.mibCounters.ifOutBandwidth.30sec

       unit name = bps
       formula = 8 * ; 8 /"
   ::= {pr1646v2LacpBPPPoEEntry 45484544}

pr1646v2LacpBPPPoEMCOutBandwidth1min OBJECT-TYPE
   SYNTAX      Integer32
   MAX-ACCESS  read-only
   STATUS      current
   DESCRIPTION
      "Path: lacpBundle.performance.pppoEClient.mibCounters.ifOutBandwidth.1min

       unit name = bps
       formula = 8 * ; 8 /"
   ::= {pr1646v2LacpBPPPoEEntry 45487104}

pr1646v2LacpBPPPoEMCOutBandwidth2min OBJECT-TYPE
   SYNTAX      Integer32
   MAX-ACCESS  read-only
   STATUS      current
   DESCRIPTION
      "Path: lacpBundle.performance.pppoEClient.mibCounters.ifOutBandwidth.2min

       unit name = bps
       formula = 8 * ; 8 /"
   ::= {pr1646v2LacpBPPPoEEntry 45492224}

pr1646v2LacpBPPPoEMCOutBandwidth5min OBJECT-TYPE
   SYNTAX      Integer32
   MAX-ACCESS  read-only
   STATUS      current
   DESCRIPTION
      "Path: lacpBundle.performance.pppoEClient.mibCounters.ifOutBandwidth.5min

       unit name = bps
       formula = 8 * ; 8 /"
   ::= {pr1646v2LacpBPPPoEEntry 45507584}

pr1646v2LacpBPPPoEPppLinkMonitoringRequestsSent OBJECT-TYPE
   SYNTAX      Gauge32
   MAX-ACCESS  read-only
   STATUS      current
   DESCRIPTION
      "Path: lacpBundle.performance.pppoEClient.ppp.linkMonitoring.requestsSent

       32 bit unsigned gauge value."
   ::= {pr1646v2LacpBPPPoEEntry 50397440}

pr1646v2LacpBPPPoEPppLinkMonitoringRepliesRcvd OBJECT-TYPE
   SYNTAX      Gauge32
   MAX-ACCESS  read-only
   STATUS      current
   DESCRIPTION
      "Path: lacpBundle.performance.pppoEClient.ppp.linkMonitoring.repliesRcvd

       32 bit unsigned gauge value."
   ::= {pr1646v2LacpBPPPoEEntry 50397696}

pr1646v2LacpBPPPoEPppLinkMonitoringRequestsRcvd OBJECT-TYPE
   SYNTAX      Gauge32
   MAX-ACCESS  read-only
   STATUS      current
   DESCRIPTION
      "Path: lacpBundle.performance.pppoEClient.ppp.linkMonitoring.requestsRcvd

       32 bit unsigned gauge value."
   ::= {pr1646v2LacpBPPPoEEntry 50397952}

pr1646v2LacpBPPPoEPppLinkMonitoringRepliesSent OBJECT-TYPE
   SYNTAX      Gauge32
   MAX-ACCESS  read-only
   STATUS      current
   DESCRIPTION
      "Path: lacpBundle.performance.pppoEClient.ppp.linkMonitoring.repliesSent

       32 bit unsigned gauge value."
   ::= {pr1646v2LacpBPPPoEEntry 50398208}

pr1646v2LacpBPPPoEMCH2P OBJECT-TYPE
   SYNTAX      SEQUENCE OF Pr1646v2LacpBPPPoEMCH2PEntry
   MAX-ACCESS  not-accessible
   STATUS      current
   DESCRIPTION
      ""
   ::= {pr1646v2LacpBPPPoE 41549824}

pr1646v2LacpBPPPoEMCH2PEntry OBJECT-TYPE
   SYNTAX      Pr1646v2LacpBPPPoEMCH2PEntry
   MAX-ACCESS  not-accessible
   STATUS      current
   DESCRIPTION
      ""
   INDEX      { pr1646v2LacpBPPPoEMCH2PGlobalIx,
                pr1646v2LacpBPPPoETableIx,
                pr1646v2LacpBPPPoEMCH2PTableIx }
   ::= {pr1646v2LacpBPPPoEMCH2P 1}

Pr1646v2LacpBPPPoEMCH2PEntry ::=
   SEQUENCE
      {
      pr1646v2LacpBPPPoEMCH2PGlobalIx
         GlobalIndex,
      pr1646v2LacpBPPPoEMCH2PTableIx
         TableIndex,
      pr1646v2LacpBPPPoEMCH2PSysUpTime
         TimeTicks,
      pr1646v2LacpBPPPoEMCH2PIfUpTime
         TimeTicks,
      pr1646v2LacpBPPPoEMCH2PIfStatChanges
         Counter32,
      pr1646v2LacpBPPPoEMCH2PIfInOctets
         Counter64,
      pr1646v2LacpBPPPoEMCH2PIfInUCPkts
         Counter64,
      pr1646v2LacpBPPPoEMCH2PIfInNUCPkts
         Counter64,
      pr1646v2LacpBPPPoEMCH2PIfInBCPkts
         Counter64,
      pr1646v2LacpBPPPoEMCH2PIfInMCPkts
         Counter64,
      pr1646v2LacpBPPPoEMCH2PIfInDiscards
         Counter64,
      pr1646v2LacpBPPPoEMCH2PIfInErrors
         Counter64,
      pr1646v2LacpBPPPoEMCH2PIfInUnkwn
         Counter64,
      pr1646v2LacpBPPPoEMCH2PInDropEx
         Counter64,
      pr1646v2LacpBPPPoEMCH2PInDropNoMac
         Counter64,
      pr1646v2LacpBPPPoEMCH2PInDropNUCast
         Counter64,
      pr1646v2LacpBPPPoEMCH2PInDropFilter
         Counter64,
      pr1646v2LacpBPPPoEMCH2PIfInBandwidth
         Integer32,
      pr1646v2LacpBPPPoEMCH2PIfOutOctets
         Counter64,
      pr1646v2LacpBPPPoEMCH2PIfOutUCPkts
         Counter64,
      pr1646v2LacpBPPPoEMCH2PIfOutNUCPkts
         Counter64,
      pr1646v2LacpBPPPoEMCH2PIfOutBCPkts
         Counter64,
      pr1646v2LacpBPPPoEMCH2PIfOutMCPkts
         Counter64,
      pr1646v2LacpBPPPoEMCH2PIfOutDiscards
         Counter64,
      pr1646v2LacpBPPPoEMCH2PIfOutErrors
         Counter64,
      pr1646v2LacpBPPPoEMCH2POutDropEx
         Counter64,
      pr1646v2LacpBPPPoEMCH2POutDropNoArp
         Counter64,
      pr1646v2LacpBPPPoEMCH2POutDropFilter
         Counter64,
      pr1646v2LacpBPPPoEMCH2PIfOutBandwidth
         Integer32,
      pr1646v2LacpBPPPoEMCH2PIfErrSec
         Counter32
      }

pr1646v2LacpBPPPoEMCH2PGlobalIx OBJECT-TYPE
   SYNTAX      GlobalIndex
   MAX-ACCESS  not-accessible
   STATUS      current
   DESCRIPTION
      "The value of the tlsCntTreeGlobalIndex of the MANAGED OBJECT."
   ::= {pr1646v2LacpBPPPoEMCH2PEntry 10}

pr1646v2LacpBPPPoEMCH2PTableIx OBJECT-TYPE
   SYNTAX      TableIndex
   MAX-ACCESS  not-accessible
   STATUS      current
   DESCRIPTION
      ""
   ::= {pr1646v2LacpBPPPoEMCH2PEntry 11}

pr1646v2LacpBPPPoEMCH2PSysUpTime OBJECT-TYPE
   SYNTAX      TimeTicks
   MAX-ACCESS  read-only
   STATUS      current
   DESCRIPTION
      "Path: lacpBundle.performance.pppoEClient.mibCounters.h2Performance.sysUpTime

       Time in centi-second."
   ::= {pr1646v2LacpBPPPoEMCH2PEntry 16777216}

pr1646v2LacpBPPPoEMCH2PIfUpTime OBJECT-TYPE
   SYNTAX      TimeTicks
   MAX-ACCESS  read-only
   STATUS      current
   DESCRIPTION
      "Path: lacpBundle.performance.pppoEClient.mibCounters.h2Performance.ifUpTime

       Time in centi-second."
   ::= {pr1646v2LacpBPPPoEMCH2PEntry 33554432}

pr1646v2LacpBPPPoEMCH2PIfStatChanges OBJECT-TYPE
   SYNTAX      Counter32
   MAX-ACCESS  read-only
   STATUS      current
   DESCRIPTION
      "Path: lacpBundle.performance.pppoEClient.mibCounters.h2Performance.ifStatusChanges

       32 bit unsigned wrappable counter."
   ::= {pr1646v2LacpBPPPoEMCH2PEntry 50331648}

pr1646v2LacpBPPPoEMCH2PIfInOctets OBJECT-TYPE
   SYNTAX      Counter64
   MAX-ACCESS  read-only
   STATUS      current
   DESCRIPTION
      "Path: lacpBundle.performance.pppoEClient.mibCounters.h2Performance.ifInOctets

       64 bit unsigned wrappable counter."
   ::= {pr1646v2LacpBPPPoEMCH2PEntry 67108864}

pr1646v2LacpBPPPoEMCH2PIfInUCPkts OBJECT-TYPE
   SYNTAX      Counter64
   MAX-ACCESS  read-only
   STATUS      current
   DESCRIPTION
      "Path: lacpBundle.performance.pppoEClient.mibCounters.h2Performance.ifInUcastPkts

       64 bit unsigned wrappable counter."
   ::= {pr1646v2LacpBPPPoEMCH2PEntry 83886080}

pr1646v2LacpBPPPoEMCH2PIfInNUCPkts OBJECT-TYPE
   SYNTAX      Counter64
   MAX-ACCESS  read-only
   STATUS      current
   DESCRIPTION
      "Path: lacpBundle.performance.pppoEClient.mibCounters.h2Performance.ifInNUcastPkts

       64 bit unsigned wrappable counter."
   ::= {pr1646v2LacpBPPPoEMCH2PEntry 100663296}

pr1646v2LacpBPPPoEMCH2PIfInBCPkts OBJECT-TYPE
   SYNTAX      Counter64
   MAX-ACCESS  read-only
   STATUS      current
   DESCRIPTION
      "Path: lacpBundle.performance.pppoEClient.mibCounters.h2Performance.ifInBcastPkts

       64 bit unsigned wrappable counter."
   ::= {pr1646v2LacpBPPPoEMCH2PEntry 419430400}

pr1646v2LacpBPPPoEMCH2PIfInMCPkts OBJECT-TYPE
   SYNTAX      Counter64
   MAX-ACCESS  read-only
   STATUS      current
   DESCRIPTION
      "Path: lacpBundle.performance.pppoEClient.mibCounters.h2Performance.ifInMcastPkts

       64 bit unsigned wrappable counter."
   ::= {pr1646v2LacpBPPPoEMCH2PEntry 436207616}

pr1646v2LacpBPPPoEMCH2PIfInDiscards OBJECT-TYPE
   SYNTAX      Counter64
   MAX-ACCESS  read-only
   STATUS      current
   DESCRIPTION
      "Path: lacpBundle.performance.pppoEClient.mibCounters.h2Performance.ifInDiscards

       64 bit unsigned wrappable counter."
   ::= {pr1646v2LacpBPPPoEMCH2PEntry 117440512}

pr1646v2LacpBPPPoEMCH2PIfInErrors OBJECT-TYPE
   SYNTAX      Counter64
   MAX-ACCESS  read-only
   STATUS      current
   DESCRIPTION
      "Path: lacpBundle.performance.pppoEClient.mibCounters.h2Performance.ifInErrors

       64 bit unsigned wrappable counter."
   ::= {pr1646v2LacpBPPPoEMCH2PEntry 134217728}

pr1646v2LacpBPPPoEMCH2PIfInUnkwn OBJECT-TYPE
   SYNTAX      Counter64
   MAX-ACCESS  read-only
   STATUS      current
   DESCRIPTION
      "Path: lacpBundle.performance.pppoEClient.mibCounters.h2Performance.ifInUnknownProtos

       64 bit unsigned wrappable counter."
   ::= {pr1646v2LacpBPPPoEMCH2PEntry 150994944}

pr1646v2LacpBPPPoEMCH2PInDropEx OBJECT-TYPE
   SYNTAX      Counter64
   MAX-ACCESS  read-only
   STATUS      current
   DESCRIPTION
      "Path: lacpBundle.performance.pppoEClient.mibCounters.h2Performance.ifInDropLevelExceeded

       64 bit unsigned wrappable counter."
   ::= {pr1646v2LacpBPPPoEMCH2PEntry 335544320}

pr1646v2LacpBPPPoEMCH2PInDropNoMac OBJECT-TYPE
   SYNTAX      Counter64
   MAX-ACCESS  read-only
   STATUS      current
   DESCRIPTION
      "Path: lacpBundle.performance.pppoEClient.mibCounters.h2Performance.fInDiscardsNoMacFit

       64 bit unsigned wrappable counter."
   ::= {pr1646v2LacpBPPPoEMCH2PEntry 301989888}

pr1646v2LacpBPPPoEMCH2PInDropNUCast OBJECT-TYPE
   SYNTAX      Counter64
   MAX-ACCESS  read-only
   STATUS      current
   DESCRIPTION
      "Path: lacpBundle.performance.pppoEClient.mibCounters.h2Performance.fInDiscardsNUCast

       64 bit unsigned wrappable counter."
   ::= {pr1646v2LacpBPPPoEMCH2PEntry 318767104}

pr1646v2LacpBPPPoEMCH2PInDropFilter OBJECT-TYPE
   SYNTAX      Counter64
   MAX-ACCESS  read-only
   STATUS      current
   DESCRIPTION
      "Path: lacpBundle.performance.pppoEClient.mibCounters.h2Performance.fInDiscardsFilter

       64 bit unsigned wrappable counter."
   ::= {pr1646v2LacpBPPPoEMCH2PEntry 385875968}

pr1646v2LacpBPPPoEMCH2PIfInBandwidth OBJECT-TYPE
   SYNTAX      Integer32
   MAX-ACCESS  read-only
   STATUS      current
   DESCRIPTION
      "Path: lacpBundle.performance.pppoEClient.mibCounters.h2Performance.ifInBandwidth

       unit name = bps
       formula = 8 * ; 8 /"
   ::= {pr1646v2LacpBPPPoEMCH2PEntry 268435456}

pr1646v2LacpBPPPoEMCH2PIfOutOctets OBJECT-TYPE
   SYNTAX      Counter64
   MAX-ACCESS  read-only
   STATUS      current
   DESCRIPTION
      "Path: lacpBundle.performance.pppoEClient.mibCounters.h2Performance.ifOutOctets

       64 bit unsigned wrappable counter."
   ::= {pr1646v2LacpBPPPoEMCH2PEntry 167772160}

pr1646v2LacpBPPPoEMCH2PIfOutUCPkts OBJECT-TYPE
   SYNTAX      Counter64
   MAX-ACCESS  read-only
   STATUS      current
   DESCRIPTION
      "Path: lacpBundle.performance.pppoEClient.mibCounters.h2Performance.ifOutUcastPkts

       64 bit unsigned wrappable counter."
   ::= {pr1646v2LacpBPPPoEMCH2PEntry 184549376}

pr1646v2LacpBPPPoEMCH2PIfOutNUCPkts OBJECT-TYPE
   SYNTAX      Counter64
   MAX-ACCESS  read-only
   STATUS      current
   DESCRIPTION
      "Path: lacpBundle.performance.pppoEClient.mibCounters.h2Performance.ifOutNUcastPkts

       64 bit unsigned wrappable counter."
   ::= {pr1646v2LacpBPPPoEMCH2PEntry 201326592}

pr1646v2LacpBPPPoEMCH2PIfOutBCPkts OBJECT-TYPE
   SYNTAX      Counter64
   MAX-ACCESS  read-only
   STATUS      current
   DESCRIPTION
      "Path: lacpBundle.performance.pppoEClient.mibCounters.h2Performance.ifOutBcastPkts

       64 bit unsigned wrappable counter."
   ::= {pr1646v2LacpBPPPoEMCH2PEntry 452984832}

pr1646v2LacpBPPPoEMCH2PIfOutMCPkts OBJECT-TYPE
   SYNTAX      Counter64
   MAX-ACCESS  read-only
   STATUS      current
   DESCRIPTION
      "Path: lacpBundle.performance.pppoEClient.mibCounters.h2Performance.ifOutMcastPkts

       64 bit unsigned wrappable counter."
   ::= {pr1646v2LacpBPPPoEMCH2PEntry 469762048}

pr1646v2LacpBPPPoEMCH2PIfOutDiscards OBJECT-TYPE
   SYNTAX      Counter64
   MAX-ACCESS  read-only
   STATUS      current
   DESCRIPTION
      "Path: lacpBundle.performance.pppoEClient.mibCounters.h2Performance.ifOutDiscards

       64 bit unsigned wrappable counter."
   ::= {pr1646v2LacpBPPPoEMCH2PEntry 218103808}

pr1646v2LacpBPPPoEMCH2PIfOutErrors OBJECT-TYPE
   SYNTAX      Counter64
   MAX-ACCESS  read-only
   STATUS      current
   DESCRIPTION
      "Path: lacpBundle.performance.pppoEClient.mibCounters.h2Performance.ifOutErrors

       64 bit unsigned wrappable counter."
   ::= {pr1646v2LacpBPPPoEMCH2PEntry 234881024}

pr1646v2LacpBPPPoEMCH2POutDropEx OBJECT-TYPE
   SYNTAX      Counter64
   MAX-ACCESS  read-only
   STATUS      current
   DESCRIPTION
      "Path: lacpBundle.performance.pppoEClient.mibCounters.h2Performance.ifOutDropLevelExceeded

       64 bit unsigned wrappable counter."
   ::= {pr1646v2LacpBPPPoEMCH2PEntry 352321536}

pr1646v2LacpBPPPoEMCH2POutDropNoArp OBJECT-TYPE
   SYNTAX      Counter64
   MAX-ACCESS  read-only
   STATUS      current
   DESCRIPTION
      "Path: lacpBundle.performance.pppoEClient.mibCounters.h2Performance.ifOutDiscardsNoArp

       64 bit unsigned wrappable counter."
   ::= {pr1646v2LacpBPPPoEMCH2PEntry 369098752}

pr1646v2LacpBPPPoEMCH2POutDropFilter OBJECT-TYPE
   SYNTAX      Counter64
   MAX-ACCESS  read-only
   STATUS      current
   DESCRIPTION
      "Path: lacpBundle.performance.pppoEClient.mibCounters.h2Performance.ifOutDiscardsFilter

       64 bit unsigned wrappable counter."
   ::= {pr1646v2LacpBPPPoEMCH2PEntry 402653184}

pr1646v2LacpBPPPoEMCH2PIfOutBandwidth OBJECT-TYPE
   SYNTAX      Integer32
   MAX-ACCESS  read-only
   STATUS      current
   DESCRIPTION
      "Path: lacpBundle.performance.pppoEClient.mibCounters.h2Performance.ifOutBandwidth

       unit name = bps
       formula = 8 * ; 8 /"
   ::= {pr1646v2LacpBPPPoEMCH2PEntry 285212672}

pr1646v2LacpBPPPoEMCH2PIfErrSec OBJECT-TYPE
   SYNTAX      Counter32
   MAX-ACCESS  read-only
   STATUS      current
   DESCRIPTION
      "Path: lacpBundle.performance.pppoEClient.mibCounters.h2Performance.ifErrSec

       32 bit unsigned wrappable counter."
   ::= {pr1646v2LacpBPPPoEMCH2PEntry 251658240}

pr1646v2LacpBPPPoEMCH24P OBJECT-TYPE
   SYNTAX      SEQUENCE OF Pr1646v2LacpBPPPoEMCH24PEntry
   MAX-ACCESS  not-accessible
   STATUS      current
   DESCRIPTION
      ""
   ::= {pr1646v2LacpBPPPoE 41615360}

pr1646v2LacpBPPPoEMCH24PEntry OBJECT-TYPE
   SYNTAX      Pr1646v2LacpBPPPoEMCH24PEntry
   MAX-ACCESS  not-accessible
   STATUS      current
   DESCRIPTION
      ""
   INDEX      { pr1646v2LacpBPPPoEMCH24PGlobalIx,
                pr1646v2LacpBPPPoETableIx,
                pr1646v2LacpBPPPoEMCH24PTableIx }
   ::= {pr1646v2LacpBPPPoEMCH24P 1}

Pr1646v2LacpBPPPoEMCH24PEntry ::=
   SEQUENCE
      {
      pr1646v2LacpBPPPoEMCH24PGlobalIx
         GlobalIndex,
      pr1646v2LacpBPPPoEMCH24PTableIx
         TableIndex,
      pr1646v2LacpBPPPoEMCH24PSysUpTime
         TimeTicks,
      pr1646v2LacpBPPPoEMCH24PIfUpTime
         TimeTicks,
      pr1646v2LacpBPPPoEMCH24PIfStatChanges
         Counter32,
      pr1646v2LacpBPPPoEMCH24PIfInOctets
         Counter64,
      pr1646v2LacpBPPPoEMCH24PIfInUCPkts
         Counter64,
      pr1646v2LacpBPPPoEMCH24PIfInNUCPkts
         Counter64,
      pr1646v2LacpBPPPoEMCH24PIfInBCPkts
         Counter64,
      pr1646v2LacpBPPPoEMCH24PIfInMCPkts
         Counter64,
      pr1646v2LacpBPPPoEMCH24PIfInDiscards
         Counter64,
      pr1646v2LacpBPPPoEMCH24PIfInErrors
         Counter64,
      pr1646v2LacpBPPPoEMCH24PIfInUnkwn
         Counter64,
      pr1646v2LacpBPPPoEMCH24PInDropEx
         Counter64,
      pr1646v2LacpBPPPoEMCH24PInDropNoMac
         Counter64,
      pr1646v2LacpBPPPoEMCH24PInDropNUCast
         Counter64,
      pr1646v2LacpBPPPoEMCH24PInDropFilter
         Counter64,
      pr1646v2LacpBPPPoEMCH24PIfInBandwidth
         Integer32,
      pr1646v2LacpBPPPoEMCH24PIfOutOctets
         Counter64,
      pr1646v2LacpBPPPoEMCH24PIfOutUCPkts
         Counter64,
      pr1646v2LacpBPPPoEMCH24PIfOutNUCPkts
         Counter64,
      pr1646v2LacpBPPPoEMCH24PIfOutBCPkts
         Counter64,
      pr1646v2LacpBPPPoEMCH24PIfOutMCPkts
         Counter64,
      pr1646v2LacpBPPPoEMCH24PIfOutDiscards
         Counter64,
      pr1646v2LacpBPPPoEMCH24PIfOutErrors
         Counter64,
      pr1646v2LacpBPPPoEMCH24POutDropEx
         Counter64,
      pr1646v2LacpBPPPoEMCH24POutDropNoArp
         Counter64,
      pr1646v2LacpBPPPoEMCH24POutDropFilter
         Counter64,
      pr1646v2LacpBPPPoEMCH24PIfOutBandwidth
         Integer32,
      pr1646v2LacpBPPPoEMCH24PIfErrSec
         Counter32
      }

pr1646v2LacpBPPPoEMCH24PGlobalIx OBJECT-TYPE
   SYNTAX      GlobalIndex
   MAX-ACCESS  not-accessible
   STATUS      current
   DESCRIPTION
      "The value of the tlsCntTreeGlobalIndex of the MANAGED OBJECT."
   ::= {pr1646v2LacpBPPPoEMCH24PEntry 10}

pr1646v2LacpBPPPoEMCH24PTableIx OBJECT-TYPE
   SYNTAX      TableIndex
   MAX-ACCESS  not-accessible
   STATUS      current
   DESCRIPTION
      ""
   ::= {pr1646v2LacpBPPPoEMCH24PEntry 11}

pr1646v2LacpBPPPoEMCH24PSysUpTime OBJECT-TYPE
   SYNTAX      TimeTicks
   MAX-ACCESS  read-only
   STATUS      current
   DESCRIPTION
      "Path: lacpBundle.performance.pppoEClient.mibCounters.h24Performance.sysUpTime

       Time in centi-second."
   ::= {pr1646v2LacpBPPPoEMCH24PEntry 16777216}

pr1646v2LacpBPPPoEMCH24PIfUpTime OBJECT-TYPE
   SYNTAX      TimeTicks
   MAX-ACCESS  read-only
   STATUS      current
   DESCRIPTION
      "Path: lacpBundle.performance.pppoEClient.mibCounters.h24Performance.ifUpTime

       Time in centi-second."
   ::= {pr1646v2LacpBPPPoEMCH24PEntry 33554432}

pr1646v2LacpBPPPoEMCH24PIfStatChanges OBJECT-TYPE
   SYNTAX      Counter32
   MAX-ACCESS  read-only
   STATUS      current
   DESCRIPTION
      "Path: lacpBundle.performance.pppoEClient.mibCounters.h24Performance.ifStatusChanges

       32 bit unsigned wrappable counter."
   ::= {pr1646v2LacpBPPPoEMCH24PEntry 50331648}

pr1646v2LacpBPPPoEMCH24PIfInOctets OBJECT-TYPE
   SYNTAX      Counter64
   MAX-ACCESS  read-only
   STATUS      current
   DESCRIPTION
      "Path: lacpBundle.performance.pppoEClient.mibCounters.h24Performance.ifInOctets

       64 bit unsigned wrappable counter."
   ::= {pr1646v2LacpBPPPoEMCH24PEntry 67108864}

pr1646v2LacpBPPPoEMCH24PIfInUCPkts OBJECT-TYPE
   SYNTAX      Counter64
   MAX-ACCESS  read-only
   STATUS      current
   DESCRIPTION
      "Path: lacpBundle.performance.pppoEClient.mibCounters.h24Performance.ifInUcastPkts

       64 bit unsigned wrappable counter."
   ::= {pr1646v2LacpBPPPoEMCH24PEntry 83886080}

pr1646v2LacpBPPPoEMCH24PIfInNUCPkts OBJECT-TYPE
   SYNTAX      Counter64
   MAX-ACCESS  read-only
   STATUS      current
   DESCRIPTION
      "Path: lacpBundle.performance.pppoEClient.mibCounters.h24Performance.ifInNUcastPkts

       64 bit unsigned wrappable counter."
   ::= {pr1646v2LacpBPPPoEMCH24PEntry 100663296}

pr1646v2LacpBPPPoEMCH24PIfInBCPkts OBJECT-TYPE
   SYNTAX      Counter64
   MAX-ACCESS  read-only
   STATUS      current
   DESCRIPTION
      "Path: lacpBundle.performance.pppoEClient.mibCounters.h24Performance.ifInBcastPkts

       64 bit unsigned wrappable counter."
   ::= {pr1646v2LacpBPPPoEMCH24PEntry 419430400}

pr1646v2LacpBPPPoEMCH24PIfInMCPkts OBJECT-TYPE
   SYNTAX      Counter64
   MAX-ACCESS  read-only
   STATUS      current
   DESCRIPTION
      "Path: lacpBundle.performance.pppoEClient.mibCounters.h24Performance.ifInMcastPkts

       64 bit unsigned wrappable counter."
   ::= {pr1646v2LacpBPPPoEMCH24PEntry 436207616}

pr1646v2LacpBPPPoEMCH24PIfInDiscards OBJECT-TYPE
   SYNTAX      Counter64
   MAX-ACCESS  read-only
   STATUS      current
   DESCRIPTION
      "Path: lacpBundle.performance.pppoEClient.mibCounters.h24Performance.ifInDiscards

       64 bit unsigned wrappable counter."
   ::= {pr1646v2LacpBPPPoEMCH24PEntry 117440512}

pr1646v2LacpBPPPoEMCH24PIfInErrors OBJECT-TYPE
   SYNTAX      Counter64
   MAX-ACCESS  read-only
   STATUS      current
   DESCRIPTION
      "Path: lacpBundle.performance.pppoEClient.mibCounters.h24Performance.ifInErrors

       64 bit unsigned wrappable counter."
   ::= {pr1646v2LacpBPPPoEMCH24PEntry 134217728}

pr1646v2LacpBPPPoEMCH24PIfInUnkwn OBJECT-TYPE
   SYNTAX      Counter64
   MAX-ACCESS  read-only
   STATUS      current
   DESCRIPTION
      "Path: lacpBundle.performance.pppoEClient.mibCounters.h24Performance.ifInUnknownProtos

       64 bit unsigned wrappable counter."
   ::= {pr1646v2LacpBPPPoEMCH24PEntry 150994944}

pr1646v2LacpBPPPoEMCH24PInDropEx OBJECT-TYPE
   SYNTAX      Counter64
   MAX-ACCESS  read-only
   STATUS      current
   DESCRIPTION
      "Path: lacpBundle.performance.pppoEClient.mibCounters.h24Performance.ifInDropLevelExceeded

       64 bit unsigned wrappable counter."
   ::= {pr1646v2LacpBPPPoEMCH24PEntry 335544320}

pr1646v2LacpBPPPoEMCH24PInDropNoMac OBJECT-TYPE
   SYNTAX      Counter64
   MAX-ACCESS  read-only
   STATUS      current
   DESCRIPTION
      "Path: lacpBundle.performance.pppoEClient.mibCounters.h24Performance.fInDiscardsNoMacFit

       64 bit unsigned wrappable counter."
   ::= {pr1646v2LacpBPPPoEMCH24PEntry 301989888}

pr1646v2LacpBPPPoEMCH24PInDropNUCast OBJECT-TYPE
   SYNTAX      Counter64
   MAX-ACCESS  read-only
   STATUS      current
   DESCRIPTION
      "Path: lacpBundle.performance.pppoEClient.mibCounters.h24Performance.fInDiscardsNUCast

       64 bit unsigned wrappable counter."
   ::= {pr1646v2LacpBPPPoEMCH24PEntry 318767104}

pr1646v2LacpBPPPoEMCH24PInDropFilter OBJECT-TYPE
   SYNTAX      Counter64
   MAX-ACCESS  read-only
   STATUS      current
   DESCRIPTION
      "Path: lacpBundle.performance.pppoEClient.mibCounters.h24Performance.fInDiscardsFilter

       64 bit unsigned wrappable counter."
   ::= {pr1646v2LacpBPPPoEMCH24PEntry 385875968}

pr1646v2LacpBPPPoEMCH24PIfInBandwidth OBJECT-TYPE
   SYNTAX      Integer32
   MAX-ACCESS  read-only
   STATUS      current
   DESCRIPTION
      "Path: lacpBundle.performance.pppoEClient.mibCounters.h24Performance.ifInBandwidth

       unit name = bps
       formula = 8 * ; 8 /"
   ::= {pr1646v2LacpBPPPoEMCH24PEntry 268435456}

pr1646v2LacpBPPPoEMCH24PIfOutOctets OBJECT-TYPE
   SYNTAX      Counter64
   MAX-ACCESS  read-only
   STATUS      current
   DESCRIPTION
      "Path: lacpBundle.performance.pppoEClient.mibCounters.h24Performance.ifOutOctets

       64 bit unsigned wrappable counter."
   ::= {pr1646v2LacpBPPPoEMCH24PEntry 167772160}

pr1646v2LacpBPPPoEMCH24PIfOutUCPkts OBJECT-TYPE
   SYNTAX      Counter64
   MAX-ACCESS  read-only
   STATUS      current
   DESCRIPTION
      "Path: lacpBundle.performance.pppoEClient.mibCounters.h24Performance.ifOutUcastPkts

       64 bit unsigned wrappable counter."
   ::= {pr1646v2LacpBPPPoEMCH24PEntry 184549376}

pr1646v2LacpBPPPoEMCH24PIfOutNUCPkts OBJECT-TYPE
   SYNTAX      Counter64
   MAX-ACCESS  read-only
   STATUS      current
   DESCRIPTION
      "Path: lacpBundle.performance.pppoEClient.mibCounters.h24Performance.ifOutNUcastPkts

       64 bit unsigned wrappable counter."
   ::= {pr1646v2LacpBPPPoEMCH24PEntry 201326592}

pr1646v2LacpBPPPoEMCH24PIfOutBCPkts OBJECT-TYPE
   SYNTAX      Counter64
   MAX-ACCESS  read-only
   STATUS      current
   DESCRIPTION
      "Path: lacpBundle.performance.pppoEClient.mibCounters.h24Performance.ifOutBcastPkts

       64 bit unsigned wrappable counter."
   ::= {pr1646v2LacpBPPPoEMCH24PEntry 452984832}

pr1646v2LacpBPPPoEMCH24PIfOutMCPkts OBJECT-TYPE
   SYNTAX      Counter64
   MAX-ACCESS  read-only
   STATUS      current
   DESCRIPTION
      "Path: lacpBundle.performance.pppoEClient.mibCounters.h24Performance.ifOutMcastPkts

       64 bit unsigned wrappable counter."
   ::= {pr1646v2LacpBPPPoEMCH24PEntry 469762048}

pr1646v2LacpBPPPoEMCH24PIfOutDiscards OBJECT-TYPE
   SYNTAX      Counter64
   MAX-ACCESS  read-only
   STATUS      current
   DESCRIPTION
      "Path: lacpBundle.performance.pppoEClient.mibCounters.h24Performance.ifOutDiscards

       64 bit unsigned wrappable counter."
   ::= {pr1646v2LacpBPPPoEMCH24PEntry 218103808}

pr1646v2LacpBPPPoEMCH24PIfOutErrors OBJECT-TYPE
   SYNTAX      Counter64
   MAX-ACCESS  read-only
   STATUS      current
   DESCRIPTION
      "Path: lacpBundle.performance.pppoEClient.mibCounters.h24Performance.ifOutErrors

       64 bit unsigned wrappable counter."
   ::= {pr1646v2LacpBPPPoEMCH24PEntry 234881024}

pr1646v2LacpBPPPoEMCH24POutDropEx OBJECT-TYPE
   SYNTAX      Counter64
   MAX-ACCESS  read-only
   STATUS      current
   DESCRIPTION
      "Path: lacpBundle.performance.pppoEClient.mibCounters.h24Performance.ifOutDropLevelExceeded

       64 bit unsigned wrappable counter."
   ::= {pr1646v2LacpBPPPoEMCH24PEntry 352321536}

pr1646v2LacpBPPPoEMCH24POutDropNoArp OBJECT-TYPE
   SYNTAX      Counter64
   MAX-ACCESS  read-only
   STATUS      current
   DESCRIPTION
      "Path: lacpBundle.performance.pppoEClient.mibCounters.h24Performance.ifOutDiscardsNoArp

       64 bit unsigned wrappable counter."
   ::= {pr1646v2LacpBPPPoEMCH24PEntry 369098752}

pr1646v2LacpBPPPoEMCH24POutDropFilter OBJECT-TYPE
   SYNTAX      Counter64
   MAX-ACCESS  read-only
   STATUS      current
   DESCRIPTION
      "Path: lacpBundle.performance.pppoEClient.mibCounters.h24Performance.ifOutDiscardsFilter

       64 bit unsigned wrappable counter."
   ::= {pr1646v2LacpBPPPoEMCH24PEntry 402653184}

pr1646v2LacpBPPPoEMCH24PIfOutBandwidth OBJECT-TYPE
   SYNTAX      Integer32
   MAX-ACCESS  read-only
   STATUS      current
   DESCRIPTION
      "Path: lacpBundle.performance.pppoEClient.mibCounters.h24Performance.ifOutBandwidth

       unit name = bps
       formula = 8 * ; 8 /"
   ::= {pr1646v2LacpBPPPoEMCH24PEntry 285212672}

pr1646v2LacpBPPPoEMCH24PIfErrSec OBJECT-TYPE
   SYNTAX      Counter32
   MAX-ACCESS  read-only
   STATUS      current
   DESCRIPTION
      "Path: lacpBundle.performance.pppoEClient.mibCounters.h24Performance.ifErrSec

       32 bit unsigned wrappable counter."
   ::= {pr1646v2LacpBPPPoEMCH24PEntry 251658240}

pr1646v2LacpBPPPoEMCD7P OBJECT-TYPE
   SYNTAX      SEQUENCE OF Pr1646v2LacpBPPPoEMCD7PEntry
   MAX-ACCESS  not-accessible
   STATUS      current
   DESCRIPTION
      ""
   ::= {pr1646v2LacpBPPPoE 41680896}

pr1646v2LacpBPPPoEMCD7PEntry OBJECT-TYPE
   SYNTAX      Pr1646v2LacpBPPPoEMCD7PEntry
   MAX-ACCESS  not-accessible
   STATUS      current
   DESCRIPTION
      ""
   INDEX      { pr1646v2LacpBPPPoEMCD7PGlobalIx,
                pr1646v2LacpBPPPoETableIx,
                pr1646v2LacpBPPPoEMCD7PTableIx }
   ::= {pr1646v2LacpBPPPoEMCD7P 1}

Pr1646v2LacpBPPPoEMCD7PEntry ::=
   SEQUENCE
      {
      pr1646v2LacpBPPPoEMCD7PGlobalIx
         GlobalIndex,
      pr1646v2LacpBPPPoEMCD7PTableIx
         TableIndex,
      pr1646v2LacpBPPPoEMCD7PSysUpTime
         TimeTicks,
      pr1646v2LacpBPPPoEMCD7PIfUpTime
         TimeTicks,
      pr1646v2LacpBPPPoEMCD7PIfStatChanges
         Counter32,
      pr1646v2LacpBPPPoEMCD7PIfInOctets
         Counter64,
      pr1646v2LacpBPPPoEMCD7PIfInUCPkts
         Counter64,
      pr1646v2LacpBPPPoEMCD7PIfInNUCPkts
         Counter64,
      pr1646v2LacpBPPPoEMCD7PIfInBCPkts
         Counter64,
      pr1646v2LacpBPPPoEMCD7PIfInMCPkts
         Counter64,
      pr1646v2LacpBPPPoEMCD7PIfInDiscards
         Counter64,
      pr1646v2LacpBPPPoEMCD7PIfInErrors
         Counter64,
      pr1646v2LacpBPPPoEMCD7PIfInUnkwn
         Counter64,
      pr1646v2LacpBPPPoEMCD7PInDropEx
         Counter64,
      pr1646v2LacpBPPPoEMCD7PInDropNoMac
         Counter64,
      pr1646v2LacpBPPPoEMCD7PInDropNUCast
         Counter64,
      pr1646v2LacpBPPPoEMCD7PInDropFilter
         Counter64,
      pr1646v2LacpBPPPoEMCD7PIfInBandwidth
         Integer32,
      pr1646v2LacpBPPPoEMCD7PIfOutOctets
         Counter64,
      pr1646v2LacpBPPPoEMCD7PIfOutUCPkts
         Counter64,
      pr1646v2LacpBPPPoEMCD7PIfOutNUCPkts
         Counter64,
      pr1646v2LacpBPPPoEMCD7PIfOutBCPkts
         Counter64,
      pr1646v2LacpBPPPoEMCD7PIfOutMCPkts
         Counter64,
      pr1646v2LacpBPPPoEMCD7PIfOutDiscards
         Counter64,
      pr1646v2LacpBPPPoEMCD7PIfOutErrors
         Counter64,
      pr1646v2LacpBPPPoEMCD7POutDropEx
         Counter64,
      pr1646v2LacpBPPPoEMCD7POutDropNoArp
         Counter64,
      pr1646v2LacpBPPPoEMCD7POutDropFilter
         Counter64,
      pr1646v2LacpBPPPoEMCD7PIfOutBandwidth
         Integer32,
      pr1646v2LacpBPPPoEMCD7PIfErrSec
         Counter32
      }

pr1646v2LacpBPPPoEMCD7PGlobalIx OBJECT-TYPE
   SYNTAX      GlobalIndex
   MAX-ACCESS  not-accessible
   STATUS      current
   DESCRIPTION
      "The value of the tlsCntTreeGlobalIndex of the MANAGED OBJECT."
   ::= {pr1646v2LacpBPPPoEMCD7PEntry 10}

pr1646v2LacpBPPPoEMCD7PTableIx OBJECT-TYPE
   SYNTAX      TableIndex
   MAX-ACCESS  not-accessible
   STATUS      current
   DESCRIPTION
      ""
   ::= {pr1646v2LacpBPPPoEMCD7PEntry 11}

pr1646v2LacpBPPPoEMCD7PSysUpTime OBJECT-TYPE
   SYNTAX      TimeTicks
   MAX-ACCESS  read-only
   STATUS      current
   DESCRIPTION
      "Path: lacpBundle.performance.pppoEClient.mibCounters.d7Performance.sysUpTime

       Time in centi-second."
   ::= {pr1646v2LacpBPPPoEMCD7PEntry 16777216}

pr1646v2LacpBPPPoEMCD7PIfUpTime OBJECT-TYPE
   SYNTAX      TimeTicks
   MAX-ACCESS  read-only
   STATUS      current
   DESCRIPTION
      "Path: lacpBundle.performance.pppoEClient.mibCounters.d7Performance.ifUpTime

       Time in centi-second."
   ::= {pr1646v2LacpBPPPoEMCD7PEntry 33554432}

pr1646v2LacpBPPPoEMCD7PIfStatChanges OBJECT-TYPE
   SYNTAX      Counter32
   MAX-ACCESS  read-only
   STATUS      current
   DESCRIPTION
      "Path: lacpBundle.performance.pppoEClient.mibCounters.d7Performance.ifStatusChanges

       32 bit unsigned wrappable counter."
   ::= {pr1646v2LacpBPPPoEMCD7PEntry 50331648}

pr1646v2LacpBPPPoEMCD7PIfInOctets OBJECT-TYPE
   SYNTAX      Counter64
   MAX-ACCESS  read-only
   STATUS      current
   DESCRIPTION
      "Path: lacpBundle.performance.pppoEClient.mibCounters.d7Performance.ifInOctets

       64 bit unsigned wrappable counter."
   ::= {pr1646v2LacpBPPPoEMCD7PEntry 67108864}

pr1646v2LacpBPPPoEMCD7PIfInUCPkts OBJECT-TYPE
   SYNTAX      Counter64
   MAX-ACCESS  read-only
   STATUS      current
   DESCRIPTION
      "Path: lacpBundle.performance.pppoEClient.mibCounters.d7Performance.ifInUcastPkts

       64 bit unsigned wrappable counter."
   ::= {pr1646v2LacpBPPPoEMCD7PEntry 83886080}

pr1646v2LacpBPPPoEMCD7PIfInNUCPkts OBJECT-TYPE
   SYNTAX      Counter64
   MAX-ACCESS  read-only
   STATUS      current
   DESCRIPTION
      "Path: lacpBundle.performance.pppoEClient.mibCounters.d7Performance.ifInNUcastPkts

       64 bit unsigned wrappable counter."
   ::= {pr1646v2LacpBPPPoEMCD7PEntry 100663296}

pr1646v2LacpBPPPoEMCD7PIfInBCPkts OBJECT-TYPE
   SYNTAX      Counter64
   MAX-ACCESS  read-only
   STATUS      current
   DESCRIPTION
      "Path: lacpBundle.performance.pppoEClient.mibCounters.d7Performance.ifInBcastPkts

       64 bit unsigned wrappable counter."
   ::= {pr1646v2LacpBPPPoEMCD7PEntry 419430400}

pr1646v2LacpBPPPoEMCD7PIfInMCPkts OBJECT-TYPE
   SYNTAX      Counter64
   MAX-ACCESS  read-only
   STATUS      current
   DESCRIPTION
      "Path: lacpBundle.performance.pppoEClient.mibCounters.d7Performance.ifInMcastPkts

       64 bit unsigned wrappable counter."
   ::= {pr1646v2LacpBPPPoEMCD7PEntry 436207616}

pr1646v2LacpBPPPoEMCD7PIfInDiscards OBJECT-TYPE
   SYNTAX      Counter64
   MAX-ACCESS  read-only
   STATUS      current
   DESCRIPTION
      "Path: lacpBundle.performance.pppoEClient.mibCounters.d7Performance.ifInDiscards

       64 bit unsigned wrappable counter."
   ::= {pr1646v2LacpBPPPoEMCD7PEntry 117440512}

pr1646v2LacpBPPPoEMCD7PIfInErrors OBJECT-TYPE
   SYNTAX      Counter64
   MAX-ACCESS  read-only
   STATUS      current
   DESCRIPTION
      "Path: lacpBundle.performance.pppoEClient.mibCounters.d7Performance.ifInErrors

       64 bit unsigned wrappable counter."
   ::= {pr1646v2LacpBPPPoEMCD7PEntry 134217728}

pr1646v2LacpBPPPoEMCD7PIfInUnkwn OBJECT-TYPE
   SYNTAX      Counter64
   MAX-ACCESS  read-only
   STATUS      current
   DESCRIPTION
      "Path: lacpBundle.performance.pppoEClient.mibCounters.d7Performance.ifInUnknownProtos

       64 bit unsigned wrappable counter."
   ::= {pr1646v2LacpBPPPoEMCD7PEntry 150994944}

pr1646v2LacpBPPPoEMCD7PInDropEx OBJECT-TYPE
   SYNTAX      Counter64
   MAX-ACCESS  read-only
   STATUS      current
   DESCRIPTION
      "Path: lacpBundle.performance.pppoEClient.mibCounters.d7Performance.ifInDropLevelExceeded

       64 bit unsigned wrappable counter."
   ::= {pr1646v2LacpBPPPoEMCD7PEntry 335544320}

pr1646v2LacpBPPPoEMCD7PInDropNoMac OBJECT-TYPE
   SYNTAX      Counter64
   MAX-ACCESS  read-only
   STATUS      current
   DESCRIPTION
      "Path: lacpBundle.performance.pppoEClient.mibCounters.d7Performance.fInDiscardsNoMacFit

       64 bit unsigned wrappable counter."
   ::= {pr1646v2LacpBPPPoEMCD7PEntry 301989888}

pr1646v2LacpBPPPoEMCD7PInDropNUCast OBJECT-TYPE
   SYNTAX      Counter64
   MAX-ACCESS  read-only
   STATUS      current
   DESCRIPTION
      "Path: lacpBundle.performance.pppoEClient.mibCounters.d7Performance.fInDiscardsNUCast

       64 bit unsigned wrappable counter."
   ::= {pr1646v2LacpBPPPoEMCD7PEntry 318767104}

pr1646v2LacpBPPPoEMCD7PInDropFilter OBJECT-TYPE
   SYNTAX      Counter64
   MAX-ACCESS  read-only
   STATUS      current
   DESCRIPTION
      "Path: lacpBundle.performance.pppoEClient.mibCounters.d7Performance.fInDiscardsFilter

       64 bit unsigned wrappable counter."
   ::= {pr1646v2LacpBPPPoEMCD7PEntry 385875968}

pr1646v2LacpBPPPoEMCD7PIfInBandwidth OBJECT-TYPE
   SYNTAX      Integer32
   MAX-ACCESS  read-only
   STATUS      current
   DESCRIPTION
      "Path: lacpBundle.performance.pppoEClient.mibCounters.d7Performance.ifInBandwidth

       unit name = bps
       formula = 8 * ; 8 /"
   ::= {pr1646v2LacpBPPPoEMCD7PEntry 268435456}

pr1646v2LacpBPPPoEMCD7PIfOutOctets OBJECT-TYPE
   SYNTAX      Counter64
   MAX-ACCESS  read-only
   STATUS      current
   DESCRIPTION
      "Path: lacpBundle.performance.pppoEClient.mibCounters.d7Performance.ifOutOctets

       64 bit unsigned wrappable counter."
   ::= {pr1646v2LacpBPPPoEMCD7PEntry 167772160}

pr1646v2LacpBPPPoEMCD7PIfOutUCPkts OBJECT-TYPE
   SYNTAX      Counter64
   MAX-ACCESS  read-only
   STATUS      current
   DESCRIPTION
      "Path: lacpBundle.performance.pppoEClient.mibCounters.d7Performance.ifOutUcastPkts

       64 bit unsigned wrappable counter."
   ::= {pr1646v2LacpBPPPoEMCD7PEntry 184549376}

pr1646v2LacpBPPPoEMCD7PIfOutNUCPkts OBJECT-TYPE
   SYNTAX      Counter64
   MAX-ACCESS  read-only
   STATUS      current
   DESCRIPTION
      "Path: lacpBundle.performance.pppoEClient.mibCounters.d7Performance.ifOutNUcastPkts

       64 bit unsigned wrappable counter."
   ::= {pr1646v2LacpBPPPoEMCD7PEntry 201326592}

pr1646v2LacpBPPPoEMCD7PIfOutBCPkts OBJECT-TYPE
   SYNTAX      Counter64
   MAX-ACCESS  read-only
   STATUS      current
   DESCRIPTION
      "Path: lacpBundle.performance.pppoEClient.mibCounters.d7Performance.ifOutBcastPkts

       64 bit unsigned wrappable counter."
   ::= {pr1646v2LacpBPPPoEMCD7PEntry 452984832}

pr1646v2LacpBPPPoEMCD7PIfOutMCPkts OBJECT-TYPE
   SYNTAX      Counter64
   MAX-ACCESS  read-only
   STATUS      current
   DESCRIPTION
      "Path: lacpBundle.performance.pppoEClient.mibCounters.d7Performance.ifOutMcastPkts

       64 bit unsigned wrappable counter."
   ::= {pr1646v2LacpBPPPoEMCD7PEntry 469762048}

pr1646v2LacpBPPPoEMCD7PIfOutDiscards OBJECT-TYPE
   SYNTAX      Counter64
   MAX-ACCESS  read-only
   STATUS      current
   DESCRIPTION
      "Path: lacpBundle.performance.pppoEClient.mibCounters.d7Performance.ifOutDiscards

       64 bit unsigned wrappable counter."
   ::= {pr1646v2LacpBPPPoEMCD7PEntry 218103808}

pr1646v2LacpBPPPoEMCD7PIfOutErrors OBJECT-TYPE
   SYNTAX      Counter64
   MAX-ACCESS  read-only
   STATUS      current
   DESCRIPTION
      "Path: lacpBundle.performance.pppoEClient.mibCounters.d7Performance.ifOutErrors

       64 bit unsigned wrappable counter."
   ::= {pr1646v2LacpBPPPoEMCD7PEntry 234881024}

pr1646v2LacpBPPPoEMCD7POutDropEx OBJECT-TYPE
   SYNTAX      Counter64
   MAX-ACCESS  read-only
   STATUS      current
   DESCRIPTION
      "Path: lacpBundle.performance.pppoEClient.mibCounters.d7Performance.ifOutDropLevelExceeded

       64 bit unsigned wrappable counter."
   ::= {pr1646v2LacpBPPPoEMCD7PEntry 352321536}

pr1646v2LacpBPPPoEMCD7POutDropNoArp OBJECT-TYPE
   SYNTAX      Counter64
   MAX-ACCESS  read-only
   STATUS      current
   DESCRIPTION
      "Path: lacpBundle.performance.pppoEClient.mibCounters.d7Performance.ifOutDiscardsNoArp

       64 bit unsigned wrappable counter."
   ::= {pr1646v2LacpBPPPoEMCD7PEntry 369098752}

pr1646v2LacpBPPPoEMCD7POutDropFilter OBJECT-TYPE
   SYNTAX      Counter64
   MAX-ACCESS  read-only
   STATUS      current
   DESCRIPTION
      "Path: lacpBundle.performance.pppoEClient.mibCounters.d7Performance.ifOutDiscardsFilter

       64 bit unsigned wrappable counter."
   ::= {pr1646v2LacpBPPPoEMCD7PEntry 402653184}

pr1646v2LacpBPPPoEMCD7PIfOutBandwidth OBJECT-TYPE
   SYNTAX      Integer32
   MAX-ACCESS  read-only
   STATUS      current
   DESCRIPTION
      "Path: lacpBundle.performance.pppoEClient.mibCounters.d7Performance.ifOutBandwidth

       unit name = bps
       formula = 8 * ; 8 /"
   ::= {pr1646v2LacpBPPPoEMCD7PEntry 285212672}

pr1646v2LacpBPPPoEMCD7PIfErrSec OBJECT-TYPE
   SYNTAX      Counter32
   MAX-ACCESS  read-only
   STATUS      current
   DESCRIPTION
      "Path: lacpBundle.performance.pppoEClient.mibCounters.d7Performance.ifErrSec

       32 bit unsigned wrappable counter."
   ::= {pr1646v2LacpBPPPoEMCD7PEntry 251658240}


pr1646v2LacpBMembers OBJECT IDENTIFIER ::= {pr1646v2LacpB 86}

pr1646v2LacpBMembersSSCTable OBJECT-TYPE
   SYNTAX      SEQUENCE OF Pr1646v2LacpBMembersEntry
   MAX-ACCESS  not-accessible
   STATUS      current
   DESCRIPTION
      "statistics of the aggregation links"
   ::= {pr1646v2LacpBMembers 1}

pr1646v2LacpBMembersEntry OBJECT-TYPE
   SYNTAX      Pr1646v2LacpBMembersEntry
   MAX-ACCESS  not-accessible
   STATUS      current
   DESCRIPTION
      ""
   INDEX      { pr1646v2LacpBMembersGlobalIx,
                pr1646v2LacpBMembersTableIx }
   ::= {pr1646v2LacpBMembersSSCTable 1}

Pr1646v2LacpBMembersEntry ::=
   SEQUENCE
      {
      pr1646v2LacpBMembersGlobalIx
         GlobalIndex,
      pr1646v2LacpBMembersTableIx
         TableIndex,
      pr1646v2LacpBMembersName
         DisplayString,
      pr1646v2LacpBMembersRxLacpdu
         Counter32,
      pr1646v2LacpBMembersRxMarkerPdu
         Counter32,
      pr1646v2LacpBMembersRxMarkerResponsePdu
         Counter32,
      pr1646v2LacpBMembersRxUnknown
         Counter32,
      pr1646v2LacpBMembersRxIllegal
         Counter32,
      pr1646v2LacpBMembersTxLacpdu
         Counter32,
      pr1646v2LacpBMembersTxMarkerPdu
         Counter32,
      pr1646v2LacpBMembersTxMarkerResponsePdu
         Counter32
      }

pr1646v2LacpBMembersGlobalIx OBJECT-TYPE
   SYNTAX      GlobalIndex
   MAX-ACCESS  not-accessible
   STATUS      current
   DESCRIPTION
      "The value of the tlsCntTreeGlobalIndex of the MANAGED OBJECT."
   ::= {pr1646v2LacpBMembersEntry 10}

pr1646v2LacpBMembersTableIx OBJECT-TYPE
   SYNTAX      TableIndex
   MAX-ACCESS  not-accessible
   STATUS      current
   DESCRIPTION
      ""
   ::= {pr1646v2LacpBMembersEntry 11}

pr1646v2LacpBMembersName OBJECT-TYPE
   SYNTAX      DisplayString
   MAX-ACCESS  read-only
   STATUS      current
   DESCRIPTION
      "Path: lacpBundle.performance.members.name"
   ::= {pr1646v2LacpBMembersEntry 16777216}

pr1646v2LacpBMembersRxLacpdu OBJECT-TYPE
   SYNTAX      Counter32
   MAX-ACCESS  read-only
   STATUS      current
   DESCRIPTION
      "Path: lacpBundle.performance.members.rxLacpdu

       32 bit unsigned wrappable counter."
   ::= {pr1646v2LacpBMembersEntry 33554432}

pr1646v2LacpBMembersRxMarkerPdu OBJECT-TYPE
   SYNTAX      Counter32
   MAX-ACCESS  read-only
   STATUS      current
   DESCRIPTION
      "Path: lacpBundle.performance.members.rxMarkerPdu

       32 bit unsigned wrappable counter."
   ::= {pr1646v2LacpBMembersEntry 50331648}

pr1646v2LacpBMembersRxMarkerResponsePdu OBJECT-TYPE
   SYNTAX      Counter32
   MAX-ACCESS  read-only
   STATUS      current
   DESCRIPTION
      "Path: lacpBundle.performance.members.rxMarkerResponsePdu

       32 bit unsigned wrappable counter."
   ::= {pr1646v2LacpBMembersEntry 67108864}

pr1646v2LacpBMembersRxUnknown OBJECT-TYPE
   SYNTAX      Counter32
   MAX-ACCESS  read-only
   STATUS      current
   DESCRIPTION
      "Path: lacpBundle.performance.members.rxUnknown

       32 bit unsigned wrappable counter."
   ::= {pr1646v2LacpBMembersEntry 83886080}

pr1646v2LacpBMembersRxIllegal OBJECT-TYPE
   SYNTAX      Counter32
   MAX-ACCESS  read-only
   STATUS      current
   DESCRIPTION
      "Path: lacpBundle.performance.members.rxIllegal

       32 bit unsigned wrappable counter."
   ::= {pr1646v2LacpBMembersEntry 100663296}

pr1646v2LacpBMembersTxLacpdu OBJECT-TYPE
   SYNTAX      Counter32
   MAX-ACCESS  read-only
   STATUS      current
   DESCRIPTION
      "Path: lacpBundle.performance.members.txLacpdu

       32 bit unsigned wrappable counter."
   ::= {pr1646v2LacpBMembersEntry 117440512}

pr1646v2LacpBMembersTxMarkerPdu OBJECT-TYPE
   SYNTAX      Counter32
   MAX-ACCESS  read-only
   STATUS      current
   DESCRIPTION
      "Path: lacpBundle.performance.members.txMarkerPdu

       32 bit unsigned wrappable counter."
   ::= {pr1646v2LacpBMembersEntry 134217728}

pr1646v2LacpBMembersTxMarkerResponsePdu OBJECT-TYPE
   SYNTAX      Counter32
   MAX-ACCESS  read-only
   STATUS      current
   DESCRIPTION
      "Path: lacpBundle.performance.members.txMarkerResponsePdu

       32 bit unsigned wrappable counter."
   ::= {pr1646v2LacpBMembersEntry 150994944}



ar1646v2LacpB OBJECT IDENTIFIER ::= {r1646v2LacpB 16}


ar1646v2LacpBClearCounters OBJECT IDENTIFIER ::= {ar1646v2LacpB 263}

ar1646v2LacpBClearCountersTable OBJECT-TYPE
   SYNTAX      SEQUENCE OF Ar1646v2LacpBClearCountersEntry
   MAX-ACCESS  not-accessible
   STATUS      current
   DESCRIPTION
      "reset counters"
   ::= {ar1646v2LacpBClearCounters 1}

ar1646v2LacpBClearCountersEntry OBJECT-TYPE
   SYNTAX      Ar1646v2LacpBClearCountersEntry
   MAX-ACCESS  not-accessible
   STATUS      current
   DESCRIPTION
      ""
   INDEX      { ar1646v2LacpBClearCountersGlobalIx }
   ::= {ar1646v2LacpBClearCountersTable 1}

Ar1646v2LacpBClearCountersEntry ::=
   SEQUENCE
      {
      ar1646v2LacpBClearCountersGlobalIx
         GlobalIndex,
      ar1646v2LacpBClearCountersValue
         Integer32
      }

ar1646v2LacpBClearCountersGlobalIx OBJECT-TYPE
   SYNTAX      GlobalIndex
   MAX-ACCESS  not-accessible
   STATUS      current
   DESCRIPTION
      "The value of the tlsCntTreeGlobalIndex of the MANAGED OBJECT."
   ::= {ar1646v2LacpBClearCountersEntry 10}

ar1646v2LacpBClearCountersValue OBJECT-TYPE
   SYNTAX      Integer32
   MAX-ACCESS  read-write
   STATUS      current
   DESCRIPTION
      "Path: lacpBundle.actions.clearCounters"
   ::= {ar1646v2LacpBClearCountersEntry 2147483648}


ar1646v2LacpBRestartIntf OBJECT IDENTIFIER ::= {ar1646v2LacpB 67}

ar1646v2LacpBRestartIntfTable OBJECT-TYPE
   SYNTAX      SEQUENCE OF Ar1646v2LacpBRestartIntfEntry
   MAX-ACCESS  not-accessible
   STATUS      current
   DESCRIPTION
      "action in the debug group"
   ::= {ar1646v2LacpBRestartIntf 1}

ar1646v2LacpBRestartIntfEntry OBJECT-TYPE
   SYNTAX      Ar1646v2LacpBRestartIntfEntry
   MAX-ACCESS  not-accessible
   STATUS      current
   DESCRIPTION
      ""
   INDEX      { ar1646v2LacpBRestartIntfGlobalIx }
   ::= {ar1646v2LacpBRestartIntfTable 1}

Ar1646v2LacpBRestartIntfEntry ::=
   SEQUENCE
      {
      ar1646v2LacpBRestartIntfGlobalIx
         GlobalIndex,
      ar1646v2LacpBRestartIntfValue
         Integer32
      }

ar1646v2LacpBRestartIntfGlobalIx OBJECT-TYPE
   SYNTAX      GlobalIndex
   MAX-ACCESS  not-accessible
   STATUS      current
   DESCRIPTION
      "The value of the tlsCntTreeGlobalIndex of the MANAGED OBJECT."
   ::= {ar1646v2LacpBRestartIntfEntry 10}

ar1646v2LacpBRestartIntfValue OBJECT-TYPE
   SYNTAX      Integer32
   MAX-ACCESS  read-write
   STATUS      current
   DESCRIPTION
      "Path: lacpBundle.actions.restartIntf"
   ::= {ar1646v2LacpBRestartIntfEntry 2147483648}


ar1646v2LacpBLoopback OBJECT IDENTIFIER ::= {ar1646v2LacpB 914}

ar1646v2LacpBLoopbackTable OBJECT-TYPE
   SYNTAX      SEQUENCE OF Ar1646v2LacpBLoopbackEntry
   MAX-ACCESS  not-accessible
   STATUS      current
   DESCRIPTION
      "ethernet loopback"
   ::= {ar1646v2LacpBLoopback 1}

ar1646v2LacpBLoopbackEntry OBJECT-TYPE
   SYNTAX      Ar1646v2LacpBLoopbackEntry
   MAX-ACCESS  not-accessible
   STATUS      current
   DESCRIPTION
      ""
   INDEX      { ar1646v2LacpBLoopbackGlobalIx }
   ::= {ar1646v2LacpBLoopbackTable 1}

Ar1646v2LacpBLoopbackEntry ::=
   SEQUENCE
      {
      ar1646v2LacpBLoopbackGlobalIx
         GlobalIndex,
      ar1646v2LacpBLoopbackValue
         Integer32
      }

ar1646v2LacpBLoopbackGlobalIx OBJECT-TYPE
   SYNTAX      GlobalIndex
   MAX-ACCESS  not-accessible
   STATUS      current
   DESCRIPTION
      "The value of the tlsCntTreeGlobalIndex of the MANAGED OBJECT."
   ::= {ar1646v2LacpBLoopbackEntry 10}

ar1646v2LacpBLoopbackValue OBJECT-TYPE
   SYNTAX      Integer32
   MAX-ACCESS  read-write
   STATUS      current
   DESCRIPTION
      "Path: lacpBundle.actions.loopback"
   ::= {ar1646v2LacpBLoopbackEntry 2147483648}


ar1646v2LacpBLoop OBJECT IDENTIFIER ::= {ar1646v2LacpB 915}

ar1646v2LacpBLoopSSCTable OBJECT-TYPE
   SYNTAX      SEQUENCE OF Ar1646v2LacpBLoopEntry
   MAX-ACCESS  not-accessible
   STATUS      current
   DESCRIPTION
      "ethernet loopback type"
   ::= {ar1646v2LacpBLoop 1}

ar1646v2LacpBLoopEntry OBJECT-TYPE
   SYNTAX      Ar1646v2LacpBLoopEntry
   MAX-ACCESS  not-accessible
   STATUS      current
   DESCRIPTION
      ""
   INDEX      { ar1646v2LacpBLoopGlobalIx }
   ::= {ar1646v2LacpBLoopSSCTable 1}

Ar1646v2LacpBLoopEntry ::=
   SEQUENCE
      {
      ar1646v2LacpBLoopGlobalIx
         GlobalIndex,
      ar1646v2LacpBLoopAction
         INTEGER,
      ar1646v2LacpBLoopTime
         TimeTicks,
      ar1646v2LacpBLoopIntfName
         DisplayString
      }

ar1646v2LacpBLoopGlobalIx OBJECT-TYPE
   SYNTAX      GlobalIndex
   MAX-ACCESS  not-accessible
   STATUS      current
   DESCRIPTION
      "The value of the tlsCntTreeGlobalIndex of the MANAGED OBJECT."
   ::= {ar1646v2LacpBLoopEntry 10}

ar1646v2LacpBLoopAction OBJECT-TYPE
   SYNTAX      INTEGER
               {
               start (1),
               stop (2)
               }
   MAX-ACCESS  read-write
   STATUS      current
   DESCRIPTION
      "Path: lacpBundle.actions.loop.action

       Possibilities:
               start   (1)
               stop   (2)"
   ::= {ar1646v2LacpBLoopEntry 16777216}

ar1646v2LacpBLoopTime OBJECT-TYPE
   SYNTAX      TimeTicks
   MAX-ACCESS  read-write
   STATUS      current
   DESCRIPTION
      "Path: lacpBundle.actions.loop.time

       Time in centi-second."
   ::= {ar1646v2LacpBLoopEntry 50331648}

ar1646v2LacpBLoopIntfName OBJECT-TYPE
   SYNTAX      DisplayString
   MAX-ACCESS  read-write
   STATUS      current
   DESCRIPTION
      "Path: lacpBundle.actions.loop.intfName"
   ::= {ar1646v2LacpBLoopEntry 67108864}


ar1646v2LacpBSendWOL OBJECT IDENTIFIER ::= {ar1646v2LacpB 333}

ar1646v2LacpBSendWOLTable OBJECT-TYPE
   SYNTAX      SEQUENCE OF Ar1646v2LacpBSendWOLEntry
   MAX-ACCESS  not-accessible
   STATUS      current
   DESCRIPTION
      "send a WakeOnLan message on this interface"
   ::= {ar1646v2LacpBSendWOL 1}

ar1646v2LacpBSendWOLEntry OBJECT-TYPE
   SYNTAX      Ar1646v2LacpBSendWOLEntry
   MAX-ACCESS  not-accessible
   STATUS      current
   DESCRIPTION
      ""
   INDEX      { ar1646v2LacpBSendWOLGlobalIx }
   ::= {ar1646v2LacpBSendWOLTable 1}

Ar1646v2LacpBSendWOLEntry ::=
   SEQUENCE
      {
      ar1646v2LacpBSendWOLGlobalIx
         GlobalIndex,
      ar1646v2LacpBSendWOLValue
         Integer32
      }

ar1646v2LacpBSendWOLGlobalIx OBJECT-TYPE
   SYNTAX      GlobalIndex
   MAX-ACCESS  not-accessible
   STATUS      current
   DESCRIPTION
      "The value of the tlsCntTreeGlobalIndex of the MANAGED OBJECT."
   ::= {ar1646v2LacpBSendWOLEntry 10}

ar1646v2LacpBSendWOLValue OBJECT-TYPE
   SYNTAX      Integer32
   MAX-ACCESS  read-write
   STATUS      current
   DESCRIPTION
      "Path: lacpBundle.actions.sendWOL"
   ::= {ar1646v2LacpBSendWOLEntry 2147483648}


ar1646v2LacpBWolInfo OBJECT IDENTIFIER ::= {ar1646v2LacpB 332}

ar1646v2LacpBWolInfoSSCTable OBJECT-TYPE
   SYNTAX      SEQUENCE OF Ar1646v2LacpBWolInfoEntry
   MAX-ACCESS  not-accessible
   STATUS      current
   DESCRIPTION
      "content of a WakeOnLan message"
   ::= {ar1646v2LacpBWolInfo 1}

ar1646v2LacpBWolInfoEntry OBJECT-TYPE
   SYNTAX      Ar1646v2LacpBWolInfoEntry
   MAX-ACCESS  not-accessible
   STATUS      current
   DESCRIPTION
      ""
   INDEX      { ar1646v2LacpBWolInfoGlobalIx }
   ::= {ar1646v2LacpBWolInfoSSCTable 1}

Ar1646v2LacpBWolInfoEntry ::=
   SEQUENCE
      {
      ar1646v2LacpBWolInfoGlobalIx
         GlobalIndex,
      ar1646v2LacpBWolInfoTargetMAC
         OCTET STRING,
      ar1646v2LacpBWolInfoPassword
         OCTET STRING
      }

ar1646v2LacpBWolInfoGlobalIx OBJECT-TYPE
   SYNTAX      GlobalIndex
   MAX-ACCESS  not-accessible
   STATUS      current
   DESCRIPTION
      "The value of the tlsCntTreeGlobalIndex of the MANAGED OBJECT."
   ::= {ar1646v2LacpBWolInfoEntry 10}

ar1646v2LacpBWolInfoTargetMAC OBJECT-TYPE
   SYNTAX      OCTET STRING
   MAX-ACCESS  read-write
   STATUS      current
   DESCRIPTION
      "Path: lacpBundle.actions.wolInfo.targetMAC

       MAC address."
   ::= {ar1646v2LacpBWolInfoEntry 16777216}

ar1646v2LacpBWolInfoPassword OBJECT-TYPE
   SYNTAX      OCTET STRING
   MAX-ACCESS  read-write
   STATUS      current
   DESCRIPTION
      "Path: lacpBundle.actions.wolInfo.password"
   ::= {ar1646v2LacpBWolInfoEntry 33554432}


ar1646v2LacpBClearArpCache OBJECT IDENTIFIER ::= {ar1646v2LacpB 25}

ar1646v2LacpBClearArpCacheTable OBJECT-TYPE
   SYNTAX      SEQUENCE OF Ar1646v2LacpBClearArpCacheEntry
   MAX-ACCESS  not-accessible
   STATUS      current
   DESCRIPTION
      "clear all dynamic enties in ARP cache table"
   ::= {ar1646v2LacpBClearArpCache 1}

ar1646v2LacpBClearArpCacheEntry OBJECT-TYPE
   SYNTAX      Ar1646v2LacpBClearArpCacheEntry
   MAX-ACCESS  not-accessible
   STATUS      current
   DESCRIPTION
      ""
   INDEX      { ar1646v2LacpBClearArpCacheGlobalIx }
   ::= {ar1646v2LacpBClearArpCacheTable 1}

Ar1646v2LacpBClearArpCacheEntry ::=
   SEQUENCE
      {
      ar1646v2LacpBClearArpCacheGlobalIx
         GlobalIndex,
      ar1646v2LacpBClearArpCacheValue
         Integer32
      }

ar1646v2LacpBClearArpCacheGlobalIx OBJECT-TYPE
   SYNTAX      GlobalIndex
   MAX-ACCESS  not-accessible
   STATUS      current
   DESCRIPTION
      "The value of the tlsCntTreeGlobalIndex of the MANAGED OBJECT."
   ::= {ar1646v2LacpBClearArpCacheEntry 10}

ar1646v2LacpBClearArpCacheValue OBJECT-TYPE
   SYNTAX      Integer32
   MAX-ACCESS  read-write
   STATUS      current
   DESCRIPTION
      "Path: lacpBundle.actions.clearArpCache"
   ::= {ar1646v2LacpBClearArpCacheEntry 2147483648}



fr1646v2LacpB OBJECT IDENTIFIER ::= {r1646v2LacpB 13}


fr1646v2LacpBAlarm OBJECT IDENTIFIER ::= {fr1646v2LacpB 207}

fr1646v2LacpBAlarmSSCTable OBJECT-TYPE
   SYNTAX      SEQUENCE OF Fr1646v2LacpBAlarmEntry
   MAX-ACCESS  not-accessible
   STATUS      current
   DESCRIPTION
      "IfAlarmInfo"
   ::= {fr1646v2LacpBAlarm 1}

fr1646v2LacpBAlarmEntry OBJECT-TYPE
   SYNTAX      Fr1646v2LacpBAlarmEntry
   MAX-ACCESS  not-accessible
   STATUS      current
   DESCRIPTION
      ""
   INDEX      { fr1646v2LacpBAlarmGlobalIx }
   ::= {fr1646v2LacpBAlarmSSCTable 1}

Fr1646v2LacpBAlarmEntry ::=
   SEQUENCE
      {
      fr1646v2LacpBAlarmGlobalIx
         GlobalIndex,
      fr1646v2LacpBAlarmDiscriminator
         Integer32,
      fr1646v2LacpBAlarmCurrent
         Integer32,
      fr1646v2LacpBAlarmPrevious
         Integer32,
      fr1646v2LacpBAlarmMask
         Integer32,
      fr1646v2LacpBAlarmLevLinkDown
         Integer32,
      fr1646v2LacpBAlarmLevPppoEDown
         Integer32
      }

fr1646v2LacpBAlarmGlobalIx OBJECT-TYPE
   SYNTAX      GlobalIndex
   MAX-ACCESS  not-accessible
   STATUS      current
   DESCRIPTION
      "The value of the tlsCntTreeGlobalIndex of the MANAGED OBJECT."
   ::= {fr1646v2LacpBAlarmEntry 10}

fr1646v2LacpBAlarmDiscriminator OBJECT-TYPE
   SYNTAX      Integer32
   MAX-ACCESS  read-only
   STATUS      current
   DESCRIPTION
      "Path: lacpBundle.alarms.alarmInfo.discriminator"
   ::= {fr1646v2LacpBAlarmEntry 16777216}

fr1646v2LacpBAlarmCurrent OBJECT-TYPE
   SYNTAX      Integer32
   MAX-ACCESS  read-only
   STATUS      current
   DESCRIPTION
      "Path: lacpBundle.alarms.alarmInfo.currentAlarms

       Bit meanings:
               bit 0 = linkDown,
               bit 9 = pppoEDown"
   ::= {fr1646v2LacpBAlarmEntry 33554432}

fr1646v2LacpBAlarmPrevious OBJECT-TYPE
   SYNTAX      Integer32
   MAX-ACCESS  read-only
   STATUS      current
   DESCRIPTION
      "Path: lacpBundle.alarms.alarmInfo.previousAlarms

       Bit meanings:
               bit 0 = linkDown,
               bit 9 = pppoEDown"
   ::= {fr1646v2LacpBAlarmEntry 50331648}

fr1646v2LacpBAlarmMask OBJECT-TYPE
   SYNTAX      Integer32
   MAX-ACCESS  read-only
   STATUS      current
   DESCRIPTION
      "Path: lacpBundle.alarms.alarmInfo.alarmMask

       Bit meanings:
               bit 0 = linkDown,
               bit 9 = pppoEDown"
   ::= {fr1646v2LacpBAlarmEntry 67108864}

fr1646v2LacpBAlarmLevLinkDown OBJECT-TYPE
   SYNTAX      Integer32
   MAX-ACCESS  read-only
   STATUS      current
   DESCRIPTION
      "Path: lacpBundle.alarms.alarmInfo.alarmLevel.linkDown"
   ::= {fr1646v2LacpBAlarmEntry 83951616}

fr1646v2LacpBAlarmLevPppoEDown OBJECT-TYPE
   SYNTAX      Integer32
   MAX-ACCESS  read-only
   STATUS      current
   DESCRIPTION
      "Path: lacpBundle.alarms.alarmInfo.alarmLevel.pppoEDown"
   ::= {fr1646v2LacpBAlarmEntry 84541440}


fr1646v2LacpBAlarmE2 OBJECT IDENTIFIER ::= {fr1646v2LacpBAlarm 2}

fr1646v2LacpBAlarmE2Entry OBJECT IDENTIFIER ::= {fr1646v2LacpBAlarmE2 1}

fr1646v2LacpBAlarmE2LinkDown OBJECT IDENTIFIER ::= {fr1646v2LacpBAlarmE2Entry 10}

fr1646v2LacpBAlarmE2LinkDownPfx OBJECT IDENTIFIER ::= {fr1646v2LacpBAlarmE2LinkDown 0}

fr1646v2LacpBAlarmE2LinkDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'lacpBundle'
                (root='router1646') has changed from the ON to the OFF state."
   ::= {fr1646v2LacpBAlarmE2LinkDownPfx 1}

fr1646v2LacpBAlarmE2LinkDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'lacpBundle'
                (root='router1646') has changed from the OFF to the ON state."
   ::= {fr1646v2LacpBAlarmE2LinkDownPfx 2}

fr1646v2LacpBAlarmE2PppoEDown OBJECT IDENTIFIER ::= {fr1646v2LacpBAlarmE2Entry 19}

fr1646v2LacpBAlarmE2PppoEDownPfx OBJECT IDENTIFIER ::= {fr1646v2LacpBAlarmE2PppoEDown 0}

fr1646v2LacpBAlarmE2PppoEDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pppoEDown'
                representing an alarm condition in the alarm word
                of attribute 'alarmInfo' of managed object 'lacpBundle'
                (root='router1646') has changed from the ON to the OFF state."
   ::= {fr1646v2LacpBAlarmE2PppoEDownPfx 1}

fr1646v2LacpBAlarmE2PppoEDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pppoEDown'
                representing an alarm condition in the alarm word
                of attribute 'alarmInfo' of managed object 'lacpBundle'
                (root='router1646') has changed from the OFF to the ON state."
   ::= {fr1646v2LacpBAlarmE2PppoEDownPfx 2}



END
