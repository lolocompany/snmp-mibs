OneAccess-R1645v2-4002-IpV6VrfRtr DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2IpV6VrfRtr OBJECT IDENTIFIER ::= {r1645Rootv2 4002}

r1645v2IpV6VrfRtrMOProp OBJECT-TYPE
   SYNTAX      SEQUENCE OF R1645v2IpV6VrfRtrMOPropEntry
   MAX-ACCESS  not-accessible
   STATUS      current
   DESCRIPTION
      ""
   ::= {r1645v2IpV6VrfRtr 1}

r1645v2IpV6VrfRtrMOPropEntry OBJECT-TYPE
   SYNTAX      R1645v2IpV6VrfRtrMOPropEntry
   MAX-ACCESS  not-accessible
   STATUS      current
   DESCRIPTION
      ""
   INDEX      { r1645v2IpV6VrfRtrMOPropGlobalIx }
   ::= {r1645v2IpV6VrfRtrMOProp 1}

R1645v2IpV6VrfRtrMOPropEntry ::=
   SEQUENCE
      {
      r1645v2IpV6VrfRtrMOPropPath
         ContainmentPath,
      r1645v2IpV6VrfRtrMOPropRev
         ObjectRevision,
      r1645v2IpV6VrfRtrMOPropGlobalIx
         GlobalIndex
      }

r1645v2IpV6VrfRtrMOPropPath OBJECT-TYPE
   SYNTAX      ContainmentPath
   MAX-ACCESS  read-only
   STATUS      current
   DESCRIPTION
      "Textual description of the containment tree from the instance of
       the root object down to the instance of the current object."
   ::= {r1645v2IpV6VrfRtrMOPropEntry 3}

r1645v2IpV6VrfRtrMOPropRev OBJECT-TYPE
   SYNTAX      ObjectRevision
   MAX-ACCESS  read-only
   STATUS      current
   DESCRIPTION
      "This value corresponds with the revision of the MANAGED OBJECT."
   ::= {r1645v2IpV6VrfRtrMOPropEntry 4}

r1645v2IpV6VrfRtrMOPropGlobalIx OBJECT-TYPE
   SYNTAX      GlobalIndex
   MAX-ACCESS  read-only
   STATUS      current
   DESCRIPTION
      "The value of the tlsCntTreeGlobalIndex of the MANAGED OBJECT."
   ::= {r1645v2IpV6VrfRtrMOPropEntry 10}



er1645v2IpV6VrfRtr OBJECT IDENTIFIER ::= {r1645v2IpV6VrfRtr 11}


er1645v2IpV6VrfRtrRoutingTable OBJECT IDENTIFIER ::= {er1645v2IpV6VrfRtr 2}

er1645v2IpV6VrfRtrRoutingTableSSCTable OBJECT-TYPE
   SYNTAX      SEQUENCE OF Er1645v2IpV6VrfRtrRoutingTableEntry
   MAX-ACCESS  not-accessible
   STATUS      current
   DESCRIPTION
      "ipV6 static route configuration"
   ::= {er1645v2IpV6VrfRtrRoutingTable 1}

er1645v2IpV6VrfRtrRoutingTableEntry OBJECT-TYPE
   SYNTAX      Er1645v2IpV6VrfRtrRoutingTableEntry
   MAX-ACCESS  not-accessible
   STATUS      current
   DESCRIPTION
      ""
   INDEX      { er1645v2IpV6VrfRtrRoutingTableGlobalIx,
                er1645v2IpV6VrfRtrRoutingTableTableIx }
   ::= {er1645v2IpV6VrfRtrRoutingTableSSCTable 1}

Er1645v2IpV6VrfRtrRoutingTableEntry ::=
   SEQUENCE
      {
      er1645v2IpV6VrfRtrRoutingTableActions
         VariableLengthTableActions,
      er1645v2IpV6VrfRtrRoutingTableGlobalIx
         GlobalIndex,
      er1645v2IpV6VrfRtrRoutingTableTableIx
         TableIndex,
      er1645v2IpV6VrfRtrRoutingTableAddress
         Ipv6Address,
      er1645v2IpV6VrfRtrRoutingTablePrefixLength
         Integer32,
      er1645v2IpV6VrfRtrRoutingTableNextHop
         Ipv6Address,
      er1645v2IpV6VrfRtrRoutingTableInterface
         DisplayString,
      er1645v2IpV6VrfRtrRoutingTablePreference
         Integer32,
      er1645v2IpV6VrfRtrRoutingTableMetric
         Integer32,
      er1645v2IpV6VrfRtrRoutingTableRemark
         DisplayString
      }

er1645v2IpV6VrfRtrRoutingTableActions OBJECT-TYPE
   SYNTAX      VariableLengthTableActions
   MAX-ACCESS  read-write
   STATUS      current
   DESCRIPTION
      "By way of this field, some manipulations
       on this table may be performed."
   ::= {er1645v2IpV6VrfRtrRoutingTableEntry 2}

er1645v2IpV6VrfRtrRoutingTableGlobalIx OBJECT-TYPE
   SYNTAX      GlobalIndex
   MAX-ACCESS  not-accessible
   STATUS      current
   DESCRIPTION
      "The value of the tlsCntTreeGlobalIndex of the MANAGED OBJECT."
   ::= {er1645v2IpV6VrfRtrRoutingTableEntry 10}

er1645v2IpV6VrfRtrRoutingTableTableIx OBJECT-TYPE
   SYNTAX      TableIndex
   MAX-ACCESS  not-accessible
   STATUS      current
   DESCRIPTION
      ""
   ::= {er1645v2IpV6VrfRtrRoutingTableEntry 11}

er1645v2IpV6VrfRtrRoutingTableAddress OBJECT-TYPE
   SYNTAX      Ipv6Address
   MAX-ACCESS  read-write
   STATUS      current
   DESCRIPTION
      "Path: vrfV6Router.editConf.routingTable.address

       ipv6 address"
   ::= {er1645v2IpV6VrfRtrRoutingTableEntry 16777216}

er1645v2IpV6VrfRtrRoutingTablePrefixLength OBJECT-TYPE
   SYNTAX      Integer32
   MAX-ACCESS  read-write
   STATUS      current
   DESCRIPTION
      "Path: vrfV6Router.editConf.routingTable.prefixLength"
   ::= {er1645v2IpV6VrfRtrRoutingTableEntry 33554432}

er1645v2IpV6VrfRtrRoutingTableNextHop OBJECT-TYPE
   SYNTAX      Ipv6Address
   MAX-ACCESS  read-write
   STATUS      current
   DESCRIPTION
      "Path: vrfV6Router.editConf.routingTable.nextHop

       ipv6 address"
   ::= {er1645v2IpV6VrfRtrRoutingTableEntry 50331648}

er1645v2IpV6VrfRtrRoutingTableInterface OBJECT-TYPE
   SYNTAX      DisplayString
   MAX-ACCESS  read-write
   STATUS      current
   DESCRIPTION
      "Path: vrfV6Router.editConf.routingTable.interface"
   ::= {er1645v2IpV6VrfRtrRoutingTableEntry 67108864}

er1645v2IpV6VrfRtrRoutingTablePreference OBJECT-TYPE
   SYNTAX      Integer32
   MAX-ACCESS  read-write
   STATUS      current
   DESCRIPTION
      "Path: vrfV6Router.editConf.routingTable.preference"
   ::= {er1645v2IpV6VrfRtrRoutingTableEntry 83886080}

er1645v2IpV6VrfRtrRoutingTableMetric OBJECT-TYPE
   SYNTAX      Integer32
   MAX-ACCESS  read-write
   STATUS      current
   DESCRIPTION
      "Path: vrfV6Router.editConf.routingTable.metric"
   ::= {er1645v2IpV6VrfRtrRoutingTableEntry 100663296}

er1645v2IpV6VrfRtrRoutingTableRemark OBJECT-TYPE
   SYNTAX      DisplayString
   MAX-ACCESS  read-write
   STATUS      current
   DESCRIPTION
      "Path: vrfV6Router.editConf.routingTable.remark"
   ::= {er1645v2IpV6VrfRtrRoutingTableEntry 1157627904}


er1645v2IpV6VrfRtrType0Routing OBJECT IDENTIFIER ::= {er1645v2IpV6VrfRtr 3}

er1645v2IpV6VrfRtrType0RoutingTable OBJECT-TYPE
   SYNTAX      SEQUENCE OF Er1645v2IpV6VrfRtrType0RoutingEntry
   MAX-ACCESS  not-accessible
   STATUS      current
   DESCRIPTION
      "enable support for type0 routing header"
   ::= {er1645v2IpV6VrfRtrType0Routing 1}

er1645v2IpV6VrfRtrType0RoutingEntry OBJECT-TYPE
   SYNTAX      Er1645v2IpV6VrfRtrType0RoutingEntry
   MAX-ACCESS  not-accessible
   STATUS      current
   DESCRIPTION
      ""
   INDEX      { er1645v2IpV6VrfRtrType0RoutingGlobalIx }
   ::= {er1645v2IpV6VrfRtrType0RoutingTable 1}

Er1645v2IpV6VrfRtrType0RoutingEntry ::=
   SEQUENCE
      {
      er1645v2IpV6VrfRtrType0RoutingGlobalIx
         GlobalIndex,
      er1645v2IpV6VrfRtrType0RoutingValue
         INTEGER
      }

er1645v2IpV6VrfRtrType0RoutingGlobalIx OBJECT-TYPE
   SYNTAX      GlobalIndex
   MAX-ACCESS  not-accessible
   STATUS      current
   DESCRIPTION
      "The value of the tlsCntTreeGlobalIndex of the MANAGED OBJECT."
   ::= {er1645v2IpV6VrfRtrType0RoutingEntry 10}

er1645v2IpV6VrfRtrType0RoutingValue OBJECT-TYPE
   SYNTAX      INTEGER
               {
               disabled (0),
               enabled (1)
               }
   MAX-ACCESS  read-write
   STATUS      current
   DESCRIPTION
      "Path: vrfV6Router.editConf.type0Routing

       Possibilities:
               disabled   (0)
               enabled   (1)"
   ::= {er1645v2IpV6VrfRtrType0RoutingEntry 2147483648}


er1645v2IpV6VrfRtrMaxPendingFrags OBJECT IDENTIFIER ::= {er1645v2IpV6VrfRtr 4}

er1645v2IpV6VrfRtrMaxPendingFragsTable OBJECT-TYPE
   SYNTAX      SEQUENCE OF Er1645v2IpV6VrfRtrMaxPendingFragsEntry
   MAX-ACCESS  not-accessible
   STATUS      current
   DESCRIPTION
      "limit the number of pending fragments"
   ::= {er1645v2IpV6VrfRtrMaxPendingFrags 1}

er1645v2IpV6VrfRtrMaxPendingFragsEntry OBJECT-TYPE
   SYNTAX      Er1645v2IpV6VrfRtrMaxPendingFragsEntry
   MAX-ACCESS  not-accessible
   STATUS      current
   DESCRIPTION
      ""
   INDEX      { er1645v2IpV6VrfRtrMaxPendingFragsGlobalIx }
   ::= {er1645v2IpV6VrfRtrMaxPendingFragsTable 1}

Er1645v2IpV6VrfRtrMaxPendingFragsEntry ::=
   SEQUENCE
      {
      er1645v2IpV6VrfRtrMaxPendingFragsGlobalIx
         GlobalIndex,
      er1645v2IpV6VrfRtrMaxPendingFragsValue
         Integer32
      }

er1645v2IpV6VrfRtrMaxPendingFragsGlobalIx OBJECT-TYPE
   SYNTAX      GlobalIndex
   MAX-ACCESS  not-accessible
   STATUS      current
   DESCRIPTION
      "The value of the tlsCntTreeGlobalIndex of the MANAGED OBJECT."
   ::= {er1645v2IpV6VrfRtrMaxPendingFragsEntry 10}

er1645v2IpV6VrfRtrMaxPendingFragsValue OBJECT-TYPE
   SYNTAX      Integer32
   MAX-ACCESS  read-write
   STATUS      current
   DESCRIPTION
      "Path: vrfV6Router.editConf.maxPendingFrags"
   ::= {er1645v2IpV6VrfRtrMaxPendingFragsEntry 2147483648}


er1645v2IpV6VrfRtrGeneralPrefixes OBJECT IDENTIFIER ::= {er1645v2IpV6VrfRtr 5}

er1645v2IpV6VrfRtrGeneralPrefixesSSCTable OBJECT-TYPE
   SYNTAX      SEQUENCE OF Er1645v2IpV6VrfRtrGeneralPrefixesEntry
   MAX-ACCESS  not-accessible
   STATUS      current
   DESCRIPTION
      "ipV6 prefix pool config"
   ::= {er1645v2IpV6VrfRtrGeneralPrefixes 1}

er1645v2IpV6VrfRtrGeneralPrefixesEntry OBJECT-TYPE
   SYNTAX      Er1645v2IpV6VrfRtrGeneralPrefixesEntry
   MAX-ACCESS  not-accessible
   STATUS      current
   DESCRIPTION
      ""
   INDEX      { er1645v2IpV6VrfRtrGeneralPrefixesGlobalIx,
                er1645v2IpV6VrfRtrGeneralPrefixesTableIx }
   ::= {er1645v2IpV6VrfRtrGeneralPrefixesSSCTable 1}

Er1645v2IpV6VrfRtrGeneralPrefixesEntry ::=
   SEQUENCE
      {
      er1645v2IpV6VrfRtrGeneralPrefixesActions
         VariableLengthTableActions,
      er1645v2IpV6VrfRtrGeneralPrefixesGlobalIx
         GlobalIndex,
      er1645v2IpV6VrfRtrGeneralPrefixesTableIx
         TableIndex,
      er1645v2IpV6VrfRtrGeneralPrefixesName
         DisplayString,
      er1645v2IpV6VrfRtrGeneralPrefixesType
         INTEGER,
      er1645v2IpV6VrfRtrGeneralPrefixesPrefix
         Ipv6Address,
      er1645v2IpV6VrfRtrGeneralPrefixesPrefixLength
         Integer32,
      er1645v2IpV6VrfRtrGeneralPrefixesAuto6to4Auto6to4Intf
         DisplayString,
      er1645v2IpV6VrfRtrGeneralPrefixesAuto6to4IpV4Address
         IpAddress,
      er1645v2IpV6VrfRtrGeneralPrefixesAuto6to4Subnet
         OCTET STRING
      }

er1645v2IpV6VrfRtrGeneralPrefixesActions OBJECT-TYPE
   SYNTAX      VariableLengthTableActions
   MAX-ACCESS  read-write
   STATUS      current
   DESCRIPTION
      "By way of this field, some manipulations
       on this table may be performed."
   ::= {er1645v2IpV6VrfRtrGeneralPrefixesEntry 2}

er1645v2IpV6VrfRtrGeneralPrefixesGlobalIx OBJECT-TYPE
   SYNTAX      GlobalIndex
   MAX-ACCESS  not-accessible
   STATUS      current
   DESCRIPTION
      "The value of the tlsCntTreeGlobalIndex of the MANAGED OBJECT."
   ::= {er1645v2IpV6VrfRtrGeneralPrefixesEntry 10}

er1645v2IpV6VrfRtrGeneralPrefixesTableIx OBJECT-TYPE
   SYNTAX      TableIndex
   MAX-ACCESS  not-accessible
   STATUS      current
   DESCRIPTION
      ""
   ::= {er1645v2IpV6VrfRtrGeneralPrefixesEntry 11}

er1645v2IpV6VrfRtrGeneralPrefixesName OBJECT-TYPE
   SYNTAX      DisplayString
   MAX-ACCESS  read-write
   STATUS      current
   DESCRIPTION
      "Path: vrfV6Router.editConf.generalPrefixes.name"
   ::= {er1645v2IpV6VrfRtrGeneralPrefixesEntry 16777216}

er1645v2IpV6VrfRtrGeneralPrefixesType OBJECT-TYPE
   SYNTAX      INTEGER
               {
               static (0),
               auto6to4 (2)
               }
   MAX-ACCESS  read-write
   STATUS      current
   DESCRIPTION
      "Path: vrfV6Router.editConf.generalPrefixes.type

       Possibilities:
               static   (0)
               auto6to4   (2)"
   ::= {er1645v2IpV6VrfRtrGeneralPrefixesEntry 67108864}

er1645v2IpV6VrfRtrGeneralPrefixesPrefix OBJECT-TYPE
   SYNTAX      Ipv6Address
   MAX-ACCESS  read-write
   STATUS      current
   DESCRIPTION
      "Path: vrfV6Router.editConf.generalPrefixes.prefix

       ipv6 address"
   ::= {er1645v2IpV6VrfRtrGeneralPrefixesEntry 33554432}

er1645v2IpV6VrfRtrGeneralPrefixesPrefixLength OBJECT-TYPE
   SYNTAX      Integer32
   MAX-ACCESS  read-write
   STATUS      current
   DESCRIPTION
      "Path: vrfV6Router.editConf.generalPrefixes.prefixLength"
   ::= {er1645v2IpV6VrfRtrGeneralPrefixesEntry 50331648}

er1645v2IpV6VrfRtrGeneralPrefixesAuto6to4Auto6to4Intf OBJECT-TYPE
   SYNTAX      DisplayString
   MAX-ACCESS  read-write
   STATUS      current
   DESCRIPTION
      "Path: vrfV6Router.editConf.generalPrefixes.auto6to4.auto6to4Intf"
   ::= {er1645v2IpV6VrfRtrGeneralPrefixesEntry 84082688}

er1645v2IpV6VrfRtrGeneralPrefixesAuto6to4IpV4Address OBJECT-TYPE
   SYNTAX      IpAddress
   MAX-ACCESS  read-write
   STATUS      current
   DESCRIPTION
      "Path: vrfV6Router.editConf.generalPrefixes.auto6to4.ipV4Address"
   ::= {er1645v2IpV6VrfRtrGeneralPrefixesEntry 83951616}

er1645v2IpV6VrfRtrGeneralPrefixesAuto6to4Subnet OBJECT-TYPE
   SYNTAX      OCTET STRING
   MAX-ACCESS  read-write
   STATUS      current
   DESCRIPTION
      "Path: vrfV6Router.editConf.generalPrefixes.auto6to4.subnet"
   ::= {er1645v2IpV6VrfRtrGeneralPrefixesEntry 84017152}


er1645v2IpV6VrfRtrDns OBJECT IDENTIFIER ::= {er1645v2IpV6VrfRtr 6}

er1645v2IpV6VrfRtrDnsSSCTable OBJECT-TYPE
   SYNTAX      SEQUENCE OF Er1645v2IpV6VrfRtrDnsEntry
   MAX-ACCESS  not-accessible
   STATUS      current
   DESCRIPTION
      "Domain Name System"
   ::= {er1645v2IpV6VrfRtrDns 1}

er1645v2IpV6VrfRtrDnsEntry OBJECT-TYPE
   SYNTAX      Er1645v2IpV6VrfRtrDnsEntry
   MAX-ACCESS  not-accessible
   STATUS      current
   DESCRIPTION
      ""
   INDEX      { er1645v2IpV6VrfRtrDnsGlobalIx }
   ::= {er1645v2IpV6VrfRtrDnsSSCTable 1}

Er1645v2IpV6VrfRtrDnsEntry ::=
   SEQUENCE
      {
      er1645v2IpV6VrfRtrDnsGlobalIx
         GlobalIndex,
      er1645v2IpV6VrfRtrDnsDomainName
         DisplayString,
      er1645v2IpV6VrfRtrDnsIpV4Router
         DisplayString,
      er1645v2IpV6VrfRtrDnsProxy
         INTEGER,
      er1645v2IpV6VrfRtrDnsCacheSize
         Integer32
      }

er1645v2IpV6VrfRtrDnsGlobalIx OBJECT-TYPE
   SYNTAX      GlobalIndex
   MAX-ACCESS  not-accessible
   STATUS      current
   DESCRIPTION
      "The value of the tlsCntTreeGlobalIndex of the MANAGED OBJECT."
   ::= {er1645v2IpV6VrfRtrDnsEntry 10}

er1645v2IpV6VrfRtrDnsDomainName OBJECT-TYPE
   SYNTAX      DisplayString
   MAX-ACCESS  read-write
   STATUS      current
   DESCRIPTION
      "Path: vrfV6Router.editConf.dns.domainName"
   ::= {er1645v2IpV6VrfRtrDnsEntry 33554432}

er1645v2IpV6VrfRtrDnsIpV4Router OBJECT-TYPE
   SYNTAX      DisplayString
   MAX-ACCESS  read-write
   STATUS      current
   DESCRIPTION
      "Path: vrfV6Router.editConf.dns.ipV4Router"
   ::= {er1645v2IpV6VrfRtrDnsEntry 67108864}

er1645v2IpV6VrfRtrDnsProxy OBJECT-TYPE
   SYNTAX      INTEGER
               {
               disabled (0),
               enabled (1)
               }
   MAX-ACCESS  read-write
   STATUS      current
   DESCRIPTION
      "Path: vrfV6Router.editConf.dns.proxy

       Possibilities:
               disabled   (0)
               enabled   (1)"
   ::= {er1645v2IpV6VrfRtrDnsEntry 83886080}

er1645v2IpV6VrfRtrDnsCacheSize OBJECT-TYPE
   SYNTAX      Integer32
   MAX-ACCESS  read-write
   STATUS      current
   DESCRIPTION
      "Path: vrfV6Router.editConf.dns.cacheSize"
   ::= {er1645v2IpV6VrfRtrDnsEntry 100663296}

er1645v2IpV6VrfRtrDnsServers OBJECT-TYPE
   SYNTAX      SEQUENCE OF Er1645v2IpV6VrfRtrDnsServersEntry
   MAX-ACCESS  not-accessible
   STATUS      current
   DESCRIPTION
      ""
   ::= {er1645v2IpV6VrfRtrDns 16777216}

er1645v2IpV6VrfRtrDnsServersEntry OBJECT-TYPE
   SYNTAX      Er1645v2IpV6VrfRtrDnsServersEntry
   MAX-ACCESS  not-accessible
   STATUS      current
   DESCRIPTION
      ""
   INDEX      { er1645v2IpV6VrfRtrDnsServersGlobalIx,
                er1645v2IpV6VrfRtrDnsServersTableIx }
   ::= {er1645v2IpV6VrfRtrDnsServers 1}

Er1645v2IpV6VrfRtrDnsServersEntry ::=
   SEQUENCE
      {
      er1645v2IpV6VrfRtrDnsServersActions
         VariableLengthTableActions,
      er1645v2IpV6VrfRtrDnsServersGlobalIx
         GlobalIndex,
      er1645v2IpV6VrfRtrDnsServersTableIx
         TableIndex,
      er1645v2IpV6VrfRtrDnsServersAddress
         Ipv6Address,
      er1645v2IpV6VrfRtrDnsServersPreference
         Integer32
      }

er1645v2IpV6VrfRtrDnsServersActions OBJECT-TYPE
   SYNTAX      VariableLengthTableActions
   MAX-ACCESS  read-write
   STATUS      current
   DESCRIPTION
      "By way of this field, some manipulations
       on this table may be performed."
   ::= {er1645v2IpV6VrfRtrDnsServersEntry 2}

er1645v2IpV6VrfRtrDnsServersGlobalIx OBJECT-TYPE
   SYNTAX      GlobalIndex
   MAX-ACCESS  not-accessible
   STATUS      current
   DESCRIPTION
      "The value of the tlsCntTreeGlobalIndex of the MANAGED OBJECT."
   ::= {er1645v2IpV6VrfRtrDnsServersEntry 10}

er1645v2IpV6VrfRtrDnsServersTableIx OBJECT-TYPE
   SYNTAX      TableIndex
   MAX-ACCESS  not-accessible
   STATUS      current
   DESCRIPTION
      ""
   ::= {er1645v2IpV6VrfRtrDnsServersEntry 11}

er1645v2IpV6VrfRtrDnsServersAddress OBJECT-TYPE
   SYNTAX      Ipv6Address
   MAX-ACCESS  read-write
   STATUS      current
   DESCRIPTION
      "Path: vrfV6Router.editConf.dns.servers.address

       ipv6 address"
   ::= {er1645v2IpV6VrfRtrDnsServersEntry 16777216}

er1645v2IpV6VrfRtrDnsServersPreference OBJECT-TYPE
   SYNTAX      Integer32
   MAX-ACCESS  read-write
   STATUS      current
   DESCRIPTION
      "Path: vrfV6Router.editConf.dns.servers.preference"
   ::= {er1645v2IpV6VrfRtrDnsServersEntry 33554432}

er1645v2IpV6VrfRtrDnsHosts OBJECT-TYPE
   SYNTAX      SEQUENCE OF Er1645v2IpV6VrfRtrDnsHostsEntry
   MAX-ACCESS  not-accessible
   STATUS      current
   DESCRIPTION
      ""
   ::= {er1645v2IpV6VrfRtrDns 50331648}

er1645v2IpV6VrfRtrDnsHostsEntry OBJECT-TYPE
   SYNTAX      Er1645v2IpV6VrfRtrDnsHostsEntry
   MAX-ACCESS  not-accessible
   STATUS      current
   DESCRIPTION
      ""
   INDEX      { er1645v2IpV6VrfRtrDnsHostsGlobalIx,
                er1645v2IpV6VrfRtrDnsHostsTableIx }
   ::= {er1645v2IpV6VrfRtrDnsHosts 1}

Er1645v2IpV6VrfRtrDnsHostsEntry ::=
   SEQUENCE
      {
      er1645v2IpV6VrfRtrDnsHostsActions
         VariableLengthTableActions,
      er1645v2IpV6VrfRtrDnsHostsGlobalIx
         GlobalIndex,
      er1645v2IpV6VrfRtrDnsHostsTableIx
         TableIndex,
      er1645v2IpV6VrfRtrDnsHostsName
         DisplayString,
      er1645v2IpV6VrfRtrDnsHostsAddress
         Ipv6Address
      }

er1645v2IpV6VrfRtrDnsHostsActions OBJECT-TYPE
   SYNTAX      VariableLengthTableActions
   MAX-ACCESS  read-write
   STATUS      current
   DESCRIPTION
      "By way of this field, some manipulations
       on this table may be performed."
   ::= {er1645v2IpV6VrfRtrDnsHostsEntry 2}

er1645v2IpV6VrfRtrDnsHostsGlobalIx OBJECT-TYPE
   SYNTAX      GlobalIndex
   MAX-ACCESS  not-accessible
   STATUS      current
   DESCRIPTION
      "The value of the tlsCntTreeGlobalIndex of the MANAGED OBJECT."
   ::= {er1645v2IpV6VrfRtrDnsHostsEntry 10}

er1645v2IpV6VrfRtrDnsHostsTableIx OBJECT-TYPE
   SYNTAX      TableIndex
   MAX-ACCESS  not-accessible
   STATUS      current
   DESCRIPTION
      ""
   ::= {er1645v2IpV6VrfRtrDnsHostsEntry 11}

er1645v2IpV6VrfRtrDnsHostsName OBJECT-TYPE
   SYNTAX      DisplayString
   MAX-ACCESS  read-write
   STATUS      current
   DESCRIPTION
      "Path: vrfV6Router.editConf.dns.hosts.name"
   ::= {er1645v2IpV6VrfRtrDnsHostsEntry 16777216}

er1645v2IpV6VrfRtrDnsHostsAddress OBJECT-TYPE
   SYNTAX      Ipv6Address
   MAX-ACCESS  read-write
   STATUS      current
   DESCRIPTION
      "Path: vrfV6Router.editConf.dns.hosts.address

       ipv6 address"
   ::= {er1645v2IpV6VrfRtrDnsHostsEntry 33554432}


er1645v2IpV6VrfRtrQMon OBJECT IDENTIFIER ::= {er1645v2IpV6VrfRtr 7}

er1645v2IpV6VrfRtrQMonSSCTable OBJECT-TYPE
   SYNTAX      SEQUENCE OF Er1645v2IpV6VrfRtrQMonEntry
   MAX-ACCESS  not-accessible
   STATUS      current
   DESCRIPTION
      "quality monitor"
   ::= {er1645v2IpV6VrfRtrQMon 1}

er1645v2IpV6VrfRtrQMonEntry OBJECT-TYPE
   SYNTAX      Er1645v2IpV6VrfRtrQMonEntry
   MAX-ACCESS  not-accessible
   STATUS      current
   DESCRIPTION
      ""
   INDEX      { er1645v2IpV6VrfRtrQMonGlobalIx }
   ::= {er1645v2IpV6VrfRtrQMonSSCTable 1}

Er1645v2IpV6VrfRtrQMonEntry ::=
   SEQUENCE
      {
      er1645v2IpV6VrfRtrQMonGlobalIx
         GlobalIndex,
      er1645v2IpV6VrfRtrQMonMonitor
         INTEGER,
      er1645v2IpV6VrfRtrQMonType
         INTEGER,
      er1645v2IpV6VrfRtrQMonStartDelay
         TimeTicks
      }

er1645v2IpV6VrfRtrQMonGlobalIx OBJECT-TYPE
   SYNTAX      GlobalIndex
   MAX-ACCESS  not-accessible
   STATUS      current
   DESCRIPTION
      "The value of the tlsCntTreeGlobalIndex of the MANAGED OBJECT."
   ::= {er1645v2IpV6VrfRtrQMonEntry 10}

er1645v2IpV6VrfRtrQMonMonitor OBJECT-TYPE
   SYNTAX      INTEGER
               {
               disabled (0),
               enabled (1)
               }
   MAX-ACCESS  read-write
   STATUS      current
   DESCRIPTION
      "Path: vrfV6Router.editConf.qualityMonitor.monitor

       Possibilities:
               disabled   (0)
               enabled   (1)"
   ::= {er1645v2IpV6VrfRtrQMonEntry 33554432}

er1645v2IpV6VrfRtrQMonType OBJECT-TYPE
   SYNTAX      INTEGER
               {
               sequential (0),
               concurrent (1)
               }
   MAX-ACCESS  read-write
   STATUS      current
   DESCRIPTION
      "Path: vrfV6Router.editConf.qualityMonitor.type

       Possibilities:
               sequential   (0)
               concurrent   (1)"
   ::= {er1645v2IpV6VrfRtrQMonEntry 16777216}

er1645v2IpV6VrfRtrQMonStartDelay OBJECT-TYPE
   SYNTAX      TimeTicks
   MAX-ACCESS  read-write
   STATUS      current
   DESCRIPTION
      "Path: vrfV6Router.editConf.qualityMonitor.startDelay

       Time in centi-second."
   ::= {er1645v2IpV6VrfRtrQMonEntry 83886080}

er1645v2IpV6VrfRtrQMonDestinations OBJECT-TYPE
   SYNTAX      SEQUENCE OF Er1645v2IpV6VrfRtrQMonDestinationsEntry
   MAX-ACCESS  not-accessible
   STATUS      current
   DESCRIPTION
      ""
   ::= {er1645v2IpV6VrfRtrQMon 50331648}

er1645v2IpV6VrfRtrQMonDestinationsEntry OBJECT-TYPE
   SYNTAX      Er1645v2IpV6VrfRtrQMonDestinationsEntry
   MAX-ACCESS  not-accessible
   STATUS      current
   DESCRIPTION
      ""
   INDEX      { er1645v2IpV6VrfRtrQMonDestinationsGlobalIx,
                er1645v2IpV6VrfRtrQMonDestinationsTableIx }
   ::= {er1645v2IpV6VrfRtrQMonDestinations 1}

Er1645v2IpV6VrfRtrQMonDestinationsEntry ::=
   SEQUENCE
      {
      er1645v2IpV6VrfRtrQMonDestinationsActions
         VariableLengthTableActions,
      er1645v2IpV6VrfRtrQMonDestinationsGlobalIx
         GlobalIndex,
      er1645v2IpV6VrfRtrQMonDestinationsTableIx
         TableIndex,
      er1645v2IpV6VrfRtrQMonDestinationsName
         DisplayString,
      er1645v2IpV6VrfRtrQMonDestinationsAdminStatus
         INTEGER,
      er1645v2IpV6VrfRtrQMonDestinationsIpAddress
         Ipv6Address,
      er1645v2IpV6VrfRtrQMonDestinationsHostName
         DisplayString,
      er1645v2IpV6VrfRtrQMonDestinationsSource
         Ipv6Address,
      er1645v2IpV6VrfRtrQMonDestinationsTrafficClass
         Integer32,
      er1645v2IpV6VrfRtrQMonDestinationsPriority
         INTEGER,
      er1645v2IpV6VrfRtrQMonDestinationsProtocolIcmpV6
         OCTET STRING,
      er1645v2IpV6VrfRtrQMonDestinationsProtocolUdpEcho
         OCTET STRING,
      er1645v2IpV6VrfRtrQMonDestinationsProtocolUdpServerPort
         Integer32,
      er1645v2IpV6VrfRtrQMonDestinationsProtocolTwampLightPort
         Integer32,
      er1645v2IpV6VrfRtrQMonDestinationsTxInterface
         DisplayString,
      er1645v2IpV6VrfRtrQMonDestinationsTxGateway
         Ipv6Address,
      er1645v2IpV6VrfRtrQMonDestinationsInterval
         Integer32,
      er1645v2IpV6VrfRtrQMonDestinationsTimeOut
         Integer32,
      er1645v2IpV6VrfRtrQMonDestinationsLength
         Integer32,
      er1645v2IpV6VrfRtrQMonDestinationsIdleSamples
         Integer32,
      er1645v2IpV6VrfRtrQMonDestinationsLossAlarmSamples
         Integer32,
      er1645v2IpV6VrfRtrQMonDestinationsLossAlarmAlarmOn
         Integer32,
      er1645v2IpV6VrfRtrQMonDestinationsLossAlarmAlarmOff
         Integer32,
      er1645v2IpV6VrfRtrQMonDestinationsLossAlarmAlarmUpOn
         Integer32,
      er1645v2IpV6VrfRtrQMonDestinationsLossAlarmAlarmUpOff
         Integer32,
      er1645v2IpV6VrfRtrQMonDestinationsLossAlarmAlarmDownOn
         Integer32,
      er1645v2IpV6VrfRtrQMonDestinationsLossAlarmAlarmDownOff
         Integer32,
      er1645v2IpV6VrfRtrQMonDestinationsDelayAlarmSamples
         Integer32,
      er1645v2IpV6VrfRtrQMonDestinationsDelayAlarmDelayAvrgOn
         Integer32,
      er1645v2IpV6VrfRtrQMonDestinationsDelayAlarmDelayAvrgOff
         Integer32,
      er1645v2IpV6VrfRtrQMonDestinationsDelayAlarmDelayMaxOn
         Integer32,
      er1645v2IpV6VrfRtrQMonDestinationsDelayAlarmDelayMaxOff
         Integer32,
      er1645v2IpV6VrfRtrQMonDestinationsDelayAlarmDelayMinMaxOn
         Integer32,
      er1645v2IpV6VrfRtrQMonDestinationsDelayAlarmDelayMinMaxOff
         Integer32,
      er1645v2IpV6VrfRtrQMonDestinationsDelayAlarmDsType
         INTEGER,
      er1645v2IpV6VrfRtrQMonDestinationsDelayAlarmDsBinsN
         INTEGER,
      er1645v2IpV6VrfRtrQMonDestinationsDelayAlarmDsBinsNMn
         Integer32,
      er1645v2IpV6VrfRtrQMonDestinationsDelayAlarmDsBinsNMx
         Integer32,
      er1645v2IpV6VrfRtrQMonDestinationsDelayAlarmDsBinsTB1
         Integer32,
      er1645v2IpV6VrfRtrQMonDestinationsDelayAlarmDsBinsTB2
         Integer32,
      er1645v2IpV6VrfRtrQMonDestinationsDelayAlarmDsBinsTB3
         Integer32,
      er1645v2IpV6VrfRtrQMonDestinationsDelayAlarmDsBinsTB4
         Integer32,
      er1645v2IpV6VrfRtrQMonDestinationsDelayAlarmDsBinsTB5
         Integer32,
      er1645v2IpV6VrfRtrQMonDestinationsDelayAlarmDsBinsTB6
         Integer32,
      er1645v2IpV6VrfRtrQMonDestinationsDelayAlarmDsBinsTB7
         Integer32,
      er1645v2IpV6VrfRtrQMonDestinationsDelayAlarmDsBinsTB8
         Integer32,
      er1645v2IpV6VrfRtrQMonDestinationsDelayAlarmDsBinsTMx
         Integer32,
      er1645v2IpV6VrfRtrQMonDestinationsDelayAlarmJitterAvrgOn
         Integer32,
      er1645v2IpV6VrfRtrQMonDestinationsDelayAlarmJitterAvrgOff
         Integer32,
      er1645v2IpV6VrfRtrQMonDestinationsDelayAlarmJitterMaxOn
         Integer32,
      er1645v2IpV6VrfRtrQMonDestinationsDelayAlarmJitterMaxOff
         Integer32,
      er1645v2IpV6VrfRtrQMonDestinationsDelayAlarmJsN
         INTEGER,
      er1645v2IpV6VrfRtrQMonDestinationsDelayAlarmJsNMn
         Integer32,
      er1645v2IpV6VrfRtrQMonDestinationsDelayAlarmJsNMx
         Integer32,
      er1645v2IpV6VrfRtrQMonDestinationsDelayAlarmJsTB1
         Integer32,
      er1645v2IpV6VrfRtrQMonDestinationsDelayAlarmJsTB2
         Integer32,
      er1645v2IpV6VrfRtrQMonDestinationsDelayAlarmJsTB3
         Integer32,
      er1645v2IpV6VrfRtrQMonDestinationsDelayAlarmJsTB4
         Integer32,
      er1645v2IpV6VrfRtrQMonDestinationsDelayAlarmJsTB5
         Integer32,
      er1645v2IpV6VrfRtrQMonDestinationsDelayAlarmJsTB6
         Integer32,
      er1645v2IpV6VrfRtrQMonDestinationsDelayAlarmJsTB7
         Integer32,
      er1645v2IpV6VrfRtrQMonDestinationsDelayAlarmJsTB8
         Integer32,
      er1645v2IpV6VrfRtrQMonDestinationsDelayAlarmJsTMx
         Integer32,
      er1645v2IpV6VrfRtrQMonDestinationsDelayAlarmJitterUpAvrgOn
         Integer32,
      er1645v2IpV6VrfRtrQMonDestinationsDelayAlarmJitterUpAvrgOff
         Integer32,
      er1645v2IpV6VrfRtrQMonDestinationsDelayAlarmJitterUpMaxOn
         Integer32,
      er1645v2IpV6VrfRtrQMonDestinationsDelayAlarmJitterUpMaxOff
         Integer32,
      er1645v2IpV6VrfRtrQMonDestinationsDelayAlarmJupsN
         INTEGER,
      er1645v2IpV6VrfRtrQMonDestinationsDelayAlarmJupsNMn
         Integer32,
      er1645v2IpV6VrfRtrQMonDestinationsDelayAlarmJupsNMx
         Integer32,
      er1645v2IpV6VrfRtrQMonDestinationsDelayAlarmJupsTB1
         Integer32,
      er1645v2IpV6VrfRtrQMonDestinationsDelayAlarmJupsTB2
         Integer32,
      er1645v2IpV6VrfRtrQMonDestinationsDelayAlarmJupsTB3
         Integer32,
      er1645v2IpV6VrfRtrQMonDestinationsDelayAlarmJupsTB4
         Integer32,
      er1645v2IpV6VrfRtrQMonDestinationsDelayAlarmJupsTB5
         Integer32,
      er1645v2IpV6VrfRtrQMonDestinationsDelayAlarmJupsTB6
         Integer32,
      er1645v2IpV6VrfRtrQMonDestinationsDelayAlarmJupsTB7
         Integer32,
      er1645v2IpV6VrfRtrQMonDestinationsDelayAlarmJupsTB8
         Integer32,
      er1645v2IpV6VrfRtrQMonDestinationsDelayAlarmJupsTMx
         Integer32,
      er1645v2IpV6VrfRtrQMonDestinationsDelayAlarmJitterDownAvrgOn
         Integer32,
      er1645v2IpV6VrfRtrQMonDestinationsDelayAlarmJitterDownAvrgOff
         Integer32,
      er1645v2IpV6VrfRtrQMonDestinationsDelayAlarmJitterDownMaxOn
         Integer32,
      er1645v2IpV6VrfRtrQMonDestinationsDelayAlarmJitterDownMaxOff
         Integer32,
      er1645v2IpV6VrfRtrQMonDestinationsDelayAlarmJdownsN
         INTEGER,
      er1645v2IpV6VrfRtrQMonDestinationsDelayAlarmJdownsNMn
         Integer32,
      er1645v2IpV6VrfRtrQMonDestinationsDelayAlarmJdownsNMx
         Integer32,
      er1645v2IpV6VrfRtrQMonDestinationsDelayAlarmJdownsTB1
         Integer32,
      er1645v2IpV6VrfRtrQMonDestinationsDelayAlarmJdownsTB2
         Integer32,
      er1645v2IpV6VrfRtrQMonDestinationsDelayAlarmJdownsTB3
         Integer32,
      er1645v2IpV6VrfRtrQMonDestinationsDelayAlarmJdownsTB4
         Integer32,
      er1645v2IpV6VrfRtrQMonDestinationsDelayAlarmJdownsTB5
         Integer32,
      er1645v2IpV6VrfRtrQMonDestinationsDelayAlarmJdownsTB6
         Integer32,
      er1645v2IpV6VrfRtrQMonDestinationsDelayAlarmJdownsTB7
         Integer32,
      er1645v2IpV6VrfRtrQMonDestinationsDelayAlarmJdownsTB8
         Integer32,
      er1645v2IpV6VrfRtrQMonDestinationsDelayAlarmJdownsTMx
         Integer32,
      er1645v2IpV6VrfRtrQMonDestinationsDelayAlarmDelayUpAvrgOn
         Integer32,
      er1645v2IpV6VrfRtrQMonDestinationsDelayAlarmDelayUpAvrgOff
         Integer32,
      er1645v2IpV6VrfRtrQMonDestinationsDelayAlarmDelayUpMaxOn
         Integer32,
      er1645v2IpV6VrfRtrQMonDestinationsDelayAlarmDelayUpMaxOff
         Integer32,
      er1645v2IpV6VrfRtrQMonDestinationsDelayAlarmDupsType
         INTEGER,
      er1645v2IpV6VrfRtrQMonDestinationsDelayAlarmDupsBinsN
         INTEGER,
      er1645v2IpV6VrfRtrQMonDestinationsDelayAlarmDupsBinsNMn
         Integer32,
      er1645v2IpV6VrfRtrQMonDestinationsDelayAlarmDupsBinsNMx
         Integer32,
      er1645v2IpV6VrfRtrQMonDestinationsDelayAlarmDupsBinsTB1
         Integer32,
      er1645v2IpV6VrfRtrQMonDestinationsDelayAlarmDupsBinsTB2
         Integer32,
      er1645v2IpV6VrfRtrQMonDestinationsDelayAlarmDupsBinsTB3
         Integer32,
      er1645v2IpV6VrfRtrQMonDestinationsDelayAlarmDupsBinsTB4
         Integer32,
      er1645v2IpV6VrfRtrQMonDestinationsDelayAlarmDupsBinsTB5
         Integer32,
      er1645v2IpV6VrfRtrQMonDestinationsDelayAlarmDupsBinsTB6
         Integer32,
      er1645v2IpV6VrfRtrQMonDestinationsDelayAlarmDupsBinsTB7
         Integer32,
      er1645v2IpV6VrfRtrQMonDestinationsDelayAlarmDupsBinsTB8
         Integer32,
      er1645v2IpV6VrfRtrQMonDestinationsDelayAlarmDupsBinsTMx
         Integer32,
      er1645v2IpV6VrfRtrQMonDestinationsDelayAlarmDelayDownAvrgOn
         Integer32,
      er1645v2IpV6VrfRtrQMonDestinationsDelayAlarmDelayDownAvrgOff
         Integer32,
      er1645v2IpV6VrfRtrQMonDestinationsDelayAlarmDelayDownMaxOn
         Integer32,
      er1645v2IpV6VrfRtrQMonDestinationsDelayAlarmDelayDownMaxOff
         Integer32,
      er1645v2IpV6VrfRtrQMonDestinationsDelayAlarmDdownsType
         INTEGER,
      er1645v2IpV6VrfRtrQMonDestinationsDelayAlarmDdownsBinsN
         INTEGER,
      er1645v2IpV6VrfRtrQMonDestinationsDelayAlarmDdownsBinsNMn
         Integer32,
      er1645v2IpV6VrfRtrQMonDestinationsDelayAlarmDdownsBinsNMx
         Integer32,
      er1645v2IpV6VrfRtrQMonDestinationsDelayAlarmDdownsBinsTB1
         Integer32,
      er1645v2IpV6VrfRtrQMonDestinationsDelayAlarmDdownsBinsTB2
         Integer32,
      er1645v2IpV6VrfRtrQMonDestinationsDelayAlarmDdownsBinsTB3
         Integer32,
      er1645v2IpV6VrfRtrQMonDestinationsDelayAlarmDdownsBinsTB4
         Integer32,
      er1645v2IpV6VrfRtrQMonDestinationsDelayAlarmDdownsBinsTB5
         Integer32,
      er1645v2IpV6VrfRtrQMonDestinationsDelayAlarmDdownsBinsTB6
         Integer32,
      er1645v2IpV6VrfRtrQMonDestinationsDelayAlarmDdownsBinsTB7
         Integer32,
      er1645v2IpV6VrfRtrQMonDestinationsDelayAlarmDdownsBinsTB8
         Integer32,
      er1645v2IpV6VrfRtrQMonDestinationsDelayAlarmDdownsBinsTMx
         Integer32,
      er1645v2IpV6VrfRtrQMonDestinationsAlarmMask
         Integer32,
      er1645v2IpV6VrfRtrQMonDestinationsLogging
         INTEGER,
      er1645v2IpV6VrfRtrQMonDestinationsLoggingDepth
         INTEGER
      }

er1645v2IpV6VrfRtrQMonDestinationsActions OBJECT-TYPE
   SYNTAX      VariableLengthTableActions
   MAX-ACCESS  read-write
   STATUS      current
   DESCRIPTION
      "By way of this field, some manipulations
       on this table may be performed."
   ::= {er1645v2IpV6VrfRtrQMonDestinationsEntry 2}

er1645v2IpV6VrfRtrQMonDestinationsGlobalIx OBJECT-TYPE
   SYNTAX      GlobalIndex
   MAX-ACCESS  not-accessible
   STATUS      current
   DESCRIPTION
      "The value of the tlsCntTreeGlobalIndex of the MANAGED OBJECT."
   ::= {er1645v2IpV6VrfRtrQMonDestinationsEntry 10}

er1645v2IpV6VrfRtrQMonDestinationsTableIx OBJECT-TYPE
   SYNTAX      TableIndex
   MAX-ACCESS  not-accessible
   STATUS      current
   DESCRIPTION
      ""
   ::= {er1645v2IpV6VrfRtrQMonDestinationsEntry 11}

er1645v2IpV6VrfRtrQMonDestinationsName OBJECT-TYPE
   SYNTAX      DisplayString
   MAX-ACCESS  read-write
   STATUS      current
   DESCRIPTION
      "Path: vrfV6Router.editConf.qualityMonitor.destinations.name"
   ::= {er1645v2IpV6VrfRtrQMonDestinationsEntry 234881024}

er1645v2IpV6VrfRtrQMonDestinationsAdminStatus OBJECT-TYPE
   SYNTAX      INTEGER
               {
               enabled (1),
               onDemand (2),
               disabled (3)
               }
   MAX-ACCESS  read-write
   STATUS      current
   DESCRIPTION
      "Path: vrfV6Router.editConf.qualityMonitor.destinations.adminStatus

       Possibilities:
               enabled   (1)
               onDemand   (2)
               disabled   (3)"
   ::= {er1645v2IpV6VrfRtrQMonDestinationsEntry 369098752}

er1645v2IpV6VrfRtrQMonDestinationsIpAddress OBJECT-TYPE
   SYNTAX      Ipv6Address
   MAX-ACCESS  read-write
   STATUS      current
   DESCRIPTION
      "Path: vrfV6Router.editConf.qualityMonitor.destinations.ipAddress

       ipv6 address"
   ::= {er1645v2IpV6VrfRtrQMonDestinationsEntry 16777216}

er1645v2IpV6VrfRtrQMonDestinationsHostName OBJECT-TYPE
   SYNTAX      DisplayString
   MAX-ACCESS  read-write
   STATUS      current
   DESCRIPTION
      "Path: vrfV6Router.editConf.qualityMonitor.destinations.hostName"
   ::= {er1645v2IpV6VrfRtrQMonDestinationsEntry 33554432}

er1645v2IpV6VrfRtrQMonDestinationsSource OBJECT-TYPE
   SYNTAX      Ipv6Address
   MAX-ACCESS  read-write
   STATUS      current
   DESCRIPTION
      "Path: vrfV6Router.editConf.qualityMonitor.destinations.source

       ipv6 address"
   ::= {er1645v2IpV6VrfRtrQMonDestinationsEntry 184549376}

er1645v2IpV6VrfRtrQMonDestinationsTrafficClass OBJECT-TYPE
   SYNTAX      Integer32
   MAX-ACCESS  read-write
   STATUS      current
   DESCRIPTION
      "Path: vrfV6Router.editConf.qualityMonitor.destinations.trafficClass"
   ::= {er1645v2IpV6VrfRtrQMonDestinationsEntry 167772160}

er1645v2IpV6VrfRtrQMonDestinationsPriority OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: vrfV6Router.editConf.qualityMonitor.destinations.priority

       Possibilities:
               queue1   (0)
               queue2   (1)
               queue3   (2)
               queue4   (3)
               queue5   (4)
               lowDelayQueue   (5)
               lowDelay2Queue   (6)
               systemQueue   (7)"
   ::= {er1645v2IpV6VrfRtrQMonDestinationsEntry 218103808}

er1645v2IpV6VrfRtrQMonDestinationsProtocolIcmpV6 OBJECT-TYPE
   SYNTAX      OCTET STRING
   MAX-ACCESS  read-write
   STATUS      current
   DESCRIPTION
      "Path: vrfV6Router.editConf.qualityMonitor.destinations.protocol.icmpV6"
   ::= {er1645v2IpV6VrfRtrQMonDestinationsEntry 50397184}

er1645v2IpV6VrfRtrQMonDestinationsProtocolUdpEcho OBJECT-TYPE
   SYNTAX      OCTET STRING
   MAX-ACCESS  read-write
   STATUS      current
   DESCRIPTION
      "Path: vrfV6Router.editConf.qualityMonitor.destinations.protocol.udpEcho"
   ::= {er1645v2IpV6VrfRtrQMonDestinationsEntry 50462720}

er1645v2IpV6VrfRtrQMonDestinationsProtocolUdpServerPort OBJECT-TYPE
   SYNTAX      Integer32
   MAX-ACCESS  read-write
   STATUS      current
   DESCRIPTION
      "Path: vrfV6Router.editConf.qualityMonitor.destinations.protocol.udpServerPort"
   ::= {er1645v2IpV6VrfRtrQMonDestinationsEntry 50528256}

er1645v2IpV6VrfRtrQMonDestinationsProtocolTwampLightPort OBJECT-TYPE
   SYNTAX      Integer32
   MAX-ACCESS  read-write
   STATUS      current
   DESCRIPTION
      "Path: vrfV6Router.editConf.qualityMonitor.destinations.protocol.twampLightPort"
   ::= {er1645v2IpV6VrfRtrQMonDestinationsEntry 50593792}

er1645v2IpV6VrfRtrQMonDestinationsTxInterface OBJECT-TYPE
   SYNTAX      DisplayString
   MAX-ACCESS  read-write
   STATUS      current
   DESCRIPTION
      "Path: vrfV6Router.editConf.qualityMonitor.destinations.txInterface"
   ::= {er1645v2IpV6VrfRtrQMonDestinationsEntry 402653184}

er1645v2IpV6VrfRtrQMonDestinationsTxGateway OBJECT-TYPE
   SYNTAX      Ipv6Address
   MAX-ACCESS  read-write
   STATUS      current
   DESCRIPTION
      "Path: vrfV6Router.editConf.qualityMonitor.destinations.txGateway

       ipv6 address"
   ::= {er1645v2IpV6VrfRtrQMonDestinationsEntry 419430400}

er1645v2IpV6VrfRtrQMonDestinationsInterval OBJECT-TYPE
   SYNTAX      Integer32
   UNITS       "100msec"
   MAX-ACCESS  read-write
   STATUS      current
   DESCRIPTION
      "Path: vrfV6Router.editConf.qualityMonitor.destinations.interval

       unit name = 100msec"
   ::= {er1645v2IpV6VrfRtrQMonDestinationsEntry 67108864}

er1645v2IpV6VrfRtrQMonDestinationsTimeOut OBJECT-TYPE
   SYNTAX      Integer32
   UNITS       "100msec"
   MAX-ACCESS  read-write
   STATUS      current
   DESCRIPTION
      "Path: vrfV6Router.editConf.qualityMonitor.destinations.timeOut

       unit name = 100msec"
   ::= {er1645v2IpV6VrfRtrQMonDestinationsEntry 150994944}

er1645v2IpV6VrfRtrQMonDestinationsLength OBJECT-TYPE
   SYNTAX      Integer32
   MAX-ACCESS  read-write
   STATUS      current
   DESCRIPTION
      "Path: vrfV6Router.editConf.qualityMonitor.destinations.length"
   ::= {er1645v2IpV6VrfRtrQMonDestinationsEntry 83886080}

er1645v2IpV6VrfRtrQMonDestinationsIdleSamples OBJECT-TYPE
   SYNTAX      Integer32
   MAX-ACCESS  read-write
   STATUS      current
   DESCRIPTION
      "Path: vrfV6Router.editConf.qualityMonitor.destinations.idleSamples"
   ::= {er1645v2IpV6VrfRtrQMonDestinationsEntry 268435456}

er1645v2IpV6VrfRtrQMonDestinationsLossAlarmSamples OBJECT-TYPE
   SYNTAX      Integer32
   MAX-ACCESS  read-write
   STATUS      current
   DESCRIPTION
      "Path: vrfV6Router.editConf.qualityMonitor.destinations.lossAlarm.samples"
   ::= {er1645v2IpV6VrfRtrQMonDestinationsEntry 100728832}

er1645v2IpV6VrfRtrQMonDestinationsLossAlarmAlarmOn OBJECT-TYPE
   SYNTAX      Integer32
   MAX-ACCESS  read-write
   STATUS      current
   DESCRIPTION
      "Path: vrfV6Router.editConf.qualityMonitor.destinations.lossAlarm.alarmOn"
   ::= {er1645v2IpV6VrfRtrQMonDestinationsEntry 100794368}

er1645v2IpV6VrfRtrQMonDestinationsLossAlarmAlarmOff OBJECT-TYPE
   SYNTAX      Integer32
   MAX-ACCESS  read-write
   STATUS      current
   DESCRIPTION
      "Path: vrfV6Router.editConf.qualityMonitor.destinations.lossAlarm.alarmOff"
   ::= {er1645v2IpV6VrfRtrQMonDestinationsEntry 100859904}

er1645v2IpV6VrfRtrQMonDestinationsLossAlarmAlarmUpOn OBJECT-TYPE
   SYNTAX      Integer32
   MAX-ACCESS  read-write
   STATUS      current
   DESCRIPTION
      "Path: vrfV6Router.editConf.qualityMonitor.destinations.lossAlarm.alarmUpOn"
   ::= {er1645v2IpV6VrfRtrQMonDestinationsEntry 100925440}

er1645v2IpV6VrfRtrQMonDestinationsLossAlarmAlarmUpOff OBJECT-TYPE
   SYNTAX      Integer32
   MAX-ACCESS  read-write
   STATUS      current
   DESCRIPTION
      "Path: vrfV6Router.editConf.qualityMonitor.destinations.lossAlarm.alarmUpOff"
   ::= {er1645v2IpV6VrfRtrQMonDestinationsEntry 100990976}

er1645v2IpV6VrfRtrQMonDestinationsLossAlarmAlarmDownOn OBJECT-TYPE
   SYNTAX      Integer32
   MAX-ACCESS  read-write
   STATUS      current
   DESCRIPTION
      "Path: vrfV6Router.editConf.qualityMonitor.destinations.lossAlarm.alarmDownOn"
   ::= {er1645v2IpV6VrfRtrQMonDestinationsEntry 101056512}

er1645v2IpV6VrfRtrQMonDestinationsLossAlarmAlarmDownOff OBJECT-TYPE
   SYNTAX      Integer32
   MAX-ACCESS  read-write
   STATUS      current
   DESCRIPTION
      "Path: vrfV6Router.editConf.qualityMonitor.destinations.lossAlarm.alarmDownOff"
   ::= {er1645v2IpV6VrfRtrQMonDestinationsEntry 101122048}

er1645v2IpV6VrfRtrQMonDestinationsDelayAlarmSamples OBJECT-TYPE
   SYNTAX      Integer32
   MAX-ACCESS  read-write
   STATUS      current
   DESCRIPTION
      "Path: vrfV6Router.editConf.qualityMonitor.destinations.delayAlarm.samples"
   ::= {er1645v2IpV6VrfRtrQMonDestinationsEntry 117506048}

er1645v2IpV6VrfRtrQMonDestinationsDelayAlarmDelayAvrgOn OBJECT-TYPE
   SYNTAX      Integer32
   UNITS       "msec"
   MAX-ACCESS  read-write
   STATUS      current
   DESCRIPTION
      "Path: vrfV6Router.editConf.qualityMonitor.destinations.delayAlarm.delayAvrgOn

       unit name = msec"
   ::= {er1645v2IpV6VrfRtrQMonDestinationsEntry 117571584}

er1645v2IpV6VrfRtrQMonDestinationsDelayAlarmDelayAvrgOff OBJECT-TYPE
   SYNTAX      Integer32
   UNITS       "msec"
   MAX-ACCESS  read-write
   STATUS      current
   DESCRIPTION
      "Path: vrfV6Router.editConf.qualityMonitor.destinations.delayAlarm.delayAvrgOff

       unit name = msec"
   ::= {er1645v2IpV6VrfRtrQMonDestinationsEntry 117637120}

er1645v2IpV6VrfRtrQMonDestinationsDelayAlarmDelayMaxOn OBJECT-TYPE
   SYNTAX      Integer32
   UNITS       "msec"
   MAX-ACCESS  read-write
   STATUS      current
   DESCRIPTION
      "Path: vrfV6Router.editConf.qualityMonitor.destinations.delayAlarm.delayMaxOn

       unit name = msec"
   ::= {er1645v2IpV6VrfRtrQMonDestinationsEntry 117702656}

er1645v2IpV6VrfRtrQMonDestinationsDelayAlarmDelayMaxOff OBJECT-TYPE
   SYNTAX      Integer32
   UNITS       "msec"
   MAX-ACCESS  read-write
   STATUS      current
   DESCRIPTION
      "Path: vrfV6Router.editConf.qualityMonitor.destinations.delayAlarm.delayMaxOff

       unit name = msec"
   ::= {er1645v2IpV6VrfRtrQMonDestinationsEntry 117768192}

er1645v2IpV6VrfRtrQMonDestinationsDelayAlarmDelayMinMaxOn OBJECT-TYPE
   SYNTAX      Integer32
   UNITS       "msec"
   MAX-ACCESS  read-write
   STATUS      current
   DESCRIPTION
      "Path: vrfV6Router.editConf.qualityMonitor.destinations.delayAlarm.delayMinMaxOn

       unit name = msec"
   ::= {er1645v2IpV6VrfRtrQMonDestinationsEntry 118095872}

er1645v2IpV6VrfRtrQMonDestinationsDelayAlarmDelayMinMaxOff OBJECT-TYPE
   SYNTAX      Integer32
   UNITS       "msec"
   MAX-ACCESS  read-write
   STATUS      current
   DESCRIPTION
      "Path: vrfV6Router.editConf.qualityMonitor.destinations.delayAlarm.delayMinMaxOff

       unit name = msec"
   ::= {er1645v2IpV6VrfRtrQMonDestinationsEntry 118161408}

er1645v2IpV6VrfRtrQMonDestinationsDelayAlarmDsType OBJECT-TYPE
   SYNTAX      INTEGER
               {
               fd (1),
               fdr (2)
               }
   MAX-ACCESS  read-write
   STATUS      current
   DESCRIPTION
      "Path: vrfV6Router.editConf.qualityMonitor.destinations.delayAlarm.delayStat.type

       Possibilities:
               fd   (1)
               fdr   (2)"
   ::= {er1645v2IpV6VrfRtrQMonDestinationsEntry 119283712}

er1645v2IpV6VrfRtrQMonDestinationsDelayAlarmDsBinsN OBJECT-TYPE
   SYNTAX      INTEGER
               {
               none (0)
               }
   MAX-ACCESS  read-write
   STATUS      current
   DESCRIPTION
      "Path: vrfV6Router.editConf.qualityMonitor.destinations.delayAlarm.delayStat.bins.none

       Possibilities:
               none   (0)"
   ::= {er1645v2IpV6VrfRtrQMonDestinationsEntry 119292928}

er1645v2IpV6VrfRtrQMonDestinationsDelayAlarmDsBinsNMn OBJECT-TYPE
   SYNTAX      Integer32
   UNITS       "msec"
   MAX-ACCESS  read-write
   STATUS      current
   DESCRIPTION
      "Path: vrfV6Router.editConf.qualityMonitor.destinations.delayAlarm.delayStat.bins.range.min

       unit name = msec"
   ::= {er1645v2IpV6VrfRtrQMonDestinationsEntry 119294080}

er1645v2IpV6VrfRtrQMonDestinationsDelayAlarmDsBinsNMx OBJECT-TYPE
   SYNTAX      Integer32
   UNITS       "msec"
   MAX-ACCESS  read-write
   STATUS      current
   DESCRIPTION
      "Path: vrfV6Router.editConf.qualityMonitor.destinations.delayAlarm.delayStat.bins.range.max

       unit name = msec"
   ::= {er1645v2IpV6VrfRtrQMonDestinationsEntry 119294208}

er1645v2IpV6VrfRtrQMonDestinationsDelayAlarmDsBinsTB1 OBJECT-TYPE
   SYNTAX      Integer32
   UNITS       "msec"
   MAX-ACCESS  read-write
   STATUS      current
   DESCRIPTION
      "Path: vrfV6Router.editConf.qualityMonitor.destinations.delayAlarm.delayStat.bins.table.bin1

       unit name = msec"
   ::= {er1645v2IpV6VrfRtrQMonDestinationsEntry 119295040}

er1645v2IpV6VrfRtrQMonDestinationsDelayAlarmDsBinsTB2 OBJECT-TYPE
   SYNTAX      Integer32
   UNITS       "msec"
   MAX-ACCESS  read-write
   STATUS      current
   DESCRIPTION
      "Path: vrfV6Router.editConf.qualityMonitor.destinations.delayAlarm.delayStat.bins.table.bin2

       unit name = msec"
   ::= {er1645v2IpV6VrfRtrQMonDestinationsEntry 119295104}

er1645v2IpV6VrfRtrQMonDestinationsDelayAlarmDsBinsTB3 OBJECT-TYPE
   SYNTAX      Integer32
   UNITS       "msec"
   MAX-ACCESS  read-write
   STATUS      current
   DESCRIPTION
      "Path: vrfV6Router.editConf.qualityMonitor.destinations.delayAlarm.delayStat.bins.table.bin3

       unit name = msec"
   ::= {er1645v2IpV6VrfRtrQMonDestinationsEntry 119295168}

er1645v2IpV6VrfRtrQMonDestinationsDelayAlarmDsBinsTB4 OBJECT-TYPE
   SYNTAX      Integer32
   UNITS       "msec"
   MAX-ACCESS  read-write
   STATUS      current
   DESCRIPTION
      "Path: vrfV6Router.editConf.qualityMonitor.destinations.delayAlarm.delayStat.bins.table.bin4

       unit name = msec"
   ::= {er1645v2IpV6VrfRtrQMonDestinationsEntry 119295232}

er1645v2IpV6VrfRtrQMonDestinationsDelayAlarmDsBinsTB5 OBJECT-TYPE
   SYNTAX      Integer32
   UNITS       "msec"
   MAX-ACCESS  read-write
   STATUS      current
   DESCRIPTION
      "Path: vrfV6Router.editConf.qualityMonitor.destinations.delayAlarm.delayStat.bins.table.bin5

       unit name = msec"
   ::= {er1645v2IpV6VrfRtrQMonDestinationsEntry 119295296}

er1645v2IpV6VrfRtrQMonDestinationsDelayAlarmDsBinsTB6 OBJECT-TYPE
   SYNTAX      Integer32
   UNITS       "msec"
   MAX-ACCESS  read-write
   STATUS      current
   DESCRIPTION
      "Path: vrfV6Router.editConf.qualityMonitor.destinations.delayAlarm.delayStat.bins.table.bin6

       unit name = msec"
   ::= {er1645v2IpV6VrfRtrQMonDestinationsEntry 119295360}

er1645v2IpV6VrfRtrQMonDestinationsDelayAlarmDsBinsTB7 OBJECT-TYPE
   SYNTAX      Integer32
   UNITS       "msec"
   MAX-ACCESS  read-write
   STATUS      current
   DESCRIPTION
      "Path: vrfV6Router.editConf.qualityMonitor.destinations.delayAlarm.delayStat.bins.table.bin7

       unit name = msec"
   ::= {er1645v2IpV6VrfRtrQMonDestinationsEntry 119295424}

er1645v2IpV6VrfRtrQMonDestinationsDelayAlarmDsBinsTB8 OBJECT-TYPE
   SYNTAX      Integer32
   UNITS       "msec"
   MAX-ACCESS  read-write
   STATUS      current
   DESCRIPTION
      "Path: vrfV6Router.editConf.qualityMonitor.destinations.delayAlarm.delayStat.bins.table.bin8

       unit name = msec"
   ::= {er1645v2IpV6VrfRtrQMonDestinationsEntry 119295488}

er1645v2IpV6VrfRtrQMonDestinationsDelayAlarmDsBinsTMx OBJECT-TYPE
   SYNTAX      Integer32
   UNITS       "msec"
   MAX-ACCESS  read-write
   STATUS      current
   DESCRIPTION
      "Path: vrfV6Router.editConf.qualityMonitor.destinations.delayAlarm.delayStat.bins.table.max

       unit name = msec"
   ::= {er1645v2IpV6VrfRtrQMonDestinationsEntry 119295552}

er1645v2IpV6VrfRtrQMonDestinationsDelayAlarmJitterAvrgOn OBJECT-TYPE
   SYNTAX      Integer32
   UNITS       "msec"
   MAX-ACCESS  read-write
   STATUS      current
   DESCRIPTION
      "Path: vrfV6Router.editConf.qualityMonitor.destinations.delayAlarm.jitterAvrgOn

       unit name = msec"
   ::= {er1645v2IpV6VrfRtrQMonDestinationsEntry 117833728}

er1645v2IpV6VrfRtrQMonDestinationsDelayAlarmJitterAvrgOff OBJECT-TYPE
   SYNTAX      Integer32
   UNITS       "msec"
   MAX-ACCESS  read-write
   STATUS      current
   DESCRIPTION
      "Path: vrfV6Router.editConf.qualityMonitor.destinations.delayAlarm.jitterAvrgOff

       unit name = msec"
   ::= {er1645v2IpV6VrfRtrQMonDestinationsEntry 117899264}

er1645v2IpV6VrfRtrQMonDestinationsDelayAlarmJitterMaxOn OBJECT-TYPE
   SYNTAX      Integer32
   UNITS       "msec"
   MAX-ACCESS  read-write
   STATUS      current
   DESCRIPTION
      "Path: vrfV6Router.editConf.qualityMonitor.destinations.delayAlarm.jitterMaxOn

       unit name = msec"
   ::= {er1645v2IpV6VrfRtrQMonDestinationsEntry 117964800}

er1645v2IpV6VrfRtrQMonDestinationsDelayAlarmJitterMaxOff OBJECT-TYPE
   SYNTAX      Integer32
   UNITS       "msec"
   MAX-ACCESS  read-write
   STATUS      current
   DESCRIPTION
      "Path: vrfV6Router.editConf.qualityMonitor.destinations.delayAlarm.jitterMaxOff

       unit name = msec"
   ::= {er1645v2IpV6VrfRtrQMonDestinationsEntry 118030336}

er1645v2IpV6VrfRtrQMonDestinationsDelayAlarmJsN OBJECT-TYPE
   SYNTAX      INTEGER
               {
               none (0)
               }
   MAX-ACCESS  read-write
   STATUS      current
   DESCRIPTION
      "Path: vrfV6Router.editConf.qualityMonitor.destinations.delayAlarm.jitterStat.none

       Possibilities:
               none   (0)"
   ::= {er1645v2IpV6VrfRtrQMonDestinationsEntry 119676928}

er1645v2IpV6VrfRtrQMonDestinationsDelayAlarmJsNMn OBJECT-TYPE
   SYNTAX      Integer32
   UNITS       "msec"
   MAX-ACCESS  read-write
   STATUS      current
   DESCRIPTION
      "Path: vrfV6Router.editConf.qualityMonitor.destinations.delayAlarm.jitterStat.range.min

       unit name = msec"
   ::= {er1645v2IpV6VrfRtrQMonDestinationsEntry 119686144}

er1645v2IpV6VrfRtrQMonDestinationsDelayAlarmJsNMx OBJECT-TYPE
   SYNTAX      Integer32
   UNITS       "msec"
   MAX-ACCESS  read-write
   STATUS      current
   DESCRIPTION
      "Path: vrfV6Router.editConf.qualityMonitor.destinations.delayAlarm.jitterStat.range.max

       unit name = msec"
   ::= {er1645v2IpV6VrfRtrQMonDestinationsEntry 119687168}

er1645v2IpV6VrfRtrQMonDestinationsDelayAlarmJsTB1 OBJECT-TYPE
   SYNTAX      Integer32
   UNITS       "msec"
   MAX-ACCESS  read-write
   STATUS      current
   DESCRIPTION
      "Path: vrfV6Router.editConf.qualityMonitor.destinations.delayAlarm.jitterStat.table.bin1

       unit name = msec"
   ::= {er1645v2IpV6VrfRtrQMonDestinationsEntry 119693824}

er1645v2IpV6VrfRtrQMonDestinationsDelayAlarmJsTB2 OBJECT-TYPE
   SYNTAX      Integer32
   UNITS       "msec"
   MAX-ACCESS  read-write
   STATUS      current
   DESCRIPTION
      "Path: vrfV6Router.editConf.qualityMonitor.destinations.delayAlarm.jitterStat.table.bin2

       unit name = msec"
   ::= {er1645v2IpV6VrfRtrQMonDestinationsEntry 119694336}

er1645v2IpV6VrfRtrQMonDestinationsDelayAlarmJsTB3 OBJECT-TYPE
   SYNTAX      Integer32
   UNITS       "msec"
   MAX-ACCESS  read-write
   STATUS      current
   DESCRIPTION
      "Path: vrfV6Router.editConf.qualityMonitor.destinations.delayAlarm.jitterStat.table.bin3

       unit name = msec"
   ::= {er1645v2IpV6VrfRtrQMonDestinationsEntry 119694848}

er1645v2IpV6VrfRtrQMonDestinationsDelayAlarmJsTB4 OBJECT-TYPE
   SYNTAX      Integer32
   UNITS       "msec"
   MAX-ACCESS  read-write
   STATUS      current
   DESCRIPTION
      "Path: vrfV6Router.editConf.qualityMonitor.destinations.delayAlarm.jitterStat.table.bin4

       unit name = msec"
   ::= {er1645v2IpV6VrfRtrQMonDestinationsEntry 119695360}

er1645v2IpV6VrfRtrQMonDestinationsDelayAlarmJsTB5 OBJECT-TYPE
   SYNTAX      Integer32
   UNITS       "msec"
   MAX-ACCESS  read-write
   STATUS      current
   DESCRIPTION
      "Path: vrfV6Router.editConf.qualityMonitor.destinations.delayAlarm.jitterStat.table.bin5

       unit name = msec"
   ::= {er1645v2IpV6VrfRtrQMonDestinationsEntry 119695872}

er1645v2IpV6VrfRtrQMonDestinationsDelayAlarmJsTB6 OBJECT-TYPE
   SYNTAX      Integer32
   UNITS       "msec"
   MAX-ACCESS  read-write
   STATUS      current
   DESCRIPTION
      "Path: vrfV6Router.editConf.qualityMonitor.destinations.delayAlarm.jitterStat.table.bin6

       unit name = msec"
   ::= {er1645v2IpV6VrfRtrQMonDestinationsEntry 119696384}

er1645v2IpV6VrfRtrQMonDestinationsDelayAlarmJsTB7 OBJECT-TYPE
   SYNTAX      Integer32
   UNITS       "msec"
   MAX-ACCESS  read-write
   STATUS      current
   DESCRIPTION
      "Path: vrfV6Router.editConf.qualityMonitor.destinations.delayAlarm.jitterStat.table.bin7

       unit name = msec"
   ::= {er1645v2IpV6VrfRtrQMonDestinationsEntry 119696896}

er1645v2IpV6VrfRtrQMonDestinationsDelayAlarmJsTB8 OBJECT-TYPE
   SYNTAX      Integer32
   UNITS       "msec"
   MAX-ACCESS  read-write
   STATUS      current
   DESCRIPTION
      "Path: vrfV6Router.editConf.qualityMonitor.destinations.delayAlarm.jitterStat.table.bin8

       unit name = msec"
   ::= {er1645v2IpV6VrfRtrQMonDestinationsEntry 119697408}

er1645v2IpV6VrfRtrQMonDestinationsDelayAlarmJsTMx OBJECT-TYPE
   SYNTAX      Integer32
   UNITS       "msec"
   MAX-ACCESS  read-write
   STATUS      current
   DESCRIPTION
      "Path: vrfV6Router.editConf.qualityMonitor.destinations.delayAlarm.jitterStat.table.max

       unit name = msec"
   ::= {er1645v2IpV6VrfRtrQMonDestinationsEntry 119697920}

er1645v2IpV6VrfRtrQMonDestinationsDelayAlarmJitterUpAvrgOn OBJECT-TYPE
   SYNTAX      Integer32
   UNITS       "msec"
   MAX-ACCESS  read-write
   STATUS      current
   DESCRIPTION
      "Path: vrfV6Router.editConf.qualityMonitor.destinations.delayAlarm.jitterUpAvrgOn

       unit name = msec"
   ::= {er1645v2IpV6VrfRtrQMonDestinationsEntry 118226944}

er1645v2IpV6VrfRtrQMonDestinationsDelayAlarmJitterUpAvrgOff OBJECT-TYPE
   SYNTAX      Integer32
   UNITS       "msec"
   MAX-ACCESS  read-write
   STATUS      current
   DESCRIPTION
      "Path: vrfV6Router.editConf.qualityMonitor.destinations.delayAlarm.jitterUpAvrgOff

       unit name = msec"
   ::= {er1645v2IpV6VrfRtrQMonDestinationsEntry 118292480}

er1645v2IpV6VrfRtrQMonDestinationsDelayAlarmJitterUpMaxOn OBJECT-TYPE
   SYNTAX      Integer32
   UNITS       "msec"
   MAX-ACCESS  read-write
   STATUS      current
   DESCRIPTION
      "Path: vrfV6Router.editConf.qualityMonitor.destinations.delayAlarm.jitterUpMaxOn

       unit name = msec"
   ::= {er1645v2IpV6VrfRtrQMonDestinationsEntry 118358016}

er1645v2IpV6VrfRtrQMonDestinationsDelayAlarmJitterUpMaxOff OBJECT-TYPE
   SYNTAX      Integer32
   UNITS       "msec"
   MAX-ACCESS  read-write
   STATUS      current
   DESCRIPTION
      "Path: vrfV6Router.editConf.qualityMonitor.destinations.delayAlarm.jitterUpMaxOff

       unit name = msec"
   ::= {er1645v2IpV6VrfRtrQMonDestinationsEntry 118423552}

er1645v2IpV6VrfRtrQMonDestinationsDelayAlarmJupsN OBJECT-TYPE
   SYNTAX      INTEGER
               {
               none (0)
               }
   MAX-ACCESS  read-write
   STATUS      current
   DESCRIPTION
      "Path: vrfV6Router.editConf.qualityMonitor.destinations.delayAlarm.jitterUpStat.none

       Possibilities:
               none   (0)"
   ::= {er1645v2IpV6VrfRtrQMonDestinationsEntry 119808000}

er1645v2IpV6VrfRtrQMonDestinationsDelayAlarmJupsNMn OBJECT-TYPE
   SYNTAX      Integer32
   UNITS       "msec"
   MAX-ACCESS  read-write
   STATUS      current
   DESCRIPTION
      "Path: vrfV6Router.editConf.qualityMonitor.destinations.delayAlarm.jitterUpStat.range.min

       unit name = msec"
   ::= {er1645v2IpV6VrfRtrQMonDestinationsEntry 119817216}

er1645v2IpV6VrfRtrQMonDestinationsDelayAlarmJupsNMx OBJECT-TYPE
   SYNTAX      Integer32
   UNITS       "msec"
   MAX-ACCESS  read-write
   STATUS      current
   DESCRIPTION
      "Path: vrfV6Router.editConf.qualityMonitor.destinations.delayAlarm.jitterUpStat.range.max

       unit name = msec"
   ::= {er1645v2IpV6VrfRtrQMonDestinationsEntry 119818240}

er1645v2IpV6VrfRtrQMonDestinationsDelayAlarmJupsTB1 OBJECT-TYPE
   SYNTAX      Integer32
   UNITS       "msec"
   MAX-ACCESS  read-write
   STATUS      current
   DESCRIPTION
      "Path: vrfV6Router.editConf.qualityMonitor.destinations.delayAlarm.jitterUpStat.table.bin1

       unit name = msec"
   ::= {er1645v2IpV6VrfRtrQMonDestinationsEntry 119824896}

er1645v2IpV6VrfRtrQMonDestinationsDelayAlarmJupsTB2 OBJECT-TYPE
   SYNTAX      Integer32
   UNITS       "msec"
   MAX-ACCESS  read-write
   STATUS      current
   DESCRIPTION
      "Path: vrfV6Router.editConf.qualityMonitor.destinations.delayAlarm.jitterUpStat.table.bin2

       unit name = msec"
   ::= {er1645v2IpV6VrfRtrQMonDestinationsEntry 119825408}

er1645v2IpV6VrfRtrQMonDestinationsDelayAlarmJupsTB3 OBJECT-TYPE
   SYNTAX      Integer32
   UNITS       "msec"
   MAX-ACCESS  read-write
   STATUS      current
   DESCRIPTION
      "Path: vrfV6Router.editConf.qualityMonitor.destinations.delayAlarm.jitterUpStat.table.bin3

       unit name = msec"
   ::= {er1645v2IpV6VrfRtrQMonDestinationsEntry 119825920}

er1645v2IpV6VrfRtrQMonDestinationsDelayAlarmJupsTB4 OBJECT-TYPE
   SYNTAX      Integer32
   UNITS       "msec"
   MAX-ACCESS  read-write
   STATUS      current
   DESCRIPTION
      "Path: vrfV6Router.editConf.qualityMonitor.destinations.delayAlarm.jitterUpStat.table.bin4

       unit name = msec"
   ::= {er1645v2IpV6VrfRtrQMonDestinationsEntry 119826432}

er1645v2IpV6VrfRtrQMonDestinationsDelayAlarmJupsTB5 OBJECT-TYPE
   SYNTAX      Integer32
   UNITS       "msec"
   MAX-ACCESS  read-write
   STATUS      current
   DESCRIPTION
      "Path: vrfV6Router.editConf.qualityMonitor.destinations.delayAlarm.jitterUpStat.table.bin5

       unit name = msec"
   ::= {er1645v2IpV6VrfRtrQMonDestinationsEntry 119826944}

er1645v2IpV6VrfRtrQMonDestinationsDelayAlarmJupsTB6 OBJECT-TYPE
   SYNTAX      Integer32
   UNITS       "msec"
   MAX-ACCESS  read-write
   STATUS      current
   DESCRIPTION
      "Path: vrfV6Router.editConf.qualityMonitor.destinations.delayAlarm.jitterUpStat.table.bin6

       unit name = msec"
   ::= {er1645v2IpV6VrfRtrQMonDestinationsEntry 119827456}

er1645v2IpV6VrfRtrQMonDestinationsDelayAlarmJupsTB7 OBJECT-TYPE
   SYNTAX      Integer32
   UNITS       "msec"
   MAX-ACCESS  read-write
   STATUS      current
   DESCRIPTION
      "Path: vrfV6Router.editConf.qualityMonitor.destinations.delayAlarm.jitterUpStat.table.bin7

       unit name = msec"
   ::= {er1645v2IpV6VrfRtrQMonDestinationsEntry 119827968}

er1645v2IpV6VrfRtrQMonDestinationsDelayAlarmJupsTB8 OBJECT-TYPE
   SYNTAX      Integer32
   UNITS       "msec"
   MAX-ACCESS  read-write
   STATUS      current
   DESCRIPTION
      "Path: vrfV6Router.editConf.qualityMonitor.destinations.delayAlarm.jitterUpStat.table.bin8

       unit name = msec"
   ::= {er1645v2IpV6VrfRtrQMonDestinationsEntry 119828480}

er1645v2IpV6VrfRtrQMonDestinationsDelayAlarmJupsTMx OBJECT-TYPE
   SYNTAX      Integer32
   UNITS       "msec"
   MAX-ACCESS  read-write
   STATUS      current
   DESCRIPTION
      "Path: vrfV6Router.editConf.qualityMonitor.destinations.delayAlarm.jitterUpStat.table.max

       unit name = msec"
   ::= {er1645v2IpV6VrfRtrQMonDestinationsEntry 119828992}

er1645v2IpV6VrfRtrQMonDestinationsDelayAlarmJitterDownAvrgOn OBJECT-TYPE
   SYNTAX      Integer32
   UNITS       "msec"
   MAX-ACCESS  read-write
   STATUS      current
   DESCRIPTION
      "Path: vrfV6Router.editConf.qualityMonitor.destinations.delayAlarm.jitterDownAvrgOn

       unit name = msec"
   ::= {er1645v2IpV6VrfRtrQMonDestinationsEntry 118489088}

er1645v2IpV6VrfRtrQMonDestinationsDelayAlarmJitterDownAvrgOff OBJECT-TYPE
   SYNTAX      Integer32
   UNITS       "msec"
   MAX-ACCESS  read-write
   STATUS      current
   DESCRIPTION
      "Path: vrfV6Router.editConf.qualityMonitor.destinations.delayAlarm.jitterDownAvrgOff

       unit name = msec"
   ::= {er1645v2IpV6VrfRtrQMonDestinationsEntry 118554624}

er1645v2IpV6VrfRtrQMonDestinationsDelayAlarmJitterDownMaxOn OBJECT-TYPE
   SYNTAX      Integer32
   UNITS       "msec"
   MAX-ACCESS  read-write
   STATUS      current
   DESCRIPTION
      "Path: vrfV6Router.editConf.qualityMonitor.destinations.delayAlarm.jitterDownMaxOn

       unit name = msec"
   ::= {er1645v2IpV6VrfRtrQMonDestinationsEntry 118620160}

er1645v2IpV6VrfRtrQMonDestinationsDelayAlarmJitterDownMaxOff OBJECT-TYPE
   SYNTAX      Integer32
   UNITS       "msec"
   MAX-ACCESS  read-write
   STATUS      current
   DESCRIPTION
      "Path: vrfV6Router.editConf.qualityMonitor.destinations.delayAlarm.jitterDownMaxOff

       unit name = msec"
   ::= {er1645v2IpV6VrfRtrQMonDestinationsEntry 118685696}

er1645v2IpV6VrfRtrQMonDestinationsDelayAlarmJdownsN OBJECT-TYPE
   SYNTAX      INTEGER
               {
               none (0)
               }
   MAX-ACCESS  read-write
   STATUS      current
   DESCRIPTION
      "Path: vrfV6Router.editConf.qualityMonitor.destinations.delayAlarm.jitterDownStat.none

       Possibilities:
               none   (0)"
   ::= {er1645v2IpV6VrfRtrQMonDestinationsEntry 119939072}

er1645v2IpV6VrfRtrQMonDestinationsDelayAlarmJdownsNMn OBJECT-TYPE
   SYNTAX      Integer32
   UNITS       "msec"
   MAX-ACCESS  read-write
   STATUS      current
   DESCRIPTION
      "Path: vrfV6Router.editConf.qualityMonitor.destinations.delayAlarm.jitterDownStat.range.min

       unit name = msec"
   ::= {er1645v2IpV6VrfRtrQMonDestinationsEntry 119948288}

er1645v2IpV6VrfRtrQMonDestinationsDelayAlarmJdownsNMx OBJECT-TYPE
   SYNTAX      Integer32
   UNITS       "msec"
   MAX-ACCESS  read-write
   STATUS      current
   DESCRIPTION
      "Path: vrfV6Router.editConf.qualityMonitor.destinations.delayAlarm.jitterDownStat.range.max

       unit name = msec"
   ::= {er1645v2IpV6VrfRtrQMonDestinationsEntry 119949312}

er1645v2IpV6VrfRtrQMonDestinationsDelayAlarmJdownsTB1 OBJECT-TYPE
   SYNTAX      Integer32
   UNITS       "msec"
   MAX-ACCESS  read-write
   STATUS      current
   DESCRIPTION
      "Path: vrfV6Router.editConf.qualityMonitor.destinations.delayAlarm.jitterDownStat.table.bin1

       unit name = msec"
   ::= {er1645v2IpV6VrfRtrQMonDestinationsEntry 119955968}

er1645v2IpV6VrfRtrQMonDestinationsDelayAlarmJdownsTB2 OBJECT-TYPE
   SYNTAX      Integer32
   UNITS       "msec"
   MAX-ACCESS  read-write
   STATUS      current
   DESCRIPTION
      "Path: vrfV6Router.editConf.qualityMonitor.destinations.delayAlarm.jitterDownStat.table.bin2

       unit name = msec"
   ::= {er1645v2IpV6VrfRtrQMonDestinationsEntry 119956480}

er1645v2IpV6VrfRtrQMonDestinationsDelayAlarmJdownsTB3 OBJECT-TYPE
   SYNTAX      Integer32
   UNITS       "msec"
   MAX-ACCESS  read-write
   STATUS      current
   DESCRIPTION
      "Path: vrfV6Router.editConf.qualityMonitor.destinations.delayAlarm.jitterDownStat.table.bin3

       unit name = msec"
   ::= {er1645v2IpV6VrfRtrQMonDestinationsEntry 119956992}

er1645v2IpV6VrfRtrQMonDestinationsDelayAlarmJdownsTB4 OBJECT-TYPE
   SYNTAX      Integer32
   UNITS       "msec"
   MAX-ACCESS  read-write
   STATUS      current
   DESCRIPTION
      "Path: vrfV6Router.editConf.qualityMonitor.destinations.delayAlarm.jitterDownStat.table.bin4

       unit name = msec"
   ::= {er1645v2IpV6VrfRtrQMonDestinationsEntry 119957504}

er1645v2IpV6VrfRtrQMonDestinationsDelayAlarmJdownsTB5 OBJECT-TYPE
   SYNTAX      Integer32
   UNITS       "msec"
   MAX-ACCESS  read-write
   STATUS      current
   DESCRIPTION
      "Path: vrfV6Router.editConf.qualityMonitor.destinations.delayAlarm.jitterDownStat.table.bin5

       unit name = msec"
   ::= {er1645v2IpV6VrfRtrQMonDestinationsEntry 119958016}

er1645v2IpV6VrfRtrQMonDestinationsDelayAlarmJdownsTB6 OBJECT-TYPE
   SYNTAX      Integer32
   UNITS       "msec"
   MAX-ACCESS  read-write
   STATUS      current
   DESCRIPTION
      "Path: vrfV6Router.editConf.qualityMonitor.destinations.delayAlarm.jitterDownStat.table.bin6

       unit name = msec"
   ::= {er1645v2IpV6VrfRtrQMonDestinationsEntry 119958528}

er1645v2IpV6VrfRtrQMonDestinationsDelayAlarmJdownsTB7 OBJECT-TYPE
   SYNTAX      Integer32
   UNITS       "msec"
   MAX-ACCESS  read-write
   STATUS      current
   DESCRIPTION
      "Path: vrfV6Router.editConf.qualityMonitor.destinations.delayAlarm.jitterDownStat.table.bin7

       unit name = msec"
   ::= {er1645v2IpV6VrfRtrQMonDestinationsEntry 119959040}

er1645v2IpV6VrfRtrQMonDestinationsDelayAlarmJdownsTB8 OBJECT-TYPE
   SYNTAX      Integer32
   UNITS       "msec"
   MAX-ACCESS  read-write
   STATUS      current
   DESCRIPTION
      "Path: vrfV6Router.editConf.qualityMonitor.destinations.delayAlarm.jitterDownStat.table.bin8

       unit name = msec"
   ::= {er1645v2IpV6VrfRtrQMonDestinationsEntry 119959552}

er1645v2IpV6VrfRtrQMonDestinationsDelayAlarmJdownsTMx OBJECT-TYPE
   SYNTAX      Integer32
   UNITS       "msec"
   MAX-ACCESS  read-write
   STATUS      current
   DESCRIPTION
      "Path: vrfV6Router.editConf.qualityMonitor.destinations.delayAlarm.jitterDownStat.table.max

       unit name = msec"
   ::= {er1645v2IpV6VrfRtrQMonDestinationsEntry 119960064}

er1645v2IpV6VrfRtrQMonDestinationsDelayAlarmDelayUpAvrgOn OBJECT-TYPE
   SYNTAX      Integer32
   UNITS       "msec"
   MAX-ACCESS  read-write
   STATUS      current
   DESCRIPTION
      "Path: vrfV6Router.editConf.qualityMonitor.destinations.delayAlarm.delayUpAvrgOn

       unit name = msec"
   ::= {er1645v2IpV6VrfRtrQMonDestinationsEntry 118751232}

er1645v2IpV6VrfRtrQMonDestinationsDelayAlarmDelayUpAvrgOff OBJECT-TYPE
   SYNTAX      Integer32
   UNITS       "msec"
   MAX-ACCESS  read-write
   STATUS      current
   DESCRIPTION
      "Path: vrfV6Router.editConf.qualityMonitor.destinations.delayAlarm.delayUpAvrgOff

       unit name = msec"
   ::= {er1645v2IpV6VrfRtrQMonDestinationsEntry 118816768}

er1645v2IpV6VrfRtrQMonDestinationsDelayAlarmDelayUpMaxOn OBJECT-TYPE
   SYNTAX      Integer32
   UNITS       "msec"
   MAX-ACCESS  read-write
   STATUS      current
   DESCRIPTION
      "Path: vrfV6Router.editConf.qualityMonitor.destinations.delayAlarm.delayUpMaxOn

       unit name = msec"
   ::= {er1645v2IpV6VrfRtrQMonDestinationsEntry 118882304}

er1645v2IpV6VrfRtrQMonDestinationsDelayAlarmDelayUpMaxOff OBJECT-TYPE
   SYNTAX      Integer32
   UNITS       "msec"
   MAX-ACCESS  read-write
   STATUS      current
   DESCRIPTION
      "Path: vrfV6Router.editConf.qualityMonitor.destinations.delayAlarm.delayUpMaxOff

       unit name = msec"
   ::= {er1645v2IpV6VrfRtrQMonDestinationsEntry 118947840}

er1645v2IpV6VrfRtrQMonDestinationsDelayAlarmDupsType OBJECT-TYPE
   SYNTAX      INTEGER
               {
               fd (1),
               fdr (2)
               }
   MAX-ACCESS  read-write
   STATUS      current
   DESCRIPTION
      "Path: vrfV6Router.editConf.qualityMonitor.destinations.delayAlarm.delayUpStat.type

       Possibilities:
               fd   (1)
               fdr   (2)"
   ::= {er1645v2IpV6VrfRtrQMonDestinationsEntry 119414784}

er1645v2IpV6VrfRtrQMonDestinationsDelayAlarmDupsBinsN OBJECT-TYPE
   SYNTAX      INTEGER
               {
               none (0)
               }
   MAX-ACCESS  read-write
   STATUS      current
   DESCRIPTION
      "Path: vrfV6Router.editConf.qualityMonitor.destinations.delayAlarm.delayUpStat.bins.none

       Possibilities:
               none   (0)"
   ::= {er1645v2IpV6VrfRtrQMonDestinationsEntry 119424000}

er1645v2IpV6VrfRtrQMonDestinationsDelayAlarmDupsBinsNMn OBJECT-TYPE
   SYNTAX      Integer32
   UNITS       "msec"
   MAX-ACCESS  read-write
   STATUS      current
   DESCRIPTION
      "Path: vrfV6Router.editConf.qualityMonitor.destinations.delayAlarm.delayUpStat.bins.range.min

       unit name = msec"
   ::= {er1645v2IpV6VrfRtrQMonDestinationsEntry 119425152}

er1645v2IpV6VrfRtrQMonDestinationsDelayAlarmDupsBinsNMx OBJECT-TYPE
   SYNTAX      Integer32
   UNITS       "msec"
   MAX-ACCESS  read-write
   STATUS      current
   DESCRIPTION
      "Path: vrfV6Router.editConf.qualityMonitor.destinations.delayAlarm.delayUpStat.bins.range.max

       unit name = msec"
   ::= {er1645v2IpV6VrfRtrQMonDestinationsEntry 119425280}

er1645v2IpV6VrfRtrQMonDestinationsDelayAlarmDupsBinsTB1 OBJECT-TYPE
   SYNTAX      Integer32
   UNITS       "msec"
   MAX-ACCESS  read-write
   STATUS      current
   DESCRIPTION
      "Path: vrfV6Router.editConf.qualityMonitor.destinations.delayAlarm.delayUpStat.bins.table.bin1

       unit name = msec"
   ::= {er1645v2IpV6VrfRtrQMonDestinationsEntry 119426112}

er1645v2IpV6VrfRtrQMonDestinationsDelayAlarmDupsBinsTB2 OBJECT-TYPE
   SYNTAX      Integer32
   UNITS       "msec"
   MAX-ACCESS  read-write
   STATUS      current
   DESCRIPTION
      "Path: vrfV6Router.editConf.qualityMonitor.destinations.delayAlarm.delayUpStat.bins.table.bin2

       unit name = msec"
   ::= {er1645v2IpV6VrfRtrQMonDestinationsEntry 119426176}

er1645v2IpV6VrfRtrQMonDestinationsDelayAlarmDupsBinsTB3 OBJECT-TYPE
   SYNTAX      Integer32
   UNITS       "msec"
   MAX-ACCESS  read-write
   STATUS      current
   DESCRIPTION
      "Path: vrfV6Router.editConf.qualityMonitor.destinations.delayAlarm.delayUpStat.bins.table.bin3

       unit name = msec"
   ::= {er1645v2IpV6VrfRtrQMonDestinationsEntry 119426240}

er1645v2IpV6VrfRtrQMonDestinationsDelayAlarmDupsBinsTB4 OBJECT-TYPE
   SYNTAX      Integer32
   UNITS       "msec"
   MAX-ACCESS  read-write
   STATUS      current
   DESCRIPTION
      "Path: vrfV6Router.editConf.qualityMonitor.destinations.delayAlarm.delayUpStat.bins.table.bin4

       unit name = msec"
   ::= {er1645v2IpV6VrfRtrQMonDestinationsEntry 119426304}

er1645v2IpV6VrfRtrQMonDestinationsDelayAlarmDupsBinsTB5 OBJECT-TYPE
   SYNTAX      Integer32
   UNITS       "msec"
   MAX-ACCESS  read-write
   STATUS      current
   DESCRIPTION
      "Path: vrfV6Router.editConf.qualityMonitor.destinations.delayAlarm.delayUpStat.bins.table.bin5

       unit name = msec"
   ::= {er1645v2IpV6VrfRtrQMonDestinationsEntry 119426368}

er1645v2IpV6VrfRtrQMonDestinationsDelayAlarmDupsBinsTB6 OBJECT-TYPE
   SYNTAX      Integer32
   UNITS       "msec"
   MAX-ACCESS  read-write
   STATUS      current
   DESCRIPTION
      "Path: vrfV6Router.editConf.qualityMonitor.destinations.delayAlarm.delayUpStat.bins.table.bin6

       unit name = msec"
   ::= {er1645v2IpV6VrfRtrQMonDestinationsEntry 119426432}

er1645v2IpV6VrfRtrQMonDestinationsDelayAlarmDupsBinsTB7 OBJECT-TYPE
   SYNTAX      Integer32
   UNITS       "msec"
   MAX-ACCESS  read-write
   STATUS      current
   DESCRIPTION
      "Path: vrfV6Router.editConf.qualityMonitor.destinations.delayAlarm.delayUpStat.bins.table.bin7

       unit name = msec"
   ::= {er1645v2IpV6VrfRtrQMonDestinationsEntry 119426496}

er1645v2IpV6VrfRtrQMonDestinationsDelayAlarmDupsBinsTB8 OBJECT-TYPE
   SYNTAX      Integer32
   UNITS       "msec"
   MAX-ACCESS  read-write
   STATUS      current
   DESCRIPTION
      "Path: vrfV6Router.editConf.qualityMonitor.destinations.delayAlarm.delayUpStat.bins.table.bin8

       unit name = msec"
   ::= {er1645v2IpV6VrfRtrQMonDestinationsEntry 119426560}

er1645v2IpV6VrfRtrQMonDestinationsDelayAlarmDupsBinsTMx OBJECT-TYPE
   SYNTAX      Integer32
   UNITS       "msec"
   MAX-ACCESS  read-write
   STATUS      current
   DESCRIPTION
      "Path: vrfV6Router.editConf.qualityMonitor.destinations.delayAlarm.delayUpStat.bins.table.max

       unit name = msec"
   ::= {er1645v2IpV6VrfRtrQMonDestinationsEntry 119426624}

er1645v2IpV6VrfRtrQMonDestinationsDelayAlarmDelayDownAvrgOn OBJECT-TYPE
   SYNTAX      Integer32
   UNITS       "msec"
   MAX-ACCESS  read-write
   STATUS      current
   DESCRIPTION
      "Path: vrfV6Router.editConf.qualityMonitor.destinations.delayAlarm.delayDownAvrgOn

       unit name = msec"
   ::= {er1645v2IpV6VrfRtrQMonDestinationsEntry 119013376}

er1645v2IpV6VrfRtrQMonDestinationsDelayAlarmDelayDownAvrgOff OBJECT-TYPE
   SYNTAX      Integer32
   UNITS       "msec"
   MAX-ACCESS  read-write
   STATUS      current
   DESCRIPTION
      "Path: vrfV6Router.editConf.qualityMonitor.destinations.delayAlarm.delayDownAvrgOff

       unit name = msec"
   ::= {er1645v2IpV6VrfRtrQMonDestinationsEntry 119078912}

er1645v2IpV6VrfRtrQMonDestinationsDelayAlarmDelayDownMaxOn OBJECT-TYPE
   SYNTAX      Integer32
   UNITS       "msec"
   MAX-ACCESS  read-write
   STATUS      current
   DESCRIPTION
      "Path: vrfV6Router.editConf.qualityMonitor.destinations.delayAlarm.delayDownMaxOn

       unit name = msec"
   ::= {er1645v2IpV6VrfRtrQMonDestinationsEntry 119144448}

er1645v2IpV6VrfRtrQMonDestinationsDelayAlarmDelayDownMaxOff OBJECT-TYPE
   SYNTAX      Integer32
   UNITS       "msec"
   MAX-ACCESS  read-write
   STATUS      current
   DESCRIPTION
      "Path: vrfV6Router.editConf.qualityMonitor.destinations.delayAlarm.delayDownMaxOff

       unit name = msec"
   ::= {er1645v2IpV6VrfRtrQMonDestinationsEntry 119209984}

er1645v2IpV6VrfRtrQMonDestinationsDelayAlarmDdownsType OBJECT-TYPE
   SYNTAX      INTEGER
               {
               fd (1),
               fdr (2)
               }
   MAX-ACCESS  read-write
   STATUS      current
   DESCRIPTION
      "Path: vrfV6Router.editConf.qualityMonitor.destinations.delayAlarm.delayDownStat.type

       Possibilities:
               fd   (1)
               fdr   (2)"
   ::= {er1645v2IpV6VrfRtrQMonDestinationsEntry 119545856}

er1645v2IpV6VrfRtrQMonDestinationsDelayAlarmDdownsBinsN OBJECT-TYPE
   SYNTAX      INTEGER
               {
               none (0)
               }
   MAX-ACCESS  read-write
   STATUS      current
   DESCRIPTION
      "Path: vrfV6Router.editConf.qualityMonitor.destinations.delayAlarm.delayDownStat.bins.none

       Possibilities:
               none   (0)"
   ::= {er1645v2IpV6VrfRtrQMonDestinationsEntry 119555072}

er1645v2IpV6VrfRtrQMonDestinationsDelayAlarmDdownsBinsNMn OBJECT-TYPE
   SYNTAX      Integer32
   UNITS       "msec"
   MAX-ACCESS  read-write
   STATUS      current
   DESCRIPTION
      "Path: vrfV6Router.editConf.qualityMonitor.destinations.delayAlarm.delayDownStat.bins.range.min

       unit name = msec"
   ::= {er1645v2IpV6VrfRtrQMonDestinationsEntry 119556224}

er1645v2IpV6VrfRtrQMonDestinationsDelayAlarmDdownsBinsNMx OBJECT-TYPE
   SYNTAX      Integer32
   UNITS       "msec"
   MAX-ACCESS  read-write
   STATUS      current
   DESCRIPTION
      "Path: vrfV6Router.editConf.qualityMonitor.destinations.delayAlarm.delayDownStat.bins.range.max

       unit name = msec"
   ::= {er1645v2IpV6VrfRtrQMonDestinationsEntry 119556352}

er1645v2IpV6VrfRtrQMonDestinationsDelayAlarmDdownsBinsTB1 OBJECT-TYPE
   SYNTAX      Integer32
   UNITS       "msec"
   MAX-ACCESS  read-write
   STATUS      current
   DESCRIPTION
      "Path: vrfV6Router.editConf.qualityMonitor.destinations.delayAlarm.delayDownStat.bins.table.bin1

       unit name = msec"
   ::= {er1645v2IpV6VrfRtrQMonDestinationsEntry 119557184}

er1645v2IpV6VrfRtrQMonDestinationsDelayAlarmDdownsBinsTB2 OBJECT-TYPE
   SYNTAX      Integer32
   UNITS       "msec"
   MAX-ACCESS  read-write
   STATUS      current
   DESCRIPTION
      "Path: vrfV6Router.editConf.qualityMonitor.destinations.delayAlarm.delayDownStat.bins.table.bin2

       unit name = msec"
   ::= {er1645v2IpV6VrfRtrQMonDestinationsEntry 119557248}

er1645v2IpV6VrfRtrQMonDestinationsDelayAlarmDdownsBinsTB3 OBJECT-TYPE
   SYNTAX      Integer32
   UNITS       "msec"
   MAX-ACCESS  read-write
   STATUS      current
   DESCRIPTION
      "Path: vrfV6Router.editConf.qualityMonitor.destinations.delayAlarm.delayDownStat.bins.table.bin3

       unit name = msec"
   ::= {er1645v2IpV6VrfRtrQMonDestinationsEntry 119557312}

er1645v2IpV6VrfRtrQMonDestinationsDelayAlarmDdownsBinsTB4 OBJECT-TYPE
   SYNTAX      Integer32
   UNITS       "msec"
   MAX-ACCESS  read-write
   STATUS      current
   DESCRIPTION
      "Path: vrfV6Router.editConf.qualityMonitor.destinations.delayAlarm.delayDownStat.bins.table.bin4

       unit name = msec"
   ::= {er1645v2IpV6VrfRtrQMonDestinationsEntry 119557376}

er1645v2IpV6VrfRtrQMonDestinationsDelayAlarmDdownsBinsTB5 OBJECT-TYPE
   SYNTAX      Integer32
   UNITS       "msec"
   MAX-ACCESS  read-write
   STATUS      current
   DESCRIPTION
      "Path: vrfV6Router.editConf.qualityMonitor.destinations.delayAlarm.delayDownStat.bins.table.bin5

       unit name = msec"
   ::= {er1645v2IpV6VrfRtrQMonDestinationsEntry 119557440}

er1645v2IpV6VrfRtrQMonDestinationsDelayAlarmDdownsBinsTB6 OBJECT-TYPE
   SYNTAX      Integer32
   UNITS       "msec"
   MAX-ACCESS  read-write
   STATUS      current
   DESCRIPTION
      "Path: vrfV6Router.editConf.qualityMonitor.destinations.delayAlarm.delayDownStat.bins.table.bin6

       unit name = msec"
   ::= {er1645v2IpV6VrfRtrQMonDestinationsEntry 119557504}

er1645v2IpV6VrfRtrQMonDestinationsDelayAlarmDdownsBinsTB7 OBJECT-TYPE
   SYNTAX      Integer32
   UNITS       "msec"
   MAX-ACCESS  read-write
   STATUS      current
   DESCRIPTION
      "Path: vrfV6Router.editConf.qualityMonitor.destinations.delayAlarm.delayDownStat.bins.table.bin7

       unit name = msec"
   ::= {er1645v2IpV6VrfRtrQMonDestinationsEntry 119557568}

er1645v2IpV6VrfRtrQMonDestinationsDelayAlarmDdownsBinsTB8 OBJECT-TYPE
   SYNTAX      Integer32
   UNITS       "msec"
   MAX-ACCESS  read-write
   STATUS      current
   DESCRIPTION
      "Path: vrfV6Router.editConf.qualityMonitor.destinations.delayAlarm.delayDownStat.bins.table.bin8

       unit name = msec"
   ::= {er1645v2IpV6VrfRtrQMonDestinationsEntry 119557632}

er1645v2IpV6VrfRtrQMonDestinationsDelayAlarmDdownsBinsTMx OBJECT-TYPE
   SYNTAX      Integer32
   UNITS       "msec"
   MAX-ACCESS  read-write
   STATUS      current
   DESCRIPTION
      "Path: vrfV6Router.editConf.qualityMonitor.destinations.delayAlarm.delayDownStat.bins.table.max

       unit name = msec"
   ::= {er1645v2IpV6VrfRtrQMonDestinationsEntry 119557696}

er1645v2IpV6VrfRtrQMonDestinationsAlarmMask OBJECT-TYPE
   SYNTAX      Integer32
   MAX-ACCESS  read-write
   STATUS      current
   DESCRIPTION
      "Path: vrfV6Router.editConf.qualityMonitor.destinations.alarmMask

       Bit meanings:
               bit 0 = loss,
               bit 1 = delayAvrg,
               bit 2 = delayMax,
               bit 3 = delayMinMax,
               bit 4 = jitterAvrg,
               bit 5 = jitterPosMax,
               bit 6 = jitterNegMax,
               bit 7 = lossUp,
               bit 8 = jitterUpAvrg,
               bit 9 = jitterUpPosMax,
               bit 10 = jitterUpNegMax,
               bit 11 = lossDown,
               bit 12 = jitterDownAvrg,
               bit 13 = jitterDownPosMax,
               bit 14 = jitterDownNegMax,
               bit 15 = delayUpAvrg,
               bit 16 = delayUpMax,
               bit 17 = delayDownAvrg,
               bit 18 = delayDownMax,
               bit 19 = bfdCtrl"
   ::= {er1645v2IpV6VrfRtrQMonDestinationsEntry 251658240}

er1645v2IpV6VrfRtrQMonDestinationsLogging OBJECT-TYPE
   SYNTAX      INTEGER
               {
               disabled (0),
               s3min (3),
               s5min (5),
               s10min (10),
               s15min (15),
               s30min (30),
               s60min (60)
               }
   MAX-ACCESS  read-write
   STATUS      current
   DESCRIPTION
      "Path: vrfV6Router.editConf.qualityMonitor.destinations.logging

       Possibilities:
               disabled   (0)
               3min   (3)
               5min   (5)
               10min   (10)
               15min   (15)
               30min   (30)
               60min   (60)"
   ::= {er1645v2IpV6VrfRtrQMonDestinationsEntry 201326592}

er1645v2IpV6VrfRtrQMonDestinationsLoggingDepth OBJECT-TYPE
   SYNTAX      INTEGER
               {
               s4 (4),
               s8 (8),
               s16 (16),
               s32 (32),
               s128 (128),
               s512 (512),
               s1024 (1024)
               }
   MAX-ACCESS  read-write
   STATUS      current
   DESCRIPTION
      "Path: vrfV6Router.editConf.qualityMonitor.destinations.loggingDepth

       Possibilities:
               4   (4)
               8   (8)
               16   (16)
               32   (32)
               128   (128)
               512   (512)
               1024   (1024)"
   ::= {er1645v2IpV6VrfRtrQMonDestinationsEntry 503316480}

er1645v2IpV6VrfRtrQMonUdpServerPort OBJECT-TYPE
   SYNTAX      SEQUENCE OF Er1645v2IpV6VrfRtrQMonUdpServerPortEntry
   MAX-ACCESS  not-accessible
   STATUS      current
   DESCRIPTION
      ""
   ::= {er1645v2IpV6VrfRtrQMon 67108864}

er1645v2IpV6VrfRtrQMonUdpServerPortEntry OBJECT-TYPE
   SYNTAX      Er1645v2IpV6VrfRtrQMonUdpServerPortEntry
   MAX-ACCESS  not-accessible
   STATUS      current
   DESCRIPTION
      ""
   INDEX      { er1645v2IpV6VrfRtrQMonUdpServerPortGlobalIx,
                er1645v2IpV6VrfRtrQMonUdpServerPortTableIx }
   ::= {er1645v2IpV6VrfRtrQMonUdpServerPort 1}

Er1645v2IpV6VrfRtrQMonUdpServerPortEntry ::=
   SEQUENCE
      {
      er1645v2IpV6VrfRtrQMonUdpServerPortActions
         VariableLengthTableActions,
      er1645v2IpV6VrfRtrQMonUdpServerPortGlobalIx
         GlobalIndex,
      er1645v2IpV6VrfRtrQMonUdpServerPortTableIx
         TableIndex,
      er1645v2IpV6VrfRtrQMonUdpServerPortDestinationPort
         Integer32,
      er1645v2IpV6VrfRtrQMonUdpServerPortService
         INTEGER,
      er1645v2IpV6VrfRtrQMonUdpServerPortPriority
         INTEGER,
      er1645v2IpV6VrfRtrQMonUdpServerPortTrafficClass
         INTEGER
      }

er1645v2IpV6VrfRtrQMonUdpServerPortActions OBJECT-TYPE
   SYNTAX      VariableLengthTableActions
   MAX-ACCESS  read-write
   STATUS      current
   DESCRIPTION
      "By way of this field, some manipulations
       on this table may be performed."
   ::= {er1645v2IpV6VrfRtrQMonUdpServerPortEntry 2}

er1645v2IpV6VrfRtrQMonUdpServerPortGlobalIx OBJECT-TYPE
   SYNTAX      GlobalIndex
   MAX-ACCESS  not-accessible
   STATUS      current
   DESCRIPTION
      "The value of the tlsCntTreeGlobalIndex of the MANAGED OBJECT."
   ::= {er1645v2IpV6VrfRtrQMonUdpServerPortEntry 10}

er1645v2IpV6VrfRtrQMonUdpServerPortTableIx OBJECT-TYPE
   SYNTAX      TableIndex
   MAX-ACCESS  not-accessible
   STATUS      current
   DESCRIPTION
      ""
   ::= {er1645v2IpV6VrfRtrQMonUdpServerPortEntry 11}

er1645v2IpV6VrfRtrQMonUdpServerPortDestinationPort OBJECT-TYPE
   SYNTAX      Integer32
   MAX-ACCESS  read-write
   STATUS      current
   DESCRIPTION
      "Path: vrfV6Router.editConf.qualityMonitor.udpServerPort.destinationPort"
   ::= {er1645v2IpV6VrfRtrQMonUdpServerPortEntry 16777216}

er1645v2IpV6VrfRtrQMonUdpServerPortService OBJECT-TYPE
   SYNTAX      INTEGER
               {
               proprietary (1),
               twampLight (2)
               }
   MAX-ACCESS  read-write
   STATUS      current
   DESCRIPTION
      "Path: vrfV6Router.editConf.qualityMonitor.udpServerPort.service

       Possibilities:
               proprietary   (1)
               twampLight   (2)"
   ::= {er1645v2IpV6VrfRtrQMonUdpServerPortEntry 234881024}

er1645v2IpV6VrfRtrQMonUdpServerPortPriority OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: vrfV6Router.editConf.qualityMonitor.udpServerPort.priority

       Possibilities:
               queue1   (0)
               queue2   (1)
               queue3   (2)
               queue4   (3)
               queue5   (4)
               lowDelayQueue   (5)
               lowDelay2Queue   (6)
               systemQueue   (7)"
   ::= {er1645v2IpV6VrfRtrQMonUdpServerPortEntry 218103808}

er1645v2IpV6VrfRtrQMonUdpServerPortTrafficClass OBJECT-TYPE
   SYNTAX      INTEGER
               {
               keepTos (-1),
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: vrfV6Router.editConf.qualityMonitor.udpServerPort.trafficClass

       Possibilities:
               keepTos   (-1)
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2IpV6VrfRtrQMonUdpServerPortEntry 167772160}


er1645v2IpV6VrfRtrAlarmMask OBJECT IDENTIFIER ::= {er1645v2IpV6VrfRtr 135}

er1645v2IpV6VrfRtrAlarmMaskTable OBJECT-TYPE
   SYNTAX      SEQUENCE OF Er1645v2IpV6VrfRtrAlarmMaskEntry
   MAX-ACCESS  not-accessible
   STATUS      current
   DESCRIPTION
      "routAlarmMask"
   ::= {er1645v2IpV6VrfRtrAlarmMask 1}

er1645v2IpV6VrfRtrAlarmMaskEntry OBJECT-TYPE
   SYNTAX      Er1645v2IpV6VrfRtrAlarmMaskEntry
   MAX-ACCESS  not-accessible
   STATUS      current
   DESCRIPTION
      ""
   INDEX      { er1645v2IpV6VrfRtrAlarmMaskGlobalIx }
   ::= {er1645v2IpV6VrfRtrAlarmMaskTable 1}

Er1645v2IpV6VrfRtrAlarmMaskEntry ::=
   SEQUENCE
      {
      er1645v2IpV6VrfRtrAlarmMaskGlobalIx
         GlobalIndex,
      er1645v2IpV6VrfRtrAlarmMaskValue
         Integer32
      }

er1645v2IpV6VrfRtrAlarmMaskGlobalIx OBJECT-TYPE
   SYNTAX      GlobalIndex
   MAX-ACCESS  not-accessible
   STATUS      current
   DESCRIPTION
      "The value of the tlsCntTreeGlobalIndex of the MANAGED OBJECT."
   ::= {er1645v2IpV6VrfRtrAlarmMaskEntry 10}

er1645v2IpV6VrfRtrAlarmMaskValue OBJECT-TYPE
   SYNTAX      Integer32
   MAX-ACCESS  read-write
   STATUS      current
   DESCRIPTION
      "Path: vrfV6Router.editConf.alarmMask

       Bit meanings:
               bit 0 = pingActive,
               bit 1 = qMonLoss,
               bit 2 = qMonDelay,
               bit 3 = qMonJitter"
   ::= {er1645v2IpV6VrfRtrAlarmMaskEntry 2147483648}


er1645v2IpV6VrfRtrAlarmLev OBJECT IDENTIFIER ::= {er1645v2IpV6VrfRtr 170}

er1645v2IpV6VrfRtrAlarmLevSSCTable OBJECT-TYPE
   SYNTAX      SEQUENCE OF Er1645v2IpV6VrfRtrAlarmLevEntry
   MAX-ACCESS  not-accessible
   STATUS      current
   DESCRIPTION
      "routAlarmLevels"
   ::= {er1645v2IpV6VrfRtrAlarmLev 1}

er1645v2IpV6VrfRtrAlarmLevEntry OBJECT-TYPE
   SYNTAX      Er1645v2IpV6VrfRtrAlarmLevEntry
   MAX-ACCESS  not-accessible
   STATUS      current
   DESCRIPTION
      ""
   INDEX      { er1645v2IpV6VrfRtrAlarmLevGlobalIx }
   ::= {er1645v2IpV6VrfRtrAlarmLevSSCTable 1}

Er1645v2IpV6VrfRtrAlarmLevEntry ::=
   SEQUENCE
      {
      er1645v2IpV6VrfRtrAlarmLevGlobalIx
         GlobalIndex,
      er1645v2IpV6VrfRtrAlarmLevPingActive
         Integer32,
      er1645v2IpV6VrfRtrAlarmLevQMonLoss
         Integer32,
      er1645v2IpV6VrfRtrAlarmLevQMonDelay
         Integer32,
      er1645v2IpV6VrfRtrAlarmLevQMonJitter
         Integer32
      }

er1645v2IpV6VrfRtrAlarmLevGlobalIx OBJECT-TYPE
   SYNTAX      GlobalIndex
   MAX-ACCESS  not-accessible
   STATUS      current
   DESCRIPTION
      "The value of the tlsCntTreeGlobalIndex of the MANAGED OBJECT."
   ::= {er1645v2IpV6VrfRtrAlarmLevEntry 10}

er1645v2IpV6VrfRtrAlarmLevPingActive OBJECT-TYPE
   SYNTAX      Integer32
   MAX-ACCESS  read-write
   STATUS      current
   DESCRIPTION
      "Path: vrfV6Router.editConf.alarmLevel.pingActive"
   ::= {er1645v2IpV6VrfRtrAlarmLevEntry 16777216}

er1645v2IpV6VrfRtrAlarmLevQMonLoss OBJECT-TYPE
   SYNTAX      Integer32
   MAX-ACCESS  read-write
   STATUS      current
   DESCRIPTION
      "Path: vrfV6Router.editConf.alarmLevel.qMonLoss"
   ::= {er1645v2IpV6VrfRtrAlarmLevEntry 33554432}

er1645v2IpV6VrfRtrAlarmLevQMonDelay OBJECT-TYPE
   SYNTAX      Integer32
   MAX-ACCESS  read-write
   STATUS      current
   DESCRIPTION
      "Path: vrfV6Router.editConf.alarmLevel.qMonDelay"
   ::= {er1645v2IpV6VrfRtrAlarmLevEntry 50331648}

er1645v2IpV6VrfRtrAlarmLevQMonJitter OBJECT-TYPE
   SYNTAX      Integer32
   MAX-ACCESS  read-write
   STATUS      current
   DESCRIPTION
      "Path: vrfV6Router.editConf.alarmLevel.qMonJitter"
   ::= {er1645v2IpV6VrfRtrAlarmLevEntry 67108864}


er1645v2IpV6VrfRtrSnmpIndexOffset OBJECT IDENTIFIER ::= {er1645v2IpV6VrfRtr 268}

er1645v2IpV6VrfRtrSnmpIndexOffsetTable OBJECT-TYPE
   SYNTAX      SEQUENCE OF Er1645v2IpV6VrfRtrSnmpIndexOffsetEntry
   MAX-ACCESS  not-accessible
   STATUS      current
   DESCRIPTION
      "Preferred offset in the range of SNMP indices for this SWinst, 0 means automatic"
   ::= {er1645v2IpV6VrfRtrSnmpIndexOffset 1}

er1645v2IpV6VrfRtrSnmpIndexOffsetEntry OBJECT-TYPE
   SYNTAX      Er1645v2IpV6VrfRtrSnmpIndexOffsetEntry
   MAX-ACCESS  not-accessible
   STATUS      current
   DESCRIPTION
      ""
   INDEX      { er1645v2IpV6VrfRtrSnmpIndexOffsetGlobalIx }
   ::= {er1645v2IpV6VrfRtrSnmpIndexOffsetTable 1}

Er1645v2IpV6VrfRtrSnmpIndexOffsetEntry ::=
   SEQUENCE
      {
      er1645v2IpV6VrfRtrSnmpIndexOffsetGlobalIx
         GlobalIndex,
      er1645v2IpV6VrfRtrSnmpIndexOffsetValue
         Integer32
      }

er1645v2IpV6VrfRtrSnmpIndexOffsetGlobalIx OBJECT-TYPE
   SYNTAX      GlobalIndex
   MAX-ACCESS  not-accessible
   STATUS      current
   DESCRIPTION
      "The value of the tlsCntTreeGlobalIndex of the MANAGED OBJECT."
   ::= {er1645v2IpV6VrfRtrSnmpIndexOffsetEntry 10}

er1645v2IpV6VrfRtrSnmpIndexOffsetValue OBJECT-TYPE
   SYNTAX      Integer32
   MAX-ACCESS  read-write
   STATUS      current
   DESCRIPTION
      "Path: vrfV6Router.editConf.snmpIndexOffset"
   ::= {er1645v2IpV6VrfRtrSnmpIndexOffsetEntry 2147483648}



sr1645v2IpV6VrfRtr OBJECT IDENTIFIER ::= {r1645v2IpV6VrfRtr 14}


sr1645v2IpV6VrfRtrInterfaces OBJECT IDENTIFIER ::= {sr1645v2IpV6VrfRtr 20}

sr1645v2IpV6VrfRtrInterfacesSSCTable OBJECT-TYPE
   SYNTAX      SEQUENCE OF Sr1645v2IpV6VrfRtrInterfacesEntry
   MAX-ACCESS  not-accessible
   STATUS      current
   DESCRIPTION
      "ipV6 routing interfaces"
   ::= {sr1645v2IpV6VrfRtrInterfaces 1}

sr1645v2IpV6VrfRtrInterfacesEntry OBJECT-TYPE
   SYNTAX      Sr1645v2IpV6VrfRtrInterfacesEntry
   MAX-ACCESS  not-accessible
   STATUS      current
   DESCRIPTION
      ""
   INDEX      { sr1645v2IpV6VrfRtrInterfacesGlobalIx,
                sr1645v2IpV6VrfRtrInterfacesTableIx }
   ::= {sr1645v2IpV6VrfRtrInterfacesSSCTable 1}

Sr1645v2IpV6VrfRtrInterfacesEntry ::=
   SEQUENCE
      {
      sr1645v2IpV6VrfRtrInterfacesGlobalIx
         GlobalIndex,
      sr1645v2IpV6VrfRtrInterfacesTableIx
         TableIndex,
      sr1645v2IpV6VrfRtrInterfacesName
         DisplayString,
      sr1645v2IpV6VrfRtrInterfacesState
         INTEGER,
      sr1645v2IpV6VrfRtrInterfacesInterfaceId
         OCTET STRING,
      sr1645v2IpV6VrfRtrInterfacesLinkMtu
         Integer32,
      sr1645v2IpV6VrfRtrInterfacesHopLimit
         Integer32,
      sr1645v2IpV6VrfRtrInterfacesTimersBaseReachableTime
         TimeTicks,
      sr1645v2IpV6VrfRtrInterfacesTimersReachableTime
         TimeTicks,
      sr1645v2IpV6VrfRtrInterfacesTimersRetransmitTime
         TimeTicks,
      sr1645v2IpV6VrfRtrInterfacesDhcpIaid
         Counter32
      }

sr1645v2IpV6VrfRtrInterfacesGlobalIx OBJECT-TYPE
   SYNTAX      GlobalIndex
   MAX-ACCESS  not-accessible
   STATUS      current
   DESCRIPTION
      "The value of the tlsCntTreeGlobalIndex of the MANAGED OBJECT."
   ::= {sr1645v2IpV6VrfRtrInterfacesEntry 10}

sr1645v2IpV6VrfRtrInterfacesTableIx OBJECT-TYPE
   SYNTAX      TableIndex
   MAX-ACCESS  not-accessible
   STATUS      current
   DESCRIPTION
      ""
   ::= {sr1645v2IpV6VrfRtrInterfacesEntry 11}

sr1645v2IpV6VrfRtrInterfacesName OBJECT-TYPE
   SYNTAX      DisplayString
   MAX-ACCESS  read-only
   STATUS      current
   DESCRIPTION
      "Path: vrfV6Router.status.interfaces.name"
   ::= {sr1645v2IpV6VrfRtrInterfacesEntry 16777216}

sr1645v2IpV6VrfRtrInterfacesState OBJECT-TYPE
   SYNTAX      INTEGER
               {
               disabled (0),
               enabled (1)
               }
   MAX-ACCESS  read-only
   STATUS      current
   DESCRIPTION
      "Path: vrfV6Router.status.interfaces.state

       Possibilities:
               disabled   (0)
               enabled   (1)"
   ::= {sr1645v2IpV6VrfRtrInterfacesEntry 33554432}

sr1645v2IpV6VrfRtrInterfacesInterfaceId OBJECT-TYPE
   SYNTAX      OCTET STRING
   MAX-ACCESS  read-only
   STATUS      current
   DESCRIPTION
      "Path: vrfV6Router.status.interfaces.interfaceId"
   ::= {sr1645v2IpV6VrfRtrInterfacesEntry 50331648}

sr1645v2IpV6VrfRtrInterfacesLinkMtu OBJECT-TYPE
   SYNTAX      Integer32
   MAX-ACCESS  read-only
   STATUS      current
   DESCRIPTION
      "Path: vrfV6Router.status.interfaces.linkMtu"
   ::= {sr1645v2IpV6VrfRtrInterfacesEntry 83886080}

sr1645v2IpV6VrfRtrInterfacesHopLimit OBJECT-TYPE
   SYNTAX      Integer32
   MAX-ACCESS  read-only
   STATUS      current
   DESCRIPTION
      "Path: vrfV6Router.status.interfaces.hopLimit"
   ::= {sr1645v2IpV6VrfRtrInterfacesEntry 100663296}

sr1645v2IpV6VrfRtrInterfacesTimersBaseReachableTime OBJECT-TYPE
   SYNTAX      TimeTicks
   MAX-ACCESS  read-only
   STATUS      current
   DESCRIPTION
      "Path: vrfV6Router.status.interfaces.timers.baseReachableTime

       Time in centi-second."
   ::= {sr1645v2IpV6VrfRtrInterfacesEntry 117506048}

sr1645v2IpV6VrfRtrInterfacesTimersReachableTime OBJECT-TYPE
   SYNTAX      TimeTicks
   MAX-ACCESS  read-only
   STATUS      current
   DESCRIPTION
      "Path: vrfV6Router.status.interfaces.timers.reachableTime

       Time in centi-second."
   ::= {sr1645v2IpV6VrfRtrInterfacesEntry 117571584}

sr1645v2IpV6VrfRtrInterfacesTimersRetransmitTime OBJECT-TYPE
   SYNTAX      TimeTicks
   MAX-ACCESS  read-only
   STATUS      current
   DESCRIPTION
      "Path: vrfV6Router.status.interfaces.timers.retransmitTime

       Time in centi-second."
   ::= {sr1645v2IpV6VrfRtrInterfacesEntry 117637120}

sr1645v2IpV6VrfRtrInterfacesDhcpIaid OBJECT-TYPE
   SYNTAX      Counter32
   MAX-ACCESS  read-only
   STATUS      current
   DESCRIPTION
      "Path: vrfV6Router.status.interfaces.dhcp.iaid

       32 bit unsigned wrappable counter."
   ::= {sr1645v2IpV6VrfRtrInterfacesEntry 134283264}

sr1645v2IpV6VrfRtrInterfacesAddresses OBJECT-TYPE
   SYNTAX      SEQUENCE OF Sr1645v2IpV6VrfRtrInterfacesAddressesEntry
   MAX-ACCESS  not-accessible
   STATUS      current
   DESCRIPTION
      ""
   ::= {sr1645v2IpV6VrfRtrInterfaces 67108864}

sr1645v2IpV6VrfRtrInterfacesAddressesEntry OBJECT-TYPE
   SYNTAX      Sr1645v2IpV6VrfRtrInterfacesAddressesEntry
   MAX-ACCESS  not-accessible
   STATUS      current
   DESCRIPTION
      ""
   INDEX      { sr1645v2IpV6VrfRtrInterfacesAddressesGlobalIx,
                sr1645v2IpV6VrfRtrInterfacesTableIx,
                sr1645v2IpV6VrfRtrInterfacesAddressesTableIx }
   ::= {sr1645v2IpV6VrfRtrInterfacesAddresses 1}

Sr1645v2IpV6VrfRtrInterfacesAddressesEntry ::=
   SEQUENCE
      {
      sr1645v2IpV6VrfRtrInterfacesAddressesGlobalIx
         GlobalIndex,
      sr1645v2IpV6VrfRtrInterfacesAddressesTableIx
         TableIndex,
      sr1645v2IpV6VrfRtrInterfacesAddressesAddress
         Ipv6Address,
      sr1645v2IpV6VrfRtrInterfacesAddressesPrefixLength
         Integer32,
      sr1645v2IpV6VrfRtrInterfacesAddressesStatus
         INTEGER,
      sr1645v2IpV6VrfRtrInterfacesAddressesOrigin
         INTEGER,
      sr1645v2IpV6VrfRtrInterfacesAddressesFlagsInterfaceId
         INTEGER,
      sr1645v2IpV6VrfRtrInterfacesAddressesFlagsAnycast
         INTEGER,
      sr1645v2IpV6VrfRtrInterfacesAddressesTimersValidLifeTime
         TimeTicks,
      sr1645v2IpV6VrfRtrInterfacesAddressesTimersPrefLifeTime
         TimeTicks
      }

sr1645v2IpV6VrfRtrInterfacesAddressesGlobalIx OBJECT-TYPE
   SYNTAX      GlobalIndex
   MAX-ACCESS  not-accessible
   STATUS      current
   DESCRIPTION
      "The value of the tlsCntTreeGlobalIndex of the MANAGED OBJECT."
   ::= {sr1645v2IpV6VrfRtrInterfacesAddressesEntry 10}

sr1645v2IpV6VrfRtrInterfacesAddressesTableIx OBJECT-TYPE
   SYNTAX      TableIndex
   MAX-ACCESS  not-accessible
   STATUS      current
   DESCRIPTION
      ""
   ::= {sr1645v2IpV6VrfRtrInterfacesAddressesEntry 11}

sr1645v2IpV6VrfRtrInterfacesAddressesAddress OBJECT-TYPE
   SYNTAX      Ipv6Address
   MAX-ACCESS  read-only
   STATUS      current
   DESCRIPTION
      "Path: vrfV6Router.status.interfaces.addresses.address

       ipv6 address"
   ::= {sr1645v2IpV6VrfRtrInterfacesAddressesEntry 16777216}

sr1645v2IpV6VrfRtrInterfacesAddressesPrefixLength OBJECT-TYPE
   SYNTAX      Integer32
   MAX-ACCESS  read-only
   STATUS      current
   DESCRIPTION
      "Path: vrfV6Router.status.interfaces.addresses.prefixLength"
   ::= {sr1645v2IpV6VrfRtrInterfacesAddressesEntry 33554432}

sr1645v2IpV6VrfRtrInterfacesAddressesStatus OBJECT-TYPE
   SYNTAX      INTEGER
               {
               invalid (0),
               tentative (1),
               deprecated (2),
               preferred (3)
               }
   MAX-ACCESS  read-only
   STATUS      current
   DESCRIPTION
      "Path: vrfV6Router.status.interfaces.addresses.status

       Possibilities:
               invalid   (0)
               tentative   (1)
               deprecated   (2)
               preferred   (3)"
   ::= {sr1645v2IpV6VrfRtrInterfacesAddressesEntry 50331648}

sr1645v2IpV6VrfRtrInterfacesAddressesOrigin OBJECT-TYPE
   SYNTAX      INTEGER
               {
               unknown (0),
               manual (1),
               generalPrefix (2),
               statelessAuto (3),
               statefullAuto (4)
               }
   MAX-ACCESS  read-only
   STATUS      current
   DESCRIPTION
      "Path: vrfV6Router.status.interfaces.addresses.origin

       Possibilities:
               unknown   (0)
               manual   (1)
               generalPrefix   (2)
               statelessAuto   (3)
               statefullAuto   (4)"
   ::= {sr1645v2IpV6VrfRtrInterfacesAddressesEntry 67108864}

sr1645v2IpV6VrfRtrInterfacesAddressesFlagsInterfaceId OBJECT-TYPE
   SYNTAX      INTEGER
               {
               no (0),
               yes (1)
               }
   MAX-ACCESS  read-only
   STATUS      current
   DESCRIPTION
      "Path: vrfV6Router.status.interfaces.addresses.flags.interfaceId

       Possibilities:
               no   (0)
               yes   (1)"
   ::= {sr1645v2IpV6VrfRtrInterfacesAddressesEntry 83951616}

sr1645v2IpV6VrfRtrInterfacesAddressesFlagsAnycast OBJECT-TYPE
   SYNTAX      INTEGER
               {
               no (0),
               yes (1)
               }
   MAX-ACCESS  read-only
   STATUS      current
   DESCRIPTION
      "Path: vrfV6Router.status.interfaces.addresses.flags.anycast

       Possibilities:
               no   (0)
               yes   (1)"
   ::= {sr1645v2IpV6VrfRtrInterfacesAddressesEntry 84017152}

sr1645v2IpV6VrfRtrInterfacesAddressesTimersValidLifeTime OBJECT-TYPE
   SYNTAX      TimeTicks
   MAX-ACCESS  read-only
   STATUS      current
   DESCRIPTION
      "Path: vrfV6Router.status.interfaces.addresses.timers.validLifeTime

       Time in centi-second."
   ::= {sr1645v2IpV6VrfRtrInterfacesAddressesEntry 100794368}

sr1645v2IpV6VrfRtrInterfacesAddressesTimersPrefLifeTime OBJECT-TYPE
   SYNTAX      TimeTicks
   MAX-ACCESS  read-only
   STATUS      current
   DESCRIPTION
      "Path: vrfV6Router.status.interfaces.addresses.timers.prefLifeTime

       Time in centi-second."
   ::= {sr1645v2IpV6VrfRtrInterfacesAddressesEntry 100728832}


sr1645v2IpV6VrfRtrRoutingTable OBJECT IDENTIFIER ::= {sr1645v2IpV6VrfRtr 21}

sr1645v2IpV6VrfRtrRoutingTableSSCTable OBJECT-TYPE
   SYNTAX      SEQUENCE OF Sr1645v2IpV6VrfRtrRoutingTableEntry
   MAX-ACCESS  not-accessible
   STATUS      current
   DESCRIPTION
      "ipV6 routing table"
   ::= {sr1645v2IpV6VrfRtrRoutingTable 1}

sr1645v2IpV6VrfRtrRoutingTableEntry OBJECT-TYPE
   SYNTAX      Sr1645v2IpV6VrfRtrRoutingTableEntry
   MAX-ACCESS  not-accessible
   STATUS      current
   DESCRIPTION
      ""
   INDEX      { sr1645v2IpV6VrfRtrRoutingTableGlobalIx,
                sr1645v2IpV6VrfRtrRoutingTableTableIx }
   ::= {sr1645v2IpV6VrfRtrRoutingTableSSCTable 1}

Sr1645v2IpV6VrfRtrRoutingTableEntry ::=
   SEQUENCE
      {
      sr1645v2IpV6VrfRtrRoutingTableGlobalIx
         GlobalIndex,
      sr1645v2IpV6VrfRtrRoutingTableTableIx
         TableIndex,
      sr1645v2IpV6VrfRtrRoutingTableAddress
         Ipv6Address,
      sr1645v2IpV6VrfRtrRoutingTablePrefixLength
         Integer32,
      sr1645v2IpV6VrfRtrRoutingTableNextHop
         Ipv6Address,
      sr1645v2IpV6VrfRtrRoutingTableInterface
         DisplayString,
      sr1645v2IpV6VrfRtrRoutingTableStatus
         INTEGER,
      sr1645v2IpV6VrfRtrRoutingTableType
         INTEGER,
      sr1645v2IpV6VrfRtrRoutingTablePreference
         Integer32,
      sr1645v2IpV6VrfRtrRoutingTableMetric
         Integer32,
      sr1645v2IpV6VrfRtrRoutingTableTimeOut
         TimeTicks
      }

sr1645v2IpV6VrfRtrRoutingTableGlobalIx OBJECT-TYPE
   SYNTAX      GlobalIndex
   MAX-ACCESS  not-accessible
   STATUS      current
   DESCRIPTION
      "The value of the tlsCntTreeGlobalIndex of the MANAGED OBJECT."
   ::= {sr1645v2IpV6VrfRtrRoutingTableEntry 10}

sr1645v2IpV6VrfRtrRoutingTableTableIx OBJECT-TYPE
   SYNTAX      TableIndex
   MAX-ACCESS  not-accessible
   STATUS      current
   DESCRIPTION
      ""
   ::= {sr1645v2IpV6VrfRtrRoutingTableEntry 11}

sr1645v2IpV6VrfRtrRoutingTableAddress OBJECT-TYPE
   SYNTAX      Ipv6Address
   MAX-ACCESS  read-only
   STATUS      current
   DESCRIPTION
      "Path: vrfV6Router.status.routingTable.address

       ipv6 address"
   ::= {sr1645v2IpV6VrfRtrRoutingTableEntry 16777216}

sr1645v2IpV6VrfRtrRoutingTablePrefixLength OBJECT-TYPE
   SYNTAX      Integer32
   MAX-ACCESS  read-only
   STATUS      current
   DESCRIPTION
      "Path: vrfV6Router.status.routingTable.prefixLength"
   ::= {sr1645v2IpV6VrfRtrRoutingTableEntry 33554432}

sr1645v2IpV6VrfRtrRoutingTableNextHop OBJECT-TYPE
   SYNTAX      Ipv6Address
   MAX-ACCESS  read-only
   STATUS      current
   DESCRIPTION
      "Path: vrfV6Router.status.routingTable.nextHop

       ipv6 address"
   ::= {sr1645v2IpV6VrfRtrRoutingTableEntry 50331648}

sr1645v2IpV6VrfRtrRoutingTableInterface OBJECT-TYPE
   SYNTAX      DisplayString
   MAX-ACCESS  read-only
   STATUS      current
   DESCRIPTION
      "Path: vrfV6Router.status.routingTable.interface"
   ::= {sr1645v2IpV6VrfRtrRoutingTableEntry 67108864}

sr1645v2IpV6VrfRtrRoutingTableStatus OBJECT-TYPE
   SYNTAX      INTEGER
               {
               down (0),
               up (1),
               discard (3)
               }
   MAX-ACCESS  read-only
   STATUS      current
   DESCRIPTION
      "Path: vrfV6Router.status.routingTable.status

       Possibilities:
               down   (0)
               up   (1)
               discard   (3)"
   ::= {sr1645v2IpV6VrfRtrRoutingTableEntry 83886080}

sr1645v2IpV6VrfRtrRoutingTableType OBJECT-TYPE
   SYNTAX      INTEGER
               {
               fixed (0),
               linkLocal (1),
               host (2),
               anycast (3),
               solicited (4),
               dhcp (5),
               redirect (8),
               advertised (9),
               static (10),
               network (11),
               natpt (12)
               }
   MAX-ACCESS  read-only
   STATUS      current
   DESCRIPTION
      "Path: vrfV6Router.status.routingTable.type

       Possibilities:
               fixed   (0)
               linkLocal   (1)
               host   (2)
               anycast   (3)
               solicited   (4)
               dhcp   (5)
               redirect   (8)
               advertised   (9)
               static   (10)
               network   (11)
               natpt   (12)"
   ::= {sr1645v2IpV6VrfRtrRoutingTableEntry 100663296}

sr1645v2IpV6VrfRtrRoutingTablePreference OBJECT-TYPE
   SYNTAX      Integer32
   MAX-ACCESS  read-only
   STATUS      current
   DESCRIPTION
      "Path: vrfV6Router.status.routingTable.preference"
   ::= {sr1645v2IpV6VrfRtrRoutingTableEntry 117440512}

sr1645v2IpV6VrfRtrRoutingTableMetric OBJECT-TYPE
   SYNTAX      Integer32
   MAX-ACCESS  read-only
   STATUS      current
   DESCRIPTION
      "Path: vrfV6Router.status.routingTable.metric"
   ::= {sr1645v2IpV6VrfRtrRoutingTableEntry 134217728}

sr1645v2IpV6VrfRtrRoutingTableTimeOut OBJECT-TYPE
   SYNTAX      TimeTicks
   MAX-ACCESS  read-only
   STATUS      current
   DESCRIPTION
      "Path: vrfV6Router.status.routingTable.timeOut

       Time in centi-second."
   ::= {sr1645v2IpV6VrfRtrRoutingTableEntry 150994944}


sr1645v2IpV6VrfRtrFragments OBJECT IDENTIFIER ::= {sr1645v2IpV6VrfRtr 22}

sr1645v2IpV6VrfRtrFragmentsSSCTable OBJECT-TYPE
   SYNTAX      SEQUENCE OF Sr1645v2IpV6VrfRtrFragmentsEntry
   MAX-ACCESS  not-accessible
   STATUS      current
   DESCRIPTION
      "ipV6 fragmentation status"
   ::= {sr1645v2IpV6VrfRtrFragments 1}

sr1645v2IpV6VrfRtrFragmentsEntry OBJECT-TYPE
   SYNTAX      Sr1645v2IpV6VrfRtrFragmentsEntry
   MAX-ACCESS  not-accessible
   STATUS      current
   DESCRIPTION
      ""
   INDEX      { sr1645v2IpV6VrfRtrFragmentsGlobalIx }
   ::= {sr1645v2IpV6VrfRtrFragmentsSSCTable 1}

Sr1645v2IpV6VrfRtrFragmentsEntry ::=
   SEQUENCE
      {
      sr1645v2IpV6VrfRtrFragmentsGlobalIx
         GlobalIndex,
      sr1645v2IpV6VrfRtrFragmentsPktsPending
         Counter64,
      sr1645v2IpV6VrfRtrFragmentsFragsPending
         Counter64
      }

sr1645v2IpV6VrfRtrFragmentsGlobalIx OBJECT-TYPE
   SYNTAX      GlobalIndex
   MAX-ACCESS  not-accessible
   STATUS      current
   DESCRIPTION
      "The value of the tlsCntTreeGlobalIndex of the MANAGED OBJECT."
   ::= {sr1645v2IpV6VrfRtrFragmentsEntry 10}

sr1645v2IpV6VrfRtrFragmentsPktsPending OBJECT-TYPE
   SYNTAX      Counter64
   MAX-ACCESS  read-only
   STATUS      current
   DESCRIPTION
      "Path: vrfV6Router.status.fragments.pktsPending

       64 bit unsigned wrappable counter."
   ::= {sr1645v2IpV6VrfRtrFragmentsEntry 16777216}

sr1645v2IpV6VrfRtrFragmentsFragsPending OBJECT-TYPE
   SYNTAX      Counter64
   MAX-ACCESS  read-only
   STATUS      current
   DESCRIPTION
      "Path: vrfV6Router.status.fragments.fragsPending

       64 bit unsigned wrappable counter."
   ::= {sr1645v2IpV6VrfRtrFragmentsEntry 33554432}


sr1645v2IpV6VrfRtrGeneralPrefixes OBJECT IDENTIFIER ::= {sr1645v2IpV6VrfRtr 23}

sr1645v2IpV6VrfRtrGeneralPrefixesSSCTable OBJECT-TYPE
   SYNTAX      SEQUENCE OF Sr1645v2IpV6VrfRtrGeneralPrefixesEntry
   MAX-ACCESS  not-accessible
   STATUS      current
   DESCRIPTION
      "ipV6 prefix pool status"
   ::= {sr1645v2IpV6VrfRtrGeneralPrefixes 1}

sr1645v2IpV6VrfRtrGeneralPrefixesEntry OBJECT-TYPE
   SYNTAX      Sr1645v2IpV6VrfRtrGeneralPrefixesEntry
   MAX-ACCESS  not-accessible
   STATUS      current
   DESCRIPTION
      ""
   INDEX      { sr1645v2IpV6VrfRtrGeneralPrefixesGlobalIx,
                sr1645v2IpV6VrfRtrGeneralPrefixesTableIx }
   ::= {sr1645v2IpV6VrfRtrGeneralPrefixesSSCTable 1}

Sr1645v2IpV6VrfRtrGeneralPrefixesEntry ::=
   SEQUENCE
      {
      sr1645v2IpV6VrfRtrGeneralPrefixesGlobalIx
         GlobalIndex,
      sr1645v2IpV6VrfRtrGeneralPrefixesTableIx
         TableIndex,
      sr1645v2IpV6VrfRtrGeneralPrefixesName
         DisplayString,
      sr1645v2IpV6VrfRtrGeneralPrefixesType
         INTEGER,
      sr1645v2IpV6VrfRtrGeneralPrefixesPrefix
         Ipv6Address,
      sr1645v2IpV6VrfRtrGeneralPrefixesPrefixLength
         Integer32,
      sr1645v2IpV6VrfRtrGeneralPrefixesValidLifeTime
         TimeTicks,
      sr1645v2IpV6VrfRtrGeneralPrefixesPrefLifeTime
         TimeTicks,
      sr1645v2IpV6VrfRtrGeneralPrefixesAvailable
         Counter64,
      sr1645v2IpV6VrfRtrGeneralPrefixesOccupied
         Counter32,
      sr1645v2IpV6VrfRtrGeneralPrefixesAuto6to4Auto6to4Intf
         DisplayString,
      sr1645v2IpV6VrfRtrGeneralPrefixesAuto6to4IpV4Address
         IpAddress,
      sr1645v2IpV6VrfRtrGeneralPrefixesAuto6to4Subnet
         OCTET STRING
      }

sr1645v2IpV6VrfRtrGeneralPrefixesGlobalIx OBJECT-TYPE
   SYNTAX      GlobalIndex
   MAX-ACCESS  not-accessible
   STATUS      current
   DESCRIPTION
      "The value of the tlsCntTreeGlobalIndex of the MANAGED OBJECT."
   ::= {sr1645v2IpV6VrfRtrGeneralPrefixesEntry 10}

sr1645v2IpV6VrfRtrGeneralPrefixesTableIx OBJECT-TYPE
   SYNTAX      TableIndex
   MAX-ACCESS  not-accessible
   STATUS      current
   DESCRIPTION
      ""
   ::= {sr1645v2IpV6VrfRtrGeneralPrefixesEntry 11}

sr1645v2IpV6VrfRtrGeneralPrefixesName OBJECT-TYPE
   SYNTAX      DisplayString
   MAX-ACCESS  read-only
   STATUS      current
   DESCRIPTION
      "Path: vrfV6Router.status.generalPrefixes.name"
   ::= {sr1645v2IpV6VrfRtrGeneralPrefixesEntry 16777216}

sr1645v2IpV6VrfRtrGeneralPrefixesType OBJECT-TYPE
   SYNTAX      INTEGER
               {
               static (0),
               dhcp (1),
               auto6to4 (2)
               }
   MAX-ACCESS  read-only
   STATUS      current
   DESCRIPTION
      "Path: vrfV6Router.status.generalPrefixes.type

       Possibilities:
               static   (0)
               dhcp   (1)
               auto6to4   (2)"
   ::= {sr1645v2IpV6VrfRtrGeneralPrefixesEntry 33554432}

sr1645v2IpV6VrfRtrGeneralPrefixesPrefix OBJECT-TYPE
   SYNTAX      Ipv6Address
   MAX-ACCESS  read-only
   STATUS      current
   DESCRIPTION
      "Path: vrfV6Router.status.generalPrefixes.prefix

       ipv6 address"
   ::= {sr1645v2IpV6VrfRtrGeneralPrefixesEntry 50331648}

sr1645v2IpV6VrfRtrGeneralPrefixesPrefixLength OBJECT-TYPE
   SYNTAX      Integer32
   MAX-ACCESS  read-only
   STATUS      current
   DESCRIPTION
      "Path: vrfV6Router.status.generalPrefixes.prefixLength"
   ::= {sr1645v2IpV6VrfRtrGeneralPrefixesEntry 67108864}

sr1645v2IpV6VrfRtrGeneralPrefixesValidLifeTime OBJECT-TYPE
   SYNTAX      TimeTicks
   MAX-ACCESS  read-only
   STATUS      current
   DESCRIPTION
      "Path: vrfV6Router.status.generalPrefixes.validLifeTime

       Time in centi-second."
   ::= {sr1645v2IpV6VrfRtrGeneralPrefixesEntry 83886080}

sr1645v2IpV6VrfRtrGeneralPrefixesPrefLifeTime OBJECT-TYPE
   SYNTAX      TimeTicks
   MAX-ACCESS  read-only
   STATUS      current
   DESCRIPTION
      "Path: vrfV6Router.status.generalPrefixes.prefLifeTime

       Time in centi-second."
   ::= {sr1645v2IpV6VrfRtrGeneralPrefixesEntry 100663296}

sr1645v2IpV6VrfRtrGeneralPrefixesAvailable OBJECT-TYPE
   SYNTAX      Counter64
   MAX-ACCESS  read-only
   STATUS      current
   DESCRIPTION
      "Path: vrfV6Router.status.generalPrefixes.available

       64 bit unsigned wrappable counter."
   ::= {sr1645v2IpV6VrfRtrGeneralPrefixesEntry 117440512}

sr1645v2IpV6VrfRtrGeneralPrefixesOccupied OBJECT-TYPE
   SYNTAX      Counter32
   MAX-ACCESS  read-only
   STATUS      current
   DESCRIPTION
      "Path: vrfV6Router.status.generalPrefixes.occupied

       32 bit unsigned wrappable counter."
   ::= {sr1645v2IpV6VrfRtrGeneralPrefixesEntry 134217728}

sr1645v2IpV6VrfRtrGeneralPrefixesAuto6to4Auto6to4Intf OBJECT-TYPE
   SYNTAX      DisplayString
   MAX-ACCESS  read-only
   STATUS      current
   DESCRIPTION
      "Path: vrfV6Router.status.generalPrefixes.auto6to4.auto6to4Intf"
   ::= {sr1645v2IpV6VrfRtrGeneralPrefixesEntry 151191552}

sr1645v2IpV6VrfRtrGeneralPrefixesAuto6to4IpV4Address OBJECT-TYPE
   SYNTAX      IpAddress
   MAX-ACCESS  read-only
   STATUS      current
   DESCRIPTION
      "Path: vrfV6Router.status.generalPrefixes.auto6to4.ipV4Address"
   ::= {sr1645v2IpV6VrfRtrGeneralPrefixesEntry 151060480}

sr1645v2IpV6VrfRtrGeneralPrefixesAuto6to4Subnet OBJECT-TYPE
   SYNTAX      OCTET STRING
   MAX-ACCESS  read-only
   STATUS      current
   DESCRIPTION
      "Path: vrfV6Router.status.generalPrefixes.auto6to4.subnet"
   ::= {sr1645v2IpV6VrfRtrGeneralPrefixesEntry 151126016}


sr1645v2IpV6VrfRtrPrefixBindings OBJECT IDENTIFIER ::= {sr1645v2IpV6VrfRtr 24}

sr1645v2IpV6VrfRtrPrefixBindingsSSCTable OBJECT-TYPE
   SYNTAX      SEQUENCE OF Sr1645v2IpV6VrfRtrPrefixBindingsEntry
   MAX-ACCESS  not-accessible
   STATUS      current
   DESCRIPTION
      "ipV6 prefix pool binding overview"
   ::= {sr1645v2IpV6VrfRtrPrefixBindings 1}

sr1645v2IpV6VrfRtrPrefixBindingsEntry OBJECT-TYPE
   SYNTAX      Sr1645v2IpV6VrfRtrPrefixBindingsEntry
   MAX-ACCESS  not-accessible
   STATUS      current
   DESCRIPTION
      ""
   INDEX      { sr1645v2IpV6VrfRtrPrefixBindingsGlobalIx,
                sr1645v2IpV6VrfRtrPrefixBindingsTableIx }
   ::= {sr1645v2IpV6VrfRtrPrefixBindingsSSCTable 1}

Sr1645v2IpV6VrfRtrPrefixBindingsEntry ::=
   SEQUENCE
      {
      sr1645v2IpV6VrfRtrPrefixBindingsGlobalIx
         GlobalIndex,
      sr1645v2IpV6VrfRtrPrefixBindingsTableIx
         TableIndex,
      sr1645v2IpV6VrfRtrPrefixBindingsPool
         DisplayString,
      sr1645v2IpV6VrfRtrPrefixBindingsInterface
         DisplayString,
      sr1645v2IpV6VrfRtrPrefixBindingsPrefix
         Ipv6Address,
      sr1645v2IpV6VrfRtrPrefixBindingsPrefixLength
         Integer32
      }

sr1645v2IpV6VrfRtrPrefixBindingsGlobalIx OBJECT-TYPE
   SYNTAX      GlobalIndex
   MAX-ACCESS  not-accessible
   STATUS      current
   DESCRIPTION
      "The value of the tlsCntTreeGlobalIndex of the MANAGED OBJECT."
   ::= {sr1645v2IpV6VrfRtrPrefixBindingsEntry 10}

sr1645v2IpV6VrfRtrPrefixBindingsTableIx OBJECT-TYPE
   SYNTAX      TableIndex
   MAX-ACCESS  not-accessible
   STATUS      current
   DESCRIPTION
      ""
   ::= {sr1645v2IpV6VrfRtrPrefixBindingsEntry 11}

sr1645v2IpV6VrfRtrPrefixBindingsPool OBJECT-TYPE
   SYNTAX      DisplayString
   MAX-ACCESS  read-only
   STATUS      current
   DESCRIPTION
      "Path: vrfV6Router.status.prefixBindings.pool"
   ::= {sr1645v2IpV6VrfRtrPrefixBindingsEntry 16777216}

sr1645v2IpV6VrfRtrPrefixBindingsInterface OBJECT-TYPE
   SYNTAX      DisplayString
   MAX-ACCESS  read-only
   STATUS      current
   DESCRIPTION
      "Path: vrfV6Router.status.prefixBindings.interface"
   ::= {sr1645v2IpV6VrfRtrPrefixBindingsEntry 33554432}

sr1645v2IpV6VrfRtrPrefixBindingsPrefix OBJECT-TYPE
   SYNTAX      Ipv6Address
   MAX-ACCESS  read-only
   STATUS      current
   DESCRIPTION
      "Path: vrfV6Router.status.prefixBindings.prefix

       ipv6 address"
   ::= {sr1645v2IpV6VrfRtrPrefixBindingsEntry 50331648}

sr1645v2IpV6VrfRtrPrefixBindingsPrefixLength OBJECT-TYPE
   SYNTAX      Integer32
   MAX-ACCESS  read-only
   STATUS      current
   DESCRIPTION
      "Path: vrfV6Router.status.prefixBindings.prefixLength"
   ::= {sr1645v2IpV6VrfRtrPrefixBindingsEntry 67108864}


sr1645v2IpV6VrfRtrMessages OBJECT IDENTIFIER ::= {sr1645v2IpV6VrfRtr 25}

sr1645v2IpV6VrfRtrMessagesSSCTable OBJECT-TYPE
   SYNTAX      SEQUENCE OF Sr1645v2IpV6VrfRtrMessagesEntry
   MAX-ACCESS  not-accessible
   STATUS      current
   DESCRIPTION
      "log or tracing messages"
   ::= {sr1645v2IpV6VrfRtrMessages 1}

sr1645v2IpV6VrfRtrMessagesEntry OBJECT-TYPE
   SYNTAX      Sr1645v2IpV6VrfRtrMessagesEntry
   MAX-ACCESS  not-accessible
   STATUS      current
   DESCRIPTION
      ""
   INDEX      { sr1645v2IpV6VrfRtrMessagesGlobalIx,
                sr1645v2IpV6VrfRtrMessagesTableIx }
   ::= {sr1645v2IpV6VrfRtrMessagesSSCTable 1}

Sr1645v2IpV6VrfRtrMessagesEntry ::=
   SEQUENCE
      {
      sr1645v2IpV6VrfRtrMessagesGlobalIx
         GlobalIndex,
      sr1645v2IpV6VrfRtrMessagesTableIx
         TableIndex,
      sr1645v2IpV6VrfRtrMessagesMessage
         DisplayString
      }

sr1645v2IpV6VrfRtrMessagesGlobalIx OBJECT-TYPE
   SYNTAX      GlobalIndex
   MAX-ACCESS  not-accessible
   STATUS      current
   DESCRIPTION
      "The value of the tlsCntTreeGlobalIndex of the MANAGED OBJECT."
   ::= {sr1645v2IpV6VrfRtrMessagesEntry 10}

sr1645v2IpV6VrfRtrMessagesTableIx OBJECT-TYPE
   SYNTAX      TableIndex
   MAX-ACCESS  not-accessible
   STATUS      current
   DESCRIPTION
      ""
   ::= {sr1645v2IpV6VrfRtrMessagesEntry 11}

sr1645v2IpV6VrfRtrMessagesMessage OBJECT-TYPE
   SYNTAX      DisplayString
   MAX-ACCESS  read-only
   STATUS      current
   DESCRIPTION
      "Path: vrfV6Router.status.messages.message"
   ::= {sr1645v2IpV6VrfRtrMessagesEntry 16777216}


sr1645v2IpV6VrfRtrDnsCache OBJECT IDENTIFIER ::= {sr1645v2IpV6VrfRtr 26}

sr1645v2IpV6VrfRtrDnsCacheSSCTable OBJECT-TYPE
   SYNTAX      SEQUENCE OF Sr1645v2IpV6VrfRtrDnsCacheEntry
   MAX-ACCESS  not-accessible
   STATUS      current
   DESCRIPTION
      "DNS cache table"
   ::= {sr1645v2IpV6VrfRtrDnsCache 1}

sr1645v2IpV6VrfRtrDnsCacheEntry OBJECT-TYPE
   SYNTAX      Sr1645v2IpV6VrfRtrDnsCacheEntry
   MAX-ACCESS  not-accessible
   STATUS      current
   DESCRIPTION
      ""
   INDEX      { sr1645v2IpV6VrfRtrDnsCacheGlobalIx,
                sr1645v2IpV6VrfRtrDnsCacheTableIx }
   ::= {sr1645v2IpV6VrfRtrDnsCacheSSCTable 1}

Sr1645v2IpV6VrfRtrDnsCacheEntry ::=
   SEQUENCE
      {
      sr1645v2IpV6VrfRtrDnsCacheGlobalIx
         GlobalIndex,
      sr1645v2IpV6VrfRtrDnsCacheTableIx
         TableIndex,
      sr1645v2IpV6VrfRtrDnsCacheIpAddress
         IpAddress,
      sr1645v2IpV6VrfRtrDnsCacheIpV6Address
         Ipv6Address,
      sr1645v2IpV6VrfRtrDnsCacheHostname
         DisplayString,
      sr1645v2IpV6VrfRtrDnsCacheTtl
         TimeTicks,
      sr1645v2IpV6VrfRtrDnsCacheInfiniteTimeOut
         INTEGER,
      sr1645v2IpV6VrfRtrDnsCacheMatches
         Counter32
      }

sr1645v2IpV6VrfRtrDnsCacheGlobalIx OBJECT-TYPE
   SYNTAX      GlobalIndex
   MAX-ACCESS  not-accessible
   STATUS      current
   DESCRIPTION
      "The value of the tlsCntTreeGlobalIndex of the MANAGED OBJECT."
   ::= {sr1645v2IpV6VrfRtrDnsCacheEntry 10}

sr1645v2IpV6VrfRtrDnsCacheTableIx OBJECT-TYPE
   SYNTAX      TableIndex
   MAX-ACCESS  not-accessible
   STATUS      current
   DESCRIPTION
      ""
   ::= {sr1645v2IpV6VrfRtrDnsCacheEntry 11}

sr1645v2IpV6VrfRtrDnsCacheIpAddress OBJECT-TYPE
   SYNTAX      IpAddress
   MAX-ACCESS  read-only
   STATUS      current
   DESCRIPTION
      "Path: vrfV6Router.status.dnsCache.ipAddress"
   ::= {sr1645v2IpV6VrfRtrDnsCacheEntry 16777216}

sr1645v2IpV6VrfRtrDnsCacheIpV6Address OBJECT-TYPE
   SYNTAX      Ipv6Address
   MAX-ACCESS  read-only
   STATUS      current
   DESCRIPTION
      "Path: vrfV6Router.status.dnsCache.ipV6Address

       ipv6 address"
   ::= {sr1645v2IpV6VrfRtrDnsCacheEntry 83886080}

sr1645v2IpV6VrfRtrDnsCacheHostname OBJECT-TYPE
   SYNTAX      DisplayString
   MAX-ACCESS  read-only
   STATUS      current
   DESCRIPTION
      "Path: vrfV6Router.status.dnsCache.hostname"
   ::= {sr1645v2IpV6VrfRtrDnsCacheEntry 33554432}

sr1645v2IpV6VrfRtrDnsCacheTtl OBJECT-TYPE
   SYNTAX      TimeTicks
   MAX-ACCESS  read-only
   STATUS      current
   DESCRIPTION
      "Path: vrfV6Router.status.dnsCache.ttl

       Time in centi-second."
   ::= {sr1645v2IpV6VrfRtrDnsCacheEntry 50331648}

sr1645v2IpV6VrfRtrDnsCacheInfiniteTimeOut OBJECT-TYPE
   SYNTAX      INTEGER
               {
               disabled (0),
               enabled (1),
               static (2)
               }
   MAX-ACCESS  read-only
   STATUS      current
   DESCRIPTION
      "Path: vrfV6Router.status.dnsCache.infiniteTimeOut

       Possibilities:
               disabled   (0)
               enabled   (1)
               static   (2)"
   ::= {sr1645v2IpV6VrfRtrDnsCacheEntry 67108864}

sr1645v2IpV6VrfRtrDnsCacheMatches OBJECT-TYPE
   SYNTAX      Counter32
   MAX-ACCESS  read-only
   STATUS      current
   DESCRIPTION
      "Path: vrfV6Router.status.dnsCache.matches

       32 bit unsigned wrappable counter."
   ::= {sr1645v2IpV6VrfRtrDnsCacheEntry 100663296}


sr1645v2IpV6VrfRtrDnsServers OBJECT IDENTIFIER ::= {sr1645v2IpV6VrfRtr 27}

sr1645v2IpV6VrfRtrDnsServersSSCTable OBJECT-TYPE
   SYNTAX      SEQUENCE OF Sr1645v2IpV6VrfRtrDnsServersEntry
   MAX-ACCESS  not-accessible
   STATUS      current
   DESCRIPTION
      "DNS server list"
   ::= {sr1645v2IpV6VrfRtrDnsServers 1}

sr1645v2IpV6VrfRtrDnsServersEntry OBJECT-TYPE
   SYNTAX      Sr1645v2IpV6VrfRtrDnsServersEntry
   MAX-ACCESS  not-accessible
   STATUS      current
   DESCRIPTION
      ""
   INDEX      { sr1645v2IpV6VrfRtrDnsServersGlobalIx,
                sr1645v2IpV6VrfRtrDnsServersTableIx }
   ::= {sr1645v2IpV6VrfRtrDnsServersSSCTable 1}

Sr1645v2IpV6VrfRtrDnsServersEntry ::=
   SEQUENCE
      {
      sr1645v2IpV6VrfRtrDnsServersGlobalIx
         GlobalIndex,
      sr1645v2IpV6VrfRtrDnsServersTableIx
         TableIndex,
      sr1645v2IpV6VrfRtrDnsServersIpAddress
         Ipv6Address,
      sr1645v2IpV6VrfRtrDnsServersType
         INTEGER,
      sr1645v2IpV6VrfRtrDnsServersRcvdInterface
         DisplayString,
      sr1645v2IpV6VrfRtrDnsServersPreference
         Integer32,
      sr1645v2IpV6VrfRtrDnsServersStatus
         INTEGER,
      sr1645v2IpV6VrfRtrDnsServersLifeTimer
         TimeTicks
      }

sr1645v2IpV6VrfRtrDnsServersGlobalIx OBJECT-TYPE
   SYNTAX      GlobalIndex
   MAX-ACCESS  not-accessible
   STATUS      current
   DESCRIPTION
      "The value of the tlsCntTreeGlobalIndex of the MANAGED OBJECT."
   ::= {sr1645v2IpV6VrfRtrDnsServersEntry 10}

sr1645v2IpV6VrfRtrDnsServersTableIx OBJECT-TYPE
   SYNTAX      TableIndex
   MAX-ACCESS  not-accessible
   STATUS      current
   DESCRIPTION
      ""
   ::= {sr1645v2IpV6VrfRtrDnsServersEntry 11}

sr1645v2IpV6VrfRtrDnsServersIpAddress OBJECT-TYPE
   SYNTAX      Ipv6Address
   MAX-ACCESS  read-only
   STATUS      current
   DESCRIPTION
      "Path: vrfV6Router.status.dnsServers.ipAddress

       ipv6 address"
   ::= {sr1645v2IpV6VrfRtrDnsServersEntry 16777216}

sr1645v2IpV6VrfRtrDnsServersType OBJECT-TYPE
   SYNTAX      INTEGER
               {
               static (0),
               dhcp (1),
               ra (3)
               }
   MAX-ACCESS  read-only
   STATUS      current
   DESCRIPTION
      "Path: vrfV6Router.status.dnsServers.type

       Possibilities:
               static   (0)
               dhcp   (1)
               ra   (3)"
   ::= {sr1645v2IpV6VrfRtrDnsServersEntry 33554432}

sr1645v2IpV6VrfRtrDnsServersRcvdInterface OBJECT-TYPE
   SYNTAX      DisplayString
   MAX-ACCESS  read-only
   STATUS      current
   DESCRIPTION
      "Path: vrfV6Router.status.dnsServers.rcvdInterface"
   ::= {sr1645v2IpV6VrfRtrDnsServersEntry 50331648}

sr1645v2IpV6VrfRtrDnsServersPreference OBJECT-TYPE
   SYNTAX      Integer32
   MAX-ACCESS  read-only
   STATUS      current
   DESCRIPTION
      "Path: vrfV6Router.status.dnsServers.preference"
   ::= {sr1645v2IpV6VrfRtrDnsServersEntry 67108864}

sr1645v2IpV6VrfRtrDnsServersStatus OBJECT-TYPE
   SYNTAX      INTEGER
               {
               unreachable (0),
               reachable (1),
               primary (2),
               secondary (3)
               }
   MAX-ACCESS  read-only
   STATUS      current
   DESCRIPTION
      "Path: vrfV6Router.status.dnsServers.status

       Possibilities:
               unreachable   (0)
               reachable   (1)
               primary   (2)
               secondary   (3)"
   ::= {sr1645v2IpV6VrfRtrDnsServersEntry 83886080}

sr1645v2IpV6VrfRtrDnsServersLifeTimer OBJECT-TYPE
   SYNTAX      TimeTicks
   MAX-ACCESS  read-only
   STATUS      current
   DESCRIPTION
      "Path: vrfV6Router.status.dnsServers.lifeTimer

       Time in centi-second."
   ::= {sr1645v2IpV6VrfRtrDnsServersEntry 100663296}


sr1645v2IpV6VrfRtrDnsDomains OBJECT IDENTIFIER ::= {sr1645v2IpV6VrfRtr 28}

sr1645v2IpV6VrfRtrDnsDomainsSSCTable OBJECT-TYPE
   SYNTAX      SEQUENCE OF Sr1645v2IpV6VrfRtrDnsDomainsEntry
   MAX-ACCESS  not-accessible
   STATUS      current
   DESCRIPTION
      "DNS domain list"
   ::= {sr1645v2IpV6VrfRtrDnsDomains 1}

sr1645v2IpV6VrfRtrDnsDomainsEntry OBJECT-TYPE
   SYNTAX      Sr1645v2IpV6VrfRtrDnsDomainsEntry
   MAX-ACCESS  not-accessible
   STATUS      current
   DESCRIPTION
      ""
   INDEX      { sr1645v2IpV6VrfRtrDnsDomainsGlobalIx,
                sr1645v2IpV6VrfRtrDnsDomainsTableIx }
   ::= {sr1645v2IpV6VrfRtrDnsDomainsSSCTable 1}

Sr1645v2IpV6VrfRtrDnsDomainsEntry ::=
   SEQUENCE
      {
      sr1645v2IpV6VrfRtrDnsDomainsGlobalIx
         GlobalIndex,
      sr1645v2IpV6VrfRtrDnsDomainsTableIx
         TableIndex,
      sr1645v2IpV6VrfRtrDnsDomainsName
         DisplayString,
      sr1645v2IpV6VrfRtrDnsDomainsType
         INTEGER,
      sr1645v2IpV6VrfRtrDnsDomainsRcvdInterface
         DisplayString,
      sr1645v2IpV6VrfRtrDnsDomainsLifeTimer
         TimeTicks
      }

sr1645v2IpV6VrfRtrDnsDomainsGlobalIx OBJECT-TYPE
   SYNTAX      GlobalIndex
   MAX-ACCESS  not-accessible
   STATUS      current
   DESCRIPTION
      "The value of the tlsCntTreeGlobalIndex of the MANAGED OBJECT."
   ::= {sr1645v2IpV6VrfRtrDnsDomainsEntry 10}

sr1645v2IpV6VrfRtrDnsDomainsTableIx OBJECT-TYPE
   SYNTAX      TableIndex
   MAX-ACCESS  not-accessible
   STATUS      current
   DESCRIPTION
      ""
   ::= {sr1645v2IpV6VrfRtrDnsDomainsEntry 11}

sr1645v2IpV6VrfRtrDnsDomainsName OBJECT-TYPE
   SYNTAX      DisplayString
   MAX-ACCESS  read-only
   STATUS      current
   DESCRIPTION
      "Path: vrfV6Router.status.dnsDomains.name"
   ::= {sr1645v2IpV6VrfRtrDnsDomainsEntry 16777216}

sr1645v2IpV6VrfRtrDnsDomainsType OBJECT-TYPE
   SYNTAX      INTEGER
               {
               static (0),
               dhcp (1),
               ra (3)
               }
   MAX-ACCESS  read-only
   STATUS      current
   DESCRIPTION
      "Path: vrfV6Router.status.dnsDomains.type

       Possibilities:
               static   (0)
               dhcp   (1)
               ra   (3)"
   ::= {sr1645v2IpV6VrfRtrDnsDomainsEntry 33554432}

sr1645v2IpV6VrfRtrDnsDomainsRcvdInterface OBJECT-TYPE
   SYNTAX      DisplayString
   MAX-ACCESS  read-only
   STATUS      current
   DESCRIPTION
      "Path: vrfV6Router.status.dnsDomains.rcvdInterface"
   ::= {sr1645v2IpV6VrfRtrDnsDomainsEntry 50331648}

sr1645v2IpV6VrfRtrDnsDomainsLifeTimer OBJECT-TYPE
   SYNTAX      TimeTicks
   MAX-ACCESS  read-only
   STATUS      current
   DESCRIPTION
      "Path: vrfV6Router.status.dnsDomains.lifeTimer

       Time in centi-second."
   ::= {sr1645v2IpV6VrfRtrDnsDomainsEntry 67108864}


sr1645v2IpV6VrfRtrSnmpIndex OBJECT IDENTIFIER ::= {sr1645v2IpV6VrfRtr 269}

sr1645v2IpV6VrfRtrSnmpIndexTable OBJECT-TYPE
   SYNTAX      SEQUENCE OF Sr1645v2IpV6VrfRtrSnmpIndexEntry
   MAX-ACCESS  not-accessible
   STATUS      current
   DESCRIPTION
      "SNMP index assigned to this object"
   ::= {sr1645v2IpV6VrfRtrSnmpIndex 1}

sr1645v2IpV6VrfRtrSnmpIndexEntry OBJECT-TYPE
   SYNTAX      Sr1645v2IpV6VrfRtrSnmpIndexEntry
   MAX-ACCESS  not-accessible
   STATUS      current
   DESCRIPTION
      ""
   INDEX      { sr1645v2IpV6VrfRtrSnmpIndexGlobalIx }
   ::= {sr1645v2IpV6VrfRtrSnmpIndexTable 1}

Sr1645v2IpV6VrfRtrSnmpIndexEntry ::=
   SEQUENCE
      {
      sr1645v2IpV6VrfRtrSnmpIndexGlobalIx
         GlobalIndex,
      sr1645v2IpV6VrfRtrSnmpIndexValue
         Integer32
      }

sr1645v2IpV6VrfRtrSnmpIndexGlobalIx OBJECT-TYPE
   SYNTAX      GlobalIndex
   MAX-ACCESS  not-accessible
   STATUS      current
   DESCRIPTION
      "The value of the tlsCntTreeGlobalIndex of the MANAGED OBJECT."
   ::= {sr1645v2IpV6VrfRtrSnmpIndexEntry 10}

sr1645v2IpV6VrfRtrSnmpIndexValue OBJECT-TYPE
   SYNTAX      Integer32
   MAX-ACCESS  read-only
   STATUS      current
   DESCRIPTION
      "Path: vrfV6Router.status.snmpIndex"
   ::= {sr1645v2IpV6VrfRtrSnmpIndexEntry 2147483648}



pr1645v2IpV6VrfRtr OBJECT IDENTIFIER ::= {r1645v2IpV6VrfRtr 12}


pr1645v2IpV6VrfRtrInterfaces OBJECT IDENTIFIER ::= {pr1645v2IpV6VrfRtr 40}

pr1645v2IpV6VrfRtrInterfacesSSCTable OBJECT-TYPE
   SYNTAX      SEQUENCE OF Pr1645v2IpV6VrfRtrInterfacesEntry
   MAX-ACCESS  not-accessible
   STATUS      current
   DESCRIPTION
      "ipV6 routing interface performance"
   ::= {pr1645v2IpV6VrfRtrInterfaces 1}

pr1645v2IpV6VrfRtrInterfacesEntry OBJECT-TYPE
   SYNTAX      Pr1645v2IpV6VrfRtrInterfacesEntry
   MAX-ACCESS  not-accessible
   STATUS      current
   DESCRIPTION
      ""
   INDEX      { pr1645v2IpV6VrfRtrInterfacesGlobalIx,
                pr1645v2IpV6VrfRtrInterfacesTableIx }
   ::= {pr1645v2IpV6VrfRtrInterfacesSSCTable 1}

Pr1645v2IpV6VrfRtrInterfacesEntry ::=
   SEQUENCE
      {
      pr1645v2IpV6VrfRtrInterfacesGlobalIx
         GlobalIndex,
      pr1645v2IpV6VrfRtrInterfacesTableIx
         TableIndex,
      pr1645v2IpV6VrfRtrInterfacesName
         DisplayString,
      pr1645v2IpV6VrfRtrInterfacesInterfaceId
         OCTET STRING,
      pr1645v2IpV6VrfRtrInterfacesSentRa
         Counter32,
      pr1645v2IpV6VrfRtrInterfacesSentRs
         Counter32,
      pr1645v2IpV6VrfRtrInterfacesSentNa
         Counter32,
      pr1645v2IpV6VrfRtrInterfacesSentNs
         Counter32,
      pr1645v2IpV6VrfRtrInterfacesSentRedirs
         Counter32,
      pr1645v2IpV6VrfRtrInterfacesRcvdRa
         Counter32,
      pr1645v2IpV6VrfRtrInterfacesRcvdRs
         Counter32,
      pr1645v2IpV6VrfRtrInterfacesRcvdNa
         Counter32,
      pr1645v2IpV6VrfRtrInterfacesRcvdNs
         Counter32,
      pr1645v2IpV6VrfRtrInterfacesRcvdRedirs
         Counter32
      }

pr1645v2IpV6VrfRtrInterfacesGlobalIx OBJECT-TYPE
   SYNTAX      GlobalIndex
   MAX-ACCESS  not-accessible
   STATUS      current
   DESCRIPTION
      "The value of the tlsCntTreeGlobalIndex of the MANAGED OBJECT."
   ::= {pr1645v2IpV6VrfRtrInterfacesEntry 10}

pr1645v2IpV6VrfRtrInterfacesTableIx OBJECT-TYPE
   SYNTAX      TableIndex
   MAX-ACCESS  not-accessible
   STATUS      current
   DESCRIPTION
      ""
   ::= {pr1645v2IpV6VrfRtrInterfacesEntry 11}

pr1645v2IpV6VrfRtrInterfacesName OBJECT-TYPE
   SYNTAX      DisplayString
   MAX-ACCESS  read-only
   STATUS      current
   DESCRIPTION
      "Path: vrfV6Router.performance.interfaces.name"
   ::= {pr1645v2IpV6VrfRtrInterfacesEntry 16777216}

pr1645v2IpV6VrfRtrInterfacesInterfaceId OBJECT-TYPE
   SYNTAX      OCTET STRING
   MAX-ACCESS  read-only
   STATUS      current
   DESCRIPTION
      "Path: vrfV6Router.performance.interfaces.interfaceId"
   ::= {pr1645v2IpV6VrfRtrInterfacesEntry 33554432}

pr1645v2IpV6VrfRtrInterfacesSentRa OBJECT-TYPE
   SYNTAX      Counter32
   MAX-ACCESS  read-only
   STATUS      current
   DESCRIPTION
      "Path: vrfV6Router.performance.interfaces.sent.ra

       32 bit unsigned wrappable counter."
   ::= {pr1645v2IpV6VrfRtrInterfacesEntry 50397184}

pr1645v2IpV6VrfRtrInterfacesSentRs OBJECT-TYPE
   SYNTAX      Counter32
   MAX-ACCESS  read-only
   STATUS      current
   DESCRIPTION
      "Path: vrfV6Router.performance.interfaces.sent.rs

       32 bit unsigned wrappable counter."
   ::= {pr1645v2IpV6VrfRtrInterfacesEntry 50462720}

pr1645v2IpV6VrfRtrInterfacesSentNa OBJECT-TYPE
   SYNTAX      Counter32
   MAX-ACCESS  read-only
   STATUS      current
   DESCRIPTION
      "Path: vrfV6Router.performance.interfaces.sent.na

       32 bit unsigned wrappable counter."
   ::= {pr1645v2IpV6VrfRtrInterfacesEntry 50528256}

pr1645v2IpV6VrfRtrInterfacesSentNs OBJECT-TYPE
   SYNTAX      Counter32
   MAX-ACCESS  read-only
   STATUS      current
   DESCRIPTION
      "Path: vrfV6Router.performance.interfaces.sent.ns

       32 bit unsigned wrappable counter."
   ::= {pr1645v2IpV6VrfRtrInterfacesEntry 50593792}

pr1645v2IpV6VrfRtrInterfacesSentRedirs OBJECT-TYPE
   SYNTAX      Counter32
   MAX-ACCESS  read-only
   STATUS      current
   DESCRIPTION
      "Path: vrfV6Router.performance.interfaces.sent.redirs

       32 bit unsigned wrappable counter."
   ::= {pr1645v2IpV6VrfRtrInterfacesEntry 50659328}

pr1645v2IpV6VrfRtrInterfacesRcvdRa OBJECT-TYPE
   SYNTAX      Counter32
   MAX-ACCESS  read-only
   STATUS      current
   DESCRIPTION
      "Path: vrfV6Router.performance.interfaces.rcvd.ra

       32 bit unsigned wrappable counter."
   ::= {pr1645v2IpV6VrfRtrInterfacesEntry 67174400}

pr1645v2IpV6VrfRtrInterfacesRcvdRs OBJECT-TYPE
   SYNTAX      Counter32
   MAX-ACCESS  read-only
   STATUS      current
   DESCRIPTION
      "Path: vrfV6Router.performance.interfaces.rcvd.rs

       32 bit unsigned wrappable counter."
   ::= {pr1645v2IpV6VrfRtrInterfacesEntry 67239936}

pr1645v2IpV6VrfRtrInterfacesRcvdNa OBJECT-TYPE
   SYNTAX      Counter32
   MAX-ACCESS  read-only
   STATUS      current
   DESCRIPTION
      "Path: vrfV6Router.performance.interfaces.rcvd.na

       32 bit unsigned wrappable counter."
   ::= {pr1645v2IpV6VrfRtrInterfacesEntry 67305472}

pr1645v2IpV6VrfRtrInterfacesRcvdNs OBJECT-TYPE
   SYNTAX      Counter32
   MAX-ACCESS  read-only
   STATUS      current
   DESCRIPTION
      "Path: vrfV6Router.performance.interfaces.rcvd.ns

       32 bit unsigned wrappable counter."
   ::= {pr1645v2IpV6VrfRtrInterfacesEntry 67371008}

pr1645v2IpV6VrfRtrInterfacesRcvdRedirs OBJECT-TYPE
   SYNTAX      Counter32
   MAX-ACCESS  read-only
   STATUS      current
   DESCRIPTION
      "Path: vrfV6Router.performance.interfaces.rcvd.redirs

       32 bit unsigned wrappable counter."
   ::= {pr1645v2IpV6VrfRtrInterfacesEntry 67436544}


pr1645v2IpV6VrfRtrRoutingTable OBJECT IDENTIFIER ::= {pr1645v2IpV6VrfRtr 41}

pr1645v2IpV6VrfRtrRoutingTableSSCTable OBJECT-TYPE
   SYNTAX      SEQUENCE OF Pr1645v2IpV6VrfRtrRoutingTableEntry
   MAX-ACCESS  not-accessible
   STATUS      current
   DESCRIPTION
      "ipV6 routing table performance"
   ::= {pr1645v2IpV6VrfRtrRoutingTable 1}

pr1645v2IpV6VrfRtrRoutingTableEntry OBJECT-TYPE
   SYNTAX      Pr1645v2IpV6VrfRtrRoutingTableEntry
   MAX-ACCESS  not-accessible
   STATUS      current
   DESCRIPTION
      ""
   INDEX      { pr1645v2IpV6VrfRtrRoutingTableGlobalIx,
                pr1645v2IpV6VrfRtrRoutingTableTableIx }
   ::= {pr1645v2IpV6VrfRtrRoutingTableSSCTable 1}

Pr1645v2IpV6VrfRtrRoutingTableEntry ::=
   SEQUENCE
      {
      pr1645v2IpV6VrfRtrRoutingTableGlobalIx
         GlobalIndex,
      pr1645v2IpV6VrfRtrRoutingTableTableIx
         TableIndex,
      pr1645v2IpV6VrfRtrRoutingTableAddress
         Ipv6Address,
      pr1645v2IpV6VrfRtrRoutingTablePrefixLength
         Integer32,
      pr1645v2IpV6VrfRtrRoutingTableNextHop
         Ipv6Address,
      pr1645v2IpV6VrfRtrRoutingTableInterface
         DisplayString,
      pr1645v2IpV6VrfRtrRoutingTableType
         INTEGER,
      pr1645v2IpV6VrfRtrRoutingTableUses
         Counter32,
      pr1645v2IpV6VrfRtrRoutingTableOctets
         Counter32
      }

pr1645v2IpV6VrfRtrRoutingTableGlobalIx OBJECT-TYPE
   SYNTAX      GlobalIndex
   MAX-ACCESS  not-accessible
   STATUS      current
   DESCRIPTION
      "The value of the tlsCntTreeGlobalIndex of the MANAGED OBJECT."
   ::= {pr1645v2IpV6VrfRtrRoutingTableEntry 10}

pr1645v2IpV6VrfRtrRoutingTableTableIx OBJECT-TYPE
   SYNTAX      TableIndex
   MAX-ACCESS  not-accessible
   STATUS      current
   DESCRIPTION
      ""
   ::= {pr1645v2IpV6VrfRtrRoutingTableEntry 11}

pr1645v2IpV6VrfRtrRoutingTableAddress OBJECT-TYPE
   SYNTAX      Ipv6Address
   MAX-ACCESS  read-only
   STATUS      current
   DESCRIPTION
      "Path: vrfV6Router.performance.routingTable.address

       ipv6 address"
   ::= {pr1645v2IpV6VrfRtrRoutingTableEntry 16777216}

pr1645v2IpV6VrfRtrRoutingTablePrefixLength OBJECT-TYPE
   SYNTAX      Integer32
   MAX-ACCESS  read-only
   STATUS      current
   DESCRIPTION
      "Path: vrfV6Router.performance.routingTable.prefixLength"
   ::= {pr1645v2IpV6VrfRtrRoutingTableEntry 33554432}

pr1645v2IpV6VrfRtrRoutingTableNextHop OBJECT-TYPE
   SYNTAX      Ipv6Address
   MAX-ACCESS  read-only
   STATUS      current
   DESCRIPTION
      "Path: vrfV6Router.performance.routingTable.nextHop

       ipv6 address"
   ::= {pr1645v2IpV6VrfRtrRoutingTableEntry 50331648}

pr1645v2IpV6VrfRtrRoutingTableInterface OBJECT-TYPE
   SYNTAX      DisplayString
   MAX-ACCESS  read-only
   STATUS      current
   DESCRIPTION
      "Path: vrfV6Router.performance.routingTable.interface"
   ::= {pr1645v2IpV6VrfRtrRoutingTableEntry 67108864}

pr1645v2IpV6VrfRtrRoutingTableType OBJECT-TYPE
   SYNTAX      INTEGER
               {
               fixed (0),
               linkLocal (1),
               host (2),
               anycast (3),
               solicited (4),
               dhcp (5),
               redirect (8),
               advertised (9),
               static (10),
               network (11),
               natpt (12)
               }
   MAX-ACCESS  read-only
   STATUS      current
   DESCRIPTION
      "Path: vrfV6Router.performance.routingTable.type

       Possibilities:
               fixed   (0)
               linkLocal   (1)
               host   (2)
               anycast   (3)
               solicited   (4)
               dhcp   (5)
               redirect   (8)
               advertised   (9)
               static   (10)
               network   (11)
               natpt   (12)"
   ::= {pr1645v2IpV6VrfRtrRoutingTableEntry 83886080}

pr1645v2IpV6VrfRtrRoutingTableUses OBJECT-TYPE
   SYNTAX      Counter32
   MAX-ACCESS  read-only
   STATUS      current
   DESCRIPTION
      "Path: vrfV6Router.performance.routingTable.uses

       32 bit unsigned wrappable counter."
   ::= {pr1645v2IpV6VrfRtrRoutingTableEntry 100663296}

pr1645v2IpV6VrfRtrRoutingTableOctets OBJECT-TYPE
   SYNTAX      Counter32
   MAX-ACCESS  read-only
   STATUS      current
   DESCRIPTION
      "Path: vrfV6Router.performance.routingTable.octets

       32 bit unsigned wrappable counter."
   ::= {pr1645v2IpV6VrfRtrRoutingTableEntry 117440512}


pr1645v2IpV6VrfRtrRouter OBJECT IDENTIFIER ::= {pr1645v2IpV6VrfRtr 42}

pr1645v2IpV6VrfRtrRouterSSCTable OBJECT-TYPE
   SYNTAX      SEQUENCE OF Pr1645v2IpV6VrfRtrRouterEntry
   MAX-ACCESS  not-accessible
   STATUS      current
   DESCRIPTION
      "ipV6 basic router counters"
   ::= {pr1645v2IpV6VrfRtrRouter 1}

pr1645v2IpV6VrfRtrRouterEntry OBJECT-TYPE
   SYNTAX      Pr1645v2IpV6VrfRtrRouterEntry
   MAX-ACCESS  not-accessible
   STATUS      current
   DESCRIPTION
      ""
   INDEX      { pr1645v2IpV6VrfRtrRouterGlobalIx }
   ::= {pr1645v2IpV6VrfRtrRouterSSCTable 1}

Pr1645v2IpV6VrfRtrRouterEntry ::=
   SEQUENCE
      {
      pr1645v2IpV6VrfRtrRouterGlobalIx
         GlobalIndex,
      pr1645v2IpV6VrfRtrRouterInPkts
         Counter64,
      pr1645v2IpV6VrfRtrRouterFwdPkts
         Counter64,
      pr1645v2IpV6VrfRtrRouterRouteCacheHits
         Counter64,
      pr1645v2IpV6VrfRtrRouterRouteCacheMisses
         Counter64
      }

pr1645v2IpV6VrfRtrRouterGlobalIx OBJECT-TYPE
   SYNTAX      GlobalIndex
   MAX-ACCESS  not-accessible
   STATUS      current
   DESCRIPTION
      "The value of the tlsCntTreeGlobalIndex of the MANAGED OBJECT."
   ::= {pr1645v2IpV6VrfRtrRouterEntry 10}

pr1645v2IpV6VrfRtrRouterInPkts OBJECT-TYPE
   SYNTAX      Counter64
   MAX-ACCESS  read-only
   STATUS      current
   DESCRIPTION
      "Path: vrfV6Router.performance.router.inPkts

       64 bit unsigned wrappable counter."
   ::= {pr1645v2IpV6VrfRtrRouterEntry 16777216}

pr1645v2IpV6VrfRtrRouterFwdPkts OBJECT-TYPE
   SYNTAX      Counter64
   MAX-ACCESS  read-only
   STATUS      current
   DESCRIPTION
      "Path: vrfV6Router.performance.router.fwdPkts

       64 bit unsigned wrappable counter."
   ::= {pr1645v2IpV6VrfRtrRouterEntry 33554432}

pr1645v2IpV6VrfRtrRouterRouteCacheHits OBJECT-TYPE
   SYNTAX      Counter64
   MAX-ACCESS  read-only
   STATUS      current
   DESCRIPTION
      "Path: vrfV6Router.performance.router.routeCacheHits

       64 bit unsigned wrappable counter."
   ::= {pr1645v2IpV6VrfRtrRouterEntry 50331648}

pr1645v2IpV6VrfRtrRouterRouteCacheMisses OBJECT-TYPE
   SYNTAX      Counter64
   MAX-ACCESS  read-only
   STATUS      current
   DESCRIPTION
      "Path: vrfV6Router.performance.router.routeCacheMisses

       64 bit unsigned wrappable counter."
   ::= {pr1645v2IpV6VrfRtrRouterEntry 67108864}


pr1645v2IpV6VrfRtrErrors OBJECT IDENTIFIER ::= {pr1645v2IpV6VrfRtr 43}

pr1645v2IpV6VrfRtrErrorsSSCTable OBJECT-TYPE
   SYNTAX      SEQUENCE OF Pr1645v2IpV6VrfRtrErrorsEntry
   MAX-ACCESS  not-accessible
   STATUS      current
   DESCRIPTION
      "ipV6 router errors"
   ::= {pr1645v2IpV6VrfRtrErrors 1}

pr1645v2IpV6VrfRtrErrorsEntry OBJECT-TYPE
   SYNTAX      Pr1645v2IpV6VrfRtrErrorsEntry
   MAX-ACCESS  not-accessible
   STATUS      current
   DESCRIPTION
      ""
   INDEX      { pr1645v2IpV6VrfRtrErrorsGlobalIx }
   ::= {pr1645v2IpV6VrfRtrErrorsSSCTable 1}

Pr1645v2IpV6VrfRtrErrorsEntry ::=
   SEQUENCE
      {
      pr1645v2IpV6VrfRtrErrorsGlobalIx
         GlobalIndex,
      pr1645v2IpV6VrfRtrErrorsPktLength
         Counter64,
      pr1645v2IpV6VrfRtrErrorsHdrLength
         Counter64,
      pr1645v2IpV6VrfRtrErrorsBadVersion
         Counter64,
      pr1645v2IpV6VrfRtrErrorsBadOption
         Counter64,
      pr1645v2IpV6VrfRtrErrorsChecksum
         Counter64,
      pr1645v2IpV6VrfRtrErrorsBadScope
         Counter64,
      pr1645v2IpV6VrfRtrErrorsNotJoined
         Counter64,
      pr1645v2IpV6VrfRtrErrorsMulticastSrc
         Counter64,
      pr1645v2IpV6VrfRtrErrorsCantForward
         Counter64,
      pr1645v2IpV6VrfRtrErrorsTooBig
         Counter64
      }

pr1645v2IpV6VrfRtrErrorsGlobalIx OBJECT-TYPE
   SYNTAX      GlobalIndex
   MAX-ACCESS  not-accessible
   STATUS      current
   DESCRIPTION
      "The value of the tlsCntTreeGlobalIndex of the MANAGED OBJECT."
   ::= {pr1645v2IpV6VrfRtrErrorsEntry 10}

pr1645v2IpV6VrfRtrErrorsPktLength OBJECT-TYPE
   SYNTAX      Counter64
   MAX-ACCESS  read-only
   STATUS      current
   DESCRIPTION
      "Path: vrfV6Router.performance.errors.pktLength

       64 bit unsigned wrappable counter."
   ::= {pr1645v2IpV6VrfRtrErrorsEntry 16777216}

pr1645v2IpV6VrfRtrErrorsHdrLength OBJECT-TYPE
   SYNTAX      Counter64
   MAX-ACCESS  read-only
   STATUS      current
   DESCRIPTION
      "Path: vrfV6Router.performance.errors.hdrLength

       64 bit unsigned wrappable counter."
   ::= {pr1645v2IpV6VrfRtrErrorsEntry 33554432}

pr1645v2IpV6VrfRtrErrorsBadVersion OBJECT-TYPE
   SYNTAX      Counter64
   MAX-ACCESS  read-only
   STATUS      current
   DESCRIPTION
      "Path: vrfV6Router.performance.errors.badVersion

       64 bit unsigned wrappable counter."
   ::= {pr1645v2IpV6VrfRtrErrorsEntry 50331648}

pr1645v2IpV6VrfRtrErrorsBadOption OBJECT-TYPE
   SYNTAX      Counter64
   MAX-ACCESS  read-only
   STATUS      current
   DESCRIPTION
      "Path: vrfV6Router.performance.errors.badOption

       64 bit unsigned wrappable counter."
   ::= {pr1645v2IpV6VrfRtrErrorsEntry 67108864}

pr1645v2IpV6VrfRtrErrorsChecksum OBJECT-TYPE
   SYNTAX      Counter64
   MAX-ACCESS  read-only
   STATUS      current
   DESCRIPTION
      "Path: vrfV6Router.performance.errors.checksum

       64 bit unsigned wrappable counter."
   ::= {pr1645v2IpV6VrfRtrErrorsEntry 83886080}

pr1645v2IpV6VrfRtrErrorsBadScope OBJECT-TYPE
   SYNTAX      Counter64
   MAX-ACCESS  read-only
   STATUS      current
   DESCRIPTION
      "Path: vrfV6Router.performance.errors.badScope

       64 bit unsigned wrappable counter."
   ::= {pr1645v2IpV6VrfRtrErrorsEntry 100663296}

pr1645v2IpV6VrfRtrErrorsNotJoined OBJECT-TYPE
   SYNTAX      Counter64
   MAX-ACCESS  read-only
   STATUS      current
   DESCRIPTION
      "Path: vrfV6Router.performance.errors.notJoined

       64 bit unsigned wrappable counter."
   ::= {pr1645v2IpV6VrfRtrErrorsEntry 117440512}

pr1645v2IpV6VrfRtrErrorsMulticastSrc OBJECT-TYPE
   SYNTAX      Counter64
   MAX-ACCESS  read-only
   STATUS      current
   DESCRIPTION
      "Path: vrfV6Router.performance.errors.multicastSrc

       64 bit unsigned wrappable counter."
   ::= {pr1645v2IpV6VrfRtrErrorsEntry 134217728}

pr1645v2IpV6VrfRtrErrorsCantForward OBJECT-TYPE
   SYNTAX      Counter64
   MAX-ACCESS  read-only
   STATUS      current
   DESCRIPTION
      "Path: vrfV6Router.performance.errors.cantForward

       64 bit unsigned wrappable counter."
   ::= {pr1645v2IpV6VrfRtrErrorsEntry 150994944}

pr1645v2IpV6VrfRtrErrorsTooBig OBJECT-TYPE
   SYNTAX      Counter64
   MAX-ACCESS  read-only
   STATUS      current
   DESCRIPTION
      "Path: vrfV6Router.performance.errors.tooBig

       64 bit unsigned wrappable counter."
   ::= {pr1645v2IpV6VrfRtrErrorsEntry 167772160}


pr1645v2IpV6VrfRtrFragments OBJECT IDENTIFIER ::= {pr1645v2IpV6VrfRtr 44}

pr1645v2IpV6VrfRtrFragmentsSSCTable OBJECT-TYPE
   SYNTAX      SEQUENCE OF Pr1645v2IpV6VrfRtrFragmentsEntry
   MAX-ACCESS  not-accessible
   STATUS      current
   DESCRIPTION
      "ipV6 fragmentation counters"
   ::= {pr1645v2IpV6VrfRtrFragments 1}

pr1645v2IpV6VrfRtrFragmentsEntry OBJECT-TYPE
   SYNTAX      Pr1645v2IpV6VrfRtrFragmentsEntry
   MAX-ACCESS  not-accessible
   STATUS      current
   DESCRIPTION
      ""
   INDEX      { pr1645v2IpV6VrfRtrFragmentsGlobalIx }
   ::= {pr1645v2IpV6VrfRtrFragmentsSSCTable 1}

Pr1645v2IpV6VrfRtrFragmentsEntry ::=
   SEQUENCE
      {
      pr1645v2IpV6VrfRtrFragmentsGlobalIx
         GlobalIndex,
      pr1645v2IpV6VrfRtrFragmentsPktsFragmented
         Counter64,
      pr1645v2IpV6VrfRtrFragmentsFragsSent
         Counter64,
      pr1645v2IpV6VrfRtrFragmentsFragFailed
         Counter64,
      pr1645v2IpV6VrfRtrFragmentsFragsRcvd
         Counter64,
      pr1645v2IpV6VrfRtrFragmentsPktsReassembled
         Counter64,
      pr1645v2IpV6VrfRtrFragmentsFragsDropped
         Counter64,
      pr1645v2IpV6VrfRtrFragmentsFragsTimedOut
         Counter64,
      pr1645v2IpV6VrfRtrFragmentsFragsOverflow
         Counter64
      }

pr1645v2IpV6VrfRtrFragmentsGlobalIx OBJECT-TYPE
   SYNTAX      GlobalIndex
   MAX-ACCESS  not-accessible
   STATUS      current
   DESCRIPTION
      "The value of the tlsCntTreeGlobalIndex of the MANAGED OBJECT."
   ::= {pr1645v2IpV6VrfRtrFragmentsEntry 10}

pr1645v2IpV6VrfRtrFragmentsPktsFragmented OBJECT-TYPE
   SYNTAX      Counter64
   MAX-ACCESS  read-only
   STATUS      current
   DESCRIPTION
      "Path: vrfV6Router.performance.fragments.pktsFragmented

       64 bit unsigned wrappable counter."
   ::= {pr1645v2IpV6VrfRtrFragmentsEntry 16777216}

pr1645v2IpV6VrfRtrFragmentsFragsSent OBJECT-TYPE
   SYNTAX      Counter64
   MAX-ACCESS  read-only
   STATUS      current
   DESCRIPTION
      "Path: vrfV6Router.performance.fragments.fragsSent

       64 bit unsigned wrappable counter."
   ::= {pr1645v2IpV6VrfRtrFragmentsEntry 33554432}

pr1645v2IpV6VrfRtrFragmentsFragFailed OBJECT-TYPE
   SYNTAX      Counter64
   MAX-ACCESS  read-only
   STATUS      current
   DESCRIPTION
      "Path: vrfV6Router.performance.fragments.fragFailed

       64 bit unsigned wrappable counter."
   ::= {pr1645v2IpV6VrfRtrFragmentsEntry 50331648}

pr1645v2IpV6VrfRtrFragmentsFragsRcvd OBJECT-TYPE
   SYNTAX      Counter64
   MAX-ACCESS  read-only
   STATUS      current
   DESCRIPTION
      "Path: vrfV6Router.performance.fragments.fragsRcvd

       64 bit unsigned wrappable counter."
   ::= {pr1645v2IpV6VrfRtrFragmentsEntry 67108864}

pr1645v2IpV6VrfRtrFragmentsPktsReassembled OBJECT-TYPE
   SYNTAX      Counter64
   MAX-ACCESS  read-only
   STATUS      current
   DESCRIPTION
      "Path: vrfV6Router.performance.fragments.pktsReassembled

       64 bit unsigned wrappable counter."
   ::= {pr1645v2IpV6VrfRtrFragmentsEntry 83886080}

pr1645v2IpV6VrfRtrFragmentsFragsDropped OBJECT-TYPE
   SYNTAX      Counter64
   MAX-ACCESS  read-only
   STATUS      current
   DESCRIPTION
      "Path: vrfV6Router.performance.fragments.fragsDropped

       64 bit unsigned wrappable counter."
   ::= {pr1645v2IpV6VrfRtrFragmentsEntry 100663296}

pr1645v2IpV6VrfRtrFragmentsFragsTimedOut OBJECT-TYPE
   SYNTAX      Counter64
   MAX-ACCESS  read-only
   STATUS      current
   DESCRIPTION
      "Path: vrfV6Router.performance.fragments.fragsTimedOut

       64 bit unsigned wrappable counter."
   ::= {pr1645v2IpV6VrfRtrFragmentsEntry 117440512}

pr1645v2IpV6VrfRtrFragmentsFragsOverflow OBJECT-TYPE
   SYNTAX      Counter64
   MAX-ACCESS  read-only
   STATUS      current
   DESCRIPTION
      "Path: vrfV6Router.performance.fragments.fragsOverflow

       64 bit unsigned wrappable counter."
   ::= {pr1645v2IpV6VrfRtrFragmentsEntry 134217728}


pr1645v2IpV6VrfRtrDns OBJECT IDENTIFIER ::= {pr1645v2IpV6VrfRtr 45}

pr1645v2IpV6VrfRtrDnsSSCTable OBJECT-TYPE
   SYNTAX      SEQUENCE OF Pr1645v2IpV6VrfRtrDnsEntry
   MAX-ACCESS  not-accessible
   STATUS      current
   DESCRIPTION
      "counter of dns module"
   ::= {pr1645v2IpV6VrfRtrDns 1}

pr1645v2IpV6VrfRtrDnsEntry OBJECT-TYPE
   SYNTAX      Pr1645v2IpV6VrfRtrDnsEntry
   MAX-ACCESS  not-accessible
   STATUS      current
   DESCRIPTION
      ""
   INDEX      { pr1645v2IpV6VrfRtrDnsGlobalIx }
   ::= {pr1645v2IpV6VrfRtrDnsSSCTable 1}

Pr1645v2IpV6VrfRtrDnsEntry ::=
   SEQUENCE
      {
      pr1645v2IpV6VrfRtrDnsGlobalIx
         GlobalIndex,
      pr1645v2IpV6VrfRtrDnsRequests
         Counter32,
      pr1645v2IpV6VrfRtrDnsInternalRequests
         Counter32,
      pr1645v2IpV6VrfRtrDnsExternalRequests
         Counter32,
      pr1645v2IpV6VrfRtrDnsForwardedRequests
         Counter32,
      pr1645v2IpV6VrfRtrDnsFailedRequests
         Counter32,
      pr1645v2IpV6VrfRtrDnsFreeCache
         Gauge32
      }

pr1645v2IpV6VrfRtrDnsGlobalIx OBJECT-TYPE
   SYNTAX      GlobalIndex
   MAX-ACCESS  not-accessible
   STATUS      current
   DESCRIPTION
      "The value of the tlsCntTreeGlobalIndex of the MANAGED OBJECT."
   ::= {pr1645v2IpV6VrfRtrDnsEntry 10}

pr1645v2IpV6VrfRtrDnsRequests OBJECT-TYPE
   SYNTAX      Counter32
   MAX-ACCESS  read-only
   STATUS      current
   DESCRIPTION
      "Path: vrfV6Router.performance.dns.requests

       32 bit unsigned wrappable counter."
   ::= {pr1645v2IpV6VrfRtrDnsEntry 16777216}

pr1645v2IpV6VrfRtrDnsInternalRequests OBJECT-TYPE
   SYNTAX      Counter32
   MAX-ACCESS  read-only
   STATUS      current
   DESCRIPTION
      "Path: vrfV6Router.performance.dns.internalRequests

       32 bit unsigned wrappable counter."
   ::= {pr1645v2IpV6VrfRtrDnsEntry 33554432}

pr1645v2IpV6VrfRtrDnsExternalRequests OBJECT-TYPE
   SYNTAX      Counter32
   MAX-ACCESS  read-only
   STATUS      current
   DESCRIPTION
      "Path: vrfV6Router.performance.dns.externalRequests

       32 bit unsigned wrappable counter."
   ::= {pr1645v2IpV6VrfRtrDnsEntry 50331648}

pr1645v2IpV6VrfRtrDnsForwardedRequests OBJECT-TYPE
   SYNTAX      Counter32
   MAX-ACCESS  read-only
   STATUS      current
   DESCRIPTION
      "Path: vrfV6Router.performance.dns.forwardedRequests

       32 bit unsigned wrappable counter."
   ::= {pr1645v2IpV6VrfRtrDnsEntry 67108864}

pr1645v2IpV6VrfRtrDnsFailedRequests OBJECT-TYPE
   SYNTAX      Counter32
   MAX-ACCESS  read-only
   STATUS      current
   DESCRIPTION
      "Path: vrfV6Router.performance.dns.failedRequests

       32 bit unsigned wrappable counter."
   ::= {pr1645v2IpV6VrfRtrDnsEntry 83886080}

pr1645v2IpV6VrfRtrDnsFreeCache OBJECT-TYPE
   SYNTAX      Gauge32
   MAX-ACCESS  read-only
   STATUS      current
   DESCRIPTION
      "Path: vrfV6Router.performance.dns.freeCache

       32 bit unsigned gauge value."
   ::= {pr1645v2IpV6VrfRtrDnsEntry 117440512}


pr1645v2IpV6VrfRtrH2Perf OBJECT IDENTIFIER ::= {pr1645v2IpV6VrfRtr 50}

pr1645v2IpV6VrfRtrH2PerfSSCTable OBJECT-TYPE
   SYNTAX      SEQUENCE OF Pr1645v2IpV6VrfRtrH2PerfEntry
   MAX-ACCESS  not-accessible
   STATUS      current
   DESCRIPTION
      "2 hour dns stats"
   ::= {pr1645v2IpV6VrfRtrH2Perf 1}

pr1645v2IpV6VrfRtrH2PerfEntry OBJECT-TYPE
   SYNTAX      Pr1645v2IpV6VrfRtrH2PerfEntry
   MAX-ACCESS  not-accessible
   STATUS      current
   DESCRIPTION
      ""
   INDEX      { pr1645v2IpV6VrfRtrH2PerfGlobalIx,
                pr1645v2IpV6VrfRtrH2PerfTableIx }
   ::= {pr1645v2IpV6VrfRtrH2PerfSSCTable 1}

Pr1645v2IpV6VrfRtrH2PerfEntry ::=
   SEQUENCE
      {
      pr1645v2IpV6VrfRtrH2PerfGlobalIx
         GlobalIndex,
      pr1645v2IpV6VrfRtrH2PerfTableIx
         TableIndex,
      pr1645v2IpV6VrfRtrH2PerfSysUpTime
         TimeTicks,
      pr1645v2IpV6VrfRtrH2PerfRequests
         Counter32,
      pr1645v2IpV6VrfRtrH2PerfInternalRequests
         Counter32,
      pr1645v2IpV6VrfRtrH2PerfExternalRequests
         Counter32,
      pr1645v2IpV6VrfRtrH2PerfForwardedRequests
         Counter32,
      pr1645v2IpV6VrfRtrH2PerfFailedRequests
         Counter32,
      pr1645v2IpV6VrfRtrH2PerfFreeCacheMin
         Gauge32,
      pr1645v2IpV6VrfRtrH2PerfFreeCacheAvrg
         Gauge32,
      pr1645v2IpV6VrfRtrH2PerfFreeCacheMax
         Gauge32
      }

pr1645v2IpV6VrfRtrH2PerfGlobalIx OBJECT-TYPE
   SYNTAX      GlobalIndex
   MAX-ACCESS  not-accessible
   STATUS      current
   DESCRIPTION
      "The value of the tlsCntTreeGlobalIndex of the MANAGED OBJECT."
   ::= {pr1645v2IpV6VrfRtrH2PerfEntry 10}

pr1645v2IpV6VrfRtrH2PerfTableIx OBJECT-TYPE
   SYNTAX      TableIndex
   MAX-ACCESS  not-accessible
   STATUS      current
   DESCRIPTION
      ""
   ::= {pr1645v2IpV6VrfRtrH2PerfEntry 11}

pr1645v2IpV6VrfRtrH2PerfSysUpTime OBJECT-TYPE
   SYNTAX      TimeTicks
   MAX-ACCESS  read-only
   STATUS      current
   DESCRIPTION
      "Path: vrfV6Router.performance.h2Dns.sysUpTime

       Time in centi-second."
   ::= {pr1645v2IpV6VrfRtrH2PerfEntry 16777216}

pr1645v2IpV6VrfRtrH2PerfRequests OBJECT-TYPE
   SYNTAX      Counter32
   MAX-ACCESS  read-only
   STATUS      current
   DESCRIPTION
      "Path: vrfV6Router.performance.h2Dns.requests

       32 bit unsigned wrappable counter."
   ::= {pr1645v2IpV6VrfRtrH2PerfEntry 33554432}

pr1645v2IpV6VrfRtrH2PerfInternalRequests OBJECT-TYPE
   SYNTAX      Counter32
   MAX-ACCESS  read-only
   STATUS      current
   DESCRIPTION
      "Path: vrfV6Router.performance.h2Dns.internalRequests

       32 bit unsigned wrappable counter."
   ::= {pr1645v2IpV6VrfRtrH2PerfEntry 50331648}

pr1645v2IpV6VrfRtrH2PerfExternalRequests OBJECT-TYPE
   SYNTAX      Counter32
   MAX-ACCESS  read-only
   STATUS      current
   DESCRIPTION
      "Path: vrfV6Router.performance.h2Dns.externalRequests

       32 bit unsigned wrappable counter."
   ::= {pr1645v2IpV6VrfRtrH2PerfEntry 67108864}

pr1645v2IpV6VrfRtrH2PerfForwardedRequests OBJECT-TYPE
   SYNTAX      Counter32
   MAX-ACCESS  read-only
   STATUS      current
   DESCRIPTION
      "Path: vrfV6Router.performance.h2Dns.forwardedRequests

       32 bit unsigned wrappable counter."
   ::= {pr1645v2IpV6VrfRtrH2PerfEntry 83886080}

pr1645v2IpV6VrfRtrH2PerfFailedRequests OBJECT-TYPE
   SYNTAX      Counter32
   MAX-ACCESS  read-only
   STATUS      current
   DESCRIPTION
      "Path: vrfV6Router.performance.h2Dns.failedRequests

       32 bit unsigned wrappable counter."
   ::= {pr1645v2IpV6VrfRtrH2PerfEntry 100663296}

pr1645v2IpV6VrfRtrH2PerfFreeCacheMin OBJECT-TYPE
   SYNTAX      Gauge32
   MAX-ACCESS  read-only
   STATUS      current
   DESCRIPTION
      "Path: vrfV6Router.performance.h2Dns.freeCacheMin

       32 bit unsigned gauge value."
   ::= {pr1645v2IpV6VrfRtrH2PerfEntry 117440512}

pr1645v2IpV6VrfRtrH2PerfFreeCacheAvrg OBJECT-TYPE
   SYNTAX      Gauge32
   MAX-ACCESS  read-only
   STATUS      current
   DESCRIPTION
      "Path: vrfV6Router.performance.h2Dns.freeCacheAvrg

       32 bit unsigned gauge value."
   ::= {pr1645v2IpV6VrfRtrH2PerfEntry 134217728}

pr1645v2IpV6VrfRtrH2PerfFreeCacheMax OBJECT-TYPE
   SYNTAX      Gauge32
   MAX-ACCESS  read-only
   STATUS      current
   DESCRIPTION
      "Path: vrfV6Router.performance.h2Dns.freeCacheMax

       32 bit unsigned gauge value."
   ::= {pr1645v2IpV6VrfRtrH2PerfEntry 150994944}


pr1645v2IpV6VrfRtrH24Perf OBJECT IDENTIFIER ::= {pr1645v2IpV6VrfRtr 51}

pr1645v2IpV6VrfRtrH24PerfSSCTable OBJECT-TYPE
   SYNTAX      SEQUENCE OF Pr1645v2IpV6VrfRtrH24PerfEntry
   MAX-ACCESS  not-accessible
   STATUS      current
   DESCRIPTION
      "24 hour dns stats"
   ::= {pr1645v2IpV6VrfRtrH24Perf 1}

pr1645v2IpV6VrfRtrH24PerfEntry OBJECT-TYPE
   SYNTAX      Pr1645v2IpV6VrfRtrH24PerfEntry
   MAX-ACCESS  not-accessible
   STATUS      current
   DESCRIPTION
      ""
   INDEX      { pr1645v2IpV6VrfRtrH24PerfGlobalIx,
                pr1645v2IpV6VrfRtrH24PerfTableIx }
   ::= {pr1645v2IpV6VrfRtrH24PerfSSCTable 1}

Pr1645v2IpV6VrfRtrH24PerfEntry ::=
   SEQUENCE
      {
      pr1645v2IpV6VrfRtrH24PerfGlobalIx
         GlobalIndex,
      pr1645v2IpV6VrfRtrH24PerfTableIx
         TableIndex,
      pr1645v2IpV6VrfRtrH24PerfSysUpTime
         TimeTicks,
      pr1645v2IpV6VrfRtrH24PerfRequests
         Counter32,
      pr1645v2IpV6VrfRtrH24PerfInternalRequests
         Counter32,
      pr1645v2IpV6VrfRtrH24PerfExternalRequests
         Counter32,
      pr1645v2IpV6VrfRtrH24PerfForwardedRequests
         Counter32,
      pr1645v2IpV6VrfRtrH24PerfFailedRequests
         Counter32,
      pr1645v2IpV6VrfRtrH24PerfFreeCacheMin
         Gauge32,
      pr1645v2IpV6VrfRtrH24PerfFreeCacheAvrg
         Gauge32,
      pr1645v2IpV6VrfRtrH24PerfFreeCacheMax
         Gauge32
      }

pr1645v2IpV6VrfRtrH24PerfGlobalIx OBJECT-TYPE
   SYNTAX      GlobalIndex
   MAX-ACCESS  not-accessible
   STATUS      current
   DESCRIPTION
      "The value of the tlsCntTreeGlobalIndex of the MANAGED OBJECT."
   ::= {pr1645v2IpV6VrfRtrH24PerfEntry 10}

pr1645v2IpV6VrfRtrH24PerfTableIx OBJECT-TYPE
   SYNTAX      TableIndex
   MAX-ACCESS  not-accessible
   STATUS      current
   DESCRIPTION
      ""
   ::= {pr1645v2IpV6VrfRtrH24PerfEntry 11}

pr1645v2IpV6VrfRtrH24PerfSysUpTime OBJECT-TYPE
   SYNTAX      TimeTicks
   MAX-ACCESS  read-only
   STATUS      current
   DESCRIPTION
      "Path: vrfV6Router.performance.h24Dns.sysUpTime

       Time in centi-second."
   ::= {pr1645v2IpV6VrfRtrH24PerfEntry 16777216}

pr1645v2IpV6VrfRtrH24PerfRequests OBJECT-TYPE
   SYNTAX      Counter32
   MAX-ACCESS  read-only
   STATUS      current
   DESCRIPTION
      "Path: vrfV6Router.performance.h24Dns.requests

       32 bit unsigned wrappable counter."
   ::= {pr1645v2IpV6VrfRtrH24PerfEntry 33554432}

pr1645v2IpV6VrfRtrH24PerfInternalRequests OBJECT-TYPE
   SYNTAX      Counter32
   MAX-ACCESS  read-only
   STATUS      current
   DESCRIPTION
      "Path: vrfV6Router.performance.h24Dns.internalRequests

       32 bit unsigned wrappable counter."
   ::= {pr1645v2IpV6VrfRtrH24PerfEntry 50331648}

pr1645v2IpV6VrfRtrH24PerfExternalRequests OBJECT-TYPE
   SYNTAX      Counter32
   MAX-ACCESS  read-only
   STATUS      current
   DESCRIPTION
      "Path: vrfV6Router.performance.h24Dns.externalRequests

       32 bit unsigned wrappable counter."
   ::= {pr1645v2IpV6VrfRtrH24PerfEntry 67108864}

pr1645v2IpV6VrfRtrH24PerfForwardedRequests OBJECT-TYPE
   SYNTAX      Counter32
   MAX-ACCESS  read-only
   STATUS      current
   DESCRIPTION
      "Path: vrfV6Router.performance.h24Dns.forwardedRequests

       32 bit unsigned wrappable counter."
   ::= {pr1645v2IpV6VrfRtrH24PerfEntry 83886080}

pr1645v2IpV6VrfRtrH24PerfFailedRequests OBJECT-TYPE
   SYNTAX      Counter32
   MAX-ACCESS  read-only
   STATUS      current
   DESCRIPTION
      "Path: vrfV6Router.performance.h24Dns.failedRequests

       32 bit unsigned wrappable counter."
   ::= {pr1645v2IpV6VrfRtrH24PerfEntry 100663296}

pr1645v2IpV6VrfRtrH24PerfFreeCacheMin OBJECT-TYPE
   SYNTAX      Gauge32
   MAX-ACCESS  read-only
   STATUS      current
   DESCRIPTION
      "Path: vrfV6Router.performance.h24Dns.freeCacheMin

       32 bit unsigned gauge value."
   ::= {pr1645v2IpV6VrfRtrH24PerfEntry 117440512}

pr1645v2IpV6VrfRtrH24PerfFreeCacheAvrg OBJECT-TYPE
   SYNTAX      Gauge32
   MAX-ACCESS  read-only
   STATUS      current
   DESCRIPTION
      "Path: vrfV6Router.performance.h24Dns.freeCacheAvrg

       32 bit unsigned gauge value."
   ::= {pr1645v2IpV6VrfRtrH24PerfEntry 134217728}

pr1645v2IpV6VrfRtrH24PerfFreeCacheMax OBJECT-TYPE
   SYNTAX      Gauge32
   MAX-ACCESS  read-only
   STATUS      current
   DESCRIPTION
      "Path: vrfV6Router.performance.h24Dns.freeCacheMax

       32 bit unsigned gauge value."
   ::= {pr1645v2IpV6VrfRtrH24PerfEntry 150994944}


pr1645v2IpV6VrfRtrD7Perf OBJECT IDENTIFIER ::= {pr1645v2IpV6VrfRtr 52}

pr1645v2IpV6VrfRtrD7PerfSSCTable OBJECT-TYPE
   SYNTAX      SEQUENCE OF Pr1645v2IpV6VrfRtrD7PerfEntry
   MAX-ACCESS  not-accessible
   STATUS      current
   DESCRIPTION
      "7 days dns stats"
   ::= {pr1645v2IpV6VrfRtrD7Perf 1}

pr1645v2IpV6VrfRtrD7PerfEntry OBJECT-TYPE
   SYNTAX      Pr1645v2IpV6VrfRtrD7PerfEntry
   MAX-ACCESS  not-accessible
   STATUS      current
   DESCRIPTION
      ""
   INDEX      { pr1645v2IpV6VrfRtrD7PerfGlobalIx,
                pr1645v2IpV6VrfRtrD7PerfTableIx }
   ::= {pr1645v2IpV6VrfRtrD7PerfSSCTable 1}

Pr1645v2IpV6VrfRtrD7PerfEntry ::=
   SEQUENCE
      {
      pr1645v2IpV6VrfRtrD7PerfGlobalIx
         GlobalIndex,
      pr1645v2IpV6VrfRtrD7PerfTableIx
         TableIndex,
      pr1645v2IpV6VrfRtrD7PerfSysUpTime
         TimeTicks,
      pr1645v2IpV6VrfRtrD7PerfRequests
         Counter32,
      pr1645v2IpV6VrfRtrD7PerfInternalRequests
         Counter32,
      pr1645v2IpV6VrfRtrD7PerfExternalRequests
         Counter32,
      pr1645v2IpV6VrfRtrD7PerfForwardedRequests
         Counter32,
      pr1645v2IpV6VrfRtrD7PerfFailedRequests
         Counter32,
      pr1645v2IpV6VrfRtrD7PerfFreeCacheMin
         Gauge32,
      pr1645v2IpV6VrfRtrD7PerfFreeCacheAvrg
         Gauge32,
      pr1645v2IpV6VrfRtrD7PerfFreeCacheMax
         Gauge32
      }

pr1645v2IpV6VrfRtrD7PerfGlobalIx OBJECT-TYPE
   SYNTAX      GlobalIndex
   MAX-ACCESS  not-accessible
   STATUS      current
   DESCRIPTION
      "The value of the tlsCntTreeGlobalIndex of the MANAGED OBJECT."
   ::= {pr1645v2IpV6VrfRtrD7PerfEntry 10}

pr1645v2IpV6VrfRtrD7PerfTableIx OBJECT-TYPE
   SYNTAX      TableIndex
   MAX-ACCESS  not-accessible
   STATUS      current
   DESCRIPTION
      ""
   ::= {pr1645v2IpV6VrfRtrD7PerfEntry 11}

pr1645v2IpV6VrfRtrD7PerfSysUpTime OBJECT-TYPE
   SYNTAX      TimeTicks
   MAX-ACCESS  read-only
   STATUS      current
   DESCRIPTION
      "Path: vrfV6Router.performance.d7Dns.sysUpTime

       Time in centi-second."
   ::= {pr1645v2IpV6VrfRtrD7PerfEntry 16777216}

pr1645v2IpV6VrfRtrD7PerfRequests OBJECT-TYPE
   SYNTAX      Counter32
   MAX-ACCESS  read-only
   STATUS      current
   DESCRIPTION
      "Path: vrfV6Router.performance.d7Dns.requests

       32 bit unsigned wrappable counter."
   ::= {pr1645v2IpV6VrfRtrD7PerfEntry 33554432}

pr1645v2IpV6VrfRtrD7PerfInternalRequests OBJECT-TYPE
   SYNTAX      Counter32
   MAX-ACCESS  read-only
   STATUS      current
   DESCRIPTION
      "Path: vrfV6Router.performance.d7Dns.internalRequests

       32 bit unsigned wrappable counter."
   ::= {pr1645v2IpV6VrfRtrD7PerfEntry 50331648}

pr1645v2IpV6VrfRtrD7PerfExternalRequests OBJECT-TYPE
   SYNTAX      Counter32
   MAX-ACCESS  read-only
   STATUS      current
   DESCRIPTION
      "Path: vrfV6Router.performance.d7Dns.externalRequests

       32 bit unsigned wrappable counter."
   ::= {pr1645v2IpV6VrfRtrD7PerfEntry 67108864}

pr1645v2IpV6VrfRtrD7PerfForwardedRequests OBJECT-TYPE
   SYNTAX      Counter32
   MAX-ACCESS  read-only
   STATUS      current
   DESCRIPTION
      "Path: vrfV6Router.performance.d7Dns.forwardedRequests

       32 bit unsigned wrappable counter."
   ::= {pr1645v2IpV6VrfRtrD7PerfEntry 83886080}

pr1645v2IpV6VrfRtrD7PerfFailedRequests OBJECT-TYPE
   SYNTAX      Counter32
   MAX-ACCESS  read-only
   STATUS      current
   DESCRIPTION
      "Path: vrfV6Router.performance.d7Dns.failedRequests

       32 bit unsigned wrappable counter."
   ::= {pr1645v2IpV6VrfRtrD7PerfEntry 100663296}

pr1645v2IpV6VrfRtrD7PerfFreeCacheMin OBJECT-TYPE
   SYNTAX      Gauge32
   MAX-ACCESS  read-only
   STATUS      current
   DESCRIPTION
      "Path: vrfV6Router.performance.d7Dns.freeCacheMin

       32 bit unsigned gauge value."
   ::= {pr1645v2IpV6VrfRtrD7PerfEntry 117440512}

pr1645v2IpV6VrfRtrD7PerfFreeCacheAvrg OBJECT-TYPE
   SYNTAX      Gauge32
   MAX-ACCESS  read-only
   STATUS      current
   DESCRIPTION
      "Path: vrfV6Router.performance.d7Dns.freeCacheAvrg

       32 bit unsigned gauge value."
   ::= {pr1645v2IpV6VrfRtrD7PerfEntry 134217728}

pr1645v2IpV6VrfRtrD7PerfFreeCacheMax OBJECT-TYPE
   SYNTAX      Gauge32
   MAX-ACCESS  read-only
   STATUS      current
   DESCRIPTION
      "Path: vrfV6Router.performance.d7Dns.freeCacheMax

       32 bit unsigned gauge value."
   ::= {pr1645v2IpV6VrfRtrD7PerfEntry 150994944}


pr1645v2IpV6VrfRtrQMon OBJECT IDENTIFIER ::= {pr1645v2IpV6VrfRtr 53}

pr1645v2IpV6VrfRtrQMonSSCTable OBJECT-TYPE
   SYNTAX      SEQUENCE OF Pr1645v2IpV6VrfRtrQMonEntry
   MAX-ACCESS  not-accessible
   STATUS      current
   DESCRIPTION
      "quality monitor"
   ::= {pr1645v2IpV6VrfRtrQMon 1}

pr1645v2IpV6VrfRtrQMonEntry OBJECT-TYPE
   SYNTAX      Pr1645v2IpV6VrfRtrQMonEntry
   MAX-ACCESS  not-accessible
   STATUS      current
   DESCRIPTION
      ""
   INDEX      { pr1645v2IpV6VrfRtrQMonGlobalIx,
                pr1645v2IpV6VrfRtrQMonTableIx }
   ::= {pr1645v2IpV6VrfRtrQMonSSCTable 1}

Pr1645v2IpV6VrfRtrQMonEntry ::=
   SEQUENCE
      {
      pr1645v2IpV6VrfRtrQMonGlobalIx
         GlobalIndex,
      pr1645v2IpV6VrfRtrQMonTableIx
         TableIndex,
      pr1645v2IpV6VrfRtrQMonName
         DisplayString,
      pr1645v2IpV6VrfRtrQMonStatus
         INTEGER,
      pr1645v2IpV6VrfRtrQMonIpAddress
         Ipv6Address,
      pr1645v2IpV6VrfRtrQMonHostName
         DisplayString,
      pr1645v2IpV6VrfRtrQMonSourceIp
         Ipv6Address,
      pr1645v2IpV6VrfRtrQMonSourceId
         Counter32,
      pr1645v2IpV6VrfRtrQMonNbrTxPckt
         Counter32,
      pr1645v2IpV6VrfRtrQMonNbrRxPckt
         Counter32,
      pr1645v2IpV6VrfRtrQMonError
         Counter32,
      pr1645v2IpV6VrfRtrQMonDelay
         Integer32,
      pr1645v2IpV6VrfRtrQMonJitter
         Integer32,
      pr1645v2IpV6VrfRtrQMonLoss
         Counter32,
      pr1645v2IpV6VrfRtrQMonLossDelay
         Counter32,
      pr1645v2IpV6VrfRtrQMonDelayMin
         Integer32,
      pr1645v2IpV6VrfRtrQMonDelayAvrg
         Integer32,
      pr1645v2IpV6VrfRtrQMonDelayMax
         Integer32,
      pr1645v2IpV6VrfRtrQMonDelayBinsType
         INTEGER,
      pr1645v2IpV6VrfRtrQMonDelayBinsMinMin
         Counter32,
      pr1645v2IpV6VrfRtrQMonDelayBinsMin
         Integer32,
      pr1645v2IpV6VrfRtrQMonDelayBinsMinBin1
         Counter32,
      pr1645v2IpV6VrfRtrQMonDelayBinsBin2
         Counter32,
      pr1645v2IpV6VrfRtrQMonDelayBinsBin3
         Counter32,
      pr1645v2IpV6VrfRtrQMonDelayBinsBin4
         Counter32,
      pr1645v2IpV6VrfRtrQMonDelayBinsBin5
         Counter32,
      pr1645v2IpV6VrfRtrQMonDelayBinsBin6
         Counter32,
      pr1645v2IpV6VrfRtrQMonDelayBinsBin7
         Counter32,
      pr1645v2IpV6VrfRtrQMonDelayBinsMaxBin8
         Counter32,
      pr1645v2IpV6VrfRtrQMonDelayBinsMax
         Integer32,
      pr1645v2IpV6VrfRtrQMonDelayBinsPlusMax
         Counter32,
      pr1645v2IpV6VrfRtrQMonJitterNegMax
         Integer32,
      pr1645v2IpV6VrfRtrQMonJitterAvrg
         Integer32,
      pr1645v2IpV6VrfRtrQMonJitterPosMax
         Integer32,
      pr1645v2IpV6VrfRtrQMonJitterBinsType
         INTEGER,
      pr1645v2IpV6VrfRtrQMonJitterBinsMinMin
         Counter32,
      pr1645v2IpV6VrfRtrQMonJitterBinsMin
         Integer32,
      pr1645v2IpV6VrfRtrQMonJitterBinsMinBin1
         Counter32,
      pr1645v2IpV6VrfRtrQMonJitterBinsBin2
         Counter32,
      pr1645v2IpV6VrfRtrQMonJitterBinsBin3
         Counter32,
      pr1645v2IpV6VrfRtrQMonJitterBinsBin4
         Counter32,
      pr1645v2IpV6VrfRtrQMonJitterBinsBin5
         Counter32,
      pr1645v2IpV6VrfRtrQMonJitterBinsBin6
         Counter32,
      pr1645v2IpV6VrfRtrQMonJitterBinsBin7
         Counter32,
      pr1645v2IpV6VrfRtrQMonJitterBinsMaxBin8
         Counter32,
      pr1645v2IpV6VrfRtrQMonJitterBinsMax
         Integer32,
      pr1645v2IpV6VrfRtrQMonJitterBinsPlusMax
         Counter32,
      pr1645v2IpV6VrfRtrQMonUpDownStatus
         INTEGER,
      pr1645v2IpV6VrfRtrQMonUpDownLossUp
         Counter32,
      pr1645v2IpV6VrfRtrQMonUpDownLossDelayUp
         Counter32,
      pr1645v2IpV6VrfRtrQMonUpDownDelayUpMin
         Integer32,
      pr1645v2IpV6VrfRtrQMonUpDownDelayUpAvrg
         Integer32,
      pr1645v2IpV6VrfRtrQMonUpDownDelayUpMax
         Integer32,
      pr1645v2IpV6VrfRtrQMonUpDownDelayUpBinsType
         INTEGER,
      pr1645v2IpV6VrfRtrQMonUpDownDelayUpBinsMinMin
         Counter32,
      pr1645v2IpV6VrfRtrQMonUpDownDelayUpBinsMin
         Integer32,
      pr1645v2IpV6VrfRtrQMonUpDownDelayUpBinsMinBin1
         Counter32,
      pr1645v2IpV6VrfRtrQMonUpDownDelayUpBinsBin2
         Counter32,
      pr1645v2IpV6VrfRtrQMonUpDownDelayUpBinsBin3
         Counter32,
      pr1645v2IpV6VrfRtrQMonUpDownDelayUpBinsBin4
         Counter32,
      pr1645v2IpV6VrfRtrQMonUpDownDelayUpBinsBin5
         Counter32,
      pr1645v2IpV6VrfRtrQMonUpDownDelayUpBinsBin6
         Counter32,
      pr1645v2IpV6VrfRtrQMonUpDownDelayUpBinsBin7
         Counter32,
      pr1645v2IpV6VrfRtrQMonUpDownDelayUpBinsMaxBin8
         Counter32,
      pr1645v2IpV6VrfRtrQMonUpDownDelayUpBinsMax
         Integer32,
      pr1645v2IpV6VrfRtrQMonUpDownDelayUpBinsPlusMax
         Counter32,
      pr1645v2IpV6VrfRtrQMonUpDownJitterUp
         Integer32,
      pr1645v2IpV6VrfRtrQMonUpDownJitterUpNegMax
         Integer32,
      pr1645v2IpV6VrfRtrQMonUpDownJitterUpAvrg
         Integer32,
      pr1645v2IpV6VrfRtrQMonUpDownJitterUpPosMax
         Integer32,
      pr1645v2IpV6VrfRtrQMonUpDownJitterUpBinsType
         INTEGER,
      pr1645v2IpV6VrfRtrQMonUpDownJitterUpBinsMinMin
         Counter32,
      pr1645v2IpV6VrfRtrQMonUpDownJitterUpBinsMin
         Integer32,
      pr1645v2IpV6VrfRtrQMonUpDownJitterUpBinsMinBin1
         Counter32,
      pr1645v2IpV6VrfRtrQMonUpDownJitterUpBinsBin2
         Counter32,
      pr1645v2IpV6VrfRtrQMonUpDownJitterUpBinsBin3
         Counter32,
      pr1645v2IpV6VrfRtrQMonUpDownJitterUpBinsBin4
         Counter32,
      pr1645v2IpV6VrfRtrQMonUpDownJitterUpBinsBin5
         Counter32,
      pr1645v2IpV6VrfRtrQMonUpDownJitterUpBinsBin6
         Counter32,
      pr1645v2IpV6VrfRtrQMonUpDownJitterUpBinsBin7
         Counter32,
      pr1645v2IpV6VrfRtrQMonUpDownJitterUpBinsMaxBin8
         Counter32,
      pr1645v2IpV6VrfRtrQMonUpDownJitterUpBinsMax
         Integer32,
      pr1645v2IpV6VrfRtrQMonUpDownJitterUpBinsPlusMax
         Counter32,
      pr1645v2IpV6VrfRtrQMonUpDownLossDown
         Counter32,
      pr1645v2IpV6VrfRtrQMonUpDownLossDelayDown
         Counter32,
      pr1645v2IpV6VrfRtrQMonUpDownDelayDownMin
         Integer32,
      pr1645v2IpV6VrfRtrQMonUpDownDelayDownAvrg
         Integer32,
      pr1645v2IpV6VrfRtrQMonUpDownDelayDownMax
         Integer32,
      pr1645v2IpV6VrfRtrQMonUpDownDelayDownBinsType
         INTEGER,
      pr1645v2IpV6VrfRtrQMonUpDownDelayDownBinsMinMin
         Counter32,
      pr1645v2IpV6VrfRtrQMonUpDownDelayDownBinsMin
         Integer32,
      pr1645v2IpV6VrfRtrQMonUpDownDelayDownBinsMinBin1
         Counter32,
      pr1645v2IpV6VrfRtrQMonUpDownDelayDownBinsBin2
         Counter32,
      pr1645v2IpV6VrfRtrQMonUpDownDelayDownBinsBin3
         Counter32,
      pr1645v2IpV6VrfRtrQMonUpDownDelayDownBinsBin4
         Counter32,
      pr1645v2IpV6VrfRtrQMonUpDownDelayDownBinsBin5
         Counter32,
      pr1645v2IpV6VrfRtrQMonUpDownDelayDownBinsBin6
         Counter32,
      pr1645v2IpV6VrfRtrQMonUpDownDelayDownBinsBin7
         Counter32,
      pr1645v2IpV6VrfRtrQMonUpDownDelayDownBinsMaxBin8
         Counter32,
      pr1645v2IpV6VrfRtrQMonUpDownDelayDownBinsMax
         Integer32,
      pr1645v2IpV6VrfRtrQMonUpDownDelayDownBinsPlusMax
         Counter32,
      pr1645v2IpV6VrfRtrQMonUpDownJitterDown
         Integer32,
      pr1645v2IpV6VrfRtrQMonUpDownJitterDownNegMax
         Integer32,
      pr1645v2IpV6VrfRtrQMonUpDownJitterDownAvrg
         Integer32,
      pr1645v2IpV6VrfRtrQMonUpDownJitterDownPosMax
         Integer32,
      pr1645v2IpV6VrfRtrQMonUpDownJitterDownBinsType
         INTEGER,
      pr1645v2IpV6VrfRtrQMonUpDownJitterDownBinsMinMin
         Counter32,
      pr1645v2IpV6VrfRtrQMonUpDownJitterDownBinsMin
         Integer32,
      pr1645v2IpV6VrfRtrQMonUpDownJitterDownBinsMinBin1
         Counter32,
      pr1645v2IpV6VrfRtrQMonUpDownJitterDownBinsBin2
         Counter32,
      pr1645v2IpV6VrfRtrQMonUpDownJitterDownBinsBin3
         Counter32,
      pr1645v2IpV6VrfRtrQMonUpDownJitterDownBinsBin4
         Counter32,
      pr1645v2IpV6VrfRtrQMonUpDownJitterDownBinsBin5
         Counter32,
      pr1645v2IpV6VrfRtrQMonUpDownJitterDownBinsBin6
         Counter32,
      pr1645v2IpV6VrfRtrQMonUpDownJitterDownBinsBin7
         Counter32,
      pr1645v2IpV6VrfRtrQMonUpDownJitterDownBinsMaxBin8
         Counter32,
      pr1645v2IpV6VrfRtrQMonUpDownJitterDownBinsMax
         Integer32,
      pr1645v2IpV6VrfRtrQMonUpDownJitterDownBinsPlusMax
         Counter32,
      pr1645v2IpV6VrfRtrQMonLastLogSysUpTime
         TimeTicks,
      pr1645v2IpV6VrfRtrQMonLastLogNbrTxPckt
         Counter32,
      pr1645v2IpV6VrfRtrQMonLastLogNbrRxPckt
         Counter32,
      pr1645v2IpV6VrfRtrQMonLastLogError
         Counter32,
      pr1645v2IpV6VrfRtrQMonLastLogLoss
         Counter32,
      pr1645v2IpV6VrfRtrQMonLastLogLossDelay
         Counter32,
      pr1645v2IpV6VrfRtrQMonLastLogDelayMin
         Integer32,
      pr1645v2IpV6VrfRtrQMonLastLogDelayAvrg
         Integer32,
      pr1645v2IpV6VrfRtrQMonLastLogDelayMax
         Integer32,
      pr1645v2IpV6VrfRtrQMonLastLogJitterNegMax
         Integer32,
      pr1645v2IpV6VrfRtrQMonLastLogJitterAvrg
         Integer32,
      pr1645v2IpV6VrfRtrQMonLastLogJitterPosMax
         Integer32,
      pr1645v2IpV6VrfRtrQMonLastLogUpDownStatus
         INTEGER,
      pr1645v2IpV6VrfRtrQMonLastLogUpDownLossUp
         Counter32,
      pr1645v2IpV6VrfRtrQMonLastLogUpDownLossDelayUp
         Counter32,
      pr1645v2IpV6VrfRtrQMonLastLogUpDownDelayUpMin
         Integer32,
      pr1645v2IpV6VrfRtrQMonLastLogUpDownDelayUpAvrg
         Integer32,
      pr1645v2IpV6VrfRtrQMonLastLogUpDownDelayUpMax
         Integer32,
      pr1645v2IpV6VrfRtrQMonLastLogUpDownJitterUpNegMax
         Integer32,
      pr1645v2IpV6VrfRtrQMonLastLogUpDownJitterUpAvrg
         Integer32,
      pr1645v2IpV6VrfRtrQMonLastLogUpDownJitterUpPosMax
         Integer32,
      pr1645v2IpV6VrfRtrQMonLastLogUpDownLossDown
         Counter32,
      pr1645v2IpV6VrfRtrQMonLastLogUpDownLossDelayDown
         Counter32,
      pr1645v2IpV6VrfRtrQMonLastLogUpDownDelayDownMin
         Integer32,
      pr1645v2IpV6VrfRtrQMonLastLogUpDownDelayDownAvrg
         Integer32,
      pr1645v2IpV6VrfRtrQMonLastLogUpDownDelayDownMax
         Integer32,
      pr1645v2IpV6VrfRtrQMonLastLogUpDownJitterDownNegMax
         Integer32,
      pr1645v2IpV6VrfRtrQMonLastLogUpDownJitterDownAvrg
         Integer32,
      pr1645v2IpV6VrfRtrQMonLastLogUpDownJitterDownPosMax
         Integer32,
      pr1645v2IpV6VrfRtrQMonLastLogDate
         DisplayString,
      pr1645v2IpV6VrfRtrQMonAlarm
         Integer32,
      pr1645v2IpV6VrfRtrQMonLastError
         DisplayString
      }

pr1645v2IpV6VrfRtrQMonGlobalIx OBJECT-TYPE
   SYNTAX      GlobalIndex
   MAX-ACCESS  not-accessible
   STATUS      current
   DESCRIPTION
      "The value of the tlsCntTreeGlobalIndex of the MANAGED OBJECT."
   ::= {pr1645v2IpV6VrfRtrQMonEntry 10}

pr1645v2IpV6VrfRtrQMonTableIx OBJECT-TYPE
   SYNTAX      TableIndex
   MAX-ACCESS  not-accessible
   STATUS      current
   DESCRIPTION
      ""
   ::= {pr1645v2IpV6VrfRtrQMonEntry 11}

pr1645v2IpV6VrfRtrQMonName OBJECT-TYPE
   SYNTAX      DisplayString
   MAX-ACCESS  read-only
   STATUS      current
   DESCRIPTION
      "Path: vrfV6Router.performance.qualityMonitor.name"
   ::= {pr1645v2IpV6VrfRtrQMonEntry 301989888}

pr1645v2IpV6VrfRtrQMonStatus OBJECT-TYPE
   SYNTAX      INTEGER
               {
               run (1),
               runOnDemand (3),
               halted (2),
               cleared (6),
               disabled (8),
               runIdle (9)
               }
   MAX-ACCESS  read-only
   STATUS      current
   DESCRIPTION
      "Path: vrfV6Router.performance.qualityMonitor.status

       Possibilities:
               run   (1)
               runOnDemand   (3)
               halted   (2)
               cleared   (6)
               disabled   (8)
               runIdle   (9)"
   ::= {pr1645v2IpV6VrfRtrQMonEntry 369098752}

pr1645v2IpV6VrfRtrQMonIpAddress OBJECT-TYPE
   SYNTAX      Ipv6Address
   MAX-ACCESS  read-only
   STATUS      current
   DESCRIPTION
      "Path: vrfV6Router.performance.qualityMonitor.ipAddress

       ipv6 address"
   ::= {pr1645v2IpV6VrfRtrQMonEntry 16777216}

pr1645v2IpV6VrfRtrQMonHostName OBJECT-TYPE
   SYNTAX      DisplayString
   MAX-ACCESS  read-only
   STATUS      current
   DESCRIPTION
      "Path: vrfV6Router.performance.qualityMonitor.hostName"
   ::= {pr1645v2IpV6VrfRtrQMonEntry 33554432}

pr1645v2IpV6VrfRtrQMonSourceIp OBJECT-TYPE
   SYNTAX      Ipv6Address
   MAX-ACCESS  read-only
   STATUS      current
   DESCRIPTION
      "Path: vrfV6Router.performance.qualityMonitor.sourceIp

       ipv6 address"
   ::= {pr1645v2IpV6VrfRtrQMonEntry 83886080}

pr1645v2IpV6VrfRtrQMonSourceId OBJECT-TYPE
   SYNTAX      Counter32
   MAX-ACCESS  read-only
   STATUS      current
   DESCRIPTION
      "Path: vrfV6Router.performance.qualityMonitor.sourceId

       32 bit unsigned wrappable counter."
   ::= {pr1645v2IpV6VrfRtrQMonEntry 352321536}

pr1645v2IpV6VrfRtrQMonNbrTxPckt OBJECT-TYPE
   SYNTAX      Counter32
   MAX-ACCESS  read-only
   STATUS      current
   DESCRIPTION
      "Path: vrfV6Router.performance.qualityMonitor.nbrOfTxPackets

       32 bit unsigned wrappable counter."
   ::= {pr1645v2IpV6VrfRtrQMonEntry 50331648}

pr1645v2IpV6VrfRtrQMonNbrRxPckt OBJECT-TYPE
   SYNTAX      Counter32
   MAX-ACCESS  read-only
   STATUS      current
   DESCRIPTION
      "Path: vrfV6Router.performance.qualityMonitor.nbrOfRxPackets

       32 bit unsigned wrappable counter."
   ::= {pr1645v2IpV6VrfRtrQMonEntry 67108864}

pr1645v2IpV6VrfRtrQMonError OBJECT-TYPE
   SYNTAX      Counter32
   MAX-ACCESS  read-only
   STATUS      current
   DESCRIPTION
      "Path: vrfV6Router.performance.qualityMonitor.error

       32 bit unsigned wrappable counter."
   ::= {pr1645v2IpV6VrfRtrQMonEntry 285212672}

pr1645v2IpV6VrfRtrQMonDelay OBJECT-TYPE
   SYNTAX      Integer32
   MAX-ACCESS  read-only
   STATUS      current
   DESCRIPTION
      "Path: vrfV6Router.performance.qualityMonitor.delay

       unit name = sec
       formula = 1000 / ; 1000 *"
   ::= {pr1645v2IpV6VrfRtrQMonEntry 201326592}

pr1645v2IpV6VrfRtrQMonJitter OBJECT-TYPE
   SYNTAX      Integer32
   MAX-ACCESS  read-only
   STATUS      current
   DESCRIPTION
      "Path: vrfV6Router.performance.qualityMonitor.jitter

       unit name = sec
       formula = 1000 / ; 1000 *"
   ::= {pr1645v2IpV6VrfRtrQMonEntry 218103808}

pr1645v2IpV6VrfRtrQMonLoss OBJECT-TYPE
   SYNTAX      Counter32
   MAX-ACCESS  read-only
   STATUS      current
   DESCRIPTION
      "Path: vrfV6Router.performance.qualityMonitor.loss

       32 bit unsigned wrappable counter."
   ::= {pr1645v2IpV6VrfRtrQMonEntry 100663296}

pr1645v2IpV6VrfRtrQMonLossDelay OBJECT-TYPE
   SYNTAX      Counter32
   MAX-ACCESS  read-only
   STATUS      current
   DESCRIPTION
      "Path: vrfV6Router.performance.qualityMonitor.lossDelay

       32 bit unsigned wrappable counter."
   ::= {pr1645v2IpV6VrfRtrQMonEntry 268435456}

pr1645v2IpV6VrfRtrQMonDelayMin OBJECT-TYPE
   SYNTAX      Integer32
   MAX-ACCESS  read-only
   STATUS      current
   DESCRIPTION
      "Path: vrfV6Router.performance.qualityMonitor.delayMin

       unit name = sec
       formula = 1000 / ; 1000 *"
   ::= {pr1645v2IpV6VrfRtrQMonEntry 184549376}

pr1645v2IpV6VrfRtrQMonDelayAvrg OBJECT-TYPE
   SYNTAX      Integer32
   MAX-ACCESS  read-only
   STATUS      current
   DESCRIPTION
      "Path: vrfV6Router.performance.qualityMonitor.delayAvrg

       unit name = sec
       formula = 1000 / ; 1000 *"
   ::= {pr1645v2IpV6VrfRtrQMonEntry 117440512}

pr1645v2IpV6VrfRtrQMonDelayMax OBJECT-TYPE
   SYNTAX      Integer32
   MAX-ACCESS  read-only
   STATUS      current
   DESCRIPTION
      "Path: vrfV6Router.performance.qualityMonitor.delayMax

       unit name = sec
       formula = 1000 / ; 1000 *"
   ::= {pr1645v2IpV6VrfRtrQMonEntry 134217728}

pr1645v2IpV6VrfRtrQMonDelayBinsType OBJECT-TYPE
   SYNTAX      INTEGER
               {
               fd (1),
               fdr (2),
               notInUse (3),
               ifdv (4)
               }
   MAX-ACCESS  read-only
   STATUS      current
   DESCRIPTION
      "Path: vrfV6Router.performance.qualityMonitor.delayBins.type

       Possibilities:
               fd   (1)
               fdr   (2)
               notInUse   (3)
               ifdv   (4)"
   ::= {pr1645v2IpV6VrfRtrQMonEntry 420937728}

pr1645v2IpV6VrfRtrQMonDelayBinsMinMin OBJECT-TYPE
   SYNTAX      Counter32
   MAX-ACCESS  read-only
   STATUS      current
   DESCRIPTION
      "Path: vrfV6Router.performance.qualityMonitor.delayBins.minMin

       32 bit unsigned wrappable counter."
   ::= {pr1645v2IpV6VrfRtrQMonEntry 419495936}

pr1645v2IpV6VrfRtrQMonDelayBinsMin OBJECT-TYPE
   SYNTAX      Integer32
   MAX-ACCESS  read-only
   STATUS      current
   DESCRIPTION
      "Path: vrfV6Router.performance.qualityMonitor.delayBins.min

       unit name = sec
       formula = 1000 / ; 1000 *"
   ::= {pr1645v2IpV6VrfRtrQMonEntry 420806656}

pr1645v2IpV6VrfRtrQMonDelayBinsMinBin1 OBJECT-TYPE
   SYNTAX      Counter32
   MAX-ACCESS  read-only
   STATUS      current
   DESCRIPTION
      "Path: vrfV6Router.performance.qualityMonitor.delayBins.minBin1

       32 bit unsigned wrappable counter."
   ::= {pr1645v2IpV6VrfRtrQMonEntry 419561472}

pr1645v2IpV6VrfRtrQMonDelayBinsBin2 OBJECT-TYPE
   SYNTAX      Counter32
   MAX-ACCESS  read-only
   STATUS      current
   DESCRIPTION
      "Path: vrfV6Router.performance.qualityMonitor.delayBins.bin2

       32 bit unsigned wrappable counter."
   ::= {pr1645v2IpV6VrfRtrQMonEntry 419627008}

pr1645v2IpV6VrfRtrQMonDelayBinsBin3 OBJECT-TYPE
   SYNTAX      Counter32
   MAX-ACCESS  read-only
   STATUS      current
   DESCRIPTION
      "Path: vrfV6Router.performance.qualityMonitor.delayBins.bin3

       32 bit unsigned wrappable counter."
   ::= {pr1645v2IpV6VrfRtrQMonEntry 419692544}

pr1645v2IpV6VrfRtrQMonDelayBinsBin4 OBJECT-TYPE
   SYNTAX      Counter32
   MAX-ACCESS  read-only
   STATUS      current
   DESCRIPTION
      "Path: vrfV6Router.performance.qualityMonitor.delayBins.bin4

       32 bit unsigned wrappable counter."
   ::= {pr1645v2IpV6VrfRtrQMonEntry 419758080}

pr1645v2IpV6VrfRtrQMonDelayBinsBin5 OBJECT-TYPE
   SYNTAX      Counter32
   MAX-ACCESS  read-only
   STATUS      current
   DESCRIPTION
      "Path: vrfV6Router.performance.qualityMonitor.delayBins.bin5

       32 bit unsigned wrappable counter."
   ::= {pr1645v2IpV6VrfRtrQMonEntry 419823616}

pr1645v2IpV6VrfRtrQMonDelayBinsBin6 OBJECT-TYPE
   SYNTAX      Counter32
   MAX-ACCESS  read-only
   STATUS      current
   DESCRIPTION
      "Path: vrfV6Router.performance.qualityMonitor.delayBins.bin6

       32 bit unsigned wrappable counter."
   ::= {pr1645v2IpV6VrfRtrQMonEntry 419889152}

pr1645v2IpV6VrfRtrQMonDelayBinsBin7 OBJECT-TYPE
   SYNTAX      Counter32
   MAX-ACCESS  read-only
   STATUS      current
   DESCRIPTION
      "Path: vrfV6Router.performance.qualityMonitor.delayBins.bin7

       32 bit unsigned wrappable counter."
   ::= {pr1645v2IpV6VrfRtrQMonEntry 419954688}

pr1645v2IpV6VrfRtrQMonDelayBinsMaxBin8 OBJECT-TYPE
   SYNTAX      Counter32
   MAX-ACCESS  read-only
   STATUS      current
   DESCRIPTION
      "Path: vrfV6Router.performance.qualityMonitor.delayBins.maxBin8

       32 bit unsigned wrappable counter."
   ::= {pr1645v2IpV6VrfRtrQMonEntry 420020224}

pr1645v2IpV6VrfRtrQMonDelayBinsMax OBJECT-TYPE
   SYNTAX      Integer32
   MAX-ACCESS  read-only
   STATUS      current
   DESCRIPTION
      "Path: vrfV6Router.performance.qualityMonitor.delayBins.max

       unit name = sec
       formula = 1000 / ; 1000 *"
   ::= {pr1645v2IpV6VrfRtrQMonEntry 420872192}

pr1645v2IpV6VrfRtrQMonDelayBinsPlusMax OBJECT-TYPE
   SYNTAX      Counter32
   MAX-ACCESS  read-only
   STATUS      current
   DESCRIPTION
      "Path: vrfV6Router.performance.qualityMonitor.delayBins.plusMax

       32 bit unsigned wrappable counter."
   ::= {pr1645v2IpV6VrfRtrQMonEntry 420085760}

pr1645v2IpV6VrfRtrQMonJitterNegMax OBJECT-TYPE
   SYNTAX      Integer32
   MAX-ACCESS  read-only
   STATUS      current
   DESCRIPTION
      "Path: vrfV6Router.performance.qualityMonitor.jitterNegMax

       unit name = sec
       formula = 1000 / ; 1000 *"
   ::= {pr1645v2IpV6VrfRtrQMonEntry 234881024}

pr1645v2IpV6VrfRtrQMonJitterAvrg OBJECT-TYPE
   SYNTAX      Integer32
   MAX-ACCESS  read-only
   STATUS      current
   DESCRIPTION
      "Path: vrfV6Router.performance.qualityMonitor.jitterAvrg

       unit name = sec
       formula = 1000 / ; 1000 *"
   ::= {pr1645v2IpV6VrfRtrQMonEntry 150994944}

pr1645v2IpV6VrfRtrQMonJitterPosMax OBJECT-TYPE
   SYNTAX      Integer32
   MAX-ACCESS  read-only
   STATUS      current
   DESCRIPTION
      "Path: vrfV6Router.performance.qualityMonitor.jitterPosMax

       unit name = sec
       formula = 1000 / ; 1000 *"
   ::= {pr1645v2IpV6VrfRtrQMonEntry 167772160}

pr1645v2IpV6VrfRtrQMonJitterBinsType OBJECT-TYPE
   SYNTAX      INTEGER
               {
               fd (1),
               fdr (2),
               notInUse (3),
               ifdv (4)
               }
   MAX-ACCESS  read-only
   STATUS      current
   DESCRIPTION
      "Path: vrfV6Router.performance.qualityMonitor.jitterBins.type

       Possibilities:
               fd   (1)
               fdr   (2)
               notInUse   (3)
               ifdv   (4)"
   ::= {pr1645v2IpV6VrfRtrQMonEntry 437714944}

pr1645v2IpV6VrfRtrQMonJitterBinsMinMin OBJECT-TYPE
   SYNTAX      Counter32
   MAX-ACCESS  read-only
   STATUS      current
   DESCRIPTION
      "Path: vrfV6Router.performance.qualityMonitor.jitterBins.minMin

       32 bit unsigned wrappable counter."
   ::= {pr1645v2IpV6VrfRtrQMonEntry 436273152}

pr1645v2IpV6VrfRtrQMonJitterBinsMin OBJECT-TYPE
   SYNTAX      Integer32
   MAX-ACCESS  read-only
   STATUS      current
   DESCRIPTION
      "Path: vrfV6Router.performance.qualityMonitor.jitterBins.min

       unit name = sec
       formula = 1000 / ; 1000 *"
   ::= {pr1645v2IpV6VrfRtrQMonEntry 437583872}

pr1645v2IpV6VrfRtrQMonJitterBinsMinBin1 OBJECT-TYPE
   SYNTAX      Counter32
   MAX-ACCESS  read-only
   STATUS      current
   DESCRIPTION
      "Path: vrfV6Router.performance.qualityMonitor.jitterBins.minBin1

       32 bit unsigned wrappable counter."
   ::= {pr1645v2IpV6VrfRtrQMonEntry 436338688}

pr1645v2IpV6VrfRtrQMonJitterBinsBin2 OBJECT-TYPE
   SYNTAX      Counter32
   MAX-ACCESS  read-only
   STATUS      current
   DESCRIPTION
      "Path: vrfV6Router.performance.qualityMonitor.jitterBins.bin2

       32 bit unsigned wrappable counter."
   ::= {pr1645v2IpV6VrfRtrQMonEntry 436404224}

pr1645v2IpV6VrfRtrQMonJitterBinsBin3 OBJECT-TYPE
   SYNTAX      Counter32
   MAX-ACCESS  read-only
   STATUS      current
   DESCRIPTION
      "Path: vrfV6Router.performance.qualityMonitor.jitterBins.bin3

       32 bit unsigned wrappable counter."
   ::= {pr1645v2IpV6VrfRtrQMonEntry 436469760}

pr1645v2IpV6VrfRtrQMonJitterBinsBin4 OBJECT-TYPE
   SYNTAX      Counter32
   MAX-ACCESS  read-only
   STATUS      current
   DESCRIPTION
      "Path: vrfV6Router.performance.qualityMonitor.jitterBins.bin4

       32 bit unsigned wrappable counter."
   ::= {pr1645v2IpV6VrfRtrQMonEntry 436535296}

pr1645v2IpV6VrfRtrQMonJitterBinsBin5 OBJECT-TYPE
   SYNTAX      Counter32
   MAX-ACCESS  read-only
   STATUS      current
   DESCRIPTION
      "Path: vrfV6Router.performance.qualityMonitor.jitterBins.bin5

       32 bit unsigned wrappable counter."
   ::= {pr1645v2IpV6VrfRtrQMonEntry 436600832}

pr1645v2IpV6VrfRtrQMonJitterBinsBin6 OBJECT-TYPE
   SYNTAX      Counter32
   MAX-ACCESS  read-only
   STATUS      current
   DESCRIPTION
      "Path: vrfV6Router.performance.qualityMonitor.jitterBins.bin6

       32 bit unsigned wrappable counter."
   ::= {pr1645v2IpV6VrfRtrQMonEntry 436666368}

pr1645v2IpV6VrfRtrQMonJitterBinsBin7 OBJECT-TYPE
   SYNTAX      Counter32
   MAX-ACCESS  read-only
   STATUS      current
   DESCRIPTION
      "Path: vrfV6Router.performance.qualityMonitor.jitterBins.bin7

       32 bit unsigned wrappable counter."
   ::= {pr1645v2IpV6VrfRtrQMonEntry 436731904}

pr1645v2IpV6VrfRtrQMonJitterBinsMaxBin8 OBJECT-TYPE
   SYNTAX      Counter32
   MAX-ACCESS  read-only
   STATUS      current
   DESCRIPTION
      "Path: vrfV6Router.performance.qualityMonitor.jitterBins.maxBin8

       32 bit unsigned wrappable counter."
   ::= {pr1645v2IpV6VrfRtrQMonEntry 436797440}

pr1645v2IpV6VrfRtrQMonJitterBinsMax OBJECT-TYPE
   SYNTAX      Integer32
   MAX-ACCESS  read-only
   STATUS      current
   DESCRIPTION
      "Path: vrfV6Router.performance.qualityMonitor.jitterBins.max

       unit name = sec
       formula = 1000 / ; 1000 *"
   ::= {pr1645v2IpV6VrfRtrQMonEntry 437649408}

pr1645v2IpV6VrfRtrQMonJitterBinsPlusMax OBJECT-TYPE
   SYNTAX      Counter32
   MAX-ACCESS  read-only
   STATUS      current
   DESCRIPTION
      "Path: vrfV6Router.performance.qualityMonitor.jitterBins.plusMax

       32 bit unsigned wrappable counter."
   ::= {pr1645v2IpV6VrfRtrQMonEntry 436862976}

pr1645v2IpV6VrfRtrQMonUpDownStatus OBJECT-TYPE
   SYNTAX      INTEGER
               {
               notInUse (3),
               onlyJitter (1),
               jitterAndLoss (2),
               all (4),
               onlyLoss (8)
               }
   MAX-ACCESS  read-only
   STATUS      current
   DESCRIPTION
      "Path: vrfV6Router.performance.qualityMonitor.upDown.status

       Possibilities:
               notInUse   (3)
               onlyJitter   (1)
               jitterAndLoss   (2)
               all   (4)
               onlyLoss   (8)"
   ::= {pr1645v2IpV6VrfRtrQMonEntry 504627200}

pr1645v2IpV6VrfRtrQMonUpDownLossUp OBJECT-TYPE
   SYNTAX      Counter32
   MAX-ACCESS  read-only
   STATUS      current
   DESCRIPTION
      "Path: vrfV6Router.performance.qualityMonitor.upDown.lossUp

       32 bit unsigned wrappable counter."
   ::= {pr1645v2IpV6VrfRtrQMonEntry 503971840}

pr1645v2IpV6VrfRtrQMonUpDownLossDelayUp OBJECT-TYPE
   SYNTAX      Counter32
   MAX-ACCESS  read-only
   STATUS      current
   DESCRIPTION
      "Path: vrfV6Router.performance.qualityMonitor.upDown.lossDelayUp

       32 bit unsigned wrappable counter."
   ::= {pr1645v2IpV6VrfRtrQMonEntry 504037376}

pr1645v2IpV6VrfRtrQMonUpDownDelayUpMin OBJECT-TYPE
   SYNTAX      Integer32
   MAX-ACCESS  read-only
   STATUS      current
   DESCRIPTION
      "Path: vrfV6Router.performance.qualityMonitor.upDown.delayUpMin

       unit name = sec
       formula = 1000 / ; 1000 *"
   ::= {pr1645v2IpV6VrfRtrQMonEntry 505282560}

pr1645v2IpV6VrfRtrQMonUpDownDelayUpAvrg OBJECT-TYPE
   SYNTAX      Integer32
   MAX-ACCESS  read-only
   STATUS      current
   DESCRIPTION
      "Path: vrfV6Router.performance.qualityMonitor.upDown.delayUpAvrg

       unit name = sec
       formula = 1000 / ; 1000 *"
   ::= {pr1645v2IpV6VrfRtrQMonEntry 505348096}

pr1645v2IpV6VrfRtrQMonUpDownDelayUpMax OBJECT-TYPE
   SYNTAX      Integer32
   MAX-ACCESS  read-only
   STATUS      current
   DESCRIPTION
      "Path: vrfV6Router.performance.qualityMonitor.upDown.delayUpMax

       unit name = sec
       formula = 1000 / ; 1000 *"
   ::= {pr1645v2IpV6VrfRtrQMonEntry 505413632}

pr1645v2IpV6VrfRtrQMonUpDownDelayUpBinsType OBJECT-TYPE
   SYNTAX      INTEGER
               {
               fd (1),
               fdr (2),
               notInUse (3),
               ifdv (4)
               }
   MAX-ACCESS  read-only
   STATUS      current
   DESCRIPTION
      "Path: vrfV6Router.performance.qualityMonitor.upDown.delayUpBins.type

       Possibilities:
               fd   (1)
               fdr   (2)
               notInUse   (3)
               ifdv   (4)"
   ::= {pr1645v2IpV6VrfRtrQMonEntry 505943808}

pr1645v2IpV6VrfRtrQMonUpDownDelayUpBinsMinMin OBJECT-TYPE
   SYNTAX      Counter32
   MAX-ACCESS  read-only
   STATUS      current
   DESCRIPTION
      "Path: vrfV6Router.performance.qualityMonitor.upDown.delayUpBins.minMin

       32 bit unsigned wrappable counter."
   ::= {pr1645v2IpV6VrfRtrQMonEntry 505938176}

pr1645v2IpV6VrfRtrQMonUpDownDelayUpBinsMin OBJECT-TYPE
   SYNTAX      Integer32
   MAX-ACCESS  read-only
   STATUS      current
   DESCRIPTION
      "Path: vrfV6Router.performance.qualityMonitor.upDown.delayUpBins.min

       unit name = sec
       formula = 1000 / ; 1000 *"
   ::= {pr1645v2IpV6VrfRtrQMonEntry 505943296}

pr1645v2IpV6VrfRtrQMonUpDownDelayUpBinsMinBin1 OBJECT-TYPE
   SYNTAX      Counter32
   MAX-ACCESS  read-only
   STATUS      current
   DESCRIPTION
      "Path: vrfV6Router.performance.qualityMonitor.upDown.delayUpBins.minBin1

       32 bit unsigned wrappable counter."
   ::= {pr1645v2IpV6VrfRtrQMonEntry 505938432}

pr1645v2IpV6VrfRtrQMonUpDownDelayUpBinsBin2 OBJECT-TYPE
   SYNTAX      Counter32
   MAX-ACCESS  read-only
   STATUS      current
   DESCRIPTION
      "Path: vrfV6Router.performance.qualityMonitor.upDown.delayUpBins.bin2

       32 bit unsigned wrappable counter."
   ::= {pr1645v2IpV6VrfRtrQMonEntry 505938688}

pr1645v2IpV6VrfRtrQMonUpDownDelayUpBinsBin3 OBJECT-TYPE
   SYNTAX      Counter32
   MAX-ACCESS  read-only
   STATUS      current
   DESCRIPTION
      "Path: vrfV6Router.performance.qualityMonitor.upDown.delayUpBins.bin3

       32 bit unsigned wrappable counter."
   ::= {pr1645v2IpV6VrfRtrQMonEntry 505938944}

pr1645v2IpV6VrfRtrQMonUpDownDelayUpBinsBin4 OBJECT-TYPE
   SYNTAX      Counter32
   MAX-ACCESS  read-only
   STATUS      current
   DESCRIPTION
      "Path: vrfV6Router.performance.qualityMonitor.upDown.delayUpBins.bin4

       32 bit unsigned wrappable counter."
   ::= {pr1645v2IpV6VrfRtrQMonEntry 505939200}

pr1645v2IpV6VrfRtrQMonUpDownDelayUpBinsBin5 OBJECT-TYPE
   SYNTAX      Counter32
   MAX-ACCESS  read-only
   STATUS      current
   DESCRIPTION
      "Path: vrfV6Router.performance.qualityMonitor.upDown.delayUpBins.bin5

       32 bit unsigned wrappable counter."
   ::= {pr1645v2IpV6VrfRtrQMonEntry 505939456}

pr1645v2IpV6VrfRtrQMonUpDownDelayUpBinsBin6 OBJECT-TYPE
   SYNTAX      Counter32
   MAX-ACCESS  read-only
   STATUS      current
   DESCRIPTION
      "Path: vrfV6Router.performance.qualityMonitor.upDown.delayUpBins.bin6

       32 bit unsigned wrappable counter."
   ::= {pr1645v2IpV6VrfRtrQMonEntry 505939712}

pr1645v2IpV6VrfRtrQMonUpDownDelayUpBinsBin7 OBJECT-TYPE
   SYNTAX      Counter32
   MAX-ACCESS  read-only
   STATUS      current
   DESCRIPTION
      "Path: vrfV6Router.performance.qualityMonitor.upDown.delayUpBins.bin7

       32 bit unsigned wrappable counter."
   ::= {pr1645v2IpV6VrfRtrQMonEntry 505939968}

pr1645v2IpV6VrfRtrQMonUpDownDelayUpBinsMaxBin8 OBJECT-TYPE
   SYNTAX      Counter32
   MAX-ACCESS  read-only
   STATUS      current
   DESCRIPTION
      "Path: vrfV6Router.performance.qualityMonitor.upDown.delayUpBins.maxBin8

       32 bit unsigned wrappable counter."
   ::= {pr1645v2IpV6VrfRtrQMonEntry 505940224}

pr1645v2IpV6VrfRtrQMonUpDownDelayUpBinsMax OBJECT-TYPE
   SYNTAX      Integer32
   MAX-ACCESS  read-only
   STATUS      current
   DESCRIPTION
      "Path: vrfV6Router.performance.qualityMonitor.upDown.delayUpBins.max

       unit name = sec
       formula = 1000 / ; 1000 *"
   ::= {pr1645v2IpV6VrfRtrQMonEntry 505943552}

pr1645v2IpV6VrfRtrQMonUpDownDelayUpBinsPlusMax OBJECT-TYPE
   SYNTAX      Counter32
   MAX-ACCESS  read-only
   STATUS      current
   DESCRIPTION
      "Path: vrfV6Router.performance.qualityMonitor.upDown.delayUpBins.plusMax

       32 bit unsigned wrappable counter."
   ::= {pr1645v2IpV6VrfRtrQMonEntry 505940480}

pr1645v2IpV6VrfRtrQMonUpDownJitterUp OBJECT-TYPE
   SYNTAX      Integer32
   MAX-ACCESS  read-only
   STATUS      current
   DESCRIPTION
      "Path: vrfV6Router.performance.qualityMonitor.upDown.jitterUp

       unit name = sec
       formula = 1000 / ; 1000 *"
   ::= {pr1645v2IpV6VrfRtrQMonEntry 503775232}

pr1645v2IpV6VrfRtrQMonUpDownJitterUpNegMax OBJECT-TYPE
   SYNTAX      Integer32
   MAX-ACCESS  read-only
   STATUS      current
   DESCRIPTION
      "Path: vrfV6Router.performance.qualityMonitor.upDown.jitterUpNegMax

       unit name = sec
       formula = 1000 / ; 1000 *"
   ::= {pr1645v2IpV6VrfRtrQMonEntry 503382016}

pr1645v2IpV6VrfRtrQMonUpDownJitterUpAvrg OBJECT-TYPE
   SYNTAX      Integer32
   MAX-ACCESS  read-only
   STATUS      current
   DESCRIPTION
      "Path: vrfV6Router.performance.qualityMonitor.upDown.jitterUpAvrg

       unit name = sec
       formula = 1000 / ; 1000 *"
   ::= {pr1645v2IpV6VrfRtrQMonEntry 503447552}

pr1645v2IpV6VrfRtrQMonUpDownJitterUpPosMax OBJECT-TYPE
   SYNTAX      Integer32
   MAX-ACCESS  read-only
   STATUS      current
   DESCRIPTION
      "Path: vrfV6Router.performance.qualityMonitor.upDown.jitterUpPosMax

       unit name = sec
       formula = 1000 / ; 1000 *"
   ::= {pr1645v2IpV6VrfRtrQMonEntry 503513088}

pr1645v2IpV6VrfRtrQMonUpDownJitterUpBinsType OBJECT-TYPE
   SYNTAX      INTEGER
               {
               fd (1),
               fdr (2),
               notInUse (3),
               ifdv (4)
               }
   MAX-ACCESS  read-only
   STATUS      current
   DESCRIPTION
      "Path: vrfV6Router.performance.qualityMonitor.upDown.jitterUpBins.type

       Possibilities:
               fd   (1)
               fdr   (2)
               notInUse   (3)
               ifdv   (4)"
   ::= {pr1645v2IpV6VrfRtrQMonEntry 506074880}

pr1645v2IpV6VrfRtrQMonUpDownJitterUpBinsMinMin OBJECT-TYPE
   SYNTAX      Counter32
   MAX-ACCESS  read-only
   STATUS      current
   DESCRIPTION
      "Path: vrfV6Router.performance.qualityMonitor.upDown.jitterUpBins.minMin

       32 bit unsigned wrappable counter."
   ::= {pr1645v2IpV6VrfRtrQMonEntry 506069248}

pr1645v2IpV6VrfRtrQMonUpDownJitterUpBinsMin OBJECT-TYPE
   SYNTAX      Integer32
   MAX-ACCESS  read-only
   STATUS      current
   DESCRIPTION
      "Path: vrfV6Router.performance.qualityMonitor.upDown.jitterUpBins.min

       unit name = sec
       formula = 1000 / ; 1000 *"
   ::= {pr1645v2IpV6VrfRtrQMonEntry 506074368}

pr1645v2IpV6VrfRtrQMonUpDownJitterUpBinsMinBin1 OBJECT-TYPE
   SYNTAX      Counter32
   MAX-ACCESS  read-only
   STATUS      current
   DESCRIPTION
      "Path: vrfV6Router.performance.qualityMonitor.upDown.jitterUpBins.minBin1

       32 bit unsigned wrappable counter."
   ::= {pr1645v2IpV6VrfRtrQMonEntry 506069504}

pr1645v2IpV6VrfRtrQMonUpDownJitterUpBinsBin2 OBJECT-TYPE
   SYNTAX      Counter32
   MAX-ACCESS  read-only
   STATUS      current
   DESCRIPTION
      "Path: vrfV6Router.performance.qualityMonitor.upDown.jitterUpBins.bin2

       32 bit unsigned wrappable counter."
   ::= {pr1645v2IpV6VrfRtrQMonEntry 506069760}

pr1645v2IpV6VrfRtrQMonUpDownJitterUpBinsBin3 OBJECT-TYPE
   SYNTAX      Counter32
   MAX-ACCESS  read-only
   STATUS      current
   DESCRIPTION
      "Path: vrfV6Router.performance.qualityMonitor.upDown.jitterUpBins.bin3

       32 bit unsigned wrappable counter."
   ::= {pr1645v2IpV6VrfRtrQMonEntry 506070016}

pr1645v2IpV6VrfRtrQMonUpDownJitterUpBinsBin4 OBJECT-TYPE
   SYNTAX      Counter32
   MAX-ACCESS  read-only
   STATUS      current
   DESCRIPTION
      "Path: vrfV6Router.performance.qualityMonitor.upDown.jitterUpBins.bin4

       32 bit unsigned wrappable counter."
   ::= {pr1645v2IpV6VrfRtrQMonEntry 506070272}

pr1645v2IpV6VrfRtrQMonUpDownJitterUpBinsBin5 OBJECT-TYPE
   SYNTAX      Counter32
   MAX-ACCESS  read-only
   STATUS      current
   DESCRIPTION
      "Path: vrfV6Router.performance.qualityMonitor.upDown.jitterUpBins.bin5

       32 bit unsigned wrappable counter."
   ::= {pr1645v2IpV6VrfRtrQMonEntry 506070528}

pr1645v2IpV6VrfRtrQMonUpDownJitterUpBinsBin6 OBJECT-TYPE
   SYNTAX      Counter32
   MAX-ACCESS  read-only
   STATUS      current
   DESCRIPTION
      "Path: vrfV6Router.performance.qualityMonitor.upDown.jitterUpBins.bin6

       32 bit unsigned wrappable counter."
   ::= {pr1645v2IpV6VrfRtrQMonEntry 506070784}

pr1645v2IpV6VrfRtrQMonUpDownJitterUpBinsBin7 OBJECT-TYPE
   SYNTAX      Counter32
   MAX-ACCESS  read-only
   STATUS      current
   DESCRIPTION
      "Path: vrfV6Router.performance.qualityMonitor.upDown.jitterUpBins.bin7

       32 bit unsigned wrappable counter."
   ::= {pr1645v2IpV6VrfRtrQMonEntry 506071040}

pr1645v2IpV6VrfRtrQMonUpDownJitterUpBinsMaxBin8 OBJECT-TYPE
   SYNTAX      Counter32
   MAX-ACCESS  read-only
   STATUS      current
   DESCRIPTION
      "Path: vrfV6Router.performance.qualityMonitor.upDown.jitterUpBins.maxBin8

       32 bit unsigned wrappable counter."
   ::= {pr1645v2IpV6VrfRtrQMonEntry 506071296}

pr1645v2IpV6VrfRtrQMonUpDownJitterUpBinsMax OBJECT-TYPE
   SYNTAX      Integer32
   MAX-ACCESS  read-only
   STATUS      current
   DESCRIPTION
      "Path: vrfV6Router.performance.qualityMonitor.upDown.jitterUpBins.max

       unit name = sec
       formula = 1000 / ; 1000 *"
   ::= {pr1645v2IpV6VrfRtrQMonEntry 506074624}

pr1645v2IpV6VrfRtrQMonUpDownJitterUpBinsPlusMax OBJECT-TYPE
   SYNTAX      Counter32
   MAX-ACCESS  read-only
   STATUS      current
   DESCRIPTION
      "Path: vrfV6Router.performance.qualityMonitor.upDown.jitterUpBins.plusMax

       32 bit unsigned wrappable counter."
   ::= {pr1645v2IpV6VrfRtrQMonEntry 506071552}

pr1645v2IpV6VrfRtrQMonUpDownLossDown OBJECT-TYPE
   SYNTAX      Counter32
   MAX-ACCESS  read-only
   STATUS      current
   DESCRIPTION
      "Path: vrfV6Router.performance.qualityMonitor.upDown.lossDown

       32 bit unsigned wrappable counter."
   ::= {pr1645v2IpV6VrfRtrQMonEntry 504102912}

pr1645v2IpV6VrfRtrQMonUpDownLossDelayDown OBJECT-TYPE
   SYNTAX      Counter32
   MAX-ACCESS  read-only
   STATUS      current
   DESCRIPTION
      "Path: vrfV6Router.performance.qualityMonitor.upDown.lossDelayDown

       32 bit unsigned wrappable counter."
   ::= {pr1645v2IpV6VrfRtrQMonEntry 504168448}

pr1645v2IpV6VrfRtrQMonUpDownDelayDownMin OBJECT-TYPE
   SYNTAX      Integer32
   MAX-ACCESS  read-only
   STATUS      current
   DESCRIPTION
      "Path: vrfV6Router.performance.qualityMonitor.upDown.delayDownMin

       unit name = sec
       formula = 1000 / ; 1000 *"
   ::= {pr1645v2IpV6VrfRtrQMonEntry 505610240}

pr1645v2IpV6VrfRtrQMonUpDownDelayDownAvrg OBJECT-TYPE
   SYNTAX      Integer32
   MAX-ACCESS  read-only
   STATUS      current
   DESCRIPTION
      "Path: vrfV6Router.performance.qualityMonitor.upDown.delayDownAvrg

       unit name = sec
       formula = 1000 / ; 1000 *"
   ::= {pr1645v2IpV6VrfRtrQMonEntry 505675776}

pr1645v2IpV6VrfRtrQMonUpDownDelayDownMax OBJECT-TYPE
   SYNTAX      Integer32
   MAX-ACCESS  read-only
   STATUS      current
   DESCRIPTION
      "Path: vrfV6Router.performance.qualityMonitor.upDown.delayDownMax

       unit name = sec
       formula = 1000 / ; 1000 *"
   ::= {pr1645v2IpV6VrfRtrQMonEntry 505741312}

pr1645v2IpV6VrfRtrQMonUpDownDelayDownBinsType OBJECT-TYPE
   SYNTAX      INTEGER
               {
               fd (1),
               fdr (2),
               notInUse (3),
               ifdv (4)
               }
   MAX-ACCESS  read-only
   STATUS      current
   DESCRIPTION
      "Path: vrfV6Router.performance.qualityMonitor.upDown.delayDownBins.type

       Possibilities:
               fd   (1)
               fdr   (2)
               notInUse   (3)
               ifdv   (4)"
   ::= {pr1645v2IpV6VrfRtrQMonEntry 506009344}

pr1645v2IpV6VrfRtrQMonUpDownDelayDownBinsMinMin OBJECT-TYPE
   SYNTAX      Counter32
   MAX-ACCESS  read-only
   STATUS      current
   DESCRIPTION
      "Path: vrfV6Router.performance.qualityMonitor.upDown.delayDownBins.minMin

       32 bit unsigned wrappable counter."
   ::= {pr1645v2IpV6VrfRtrQMonEntry 506003712}

pr1645v2IpV6VrfRtrQMonUpDownDelayDownBinsMin OBJECT-TYPE
   SYNTAX      Integer32
   MAX-ACCESS  read-only
   STATUS      current
   DESCRIPTION
      "Path: vrfV6Router.performance.qualityMonitor.upDown.delayDownBins.min

       unit name = sec
       formula = 1000 / ; 1000 *"
   ::= {pr1645v2IpV6VrfRtrQMonEntry 506008832}

pr1645v2IpV6VrfRtrQMonUpDownDelayDownBinsMinBin1 OBJECT-TYPE
   SYNTAX      Counter32
   MAX-ACCESS  read-only
   STATUS      current
   DESCRIPTION
      "Path: vrfV6Router.performance.qualityMonitor.upDown.delayDownBins.minBin1

       32 bit unsigned wrappable counter."
   ::= {pr1645v2IpV6VrfRtrQMonEntry 506003968}

pr1645v2IpV6VrfRtrQMonUpDownDelayDownBinsBin2 OBJECT-TYPE
   SYNTAX      Counter32
   MAX-ACCESS  read-only
   STATUS      current
   DESCRIPTION
      "Path: vrfV6Router.performance.qualityMonitor.upDown.delayDownBins.bin2

       32 bit unsigned wrappable counter."
   ::= {pr1645v2IpV6VrfRtrQMonEntry 506004224}

pr1645v2IpV6VrfRtrQMonUpDownDelayDownBinsBin3 OBJECT-TYPE
   SYNTAX      Counter32
   MAX-ACCESS  read-only
   STATUS      current
   DESCRIPTION
      "Path: vrfV6Router.performance.qualityMonitor.upDown.delayDownBins.bin3

       32 bit unsigned wrappable counter."
   ::= {pr1645v2IpV6VrfRtrQMonEntry 506004480}

pr1645v2IpV6VrfRtrQMonUpDownDelayDownBinsBin4 OBJECT-TYPE
   SYNTAX      Counter32
   MAX-ACCESS  read-only
   STATUS      current
   DESCRIPTION
      "Path: vrfV6Router.performance.qualityMonitor.upDown.delayDownBins.bin4

       32 bit unsigned wrappable counter."
   ::= {pr1645v2IpV6VrfRtrQMonEntry 506004736}

pr1645v2IpV6VrfRtrQMonUpDownDelayDownBinsBin5 OBJECT-TYPE
   SYNTAX      Counter32
   MAX-ACCESS  read-only
   STATUS      current
   DESCRIPTION
      "Path: vrfV6Router.performance.qualityMonitor.upDown.delayDownBins.bin5

       32 bit unsigned wrappable counter."
   ::= {pr1645v2IpV6VrfRtrQMonEntry 506004992}

pr1645v2IpV6VrfRtrQMonUpDownDelayDownBinsBin6 OBJECT-TYPE
   SYNTAX      Counter32
   MAX-ACCESS  read-only
   STATUS      current
   DESCRIPTION
      "Path: vrfV6Router.performance.qualityMonitor.upDown.delayDownBins.bin6

       32 bit unsigned wrappable counter."
   ::= {pr1645v2IpV6VrfRtrQMonEntry 506005248}

pr1645v2IpV6VrfRtrQMonUpDownDelayDownBinsBin7 OBJECT-TYPE
   SYNTAX      Counter32
   MAX-ACCESS  read-only
   STATUS      current
   DESCRIPTION
      "Path: vrfV6Router.performance.qualityMonitor.upDown.delayDownBins.bin7

       32 bit unsigned wrappable counter."
   ::= {pr1645v2IpV6VrfRtrQMonEntry 506005504}

pr1645v2IpV6VrfRtrQMonUpDownDelayDownBinsMaxBin8 OBJECT-TYPE
   SYNTAX      Counter32
   MAX-ACCESS  read-only
   STATUS      current
   DESCRIPTION
      "Path: vrfV6Router.performance.qualityMonitor.upDown.delayDownBins.maxBin8

       32 bit unsigned wrappable counter."
   ::= {pr1645v2IpV6VrfRtrQMonEntry 506005760}

pr1645v2IpV6VrfRtrQMonUpDownDelayDownBinsMax OBJECT-TYPE
   SYNTAX      Integer32
   MAX-ACCESS  read-only
   STATUS      current
   DESCRIPTION
      "Path: vrfV6Router.performance.qualityMonitor.upDown.delayDownBins.max

       unit name = sec
       formula = 1000 / ; 1000 *"
   ::= {pr1645v2IpV6VrfRtrQMonEntry 506009088}

pr1645v2IpV6VrfRtrQMonUpDownDelayDownBinsPlusMax OBJECT-TYPE
   SYNTAX      Counter32
   MAX-ACCESS  read-only
   STATUS      current
   DESCRIPTION
      "Path: vrfV6Router.performance.qualityMonitor.upDown.delayDownBins.plusMax

       32 bit unsigned wrappable counter."
   ::= {pr1645v2IpV6VrfRtrQMonEntry 506006016}

pr1645v2IpV6VrfRtrQMonUpDownJitterDown OBJECT-TYPE
   SYNTAX      Integer32
   MAX-ACCESS  read-only
   STATUS      current
   DESCRIPTION
      "Path: vrfV6Router.performance.qualityMonitor.upDown.jitterDown

       unit name = sec
       formula = 1000 / ; 1000 *"
   ::= {pr1645v2IpV6VrfRtrQMonEntry 503840768}

pr1645v2IpV6VrfRtrQMonUpDownJitterDownNegMax OBJECT-TYPE
   SYNTAX      Integer32
   MAX-ACCESS  read-only
   STATUS      current
   DESCRIPTION
      "Path: vrfV6Router.performance.qualityMonitor.upDown.jitterDownNegMax

       unit name = sec
       formula = 1000 / ; 1000 *"
   ::= {pr1645v2IpV6VrfRtrQMonEntry 503578624}

pr1645v2IpV6VrfRtrQMonUpDownJitterDownAvrg OBJECT-TYPE
   SYNTAX      Integer32
   MAX-ACCESS  read-only
   STATUS      current
   DESCRIPTION
      "Path: vrfV6Router.performance.qualityMonitor.upDown.jitterDownAvrg

       unit name = sec
       formula = 1000 / ; 1000 *"
   ::= {pr1645v2IpV6VrfRtrQMonEntry 503644160}

pr1645v2IpV6VrfRtrQMonUpDownJitterDownPosMax OBJECT-TYPE
   SYNTAX      Integer32
   MAX-ACCESS  read-only
   STATUS      current
   DESCRIPTION
      "Path: vrfV6Router.performance.qualityMonitor.upDown.jitterDownPosMax

       unit name = sec
       formula = 1000 / ; 1000 *"
   ::= {pr1645v2IpV6VrfRtrQMonEntry 503709696}

pr1645v2IpV6VrfRtrQMonUpDownJitterDownBinsType OBJECT-TYPE
   SYNTAX      INTEGER
               {
               fd (1),
               fdr (2),
               notInUse (3),
               ifdv (4)
               }
   MAX-ACCESS  read-only
   STATUS      current
   DESCRIPTION
      "Path: vrfV6Router.performance.qualityMonitor.upDown.jitterDownBins.type

       Possibilities:
               fd   (1)
               fdr   (2)
               notInUse   (3)
               ifdv   (4)"
   ::= {pr1645v2IpV6VrfRtrQMonEntry 506205952}

pr1645v2IpV6VrfRtrQMonUpDownJitterDownBinsMinMin OBJECT-TYPE
   SYNTAX      Counter32
   MAX-ACCESS  read-only
   STATUS      current
   DESCRIPTION
      "Path: vrfV6Router.performance.qualityMonitor.upDown.jitterDownBins.minMin

       32 bit unsigned wrappable counter."
   ::= {pr1645v2IpV6VrfRtrQMonEntry 506200320}

pr1645v2IpV6VrfRtrQMonUpDownJitterDownBinsMin OBJECT-TYPE
   SYNTAX      Integer32
   MAX-ACCESS  read-only
   STATUS      current
   DESCRIPTION
      "Path: vrfV6Router.performance.qualityMonitor.upDown.jitterDownBins.min

       unit name = sec
       formula = 1000 / ; 1000 *"
   ::= {pr1645v2IpV6VrfRtrQMonEntry 506205440}

pr1645v2IpV6VrfRtrQMonUpDownJitterDownBinsMinBin1 OBJECT-TYPE
   SYNTAX      Counter32
   MAX-ACCESS  read-only
   STATUS      current
   DESCRIPTION
      "Path: vrfV6Router.performance.qualityMonitor.upDown.jitterDownBins.minBin1

       32 bit unsigned wrappable counter."
   ::= {pr1645v2IpV6VrfRtrQMonEntry 506200576}

pr1645v2IpV6VrfRtrQMonUpDownJitterDownBinsBin2 OBJECT-TYPE
   SYNTAX      Counter32
   MAX-ACCESS  read-only
   STATUS      current
   DESCRIPTION
      "Path: vrfV6Router.performance.qualityMonitor.upDown.jitterDownBins.bin2

       32 bit unsigned wrappable counter."
   ::= {pr1645v2IpV6VrfRtrQMonEntry 506200832}

pr1645v2IpV6VrfRtrQMonUpDownJitterDownBinsBin3 OBJECT-TYPE
   SYNTAX      Counter32
   MAX-ACCESS  read-only
   STATUS      current
   DESCRIPTION
      "Path: vrfV6Router.performance.qualityMonitor.upDown.jitterDownBins.bin3

       32 bit unsigned wrappable counter."
   ::= {pr1645v2IpV6VrfRtrQMonEntry 506201088}

pr1645v2IpV6VrfRtrQMonUpDownJitterDownBinsBin4 OBJECT-TYPE
   SYNTAX      Counter32
   MAX-ACCESS  read-only
   STATUS      current
   DESCRIPTION
      "Path: vrfV6Router.performance.qualityMonitor.upDown.jitterDownBins.bin4

       32 bit unsigned wrappable counter."
   ::= {pr1645v2IpV6VrfRtrQMonEntry 506201344}

pr1645v2IpV6VrfRtrQMonUpDownJitterDownBinsBin5 OBJECT-TYPE
   SYNTAX      Counter32
   MAX-ACCESS  read-only
   STATUS      current
   DESCRIPTION
      "Path: vrfV6Router.performance.qualityMonitor.upDown.jitterDownBins.bin5

       32 bit unsigned wrappable counter."
   ::= {pr1645v2IpV6VrfRtrQMonEntry 506201600}

pr1645v2IpV6VrfRtrQMonUpDownJitterDownBinsBin6 OBJECT-TYPE
   SYNTAX      Counter32
   MAX-ACCESS  read-only
   STATUS      current
   DESCRIPTION
      "Path: vrfV6Router.performance.qualityMonitor.upDown.jitterDownBins.bin6

       32 bit unsigned wrappable counter."
   ::= {pr1645v2IpV6VrfRtrQMonEntry 506201856}

pr1645v2IpV6VrfRtrQMonUpDownJitterDownBinsBin7 OBJECT-TYPE
   SYNTAX      Counter32
   MAX-ACCESS  read-only
   STATUS      current
   DESCRIPTION
      "Path: vrfV6Router.performance.qualityMonitor.upDown.jitterDownBins.bin7

       32 bit unsigned wrappable counter."
   ::= {pr1645v2IpV6VrfRtrQMonEntry 506202112}

pr1645v2IpV6VrfRtrQMonUpDownJitterDownBinsMaxBin8 OBJECT-TYPE
   SYNTAX      Counter32
   MAX-ACCESS  read-only
   STATUS      current
   DESCRIPTION
      "Path: vrfV6Router.performance.qualityMonitor.upDown.jitterDownBins.maxBin8

       32 bit unsigned wrappable counter."
   ::= {pr1645v2IpV6VrfRtrQMonEntry 506202368}

pr1645v2IpV6VrfRtrQMonUpDownJitterDownBinsMax OBJECT-TYPE
   SYNTAX      Integer32
   MAX-ACCESS  read-only
   STATUS      current
   DESCRIPTION
      "Path: vrfV6Router.performance.qualityMonitor.upDown.jitterDownBins.max

       unit name = sec
       formula = 1000 / ; 1000 *"
   ::= {pr1645v2IpV6VrfRtrQMonEntry 506205696}

pr1645v2IpV6VrfRtrQMonUpDownJitterDownBinsPlusMax OBJECT-TYPE
   SYNTAX      Counter32
   MAX-ACCESS  read-only
   STATUS      current
   DESCRIPTION
      "Path: vrfV6Router.performance.qualityMonitor.upDown.jitterDownBins.plusMax

       32 bit unsigned wrappable counter."
   ::= {pr1645v2IpV6VrfRtrQMonEntry 506202624}

pr1645v2IpV6VrfRtrQMonLastLogSysUpTime OBJECT-TYPE
   SYNTAX      TimeTicks
   MAX-ACCESS  read-only
   STATUS      current
   DESCRIPTION
      "Path: vrfV6Router.performance.qualityMonitor.lastLog.sysUpTime

       Time in centi-second."
   ::= {pr1645v2IpV6VrfRtrQMonEntry 671154176}

pr1645v2IpV6VrfRtrQMonLastLogNbrTxPckt OBJECT-TYPE
   SYNTAX      Counter32
   MAX-ACCESS  read-only
   STATUS      current
   DESCRIPTION
      "Path: vrfV6Router.performance.qualityMonitor.lastLog.nbrOfTxPackets

       32 bit unsigned wrappable counter."
   ::= {pr1645v2IpV6VrfRtrQMonEntry 671285248}

pr1645v2IpV6VrfRtrQMonLastLogNbrRxPckt OBJECT-TYPE
   SYNTAX      Counter32
   MAX-ACCESS  read-only
   STATUS      current
   DESCRIPTION
      "Path: vrfV6Router.performance.qualityMonitor.lastLog.nbrOfRxPackets

       32 bit unsigned wrappable counter."
   ::= {pr1645v2IpV6VrfRtrQMonEntry 671350784}

pr1645v2IpV6VrfRtrQMonLastLogError OBJECT-TYPE
   SYNTAX      Counter32
   MAX-ACCESS  read-only
   STATUS      current
   DESCRIPTION
      "Path: vrfV6Router.performance.qualityMonitor.lastLog.error

       32 bit unsigned wrappable counter."
   ::= {pr1645v2IpV6VrfRtrQMonEntry 672202752}

pr1645v2IpV6VrfRtrQMonLastLogLoss OBJECT-TYPE
   SYNTAX      Counter32
   MAX-ACCESS  read-only
   STATUS      current
   DESCRIPTION
      "Path: vrfV6Router.performance.qualityMonitor.lastLog.loss

       32 bit unsigned wrappable counter."
   ::= {pr1645v2IpV6VrfRtrQMonEntry 671481856}

pr1645v2IpV6VrfRtrQMonLastLogLossDelay OBJECT-TYPE
   SYNTAX      Counter32
   MAX-ACCESS  read-only
   STATUS      current
   DESCRIPTION
      "Path: vrfV6Router.performance.qualityMonitor.lastLog.lossDelay

       32 bit unsigned wrappable counter."
   ::= {pr1645v2IpV6VrfRtrQMonEntry 672137216}

pr1645v2IpV6VrfRtrQMonLastLogDelayMin OBJECT-TYPE
   SYNTAX      Integer32
   MAX-ACCESS  read-only
   STATUS      current
   DESCRIPTION
      "Path: vrfV6Router.performance.qualityMonitor.lastLog.delayMin

       unit name = sec
       formula = 1000 / ; 1000 *"
   ::= {pr1645v2IpV6VrfRtrQMonEntry 671809536}

pr1645v2IpV6VrfRtrQMonLastLogDelayAvrg OBJECT-TYPE
   SYNTAX      Integer32
   MAX-ACCESS  read-only
   STATUS      current
   DESCRIPTION
      "Path: vrfV6Router.performance.qualityMonitor.lastLog.delayAvrg

       unit name = sec
       formula = 1000 / ; 1000 *"
   ::= {pr1645v2IpV6VrfRtrQMonEntry 671547392}

pr1645v2IpV6VrfRtrQMonLastLogDelayMax OBJECT-TYPE
   SYNTAX      Integer32
   MAX-ACCESS  read-only
   STATUS      current
   DESCRIPTION
      "Path: vrfV6Router.performance.qualityMonitor.lastLog.delayMax

       unit name = sec
       formula = 1000 / ; 1000 *"
   ::= {pr1645v2IpV6VrfRtrQMonEntry 671612928}

pr1645v2IpV6VrfRtrQMonLastLogJitterNegMax OBJECT-TYPE
   SYNTAX      Integer32
   MAX-ACCESS  read-only
   STATUS      current
   DESCRIPTION
      "Path: vrfV6Router.performance.qualityMonitor.lastLog.jitterNegMax

       unit name = sec
       formula = 1000 / ; 1000 *"
   ::= {pr1645v2IpV6VrfRtrQMonEntry 672006144}

pr1645v2IpV6VrfRtrQMonLastLogJitterAvrg OBJECT-TYPE
   SYNTAX      Integer32
   MAX-ACCESS  read-only
   STATUS      current
   DESCRIPTION
      "Path: vrfV6Router.performance.qualityMonitor.lastLog.jitterAvrg

       unit name = sec
       formula = 1000 / ; 1000 *"
   ::= {pr1645v2IpV6VrfRtrQMonEntry 671678464}

pr1645v2IpV6VrfRtrQMonLastLogJitterPosMax OBJECT-TYPE
   SYNTAX      Integer32
   MAX-ACCESS  read-only
   STATUS      current
   DESCRIPTION
      "Path: vrfV6Router.performance.qualityMonitor.lastLog.jitterPosMax

       unit name = sec
       formula = 1000 / ; 1000 *"
   ::= {pr1645v2IpV6VrfRtrQMonEntry 671744000}

pr1645v2IpV6VrfRtrQMonLastLogUpDownStatus OBJECT-TYPE
   SYNTAX      INTEGER
               {
               notInUse (3),
               onlyJitter (1),
               jitterAndLoss (2),
               all (4),
               onlyLoss (8)
               }
   MAX-ACCESS  read-only
   STATUS      current
   DESCRIPTION
      "Path: vrfV6Router.performance.qualityMonitor.lastLog.upDown.status

       Possibilities:
               notInUse   (3)
               onlyJitter   (1)
               jitterAndLoss   (2)
               all   (4)
               onlyLoss   (8)"
   ::= {pr1645v2IpV6VrfRtrQMonEntry 673059840}

pr1645v2IpV6VrfRtrQMonLastLogUpDownLossUp OBJECT-TYPE
   SYNTAX      Counter32
   MAX-ACCESS  read-only
   STATUS      current
   DESCRIPTION
      "Path: vrfV6Router.performance.qualityMonitor.lastLog.upDown.lossUp

       32 bit unsigned wrappable counter."
   ::= {pr1645v2IpV6VrfRtrQMonEntry 673057280}

pr1645v2IpV6VrfRtrQMonLastLogUpDownLossDelayUp OBJECT-TYPE
   SYNTAX      Counter32
   MAX-ACCESS  read-only
   STATUS      current
   DESCRIPTION
      "Path: vrfV6Router.performance.qualityMonitor.lastLog.upDown.lossDelayUp

       32 bit unsigned wrappable counter."
   ::= {pr1645v2IpV6VrfRtrQMonEntry 673057536}

pr1645v2IpV6VrfRtrQMonLastLogUpDownDelayUpMin OBJECT-TYPE
   SYNTAX      Integer32
   MAX-ACCESS  read-only
   STATUS      current
   DESCRIPTION
      "Path: vrfV6Router.performance.qualityMonitor.lastLog.upDown.delayUpMin

       unit name = sec
       formula = 1000 / ; 1000 *"
   ::= {pr1645v2IpV6VrfRtrQMonEntry 673062400}

pr1645v2IpV6VrfRtrQMonLastLogUpDownDelayUpAvrg OBJECT-TYPE
   SYNTAX      Integer32
   MAX-ACCESS  read-only
   STATUS      current
   DESCRIPTION
      "Path: vrfV6Router.performance.qualityMonitor.lastLog.upDown.delayUpAvrg

       unit name = sec
       formula = 1000 / ; 1000 *"
   ::= {pr1645v2IpV6VrfRtrQMonEntry 673062656}

pr1645v2IpV6VrfRtrQMonLastLogUpDownDelayUpMax OBJECT-TYPE
   SYNTAX      Integer32
   MAX-ACCESS  read-only
   STATUS      current
   DESCRIPTION
      "Path: vrfV6Router.performance.qualityMonitor.lastLog.upDown.delayUpMax

       unit name = sec
       formula = 1000 / ; 1000 *"
   ::= {pr1645v2IpV6VrfRtrQMonEntry 673062912}

pr1645v2IpV6VrfRtrQMonLastLogUpDownJitterUpNegMax OBJECT-TYPE
   SYNTAX      Integer32
   MAX-ACCESS  read-only
   STATUS      current
   DESCRIPTION
      "Path: vrfV6Router.performance.qualityMonitor.lastLog.upDown.jitterUpNegMax

       unit name = sec
       formula = 1000 / ; 1000 *"
   ::= {pr1645v2IpV6VrfRtrQMonEntry 673054976}

pr1645v2IpV6VrfRtrQMonLastLogUpDownJitterUpAvrg OBJECT-TYPE
   SYNTAX      Integer32
   MAX-ACCESS  read-only
   STATUS      current
   DESCRIPTION
      "Path: vrfV6Router.performance.qualityMonitor.lastLog.upDown.jitterUpAvrg

       unit name = sec
       formula = 1000 / ; 1000 *"
   ::= {pr1645v2IpV6VrfRtrQMonEntry 673055232}

pr1645v2IpV6VrfRtrQMonLastLogUpDownJitterUpPosMax OBJECT-TYPE
   SYNTAX      Integer32
   MAX-ACCESS  read-only
   STATUS      current
   DESCRIPTION
      "Path: vrfV6Router.performance.qualityMonitor.lastLog.upDown.jitterUpPosMax

       unit name = sec
       formula = 1000 / ; 1000 *"
   ::= {pr1645v2IpV6VrfRtrQMonEntry 673055488}

pr1645v2IpV6VrfRtrQMonLastLogUpDownLossDown OBJECT-TYPE
   SYNTAX      Counter32
   MAX-ACCESS  read-only
   STATUS      current
   DESCRIPTION
      "Path: vrfV6Router.performance.qualityMonitor.lastLog.upDown.lossDown

       32 bit unsigned wrappable counter."
   ::= {pr1645v2IpV6VrfRtrQMonEntry 673057792}

pr1645v2IpV6VrfRtrQMonLastLogUpDownLossDelayDown OBJECT-TYPE
   SYNTAX      Counter32
   MAX-ACCESS  read-only
   STATUS      current
   DESCRIPTION
      "Path: vrfV6Router.performance.qualityMonitor.lastLog.upDown.lossDelayDown

       32 bit unsigned wrappable counter."
   ::= {pr1645v2IpV6VrfRtrQMonEntry 673058048}

pr1645v2IpV6VrfRtrQMonLastLogUpDownDelayDownMin OBJECT-TYPE
   SYNTAX      Integer32
   MAX-ACCESS  read-only
   STATUS      current
   DESCRIPTION
      "Path: vrfV6Router.performance.qualityMonitor.lastLog.upDown.delayDownMin

       unit name = sec
       formula = 1000 / ; 1000 *"
   ::= {pr1645v2IpV6VrfRtrQMonEntry 673063680}

pr1645v2IpV6VrfRtrQMonLastLogUpDownDelayDownAvrg OBJECT-TYPE
   SYNTAX      Integer32
   MAX-ACCESS  read-only
   STATUS      current
   DESCRIPTION
      "Path: vrfV6Router.performance.qualityMonitor.lastLog.upDown.delayDownAvrg

       unit name = sec
       formula = 1000 / ; 1000 *"
   ::= {pr1645v2IpV6VrfRtrQMonEntry 673063936}

pr1645v2IpV6VrfRtrQMonLastLogUpDownDelayDownMax OBJECT-TYPE
   SYNTAX      Integer32
   MAX-ACCESS  read-only
   STATUS      current
   DESCRIPTION
      "Path: vrfV6Router.performance.qualityMonitor.lastLog.upDown.delayDownMax

       unit name = sec
       formula = 1000 / ; 1000 *"
   ::= {pr1645v2IpV6VrfRtrQMonEntry 673064192}

pr1645v2IpV6VrfRtrQMonLastLogUpDownJitterDownNegMax OBJECT-TYPE
   SYNTAX      Integer32
   MAX-ACCESS  read-only
   STATUS      current
   DESCRIPTION
      "Path: vrfV6Router.performance.qualityMonitor.lastLog.upDown.jitterDownNegMax

       unit name = sec
       formula = 1000 / ; 1000 *"
   ::= {pr1645v2IpV6VrfRtrQMonEntry 673055744}

pr1645v2IpV6VrfRtrQMonLastLogUpDownJitterDownAvrg OBJECT-TYPE
   SYNTAX      Integer32
   MAX-ACCESS  read-only
   STATUS      current
   DESCRIPTION
      "Path: vrfV6Router.performance.qualityMonitor.lastLog.upDown.jitterDownAvrg

       unit name = sec
       formula = 1000 / ; 1000 *"
   ::= {pr1645v2IpV6VrfRtrQMonEntry 673056000}

pr1645v2IpV6VrfRtrQMonLastLogUpDownJitterDownPosMax OBJECT-TYPE
   SYNTAX      Integer32
   MAX-ACCESS  read-only
   STATUS      current
   DESCRIPTION
      "Path: vrfV6Router.performance.qualityMonitor.lastLog.upDown.jitterDownPosMax

       unit name = sec
       formula = 1000 / ; 1000 *"
   ::= {pr1645v2IpV6VrfRtrQMonEntry 673056256}

pr1645v2IpV6VrfRtrQMonLastLogDate OBJECT-TYPE
   SYNTAX      DisplayString
   MAX-ACCESS  read-only
   STATUS      current
   DESCRIPTION
      "Path: vrfV6Router.performance.qualityMonitor.lastLog.date"
   ::= {pr1645v2IpV6VrfRtrQMonEntry 673120256}

pr1645v2IpV6VrfRtrQMonAlarm OBJECT-TYPE
   SYNTAX      Integer32
   MAX-ACCESS  read-only
   STATUS      current
   DESCRIPTION
      "Path: vrfV6Router.performance.qualityMonitor.alarm

       Bit meanings:
               bit 0 = loss,
               bit 1 = delayAvrg,
               bit 2 = delayMax,
               bit 3 = delayMinMax,
               bit 4 = jitterAvrg,
               bit 5 = jitterPosMax,
               bit 6 = jitterNegMax,
               bit 7 = lossUp,
               bit 8 = jitterUpAvrg,
               bit 9 = jitterUpPosMax,
               bit 10 = jitterUpNegMax,
               bit 11 = lossDown,
               bit 12 = jitterDownAvrg,
               bit 13 = jitterDownPosMax,
               bit 14 = jitterDownNegMax,
               bit 15 = delayUpAvrg,
               bit 16 = delayUpMax,
               bit 17 = delayDownAvrg,
               bit 18 = delayDownMax,
               bit 19 = bfdCtrl"
   ::= {pr1645v2IpV6VrfRtrQMonEntry 251658240}

pr1645v2IpV6VrfRtrQMonLastError OBJECT-TYPE
   SYNTAX      DisplayString
   MAX-ACCESS  read-only
   STATUS      current
   DESCRIPTION
      "Path: vrfV6Router.performance.qualityMonitor.lastError"
   ::= {pr1645v2IpV6VrfRtrQMonEntry 318767104}

pr1645v2IpV6VrfRtrQMonLogging OBJECT-TYPE
   SYNTAX      SEQUENCE OF Pr1645v2IpV6VrfRtrQMonLoggingEntry
   MAX-ACCESS  not-accessible
   STATUS      current
   DESCRIPTION
      ""
   ::= {pr1645v2IpV6VrfRtrQMon 335544320}

pr1645v2IpV6VrfRtrQMonLoggingEntry OBJECT-TYPE
   SYNTAX      Pr1645v2IpV6VrfRtrQMonLoggingEntry
   MAX-ACCESS  not-accessible
   STATUS      current
   DESCRIPTION
      ""
   INDEX      { pr1645v2IpV6VrfRtrQMonLoggingGlobalIx,
                pr1645v2IpV6VrfRtrQMonTableIx,
                pr1645v2IpV6VrfRtrQMonLoggingTableIx }
   ::= {pr1645v2IpV6VrfRtrQMonLogging 1}

Pr1645v2IpV6VrfRtrQMonLoggingEntry ::=
   SEQUENCE
      {
      pr1645v2IpV6VrfRtrQMonLoggingGlobalIx
         GlobalIndex,
      pr1645v2IpV6VrfRtrQMonLoggingTableIx
         TableIndex,
      pr1645v2IpV6VrfRtrQMonLoggingSysUpTime
         TimeTicks,
      pr1645v2IpV6VrfRtrQMonLoggingNbrTxPckt
         Counter32,
      pr1645v2IpV6VrfRtrQMonLoggingNbrRxPckt
         Counter32,
      pr1645v2IpV6VrfRtrQMonLoggingError
         Counter32,
      pr1645v2IpV6VrfRtrQMonLoggingLoss
         Counter32,
      pr1645v2IpV6VrfRtrQMonLoggingLossDelay
         Counter32,
      pr1645v2IpV6VrfRtrQMonLoggingDelayMin
         Integer32,
      pr1645v2IpV6VrfRtrQMonLoggingDelayAvrg
         Integer32,
      pr1645v2IpV6VrfRtrQMonLoggingDelayMax
         Integer32,
      pr1645v2IpV6VrfRtrQMonLoggingJitterNegMax
         Integer32,
      pr1645v2IpV6VrfRtrQMonLoggingJitterAvrg
         Integer32,
      pr1645v2IpV6VrfRtrQMonLoggingJitterPosMax
         Integer32,
      pr1645v2IpV6VrfRtrQMonLoggingUpDownStatus
         INTEGER,
      pr1645v2IpV6VrfRtrQMonLoggingUpDownLossUp
         Counter32,
      pr1645v2IpV6VrfRtrQMonLoggingUpDownLossDelayUp
         Counter32,
      pr1645v2IpV6VrfRtrQMonLoggingUpDownDelayUpMin
         Integer32,
      pr1645v2IpV6VrfRtrQMonLoggingUpDownDelayUpAvrg
         Integer32,
      pr1645v2IpV6VrfRtrQMonLoggingUpDownDelayUpMax
         Integer32,
      pr1645v2IpV6VrfRtrQMonLoggingUpDownJitterUpNegMax
         Integer32,
      pr1645v2IpV6VrfRtrQMonLoggingUpDownJitterUpAvrg
         Integer32,
      pr1645v2IpV6VrfRtrQMonLoggingUpDownJitterUpPosMax
         Integer32,
      pr1645v2IpV6VrfRtrQMonLoggingUpDownLossDown
         Counter32,
      pr1645v2IpV6VrfRtrQMonLoggingUpDownLossDelayDown
         Counter32,
      pr1645v2IpV6VrfRtrQMonLoggingUpDownDelayDownMin
         Integer32,
      pr1645v2IpV6VrfRtrQMonLoggingUpDownDelayDownAvrg
         Integer32,
      pr1645v2IpV6VrfRtrQMonLoggingUpDownDelayDownMax
         Integer32,
      pr1645v2IpV6VrfRtrQMonLoggingUpDownJitterDownNegMax
         Integer32,
      pr1645v2IpV6VrfRtrQMonLoggingUpDownJitterDownAvrg
         Integer32,
      pr1645v2IpV6VrfRtrQMonLoggingUpDownJitterDownPosMax
         Integer32,
      pr1645v2IpV6VrfRtrQMonLoggingDate
         DisplayString
      }

pr1645v2IpV6VrfRtrQMonLoggingGlobalIx OBJECT-TYPE
   SYNTAX      GlobalIndex
   MAX-ACCESS  not-accessible
   STATUS      current
   DESCRIPTION
      "The value of the tlsCntTreeGlobalIndex of the MANAGED OBJECT."
   ::= {pr1645v2IpV6VrfRtrQMonLoggingEntry 10}

pr1645v2IpV6VrfRtrQMonLoggingTableIx OBJECT-TYPE
   SYNTAX      TableIndex
   MAX-ACCESS  not-accessible
   STATUS      current
   DESCRIPTION
      ""
   ::= {pr1645v2IpV6VrfRtrQMonLoggingEntry 11}

pr1645v2IpV6VrfRtrQMonLoggingSysUpTime OBJECT-TYPE
   SYNTAX      TimeTicks
   MAX-ACCESS  read-only
   STATUS      current
   DESCRIPTION
      "Path: vrfV6Router.performance.qualityMonitor.logging.sysUpTime

       Time in centi-second."
   ::= {pr1645v2IpV6VrfRtrQMonLoggingEntry 16777216}

pr1645v2IpV6VrfRtrQMonLoggingNbrTxPckt OBJECT-TYPE
   SYNTAX      Counter32
   MAX-ACCESS  read-only
   STATUS      current
   DESCRIPTION
      "Path: vrfV6Router.performance.qualityMonitor.logging.nbrOfTxPackets

       32 bit unsigned wrappable counter."
   ::= {pr1645v2IpV6VrfRtrQMonLoggingEntry 50331648}

pr1645v2IpV6VrfRtrQMonLoggingNbrRxPckt OBJECT-TYPE
   SYNTAX      Counter32
   MAX-ACCESS  read-only
   STATUS      current
   DESCRIPTION
      "Path: vrfV6Router.performance.qualityMonitor.logging.nbrOfRxPackets

       32 bit unsigned wrappable counter."
   ::= {pr1645v2IpV6VrfRtrQMonLoggingEntry 67108864}

pr1645v2IpV6VrfRtrQMonLoggingError OBJECT-TYPE
   SYNTAX      Counter32
   MAX-ACCESS  read-only
   STATUS      current
   DESCRIPTION
      "Path: vrfV6Router.performance.qualityMonitor.logging.error

       32 bit unsigned wrappable counter."
   ::= {pr1645v2IpV6VrfRtrQMonLoggingEntry 285212672}

pr1645v2IpV6VrfRtrQMonLoggingLoss OBJECT-TYPE
   SYNTAX      Counter32
   MAX-ACCESS  read-only
   STATUS      current
   DESCRIPTION
      "Path: vrfV6Router.performance.qualityMonitor.logging.loss

       32 bit unsigned wrappable counter."
   ::= {pr1645v2IpV6VrfRtrQMonLoggingEntry 100663296}

pr1645v2IpV6VrfRtrQMonLoggingLossDelay OBJECT-TYPE
   SYNTAX      Counter32
   MAX-ACCESS  read-only
   STATUS      current
   DESCRIPTION
      "Path: vrfV6Router.performance.qualityMonitor.logging.lossDelay

       32 bit unsigned wrappable counter."
   ::= {pr1645v2IpV6VrfRtrQMonLoggingEntry 268435456}

pr1645v2IpV6VrfRtrQMonLoggingDelayMin OBJECT-TYPE
   SYNTAX      Integer32
   MAX-ACCESS  read-only
   STATUS      current
   DESCRIPTION
      "Path: vrfV6Router.performance.qualityMonitor.logging.delayMin

       unit name = sec
       formula = 1000 / ; 1000 *"
   ::= {pr1645v2IpV6VrfRtrQMonLoggingEntry 184549376}

pr1645v2IpV6VrfRtrQMonLoggingDelayAvrg OBJECT-TYPE
   SYNTAX      Integer32
   MAX-ACCESS  read-only
   STATUS      current
   DESCRIPTION
      "Path: vrfV6Router.performance.qualityMonitor.logging.delayAvrg

       unit name = sec
       formula = 1000 / ; 1000 *"
   ::= {pr1645v2IpV6VrfRtrQMonLoggingEntry 117440512}

pr1645v2IpV6VrfRtrQMonLoggingDelayMax OBJECT-TYPE
   SYNTAX      Integer32
   MAX-ACCESS  read-only
   STATUS      current
   DESCRIPTION
      "Path: vrfV6Router.performance.qualityMonitor.logging.delayMax

       unit name = sec
       formula = 1000 / ; 1000 *"
   ::= {pr1645v2IpV6VrfRtrQMonLoggingEntry 134217728}

pr1645v2IpV6VrfRtrQMonLoggingJitterNegMax OBJECT-TYPE
   SYNTAX      Integer32
   MAX-ACCESS  read-only
   STATUS      current
   DESCRIPTION
      "Path: vrfV6Router.performance.qualityMonitor.logging.jitterNegMax

       unit name = sec
       formula = 1000 / ; 1000 *"
   ::= {pr1645v2IpV6VrfRtrQMonLoggingEntry 234881024}

pr1645v2IpV6VrfRtrQMonLoggingJitterAvrg OBJECT-TYPE
   SYNTAX      Integer32
   MAX-ACCESS  read-only
   STATUS      current
   DESCRIPTION
      "Path: vrfV6Router.performance.qualityMonitor.logging.jitterAvrg

       unit name = sec
       formula = 1000 / ; 1000 *"
   ::= {pr1645v2IpV6VrfRtrQMonLoggingEntry 150994944}

pr1645v2IpV6VrfRtrQMonLoggingJitterPosMax OBJECT-TYPE
   SYNTAX      Integer32
   MAX-ACCESS  read-only
   STATUS      current
   DESCRIPTION
      "Path: vrfV6Router.performance.qualityMonitor.logging.jitterPosMax

       unit name = sec
       formula = 1000 / ; 1000 *"
   ::= {pr1645v2IpV6VrfRtrQMonLoggingEntry 167772160}

pr1645v2IpV6VrfRtrQMonLoggingUpDownStatus OBJECT-TYPE
   SYNTAX      INTEGER
               {
               notInUse (3),
               onlyJitter (1),
               jitterAndLoss (2),
               all (4),
               onlyLoss (8)
               }
   MAX-ACCESS  read-only
   STATUS      current
   DESCRIPTION
      "Path: vrfV6Router.performance.qualityMonitor.logging.upDown.status

       Possibilities:
               notInUse   (3)
               onlyJitter   (1)
               jitterAndLoss   (2)
               all   (4)
               onlyLoss   (8)"
   ::= {pr1645v2IpV6VrfRtrQMonLoggingEntry 504627200}

pr1645v2IpV6VrfRtrQMonLoggingUpDownLossUp OBJECT-TYPE
   SYNTAX      Counter32
   MAX-ACCESS  read-only
   STATUS      current
   DESCRIPTION
      "Path: vrfV6Router.performance.qualityMonitor.logging.upDown.lossUp

       32 bit unsigned wrappable counter."
   ::= {pr1645v2IpV6VrfRtrQMonLoggingEntry 503971840}

pr1645v2IpV6VrfRtrQMonLoggingUpDownLossDelayUp OBJECT-TYPE
   SYNTAX      Counter32
   MAX-ACCESS  read-only
   STATUS      current
   DESCRIPTION
      "Path: vrfV6Router.performance.qualityMonitor.logging.upDown.lossDelayUp

       32 bit unsigned wrappable counter."
   ::= {pr1645v2IpV6VrfRtrQMonLoggingEntry 504037376}

pr1645v2IpV6VrfRtrQMonLoggingUpDownDelayUpMin OBJECT-TYPE
   SYNTAX      Integer32
   MAX-ACCESS  read-only
   STATUS      current
   DESCRIPTION
      "Path: vrfV6Router.performance.qualityMonitor.logging.upDown.delayUpMin

       unit name = sec
       formula = 1000 / ; 1000 *"
   ::= {pr1645v2IpV6VrfRtrQMonLoggingEntry 505282560}

pr1645v2IpV6VrfRtrQMonLoggingUpDownDelayUpAvrg OBJECT-TYPE
   SYNTAX      Integer32
   MAX-ACCESS  read-only
   STATUS      current
   DESCRIPTION
      "Path: vrfV6Router.performance.qualityMonitor.logging.upDown.delayUpAvrg

       unit name = sec
       formula = 1000 / ; 1000 *"
   ::= {pr1645v2IpV6VrfRtrQMonLoggingEntry 505348096}

pr1645v2IpV6VrfRtrQMonLoggingUpDownDelayUpMax OBJECT-TYPE
   SYNTAX      Integer32
   MAX-ACCESS  read-only
   STATUS      current
   DESCRIPTION
      "Path: vrfV6Router.performance.qualityMonitor.logging.upDown.delayUpMax

       unit name = sec
       formula = 1000 / ; 1000 *"
   ::= {pr1645v2IpV6VrfRtrQMonLoggingEntry 505413632}

pr1645v2IpV6VrfRtrQMonLoggingUpDownJitterUpNegMax OBJECT-TYPE
   SYNTAX      Integer32
   MAX-ACCESS  read-only
   STATUS      current
   DESCRIPTION
      "Path: vrfV6Router.performance.qualityMonitor.logging.upDown.jitterUpNegMax

       unit name = sec
       formula = 1000 / ; 1000 *"
   ::= {pr1645v2IpV6VrfRtrQMonLoggingEntry 503382016}

pr1645v2IpV6VrfRtrQMonLoggingUpDownJitterUpAvrg OBJECT-TYPE
   SYNTAX      Integer32
   MAX-ACCESS  read-only
   STATUS      current
   DESCRIPTION
      "Path: vrfV6Router.performance.qualityMonitor.logging.upDown.jitterUpAvrg

       unit name = sec
       formula = 1000 / ; 1000 *"
   ::= {pr1645v2IpV6VrfRtrQMonLoggingEntry 503447552}

pr1645v2IpV6VrfRtrQMonLoggingUpDownJitterUpPosMax OBJECT-TYPE
   SYNTAX      Integer32
   MAX-ACCESS  read-only
   STATUS      current
   DESCRIPTION
      "Path: vrfV6Router.performance.qualityMonitor.logging.upDown.jitterUpPosMax

       unit name = sec
       formula = 1000 / ; 1000 *"
   ::= {pr1645v2IpV6VrfRtrQMonLoggingEntry 503513088}

pr1645v2IpV6VrfRtrQMonLoggingUpDownLossDown OBJECT-TYPE
   SYNTAX      Counter32
   MAX-ACCESS  read-only
   STATUS      current
   DESCRIPTION
      "Path: vrfV6Router.performance.qualityMonitor.logging.upDown.lossDown

       32 bit unsigned wrappable counter."
   ::= {pr1645v2IpV6VrfRtrQMonLoggingEntry 504102912}

pr1645v2IpV6VrfRtrQMonLoggingUpDownLossDelayDown OBJECT-TYPE
   SYNTAX      Counter32
   MAX-ACCESS  read-only
   STATUS      current
   DESCRIPTION
      "Path: vrfV6Router.performance.qualityMonitor.logging.upDown.lossDelayDown

       32 bit unsigned wrappable counter."
   ::= {pr1645v2IpV6VrfRtrQMonLoggingEntry 504168448}

pr1645v2IpV6VrfRtrQMonLoggingUpDownDelayDownMin OBJECT-TYPE
   SYNTAX      Integer32
   MAX-ACCESS  read-only
   STATUS      current
   DESCRIPTION
      "Path: vrfV6Router.performance.qualityMonitor.logging.upDown.delayDownMin

       unit name = sec
       formula = 1000 / ; 1000 *"
   ::= {pr1645v2IpV6VrfRtrQMonLoggingEntry 505610240}

pr1645v2IpV6VrfRtrQMonLoggingUpDownDelayDownAvrg OBJECT-TYPE
   SYNTAX      Integer32
   MAX-ACCESS  read-only
   STATUS      current
   DESCRIPTION
      "Path: vrfV6Router.performance.qualityMonitor.logging.upDown.delayDownAvrg

       unit name = sec
       formula = 1000 / ; 1000 *"
   ::= {pr1645v2IpV6VrfRtrQMonLoggingEntry 505675776}

pr1645v2IpV6VrfRtrQMonLoggingUpDownDelayDownMax OBJECT-TYPE
   SYNTAX      Integer32
   MAX-ACCESS  read-only
   STATUS      current
   DESCRIPTION
      "Path: vrfV6Router.performance.qualityMonitor.logging.upDown.delayDownMax

       unit name = sec
       formula = 1000 / ; 1000 *"
   ::= {pr1645v2IpV6VrfRtrQMonLoggingEntry 505741312}

pr1645v2IpV6VrfRtrQMonLoggingUpDownJitterDownNegMax OBJECT-TYPE
   SYNTAX      Integer32
   MAX-ACCESS  read-only
   STATUS      current
   DESCRIPTION
      "Path: vrfV6Router.performance.qualityMonitor.logging.upDown.jitterDownNegMax

       unit name = sec
       formula = 1000 / ; 1000 *"
   ::= {pr1645v2IpV6VrfRtrQMonLoggingEntry 503578624}

pr1645v2IpV6VrfRtrQMonLoggingUpDownJitterDownAvrg OBJECT-TYPE
   SYNTAX      Integer32
   MAX-ACCESS  read-only
   STATUS      current
   DESCRIPTION
      "Path: vrfV6Router.performance.qualityMonitor.logging.upDown.jitterDownAvrg

       unit name = sec
       formula = 1000 / ; 1000 *"
   ::= {pr1645v2IpV6VrfRtrQMonLoggingEntry 503644160}

pr1645v2IpV6VrfRtrQMonLoggingUpDownJitterDownPosMax OBJECT-TYPE
   SYNTAX      Integer32
   MAX-ACCESS  read-only
   STATUS      current
   DESCRIPTION
      "Path: vrfV6Router.performance.qualityMonitor.logging.upDown.jitterDownPosMax

       unit name = sec
       formula = 1000 / ; 1000 *"
   ::= {pr1645v2IpV6VrfRtrQMonLoggingEntry 503709696}

pr1645v2IpV6VrfRtrQMonLoggingDate OBJECT-TYPE
   SYNTAX      DisplayString
   MAX-ACCESS  read-only
   STATUS      current
   DESCRIPTION
      "Path: vrfV6Router.performance.qualityMonitor.logging.date"
   ::= {pr1645v2IpV6VrfRtrQMonLoggingEntry 520093696}

pr1645v2IpV6VrfRtrQMonLoggingBin OBJECT-TYPE
   SYNTAX      SEQUENCE OF Pr1645v2IpV6VrfRtrQMonLoggingBinEntry
   MAX-ACCESS  not-accessible
   STATUS      current
   DESCRIPTION
      ""
   ::= {pr1645v2IpV6VrfRtrQMon 337641472}

pr1645v2IpV6VrfRtrQMonLoggingBinEntry OBJECT-TYPE
   SYNTAX      Pr1645v2IpV6VrfRtrQMonLoggingBinEntry
   MAX-ACCESS  not-accessible
   STATUS      current
   DESCRIPTION
      ""
   INDEX      { pr1645v2IpV6VrfRtrQMonLoggingBinGlobalIx,
                pr1645v2IpV6VrfRtrQMonTableIx,
                pr1645v2IpV6VrfRtrQMonLoggingTableIx,
                pr1645v2IpV6VrfRtrQMonLoggingBinTableIx }
   ::= {pr1645v2IpV6VrfRtrQMonLoggingBin 1}

Pr1645v2IpV6VrfRtrQMonLoggingBinEntry ::=
   SEQUENCE
      {
      pr1645v2IpV6VrfRtrQMonLoggingBinGlobalIx
         GlobalIndex,
      pr1645v2IpV6VrfRtrQMonLoggingBinTableIx
         TableIndex,
      pr1645v2IpV6VrfRtrQMonLoggingBinName
         INTEGER,
      pr1645v2IpV6VrfRtrQMonLoggingBinType
         INTEGER,
      pr1645v2IpV6VrfRtrQMonLoggingBinMinMin
         Counter32,
      pr1645v2IpV6VrfRtrQMonLoggingBinMin
         Integer32,
      pr1645v2IpV6VrfRtrQMonLoggingBinMinBin1
         Counter32,
      pr1645v2IpV6VrfRtrQMonLoggingBinBin2
         Counter32,
      pr1645v2IpV6VrfRtrQMonLoggingBinBin3
         Counter32,
      pr1645v2IpV6VrfRtrQMonLoggingBinBin4
         Counter32,
      pr1645v2IpV6VrfRtrQMonLoggingBinBin5
         Counter32,
      pr1645v2IpV6VrfRtrQMonLoggingBinBin6
         Counter32,
      pr1645v2IpV6VrfRtrQMonLoggingBinBin7
         Counter32,
      pr1645v2IpV6VrfRtrQMonLoggingBinMaxBin8
         Counter32,
      pr1645v2IpV6VrfRtrQMonLoggingBinMax
         Integer32,
      pr1645v2IpV6VrfRtrQMonLoggingBinPlusMax
         Counter32
      }

pr1645v2IpV6VrfRtrQMonLoggingBinGlobalIx OBJECT-TYPE
   SYNTAX      GlobalIndex
   MAX-ACCESS  not-accessible
   STATUS      current
   DESCRIPTION
      "The value of the tlsCntTreeGlobalIndex of the MANAGED OBJECT."
   ::= {pr1645v2IpV6VrfRtrQMonLoggingBinEntry 10}

pr1645v2IpV6VrfRtrQMonLoggingBinTableIx OBJECT-TYPE
   SYNTAX      TableIndex
   MAX-ACCESS  not-accessible
   STATUS      current
   DESCRIPTION
      ""
   ::= {pr1645v2IpV6VrfRtrQMonLoggingBinEntry 11}

pr1645v2IpV6VrfRtrQMonLoggingBinName OBJECT-TYPE
   SYNTAX      INTEGER
               {
               delay (1),
               delayUp (2),
               delayDown (3),
               jitter (4),
               jitterUp (5),
               jitterDown (6)
               }
   MAX-ACCESS  read-only
   STATUS      current
   DESCRIPTION
      "Path: vrfV6Router.performance.qualityMonitor.logging.bin.name

       Possibilities:
               delay   (1)
               delayUp   (2)
               delayDown   (3)
               jitter   (4)
               jitterUp   (5)
               jitterDown   (6)"
   ::= {pr1645v2IpV6VrfRtrQMonLoggingBinEntry 503316480}

pr1645v2IpV6VrfRtrQMonLoggingBinType OBJECT-TYPE
   SYNTAX      INTEGER
               {
               fd (1),
               fdr (2),
               notInUse (3),
               ifdv (4)
               }
   MAX-ACCESS  read-only
   STATUS      current
   DESCRIPTION
      "Path: vrfV6Router.performance.qualityMonitor.logging.bin.type

       Possibilities:
               fd   (1)
               fdr   (2)
               notInUse   (3)
               ifdv   (4)"
   ::= {pr1645v2IpV6VrfRtrQMonLoggingBinEntry 520093696}

pr1645v2IpV6VrfRtrQMonLoggingBinMinMin OBJECT-TYPE
   SYNTAX      Counter32
   MAX-ACCESS  read-only
   STATUS      current
   DESCRIPTION
      "Path: vrfV6Router.performance.qualityMonitor.logging.bin.minMin

       32 bit unsigned wrappable counter."
   ::= {pr1645v2IpV6VrfRtrQMonLoggingBinEntry 16777216}

pr1645v2IpV6VrfRtrQMonLoggingBinMin OBJECT-TYPE
   SYNTAX      Integer32
   MAX-ACCESS  read-only
   STATUS      current
   DESCRIPTION
      "Path: vrfV6Router.performance.qualityMonitor.logging.bin.min

       unit name = sec
       formula = 1000 / ; 1000 *"
   ::= {pr1645v2IpV6VrfRtrQMonLoggingBinEntry 352321536}

pr1645v2IpV6VrfRtrQMonLoggingBinMinBin1 OBJECT-TYPE
   SYNTAX      Counter32
   MAX-ACCESS  read-only
   STATUS      current
   DESCRIPTION
      "Path: vrfV6Router.performance.qualityMonitor.logging.bin.minBin1

       32 bit unsigned wrappable counter."
   ::= {pr1645v2IpV6VrfRtrQMonLoggingBinEntry 33554432}

pr1645v2IpV6VrfRtrQMonLoggingBinBin2 OBJECT-TYPE
   SYNTAX      Counter32
   MAX-ACCESS  read-only
   STATUS      current
   DESCRIPTION
      "Path: vrfV6Router.performance.qualityMonitor.logging.bin.bin2

       32 bit unsigned wrappable counter."
   ::= {pr1645v2IpV6VrfRtrQMonLoggingBinEntry 50331648}

pr1645v2IpV6VrfRtrQMonLoggingBinBin3 OBJECT-TYPE
   SYNTAX      Counter32
   MAX-ACCESS  read-only
   STATUS      current
   DESCRIPTION
      "Path: vrfV6Router.performance.qualityMonitor.logging.bin.bin3

       32 bit unsigned wrappable counter."
   ::= {pr1645v2IpV6VrfRtrQMonLoggingBinEntry 67108864}

pr1645v2IpV6VrfRtrQMonLoggingBinBin4 OBJECT-TYPE
   SYNTAX      Counter32
   MAX-ACCESS  read-only
   STATUS      current
   DESCRIPTION
      "Path: vrfV6Router.performance.qualityMonitor.logging.bin.bin4

       32 bit unsigned wrappable counter."
   ::= {pr1645v2IpV6VrfRtrQMonLoggingBinEntry 83886080}

pr1645v2IpV6VrfRtrQMonLoggingBinBin5 OBJECT-TYPE
   SYNTAX      Counter32
   MAX-ACCESS  read-only
   STATUS      current
   DESCRIPTION
      "Path: vrfV6Router.performance.qualityMonitor.logging.bin.bin5

       32 bit unsigned wrappable counter."
   ::= {pr1645v2IpV6VrfRtrQMonLoggingBinEntry 100663296}

pr1645v2IpV6VrfRtrQMonLoggingBinBin6 OBJECT-TYPE
   SYNTAX      Counter32
   MAX-ACCESS  read-only
   STATUS      current
   DESCRIPTION
      "Path: vrfV6Router.performance.qualityMonitor.logging.bin.bin6

       32 bit unsigned wrappable counter."
   ::= {pr1645v2IpV6VrfRtrQMonLoggingBinEntry 117440512}

pr1645v2IpV6VrfRtrQMonLoggingBinBin7 OBJECT-TYPE
   SYNTAX      Counter32
   MAX-ACCESS  read-only
   STATUS      current
   DESCRIPTION
      "Path: vrfV6Router.performance.qualityMonitor.logging.bin.bin7

       32 bit unsigned wrappable counter."
   ::= {pr1645v2IpV6VrfRtrQMonLoggingBinEntry 134217728}

pr1645v2IpV6VrfRtrQMonLoggingBinMaxBin8 OBJECT-TYPE
   SYNTAX      Counter32
   MAX-ACCESS  read-only
   STATUS      current
   DESCRIPTION
      "Path: vrfV6Router.performance.qualityMonitor.logging.bin.maxBin8

       32 bit unsigned wrappable counter."
   ::= {pr1645v2IpV6VrfRtrQMonLoggingBinEntry 150994944}

pr1645v2IpV6VrfRtrQMonLoggingBinMax OBJECT-TYPE
   SYNTAX      Integer32
   MAX-ACCESS  read-only
   STATUS      current
   DESCRIPTION
      "Path: vrfV6Router.performance.qualityMonitor.logging.bin.max

       unit name = sec
       formula = 1000 / ; 1000 *"
   ::= {pr1645v2IpV6VrfRtrQMonLoggingBinEntry 369098752}

pr1645v2IpV6VrfRtrQMonLoggingBinPlusMax OBJECT-TYPE
   SYNTAX      Counter32
   MAX-ACCESS  read-only
   STATUS      current
   DESCRIPTION
      "Path: vrfV6Router.performance.qualityMonitor.logging.bin.plusMax

       32 bit unsigned wrappable counter."
   ::= {pr1645v2IpV6VrfRtrQMonLoggingBinEntry 167772160}

pr1645v2IpV6VrfRtrQMonLastLogBin OBJECT-TYPE
   SYNTAX      SEQUENCE OF Pr1645v2IpV6VrfRtrQMonLastLogBinEntry
   MAX-ACCESS  not-accessible
   STATUS      current
   DESCRIPTION
      ""
   ::= {pr1645v2IpV6VrfRtrQMon 673185792}

pr1645v2IpV6VrfRtrQMonLastLogBinEntry OBJECT-TYPE
   SYNTAX      Pr1645v2IpV6VrfRtrQMonLastLogBinEntry
   MAX-ACCESS  not-accessible
   STATUS      current
   DESCRIPTION
      ""
   INDEX      { pr1645v2IpV6VrfRtrQMonLastLogBinGlobalIx,
                pr1645v2IpV6VrfRtrQMonTableIx,
                pr1645v2IpV6VrfRtrQMonLastLogBinTableIx }
   ::= {pr1645v2IpV6VrfRtrQMonLastLogBin 1}

Pr1645v2IpV6VrfRtrQMonLastLogBinEntry ::=
   SEQUENCE
      {
      pr1645v2IpV6VrfRtrQMonLastLogBinGlobalIx
         GlobalIndex,
      pr1645v2IpV6VrfRtrQMonLastLogBinTableIx
         TableIndex,
      pr1645v2IpV6VrfRtrQMonLastLogBinName
         INTEGER,
      pr1645v2IpV6VrfRtrQMonLastLogBinType
         INTEGER,
      pr1645v2IpV6VrfRtrQMonLastLogBinMinMin
         Counter32,
      pr1645v2IpV6VrfRtrQMonLastLogBinMin
         Integer32,
      pr1645v2IpV6VrfRtrQMonLastLogBinMinBin1
         Counter32,
      pr1645v2IpV6VrfRtrQMonLastLogBinBin2
         Counter32,
      pr1645v2IpV6VrfRtrQMonLastLogBinBin3
         Counter32,
      pr1645v2IpV6VrfRtrQMonLastLogBinBin4
         Counter32,
      pr1645v2IpV6VrfRtrQMonLastLogBinBin5
         Counter32,
      pr1645v2IpV6VrfRtrQMonLastLogBinBin6
         Counter32,
      pr1645v2IpV6VrfRtrQMonLastLogBinBin7
         Counter32,
      pr1645v2IpV6VrfRtrQMonLastLogBinMaxBin8
         Counter32,
      pr1645v2IpV6VrfRtrQMonLastLogBinMax
         Integer32,
      pr1645v2IpV6VrfRtrQMonLastLogBinPlusMax
         Counter32
      }

pr1645v2IpV6VrfRtrQMonLastLogBinGlobalIx OBJECT-TYPE
   SYNTAX      GlobalIndex
   MAX-ACCESS  not-accessible
   STATUS      current
   DESCRIPTION
      "The value of the tlsCntTreeGlobalIndex of the MANAGED OBJECT."
   ::= {pr1645v2IpV6VrfRtrQMonLastLogBinEntry 10}

pr1645v2IpV6VrfRtrQMonLastLogBinTableIx OBJECT-TYPE
   SYNTAX      TableIndex
   MAX-ACCESS  not-accessible
   STATUS      current
   DESCRIPTION
      ""
   ::= {pr1645v2IpV6VrfRtrQMonLastLogBinEntry 11}

pr1645v2IpV6VrfRtrQMonLastLogBinName OBJECT-TYPE
   SYNTAX      INTEGER
               {
               delay (1),
               delayUp (2),
               delayDown (3),
               jitter (4),
               jitterUp (5),
               jitterDown (6)
               }
   MAX-ACCESS  read-only
   STATUS      current
   DESCRIPTION
      "Path: vrfV6Router.performance.qualityMonitor.lastLog.bin.name

       Possibilities:
               delay   (1)
               delayUp   (2)
               delayDown   (3)
               jitter   (4)
               jitterUp   (5)
               jitterDown   (6)"
   ::= {pr1645v2IpV6VrfRtrQMonLastLogBinEntry 503316480}

pr1645v2IpV6VrfRtrQMonLastLogBinType OBJECT-TYPE
   SYNTAX      INTEGER
               {
               fd (1),
               fdr (2),
               notInUse (3),
               ifdv (4)
               }
   MAX-ACCESS  read-only
   STATUS      current
   DESCRIPTION
      "Path: vrfV6Router.performance.qualityMonitor.lastLog.bin.type

       Possibilities:
               fd   (1)
               fdr   (2)
               notInUse   (3)
               ifdv   (4)"
   ::= {pr1645v2IpV6VrfRtrQMonLastLogBinEntry 520093696}

pr1645v2IpV6VrfRtrQMonLastLogBinMinMin OBJECT-TYPE
   SYNTAX      Counter32
   MAX-ACCESS  read-only
   STATUS      current
   DESCRIPTION
      "Path: vrfV6Router.performance.qualityMonitor.lastLog.bin.minMin

       32 bit unsigned wrappable counter."
   ::= {pr1645v2IpV6VrfRtrQMonLastLogBinEntry 16777216}

pr1645v2IpV6VrfRtrQMonLastLogBinMin OBJECT-TYPE
   SYNTAX      Integer32
   MAX-ACCESS  read-only
   STATUS      current
   DESCRIPTION
      "Path: vrfV6Router.performance.qualityMonitor.lastLog.bin.min

       unit name = sec
       formula = 1000 / ; 1000 *"
   ::= {pr1645v2IpV6VrfRtrQMonLastLogBinEntry 352321536}

pr1645v2IpV6VrfRtrQMonLastLogBinMinBin1 OBJECT-TYPE
   SYNTAX      Counter32
   MAX-ACCESS  read-only
   STATUS      current
   DESCRIPTION
      "Path: vrfV6Router.performance.qualityMonitor.lastLog.bin.minBin1

       32 bit unsigned wrappable counter."
   ::= {pr1645v2IpV6VrfRtrQMonLastLogBinEntry 33554432}

pr1645v2IpV6VrfRtrQMonLastLogBinBin2 OBJECT-TYPE
   SYNTAX      Counter32
   MAX-ACCESS  read-only
   STATUS      current
   DESCRIPTION
      "Path: vrfV6Router.performance.qualityMonitor.lastLog.bin.bin2

       32 bit unsigned wrappable counter."
   ::= {pr1645v2IpV6VrfRtrQMonLastLogBinEntry 50331648}

pr1645v2IpV6VrfRtrQMonLastLogBinBin3 OBJECT-TYPE
   SYNTAX      Counter32
   MAX-ACCESS  read-only
   STATUS      current
   DESCRIPTION
      "Path: vrfV6Router.performance.qualityMonitor.lastLog.bin.bin3

       32 bit unsigned wrappable counter."
   ::= {pr1645v2IpV6VrfRtrQMonLastLogBinEntry 67108864}

pr1645v2IpV6VrfRtrQMonLastLogBinBin4 OBJECT-TYPE
   SYNTAX      Counter32
   MAX-ACCESS  read-only
   STATUS      current
   DESCRIPTION
      "Path: vrfV6Router.performance.qualityMonitor.lastLog.bin.bin4

       32 bit unsigned wrappable counter."
   ::= {pr1645v2IpV6VrfRtrQMonLastLogBinEntry 83886080}

pr1645v2IpV6VrfRtrQMonLastLogBinBin5 OBJECT-TYPE
   SYNTAX      Counter32
   MAX-ACCESS  read-only
   STATUS      current
   DESCRIPTION
      "Path: vrfV6Router.performance.qualityMonitor.lastLog.bin.bin5

       32 bit unsigned wrappable counter."
   ::= {pr1645v2IpV6VrfRtrQMonLastLogBinEntry 100663296}

pr1645v2IpV6VrfRtrQMonLastLogBinBin6 OBJECT-TYPE
   SYNTAX      Counter32
   MAX-ACCESS  read-only
   STATUS      current
   DESCRIPTION
      "Path: vrfV6Router.performance.qualityMonitor.lastLog.bin.bin6

       32 bit unsigned wrappable counter."
   ::= {pr1645v2IpV6VrfRtrQMonLastLogBinEntry 117440512}

pr1645v2IpV6VrfRtrQMonLastLogBinBin7 OBJECT-TYPE
   SYNTAX      Counter32
   MAX-ACCESS  read-only
   STATUS      current
   DESCRIPTION
      "Path: vrfV6Router.performance.qualityMonitor.lastLog.bin.bin7

       32 bit unsigned wrappable counter."
   ::= {pr1645v2IpV6VrfRtrQMonLastLogBinEntry 134217728}

pr1645v2IpV6VrfRtrQMonLastLogBinMaxBin8 OBJECT-TYPE
   SYNTAX      Counter32
   MAX-ACCESS  read-only
   STATUS      current
   DESCRIPTION
      "Path: vrfV6Router.performance.qualityMonitor.lastLog.bin.maxBin8

       32 bit unsigned wrappable counter."
   ::= {pr1645v2IpV6VrfRtrQMonLastLogBinEntry 150994944}

pr1645v2IpV6VrfRtrQMonLastLogBinMax OBJECT-TYPE
   SYNTAX      Integer32
   MAX-ACCESS  read-only
   STATUS      current
   DESCRIPTION
      "Path: vrfV6Router.performance.qualityMonitor.lastLog.bin.max

       unit name = sec
       formula = 1000 / ; 1000 *"
   ::= {pr1645v2IpV6VrfRtrQMonLastLogBinEntry 369098752}

pr1645v2IpV6VrfRtrQMonLastLogBinPlusMax OBJECT-TYPE
   SYNTAX      Counter32
   MAX-ACCESS  read-only
   STATUS      current
   DESCRIPTION
      "Path: vrfV6Router.performance.qualityMonitor.lastLog.bin.plusMax

       32 bit unsigned wrappable counter."
   ::= {pr1645v2IpV6VrfRtrQMonLastLogBinEntry 167772160}


pr1645v2IpV6VrfRtrUdpServer OBJECT IDENTIFIER ::= {pr1645v2IpV6VrfRtr 55}

pr1645v2IpV6VrfRtrUdpServerSSCTable OBJECT-TYPE
   SYNTAX      SEQUENCE OF Pr1645v2IpV6VrfRtrUdpServerEntry
   MAX-ACCESS  not-accessible
   STATUS      current
   DESCRIPTION
      "udpServer"
   ::= {pr1645v2IpV6VrfRtrUdpServer 1}

pr1645v2IpV6VrfRtrUdpServerEntry OBJECT-TYPE
   SYNTAX      Pr1645v2IpV6VrfRtrUdpServerEntry
   MAX-ACCESS  not-accessible
   STATUS      current
   DESCRIPTION
      ""
   INDEX      { pr1645v2IpV6VrfRtrUdpServerGlobalIx,
                pr1645v2IpV6VrfRtrUdpServerTableIx }
   ::= {pr1645v2IpV6VrfRtrUdpServerSSCTable 1}

Pr1645v2IpV6VrfRtrUdpServerEntry ::=
   SEQUENCE
      {
      pr1645v2IpV6VrfRtrUdpServerGlobalIx
         GlobalIndex,
      pr1645v2IpV6VrfRtrUdpServerTableIx
         TableIndex,
      pr1645v2IpV6VrfRtrUdpServerDestinationPort
         Integer32,
      pr1645v2IpV6VrfRtrUdpServerActiveSessions
         Gauge32,
      pr1645v2IpV6VrfRtrUdpServerNbrPckt
         Counter64
      }

pr1645v2IpV6VrfRtrUdpServerGlobalIx OBJECT-TYPE
   SYNTAX      GlobalIndex
   MAX-ACCESS  not-accessible
   STATUS      current
   DESCRIPTION
      "The value of the tlsCntTreeGlobalIndex of the MANAGED OBJECT."
   ::= {pr1645v2IpV6VrfRtrUdpServerEntry 10}

pr1645v2IpV6VrfRtrUdpServerTableIx OBJECT-TYPE
   SYNTAX      TableIndex
   MAX-ACCESS  not-accessible
   STATUS      current
   DESCRIPTION
      ""
   ::= {pr1645v2IpV6VrfRtrUdpServerEntry 11}

pr1645v2IpV6VrfRtrUdpServerDestinationPort OBJECT-TYPE
   SYNTAX      Integer32
   MAX-ACCESS  read-only
   STATUS      current
   DESCRIPTION
      "Path: vrfV6Router.performance.udpServer.destinationPort"
   ::= {pr1645v2IpV6VrfRtrUdpServerEntry 16777216}

pr1645v2IpV6VrfRtrUdpServerActiveSessions OBJECT-TYPE
   SYNTAX      Gauge32
   MAX-ACCESS  read-only
   STATUS      current
   DESCRIPTION
      "Path: vrfV6Router.performance.udpServer.activeSessions

       32 bit unsigned gauge value."
   ::= {pr1645v2IpV6VrfRtrUdpServerEntry 33554432}

pr1645v2IpV6VrfRtrUdpServerNbrPckt OBJECT-TYPE
   SYNTAX      Counter64
   MAX-ACCESS  read-only
   STATUS      current
   DESCRIPTION
      "Path: vrfV6Router.performance.udpServer.nbrOfPackets

       64 bit unsigned wrappable counter."
   ::= {pr1645v2IpV6VrfRtrUdpServerEntry 50331648}

pr1645v2IpV6VrfRtrUdpServerSessions OBJECT-TYPE
   SYNTAX      SEQUENCE OF Pr1645v2IpV6VrfRtrUdpServerSessionsEntry
   MAX-ACCESS  not-accessible
   STATUS      current
   DESCRIPTION
      ""
   ::= {pr1645v2IpV6VrfRtrUdpServer 67108864}

pr1645v2IpV6VrfRtrUdpServerSessionsEntry OBJECT-TYPE
   SYNTAX      Pr1645v2IpV6VrfRtrUdpServerSessionsEntry
   MAX-ACCESS  not-accessible
   STATUS      current
   DESCRIPTION
      ""
   INDEX      { pr1645v2IpV6VrfRtrUdpServerSessionsGlobalIx,
                pr1645v2IpV6VrfRtrUdpServerTableIx,
                pr1645v2IpV6VrfRtrUdpServerSessionsTableIx }
   ::= {pr1645v2IpV6VrfRtrUdpServerSessions 1}

Pr1645v2IpV6VrfRtrUdpServerSessionsEntry ::=
   SEQUENCE
      {
      pr1645v2IpV6VrfRtrUdpServerSessionsGlobalIx
         GlobalIndex,
      pr1645v2IpV6VrfRtrUdpServerSessionsTableIx
         TableIndex,
      pr1645v2IpV6VrfRtrUdpServerSessionsSourceIpV6Address
         Ipv6Address,
      pr1645v2IpV6VrfRtrUdpServerSessionsSourcePort
         Integer32,
      pr1645v2IpV6VrfRtrUdpServerSessionsNbrPckt
         Counter64,
      pr1645v2IpV6VrfRtrUdpServerSessionsFirstActivityTime
         TimeTicks,
      pr1645v2IpV6VrfRtrUdpServerSessionsLastActivityTime
         TimeTicks
      }

pr1645v2IpV6VrfRtrUdpServerSessionsGlobalIx OBJECT-TYPE
   SYNTAX      GlobalIndex
   MAX-ACCESS  not-accessible
   STATUS      current
   DESCRIPTION
      "The value of the tlsCntTreeGlobalIndex of the MANAGED OBJECT."
   ::= {pr1645v2IpV6VrfRtrUdpServerSessionsEntry 10}

pr1645v2IpV6VrfRtrUdpServerSessionsTableIx OBJECT-TYPE
   SYNTAX      TableIndex
   MAX-ACCESS  not-accessible
   STATUS      current
   DESCRIPTION
      ""
   ::= {pr1645v2IpV6VrfRtrUdpServerSessionsEntry 11}

pr1645v2IpV6VrfRtrUdpServerSessionsSourceIpV6Address OBJECT-TYPE
   SYNTAX      Ipv6Address
   MAX-ACCESS  read-only
   STATUS      current
   DESCRIPTION
      "Path: vrfV6Router.performance.udpServer.sessions.sourceIpV6Address

       ipv6 address"
   ::= {pr1645v2IpV6VrfRtrUdpServerSessionsEntry 16777216}

pr1645v2IpV6VrfRtrUdpServerSessionsSourcePort OBJECT-TYPE
   SYNTAX      Integer32
   MAX-ACCESS  read-only
   STATUS      current
   DESCRIPTION
      "Path: vrfV6Router.performance.udpServer.sessions.sourcePort"
   ::= {pr1645v2IpV6VrfRtrUdpServerSessionsEntry 33554432}

pr1645v2IpV6VrfRtrUdpServerSessionsNbrPckt OBJECT-TYPE
   SYNTAX      Counter64
   MAX-ACCESS  read-only
   STATUS      current
   DESCRIPTION
      "Path: vrfV6Router.performance.udpServer.sessions.nbrOfPackets

       64 bit unsigned wrappable counter."
   ::= {pr1645v2IpV6VrfRtrUdpServerSessionsEntry 50331648}

pr1645v2IpV6VrfRtrUdpServerSessionsFirstActivityTime OBJECT-TYPE
   SYNTAX      TimeTicks
   MAX-ACCESS  read-only
   STATUS      current
   DESCRIPTION
      "Path: vrfV6Router.performance.udpServer.sessions.firstActivityTime

       Time in centi-second."
   ::= {pr1645v2IpV6VrfRtrUdpServerSessionsEntry 67108864}

pr1645v2IpV6VrfRtrUdpServerSessionsLastActivityTime OBJECT-TYPE
   SYNTAX      TimeTicks
   MAX-ACCESS  read-only
   STATUS      current
   DESCRIPTION
      "Path: vrfV6Router.performance.udpServer.sessions.lastActivityTime

       Time in centi-second."
   ::= {pr1645v2IpV6VrfRtrUdpServerSessionsEntry 83886080}


pr1645v2IpV6VrfRtrPingResults OBJECT IDENTIFIER ::= {pr1645v2IpV6VrfRtr 54}

pr1645v2IpV6VrfRtrPingResultsSSCTable OBJECT-TYPE
   SYNTAX      SEQUENCE OF Pr1645v2IpV6VrfRtrPingResultsEntry
   MAX-ACCESS  not-accessible
   STATUS      current
   DESCRIPTION
      "ping statistics"
   ::= {pr1645v2IpV6VrfRtrPingResults 1}

pr1645v2IpV6VrfRtrPingResultsEntry OBJECT-TYPE
   SYNTAX      Pr1645v2IpV6VrfRtrPingResultsEntry
   MAX-ACCESS  not-accessible
   STATUS      current
   DESCRIPTION
      ""
   INDEX      { pr1645v2IpV6VrfRtrPingResultsGlobalIx }
   ::= {pr1645v2IpV6VrfRtrPingResultsSSCTable 1}

Pr1645v2IpV6VrfRtrPingResultsEntry ::=
   SEQUENCE
      {
      pr1645v2IpV6VrfRtrPingResultsGlobalIx
         GlobalIndex,
      pr1645v2IpV6VrfRtrPingResultsIpAddr
         Ipv6Address,
      pr1645v2IpV6VrfRtrPingResultsNbrTxPckt
         Counter32,
      pr1645v2IpV6VrfRtrPingResultsNbrRxPckt
         Counter32,
      pr1645v2IpV6VrfRtrPingResultsRepTimMin
         TimeTicks,
      pr1645v2IpV6VrfRtrPingResultsRepTimMax
         TimeTicks,
      pr1645v2IpV6VrfRtrPingResultsRepTimAvrg
         TimeTicks,
      pr1645v2IpV6VrfRtrPingResultsLastError
         DisplayString
      }

pr1645v2IpV6VrfRtrPingResultsGlobalIx OBJECT-TYPE
   SYNTAX      GlobalIndex
   MAX-ACCESS  not-accessible
   STATUS      current
   DESCRIPTION
      "The value of the tlsCntTreeGlobalIndex of the MANAGED OBJECT."
   ::= {pr1645v2IpV6VrfRtrPingResultsEntry 10}

pr1645v2IpV6VrfRtrPingResultsIpAddr OBJECT-TYPE
   SYNTAX      Ipv6Address
   MAX-ACCESS  read-only
   STATUS      current
   DESCRIPTION
      "Path: vrfV6Router.performance.pingResults.ipV6Address

       ipv6 address"
   ::= {pr1645v2IpV6VrfRtrPingResultsEntry 16777216}

pr1645v2IpV6VrfRtrPingResultsNbrTxPckt OBJECT-TYPE
   SYNTAX      Counter32
   MAX-ACCESS  read-only
   STATUS      current
   DESCRIPTION
      "Path: vrfV6Router.performance.pingResults.nbrOfTxPackets

       32 bit unsigned wrappable counter."
   ::= {pr1645v2IpV6VrfRtrPingResultsEntry 33554432}

pr1645v2IpV6VrfRtrPingResultsNbrRxPckt OBJECT-TYPE
   SYNTAX      Counter32
   MAX-ACCESS  read-only
   STATUS      current
   DESCRIPTION
      "Path: vrfV6Router.performance.pingResults.nbrOfRxPackets

       32 bit unsigned wrappable counter."
   ::= {pr1645v2IpV6VrfRtrPingResultsEntry 50331648}

pr1645v2IpV6VrfRtrPingResultsRepTimMin OBJECT-TYPE
   SYNTAX      TimeTicks
   MAX-ACCESS  read-only
   STATUS      current
   DESCRIPTION
      "Path: vrfV6Router.performance.pingResults.replyTimeMin

       Time in centi-second."
   ::= {pr1645v2IpV6VrfRtrPingResultsEntry 67108864}

pr1645v2IpV6VrfRtrPingResultsRepTimMax OBJECT-TYPE
   SYNTAX      TimeTicks
   MAX-ACCESS  read-only
   STATUS      current
   DESCRIPTION
      "Path: vrfV6Router.performance.pingResults.replyTimeMax

       Time in centi-second."
   ::= {pr1645v2IpV6VrfRtrPingResultsEntry 83886080}

pr1645v2IpV6VrfRtrPingResultsRepTimAvrg OBJECT-TYPE
   SYNTAX      TimeTicks
   MAX-ACCESS  read-only
   STATUS      current
   DESCRIPTION
      "Path: vrfV6Router.performance.pingResults.replyTimeAvrg

       Time in centi-second."
   ::= {pr1645v2IpV6VrfRtrPingResultsEntry 100663296}

pr1645v2IpV6VrfRtrPingResultsLastError OBJECT-TYPE
   SYNTAX      DisplayString
   MAX-ACCESS  read-only
   STATUS      current
   DESCRIPTION
      "Path: vrfV6Router.performance.pingResults.lastError"
   ::= {pr1645v2IpV6VrfRtrPingResultsEntry 117440512}



fr1645v2IpV6VrfRtr OBJECT IDENTIFIER ::= {r1645v2IpV6VrfRtr 13}


fr1645v2IpV6VrfRtrAlarm OBJECT IDENTIFIER ::= {fr1645v2IpV6VrfRtr 202}

fr1645v2IpV6VrfRtrAlarmSSCTable OBJECT-TYPE
   SYNTAX      SEQUENCE OF Fr1645v2IpV6VrfRtrAlarmEntry
   MAX-ACCESS  not-accessible
   STATUS      current
   DESCRIPTION
      "routAlarmInfo"
   ::= {fr1645v2IpV6VrfRtrAlarm 1}

fr1645v2IpV6VrfRtrAlarmEntry OBJECT-TYPE
   SYNTAX      Fr1645v2IpV6VrfRtrAlarmEntry
   MAX-ACCESS  not-accessible
   STATUS      current
   DESCRIPTION
      ""
   INDEX      { fr1645v2IpV6VrfRtrAlarmGlobalIx }
   ::= {fr1645v2IpV6VrfRtrAlarmSSCTable 1}

Fr1645v2IpV6VrfRtrAlarmEntry ::=
   SEQUENCE
      {
      fr1645v2IpV6VrfRtrAlarmGlobalIx
         GlobalIndex,
      fr1645v2IpV6VrfRtrAlarmDiscriminator
         Integer32,
      fr1645v2IpV6VrfRtrAlarmCurrent
         Integer32,
      fr1645v2IpV6VrfRtrAlarmPrevious
         Integer32,
      fr1645v2IpV6VrfRtrAlarmMask
         Integer32,
      fr1645v2IpV6VrfRtrAlarmLevPingActive
         Integer32,
      fr1645v2IpV6VrfRtrAlarmLevQMonLoss
         Integer32,
      fr1645v2IpV6VrfRtrAlarmLevQMonDelay
         Integer32,
      fr1645v2IpV6VrfRtrAlarmLevQMonJitter
         Integer32
      }

fr1645v2IpV6VrfRtrAlarmGlobalIx OBJECT-TYPE
   SYNTAX      GlobalIndex
   MAX-ACCESS  not-accessible
   STATUS      current
   DESCRIPTION
      "The value of the tlsCntTreeGlobalIndex of the MANAGED OBJECT."
   ::= {fr1645v2IpV6VrfRtrAlarmEntry 10}

fr1645v2IpV6VrfRtrAlarmDiscriminator OBJECT-TYPE
   SYNTAX      Integer32
   MAX-ACCESS  read-only
   STATUS      current
   DESCRIPTION
      "Path: vrfV6Router.alarms.alarmInfo.discriminator"
   ::= {fr1645v2IpV6VrfRtrAlarmEntry 16777216}

fr1645v2IpV6VrfRtrAlarmCurrent OBJECT-TYPE
   SYNTAX      Integer32
   MAX-ACCESS  read-only
   STATUS      current
   DESCRIPTION
      "Path: vrfV6Router.alarms.alarmInfo.currentAlarms

       Bit meanings:
               bit 0 = pingActive,
               bit 1 = qMonLoss,
               bit 2 = qMonDelay,
               bit 3 = qMonJitter"
   ::= {fr1645v2IpV6VrfRtrAlarmEntry 33554432}

fr1645v2IpV6VrfRtrAlarmPrevious OBJECT-TYPE
   SYNTAX      Integer32
   MAX-ACCESS  read-only
   STATUS      current
   DESCRIPTION
      "Path: vrfV6Router.alarms.alarmInfo.previousAlarms

       Bit meanings:
               bit 0 = pingActive,
               bit 1 = qMonLoss,
               bit 2 = qMonDelay,
               bit 3 = qMonJitter"
   ::= {fr1645v2IpV6VrfRtrAlarmEntry 50331648}

fr1645v2IpV6VrfRtrAlarmMask OBJECT-TYPE
   SYNTAX      Integer32
   MAX-ACCESS  read-only
   STATUS      current
   DESCRIPTION
      "Path: vrfV6Router.alarms.alarmInfo.alarmMask

       Bit meanings:
               bit 0 = pingActive,
               bit 1 = qMonLoss,
               bit 2 = qMonDelay,
               bit 3 = qMonJitter"
   ::= {fr1645v2IpV6VrfRtrAlarmEntry 67108864}

fr1645v2IpV6VrfRtrAlarmLevPingActive OBJECT-TYPE
   SYNTAX      Integer32
   MAX-ACCESS  read-only
   STATUS      current
   DESCRIPTION
      "Path: vrfV6Router.alarms.alarmInfo.alarmLevel.pingActive"
   ::= {fr1645v2IpV6VrfRtrAlarmEntry 83951616}

fr1645v2IpV6VrfRtrAlarmLevQMonLoss OBJECT-TYPE
   SYNTAX      Integer32
   MAX-ACCESS  read-only
   STATUS      current
   DESCRIPTION
      "Path: vrfV6Router.alarms.alarmInfo.alarmLevel.qMonLoss"
   ::= {fr1645v2IpV6VrfRtrAlarmEntry 84017152}

fr1645v2IpV6VrfRtrAlarmLevQMonDelay OBJECT-TYPE
   SYNTAX      Integer32
   MAX-ACCESS  read-only
   STATUS      current
   DESCRIPTION
      "Path: vrfV6Router.alarms.alarmInfo.alarmLevel.qMonDelay"
   ::= {fr1645v2IpV6VrfRtrAlarmEntry 84082688}

fr1645v2IpV6VrfRtrAlarmLevQMonJitter OBJECT-TYPE
   SYNTAX      Integer32
   MAX-ACCESS  read-only
   STATUS      current
   DESCRIPTION
      "Path: vrfV6Router.alarms.alarmInfo.alarmLevel.qMonJitter"
   ::= {fr1645v2IpV6VrfRtrAlarmEntry 84148224}


fr1645v2IpV6VrfRtrAlarmE2 OBJECT IDENTIFIER ::= {fr1645v2IpV6VrfRtrAlarm 2}

fr1645v2IpV6VrfRtrAlarmE2Entry OBJECT IDENTIFIER ::= {fr1645v2IpV6VrfRtrAlarmE2 1}

fr1645v2IpV6VrfRtrAlarmE2PingActive OBJECT IDENTIFIER ::= {fr1645v2IpV6VrfRtrAlarmE2Entry 10}

fr1645v2IpV6VrfRtrAlarmE2PingActivePfx OBJECT IDENTIFIER ::= {fr1645v2IpV6VrfRtrAlarmE2PingActive 0}

fr1645v2IpV6VrfRtrAlarmE2PingActiveOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pingActive'
                representing an alarm condition in the alarm word
                of attribute 'alarmInfo' of managed object 'ipV6VrfRouter'
                (root='router1645') has changed from the ON to the OFF state."
   ::= {fr1645v2IpV6VrfRtrAlarmE2PingActivePfx 1}

fr1645v2IpV6VrfRtrAlarmE2PingActiveOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pingActive'
                representing an alarm condition in the alarm word
                of attribute 'alarmInfo' of managed object 'ipV6VrfRouter'
                (root='router1645') has changed from the OFF to the ON state."
   ::= {fr1645v2IpV6VrfRtrAlarmE2PingActivePfx 2}

fr1645v2IpV6VrfRtrAlarmE2QMonLoss OBJECT IDENTIFIER ::= {fr1645v2IpV6VrfRtrAlarmE2Entry 11}

fr1645v2IpV6VrfRtrAlarmE2QMonLossPfx OBJECT IDENTIFIER ::= {fr1645v2IpV6VrfRtrAlarmE2QMonLoss 0}

fr1645v2IpV6VrfRtrAlarmE2QMonLossOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qMonLoss'
                representing an alarm condition in the alarm word
                of attribute 'alarmInfo' of managed object 'ipV6VrfRouter'
                (root='router1645') has changed from the ON to the OFF state."
   ::= {fr1645v2IpV6VrfRtrAlarmE2QMonLossPfx 1}

fr1645v2IpV6VrfRtrAlarmE2QMonLossOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qMonLoss'
                representing an alarm condition in the alarm word
                of attribute 'alarmInfo' of managed object 'ipV6VrfRouter'
                (root='router1645') has changed from the OFF to the ON state."
   ::= {fr1645v2IpV6VrfRtrAlarmE2QMonLossPfx 2}

fr1645v2IpV6VrfRtrAlarmE2QMonDelay OBJECT IDENTIFIER ::= {fr1645v2IpV6VrfRtrAlarmE2Entry 12}

fr1645v2IpV6VrfRtrAlarmE2QMonDelayPfx OBJECT IDENTIFIER ::= {fr1645v2IpV6VrfRtrAlarmE2QMonDelay 0}

fr1645v2IpV6VrfRtrAlarmE2QMonDelayOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qMonDelay'
                representing an alarm condition in the alarm word
                of attribute 'alarmInfo' of managed object 'ipV6VrfRouter'
                (root='router1645') has changed from the ON to the OFF state."
   ::= {fr1645v2IpV6VrfRtrAlarmE2QMonDelayPfx 1}

fr1645v2IpV6VrfRtrAlarmE2QMonDelayOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qMonDelay'
                representing an alarm condition in the alarm word
                of attribute 'alarmInfo' of managed object 'ipV6VrfRouter'
                (root='router1645') has changed from the OFF to the ON state."
   ::= {fr1645v2IpV6VrfRtrAlarmE2QMonDelayPfx 2}

fr1645v2IpV6VrfRtrAlarmE2QMonJitter OBJECT IDENTIFIER ::= {fr1645v2IpV6VrfRtrAlarmE2Entry 13}

fr1645v2IpV6VrfRtrAlarmE2QMonJitterPfx OBJECT IDENTIFIER ::= {fr1645v2IpV6VrfRtrAlarmE2QMonJitter 0}

fr1645v2IpV6VrfRtrAlarmE2QMonJitterOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qMonJitter'
                representing an alarm condition in the alarm word
                of attribute 'alarmInfo' of managed object 'ipV6VrfRouter'
                (root='router1645') has changed from the ON to the OFF state."
   ::= {fr1645v2IpV6VrfRtrAlarmE2QMonJitterPfx 1}

fr1645v2IpV6VrfRtrAlarmE2QMonJitterOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qMonJitter'
                representing an alarm condition in the alarm word
                of attribute 'alarmInfo' of managed object 'ipV6VrfRouter'
                (root='router1645') has changed from the OFF to the ON state."
   ::= {fr1645v2IpV6VrfRtrAlarmE2QMonJitterPfx 2}



ar1645v2IpV6VrfRtr OBJECT IDENTIFIER ::= {r1645v2IpV6VrfRtr 16}


ar1645v2IpV6VrfRtrQmOnDemand OBJECT IDENTIFIER ::= {ar1645v2IpV6VrfRtr 8043}

ar1645v2IpV6VrfRtrQmOnDemandTable OBJECT-TYPE
   SYNTAX      SEQUENCE OF Ar1645v2IpV6VrfRtrQmOnDemandEntry
   MAX-ACCESS  not-accessible
   STATUS      current
   DESCRIPTION
      "start sending pings"
   ::= {ar1645v2IpV6VrfRtrQmOnDemand 1}

ar1645v2IpV6VrfRtrQmOnDemandEntry OBJECT-TYPE
   SYNTAX      Ar1645v2IpV6VrfRtrQmOnDemandEntry
   MAX-ACCESS  not-accessible
   STATUS      current
   DESCRIPTION
      ""
   INDEX      { ar1645v2IpV6VrfRtrQmOnDemandGlobalIx }
   ::= {ar1645v2IpV6VrfRtrQmOnDemandTable 1}

Ar1645v2IpV6VrfRtrQmOnDemandEntry ::=
   SEQUENCE
      {
      ar1645v2IpV6VrfRtrQmOnDemandGlobalIx
         GlobalIndex,
      ar1645v2IpV6VrfRtrQmOnDemandValue
         Integer32
      }

ar1645v2IpV6VrfRtrQmOnDemandGlobalIx OBJECT-TYPE
   SYNTAX      GlobalIndex
   MAX-ACCESS  not-accessible
   STATUS      current
   DESCRIPTION
      "The value of the tlsCntTreeGlobalIndex of the MANAGED OBJECT."
   ::= {ar1645v2IpV6VrfRtrQmOnDemandEntry 10}

ar1645v2IpV6VrfRtrQmOnDemandValue OBJECT-TYPE
   SYNTAX      Integer32
   MAX-ACCESS  read-write
   STATUS      current
   DESCRIPTION
      "Path: vrfV6Router.actions.qmOnDemand"
   ::= {ar1645v2IpV6VrfRtrQmOnDemandEntry 2147483648}


ar1645v2IpV6VrfRtrAction OBJECT IDENTIFIER ::= {ar1645v2IpV6VrfRtr 8044}

ar1645v2IpV6VrfRtrActionSSCTable OBJECT-TYPE
   SYNTAX      SEQUENCE OF Ar1645v2IpV6VrfRtrActionEntry
   MAX-ACCESS  not-accessible
   STATUS      current
   DESCRIPTION
      "data needed for ping"
   ::= {ar1645v2IpV6VrfRtrAction 1}

ar1645v2IpV6VrfRtrActionEntry OBJECT-TYPE
   SYNTAX      Ar1645v2IpV6VrfRtrActionEntry
   MAX-ACCESS  not-accessible
   STATUS      current
   DESCRIPTION
      ""
   INDEX      { ar1645v2IpV6VrfRtrActionGlobalIx }
   ::= {ar1645v2IpV6VrfRtrActionSSCTable 1}

Ar1645v2IpV6VrfRtrActionEntry ::=
   SEQUENCE
      {
      ar1645v2IpV6VrfRtrActionGlobalIx
         GlobalIndex,
      ar1645v2IpV6VrfRtrActionAction
         INTEGER,
      ar1645v2IpV6VrfRtrActionName
         DisplayString
      }

ar1645v2IpV6VrfRtrActionGlobalIx OBJECT-TYPE
   SYNTAX      GlobalIndex
   MAX-ACCESS  not-accessible
   STATUS      current
   DESCRIPTION
      "The value of the tlsCntTreeGlobalIndex of the MANAGED OBJECT."
   ::= {ar1645v2IpV6VrfRtrActionEntry 10}

ar1645v2IpV6VrfRtrActionAction OBJECT-TYPE
   SYNTAX      INTEGER
               {
               restart (1),
               restartLossWindow (2),
               stop (3),
               stopAndClear (4)
               }
   MAX-ACCESS  read-write
   STATUS      current
   DESCRIPTION
      "Path: vrfV6Router.actions.action.action

       Possibilities:
               restart   (1)
               restartLossWindow   (2)
               stop   (3)
               stopAndClear   (4)"
   ::= {ar1645v2IpV6VrfRtrActionEntry 16777216}

ar1645v2IpV6VrfRtrActionName OBJECT-TYPE
   SYNTAX      DisplayString
   MAX-ACCESS  read-write
   STATUS      current
   DESCRIPTION
      "Path: vrfV6Router.actions.action.name"
   ::= {ar1645v2IpV6VrfRtrActionEntry 33554432}


ar1645v2IpV6VrfRtrStopPing OBJECT IDENTIFIER ::= {ar1645v2IpV6VrfRtr 115}

ar1645v2IpV6VrfRtrStopPingTable OBJECT-TYPE
   SYNTAX      SEQUENCE OF Ar1645v2IpV6VrfRtrStopPingEntry
   MAX-ACCESS  not-accessible
   STATUS      current
   DESCRIPTION
      "stop sending pings"
   ::= {ar1645v2IpV6VrfRtrStopPing 1}

ar1645v2IpV6VrfRtrStopPingEntry OBJECT-TYPE
   SYNTAX      Ar1645v2IpV6VrfRtrStopPingEntry
   MAX-ACCESS  not-accessible
   STATUS      current
   DESCRIPTION
      ""
   INDEX      { ar1645v2IpV6VrfRtrStopPingGlobalIx }
   ::= {ar1645v2IpV6VrfRtrStopPingTable 1}

Ar1645v2IpV6VrfRtrStopPingEntry ::=
   SEQUENCE
      {
      ar1645v2IpV6VrfRtrStopPingGlobalIx
         GlobalIndex,
      ar1645v2IpV6VrfRtrStopPingValue
         Integer32
      }

ar1645v2IpV6VrfRtrStopPingGlobalIx OBJECT-TYPE
   SYNTAX      GlobalIndex
   MAX-ACCESS  not-accessible
   STATUS      current
   DESCRIPTION
      "The value of the tlsCntTreeGlobalIndex of the MANAGED OBJECT."
   ::= {ar1645v2IpV6VrfRtrStopPingEntry 10}

ar1645v2IpV6VrfRtrStopPingValue OBJECT-TYPE
   SYNTAX      Integer32
   MAX-ACCESS  read-write
   STATUS      current
   DESCRIPTION
      "Path: vrfV6Router.actions.stopPing"
   ::= {ar1645v2IpV6VrfRtrStopPingEntry 2147483648}


ar1645v2IpV6VrfRtrStartPing OBJECT IDENTIFIER ::= {ar1645v2IpV6VrfRtr 113}

ar1645v2IpV6VrfRtrStartPingTable OBJECT-TYPE
   SYNTAX      SEQUENCE OF Ar1645v2IpV6VrfRtrStartPingEntry
   MAX-ACCESS  not-accessible
   STATUS      current
   DESCRIPTION
      "start sending pings"
   ::= {ar1645v2IpV6VrfRtrStartPing 1}

ar1645v2IpV6VrfRtrStartPingEntry OBJECT-TYPE
   SYNTAX      Ar1645v2IpV6VrfRtrStartPingEntry
   MAX-ACCESS  not-accessible
   STATUS      current
   DESCRIPTION
      ""
   INDEX      { ar1645v2IpV6VrfRtrStartPingGlobalIx }
   ::= {ar1645v2IpV6VrfRtrStartPingTable 1}

Ar1645v2IpV6VrfRtrStartPingEntry ::=
   SEQUENCE
      {
      ar1645v2IpV6VrfRtrStartPingGlobalIx
         GlobalIndex,
      ar1645v2IpV6VrfRtrStartPingValue
         Integer32
      }

ar1645v2IpV6VrfRtrStartPingGlobalIx OBJECT-TYPE
   SYNTAX      GlobalIndex
   MAX-ACCESS  not-accessible
   STATUS      current
   DESCRIPTION
      "The value of the tlsCntTreeGlobalIndex of the MANAGED OBJECT."
   ::= {ar1645v2IpV6VrfRtrStartPingEntry 10}

ar1645v2IpV6VrfRtrStartPingValue OBJECT-TYPE
   SYNTAX      Integer32
   MAX-ACCESS  read-write
   STATUS      current
   DESCRIPTION
      "Path: vrfV6Router.actions.startPing"
   ::= {ar1645v2IpV6VrfRtrStartPingEntry 2147483648}


ar1645v2IpV6VrfRtrPingData OBJECT IDENTIFIER ::= {ar1645v2IpV6VrfRtr 114}

ar1645v2IpV6VrfRtrPingDataSSCTable OBJECT-TYPE
   SYNTAX      SEQUENCE OF Ar1645v2IpV6VrfRtrPingDataEntry
   MAX-ACCESS  not-accessible
   STATUS      current
   DESCRIPTION
      "data needed for ping"
   ::= {ar1645v2IpV6VrfRtrPingData 1}

ar1645v2IpV6VrfRtrPingDataEntry OBJECT-TYPE
   SYNTAX      Ar1645v2IpV6VrfRtrPingDataEntry
   MAX-ACCESS  not-accessible
   STATUS      current
   DESCRIPTION
      ""
   INDEX      { ar1645v2IpV6VrfRtrPingDataGlobalIx }
   ::= {ar1645v2IpV6VrfRtrPingDataSSCTable 1}

Ar1645v2IpV6VrfRtrPingDataEntry ::=
   SEQUENCE
      {
      ar1645v2IpV6VrfRtrPingDataGlobalIx
         GlobalIndex,
      ar1645v2IpV6VrfRtrPingDataIpV6Address
         Ipv6Address,
      ar1645v2IpV6VrfRtrPingDataHostName
         DisplayString,
      ar1645v2IpV6VrfRtrPingDataSourceIpV6
         Ipv6Address,
      ar1645v2IpV6VrfRtrPingDataTrafficClass
         Integer32,
      ar1645v2IpV6VrfRtrPingDataFragment
         INTEGER,
      ar1645v2IpV6VrfRtrPingDataTtl
         Integer32,
      ar1645v2IpV6VrfRtrPingDataIterations
         INTEGER,
      ar1645v2IpV6VrfRtrPingDataInterval
         Integer32,
      ar1645v2IpV6VrfRtrPingDataDataLength
         Integer32,
      ar1645v2IpV6VrfRtrPingDataTimeOut
         TimeTicks
      }

ar1645v2IpV6VrfRtrPingDataGlobalIx OBJECT-TYPE
   SYNTAX      GlobalIndex
   MAX-ACCESS  not-accessible
   STATUS      current
   DESCRIPTION
      "The value of the tlsCntTreeGlobalIndex of the MANAGED OBJECT."
   ::= {ar1645v2IpV6VrfRtrPingDataEntry 10}

ar1645v2IpV6VrfRtrPingDataIpV6Address OBJECT-TYPE
   SYNTAX      Ipv6Address
   MAX-ACCESS  read-write
   STATUS      current
   DESCRIPTION
      "Path: vrfV6Router.actions.pingData.ipV6Address

       ipv6 address"
   ::= {ar1645v2IpV6VrfRtrPingDataEntry 16777216}

ar1645v2IpV6VrfRtrPingDataHostName OBJECT-TYPE
   SYNTAX      DisplayString
   MAX-ACCESS  read-write
   STATUS      current
   DESCRIPTION
      "Path: vrfV6Router.actions.pingData.hostName"
   ::= {ar1645v2IpV6VrfRtrPingDataEntry 100663296}

ar1645v2IpV6VrfRtrPingDataSourceIpV6 OBJECT-TYPE
   SYNTAX      Ipv6Address
   MAX-ACCESS  read-write
   STATUS      current
   DESCRIPTION
      "Path: vrfV6Router.actions.pingData.sourceIpV6

       ipv6 address"
   ::= {ar1645v2IpV6VrfRtrPingDataEntry 117440512}

ar1645v2IpV6VrfRtrPingDataTrafficClass OBJECT-TYPE
   SYNTAX      Integer32
   MAX-ACCESS  read-write
   STATUS      current
   DESCRIPTION
      "Path: vrfV6Router.actions.pingData.trafficClass"
   ::= {ar1645v2IpV6VrfRtrPingDataEntry 134217728}

ar1645v2IpV6VrfRtrPingDataFragment OBJECT-TYPE
   SYNTAX      INTEGER
               {
               yes (1),
               no (2)
               }
   MAX-ACCESS  read-write
   STATUS      current
   DESCRIPTION
      "Path: vrfV6Router.actions.pingData.fragment

       Possibilities:
               yes   (1)
               no   (2)"
   ::= {ar1645v2IpV6VrfRtrPingDataEntry 150994944}

ar1645v2IpV6VrfRtrPingDataTtl OBJECT-TYPE
   SYNTAX      Integer32
   MAX-ACCESS  read-write
   STATUS      current
   DESCRIPTION
      "Path: vrfV6Router.actions.pingData.ttl"
   ::= {ar1645v2IpV6VrfRtrPingDataEntry 167772160}

ar1645v2IpV6VrfRtrPingDataIterations OBJECT-TYPE
   SYNTAX      INTEGER
               {
               unlimited (0)
               }
   MAX-ACCESS  read-write
   STATUS      current
   DESCRIPTION
      "Path: vrfV6Router.actions.pingData.iterations

       Possibilities:
               unlimited   (0)"
   ::= {ar1645v2IpV6VrfRtrPingDataEntry 33554432}

ar1645v2IpV6VrfRtrPingDataInterval OBJECT-TYPE
   SYNTAX      Integer32
   MAX-ACCESS  read-write
   STATUS      current
   DESCRIPTION
      "Path: vrfV6Router.actions.pingData.interval"
   ::= {ar1645v2IpV6VrfRtrPingDataEntry 50331648}

ar1645v2IpV6VrfRtrPingDataDataLength OBJECT-TYPE
   SYNTAX      Integer32
   MAX-ACCESS  read-write
   STATUS      current
   DESCRIPTION
      "Path: vrfV6Router.actions.pingData.dataLength"
   ::= {ar1645v2IpV6VrfRtrPingDataEntry 67108864}

ar1645v2IpV6VrfRtrPingDataTimeOut OBJECT-TYPE
   SYNTAX      TimeTicks
   MAX-ACCESS  read-write
   STATUS      current
   DESCRIPTION
      "Path: vrfV6Router.actions.pingData.timeOut

       Time in centi-second."
   ::= {ar1645v2IpV6VrfRtrPingDataEntry 83886080}


ar1645v2IpV6VrfRtrClearCounters OBJECT IDENTIFIER ::= {ar1645v2IpV6VrfRtr 263}

ar1645v2IpV6VrfRtrClearCountersTable OBJECT-TYPE
   SYNTAX      SEQUENCE OF Ar1645v2IpV6VrfRtrClearCountersEntry
   MAX-ACCESS  not-accessible
   STATUS      current
   DESCRIPTION
      "reset counters"
   ::= {ar1645v2IpV6VrfRtrClearCounters 1}

ar1645v2IpV6VrfRtrClearCountersEntry OBJECT-TYPE
   SYNTAX      Ar1645v2IpV6VrfRtrClearCountersEntry
   MAX-ACCESS  not-accessible
   STATUS      current
   DESCRIPTION
      ""
   INDEX      { ar1645v2IpV6VrfRtrClearCountersGlobalIx }
   ::= {ar1645v2IpV6VrfRtrClearCountersTable 1}

Ar1645v2IpV6VrfRtrClearCountersEntry ::=
   SEQUENCE
      {
      ar1645v2IpV6VrfRtrClearCountersGlobalIx
         GlobalIndex,
      ar1645v2IpV6VrfRtrClearCountersValue
         Integer32
      }

ar1645v2IpV6VrfRtrClearCountersGlobalIx OBJECT-TYPE
   SYNTAX      GlobalIndex
   MAX-ACCESS  not-accessible
   STATUS      current
   DESCRIPTION
      "The value of the tlsCntTreeGlobalIndex of the MANAGED OBJECT."
   ::= {ar1645v2IpV6VrfRtrClearCountersEntry 10}

ar1645v2IpV6VrfRtrClearCountersValue OBJECT-TYPE
   SYNTAX      Integer32
   MAX-ACCESS  read-write
   STATUS      current
   DESCRIPTION
      "Path: vrfV6Router.actions.clearCounters"
   ::= {ar1645v2IpV6VrfRtrClearCountersEntry 2147483648}


ar1645v2IpV6VrfRtrRequestDnsByAddress OBJECT IDENTIFIER ::= {ar1645v2IpV6VrfRtr 103}

ar1645v2IpV6VrfRtrRequestDnsByAddressTable OBJECT-TYPE
   SYNTAX      SEQUENCE OF Ar1645v2IpV6VrfRtrRequestDnsByAddressEntry
   MAX-ACCESS  not-accessible
   STATUS      current
   DESCRIPTION
      "do a DNS request"
   ::= {ar1645v2IpV6VrfRtrRequestDnsByAddress 1}

ar1645v2IpV6VrfRtrRequestDnsByAddressEntry OBJECT-TYPE
   SYNTAX      Ar1645v2IpV6VrfRtrRequestDnsByAddressEntry
   MAX-ACCESS  not-accessible
   STATUS      current
   DESCRIPTION
      ""
   INDEX      { ar1645v2IpV6VrfRtrRequestDnsByAddressGlobalIx }
   ::= {ar1645v2IpV6VrfRtrRequestDnsByAddressTable 1}

Ar1645v2IpV6VrfRtrRequestDnsByAddressEntry ::=
   SEQUENCE
      {
      ar1645v2IpV6VrfRtrRequestDnsByAddressGlobalIx
         GlobalIndex,
      ar1645v2IpV6VrfRtrRequestDnsByAddressValue
         Integer32
      }

ar1645v2IpV6VrfRtrRequestDnsByAddressGlobalIx OBJECT-TYPE
   SYNTAX      GlobalIndex
   MAX-ACCESS  not-accessible
   STATUS      current
   DESCRIPTION
      "The value of the tlsCntTreeGlobalIndex of the MANAGED OBJECT."
   ::= {ar1645v2IpV6VrfRtrRequestDnsByAddressEntry 10}

ar1645v2IpV6VrfRtrRequestDnsByAddressValue OBJECT-TYPE
   SYNTAX      Integer32
   MAX-ACCESS  read-write
   STATUS      current
   DESCRIPTION
      "Path: vrfV6Router.actions.requestDnsByAddress"
   ::= {ar1645v2IpV6VrfRtrRequestDnsByAddressEntry 2147483648}


ar1645v2IpV6VrfRtrHostAddress OBJECT IDENTIFIER ::= {ar1645v2IpV6VrfRtr 104}

ar1645v2IpV6VrfRtrHostAddressTable OBJECT-TYPE
   SYNTAX      SEQUENCE OF Ar1645v2IpV6VrfRtrHostAddressEntry
   MAX-ACCESS  not-accessible
   STATUS      current
   DESCRIPTION
      "address of the host"
   ::= {ar1645v2IpV6VrfRtrHostAddress 1}

ar1645v2IpV6VrfRtrHostAddressEntry OBJECT-TYPE
   SYNTAX      Ar1645v2IpV6VrfRtrHostAddressEntry
   MAX-ACCESS  not-accessible
   STATUS      current
   DESCRIPTION
      ""
   INDEX      { ar1645v2IpV6VrfRtrHostAddressGlobalIx }
   ::= {ar1645v2IpV6VrfRtrHostAddressTable 1}

Ar1645v2IpV6VrfRtrHostAddressEntry ::=
   SEQUENCE
      {
      ar1645v2IpV6VrfRtrHostAddressGlobalIx
         GlobalIndex,
      ar1645v2IpV6VrfRtrHostAddressValue
         Ipv6Address
      }

ar1645v2IpV6VrfRtrHostAddressGlobalIx OBJECT-TYPE
   SYNTAX      GlobalIndex
   MAX-ACCESS  not-accessible
   STATUS      current
   DESCRIPTION
      "The value of the tlsCntTreeGlobalIndex of the MANAGED OBJECT."
   ::= {ar1645v2IpV6VrfRtrHostAddressEntry 10}

ar1645v2IpV6VrfRtrHostAddressValue OBJECT-TYPE
   SYNTAX      Ipv6Address
   MAX-ACCESS  read-write
   STATUS      current
   DESCRIPTION
      "Path: vrfV6Router.actions.hostAddress

       ipv6 address"
   ::= {ar1645v2IpV6VrfRtrHostAddressEntry 2147483648}


ar1645v2IpV6VrfRtrRequestDnsByName OBJECT IDENTIFIER ::= {ar1645v2IpV6VrfRtr 101}

ar1645v2IpV6VrfRtrRequestDnsByNameTable OBJECT-TYPE
   SYNTAX      SEQUENCE OF Ar1645v2IpV6VrfRtrRequestDnsByNameEntry
   MAX-ACCESS  not-accessible
   STATUS      current
   DESCRIPTION
      "do a DNS request"
   ::= {ar1645v2IpV6VrfRtrRequestDnsByName 1}

ar1645v2IpV6VrfRtrRequestDnsByNameEntry OBJECT-TYPE
   SYNTAX      Ar1645v2IpV6VrfRtrRequestDnsByNameEntry
   MAX-ACCESS  not-accessible
   STATUS      current
   DESCRIPTION
      ""
   INDEX      { ar1645v2IpV6VrfRtrRequestDnsByNameGlobalIx }
   ::= {ar1645v2IpV6VrfRtrRequestDnsByNameTable 1}

Ar1645v2IpV6VrfRtrRequestDnsByNameEntry ::=
   SEQUENCE
      {
      ar1645v2IpV6VrfRtrRequestDnsByNameGlobalIx
         GlobalIndex,
      ar1645v2IpV6VrfRtrRequestDnsByNameValue
         Integer32
      }

ar1645v2IpV6VrfRtrRequestDnsByNameGlobalIx OBJECT-TYPE
   SYNTAX      GlobalIndex
   MAX-ACCESS  not-accessible
   STATUS      current
   DESCRIPTION
      "The value of the tlsCntTreeGlobalIndex of the MANAGED OBJECT."
   ::= {ar1645v2IpV6VrfRtrRequestDnsByNameEntry 10}

ar1645v2IpV6VrfRtrRequestDnsByNameValue OBJECT-TYPE
   SYNTAX      Integer32
   MAX-ACCESS  read-write
   STATUS      current
   DESCRIPTION
      "Path: vrfV6Router.actions.requestDnsByName"
   ::= {ar1645v2IpV6VrfRtrRequestDnsByNameEntry 2147483648}


ar1645v2IpV6VrfRtrHostName OBJECT IDENTIFIER ::= {ar1645v2IpV6VrfRtr 102}

ar1645v2IpV6VrfRtrHostNameTable OBJECT-TYPE
   SYNTAX      SEQUENCE OF Ar1645v2IpV6VrfRtrHostNameEntry
   MAX-ACCESS  not-accessible
   STATUS      current
   DESCRIPTION
      "name of the host"
   ::= {ar1645v2IpV6VrfRtrHostName 1}

ar1645v2IpV6VrfRtrHostNameEntry OBJECT-TYPE
   SYNTAX      Ar1645v2IpV6VrfRtrHostNameEntry
   MAX-ACCESS  not-accessible
   STATUS      current
   DESCRIPTION
      ""
   INDEX      { ar1645v2IpV6VrfRtrHostNameGlobalIx }
   ::= {ar1645v2IpV6VrfRtrHostNameTable 1}

Ar1645v2IpV6VrfRtrHostNameEntry ::=
   SEQUENCE
      {
      ar1645v2IpV6VrfRtrHostNameGlobalIx
         GlobalIndex,
      ar1645v2IpV6VrfRtrHostNameValue
         DisplayString
      }

ar1645v2IpV6VrfRtrHostNameGlobalIx OBJECT-TYPE
   SYNTAX      GlobalIndex
   MAX-ACCESS  not-accessible
   STATUS      current
   DESCRIPTION
      "The value of the tlsCntTreeGlobalIndex of the MANAGED OBJECT."
   ::= {ar1645v2IpV6VrfRtrHostNameEntry 10}

ar1645v2IpV6VrfRtrHostNameValue OBJECT-TYPE
   SYNTAX      DisplayString
   MAX-ACCESS  read-write
   STATUS      current
   DESCRIPTION
      "Path: vrfV6Router.actions.hostName"
   ::= {ar1645v2IpV6VrfRtrHostNameEntry 2147483648}


ar1645v2IpV6VrfRtrClearDnsCache OBJECT IDENTIFIER ::= {ar1645v2IpV6VrfRtr 155}

ar1645v2IpV6VrfRtrClearDnsCacheTable OBJECT-TYPE
   SYNTAX      SEQUENCE OF Ar1645v2IpV6VrfRtrClearDnsCacheEntry
   MAX-ACCESS  not-accessible
   STATUS      current
   DESCRIPTION
      "clear the DNS cache table"
   ::= {ar1645v2IpV6VrfRtrClearDnsCache 1}

ar1645v2IpV6VrfRtrClearDnsCacheEntry OBJECT-TYPE
   SYNTAX      Ar1645v2IpV6VrfRtrClearDnsCacheEntry
   MAX-ACCESS  not-accessible
   STATUS      current
   DESCRIPTION
      ""
   INDEX      { ar1645v2IpV6VrfRtrClearDnsCacheGlobalIx }
   ::= {ar1645v2IpV6VrfRtrClearDnsCacheTable 1}

Ar1645v2IpV6VrfRtrClearDnsCacheEntry ::=
   SEQUENCE
      {
      ar1645v2IpV6VrfRtrClearDnsCacheGlobalIx
         GlobalIndex,
      ar1645v2IpV6VrfRtrClearDnsCacheValue
         Integer32
      }

ar1645v2IpV6VrfRtrClearDnsCacheGlobalIx OBJECT-TYPE
   SYNTAX      GlobalIndex
   MAX-ACCESS  not-accessible
   STATUS      current
   DESCRIPTION
      "The value of the tlsCntTreeGlobalIndex of the MANAGED OBJECT."
   ::= {ar1645v2IpV6VrfRtrClearDnsCacheEntry 10}

ar1645v2IpV6VrfRtrClearDnsCacheValue OBJECT-TYPE
   SYNTAX      Integer32
   MAX-ACCESS  read-write
   STATUS      current
   DESCRIPTION
      "Path: vrfV6Router.actions.clearDnsCache"
   ::= {ar1645v2IpV6VrfRtrClearDnsCacheEntry 2147483648}



END
