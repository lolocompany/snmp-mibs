OneAccess-R1646v2-4476-Efm DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1646Rootv2 MODULE-IDENTITY
   LAST-UPDATED "202107151728Z"
   ORGANIZATION "OneAccess"
   CONTACT-INFO "http://www.oneaccess-net.com/telindus/"
   DESCRIPTION
      "..."
   ::= {telindus 1132}




r1646v2Efm OBJECT IDENTIFIER ::= {r1646Rootv2 4476}

r1646v2EfmMOProp OBJECT IDENTIFIER ::= {r1646v2Efm 1}

r1646v2EfmMOPropEntry OBJECT IDENTIFIER ::= {r1646v2EfmMOProp 1}

r1646v2EfmMOPropPath OBJECT-TYPE
   SYNTAX      ContainmentPath
   MAX-ACCESS  read-only
   STATUS      current
   DESCRIPTION
      "Textual description of the containment tree from the instance of
       the root object down to the instance of the current object."
   ::= {r1646v2EfmMOPropEntry 3}

r1646v2EfmMOPropRev OBJECT-TYPE
   SYNTAX      ObjectRevision
   MAX-ACCESS  read-only
   STATUS      current
   DESCRIPTION
      "This value corresponds with the revision of the MANAGED OBJECT."
   ::= {r1646v2EfmMOPropEntry 4}



er1646v2Efm OBJECT IDENTIFIER ::= {r1646v2Efm 11}


er1646v2EfmRemark OBJECT-TYPE
   SYNTAX      DisplayString
   MAX-ACCESS  read-write
   STATUS      current
   DESCRIPTION
      "Path: efm.editConf.remark
       Info: intfRemark"
   ::= {er1646v2Efm 321}


er1646v2EfmBw OBJECT IDENTIFIER ::= {er1646v2Efm 5}

er1646v2EfmBwSSC OBJECT IDENTIFIER ::= {er1646v2EfmBw 1}

er1646v2EfmBwEntry OBJECT IDENTIFIER ::= {er1646v2EfmBwSSC 1}

er1646v2EfmBwMode OBJECT-TYPE
   SYNTAX      INTEGER
               {
               reshaping (1),
               policing (2),
               policingReshape (3)
               }
   MAX-ACCESS  read-write
   STATUS      current
   DESCRIPTION
      "Path: efm.editConf.bandwidth.mode

       Possibilities:
               reshaping   (1)
               policing   (2)
               policingReshape   (3)"
   ::= {er1646v2EfmBwEntry 3758096384}

er1646v2EfmBwCir OBJECT-TYPE
   SYNTAX      Integer32
   MAX-ACCESS  read-write
   STATUS      current
   DESCRIPTION
      "Path: efm.editConf.bandwidth.cir"
   ::= {er1646v2EfmBwEntry 268435456}

er1646v2EfmBwEir OBJECT-TYPE
   SYNTAX      Integer32
   MAX-ACCESS  read-write
   STATUS      current
   DESCRIPTION
      "Path: efm.editConf.bandwidth.eir"
   ::= {er1646v2EfmBwEntry 1879048192}

er1646v2EfmBwUnit OBJECT-TYPE
   SYNTAX      INTEGER
               {
               bitssec (1),
               percent (2)
               }
   MAX-ACCESS  read-write
   STATUS      current
   DESCRIPTION
      "Path: efm.editConf.bandwidth.unit

       Possibilities:
               bits/sec   (1)
               percent   (2)"
   ::= {er1646v2EfmBwEntry 1342177280}

er1646v2EfmBwTc OBJECT-TYPE
   SYNTAX      INTEGER
               {
               auto (0)
               }
   MAX-ACCESS  read-write
   STATUS      current
   DESCRIPTION
      "Path: efm.editConf.bandwidth.tc

       Possibilities:
               auto   (0)"
   ::= {er1646v2EfmBwEntry 1610612736}

er1646v2EfmBwTcFactor OBJECT-TYPE
   SYNTAX      INTEGER
               {
               ms (10),
               s100us (1)
               }
   MAX-ACCESS  read-write
   STATUS      current
   DESCRIPTION
      "Path: efm.editConf.bandwidth.tcFactor

       Possibilities:
               ms   (10)
               *100us   (1)"
   ::= {er1646v2EfmBwEntry 2147483648}

er1646v2EfmBwCorrType OBJECT-TYPE
   SYNTAX      INTEGER
               {
               noCorrection (0),
               predefined (1),
               manual (2)
               }
   MAX-ACCESS  read-write
   STATUS      current
   DESCRIPTION
      "Path: efm.editConf.bandwidth.correction.type

       Possibilities:
               noCorrection   (0)
               predefined   (1)
               manual   (2)"
   ::= {er1646v2EfmBwEntry 570425344}

er1646v2EfmBwCorrPredefEncapsFrameRelay OBJECT-TYPE
   SYNTAX      DisplayString
   MAX-ACCESS  read-write
   STATUS      current
   DESCRIPTION
      "Path: efm.editConf.bandwidth.correction.predefined.encapsulation.frameRelay"
   ::= {er1646v2EfmBwEntry 608436224}

er1646v2EfmBwCorrPredefEncapsPpp OBJECT-TYPE
   SYNTAX      DisplayString
   MAX-ACCESS  read-write
   STATUS      current
   DESCRIPTION
      "Path: efm.editConf.bandwidth.correction.predefined.encapsulation.ppp"
   ::= {er1646v2EfmBwEntry 608698368}

er1646v2EfmBwCorrPredefEncapsAtmHl OBJECT-TYPE
   SYNTAX      INTEGER
               {
               rfc2684 (0),
               ppp (1),
               pppOverEthernet (2)
               }
   MAX-ACCESS  read-write
   STATUS      current
   DESCRIPTION
      "Path: efm.editConf.bandwidth.correction.predefined.encapsulation.atm.higherLayer

       Possibilities:
               rfc2684   (0)
               ppp   (1)
               pppOverEthernet   (2)"
   ::= {er1646v2EfmBwEntry 608993280}

er1646v2EfmBwCorrPredefEncapsAtmMp OBJECT-TYPE
   SYNTAX      INTEGER
               {
               llcEncapsulation (0),
               vcMultiplexing (1)
               }
   MAX-ACCESS  read-write
   STATUS      current
   DESCRIPTION
      "Path: efm.editConf.bandwidth.correction.predefined.encapsulation.atm.multiProtocol

       Possibilities:
               llcEncapsulation   (0)
               vcMultiplexing   (1)"
   ::= {er1646v2EfmBwEntry 609026048}

er1646v2EfmBwCorrPredefEncapsHdlc OBJECT-TYPE
   SYNTAX      DisplayString
   MAX-ACCESS  read-write
   STATUS      current
   DESCRIPTION
      "Path: efm.editConf.bandwidth.correction.predefined.encapsulation.hdlc"
   ::= {er1646v2EfmBwEntry 609222656}

er1646v2EfmBwCorrPredefEncapsEfmFs OBJECT-TYPE
   SYNTAX      Integer32
   MAX-ACCESS  read-write
   STATUS      current
   DESCRIPTION
      "Path: efm.editConf.bandwidth.correction.predefined.encapsulation.efm.fragmentSize"
   ::= {er1646v2EfmBwEntry 609517568}

er1646v2EfmBwCorrPredefEncapsEfmIb OBJECT-TYPE
   SYNTAX      Integer32
   MAX-ACCESS  read-write
   STATUS      current
   DESCRIPTION
      "Path: efm.editConf.bandwidth.correction.predefined.encapsulation.efm.idleBytes"
   ::= {er1646v2EfmBwEntry 609550336}

er1646v2EfmBwCorrPredefMode OBJECT-TYPE
   SYNTAX      INTEGER
               {
               routing (0),
               bridging (1)
               }
   MAX-ACCESS  read-write
   STATUS      current
   DESCRIPTION
      "Path: efm.editConf.bandwidth.correction.predefined.mode

       Possibilities:
               routing   (0)
               bridging   (1)"
   ::= {er1646v2EfmBwEntry 612368384}

er1646v2EfmBwCorrManualOverhead OBJECT-TYPE
   SYNTAX      Integer32
   MAX-ACCESS  read-write
   STATUS      current
   DESCRIPTION
      "Path: efm.editConf.bandwidth.correction.manual.overhead"
   ::= {er1646v2EfmBwEntry 637665280}

er1646v2EfmBwCorrManualFrameData OBJECT-TYPE
   SYNTAX      Counter32
   MAX-ACCESS  read-write
   STATUS      current
   DESCRIPTION
      "Path: efm.editConf.bandwidth.correction.manual.frameData

       32 bit unsigned wrappable counter."
   ::= {er1646v2EfmBwEntry 637796352}

er1646v2EfmBwCorrManualFrameHeader OBJECT-TYPE
   SYNTAX      Counter32
   MAX-ACCESS  read-write
   STATUS      current
   DESCRIPTION
      "Path: efm.editConf.bandwidth.correction.manual.frameHeader

       32 bit unsigned wrappable counter."
   ::= {er1646v2EfmBwEntry 637927424}

er1646v2EfmBwMaxFifoQLen OBJECT-TYPE
   SYNTAX      Integer32
   MAX-ACCESS  read-write
   STATUS      current
   DESCRIPTION
      "Path: efm.editConf.bandwidth.maxFifoQLen"
   ::= {er1646v2EfmBwEntry 805306368}

er1646v2EfmBwDeFlagCir OBJECT-TYPE
   SYNTAX      INTEGER
               {
               allowed (1),
               notAllowed (2)
               }
   MAX-ACCESS  read-write
   STATUS      current
   DESCRIPTION
      "Path: efm.editConf.bandwidth.deFlag.cir

       Possibilities:
               allowed   (1)
               notAllowed   (2)"
   ::= {er1646v2EfmBwEntry 3490709504}

er1646v2EfmBwDeFlagEir OBJECT-TYPE
   SYNTAX      INTEGER
               {
               allowed (1),
               notAllowed (2)
               }
   MAX-ACCESS  read-write
   STATUS      current
   DESCRIPTION
      "Path: efm.editConf.bandwidth.deFlag.eir

       Possibilities:
               allowed   (1)
               notAllowed   (2)"
   ::= {er1646v2EfmBwEntry 3491758080}

er1646v2EfmBwDeFlagViolate OBJECT-TYPE
   SYNTAX      INTEGER
               {
               allowed (1),
               notAllowed (2)
               }
   MAX-ACCESS  read-write
   STATUS      current
   DESCRIPTION
      "Path: efm.editConf.bandwidth.deFlag.violate

       Possibilities:
               allowed   (1)
               notAllowed   (2)"
   ::= {er1646v2EfmBwEntry 3492806656}

er1646v2EfmBwActCirActNone OBJECT-TYPE
   SYNTAX      OCTET STRING
   MAX-ACCESS  read-write
   STATUS      current
   DESCRIPTION
      "Path: efm.editConf.bandwidth.action.cirAction.none"
   ::= {er1646v2EfmBwEntry 4062183424}

er1646v2EfmBwActCirActEthCos1 OBJECT-TYPE
   SYNTAX      INTEGER
               {
               unchanged (256)
               }
   MAX-ACCESS  read-write
   STATUS      current
   DESCRIPTION
      "Path: efm.editConf.bandwidth.action.cirAction.ethernet.cosDepth1

       Possibilities:
               unchanged   (256)"
   ::= {er1646v2EfmBwEntry 4064346112}

er1646v2EfmBwActCirActEthDei1 OBJECT-TYPE
   SYNTAX      INTEGER
               {
               unchanged (255),
               clear (0),
               set (1)
               }
   MAX-ACCESS  read-write
   STATUS      current
   DESCRIPTION
      "Path: efm.editConf.bandwidth.action.cirAction.ethernet.deiDepth1

       Possibilities:
               unchanged   (255)
               clear   (0)
               set   (1)"
   ::= {er1646v2EfmBwEntry 4065656832}

er1646v2EfmBwActCirActEthCos2 OBJECT-TYPE
   SYNTAX      INTEGER
               {
               unchanged (256)
               }
   MAX-ACCESS  read-write
   STATUS      current
   DESCRIPTION
      "Path: efm.editConf.bandwidth.action.cirAction.ethernet.cosDepth2

       Possibilities:
               unchanged   (256)"
   ::= {er1646v2EfmBwEntry 4064411648}

er1646v2EfmBwActCirActEthDei2 OBJECT-TYPE
   SYNTAX      INTEGER
               {
               unchanged (255),
               clear (0),
               set (1)
               }
   MAX-ACCESS  read-write
   STATUS      current
   DESCRIPTION
      "Path: efm.editConf.bandwidth.action.cirAction.ethernet.deiDepth2

       Possibilities:
               unchanged   (255)
               clear   (0)
               set   (1)"
   ::= {er1646v2EfmBwEntry 4065722368}

er1646v2EfmBwActCirActEthCos3 OBJECT-TYPE
   SYNTAX      INTEGER
               {
               unchanged (256)
               }
   MAX-ACCESS  read-write
   STATUS      current
   DESCRIPTION
      "Path: efm.editConf.bandwidth.action.cirAction.ethernet.cosDepth3

       Possibilities:
               unchanged   (256)"
   ::= {er1646v2EfmBwEntry 4064477184}

er1646v2EfmBwActCirActEthDei3 OBJECT-TYPE
   SYNTAX      INTEGER
               {
               unchanged (255),
               clear (0),
               set (1)
               }
   MAX-ACCESS  read-write
   STATUS      current
   DESCRIPTION
      "Path: efm.editConf.bandwidth.action.cirAction.ethernet.deiDepth3

       Possibilities:
               unchanged   (255)
               clear   (0)
               set   (1)"
   ::= {er1646v2EfmBwEntry 4065787904}

er1646v2EfmBwActCirActEthCos4 OBJECT-TYPE
   SYNTAX      INTEGER
               {
               unchanged (256)
               }
   MAX-ACCESS  read-write
   STATUS      current
   DESCRIPTION
      "Path: efm.editConf.bandwidth.action.cirAction.ethernet.cosDepth4

       Possibilities:
               unchanged   (256)"
   ::= {er1646v2EfmBwEntry 4064542720}

er1646v2EfmBwActCirActEthDei4 OBJECT-TYPE
   SYNTAX      INTEGER
               {
               unchanged (255),
               clear (0),
               set (1)
               }
   MAX-ACCESS  read-write
   STATUS      current
   DESCRIPTION
      "Path: efm.editConf.bandwidth.action.cirAction.ethernet.deiDepth4

       Possibilities:
               unchanged   (255)
               clear   (0)
               set   (1)"
   ::= {er1646v2EfmBwEntry 4065853440}

er1646v2EfmBwActCirActEthCos5 OBJECT-TYPE
   SYNTAX      INTEGER
               {
               unchanged (256)
               }
   MAX-ACCESS  read-write
   STATUS      current
   DESCRIPTION
      "Path: efm.editConf.bandwidth.action.cirAction.ethernet.cosDepth5

       Possibilities:
               unchanged   (256)"
   ::= {er1646v2EfmBwEntry 4064608256}

er1646v2EfmBwActCirActEthDei5 OBJECT-TYPE
   SYNTAX      INTEGER
               {
               unchanged (255),
               clear (0),
               set (1)
               }
   MAX-ACCESS  read-write
   STATUS      current
   DESCRIPTION
      "Path: efm.editConf.bandwidth.action.cirAction.ethernet.deiDepth5

       Possibilities:
               unchanged   (255)
               clear   (0)
               set   (1)"
   ::= {er1646v2EfmBwEntry 4065918976}

er1646v2EfmBwActCirActEthCos6 OBJECT-TYPE
   SYNTAX      INTEGER
               {
               unchanged (256)
               }
   MAX-ACCESS  read-write
   STATUS      current
   DESCRIPTION
      "Path: efm.editConf.bandwidth.action.cirAction.ethernet.cosDepth6

       Possibilities:
               unchanged   (256)"
   ::= {er1646v2EfmBwEntry 4064673792}

er1646v2EfmBwActCirActEthDei6 OBJECT-TYPE
   SYNTAX      INTEGER
               {
               unchanged (255),
               clear (0),
               set (1)
               }
   MAX-ACCESS  read-write
   STATUS      current
   DESCRIPTION
      "Path: efm.editConf.bandwidth.action.cirAction.ethernet.deiDepth6

       Possibilities:
               unchanged   (255)
               clear   (0)
               set   (1)"
   ::= {er1646v2EfmBwEntry 4065984512}

er1646v2EfmBwActCirActEthCos7 OBJECT-TYPE
   SYNTAX      INTEGER
               {
               unchanged (256)
               }
   MAX-ACCESS  read-write
   STATUS      current
   DESCRIPTION
      "Path: efm.editConf.bandwidth.action.cirAction.ethernet.cosDepth7

       Possibilities:
               unchanged   (256)"
   ::= {er1646v2EfmBwEntry 4064739328}

er1646v2EfmBwActCirActEthDei7 OBJECT-TYPE
   SYNTAX      INTEGER
               {
               unchanged (255),
               clear (0),
               set (1)
               }
   MAX-ACCESS  read-write
   STATUS      current
   DESCRIPTION
      "Path: efm.editConf.bandwidth.action.cirAction.ethernet.deiDepth7

       Possibilities:
               unchanged   (255)
               clear   (0)
               set   (1)"
   ::= {er1646v2EfmBwEntry 4066050048}

er1646v2EfmBwActCirActEthCos8 OBJECT-TYPE
   SYNTAX      INTEGER
               {
               unchanged (256)
               }
   MAX-ACCESS  read-write
   STATUS      current
   DESCRIPTION
      "Path: efm.editConf.bandwidth.action.cirAction.ethernet.cosDepth8

       Possibilities:
               unchanged   (256)"
   ::= {er1646v2EfmBwEntry 4064804864}

er1646v2EfmBwActCirActEthDei8 OBJECT-TYPE
   SYNTAX      INTEGER
               {
               unchanged (255),
               clear (0),
               set (1)
               }
   MAX-ACCESS  read-write
   STATUS      current
   DESCRIPTION
      "Path: efm.editConf.bandwidth.action.cirAction.ethernet.deiDepth8

       Possibilities:
               unchanged   (255)
               clear   (0)
               set   (1)"
   ::= {er1646v2EfmBwEntry 4066115584}

er1646v2EfmBwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EfmBwEntry 4064870400}

er1646v2EfmBwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EfmBwEntry 4064935936}

er1646v2EfmBwActCirActEthDrpLev OBJECT-TYPE
   SYNTAX      INTEGER
               {
               unchanged (0)
               }
   MAX-ACCESS  read-write
   STATUS      current
   DESCRIPTION
      "Path: efm.editConf.bandwidth.action.cirAction.ethernet.dropLevel

       Possibilities:
               unchanged   (0)"
   ::= {er1646v2EfmBwEntry 4065001472}

er1646v2EfmBwActCirActEthDeFlag OBJECT-TYPE
   SYNTAX      INTEGER
               {
               unchanged (255),
               clear (0),
               set (1)
               }
   MAX-ACCESS  read-write
   STATUS      current
   DESCRIPTION
      "Path: efm.editConf.bandwidth.action.cirAction.ethernet.deFlag

       Possibilities:
               unchanged   (255)
               clear   (0)
               set   (1)"
   ::= {er1646v2EfmBwEntry 4065198080}

er1646v2EfmBwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EfmBwEntry 4071161856}

er1646v2EfmBwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EfmBwEntry 4071227392}

er1646v2EfmBwActCirActIpDrpLev OBJECT-TYPE
   SYNTAX      INTEGER
               {
               unchanged (0)
               }
   MAX-ACCESS  read-write
   STATUS      current
   DESCRIPTION
      "Path: efm.editConf.bandwidth.action.cirAction.ip.dropLevel

       Possibilities:
               unchanged   (0)"
   ::= {er1646v2EfmBwEntry 4071292928}

er1646v2EfmBwActCirActIpDeFlag OBJECT-TYPE
   SYNTAX      INTEGER
               {
               unchanged (255),
               clear (0),
               set (1)
               }
   MAX-ACCESS  read-write
   STATUS      current
   DESCRIPTION
      "Path: efm.editConf.bandwidth.action.cirAction.ip.deFlag

       Possibilities:
               unchanged   (255)
               clear   (0)
               set   (1)"
   ::= {er1646v2EfmBwEntry 4071489536}

er1646v2EfmBwActEirActNone OBJECT-TYPE
   SYNTAX      OCTET STRING
   MAX-ACCESS  read-write
   STATUS      current
   DESCRIPTION
      "Path: efm.editConf.bandwidth.action.eirAction.none"
   ::= {er1646v2EfmBwEntry 4095737856}

er1646v2EfmBwActEirActEthCos1 OBJECT-TYPE
   SYNTAX      INTEGER
               {
               unchanged (256)
               }
   MAX-ACCESS  read-write
   STATUS      current
   DESCRIPTION
      "Path: efm.editConf.bandwidth.action.eirAction.ethernet.cosDepth1

       Possibilities:
               unchanged   (256)"
   ::= {er1646v2EfmBwEntry 4097900544}

er1646v2EfmBwActEirActEthDei1 OBJECT-TYPE
   SYNTAX      INTEGER
               {
               unchanged (255),
               clear (0),
               set (1)
               }
   MAX-ACCESS  read-write
   STATUS      current
   DESCRIPTION
      "Path: efm.editConf.bandwidth.action.eirAction.ethernet.deiDepth1

       Possibilities:
               unchanged   (255)
               clear   (0)
               set   (1)"
   ::= {er1646v2EfmBwEntry 4099211264}

er1646v2EfmBwActEirActEthCos2 OBJECT-TYPE
   SYNTAX      INTEGER
               {
               unchanged (256)
               }
   MAX-ACCESS  read-write
   STATUS      current
   DESCRIPTION
      "Path: efm.editConf.bandwidth.action.eirAction.ethernet.cosDepth2

       Possibilities:
               unchanged   (256)"
   ::= {er1646v2EfmBwEntry 4097966080}

er1646v2EfmBwActEirActEthDei2 OBJECT-TYPE
   SYNTAX      INTEGER
               {
               unchanged (255),
               clear (0),
               set (1)
               }
   MAX-ACCESS  read-write
   STATUS      current
   DESCRIPTION
      "Path: efm.editConf.bandwidth.action.eirAction.ethernet.deiDepth2

       Possibilities:
               unchanged   (255)
               clear   (0)
               set   (1)"
   ::= {er1646v2EfmBwEntry 4099276800}

er1646v2EfmBwActEirActEthCos3 OBJECT-TYPE
   SYNTAX      INTEGER
               {
               unchanged (256)
               }
   MAX-ACCESS  read-write
   STATUS      current
   DESCRIPTION
      "Path: efm.editConf.bandwidth.action.eirAction.ethernet.cosDepth3

       Possibilities:
               unchanged   (256)"
   ::= {er1646v2EfmBwEntry 4098031616}

er1646v2EfmBwActEirActEthDei3 OBJECT-TYPE
   SYNTAX      INTEGER
               {
               unchanged (255),
               clear (0),
               set (1)
               }
   MAX-ACCESS  read-write
   STATUS      current
   DESCRIPTION
      "Path: efm.editConf.bandwidth.action.eirAction.ethernet.deiDepth3

       Possibilities:
               unchanged   (255)
               clear   (0)
               set   (1)"
   ::= {er1646v2EfmBwEntry 4099342336}

er1646v2EfmBwActEirActEthCos4 OBJECT-TYPE
   SYNTAX      INTEGER
               {
               unchanged (256)
               }
   MAX-ACCESS  read-write
   STATUS      current
   DESCRIPTION
      "Path: efm.editConf.bandwidth.action.eirAction.ethernet.cosDepth4

       Possibilities:
               unchanged   (256)"
   ::= {er1646v2EfmBwEntry 4098097152}

er1646v2EfmBwActEirActEthDei4 OBJECT-TYPE
   SYNTAX      INTEGER
               {
               unchanged (255),
               clear (0),
               set (1)
               }
   MAX-ACCESS  read-write
   STATUS      current
   DESCRIPTION
      "Path: efm.editConf.bandwidth.action.eirAction.ethernet.deiDepth4

       Possibilities:
               unchanged   (255)
               clear   (0)
               set   (1)"
   ::= {er1646v2EfmBwEntry 4099407872}

er1646v2EfmBwActEirActEthCos5 OBJECT-TYPE
   SYNTAX      INTEGER
               {
               unchanged (256)
               }
   MAX-ACCESS  read-write
   STATUS      current
   DESCRIPTION
      "Path: efm.editConf.bandwidth.action.eirAction.ethernet.cosDepth5

       Possibilities:
               unchanged   (256)"
   ::= {er1646v2EfmBwEntry 4098162688}

er1646v2EfmBwActEirActEthDei5 OBJECT-TYPE
   SYNTAX      INTEGER
               {
               unchanged (255),
               clear (0),
               set (1)
               }
   MAX-ACCESS  read-write
   STATUS      current
   DESCRIPTION
      "Path: efm.editConf.bandwidth.action.eirAction.ethernet.deiDepth5

       Possibilities:
               unchanged   (255)
               clear   (0)
               set   (1)"
   ::= {er1646v2EfmBwEntry 4099473408}

er1646v2EfmBwActEirActEthCos6 OBJECT-TYPE
   SYNTAX      INTEGER
               {
               unchanged (256)
               }
   MAX-ACCESS  read-write
   STATUS      current
   DESCRIPTION
      "Path: efm.editConf.bandwidth.action.eirAction.ethernet.cosDepth6

       Possibilities:
               unchanged   (256)"
   ::= {er1646v2EfmBwEntry 4098228224}

er1646v2EfmBwActEirActEthDei6 OBJECT-TYPE
   SYNTAX      INTEGER
               {
               unchanged (255),
               clear (0),
               set (1)
               }
   MAX-ACCESS  read-write
   STATUS      current
   DESCRIPTION
      "Path: efm.editConf.bandwidth.action.eirAction.ethernet.deiDepth6

       Possibilities:
               unchanged   (255)
               clear   (0)
               set   (1)"
   ::= {er1646v2EfmBwEntry 4099538944}

er1646v2EfmBwActEirActEthCos7 OBJECT-TYPE
   SYNTAX      INTEGER
               {
               unchanged (256)
               }
   MAX-ACCESS  read-write
   STATUS      current
   DESCRIPTION
      "Path: efm.editConf.bandwidth.action.eirAction.ethernet.cosDepth7

       Possibilities:
               unchanged   (256)"
   ::= {er1646v2EfmBwEntry 4098293760}

er1646v2EfmBwActEirActEthDei7 OBJECT-TYPE
   SYNTAX      INTEGER
               {
               unchanged (255),
               clear (0),
               set (1)
               }
   MAX-ACCESS  read-write
   STATUS      current
   DESCRIPTION
      "Path: efm.editConf.bandwidth.action.eirAction.ethernet.deiDepth7

       Possibilities:
               unchanged   (255)
               clear   (0)
               set   (1)"
   ::= {er1646v2EfmBwEntry 4099604480}

er1646v2EfmBwActEirActEthCos8 OBJECT-TYPE
   SYNTAX      INTEGER
               {
               unchanged (256)
               }
   MAX-ACCESS  read-write
   STATUS      current
   DESCRIPTION
      "Path: efm.editConf.bandwidth.action.eirAction.ethernet.cosDepth8

       Possibilities:
               unchanged   (256)"
   ::= {er1646v2EfmBwEntry 4098359296}

er1646v2EfmBwActEirActEthDei8 OBJECT-TYPE
   SYNTAX      INTEGER
               {
               unchanged (255),
               clear (0),
               set (1)
               }
   MAX-ACCESS  read-write
   STATUS      current
   DESCRIPTION
      "Path: efm.editConf.bandwidth.action.eirAction.ethernet.deiDepth8

       Possibilities:
               unchanged   (255)
               clear   (0)
               set   (1)"
   ::= {er1646v2EfmBwEntry 4099670016}

er1646v2EfmBwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EfmBwEntry 4098424832}

er1646v2EfmBwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EfmBwEntry 4098490368}

er1646v2EfmBwActEirActEthDrpLev OBJECT-TYPE
   SYNTAX      INTEGER
               {
               unchanged (0)
               }
   MAX-ACCESS  read-write
   STATUS      current
   DESCRIPTION
      "Path: efm.editConf.bandwidth.action.eirAction.ethernet.dropLevel

       Possibilities:
               unchanged   (0)"
   ::= {er1646v2EfmBwEntry 4098555904}

er1646v2EfmBwActEirActEthDeFlag OBJECT-TYPE
   SYNTAX      INTEGER
               {
               unchanged (255),
               clear (0),
               set (1)
               }
   MAX-ACCESS  read-write
   STATUS      current
   DESCRIPTION
      "Path: efm.editConf.bandwidth.action.eirAction.ethernet.deFlag

       Possibilities:
               unchanged   (255)
               clear   (0)
               set   (1)"
   ::= {er1646v2EfmBwEntry 4098752512}

er1646v2EfmBwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EfmBwEntry 4104716288}

er1646v2EfmBwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EfmBwEntry 4104781824}

er1646v2EfmBwActEirActIpDrpLev OBJECT-TYPE
   SYNTAX      INTEGER
               {
               unchanged (0)
               }
   MAX-ACCESS  read-write
   STATUS      current
   DESCRIPTION
      "Path: efm.editConf.bandwidth.action.eirAction.ip.dropLevel

       Possibilities:
               unchanged   (0)"
   ::= {er1646v2EfmBwEntry 4104847360}

er1646v2EfmBwActEirActIpDeFlag OBJECT-TYPE
   SYNTAX      INTEGER
               {
               unchanged (255),
               clear (0),
               set (1)
               }
   MAX-ACCESS  read-write
   STATUS      current
   DESCRIPTION
      "Path: efm.editConf.bandwidth.action.eirAction.ip.deFlag

       Possibilities:
               unchanged   (255)
               clear   (0)
               set   (1)"
   ::= {er1646v2EfmBwEntry 4105043968}

er1646v2EfmBwActViolActNone OBJECT-TYPE
   SYNTAX      OCTET STRING
   MAX-ACCESS  read-write
   STATUS      current
   DESCRIPTION
      "Path: efm.editConf.bandwidth.action.violateAction.none"
   ::= {er1646v2EfmBwEntry 4129292288}

er1646v2EfmBwActViolActDrop OBJECT-TYPE
   SYNTAX      OCTET STRING
   MAX-ACCESS  read-write
   STATUS      current
   DESCRIPTION
      "Path: efm.editConf.bandwidth.action.violateAction.drop"
   ::= {er1646v2EfmBwEntry 4133486592}

er1646v2EfmBwActViolActEthCos1 OBJECT-TYPE
   SYNTAX      INTEGER
               {
               unchanged (256)
               }
   MAX-ACCESS  read-write
   STATUS      current
   DESCRIPTION
      "Path: efm.editConf.bandwidth.action.violateAction.ethernet.cosDepth1

       Possibilities:
               unchanged   (256)"
   ::= {er1646v2EfmBwEntry 4131454976}

er1646v2EfmBwActViolActEthDei1 OBJECT-TYPE
   SYNTAX      INTEGER
               {
               unchanged (255),
               clear (0),
               set (1)
               }
   MAX-ACCESS  read-write
   STATUS      current
   DESCRIPTION
      "Path: efm.editConf.bandwidth.action.violateAction.ethernet.deiDepth1

       Possibilities:
               unchanged   (255)
               clear   (0)
               set   (1)"
   ::= {er1646v2EfmBwEntry 4132765696}

er1646v2EfmBwActViolActEthCos2 OBJECT-TYPE
   SYNTAX      INTEGER
               {
               unchanged (256)
               }
   MAX-ACCESS  read-write
   STATUS      current
   DESCRIPTION
      "Path: efm.editConf.bandwidth.action.violateAction.ethernet.cosDepth2

       Possibilities:
               unchanged   (256)"
   ::= {er1646v2EfmBwEntry 4131520512}

er1646v2EfmBwActViolActEthDei2 OBJECT-TYPE
   SYNTAX      INTEGER
               {
               unchanged (255),
               clear (0),
               set (1)
               }
   MAX-ACCESS  read-write
   STATUS      current
   DESCRIPTION
      "Path: efm.editConf.bandwidth.action.violateAction.ethernet.deiDepth2

       Possibilities:
               unchanged   (255)
               clear   (0)
               set   (1)"
   ::= {er1646v2EfmBwEntry 4132831232}

er1646v2EfmBwActViolActEthCos3 OBJECT-TYPE
   SYNTAX      INTEGER
               {
               unchanged (256)
               }
   MAX-ACCESS  read-write
   STATUS      current
   DESCRIPTION
      "Path: efm.editConf.bandwidth.action.violateAction.ethernet.cosDepth3

       Possibilities:
               unchanged   (256)"
   ::= {er1646v2EfmBwEntry 4131586048}

er1646v2EfmBwActViolActEthDei3 OBJECT-TYPE
   SYNTAX      INTEGER
               {
               unchanged (255),
               clear (0),
               set (1)
               }
   MAX-ACCESS  read-write
   STATUS      current
   DESCRIPTION
      "Path: efm.editConf.bandwidth.action.violateAction.ethernet.deiDepth3

       Possibilities:
               unchanged   (255)
               clear   (0)
               set   (1)"
   ::= {er1646v2EfmBwEntry 4132896768}

er1646v2EfmBwActViolActEthCos4 OBJECT-TYPE
   SYNTAX      INTEGER
               {
               unchanged (256)
               }
   MAX-ACCESS  read-write
   STATUS      current
   DESCRIPTION
      "Path: efm.editConf.bandwidth.action.violateAction.ethernet.cosDepth4

       Possibilities:
               unchanged   (256)"
   ::= {er1646v2EfmBwEntry 4131651584}

er1646v2EfmBwActViolActEthDei4 OBJECT-TYPE
   SYNTAX      INTEGER
               {
               unchanged (255),
               clear (0),
               set (1)
               }
   MAX-ACCESS  read-write
   STATUS      current
   DESCRIPTION
      "Path: efm.editConf.bandwidth.action.violateAction.ethernet.deiDepth4

       Possibilities:
               unchanged   (255)
               clear   (0)
               set   (1)"
   ::= {er1646v2EfmBwEntry 4132962304}

er1646v2EfmBwActViolActEthCos5 OBJECT-TYPE
   SYNTAX      INTEGER
               {
               unchanged (256)
               }
   MAX-ACCESS  read-write
   STATUS      current
   DESCRIPTION
      "Path: efm.editConf.bandwidth.action.violateAction.ethernet.cosDepth5

       Possibilities:
               unchanged   (256)"
   ::= {er1646v2EfmBwEntry 4131717120}

er1646v2EfmBwActViolActEthDei5 OBJECT-TYPE
   SYNTAX      INTEGER
               {
               unchanged (255),
               clear (0),
               set (1)
               }
   MAX-ACCESS  read-write
   STATUS      current
   DESCRIPTION
      "Path: efm.editConf.bandwidth.action.violateAction.ethernet.deiDepth5

       Possibilities:
               unchanged   (255)
               clear   (0)
               set   (1)"
   ::= {er1646v2EfmBwEntry 4133027840}

er1646v2EfmBwActViolActEthCos6 OBJECT-TYPE
   SYNTAX      INTEGER
               {
               unchanged (256)
               }
   MAX-ACCESS  read-write
   STATUS      current
   DESCRIPTION
      "Path: efm.editConf.bandwidth.action.violateAction.ethernet.cosDepth6

       Possibilities:
               unchanged   (256)"
   ::= {er1646v2EfmBwEntry 4131782656}

er1646v2EfmBwActViolActEthDei6 OBJECT-TYPE
   SYNTAX      INTEGER
               {
               unchanged (255),
               clear (0),
               set (1)
               }
   MAX-ACCESS  read-write
   STATUS      current
   DESCRIPTION
      "Path: efm.editConf.bandwidth.action.violateAction.ethernet.deiDepth6

       Possibilities:
               unchanged   (255)
               clear   (0)
               set   (1)"
   ::= {er1646v2EfmBwEntry 4133093376}

er1646v2EfmBwActViolActEthCos7 OBJECT-TYPE
   SYNTAX      INTEGER
               {
               unchanged (256)
               }
   MAX-ACCESS  read-write
   STATUS      current
   DESCRIPTION
      "Path: efm.editConf.bandwidth.action.violateAction.ethernet.cosDepth7

       Possibilities:
               unchanged   (256)"
   ::= {er1646v2EfmBwEntry 4131848192}

er1646v2EfmBwActViolActEthDei7 OBJECT-TYPE
   SYNTAX      INTEGER
               {
               unchanged (255),
               clear (0),
               set (1)
               }
   MAX-ACCESS  read-write
   STATUS      current
   DESCRIPTION
      "Path: efm.editConf.bandwidth.action.violateAction.ethernet.deiDepth7

       Possibilities:
               unchanged   (255)
               clear   (0)
               set   (1)"
   ::= {er1646v2EfmBwEntry 4133158912}

er1646v2EfmBwActViolActEthCos8 OBJECT-TYPE
   SYNTAX      INTEGER
               {
               unchanged (256)
               }
   MAX-ACCESS  read-write
   STATUS      current
   DESCRIPTION
      "Path: efm.editConf.bandwidth.action.violateAction.ethernet.cosDepth8

       Possibilities:
               unchanged   (256)"
   ::= {er1646v2EfmBwEntry 4131913728}

er1646v2EfmBwActViolActEthDei8 OBJECT-TYPE
   SYNTAX      INTEGER
               {
               unchanged (255),
               clear (0),
               set (1)
               }
   MAX-ACCESS  read-write
   STATUS      current
   DESCRIPTION
      "Path: efm.editConf.bandwidth.action.violateAction.ethernet.deiDepth8

       Possibilities:
               unchanged   (255)
               clear   (0)
               set   (1)"
   ::= {er1646v2EfmBwEntry 4133224448}

er1646v2EfmBwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EfmBwEntry 4131979264}

er1646v2EfmBwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EfmBwEntry 4132044800}

er1646v2EfmBwActViolActEthDrpLev OBJECT-TYPE
   SYNTAX      INTEGER
               {
               unchanged (0)
               }
   MAX-ACCESS  read-write
   STATUS      current
   DESCRIPTION
      "Path: efm.editConf.bandwidth.action.violateAction.ethernet.dropLevel

       Possibilities:
               unchanged   (0)"
   ::= {er1646v2EfmBwEntry 4132110336}

er1646v2EfmBwActViolActEthDeFlag OBJECT-TYPE
   SYNTAX      INTEGER
               {
               unchanged (255),
               clear (0),
               set (1)
               }
   MAX-ACCESS  read-write
   STATUS      current
   DESCRIPTION
      "Path: efm.editConf.bandwidth.action.violateAction.ethernet.deFlag

       Possibilities:
               unchanged   (255)
               clear   (0)
               set   (1)"
   ::= {er1646v2EfmBwEntry 4132306944}

er1646v2EfmBwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EfmBwEntry 4138270720}

er1646v2EfmBwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EfmBwEntry 4138336256}

er1646v2EfmBwActViolActIpDrpLev OBJECT-TYPE
   SYNTAX      INTEGER
               {
               unchanged (0)
               }
   MAX-ACCESS  read-write
   STATUS      current
   DESCRIPTION
      "Path: efm.editConf.bandwidth.action.violateAction.ip.dropLevel

       Possibilities:
               unchanged   (0)"
   ::= {er1646v2EfmBwEntry 4138401792}

er1646v2EfmBwActViolActIpDeFlag OBJECT-TYPE
   SYNTAX      INTEGER
               {
               unchanged (255),
               clear (0),
               set (1)
               }
   MAX-ACCESS  read-write
   STATUS      current
   DESCRIPTION
      "Path: efm.editConf.bandwidth.action.violateAction.ip.deFlag

       Possibilities:
               unchanged   (255)
               clear   (0)
               set   (1)"
   ::= {er1646v2EfmBwEntry 4138598400}


er1646v2EfmPriorityPolicy OBJECT-TYPE
   SYNTAX      DisplayString
   MAX-ACCESS  read-write
   STATUS      current
   DESCRIPTION
      "Path: efm.editConf.priorityPolicy
       Info: Preferred Policy"
   ::= {er1646v2Efm 39}


er1646v2EfmDelayOptimisation OBJECT-TYPE
   SYNTAX      INTEGER
               {
               disabled (0),
               enabled (1)
               }
   MAX-ACCESS  read-write
   STATUS      current
   DESCRIPTION
      "Path: efm.editConf.delayOptimisation
       Info: optimise delay

       Possibilities:
               disabled   (0)
               enabled   (1)"
   ::= {er1646v2Efm 80}


er1646v2EfmArp OBJECT IDENTIFIER ::= {er1646v2Efm 19}

er1646v2EfmArpSSC OBJECT IDENTIFIER ::= {er1646v2EfmArp 1}

er1646v2EfmArpEntry OBJECT IDENTIFIER ::= {er1646v2EfmArpSSC 1}

er1646v2EfmArpTimeOut OBJECT-TYPE
   SYNTAX      TimeTicks
   MAX-ACCESS  read-write
   STATUS      current
   DESCRIPTION
      "Path: efm.editConf.arp.timeOut

       Time in centi-second."
   ::= {er1646v2EfmArpEntry 201326592}

er1646v2EfmArpProxyArp OBJECT-TYPE
   SYNTAX      INTEGER
               {
               disabled (0),
               enabled (1)
               }
   MAX-ACCESS  read-write
   STATUS      current
   DESCRIPTION
      "Path: efm.editConf.arp.proxyArp

       Possibilities:
               disabled   (0)
               enabled   (1)"
   ::= {er1646v2EfmArpEntry 838860800}

er1646v2EfmArpStaticArp OBJECT-TYPE
   SYNTAX      SEQUENCE OF Er1646v2EfmArpStaticArpEntry
   MAX-ACCESS  not-accessible
   STATUS      current
   DESCRIPTION
      ""
   ::= {er1646v2EfmArp 50331648}

er1646v2EfmArpStaticArpEntry OBJECT-TYPE
   SYNTAX      Er1646v2EfmArpStaticArpEntry
   MAX-ACCESS  not-accessible
   STATUS      current
   DESCRIPTION
      ""
   INDEX      { er1646v2EfmArpStaticArpTableIx }
   ::= {er1646v2EfmArpStaticArp 1}

Er1646v2EfmArpStaticArpEntry ::=
   SEQUENCE
      {
      er1646v2EfmArpStaticArpActions
         VariableLengthTableActions,
      er1646v2EfmArpStaticArpTableIx
         TableIndex,
      er1646v2EfmArpStaticArpMacAddress
         OCTET STRING,
      er1646v2EfmArpStaticArpIpAddress
         IpAddress
      }

er1646v2EfmArpStaticArpActions OBJECT-TYPE
   SYNTAX      VariableLengthTableActions
   MAX-ACCESS  read-write
   STATUS      current
   DESCRIPTION
      "By way of this field, some manipulations
       on this table may be performed."
   ::= {er1646v2EfmArpStaticArpEntry 2}

er1646v2EfmArpStaticArpTableIx OBJECT-TYPE
   SYNTAX      TableIndex
   MAX-ACCESS  not-accessible
   STATUS      current
   DESCRIPTION
      ""
   ::= {er1646v2EfmArpStaticArpEntry 11}

er1646v2EfmArpStaticArpMacAddress OBJECT-TYPE
   SYNTAX      OCTET STRING
   MAX-ACCESS  read-write
   STATUS      current
   DESCRIPTION
      "Path: efm.editConf.arp.staticArp.macAddress

       MAC address."
   ::= {er1646v2EfmArpStaticArpEntry 16777216}

er1646v2EfmArpStaticArpIpAddress OBJECT-TYPE
   SYNTAX      IpAddress
   MAX-ACCESS  read-write
   STATUS      current
   DESCRIPTION
      "Path: efm.editConf.arp.staticArp.ipAddress"
   ::= {er1646v2EfmArpStaticArpEntry 33554432}


er1646v2EfmBrC OBJECT IDENTIFIER ::= {er1646v2Efm 27}

er1646v2EfmBrCSSC OBJECT IDENTIFIER ::= {er1646v2EfmBrC 1}

er1646v2EfmBrCEntry OBJECT IDENTIFIER ::= {er1646v2EfmBrCSSC 1}

er1646v2EfmBrCAccessList OBJECT-TYPE
   SYNTAX      DisplayString
   MAX-ACCESS  read-write
   STATUS      current
   DESCRIPTION
      "Path: efm.editConf.bridging.accessList"
   ::= {er1646v2EfmBrCEntry 83886080}

er1646v2EfmBrCInAccessList OBJECT-TYPE
   SYNTAX      DisplayString
   MAX-ACCESS  read-write
   STATUS      current
   DESCRIPTION
      "Path: efm.editConf.bridging.inAccessList"
   ::= {er1646v2EfmBrCEntry 251658240}

er1646v2EfmBrCTp OBJECT-TYPE
   SYNTAX      DisplayString
   MAX-ACCESS  read-write
   STATUS      current
   DESCRIPTION
      "Path: efm.editConf.bridging.trafficPolicy"
   ::= {er1646v2EfmBrCEntry 100663296}

er1646v2EfmBrCBridgeGroup OBJECT-TYPE
   SYNTAX      DisplayString
   MAX-ACCESS  read-write
   STATUS      current
   DESCRIPTION
      "Path: efm.editConf.bridging.bridgeGroup"
   ::= {er1646v2EfmBrCEntry 117440512}

er1646v2EfmBrCLimBC OBJECT-TYPE
   SYNTAX      INTEGER
               {
               disabled (0),
               enabled (1)
               }
   MAX-ACCESS  read-write
   STATUS      current
   DESCRIPTION
      "Path: efm.editConf.bridging.limitBroadcasts

       Possibilities:
               disabled   (0)
               enabled   (1)"
   ::= {er1646v2EfmBrCEntry 134217728}

er1646v2EfmBrCPrivateMode OBJECT-TYPE
   SYNTAX      INTEGER
               {
               disabled (0),
               enabled (1)
               }
   MAX-ACCESS  read-write
   STATUS      current
   DESCRIPTION
      "Path: efm.editConf.bridging.privateMode

       Possibilities:
               disabled   (0)
               enabled   (1)"
   ::= {er1646v2EfmBrCEntry 419430400}

er1646v2EfmBrCLearning OBJECT-TYPE
   SYNTAX      INTEGER
               {
               disabled (0),
               enabled (1)
               }
   MAX-ACCESS  read-write
   STATUS      current
   DESCRIPTION
      "Path: efm.editConf.bridging.learning

       Possibilities:
               disabled   (0)
               enabled   (1)"
   ::= {er1646v2EfmBrCEntry 201326592}

er1646v2EfmBrCMaxCacheSize OBJECT-TYPE
   SYNTAX      INTEGER
               {
               unlimited (0)
               }
   MAX-ACCESS  read-write
   STATUS      current
   DESCRIPTION
      "Path: efm.editConf.bridging.maxCacheSize

       Possibilities:
               unlimited   (0)"
   ::= {er1646v2EfmBrCEntry 218103808}

er1646v2EfmBrCRelearnDropOnRelearn OBJECT-TYPE
   SYNTAX      INTEGER
               {
               disabled (0),
               enabled (1)
               }
   MAX-ACCESS  read-write
   STATUS      current
   DESCRIPTION
      "Path: efm.editConf.bridging.relearn.dropOnRelearn

       Possibilities:
               disabled   (0)
               enabled   (1)"
   ::= {er1646v2EfmBrCEntry 234946560}

er1646v2EfmBrCRelearnShutdownThreshold OBJECT-TYPE
   SYNTAX      Integer32
   MAX-ACCESS  read-write
   STATUS      current
   DESCRIPTION
      "Path: efm.editConf.bridging.relearn.shutdownThreshold"
   ::= {er1646v2EfmBrCEntry 235012096}

er1646v2EfmBrCRelearnShutdownTime OBJECT-TYPE
   SYNTAX      TimeTicks
   MAX-ACCESS  read-write
   STATUS      current
   DESCRIPTION
      "Path: efm.editConf.bridging.relearn.shutdownTime

       Time in centi-second."
   ::= {er1646v2EfmBrCEntry 235077632}

er1646v2EfmBrCRelearnLoopDetection OBJECT-TYPE
   SYNTAX      INTEGER
               {
               disabled (0),
               passive (1),
               active (2)
               }
   MAX-ACCESS  read-write
   STATUS      current
   DESCRIPTION
      "Path: efm.editConf.bridging.relearn.loopDetection

       Possibilities:
               disabled   (0)
               passive   (1)
               active   (2)"
   ::= {er1646v2EfmBrCEntry 235143168}

er1646v2EfmBrCRelearnLoopDetectionInterval OBJECT-TYPE
   SYNTAX      TimeTicks
   MAX-ACCESS  read-write
   STATUS      current
   DESCRIPTION
      "Path: efm.editConf.bridging.relearn.loopDetectionInterval

       Time in centi-second."
   ::= {er1646v2EfmBrCEntry 235208704}

er1646v2EfmBrCVlanMemberShip OBJECT-TYPE
   SYNTAX      INTEGER
               {
               all (0),
               none (1),
               grouped (2)
               }
   MAX-ACCESS  read-write
   STATUS      current
   DESCRIPTION
      "Path: efm.editConf.bridging.vlanMemberShip

       Possibilities:
               all   (0)
               none   (1)
               grouped   (2)"
   ::= {er1646v2EfmBrCEntry 318767104}

er1646v2EfmBrCDot1adType OBJECT-TYPE
   SYNTAX      INTEGER
               {
               slOPTg (0),
               cPort (4),
               sPort (1),
               nni (2)
               }
   MAX-ACCESS  read-write
   STATUS      current
   DESCRIPTION
      "Path: efm.editConf.bridging.dot1ad.type

       Possibilities:
               <OPT>   (0)
               cPort   (4)
               sPort   (1)
               nni   (2)"
   ::= {er1646v2EfmBrCEntry 503382016}

er1646v2EfmBrCPriority OBJECT-TYPE
   SYNTAX      Integer32
   MAX-ACCESS  read-write
   STATUS      current
   DESCRIPTION
      "Path: efm.editConf.bridging.priority"
   ::= {er1646v2EfmBrCEntry 33554432}

er1646v2EfmBrCPathCost OBJECT-TYPE
   SYNTAX      Integer32
   MAX-ACCESS  read-write
   STATUS      current
   DESCRIPTION
      "Path: efm.editConf.bridging.pathCost"
   ::= {er1646v2EfmBrCEntry 50331648}

er1646v2EfmBrCInternalPathCost OBJECT-TYPE
   SYNTAX      Integer32
   MAX-ACCESS  read-write
   STATUS      current
   DESCRIPTION
      "Path: efm.editConf.bridging.internalPathCost"
   ::= {er1646v2EfmBrCEntry 301989888}

er1646v2EfmBrCTCD OBJECT-TYPE
   SYNTAX      INTEGER
               {
               disabled (0),
               enabled (1)
               }
   MAX-ACCESS  read-write
   STATUS      current
   DESCRIPTION
      "Path: efm.editConf.bridging.topologyChangeDetection

       Possibilities:
               disabled   (0)
               enabled   (1)"
   ::= {er1646v2EfmBrCEntry 67108864}

er1646v2EfmBrCRestrictedRole OBJECT-TYPE
   SYNTAX      INTEGER
               {
               disabled (0),
               enabled (1)
               }
   MAX-ACCESS  read-write
   STATUS      current
   DESCRIPTION
      "Path: efm.editConf.bridging.restrictedRole

       Possibilities:
               disabled   (0)
               enabled   (1)"
   ::= {er1646v2EfmBrCEntry 335544320}

er1646v2EfmBrCAdminEdge OBJECT-TYPE
   SYNTAX      INTEGER
               {
               disabled (0),
               enabled (1)
               }
   MAX-ACCESS  read-write
   STATUS      current
   DESCRIPTION
      "Path: efm.editConf.bridging.adminEdge

       Possibilities:
               disabled   (0)
               enabled   (1)"
   ::= {er1646v2EfmBrCEntry 268435456}

er1646v2EfmBrCMgmtInline OBJECT-TYPE
   SYNTAX      INTEGER
               {
               disabled (0),
               enabled (1)
               }
   MAX-ACCESS  read-write
   STATUS      current
   DESCRIPTION
      "Path: efm.editConf.bridging.mgmtInline

       Possibilities:
               disabled   (0)
               enabled   (1)"
   ::= {er1646v2EfmBrCEntry 369098752}

er1646v2EfmBrCL2ptMode OBJECT-TYPE
   SYNTAX      INTEGER
               {
               disabled (0),
               enabled (1)
               }
   MAX-ACCESS  read-write
   STATUS      current
   DESCRIPTION
      "Path: efm.editConf.bridging.l2ProtTunnel.mode

       Possibilities:
               disabled   (0)
               enabled   (1)"
   ::= {er1646v2EfmBrCEntry 403701760}

er1646v2EfmBrCL2ptProtocols OBJECT-TYPE
   SYNTAX      Integer32
   MAX-ACCESS  read-write
   STATUS      current
   DESCRIPTION
      "Path: efm.editConf.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1646v2EfmBrCEntry 404750336}

er1646v2EfmBrCL2ptDestMac OBJECT-TYPE
   SYNTAX      OCTET STRING
   MAX-ACCESS  read-write
   STATUS      current
   DESCRIPTION
      "Path: efm.editConf.bridging.l2ProtTunnel.destinationMac

       MAC address."
   ::= {er1646v2EfmBrCEntry 405798912}

er1646v2EfmBrCL2ptCos OBJECT-TYPE
   SYNTAX      INTEGER
               {
               unchanged (255)
               }
   MAX-ACCESS  read-write
   STATUS      current
   DESCRIPTION
      "Path: efm.editConf.bridging.l2ProtTunnel.cos

       Possibilities:
               unchanged   (255)"
   ::= {er1646v2EfmBrCEntry 406847488}

er1646v2EfmBrCL2ptDropThrStp OBJECT-TYPE
   SYNTAX      INTEGER
               {
               unlimited (0)
               }
   UNITS       "packets/sec"
   MAX-ACCESS  read-write
   STATUS      current
   DESCRIPTION
      "Path: efm.editConf.bridging.l2ProtTunnel.dropThresholds.stp

       unit name = packets/sec

       Possibilities:
               unlimited   (0)"
   ::= {er1646v2EfmBrCEntry 407900160}

er1646v2EfmBrCL2ptDropThrLldp OBJECT-TYPE
   SYNTAX      INTEGER
               {
               unlimited (0)
               }
   UNITS       "packets/sec"
   MAX-ACCESS  read-write
   STATUS      current
   DESCRIPTION
      "Path: efm.editConf.bridging.l2ProtTunnel.dropThresholds.lldp

       unit name = packets/sec

       Possibilities:
               unlimited   (0)"
   ::= {er1646v2EfmBrCEntry 407904256}

er1646v2EfmBrCL2ptDropThrOam OBJECT-TYPE
   SYNTAX      INTEGER
               {
               unlimited (0)
               }
   UNITS       "packets/sec"
   MAX-ACCESS  read-write
   STATUS      current
   DESCRIPTION
      "Path: efm.editConf.bridging.l2ProtTunnel.dropThresholds.oam

       unit name = packets/sec

       Possibilities:
               unlimited   (0)"
   ::= {er1646v2EfmBrCEntry 407908352}

er1646v2EfmBrCL2ptDropThrCdp OBJECT-TYPE
   SYNTAX      INTEGER
               {
               unlimited (0)
               }
   UNITS       "packets/sec"
   MAX-ACCESS  read-write
   STATUS      current
   DESCRIPTION
      "Path: efm.editConf.bridging.l2ProtTunnel.dropThresholds.cdp

       unit name = packets/sec

       Possibilities:
               unlimited   (0)"
   ::= {er1646v2EfmBrCEntry 407912448}

er1646v2EfmBrCL2ptDropThrVtp OBJECT-TYPE
   SYNTAX      INTEGER
               {
               unlimited (0)
               }
   UNITS       "packets/sec"
   MAX-ACCESS  read-write
   STATUS      current
   DESCRIPTION
      "Path: efm.editConf.bridging.l2ProtTunnel.dropThresholds.vtp

       unit name = packets/sec

       Possibilities:
               unlimited   (0)"
   ::= {er1646v2EfmBrCEntry 407916544}

er1646v2EfmBrCL2ptDropThrLacp OBJECT-TYPE
   SYNTAX      INTEGER
               {
               unlimited (0)
               }
   UNITS       "packets/sec"
   MAX-ACCESS  read-write
   STATUS      current
   DESCRIPTION
      "Path: efm.editConf.bridging.l2ProtTunnel.dropThresholds.lacp

       unit name = packets/sec

       Possibilities:
               unlimited   (0)"
   ::= {er1646v2EfmBrCEntry 407920640}

er1646v2EfmBrCL2ptDropThrEfmOam OBJECT-TYPE
   SYNTAX      INTEGER
               {
               unlimited (0)
               }
   UNITS       "packets/sec"
   MAX-ACCESS  read-write
   STATUS      current
   DESCRIPTION
      "Path: efm.editConf.bridging.l2ProtTunnel.dropThresholds.efmOam

       unit name = packets/sec

       Possibilities:
               unlimited   (0)"
   ::= {er1646v2EfmBrCEntry 407924736}

er1646v2EfmBrCL2ptDropThrPvst OBJECT-TYPE
   SYNTAX      INTEGER
               {
               unlimited (0)
               }
   UNITS       "packets/sec"
   MAX-ACCESS  read-write
   STATUS      current
   DESCRIPTION
      "Path: efm.editConf.bridging.l2ProtTunnel.dropThresholds.pvst

       unit name = packets/sec

       Possibilities:
               unlimited   (0)"
   ::= {er1646v2EfmBrCEntry 407928832}

er1646v2EfmBrCL2ptDropThrMmrp OBJECT-TYPE
   SYNTAX      INTEGER
               {
               unlimited (0)
               }
   UNITS       "packets/sec"
   MAX-ACCESS  read-write
   STATUS      current
   DESCRIPTION
      "Path: efm.editConf.bridging.l2ProtTunnel.dropThresholds.mmrp

       unit name = packets/sec

       Possibilities:
               unlimited   (0)"
   ::= {er1646v2EfmBrCEntry 407932928}

er1646v2EfmBrCL2ptDropThrMvrp OBJECT-TYPE
   SYNTAX      INTEGER
               {
               unlimited (0)
               }
   UNITS       "packets/sec"
   MAX-ACCESS  read-write
   STATUS      current
   DESCRIPTION
      "Path: efm.editConf.bridging.l2ProtTunnel.dropThresholds.mvrp

       unit name = packets/sec

       Possibilities:
               unlimited   (0)"
   ::= {er1646v2EfmBrCEntry 407937024}

er1646v2EfmBrCL2ptDropThrGvrp OBJECT-TYPE
   SYNTAX      INTEGER
               {
               unlimited (0)
               }
   UNITS       "packets/sec"
   MAX-ACCESS  read-write
   STATUS      current
   DESCRIPTION
      "Path: efm.editConf.bridging.l2ProtTunnel.dropThresholds.gvrp

       unit name = packets/sec

       Possibilities:
               unlimited   (0)"
   ::= {er1646v2EfmBrCEntry 407941120}

er1646v2EfmBrCL2ptDropThrGmrp OBJECT-TYPE
   SYNTAX      INTEGER
               {
               unlimited (0)
               }
   UNITS       "packets/sec"
   MAX-ACCESS  read-write
   STATUS      current
   DESCRIPTION
      "Path: efm.editConf.bridging.l2ProtTunnel.dropThresholds.gmrp

       unit name = packets/sec

       Possibilities:
               unlimited   (0)"
   ::= {er1646v2EfmBrCEntry 407945216}

er1646v2EfmBrCL2ptDropThrDtp OBJECT-TYPE
   SYNTAX      INTEGER
               {
               unlimited (0)
               }
   UNITS       "packets/sec"
   MAX-ACCESS  read-write
   STATUS      current
   DESCRIPTION
      "Path: efm.editConf.bridging.l2ProtTunnel.dropThresholds.dtp

       unit name = packets/sec

       Possibilities:
               unlimited   (0)"
   ::= {er1646v2EfmBrCEntry 407949312}

er1646v2EfmBrCL2ptDropThrPagp OBJECT-TYPE
   SYNTAX      INTEGER
               {
               unlimited (0)
               }
   UNITS       "packets/sec"
   MAX-ACCESS  read-write
   STATUS      current
   DESCRIPTION
      "Path: efm.editConf.bridging.l2ProtTunnel.dropThresholds.pagp

       unit name = packets/sec

       Possibilities:
               unlimited   (0)"
   ::= {er1646v2EfmBrCEntry 407953408}

er1646v2EfmBrCL2ptDropThrUdld OBJECT-TYPE
   SYNTAX      INTEGER
               {
               unlimited (0)
               }
   UNITS       "packets/sec"
   MAX-ACCESS  read-write
   STATUS      current
   DESCRIPTION
      "Path: efm.editConf.bridging.l2ProtTunnel.dropThresholds.udld

       unit name = packets/sec

       Possibilities:
               unlimited   (0)"
   ::= {er1646v2EfmBrCEntry 407957504}


er1646v2EfmVlanTagging OBJECT IDENTIFIER ::= {er1646v2Efm 14}

er1646v2EfmVlanTaggingSSC OBJECT IDENTIFIER ::= {er1646v2EfmVlanTagging 1}

er1646v2EfmVlanTaggingEntry OBJECT IDENTIFIER ::= {er1646v2EfmVlanTaggingSSC 1}

er1646v2EfmVlanTaggingUntaggedAction OBJECT-TYPE
   SYNTAX      INTEGER
               {
               discard (0),
               accept (1),
               tag (2)
               }
   MAX-ACCESS  read-write
   STATUS      current
   DESCRIPTION
      "Path: efm.editConf.vlanTagging.untagged.action

       Possibilities:
               discard   (0)
               accept   (1)
               tag   (2)"
   ::= {er1646v2EfmVlanTaggingEntry 671088640}

er1646v2EfmVlanTaggingUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: efm.editConf.vlanTagging.untagged.tagInfo.tpid

       Possibilities:
               dot1Q   (33024)
               dot1ad   (34984)
               0x9100   (37120)
               0x9200   (37376)
               0x9300   (37632)"
   ::= {er1646v2EfmVlanTaggingEntry 746586112}

er1646v2EfmVlanTaggingUntaggedTagInfoVid OBJECT-TYPE
   SYNTAX      Integer32
   MAX-ACCESS  read-write
   STATUS      current
   DESCRIPTION
      "Path: efm.editConf.vlanTagging.untagged.tagInfo.vid"
   ::= {er1646v2EfmVlanTaggingEntry 754974720}

er1646v2EfmVlanTaggingUnknownVlansAction OBJECT-TYPE
   SYNTAX      INTEGER
               {
               discard (0),
               accept (1),
               tag (2)
               }
   MAX-ACCESS  read-write
   STATUS      current
   DESCRIPTION
      "Path: efm.editConf.vlanTagging.unknownVlans.action

       Possibilities:
               discard   (0)
               accept   (1)
               tag   (2)"
   ::= {er1646v2EfmVlanTaggingEntry 1744830464}

er1646v2EfmVlanTaggingUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: efm.editConf.vlanTagging.unknownVlans.tagInfo.tpid

       Possibilities:
               dot1Q   (33024)
               dot1ad   (34984)
               0x9100   (37120)
               0x9200   (37376)
               0x9300   (37632)"
   ::= {er1646v2EfmVlanTaggingEntry 1820327936}

er1646v2EfmVlanTaggingUnknownVlansTagInfoVid OBJECT-TYPE
   SYNTAX      Integer32
   MAX-ACCESS  read-write
   STATUS      current
   DESCRIPTION
      "Path: efm.editConf.vlanTagging.unknownVlans.tagInfo.vid"
   ::= {er1646v2EfmVlanTaggingEntry 1828716544}

er1646v2EfmVlanTaggingVlans OBJECT-TYPE
   SYNTAX      SEQUENCE OF Er1646v2EfmVlanTaggingVlansEntry
   MAX-ACCESS  not-accessible
   STATUS      current
   DESCRIPTION
      ""
   ::= {er1646v2EfmVlanTagging 1073741824}

er1646v2EfmVlanTaggingVlansEntry OBJECT-TYPE
   SYNTAX      Er1646v2EfmVlanTaggingVlansEntry
   MAX-ACCESS  not-accessible
   STATUS      current
   DESCRIPTION
      ""
   INDEX      { er1646v2EfmVlanTaggingVlansTableIx }
   ::= {er1646v2EfmVlanTaggingVlans 1}

Er1646v2EfmVlanTaggingVlansEntry ::=
   SEQUENCE
      {
      er1646v2EfmVlanTaggingVlansActions
         VariableLengthTableActions,
      er1646v2EfmVlanTaggingVlansTableIx
         TableIndex,
      er1646v2EfmVlanTaggingVlansVid
         Integer32,
      er1646v2EfmVlanTaggingVlansEndVid
         Integer32,
      er1646v2EfmVlanTaggingVlansAction
         INTEGER,
      er1646v2EfmVlanTaggingVlansTagInfoTpid
         INTEGER,
      er1646v2EfmVlanTaggingVlansTagInfoVid
         Integer32
      }

er1646v2EfmVlanTaggingVlansActions OBJECT-TYPE
   SYNTAX      VariableLengthTableActions
   MAX-ACCESS  read-write
   STATUS      current
   DESCRIPTION
      "By way of this field, some manipulations
       on this table may be performed."
   ::= {er1646v2EfmVlanTaggingVlansEntry 2}

er1646v2EfmVlanTaggingVlansTableIx OBJECT-TYPE
   SYNTAX      TableIndex
   MAX-ACCESS  not-accessible
   STATUS      current
   DESCRIPTION
      ""
   ::= {er1646v2EfmVlanTaggingVlansEntry 11}

er1646v2EfmVlanTaggingVlansVid OBJECT-TYPE
   SYNTAX      Integer32
   MAX-ACCESS  read-write
   STATUS      current
   DESCRIPTION
      "Path: efm.editConf.vlanTagging.vlans.vid"
   ::= {er1646v2EfmVlanTaggingVlansEntry 536870912}

er1646v2EfmVlanTaggingVlansEndVid OBJECT-TYPE
   SYNTAX      Integer32
   MAX-ACCESS  read-write
   STATUS      current
   DESCRIPTION
      "Path: efm.editConf.vlanTagging.vlans.endVid"
   ::= {er1646v2EfmVlanTaggingVlansEntry 2147483648}

er1646v2EfmVlanTaggingVlansAction OBJECT-TYPE
   SYNTAX      INTEGER
               {
               discard (0),
               accept (1),
               tag (2)
               }
   MAX-ACCESS  read-write
   STATUS      current
   DESCRIPTION
      "Path: efm.editConf.vlanTagging.vlans.action

       Possibilities:
               discard   (0)
               accept   (1)
               tag   (2)"
   ::= {er1646v2EfmVlanTaggingVlansEntry 1073741824}

er1646v2EfmVlanTaggingVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: efm.editConf.vlanTagging.vlans.tagInfo.tpid

       Possibilities:
               dot1Q   (33024)
               dot1ad   (34984)
               0x9100   (37120)
               0x9200   (37376)
               0x9300   (37632)"
   ::= {er1646v2EfmVlanTaggingVlansEntry 1677721600}

er1646v2EfmVlanTaggingVlansTagInfoVid OBJECT-TYPE
   SYNTAX      Integer32
   MAX-ACCESS  read-write
   STATUS      current
   DESCRIPTION
      "Path: efm.editConf.vlanTagging.vlans.tagInfo.vid"
   ::= {er1646v2EfmVlanTaggingVlansEntry 1744830464}


er1646v2EfmOam OBJECT IDENTIFIER ::= {er1646v2Efm 900}

er1646v2EfmOamSSC OBJECT IDENTIFIER ::= {er1646v2EfmOam 1}

er1646v2EfmOamEntry OBJECT IDENTIFIER ::= {er1646v2EfmOamSSC 1}

er1646v2EfmOamMode OBJECT-TYPE
   SYNTAX      INTEGER
               {
               disabled (0),
               passive (3),
               active (2)
               }
   MAX-ACCESS  read-write
   STATUS      current
   DESCRIPTION
      "Path: efm.editConf.oam.mode

       Possibilities:
               disabled   (0)
               passive   (3)
               active   (2)"
   ::= {er1646v2EfmOamEntry 16777216}

er1646v2EfmOamLpbkLocalParAction OBJECT-TYPE
   SYNTAX      INTEGER
               {
               discard (0),
               forward (1)
               }
   MAX-ACCESS  read-write
   STATUS      current
   DESCRIPTION
      "Path: efm.editConf.oam.loopbackLocalParserAction

       Possibilities:
               discard   (0)
               forward   (1)"
   ::= {er1646v2EfmOamEntry 33554432}

er1646v2EfmOamLpbkSwapMacAddr OBJECT-TYPE
   SYNTAX      INTEGER
               {
               disabled (0),
               enabled (1)
               }
   MAX-ACCESS  read-write
   STATUS      current
   DESCRIPTION
      "Path: efm.editConf.oam.loopbackSwapMacAddresses

       Possibilities:
               disabled   (0)
               enabled   (1)"
   ::= {er1646v2EfmOamEntry 50331648}

er1646v2EfmOamLoopbackIgnoreRx OBJECT-TYPE
   SYNTAX      INTEGER
               {
               no (0),
               yes (1)
               }
   MAX-ACCESS  read-write
   STATUS      current
   DESCRIPTION
      "Path: efm.editConf.oam.loopbackIgnoreRx

       Possibilities:
               no   (0)
               yes   (1)"
   ::= {er1646v2EfmOamEntry 67108864}

er1646v2EfmOamEventsErroredSymbolEnabled OBJECT-TYPE
   SYNTAX      INTEGER
               {
               no (0),
               yes (1)
               }
   MAX-ACCESS  read-write
   STATUS      current
   DESCRIPTION
      "Path: efm.editConf.oam.events.erroredSymbol.enabled

       Possibilities:
               no   (0)
               yes   (1)"
   ::= {er1646v2EfmOamEntry 83951872}

er1646v2EfmOamEventsErroredSymbolWindowHi OBJECT-TYPE
   SYNTAX      INTEGER
               {
               default (0)
               }
   UNITS       "symbols"
   MAX-ACCESS  read-write
   STATUS      current
   DESCRIPTION
      "Path: efm.editConf.oam.events.erroredSymbol.windowHi

       unit name = symbols

       Possibilities:
               default   (0)"
   ::= {er1646v2EfmOamEntry 83952128}

er1646v2EfmOamEventsErroredSymbolWindowLo OBJECT-TYPE
   SYNTAX      INTEGER
               {
               default (0)
               }
   UNITS       "symbols"
   MAX-ACCESS  read-write
   STATUS      current
   DESCRIPTION
      "Path: efm.editConf.oam.events.erroredSymbol.windowLo

       unit name = symbols

       Possibilities:
               default   (0)"
   ::= {er1646v2EfmOamEntry 83952384}

er1646v2EfmOamEventsErroredSymbolThresholdHi OBJECT-TYPE
   SYNTAX      Integer32
   UNITS       "symbols"
   MAX-ACCESS  read-write
   STATUS      current
   DESCRIPTION
      "Path: efm.editConf.oam.events.erroredSymbol.thresholdHi

       unit name = symbols"
   ::= {er1646v2EfmOamEntry 83952640}

er1646v2EfmOamEventsErroredSymbolThresholdLo OBJECT-TYPE
   SYNTAX      Integer32
   UNITS       "symbols"
   MAX-ACCESS  read-write
   STATUS      current
   DESCRIPTION
      "Path: efm.editConf.oam.events.erroredSymbol.thresholdLo

       unit name = symbols"
   ::= {er1646v2EfmOamEntry 83952896}

er1646v2EfmOamEventsErroredFramePeriodEnabled OBJECT-TYPE
   SYNTAX      INTEGER
               {
               no (0),
               yes (1)
               }
   MAX-ACCESS  read-write
   STATUS      current
   DESCRIPTION
      "Path: efm.editConf.oam.events.erroredFramePeriod.enabled

       Possibilities:
               no   (0)
               yes   (1)"
   ::= {er1646v2EfmOamEntry 84017408}

er1646v2EfmOamEventsErroredFramePeriodWindow OBJECT-TYPE
   SYNTAX      INTEGER
               {
               default (0)
               }
   UNITS       "frames"
   MAX-ACCESS  read-write
   STATUS      current
   DESCRIPTION
      "Path: efm.editConf.oam.events.erroredFramePeriod.window

       unit name = frames

       Possibilities:
               default   (0)"
   ::= {er1646v2EfmOamEntry 84017664}

er1646v2EfmOamEventsErroredFramePeriodThreshold OBJECT-TYPE
   SYNTAX      Integer32
   UNITS       "frames"
   MAX-ACCESS  read-write
   STATUS      current
   DESCRIPTION
      "Path: efm.editConf.oam.events.erroredFramePeriod.threshold

       unit name = frames"
   ::= {er1646v2EfmOamEntry 84017920}

er1646v2EfmOamEventsErroredFrameEnabled OBJECT-TYPE
   SYNTAX      INTEGER
               {
               no (0),
               yes (1)
               }
   MAX-ACCESS  read-write
   STATUS      current
   DESCRIPTION
      "Path: efm.editConf.oam.events.erroredFrame.enabled

       Possibilities:
               no   (0)
               yes   (1)"
   ::= {er1646v2EfmOamEntry 84082944}

er1646v2EfmOamEventsErroredFrameWindow OBJECT-TYPE
   SYNTAX      Integer32
   UNITS       "100msec"
   MAX-ACCESS  read-write
   STATUS      current
   DESCRIPTION
      "Path: efm.editConf.oam.events.erroredFrame.window

       unit name = 100msec"
   ::= {er1646v2EfmOamEntry 84083200}

er1646v2EfmOamEventsErroredFrameThreshold OBJECT-TYPE
   SYNTAX      Integer32
   UNITS       "frames"
   MAX-ACCESS  read-write
   STATUS      current
   DESCRIPTION
      "Path: efm.editConf.oam.events.erroredFrame.threshold

       unit name = frames"
   ::= {er1646v2EfmOamEntry 84083456}

er1646v2EfmOamEventsErroredFrameSecondsEnabled OBJECT-TYPE
   SYNTAX      INTEGER
               {
               no (0),
               yes (1)
               }
   MAX-ACCESS  read-write
   STATUS      current
   DESCRIPTION
      "Path: efm.editConf.oam.events.erroredFrameSeconds.enabled

       Possibilities:
               no   (0)
               yes   (1)"
   ::= {er1646v2EfmOamEntry 84148480}

er1646v2EfmOamEventsErroredFrameSecondsWindow OBJECT-TYPE
   SYNTAX      Integer32
   UNITS       "100msec"
   MAX-ACCESS  read-write
   STATUS      current
   DESCRIPTION
      "Path: efm.editConf.oam.events.erroredFrameSeconds.window

       unit name = 100msec"
   ::= {er1646v2EfmOamEntry 84148736}

er1646v2EfmOamEventsErroredFrameSecondsThreshold OBJECT-TYPE
   SYNTAX      Integer32
   UNITS       "frames"
   MAX-ACCESS  read-write
   STATUS      current
   DESCRIPTION
      "Path: efm.editConf.oam.events.erroredFrameSeconds.threshold

       unit name = frames"
   ::= {er1646v2EfmOamEntry 84148992}

er1646v2EfmOamEventsDyingGasp OBJECT-TYPE
   SYNTAX      INTEGER
               {
               disabled (0),
               enabled (1)
               }
   MAX-ACCESS  read-write
   STATUS      current
   DESCRIPTION
      "Path: efm.editConf.oam.events.dyingGasp

       Possibilities:
               disabled   (0)
               enabled   (1)"
   ::= {er1646v2EfmOamEntry 84213760}

er1646v2EfmOamEventsCriticalEvent OBJECT-TYPE
   SYNTAX      INTEGER
               {
               disabled (0),
               enabled (1)
               }
   MAX-ACCESS  read-write
   STATUS      current
   DESCRIPTION
      "Path: efm.editConf.oam.events.criticalEvent

       Possibilities:
               disabled   (0)
               enabled   (1)"
   ::= {er1646v2EfmOamEntry 84279296}


er1646v2EfmIp OBJECT IDENTIFIER ::= {er1646v2Efm 1}

er1646v2EfmIpSSC OBJECT IDENTIFIER ::= {er1646v2EfmIp 1}

er1646v2EfmIpEntry OBJECT IDENTIFIER ::= {er1646v2EfmIpSSC 1}

er1646v2EfmIpVrfRouter OBJECT-TYPE
   SYNTAX      DisplayString
   MAX-ACCESS  read-write
   STATUS      current
   DESCRIPTION
      "Path: efm.editConf.ip.vrfRouter"
   ::= {er1646v2EfmIpEntry 738197504}

er1646v2EfmIpAdr OBJECT-TYPE
   SYNTAX      IpAddress
   MAX-ACCESS  read-write
   STATUS      current
   DESCRIPTION
      "Path: efm.editConf.ip.address"
   ::= {er1646v2EfmIpEntry 2030043136}

er1646v2EfmIpNetm OBJECT-TYPE
   SYNTAX      IpAddress
   MAX-ACCESS  read-write
   STATUS      current
   DESCRIPTION
      "Path: efm.editConf.ip.netMask"
   ::= {er1646v2EfmIpEntry 2063597568}

er1646v2EfmIpSNetName OBJECT-TYPE
   SYNTAX      INTEGER
               {
               slOPTg (0),
               corp (2),
               dmz (3),
               internet (1)
               }
   MAX-ACCESS  read-write
   STATUS      current
   DESCRIPTION
      "Path: efm.editConf.ip.sNet.name

       Possibilities:
               <OPT>   (0)
               corp   (2)
               dmz   (3)
               internet   (1)"
   ::= {er1646v2EfmIpEntry 855703552}

er1646v2EfmIpSNetCust OBJECT-TYPE
   SYNTAX      DisplayString
   MAX-ACCESS  read-write
   STATUS      current
   DESCRIPTION
      "Path: efm.editConf.ip.sNet.custom"
   ::= {er1646v2EfmIpEntry 855769088}

er1646v2EfmIpDhcpC OBJECT-TYPE
   SYNTAX      INTEGER
               {
               disabled (0),
               enabled (1)
               }
   MAX-ACCESS  read-write
   STATUS      current
   DESCRIPTION
      "Path: efm.editConf.ip.dhcpClient

       Possibilities:
               disabled   (0)
               enabled   (1)"
   ::= {er1646v2EfmIpEntry 838860800}

er1646v2EfmIpDhcpGatewayPreference OBJECT-TYPE
   SYNTAX      Integer32
   MAX-ACCESS  read-write
   STATUS      current
   DESCRIPTION
      "Path: efm.editConf.ip.dhcp.gatewayPreference"
   ::= {er1646v2EfmIpEntry 872480768}

er1646v2EfmIpDhcpRoutePreference OBJECT-TYPE
   SYNTAX      Integer32
   MAX-ACCESS  read-write
   STATUS      current
   DESCRIPTION
      "Path: efm.editConf.ip.dhcp.routePreference"
   ::= {er1646v2EfmIpEntry 872546304}

er1646v2EfmIpDhcpDnsPreference OBJECT-TYPE
   SYNTAX      Integer32
   MAX-ACCESS  read-write
   STATUS      current
   DESCRIPTION
      "Path: efm.editConf.ip.dhcp.dnsPreference"
   ::= {er1646v2EfmIpEntry 872611840}

er1646v2EfmIpMtu OBJECT-TYPE
   SYNTAX      Integer32
   MAX-ACCESS  read-write
   STATUS      current
   DESCRIPTION
      "Path: efm.editConf.ip.mtu"
   ::= {er1646v2EfmIpEntry 671088640}

er1646v2EfmIpMssAdjust OBJECT-TYPE
   SYNTAX      INTEGER
               {
               disabled (0),
               auto (65536)
               }
   MAX-ACCESS  read-write
   STATUS      current
   DESCRIPTION
      "Path: efm.editConf.ip.mssAdjust

       Possibilities:
               disabled   (0)
               auto   (65536)"
   ::= {er1646v2EfmIpEntry 754974720}

er1646v2EfmIpRipMetric OBJECT-TYPE
   SYNTAX      Integer32
   MAX-ACCESS  read-write
   STATUS      current
   DESCRIPTION
      "Path: efm.editConf.ip.rip.metric"
   ::= {er1646v2EfmIpEntry 353566720}

er1646v2EfmIpRipMetricOut OBJECT-TYPE
   SYNTAX      Integer32
   MAX-ACCESS  read-write
   STATUS      current
   DESCRIPTION
      "Path: efm.editConf.ip.rip.metricOut"
   ::= {er1646v2EfmIpEntry 353632256}

er1646v2EfmIpRipMode OBJECT-TYPE
   SYNTAX      INTEGER
               {
               disabled (0),
               passive (1),
               active (2)
               }
   MAX-ACCESS  read-write
   STATUS      current
   DESCRIPTION
      "Path: efm.editConf.ip.rip.mode

       Possibilities:
               disabled   (0)
               passive   (1)
               active   (2)"
   ::= {er1646v2EfmIpEntry 353697792}

er1646v2EfmIpRipTxVer OBJECT-TYPE
   SYNTAX      INTEGER
               {
               rip1 (0),
               rip2 (1),
               rip1mcompatible (2)
               }
   MAX-ACCESS  read-write
   STATUS      current
   DESCRIPTION
      "Path: efm.editConf.ip.rip.txVersion

       Possibilities:
               rip1   (0)
               rip2   (1)
               rip1-compatible   (2)"
   ::= {er1646v2EfmIpEntry 354615296}

er1646v2EfmIpRipRxVer OBJECT-TYPE
   SYNTAX      INTEGER
               {
               rip1only (0),
               rip2only (1),
               rip12 (2)
               }
   MAX-ACCESS  read-write
   STATUS      current
   DESCRIPTION
      "Path: efm.editConf.ip.rip.rxVersion

       Possibilities:
               rip1only   (0)
               rip2only   (1)
               rip1&2   (2)"
   ::= {er1646v2EfmIpEntry 354680832}

er1646v2EfmIpRipSplitH OBJECT-TYPE
   SYNTAX      INTEGER
               {
               disabled (0),
               enabled (1),
               poisonedReverse (2)
               }
   MAX-ACCESS  read-write
   STATUS      current
   DESCRIPTION
      "Path: efm.editConf.ip.rip.splitHorizon

       Possibilities:
               disabled   (0)
               enabled   (1)
               poisonedReverse   (2)"
   ::= {er1646v2EfmIpEntry 353828864}

er1646v2EfmIpRipAuth OBJECT-TYPE
   SYNTAX      INTEGER
               {
               disabled (0),
               texts (1),
               md5 (2)
               }
   MAX-ACCESS  read-write
   STATUS      current
   DESCRIPTION
      "Path: efm.editConf.ip.rip.authentication

       Possibilities:
               disabled   (0)
               text    (1)
               md5   (2)"
   ::= {er1646v2EfmIpEntry 353501184}

er1646v2EfmIpRipFilter OBJECT-TYPE
   SYNTAX      DisplayString
   MAX-ACCESS  read-write
   STATUS      current
   DESCRIPTION
      "Path: efm.editConf.ip.rip.filter"
   ::= {er1646v2EfmIpEntry 354418688}

er1646v2EfmIpRipFilterIn OBJECT-TYPE
   SYNTAX      DisplayString
   MAX-ACCESS  read-write
   STATUS      current
   DESCRIPTION
      "Path: efm.editConf.ip.rip.filterIn"
   ::= {er1646v2EfmIpEntry 354484224}

er1646v2EfmIpRipClearNextHop OBJECT-TYPE
   SYNTAX      INTEGER
               {
               disabled (0),
               enabled (1)
               }
   MAX-ACCESS  read-write
   STATUS      current
   DESCRIPTION
      "Path: efm.editConf.ip.rip.clearNextHop

       Possibilities:
               disabled   (0)
               enabled   (1)"
   ::= {er1646v2EfmIpEntry 352452608}

er1646v2EfmIpAccPol OBJECT-TYPE
   SYNTAX      DisplayString
   MAX-ACCESS  read-write
   STATUS      current
   DESCRIPTION
      "Path: efm.editConf.ip.accessPolicy"
   ::= {er1646v2EfmIpEntry 704643072}

er1646v2EfmIpAB OBJECT-TYPE
   SYNTAX      DisplayString
   MAX-ACCESS  read-write
   STATUS      current
   DESCRIPTION
      "Path: efm.editConf.ip.trafficPolicy"
   ::= {er1646v2EfmIpEntry 234881024}

er1646v2EfmIpMA OBJECT-TYPE
   SYNTAX      INTEGER
               {
               disabled (0),
               enabled (1)
               }
   MAX-ACCESS  read-write
   STATUS      current
   DESCRIPTION
      "Path: efm.editConf.ip.mgmtAccess

       Possibilities:
               disabled   (0)
               enabled   (1)"
   ::= {er1646v2EfmIpEntry 268435456}

er1646v2EfmIpMF OBJECT-TYPE
   SYNTAX      Integer32
   MAX-ACCESS  read-write
   STATUS      current
   DESCRIPTION
      "Path: efm.editConf.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1646v2EfmIpEntry 285212672}

er1646v2EfmIpDB OBJECT-TYPE
   SYNTAX      INTEGER
               {
               disabled (0),
               enabled (1)
               }
   MAX-ACCESS  read-write
   STATUS      current
   DESCRIPTION
      "Path: efm.editConf.ip.directedBroadcasts

       Possibilities:
               disabled   (0)
               enabled   (1)"
   ::= {er1646v2EfmIpEntry 369098752}

er1646v2EfmIpIR OBJECT-TYPE
   SYNTAX      INTEGER
               {
               disabled (0),
               enabled (1)
               }
   MAX-ACCESS  read-write
   STATUS      current
   DESCRIPTION
      "Path: efm.editConf.ip.icmpRedirects

       Possibilities:
               disabled   (0)
               enabled   (1)"
   ::= {er1646v2EfmIpEntry 436207616}

er1646v2EfmIpIgmp OBJECT-TYPE
   SYNTAX      INTEGER
               {
               disabled (0),
               proxy (1),
               router (2),
               v3Router (5)
               }
   MAX-ACCESS  read-write
   STATUS      current
   DESCRIPTION
      "Path: efm.editConf.ip.igmp

       Possibilities:
               disabled   (0)
               proxy   (1)
               router   (2)
               v3Router   (5)"
   ::= {er1646v2EfmIpEntry 536870912}

er1646v2EfmIpNN OBJECT-TYPE
   SYNTAX      DisplayString
   MAX-ACCESS  read-write
   STATUS      current
   DESCRIPTION
      "Path: efm.editConf.ip.nat"
   ::= {er1646v2EfmIpEntry 452984832}

er1646v2EfmIpVrrp OBJECT-TYPE
   SYNTAX      INTEGER
               {
               disabled (0),
               enabled (1)
               }
   MAX-ACCESS  read-write
   STATUS      current
   DESCRIPTION
      "Path: efm.editConf.ip.vrrp

       Possibilities:
               disabled   (0)
               enabled   (1)"
   ::= {er1646v2EfmIpEntry 721420288}

er1646v2EfmIpPimMode OBJECT-TYPE
   SYNTAX      INTEGER
               {
               disabled (0),
               sparse (1),
               passive (2)
               }
   MAX-ACCESS  read-write
   STATUS      current
   DESCRIPTION
      "Path: efm.editConf.ip.pim.mode

       Possibilities:
               disabled   (0)
               sparse   (1)
               passive   (2)"
   ::= {er1646v2EfmIpEntry 771817472}

er1646v2EfmIpPimDrPriority OBJECT-TYPE
   SYNTAX      Counter32
   MAX-ACCESS  read-write
   STATUS      current
   DESCRIPTION
      "Path: efm.editConf.ip.pim.drPriority

       32 bit unsigned wrappable counter."
   ::= {er1646v2EfmIpEntry 771883008}

er1646v2EfmIpPimHelloTime OBJECT-TYPE
   SYNTAX      TimeTicks
   MAX-ACCESS  read-write
   STATUS      current
   DESCRIPTION
      "Path: efm.editConf.ip.pim.helloTime

       Time in centi-second."
   ::= {er1646v2EfmIpEntry 771948544}

er1646v2EfmIpPimPropagationDelay OBJECT-TYPE
   SYNTAX      TimeTicks
   MAX-ACCESS  read-write
   STATUS      current
   DESCRIPTION
      "Path: efm.editConf.ip.pim.propagationDelay

       Time in centi-second."
   ::= {er1646v2EfmIpEntry 772014080}

er1646v2EfmIpPimOverrideInterval OBJECT-TYPE
   SYNTAX      TimeTicks
   MAX-ACCESS  read-write
   STATUS      current
   DESCRIPTION
      "Path: efm.editConf.ip.pim.overrideInterval

       Time in centi-second."
   ::= {er1646v2EfmIpEntry 772079616}

er1646v2EfmIpPimBsrBorder OBJECT-TYPE
   SYNTAX      INTEGER
               {
               disabled (0),
               enabled (1)
               }
   MAX-ACCESS  read-write
   STATUS      current
   DESCRIPTION
      "Path: efm.editConf.ip.pim.bsrBorder

       Possibilities:
               disabled   (0)
               enabled   (1)"
   ::= {er1646v2EfmIpEntry 772145152}

er1646v2EfmIpPimTtlThreshold OBJECT-TYPE
   SYNTAX      Integer32
   MAX-ACCESS  read-write
   STATUS      current
   DESCRIPTION
      "Path: efm.editConf.ip.pim.ttlThreshold"
   ::= {er1646v2EfmIpEntry 772210688}

er1646v2EfmIpIMNetworkUnreachable OBJECT-TYPE
   SYNTAX      INTEGER
               {
               disabled (0),
               enabled (1)
               }
   MAX-ACCESS  read-write
   STATUS      current
   DESCRIPTION
      "Path: efm.editConf.ip.icmpMessages.networkUnreachable

       Possibilities:
               disabled   (0)
               enabled   (1)"
   ::= {er1646v2EfmIpEntry 788594688}

er1646v2EfmIpIMHostUnreachable OBJECT-TYPE
   SYNTAX      INTEGER
               {
               disabled (0),
               enabled (1)
               }
   MAX-ACCESS  read-write
   STATUS      current
   DESCRIPTION
      "Path: efm.editConf.ip.icmpMessages.hostUnreachable

       Possibilities:
               disabled   (0)
               enabled   (1)"
   ::= {er1646v2EfmIpEntry 788660224}

er1646v2EfmIpIMProtocolUnreachable OBJECT-TYPE
   SYNTAX      INTEGER
               {
               disabled (0),
               enabled (1)
               }
   MAX-ACCESS  read-write
   STATUS      current
   DESCRIPTION
      "Path: efm.editConf.ip.icmpMessages.protocolUnreachable

       Possibilities:
               disabled   (0)
               enabled   (1)"
   ::= {er1646v2EfmIpEntry 788725760}

er1646v2EfmIpIMPortUnreachable OBJECT-TYPE
   SYNTAX      INTEGER
               {
               disabled (0),
               enabled (1)
               }
   MAX-ACCESS  read-write
   STATUS      current
   DESCRIPTION
      "Path: efm.editConf.ip.icmpMessages.portUnreachable

       Possibilities:
               disabled   (0)
               enabled   (1)"
   ::= {er1646v2EfmIpEntry 788791296}

er1646v2EfmIpIMMtuExceeded OBJECT-TYPE
   SYNTAX      INTEGER
               {
               disabled (0),
               enabled (1)
               }
   MAX-ACCESS  read-write
   STATUS      current
   DESCRIPTION
      "Path: efm.editConf.ip.icmpMessages.mtuExceeded

       Possibilities:
               disabled   (0)
               enabled   (1)"
   ::= {er1646v2EfmIpEntry 788856832}

er1646v2EfmIpIMAdminProhibited OBJECT-TYPE
   SYNTAX      INTEGER
               {
               disabled (0),
               enabled (1)
               }
   MAX-ACCESS  read-write
   STATUS      current
   DESCRIPTION
      "Path: efm.editConf.ip.icmpMessages.adminProhibited

       Possibilities:
               disabled   (0)
               enabled   (1)"
   ::= {er1646v2EfmIpEntry 788922368}

er1646v2EfmIpIMTtlExceeded OBJECT-TYPE
   SYNTAX      INTEGER
               {
               disabled (0),
               enabled (1)
               }
   MAX-ACCESS  read-write
   STATUS      current
   DESCRIPTION
      "Path: efm.editConf.ip.icmpMessages.ttlExceeded

       Possibilities:
               disabled   (0)
               enabled   (1)"
   ::= {er1646v2EfmIpEntry 788987904}

er1646v2EfmIpIMRedirect OBJECT-TYPE
   SYNTAX      INTEGER
               {
               disabled (0),
               enabled (1)
               }
   MAX-ACCESS  read-write
   STATUS      current
   DESCRIPTION
      "Path: efm.editConf.ip.icmpMessages.redirect

       Possibilities:
               disabled   (0)
               enabled   (1)"
   ::= {er1646v2EfmIpEntry 789053440}

er1646v2EfmIpSaddr OBJECT-TYPE
   SYNTAX      SEQUENCE OF Er1646v2EfmIpSaddrEntry
   MAX-ACCESS  not-accessible
   STATUS      current
   DESCRIPTION
      ""
   ::= {er1646v2EfmIp 385875968}

er1646v2EfmIpSaddrEntry OBJECT-TYPE
   SYNTAX      Er1646v2EfmIpSaddrEntry
   MAX-ACCESS  not-accessible
   STATUS      current
   DESCRIPTION
      ""
   INDEX      { er1646v2EfmIpSaddrTableIx }
   ::= {er1646v2EfmIpSaddr 1}

Er1646v2EfmIpSaddrEntry ::=
   SEQUENCE
      {
      er1646v2EfmIpSaddrActions
         VariableLengthTableActions,
      er1646v2EfmIpSaddrTableIx
         TableIndex,
      er1646v2EfmIpSaddrAddress
         IpAddress,
      er1646v2EfmIpSaddrNetMask
         IpAddress
      }

er1646v2EfmIpSaddrActions OBJECT-TYPE
   SYNTAX      VariableLengthTableActions
   MAX-ACCESS  read-write
   STATUS      current
   DESCRIPTION
      "By way of this field, some manipulations
       on this table may be performed."
   ::= {er1646v2EfmIpSaddrEntry 2}

er1646v2EfmIpSaddrTableIx OBJECT-TYPE
   SYNTAX      TableIndex
   MAX-ACCESS  not-accessible
   STATUS      current
   DESCRIPTION
      ""
   ::= {er1646v2EfmIpSaddrEntry 11}

er1646v2EfmIpSaddrAddress OBJECT-TYPE
   SYNTAX      IpAddress
   MAX-ACCESS  read-write
   STATUS      current
   DESCRIPTION
      "Path: efm.editConf.ip.secondaryIp.address"
   ::= {er1646v2EfmIpSaddrEntry 2030043136}

er1646v2EfmIpSaddrNetMask OBJECT-TYPE
   SYNTAX      IpAddress
   MAX-ACCESS  read-write
   STATUS      current
   DESCRIPTION
      "Path: efm.editConf.ip.secondaryIp.netMask"
   ::= {er1646v2EfmIpSaddrEntry 2063597568}

er1646v2EfmIpH OBJECT-TYPE
   SYNTAX      SEQUENCE OF Er1646v2EfmIpHEntry
   MAX-ACCESS  not-accessible
   STATUS      current
   DESCRIPTION
      ""
   ::= {er1646v2EfmIp 251658240}

er1646v2EfmIpHEntry OBJECT-TYPE
   SYNTAX      Er1646v2EfmIpHEntry
   MAX-ACCESS  not-accessible
   STATUS      current
   DESCRIPTION
      ""
   INDEX      { er1646v2EfmIpHTableIx }
   ::= {er1646v2EfmIpH 1}

Er1646v2EfmIpHEntry ::=
   SEQUENCE
      {
      er1646v2EfmIpHActions
         VariableLengthTableActions,
      er1646v2EfmIpHTableIx
         TableIndex,
      er1646v2EfmIpHAddress
         IpAddress,
      er1646v2EfmIpHDhcpRelayOptionSubscriberId
         DisplayString
      }

er1646v2EfmIpHActions OBJECT-TYPE
   SYNTAX      VariableLengthTableActions
   MAX-ACCESS  read-write
   STATUS      current
   DESCRIPTION
      "By way of this field, some manipulations
       on this table may be performed."
   ::= {er1646v2EfmIpHEntry 2}

er1646v2EfmIpHTableIx OBJECT-TYPE
   SYNTAX      TableIndex
   MAX-ACCESS  not-accessible
   STATUS      current
   DESCRIPTION
      ""
   ::= {er1646v2EfmIpHEntry 11}

er1646v2EfmIpHAddress OBJECT-TYPE
   SYNTAX      IpAddress
   MAX-ACCESS  read-write
   STATUS      current
   DESCRIPTION
      "Path: efm.editConf.ip.helpers.address"
   ::= {er1646v2EfmIpHEntry 16777216}

er1646v2EfmIpHDhcpRelayOptionSubscriberId OBJECT-TYPE
   SYNTAX      DisplayString
   MAX-ACCESS  read-write
   STATUS      current
   DESCRIPTION
      "Path: efm.editConf.ip.helpers.dhcpRelayOption.subscriberId"
   ::= {er1646v2EfmIpHEntry 33947648}


er1646v2EfmVlan OBJECT IDENTIFIER ::= {er1646v2Efm 33}

er1646v2EfmVlanSSCTable OBJECT-TYPE
   SYNTAX      SEQUENCE OF Er1646v2EfmVlanEntry
   MAX-ACCESS  not-accessible
   STATUS      current
   DESCRIPTION
      ""
   ::= {er1646v2EfmVlan 1}

er1646v2EfmVlanEntry OBJECT-TYPE
   SYNTAX      Er1646v2EfmVlanEntry
   MAX-ACCESS  not-accessible
   STATUS      current
   DESCRIPTION
      ""
   INDEX      { er1646v2EfmVlanTableIx }
   ::= {er1646v2EfmVlanSSCTable 1}

Er1646v2EfmVlanEntry ::=
   SEQUENCE
      {
      er1646v2EfmVlanActions
         VariableLengthTableActions,
      er1646v2EfmVlanTableIx
         TableIndex,
      er1646v2EfmVlanName
         DisplayString,
      er1646v2EfmVlanRemark
         DisplayString,
      er1646v2EfmVlanAdminStatus
         INTEGER,
      er1646v2EfmVlanMode
         INTEGER,
      er1646v2EfmVlanPriorityPolicy
         DisplayString,
      er1646v2EfmVlanIpVrfRouter
         DisplayString,
      er1646v2EfmVlanIpAdr
         IpAddress,
      er1646v2EfmVlanIpNetm
         IpAddress,
      er1646v2EfmVlanIpSNetName
         INTEGER,
      er1646v2EfmVlanIpSNetCust
         DisplayString,
      er1646v2EfmVlanIpDhcpC
         INTEGER,
      er1646v2EfmVlanIpDhcpGatewayPreference
         Integer32,
      er1646v2EfmVlanIpDhcpRoutePreference
         Integer32,
      er1646v2EfmVlanIpDhcpDnsPreference
         Integer32,
      er1646v2EfmVlanIpMtu
         Integer32,
      er1646v2EfmVlanIpMssAdjust
         INTEGER,
      er1646v2EfmVlanIpRipMetric
         Integer32,
      er1646v2EfmVlanIpRipMetricOut
         Integer32,
      er1646v2EfmVlanIpRipMode
         INTEGER,
      er1646v2EfmVlanIpRipTxVer
         INTEGER,
      er1646v2EfmVlanIpRipRxVer
         INTEGER,
      er1646v2EfmVlanIpRipSplitH
         INTEGER,
      er1646v2EfmVlanIpRipAuth
         INTEGER,
      er1646v2EfmVlanIpRipFilter
         DisplayString,
      er1646v2EfmVlanIpRipFilterIn
         DisplayString,
      er1646v2EfmVlanIpRipClearNextHop
         INTEGER,
      er1646v2EfmVlanIpAccPol
         DisplayString,
      er1646v2EfmVlanIpAB
         DisplayString,
      er1646v2EfmVlanIpMA
         INTEGER,
      er1646v2EfmVlanIpMF
         Integer32,
      er1646v2EfmVlanIpDB
         INTEGER,
      er1646v2EfmVlanIpIR
         INTEGER,
      er1646v2EfmVlanIpIgmp
         INTEGER,
      er1646v2EfmVlanIpNN
         DisplayString,
      er1646v2EfmVlanIpVrrp
         INTEGER,
      er1646v2EfmVlanIpPimMode
         INTEGER,
      er1646v2EfmVlanIpPimDrPriority
         Counter32,
      er1646v2EfmVlanIpPimHelloTime
         TimeTicks,
      er1646v2EfmVlanIpPimPropagationDelay
         TimeTicks,
      er1646v2EfmVlanIpPimOverrideInterval
         TimeTicks,
      er1646v2EfmVlanIpPimBsrBorder
         INTEGER,
      er1646v2EfmVlanIpPimTtlThreshold
         Integer32,
      er1646v2EfmVlanIpIMNetworkUnreachable
         INTEGER,
      er1646v2EfmVlanIpIMHostUnreachable
         INTEGER,
      er1646v2EfmVlanIpIMProtocolUnreachable
         INTEGER,
      er1646v2EfmVlanIpIMPortUnreachable
         INTEGER,
      er1646v2EfmVlanIpIMMtuExceeded
         INTEGER,
      er1646v2EfmVlanIpIMAdminProhibited
         INTEGER,
      er1646v2EfmVlanIpIMTtlExceeded
         INTEGER,
      er1646v2EfmVlanIpIMRedirect
         INTEGER,
      er1646v2EfmVlanIpV6VrfRouter
         DisplayString,
      er1646v2EfmVlanIpV6AddrAutoConfigNrDupAddrDetects
         Integer32,
      er1646v2EfmVlanIpV6AddrAutoConfigAcceptRa
         INTEGER,
      er1646v2EfmVlanIpV6AddrAutoConfigAcceptRaRdnss
         INTEGER,
      er1646v2EfmVlanIpV6AddrAutoConfigAcceptRaDnssl
         INTEGER,
      er1646v2EfmVlanIpV6DefaultRoute
         INTEGER,
      er1646v2EfmVlanIpV6RaSend
         INTEGER,
      er1646v2EfmVlanIpV6RaMinInterval
         TimeTicks,
      er1646v2EfmVlanIpV6RaMaxInterval
         TimeTicks,
      er1646v2EfmVlanIpV6RaManagedFlag
         INTEGER,
      er1646v2EfmVlanIpV6RaOtherConfFlag
         INTEGER,
      er1646v2EfmVlanIpV6RaLinkMtu
         Integer32,
      er1646v2EfmVlanIpV6RaReachableTime
         TimeTicks,
      er1646v2EfmVlanIpV6RaRetransmitTime
         TimeTicks,
      er1646v2EfmVlanIpV6RaHopLimit
         Integer32,
      er1646v2EfmVlanIpV6RaDefaultLifeTime
         TimeTicks,
      er1646v2EfmVlanIpV6RaDnsOptionsRdnssLifeTime
         TimeTicks,
      er1646v2EfmVlanIpV6RaDnsOptionsRdnssImportServers
         INTEGER,
      er1646v2EfmVlanIpV6RaDnsOptionsDnsslLifeTime
         TimeTicks,
      er1646v2EfmVlanIpV6RaDnsOptionsDnsslImportDomains
         INTEGER,
      er1646v2EfmVlanIpV6RsSend
         INTEGER,
      er1646v2EfmVlanIpV6RsMaxRandomDelay
         TimeTicks,
      er1646v2EfmVlanIpV6RsInterval
         TimeTicks,
      er1646v2EfmVlanIpV6RsMaxSolicitations
         Integer32,
      er1646v2EfmVlanIpV6TrafficPolicyInbound
         DisplayString,
      er1646v2EfmVlanIpV6TrafficPolicyOutbound
         DisplayString,
      er1646v2EfmVlanIpV6FirewallZone
         DisplayString,
      er1646v2EfmVlanIpV6DhcpClientAddrAC
         INTEGER,
      er1646v2EfmVlanIpV6DhcpClientPrDelMode
         INTEGER,
      er1646v2EfmVlanIpV6DhcpClientPrDelPool
         DisplayString,
      er1646v2EfmVlanIpV6DhcpClientPrDelPdExclOpt
         INTEGER,
      er1646v2EfmVlanIpV6DhcpClientDnsServerPref
         Integer32,
      er1646v2EfmVlanIpV6DhcpClientRapidCommit
         INTEGER,
      er1646v2EfmVlanIpV6DhcpClientTimersSolTimeOut
         TimeTicks,
      er1646v2EfmVlanIpV6DhcpClientTimersSolMaxRt
         TimeTicks,
      er1646v2EfmVlanIpV6DhcpClientTimersInfoRefresh
         TimeTicks,
      er1646v2EfmVlanIpV6DhcpServerMode
         INTEGER,
      er1646v2EfmVlanIpV6DhcpServerPreference
         Integer32,
      er1646v2EfmVlanIpV6DhcpServerPool
         DisplayString,
      er1646v2EfmVlanIpV6DhcpServerRapidCommit
         INTEGER,
      er1646v2EfmVlanIpV6DhcpServerTimersInfoRefresh
         TimeTicks,
      er1646v2EfmVlanIpV6DhcpRelayMode
         INTEGER,
      er1646v2EfmVlanIpV6SendRedirect
         INTEGER,
      er1646v2EfmVlanIpV6LinkMtu
         Integer32,
      er1646v2EfmVlanIpV6InterfaceId
         OCTET STRING,
      er1646v2EfmVlanIpV6MF
         Integer32,
      er1646v2EfmVlanIpV6IcmpMessagesNoRoute
         INTEGER,
      er1646v2EfmVlanIpV6IcmpMessagesBeyondScope
         INTEGER,
      er1646v2EfmVlanIpV6IcmpMessagesAddressUnreachable
         INTEGER,
      er1646v2EfmVlanIpV6IcmpMessagesPortUnreachable
         INTEGER,
      er1646v2EfmVlanIpV6IcmpMessagesPacketTooBig
         INTEGER,
      er1646v2EfmVlanIpV6IcmpMessagesHopLimitExceeded
         INTEGER,
      er1646v2EfmVlanIpV6IcmpMessagesFragTimeExceeded
         INTEGER,
      er1646v2EfmVlanIpV6IcmpMessagesHeaderFieldErr
         INTEGER,
      er1646v2EfmVlanIpV6IcmpMessagesOptionUnrecognized
         INTEGER,
      er1646v2EfmVlanIpV6IcmpMessagesRedirect
         INTEGER,
      er1646v2EfmVlanBridgingAccList
         DisplayString,
      er1646v2EfmVlanBridgingInACL
         DisplayString,
      er1646v2EfmVlanBridgingTp
         DisplayString,
      er1646v2EfmVlanBridgingBrGrp
         DisplayString,
      er1646v2EfmVlanBridgingLimBC
         INTEGER,
      er1646v2EfmVlanBridgingPrivateMode
         INTEGER,
      er1646v2EfmVlanBridgingLearning
         INTEGER,
      er1646v2EfmVlanBridgingMaxCacheSize
         INTEGER,
      er1646v2EfmVlanBridgingRelearnDropOnRelearn
         INTEGER,
      er1646v2EfmVlanBridgingRelearnShutdownThreshold
         Integer32,
      er1646v2EfmVlanBridgingRelearnShutdownTime
         TimeTicks,
      er1646v2EfmVlanBridgingRelearnLoopDetection
         INTEGER,
      er1646v2EfmVlanBridgingRelearnLoopDetectionInterval
         TimeTicks,
      er1646v2EfmVlanBridgingVlanMemberShip
         INTEGER,
      er1646v2EfmVlanBridgingVlTUntaggedAction
         INTEGER,
      er1646v2EfmVlanBridgingVlTUntaggedTagInfoTpid
         INTEGER,
      er1646v2EfmVlanBridgingVlTUntaggedTagInfoVid
         Integer32,
      er1646v2EfmVlanBridgingVlTUnknownVlansAction
         INTEGER,
      er1646v2EfmVlanBridgingVlTUnknownVlansTagInfoTpid
         INTEGER,
      er1646v2EfmVlanBridgingVlTUnknownVlansTagInfoVid
         Integer32,
      er1646v2EfmVlanBridgingDot1adType
         INTEGER,
      er1646v2EfmVlanBridgingPriority
         Integer32,
      er1646v2EfmVlanBridgingPathCost
         Integer32,
      er1646v2EfmVlanBridgingInternalPathCost
         Integer32,
      er1646v2EfmVlanBridgingTCD
         INTEGER,
      er1646v2EfmVlanBridgingRestrictedRole
         INTEGER,
      er1646v2EfmVlanBridgingAdminEdge
         INTEGER,
      er1646v2EfmVlanBridgingOamMacDeviceMac
         DisplayString,
      er1646v2EfmVlanBridgingOamMacUserMac
         OCTET STRING,
      er1646v2EfmVlanBridgingOamMacBridgeMac
         DisplayString,
      er1646v2EfmVlanBridgingMgmtInline
         INTEGER,
      er1646v2EfmVlanBridgingL2ptMode
         INTEGER,
      er1646v2EfmVlanBridgingL2ptProtocols
         Integer32,
      er1646v2EfmVlanBridgingL2ptDestMac
         OCTET STRING,
      er1646v2EfmVlanBridgingL2ptCos
         INTEGER,
      er1646v2EfmVlanBridgingL2ptDropThrStp
         INTEGER,
      er1646v2EfmVlanBridgingL2ptDropThrLldp
         INTEGER,
      er1646v2EfmVlanBridgingL2ptDropThrOam
         INTEGER,
      er1646v2EfmVlanBridgingL2ptDropThrCdp
         INTEGER,
      er1646v2EfmVlanBridgingL2ptDropThrVtp
         INTEGER,
      er1646v2EfmVlanBridgingL2ptDropThrLacp
         INTEGER,
      er1646v2EfmVlanBridgingL2ptDropThrEfmOam
         INTEGER,
      er1646v2EfmVlanBridgingL2ptDropThrPvst
         INTEGER,
      er1646v2EfmVlanBridgingL2ptDropThrMmrp
         INTEGER,
      er1646v2EfmVlanBridgingL2ptDropThrMvrp
         INTEGER,
      er1646v2EfmVlanBridgingL2ptDropThrGvrp
         INTEGER,
      er1646v2EfmVlanBridgingL2ptDropThrGmrp
         INTEGER,
      er1646v2EfmVlanBridgingL2ptDropThrDtp
         INTEGER,
      er1646v2EfmVlanBridgingL2ptDropThrPagp
         INTEGER,
      er1646v2EfmVlanBridgingL2ptDropThrUdld
         INTEGER,
      er1646v2EfmVlanVlanVid
         INTEGER,
      er1646v2EfmVlanVlanVidExtensionSingle
         OCTET STRING,
      er1646v2EfmVlanVlanVidExtensionEndVid
         Integer32,
      er1646v2EfmVlanVlanTpid
         INTEGER,
      er1646v2EfmVlanVlanTagSign
         INTEGER,
      er1646v2EfmVlanVlanChTos
         INTEGER,
      er1646v2EfmVlanVlanCTMapP0
         INTEGER,
      er1646v2EfmVlanVlanCTMapP1
         INTEGER,
      er1646v2EfmVlanVlanCTMapP2
         INTEGER,
      er1646v2EfmVlanVlanCTMapP3
         INTEGER,
      er1646v2EfmVlanVlanCTMapP4
         INTEGER,
      er1646v2EfmVlanVlanCTMapP5
         INTEGER,
      er1646v2EfmVlanVlanCTMapP6
         INTEGER,
      er1646v2EfmVlanVlanCTMapP7
         INTEGER,
      er1646v2EfmVlanVlanTxCos
         INTEGER,
      er1646v2EfmVlanVlanCCMapP0
         Integer32,
      er1646v2EfmVlanVlanCCMapP1
         Integer32,
      er1646v2EfmVlanVlanCCMapP2
         Integer32,
      er1646v2EfmVlanVlanCCMapP3
         Integer32,
      er1646v2EfmVlanVlanCCMapP4
         Integer32,
      er1646v2EfmVlanVlanCCMapP5
         Integer32,
      er1646v2EfmVlanVlanCCMapP6
         Integer32,
      er1646v2EfmVlanVlanCCMapP7
         Integer32,
      er1646v2EfmVlanVlanQCMapQueue1
         Integer32,
      er1646v2EfmVlanVlanQCMapQueue2
         Integer32,
      er1646v2EfmVlanVlanQCMapQueue3
         Integer32,
      er1646v2EfmVlanVlanQCMapQueue4
         Integer32,
      er1646v2EfmVlanVlanQCMapQueue5
         Integer32,
      er1646v2EfmVlanVlanQCMapLowDelayQueue
         Integer32,
      er1646v2EfmVlanVlanQCMapLowDelay2Queue
         Integer32,
      er1646v2EfmVlanVlanQCMapSystemQueue
         Integer32,
      er1646v2EfmVlanVlanQinQSVid
         Integer32,
      er1646v2EfmVlanVlanQinQSTpid
         INTEGER,
      er1646v2EfmVlanVlanArpTimeOut
         TimeTicks,
      er1646v2EfmVlanVlanArpProxyArp
         INTEGER,
      er1646v2EfmVlanBandwidthMode
         INTEGER,
      er1646v2EfmVlanBandwidthCir
         Integer32,
      er1646v2EfmVlanBandwidthEir
         Integer32,
      er1646v2EfmVlanBandwidthUnit
         INTEGER,
      er1646v2EfmVlanBandwidthTc
         INTEGER,
      er1646v2EfmVlanBandwidthTcFactor
         INTEGER,
      er1646v2EfmVlanBandwidthCorrType
         INTEGER,
      er1646v2EfmVlanBandwidthCorrPredefEncapsFrameRelay
         DisplayString,
      er1646v2EfmVlanBandwidthCorrPredefEncapsPpp
         DisplayString,
      er1646v2EfmVlanBandwidthCorrPredefEncapsAtmHl
         INTEGER,
      er1646v2EfmVlanBandwidthCorrPredefEncapsAtmMp
         INTEGER,
      er1646v2EfmVlanBandwidthCorrPredefEncapsHdlc
         DisplayString,
      er1646v2EfmVlanBandwidthCorrPredefEncapsEfmFs
         Integer32,
      er1646v2EfmVlanBandwidthCorrPredefEncapsEfmIb
         Integer32,
      er1646v2EfmVlanBandwidthCorrPredefMode
         INTEGER,
      er1646v2EfmVlanBandwidthCorrManualOverhead
         Integer32,
      er1646v2EfmVlanBandwidthCorrManualFrameData
         Counter32,
      er1646v2EfmVlanBandwidthCorrManualFrameHeader
         Counter32,
      er1646v2EfmVlanBandwidthMaxFifoQLen
         Integer32,
      er1646v2EfmVlanBandwidthDeFlagCir
         INTEGER,
      er1646v2EfmVlanBandwidthDeFlagEir
         INTEGER,
      er1646v2EfmVlanBandwidthDeFlagViolate
         INTEGER,
      er1646v2EfmVlanBandwidthActCirActNone
         OCTET STRING,
      er1646v2EfmVlanBandwidthActCirActEthCos1
         INTEGER,
      er1646v2EfmVlanBandwidthActCirActEthDei1
         INTEGER,
      er1646v2EfmVlanBandwidthActCirActEthCos2
         INTEGER,
      er1646v2EfmVlanBandwidthActCirActEthDei2
         INTEGER,
      er1646v2EfmVlanBandwidthActCirActEthCos3
         INTEGER,
      er1646v2EfmVlanBandwidthActCirActEthDei3
         INTEGER,
      er1646v2EfmVlanBandwidthActCirActEthCos4
         INTEGER,
      er1646v2EfmVlanBandwidthActCirActEthDei4
         INTEGER,
      er1646v2EfmVlanBandwidthActCirActEthCos5
         INTEGER,
      er1646v2EfmVlanBandwidthActCirActEthDei5
         INTEGER,
      er1646v2EfmVlanBandwidthActCirActEthCos6
         INTEGER,
      er1646v2EfmVlanBandwidthActCirActEthDei6
         INTEGER,
      er1646v2EfmVlanBandwidthActCirActEthCos7
         INTEGER,
      er1646v2EfmVlanBandwidthActCirActEthDei7
         INTEGER,
      er1646v2EfmVlanBandwidthActCirActEthCos8
         INTEGER,
      er1646v2EfmVlanBandwidthActCirActEthDei8
         INTEGER,
      er1646v2EfmVlanBandwidthActCirActEthTos
         INTEGER,
      er1646v2EfmVlanBandwidthActCirActEthQueue
         INTEGER,
      er1646v2EfmVlanBandwidthActCirActEthDrpLev
         INTEGER,
      er1646v2EfmVlanBandwidthActCirActEthDeFlag
         INTEGER,
      er1646v2EfmVlanBandwidthActCirActIpTos
         INTEGER,
      er1646v2EfmVlanBandwidthActCirActIpQueue
         INTEGER,
      er1646v2EfmVlanBandwidthActCirActIpDrpLev
         INTEGER,
      er1646v2EfmVlanBandwidthActCirActIpDeFlag
         INTEGER,
      er1646v2EfmVlanBandwidthActEirActNone
         OCTET STRING,
      er1646v2EfmVlanBandwidthActEirActEthCos1
         INTEGER,
      er1646v2EfmVlanBandwidthActEirActEthDei1
         INTEGER,
      er1646v2EfmVlanBandwidthActEirActEthCos2
         INTEGER,
      er1646v2EfmVlanBandwidthActEirActEthDei2
         INTEGER,
      er1646v2EfmVlanBandwidthActEirActEthCos3
         INTEGER,
      er1646v2EfmVlanBandwidthActEirActEthDei3
         INTEGER,
      er1646v2EfmVlanBandwidthActEirActEthCos4
         INTEGER,
      er1646v2EfmVlanBandwidthActEirActEthDei4
         INTEGER,
      er1646v2EfmVlanBandwidthActEirActEthCos5
         INTEGER,
      er1646v2EfmVlanBandwidthActEirActEthDei5
         INTEGER,
      er1646v2EfmVlanBandwidthActEirActEthCos6
         INTEGER,
      er1646v2EfmVlanBandwidthActEirActEthDei6
         INTEGER,
      er1646v2EfmVlanBandwidthActEirActEthCos7
         INTEGER,
      er1646v2EfmVlanBandwidthActEirActEthDei7
         INTEGER,
      er1646v2EfmVlanBandwidthActEirActEthCos8
         INTEGER,
      er1646v2EfmVlanBandwidthActEirActEthDei8
         INTEGER,
      er1646v2EfmVlanBandwidthActEirActEthTos
         INTEGER,
      er1646v2EfmVlanBandwidthActEirActEthQueue
         INTEGER,
      er1646v2EfmVlanBandwidthActEirActEthDrpLev
         INTEGER,
      er1646v2EfmVlanBandwidthActEirActEthDeFlag
         INTEGER,
      er1646v2EfmVlanBandwidthActEirActIpTos
         INTEGER,
      er1646v2EfmVlanBandwidthActEirActIpQueue
         INTEGER,
      er1646v2EfmVlanBandwidthActEirActIpDrpLev
         INTEGER,
      er1646v2EfmVlanBandwidthActEirActIpDeFlag
         INTEGER,
      er1646v2EfmVlanBandwidthActViolActNone
         OCTET STRING,
      er1646v2EfmVlanBandwidthActViolActDrop
         OCTET STRING,
      er1646v2EfmVlanBandwidthActViolActEthCos1
         INTEGER,
      er1646v2EfmVlanBandwidthActViolActEthDei1
         INTEGER,
      er1646v2EfmVlanBandwidthActViolActEthCos2
         INTEGER,
      er1646v2EfmVlanBandwidthActViolActEthDei2
         INTEGER,
      er1646v2EfmVlanBandwidthActViolActEthCos3
         INTEGER,
      er1646v2EfmVlanBandwidthActViolActEthDei3
         INTEGER,
      er1646v2EfmVlanBandwidthActViolActEthCos4
         INTEGER,
      er1646v2EfmVlanBandwidthActViolActEthDei4
         INTEGER,
      er1646v2EfmVlanBandwidthActViolActEthCos5
         INTEGER,
      er1646v2EfmVlanBandwidthActViolActEthDei5
         INTEGER,
      er1646v2EfmVlanBandwidthActViolActEthCos6
         INTEGER,
      er1646v2EfmVlanBandwidthActViolActEthDei6
         INTEGER,
      er1646v2EfmVlanBandwidthActViolActEthCos7
         INTEGER,
      er1646v2EfmVlanBandwidthActViolActEthDei7
         INTEGER,
      er1646v2EfmVlanBandwidthActViolActEthCos8
         INTEGER,
      er1646v2EfmVlanBandwidthActViolActEthDei8
         INTEGER,
      er1646v2EfmVlanBandwidthActViolActEthTos
         INTEGER,
      er1646v2EfmVlanBandwidthActViolActEthQueue
         INTEGER,
      er1646v2EfmVlanBandwidthActViolActEthDrpLev
         INTEGER,
      er1646v2EfmVlanBandwidthActViolActEthDeFlag
         INTEGER,
      er1646v2EfmVlanBandwidthActViolActIpTos
         INTEGER,
      er1646v2EfmVlanBandwidthActViolActIpQueue
         INTEGER,
      er1646v2EfmVlanBandwidthActViolActIpDrpLev
         INTEGER,
      er1646v2EfmVlanBandwidthActViolActIpDeFlag
         INTEGER,
      er1646v2EfmVlanInbBwMode
         INTEGER,
      er1646v2EfmVlanInbBwCir
         Integer32,
      er1646v2EfmVlanInbBwEir
         Integer32,
      er1646v2EfmVlanInbBwUnit
         INTEGER,
      er1646v2EfmVlanInbBwTc
         INTEGER,
      er1646v2EfmVlanInbBwTcFactor
         INTEGER,
      er1646v2EfmVlanInbBwCorrType
         INTEGER,
      er1646v2EfmVlanInbBwCorrPredefEncapsFrameRelay
         DisplayString,
      er1646v2EfmVlanInbBwCorrPredefEncapsPpp
         DisplayString,
      er1646v2EfmVlanInbBwCorrPredefEncapsAtmHl
         INTEGER,
      er1646v2EfmVlanInbBwCorrPredefEncapsAtmMp
         INTEGER,
      er1646v2EfmVlanInbBwCorrPredefEncapsHdlc
         DisplayString,
      er1646v2EfmVlanInbBwCorrPredefEncapsEfmFs
         Integer32,
      er1646v2EfmVlanInbBwCorrPredefEncapsEfmIb
         Integer32,
      er1646v2EfmVlanInbBwCorrPredefMode
         INTEGER,
      er1646v2EfmVlanInbBwCorrManualOverhead
         Integer32,
      er1646v2EfmVlanInbBwCorrManualFrameData
         Counter32,
      er1646v2EfmVlanInbBwCorrManualFrameHeader
         Counter32,
      er1646v2EfmVlanInbBwMaxFifoQLen
         Integer32,
      er1646v2EfmVlanInbBwPriorityPolicy
         DisplayString,
      er1646v2EfmVlanInbBwDeFlagCir
         INTEGER,
      er1646v2EfmVlanInbBwDeFlagEir
         INTEGER,
      er1646v2EfmVlanInbBwDeFlagViolate
         INTEGER,
      er1646v2EfmVlanInbBwActCirActNone
         OCTET STRING,
      er1646v2EfmVlanInbBwActCirActEthCos1
         INTEGER,
      er1646v2EfmVlanInbBwActCirActEthDei1
         INTEGER,
      er1646v2EfmVlanInbBwActCirActEthCos2
         INTEGER,
      er1646v2EfmVlanInbBwActCirActEthDei2
         INTEGER,
      er1646v2EfmVlanInbBwActCirActEthCos3
         INTEGER,
      er1646v2EfmVlanInbBwActCirActEthDei3
         INTEGER,
      er1646v2EfmVlanInbBwActCirActEthCos4
         INTEGER,
      er1646v2EfmVlanInbBwActCirActEthDei4
         INTEGER,
      er1646v2EfmVlanInbBwActCirActEthCos5
         INTEGER,
      er1646v2EfmVlanInbBwActCirActEthDei5
         INTEGER,
      er1646v2EfmVlanInbBwActCirActEthCos6
         INTEGER,
      er1646v2EfmVlanInbBwActCirActEthDei6
         INTEGER,
      er1646v2EfmVlanInbBwActCirActEthCos7
         INTEGER,
      er1646v2EfmVlanInbBwActCirActEthDei7
         INTEGER,
      er1646v2EfmVlanInbBwActCirActEthCos8
         INTEGER,
      er1646v2EfmVlanInbBwActCirActEthDei8
         INTEGER,
      er1646v2EfmVlanInbBwActCirActEthTos
         INTEGER,
      er1646v2EfmVlanInbBwActCirActEthQueue
         INTEGER,
      er1646v2EfmVlanInbBwActCirActEthDrpLev
         INTEGER,
      er1646v2EfmVlanInbBwActCirActEthDeFlag
         INTEGER,
      er1646v2EfmVlanInbBwActCirActIpTos
         INTEGER,
      er1646v2EfmVlanInbBwActCirActIpQueue
         INTEGER,
      er1646v2EfmVlanInbBwActCirActIpDrpLev
         INTEGER,
      er1646v2EfmVlanInbBwActCirActIpDeFlag
         INTEGER,
      er1646v2EfmVlanInbBwActEirActNone
         OCTET STRING,
      er1646v2EfmVlanInbBwActEirActEthCos1
         INTEGER,
      er1646v2EfmVlanInbBwActEirActEthDei1
         INTEGER,
      er1646v2EfmVlanInbBwActEirActEthCos2
         INTEGER,
      er1646v2EfmVlanInbBwActEirActEthDei2
         INTEGER,
      er1646v2EfmVlanInbBwActEirActEthCos3
         INTEGER,
      er1646v2EfmVlanInbBwActEirActEthDei3
         INTEGER,
      er1646v2EfmVlanInbBwActEirActEthCos4
         INTEGER,
      er1646v2EfmVlanInbBwActEirActEthDei4
         INTEGER,
      er1646v2EfmVlanInbBwActEirActEthCos5
         INTEGER,
      er1646v2EfmVlanInbBwActEirActEthDei5
         INTEGER,
      er1646v2EfmVlanInbBwActEirActEthCos6
         INTEGER,
      er1646v2EfmVlanInbBwActEirActEthDei6
         INTEGER,
      er1646v2EfmVlanInbBwActEirActEthCos7
         INTEGER,
      er1646v2EfmVlanInbBwActEirActEthDei7
         INTEGER,
      er1646v2EfmVlanInbBwActEirActEthCos8
         INTEGER,
      er1646v2EfmVlanInbBwActEirActEthDei8
         INTEGER,
      er1646v2EfmVlanInbBwActEirActEthTos
         INTEGER,
      er1646v2EfmVlanInbBwActEirActEthQueue
         INTEGER,
      er1646v2EfmVlanInbBwActEirActEthDrpLev
         INTEGER,
      er1646v2EfmVlanInbBwActEirActEthDeFlag
         INTEGER,
      er1646v2EfmVlanInbBwActEirActIpTos
         INTEGER,
      er1646v2EfmVlanInbBwActEirActIpQueue
         INTEGER,
      er1646v2EfmVlanInbBwActEirActIpDrpLev
         INTEGER,
      er1646v2EfmVlanInbBwActEirActIpDeFlag
         INTEGER,
      er1646v2EfmVlanInbBwActViolActNone
         OCTET STRING,
      er1646v2EfmVlanInbBwActViolActDrop
         OCTET STRING,
      er1646v2EfmVlanInbBwActViolActEthCos1
         INTEGER,
      er1646v2EfmVlanInbBwActViolActEthDei1
         INTEGER,
      er1646v2EfmVlanInbBwActViolActEthCos2
         INTEGER,
      er1646v2EfmVlanInbBwActViolActEthDei2
         INTEGER,
      er1646v2EfmVlanInbBwActViolActEthCos3
         INTEGER,
      er1646v2EfmVlanInbBwActViolActEthDei3
         INTEGER,
      er1646v2EfmVlanInbBwActViolActEthCos4
         INTEGER,
      er1646v2EfmVlanInbBwActViolActEthDei4
         INTEGER,
      er1646v2EfmVlanInbBwActViolActEthCos5
         INTEGER,
      er1646v2EfmVlanInbBwActViolActEthDei5
         INTEGER,
      er1646v2EfmVlanInbBwActViolActEthCos6
         INTEGER,
      er1646v2EfmVlanInbBwActViolActEthDei6
         INTEGER,
      er1646v2EfmVlanInbBwActViolActEthCos7
         INTEGER,
      er1646v2EfmVlanInbBwActViolActEthDei7
         INTEGER,
      er1646v2EfmVlanInbBwActViolActEthCos8
         INTEGER,
      er1646v2EfmVlanInbBwActViolActEthDei8
         INTEGER,
      er1646v2EfmVlanInbBwActViolActEthTos
         INTEGER,
      er1646v2EfmVlanInbBwActViolActEthQueue
         INTEGER,
      er1646v2EfmVlanInbBwActViolActEthDrpLev
         INTEGER,
      er1646v2EfmVlanInbBwActViolActEthDeFlag
         INTEGER,
      er1646v2EfmVlanInbBwActViolActIpTos
         INTEGER,
      er1646v2EfmVlanInbBwActViolActIpQueue
         INTEGER,
      er1646v2EfmVlanInbBwActViolActIpDrpLev
         INTEGER,
      er1646v2EfmVlanInbBwActViolActIpDeFlag
         INTEGER,
      er1646v2EfmVlanPppoE
         INTEGER,
      er1646v2EfmVlanPppLnkMOperation
         INTEGER,
      er1646v2EfmVlanPppLnkMInterval
         TimeTicks,
      er1646v2EfmVlanPppLnkMRepTimeOut
         TimeTicks,
      er1646v2EfmVlanPppLnkMFailsPrmt
         Integer32,
      er1646v2EfmVlanPppAuthentication
         INTEGER,
      er1646v2EfmVlanPppAuthenPeriod
         TimeTicks,
      er1646v2EfmVlanPppSessionName
         DisplayString,
      er1646v2EfmVlanPppSessionSecret
         DisplayString,
      er1646v2EfmVlanPppEncModeSessionSecret
         INTEGER,
      er1646v2EfmVlanPppEncSessionSecret
         DisplayString,
      er1646v2EfmVlanPppServiceName
         DisplayString,
      er1646v2EfmVlanPbbMode
         INTEGER,
      er1646v2EfmVlanPbbTxCos
         Integer32,
      er1646v2EfmVlanPbbIsid
         Integer32,
      er1646v2EfmVlanPbbDestMac
         OCTET STRING,
      er1646v2EfmVlanPbbCustomGroupMac
         OCTET STRING
      }

er1646v2EfmVlanActions OBJECT-TYPE
   SYNTAX      VariableLengthTableActions
   MAX-ACCESS  read-write
   STATUS      current
   DESCRIPTION
      "By way of this field, some manipulations
       on this table may be performed."
   ::= {er1646v2EfmVlanEntry 2}

er1646v2EfmVlanTableIx OBJECT-TYPE
   SYNTAX      TableIndex
   MAX-ACCESS  not-accessible
   STATUS      current
   DESCRIPTION
      ""
   ::= {er1646v2EfmVlanEntry 11}

er1646v2EfmVlanName OBJECT-TYPE
   SYNTAX      DisplayString
   MAX-ACCESS  read-write
   STATUS      current
   DESCRIPTION
      "Path: efm.editConf.vlan.name"
   ::= {er1646v2EfmVlanEntry 16777216}

er1646v2EfmVlanRemark OBJECT-TYPE
   SYNTAX      DisplayString
   MAX-ACCESS  read-write
   STATUS      current
   DESCRIPTION
      "Path: efm.editConf.vlan.remark"
   ::= {er1646v2EfmVlanEntry 1157627904}

er1646v2EfmVlanAdminStatus OBJECT-TYPE
   SYNTAX      INTEGER
               {
               up (1),
               down (2)
               }
   MAX-ACCESS  read-write
   STATUS      current
   DESCRIPTION
      "Path: efm.editConf.vlan.adminStatus

       Possibilities:
               up   (1)
               down   (2)"
   ::= {er1646v2EfmVlanEntry 33554432}

er1646v2EfmVlanMode OBJECT-TYPE
   SYNTAX      INTEGER
               {
               routing (1),
               bridging (2),
               ipV6 (16),
               ipV6ipV4 (17),
               multilink (8)
               }
   MAX-ACCESS  read-write
   STATUS      current
   DESCRIPTION
      "Path: efm.editConf.vlan.mode

       Possibilities:
               routing   (1)
               bridging   (2)
               ipV6   (16)
               ipV6/ipV4   (17)
               multilink   (8)"
   ::= {er1646v2EfmVlanEntry 67108864}

er1646v2EfmVlanPriorityPolicy OBJECT-TYPE
   SYNTAX      DisplayString
   MAX-ACCESS  read-write
   STATUS      current
   DESCRIPTION
      "Path: efm.editConf.vlan.priorityPolicy"
   ::= {er1646v2EfmVlanEntry 83886080}

er1646v2EfmVlanIpVrfRouter OBJECT-TYPE
   SYNTAX      DisplayString
   MAX-ACCESS  read-write
   STATUS      current
   DESCRIPTION
      "Path: efm.editConf.vlan.ip.vrfRouter"
   ::= {er1646v2EfmVlanEntry 53215232}

er1646v2EfmVlanIpAdr OBJECT-TYPE
   SYNTAX      IpAddress
   MAX-ACCESS  read-write
   STATUS      current
   DESCRIPTION
      "Path: efm.editConf.vlan.ip.address"
   ::= {er1646v2EfmVlanEntry 58261504}

er1646v2EfmVlanIpNetm OBJECT-TYPE
   SYNTAX      IpAddress
   MAX-ACCESS  read-write
   STATUS      current
   DESCRIPTION
      "Path: efm.editConf.vlan.ip.netMask"
   ::= {er1646v2EfmVlanEntry 58392576}

er1646v2EfmVlanIpSNetName OBJECT-TYPE
   SYNTAX      INTEGER
               {
               slOPTg (0),
               corp (2),
               dmz (3),
               internet (1)
               }
   MAX-ACCESS  read-write
   STATUS      current
   DESCRIPTION
      "Path: efm.editConf.vlan.ip.sNet.name

       Possibilities:
               <OPT>   (0)
               corp   (2)
               dmz   (3)
               internet   (1)"
   ::= {er1646v2EfmVlanEntry 53674240}

er1646v2EfmVlanIpSNetCust OBJECT-TYPE
   SYNTAX      DisplayString
   MAX-ACCESS  read-write
   STATUS      current
   DESCRIPTION
      "Path: efm.editConf.vlan.ip.sNet.custom"
   ::= {er1646v2EfmVlanEntry 53674496}

er1646v2EfmVlanIpDhcpC OBJECT-TYPE
   SYNTAX      INTEGER
               {
               disabled (0),
               enabled (1)
               }
   MAX-ACCESS  read-write
   STATUS      current
   DESCRIPTION
      "Path: efm.editConf.vlan.ip.dhcpClient

       Possibilities:
               disabled   (0)
               enabled   (1)"
   ::= {er1646v2EfmVlanEntry 53608448}

er1646v2EfmVlanIpDhcpGatewayPreference OBJECT-TYPE
   SYNTAX      Integer32
   MAX-ACCESS  read-write
   STATUS      current
   DESCRIPTION
      "Path: efm.editConf.vlan.ip.dhcp.gatewayPreference"
   ::= {er1646v2EfmVlanEntry 53739776}

er1646v2EfmVlanIpDhcpRoutePreference OBJECT-TYPE
   SYNTAX      Integer32
   MAX-ACCESS  read-write
   STATUS      current
   DESCRIPTION
      "Path: efm.editConf.vlan.ip.dhcp.routePreference"
   ::= {er1646v2EfmVlanEntry 53740032}

er1646v2EfmVlanIpDhcpDnsPreference OBJECT-TYPE
   SYNTAX      Integer32
   MAX-ACCESS  read-write
   STATUS      current
   DESCRIPTION
      "Path: efm.editConf.vlan.ip.dhcp.dnsPreference"
   ::= {er1646v2EfmVlanEntry 53740288}

er1646v2EfmVlanIpMtu OBJECT-TYPE
   SYNTAX      Integer32
   MAX-ACCESS  read-write
   STATUS      current
   DESCRIPTION
      "Path: efm.editConf.vlan.ip.mtu"
   ::= {er1646v2EfmVlanEntry 52953088}

er1646v2EfmVlanIpMssAdjust OBJECT-TYPE
   SYNTAX      INTEGER
               {
               disabled (0),
               auto (65536)
               }
   MAX-ACCESS  read-write
   STATUS      current
   DESCRIPTION
      "Path: efm.editConf.vlan.ip.mssAdjust

       Possibilities:
               disabled   (0)
               auto   (65536)"
   ::= {er1646v2EfmVlanEntry 53280768}

er1646v2EfmVlanIpRipMetric OBJECT-TYPE
   SYNTAX      Integer32
   MAX-ACCESS  read-write
   STATUS      current
   DESCRIPTION
      "Path: efm.editConf.vlan.ip.rip.metric"
   ::= {er1646v2EfmVlanEntry 51712768}

er1646v2EfmVlanIpRipMetricOut OBJECT-TYPE
   SYNTAX      Integer32
   MAX-ACCESS  read-write
   STATUS      current
   DESCRIPTION
      "Path: efm.editConf.vlan.ip.rip.metricOut"
   ::= {er1646v2EfmVlanEntry 51713024}

er1646v2EfmVlanIpRipMode OBJECT-TYPE
   SYNTAX      INTEGER
               {
               disabled (0),
               passive (1),
               active (2)
               }
   MAX-ACCESS  read-write
   STATUS      current
   DESCRIPTION
      "Path: efm.editConf.vlan.ip.rip.mode

       Possibilities:
               disabled   (0)
               passive   (1)
               active   (2)"
   ::= {er1646v2EfmVlanEntry 51713280}

er1646v2EfmVlanIpRipTxVer OBJECT-TYPE
   SYNTAX      INTEGER
               {
               rip1 (0),
               rip2 (1),
               rip1mcompatible (2)
               }
   MAX-ACCESS  read-write
   STATUS      current
   DESCRIPTION
      "Path: efm.editConf.vlan.ip.rip.txVersion

       Possibilities:
               rip1   (0)
               rip2   (1)
               rip1-compatible   (2)"
   ::= {er1646v2EfmVlanEntry 51716864}

er1646v2EfmVlanIpRipRxVer OBJECT-TYPE
   SYNTAX      INTEGER
               {
               rip1only (0),
               rip2only (1),
               rip12 (2)
               }
   MAX-ACCESS  read-write
   STATUS      current
   DESCRIPTION
      "Path: efm.editConf.vlan.ip.rip.rxVersion

       Possibilities:
               rip1only   (0)
               rip2only   (1)
               rip1&2   (2)"
   ::= {er1646v2EfmVlanEntry 51717120}

er1646v2EfmVlanIpRipSplitH OBJECT-TYPE
   SYNTAX      INTEGER
               {
               disabled (0),
               enabled (1),
               poisonedReverse (2)
               }
   MAX-ACCESS  read-write
   STATUS      current
   DESCRIPTION
      "Path: efm.editConf.vlan.ip.rip.splitHorizon

       Possibilities:
               disabled   (0)
               enabled   (1)
               poisonedReverse   (2)"
   ::= {er1646v2EfmVlanEntry 51713792}

er1646v2EfmVlanIpRipAuth OBJECT-TYPE
   SYNTAX      INTEGER
               {
               disabled (0),
               texts (1),
               md5 (2)
               }
   MAX-ACCESS  read-write
   STATUS      current
   DESCRIPTION
      "Path: efm.editConf.vlan.ip.rip.authentication

       Possibilities:
               disabled   (0)
               text    (1)
               md5   (2)"
   ::= {er1646v2EfmVlanEntry 51712512}

er1646v2EfmVlanIpRipFilter OBJECT-TYPE
   SYNTAX      DisplayString
   MAX-ACCESS  read-write
   STATUS      current
   DESCRIPTION
      "Path: efm.editConf.vlan.ip.rip.filter"
   ::= {er1646v2EfmVlanEntry 51716096}

er1646v2EfmVlanIpRipFilterIn OBJECT-TYPE
   SYNTAX      DisplayString
   MAX-ACCESS  read-write
   STATUS      current
   DESCRIPTION
      "Path: efm.editConf.vlan.ip.rip.filterIn"
   ::= {er1646v2EfmVlanEntry 51716352}

er1646v2EfmVlanIpRipClearNextHop OBJECT-TYPE
   SYNTAX      INTEGER
               {
               disabled (0),
               enabled (1)
               }
   MAX-ACCESS  read-write
   STATUS      current
   DESCRIPTION
      "Path: efm.editConf.vlan.ip.rip.clearNextHop

       Possibilities:
               disabled   (0)
               enabled   (1)"
   ::= {er1646v2EfmVlanEntry 51708416}

er1646v2EfmVlanIpAccPol OBJECT-TYPE
   SYNTAX      DisplayString
   MAX-ACCESS  read-write
   STATUS      current
   DESCRIPTION
      "Path: efm.editConf.vlan.ip.accessPolicy"
   ::= {er1646v2EfmVlanEntry 53084160}

er1646v2EfmVlanIpAB OBJECT-TYPE
   SYNTAX      DisplayString
   MAX-ACCESS  read-write
   STATUS      current
   DESCRIPTION
      "Path: efm.editConf.vlan.ip.trafficPolicy"
   ::= {er1646v2EfmVlanEntry 51249152}

er1646v2EfmVlanIpMA OBJECT-TYPE
   SYNTAX      INTEGER
               {
               disabled (0),
               enabled (1)
               }
   MAX-ACCESS  read-write
   STATUS      current
   DESCRIPTION
      "Path: efm.editConf.vlan.ip.mgmtAccess

       Possibilities:
               disabled   (0)
               enabled   (1)"
   ::= {er1646v2EfmVlanEntry 51380224}

er1646v2EfmVlanIpMF OBJECT-TYPE
   SYNTAX      Integer32
   MAX-ACCESS  read-write
   STATUS      current
   DESCRIPTION
      "Path: efm.editConf.vlan.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1646v2EfmVlanEntry 51445760}

er1646v2EfmVlanIpDB OBJECT-TYPE
   SYNTAX      INTEGER
               {
               disabled (0),
               enabled (1)
               }
   MAX-ACCESS  read-write
   STATUS      current
   DESCRIPTION
      "Path: efm.editConf.vlan.ip.directedBroadcasts

       Possibilities:
               disabled   (0)
               enabled   (1)"
   ::= {er1646v2EfmVlanEntry 51773440}

er1646v2EfmVlanIpIR OBJECT-TYPE
   SYNTAX      INTEGER
               {
               disabled (0),
               enabled (1)
               }
   MAX-ACCESS  read-write
   STATUS      current
   DESCRIPTION
      "Path: efm.editConf.vlan.ip.icmpRedirects

       Possibilities:
               disabled   (0)
               enabled   (1)"
   ::= {er1646v2EfmVlanEntry 52035584}

er1646v2EfmVlanIpIgmp OBJECT-TYPE
   SYNTAX      INTEGER
               {
               disabled (0),
               proxy (1),
               router (2),
               v3Router (5)
               }
   MAX-ACCESS  read-write
   STATUS      current
   DESCRIPTION
      "Path: efm.editConf.vlan.ip.igmp

       Possibilities:
               disabled   (0)
               proxy   (1)
               router   (2)
               v3Router   (5)"
   ::= {er1646v2EfmVlanEntry 52428800}

er1646v2EfmVlanIpNN OBJECT-TYPE
   SYNTAX      DisplayString
   MAX-ACCESS  read-write
   STATUS      current
   DESCRIPTION
      "Path: efm.editConf.vlan.ip.nat"
   ::= {er1646v2EfmVlanEntry 52101120}

er1646v2EfmVlanIpVrrp OBJECT-TYPE
   SYNTAX      INTEGER
               {
               disabled (0),
               enabled (1)
               }
   MAX-ACCESS  read-write
   STATUS      current
   DESCRIPTION
      "Path: efm.editConf.vlan.ip.vrrp

       Possibilities:
               disabled   (0)
               enabled   (1)"
   ::= {er1646v2EfmVlanEntry 53149696}

er1646v2EfmVlanIpPimMode OBJECT-TYPE
   SYNTAX      INTEGER
               {
               disabled (0),
               sparse (1),
               passive (2)
               }
   MAX-ACCESS  read-write
   STATUS      current
   DESCRIPTION
      "Path: efm.editConf.vlan.ip.pim.mode

       Possibilities:
               disabled   (0)
               sparse   (1)
               passive   (2)"
   ::= {er1646v2EfmVlanEntry 53346560}

er1646v2EfmVlanIpPimDrPriority OBJECT-TYPE
   SYNTAX      Counter32
   MAX-ACCESS  read-write
   STATUS      current
   DESCRIPTION
      "Path: efm.editConf.vlan.ip.pim.drPriority

       32 bit unsigned wrappable counter."
   ::= {er1646v2EfmVlanEntry 53346816}

er1646v2EfmVlanIpPimHelloTime OBJECT-TYPE
   SYNTAX      TimeTicks
   MAX-ACCESS  read-write
   STATUS      current
   DESCRIPTION
      "Path: efm.editConf.vlan.ip.pim.helloTime

       Time in centi-second."
   ::= {er1646v2EfmVlanEntry 53347072}

er1646v2EfmVlanIpPimPropagationDelay OBJECT-TYPE
   SYNTAX      TimeTicks
   MAX-ACCESS  read-write
   STATUS      current
   DESCRIPTION
      "Path: efm.editConf.vlan.ip.pim.propagationDelay

       Time in centi-second."
   ::= {er1646v2EfmVlanEntry 53347328}

er1646v2EfmVlanIpPimOverrideInterval OBJECT-TYPE
   SYNTAX      TimeTicks
   MAX-ACCESS  read-write
   STATUS      current
   DESCRIPTION
      "Path: efm.editConf.vlan.ip.pim.overrideInterval

       Time in centi-second."
   ::= {er1646v2EfmVlanEntry 53347584}

er1646v2EfmVlanIpPimBsrBorder OBJECT-TYPE
   SYNTAX      INTEGER
               {
               disabled (0),
               enabled (1)
               }
   MAX-ACCESS  read-write
   STATUS      current
   DESCRIPTION
      "Path: efm.editConf.vlan.ip.pim.bsrBorder

       Possibilities:
               disabled   (0)
               enabled   (1)"
   ::= {er1646v2EfmVlanEntry 53347840}

er1646v2EfmVlanIpPimTtlThreshold OBJECT-TYPE
   SYNTAX      Integer32
   MAX-ACCESS  read-write
   STATUS      current
   DESCRIPTION
      "Path: efm.editConf.vlan.ip.pim.ttlThreshold"
   ::= {er1646v2EfmVlanEntry 53348096}

er1646v2EfmVlanIpIMNetworkUnreachable OBJECT-TYPE
   SYNTAX      INTEGER
               {
               disabled (0),
               enabled (1)
               }
   MAX-ACCESS  read-write
   STATUS      current
   DESCRIPTION
      "Path: efm.editConf.vlan.ip.icmpMessages.networkUnreachable

       Possibilities:
               disabled   (0)
               enabled   (1)"
   ::= {er1646v2EfmVlanEntry 53412096}

er1646v2EfmVlanIpIMHostUnreachable OBJECT-TYPE
   SYNTAX      INTEGER
               {
               disabled (0),
               enabled (1)
               }
   MAX-ACCESS  read-write
   STATUS      current
   DESCRIPTION
      "Path: efm.editConf.vlan.ip.icmpMessages.hostUnreachable

       Possibilities:
               disabled   (0)
               enabled   (1)"
   ::= {er1646v2EfmVlanEntry 53412352}

er1646v2EfmVlanIpIMProtocolUnreachable OBJECT-TYPE
   SYNTAX      INTEGER
               {
               disabled (0),
               enabled (1)
               }
   MAX-ACCESS  read-write
   STATUS      current
   DESCRIPTION
      "Path: efm.editConf.vlan.ip.icmpMessages.protocolUnreachable

       Possibilities:
               disabled   (0)
               enabled   (1)"
   ::= {er1646v2EfmVlanEntry 53412608}

er1646v2EfmVlanIpIMPortUnreachable OBJECT-TYPE
   SYNTAX      INTEGER
               {
               disabled (0),
               enabled (1)
               }
   MAX-ACCESS  read-write
   STATUS      current
   DESCRIPTION
      "Path: efm.editConf.vlan.ip.icmpMessages.portUnreachable

       Possibilities:
               disabled   (0)
               enabled   (1)"
   ::= {er1646v2EfmVlanEntry 53412864}

er1646v2EfmVlanIpIMMtuExceeded OBJECT-TYPE
   SYNTAX      INTEGER
               {
               disabled (0),
               enabled (1)
               }
   MAX-ACCESS  read-write
   STATUS      current
   DESCRIPTION
      "Path: efm.editConf.vlan.ip.icmpMessages.mtuExceeded

       Possibilities:
               disabled   (0)
               enabled   (1)"
   ::= {er1646v2EfmVlanEntry 53413120}

er1646v2EfmVlanIpIMAdminProhibited OBJECT-TYPE
   SYNTAX      INTEGER
               {
               disabled (0),
               enabled (1)
               }
   MAX-ACCESS  read-write
   STATUS      current
   DESCRIPTION
      "Path: efm.editConf.vlan.ip.icmpMessages.adminProhibited

       Possibilities:
               disabled   (0)
               enabled   (1)"
   ::= {er1646v2EfmVlanEntry 53413376}

er1646v2EfmVlanIpIMTtlExceeded OBJECT-TYPE
   SYNTAX      INTEGER
               {
               disabled (0),
               enabled (1)
               }
   MAX-ACCESS  read-write
   STATUS      current
   DESCRIPTION
      "Path: efm.editConf.vlan.ip.icmpMessages.ttlExceeded

       Possibilities:
               disabled   (0)
               enabled   (1)"
   ::= {er1646v2EfmVlanEntry 53413632}

er1646v2EfmVlanIpIMRedirect OBJECT-TYPE
   SYNTAX      INTEGER
               {
               disabled (0),
               enabled (1)
               }
   MAX-ACCESS  read-write
   STATUS      current
   DESCRIPTION
      "Path: efm.editConf.vlan.ip.icmpMessages.redirect

       Possibilities:
               disabled   (0)
               enabled   (1)"
   ::= {er1646v2EfmVlanEntry 53413888}

er1646v2EfmVlanIpV6VrfRouter OBJECT-TYPE
   SYNTAX      DisplayString
   MAX-ACCESS  read-write
   STATUS      current
   DESCRIPTION
      "Path: efm.editConf.vlan.ipV6.vrfRouter"
   ::= {er1646v2EfmVlanEntry 704708608}

er1646v2EfmVlanIpV6AddrAutoConfigNrDupAddrDetects OBJECT-TYPE
   SYNTAX      Integer32
   MAX-ACCESS  read-write
   STATUS      current
   DESCRIPTION
      "Path: efm.editConf.vlan.ipV6.addrAutoConfig.nrDupAddrDetects"
   ::= {er1646v2EfmVlanEntry 704905472}

er1646v2EfmVlanIpV6AddrAutoConfigAcceptRa OBJECT-TYPE
   SYNTAX      INTEGER
               {
               disabled (0),
               enabled (1)
               }
   MAX-ACCESS  read-write
   STATUS      current
   DESCRIPTION
      "Path: efm.editConf.vlan.ipV6.addrAutoConfig.acceptRa

       Possibilities:
               disabled   (0)
               enabled   (1)"
   ::= {er1646v2EfmVlanEntry 704905728}

er1646v2EfmVlanIpV6AddrAutoConfigAcceptRaRdnss OBJECT-TYPE
   SYNTAX      INTEGER
               {
               disabled (0),
               enabled (1)
               }
   MAX-ACCESS  read-write
   STATUS      current
   DESCRIPTION
      "Path: efm.editConf.vlan.ipV6.addrAutoConfig.acceptRaRdnss

       Possibilities:
               disabled   (0)
               enabled   (1)"
   ::= {er1646v2EfmVlanEntry 704905984}

er1646v2EfmVlanIpV6AddrAutoConfigAcceptRaDnssl OBJECT-TYPE
   SYNTAX      INTEGER
               {
               disabled (0),
               enabled (1)
               }
   MAX-ACCESS  read-write
   STATUS      current
   DESCRIPTION
      "Path: efm.editConf.vlan.ipV6.addrAutoConfig.acceptRaDnssl

       Possibilities:
               disabled   (0)
               enabled   (1)"
   ::= {er1646v2EfmVlanEntry 704906240}

er1646v2EfmVlanIpV6DefaultRoute OBJECT-TYPE
   SYNTAX      INTEGER
               {
               disabled (0),
               enabled (1)
               }
   MAX-ACCESS  read-write
   STATUS      current
   DESCRIPTION
      "Path: efm.editConf.vlan.ipV6.defaultRoute

       Possibilities:
               disabled   (0)
               enabled   (1)"
   ::= {er1646v2EfmVlanEntry 704970752}

er1646v2EfmVlanIpV6RaSend OBJECT-TYPE
   SYNTAX      INTEGER
               {
               disabled (0),
               enabled (1)
               }
   MAX-ACCESS  read-write
   STATUS      current
   DESCRIPTION
      "Path: efm.editConf.vlan.ipV6.ra.send

       Possibilities:
               disabled   (0)
               enabled   (1)"
   ::= {er1646v2EfmVlanEntry 705036544}

er1646v2EfmVlanIpV6RaMinInterval OBJECT-TYPE
   SYNTAX      TimeTicks
   MAX-ACCESS  read-write
   STATUS      current
   DESCRIPTION
      "Path: efm.editConf.vlan.ipV6.ra.minInterval

       Time in centi-second."
   ::= {er1646v2EfmVlanEntry 705036800}

er1646v2EfmVlanIpV6RaMaxInterval OBJECT-TYPE
   SYNTAX      TimeTicks
   MAX-ACCESS  read-write
   STATUS      current
   DESCRIPTION
      "Path: efm.editConf.vlan.ipV6.ra.maxInterval

       Time in centi-second."
   ::= {er1646v2EfmVlanEntry 705037056}

er1646v2EfmVlanIpV6RaManagedFlag OBJECT-TYPE
   SYNTAX      INTEGER
               {
               disabled (0),
               enabled (1)
               }
   MAX-ACCESS  read-write
   STATUS      current
   DESCRIPTION
      "Path: efm.editConf.vlan.ipV6.ra.managedFlag

       Possibilities:
               disabled   (0)
               enabled   (1)"
   ::= {er1646v2EfmVlanEntry 705037312}

er1646v2EfmVlanIpV6RaOtherConfFlag OBJECT-TYPE
   SYNTAX      INTEGER
               {
               disabled (0),
               enabled (1)
               }
   MAX-ACCESS  read-write
   STATUS      current
   DESCRIPTION
      "Path: efm.editConf.vlan.ipV6.ra.otherConfFlag

       Possibilities:
               disabled   (0)
               enabled   (1)"
   ::= {er1646v2EfmVlanEntry 705037568}

er1646v2EfmVlanIpV6RaLinkMtu OBJECT-TYPE
   SYNTAX      Integer32
   MAX-ACCESS  read-write
   STATUS      current
   DESCRIPTION
      "Path: efm.editConf.vlan.ipV6.ra.linkMtu"
   ::= {er1646v2EfmVlanEntry 705037824}

er1646v2EfmVlanIpV6RaReachableTime OBJECT-TYPE
   SYNTAX      TimeTicks
   MAX-ACCESS  read-write
   STATUS      current
   DESCRIPTION
      "Path: efm.editConf.vlan.ipV6.ra.reachableTime

       Time in centi-second."
   ::= {er1646v2EfmVlanEntry 705038080}

er1646v2EfmVlanIpV6RaRetransmitTime OBJECT-TYPE
   SYNTAX      TimeTicks
   MAX-ACCESS  read-write
   STATUS      current
   DESCRIPTION
      "Path: efm.editConf.vlan.ipV6.ra.retransmitTime

       Time in centi-second."
   ::= {er1646v2EfmVlanEntry 705038336}

er1646v2EfmVlanIpV6RaHopLimit OBJECT-TYPE
   SYNTAX      Integer32
   MAX-ACCESS  read-write
   STATUS      current
   DESCRIPTION
      "Path: efm.editConf.vlan.ipV6.ra.hopLimit"
   ::= {er1646v2EfmVlanEntry 705038592}

er1646v2EfmVlanIpV6RaDefaultLifeTime OBJECT-TYPE
   SYNTAX      TimeTicks
   MAX-ACCESS  read-write
   STATUS      current
   DESCRIPTION
      "Path: efm.editConf.vlan.ipV6.ra.defaultLifeTime

       Time in centi-second."
   ::= {er1646v2EfmVlanEntry 705038848}

er1646v2EfmVlanIpV6RaDnsOptionsRdnssLifeTime OBJECT-TYPE
   SYNTAX      TimeTicks
   MAX-ACCESS  read-write
   STATUS      current
   DESCRIPTION
      "Path: efm.editConf.vlan.ipV6.ra.dnsOptions.rdnss.lifeTime

       Time in centi-second."
   ::= {er1646v2EfmVlanEntry 705039140}

er1646v2EfmVlanIpV6RaDnsOptionsRdnssImportServers OBJECT-TYPE
   SYNTAX      INTEGER
               {
               disabled (0),
               enabled (1)
               }
   MAX-ACCESS  read-write
   STATUS      current
   DESCRIPTION
      "Path: efm.editConf.vlan.ipV6.ra.dnsOptions.rdnss.importServers

       Possibilities:
               disabled   (0)
               enabled   (1)"
   ::= {er1646v2EfmVlanEntry 705039148}

er1646v2EfmVlanIpV6RaDnsOptionsDnsslLifeTime OBJECT-TYPE
   SYNTAX      TimeTicks
   MAX-ACCESS  read-write
   STATUS      current
   DESCRIPTION
      "Path: efm.editConf.vlan.ipV6.ra.dnsOptions.dnssl.lifeTime

       Time in centi-second."
   ::= {er1646v2EfmVlanEntry 705039172}

er1646v2EfmVlanIpV6RaDnsOptionsDnsslImportDomains OBJECT-TYPE
   SYNTAX      INTEGER
               {
               disabled (0),
               enabled (1)
               }
   MAX-ACCESS  read-write
   STATUS      current
   DESCRIPTION
      "Path: efm.editConf.vlan.ipV6.ra.dnsOptions.dnssl.importDomains

       Possibilities:
               disabled   (0)
               enabled   (1)"
   ::= {er1646v2EfmVlanEntry 705039180}

er1646v2EfmVlanIpV6RsSend OBJECT-TYPE
   SYNTAX      INTEGER
               {
               disabled (0),
               enabled (1)
               }
   MAX-ACCESS  read-write
   STATUS      current
   DESCRIPTION
      "Path: efm.editConf.vlan.ipV6.rs.send

       Possibilities:
               disabled   (0)
               enabled   (1)"
   ::= {er1646v2EfmVlanEntry 705954048}

er1646v2EfmVlanIpV6RsMaxRandomDelay OBJECT-TYPE
   SYNTAX      TimeTicks
   MAX-ACCESS  read-write
   STATUS      current
   DESCRIPTION
      "Path: efm.editConf.vlan.ipV6.rs.maxRandomDelay

       Time in centi-second."
   ::= {er1646v2EfmVlanEntry 705954304}

er1646v2EfmVlanIpV6RsInterval OBJECT-TYPE
   SYNTAX      TimeTicks
   MAX-ACCESS  read-write
   STATUS      current
   DESCRIPTION
      "Path: efm.editConf.vlan.ipV6.rs.interval

       Time in centi-second."
   ::= {er1646v2EfmVlanEntry 705954560}

er1646v2EfmVlanIpV6RsMaxSolicitations OBJECT-TYPE
   SYNTAX      Integer32
   MAX-ACCESS  read-write
   STATUS      current
   DESCRIPTION
      "Path: efm.editConf.vlan.ipV6.rs.maxSolicitations"
   ::= {er1646v2EfmVlanEntry 705954816}

er1646v2EfmVlanIpV6TrafficPolicyInbound OBJECT-TYPE
   SYNTAX      DisplayString
   MAX-ACCESS  read-write
   STATUS      current
   DESCRIPTION
      "Path: efm.editConf.vlan.ipV6.trafficPolicy.inbound"
   ::= {er1646v2EfmVlanEntry 705364224}

er1646v2EfmVlanIpV6TrafficPolicyOutbound OBJECT-TYPE
   SYNTAX      DisplayString
   MAX-ACCESS  read-write
   STATUS      current
   DESCRIPTION
      "Path: efm.editConf.vlan.ipV6.trafficPolicy.outbound"
   ::= {er1646v2EfmVlanEntry 705364480}

er1646v2EfmVlanIpV6FirewallZone OBJECT-TYPE
   SYNTAX      DisplayString
   MAX-ACCESS  read-write
   STATUS      current
   DESCRIPTION
      "Path: efm.editConf.vlan.ipV6.firewall.zone"
   ::= {er1646v2EfmVlanEntry 705429760}

er1646v2EfmVlanIpV6DhcpClientAddrAC OBJECT-TYPE
   SYNTAX      INTEGER
               {
               disabled (0),
               enabled (1)
               }
   MAX-ACCESS  read-write
   STATUS      current
   DESCRIPTION
      "Path: efm.editConf.vlan.ipV6.dhcp.client.addrAutoConfig

       Possibilities:
               disabled   (0)
               enabled   (1)"
   ::= {er1646v2EfmVlanEntry 705307648}

er1646v2EfmVlanIpV6DhcpClientPrDelMode OBJECT-TYPE
   SYNTAX      INTEGER
               {
               disabled (0),
               enabled (1)
               }
   MAX-ACCESS  read-write
   STATUS      current
   DESCRIPTION
      "Path: efm.editConf.vlan.ipV6.dhcp.client.pd.mode

       Possibilities:
               disabled   (0)
               enabled   (1)"
   ::= {er1646v2EfmVlanEntry 705308676}

er1646v2EfmVlanIpV6DhcpClientPrDelPool OBJECT-TYPE
   SYNTAX      DisplayString
   MAX-ACCESS  read-write
   STATUS      current
   DESCRIPTION
      "Path: efm.editConf.vlan.ipV6.dhcp.client.pd.pool"
   ::= {er1646v2EfmVlanEntry 705308680}

er1646v2EfmVlanIpV6DhcpClientPrDelPdExclOpt OBJECT-TYPE
   SYNTAX      INTEGER
               {
               disabled (0),
               enabled (1)
               }
   MAX-ACCESS  read-write
   STATUS      current
   DESCRIPTION
      "Path: efm.editConf.vlan.ipV6.dhcp.client.pd.pdExclOpt

       Possibilities:
               disabled   (0)
               enabled   (1)"
   ::= {er1646v2EfmVlanEntry 705308684}

er1646v2EfmVlanIpV6DhcpClientDnsServerPref OBJECT-TYPE
   SYNTAX      Integer32
   MAX-ACCESS  read-write
   STATUS      current
   DESCRIPTION
      "Path: efm.editConf.vlan.ipV6.dhcp.client.dns.serverPref"
   ::= {er1646v2EfmVlanEntry 705310724}

er1646v2EfmVlanIpV6DhcpClientRapidCommit OBJECT-TYPE
   SYNTAX      INTEGER
               {
               disabled (0),
               enabled (1)
               }
   MAX-ACCESS  read-write
   STATUS      current
   DESCRIPTION
      "Path: efm.editConf.vlan.ipV6.dhcp.client.rapidCommit

       Possibilities:
               disabled   (0)
               enabled   (1)"
   ::= {er1646v2EfmVlanEntry 705309696}

er1646v2EfmVlanIpV6DhcpClientTimersSolTimeOut OBJECT-TYPE
   SYNTAX      TimeTicks
   MAX-ACCESS  read-write
   STATUS      current
   DESCRIPTION
      "Path: efm.editConf.vlan.ipV6.dhcp.client.timers.solTimeOut

       Time in centi-second."
   ::= {er1646v2EfmVlanEntry 705311748}

er1646v2EfmVlanIpV6DhcpClientTimersSolMaxRt OBJECT-TYPE
   SYNTAX      TimeTicks
   MAX-ACCESS  read-write
   STATUS      current
   DESCRIPTION
      "Path: efm.editConf.vlan.ipV6.dhcp.client.timers.solMaxRt

       Time in centi-second."
   ::= {er1646v2EfmVlanEntry 705311752}

er1646v2EfmVlanIpV6DhcpClientTimersInfoRefresh OBJECT-TYPE
   SYNTAX      TimeTicks
   MAX-ACCESS  read-write
   STATUS      current
   DESCRIPTION
      "Path: efm.editConf.vlan.ipV6.dhcp.client.timers.infoRefresh

       Time in centi-second."
   ::= {er1646v2EfmVlanEntry 705311756}

er1646v2EfmVlanIpV6DhcpServerMode OBJECT-TYPE
   SYNTAX      INTEGER
               {
               disabled (0),
               enabled (1)
               }
   MAX-ACCESS  read-write
   STATUS      current
   DESCRIPTION
      "Path: efm.editConf.vlan.ipV6.dhcp.server.mode

       Possibilities:
               disabled   (0)
               enabled   (1)"
   ::= {er1646v2EfmVlanEntry 705315840}

er1646v2EfmVlanIpV6DhcpServerPreference OBJECT-TYPE
   SYNTAX      Integer32
   MAX-ACCESS  read-write
   STATUS      current
   DESCRIPTION
      "Path: efm.editConf.vlan.ipV6.dhcp.server.preference"
   ::= {er1646v2EfmVlanEntry 705316864}

er1646v2EfmVlanIpV6DhcpServerPool OBJECT-TYPE
   SYNTAX      DisplayString
   MAX-ACCESS  read-write
   STATUS      current
   DESCRIPTION
      "Path: efm.editConf.vlan.ipV6.dhcp.server.pool"
   ::= {er1646v2EfmVlanEntry 705317888}

er1646v2EfmVlanIpV6DhcpServerRapidCommit OBJECT-TYPE
   SYNTAX      INTEGER
               {
               disabled (0),
               enabled (1)
               }
   MAX-ACCESS  read-write
   STATUS      current
   DESCRIPTION
      "Path: efm.editConf.vlan.ipV6.dhcp.server.rapidCommit

       Possibilities:
               disabled   (0)
               enabled   (1)"
   ::= {er1646v2EfmVlanEntry 705318912}

er1646v2EfmVlanIpV6DhcpServerTimersInfoRefresh OBJECT-TYPE
   SYNTAX      TimeTicks
   MAX-ACCESS  read-write
   STATUS      current
   DESCRIPTION
      "Path: efm.editConf.vlan.ipV6.dhcp.server.timers.infoRefresh

       Time in centi-second."
   ::= {er1646v2EfmVlanEntry 705319940}

er1646v2EfmVlanIpV6DhcpRelayMode OBJECT-TYPE
   SYNTAX      INTEGER
               {
               disabled (0),
               enabled (1)
               }
   MAX-ACCESS  read-write
   STATUS      current
   DESCRIPTION
      "Path: efm.editConf.vlan.ipV6.dhcp.relay.mode

       Possibilities:
               disabled   (0)
               enabled   (1)"
   ::= {er1646v2EfmVlanEntry 705323040}

er1646v2EfmVlanIpV6SendRedirect OBJECT-TYPE
   SYNTAX      INTEGER
               {
               disabled (0),
               enabled (1)
               }
   MAX-ACCESS  read-write
   STATUS      current
   DESCRIPTION
      "Path: efm.editConf.vlan.ipV6.sendRedirect

       Possibilities:
               disabled   (0)
               enabled   (1)"
   ::= {er1646v2EfmVlanEntry 705101824}

er1646v2EfmVlanIpV6LinkMtu OBJECT-TYPE
   SYNTAX      Integer32
   MAX-ACCESS  read-write
   STATUS      current
   DESCRIPTION
      "Path: efm.editConf.vlan.ipV6.linkMtu"
   ::= {er1646v2EfmVlanEntry 705167360}

er1646v2EfmVlanIpV6InterfaceId OBJECT-TYPE
   SYNTAX      OCTET STRING
   MAX-ACCESS  read-write
   STATUS      current
   DESCRIPTION
      "Path: efm.editConf.vlan.ipV6.interfaceId"
   ::= {er1646v2EfmVlanEntry 705232896}

er1646v2EfmVlanIpV6MF OBJECT-TYPE
   SYNTAX      Integer32
   MAX-ACCESS  read-write
   STATUS      current
   DESCRIPTION
      "Path: efm.editConf.vlan.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1646v2EfmVlanEntry 705757184}

er1646v2EfmVlanIpV6IcmpMessagesNoRoute OBJECT-TYPE
   SYNTAX      INTEGER
               {
               disabled (0),
               enabled (1)
               }
   MAX-ACCESS  read-write
   STATUS      current
   DESCRIPTION
      "Path: efm.editConf.vlan.ipV6.icmpMessages.noRoute

       Possibilities:
               disabled   (0)
               enabled   (1)"
   ::= {er1646v2EfmVlanEntry 705822976}

er1646v2EfmVlanIpV6IcmpMessagesBeyondScope OBJECT-TYPE
   SYNTAX      INTEGER
               {
               disabled (0),
               enabled (1)
               }
   MAX-ACCESS  read-write
   STATUS      current
   DESCRIPTION
      "Path: efm.editConf.vlan.ipV6.icmpMessages.beyondScope

       Possibilities:
               disabled   (0)
               enabled   (1)"
   ::= {er1646v2EfmVlanEntry 705823488}

er1646v2EfmVlanIpV6IcmpMessagesAddressUnreachable OBJECT-TYPE
   SYNTAX      INTEGER
               {
               disabled (0),
               enabled (1)
               }
   MAX-ACCESS  read-write
   STATUS      current
   DESCRIPTION
      "Path: efm.editConf.vlan.ipV6.icmpMessages.addressUnreachable

       Possibilities:
               disabled   (0)
               enabled   (1)"
   ::= {er1646v2EfmVlanEntry 705823744}

er1646v2EfmVlanIpV6IcmpMessagesPortUnreachable OBJECT-TYPE
   SYNTAX      INTEGER
               {
               disabled (0),
               enabled (1)
               }
   MAX-ACCESS  read-write
   STATUS      current
   DESCRIPTION
      "Path: efm.editConf.vlan.ipV6.icmpMessages.portUnreachable

       Possibilities:
               disabled   (0)
               enabled   (1)"
   ::= {er1646v2EfmVlanEntry 705824000}

er1646v2EfmVlanIpV6IcmpMessagesPacketTooBig OBJECT-TYPE
   SYNTAX      INTEGER
               {
               disabled (0),
               enabled (1)
               }
   MAX-ACCESS  read-write
   STATUS      current
   DESCRIPTION
      "Path: efm.editConf.vlan.ipV6.icmpMessages.packetTooBig

       Possibilities:
               disabled   (0)
               enabled   (1)"
   ::= {er1646v2EfmVlanEntry 705825280}

er1646v2EfmVlanIpV6IcmpMessagesHopLimitExceeded OBJECT-TYPE
   SYNTAX      INTEGER
               {
               disabled (0),
               enabled (1)
               }
   MAX-ACCESS  read-write
   STATUS      current
   DESCRIPTION
      "Path: efm.editConf.vlan.ipV6.icmpMessages.hopLimitExceeded

       Possibilities:
               disabled   (0)
               enabled   (1)"
   ::= {er1646v2EfmVlanEntry 705827840}

er1646v2EfmVlanIpV6IcmpMessagesFragTimeExceeded OBJECT-TYPE
   SYNTAX      INTEGER
               {
               disabled (0),
               enabled (1)
               }
   MAX-ACCESS  read-write
   STATUS      current
   DESCRIPTION
      "Path: efm.editConf.vlan.ipV6.icmpMessages.fragTimeExceeded

       Possibilities:
               disabled   (0)
               enabled   (1)"
   ::= {er1646v2EfmVlanEntry 705828096}

er1646v2EfmVlanIpV6IcmpMessagesHeaderFieldErr OBJECT-TYPE
   SYNTAX      INTEGER
               {
               disabled (0),
               enabled (1)
               }
   MAX-ACCESS  read-write
   STATUS      current
   DESCRIPTION
      "Path: efm.editConf.vlan.ipV6.icmpMessages.headerFieldErr

       Possibilities:
               disabled   (0)
               enabled   (1)"
   ::= {er1646v2EfmVlanEntry 705830400}

er1646v2EfmVlanIpV6IcmpMessagesOptionUnrecognized OBJECT-TYPE
   SYNTAX      INTEGER
               {
               disabled (0),
               enabled (1)
               }
   MAX-ACCESS  read-write
   STATUS      current
   DESCRIPTION
      "Path: efm.editConf.vlan.ipV6.icmpMessages.optionUnrecognized

       Possibilities:
               disabled   (0)
               enabled   (1)"
   ::= {er1646v2EfmVlanEntry 705830912}

er1646v2EfmVlanIpV6IcmpMessagesRedirect OBJECT-TYPE
   SYNTAX      INTEGER
               {
               disabled (0),
               enabled (1)
               }
   MAX-ACCESS  read-write
   STATUS      current
   DESCRIPTION
      "Path: efm.editConf.vlan.ipV6.icmpMessages.redirect

       Possibilities:
               disabled   (0)
               enabled   (1)"
   ::= {er1646v2EfmVlanEntry 705832960}

er1646v2EfmVlanBridgingAccList OBJECT-TYPE
   SYNTAX      DisplayString
   MAX-ACCESS  read-write
   STATUS      current
   DESCRIPTION
      "Path: efm.editConf.vlan.bridging.accessList"
   ::= {er1646v2EfmVlanEntry 453246976}

er1646v2EfmVlanBridgingInACL OBJECT-TYPE
   SYNTAX      DisplayString
   MAX-ACCESS  read-write
   STATUS      current
   DESCRIPTION
      "Path: efm.editConf.vlan.bridging.inAccessList"
   ::= {er1646v2EfmVlanEntry 456916992}

er1646v2EfmVlanBridgingTp OBJECT-TYPE
   SYNTAX      DisplayString
   MAX-ACCESS  read-write
   STATUS      current
   DESCRIPTION
      "Path: efm.editConf.vlan.bridging.trafficPolicy"
   ::= {er1646v2EfmVlanEntry 454295552}

er1646v2EfmVlanBridgingBrGrp OBJECT-TYPE
   SYNTAX      DisplayString
   MAX-ACCESS  read-write
   STATUS      current
   DESCRIPTION
      "Path: efm.editConf.vlan.bridging.bridgeGroup"
   ::= {er1646v2EfmVlanEntry 454819840}

er1646v2EfmVlanBridgingLimBC OBJECT-TYPE
   SYNTAX      INTEGER
               {
               disabled (0),
               enabled (1)
               }
   MAX-ACCESS  read-write
   STATUS      current
   DESCRIPTION
      "Path: efm.editConf.vlan.bridging.limitBroadcasts

       Possibilities:
               disabled   (0)
               enabled   (1)"
   ::= {er1646v2EfmVlanEntry 455081984}

er1646v2EfmVlanBridgingPrivateMode OBJECT-TYPE
   SYNTAX      INTEGER
               {
               disabled (0),
               enabled (1)
               }
   MAX-ACCESS  read-write
   STATUS      current
   DESCRIPTION
      "Path: efm.editConf.vlan.bridging.privateMode

       Possibilities:
               disabled   (0)
               enabled   (1)"
   ::= {er1646v2EfmVlanEntry 459538432}

er1646v2EfmVlanBridgingLearning OBJECT-TYPE
   SYNTAX      INTEGER
               {
               disabled (0),
               enabled (1)
               }
   MAX-ACCESS  read-write
   STATUS      current
   DESCRIPTION
      "Path: efm.editConf.vlan.bridging.learning

       Possibilities:
               disabled   (0)
               enabled   (1)"
   ::= {er1646v2EfmVlanEntry 456130560}

er1646v2EfmVlanBridgingMaxCacheSize OBJECT-TYPE
   SYNTAX      INTEGER
               {
               unlimited (0)
               }
   MAX-ACCESS  read-write
   STATUS      current
   DESCRIPTION
      "Path: efm.editConf.vlan.bridging.maxCacheSize

       Possibilities:
               unlimited   (0)"
   ::= {er1646v2EfmVlanEntry 456392704}

er1646v2EfmVlanBridgingRelearnDropOnRelearn OBJECT-TYPE
   SYNTAX      INTEGER
               {
               disabled (0),
               enabled (1)
               }
   MAX-ACCESS  read-write
   STATUS      current
   DESCRIPTION
      "Path: efm.editConf.vlan.bridging.relearn.dropOnRelearn

       Possibilities:
               disabled   (0)
               enabled   (1)"
   ::= {er1646v2EfmVlanEntry 456655872}

er1646v2EfmVlanBridgingRelearnShutdownThreshold OBJECT-TYPE
   SYNTAX      Integer32
   MAX-ACCESS  read-write
   STATUS      current
   DESCRIPTION
      "Path: efm.editConf.vlan.bridging.relearn.shutdownThreshold"
   ::= {er1646v2EfmVlanEntry 456656896}

er1646v2EfmVlanBridgingRelearnShutdownTime OBJECT-TYPE
   SYNTAX      TimeTicks
   MAX-ACCESS  read-write
   STATUS      current
   DESCRIPTION
      "Path: efm.editConf.vlan.bridging.relearn.shutdownTime

       Time in centi-second."
   ::= {er1646v2EfmVlanEntry 456657920}

er1646v2EfmVlanBridgingRelearnLoopDetection OBJECT-TYPE
   SYNTAX      INTEGER
               {
               disabled (0),
               passive (1),
               active (2)
               }
   MAX-ACCESS  read-write
   STATUS      current
   DESCRIPTION
      "Path: efm.editConf.vlan.bridging.relearn.loopDetection

       Possibilities:
               disabled   (0)
               passive   (1)
               active   (2)"
   ::= {er1646v2EfmVlanEntry 456658944}

er1646v2EfmVlanBridgingRelearnLoopDetectionInterval OBJECT-TYPE
   SYNTAX      TimeTicks
   MAX-ACCESS  read-write
   STATUS      current
   DESCRIPTION
      "Path: efm.editConf.vlan.bridging.relearn.loopDetectionInterval

       Time in centi-second."
   ::= {er1646v2EfmVlanEntry 456659968}

er1646v2EfmVlanBridgingVlanMemberShip OBJECT-TYPE
   SYNTAX      INTEGER
               {
               all (0),
               none (1),
               grouped (2)
               }
   MAX-ACCESS  read-write
   STATUS      current
   DESCRIPTION
      "Path: efm.editConf.vlan.bridging.vlanMemberShip

       Possibilities:
               all   (0)
               none   (1)
               grouped   (2)"
   ::= {er1646v2EfmVlanEntry 457965568}

er1646v2EfmVlanBridgingVlTUntaggedAction OBJECT-TYPE
   SYNTAX      INTEGER
               {
               discard (0),
               accept (1),
               tag (2)
               }
   MAX-ACCESS  read-write
   STATUS      current
   DESCRIPTION
      "Path: efm.editConf.vlan.bridging.vlanTagging.untagged.action

       Possibilities:
               discard   (0)
               accept   (1)
               tag   (2)"
   ::= {er1646v2EfmVlanEntry 459055104}

er1646v2EfmVlanBridgingVlTUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: efm.editConf.vlan.bridging.vlanTagging.untagged.tagInfo.tpid

       Possibilities:
               dot1Q   (33024)
               dot1ad   (34984)
               0x9100   (37120)
               0x9200   (37376)
               0x9300   (37632)"
   ::= {er1646v2EfmVlanEntry 459059712}

er1646v2EfmVlanBridgingVlTUntaggedTagInfoVid OBJECT-TYPE
   SYNTAX      Integer32
   MAX-ACCESS  read-write
   STATUS      current
   DESCRIPTION
      "Path: efm.editConf.vlan.bridging.vlanTagging.untagged.tagInfo.vid"
   ::= {er1646v2EfmVlanEntry 459060224}

er1646v2EfmVlanBridgingVlTUnknownVlansAction OBJECT-TYPE
   SYNTAX      INTEGER
               {
               discard (0),
               accept (1),
               tag (2)
               }
   MAX-ACCESS  read-write
   STATUS      current
   DESCRIPTION
      "Path: efm.editConf.vlan.bridging.vlanTagging.unknownVlans.action

       Possibilities:
               discard   (0)
               accept   (1)
               tag   (2)"
   ::= {er1646v2EfmVlanEntry 459120640}

er1646v2EfmVlanBridgingVlTUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: efm.editConf.vlan.bridging.vlanTagging.unknownVlans.tagInfo.tpid

       Possibilities:
               dot1Q   (33024)
               dot1ad   (34984)
               0x9100   (37120)
               0x9200   (37376)
               0x9300   (37632)"
   ::= {er1646v2EfmVlanEntry 459125248}

er1646v2EfmVlanBridgingVlTUnknownVlansTagInfoVid OBJECT-TYPE
   SYNTAX      Integer32
   MAX-ACCESS  read-write
   STATUS      current
   DESCRIPTION
      "Path: efm.editConf.vlan.bridging.vlanTagging.unknownVlans.tagInfo.vid"
   ::= {er1646v2EfmVlanEntry 459125760}

er1646v2EfmVlanBridgingDot1adType OBJECT-TYPE
   SYNTAX      INTEGER
               {
               slOPTg (0),
               cPort (4),
               sPort (1),
               nni (2)
               }
   MAX-ACCESS  read-write
   STATUS      current
   DESCRIPTION
      "Path: efm.editConf.vlan.bridging.dot1ad.type

       Possibilities:
               <OPT>   (0)
               cPort   (4)
               sPort   (1)
               nni   (2)"
   ::= {er1646v2EfmVlanEntry 460850176}

er1646v2EfmVlanBridgingPriority OBJECT-TYPE
   SYNTAX      Integer32
   MAX-ACCESS  read-write
   STATUS      current
   DESCRIPTION
      "Path: efm.editConf.vlan.bridging.priority"
   ::= {er1646v2EfmVlanEntry 453509120}

er1646v2EfmVlanBridgingPathCost OBJECT-TYPE
   SYNTAX      Integer32
   MAX-ACCESS  read-write
   STATUS      current
   DESCRIPTION
      "Path: efm.editConf.vlan.bridging.pathCost"
   ::= {er1646v2EfmVlanEntry 453771264}

er1646v2EfmVlanBridgingInternalPathCost OBJECT-TYPE
   SYNTAX      Integer32
   MAX-ACCESS  read-write
   STATUS      current
   DESCRIPTION
      "Path: efm.editConf.vlan.bridging.internalPathCost"
   ::= {er1646v2EfmVlanEntry 457703424}

er1646v2EfmVlanBridgingTCD OBJECT-TYPE
   SYNTAX      INTEGER
               {
               disabled (0),
               enabled (1)
               }
   MAX-ACCESS  read-write
   STATUS      current
   DESCRIPTION
      "Path: efm.editConf.vlan.bridging.topologyChangeDetection

       Possibilities:
               disabled   (0)
               enabled   (1)"
   ::= {er1646v2EfmVlanEntry 454033408}

er1646v2EfmVlanBridgingRestrictedRole OBJECT-TYPE
   SYNTAX      INTEGER
               {
               disabled (0),
               enabled (1)
               }
   MAX-ACCESS  read-write
   STATUS      current
   DESCRIPTION
      "Path: efm.editConf.vlan.bridging.restrictedRole

       Possibilities:
               disabled   (0)
               enabled   (1)"
   ::= {er1646v2EfmVlanEntry 458227712}

er1646v2EfmVlanBridgingAdminEdge OBJECT-TYPE
   SYNTAX      INTEGER
               {
               disabled (0),
               enabled (1)
               }
   MAX-ACCESS  read-write
   STATUS      current
   DESCRIPTION
      "Path: efm.editConf.vlan.bridging.adminEdge

       Possibilities:
               disabled   (0)
               enabled   (1)"
   ::= {er1646v2EfmVlanEntry 457179136}

er1646v2EfmVlanBridgingOamMacDeviceMac OBJECT-TYPE
   SYNTAX      DisplayString
   MAX-ACCESS  read-write
   STATUS      current
   DESCRIPTION
      "Path: efm.editConf.vlan.bridging.ethOam.macAddress.deviceMac"
   ::= {er1646v2EfmVlanEntry 458506496}

er1646v2EfmVlanBridgingOamMacUserMac OBJECT-TYPE
   SYNTAX      OCTET STRING
   MAX-ACCESS  read-write
   STATUS      current
   DESCRIPTION
      "Path: efm.editConf.vlan.bridging.ethOam.macAddress.userMac

       MAC address."
   ::= {er1646v2EfmVlanEntry 458506368}

er1646v2EfmVlanBridgingOamMacBridgeMac OBJECT-TYPE
   SYNTAX      DisplayString
   MAX-ACCESS  read-write
   STATUS      current
   DESCRIPTION
      "Path: efm.editConf.vlan.bridging.ethOam.macAddress.bridgeMac"
   ::= {er1646v2EfmVlanEntry 458506432}

er1646v2EfmVlanBridgingMgmtInline OBJECT-TYPE
   SYNTAX      INTEGER
               {
               disabled (0),
               enabled (1)
               }
   MAX-ACCESS  read-write
   STATUS      current
   DESCRIPTION
      "Path: efm.editConf.vlan.bridging.mgmtInline

       Possibilities:
               disabled   (0)
               enabled   (1)"
   ::= {er1646v2EfmVlanEntry 458752000}

er1646v2EfmVlanBridgingL2ptMode OBJECT-TYPE
   SYNTAX      INTEGER
               {
               disabled (0),
               enabled (1)
               }
   MAX-ACCESS  read-write
   STATUS      current
   DESCRIPTION
      "Path: efm.editConf.vlan.bridging.l2ProtTunnel.mode

       Possibilities:
               disabled   (0)
               enabled   (1)"
   ::= {er1646v2EfmVlanEntry 459292672}

er1646v2EfmVlanBridgingL2ptProtocols OBJECT-TYPE
   SYNTAX      Integer32
   MAX-ACCESS  read-write
   STATUS      current
   DESCRIPTION
      "Path: efm.editConf.vlan.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1646v2EfmVlanEntry 459309056}

er1646v2EfmVlanBridgingL2ptDestMac OBJECT-TYPE
   SYNTAX      OCTET STRING
   MAX-ACCESS  read-write
   STATUS      current
   DESCRIPTION
      "Path: efm.editConf.vlan.bridging.l2ProtTunnel.destinationMac

       MAC address."
   ::= {er1646v2EfmVlanEntry 459325440}

er1646v2EfmVlanBridgingL2ptCos OBJECT-TYPE
   SYNTAX      INTEGER
               {
               unchanged (255)
               }
   MAX-ACCESS  read-write
   STATUS      current
   DESCRIPTION
      "Path: efm.editConf.vlan.bridging.l2ProtTunnel.cos

       Possibilities:
               unchanged   (255)"
   ::= {er1646v2EfmVlanEntry 459341824}

er1646v2EfmVlanBridgingL2ptDropThrStp OBJECT-TYPE
   SYNTAX      INTEGER
               {
               unlimited (0)
               }
   UNITS       "packets/sec"
   MAX-ACCESS  read-write
   STATUS      current
   DESCRIPTION
      "Path: efm.editConf.vlan.bridging.l2ProtTunnel.dropThresholds.stp

       unit name = packets/sec

       Possibilities:
               unlimited   (0)"
   ::= {er1646v2EfmVlanEntry 459358272}

er1646v2EfmVlanBridgingL2ptDropThrLldp OBJECT-TYPE
   SYNTAX      INTEGER
               {
               unlimited (0)
               }
   UNITS       "packets/sec"
   MAX-ACCESS  read-write
   STATUS      current
   DESCRIPTION
      "Path: efm.editConf.vlan.bridging.l2ProtTunnel.dropThresholds.lldp

       unit name = packets/sec

       Possibilities:
               unlimited   (0)"
   ::= {er1646v2EfmVlanEntry 459358336}

er1646v2EfmVlanBridgingL2ptDropThrOam OBJECT-TYPE
   SYNTAX      INTEGER
               {
               unlimited (0)
               }
   UNITS       "packets/sec"
   MAX-ACCESS  read-write
   STATUS      current
   DESCRIPTION
      "Path: efm.editConf.vlan.bridging.l2ProtTunnel.dropThresholds.oam

       unit name = packets/sec

       Possibilities:
               unlimited   (0)"
   ::= {er1646v2EfmVlanEntry 459358400}

er1646v2EfmVlanBridgingL2ptDropThrCdp OBJECT-TYPE
   SYNTAX      INTEGER
               {
               unlimited (0)
               }
   UNITS       "packets/sec"
   MAX-ACCESS  read-write
   STATUS      current
   DESCRIPTION
      "Path: efm.editConf.vlan.bridging.l2ProtTunnel.dropThresholds.cdp

       unit name = packets/sec

       Possibilities:
               unlimited   (0)"
   ::= {er1646v2EfmVlanEntry 459358464}

er1646v2EfmVlanBridgingL2ptDropThrVtp OBJECT-TYPE
   SYNTAX      INTEGER
               {
               unlimited (0)
               }
   UNITS       "packets/sec"
   MAX-ACCESS  read-write
   STATUS      current
   DESCRIPTION
      "Path: efm.editConf.vlan.bridging.l2ProtTunnel.dropThresholds.vtp

       unit name = packets/sec

       Possibilities:
               unlimited   (0)"
   ::= {er1646v2EfmVlanEntry 459358528}

er1646v2EfmVlanBridgingL2ptDropThrLacp OBJECT-TYPE
   SYNTAX      INTEGER
               {
               unlimited (0)
               }
   UNITS       "packets/sec"
   MAX-ACCESS  read-write
   STATUS      current
   DESCRIPTION
      "Path: efm.editConf.vlan.bridging.l2ProtTunnel.dropThresholds.lacp

       unit name = packets/sec

       Possibilities:
               unlimited   (0)"
   ::= {er1646v2EfmVlanEntry 459358592}

er1646v2EfmVlanBridgingL2ptDropThrEfmOam OBJECT-TYPE
   SYNTAX      INTEGER
               {
               unlimited (0)
               }
   UNITS       "packets/sec"
   MAX-ACCESS  read-write
   STATUS      current
   DESCRIPTION
      "Path: efm.editConf.vlan.bridging.l2ProtTunnel.dropThresholds.efmOam

       unit name = packets/sec

       Possibilities:
               unlimited   (0)"
   ::= {er1646v2EfmVlanEntry 459358656}

er1646v2EfmVlanBridgingL2ptDropThrPvst OBJECT-TYPE
   SYNTAX      INTEGER
               {
               unlimited (0)
               }
   UNITS       "packets/sec"
   MAX-ACCESS  read-write
   STATUS      current
   DESCRIPTION
      "Path: efm.editConf.vlan.bridging.l2ProtTunnel.dropThresholds.pvst

       unit name = packets/sec

       Possibilities:
               unlimited   (0)"
   ::= {er1646v2EfmVlanEntry 459358720}

er1646v2EfmVlanBridgingL2ptDropThrMmrp OBJECT-TYPE
   SYNTAX      INTEGER
               {
               unlimited (0)
               }
   UNITS       "packets/sec"
   MAX-ACCESS  read-write
   STATUS      current
   DESCRIPTION
      "Path: efm.editConf.vlan.bridging.l2ProtTunnel.dropThresholds.mmrp

       unit name = packets/sec

       Possibilities:
               unlimited   (0)"
   ::= {er1646v2EfmVlanEntry 459358784}

er1646v2EfmVlanBridgingL2ptDropThrMvrp OBJECT-TYPE
   SYNTAX      INTEGER
               {
               unlimited (0)
               }
   UNITS       "packets/sec"
   MAX-ACCESS  read-write
   STATUS      current
   DESCRIPTION
      "Path: efm.editConf.vlan.bridging.l2ProtTunnel.dropThresholds.mvrp

       unit name = packets/sec

       Possibilities:
               unlimited   (0)"
   ::= {er1646v2EfmVlanEntry 459358848}

er1646v2EfmVlanBridgingL2ptDropThrGvrp OBJECT-TYPE
   SYNTAX      INTEGER
               {
               unlimited (0)
               }
   UNITS       "packets/sec"
   MAX-ACCESS  read-write
   STATUS      current
   DESCRIPTION
      "Path: efm.editConf.vlan.bridging.l2ProtTunnel.dropThresholds.gvrp

       unit name = packets/sec

       Possibilities:
               unlimited   (0)"
   ::= {er1646v2EfmVlanEntry 459358912}

er1646v2EfmVlanBridgingL2ptDropThrGmrp OBJECT-TYPE
   SYNTAX      INTEGER
               {
               unlimited (0)
               }
   UNITS       "packets/sec"
   MAX-ACCESS  read-write
   STATUS      current
   DESCRIPTION
      "Path: efm.editConf.vlan.bridging.l2ProtTunnel.dropThresholds.gmrp

       unit name = packets/sec

       Possibilities:
               unlimited   (0)"
   ::= {er1646v2EfmVlanEntry 459358976}

er1646v2EfmVlanBridgingL2ptDropThrDtp OBJECT-TYPE
   SYNTAX      INTEGER
               {
               unlimited (0)
               }
   UNITS       "packets/sec"
   MAX-ACCESS  read-write
   STATUS      current
   DESCRIPTION
      "Path: efm.editConf.vlan.bridging.l2ProtTunnel.dropThresholds.dtp

       unit name = packets/sec

       Possibilities:
               unlimited   (0)"
   ::= {er1646v2EfmVlanEntry 459359040}

er1646v2EfmVlanBridgingL2ptDropThrPagp OBJECT-TYPE
   SYNTAX      INTEGER
               {
               unlimited (0)
               }
   UNITS       "packets/sec"
   MAX-ACCESS  read-write
   STATUS      current
   DESCRIPTION
      "Path: efm.editConf.vlan.bridging.l2ProtTunnel.dropThresholds.pagp

       unit name = packets/sec

       Possibilities:
               unlimited   (0)"
   ::= {er1646v2EfmVlanEntry 459359104}

er1646v2EfmVlanBridgingL2ptDropThrUdld OBJECT-TYPE
   SYNTAX      INTEGER
               {
               unlimited (0)
               }
   UNITS       "packets/sec"
   MAX-ACCESS  read-write
   STATUS      current
   DESCRIPTION
      "Path: efm.editConf.vlan.bridging.l2ProtTunnel.dropThresholds.udld

       unit name = packets/sec

       Possibilities:
               unlimited   (0)"
   ::= {er1646v2EfmVlanEntry 459359168}

er1646v2EfmVlanVlanVid OBJECT-TYPE
   SYNTAX      INTEGER
               {
               untagged (0),
               prioTagged (4096),
               notUsed (4097)
               }
   MAX-ACCESS  read-write
   STATUS      current
   DESCRIPTION
      "Path: efm.editConf.vlan.vlan.vid

       Possibilities:
               untagged   (0)
               prioTagged   (4096)
               notUsed   (4097)"
   ::= {er1646v2EfmVlanEntry 234946560}

er1646v2EfmVlanVlanVidExtensionSingle OBJECT-TYPE
   SYNTAX      OCTET STRING
   MAX-ACCESS  read-write
   STATUS      current
   DESCRIPTION
      "Path: efm.editConf.vlan.vlan.vidExtension.single"
   ::= {er1646v2EfmVlanEntry 235340032}

er1646v2EfmVlanVlanVidExtensionEndVid OBJECT-TYPE
   SYNTAX      Integer32
   MAX-ACCESS  read-write
   STATUS      current
   DESCRIPTION
      "Path: efm.editConf.vlan.vlan.vidExtension.endVid"
   ::= {er1646v2EfmVlanEntry 235340288}

er1646v2EfmVlanVlanTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: efm.editConf.vlan.vlan.tpid

       Possibilities:
               dot1Q   (33024)
               dot1ad   (34984)
               0x9100   (37120)
               0x9200   (37376)
               0x9300   (37632)"
   ::= {er1646v2EfmVlanEntry 241238016}

er1646v2EfmVlanVlanTagSign OBJECT-TYPE
   SYNTAX      INTEGER
               {
               global (0),
               local (1),
               sVlan (2),
               sVlanGlobal (6),
               cVlan (3),
               scVlan (5),
               cVlanLocal (4)
               }
   MAX-ACCESS  read-write
   STATUS      current
   DESCRIPTION
      "Path: efm.editConf.vlan.vlan.tagSignificance

       Possibilities:
               global   (0)
               local   (1)
               sVlan   (2)
               sVlanGlobal   (6)
               cVlan   (3)
               scVlan   (5)
               cVlanLocal   (4)"
   ::= {er1646v2EfmVlanEntry 235012096}

er1646v2EfmVlanVlanChTos OBJECT-TYPE
   SYNTAX      INTEGER
               {
               disabled (0),
               enabled (1)
               }
   MAX-ACCESS  read-write
   STATUS      current
   DESCRIPTION
      "Path: efm.editConf.vlan.vlan.changeTos

       Possibilities:
               disabled   (0)
               enabled   (1)"
   ::= {er1646v2EfmVlanEntry 235208704}

er1646v2EfmVlanVlanCTMapP0 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: efm.editConf.vlan.vlan.cosTosMap.p0

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2EfmVlanEntry 235143424}

er1646v2EfmVlanVlanCTMapP1 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: efm.editConf.vlan.vlan.cosTosMap.p1

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2EfmVlanEntry 235143680}

er1646v2EfmVlanVlanCTMapP2 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: efm.editConf.vlan.vlan.cosTosMap.p2

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2EfmVlanEntry 235143936}

er1646v2EfmVlanVlanCTMapP3 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: efm.editConf.vlan.vlan.cosTosMap.p3

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2EfmVlanEntry 235144192}

er1646v2EfmVlanVlanCTMapP4 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: efm.editConf.vlan.vlan.cosTosMap.p4

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2EfmVlanEntry 235144448}

er1646v2EfmVlanVlanCTMapP5 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: efm.editConf.vlan.vlan.cosTosMap.p5

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2EfmVlanEntry 235144704}

er1646v2EfmVlanVlanCTMapP6 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: efm.editConf.vlan.vlan.cosTosMap.p6

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2EfmVlanEntry 235144960}

er1646v2EfmVlanVlanCTMapP7 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: efm.editConf.vlan.vlan.cosTosMap.p7

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2EfmVlanEntry 235145216}

er1646v2EfmVlanVlanTxCos OBJECT-TYPE
   SYNTAX      INTEGER
               {
               tosCosMap (8),
               queueCosMap (16)
               }
   MAX-ACCESS  read-write
   STATUS      current
   DESCRIPTION
      "Path: efm.editConf.vlan.vlan.txCos

       Possibilities:
               tosCosMap   (8)
               queueCosMap   (16)"
   ::= {er1646v2EfmVlanEntry 235077632}

er1646v2EfmVlanVlanCCMapP0 OBJECT-TYPE
   SYNTAX      Integer32
   MAX-ACCESS  read-write
   STATUS      current
   DESCRIPTION
      "Path: efm.editConf.vlan.vlan.cosCosMap.p0"
   ::= {er1646v2EfmVlanEntry 241303808}

er1646v2EfmVlanVlanCCMapP1 OBJECT-TYPE
   SYNTAX      Integer32
   MAX-ACCESS  read-write
   STATUS      current
   DESCRIPTION
      "Path: efm.editConf.vlan.vlan.cosCosMap.p1"
   ::= {er1646v2EfmVlanEntry 241304064}

er1646v2EfmVlanVlanCCMapP2 OBJECT-TYPE
   SYNTAX      Integer32
   MAX-ACCESS  read-write
   STATUS      current
   DESCRIPTION
      "Path: efm.editConf.vlan.vlan.cosCosMap.p2"
   ::= {er1646v2EfmVlanEntry 241304320}

er1646v2EfmVlanVlanCCMapP3 OBJECT-TYPE
   SYNTAX      Integer32
   MAX-ACCESS  read-write
   STATUS      current
   DESCRIPTION
      "Path: efm.editConf.vlan.vlan.cosCosMap.p3"
   ::= {er1646v2EfmVlanEntry 241304576}

er1646v2EfmVlanVlanCCMapP4 OBJECT-TYPE
   SYNTAX      Integer32
   MAX-ACCESS  read-write
   STATUS      current
   DESCRIPTION
      "Path: efm.editConf.vlan.vlan.cosCosMap.p4"
   ::= {er1646v2EfmVlanEntry 241304832}

er1646v2EfmVlanVlanCCMapP5 OBJECT-TYPE
   SYNTAX      Integer32
   MAX-ACCESS  read-write
   STATUS      current
   DESCRIPTION
      "Path: efm.editConf.vlan.vlan.cosCosMap.p5"
   ::= {er1646v2EfmVlanEntry 241305088}

er1646v2EfmVlanVlanCCMapP6 OBJECT-TYPE
   SYNTAX      Integer32
   MAX-ACCESS  read-write
   STATUS      current
   DESCRIPTION
      "Path: efm.editConf.vlan.vlan.cosCosMap.p6"
   ::= {er1646v2EfmVlanEntry 241305344}

er1646v2EfmVlanVlanCCMapP7 OBJECT-TYPE
   SYNTAX      Integer32
   MAX-ACCESS  read-write
   STATUS      current
   DESCRIPTION
      "Path: efm.editConf.vlan.vlan.cosCosMap.p7"
   ::= {er1646v2EfmVlanEntry 241305600}

er1646v2EfmVlanVlanQCMapQueue1 OBJECT-TYPE
   SYNTAX      Integer32
   MAX-ACCESS  read-write
   STATUS      current
   DESCRIPTION
      "Path: efm.editConf.vlan.vlan.queueCosMap.queue1"
   ::= {er1646v2EfmVlanEntry 241434880}

er1646v2EfmVlanVlanQCMapQueue2 OBJECT-TYPE
   SYNTAX      Integer32
   MAX-ACCESS  read-write
   STATUS      current
   DESCRIPTION
      "Path: efm.editConf.vlan.vlan.queueCosMap.queue2"
   ::= {er1646v2EfmVlanEntry 241435136}

er1646v2EfmVlanVlanQCMapQueue3 OBJECT-TYPE
   SYNTAX      Integer32
   MAX-ACCESS  read-write
   STATUS      current
   DESCRIPTION
      "Path: efm.editConf.vlan.vlan.queueCosMap.queue3"
   ::= {er1646v2EfmVlanEntry 241435392}

er1646v2EfmVlanVlanQCMapQueue4 OBJECT-TYPE
   SYNTAX      Integer32
   MAX-ACCESS  read-write
   STATUS      current
   DESCRIPTION
      "Path: efm.editConf.vlan.vlan.queueCosMap.queue4"
   ::= {er1646v2EfmVlanEntry 241435648}

er1646v2EfmVlanVlanQCMapQueue5 OBJECT-TYPE
   SYNTAX      Integer32
   MAX-ACCESS  read-write
   STATUS      current
   DESCRIPTION
      "Path: efm.editConf.vlan.vlan.queueCosMap.queue5"
   ::= {er1646v2EfmVlanEntry 241435904}

er1646v2EfmVlanVlanQCMapLowDelayQueue OBJECT-TYPE
   SYNTAX      Integer32
   MAX-ACCESS  read-write
   STATUS      current
   DESCRIPTION
      "Path: efm.editConf.vlan.vlan.queueCosMap.lowDelayQueue"
   ::= {er1646v2EfmVlanEntry 241436160}

er1646v2EfmVlanVlanQCMapLowDelay2Queue OBJECT-TYPE
   SYNTAX      Integer32
   MAX-ACCESS  read-write
   STATUS      current
   DESCRIPTION
      "Path: efm.editConf.vlan.vlan.queueCosMap.lowDelay2Queue"
   ::= {er1646v2EfmVlanEntry 241436416}

er1646v2EfmVlanVlanQCMapSystemQueue OBJECT-TYPE
   SYNTAX      Integer32
   MAX-ACCESS  read-write
   STATUS      current
   DESCRIPTION
      "Path: efm.editConf.vlan.vlan.queueCosMap.systemQueue"
   ::= {er1646v2EfmVlanEntry 241436672}

er1646v2EfmVlanVlanQinQSVid OBJECT-TYPE
   SYNTAX      Integer32
   MAX-ACCESS  read-write
   STATUS      current
   DESCRIPTION
      "Path: efm.editConf.vlan.vlan.tunnel.sVid"
   ::= {er1646v2EfmVlanEntry 241172736}

er1646v2EfmVlanVlanQinQSTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: efm.editConf.vlan.vlan.tunnel.sTpid

       Possibilities:
               dot1Q   (33024)
               dot1ad   (34984)
               0x9100   (37120)
               0x9200   (37376)
               0x9300   (37632)"
   ::= {er1646v2EfmVlanEntry 241172992}

er1646v2EfmVlanVlanArpTimeOut OBJECT-TYPE
   SYNTAX      TimeTicks
   MAX-ACCESS  read-write
   STATUS      current
   DESCRIPTION
      "Path: efm.editConf.vlan.vlan.arp.timeOut

       Time in centi-second."
   ::= {er1646v2EfmVlanEntry 235277312}

er1646v2EfmVlanVlanArpProxyArp OBJECT-TYPE
   SYNTAX      INTEGER
               {
               disabled (0),
               enabled (1)
               }
   MAX-ACCESS  read-write
   STATUS      current
   DESCRIPTION
      "Path: efm.editConf.vlan.vlan.arp.proxyArp

       Possibilities:
               disabled   (0)
               enabled   (1)"
   ::= {er1646v2EfmVlanEntry 235287040}

er1646v2EfmVlanBandwidthMode OBJECT-TYPE
   SYNTAX      INTEGER
               {
               reshaping (1),
               policing (2),
               policingReshape (3)
               }
   MAX-ACCESS  read-write
   STATUS      current
   DESCRIPTION
      "Path: efm.editConf.vlan.bandwidth.mode

       Possibilities:
               reshaping   (1)
               policing   (2)
               policingReshape   (3)"
   ::= {er1646v2EfmVlanEntry 148897792}

er1646v2EfmVlanBandwidthCir OBJECT-TYPE
   SYNTAX      Integer32
   MAX-ACCESS  read-write
   STATUS      current
   DESCRIPTION
      "Path: efm.editConf.vlan.bandwidth.cir"
   ::= {er1646v2EfmVlanEntry 135266304}

er1646v2EfmVlanBandwidthEir OBJECT-TYPE
   SYNTAX      Integer32
   MAX-ACCESS  read-write
   STATUS      current
   DESCRIPTION
      "Path: efm.editConf.vlan.bandwidth.eir"
   ::= {er1646v2EfmVlanEntry 141557760}

er1646v2EfmVlanBandwidthUnit OBJECT-TYPE
   SYNTAX      INTEGER
               {
               bitssec (1),
               percent (2)
               }
   MAX-ACCESS  read-write
   STATUS      current
   DESCRIPTION
      "Path: efm.editConf.vlan.bandwidth.unit

       Possibilities:
               bits/sec   (1)
               percent   (2)"
   ::= {er1646v2EfmVlanEntry 139460608}

er1646v2EfmVlanBandwidthTc OBJECT-TYPE
   SYNTAX      INTEGER
               {
               auto (0)
               }
   MAX-ACCESS  read-write
   STATUS      current
   DESCRIPTION
      "Path: efm.editConf.vlan.bandwidth.tc

       Possibilities:
               auto   (0)"
   ::= {er1646v2EfmVlanEntry 140509184}

er1646v2EfmVlanBandwidthTcFactor OBJECT-TYPE
   SYNTAX      INTEGER
               {
               ms (10),
               s100us (1)
               }
   MAX-ACCESS  read-write
   STATUS      current
   DESCRIPTION
      "Path: efm.editConf.vlan.bandwidth.tcFactor

       Possibilities:
               ms   (10)
               *100us   (1)"
   ::= {er1646v2EfmVlanEntry 142606336}

er1646v2EfmVlanBandwidthCorrType OBJECT-TYPE
   SYNTAX      INTEGER
               {
               noCorrection (0),
               predefined (1),
               manual (2)
               }
   MAX-ACCESS  read-write
   STATUS      current
   DESCRIPTION
      "Path: efm.editConf.vlan.bandwidth.correction.type

       Possibilities:
               noCorrection   (0)
               predefined   (1)
               manual   (2)"
   ::= {er1646v2EfmVlanEntry 136445952}

er1646v2EfmVlanBandwidthCorrPredefEncapsFrameRelay OBJECT-TYPE
   SYNTAX      DisplayString
   MAX-ACCESS  read-write
   STATUS      current
   DESCRIPTION
      "Path: efm.editConf.vlan.bandwidth.correction.predefined.encapsulation.frameRelay"
   ::= {er1646v2EfmVlanEntry 136594432}

er1646v2EfmVlanBandwidthCorrPredefEncapsPpp OBJECT-TYPE
   SYNTAX      DisplayString
   MAX-ACCESS  read-write
   STATUS      current
   DESCRIPTION
      "Path: efm.editConf.vlan.bandwidth.correction.predefined.encapsulation.ppp"
   ::= {er1646v2EfmVlanEntry 136595456}

er1646v2EfmVlanBandwidthCorrPredefEncapsAtmHl OBJECT-TYPE
   SYNTAX      INTEGER
               {
               rfc2684 (0),
               ppp (1),
               pppOverEthernet (2)
               }
   MAX-ACCESS  read-write
   STATUS      current
   DESCRIPTION
      "Path: efm.editConf.vlan.bandwidth.correction.predefined.encapsulation.atm.higherLayer

       Possibilities:
               rfc2684   (0)
               ppp   (1)
               pppOverEthernet   (2)"
   ::= {er1646v2EfmVlanEntry 136596608}

er1646v2EfmVlanBandwidthCorrPredefEncapsAtmMp OBJECT-TYPE
   SYNTAX      INTEGER
               {
               llcEncapsulation (0),
               vcMultiplexing (1)
               }
   MAX-ACCESS  read-write
   STATUS      current
   DESCRIPTION
      "Path: efm.editConf.vlan.bandwidth.correction.predefined.encapsulation.atm.multiProtocol

       Possibilities:
               llcEncapsulation   (0)
               vcMultiplexing   (1)"
   ::= {er1646v2EfmVlanEntry 136596736}

er1646v2EfmVlanBandwidthCorrPredefEncapsHdlc OBJECT-TYPE
   SYNTAX      DisplayString
   MAX-ACCESS  read-write
   STATUS      current
   DESCRIPTION
      "Path: efm.editConf.vlan.bandwidth.correction.predefined.encapsulation.hdlc"
   ::= {er1646v2EfmVlanEntry 136597504}

er1646v2EfmVlanBandwidthCorrPredefEncapsEfmFs OBJECT-TYPE
   SYNTAX      Integer32
   MAX-ACCESS  read-write
   STATUS      current
   DESCRIPTION
      "Path: efm.editConf.vlan.bandwidth.correction.predefined.encapsulation.efm.fragmentSize"
   ::= {er1646v2EfmVlanEntry 136598656}

er1646v2EfmVlanBandwidthCorrPredefEncapsEfmIb OBJECT-TYPE
   SYNTAX      Integer32
   MAX-ACCESS  read-write
   STATUS      current
   DESCRIPTION
      "Path: efm.editConf.vlan.bandwidth.correction.predefined.encapsulation.efm.idleBytes"
   ::= {er1646v2EfmVlanEntry 136598784}

er1646v2EfmVlanBandwidthCorrPredefMode OBJECT-TYPE
   SYNTAX      INTEGER
               {
               routing (0),
               bridging (1)
               }
   MAX-ACCESS  read-write
   STATUS      current
   DESCRIPTION
      "Path: efm.editConf.vlan.bandwidth.correction.predefined.mode

       Possibilities:
               routing   (0)
               bridging   (1)"
   ::= {er1646v2EfmVlanEntry 136609792}

er1646v2EfmVlanBandwidthCorrManualOverhead OBJECT-TYPE
   SYNTAX      Integer32
   MAX-ACCESS  read-write
   STATUS      current
   DESCRIPTION
      "Path: efm.editConf.vlan.bandwidth.correction.manual.overhead"
   ::= {er1646v2EfmVlanEntry 136708608}

er1646v2EfmVlanBandwidthCorrManualFrameData OBJECT-TYPE
   SYNTAX      Counter32
   MAX-ACCESS  read-write
   STATUS      current
   DESCRIPTION
      "Path: efm.editConf.vlan.bandwidth.correction.manual.frameData

       32 bit unsigned wrappable counter."
   ::= {er1646v2EfmVlanEntry 136709120}

er1646v2EfmVlanBandwidthCorrManualFrameHeader OBJECT-TYPE
   SYNTAX      Counter32
   MAX-ACCESS  read-write
   STATUS      current
   DESCRIPTION
      "Path: efm.editConf.vlan.bandwidth.correction.manual.frameHeader

       32 bit unsigned wrappable counter."
   ::= {er1646v2EfmVlanEntry 136709632}

er1646v2EfmVlanBandwidthMaxFifoQLen OBJECT-TYPE
   SYNTAX      Integer32
   MAX-ACCESS  read-write
   STATUS      current
   DESCRIPTION
      "Path: efm.editConf.vlan.bandwidth.maxFifoQLen"
   ::= {er1646v2EfmVlanEntry 137363456}

er1646v2EfmVlanBandwidthDeFlagCir OBJECT-TYPE
   SYNTAX      INTEGER
               {
               allowed (1),
               notAllowed (2)
               }
   MAX-ACCESS  read-write
   STATUS      current
   DESCRIPTION
      "Path: efm.editConf.vlan.bandwidth.deFlag.cir

       Possibilities:
               allowed   (1)
               notAllowed   (2)"
   ::= {er1646v2EfmVlanEntry 147853312}

er1646v2EfmVlanBandwidthDeFlagEir OBJECT-TYPE
   SYNTAX      INTEGER
               {
               allowed (1),
               notAllowed (2)
               }
   MAX-ACCESS  read-write
   STATUS      current
   DESCRIPTION
      "Path: efm.editConf.vlan.bandwidth.deFlag.eir

       Possibilities:
               allowed   (1)
               notAllowed   (2)"
   ::= {er1646v2EfmVlanEntry 147857408}

er1646v2EfmVlanBandwidthDeFlagViolate OBJECT-TYPE
   SYNTAX      INTEGER
               {
               allowed (1),
               notAllowed (2)
               }
   MAX-ACCESS  read-write
   STATUS      current
   DESCRIPTION
      "Path: efm.editConf.vlan.bandwidth.deFlag.violate

       Possibilities:
               allowed   (1)
               notAllowed   (2)"
   ::= {er1646v2EfmVlanEntry 147861504}

er1646v2EfmVlanBandwidthActCirActNone OBJECT-TYPE
   SYNTAX      OCTET STRING
   MAX-ACCESS  read-write
   STATUS      current
   DESCRIPTION
      "Path: efm.editConf.vlan.bandwidth.action.cirAction.none"
   ::= {er1646v2EfmVlanEntry 150085632}

er1646v2EfmVlanBandwidthActCirActEthCos1 OBJECT-TYPE
   SYNTAX      INTEGER
               {
               unchanged (256)
               }
   MAX-ACCESS  read-write
   STATUS      current
   DESCRIPTION
      "Path: efm.editConf.vlan.bandwidth.action.cirAction.ethernet.cosDepth1

       Possibilities:
               unchanged   (256)"
   ::= {er1646v2EfmVlanEntry 150094080}

er1646v2EfmVlanBandwidthActCirActEthDei1 OBJECT-TYPE
   SYNTAX      INTEGER
               {
               unchanged (255),
               clear (0),
               set (1)
               }
   MAX-ACCESS  read-write
   STATUS      current
   DESCRIPTION
      "Path: efm.editConf.vlan.bandwidth.action.cirAction.ethernet.deiDepth1

       Possibilities:
               unchanged   (255)
               clear   (0)
               set   (1)"
   ::= {er1646v2EfmVlanEntry 150099200}

er1646v2EfmVlanBandwidthActCirActEthCos2 OBJECT-TYPE
   SYNTAX      INTEGER
               {
               unchanged (256)
               }
   MAX-ACCESS  read-write
   STATUS      current
   DESCRIPTION
      "Path: efm.editConf.vlan.bandwidth.action.cirAction.ethernet.cosDepth2

       Possibilities:
               unchanged   (256)"
   ::= {er1646v2EfmVlanEntry 150094336}

er1646v2EfmVlanBandwidthActCirActEthDei2 OBJECT-TYPE
   SYNTAX      INTEGER
               {
               unchanged (255),
               clear (0),
               set (1)
               }
   MAX-ACCESS  read-write
   STATUS      current
   DESCRIPTION
      "Path: efm.editConf.vlan.bandwidth.action.cirAction.ethernet.deiDepth2

       Possibilities:
               unchanged   (255)
               clear   (0)
               set   (1)"
   ::= {er1646v2EfmVlanEntry 150099456}

er1646v2EfmVlanBandwidthActCirActEthCos3 OBJECT-TYPE
   SYNTAX      INTEGER
               {
               unchanged (256)
               }
   MAX-ACCESS  read-write
   STATUS      current
   DESCRIPTION
      "Path: efm.editConf.vlan.bandwidth.action.cirAction.ethernet.cosDepth3

       Possibilities:
               unchanged   (256)"
   ::= {er1646v2EfmVlanEntry 150094592}

er1646v2EfmVlanBandwidthActCirActEthDei3 OBJECT-TYPE
   SYNTAX      INTEGER
               {
               unchanged (255),
               clear (0),
               set (1)
               }
   MAX-ACCESS  read-write
   STATUS      current
   DESCRIPTION
      "Path: efm.editConf.vlan.bandwidth.action.cirAction.ethernet.deiDepth3

       Possibilities:
               unchanged   (255)
               clear   (0)
               set   (1)"
   ::= {er1646v2EfmVlanEntry 150099712}

er1646v2EfmVlanBandwidthActCirActEthCos4 OBJECT-TYPE
   SYNTAX      INTEGER
               {
               unchanged (256)
               }
   MAX-ACCESS  read-write
   STATUS      current
   DESCRIPTION
      "Path: efm.editConf.vlan.bandwidth.action.cirAction.ethernet.cosDepth4

       Possibilities:
               unchanged   (256)"
   ::= {er1646v2EfmVlanEntry 150094848}

er1646v2EfmVlanBandwidthActCirActEthDei4 OBJECT-TYPE
   SYNTAX      INTEGER
               {
               unchanged (255),
               clear (0),
               set (1)
               }
   MAX-ACCESS  read-write
   STATUS      current
   DESCRIPTION
      "Path: efm.editConf.vlan.bandwidth.action.cirAction.ethernet.deiDepth4

       Possibilities:
               unchanged   (255)
               clear   (0)
               set   (1)"
   ::= {er1646v2EfmVlanEntry 150099968}

er1646v2EfmVlanBandwidthActCirActEthCos5 OBJECT-TYPE
   SYNTAX      INTEGER
               {
               unchanged (256)
               }
   MAX-ACCESS  read-write
   STATUS      current
   DESCRIPTION
      "Path: efm.editConf.vlan.bandwidth.action.cirAction.ethernet.cosDepth5

       Possibilities:
               unchanged   (256)"
   ::= {er1646v2EfmVlanEntry 150095104}

er1646v2EfmVlanBandwidthActCirActEthDei5 OBJECT-TYPE
   SYNTAX      INTEGER
               {
               unchanged (255),
               clear (0),
               set (1)
               }
   MAX-ACCESS  read-write
   STATUS      current
   DESCRIPTION
      "Path: efm.editConf.vlan.bandwidth.action.cirAction.ethernet.deiDepth5

       Possibilities:
               unchanged   (255)
               clear   (0)
               set   (1)"
   ::= {er1646v2EfmVlanEntry 150100224}

er1646v2EfmVlanBandwidthActCirActEthCos6 OBJECT-TYPE
   SYNTAX      INTEGER
               {
               unchanged (256)
               }
   MAX-ACCESS  read-write
   STATUS      current
   DESCRIPTION
      "Path: efm.editConf.vlan.bandwidth.action.cirAction.ethernet.cosDepth6

       Possibilities:
               unchanged   (256)"
   ::= {er1646v2EfmVlanEntry 150095360}

er1646v2EfmVlanBandwidthActCirActEthDei6 OBJECT-TYPE
   SYNTAX      INTEGER
               {
               unchanged (255),
               clear (0),
               set (1)
               }
   MAX-ACCESS  read-write
   STATUS      current
   DESCRIPTION
      "Path: efm.editConf.vlan.bandwidth.action.cirAction.ethernet.deiDepth6

       Possibilities:
               unchanged   (255)
               clear   (0)
               set   (1)"
   ::= {er1646v2EfmVlanEntry 150100480}

er1646v2EfmVlanBandwidthActCirActEthCos7 OBJECT-TYPE
   SYNTAX      INTEGER
               {
               unchanged (256)
               }
   MAX-ACCESS  read-write
   STATUS      current
   DESCRIPTION
      "Path: efm.editConf.vlan.bandwidth.action.cirAction.ethernet.cosDepth7

       Possibilities:
               unchanged   (256)"
   ::= {er1646v2EfmVlanEntry 150095616}

er1646v2EfmVlanBandwidthActCirActEthDei7 OBJECT-TYPE
   SYNTAX      INTEGER
               {
               unchanged (255),
               clear (0),
               set (1)
               }
   MAX-ACCESS  read-write
   STATUS      current
   DESCRIPTION
      "Path: efm.editConf.vlan.bandwidth.action.cirAction.ethernet.deiDepth7

       Possibilities:
               unchanged   (255)
               clear   (0)
               set   (1)"
   ::= {er1646v2EfmVlanEntry 150100736}

er1646v2EfmVlanBandwidthActCirActEthCos8 OBJECT-TYPE
   SYNTAX      INTEGER
               {
               unchanged (256)
               }
   MAX-ACCESS  read-write
   STATUS      current
   DESCRIPTION
      "Path: efm.editConf.vlan.bandwidth.action.cirAction.ethernet.cosDepth8

       Possibilities:
               unchanged   (256)"
   ::= {er1646v2EfmVlanEntry 150095872}

er1646v2EfmVlanBandwidthActCirActEthDei8 OBJECT-TYPE
   SYNTAX      INTEGER
               {
               unchanged (255),
               clear (0),
               set (1)
               }
   MAX-ACCESS  read-write
   STATUS      current
   DESCRIPTION
      "Path: efm.editConf.vlan.bandwidth.action.cirAction.ethernet.deiDepth8

       Possibilities:
               unchanged   (255)
               clear   (0)
               set   (1)"
   ::= {er1646v2EfmVlanEntry 150100992}

er1646v2EfmVlanBandwidthActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.vlan.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EfmVlanEntry 150096128}

er1646v2EfmVlanBandwidthActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.vlan.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EfmVlanEntry 150096384}

er1646v2EfmVlanBandwidthActCirActEthDrpLev OBJECT-TYPE
   SYNTAX      INTEGER
               {
               unchanged (0)
               }
   MAX-ACCESS  read-write
   STATUS      current
   DESCRIPTION
      "Path: efm.editConf.vlan.bandwidth.action.cirAction.ethernet.dropLevel

       Possibilities:
               unchanged   (0)"
   ::= {er1646v2EfmVlanEntry 150096640}

er1646v2EfmVlanBandwidthActCirActEthDeFlag OBJECT-TYPE
   SYNTAX      INTEGER
               {
               unchanged (255),
               clear (0),
               set (1)
               }
   MAX-ACCESS  read-write
   STATUS      current
   DESCRIPTION
      "Path: efm.editConf.vlan.bandwidth.action.cirAction.ethernet.deFlag

       Possibilities:
               unchanged   (255)
               clear   (0)
               set   (1)"
   ::= {er1646v2EfmVlanEntry 150097408}

er1646v2EfmVlanBandwidthActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.vlan.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EfmVlanEntry 150120704}

er1646v2EfmVlanBandwidthActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.vlan.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EfmVlanEntry 150120960}

er1646v2EfmVlanBandwidthActCirActIpDrpLev OBJECT-TYPE
   SYNTAX      INTEGER
               {
               unchanged (0)
               }
   MAX-ACCESS  read-write
   STATUS      current
   DESCRIPTION
      "Path: efm.editConf.vlan.bandwidth.action.cirAction.ip.dropLevel

       Possibilities:
               unchanged   (0)"
   ::= {er1646v2EfmVlanEntry 150121216}

er1646v2EfmVlanBandwidthActCirActIpDeFlag OBJECT-TYPE
   SYNTAX      INTEGER
               {
               unchanged (255),
               clear (0),
               set (1)
               }
   MAX-ACCESS  read-write
   STATUS      current
   DESCRIPTION
      "Path: efm.editConf.vlan.bandwidth.action.cirAction.ip.deFlag

       Possibilities:
               unchanged   (255)
               clear   (0)
               set   (1)"
   ::= {er1646v2EfmVlanEntry 150121984}

er1646v2EfmVlanBandwidthActEirActNone OBJECT-TYPE
   SYNTAX      OCTET STRING
   MAX-ACCESS  read-write
   STATUS      current
   DESCRIPTION
      "Path: efm.editConf.vlan.bandwidth.action.eirAction.none"
   ::= {er1646v2EfmVlanEntry 150216704}

er1646v2EfmVlanBandwidthActEirActEthCos1 OBJECT-TYPE
   SYNTAX      INTEGER
               {
               unchanged (256)
               }
   MAX-ACCESS  read-write
   STATUS      current
   DESCRIPTION
      "Path: efm.editConf.vlan.bandwidth.action.eirAction.ethernet.cosDepth1

       Possibilities:
               unchanged   (256)"
   ::= {er1646v2EfmVlanEntry 150225152}

er1646v2EfmVlanBandwidthActEirActEthDei1 OBJECT-TYPE
   SYNTAX      INTEGER
               {
               unchanged (255),
               clear (0),
               set (1)
               }
   MAX-ACCESS  read-write
   STATUS      current
   DESCRIPTION
      "Path: efm.editConf.vlan.bandwidth.action.eirAction.ethernet.deiDepth1

       Possibilities:
               unchanged   (255)
               clear   (0)
               set   (1)"
   ::= {er1646v2EfmVlanEntry 150230272}

er1646v2EfmVlanBandwidthActEirActEthCos2 OBJECT-TYPE
   SYNTAX      INTEGER
               {
               unchanged (256)
               }
   MAX-ACCESS  read-write
   STATUS      current
   DESCRIPTION
      "Path: efm.editConf.vlan.bandwidth.action.eirAction.ethernet.cosDepth2

       Possibilities:
               unchanged   (256)"
   ::= {er1646v2EfmVlanEntry 150225408}

er1646v2EfmVlanBandwidthActEirActEthDei2 OBJECT-TYPE
   SYNTAX      INTEGER
               {
               unchanged (255),
               clear (0),
               set (1)
               }
   MAX-ACCESS  read-write
   STATUS      current
   DESCRIPTION
      "Path: efm.editConf.vlan.bandwidth.action.eirAction.ethernet.deiDepth2

       Possibilities:
               unchanged   (255)
               clear   (0)
               set   (1)"
   ::= {er1646v2EfmVlanEntry 150230528}

er1646v2EfmVlanBandwidthActEirActEthCos3 OBJECT-TYPE
   SYNTAX      INTEGER
               {
               unchanged (256)
               }
   MAX-ACCESS  read-write
   STATUS      current
   DESCRIPTION
      "Path: efm.editConf.vlan.bandwidth.action.eirAction.ethernet.cosDepth3

       Possibilities:
               unchanged   (256)"
   ::= {er1646v2EfmVlanEntry 150225664}

er1646v2EfmVlanBandwidthActEirActEthDei3 OBJECT-TYPE
   SYNTAX      INTEGER
               {
               unchanged (255),
               clear (0),
               set (1)
               }
   MAX-ACCESS  read-write
   STATUS      current
   DESCRIPTION
      "Path: efm.editConf.vlan.bandwidth.action.eirAction.ethernet.deiDepth3

       Possibilities:
               unchanged   (255)
               clear   (0)
               set   (1)"
   ::= {er1646v2EfmVlanEntry 150230784}

er1646v2EfmVlanBandwidthActEirActEthCos4 OBJECT-TYPE
   SYNTAX      INTEGER
               {
               unchanged (256)
               }
   MAX-ACCESS  read-write
   STATUS      current
   DESCRIPTION
      "Path: efm.editConf.vlan.bandwidth.action.eirAction.ethernet.cosDepth4

       Possibilities:
               unchanged   (256)"
   ::= {er1646v2EfmVlanEntry 150225920}

er1646v2EfmVlanBandwidthActEirActEthDei4 OBJECT-TYPE
   SYNTAX      INTEGER
               {
               unchanged (255),
               clear (0),
               set (1)
               }
   MAX-ACCESS  read-write
   STATUS      current
   DESCRIPTION
      "Path: efm.editConf.vlan.bandwidth.action.eirAction.ethernet.deiDepth4

       Possibilities:
               unchanged   (255)
               clear   (0)
               set   (1)"
   ::= {er1646v2EfmVlanEntry 150231040}

er1646v2EfmVlanBandwidthActEirActEthCos5 OBJECT-TYPE
   SYNTAX      INTEGER
               {
               unchanged (256)
               }
   MAX-ACCESS  read-write
   STATUS      current
   DESCRIPTION
      "Path: efm.editConf.vlan.bandwidth.action.eirAction.ethernet.cosDepth5

       Possibilities:
               unchanged   (256)"
   ::= {er1646v2EfmVlanEntry 150226176}

er1646v2EfmVlanBandwidthActEirActEthDei5 OBJECT-TYPE
   SYNTAX      INTEGER
               {
               unchanged (255),
               clear (0),
               set (1)
               }
   MAX-ACCESS  read-write
   STATUS      current
   DESCRIPTION
      "Path: efm.editConf.vlan.bandwidth.action.eirAction.ethernet.deiDepth5

       Possibilities:
               unchanged   (255)
               clear   (0)
               set   (1)"
   ::= {er1646v2EfmVlanEntry 150231296}

er1646v2EfmVlanBandwidthActEirActEthCos6 OBJECT-TYPE
   SYNTAX      INTEGER
               {
               unchanged (256)
               }
   MAX-ACCESS  read-write
   STATUS      current
   DESCRIPTION
      "Path: efm.editConf.vlan.bandwidth.action.eirAction.ethernet.cosDepth6

       Possibilities:
               unchanged   (256)"
   ::= {er1646v2EfmVlanEntry 150226432}

er1646v2EfmVlanBandwidthActEirActEthDei6 OBJECT-TYPE
   SYNTAX      INTEGER
               {
               unchanged (255),
               clear (0),
               set (1)
               }
   MAX-ACCESS  read-write
   STATUS      current
   DESCRIPTION
      "Path: efm.editConf.vlan.bandwidth.action.eirAction.ethernet.deiDepth6

       Possibilities:
               unchanged   (255)
               clear   (0)
               set   (1)"
   ::= {er1646v2EfmVlanEntry 150231552}

er1646v2EfmVlanBandwidthActEirActEthCos7 OBJECT-TYPE
   SYNTAX      INTEGER
               {
               unchanged (256)
               }
   MAX-ACCESS  read-write
   STATUS      current
   DESCRIPTION
      "Path: efm.editConf.vlan.bandwidth.action.eirAction.ethernet.cosDepth7

       Possibilities:
               unchanged   (256)"
   ::= {er1646v2EfmVlanEntry 150226688}

er1646v2EfmVlanBandwidthActEirActEthDei7 OBJECT-TYPE
   SYNTAX      INTEGER
               {
               unchanged (255),
               clear (0),
               set (1)
               }
   MAX-ACCESS  read-write
   STATUS      current
   DESCRIPTION
      "Path: efm.editConf.vlan.bandwidth.action.eirAction.ethernet.deiDepth7

       Possibilities:
               unchanged   (255)
               clear   (0)
               set   (1)"
   ::= {er1646v2EfmVlanEntry 150231808}

er1646v2EfmVlanBandwidthActEirActEthCos8 OBJECT-TYPE
   SYNTAX      INTEGER
               {
               unchanged (256)
               }
   MAX-ACCESS  read-write
   STATUS      current
   DESCRIPTION
      "Path: efm.editConf.vlan.bandwidth.action.eirAction.ethernet.cosDepth8

       Possibilities:
               unchanged   (256)"
   ::= {er1646v2EfmVlanEntry 150226944}

er1646v2EfmVlanBandwidthActEirActEthDei8 OBJECT-TYPE
   SYNTAX      INTEGER
               {
               unchanged (255),
               clear (0),
               set (1)
               }
   MAX-ACCESS  read-write
   STATUS      current
   DESCRIPTION
      "Path: efm.editConf.vlan.bandwidth.action.eirAction.ethernet.deiDepth8

       Possibilities:
               unchanged   (255)
               clear   (0)
               set   (1)"
   ::= {er1646v2EfmVlanEntry 150232064}

er1646v2EfmVlanBandwidthActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.vlan.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EfmVlanEntry 150227200}

er1646v2EfmVlanBandwidthActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.vlan.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EfmVlanEntry 150227456}

er1646v2EfmVlanBandwidthActEirActEthDrpLev OBJECT-TYPE
   SYNTAX      INTEGER
               {
               unchanged (0)
               }
   MAX-ACCESS  read-write
   STATUS      current
   DESCRIPTION
      "Path: efm.editConf.vlan.bandwidth.action.eirAction.ethernet.dropLevel

       Possibilities:
               unchanged   (0)"
   ::= {er1646v2EfmVlanEntry 150227712}

er1646v2EfmVlanBandwidthActEirActEthDeFlag OBJECT-TYPE
   SYNTAX      INTEGER
               {
               unchanged (255),
               clear (0),
               set (1)
               }
   MAX-ACCESS  read-write
   STATUS      current
   DESCRIPTION
      "Path: efm.editConf.vlan.bandwidth.action.eirAction.ethernet.deFlag

       Possibilities:
               unchanged   (255)
               clear   (0)
               set   (1)"
   ::= {er1646v2EfmVlanEntry 150228480}

er1646v2EfmVlanBandwidthActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.vlan.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EfmVlanEntry 150251776}

er1646v2EfmVlanBandwidthActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.vlan.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EfmVlanEntry 150252032}

er1646v2EfmVlanBandwidthActEirActIpDrpLev OBJECT-TYPE
   SYNTAX      INTEGER
               {
               unchanged (0)
               }
   MAX-ACCESS  read-write
   STATUS      current
   DESCRIPTION
      "Path: efm.editConf.vlan.bandwidth.action.eirAction.ip.dropLevel

       Possibilities:
               unchanged   (0)"
   ::= {er1646v2EfmVlanEntry 150252288}

er1646v2EfmVlanBandwidthActEirActIpDeFlag OBJECT-TYPE
   SYNTAX      INTEGER
               {
               unchanged (255),
               clear (0),
               set (1)
               }
   MAX-ACCESS  read-write
   STATUS      current
   DESCRIPTION
      "Path: efm.editConf.vlan.bandwidth.action.eirAction.ip.deFlag

       Possibilities:
               unchanged   (255)
               clear   (0)
               set   (1)"
   ::= {er1646v2EfmVlanEntry 150253056}

er1646v2EfmVlanBandwidthActViolActNone OBJECT-TYPE
   SYNTAX      OCTET STRING
   MAX-ACCESS  read-write
   STATUS      current
   DESCRIPTION
      "Path: efm.editConf.vlan.bandwidth.action.violateAction.none"
   ::= {er1646v2EfmVlanEntry 150347776}

er1646v2EfmVlanBandwidthActViolActDrop OBJECT-TYPE
   SYNTAX      OCTET STRING
   MAX-ACCESS  read-write
   STATUS      current
   DESCRIPTION
      "Path: efm.editConf.vlan.bandwidth.action.violateAction.drop"
   ::= {er1646v2EfmVlanEntry 150364160}

er1646v2EfmVlanBandwidthActViolActEthCos1 OBJECT-TYPE
   SYNTAX      INTEGER
               {
               unchanged (256)
               }
   MAX-ACCESS  read-write
   STATUS      current
   DESCRIPTION
      "Path: efm.editConf.vlan.bandwidth.action.violateAction.ethernet.cosDepth1

       Possibilities:
               unchanged   (256)"
   ::= {er1646v2EfmVlanEntry 150356224}

er1646v2EfmVlanBandwidthActViolActEthDei1 OBJECT-TYPE
   SYNTAX      INTEGER
               {
               unchanged (255),
               clear (0),
               set (1)
               }
   MAX-ACCESS  read-write
   STATUS      current
   DESCRIPTION
      "Path: efm.editConf.vlan.bandwidth.action.violateAction.ethernet.deiDepth1

       Possibilities:
               unchanged   (255)
               clear   (0)
               set   (1)"
   ::= {er1646v2EfmVlanEntry 150361344}

er1646v2EfmVlanBandwidthActViolActEthCos2 OBJECT-TYPE
   SYNTAX      INTEGER
               {
               unchanged (256)
               }
   MAX-ACCESS  read-write
   STATUS      current
   DESCRIPTION
      "Path: efm.editConf.vlan.bandwidth.action.violateAction.ethernet.cosDepth2

       Possibilities:
               unchanged   (256)"
   ::= {er1646v2EfmVlanEntry 150356480}

er1646v2EfmVlanBandwidthActViolActEthDei2 OBJECT-TYPE
   SYNTAX      INTEGER
               {
               unchanged (255),
               clear (0),
               set (1)
               }
   MAX-ACCESS  read-write
   STATUS      current
   DESCRIPTION
      "Path: efm.editConf.vlan.bandwidth.action.violateAction.ethernet.deiDepth2

       Possibilities:
               unchanged   (255)
               clear   (0)
               set   (1)"
   ::= {er1646v2EfmVlanEntry 150361600}

er1646v2EfmVlanBandwidthActViolActEthCos3 OBJECT-TYPE
   SYNTAX      INTEGER
               {
               unchanged (256)
               }
   MAX-ACCESS  read-write
   STATUS      current
   DESCRIPTION
      "Path: efm.editConf.vlan.bandwidth.action.violateAction.ethernet.cosDepth3

       Possibilities:
               unchanged   (256)"
   ::= {er1646v2EfmVlanEntry 150356736}

er1646v2EfmVlanBandwidthActViolActEthDei3 OBJECT-TYPE
   SYNTAX      INTEGER
               {
               unchanged (255),
               clear (0),
               set (1)
               }
   MAX-ACCESS  read-write
   STATUS      current
   DESCRIPTION
      "Path: efm.editConf.vlan.bandwidth.action.violateAction.ethernet.deiDepth3

       Possibilities:
               unchanged   (255)
               clear   (0)
               set   (1)"
   ::= {er1646v2EfmVlanEntry 150361856}

er1646v2EfmVlanBandwidthActViolActEthCos4 OBJECT-TYPE
   SYNTAX      INTEGER
               {
               unchanged (256)
               }
   MAX-ACCESS  read-write
   STATUS      current
   DESCRIPTION
      "Path: efm.editConf.vlan.bandwidth.action.violateAction.ethernet.cosDepth4

       Possibilities:
               unchanged   (256)"
   ::= {er1646v2EfmVlanEntry 150356992}

er1646v2EfmVlanBandwidthActViolActEthDei4 OBJECT-TYPE
   SYNTAX      INTEGER
               {
               unchanged (255),
               clear (0),
               set (1)
               }
   MAX-ACCESS  read-write
   STATUS      current
   DESCRIPTION
      "Path: efm.editConf.vlan.bandwidth.action.violateAction.ethernet.deiDepth4

       Possibilities:
               unchanged   (255)
               clear   (0)
               set   (1)"
   ::= {er1646v2EfmVlanEntry 150362112}

er1646v2EfmVlanBandwidthActViolActEthCos5 OBJECT-TYPE
   SYNTAX      INTEGER
               {
               unchanged (256)
               }
   MAX-ACCESS  read-write
   STATUS      current
   DESCRIPTION
      "Path: efm.editConf.vlan.bandwidth.action.violateAction.ethernet.cosDepth5

       Possibilities:
               unchanged   (256)"
   ::= {er1646v2EfmVlanEntry 150357248}

er1646v2EfmVlanBandwidthActViolActEthDei5 OBJECT-TYPE
   SYNTAX      INTEGER
               {
               unchanged (255),
               clear (0),
               set (1)
               }
   MAX-ACCESS  read-write
   STATUS      current
   DESCRIPTION
      "Path: efm.editConf.vlan.bandwidth.action.violateAction.ethernet.deiDepth5

       Possibilities:
               unchanged   (255)
               clear   (0)
               set   (1)"
   ::= {er1646v2EfmVlanEntry 150362368}

er1646v2EfmVlanBandwidthActViolActEthCos6 OBJECT-TYPE
   SYNTAX      INTEGER
               {
               unchanged (256)
               }
   MAX-ACCESS  read-write
   STATUS      current
   DESCRIPTION
      "Path: efm.editConf.vlan.bandwidth.action.violateAction.ethernet.cosDepth6

       Possibilities:
               unchanged   (256)"
   ::= {er1646v2EfmVlanEntry 150357504}

er1646v2EfmVlanBandwidthActViolActEthDei6 OBJECT-TYPE
   SYNTAX      INTEGER
               {
               unchanged (255),
               clear (0),
               set (1)
               }
   MAX-ACCESS  read-write
   STATUS      current
   DESCRIPTION
      "Path: efm.editConf.vlan.bandwidth.action.violateAction.ethernet.deiDepth6

       Possibilities:
               unchanged   (255)
               clear   (0)
               set   (1)"
   ::= {er1646v2EfmVlanEntry 150362624}

er1646v2EfmVlanBandwidthActViolActEthCos7 OBJECT-TYPE
   SYNTAX      INTEGER
               {
               unchanged (256)
               }
   MAX-ACCESS  read-write
   STATUS      current
   DESCRIPTION
      "Path: efm.editConf.vlan.bandwidth.action.violateAction.ethernet.cosDepth7

       Possibilities:
               unchanged   (256)"
   ::= {er1646v2EfmVlanEntry 150357760}

er1646v2EfmVlanBandwidthActViolActEthDei7 OBJECT-TYPE
   SYNTAX      INTEGER
               {
               unchanged (255),
               clear (0),
               set (1)
               }
   MAX-ACCESS  read-write
   STATUS      current
   DESCRIPTION
      "Path: efm.editConf.vlan.bandwidth.action.violateAction.ethernet.deiDepth7

       Possibilities:
               unchanged   (255)
               clear   (0)
               set   (1)"
   ::= {er1646v2EfmVlanEntry 150362880}

er1646v2EfmVlanBandwidthActViolActEthCos8 OBJECT-TYPE
   SYNTAX      INTEGER
               {
               unchanged (256)
               }
   MAX-ACCESS  read-write
   STATUS      current
   DESCRIPTION
      "Path: efm.editConf.vlan.bandwidth.action.violateAction.ethernet.cosDepth8

       Possibilities:
               unchanged   (256)"
   ::= {er1646v2EfmVlanEntry 150358016}

er1646v2EfmVlanBandwidthActViolActEthDei8 OBJECT-TYPE
   SYNTAX      INTEGER
               {
               unchanged (255),
               clear (0),
               set (1)
               }
   MAX-ACCESS  read-write
   STATUS      current
   DESCRIPTION
      "Path: efm.editConf.vlan.bandwidth.action.violateAction.ethernet.deiDepth8

       Possibilities:
               unchanged   (255)
               clear   (0)
               set   (1)"
   ::= {er1646v2EfmVlanEntry 150363136}

er1646v2EfmVlanBandwidthActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.vlan.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EfmVlanEntry 150358272}

er1646v2EfmVlanBandwidthActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.vlan.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EfmVlanEntry 150358528}

er1646v2EfmVlanBandwidthActViolActEthDrpLev OBJECT-TYPE
   SYNTAX      INTEGER
               {
               unchanged (0)
               }
   MAX-ACCESS  read-write
   STATUS      current
   DESCRIPTION
      "Path: efm.editConf.vlan.bandwidth.action.violateAction.ethernet.dropLevel

       Possibilities:
               unchanged   (0)"
   ::= {er1646v2EfmVlanEntry 150358784}

er1646v2EfmVlanBandwidthActViolActEthDeFlag OBJECT-TYPE
   SYNTAX      INTEGER
               {
               unchanged (255),
               clear (0),
               set (1)
               }
   MAX-ACCESS  read-write
   STATUS      current
   DESCRIPTION
      "Path: efm.editConf.vlan.bandwidth.action.violateAction.ethernet.deFlag

       Possibilities:
               unchanged   (255)
               clear   (0)
               set   (1)"
   ::= {er1646v2EfmVlanEntry 150359552}

er1646v2EfmVlanBandwidthActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.vlan.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EfmVlanEntry 150382848}

er1646v2EfmVlanBandwidthActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.vlan.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EfmVlanEntry 150383104}

er1646v2EfmVlanBandwidthActViolActIpDrpLev OBJECT-TYPE
   SYNTAX      INTEGER
               {
               unchanged (0)
               }
   MAX-ACCESS  read-write
   STATUS      current
   DESCRIPTION
      "Path: efm.editConf.vlan.bandwidth.action.violateAction.ip.dropLevel

       Possibilities:
               unchanged   (0)"
   ::= {er1646v2EfmVlanEntry 150383360}

er1646v2EfmVlanBandwidthActViolActIpDeFlag OBJECT-TYPE
   SYNTAX      INTEGER
               {
               unchanged (255),
               clear (0),
               set (1)
               }
   MAX-ACCESS  read-write
   STATUS      current
   DESCRIPTION
      "Path: efm.editConf.vlan.bandwidth.action.violateAction.ip.deFlag

       Possibilities:
               unchanged   (255)
               clear   (0)
               set   (1)"
   ::= {er1646v2EfmVlanEntry 150384128}

er1646v2EfmVlanInbBwMode OBJECT-TYPE
   SYNTAX      INTEGER
               {
               reshaping (1),
               policing (2)
               }
   MAX-ACCESS  read-write
   STATUS      current
   DESCRIPTION
      "Path: efm.editConf.vlan.inboundBandwidth.mode

       Possibilities:
               reshaping   (1)
               policing   (2)"
   ::= {er1646v2EfmVlanEntry 132120576}

er1646v2EfmVlanInbBwCir OBJECT-TYPE
   SYNTAX      Integer32
   MAX-ACCESS  read-write
   STATUS      current
   DESCRIPTION
      "Path: efm.editConf.vlan.inboundBandwidth.cir"
   ::= {er1646v2EfmVlanEntry 118489088}

er1646v2EfmVlanInbBwEir OBJECT-TYPE
   SYNTAX      Integer32
   MAX-ACCESS  read-write
   STATUS      current
   DESCRIPTION
      "Path: efm.editConf.vlan.inboundBandwidth.eir"
   ::= {er1646v2EfmVlanEntry 124780544}

er1646v2EfmVlanInbBwUnit OBJECT-TYPE
   SYNTAX      INTEGER
               {
               bitssec (1),
               percent (2)
               }
   MAX-ACCESS  read-write
   STATUS      current
   DESCRIPTION
      "Path: efm.editConf.vlan.inboundBandwidth.unit

       Possibilities:
               bits/sec   (1)
               percent   (2)"
   ::= {er1646v2EfmVlanEntry 122683392}

er1646v2EfmVlanInbBwTc OBJECT-TYPE
   SYNTAX      INTEGER
               {
               auto (0)
               }
   MAX-ACCESS  read-write
   STATUS      current
   DESCRIPTION
      "Path: efm.editConf.vlan.inboundBandwidth.tc

       Possibilities:
               auto   (0)"
   ::= {er1646v2EfmVlanEntry 123731968}

er1646v2EfmVlanInbBwTcFactor OBJECT-TYPE
   SYNTAX      INTEGER
               {
               ms (10),
               s100us (1)
               }
   MAX-ACCESS  read-write
   STATUS      current
   DESCRIPTION
      "Path: efm.editConf.vlan.inboundBandwidth.tcFactor

       Possibilities:
               ms   (10)
               *100us   (1)"
   ::= {er1646v2EfmVlanEntry 125829120}

er1646v2EfmVlanInbBwCorrType OBJECT-TYPE
   SYNTAX      INTEGER
               {
               noCorrection (0),
               predefined (1),
               manual (2)
               }
   MAX-ACCESS  read-write
   STATUS      current
   DESCRIPTION
      "Path: efm.editConf.vlan.inboundBandwidth.correction.type

       Possibilities:
               noCorrection   (0)
               predefined   (1)
               manual   (2)"
   ::= {er1646v2EfmVlanEntry 119668736}

er1646v2EfmVlanInbBwCorrPredefEncapsFrameRelay OBJECT-TYPE
   SYNTAX      DisplayString
   MAX-ACCESS  read-write
   STATUS      current
   DESCRIPTION
      "Path: efm.editConf.vlan.inboundBandwidth.correction.predefined.encapsulation.frameRelay"
   ::= {er1646v2EfmVlanEntry 119817216}

er1646v2EfmVlanInbBwCorrPredefEncapsPpp OBJECT-TYPE
   SYNTAX      DisplayString
   MAX-ACCESS  read-write
   STATUS      current
   DESCRIPTION
      "Path: efm.editConf.vlan.inboundBandwidth.correction.predefined.encapsulation.ppp"
   ::= {er1646v2EfmVlanEntry 119818240}

er1646v2EfmVlanInbBwCorrPredefEncapsAtmHl OBJECT-TYPE
   SYNTAX      INTEGER
               {
               rfc2684 (0),
               ppp (1),
               pppOverEthernet (2)
               }
   MAX-ACCESS  read-write
   STATUS      current
   DESCRIPTION
      "Path: efm.editConf.vlan.inboundBandwidth.correction.predefined.encapsulation.atm.higherLayer

       Possibilities:
               rfc2684   (0)
               ppp   (1)
               pppOverEthernet   (2)"
   ::= {er1646v2EfmVlanEntry 119819392}

er1646v2EfmVlanInbBwCorrPredefEncapsAtmMp OBJECT-TYPE
   SYNTAX      INTEGER
               {
               llcEncapsulation (0),
               vcMultiplexing (1)
               }
   MAX-ACCESS  read-write
   STATUS      current
   DESCRIPTION
      "Path: efm.editConf.vlan.inboundBandwidth.correction.predefined.encapsulation.atm.multiProtocol

       Possibilities:
               llcEncapsulation   (0)
               vcMultiplexing   (1)"
   ::= {er1646v2EfmVlanEntry 119819520}

er1646v2EfmVlanInbBwCorrPredefEncapsHdlc OBJECT-TYPE
   SYNTAX      DisplayString
   MAX-ACCESS  read-write
   STATUS      current
   DESCRIPTION
      "Path: efm.editConf.vlan.inboundBandwidth.correction.predefined.encapsulation.hdlc"
   ::= {er1646v2EfmVlanEntry 119820288}

er1646v2EfmVlanInbBwCorrPredefEncapsEfmFs OBJECT-TYPE
   SYNTAX      Integer32
   MAX-ACCESS  read-write
   STATUS      current
   DESCRIPTION
      "Path: efm.editConf.vlan.inboundBandwidth.correction.predefined.encapsulation.efm.fragmentSize"
   ::= {er1646v2EfmVlanEntry 119821440}

er1646v2EfmVlanInbBwCorrPredefEncapsEfmIb OBJECT-TYPE
   SYNTAX      Integer32
   MAX-ACCESS  read-write
   STATUS      current
   DESCRIPTION
      "Path: efm.editConf.vlan.inboundBandwidth.correction.predefined.encapsulation.efm.idleBytes"
   ::= {er1646v2EfmVlanEntry 119821568}

er1646v2EfmVlanInbBwCorrPredefMode OBJECT-TYPE
   SYNTAX      INTEGER
               {
               routing (0),
               bridging (1)
               }
   MAX-ACCESS  read-write
   STATUS      current
   DESCRIPTION
      "Path: efm.editConf.vlan.inboundBandwidth.correction.predefined.mode

       Possibilities:
               routing   (0)
               bridging   (1)"
   ::= {er1646v2EfmVlanEntry 119832576}

er1646v2EfmVlanInbBwCorrManualOverhead OBJECT-TYPE
   SYNTAX      Integer32
   MAX-ACCESS  read-write
   STATUS      current
   DESCRIPTION
      "Path: efm.editConf.vlan.inboundBandwidth.correction.manual.overhead"
   ::= {er1646v2EfmVlanEntry 119931392}

er1646v2EfmVlanInbBwCorrManualFrameData OBJECT-TYPE
   SYNTAX      Counter32
   MAX-ACCESS  read-write
   STATUS      current
   DESCRIPTION
      "Path: efm.editConf.vlan.inboundBandwidth.correction.manual.frameData

       32 bit unsigned wrappable counter."
   ::= {er1646v2EfmVlanEntry 119931904}

er1646v2EfmVlanInbBwCorrManualFrameHeader OBJECT-TYPE
   SYNTAX      Counter32
   MAX-ACCESS  read-write
   STATUS      current
   DESCRIPTION
      "Path: efm.editConf.vlan.inboundBandwidth.correction.manual.frameHeader

       32 bit unsigned wrappable counter."
   ::= {er1646v2EfmVlanEntry 119932416}

er1646v2EfmVlanInbBwMaxFifoQLen OBJECT-TYPE
   SYNTAX      Integer32
   MAX-ACCESS  read-write
   STATUS      current
   DESCRIPTION
      "Path: efm.editConf.vlan.inboundBandwidth.maxFifoQLen"
   ::= {er1646v2EfmVlanEntry 120586240}

er1646v2EfmVlanInbBwPriorityPolicy OBJECT-TYPE
   SYNTAX      DisplayString
   MAX-ACCESS  read-write
   STATUS      current
   DESCRIPTION
      "Path: efm.editConf.vlan.inboundBandwidth.priorityPolicy"
   ::= {er1646v2EfmVlanEntry 121634816}

er1646v2EfmVlanInbBwDeFlagCir OBJECT-TYPE
   SYNTAX      INTEGER
               {
               allowed (1),
               notAllowed (2)
               }
   MAX-ACCESS  read-write
   STATUS      current
   DESCRIPTION
      "Path: efm.editConf.vlan.inboundBandwidth.deFlag.cir

       Possibilities:
               allowed   (1)
               notAllowed   (2)"
   ::= {er1646v2EfmVlanEntry 131076096}

er1646v2EfmVlanInbBwDeFlagEir OBJECT-TYPE
   SYNTAX      INTEGER
               {
               allowed (1),
               notAllowed (2)
               }
   MAX-ACCESS  read-write
   STATUS      current
   DESCRIPTION
      "Path: efm.editConf.vlan.inboundBandwidth.deFlag.eir

       Possibilities:
               allowed   (1)
               notAllowed   (2)"
   ::= {er1646v2EfmVlanEntry 131080192}

er1646v2EfmVlanInbBwDeFlagViolate OBJECT-TYPE
   SYNTAX      INTEGER
               {
               allowed (1),
               notAllowed (2)
               }
   MAX-ACCESS  read-write
   STATUS      current
   DESCRIPTION
      "Path: efm.editConf.vlan.inboundBandwidth.deFlag.violate

       Possibilities:
               allowed   (1)
               notAllowed   (2)"
   ::= {er1646v2EfmVlanEntry 131084288}

er1646v2EfmVlanInbBwActCirActNone OBJECT-TYPE
   SYNTAX      OCTET STRING
   MAX-ACCESS  read-write
   STATUS      current
   DESCRIPTION
      "Path: efm.editConf.vlan.inboundBandwidth.action.cirAction.none"
   ::= {er1646v2EfmVlanEntry 133308416}

er1646v2EfmVlanInbBwActCirActEthCos1 OBJECT-TYPE
   SYNTAX      INTEGER
               {
               unchanged (256)
               }
   MAX-ACCESS  read-write
   STATUS      current
   DESCRIPTION
      "Path: efm.editConf.vlan.inboundBandwidth.action.cirAction.ethernet.cosDepth1

       Possibilities:
               unchanged   (256)"
   ::= {er1646v2EfmVlanEntry 133316864}

er1646v2EfmVlanInbBwActCirActEthDei1 OBJECT-TYPE
   SYNTAX      INTEGER
               {
               unchanged (255),
               clear (0),
               set (1)
               }
   MAX-ACCESS  read-write
   STATUS      current
   DESCRIPTION
      "Path: efm.editConf.vlan.inboundBandwidth.action.cirAction.ethernet.deiDepth1

       Possibilities:
               unchanged   (255)
               clear   (0)
               set   (1)"
   ::= {er1646v2EfmVlanEntry 133321984}

er1646v2EfmVlanInbBwActCirActEthCos2 OBJECT-TYPE
   SYNTAX      INTEGER
               {
               unchanged (256)
               }
   MAX-ACCESS  read-write
   STATUS      current
   DESCRIPTION
      "Path: efm.editConf.vlan.inboundBandwidth.action.cirAction.ethernet.cosDepth2

       Possibilities:
               unchanged   (256)"
   ::= {er1646v2EfmVlanEntry 133317120}

er1646v2EfmVlanInbBwActCirActEthDei2 OBJECT-TYPE
   SYNTAX      INTEGER
               {
               unchanged (255),
               clear (0),
               set (1)
               }
   MAX-ACCESS  read-write
   STATUS      current
   DESCRIPTION
      "Path: efm.editConf.vlan.inboundBandwidth.action.cirAction.ethernet.deiDepth2

       Possibilities:
               unchanged   (255)
               clear   (0)
               set   (1)"
   ::= {er1646v2EfmVlanEntry 133322240}

er1646v2EfmVlanInbBwActCirActEthCos3 OBJECT-TYPE
   SYNTAX      INTEGER
               {
               unchanged (256)
               }
   MAX-ACCESS  read-write
   STATUS      current
   DESCRIPTION
      "Path: efm.editConf.vlan.inboundBandwidth.action.cirAction.ethernet.cosDepth3

       Possibilities:
               unchanged   (256)"
   ::= {er1646v2EfmVlanEntry 133317376}

er1646v2EfmVlanInbBwActCirActEthDei3 OBJECT-TYPE
   SYNTAX      INTEGER
               {
               unchanged (255),
               clear (0),
               set (1)
               }
   MAX-ACCESS  read-write
   STATUS      current
   DESCRIPTION
      "Path: efm.editConf.vlan.inboundBandwidth.action.cirAction.ethernet.deiDepth3

       Possibilities:
               unchanged   (255)
               clear   (0)
               set   (1)"
   ::= {er1646v2EfmVlanEntry 133322496}

er1646v2EfmVlanInbBwActCirActEthCos4 OBJECT-TYPE
   SYNTAX      INTEGER
               {
               unchanged (256)
               }
   MAX-ACCESS  read-write
   STATUS      current
   DESCRIPTION
      "Path: efm.editConf.vlan.inboundBandwidth.action.cirAction.ethernet.cosDepth4

       Possibilities:
               unchanged   (256)"
   ::= {er1646v2EfmVlanEntry 133317632}

er1646v2EfmVlanInbBwActCirActEthDei4 OBJECT-TYPE
   SYNTAX      INTEGER
               {
               unchanged (255),
               clear (0),
               set (1)
               }
   MAX-ACCESS  read-write
   STATUS      current
   DESCRIPTION
      "Path: efm.editConf.vlan.inboundBandwidth.action.cirAction.ethernet.deiDepth4

       Possibilities:
               unchanged   (255)
               clear   (0)
               set   (1)"
   ::= {er1646v2EfmVlanEntry 133322752}

er1646v2EfmVlanInbBwActCirActEthCos5 OBJECT-TYPE
   SYNTAX      INTEGER
               {
               unchanged (256)
               }
   MAX-ACCESS  read-write
   STATUS      current
   DESCRIPTION
      "Path: efm.editConf.vlan.inboundBandwidth.action.cirAction.ethernet.cosDepth5

       Possibilities:
               unchanged   (256)"
   ::= {er1646v2EfmVlanEntry 133317888}

er1646v2EfmVlanInbBwActCirActEthDei5 OBJECT-TYPE
   SYNTAX      INTEGER
               {
               unchanged (255),
               clear (0),
               set (1)
               }
   MAX-ACCESS  read-write
   STATUS      current
   DESCRIPTION
      "Path: efm.editConf.vlan.inboundBandwidth.action.cirAction.ethernet.deiDepth5

       Possibilities:
               unchanged   (255)
               clear   (0)
               set   (1)"
   ::= {er1646v2EfmVlanEntry 133323008}

er1646v2EfmVlanInbBwActCirActEthCos6 OBJECT-TYPE
   SYNTAX      INTEGER
               {
               unchanged (256)
               }
   MAX-ACCESS  read-write
   STATUS      current
   DESCRIPTION
      "Path: efm.editConf.vlan.inboundBandwidth.action.cirAction.ethernet.cosDepth6

       Possibilities:
               unchanged   (256)"
   ::= {er1646v2EfmVlanEntry 133318144}

er1646v2EfmVlanInbBwActCirActEthDei6 OBJECT-TYPE
   SYNTAX      INTEGER
               {
               unchanged (255),
               clear (0),
               set (1)
               }
   MAX-ACCESS  read-write
   STATUS      current
   DESCRIPTION
      "Path: efm.editConf.vlan.inboundBandwidth.action.cirAction.ethernet.deiDepth6

       Possibilities:
               unchanged   (255)
               clear   (0)
               set   (1)"
   ::= {er1646v2EfmVlanEntry 133323264}

er1646v2EfmVlanInbBwActCirActEthCos7 OBJECT-TYPE
   SYNTAX      INTEGER
               {
               unchanged (256)
               }
   MAX-ACCESS  read-write
   STATUS      current
   DESCRIPTION
      "Path: efm.editConf.vlan.inboundBandwidth.action.cirAction.ethernet.cosDepth7

       Possibilities:
               unchanged   (256)"
   ::= {er1646v2EfmVlanEntry 133318400}

er1646v2EfmVlanInbBwActCirActEthDei7 OBJECT-TYPE
   SYNTAX      INTEGER
               {
               unchanged (255),
               clear (0),
               set (1)
               }
   MAX-ACCESS  read-write
   STATUS      current
   DESCRIPTION
      "Path: efm.editConf.vlan.inboundBandwidth.action.cirAction.ethernet.deiDepth7

       Possibilities:
               unchanged   (255)
               clear   (0)
               set   (1)"
   ::= {er1646v2EfmVlanEntry 133323520}

er1646v2EfmVlanInbBwActCirActEthCos8 OBJECT-TYPE
   SYNTAX      INTEGER
               {
               unchanged (256)
               }
   MAX-ACCESS  read-write
   STATUS      current
   DESCRIPTION
      "Path: efm.editConf.vlan.inboundBandwidth.action.cirAction.ethernet.cosDepth8

       Possibilities:
               unchanged   (256)"
   ::= {er1646v2EfmVlanEntry 133318656}

er1646v2EfmVlanInbBwActCirActEthDei8 OBJECT-TYPE
   SYNTAX      INTEGER
               {
               unchanged (255),
               clear (0),
               set (1)
               }
   MAX-ACCESS  read-write
   STATUS      current
   DESCRIPTION
      "Path: efm.editConf.vlan.inboundBandwidth.action.cirAction.ethernet.deiDepth8

       Possibilities:
               unchanged   (255)
               clear   (0)
               set   (1)"
   ::= {er1646v2EfmVlanEntry 133323776}

er1646v2EfmVlanInbBwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.vlan.inboundBandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EfmVlanEntry 133318912}

er1646v2EfmVlanInbBwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.vlan.inboundBandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EfmVlanEntry 133319168}

er1646v2EfmVlanInbBwActCirActEthDrpLev OBJECT-TYPE
   SYNTAX      INTEGER
               {
               unchanged (0)
               }
   MAX-ACCESS  read-write
   STATUS      current
   DESCRIPTION
      "Path: efm.editConf.vlan.inboundBandwidth.action.cirAction.ethernet.dropLevel

       Possibilities:
               unchanged   (0)"
   ::= {er1646v2EfmVlanEntry 133319424}

er1646v2EfmVlanInbBwActCirActEthDeFlag OBJECT-TYPE
   SYNTAX      INTEGER
               {
               unchanged (255),
               clear (0),
               set (1)
               }
   MAX-ACCESS  read-write
   STATUS      current
   DESCRIPTION
      "Path: efm.editConf.vlan.inboundBandwidth.action.cirAction.ethernet.deFlag

       Possibilities:
               unchanged   (255)
               clear   (0)
               set   (1)"
   ::= {er1646v2EfmVlanEntry 133320192}

er1646v2EfmVlanInbBwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.vlan.inboundBandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EfmVlanEntry 133343488}

er1646v2EfmVlanInbBwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.vlan.inboundBandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EfmVlanEntry 133343744}

er1646v2EfmVlanInbBwActCirActIpDrpLev OBJECT-TYPE
   SYNTAX      INTEGER
               {
               unchanged (0)
               }
   MAX-ACCESS  read-write
   STATUS      current
   DESCRIPTION
      "Path: efm.editConf.vlan.inboundBandwidth.action.cirAction.ip.dropLevel

       Possibilities:
               unchanged   (0)"
   ::= {er1646v2EfmVlanEntry 133344000}

er1646v2EfmVlanInbBwActCirActIpDeFlag OBJECT-TYPE
   SYNTAX      INTEGER
               {
               unchanged (255),
               clear (0),
               set (1)
               }
   MAX-ACCESS  read-write
   STATUS      current
   DESCRIPTION
      "Path: efm.editConf.vlan.inboundBandwidth.action.cirAction.ip.deFlag

       Possibilities:
               unchanged   (255)
               clear   (0)
               set   (1)"
   ::= {er1646v2EfmVlanEntry 133344768}

er1646v2EfmVlanInbBwActEirActNone OBJECT-TYPE
   SYNTAX      OCTET STRING
   MAX-ACCESS  read-write
   STATUS      current
   DESCRIPTION
      "Path: efm.editConf.vlan.inboundBandwidth.action.eirAction.none"
   ::= {er1646v2EfmVlanEntry 133439488}

er1646v2EfmVlanInbBwActEirActEthCos1 OBJECT-TYPE
   SYNTAX      INTEGER
               {
               unchanged (256)
               }
   MAX-ACCESS  read-write
   STATUS      current
   DESCRIPTION
      "Path: efm.editConf.vlan.inboundBandwidth.action.eirAction.ethernet.cosDepth1

       Possibilities:
               unchanged   (256)"
   ::= {er1646v2EfmVlanEntry 133447936}

er1646v2EfmVlanInbBwActEirActEthDei1 OBJECT-TYPE
   SYNTAX      INTEGER
               {
               unchanged (255),
               clear (0),
               set (1)
               }
   MAX-ACCESS  read-write
   STATUS      current
   DESCRIPTION
      "Path: efm.editConf.vlan.inboundBandwidth.action.eirAction.ethernet.deiDepth1

       Possibilities:
               unchanged   (255)
               clear   (0)
               set   (1)"
   ::= {er1646v2EfmVlanEntry 133453056}

er1646v2EfmVlanInbBwActEirActEthCos2 OBJECT-TYPE
   SYNTAX      INTEGER
               {
               unchanged (256)
               }
   MAX-ACCESS  read-write
   STATUS      current
   DESCRIPTION
      "Path: efm.editConf.vlan.inboundBandwidth.action.eirAction.ethernet.cosDepth2

       Possibilities:
               unchanged   (256)"
   ::= {er1646v2EfmVlanEntry 133448192}

er1646v2EfmVlanInbBwActEirActEthDei2 OBJECT-TYPE
   SYNTAX      INTEGER
               {
               unchanged (255),
               clear (0),
               set (1)
               }
   MAX-ACCESS  read-write
   STATUS      current
   DESCRIPTION
      "Path: efm.editConf.vlan.inboundBandwidth.action.eirAction.ethernet.deiDepth2

       Possibilities:
               unchanged   (255)
               clear   (0)
               set   (1)"
   ::= {er1646v2EfmVlanEntry 133453312}

er1646v2EfmVlanInbBwActEirActEthCos3 OBJECT-TYPE
   SYNTAX      INTEGER
               {
               unchanged (256)
               }
   MAX-ACCESS  read-write
   STATUS      current
   DESCRIPTION
      "Path: efm.editConf.vlan.inboundBandwidth.action.eirAction.ethernet.cosDepth3

       Possibilities:
               unchanged   (256)"
   ::= {er1646v2EfmVlanEntry 133448448}

er1646v2EfmVlanInbBwActEirActEthDei3 OBJECT-TYPE
   SYNTAX      INTEGER
               {
               unchanged (255),
               clear (0),
               set (1)
               }
   MAX-ACCESS  read-write
   STATUS      current
   DESCRIPTION
      "Path: efm.editConf.vlan.inboundBandwidth.action.eirAction.ethernet.deiDepth3

       Possibilities:
               unchanged   (255)
               clear   (0)
               set   (1)"
   ::= {er1646v2EfmVlanEntry 133453568}

er1646v2EfmVlanInbBwActEirActEthCos4 OBJECT-TYPE
   SYNTAX      INTEGER
               {
               unchanged (256)
               }
   MAX-ACCESS  read-write
   STATUS      current
   DESCRIPTION
      "Path: efm.editConf.vlan.inboundBandwidth.action.eirAction.ethernet.cosDepth4

       Possibilities:
               unchanged   (256)"
   ::= {er1646v2EfmVlanEntry 133448704}

er1646v2EfmVlanInbBwActEirActEthDei4 OBJECT-TYPE
   SYNTAX      INTEGER
               {
               unchanged (255),
               clear (0),
               set (1)
               }
   MAX-ACCESS  read-write
   STATUS      current
   DESCRIPTION
      "Path: efm.editConf.vlan.inboundBandwidth.action.eirAction.ethernet.deiDepth4

       Possibilities:
               unchanged   (255)
               clear   (0)
               set   (1)"
   ::= {er1646v2EfmVlanEntry 133453824}

er1646v2EfmVlanInbBwActEirActEthCos5 OBJECT-TYPE
   SYNTAX      INTEGER
               {
               unchanged (256)
               }
   MAX-ACCESS  read-write
   STATUS      current
   DESCRIPTION
      "Path: efm.editConf.vlan.inboundBandwidth.action.eirAction.ethernet.cosDepth5

       Possibilities:
               unchanged   (256)"
   ::= {er1646v2EfmVlanEntry 133448960}

er1646v2EfmVlanInbBwActEirActEthDei5 OBJECT-TYPE
   SYNTAX      INTEGER
               {
               unchanged (255),
               clear (0),
               set (1)
               }
   MAX-ACCESS  read-write
   STATUS      current
   DESCRIPTION
      "Path: efm.editConf.vlan.inboundBandwidth.action.eirAction.ethernet.deiDepth5

       Possibilities:
               unchanged   (255)
               clear   (0)
               set   (1)"
   ::= {er1646v2EfmVlanEntry 133454080}

er1646v2EfmVlanInbBwActEirActEthCos6 OBJECT-TYPE
   SYNTAX      INTEGER
               {
               unchanged (256)
               }
   MAX-ACCESS  read-write
   STATUS      current
   DESCRIPTION
      "Path: efm.editConf.vlan.inboundBandwidth.action.eirAction.ethernet.cosDepth6

       Possibilities:
               unchanged   (256)"
   ::= {er1646v2EfmVlanEntry 133449216}

er1646v2EfmVlanInbBwActEirActEthDei6 OBJECT-TYPE
   SYNTAX      INTEGER
               {
               unchanged (255),
               clear (0),
               set (1)
               }
   MAX-ACCESS  read-write
   STATUS      current
   DESCRIPTION
      "Path: efm.editConf.vlan.inboundBandwidth.action.eirAction.ethernet.deiDepth6

       Possibilities:
               unchanged   (255)
               clear   (0)
               set   (1)"
   ::= {er1646v2EfmVlanEntry 133454336}

er1646v2EfmVlanInbBwActEirActEthCos7 OBJECT-TYPE
   SYNTAX      INTEGER
               {
               unchanged (256)
               }
   MAX-ACCESS  read-write
   STATUS      current
   DESCRIPTION
      "Path: efm.editConf.vlan.inboundBandwidth.action.eirAction.ethernet.cosDepth7

       Possibilities:
               unchanged   (256)"
   ::= {er1646v2EfmVlanEntry 133449472}

er1646v2EfmVlanInbBwActEirActEthDei7 OBJECT-TYPE
   SYNTAX      INTEGER
               {
               unchanged (255),
               clear (0),
               set (1)
               }
   MAX-ACCESS  read-write
   STATUS      current
   DESCRIPTION
      "Path: efm.editConf.vlan.inboundBandwidth.action.eirAction.ethernet.deiDepth7

       Possibilities:
               unchanged   (255)
               clear   (0)
               set   (1)"
   ::= {er1646v2EfmVlanEntry 133454592}

er1646v2EfmVlanInbBwActEirActEthCos8 OBJECT-TYPE
   SYNTAX      INTEGER
               {
               unchanged (256)
               }
   MAX-ACCESS  read-write
   STATUS      current
   DESCRIPTION
      "Path: efm.editConf.vlan.inboundBandwidth.action.eirAction.ethernet.cosDepth8

       Possibilities:
               unchanged   (256)"
   ::= {er1646v2EfmVlanEntry 133449728}

er1646v2EfmVlanInbBwActEirActEthDei8 OBJECT-TYPE
   SYNTAX      INTEGER
               {
               unchanged (255),
               clear (0),
               set (1)
               }
   MAX-ACCESS  read-write
   STATUS      current
   DESCRIPTION
      "Path: efm.editConf.vlan.inboundBandwidth.action.eirAction.ethernet.deiDepth8

       Possibilities:
               unchanged   (255)
               clear   (0)
               set   (1)"
   ::= {er1646v2EfmVlanEntry 133454848}

er1646v2EfmVlanInbBwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.vlan.inboundBandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EfmVlanEntry 133449984}

er1646v2EfmVlanInbBwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.vlan.inboundBandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EfmVlanEntry 133450240}

er1646v2EfmVlanInbBwActEirActEthDrpLev OBJECT-TYPE
   SYNTAX      INTEGER
               {
               unchanged (0)
               }
   MAX-ACCESS  read-write
   STATUS      current
   DESCRIPTION
      "Path: efm.editConf.vlan.inboundBandwidth.action.eirAction.ethernet.dropLevel

       Possibilities:
               unchanged   (0)"
   ::= {er1646v2EfmVlanEntry 133450496}

er1646v2EfmVlanInbBwActEirActEthDeFlag OBJECT-TYPE
   SYNTAX      INTEGER
               {
               unchanged (255),
               clear (0),
               set (1)
               }
   MAX-ACCESS  read-write
   STATUS      current
   DESCRIPTION
      "Path: efm.editConf.vlan.inboundBandwidth.action.eirAction.ethernet.deFlag

       Possibilities:
               unchanged   (255)
               clear   (0)
               set   (1)"
   ::= {er1646v2EfmVlanEntry 133451264}

er1646v2EfmVlanInbBwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.vlan.inboundBandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EfmVlanEntry 133474560}

er1646v2EfmVlanInbBwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.vlan.inboundBandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EfmVlanEntry 133474816}

er1646v2EfmVlanInbBwActEirActIpDrpLev OBJECT-TYPE
   SYNTAX      INTEGER
               {
               unchanged (0)
               }
   MAX-ACCESS  read-write
   STATUS      current
   DESCRIPTION
      "Path: efm.editConf.vlan.inboundBandwidth.action.eirAction.ip.dropLevel

       Possibilities:
               unchanged   (0)"
   ::= {er1646v2EfmVlanEntry 133475072}

er1646v2EfmVlanInbBwActEirActIpDeFlag OBJECT-TYPE
   SYNTAX      INTEGER
               {
               unchanged (255),
               clear (0),
               set (1)
               }
   MAX-ACCESS  read-write
   STATUS      current
   DESCRIPTION
      "Path: efm.editConf.vlan.inboundBandwidth.action.eirAction.ip.deFlag

       Possibilities:
               unchanged   (255)
               clear   (0)
               set   (1)"
   ::= {er1646v2EfmVlanEntry 133475840}

er1646v2EfmVlanInbBwActViolActNone OBJECT-TYPE
   SYNTAX      OCTET STRING
   MAX-ACCESS  read-write
   STATUS      current
   DESCRIPTION
      "Path: efm.editConf.vlan.inboundBandwidth.action.violateAction.none"
   ::= {er1646v2EfmVlanEntry 133570560}

er1646v2EfmVlanInbBwActViolActDrop OBJECT-TYPE
   SYNTAX      OCTET STRING
   MAX-ACCESS  read-write
   STATUS      current
   DESCRIPTION
      "Path: efm.editConf.vlan.inboundBandwidth.action.violateAction.drop"
   ::= {er1646v2EfmVlanEntry 133586944}

er1646v2EfmVlanInbBwActViolActEthCos1 OBJECT-TYPE
   SYNTAX      INTEGER
               {
               unchanged (256)
               }
   MAX-ACCESS  read-write
   STATUS      current
   DESCRIPTION
      "Path: efm.editConf.vlan.inboundBandwidth.action.violateAction.ethernet.cosDepth1

       Possibilities:
               unchanged   (256)"
   ::= {er1646v2EfmVlanEntry 133579008}

er1646v2EfmVlanInbBwActViolActEthDei1 OBJECT-TYPE
   SYNTAX      INTEGER
               {
               unchanged (255),
               clear (0),
               set (1)
               }
   MAX-ACCESS  read-write
   STATUS      current
   DESCRIPTION
      "Path: efm.editConf.vlan.inboundBandwidth.action.violateAction.ethernet.deiDepth1

       Possibilities:
               unchanged   (255)
               clear   (0)
               set   (1)"
   ::= {er1646v2EfmVlanEntry 133584128}

er1646v2EfmVlanInbBwActViolActEthCos2 OBJECT-TYPE
   SYNTAX      INTEGER
               {
               unchanged (256)
               }
   MAX-ACCESS  read-write
   STATUS      current
   DESCRIPTION
      "Path: efm.editConf.vlan.inboundBandwidth.action.violateAction.ethernet.cosDepth2

       Possibilities:
               unchanged   (256)"
   ::= {er1646v2EfmVlanEntry 133579264}

er1646v2EfmVlanInbBwActViolActEthDei2 OBJECT-TYPE
   SYNTAX      INTEGER
               {
               unchanged (255),
               clear (0),
               set (1)
               }
   MAX-ACCESS  read-write
   STATUS      current
   DESCRIPTION
      "Path: efm.editConf.vlan.inboundBandwidth.action.violateAction.ethernet.deiDepth2

       Possibilities:
               unchanged   (255)
               clear   (0)
               set   (1)"
   ::= {er1646v2EfmVlanEntry 133584384}

er1646v2EfmVlanInbBwActViolActEthCos3 OBJECT-TYPE
   SYNTAX      INTEGER
               {
               unchanged (256)
               }
   MAX-ACCESS  read-write
   STATUS      current
   DESCRIPTION
      "Path: efm.editConf.vlan.inboundBandwidth.action.violateAction.ethernet.cosDepth3

       Possibilities:
               unchanged   (256)"
   ::= {er1646v2EfmVlanEntry 133579520}

er1646v2EfmVlanInbBwActViolActEthDei3 OBJECT-TYPE
   SYNTAX      INTEGER
               {
               unchanged (255),
               clear (0),
               set (1)
               }
   MAX-ACCESS  read-write
   STATUS      current
   DESCRIPTION
      "Path: efm.editConf.vlan.inboundBandwidth.action.violateAction.ethernet.deiDepth3

       Possibilities:
               unchanged   (255)
               clear   (0)
               set   (1)"
   ::= {er1646v2EfmVlanEntry 133584640}

er1646v2EfmVlanInbBwActViolActEthCos4 OBJECT-TYPE
   SYNTAX      INTEGER
               {
               unchanged (256)
               }
   MAX-ACCESS  read-write
   STATUS      current
   DESCRIPTION
      "Path: efm.editConf.vlan.inboundBandwidth.action.violateAction.ethernet.cosDepth4

       Possibilities:
               unchanged   (256)"
   ::= {er1646v2EfmVlanEntry 133579776}

er1646v2EfmVlanInbBwActViolActEthDei4 OBJECT-TYPE
   SYNTAX      INTEGER
               {
               unchanged (255),
               clear (0),
               set (1)
               }
   MAX-ACCESS  read-write
   STATUS      current
   DESCRIPTION
      "Path: efm.editConf.vlan.inboundBandwidth.action.violateAction.ethernet.deiDepth4

       Possibilities:
               unchanged   (255)
               clear   (0)
               set   (1)"
   ::= {er1646v2EfmVlanEntry 133584896}

er1646v2EfmVlanInbBwActViolActEthCos5 OBJECT-TYPE
   SYNTAX      INTEGER
               {
               unchanged (256)
               }
   MAX-ACCESS  read-write
   STATUS      current
   DESCRIPTION
      "Path: efm.editConf.vlan.inboundBandwidth.action.violateAction.ethernet.cosDepth5

       Possibilities:
               unchanged   (256)"
   ::= {er1646v2EfmVlanEntry 133580032}

er1646v2EfmVlanInbBwActViolActEthDei5 OBJECT-TYPE
   SYNTAX      INTEGER
               {
               unchanged (255),
               clear (0),
               set (1)
               }
   MAX-ACCESS  read-write
   STATUS      current
   DESCRIPTION
      "Path: efm.editConf.vlan.inboundBandwidth.action.violateAction.ethernet.deiDepth5

       Possibilities:
               unchanged   (255)
               clear   (0)
               set   (1)"
   ::= {er1646v2EfmVlanEntry 133585152}

er1646v2EfmVlanInbBwActViolActEthCos6 OBJECT-TYPE
   SYNTAX      INTEGER
               {
               unchanged (256)
               }
   MAX-ACCESS  read-write
   STATUS      current
   DESCRIPTION
      "Path: efm.editConf.vlan.inboundBandwidth.action.violateAction.ethernet.cosDepth6

       Possibilities:
               unchanged   (256)"
   ::= {er1646v2EfmVlanEntry 133580288}

er1646v2EfmVlanInbBwActViolActEthDei6 OBJECT-TYPE
   SYNTAX      INTEGER
               {
               unchanged (255),
               clear (0),
               set (1)
               }
   MAX-ACCESS  read-write
   STATUS      current
   DESCRIPTION
      "Path: efm.editConf.vlan.inboundBandwidth.action.violateAction.ethernet.deiDepth6

       Possibilities:
               unchanged   (255)
               clear   (0)
               set   (1)"
   ::= {er1646v2EfmVlanEntry 133585408}

er1646v2EfmVlanInbBwActViolActEthCos7 OBJECT-TYPE
   SYNTAX      INTEGER
               {
               unchanged (256)
               }
   MAX-ACCESS  read-write
   STATUS      current
   DESCRIPTION
      "Path: efm.editConf.vlan.inboundBandwidth.action.violateAction.ethernet.cosDepth7

       Possibilities:
               unchanged   (256)"
   ::= {er1646v2EfmVlanEntry 133580544}

er1646v2EfmVlanInbBwActViolActEthDei7 OBJECT-TYPE
   SYNTAX      INTEGER
               {
               unchanged (255),
               clear (0),
               set (1)
               }
   MAX-ACCESS  read-write
   STATUS      current
   DESCRIPTION
      "Path: efm.editConf.vlan.inboundBandwidth.action.violateAction.ethernet.deiDepth7

       Possibilities:
               unchanged   (255)
               clear   (0)
               set   (1)"
   ::= {er1646v2EfmVlanEntry 133585664}

er1646v2EfmVlanInbBwActViolActEthCos8 OBJECT-TYPE
   SYNTAX      INTEGER
               {
               unchanged (256)
               }
   MAX-ACCESS  read-write
   STATUS      current
   DESCRIPTION
      "Path: efm.editConf.vlan.inboundBandwidth.action.violateAction.ethernet.cosDepth8

       Possibilities:
               unchanged   (256)"
   ::= {er1646v2EfmVlanEntry 133580800}

er1646v2EfmVlanInbBwActViolActEthDei8 OBJECT-TYPE
   SYNTAX      INTEGER
               {
               unchanged (255),
               clear (0),
               set (1)
               }
   MAX-ACCESS  read-write
   STATUS      current
   DESCRIPTION
      "Path: efm.editConf.vlan.inboundBandwidth.action.violateAction.ethernet.deiDepth8

       Possibilities:
               unchanged   (255)
               clear   (0)
               set   (1)"
   ::= {er1646v2EfmVlanEntry 133585920}

er1646v2EfmVlanInbBwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.vlan.inboundBandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EfmVlanEntry 133581056}

er1646v2EfmVlanInbBwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.vlan.inboundBandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EfmVlanEntry 133581312}

er1646v2EfmVlanInbBwActViolActEthDrpLev OBJECT-TYPE
   SYNTAX      INTEGER
               {
               unchanged (0)
               }
   MAX-ACCESS  read-write
   STATUS      current
   DESCRIPTION
      "Path: efm.editConf.vlan.inboundBandwidth.action.violateAction.ethernet.dropLevel

       Possibilities:
               unchanged   (0)"
   ::= {er1646v2EfmVlanEntry 133581568}

er1646v2EfmVlanInbBwActViolActEthDeFlag OBJECT-TYPE
   SYNTAX      INTEGER
               {
               unchanged (255),
               clear (0),
               set (1)
               }
   MAX-ACCESS  read-write
   STATUS      current
   DESCRIPTION
      "Path: efm.editConf.vlan.inboundBandwidth.action.violateAction.ethernet.deFlag

       Possibilities:
               unchanged   (255)
               clear   (0)
               set   (1)"
   ::= {er1646v2EfmVlanEntry 133582336}

er1646v2EfmVlanInbBwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.vlan.inboundBandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EfmVlanEntry 133605632}

er1646v2EfmVlanInbBwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.vlan.inboundBandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EfmVlanEntry 133605888}

er1646v2EfmVlanInbBwActViolActIpDrpLev OBJECT-TYPE
   SYNTAX      INTEGER
               {
               unchanged (0)
               }
   MAX-ACCESS  read-write
   STATUS      current
   DESCRIPTION
      "Path: efm.editConf.vlan.inboundBandwidth.action.violateAction.ip.dropLevel

       Possibilities:
               unchanged   (0)"
   ::= {er1646v2EfmVlanEntry 133606144}

er1646v2EfmVlanInbBwActViolActIpDeFlag OBJECT-TYPE
   SYNTAX      INTEGER
               {
               unchanged (255),
               clear (0),
               set (1)
               }
   MAX-ACCESS  read-write
   STATUS      current
   DESCRIPTION
      "Path: efm.editConf.vlan.inboundBandwidth.action.violateAction.ip.deFlag

       Possibilities:
               unchanged   (255)
               clear   (0)
               set   (1)"
   ::= {er1646v2EfmVlanEntry 133606912}

er1646v2EfmVlanPppoE OBJECT-TYPE
   SYNTAX      INTEGER
               {
               disabled (0),
               enabled (1)
               }
   MAX-ACCESS  read-write
   STATUS      current
   DESCRIPTION
      "Path: efm.editConf.vlan.pppoE

       Possibilities:
               disabled   (0)
               enabled   (1)"
   ::= {er1646v2EfmVlanEntry 838860800}

er1646v2EfmVlanPppLnkMOperation OBJECT-TYPE
   SYNTAX      INTEGER
               {
               disabled (0),
               enabled (1)
               }
   MAX-ACCESS  read-write
   STATUS      current
   DESCRIPTION
      "Path: efm.editConf.vlan.ppp.linkMonitoring.operation

       Possibilities:
               disabled   (0)
               enabled   (1)"
   ::= {er1646v2EfmVlanEntry 251724032}

er1646v2EfmVlanPppLnkMInterval OBJECT-TYPE
   SYNTAX      TimeTicks
   MAX-ACCESS  read-write
   STATUS      current
   DESCRIPTION
      "Path: efm.editConf.vlan.ppp.linkMonitoring.interval

       Time in centi-second."
   ::= {er1646v2EfmVlanEntry 251724288}

er1646v2EfmVlanPppLnkMRepTimeOut OBJECT-TYPE
   SYNTAX      TimeTicks
   MAX-ACCESS  read-write
   STATUS      current
   DESCRIPTION
      "Path: efm.editConf.vlan.ppp.linkMonitoring.replyTimeOut

       Time in centi-second."
   ::= {er1646v2EfmVlanEntry 251724544}

er1646v2EfmVlanPppLnkMFailsPrmt OBJECT-TYPE
   SYNTAX      Integer32
   MAX-ACCESS  read-write
   STATUS      current
   DESCRIPTION
      "Path: efm.editConf.vlan.ppp.linkMonitoring.failsPermitted"
   ::= {er1646v2EfmVlanEntry 251724800}

er1646v2EfmVlanPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: efm.editConf.vlan.ppp.authentication

       Possibilities:
               disabled   (0)
               chap   (1)
               pap   (2)
               chapOrPap   (3)
               msChap   (4)
               msChapV2   (5)"
   ::= {er1646v2EfmVlanEntry 251789312}

er1646v2EfmVlanPppAuthenPeriod OBJECT-TYPE
   SYNTAX      TimeTicks
   MAX-ACCESS  read-write
   STATUS      current
   DESCRIPTION
      "Path: efm.editConf.vlan.ppp.authenPeriod

       Time in centi-second."
   ::= {er1646v2EfmVlanEntry 251854848}

er1646v2EfmVlanPppSessionName OBJECT-TYPE
   SYNTAX      DisplayString
   MAX-ACCESS  read-write
   STATUS      current
   DESCRIPTION
      "Path: efm.editConf.vlan.ppp.sessionName"
   ::= {er1646v2EfmVlanEntry 251985920}

er1646v2EfmVlanPppSessionSecret OBJECT-TYPE
   SYNTAX      DisplayString
   MAX-ACCESS  read-write
   STATUS      current
   DESCRIPTION
      "Path: efm.editConf.vlan.ppp.sessionSecret"
   ::= {er1646v2EfmVlanEntry 252051456}

er1646v2EfmVlanPppEncModeSessionSecret OBJECT-TYPE
   SYNTAX      INTEGER
               {
               none (1),
               encrypt (2),
               encType1 (3),
               invalid (128)
               }
   MAX-ACCESS  read-write
   STATUS      current
   DESCRIPTION
      "Path: efm.editConf.vlan.ppp.encModeSessionSecret

       Possibilities:
               none   (1)
               encrypt   (2)
               encType1   (3)
               invalid   (128)"
   ::= {er1646v2EfmVlanEntry 252182528}

er1646v2EfmVlanPppEncSessionSecret OBJECT-TYPE
   SYNTAX      DisplayString
   MAX-ACCESS  read-write
   STATUS      current
   DESCRIPTION
      "Path: efm.editConf.vlan.ppp.encSessionSecret"
   ::= {er1646v2EfmVlanEntry 252248064}

er1646v2EfmVlanPppServiceName OBJECT-TYPE
   SYNTAX      DisplayString
   MAX-ACCESS  read-write
   STATUS      current
   DESCRIPTION
      "Path: efm.editConf.vlan.ppp.serviceName"
   ::= {er1646v2EfmVlanEntry 252116992}

er1646v2EfmVlanPbbMode OBJECT-TYPE
   SYNTAX      INTEGER
               {
               disabled (0),
               static (1),
               dynamicPtp (2),
               dynamicPtmp (3)
               }
   MAX-ACCESS  read-write
   STATUS      current
   DESCRIPTION
      "Path: efm.editConf.vlan.pbb.mode

       Possibilities:
               disabled   (0)
               static   (1)
               dynamicPtp   (2)
               dynamicPtmp   (3)"
   ::= {er1646v2EfmVlanEntry 1174667264}

er1646v2EfmVlanPbbTxCos OBJECT-TYPE
   SYNTAX      Integer32
   MAX-ACCESS  read-write
   STATUS      current
   DESCRIPTION
      "Path: efm.editConf.vlan.pbb.txCos"
   ::= {er1646v2EfmVlanEntry 1175191552}

er1646v2EfmVlanPbbIsid OBJECT-TYPE
   SYNTAX      Integer32
   MAX-ACCESS  read-write
   STATUS      current
   DESCRIPTION
      "Path: efm.editConf.vlan.pbb.isid"
   ::= {er1646v2EfmVlanEntry 1175453696}

er1646v2EfmVlanPbbDestMac OBJECT-TYPE
   SYNTAX      OCTET STRING
   MAX-ACCESS  read-write
   STATUS      current
   DESCRIPTION
      "Path: efm.editConf.vlan.pbb.destMac

       MAC address."
   ::= {er1646v2EfmVlanEntry 1175715840}

er1646v2EfmVlanPbbCustomGroupMac OBJECT-TYPE
   SYNTAX      OCTET STRING
   MAX-ACCESS  read-write
   STATUS      current
   DESCRIPTION
      "Path: efm.editConf.vlan.pbb.customGroupMac

       MAC address."
   ::= {er1646v2EfmVlanEntry 1175977984}

er1646v2EfmVlanIpSaddr OBJECT-TYPE
   SYNTAX      SEQUENCE OF Er1646v2EfmVlanIpSaddrEntry
   MAX-ACCESS  not-accessible
   STATUS      current
   DESCRIPTION
      ""
   ::= {er1646v2EfmVlan 51838976}

er1646v2EfmVlanIpSaddrEntry OBJECT-TYPE
   SYNTAX      Er1646v2EfmVlanIpSaddrEntry
   MAX-ACCESS  not-accessible
   STATUS      current
   DESCRIPTION
      ""
   INDEX      { er1646v2EfmVlanTableIx,
                er1646v2EfmVlanIpSaddrTableIx }
   ::= {er1646v2EfmVlanIpSaddr 1}

Er1646v2EfmVlanIpSaddrEntry ::=
   SEQUENCE
      {
      er1646v2EfmVlanIpSaddrActions
         VariableLengthTableActions,
      er1646v2EfmVlanIpSaddrTableIx
         TableIndex,
      er1646v2EfmVlanIpSaddrAddress
         IpAddress,
      er1646v2EfmVlanIpSaddrNetMask
         IpAddress
      }

er1646v2EfmVlanIpSaddrActions OBJECT-TYPE
   SYNTAX      VariableLengthTableActions
   MAX-ACCESS  read-write
   STATUS      current
   DESCRIPTION
      "By way of this field, some manipulations
       on this table may be performed."
   ::= {er1646v2EfmVlanIpSaddrEntry 2}

er1646v2EfmVlanIpSaddrTableIx OBJECT-TYPE
   SYNTAX      TableIndex
   MAX-ACCESS  not-accessible
   STATUS      current
   DESCRIPTION
      ""
   ::= {er1646v2EfmVlanIpSaddrEntry 11}

er1646v2EfmVlanIpSaddrAddress OBJECT-TYPE
   SYNTAX      IpAddress
   MAX-ACCESS  read-write
   STATUS      current
   DESCRIPTION
      "Path: efm.editConf.vlan.ip.secondaryIp.address"
   ::= {er1646v2EfmVlanIpSaddrEntry 2030043136}

er1646v2EfmVlanIpSaddrNetMask OBJECT-TYPE
   SYNTAX      IpAddress
   MAX-ACCESS  read-write
   STATUS      current
   DESCRIPTION
      "Path: efm.editConf.vlan.ip.secondaryIp.netMask"
   ::= {er1646v2EfmVlanIpSaddrEntry 2063597568}

er1646v2EfmVlanIpH OBJECT-TYPE
   SYNTAX      SEQUENCE OF Er1646v2EfmVlanIpHEntry
   MAX-ACCESS  not-accessible
   STATUS      current
   DESCRIPTION
      ""
   ::= {er1646v2EfmVlan 51314688}

er1646v2EfmVlanIpHEntry OBJECT-TYPE
   SYNTAX      Er1646v2EfmVlanIpHEntry
   MAX-ACCESS  not-accessible
   STATUS      current
   DESCRIPTION
      ""
   INDEX      { er1646v2EfmVlanTableIx,
                er1646v2EfmVlanIpHTableIx }
   ::= {er1646v2EfmVlanIpH 1}

Er1646v2EfmVlanIpHEntry ::=
   SEQUENCE
      {
      er1646v2EfmVlanIpHActions
         VariableLengthTableActions,
      er1646v2EfmVlanIpHTableIx
         TableIndex,
      er1646v2EfmVlanIpHAddress
         IpAddress,
      er1646v2EfmVlanIpHDhcpRelayOptionSubscriberId
         DisplayString
      }

er1646v2EfmVlanIpHActions OBJECT-TYPE
   SYNTAX      VariableLengthTableActions
   MAX-ACCESS  read-write
   STATUS      current
   DESCRIPTION
      "By way of this field, some manipulations
       on this table may be performed."
   ::= {er1646v2EfmVlanIpHEntry 2}

er1646v2EfmVlanIpHTableIx OBJECT-TYPE
   SYNTAX      TableIndex
   MAX-ACCESS  not-accessible
   STATUS      current
   DESCRIPTION
      ""
   ::= {er1646v2EfmVlanIpHEntry 11}

er1646v2EfmVlanIpHAddress OBJECT-TYPE
   SYNTAX      IpAddress
   MAX-ACCESS  read-write
   STATUS      current
   DESCRIPTION
      "Path: efm.editConf.vlan.ip.helpers.address"
   ::= {er1646v2EfmVlanIpHEntry 16777216}

er1646v2EfmVlanIpHDhcpRelayOptionSubscriberId OBJECT-TYPE
   SYNTAX      DisplayString
   MAX-ACCESS  read-write
   STATUS      current
   DESCRIPTION
      "Path: efm.editConf.vlan.ip.helpers.dhcpRelayOption.subscriberId"
   ::= {er1646v2EfmVlanIpHEntry 33947648}

er1646v2EfmVlanIpV6Addresses OBJECT-TYPE
   SYNTAX      SEQUENCE OF Er1646v2EfmVlanIpV6AddressesEntry
   MAX-ACCESS  not-accessible
   STATUS      current
   DESCRIPTION
      ""
   ::= {er1646v2EfmVlan 704839680}

er1646v2EfmVlanIpV6AddressesEntry OBJECT-TYPE
   SYNTAX      Er1646v2EfmVlanIpV6AddressesEntry
   MAX-ACCESS  not-accessible
   STATUS      current
   DESCRIPTION
      ""
   INDEX      { er1646v2EfmVlanTableIx,
                er1646v2EfmVlanIpV6AddressesTableIx }
   ::= {er1646v2EfmVlanIpV6Addresses 1}

Er1646v2EfmVlanIpV6AddressesEntry ::=
   SEQUENCE
      {
      er1646v2EfmVlanIpV6AddressesActions
         VariableLengthTableActions,
      er1646v2EfmVlanIpV6AddressesTableIx
         TableIndex,
      er1646v2EfmVlanIpV6AddressesType
         INTEGER,
      er1646v2EfmVlanIpV6AddressesAddress
         Ipv6Address,
      er1646v2EfmVlanIpV6AddressesPrefixLength
         Integer32,
      er1646v2EfmVlanIpV6AddressesGeneralPrefix
         DisplayString,
      er1646v2EfmVlanIpV6AddressesRaSend
         INTEGER,
      er1646v2EfmVlanIpV6AddressesRaOnLinkFlag
         INTEGER,
      er1646v2EfmVlanIpV6AddressesRaAutoFlag
         INTEGER,
      er1646v2EfmVlanIpV6AddressesRaValidLifeTime
         TimeTicks,
      er1646v2EfmVlanIpV6AddressesRaValidLTMode
         INTEGER,
      er1646v2EfmVlanIpV6AddressesRaPrefLifeTime
         TimeTicks,
      er1646v2EfmVlanIpV6AddressesRaPrefLTMode
         INTEGER
      }

er1646v2EfmVlanIpV6AddressesActions OBJECT-TYPE
   SYNTAX      VariableLengthTableActions
   MAX-ACCESS  read-write
   STATUS      current
   DESCRIPTION
      "By way of this field, some manipulations
       on this table may be performed."
   ::= {er1646v2EfmVlanIpV6AddressesEntry 2}

er1646v2EfmVlanIpV6AddressesTableIx OBJECT-TYPE
   SYNTAX      TableIndex
   MAX-ACCESS  not-accessible
   STATUS      current
   DESCRIPTION
      ""
   ::= {er1646v2EfmVlanIpV6AddressesEntry 11}

er1646v2EfmVlanIpV6AddressesType OBJECT-TYPE
   SYNTAX      INTEGER
               {
               unicast (0),
               eui64 (1),
               anycast (2),
               linkLocal (3),
               generalPrefix (4)
               }
   MAX-ACCESS  read-write
   STATUS      current
   DESCRIPTION
      "Path: efm.editConf.vlan.ipV6.addresses.type

       Possibilities:
               unicast   (0)
               eui64   (1)
               anycast   (2)
               linkLocal   (3)
               generalPrefix   (4)"
   ::= {er1646v2EfmVlanIpV6AddressesEntry 50331648}

er1646v2EfmVlanIpV6AddressesAddress OBJECT-TYPE
   SYNTAX      Ipv6Address
   MAX-ACCESS  read-write
   STATUS      current
   DESCRIPTION
      "Path: efm.editConf.vlan.ipV6.addresses.address

       ipv6 address"
   ::= {er1646v2EfmVlanIpV6AddressesEntry 16777216}

er1646v2EfmVlanIpV6AddressesPrefixLength OBJECT-TYPE
   SYNTAX      Integer32
   MAX-ACCESS  read-write
   STATUS      current
   DESCRIPTION
      "Path: efm.editConf.vlan.ipV6.addresses.prefixLength"
   ::= {er1646v2EfmVlanIpV6AddressesEntry 33554432}

er1646v2EfmVlanIpV6AddressesGeneralPrefix OBJECT-TYPE
   SYNTAX      DisplayString
   MAX-ACCESS  read-write
   STATUS      current
   DESCRIPTION
      "Path: efm.editConf.vlan.ipV6.addresses.generalPrefix"
   ::= {er1646v2EfmVlanIpV6AddressesEntry 83886080}

er1646v2EfmVlanIpV6AddressesRaSend OBJECT-TYPE
   SYNTAX      INTEGER
               {
               disabled (0),
               enabled (1)
               }
   MAX-ACCESS  read-write
   STATUS      current
   DESCRIPTION
      "Path: efm.editConf.vlan.ipV6.addresses.ra.send

       Possibilities:
               disabled   (0)
               enabled   (1)"
   ::= {er1646v2EfmVlanIpV6AddressesEntry 67174400}

er1646v2EfmVlanIpV6AddressesRaOnLinkFlag OBJECT-TYPE
   SYNTAX      INTEGER
               {
               disabled (0),
               enabled (1)
               }
   MAX-ACCESS  read-write
   STATUS      current
   DESCRIPTION
      "Path: efm.editConf.vlan.ipV6.addresses.ra.onLinkFlag

       Possibilities:
               disabled   (0)
               enabled   (1)"
   ::= {er1646v2EfmVlanIpV6AddressesEntry 67371008}

er1646v2EfmVlanIpV6AddressesRaAutoFlag OBJECT-TYPE
   SYNTAX      INTEGER
               {
               disabled (0),
               enabled (1)
               }
   MAX-ACCESS  read-write
   STATUS      current
   DESCRIPTION
      "Path: efm.editConf.vlan.ipV6.addresses.ra.autonomousFlag

       Possibilities:
               disabled   (0)
               enabled   (1)"
   ::= {er1646v2EfmVlanIpV6AddressesEntry 67567616}

er1646v2EfmVlanIpV6AddressesRaValidLifeTime OBJECT-TYPE
   SYNTAX      TimeTicks
   MAX-ACCESS  read-write
   STATUS      current
   DESCRIPTION
      "Path: efm.editConf.vlan.ipV6.addresses.ra.validLifeTime

       Time in centi-second."
   ::= {er1646v2EfmVlanIpV6AddressesEntry 67239936}

er1646v2EfmVlanIpV6AddressesRaValidLTMode OBJECT-TYPE
   SYNTAX      INTEGER
               {
               fixed (0),
               infinite (2)
               }
   MAX-ACCESS  read-write
   STATUS      current
   DESCRIPTION
      "Path: efm.editConf.vlan.ipV6.addresses.ra.validLifeTimeMode

       Possibilities:
               fixed   (0)
               infinite   (2)"
   ::= {er1646v2EfmVlanIpV6AddressesEntry 67305472}

er1646v2EfmVlanIpV6AddressesRaPrefLifeTime OBJECT-TYPE
   SYNTAX      TimeTicks
   MAX-ACCESS  read-write
   STATUS      current
   DESCRIPTION
      "Path: efm.editConf.vlan.ipV6.addresses.ra.prefLifeTime

       Time in centi-second."
   ::= {er1646v2EfmVlanIpV6AddressesEntry 67436544}

er1646v2EfmVlanIpV6AddressesRaPrefLTMode OBJECT-TYPE
   SYNTAX      INTEGER
               {
               fixed (0),
               infinite (2)
               }
   MAX-ACCESS  read-write
   STATUS      current
   DESCRIPTION
      "Path: efm.editConf.vlan.ipV6.addresses.ra.prefLifeTimeMode

       Possibilities:
               fixed   (0)
               infinite   (2)"
   ::= {er1646v2EfmVlanIpV6AddressesEntry 67502080}

er1646v2EfmVlanIpV6RaDnsOptionsRdnssServers OBJECT-TYPE
   SYNTAX      SEQUENCE OF Er1646v2EfmVlanIpV6RaDnsOptionsRdnssServersEntry
   MAX-ACCESS  not-accessible
   STATUS      current
   DESCRIPTION
      ""
   ::= {er1646v2EfmVlan 705039144}

er1646v2EfmVlanIpV6RaDnsOptionsRdnssServersEntry OBJECT-TYPE
   SYNTAX      Er1646v2EfmVlanIpV6RaDnsOptionsRdnssServersEntry
   MAX-ACCESS  not-accessible
   STATUS      current
   DESCRIPTION
      ""
   INDEX      { er1646v2EfmVlanTableIx,
                er1646v2EfmVlanIpV6RaDnsOptionsRdnssServersTableIx }
   ::= {er1646v2EfmVlanIpV6RaDnsOptionsRdnssServers 1}

Er1646v2EfmVlanIpV6RaDnsOptionsRdnssServersEntry ::=
   SEQUENCE
      {
      er1646v2EfmVlanIpV6RaDnsOptionsRdnssServersActions
         VariableLengthTableActions,
      er1646v2EfmVlanIpV6RaDnsOptionsRdnssServersTableIx
         TableIndex,
      er1646v2EfmVlanIpV6RaDnsOptionsRdnssServersAddress
         Ipv6Address
      }

er1646v2EfmVlanIpV6RaDnsOptionsRdnssServersActions OBJECT-TYPE
   SYNTAX      VariableLengthTableActions
   MAX-ACCESS  read-write
   STATUS      current
   DESCRIPTION
      "By way of this field, some manipulations
       on this table may be performed."
   ::= {er1646v2EfmVlanIpV6RaDnsOptionsRdnssServersEntry 2}

er1646v2EfmVlanIpV6RaDnsOptionsRdnssServersTableIx OBJECT-TYPE
   SYNTAX      TableIndex
   MAX-ACCESS  not-accessible
   STATUS      current
   DESCRIPTION
      ""
   ::= {er1646v2EfmVlanIpV6RaDnsOptionsRdnssServersEntry 11}

er1646v2EfmVlanIpV6RaDnsOptionsRdnssServersAddress OBJECT-TYPE
   SYNTAX      Ipv6Address
   MAX-ACCESS  read-write
   STATUS      current
   DESCRIPTION
      "Path: efm.editConf.vlan.ipV6.ra.dnsOptions.rdnss.servers.address

       ipv6 address"
   ::= {er1646v2EfmVlanIpV6RaDnsOptionsRdnssServersEntry 16777216}

er1646v2EfmVlanIpV6RaDnsOptionsDnsslDomains OBJECT-TYPE
   SYNTAX      SEQUENCE OF Er1646v2EfmVlanIpV6RaDnsOptionsDnsslDomainsEntry
   MAX-ACCESS  not-accessible
   STATUS      current
   DESCRIPTION
      ""
   ::= {er1646v2EfmVlan 705039176}

er1646v2EfmVlanIpV6RaDnsOptionsDnsslDomainsEntry OBJECT-TYPE
   SYNTAX      Er1646v2EfmVlanIpV6RaDnsOptionsDnsslDomainsEntry
   MAX-ACCESS  not-accessible
   STATUS      current
   DESCRIPTION
      ""
   INDEX      { er1646v2EfmVlanTableIx,
                er1646v2EfmVlanIpV6RaDnsOptionsDnsslDomainsTableIx }
   ::= {er1646v2EfmVlanIpV6RaDnsOptionsDnsslDomains 1}

Er1646v2EfmVlanIpV6RaDnsOptionsDnsslDomainsEntry ::=
   SEQUENCE
      {
      er1646v2EfmVlanIpV6RaDnsOptionsDnsslDomainsActions
         VariableLengthTableActions,
      er1646v2EfmVlanIpV6RaDnsOptionsDnsslDomainsTableIx
         TableIndex,
      er1646v2EfmVlanIpV6RaDnsOptionsDnsslDomainsName
         DisplayString
      }

er1646v2EfmVlanIpV6RaDnsOptionsDnsslDomainsActions OBJECT-TYPE
   SYNTAX      VariableLengthTableActions
   MAX-ACCESS  read-write
   STATUS      current
   DESCRIPTION
      "By way of this field, some manipulations
       on this table may be performed."
   ::= {er1646v2EfmVlanIpV6RaDnsOptionsDnsslDomainsEntry 2}

er1646v2EfmVlanIpV6RaDnsOptionsDnsslDomainsTableIx OBJECT-TYPE
   SYNTAX      TableIndex
   MAX-ACCESS  not-accessible
   STATUS      current
   DESCRIPTION
      ""
   ::= {er1646v2EfmVlanIpV6RaDnsOptionsDnsslDomainsEntry 11}

er1646v2EfmVlanIpV6RaDnsOptionsDnsslDomainsName OBJECT-TYPE
   SYNTAX      DisplayString
   MAX-ACCESS  read-write
   STATUS      current
   DESCRIPTION
      "Path: efm.editConf.vlan.ipV6.ra.dnsOptions.dnssl.domains.name"
   ::= {er1646v2EfmVlanIpV6RaDnsOptionsDnsslDomainsEntry 16777216}

er1646v2EfmVlanIpV6DhcpClientUserClassOpt OBJECT-TYPE
   SYNTAX      SEQUENCE OF Er1646v2EfmVlanIpV6DhcpClientUserClassOptEntry
   MAX-ACCESS  not-accessible
   STATUS      current
   DESCRIPTION
      ""
   ::= {er1646v2EfmVlan 705312768}

er1646v2EfmVlanIpV6DhcpClientUserClassOptEntry OBJECT-TYPE
   SYNTAX      Er1646v2EfmVlanIpV6DhcpClientUserClassOptEntry
   MAX-ACCESS  not-accessible
   STATUS      current
   DESCRIPTION
      ""
   INDEX      { er1646v2EfmVlanTableIx,
                er1646v2EfmVlanIpV6DhcpClientUserClassOptTableIx }
   ::= {er1646v2EfmVlanIpV6DhcpClientUserClassOpt 1}

Er1646v2EfmVlanIpV6DhcpClientUserClassOptEntry ::=
   SEQUENCE
      {
      er1646v2EfmVlanIpV6DhcpClientUserClassOptActions
         VariableLengthTableActions,
      er1646v2EfmVlanIpV6DhcpClientUserClassOptTableIx
         TableIndex,
      er1646v2EfmVlanIpV6DhcpClientUserClassOptValueAscii
         DisplayString,
      er1646v2EfmVlanIpV6DhcpClientUserClassOptValueDecimal
         Integer32,
      er1646v2EfmVlanIpV6DhcpClientUserClassOptValueHexData
         OCTET STRING
      }

er1646v2EfmVlanIpV6DhcpClientUserClassOptActions OBJECT-TYPE
   SYNTAX      VariableLengthTableActions
   MAX-ACCESS  read-write
   STATUS      current
   DESCRIPTION
      "By way of this field, some manipulations
       on this table may be performed."
   ::= {er1646v2EfmVlanIpV6DhcpClientUserClassOptEntry 2}

er1646v2EfmVlanIpV6DhcpClientUserClassOptTableIx OBJECT-TYPE
   SYNTAX      TableIndex
   MAX-ACCESS  not-accessible
   STATUS      current
   DESCRIPTION
      ""
   ::= {er1646v2EfmVlanIpV6DhcpClientUserClassOptEntry 11}

er1646v2EfmVlanIpV6DhcpClientUserClassOptValueAscii OBJECT-TYPE
   SYNTAX      DisplayString
   MAX-ACCESS  read-write
   STATUS      current
   DESCRIPTION
      "Path: efm.editConf.vlan.ipV6.dhcp.client.userClassOpt.value.ascii"
   ::= {er1646v2EfmVlanIpV6DhcpClientUserClassOptEntry 16842752}

er1646v2EfmVlanIpV6DhcpClientUserClassOptValueDecimal OBJECT-TYPE
   SYNTAX      Integer32
   MAX-ACCESS  read-write
   STATUS      current
   DESCRIPTION
      "Path: efm.editConf.vlan.ipV6.dhcp.client.userClassOpt.value.decimal"
   ::= {er1646v2EfmVlanIpV6DhcpClientUserClassOptEntry 16908288}

er1646v2EfmVlanIpV6DhcpClientUserClassOptValueHexData OBJECT-TYPE
   SYNTAX      OCTET STRING
   MAX-ACCESS  read-write
   STATUS      current
   DESCRIPTION
      "Path: efm.editConf.vlan.ipV6.dhcp.client.userClassOpt.value.hexData"
   ::= {er1646v2EfmVlanIpV6DhcpClientUserClassOptEntry 16973824}

er1646v2EfmVlanIpV6DhcpClientVendorCl OBJECT-TYPE
   SYNTAX      SEQUENCE OF Er1646v2EfmVlanIpV6DhcpClientVendorClEntry
   MAX-ACCESS  not-accessible
   STATUS      current
   DESCRIPTION
      ""
   ::= {er1646v2EfmVlan 705313792}

er1646v2EfmVlanIpV6DhcpClientVendorClEntry OBJECT-TYPE
   SYNTAX      Er1646v2EfmVlanIpV6DhcpClientVendorClEntry
   MAX-ACCESS  not-accessible
   STATUS      current
   DESCRIPTION
      ""
   INDEX      { er1646v2EfmVlanTableIx,
                er1646v2EfmVlanIpV6DhcpClientVendorClTableIx }
   ::= {er1646v2EfmVlanIpV6DhcpClientVendorCl 1}

Er1646v2EfmVlanIpV6DhcpClientVendorClEntry ::=
   SEQUENCE
      {
      er1646v2EfmVlanIpV6DhcpClientVendorClActions
         VariableLengthTableActions,
      er1646v2EfmVlanIpV6DhcpClientVendorClTableIx
         TableIndex,
      er1646v2EfmVlanIpV6DhcpClientVendorClValueAscii
         DisplayString,
      er1646v2EfmVlanIpV6DhcpClientVendorClValueDecimal
         Integer32,
      er1646v2EfmVlanIpV6DhcpClientVendorClValueHexData
         OCTET STRING
      }

er1646v2EfmVlanIpV6DhcpClientVendorClActions OBJECT-TYPE
   SYNTAX      VariableLengthTableActions
   MAX-ACCESS  read-write
   STATUS      current
   DESCRIPTION
      "By way of this field, some manipulations
       on this table may be performed."
   ::= {er1646v2EfmVlanIpV6DhcpClientVendorClEntry 2}

er1646v2EfmVlanIpV6DhcpClientVendorClTableIx OBJECT-TYPE
   SYNTAX      TableIndex
   MAX-ACCESS  not-accessible
   STATUS      current
   DESCRIPTION
      ""
   ::= {er1646v2EfmVlanIpV6DhcpClientVendorClEntry 11}

er1646v2EfmVlanIpV6DhcpClientVendorClValueAscii OBJECT-TYPE
   SYNTAX      DisplayString
   MAX-ACCESS  read-write
   STATUS      current
   DESCRIPTION
      "Path: efm.editConf.vlan.ipV6.dhcp.client.vendorClassOpt.value.ascii"
   ::= {er1646v2EfmVlanIpV6DhcpClientVendorClEntry 16842752}

er1646v2EfmVlanIpV6DhcpClientVendorClValueDecimal OBJECT-TYPE
   SYNTAX      Integer32
   MAX-ACCESS  read-write
   STATUS      current
   DESCRIPTION
      "Path: efm.editConf.vlan.ipV6.dhcp.client.vendorClassOpt.value.decimal"
   ::= {er1646v2EfmVlanIpV6DhcpClientVendorClEntry 16908288}

er1646v2EfmVlanIpV6DhcpClientVendorClValueHexData OBJECT-TYPE
   SYNTAX      OCTET STRING
   MAX-ACCESS  read-write
   STATUS      current
   DESCRIPTION
      "Path: efm.editConf.vlan.ipV6.dhcp.client.vendorClassOpt.value.hexData"
   ::= {er1646v2EfmVlanIpV6DhcpClientVendorClEntry 16973824}

er1646v2EfmVlanIpV6DhcpRelayDestinations OBJECT-TYPE
   SYNTAX      SEQUENCE OF Er1646v2EfmVlanIpV6DhcpRelayDestinationsEntry
   MAX-ACCESS  not-accessible
   STATUS      current
   DESCRIPTION
      ""
   ::= {er1646v2EfmVlan 705323072}

er1646v2EfmVlanIpV6DhcpRelayDestinationsEntry OBJECT-TYPE
   SYNTAX      Er1646v2EfmVlanIpV6DhcpRelayDestinationsEntry
   MAX-ACCESS  not-accessible
   STATUS      current
   DESCRIPTION
      ""
   INDEX      { er1646v2EfmVlanTableIx,
                er1646v2EfmVlanIpV6DhcpRelayDestinationsTableIx }
   ::= {er1646v2EfmVlanIpV6DhcpRelayDestinations 1}

Er1646v2EfmVlanIpV6DhcpRelayDestinationsEntry ::=
   SEQUENCE
      {
      er1646v2EfmVlanIpV6DhcpRelayDestinationsActions
         VariableLengthTableActions,
      er1646v2EfmVlanIpV6DhcpRelayDestinationsTableIx
         TableIndex,
      er1646v2EfmVlanIpV6DhcpRelayDestinationsAddress
         Ipv6Address,
      er1646v2EfmVlanIpV6DhcpRelayDestinationsInterface
         DisplayString
      }

er1646v2EfmVlanIpV6DhcpRelayDestinationsActions OBJECT-TYPE
   SYNTAX      VariableLengthTableActions
   MAX-ACCESS  read-write
   STATUS      current
   DESCRIPTION
      "By way of this field, some manipulations
       on this table may be performed."
   ::= {er1646v2EfmVlanIpV6DhcpRelayDestinationsEntry 2}

er1646v2EfmVlanIpV6DhcpRelayDestinationsTableIx OBJECT-TYPE
   SYNTAX      TableIndex
   MAX-ACCESS  not-accessible
   STATUS      current
   DESCRIPTION
      ""
   ::= {er1646v2EfmVlanIpV6DhcpRelayDestinationsEntry 11}

er1646v2EfmVlanIpV6DhcpRelayDestinationsAddress OBJECT-TYPE
   SYNTAX      Ipv6Address
   MAX-ACCESS  read-write
   STATUS      current
   DESCRIPTION
      "Path: efm.editConf.vlan.ipV6.dhcp.relay.destinations.address

       ipv6 address"
   ::= {er1646v2EfmVlanIpV6DhcpRelayDestinationsEntry 16777216}

er1646v2EfmVlanIpV6DhcpRelayDestinationsInterface OBJECT-TYPE
   SYNTAX      DisplayString
   MAX-ACCESS  read-write
   STATUS      current
   DESCRIPTION
      "Path: efm.editConf.vlan.ipV6.dhcp.relay.destinations.interface"
   ::= {er1646v2EfmVlanIpV6DhcpRelayDestinationsEntry 33554432}

er1646v2EfmVlanBridgingVlTVlans OBJECT-TYPE
   SYNTAX      SEQUENCE OF Er1646v2EfmVlanBridgingVlTVlansEntry
   MAX-ACCESS  not-accessible
   STATUS      current
   DESCRIPTION
      ""
   ::= {er1646v2EfmVlan 459079680}

er1646v2EfmVlanBridgingVlTVlansEntry OBJECT-TYPE
   SYNTAX      Er1646v2EfmVlanBridgingVlTVlansEntry
   MAX-ACCESS  not-accessible
   STATUS      current
   DESCRIPTION
      ""
   INDEX      { er1646v2EfmVlanTableIx,
                er1646v2EfmVlanBridgingVlTVlansTableIx }
   ::= {er1646v2EfmVlanBridgingVlTVlans 1}

Er1646v2EfmVlanBridgingVlTVlansEntry ::=
   SEQUENCE
      {
      er1646v2EfmVlanBridgingVlTVlansActions
         VariableLengthTableActions,
      er1646v2EfmVlanBridgingVlTVlansTableIx
         TableIndex,
      er1646v2EfmVlanBridgingVlTVlansVid
         Integer32,
      er1646v2EfmVlanBridgingVlTVlansEndVid
         Integer32,
      er1646v2EfmVlanBridgingVlTVlansAction
         INTEGER,
      er1646v2EfmVlanBridgingVlTVlansTagInfoTpid
         INTEGER,
      er1646v2EfmVlanBridgingVlTVlansTagInfoVid
         Integer32
      }

er1646v2EfmVlanBridgingVlTVlansActions OBJECT-TYPE
   SYNTAX      VariableLengthTableActions
   MAX-ACCESS  read-write
   STATUS      current
   DESCRIPTION
      "By way of this field, some manipulations
       on this table may be performed."
   ::= {er1646v2EfmVlanBridgingVlTVlansEntry 2}

er1646v2EfmVlanBridgingVlTVlansTableIx OBJECT-TYPE
   SYNTAX      TableIndex
   MAX-ACCESS  not-accessible
   STATUS      current
   DESCRIPTION
      ""
   ::= {er1646v2EfmVlanBridgingVlTVlansEntry 11}

er1646v2EfmVlanBridgingVlTVlansVid OBJECT-TYPE
   SYNTAX      Integer32
   MAX-ACCESS  read-write
   STATUS      current
   DESCRIPTION
      "Path: efm.editConf.vlan.bridging.vlanTagging.vlans.vid"
   ::= {er1646v2EfmVlanBridgingVlTVlansEntry 536870912}

er1646v2EfmVlanBridgingVlTVlansEndVid OBJECT-TYPE
   SYNTAX      Integer32
   MAX-ACCESS  read-write
   STATUS      current
   DESCRIPTION
      "Path: efm.editConf.vlan.bridging.vlanTagging.vlans.endVid"
   ::= {er1646v2EfmVlanBridgingVlTVlansEntry 2147483648}

er1646v2EfmVlanBridgingVlTVlansAction OBJECT-TYPE
   SYNTAX      INTEGER
               {
               discard (0),
               accept (1),
               tag (2)
               }
   MAX-ACCESS  read-write
   STATUS      current
   DESCRIPTION
      "Path: efm.editConf.vlan.bridging.vlanTagging.vlans.action

       Possibilities:
               discard   (0)
               accept   (1)
               tag   (2)"
   ::= {er1646v2EfmVlanBridgingVlTVlansEntry 1073741824}

er1646v2EfmVlanBridgingVlTVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: efm.editConf.vlan.bridging.vlanTagging.vlans.tagInfo.tpid

       Possibilities:
               dot1Q   (33024)
               dot1ad   (34984)
               0x9100   (37120)
               0x9200   (37376)
               0x9300   (37632)"
   ::= {er1646v2EfmVlanBridgingVlTVlansEntry 1677721600}

er1646v2EfmVlanBridgingVlTVlansTagInfoVid OBJECT-TYPE
   SYNTAX      Integer32
   MAX-ACCESS  read-write
   STATUS      current
   DESCRIPTION
      "Path: efm.editConf.vlan.bridging.vlanTagging.vlans.tagInfo.vid"
   ::= {er1646v2EfmVlanBridgingVlTVlansEntry 1744830464}

er1646v2EfmVlanVlanVidExtensionTable OBJECT-TYPE
   SYNTAX      SEQUENCE OF Er1646v2EfmVlanVlanVidExtensionTableEntry
   MAX-ACCESS  not-accessible
   STATUS      current
   DESCRIPTION
      ""
   ::= {er1646v2EfmVlan 235340544}

er1646v2EfmVlanVlanVidExtensionTableEntry OBJECT-TYPE
   SYNTAX      Er1646v2EfmVlanVlanVidExtensionTableEntry
   MAX-ACCESS  not-accessible
   STATUS      current
   DESCRIPTION
      ""
   INDEX      { er1646v2EfmVlanTableIx,
                er1646v2EfmVlanVlanVidExtensionTableTableIx }
   ::= {er1646v2EfmVlanVlanVidExtensionTable 1}

Er1646v2EfmVlanVlanVidExtensionTableEntry ::=
   SEQUENCE
      {
      er1646v2EfmVlanVlanVidExtensionTableActions
         VariableLengthTableActions,
      er1646v2EfmVlanVlanVidExtensionTableTableIx
         TableIndex,
      er1646v2EfmVlanVlanVidExtensionTableTpid
         INTEGER,
      er1646v2EfmVlanVlanVidExtensionTableVid
         Integer32,
      er1646v2EfmVlanVlanVidExtensionTableEndVid
         Integer32
      }

er1646v2EfmVlanVlanVidExtensionTableActions OBJECT-TYPE
   SYNTAX      VariableLengthTableActions
   MAX-ACCESS  read-write
   STATUS      current
   DESCRIPTION
      "By way of this field, some manipulations
       on this table may be performed."
   ::= {er1646v2EfmVlanVlanVidExtensionTableEntry 2}

er1646v2EfmVlanVlanVidExtensionTableTableIx OBJECT-TYPE
   SYNTAX      TableIndex
   MAX-ACCESS  not-accessible
   STATUS      current
   DESCRIPTION
      ""
   ::= {er1646v2EfmVlanVlanVidExtensionTableEntry 11}

er1646v2EfmVlanVlanVidExtensionTableTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: efm.editConf.vlan.vlan.vidExtension.table.tpid

       Possibilities:
               dot1Q   (33024)
               dot1ad   (34984)
               0x9100   (37120)
               0x9200   (37376)
               0x9300   (37632)"
   ::= {er1646v2EfmVlanVlanVidExtensionTableEntry 16777216}

er1646v2EfmVlanVlanVidExtensionTableVid OBJECT-TYPE
   SYNTAX      Integer32
   MAX-ACCESS  read-write
   STATUS      current
   DESCRIPTION
      "Path: efm.editConf.vlan.vlan.vidExtension.table.vid"
   ::= {er1646v2EfmVlanVlanVidExtensionTableEntry 33554432}

er1646v2EfmVlanVlanVidExtensionTableEndVid OBJECT-TYPE
   SYNTAX      Integer32
   MAX-ACCESS  read-write
   STATUS      current
   DESCRIPTION
      "Path: efm.editConf.vlan.vlan.vidExtension.table.endVid"
   ::= {er1646v2EfmVlanVlanVidExtensionTableEntry 50331648}

er1646v2EfmVlanVlanCSMap OBJECT-TYPE
   SYNTAX      SEQUENCE OF Er1646v2EfmVlanVlanCSMapEntry
   MAX-ACCESS  not-accessible
   STATUS      current
   DESCRIPTION
      ""
   ::= {er1646v2EfmVlan 235405312}

er1646v2EfmVlanVlanCSMapEntry OBJECT-TYPE
   SYNTAX      Er1646v2EfmVlanVlanCSMapEntry
   MAX-ACCESS  not-accessible
   STATUS      current
   DESCRIPTION
      ""
   INDEX      { er1646v2EfmVlanTableIx,
                er1646v2EfmVlanVlanCSMapTableIx }
   ::= {er1646v2EfmVlanVlanCSMap 1}

Er1646v2EfmVlanVlanCSMapEntry ::=
   SEQUENCE
      {
      er1646v2EfmVlanVlanCSMapActions
         VariableLengthTableActions,
      er1646v2EfmVlanVlanCSMapTableIx
         TableIndex,
      er1646v2EfmVlanVlanCSMapCos
         INTEGER,
      er1646v2EfmVlanVlanCSMapDei
         INTEGER,
      er1646v2EfmVlanVlanCSMapTos
         INTEGER,
      er1646v2EfmVlanVlanCSMapQueue
         INTEGER,
      er1646v2EfmVlanVlanCSMapDropLevel
         INTEGER,
      er1646v2EfmVlanVlanCSMapDeFlag
         INTEGER
      }

er1646v2EfmVlanVlanCSMapActions OBJECT-TYPE
   SYNTAX      VariableLengthTableActions
   MAX-ACCESS  read-write
   STATUS      current
   DESCRIPTION
      "By way of this field, some manipulations
       on this table may be performed."
   ::= {er1646v2EfmVlanVlanCSMapEntry 2}

er1646v2EfmVlanVlanCSMapTableIx OBJECT-TYPE
   SYNTAX      TableIndex
   MAX-ACCESS  not-accessible
   STATUS      current
   DESCRIPTION
      ""
   ::= {er1646v2EfmVlanVlanCSMapEntry 11}

er1646v2EfmVlanVlanCSMapCos OBJECT-TYPE
   SYNTAX      INTEGER
               {
               any (8)
               }
   MAX-ACCESS  read-write
   STATUS      current
   DESCRIPTION
      "Path: efm.editConf.vlan.vlan.cosMap.cos

       Possibilities:
               any   (8)"
   ::= {er1646v2EfmVlanVlanCSMapEntry 16777216}

er1646v2EfmVlanVlanCSMapDei OBJECT-TYPE
   SYNTAX      INTEGER
               {
               clear (0),
               set (1),
               any (2)
               }
   MAX-ACCESS  read-write
   STATUS      current
   DESCRIPTION
      "Path: efm.editConf.vlan.vlan.cosMap.dei

       Possibilities:
               clear   (0)
               set   (1)
               any   (2)"
   ::= {er1646v2EfmVlanVlanCSMapEntry 33554432}

er1646v2EfmVlanVlanCSMapTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.vlan.vlan.cosMap.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EfmVlanVlanCSMapEntry 50331648}

er1646v2EfmVlanVlanCSMapQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.vlan.vlan.cosMap.queue

       Possibilities:
               unchanged   (-1)
               queue1   (0)
               queue2   (1)
               queue3   (2)
               queue4   (3)
               queue5   (4)
               lowDelayQueue   (5)
               lowDelay2Queue   (6)
               systemQueue   (7)"
   ::= {er1646v2EfmVlanVlanCSMapEntry 67108864}

er1646v2EfmVlanVlanCSMapDropLevel OBJECT-TYPE
   SYNTAX      INTEGER
               {
               unchanged (-1),
               dropOnQueue (0)
               }
   MAX-ACCESS  read-write
   STATUS      current
   DESCRIPTION
      "Path: efm.editConf.vlan.vlan.cosMap.dropLevel

       Possibilities:
               unchanged   (-1)
               dropOnQueue   (0)"
   ::= {er1646v2EfmVlanVlanCSMapEntry 83886080}

er1646v2EfmVlanVlanCSMapDeFlag OBJECT-TYPE
   SYNTAX      INTEGER
               {
               unchanged (255),
               clear (0),
               set (1)
               }
   MAX-ACCESS  read-write
   STATUS      current
   DESCRIPTION
      "Path: efm.editConf.vlan.vlan.cosMap.deFlag

       Possibilities:
               unchanged   (255)
               clear   (0)
               set   (1)"
   ::= {er1646v2EfmVlanVlanCSMapEntry 117440512}

er1646v2EfmVlanVlanTCMap OBJECT-TYPE
   SYNTAX      SEQUENCE OF Er1646v2EfmVlanVlanTCMapEntry
   MAX-ACCESS  not-accessible
   STATUS      current
   DESCRIPTION
      ""
   ::= {er1646v2EfmVlan 241369088}

er1646v2EfmVlanVlanTCMapEntry OBJECT-TYPE
   SYNTAX      Er1646v2EfmVlanVlanTCMapEntry
   MAX-ACCESS  not-accessible
   STATUS      current
   DESCRIPTION
      ""
   INDEX      { er1646v2EfmVlanTableIx,
                er1646v2EfmVlanVlanTCMapTableIx }
   ::= {er1646v2EfmVlanVlanTCMap 1}

Er1646v2EfmVlanVlanTCMapEntry ::=
   SEQUENCE
      {
      er1646v2EfmVlanVlanTCMapActions
         VariableLengthTableActions,
      er1646v2EfmVlanVlanTCMapTableIx
         TableIndex,
      er1646v2EfmVlanVlanTCMapStartTos
         INTEGER,
      er1646v2EfmVlanVlanTCMapEndTos
         INTEGER,
      er1646v2EfmVlanVlanTCMapCos
         INTEGER
      }

er1646v2EfmVlanVlanTCMapActions OBJECT-TYPE
   SYNTAX      VariableLengthTableActions
   MAX-ACCESS  read-write
   STATUS      current
   DESCRIPTION
      "By way of this field, some manipulations
       on this table may be performed."
   ::= {er1646v2EfmVlanVlanTCMapEntry 2}

er1646v2EfmVlanVlanTCMapTableIx OBJECT-TYPE
   SYNTAX      TableIndex
   MAX-ACCESS  not-accessible
   STATUS      current
   DESCRIPTION
      ""
   ::= {er1646v2EfmVlanVlanTCMapEntry 11}

er1646v2EfmVlanVlanTCMapStartTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: efm.editConf.vlan.vlan.tosCosMap.startTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1646v2EfmVlanVlanTCMapEntry 16777216}

er1646v2EfmVlanVlanTCMapEndTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: efm.editConf.vlan.vlan.tosCosMap.endTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1646v2EfmVlanVlanTCMapEntry 33554432}

er1646v2EfmVlanVlanTCMapCos OBJECT-TYPE
   SYNTAX      INTEGER
               {
               queueCosMap (8)
               }
   MAX-ACCESS  read-write
   STATUS      current
   DESCRIPTION
      "Path: efm.editConf.vlan.vlan.tosCosMap.cos

       Possibilities:
               queueCosMap   (8)"
   ::= {er1646v2EfmVlanVlanTCMapEntry 50331648}

er1646v2EfmVlanVlanArpStaticArp OBJECT-TYPE
   SYNTAX      SEQUENCE OF Er1646v2EfmVlanVlanArpStaticArpEntry
   MAX-ACCESS  not-accessible
   STATUS      current
   DESCRIPTION
      ""
   ::= {er1646v2EfmVlan 235275008}

er1646v2EfmVlanVlanArpStaticArpEntry OBJECT-TYPE
   SYNTAX      Er1646v2EfmVlanVlanArpStaticArpEntry
   MAX-ACCESS  not-accessible
   STATUS      current
   DESCRIPTION
      ""
   INDEX      { er1646v2EfmVlanTableIx,
                er1646v2EfmVlanVlanArpStaticArpTableIx }
   ::= {er1646v2EfmVlanVlanArpStaticArp 1}

Er1646v2EfmVlanVlanArpStaticArpEntry ::=
   SEQUENCE
      {
      er1646v2EfmVlanVlanArpStaticArpActions
         VariableLengthTableActions,
      er1646v2EfmVlanVlanArpStaticArpTableIx
         TableIndex,
      er1646v2EfmVlanVlanArpStaticArpMacAddress
         OCTET STRING,
      er1646v2EfmVlanVlanArpStaticArpIpAddress
         IpAddress
      }

er1646v2EfmVlanVlanArpStaticArpActions OBJECT-TYPE
   SYNTAX      VariableLengthTableActions
   MAX-ACCESS  read-write
   STATUS      current
   DESCRIPTION
      "By way of this field, some manipulations
       on this table may be performed."
   ::= {er1646v2EfmVlanVlanArpStaticArpEntry 2}

er1646v2EfmVlanVlanArpStaticArpTableIx OBJECT-TYPE
   SYNTAX      TableIndex
   MAX-ACCESS  not-accessible
   STATUS      current
   DESCRIPTION
      ""
   ::= {er1646v2EfmVlanVlanArpStaticArpEntry 11}

er1646v2EfmVlanVlanArpStaticArpMacAddress OBJECT-TYPE
   SYNTAX      OCTET STRING
   MAX-ACCESS  read-write
   STATUS      current
   DESCRIPTION
      "Path: efm.editConf.vlan.vlan.arp.staticArp.macAddress

       MAC address."
   ::= {er1646v2EfmVlanVlanArpStaticArpEntry 16777216}

er1646v2EfmVlanVlanArpStaticArpIpAddress OBJECT-TYPE
   SYNTAX      IpAddress
   MAX-ACCESS  read-write
   STATUS      current
   DESCRIPTION
      "Path: efm.editConf.vlan.vlan.arp.staticArp.ipAddress"
   ::= {er1646v2EfmVlanVlanArpStaticArpEntry 33554432}


er1646v2EfmPppOE OBJECT IDENTIFIER ::= {er1646v2Efm 35}

er1646v2EfmPppOESSCTable OBJECT-TYPE
   SYNTAX      SEQUENCE OF Er1646v2EfmPppOEEntry
   MAX-ACCESS  not-accessible
   STATUS      current
   DESCRIPTION
      ""
   ::= {er1646v2EfmPppOE 1}

er1646v2EfmPppOEEntry OBJECT-TYPE
   SYNTAX      Er1646v2EfmPppOEEntry
   MAX-ACCESS  not-accessible
   STATUS      current
   DESCRIPTION
      ""
   INDEX      { er1646v2EfmPppOETableIx }
   ::= {er1646v2EfmPppOESSCTable 1}

Er1646v2EfmPppOEEntry ::=
   SEQUENCE
      {
      er1646v2EfmPppOEActions
         VariableLengthTableActions,
      er1646v2EfmPppOETableIx
         TableIndex,
      er1646v2EfmPppOEName
         DisplayString,
      er1646v2EfmPppOERemark
         DisplayString,
      er1646v2EfmPppOEAdminStatus
         INTEGER,
      er1646v2EfmPppOEMode
         INTEGER,
      er1646v2EfmPppOEIpVrfRouter
         DisplayString,
      er1646v2EfmPppOEIpAdr
         IpAddress,
      er1646v2EfmPppOEIpNetm
         IpAddress,
      er1646v2EfmPppOEIpSNetName
         INTEGER,
      er1646v2EfmPppOEIpSNetCust
         DisplayString,
      er1646v2EfmPppOEIpRem
         IpAddress,
      er1646v2EfmPppOEIpUnnumbered
         DisplayString,
      er1646v2EfmPppOEIpGwPref
         Integer32,
      er1646v2EfmPppOEIpRsn
         INTEGER,
      er1646v2EfmPppOEIpMtu
         Integer32,
      er1646v2EfmPppOEIpMssAdjust
         INTEGER,
      er1646v2EfmPppOEIpRipMetric
         Integer32,
      er1646v2EfmPppOEIpRipMetricOut
         Integer32,
      er1646v2EfmPppOEIpRipMode
         INTEGER,
      er1646v2EfmPppOEIpRipTxVer
         INTEGER,
      er1646v2EfmPppOEIpRipRxVer
         INTEGER,
      er1646v2EfmPppOEIpRipSplitH
         INTEGER,
      er1646v2EfmPppOEIpRipAuth
         INTEGER,
      er1646v2EfmPppOEIpRipFilter
         DisplayString,
      er1646v2EfmPppOEIpRipFilterIn
         DisplayString,
      er1646v2EfmPppOEIpRipClearNextHop
         INTEGER,
      er1646v2EfmPppOEIpAccPol
         DisplayString,
      er1646v2EfmPppOEIpAB
         DisplayString,
      er1646v2EfmPppOEIpMA
         INTEGER,
      er1646v2EfmPppOEIpMF
         Integer32,
      er1646v2EfmPppOEIpDB
         INTEGER,
      er1646v2EfmPppOEIpIR
         INTEGER,
      er1646v2EfmPppOEIpIgmp
         INTEGER,
      er1646v2EfmPppOEIpNN
         DisplayString,
      er1646v2EfmPppOEIpPimMode
         INTEGER,
      er1646v2EfmPppOEIpPimDrPriority
         Counter32,
      er1646v2EfmPppOEIpPimHelloTime
         TimeTicks,
      er1646v2EfmPppOEIpPimPropagationDelay
         TimeTicks,
      er1646v2EfmPppOEIpPimOverrideInterval
         TimeTicks,
      er1646v2EfmPppOEIpPimBsrBorder
         INTEGER,
      er1646v2EfmPppOEIpPimTtlThreshold
         Integer32,
      er1646v2EfmPppOEIpIMNetworkUnreachable
         INTEGER,
      er1646v2EfmPppOEIpIMHostUnreachable
         INTEGER,
      er1646v2EfmPppOEIpIMProtocolUnreachable
         INTEGER,
      er1646v2EfmPppOEIpIMPortUnreachable
         INTEGER,
      er1646v2EfmPppOEIpIMMtuExceeded
         INTEGER,
      er1646v2EfmPppOEIpIMAdminProhibited
         INTEGER,
      er1646v2EfmPppOEIpIMTtlExceeded
         INTEGER,
      er1646v2EfmPppOEIpIMRedirect
         INTEGER,
      er1646v2EfmPppOEIpV6VrfRouter
         DisplayString,
      er1646v2EfmPppOEIpV6AddrAutoConfigNrDupAddrDetects
         Integer32,
      er1646v2EfmPppOEIpV6AddrAutoConfigAcceptRa
         INTEGER,
      er1646v2EfmPppOEIpV6AddrAutoConfigAcceptRaRdnss
         INTEGER,
      er1646v2EfmPppOEIpV6AddrAutoConfigAcceptRaDnssl
         INTEGER,
      er1646v2EfmPppOEIpV6DefaultRoute
         INTEGER,
      er1646v2EfmPppOEIpV6RaSend
         INTEGER,
      er1646v2EfmPppOEIpV6RaMinInterval
         TimeTicks,
      er1646v2EfmPppOEIpV6RaMaxInterval
         TimeTicks,
      er1646v2EfmPppOEIpV6RaManagedFlag
         INTEGER,
      er1646v2EfmPppOEIpV6RaOtherConfFlag
         INTEGER,
      er1646v2EfmPppOEIpV6RaLinkMtu
         Integer32,
      er1646v2EfmPppOEIpV6RaReachableTime
         TimeTicks,
      er1646v2EfmPppOEIpV6RaRetransmitTime
         TimeTicks,
      er1646v2EfmPppOEIpV6RaHopLimit
         Integer32,
      er1646v2EfmPppOEIpV6RaDefaultLifeTime
         TimeTicks,
      er1646v2EfmPppOEIpV6RaDnsOptionsRdnssLifeTime
         TimeTicks,
      er1646v2EfmPppOEIpV6RaDnsOptionsRdnssImportServers
         INTEGER,
      er1646v2EfmPppOEIpV6RaDnsOptionsDnsslLifeTime
         TimeTicks,
      er1646v2EfmPppOEIpV6RaDnsOptionsDnsslImportDomains
         INTEGER,
      er1646v2EfmPppOEIpV6RsSend
         INTEGER,
      er1646v2EfmPppOEIpV6RsMaxRandomDelay
         TimeTicks,
      er1646v2EfmPppOEIpV6RsInterval
         TimeTicks,
      er1646v2EfmPppOEIpV6RsMaxSolicitations
         Integer32,
      er1646v2EfmPppOEIpV6TrafficPolicyInbound
         DisplayString,
      er1646v2EfmPppOEIpV6TrafficPolicyOutbound
         DisplayString,
      er1646v2EfmPppOEIpV6FirewallZone
         DisplayString,
      er1646v2EfmPppOEIpV6DhcpClientAddrAC
         INTEGER,
      er1646v2EfmPppOEIpV6DhcpClientPrDelMode
         INTEGER,
      er1646v2EfmPppOEIpV6DhcpClientPrDelPool
         DisplayString,
      er1646v2EfmPppOEIpV6DhcpClientPrDelPdExclOpt
         INTEGER,
      er1646v2EfmPppOEIpV6DhcpClientDnsServerPref
         Integer32,
      er1646v2EfmPppOEIpV6DhcpClientRapidCommit
         INTEGER,
      er1646v2EfmPppOEIpV6DhcpClientTimersSolTimeOut
         TimeTicks,
      er1646v2EfmPppOEIpV6DhcpClientTimersSolMaxRt
         TimeTicks,
      er1646v2EfmPppOEIpV6DhcpClientTimersInfoRefresh
         TimeTicks,
      er1646v2EfmPppOEIpV6DhcpServerMode
         INTEGER,
      er1646v2EfmPppOEIpV6DhcpServerPreference
         Integer32,
      er1646v2EfmPppOEIpV6DhcpServerPool
         DisplayString,
      er1646v2EfmPppOEIpV6DhcpServerRapidCommit
         INTEGER,
      er1646v2EfmPppOEIpV6DhcpServerTimersInfoRefresh
         TimeTicks,
      er1646v2EfmPppOEIpV6DhcpRelayMode
         INTEGER,
      er1646v2EfmPppOEIpV6SendRedirect
         INTEGER,
      er1646v2EfmPppOEIpV6LinkMtu
         Integer32,
      er1646v2EfmPppOEIpV6InterfaceId
         OCTET STRING,
      er1646v2EfmPppOEIpV6MF
         Integer32,
      er1646v2EfmPppOEIpV6IcmpMessagesNoRoute
         INTEGER,
      er1646v2EfmPppOEIpV6IcmpMessagesBeyondScope
         INTEGER,
      er1646v2EfmPppOEIpV6IcmpMessagesAddressUnreachable
         INTEGER,
      er1646v2EfmPppOEIpV6IcmpMessagesPortUnreachable
         INTEGER,
      er1646v2EfmPppOEIpV6IcmpMessagesPacketTooBig
         INTEGER,
      er1646v2EfmPppOEIpV6IcmpMessagesHopLimitExceeded
         INTEGER,
      er1646v2EfmPppOEIpV6IcmpMessagesFragTimeExceeded
         INTEGER,
      er1646v2EfmPppOEIpV6IcmpMessagesHeaderFieldErr
         INTEGER,
      er1646v2EfmPppOEIpV6IcmpMessagesOptionUnrecognized
         INTEGER,
      er1646v2EfmPppOEIpV6IcmpMessagesRedirect
         INTEGER,
      er1646v2EfmPppOEPppLnkMOperation
         INTEGER,
      er1646v2EfmPppOEPppLnkMInterval
         TimeTicks,
      er1646v2EfmPppOEPppLnkMRepTimeOut
         TimeTicks,
      er1646v2EfmPppOEPppLnkMFailsPrmt
         Integer32,
      er1646v2EfmPppOEPppAuthentication
         INTEGER,
      er1646v2EfmPppOEPppAuthenPeriod
         TimeTicks,
      er1646v2EfmPppOEPppSessionName
         DisplayString,
      er1646v2EfmPppOEPppSessionSecret
         DisplayString,
      er1646v2EfmPppOEPppEncModeSessionSecret
         INTEGER,
      er1646v2EfmPppOEPppEncSessionSecret
         DisplayString,
      er1646v2EfmPppOEPppServiceName
         DisplayString
      }

er1646v2EfmPppOEActions OBJECT-TYPE
   SYNTAX      VariableLengthTableActions
   MAX-ACCESS  read-write
   STATUS      current
   DESCRIPTION
      "By way of this field, some manipulations
       on this table may be performed."
   ::= {er1646v2EfmPppOEEntry 2}

er1646v2EfmPppOETableIx OBJECT-TYPE
   SYNTAX      TableIndex
   MAX-ACCESS  not-accessible
   STATUS      current
   DESCRIPTION
      ""
   ::= {er1646v2EfmPppOEEntry 11}

er1646v2EfmPppOEName OBJECT-TYPE
   SYNTAX      DisplayString
   MAX-ACCESS  read-write
   STATUS      current
   DESCRIPTION
      "Path: efm.editConf.pppoEClient.name"
   ::= {er1646v2EfmPppOEEntry 16777216}

er1646v2EfmPppOERemark OBJECT-TYPE
   SYNTAX      DisplayString
   MAX-ACCESS  read-write
   STATUS      current
   DESCRIPTION
      "Path: efm.editConf.pppoEClient.remark"
   ::= {er1646v2EfmPppOEEntry 1157627904}

er1646v2EfmPppOEAdminStatus OBJECT-TYPE
   SYNTAX      INTEGER
               {
               up (1),
               down (2)
               }
   MAX-ACCESS  read-write
   STATUS      current
   DESCRIPTION
      "Path: efm.editConf.pppoEClient.adminStatus

       Possibilities:
               up   (1)
               down   (2)"
   ::= {er1646v2EfmPppOEEntry 33554432}

er1646v2EfmPppOEMode OBJECT-TYPE
   SYNTAX      INTEGER
               {
               routing (1),
               multilink (8),
               ipV6 (16),
               ipV6ipV4 (17)
               }
   MAX-ACCESS  read-write
   STATUS      current
   DESCRIPTION
      "Path: efm.editConf.pppoEClient.mode

       Possibilities:
               routing   (1)
               multilink   (8)
               ipV6   (16)
               ipV6/ipV4   (17)"
   ::= {er1646v2EfmPppOEEntry 67108864}

er1646v2EfmPppOEIpVrfRouter OBJECT-TYPE
   SYNTAX      DisplayString
   MAX-ACCESS  read-write
   STATUS      current
   DESCRIPTION
      "Path: efm.editConf.pppoEClient.ip.vrfRouter"
   ::= {er1646v2EfmPppOEEntry 53215232}

er1646v2EfmPppOEIpAdr OBJECT-TYPE
   SYNTAX      IpAddress
   MAX-ACCESS  read-write
   STATUS      current
   DESCRIPTION
      "Path: efm.editConf.pppoEClient.ip.address"
   ::= {er1646v2EfmPppOEEntry 58261504}

er1646v2EfmPppOEIpNetm OBJECT-TYPE
   SYNTAX      IpAddress
   MAX-ACCESS  read-write
   STATUS      current
   DESCRIPTION
      "Path: efm.editConf.pppoEClient.ip.netMask"
   ::= {er1646v2EfmPppOEEntry 58392576}

er1646v2EfmPppOEIpSNetName OBJECT-TYPE
   SYNTAX      INTEGER
               {
               slOPTg (0),
               corp (2),
               dmz (3),
               internet (1)
               }
   MAX-ACCESS  read-write
   STATUS      current
   DESCRIPTION
      "Path: efm.editConf.pppoEClient.ip.sNet.name

       Possibilities:
               <OPT>   (0)
               corp   (2)
               dmz   (3)
               internet   (1)"
   ::= {er1646v2EfmPppOEEntry 53674240}

er1646v2EfmPppOEIpSNetCust OBJECT-TYPE
   SYNTAX      DisplayString
   MAX-ACCESS  read-write
   STATUS      current
   DESCRIPTION
      "Path: efm.editConf.pppoEClient.ip.sNet.custom"
   ::= {er1646v2EfmPppOEEntry 53674496}

er1646v2EfmPppOEIpRem OBJECT-TYPE
   SYNTAX      IpAddress
   MAX-ACCESS  read-write
   STATUS      current
   DESCRIPTION
      "Path: efm.editConf.pppoEClient.ip.remote"
   ::= {er1646v2EfmPppOEEntry 58458112}

er1646v2EfmPppOEIpUnnumbered OBJECT-TYPE
   SYNTAX      DisplayString
   MAX-ACCESS  read-write
   STATUS      current
   DESCRIPTION
      "Path: efm.editConf.pppoEClient.ip.unnumbered"
   ::= {er1646v2EfmPppOEEntry 52625408}

er1646v2EfmPppOEIpGwPref OBJECT-TYPE
   SYNTAX      Integer32
   MAX-ACCESS  read-write
   STATUS      current
   DESCRIPTION
      "Path: efm.editConf.pppoEClient.ip.gatewayPreference"
   ::= {er1646v2EfmPppOEEntry 52690944}

er1646v2EfmPppOEIpRsn OBJECT-TYPE
   SYNTAX      INTEGER
               {
               disabled (0),
               enabled (1)
               }
   MAX-ACCESS  read-write
   STATUS      current
   DESCRIPTION
      "Path: efm.editConf.pppoEClient.ip.requestSubnet

       Possibilities:
               disabled   (0)
               enabled   (1)"
   ::= {er1646v2EfmPppOEEntry 56688640}

er1646v2EfmPppOEIpMtu OBJECT-TYPE
   SYNTAX      Integer32
   MAX-ACCESS  read-write
   STATUS      current
   DESCRIPTION
      "Path: efm.editConf.pppoEClient.ip.mtu"
   ::= {er1646v2EfmPppOEEntry 52953088}

er1646v2EfmPppOEIpMssAdjust OBJECT-TYPE
   SYNTAX      INTEGER
               {
               disabled (0),
               auto (65536)
               }
   MAX-ACCESS  read-write
   STATUS      current
   DESCRIPTION
      "Path: efm.editConf.pppoEClient.ip.mssAdjust

       Possibilities:
               disabled   (0)
               auto   (65536)"
   ::= {er1646v2EfmPppOEEntry 53280768}

er1646v2EfmPppOEIpRipMetric OBJECT-TYPE
   SYNTAX      Integer32
   MAX-ACCESS  read-write
   STATUS      current
   DESCRIPTION
      "Path: efm.editConf.pppoEClient.ip.rip.metric"
   ::= {er1646v2EfmPppOEEntry 51712768}

er1646v2EfmPppOEIpRipMetricOut OBJECT-TYPE
   SYNTAX      Integer32
   MAX-ACCESS  read-write
   STATUS      current
   DESCRIPTION
      "Path: efm.editConf.pppoEClient.ip.rip.metricOut"
   ::= {er1646v2EfmPppOEEntry 51713024}

er1646v2EfmPppOEIpRipMode OBJECT-TYPE
   SYNTAX      INTEGER
               {
               disabled (0),
               passive (1),
               active (2)
               }
   MAX-ACCESS  read-write
   STATUS      current
   DESCRIPTION
      "Path: efm.editConf.pppoEClient.ip.rip.mode

       Possibilities:
               disabled   (0)
               passive   (1)
               active   (2)"
   ::= {er1646v2EfmPppOEEntry 51713280}

er1646v2EfmPppOEIpRipTxVer OBJECT-TYPE
   SYNTAX      INTEGER
               {
               rip1 (0),
               rip2 (1),
               rip1mcompatible (2)
               }
   MAX-ACCESS  read-write
   STATUS      current
   DESCRIPTION
      "Path: efm.editConf.pppoEClient.ip.rip.txVersion

       Possibilities:
               rip1   (0)
               rip2   (1)
               rip1-compatible   (2)"
   ::= {er1646v2EfmPppOEEntry 51716864}

er1646v2EfmPppOEIpRipRxVer OBJECT-TYPE
   SYNTAX      INTEGER
               {
               rip1only (0),
               rip2only (1),
               rip12 (2)
               }
   MAX-ACCESS  read-write
   STATUS      current
   DESCRIPTION
      "Path: efm.editConf.pppoEClient.ip.rip.rxVersion

       Possibilities:
               rip1only   (0)
               rip2only   (1)
               rip1&2   (2)"
   ::= {er1646v2EfmPppOEEntry 51717120}

er1646v2EfmPppOEIpRipSplitH OBJECT-TYPE
   SYNTAX      INTEGER
               {
               disabled (0),
               enabled (1),
               poisonedReverse (2)
               }
   MAX-ACCESS  read-write
   STATUS      current
   DESCRIPTION
      "Path: efm.editConf.pppoEClient.ip.rip.splitHorizon

       Possibilities:
               disabled   (0)
               enabled   (1)
               poisonedReverse   (2)"
   ::= {er1646v2EfmPppOEEntry 51713792}

er1646v2EfmPppOEIpRipAuth OBJECT-TYPE
   SYNTAX      INTEGER
               {
               disabled (0),
               texts (1),
               md5 (2)
               }
   MAX-ACCESS  read-write
   STATUS      current
   DESCRIPTION
      "Path: efm.editConf.pppoEClient.ip.rip.authentication

       Possibilities:
               disabled   (0)
               text    (1)
               md5   (2)"
   ::= {er1646v2EfmPppOEEntry 51712512}

er1646v2EfmPppOEIpRipFilter OBJECT-TYPE
   SYNTAX      DisplayString
   MAX-ACCESS  read-write
   STATUS      current
   DESCRIPTION
      "Path: efm.editConf.pppoEClient.ip.rip.filter"
   ::= {er1646v2EfmPppOEEntry 51716096}

er1646v2EfmPppOEIpRipFilterIn OBJECT-TYPE
   SYNTAX      DisplayString
   MAX-ACCESS  read-write
   STATUS      current
   DESCRIPTION
      "Path: efm.editConf.pppoEClient.ip.rip.filterIn"
   ::= {er1646v2EfmPppOEEntry 51716352}

er1646v2EfmPppOEIpRipClearNextHop OBJECT-TYPE
   SYNTAX      INTEGER
               {
               disabled (0),
               enabled (1)
               }
   MAX-ACCESS  read-write
   STATUS      current
   DESCRIPTION
      "Path: efm.editConf.pppoEClient.ip.rip.clearNextHop

       Possibilities:
               disabled   (0)
               enabled   (1)"
   ::= {er1646v2EfmPppOEEntry 51708416}

er1646v2EfmPppOEIpAccPol OBJECT-TYPE
   SYNTAX      DisplayString
   MAX-ACCESS  read-write
   STATUS      current
   DESCRIPTION
      "Path: efm.editConf.pppoEClient.ip.accessPolicy"
   ::= {er1646v2EfmPppOEEntry 53084160}

er1646v2EfmPppOEIpAB OBJECT-TYPE
   SYNTAX      DisplayString
   MAX-ACCESS  read-write
   STATUS      current
   DESCRIPTION
      "Path: efm.editConf.pppoEClient.ip.trafficPolicy"
   ::= {er1646v2EfmPppOEEntry 51249152}

er1646v2EfmPppOEIpMA OBJECT-TYPE
   SYNTAX      INTEGER
               {
               disabled (0),
               enabled (1)
               }
   MAX-ACCESS  read-write
   STATUS      current
   DESCRIPTION
      "Path: efm.editConf.pppoEClient.ip.mgmtAccess

       Possibilities:
               disabled   (0)
               enabled   (1)"
   ::= {er1646v2EfmPppOEEntry 51380224}

er1646v2EfmPppOEIpMF OBJECT-TYPE
   SYNTAX      Integer32
   MAX-ACCESS  read-write
   STATUS      current
   DESCRIPTION
      "Path: efm.editConf.pppoEClient.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1646v2EfmPppOEEntry 51445760}

er1646v2EfmPppOEIpDB OBJECT-TYPE
   SYNTAX      INTEGER
               {
               disabled (0),
               enabled (1)
               }
   MAX-ACCESS  read-write
   STATUS      current
   DESCRIPTION
      "Path: efm.editConf.pppoEClient.ip.directedBroadcasts

       Possibilities:
               disabled   (0)
               enabled   (1)"
   ::= {er1646v2EfmPppOEEntry 51773440}

er1646v2EfmPppOEIpIR OBJECT-TYPE
   SYNTAX      INTEGER
               {
               disabled (0),
               enabled (1)
               }
   MAX-ACCESS  read-write
   STATUS      current
   DESCRIPTION
      "Path: efm.editConf.pppoEClient.ip.icmpRedirects

       Possibilities:
               disabled   (0)
               enabled   (1)"
   ::= {er1646v2EfmPppOEEntry 52035584}

er1646v2EfmPppOEIpIgmp OBJECT-TYPE
   SYNTAX      INTEGER
               {
               disabled (0),
               proxy (1),
               router (2),
               v3Router (5)
               }
   MAX-ACCESS  read-write
   STATUS      current
   DESCRIPTION
      "Path: efm.editConf.pppoEClient.ip.igmp

       Possibilities:
               disabled   (0)
               proxy   (1)
               router   (2)
               v3Router   (5)"
   ::= {er1646v2EfmPppOEEntry 52428800}

er1646v2EfmPppOEIpNN OBJECT-TYPE
   SYNTAX      DisplayString
   MAX-ACCESS  read-write
   STATUS      current
   DESCRIPTION
      "Path: efm.editConf.pppoEClient.ip.nat"
   ::= {er1646v2EfmPppOEEntry 52101120}

er1646v2EfmPppOEIpPimMode OBJECT-TYPE
   SYNTAX      INTEGER
               {
               disabled (0),
               sparse (1),
               passive (2)
               }
   MAX-ACCESS  read-write
   STATUS      current
   DESCRIPTION
      "Path: efm.editConf.pppoEClient.ip.pim.mode

       Possibilities:
               disabled   (0)
               sparse   (1)
               passive   (2)"
   ::= {er1646v2EfmPppOEEntry 53346560}

er1646v2EfmPppOEIpPimDrPriority OBJECT-TYPE
   SYNTAX      Counter32
   MAX-ACCESS  read-write
   STATUS      current
   DESCRIPTION
      "Path: efm.editConf.pppoEClient.ip.pim.drPriority

       32 bit unsigned wrappable counter."
   ::= {er1646v2EfmPppOEEntry 53346816}

er1646v2EfmPppOEIpPimHelloTime OBJECT-TYPE
   SYNTAX      TimeTicks
   MAX-ACCESS  read-write
   STATUS      current
   DESCRIPTION
      "Path: efm.editConf.pppoEClient.ip.pim.helloTime

       Time in centi-second."
   ::= {er1646v2EfmPppOEEntry 53347072}

er1646v2EfmPppOEIpPimPropagationDelay OBJECT-TYPE
   SYNTAX      TimeTicks
   MAX-ACCESS  read-write
   STATUS      current
   DESCRIPTION
      "Path: efm.editConf.pppoEClient.ip.pim.propagationDelay

       Time in centi-second."
   ::= {er1646v2EfmPppOEEntry 53347328}

er1646v2EfmPppOEIpPimOverrideInterval OBJECT-TYPE
   SYNTAX      TimeTicks
   MAX-ACCESS  read-write
   STATUS      current
   DESCRIPTION
      "Path: efm.editConf.pppoEClient.ip.pim.overrideInterval

       Time in centi-second."
   ::= {er1646v2EfmPppOEEntry 53347584}

er1646v2EfmPppOEIpPimBsrBorder OBJECT-TYPE
   SYNTAX      INTEGER
               {
               disabled (0),
               enabled (1)
               }
   MAX-ACCESS  read-write
   STATUS      current
   DESCRIPTION
      "Path: efm.editConf.pppoEClient.ip.pim.bsrBorder

       Possibilities:
               disabled   (0)
               enabled   (1)"
   ::= {er1646v2EfmPppOEEntry 53347840}

er1646v2EfmPppOEIpPimTtlThreshold OBJECT-TYPE
   SYNTAX      Integer32
   MAX-ACCESS  read-write
   STATUS      current
   DESCRIPTION
      "Path: efm.editConf.pppoEClient.ip.pim.ttlThreshold"
   ::= {er1646v2EfmPppOEEntry 53348096}

er1646v2EfmPppOEIpIMNetworkUnreachable OBJECT-TYPE
   SYNTAX      INTEGER
               {
               disabled (0),
               enabled (1)
               }
   MAX-ACCESS  read-write
   STATUS      current
   DESCRIPTION
      "Path: efm.editConf.pppoEClient.ip.icmpMessages.networkUnreachable

       Possibilities:
               disabled   (0)
               enabled   (1)"
   ::= {er1646v2EfmPppOEEntry 53412096}

er1646v2EfmPppOEIpIMHostUnreachable OBJECT-TYPE
   SYNTAX      INTEGER
               {
               disabled (0),
               enabled (1)
               }
   MAX-ACCESS  read-write
   STATUS      current
   DESCRIPTION
      "Path: efm.editConf.pppoEClient.ip.icmpMessages.hostUnreachable

       Possibilities:
               disabled   (0)
               enabled   (1)"
   ::= {er1646v2EfmPppOEEntry 53412352}

er1646v2EfmPppOEIpIMProtocolUnreachable OBJECT-TYPE
   SYNTAX      INTEGER
               {
               disabled (0),
               enabled (1)
               }
   MAX-ACCESS  read-write
   STATUS      current
   DESCRIPTION
      "Path: efm.editConf.pppoEClient.ip.icmpMessages.protocolUnreachable

       Possibilities:
               disabled   (0)
               enabled   (1)"
   ::= {er1646v2EfmPppOEEntry 53412608}

er1646v2EfmPppOEIpIMPortUnreachable OBJECT-TYPE
   SYNTAX      INTEGER
               {
               disabled (0),
               enabled (1)
               }
   MAX-ACCESS  read-write
   STATUS      current
   DESCRIPTION
      "Path: efm.editConf.pppoEClient.ip.icmpMessages.portUnreachable

       Possibilities:
               disabled   (0)
               enabled   (1)"
   ::= {er1646v2EfmPppOEEntry 53412864}

er1646v2EfmPppOEIpIMMtuExceeded OBJECT-TYPE
   SYNTAX      INTEGER
               {
               disabled (0),
               enabled (1)
               }
   MAX-ACCESS  read-write
   STATUS      current
   DESCRIPTION
      "Path: efm.editConf.pppoEClient.ip.icmpMessages.mtuExceeded

       Possibilities:
               disabled   (0)
               enabled   (1)"
   ::= {er1646v2EfmPppOEEntry 53413120}

er1646v2EfmPppOEIpIMAdminProhibited OBJECT-TYPE
   SYNTAX      INTEGER
               {
               disabled (0),
               enabled (1)
               }
   MAX-ACCESS  read-write
   STATUS      current
   DESCRIPTION
      "Path: efm.editConf.pppoEClient.ip.icmpMessages.adminProhibited

       Possibilities:
               disabled   (0)
               enabled   (1)"
   ::= {er1646v2EfmPppOEEntry 53413376}

er1646v2EfmPppOEIpIMTtlExceeded OBJECT-TYPE
   SYNTAX      INTEGER
               {
               disabled (0),
               enabled (1)
               }
   MAX-ACCESS  read-write
   STATUS      current
   DESCRIPTION
      "Path: efm.editConf.pppoEClient.ip.icmpMessages.ttlExceeded

       Possibilities:
               disabled   (0)
               enabled   (1)"
   ::= {er1646v2EfmPppOEEntry 53413632}

er1646v2EfmPppOEIpIMRedirect OBJECT-TYPE
   SYNTAX      INTEGER
               {
               disabled (0),
               enabled (1)
               }
   MAX-ACCESS  read-write
   STATUS      current
   DESCRIPTION
      "Path: efm.editConf.pppoEClient.ip.icmpMessages.redirect

       Possibilities:
               disabled   (0)
               enabled   (1)"
   ::= {er1646v2EfmPppOEEntry 53413888}

er1646v2EfmPppOEIpV6VrfRouter OBJECT-TYPE
   SYNTAX      DisplayString
   MAX-ACCESS  read-write
   STATUS      current
   DESCRIPTION
      "Path: efm.editConf.pppoEClient.ipV6.vrfRouter"
   ::= {er1646v2EfmPppOEEntry 704708608}

er1646v2EfmPppOEIpV6AddrAutoConfigNrDupAddrDetects OBJECT-TYPE
   SYNTAX      Integer32
   MAX-ACCESS  read-write
   STATUS      current
   DESCRIPTION
      "Path: efm.editConf.pppoEClient.ipV6.addrAutoConfig.nrDupAddrDetects"
   ::= {er1646v2EfmPppOEEntry 704905472}

er1646v2EfmPppOEIpV6AddrAutoConfigAcceptRa OBJECT-TYPE
   SYNTAX      INTEGER
               {
               disabled (0),
               enabled (1)
               }
   MAX-ACCESS  read-write
   STATUS      current
   DESCRIPTION
      "Path: efm.editConf.pppoEClient.ipV6.addrAutoConfig.acceptRa

       Possibilities:
               disabled   (0)
               enabled   (1)"
   ::= {er1646v2EfmPppOEEntry 704905728}

er1646v2EfmPppOEIpV6AddrAutoConfigAcceptRaRdnss OBJECT-TYPE
   SYNTAX      INTEGER
               {
               disabled (0),
               enabled (1)
               }
   MAX-ACCESS  read-write
   STATUS      current
   DESCRIPTION
      "Path: efm.editConf.pppoEClient.ipV6.addrAutoConfig.acceptRaRdnss

       Possibilities:
               disabled   (0)
               enabled   (1)"
   ::= {er1646v2EfmPppOEEntry 704905984}

er1646v2EfmPppOEIpV6AddrAutoConfigAcceptRaDnssl OBJECT-TYPE
   SYNTAX      INTEGER
               {
               disabled (0),
               enabled (1)
               }
   MAX-ACCESS  read-write
   STATUS      current
   DESCRIPTION
      "Path: efm.editConf.pppoEClient.ipV6.addrAutoConfig.acceptRaDnssl

       Possibilities:
               disabled   (0)
               enabled   (1)"
   ::= {er1646v2EfmPppOEEntry 704906240}

er1646v2EfmPppOEIpV6DefaultRoute OBJECT-TYPE
   SYNTAX      INTEGER
               {
               disabled (0),
               enabled (1)
               }
   MAX-ACCESS  read-write
   STATUS      current
   DESCRIPTION
      "Path: efm.editConf.pppoEClient.ipV6.defaultRoute

       Possibilities:
               disabled   (0)
               enabled   (1)"
   ::= {er1646v2EfmPppOEEntry 704970752}

er1646v2EfmPppOEIpV6RaSend OBJECT-TYPE
   SYNTAX      INTEGER
               {
               disabled (0),
               enabled (1)
               }
   MAX-ACCESS  read-write
   STATUS      current
   DESCRIPTION
      "Path: efm.editConf.pppoEClient.ipV6.ra.send

       Possibilities:
               disabled   (0)
               enabled   (1)"
   ::= {er1646v2EfmPppOEEntry 705036544}

er1646v2EfmPppOEIpV6RaMinInterval OBJECT-TYPE
   SYNTAX      TimeTicks
   MAX-ACCESS  read-write
   STATUS      current
   DESCRIPTION
      "Path: efm.editConf.pppoEClient.ipV6.ra.minInterval

       Time in centi-second."
   ::= {er1646v2EfmPppOEEntry 705036800}

er1646v2EfmPppOEIpV6RaMaxInterval OBJECT-TYPE
   SYNTAX      TimeTicks
   MAX-ACCESS  read-write
   STATUS      current
   DESCRIPTION
      "Path: efm.editConf.pppoEClient.ipV6.ra.maxInterval

       Time in centi-second."
   ::= {er1646v2EfmPppOEEntry 705037056}

er1646v2EfmPppOEIpV6RaManagedFlag OBJECT-TYPE
   SYNTAX      INTEGER
               {
               disabled (0),
               enabled (1)
               }
   MAX-ACCESS  read-write
   STATUS      current
   DESCRIPTION
      "Path: efm.editConf.pppoEClient.ipV6.ra.managedFlag

       Possibilities:
               disabled   (0)
               enabled   (1)"
   ::= {er1646v2EfmPppOEEntry 705037312}

er1646v2EfmPppOEIpV6RaOtherConfFlag OBJECT-TYPE
   SYNTAX      INTEGER
               {
               disabled (0),
               enabled (1)
               }
   MAX-ACCESS  read-write
   STATUS      current
   DESCRIPTION
      "Path: efm.editConf.pppoEClient.ipV6.ra.otherConfFlag

       Possibilities:
               disabled   (0)
               enabled   (1)"
   ::= {er1646v2EfmPppOEEntry 705037568}

er1646v2EfmPppOEIpV6RaLinkMtu OBJECT-TYPE
   SYNTAX      Integer32
   MAX-ACCESS  read-write
   STATUS      current
   DESCRIPTION
      "Path: efm.editConf.pppoEClient.ipV6.ra.linkMtu"
   ::= {er1646v2EfmPppOEEntry 705037824}

er1646v2EfmPppOEIpV6RaReachableTime OBJECT-TYPE
   SYNTAX      TimeTicks
   MAX-ACCESS  read-write
   STATUS      current
   DESCRIPTION
      "Path: efm.editConf.pppoEClient.ipV6.ra.reachableTime

       Time in centi-second."
   ::= {er1646v2EfmPppOEEntry 705038080}

er1646v2EfmPppOEIpV6RaRetransmitTime OBJECT-TYPE
   SYNTAX      TimeTicks
   MAX-ACCESS  read-write
   STATUS      current
   DESCRIPTION
      "Path: efm.editConf.pppoEClient.ipV6.ra.retransmitTime

       Time in centi-second."
   ::= {er1646v2EfmPppOEEntry 705038336}

er1646v2EfmPppOEIpV6RaHopLimit OBJECT-TYPE
   SYNTAX      Integer32
   MAX-ACCESS  read-write
   STATUS      current
   DESCRIPTION
      "Path: efm.editConf.pppoEClient.ipV6.ra.hopLimit"
   ::= {er1646v2EfmPppOEEntry 705038592}

er1646v2EfmPppOEIpV6RaDefaultLifeTime OBJECT-TYPE
   SYNTAX      TimeTicks
   MAX-ACCESS  read-write
   STATUS      current
   DESCRIPTION
      "Path: efm.editConf.pppoEClient.ipV6.ra.defaultLifeTime

       Time in centi-second."
   ::= {er1646v2EfmPppOEEntry 705038848}

er1646v2EfmPppOEIpV6RaDnsOptionsRdnssLifeTime OBJECT-TYPE
   SYNTAX      TimeTicks
   MAX-ACCESS  read-write
   STATUS      current
   DESCRIPTION
      "Path: efm.editConf.pppoEClient.ipV6.ra.dnsOptions.rdnss.lifeTime

       Time in centi-second."
   ::= {er1646v2EfmPppOEEntry 705039140}

er1646v2EfmPppOEIpV6RaDnsOptionsRdnssImportServers OBJECT-TYPE
   SYNTAX      INTEGER
               {
               disabled (0),
               enabled (1)
               }
   MAX-ACCESS  read-write
   STATUS      current
   DESCRIPTION
      "Path: efm.editConf.pppoEClient.ipV6.ra.dnsOptions.rdnss.importServers

       Possibilities:
               disabled   (0)
               enabled   (1)"
   ::= {er1646v2EfmPppOEEntry 705039148}

er1646v2EfmPppOEIpV6RaDnsOptionsDnsslLifeTime OBJECT-TYPE
   SYNTAX      TimeTicks
   MAX-ACCESS  read-write
   STATUS      current
   DESCRIPTION
      "Path: efm.editConf.pppoEClient.ipV6.ra.dnsOptions.dnssl.lifeTime

       Time in centi-second."
   ::= {er1646v2EfmPppOEEntry 705039172}

er1646v2EfmPppOEIpV6RaDnsOptionsDnsslImportDomains OBJECT-TYPE
   SYNTAX      INTEGER
               {
               disabled (0),
               enabled (1)
               }
   MAX-ACCESS  read-write
   STATUS      current
   DESCRIPTION
      "Path: efm.editConf.pppoEClient.ipV6.ra.dnsOptions.dnssl.importDomains

       Possibilities:
               disabled   (0)
               enabled   (1)"
   ::= {er1646v2EfmPppOEEntry 705039180}

er1646v2EfmPppOEIpV6RsSend OBJECT-TYPE
   SYNTAX      INTEGER
               {
               disabled (0),
               enabled (1)
               }
   MAX-ACCESS  read-write
   STATUS      current
   DESCRIPTION
      "Path: efm.editConf.pppoEClient.ipV6.rs.send

       Possibilities:
               disabled   (0)
               enabled   (1)"
   ::= {er1646v2EfmPppOEEntry 705954048}

er1646v2EfmPppOEIpV6RsMaxRandomDelay OBJECT-TYPE
   SYNTAX      TimeTicks
   MAX-ACCESS  read-write
   STATUS      current
   DESCRIPTION
      "Path: efm.editConf.pppoEClient.ipV6.rs.maxRandomDelay

       Time in centi-second."
   ::= {er1646v2EfmPppOEEntry 705954304}

er1646v2EfmPppOEIpV6RsInterval OBJECT-TYPE
   SYNTAX      TimeTicks
   MAX-ACCESS  read-write
   STATUS      current
   DESCRIPTION
      "Path: efm.editConf.pppoEClient.ipV6.rs.interval

       Time in centi-second."
   ::= {er1646v2EfmPppOEEntry 705954560}

er1646v2EfmPppOEIpV6RsMaxSolicitations OBJECT-TYPE
   SYNTAX      Integer32
   MAX-ACCESS  read-write
   STATUS      current
   DESCRIPTION
      "Path: efm.editConf.pppoEClient.ipV6.rs.maxSolicitations"
   ::= {er1646v2EfmPppOEEntry 705954816}

er1646v2EfmPppOEIpV6TrafficPolicyInbound OBJECT-TYPE
   SYNTAX      DisplayString
   MAX-ACCESS  read-write
   STATUS      current
   DESCRIPTION
      "Path: efm.editConf.pppoEClient.ipV6.trafficPolicy.inbound"
   ::= {er1646v2EfmPppOEEntry 705364224}

er1646v2EfmPppOEIpV6TrafficPolicyOutbound OBJECT-TYPE
   SYNTAX      DisplayString
   MAX-ACCESS  read-write
   STATUS      current
   DESCRIPTION
      "Path: efm.editConf.pppoEClient.ipV6.trafficPolicy.outbound"
   ::= {er1646v2EfmPppOEEntry 705364480}

er1646v2EfmPppOEIpV6FirewallZone OBJECT-TYPE
   SYNTAX      DisplayString
   MAX-ACCESS  read-write
   STATUS      current
   DESCRIPTION
      "Path: efm.editConf.pppoEClient.ipV6.firewall.zone"
   ::= {er1646v2EfmPppOEEntry 705429760}

er1646v2EfmPppOEIpV6DhcpClientAddrAC OBJECT-TYPE
   SYNTAX      INTEGER
               {
               disabled (0),
               enabled (1)
               }
   MAX-ACCESS  read-write
   STATUS      current
   DESCRIPTION
      "Path: efm.editConf.pppoEClient.ipV6.dhcp.client.addrAutoConfig

       Possibilities:
               disabled   (0)
               enabled   (1)"
   ::= {er1646v2EfmPppOEEntry 705307648}

er1646v2EfmPppOEIpV6DhcpClientPrDelMode OBJECT-TYPE
   SYNTAX      INTEGER
               {
               disabled (0),
               enabled (1)
               }
   MAX-ACCESS  read-write
   STATUS      current
   DESCRIPTION
      "Path: efm.editConf.pppoEClient.ipV6.dhcp.client.pd.mode

       Possibilities:
               disabled   (0)
               enabled   (1)"
   ::= {er1646v2EfmPppOEEntry 705308676}

er1646v2EfmPppOEIpV6DhcpClientPrDelPool OBJECT-TYPE
   SYNTAX      DisplayString
   MAX-ACCESS  read-write
   STATUS      current
   DESCRIPTION
      "Path: efm.editConf.pppoEClient.ipV6.dhcp.client.pd.pool"
   ::= {er1646v2EfmPppOEEntry 705308680}

er1646v2EfmPppOEIpV6DhcpClientPrDelPdExclOpt OBJECT-TYPE
   SYNTAX      INTEGER
               {
               disabled (0),
               enabled (1)
               }
   MAX-ACCESS  read-write
   STATUS      current
   DESCRIPTION
      "Path: efm.editConf.pppoEClient.ipV6.dhcp.client.pd.pdExclOpt

       Possibilities:
               disabled   (0)
               enabled   (1)"
   ::= {er1646v2EfmPppOEEntry 705308684}

er1646v2EfmPppOEIpV6DhcpClientDnsServerPref OBJECT-TYPE
   SYNTAX      Integer32
   MAX-ACCESS  read-write
   STATUS      current
   DESCRIPTION
      "Path: efm.editConf.pppoEClient.ipV6.dhcp.client.dns.serverPref"
   ::= {er1646v2EfmPppOEEntry 705310724}

er1646v2EfmPppOEIpV6DhcpClientRapidCommit OBJECT-TYPE
   SYNTAX      INTEGER
               {
               disabled (0),
               enabled (1)
               }
   MAX-ACCESS  read-write
   STATUS      current
   DESCRIPTION
      "Path: efm.editConf.pppoEClient.ipV6.dhcp.client.rapidCommit

       Possibilities:
               disabled   (0)
               enabled   (1)"
   ::= {er1646v2EfmPppOEEntry 705309696}

er1646v2EfmPppOEIpV6DhcpClientTimersSolTimeOut OBJECT-TYPE
   SYNTAX      TimeTicks
   MAX-ACCESS  read-write
   STATUS      current
   DESCRIPTION
      "Path: efm.editConf.pppoEClient.ipV6.dhcp.client.timers.solTimeOut

       Time in centi-second."
   ::= {er1646v2EfmPppOEEntry 705311748}

er1646v2EfmPppOEIpV6DhcpClientTimersSolMaxRt OBJECT-TYPE
   SYNTAX      TimeTicks
   MAX-ACCESS  read-write
   STATUS      current
   DESCRIPTION
      "Path: efm.editConf.pppoEClient.ipV6.dhcp.client.timers.solMaxRt

       Time in centi-second."
   ::= {er1646v2EfmPppOEEntry 705311752}

er1646v2EfmPppOEIpV6DhcpClientTimersInfoRefresh OBJECT-TYPE
   SYNTAX      TimeTicks
   MAX-ACCESS  read-write
   STATUS      current
   DESCRIPTION
      "Path: efm.editConf.pppoEClient.ipV6.dhcp.client.timers.infoRefresh

       Time in centi-second."
   ::= {er1646v2EfmPppOEEntry 705311756}

er1646v2EfmPppOEIpV6DhcpServerMode OBJECT-TYPE
   SYNTAX      INTEGER
               {
               disabled (0),
               enabled (1)
               }
   MAX-ACCESS  read-write
   STATUS      current
   DESCRIPTION
      "Path: efm.editConf.pppoEClient.ipV6.dhcp.server.mode

       Possibilities:
               disabled   (0)
               enabled   (1)"
   ::= {er1646v2EfmPppOEEntry 705315840}

er1646v2EfmPppOEIpV6DhcpServerPreference OBJECT-TYPE
   SYNTAX      Integer32
   MAX-ACCESS  read-write
   STATUS      current
   DESCRIPTION
      "Path: efm.editConf.pppoEClient.ipV6.dhcp.server.preference"
   ::= {er1646v2EfmPppOEEntry 705316864}

er1646v2EfmPppOEIpV6DhcpServerPool OBJECT-TYPE
   SYNTAX      DisplayString
   MAX-ACCESS  read-write
   STATUS      current
   DESCRIPTION
      "Path: efm.editConf.pppoEClient.ipV6.dhcp.server.pool"
   ::= {er1646v2EfmPppOEEntry 705317888}

er1646v2EfmPppOEIpV6DhcpServerRapidCommit OBJECT-TYPE
   SYNTAX      INTEGER
               {
               disabled (0),
               enabled (1)
               }
   MAX-ACCESS  read-write
   STATUS      current
   DESCRIPTION
      "Path: efm.editConf.pppoEClient.ipV6.dhcp.server.rapidCommit

       Possibilities:
               disabled   (0)
               enabled   (1)"
   ::= {er1646v2EfmPppOEEntry 705318912}

er1646v2EfmPppOEIpV6DhcpServerTimersInfoRefresh OBJECT-TYPE
   SYNTAX      TimeTicks
   MAX-ACCESS  read-write
   STATUS      current
   DESCRIPTION
      "Path: efm.editConf.pppoEClient.ipV6.dhcp.server.timers.infoRefresh

       Time in centi-second."
   ::= {er1646v2EfmPppOEEntry 705319940}

er1646v2EfmPppOEIpV6DhcpRelayMode OBJECT-TYPE
   SYNTAX      INTEGER
               {
               disabled (0),
               enabled (1)
               }
   MAX-ACCESS  read-write
   STATUS      current
   DESCRIPTION
      "Path: efm.editConf.pppoEClient.ipV6.dhcp.relay.mode

       Possibilities:
               disabled   (0)
               enabled   (1)"
   ::= {er1646v2EfmPppOEEntry 705323040}

er1646v2EfmPppOEIpV6SendRedirect OBJECT-TYPE
   SYNTAX      INTEGER
               {
               disabled (0),
               enabled (1)
               }
   MAX-ACCESS  read-write
   STATUS      current
   DESCRIPTION
      "Path: efm.editConf.pppoEClient.ipV6.sendRedirect

       Possibilities:
               disabled   (0)
               enabled   (1)"
   ::= {er1646v2EfmPppOEEntry 705101824}

er1646v2EfmPppOEIpV6LinkMtu OBJECT-TYPE
   SYNTAX      Integer32
   MAX-ACCESS  read-write
   STATUS      current
   DESCRIPTION
      "Path: efm.editConf.pppoEClient.ipV6.linkMtu"
   ::= {er1646v2EfmPppOEEntry 705167360}

er1646v2EfmPppOEIpV6InterfaceId OBJECT-TYPE
   SYNTAX      OCTET STRING
   MAX-ACCESS  read-write
   STATUS      current
   DESCRIPTION
      "Path: efm.editConf.pppoEClient.ipV6.interfaceId"
   ::= {er1646v2EfmPppOEEntry 705232896}

er1646v2EfmPppOEIpV6MF OBJECT-TYPE
   SYNTAX      Integer32
   MAX-ACCESS  read-write
   STATUS      current
   DESCRIPTION
      "Path: efm.editConf.pppoEClient.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1646v2EfmPppOEEntry 705757184}

er1646v2EfmPppOEIpV6IcmpMessagesNoRoute OBJECT-TYPE
   SYNTAX      INTEGER
               {
               disabled (0),
               enabled (1)
               }
   MAX-ACCESS  read-write
   STATUS      current
   DESCRIPTION
      "Path: efm.editConf.pppoEClient.ipV6.icmpMessages.noRoute

       Possibilities:
               disabled   (0)
               enabled   (1)"
   ::= {er1646v2EfmPppOEEntry 705822976}

er1646v2EfmPppOEIpV6IcmpMessagesBeyondScope OBJECT-TYPE
   SYNTAX      INTEGER
               {
               disabled (0),
               enabled (1)
               }
   MAX-ACCESS  read-write
   STATUS      current
   DESCRIPTION
      "Path: efm.editConf.pppoEClient.ipV6.icmpMessages.beyondScope

       Possibilities:
               disabled   (0)
               enabled   (1)"
   ::= {er1646v2EfmPppOEEntry 705823488}

er1646v2EfmPppOEIpV6IcmpMessagesAddressUnreachable OBJECT-TYPE
   SYNTAX      INTEGER
               {
               disabled (0),
               enabled (1)
               }
   MAX-ACCESS  read-write
   STATUS      current
   DESCRIPTION
      "Path: efm.editConf.pppoEClient.ipV6.icmpMessages.addressUnreachable

       Possibilities:
               disabled   (0)
               enabled   (1)"
   ::= {er1646v2EfmPppOEEntry 705823744}

er1646v2EfmPppOEIpV6IcmpMessagesPortUnreachable OBJECT-TYPE
   SYNTAX      INTEGER
               {
               disabled (0),
               enabled (1)
               }
   MAX-ACCESS  read-write
   STATUS      current
   DESCRIPTION
      "Path: efm.editConf.pppoEClient.ipV6.icmpMessages.portUnreachable

       Possibilities:
               disabled   (0)
               enabled   (1)"
   ::= {er1646v2EfmPppOEEntry 705824000}

er1646v2EfmPppOEIpV6IcmpMessagesPacketTooBig OBJECT-TYPE
   SYNTAX      INTEGER
               {
               disabled (0),
               enabled (1)
               }
   MAX-ACCESS  read-write
   STATUS      current
   DESCRIPTION
      "Path: efm.editConf.pppoEClient.ipV6.icmpMessages.packetTooBig

       Possibilities:
               disabled   (0)
               enabled   (1)"
   ::= {er1646v2EfmPppOEEntry 705825280}

er1646v2EfmPppOEIpV6IcmpMessagesHopLimitExceeded OBJECT-TYPE
   SYNTAX      INTEGER
               {
               disabled (0),
               enabled (1)
               }
   MAX-ACCESS  read-write
   STATUS      current
   DESCRIPTION
      "Path: efm.editConf.pppoEClient.ipV6.icmpMessages.hopLimitExceeded

       Possibilities:
               disabled   (0)
               enabled   (1)"
   ::= {er1646v2EfmPppOEEntry 705827840}

er1646v2EfmPppOEIpV6IcmpMessagesFragTimeExceeded OBJECT-TYPE
   SYNTAX      INTEGER
               {
               disabled (0),
               enabled (1)
               }
   MAX-ACCESS  read-write
   STATUS      current
   DESCRIPTION
      "Path: efm.editConf.pppoEClient.ipV6.icmpMessages.fragTimeExceeded

       Possibilities:
               disabled   (0)
               enabled   (1)"
   ::= {er1646v2EfmPppOEEntry 705828096}

er1646v2EfmPppOEIpV6IcmpMessagesHeaderFieldErr OBJECT-TYPE
   SYNTAX      INTEGER
               {
               disabled (0),
               enabled (1)
               }
   MAX-ACCESS  read-write
   STATUS      current
   DESCRIPTION
      "Path: efm.editConf.pppoEClient.ipV6.icmpMessages.headerFieldErr

       Possibilities:
               disabled   (0)
               enabled   (1)"
   ::= {er1646v2EfmPppOEEntry 705830400}

er1646v2EfmPppOEIpV6IcmpMessagesOptionUnrecognized OBJECT-TYPE
   SYNTAX      INTEGER
               {
               disabled (0),
               enabled (1)
               }
   MAX-ACCESS  read-write
   STATUS      current
   DESCRIPTION
      "Path: efm.editConf.pppoEClient.ipV6.icmpMessages.optionUnrecognized

       Possibilities:
               disabled   (0)
               enabled   (1)"
   ::= {er1646v2EfmPppOEEntry 705830912}

er1646v2EfmPppOEIpV6IcmpMessagesRedirect OBJECT-TYPE
   SYNTAX      INTEGER
               {
               disabled (0),
               enabled (1)
               }
   MAX-ACCESS  read-write
   STATUS      current
   DESCRIPTION
      "Path: efm.editConf.pppoEClient.ipV6.icmpMessages.redirect

       Possibilities:
               disabled   (0)
               enabled   (1)"
   ::= {er1646v2EfmPppOEEntry 705832960}

er1646v2EfmPppOEPppLnkMOperation OBJECT-TYPE
   SYNTAX      INTEGER
               {
               disabled (0),
               enabled (1)
               }
   MAX-ACCESS  read-write
   STATUS      current
   DESCRIPTION
      "Path: efm.editConf.pppoEClient.ppp.linkMonitoring.operation

       Possibilities:
               disabled   (0)
               enabled   (1)"
   ::= {er1646v2EfmPppOEEntry 251724032}

er1646v2EfmPppOEPppLnkMInterval OBJECT-TYPE
   SYNTAX      TimeTicks
   MAX-ACCESS  read-write
   STATUS      current
   DESCRIPTION
      "Path: efm.editConf.pppoEClient.ppp.linkMonitoring.interval

       Time in centi-second."
   ::= {er1646v2EfmPppOEEntry 251724288}

er1646v2EfmPppOEPppLnkMRepTimeOut OBJECT-TYPE
   SYNTAX      TimeTicks
   MAX-ACCESS  read-write
   STATUS      current
   DESCRIPTION
      "Path: efm.editConf.pppoEClient.ppp.linkMonitoring.replyTimeOut

       Time in centi-second."
   ::= {er1646v2EfmPppOEEntry 251724544}

er1646v2EfmPppOEPppLnkMFailsPrmt OBJECT-TYPE
   SYNTAX      Integer32
   MAX-ACCESS  read-write
   STATUS      current
   DESCRIPTION
      "Path: efm.editConf.pppoEClient.ppp.linkMonitoring.failsPermitted"
   ::= {er1646v2EfmPppOEEntry 251724800}

er1646v2EfmPppOEPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: efm.editConf.pppoEClient.ppp.authentication

       Possibilities:
               disabled   (0)
               chap   (1)
               pap   (2)
               chapOrPap   (3)
               msChap   (4)
               msChapV2   (5)"
   ::= {er1646v2EfmPppOEEntry 251789312}

er1646v2EfmPppOEPppAuthenPeriod OBJECT-TYPE
   SYNTAX      TimeTicks
   MAX-ACCESS  read-write
   STATUS      current
   DESCRIPTION
      "Path: efm.editConf.pppoEClient.ppp.authenPeriod

       Time in centi-second."
   ::= {er1646v2EfmPppOEEntry 251854848}

er1646v2EfmPppOEPppSessionName OBJECT-TYPE
   SYNTAX      DisplayString
   MAX-ACCESS  read-write
   STATUS      current
   DESCRIPTION
      "Path: efm.editConf.pppoEClient.ppp.sessionName"
   ::= {er1646v2EfmPppOEEntry 251985920}

er1646v2EfmPppOEPppSessionSecret OBJECT-TYPE
   SYNTAX      DisplayString
   MAX-ACCESS  read-write
   STATUS      current
   DESCRIPTION
      "Path: efm.editConf.pppoEClient.ppp.sessionSecret"
   ::= {er1646v2EfmPppOEEntry 252051456}

er1646v2EfmPppOEPppEncModeSessionSecret OBJECT-TYPE
   SYNTAX      INTEGER
               {
               none (1),
               encrypt (2),
               encType1 (3),
               invalid (128)
               }
   MAX-ACCESS  read-write
   STATUS      current
   DESCRIPTION
      "Path: efm.editConf.pppoEClient.ppp.encModeSessionSecret

       Possibilities:
               none   (1)
               encrypt   (2)
               encType1   (3)
               invalid   (128)"
   ::= {er1646v2EfmPppOEEntry 252182528}

er1646v2EfmPppOEPppEncSessionSecret OBJECT-TYPE
   SYNTAX      DisplayString
   MAX-ACCESS  read-write
   STATUS      current
   DESCRIPTION
      "Path: efm.editConf.pppoEClient.ppp.encSessionSecret"
   ::= {er1646v2EfmPppOEEntry 252248064}

er1646v2EfmPppOEPppServiceName OBJECT-TYPE
   SYNTAX      DisplayString
   MAX-ACCESS  read-write
   STATUS      current
   DESCRIPTION
      "Path: efm.editConf.pppoEClient.ppp.serviceName"
   ::= {er1646v2EfmPppOEEntry 252116992}

er1646v2EfmPppOEIpH OBJECT-TYPE
   SYNTAX      SEQUENCE OF Er1646v2EfmPppOEIpHEntry
   MAX-ACCESS  not-accessible
   STATUS      current
   DESCRIPTION
      ""
   ::= {er1646v2EfmPppOE 51314688}

er1646v2EfmPppOEIpHEntry OBJECT-TYPE
   SYNTAX      Er1646v2EfmPppOEIpHEntry
   MAX-ACCESS  not-accessible
   STATUS      current
   DESCRIPTION
      ""
   INDEX      { er1646v2EfmPppOETableIx,
                er1646v2EfmPppOEIpHTableIx }
   ::= {er1646v2EfmPppOEIpH 1}

Er1646v2EfmPppOEIpHEntry ::=
   SEQUENCE
      {
      er1646v2EfmPppOEIpHActions
         VariableLengthTableActions,
      er1646v2EfmPppOEIpHTableIx
         TableIndex,
      er1646v2EfmPppOEIpHAddress
         IpAddress,
      er1646v2EfmPppOEIpHDhcpRelayOptionSubscriberId
         DisplayString
      }

er1646v2EfmPppOEIpHActions OBJECT-TYPE
   SYNTAX      VariableLengthTableActions
   MAX-ACCESS  read-write
   STATUS      current
   DESCRIPTION
      "By way of this field, some manipulations
       on this table may be performed."
   ::= {er1646v2EfmPppOEIpHEntry 2}

er1646v2EfmPppOEIpHTableIx OBJECT-TYPE
   SYNTAX      TableIndex
   MAX-ACCESS  not-accessible
   STATUS      current
   DESCRIPTION
      ""
   ::= {er1646v2EfmPppOEIpHEntry 11}

er1646v2EfmPppOEIpHAddress OBJECT-TYPE
   SYNTAX      IpAddress
   MAX-ACCESS  read-write
   STATUS      current
   DESCRIPTION
      "Path: efm.editConf.pppoEClient.ip.helpers.address"
   ::= {er1646v2EfmPppOEIpHEntry 16777216}

er1646v2EfmPppOEIpHDhcpRelayOptionSubscriberId OBJECT-TYPE
   SYNTAX      DisplayString
   MAX-ACCESS  read-write
   STATUS      current
   DESCRIPTION
      "Path: efm.editConf.pppoEClient.ip.helpers.dhcpRelayOption.subscriberId"
   ::= {er1646v2EfmPppOEIpHEntry 33947648}

er1646v2EfmPppOEIpV6Addresses OBJECT-TYPE
   SYNTAX      SEQUENCE OF Er1646v2EfmPppOEIpV6AddressesEntry
   MAX-ACCESS  not-accessible
   STATUS      current
   DESCRIPTION
      ""
   ::= {er1646v2EfmPppOE 704839680}

er1646v2EfmPppOEIpV6AddressesEntry OBJECT-TYPE
   SYNTAX      Er1646v2EfmPppOEIpV6AddressesEntry
   MAX-ACCESS  not-accessible
   STATUS      current
   DESCRIPTION
      ""
   INDEX      { er1646v2EfmPppOETableIx,
                er1646v2EfmPppOEIpV6AddressesTableIx }
   ::= {er1646v2EfmPppOEIpV6Addresses 1}

Er1646v2EfmPppOEIpV6AddressesEntry ::=
   SEQUENCE
      {
      er1646v2EfmPppOEIpV6AddressesActions
         VariableLengthTableActions,
      er1646v2EfmPppOEIpV6AddressesTableIx
         TableIndex,
      er1646v2EfmPppOEIpV6AddressesType
         INTEGER,
      er1646v2EfmPppOEIpV6AddressesAddress
         Ipv6Address,
      er1646v2EfmPppOEIpV6AddressesPrefixLength
         Integer32,
      er1646v2EfmPppOEIpV6AddressesGeneralPrefix
         DisplayString,
      er1646v2EfmPppOEIpV6AddressesRaSend
         INTEGER,
      er1646v2EfmPppOEIpV6AddressesRaOnLinkFlag
         INTEGER,
      er1646v2EfmPppOEIpV6AddressesRaAutoFlag
         INTEGER,
      er1646v2EfmPppOEIpV6AddressesRaValidLifeTime
         TimeTicks,
      er1646v2EfmPppOEIpV6AddressesRaValidLTMode
         INTEGER,
      er1646v2EfmPppOEIpV6AddressesRaPrefLifeTime
         TimeTicks,
      er1646v2EfmPppOEIpV6AddressesRaPrefLTMode
         INTEGER
      }

er1646v2EfmPppOEIpV6AddressesActions OBJECT-TYPE
   SYNTAX      VariableLengthTableActions
   MAX-ACCESS  read-write
   STATUS      current
   DESCRIPTION
      "By way of this field, some manipulations
       on this table may be performed."
   ::= {er1646v2EfmPppOEIpV6AddressesEntry 2}

er1646v2EfmPppOEIpV6AddressesTableIx OBJECT-TYPE
   SYNTAX      TableIndex
   MAX-ACCESS  not-accessible
   STATUS      current
   DESCRIPTION
      ""
   ::= {er1646v2EfmPppOEIpV6AddressesEntry 11}

er1646v2EfmPppOEIpV6AddressesType OBJECT-TYPE
   SYNTAX      INTEGER
               {
               unicast (0),
               eui64 (1),
               anycast (2),
               linkLocal (3),
               generalPrefix (4)
               }
   MAX-ACCESS  read-write
   STATUS      current
   DESCRIPTION
      "Path: efm.editConf.pppoEClient.ipV6.addresses.type

       Possibilities:
               unicast   (0)
               eui64   (1)
               anycast   (2)
               linkLocal   (3)
               generalPrefix   (4)"
   ::= {er1646v2EfmPppOEIpV6AddressesEntry 50331648}

er1646v2EfmPppOEIpV6AddressesAddress OBJECT-TYPE
   SYNTAX      Ipv6Address
   MAX-ACCESS  read-write
   STATUS      current
   DESCRIPTION
      "Path: efm.editConf.pppoEClient.ipV6.addresses.address

       ipv6 address"
   ::= {er1646v2EfmPppOEIpV6AddressesEntry 16777216}

er1646v2EfmPppOEIpV6AddressesPrefixLength OBJECT-TYPE
   SYNTAX      Integer32
   MAX-ACCESS  read-write
   STATUS      current
   DESCRIPTION
      "Path: efm.editConf.pppoEClient.ipV6.addresses.prefixLength"
   ::= {er1646v2EfmPppOEIpV6AddressesEntry 33554432}

er1646v2EfmPppOEIpV6AddressesGeneralPrefix OBJECT-TYPE
   SYNTAX      DisplayString
   MAX-ACCESS  read-write
   STATUS      current
   DESCRIPTION
      "Path: efm.editConf.pppoEClient.ipV6.addresses.generalPrefix"
   ::= {er1646v2EfmPppOEIpV6AddressesEntry 83886080}

er1646v2EfmPppOEIpV6AddressesRaSend OBJECT-TYPE
   SYNTAX      INTEGER
               {
               disabled (0),
               enabled (1)
               }
   MAX-ACCESS  read-write
   STATUS      current
   DESCRIPTION
      "Path: efm.editConf.pppoEClient.ipV6.addresses.ra.send

       Possibilities:
               disabled   (0)
               enabled   (1)"
   ::= {er1646v2EfmPppOEIpV6AddressesEntry 67174400}

er1646v2EfmPppOEIpV6AddressesRaOnLinkFlag OBJECT-TYPE
   SYNTAX      INTEGER
               {
               disabled (0),
               enabled (1)
               }
   MAX-ACCESS  read-write
   STATUS      current
   DESCRIPTION
      "Path: efm.editConf.pppoEClient.ipV6.addresses.ra.onLinkFlag

       Possibilities:
               disabled   (0)
               enabled   (1)"
   ::= {er1646v2EfmPppOEIpV6AddressesEntry 67371008}

er1646v2EfmPppOEIpV6AddressesRaAutoFlag OBJECT-TYPE
   SYNTAX      INTEGER
               {
               disabled (0),
               enabled (1)
               }
   MAX-ACCESS  read-write
   STATUS      current
   DESCRIPTION
      "Path: efm.editConf.pppoEClient.ipV6.addresses.ra.autonomousFlag

       Possibilities:
               disabled   (0)
               enabled   (1)"
   ::= {er1646v2EfmPppOEIpV6AddressesEntry 67567616}

er1646v2EfmPppOEIpV6AddressesRaValidLifeTime OBJECT-TYPE
   SYNTAX      TimeTicks
   MAX-ACCESS  read-write
   STATUS      current
   DESCRIPTION
      "Path: efm.editConf.pppoEClient.ipV6.addresses.ra.validLifeTime

       Time in centi-second."
   ::= {er1646v2EfmPppOEIpV6AddressesEntry 67239936}

er1646v2EfmPppOEIpV6AddressesRaValidLTMode OBJECT-TYPE
   SYNTAX      INTEGER
               {
               fixed (0),
               infinite (2)
               }
   MAX-ACCESS  read-write
   STATUS      current
   DESCRIPTION
      "Path: efm.editConf.pppoEClient.ipV6.addresses.ra.validLifeTimeMode

       Possibilities:
               fixed   (0)
               infinite   (2)"
   ::= {er1646v2EfmPppOEIpV6AddressesEntry 67305472}

er1646v2EfmPppOEIpV6AddressesRaPrefLifeTime OBJECT-TYPE
   SYNTAX      TimeTicks
   MAX-ACCESS  read-write
   STATUS      current
   DESCRIPTION
      "Path: efm.editConf.pppoEClient.ipV6.addresses.ra.prefLifeTime

       Time in centi-second."
   ::= {er1646v2EfmPppOEIpV6AddressesEntry 67436544}

er1646v2EfmPppOEIpV6AddressesRaPrefLTMode OBJECT-TYPE
   SYNTAX      INTEGER
               {
               fixed (0),
               infinite (2)
               }
   MAX-ACCESS  read-write
   STATUS      current
   DESCRIPTION
      "Path: efm.editConf.pppoEClient.ipV6.addresses.ra.prefLifeTimeMode

       Possibilities:
               fixed   (0)
               infinite   (2)"
   ::= {er1646v2EfmPppOEIpV6AddressesEntry 67502080}

er1646v2EfmPppOEIpV6RaDnsOptionsRdnssServers OBJECT-TYPE
   SYNTAX      SEQUENCE OF Er1646v2EfmPppOEIpV6RaDnsOptionsRdnssServersEntry
   MAX-ACCESS  not-accessible
   STATUS      current
   DESCRIPTION
      ""
   ::= {er1646v2EfmPppOE 705039144}

er1646v2EfmPppOEIpV6RaDnsOptionsRdnssServersEntry OBJECT-TYPE
   SYNTAX      Er1646v2EfmPppOEIpV6RaDnsOptionsRdnssServersEntry
   MAX-ACCESS  not-accessible
   STATUS      current
   DESCRIPTION
      ""
   INDEX      { er1646v2EfmPppOETableIx,
                er1646v2EfmPppOEIpV6RaDnsOptionsRdnssServersTableIx }
   ::= {er1646v2EfmPppOEIpV6RaDnsOptionsRdnssServers 1}

Er1646v2EfmPppOEIpV6RaDnsOptionsRdnssServersEntry ::=
   SEQUENCE
      {
      er1646v2EfmPppOEIpV6RaDnsOptionsRdnssServersActions
         VariableLengthTableActions,
      er1646v2EfmPppOEIpV6RaDnsOptionsRdnssServersTableIx
         TableIndex,
      er1646v2EfmPppOEIpV6RaDnsOptionsRdnssServersAddress
         Ipv6Address
      }

er1646v2EfmPppOEIpV6RaDnsOptionsRdnssServersActions OBJECT-TYPE
   SYNTAX      VariableLengthTableActions
   MAX-ACCESS  read-write
   STATUS      current
   DESCRIPTION
      "By way of this field, some manipulations
       on this table may be performed."
   ::= {er1646v2EfmPppOEIpV6RaDnsOptionsRdnssServersEntry 2}

er1646v2EfmPppOEIpV6RaDnsOptionsRdnssServersTableIx OBJECT-TYPE
   SYNTAX      TableIndex
   MAX-ACCESS  not-accessible
   STATUS      current
   DESCRIPTION
      ""
   ::= {er1646v2EfmPppOEIpV6RaDnsOptionsRdnssServersEntry 11}

er1646v2EfmPppOEIpV6RaDnsOptionsRdnssServersAddress OBJECT-TYPE
   SYNTAX      Ipv6Address
   MAX-ACCESS  read-write
   STATUS      current
   DESCRIPTION
      "Path: efm.editConf.pppoEClient.ipV6.ra.dnsOptions.rdnss.servers.address

       ipv6 address"
   ::= {er1646v2EfmPppOEIpV6RaDnsOptionsRdnssServersEntry 16777216}

er1646v2EfmPppOEIpV6RaDnsOptionsDnsslDomains OBJECT-TYPE
   SYNTAX      SEQUENCE OF Er1646v2EfmPppOEIpV6RaDnsOptionsDnsslDomainsEntry
   MAX-ACCESS  not-accessible
   STATUS      current
   DESCRIPTION
      ""
   ::= {er1646v2EfmPppOE 705039176}

er1646v2EfmPppOEIpV6RaDnsOptionsDnsslDomainsEntry OBJECT-TYPE
   SYNTAX      Er1646v2EfmPppOEIpV6RaDnsOptionsDnsslDomainsEntry
   MAX-ACCESS  not-accessible
   STATUS      current
   DESCRIPTION
      ""
   INDEX      { er1646v2EfmPppOETableIx,
                er1646v2EfmPppOEIpV6RaDnsOptionsDnsslDomainsTableIx }
   ::= {er1646v2EfmPppOEIpV6RaDnsOptionsDnsslDomains 1}

Er1646v2EfmPppOEIpV6RaDnsOptionsDnsslDomainsEntry ::=
   SEQUENCE
      {
      er1646v2EfmPppOEIpV6RaDnsOptionsDnsslDomainsActions
         VariableLengthTableActions,
      er1646v2EfmPppOEIpV6RaDnsOptionsDnsslDomainsTableIx
         TableIndex,
      er1646v2EfmPppOEIpV6RaDnsOptionsDnsslDomainsName
         DisplayString
      }

er1646v2EfmPppOEIpV6RaDnsOptionsDnsslDomainsActions OBJECT-TYPE
   SYNTAX      VariableLengthTableActions
   MAX-ACCESS  read-write
   STATUS      current
   DESCRIPTION
      "By way of this field, some manipulations
       on this table may be performed."
   ::= {er1646v2EfmPppOEIpV6RaDnsOptionsDnsslDomainsEntry 2}

er1646v2EfmPppOEIpV6RaDnsOptionsDnsslDomainsTableIx OBJECT-TYPE
   SYNTAX      TableIndex
   MAX-ACCESS  not-accessible
   STATUS      current
   DESCRIPTION
      ""
   ::= {er1646v2EfmPppOEIpV6RaDnsOptionsDnsslDomainsEntry 11}

er1646v2EfmPppOEIpV6RaDnsOptionsDnsslDomainsName OBJECT-TYPE
   SYNTAX      DisplayString
   MAX-ACCESS  read-write
   STATUS      current
   DESCRIPTION
      "Path: efm.editConf.pppoEClient.ipV6.ra.dnsOptions.dnssl.domains.name"
   ::= {er1646v2EfmPppOEIpV6RaDnsOptionsDnsslDomainsEntry 16777216}

er1646v2EfmPppOEIpV6DhcpClientUserClassOpt OBJECT-TYPE
   SYNTAX      SEQUENCE OF Er1646v2EfmPppOEIpV6DhcpClientUserClassOptEntry
   MAX-ACCESS  not-accessible
   STATUS      current
   DESCRIPTION
      ""
   ::= {er1646v2EfmPppOE 705312768}

er1646v2EfmPppOEIpV6DhcpClientUserClassOptEntry OBJECT-TYPE
   SYNTAX      Er1646v2EfmPppOEIpV6DhcpClientUserClassOptEntry
   MAX-ACCESS  not-accessible
   STATUS      current
   DESCRIPTION
      ""
   INDEX      { er1646v2EfmPppOETableIx,
                er1646v2EfmPppOEIpV6DhcpClientUserClassOptTableIx }
   ::= {er1646v2EfmPppOEIpV6DhcpClientUserClassOpt 1}

Er1646v2EfmPppOEIpV6DhcpClientUserClassOptEntry ::=
   SEQUENCE
      {
      er1646v2EfmPppOEIpV6DhcpClientUserClassOptActions
         VariableLengthTableActions,
      er1646v2EfmPppOEIpV6DhcpClientUserClassOptTableIx
         TableIndex,
      er1646v2EfmPppOEIpV6DhcpClientUserClassOptValueAscii
         DisplayString,
      er1646v2EfmPppOEIpV6DhcpClientUserClassOptValueDecimal
         Integer32,
      er1646v2EfmPppOEIpV6DhcpClientUserClassOptValueHexData
         OCTET STRING
      }

er1646v2EfmPppOEIpV6DhcpClientUserClassOptActions OBJECT-TYPE
   SYNTAX      VariableLengthTableActions
   MAX-ACCESS  read-write
   STATUS      current
   DESCRIPTION
      "By way of this field, some manipulations
       on this table may be performed."
   ::= {er1646v2EfmPppOEIpV6DhcpClientUserClassOptEntry 2}

er1646v2EfmPppOEIpV6DhcpClientUserClassOptTableIx OBJECT-TYPE
   SYNTAX      TableIndex
   MAX-ACCESS  not-accessible
   STATUS      current
   DESCRIPTION
      ""
   ::= {er1646v2EfmPppOEIpV6DhcpClientUserClassOptEntry 11}

er1646v2EfmPppOEIpV6DhcpClientUserClassOptValueAscii OBJECT-TYPE
   SYNTAX      DisplayString
   MAX-ACCESS  read-write
   STATUS      current
   DESCRIPTION
      "Path: efm.editConf.pppoEClient.ipV6.dhcp.client.userClassOpt.value.ascii"
   ::= {er1646v2EfmPppOEIpV6DhcpClientUserClassOptEntry 16842752}

er1646v2EfmPppOEIpV6DhcpClientUserClassOptValueDecimal OBJECT-TYPE
   SYNTAX      Integer32
   MAX-ACCESS  read-write
   STATUS      current
   DESCRIPTION
      "Path: efm.editConf.pppoEClient.ipV6.dhcp.client.userClassOpt.value.decimal"
   ::= {er1646v2EfmPppOEIpV6DhcpClientUserClassOptEntry 16908288}

er1646v2EfmPppOEIpV6DhcpClientUserClassOptValueHexData OBJECT-TYPE
   SYNTAX      OCTET STRING
   MAX-ACCESS  read-write
   STATUS      current
   DESCRIPTION
      "Path: efm.editConf.pppoEClient.ipV6.dhcp.client.userClassOpt.value.hexData"
   ::= {er1646v2EfmPppOEIpV6DhcpClientUserClassOptEntry 16973824}

er1646v2EfmPppOEIpV6DhcpClientVendorCl OBJECT-TYPE
   SYNTAX      SEQUENCE OF Er1646v2EfmPppOEIpV6DhcpClientVendorClEntry
   MAX-ACCESS  not-accessible
   STATUS      current
   DESCRIPTION
      ""
   ::= {er1646v2EfmPppOE 705313792}

er1646v2EfmPppOEIpV6DhcpClientVendorClEntry OBJECT-TYPE
   SYNTAX      Er1646v2EfmPppOEIpV6DhcpClientVendorClEntry
   MAX-ACCESS  not-accessible
   STATUS      current
   DESCRIPTION
      ""
   INDEX      { er1646v2EfmPppOETableIx,
                er1646v2EfmPppOEIpV6DhcpClientVendorClTableIx }
   ::= {er1646v2EfmPppOEIpV6DhcpClientVendorCl 1}

Er1646v2EfmPppOEIpV6DhcpClientVendorClEntry ::=
   SEQUENCE
      {
      er1646v2EfmPppOEIpV6DhcpClientVendorClActions
         VariableLengthTableActions,
      er1646v2EfmPppOEIpV6DhcpClientVendorClTableIx
         TableIndex,
      er1646v2EfmPppOEIpV6DhcpClientVendorClValueAscii
         DisplayString,
      er1646v2EfmPppOEIpV6DhcpClientVendorClValueDecimal
         Integer32,
      er1646v2EfmPppOEIpV6DhcpClientVendorClValueHexData
         OCTET STRING
      }

er1646v2EfmPppOEIpV6DhcpClientVendorClActions OBJECT-TYPE
   SYNTAX      VariableLengthTableActions
   MAX-ACCESS  read-write
   STATUS      current
   DESCRIPTION
      "By way of this field, some manipulations
       on this table may be performed."
   ::= {er1646v2EfmPppOEIpV6DhcpClientVendorClEntry 2}

er1646v2EfmPppOEIpV6DhcpClientVendorClTableIx OBJECT-TYPE
   SYNTAX      TableIndex
   MAX-ACCESS  not-accessible
   STATUS      current
   DESCRIPTION
      ""
   ::= {er1646v2EfmPppOEIpV6DhcpClientVendorClEntry 11}

er1646v2EfmPppOEIpV6DhcpClientVendorClValueAscii OBJECT-TYPE
   SYNTAX      DisplayString
   MAX-ACCESS  read-write
   STATUS      current
   DESCRIPTION
      "Path: efm.editConf.pppoEClient.ipV6.dhcp.client.vendorClassOpt.value.ascii"
   ::= {er1646v2EfmPppOEIpV6DhcpClientVendorClEntry 16842752}

er1646v2EfmPppOEIpV6DhcpClientVendorClValueDecimal OBJECT-TYPE
   SYNTAX      Integer32
   MAX-ACCESS  read-write
   STATUS      current
   DESCRIPTION
      "Path: efm.editConf.pppoEClient.ipV6.dhcp.client.vendorClassOpt.value.decimal"
   ::= {er1646v2EfmPppOEIpV6DhcpClientVendorClEntry 16908288}

er1646v2EfmPppOEIpV6DhcpClientVendorClValueHexData OBJECT-TYPE
   SYNTAX      OCTET STRING
   MAX-ACCESS  read-write
   STATUS      current
   DESCRIPTION
      "Path: efm.editConf.pppoEClient.ipV6.dhcp.client.vendorClassOpt.value.hexData"
   ::= {er1646v2EfmPppOEIpV6DhcpClientVendorClEntry 16973824}

er1646v2EfmPppOEIpV6DhcpRelayDestinations OBJECT-TYPE
   SYNTAX      SEQUENCE OF Er1646v2EfmPppOEIpV6DhcpRelayDestinationsEntry
   MAX-ACCESS  not-accessible
   STATUS      current
   DESCRIPTION
      ""
   ::= {er1646v2EfmPppOE 705323072}

er1646v2EfmPppOEIpV6DhcpRelayDestinationsEntry OBJECT-TYPE
   SYNTAX      Er1646v2EfmPppOEIpV6DhcpRelayDestinationsEntry
   MAX-ACCESS  not-accessible
   STATUS      current
   DESCRIPTION
      ""
   INDEX      { er1646v2EfmPppOETableIx,
                er1646v2EfmPppOEIpV6DhcpRelayDestinationsTableIx }
   ::= {er1646v2EfmPppOEIpV6DhcpRelayDestinations 1}

Er1646v2EfmPppOEIpV6DhcpRelayDestinationsEntry ::=
   SEQUENCE
      {
      er1646v2EfmPppOEIpV6DhcpRelayDestinationsActions
         VariableLengthTableActions,
      er1646v2EfmPppOEIpV6DhcpRelayDestinationsTableIx
         TableIndex,
      er1646v2EfmPppOEIpV6DhcpRelayDestinationsAddress
         Ipv6Address,
      er1646v2EfmPppOEIpV6DhcpRelayDestinationsInterface
         DisplayString
      }

er1646v2EfmPppOEIpV6DhcpRelayDestinationsActions OBJECT-TYPE
   SYNTAX      VariableLengthTableActions
   MAX-ACCESS  read-write
   STATUS      current
   DESCRIPTION
      "By way of this field, some manipulations
       on this table may be performed."
   ::= {er1646v2EfmPppOEIpV6DhcpRelayDestinationsEntry 2}

er1646v2EfmPppOEIpV6DhcpRelayDestinationsTableIx OBJECT-TYPE
   SYNTAX      TableIndex
   MAX-ACCESS  not-accessible
   STATUS      current
   DESCRIPTION
      ""
   ::= {er1646v2EfmPppOEIpV6DhcpRelayDestinationsEntry 11}

er1646v2EfmPppOEIpV6DhcpRelayDestinationsAddress OBJECT-TYPE
   SYNTAX      Ipv6Address
   MAX-ACCESS  read-write
   STATUS      current
   DESCRIPTION
      "Path: efm.editConf.pppoEClient.ipV6.dhcp.relay.destinations.address

       ipv6 address"
   ::= {er1646v2EfmPppOEIpV6DhcpRelayDestinationsEntry 16777216}

er1646v2EfmPppOEIpV6DhcpRelayDestinationsInterface OBJECT-TYPE
   SYNTAX      DisplayString
   MAX-ACCESS  read-write
   STATUS      current
   DESCRIPTION
      "Path: efm.editConf.pppoEClient.ipV6.dhcp.relay.destinations.interface"
   ::= {er1646v2EfmPppOEIpV6DhcpRelayDestinationsEntry 33554432}


er1646v2EfmDot1x OBJECT IDENTIFIER ::= {er1646v2Efm 191}

er1646v2EfmDot1xSSC OBJECT IDENTIFIER ::= {er1646v2EfmDot1x 1}

er1646v2EfmDot1xEntry OBJECT IDENTIFIER ::= {er1646v2EfmDot1xSSC 1}

er1646v2EfmDot1xMode OBJECT-TYPE
   SYNTAX      INTEGER
               {
               inactive (0),
               auto (1)
               }
   MAX-ACCESS  read-write
   STATUS      current
   DESCRIPTION
      "Path: efm.editConf.dot1x.mode

       Possibilities:
               inactive   (0)
               auto   (1)"
   ::= {er1646v2EfmDot1xEntry 16777216}

er1646v2EfmDot1xMaxHosts OBJECT-TYPE
   SYNTAX      Integer32
   MAX-ACCESS  read-write
   STATUS      current
   DESCRIPTION
      "Path: efm.editConf.dot1x.maxHosts"
   ::= {er1646v2EfmDot1xEntry 33554432}

er1646v2EfmDot1xReAuthentication OBJECT-TYPE
   SYNTAX      INTEGER
               {
               disabled (0),
               enabled (1)
               }
   MAX-ACCESS  read-write
   STATUS      current
   DESCRIPTION
      "Path: efm.editConf.dot1x.reAuthentication

       Possibilities:
               disabled   (0)
               enabled   (1)"
   ::= {er1646v2EfmDot1xEntry 50331648}

er1646v2EfmDot1xReAuthPeriod OBJECT-TYPE
   SYNTAX      TimeTicks
   MAX-ACCESS  read-write
   STATUS      current
   DESCRIPTION
      "Path: efm.editConf.dot1x.reAuthPeriod

       Time in centi-second."
   ::= {er1646v2EfmDot1xEntry 67108864}

er1646v2EfmDot1xQuietPeriod OBJECT-TYPE
   SYNTAX      TimeTicks
   MAX-ACCESS  read-write
   STATUS      current
   DESCRIPTION
      "Path: efm.editConf.dot1x.quietPeriod

       Time in centi-second."
   ::= {er1646v2EfmDot1xEntry 83886080}

er1646v2EfmDot1xSupplTimeout OBJECT-TYPE
   SYNTAX      TimeTicks
   MAX-ACCESS  read-write
   STATUS      current
   DESCRIPTION
      "Path: efm.editConf.dot1x.supplTimeout

       Time in centi-second."
   ::= {er1646v2EfmDot1xEntry 100663296}

er1646v2EfmDot1xServerTimeout OBJECT-TYPE
   SYNTAX      TimeTicks
   MAX-ACCESS  read-write
   STATUS      current
   DESCRIPTION
      "Path: efm.editConf.dot1x.serverTimeout

       Time in centi-second."
   ::= {er1646v2EfmDot1xEntry 117440512}

er1646v2EfmDot1xMaxReqCount OBJECT-TYPE
   SYNTAX      Integer32
   MAX-ACCESS  read-write
   STATUS      current
   DESCRIPTION
      "Path: efm.editConf.dot1x.maxReqCount"
   ::= {er1646v2EfmDot1xEntry 134217728}


er1646v2EfmName OBJECT-TYPE
   SYNTAX      DisplayString
   MAX-ACCESS  read-write
   STATUS      current
   DESCRIPTION
      "Path: efm.editConf.name
       Info: config interface name"
   ::= {er1646v2Efm 2}


er1646v2EfmMode OBJECT-TYPE
   SYNTAX      INTEGER
               {
               bridging (0),
               routing (1),
               routingAndBridging (2),
               ipV6 (3),
               ipV6ipV4 (4),
               multilink (5)
               }
   MAX-ACCESS  read-write
   STATUS      current
   DESCRIPTION
      "Path: efm.editConf.mode
       Info: routing and/or bridging or ipV6 or multilink selection

       Possibilities:
               bridging   (0)
               routing   (1)
               routingAndBridging   (2)
               ipV6   (3)
               ipV6/ipV4   (4)
               multilink   (5)"
   ::= {er1646v2Efm 29}


er1646v2EfmIpV6 OBJECT IDENTIFIER ::= {er1646v2Efm 15}

er1646v2EfmIpV6SSC OBJECT IDENTIFIER ::= {er1646v2EfmIpV6 1}

er1646v2EfmIpV6Entry OBJECT IDENTIFIER ::= {er1646v2EfmIpV6SSC 1}

er1646v2EfmIpV6VrfRouter OBJECT-TYPE
   SYNTAX      DisplayString
   MAX-ACCESS  read-write
   STATUS      current
   DESCRIPTION
      "Path: efm.editConf.ipV6.vrfRouter"
   ::= {er1646v2EfmIpV6Entry 16777216}

er1646v2EfmIpV6AddrAutoConfigNrDupAddrDetects OBJECT-TYPE
   SYNTAX      Integer32
   MAX-ACCESS  read-write
   STATUS      current
   DESCRIPTION
      "Path: efm.editConf.ipV6.addrAutoConfig.nrDupAddrDetects"
   ::= {er1646v2EfmIpV6Entry 67174400}

er1646v2EfmIpV6AddrAutoConfigAcceptRa OBJECT-TYPE
   SYNTAX      INTEGER
               {
               disabled (0),
               enabled (1)
               }
   MAX-ACCESS  read-write
   STATUS      current
   DESCRIPTION
      "Path: efm.editConf.ipV6.addrAutoConfig.acceptRa

       Possibilities:
               disabled   (0)
               enabled   (1)"
   ::= {er1646v2EfmIpV6Entry 67239936}

er1646v2EfmIpV6AddrAutoConfigAcceptRaRdnss OBJECT-TYPE
   SYNTAX      INTEGER
               {
               disabled (0),
               enabled (1)
               }
   MAX-ACCESS  read-write
   STATUS      current
   DESCRIPTION
      "Path: efm.editConf.ipV6.addrAutoConfig.acceptRaRdnss

       Possibilities:
               disabled   (0)
               enabled   (1)"
   ::= {er1646v2EfmIpV6Entry 67305472}

er1646v2EfmIpV6AddrAutoConfigAcceptRaDnssl OBJECT-TYPE
   SYNTAX      INTEGER
               {
               disabled (0),
               enabled (1)
               }
   MAX-ACCESS  read-write
   STATUS      current
   DESCRIPTION
      "Path: efm.editConf.ipV6.addrAutoConfig.acceptRaDnssl

       Possibilities:
               disabled   (0)
               enabled   (1)"
   ::= {er1646v2EfmIpV6Entry 67371008}

er1646v2EfmIpV6DefaultRoute OBJECT-TYPE
   SYNTAX      INTEGER
               {
               disabled (0),
               enabled (1)
               }
   MAX-ACCESS  read-write
   STATUS      current
   DESCRIPTION
      "Path: efm.editConf.ipV6.defaultRoute

       Possibilities:
               disabled   (0)
               enabled   (1)"
   ::= {er1646v2EfmIpV6Entry 83886080}

er1646v2EfmIpV6RaSend OBJECT-TYPE
   SYNTAX      INTEGER
               {
               disabled (0),
               enabled (1)
               }
   MAX-ACCESS  read-write
   STATUS      current
   DESCRIPTION
      "Path: efm.editConf.ipV6.ra.send

       Possibilities:
               disabled   (0)
               enabled   (1)"
   ::= {er1646v2EfmIpV6Entry 100728832}

er1646v2EfmIpV6RaMinInterval OBJECT-TYPE
   SYNTAX      TimeTicks
   MAX-ACCESS  read-write
   STATUS      current
   DESCRIPTION
      "Path: efm.editConf.ipV6.ra.minInterval

       Time in centi-second."
   ::= {er1646v2EfmIpV6Entry 100794368}

er1646v2EfmIpV6RaMaxInterval OBJECT-TYPE
   SYNTAX      TimeTicks
   MAX-ACCESS  read-write
   STATUS      current
   DESCRIPTION
      "Path: efm.editConf.ipV6.ra.maxInterval

       Time in centi-second."
   ::= {er1646v2EfmIpV6Entry 100859904}

er1646v2EfmIpV6RaManagedFlag OBJECT-TYPE
   SYNTAX      INTEGER
               {
               disabled (0),
               enabled (1)
               }
   MAX-ACCESS  read-write
   STATUS      current
   DESCRIPTION
      "Path: efm.editConf.ipV6.ra.managedFlag

       Possibilities:
               disabled   (0)
               enabled   (1)"
   ::= {er1646v2EfmIpV6Entry 100925440}

er1646v2EfmIpV6RaOtherConfFlag OBJECT-TYPE
   SYNTAX      INTEGER
               {
               disabled (0),
               enabled (1)
               }
   MAX-ACCESS  read-write
   STATUS      current
   DESCRIPTION
      "Path: efm.editConf.ipV6.ra.otherConfFlag

       Possibilities:
               disabled   (0)
               enabled   (1)"
   ::= {er1646v2EfmIpV6Entry 100990976}

er1646v2EfmIpV6RaLinkMtu OBJECT-TYPE
   SYNTAX      Integer32
   MAX-ACCESS  read-write
   STATUS      current
   DESCRIPTION
      "Path: efm.editConf.ipV6.ra.linkMtu"
   ::= {er1646v2EfmIpV6Entry 101056512}

er1646v2EfmIpV6RaReachableTime OBJECT-TYPE
   SYNTAX      TimeTicks
   MAX-ACCESS  read-write
   STATUS      current
   DESCRIPTION
      "Path: efm.editConf.ipV6.ra.reachableTime

       Time in centi-second."
   ::= {er1646v2EfmIpV6Entry 101122048}

er1646v2EfmIpV6RaRetransmitTime OBJECT-TYPE
   SYNTAX      TimeTicks
   MAX-ACCESS  read-write
   STATUS      current
   DESCRIPTION
      "Path: efm.editConf.ipV6.ra.retransmitTime

       Time in centi-second."
   ::= {er1646v2EfmIpV6Entry 101187584}

er1646v2EfmIpV6RaHopLimit OBJECT-TYPE
   SYNTAX      Integer32
   MAX-ACCESS  read-write
   STATUS      current
   DESCRIPTION
      "Path: efm.editConf.ipV6.ra.hopLimit"
   ::= {er1646v2EfmIpV6Entry 101253120}

er1646v2EfmIpV6RaDefaultLifeTime OBJECT-TYPE
   SYNTAX      TimeTicks
   MAX-ACCESS  read-write
   STATUS      current
   DESCRIPTION
      "Path: efm.editConf.ipV6.ra.defaultLifeTime

       Time in centi-second."
   ::= {er1646v2EfmIpV6Entry 101318656}

er1646v2EfmIpV6RaDnsOptionsRdnssLifeTime OBJECT-TYPE
   SYNTAX      TimeTicks
   MAX-ACCESS  read-write
   STATUS      current
   DESCRIPTION
      "Path: efm.editConf.ipV6.ra.dnsOptions.rdnss.lifeTime

       Time in centi-second."
   ::= {er1646v2EfmIpV6Entry 101393408}

er1646v2EfmIpV6RaDnsOptionsRdnssImportServers OBJECT-TYPE
   SYNTAX      INTEGER
               {
               disabled (0),
               enabled (1)
               }
   MAX-ACCESS  read-write
   STATUS      current
   DESCRIPTION
      "Path: efm.editConf.ipV6.ra.dnsOptions.rdnss.importServers

       Possibilities:
               disabled   (0)
               enabled   (1)"
   ::= {er1646v2EfmIpV6Entry 101395456}

er1646v2EfmIpV6RaDnsOptionsDnsslLifeTime OBJECT-TYPE
   SYNTAX      TimeTicks
   MAX-ACCESS  read-write
   STATUS      current
   DESCRIPTION
      "Path: efm.editConf.ipV6.ra.dnsOptions.dnssl.lifeTime

       Time in centi-second."
   ::= {er1646v2EfmIpV6Entry 101401600}

er1646v2EfmIpV6RaDnsOptionsDnsslImportDomains OBJECT-TYPE
   SYNTAX      INTEGER
               {
               disabled (0),
               enabled (1)
               }
   MAX-ACCESS  read-write
   STATUS      current
   DESCRIPTION
      "Path: efm.editConf.ipV6.ra.dnsOptions.dnssl.importDomains

       Possibilities:
               disabled   (0)
               enabled   (1)"
   ::= {er1646v2EfmIpV6Entry 101403648}

er1646v2EfmIpV6RsSend OBJECT-TYPE
   SYNTAX      INTEGER
               {
               disabled (0),
               enabled (1)
               }
   MAX-ACCESS  read-write
   STATUS      current
   DESCRIPTION
      "Path: efm.editConf.ipV6.rs.send

       Possibilities:
               disabled   (0)
               enabled   (1)"
   ::= {er1646v2EfmIpV6Entry 335609856}

er1646v2EfmIpV6RsMaxRandomDelay OBJECT-TYPE
   SYNTAX      TimeTicks
   MAX-ACCESS  read-write
   STATUS      current
   DESCRIPTION
      "Path: efm.editConf.ipV6.rs.maxRandomDelay

       Time in centi-second."
   ::= {er1646v2EfmIpV6Entry 335675392}

er1646v2EfmIpV6RsInterval OBJECT-TYPE
   SYNTAX      TimeTicks
   MAX-ACCESS  read-write
   STATUS      current
   DESCRIPTION
      "Path: efm.editConf.ipV6.rs.interval

       Time in centi-second."
   ::= {er1646v2EfmIpV6Entry 335740928}

er1646v2EfmIpV6RsMaxSolicitations OBJECT-TYPE
   SYNTAX      Integer32
   MAX-ACCESS  read-write
   STATUS      current
   DESCRIPTION
      "Path: efm.editConf.ipV6.rs.maxSolicitations"
   ::= {er1646v2EfmIpV6Entry 335806464}

er1646v2EfmIpV6TrafficPolicyInbound OBJECT-TYPE
   SYNTAX      DisplayString
   MAX-ACCESS  read-write
   STATUS      current
   DESCRIPTION
      "Path: efm.editConf.ipV6.trafficPolicy.inbound"
   ::= {er1646v2EfmIpV6Entry 184614912}

er1646v2EfmIpV6TrafficPolicyOutbound OBJECT-TYPE
   SYNTAX      DisplayString
   MAX-ACCESS  read-write
   STATUS      current
   DESCRIPTION
      "Path: efm.editConf.ipV6.trafficPolicy.outbound"
   ::= {er1646v2EfmIpV6Entry 184680448}

er1646v2EfmIpV6FirewallZone OBJECT-TYPE
   SYNTAX      DisplayString
   MAX-ACCESS  read-write
   STATUS      current
   DESCRIPTION
      "Path: efm.editConf.ipV6.firewall.zone"
   ::= {er1646v2EfmIpV6Entry 201392128}

er1646v2EfmIpV6DhcpClientAddrAC OBJECT-TYPE
   SYNTAX      INTEGER
               {
               disabled (0),
               enabled (1)
               }
   MAX-ACCESS  read-write
   STATUS      current
   DESCRIPTION
      "Path: efm.editConf.ipV6.dhcp.client.addrAutoConfig

       Possibilities:
               disabled   (0)
               enabled   (1)"
   ::= {er1646v2EfmIpV6Entry 170131456}

er1646v2EfmIpV6DhcpClientPrDelMode OBJECT-TYPE
   SYNTAX      INTEGER
               {
               disabled (0),
               enabled (1)
               }
   MAX-ACCESS  read-write
   STATUS      current
   DESCRIPTION
      "Path: efm.editConf.ipV6.dhcp.client.pd.mode

       Possibilities:
               disabled   (0)
               enabled   (1)"
   ::= {er1646v2EfmIpV6Entry 170394624}

er1646v2EfmIpV6DhcpClientPrDelPool OBJECT-TYPE
   SYNTAX      DisplayString
   MAX-ACCESS  read-write
   STATUS      current
   DESCRIPTION
      "Path: efm.editConf.ipV6.dhcp.client.pd.pool"
   ::= {er1646v2EfmIpV6Entry 170395648}

er1646v2EfmIpV6DhcpClientPrDelPdExclOpt OBJECT-TYPE
   SYNTAX      INTEGER
               {
               disabled (0),
               enabled (1)
               }
   MAX-ACCESS  read-write
   STATUS      current
   DESCRIPTION
      "Path: efm.editConf.ipV6.dhcp.client.pd.pdExclOpt

       Possibilities:
               disabled   (0)
               enabled   (1)"
   ::= {er1646v2EfmIpV6Entry 170396672}

er1646v2EfmIpV6DhcpClientDnsServerPref OBJECT-TYPE
   SYNTAX      Integer32
   MAX-ACCESS  read-write
   STATUS      current
   DESCRIPTION
      "Path: efm.editConf.ipV6.dhcp.client.dns.serverPref"
   ::= {er1646v2EfmIpV6Entry 170918912}

er1646v2EfmIpV6DhcpClientRapidCommit OBJECT-TYPE
   SYNTAX      INTEGER
               {
               disabled (0),
               enabled (1)
               }
   MAX-ACCESS  read-write
   STATUS      current
   DESCRIPTION
      "Path: efm.editConf.ipV6.dhcp.client.rapidCommit

       Possibilities:
               disabled   (0)
               enabled   (1)"
   ::= {er1646v2EfmIpV6Entry 170655744}

er1646v2EfmIpV6DhcpClientTimersSolTimeOut OBJECT-TYPE
   SYNTAX      TimeTicks
   MAX-ACCESS  read-write
   STATUS      current
   DESCRIPTION
      "Path: efm.editConf.ipV6.dhcp.client.timers.solTimeOut

       Time in centi-second."
   ::= {er1646v2EfmIpV6Entry 171181056}

er1646v2EfmIpV6DhcpClientTimersSolMaxRt OBJECT-TYPE
   SYNTAX      TimeTicks
   MAX-ACCESS  read-write
   STATUS      current
   DESCRIPTION
      "Path: efm.editConf.ipV6.dhcp.client.timers.solMaxRt

       Time in centi-second."
   ::= {er1646v2EfmIpV6Entry 171182080}

er1646v2EfmIpV6DhcpClientTimersInfoRefresh OBJECT-TYPE
   SYNTAX      TimeTicks
   MAX-ACCESS  read-write
   STATUS      current
   DESCRIPTION
      "Path: efm.editConf.ipV6.dhcp.client.timers.infoRefresh

       Time in centi-second."
   ::= {er1646v2EfmIpV6Entry 171183104}

er1646v2EfmIpV6DhcpServerMode OBJECT-TYPE
   SYNTAX      INTEGER
               {
               disabled (0),
               enabled (1)
               }
   MAX-ACCESS  read-write
   STATUS      current
   DESCRIPTION
      "Path: efm.editConf.ipV6.dhcp.server.mode

       Possibilities:
               disabled   (0)
               enabled   (1)"
   ::= {er1646v2EfmIpV6Entry 172228608}

er1646v2EfmIpV6DhcpServerPreference OBJECT-TYPE
   SYNTAX      Integer32
   MAX-ACCESS  read-write
   STATUS      current
   DESCRIPTION
      "Path: efm.editConf.ipV6.dhcp.server.preference"
   ::= {er1646v2EfmIpV6Entry 172490752}

er1646v2EfmIpV6DhcpServerPool OBJECT-TYPE
   SYNTAX      DisplayString
   MAX-ACCESS  read-write
   STATUS      current
   DESCRIPTION
      "Path: efm.editConf.ipV6.dhcp.server.pool"
   ::= {er1646v2EfmIpV6Entry 172752896}

er1646v2EfmIpV6DhcpServerRapidCommit OBJECT-TYPE
   SYNTAX      INTEGER
               {
               disabled (0),
               enabled (1)
               }
   MAX-ACCESS  read-write
   STATUS      current
   DESCRIPTION
      "Path: efm.editConf.ipV6.dhcp.server.rapidCommit

       Possibilities:
               disabled   (0)
               enabled   (1)"
   ::= {er1646v2EfmIpV6Entry 173015040}

er1646v2EfmIpV6DhcpServerTimersInfoRefresh OBJECT-TYPE
   SYNTAX      TimeTicks
   MAX-ACCESS  read-write
   STATUS      current
   DESCRIPTION
      "Path: efm.editConf.ipV6.dhcp.server.timers.infoRefresh

       Time in centi-second."
   ::= {er1646v2EfmIpV6Entry 173278208}

er1646v2EfmIpV6DhcpRelayMode OBJECT-TYPE
   SYNTAX      INTEGER
               {
               disabled (0),
               enabled (1)
               }
   MAX-ACCESS  read-write
   STATUS      current
   DESCRIPTION
      "Path: efm.editConf.ipV6.dhcp.relay.mode

       Possibilities:
               disabled   (0)
               enabled   (1)"
   ::= {er1646v2EfmIpV6Entry 174071808}

er1646v2EfmIpV6SendRedirect OBJECT-TYPE
   SYNTAX      INTEGER
               {
               disabled (0),
               enabled (1)
               }
   MAX-ACCESS  read-write
   STATUS      current
   DESCRIPTION
      "Path: efm.editConf.ipV6.sendRedirect

       Possibilities:
               disabled   (0)
               enabled   (1)"
   ::= {er1646v2EfmIpV6Entry 117440512}

er1646v2EfmIpV6LinkMtu OBJECT-TYPE
   SYNTAX      Integer32
   MAX-ACCESS  read-write
   STATUS      current
   DESCRIPTION
      "Path: efm.editConf.ipV6.linkMtu"
   ::= {er1646v2EfmIpV6Entry 134217728}

er1646v2EfmIpV6InterfaceId OBJECT-TYPE
   SYNTAX      OCTET STRING
   MAX-ACCESS  read-write
   STATUS      current
   DESCRIPTION
      "Path: efm.editConf.ipV6.interfaceId"
   ::= {er1646v2EfmIpV6Entry 150994944}

er1646v2EfmIpV6MF OBJECT-TYPE
   SYNTAX      Integer32
   MAX-ACCESS  read-write
   STATUS      current
   DESCRIPTION
      "Path: efm.editConf.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1646v2EfmIpV6Entry 285212672}

er1646v2EfmIpV6IcmpMessagesNoRoute OBJECT-TYPE
   SYNTAX      INTEGER
               {
               disabled (0),
               enabled (1)
               }
   MAX-ACCESS  read-write
   STATUS      current
   DESCRIPTION
      "Path: efm.editConf.ipV6.icmpMessages.noRoute

       Possibilities:
               disabled   (0)
               enabled   (1)"
   ::= {er1646v2EfmIpV6Entry 302055424}

er1646v2EfmIpV6IcmpMessagesBeyondScope OBJECT-TYPE
   SYNTAX      INTEGER
               {
               disabled (0),
               enabled (1)
               }
   MAX-ACCESS  read-write
   STATUS      current
   DESCRIPTION
      "Path: efm.editConf.ipV6.icmpMessages.beyondScope

       Possibilities:
               disabled   (0)
               enabled   (1)"
   ::= {er1646v2EfmIpV6Entry 302186496}

er1646v2EfmIpV6IcmpMessagesAddressUnreachable OBJECT-TYPE
   SYNTAX      INTEGER
               {
               disabled (0),
               enabled (1)
               }
   MAX-ACCESS  read-write
   STATUS      current
   DESCRIPTION
      "Path: efm.editConf.ipV6.icmpMessages.addressUnreachable

       Possibilities:
               disabled   (0)
               enabled   (1)"
   ::= {er1646v2EfmIpV6Entry 302252032}

er1646v2EfmIpV6IcmpMessagesPortUnreachable OBJECT-TYPE
   SYNTAX      INTEGER
               {
               disabled (0),
               enabled (1)
               }
   MAX-ACCESS  read-write
   STATUS      current
   DESCRIPTION
      "Path: efm.editConf.ipV6.icmpMessages.portUnreachable

       Possibilities:
               disabled   (0)
               enabled   (1)"
   ::= {er1646v2EfmIpV6Entry 302317568}

er1646v2EfmIpV6IcmpMessagesPacketTooBig OBJECT-TYPE
   SYNTAX      INTEGER
               {
               disabled (0),
               enabled (1)
               }
   MAX-ACCESS  read-write
   STATUS      current
   DESCRIPTION
      "Path: efm.editConf.ipV6.icmpMessages.packetTooBig

       Possibilities:
               disabled   (0)
               enabled   (1)"
   ::= {er1646v2EfmIpV6Entry 302645248}

er1646v2EfmIpV6IcmpMessagesHopLimitExceeded OBJECT-TYPE
   SYNTAX      INTEGER
               {
               disabled (0),
               enabled (1)
               }
   MAX-ACCESS  read-write
   STATUS      current
   DESCRIPTION
      "Path: efm.editConf.ipV6.icmpMessages.hopLimitExceeded

       Possibilities:
               disabled   (0)
               enabled   (1)"
   ::= {er1646v2EfmIpV6Entry 303300608}

er1646v2EfmIpV6IcmpMessagesFragTimeExceeded OBJECT-TYPE
   SYNTAX      INTEGER
               {
               disabled (0),
               enabled (1)
               }
   MAX-ACCESS  read-write
   STATUS      current
   DESCRIPTION
      "Path: efm.editConf.ipV6.icmpMessages.fragTimeExceeded

       Possibilities:
               disabled   (0)
               enabled   (1)"
   ::= {er1646v2EfmIpV6Entry 303366144}

er1646v2EfmIpV6IcmpMessagesHeaderFieldErr OBJECT-TYPE
   SYNTAX      INTEGER
               {
               disabled (0),
               enabled (1)
               }
   MAX-ACCESS  read-write
   STATUS      current
   DESCRIPTION
      "Path: efm.editConf.ipV6.icmpMessages.headerFieldErr

       Possibilities:
               disabled   (0)
               enabled   (1)"
   ::= {er1646v2EfmIpV6Entry 303955968}

er1646v2EfmIpV6IcmpMessagesOptionUnrecognized OBJECT-TYPE
   SYNTAX      INTEGER
               {
               disabled (0),
               enabled (1)
               }
   MAX-ACCESS  read-write
   STATUS      current
   DESCRIPTION
      "Path: efm.editConf.ipV6.icmpMessages.optionUnrecognized

       Possibilities:
               disabled   (0)
               enabled   (1)"
   ::= {er1646v2EfmIpV6Entry 304087040}

er1646v2EfmIpV6IcmpMessagesRedirect OBJECT-TYPE
   SYNTAX      INTEGER
               {
               disabled (0),
               enabled (1)
               }
   MAX-ACCESS  read-write
   STATUS      current
   DESCRIPTION
      "Path: efm.editConf.ipV6.icmpMessages.redirect

       Possibilities:
               disabled   (0)
               enabled   (1)"
   ::= {er1646v2EfmIpV6Entry 304611328}

er1646v2EfmIpV6Addresses OBJECT-TYPE
   SYNTAX      SEQUENCE OF Er1646v2EfmIpV6AddressesEntry
   MAX-ACCESS  not-accessible
   STATUS      current
   DESCRIPTION
      ""
   ::= {er1646v2EfmIpV6 50331648}

er1646v2EfmIpV6AddressesEntry OBJECT-TYPE
   SYNTAX      Er1646v2EfmIpV6AddressesEntry
   MAX-ACCESS  not-accessible
   STATUS      current
   DESCRIPTION
      ""
   INDEX      { er1646v2EfmIpV6AddressesTableIx }
   ::= {er1646v2EfmIpV6Addresses 1}

Er1646v2EfmIpV6AddressesEntry ::=
   SEQUENCE
      {
      er1646v2EfmIpV6AddressesActions
         VariableLengthTableActions,
      er1646v2EfmIpV6AddressesTableIx
         TableIndex,
      er1646v2EfmIpV6AddressesType
         INTEGER,
      er1646v2EfmIpV6AddressesAddress
         Ipv6Address,
      er1646v2EfmIpV6AddressesPrefixLength
         Integer32,
      er1646v2EfmIpV6AddressesGeneralPrefix
         DisplayString,
      er1646v2EfmIpV6AddressesRaSend
         INTEGER,
      er1646v2EfmIpV6AddressesRaOnLinkFlag
         INTEGER,
      er1646v2EfmIpV6AddressesRaAutoFlag
         INTEGER,
      er1646v2EfmIpV6AddressesRaValidLifeTime
         TimeTicks,
      er1646v2EfmIpV6AddressesRaValidLTMode
         INTEGER,
      er1646v2EfmIpV6AddressesRaPrefLifeTime
         TimeTicks,
      er1646v2EfmIpV6AddressesRaPrefLTMode
         INTEGER
      }

er1646v2EfmIpV6AddressesActions OBJECT-TYPE
   SYNTAX      VariableLengthTableActions
   MAX-ACCESS  read-write
   STATUS      current
   DESCRIPTION
      "By way of this field, some manipulations
       on this table may be performed."
   ::= {er1646v2EfmIpV6AddressesEntry 2}

er1646v2EfmIpV6AddressesTableIx OBJECT-TYPE
   SYNTAX      TableIndex
   MAX-ACCESS  not-accessible
   STATUS      current
   DESCRIPTION
      ""
   ::= {er1646v2EfmIpV6AddressesEntry 11}

er1646v2EfmIpV6AddressesType OBJECT-TYPE
   SYNTAX      INTEGER
               {
               unicast (0),
               eui64 (1),
               anycast (2),
               linkLocal (3),
               generalPrefix (4)
               }
   MAX-ACCESS  read-write
   STATUS      current
   DESCRIPTION
      "Path: efm.editConf.ipV6.addresses.type

       Possibilities:
               unicast   (0)
               eui64   (1)
               anycast   (2)
               linkLocal   (3)
               generalPrefix   (4)"
   ::= {er1646v2EfmIpV6AddressesEntry 50331648}

er1646v2EfmIpV6AddressesAddress OBJECT-TYPE
   SYNTAX      Ipv6Address
   MAX-ACCESS  read-write
   STATUS      current
   DESCRIPTION
      "Path: efm.editConf.ipV6.addresses.address

       ipv6 address"
   ::= {er1646v2EfmIpV6AddressesEntry 16777216}

er1646v2EfmIpV6AddressesPrefixLength OBJECT-TYPE
   SYNTAX      Integer32
   MAX-ACCESS  read-write
   STATUS      current
   DESCRIPTION
      "Path: efm.editConf.ipV6.addresses.prefixLength"
   ::= {er1646v2EfmIpV6AddressesEntry 33554432}

er1646v2EfmIpV6AddressesGeneralPrefix OBJECT-TYPE
   SYNTAX      DisplayString
   MAX-ACCESS  read-write
   STATUS      current
   DESCRIPTION
      "Path: efm.editConf.ipV6.addresses.generalPrefix"
   ::= {er1646v2EfmIpV6AddressesEntry 83886080}

er1646v2EfmIpV6AddressesRaSend OBJECT-TYPE
   SYNTAX      INTEGER
               {
               disabled (0),
               enabled (1)
               }
   MAX-ACCESS  read-write
   STATUS      current
   DESCRIPTION
      "Path: efm.editConf.ipV6.addresses.ra.send

       Possibilities:
               disabled   (0)
               enabled   (1)"
   ::= {er1646v2EfmIpV6AddressesEntry 67174400}

er1646v2EfmIpV6AddressesRaOnLinkFlag OBJECT-TYPE
   SYNTAX      INTEGER
               {
               disabled (0),
               enabled (1)
               }
   MAX-ACCESS  read-write
   STATUS      current
   DESCRIPTION
      "Path: efm.editConf.ipV6.addresses.ra.onLinkFlag

       Possibilities:
               disabled   (0)
               enabled   (1)"
   ::= {er1646v2EfmIpV6AddressesEntry 67371008}

er1646v2EfmIpV6AddressesRaAutoFlag OBJECT-TYPE
   SYNTAX      INTEGER
               {
               disabled (0),
               enabled (1)
               }
   MAX-ACCESS  read-write
   STATUS      current
   DESCRIPTION
      "Path: efm.editConf.ipV6.addresses.ra.autonomousFlag

       Possibilities:
               disabled   (0)
               enabled   (1)"
   ::= {er1646v2EfmIpV6AddressesEntry 67567616}

er1646v2EfmIpV6AddressesRaValidLifeTime OBJECT-TYPE
   SYNTAX      TimeTicks
   MAX-ACCESS  read-write
   STATUS      current
   DESCRIPTION
      "Path: efm.editConf.ipV6.addresses.ra.validLifeTime

       Time in centi-second."
   ::= {er1646v2EfmIpV6AddressesEntry 67239936}

er1646v2EfmIpV6AddressesRaValidLTMode OBJECT-TYPE
   SYNTAX      INTEGER
               {
               fixed (0),
               infinite (2)
               }
   MAX-ACCESS  read-write
   STATUS      current
   DESCRIPTION
      "Path: efm.editConf.ipV6.addresses.ra.validLifeTimeMode

       Possibilities:
               fixed   (0)
               infinite   (2)"
   ::= {er1646v2EfmIpV6AddressesEntry 67305472}

er1646v2EfmIpV6AddressesRaPrefLifeTime OBJECT-TYPE
   SYNTAX      TimeTicks
   MAX-ACCESS  read-write
   STATUS      current
   DESCRIPTION
      "Path: efm.editConf.ipV6.addresses.ra.prefLifeTime

       Time in centi-second."
   ::= {er1646v2EfmIpV6AddressesEntry 67436544}

er1646v2EfmIpV6AddressesRaPrefLTMode OBJECT-TYPE
   SYNTAX      INTEGER
               {
               fixed (0),
               infinite (2)
               }
   MAX-ACCESS  read-write
   STATUS      current
   DESCRIPTION
      "Path: efm.editConf.ipV6.addresses.ra.prefLifeTimeMode

       Possibilities:
               fixed   (0)
               infinite   (2)"
   ::= {er1646v2EfmIpV6AddressesEntry 67502080}

er1646v2EfmIpV6RaDnsOptionsRdnssServers OBJECT-TYPE
   SYNTAX      SEQUENCE OF Er1646v2EfmIpV6RaDnsOptionsRdnssServersEntry
   MAX-ACCESS  not-accessible
   STATUS      current
   DESCRIPTION
      ""
   ::= {er1646v2EfmIpV6 101394432}

er1646v2EfmIpV6RaDnsOptionsRdnssServersEntry OBJECT-TYPE
   SYNTAX      Er1646v2EfmIpV6RaDnsOptionsRdnssServersEntry
   MAX-ACCESS  not-accessible
   STATUS      current
   DESCRIPTION
      ""
   INDEX      { er1646v2EfmIpV6RaDnsOptionsRdnssServersTableIx }
   ::= {er1646v2EfmIpV6RaDnsOptionsRdnssServers 1}

Er1646v2EfmIpV6RaDnsOptionsRdnssServersEntry ::=
   SEQUENCE
      {
      er1646v2EfmIpV6RaDnsOptionsRdnssServersActions
         VariableLengthTableActions,
      er1646v2EfmIpV6RaDnsOptionsRdnssServersTableIx
         TableIndex,
      er1646v2EfmIpV6RaDnsOptionsRdnssServersAddress
         Ipv6Address
      }

er1646v2EfmIpV6RaDnsOptionsRdnssServersActions OBJECT-TYPE
   SYNTAX      VariableLengthTableActions
   MAX-ACCESS  read-write
   STATUS      current
   DESCRIPTION
      "By way of this field, some manipulations
       on this table may be performed."
   ::= {er1646v2EfmIpV6RaDnsOptionsRdnssServersEntry 2}

er1646v2EfmIpV6RaDnsOptionsRdnssServersTableIx OBJECT-TYPE
   SYNTAX      TableIndex
   MAX-ACCESS  not-accessible
   STATUS      current
   DESCRIPTION
      ""
   ::= {er1646v2EfmIpV6RaDnsOptionsRdnssServersEntry 11}

er1646v2EfmIpV6RaDnsOptionsRdnssServersAddress OBJECT-TYPE
   SYNTAX      Ipv6Address
   MAX-ACCESS  read-write
   STATUS      current
   DESCRIPTION
      "Path: efm.editConf.ipV6.ra.dnsOptions.rdnss.servers.address

       ipv6 address"
   ::= {er1646v2EfmIpV6RaDnsOptionsRdnssServersEntry 16777216}

er1646v2EfmIpV6RaDnsOptionsDnsslDomains OBJECT-TYPE
   SYNTAX      SEQUENCE OF Er1646v2EfmIpV6RaDnsOptionsDnsslDomainsEntry
   MAX-ACCESS  not-accessible
   STATUS      current
   DESCRIPTION
      ""
   ::= {er1646v2EfmIpV6 101402624}

er1646v2EfmIpV6RaDnsOptionsDnsslDomainsEntry OBJECT-TYPE
   SYNTAX      Er1646v2EfmIpV6RaDnsOptionsDnsslDomainsEntry
   MAX-ACCESS  not-accessible
   STATUS      current
   DESCRIPTION
      ""
   INDEX      { er1646v2EfmIpV6RaDnsOptionsDnsslDomainsTableIx }
   ::= {er1646v2EfmIpV6RaDnsOptionsDnsslDomains 1}

Er1646v2EfmIpV6RaDnsOptionsDnsslDomainsEntry ::=
   SEQUENCE
      {
      er1646v2EfmIpV6RaDnsOptionsDnsslDomainsActions
         VariableLengthTableActions,
      er1646v2EfmIpV6RaDnsOptionsDnsslDomainsTableIx
         TableIndex,
      er1646v2EfmIpV6RaDnsOptionsDnsslDomainsName
         DisplayString
      }

er1646v2EfmIpV6RaDnsOptionsDnsslDomainsActions OBJECT-TYPE
   SYNTAX      VariableLengthTableActions
   MAX-ACCESS  read-write
   STATUS      current
   DESCRIPTION
      "By way of this field, some manipulations
       on this table may be performed."
   ::= {er1646v2EfmIpV6RaDnsOptionsDnsslDomainsEntry 2}

er1646v2EfmIpV6RaDnsOptionsDnsslDomainsTableIx OBJECT-TYPE
   SYNTAX      TableIndex
   MAX-ACCESS  not-accessible
   STATUS      current
   DESCRIPTION
      ""
   ::= {er1646v2EfmIpV6RaDnsOptionsDnsslDomainsEntry 11}

er1646v2EfmIpV6RaDnsOptionsDnsslDomainsName OBJECT-TYPE
   SYNTAX      DisplayString
   MAX-ACCESS  read-write
   STATUS      current
   DESCRIPTION
      "Path: efm.editConf.ipV6.ra.dnsOptions.dnssl.domains.name"
   ::= {er1646v2EfmIpV6RaDnsOptionsDnsslDomainsEntry 16777216}

er1646v2EfmIpV6DhcpClientUserClassOpt OBJECT-TYPE
   SYNTAX      SEQUENCE OF Er1646v2EfmIpV6DhcpClientUserClassOptEntry
   MAX-ACCESS  not-accessible
   STATUS      current
   DESCRIPTION
      ""
   ::= {er1646v2EfmIpV6 171442176}

er1646v2EfmIpV6DhcpClientUserClassOptEntry OBJECT-TYPE
   SYNTAX      Er1646v2EfmIpV6DhcpClientUserClassOptEntry
   MAX-ACCESS  not-accessible
   STATUS      current
   DESCRIPTION
      ""
   INDEX      { er1646v2EfmIpV6DhcpClientUserClassOptTableIx }
   ::= {er1646v2EfmIpV6DhcpClientUserClassOpt 1}

Er1646v2EfmIpV6DhcpClientUserClassOptEntry ::=
   SEQUENCE
      {
      er1646v2EfmIpV6DhcpClientUserClassOptActions
         VariableLengthTableActions,
      er1646v2EfmIpV6DhcpClientUserClassOptTableIx
         TableIndex,
      er1646v2EfmIpV6DhcpClientUserClassOptValueAscii
         DisplayString,
      er1646v2EfmIpV6DhcpClientUserClassOptValueDecimal
         Integer32,
      er1646v2EfmIpV6DhcpClientUserClassOptValueHexData
         OCTET STRING
      }

er1646v2EfmIpV6DhcpClientUserClassOptActions OBJECT-TYPE
   SYNTAX      VariableLengthTableActions
   MAX-ACCESS  read-write
   STATUS      current
   DESCRIPTION
      "By way of this field, some manipulations
       on this table may be performed."
   ::= {er1646v2EfmIpV6DhcpClientUserClassOptEntry 2}

er1646v2EfmIpV6DhcpClientUserClassOptTableIx OBJECT-TYPE
   SYNTAX      TableIndex
   MAX-ACCESS  not-accessible
   STATUS      current
   DESCRIPTION
      ""
   ::= {er1646v2EfmIpV6DhcpClientUserClassOptEntry 11}

er1646v2EfmIpV6DhcpClientUserClassOptValueAscii OBJECT-TYPE
   SYNTAX      DisplayString
   MAX-ACCESS  read-write
   STATUS      current
   DESCRIPTION
      "Path: efm.editConf.ipV6.dhcp.client.userClassOpt.value.ascii"
   ::= {er1646v2EfmIpV6DhcpClientUserClassOptEntry 16842752}

er1646v2EfmIpV6DhcpClientUserClassOptValueDecimal OBJECT-TYPE
   SYNTAX      Integer32
   MAX-ACCESS  read-write
   STATUS      current
   DESCRIPTION
      "Path: efm.editConf.ipV6.dhcp.client.userClassOpt.value.decimal"
   ::= {er1646v2EfmIpV6DhcpClientUserClassOptEntry 16908288}

er1646v2EfmIpV6DhcpClientUserClassOptValueHexData OBJECT-TYPE
   SYNTAX      OCTET STRING
   MAX-ACCESS  read-write
   STATUS      current
   DESCRIPTION
      "Path: efm.editConf.ipV6.dhcp.client.userClassOpt.value.hexData"
   ::= {er1646v2EfmIpV6DhcpClientUserClassOptEntry 16973824}

er1646v2EfmIpV6DhcpClientVendorCl OBJECT-TYPE
   SYNTAX      SEQUENCE OF Er1646v2EfmIpV6DhcpClientVendorClEntry
   MAX-ACCESS  not-accessible
   STATUS      current
   DESCRIPTION
      ""
   ::= {er1646v2EfmIpV6 171704320}

er1646v2EfmIpV6DhcpClientVendorClEntry OBJECT-TYPE
   SYNTAX      Er1646v2EfmIpV6DhcpClientVendorClEntry
   MAX-ACCESS  not-accessible
   STATUS      current
   DESCRIPTION
      ""
   INDEX      { er1646v2EfmIpV6DhcpClientVendorClTableIx }
   ::= {er1646v2EfmIpV6DhcpClientVendorCl 1}

Er1646v2EfmIpV6DhcpClientVendorClEntry ::=
   SEQUENCE
      {
      er1646v2EfmIpV6DhcpClientVendorClActions
         VariableLengthTableActions,
      er1646v2EfmIpV6DhcpClientVendorClTableIx
         TableIndex,
      er1646v2EfmIpV6DhcpClientVendorClValueAscii
         DisplayString,
      er1646v2EfmIpV6DhcpClientVendorClValueDecimal
         Integer32,
      er1646v2EfmIpV6DhcpClientVendorClValueHexData
         OCTET STRING
      }

er1646v2EfmIpV6DhcpClientVendorClActions OBJECT-TYPE
   SYNTAX      VariableLengthTableActions
   MAX-ACCESS  read-write
   STATUS      current
   DESCRIPTION
      "By way of this field, some manipulations
       on this table may be performed."
   ::= {er1646v2EfmIpV6DhcpClientVendorClEntry 2}

er1646v2EfmIpV6DhcpClientVendorClTableIx OBJECT-TYPE
   SYNTAX      TableIndex
   MAX-ACCESS  not-accessible
   STATUS      current
   DESCRIPTION
      ""
   ::= {er1646v2EfmIpV6DhcpClientVendorClEntry 11}

er1646v2EfmIpV6DhcpClientVendorClValueAscii OBJECT-TYPE
   SYNTAX      DisplayString
   MAX-ACCESS  read-write
   STATUS      current
   DESCRIPTION
      "Path: efm.editConf.ipV6.dhcp.client.vendorClassOpt.value.ascii"
   ::= {er1646v2EfmIpV6DhcpClientVendorClEntry 16842752}

er1646v2EfmIpV6DhcpClientVendorClValueDecimal OBJECT-TYPE
   SYNTAX      Integer32
   MAX-ACCESS  read-write
   STATUS      current
   DESCRIPTION
      "Path: efm.editConf.ipV6.dhcp.client.vendorClassOpt.value.decimal"
   ::= {er1646v2EfmIpV6DhcpClientVendorClEntry 16908288}

er1646v2EfmIpV6DhcpClientVendorClValueHexData OBJECT-TYPE
   SYNTAX      OCTET STRING
   MAX-ACCESS  read-write
   STATUS      current
   DESCRIPTION
      "Path: efm.editConf.ipV6.dhcp.client.vendorClassOpt.value.hexData"
   ::= {er1646v2EfmIpV6DhcpClientVendorClEntry 16973824}

er1646v2EfmIpV6DhcpRelayDestinations OBJECT-TYPE
   SYNTAX      SEQUENCE OF Er1646v2EfmIpV6DhcpRelayDestinationsEntry
   MAX-ACCESS  not-accessible
   STATUS      current
   DESCRIPTION
      ""
   ::= {er1646v2EfmIpV6 174080000}

er1646v2EfmIpV6DhcpRelayDestinationsEntry OBJECT-TYPE
   SYNTAX      Er1646v2EfmIpV6DhcpRelayDestinationsEntry
   MAX-ACCESS  not-accessible
   STATUS      current
   DESCRIPTION
      ""
   INDEX      { er1646v2EfmIpV6DhcpRelayDestinationsTableIx }
   ::= {er1646v2EfmIpV6DhcpRelayDestinations 1}

Er1646v2EfmIpV6DhcpRelayDestinationsEntry ::=
   SEQUENCE
      {
      er1646v2EfmIpV6DhcpRelayDestinationsActions
         VariableLengthTableActions,
      er1646v2EfmIpV6DhcpRelayDestinationsTableIx
         TableIndex,
      er1646v2EfmIpV6DhcpRelayDestinationsAddress
         Ipv6Address,
      er1646v2EfmIpV6DhcpRelayDestinationsInterface
         DisplayString
      }

er1646v2EfmIpV6DhcpRelayDestinationsActions OBJECT-TYPE
   SYNTAX      VariableLengthTableActions
   MAX-ACCESS  read-write
   STATUS      current
   DESCRIPTION
      "By way of this field, some manipulations
       on this table may be performed."
   ::= {er1646v2EfmIpV6DhcpRelayDestinationsEntry 2}

er1646v2EfmIpV6DhcpRelayDestinationsTableIx OBJECT-TYPE
   SYNTAX      TableIndex
   MAX-ACCESS  not-accessible
   STATUS      current
   DESCRIPTION
      ""
   ::= {er1646v2EfmIpV6DhcpRelayDestinationsEntry 11}

er1646v2EfmIpV6DhcpRelayDestinationsAddress OBJECT-TYPE
   SYNTAX      Ipv6Address
   MAX-ACCESS  read-write
   STATUS      current
   DESCRIPTION
      "Path: efm.editConf.ipV6.dhcp.relay.destinations.address

       ipv6 address"
   ::= {er1646v2EfmIpV6DhcpRelayDestinationsEntry 16777216}

er1646v2EfmIpV6DhcpRelayDestinationsInterface OBJECT-TYPE
   SYNTAX      DisplayString
   MAX-ACCESS  read-write
   STATUS      current
   DESCRIPTION
      "Path: efm.editConf.ipV6.dhcp.relay.destinations.interface"
   ::= {er1646v2EfmIpV6DhcpRelayDestinationsEntry 33554432}


er1646v2EfmIbw OBJECT IDENTIFIER ::= {er1646v2Efm 13}

er1646v2EfmIbwSSC OBJECT IDENTIFIER ::= {er1646v2EfmIbw 1}

er1646v2EfmIbwEntry OBJECT IDENTIFIER ::= {er1646v2EfmIbwSSC 1}

er1646v2EfmIbwMode OBJECT-TYPE
   SYNTAX      INTEGER
               {
               reshaping (1),
               policing (2)
               }
   MAX-ACCESS  read-write
   STATUS      current
   DESCRIPTION
      "Path: efm.editConf.inboundBandwidth.mode

       Possibilities:
               reshaping   (1)
               policing   (2)"
   ::= {er1646v2EfmIbwEntry 3758096384}

er1646v2EfmIbwCir OBJECT-TYPE
   SYNTAX      Integer32
   MAX-ACCESS  read-write
   STATUS      current
   DESCRIPTION
      "Path: efm.editConf.inboundBandwidth.cir"
   ::= {er1646v2EfmIbwEntry 268435456}

er1646v2EfmIbwEir OBJECT-TYPE
   SYNTAX      Integer32
   MAX-ACCESS  read-write
   STATUS      current
   DESCRIPTION
      "Path: efm.editConf.inboundBandwidth.eir"
   ::= {er1646v2EfmIbwEntry 1879048192}

er1646v2EfmIbwUnit OBJECT-TYPE
   SYNTAX      INTEGER
               {
               bitssec (1),
               percent (2)
               }
   MAX-ACCESS  read-write
   STATUS      current
   DESCRIPTION
      "Path: efm.editConf.inboundBandwidth.unit

       Possibilities:
               bits/sec   (1)
               percent   (2)"
   ::= {er1646v2EfmIbwEntry 1342177280}

er1646v2EfmIbwTc OBJECT-TYPE
   SYNTAX      INTEGER
               {
               auto (0)
               }
   MAX-ACCESS  read-write
   STATUS      current
   DESCRIPTION
      "Path: efm.editConf.inboundBandwidth.tc

       Possibilities:
               auto   (0)"
   ::= {er1646v2EfmIbwEntry 1610612736}

er1646v2EfmIbwTcFactor OBJECT-TYPE
   SYNTAX      INTEGER
               {
               ms (10),
               s100us (1)
               }
   MAX-ACCESS  read-write
   STATUS      current
   DESCRIPTION
      "Path: efm.editConf.inboundBandwidth.tcFactor

       Possibilities:
               ms   (10)
               *100us   (1)"
   ::= {er1646v2EfmIbwEntry 2147483648}

er1646v2EfmIbwCorrType OBJECT-TYPE
   SYNTAX      INTEGER
               {
               noCorrection (0),
               predefined (1),
               manual (2)
               }
   MAX-ACCESS  read-write
   STATUS      current
   DESCRIPTION
      "Path: efm.editConf.inboundBandwidth.correction.type

       Possibilities:
               noCorrection   (0)
               predefined   (1)
               manual   (2)"
   ::= {er1646v2EfmIbwEntry 570425344}

er1646v2EfmIbwCorrPredefEncapsFrameRelay OBJECT-TYPE
   SYNTAX      DisplayString
   MAX-ACCESS  read-write
   STATUS      current
   DESCRIPTION
      "Path: efm.editConf.inboundBandwidth.correction.predefined.encapsulation.frameRelay"
   ::= {er1646v2EfmIbwEntry 608436224}

er1646v2EfmIbwCorrPredefEncapsPpp OBJECT-TYPE
   SYNTAX      DisplayString
   MAX-ACCESS  read-write
   STATUS      current
   DESCRIPTION
      "Path: efm.editConf.inboundBandwidth.correction.predefined.encapsulation.ppp"
   ::= {er1646v2EfmIbwEntry 608698368}

er1646v2EfmIbwCorrPredefEncapsAtmHl OBJECT-TYPE
   SYNTAX      INTEGER
               {
               rfc2684 (0),
               ppp (1),
               pppOverEthernet (2)
               }
   MAX-ACCESS  read-write
   STATUS      current
   DESCRIPTION
      "Path: efm.editConf.inboundBandwidth.correction.predefined.encapsulation.atm.higherLayer

       Possibilities:
               rfc2684   (0)
               ppp   (1)
               pppOverEthernet   (2)"
   ::= {er1646v2EfmIbwEntry 608993280}

er1646v2EfmIbwCorrPredefEncapsAtmMp OBJECT-TYPE
   SYNTAX      INTEGER
               {
               llcEncapsulation (0),
               vcMultiplexing (1)
               }
   MAX-ACCESS  read-write
   STATUS      current
   DESCRIPTION
      "Path: efm.editConf.inboundBandwidth.correction.predefined.encapsulation.atm.multiProtocol

       Possibilities:
               llcEncapsulation   (0)
               vcMultiplexing   (1)"
   ::= {er1646v2EfmIbwEntry 609026048}

er1646v2EfmIbwCorrPredefEncapsHdlc OBJECT-TYPE
   SYNTAX      DisplayString
   MAX-ACCESS  read-write
   STATUS      current
   DESCRIPTION
      "Path: efm.editConf.inboundBandwidth.correction.predefined.encapsulation.hdlc"
   ::= {er1646v2EfmIbwEntry 609222656}

er1646v2EfmIbwCorrPredefEncapsEfmFs OBJECT-TYPE
   SYNTAX      Integer32
   MAX-ACCESS  read-write
   STATUS      current
   DESCRIPTION
      "Path: efm.editConf.inboundBandwidth.correction.predefined.encapsulation.efm.fragmentSize"
   ::= {er1646v2EfmIbwEntry 609517568}

er1646v2EfmIbwCorrPredefEncapsEfmIb OBJECT-TYPE
   SYNTAX      Integer32
   MAX-ACCESS  read-write
   STATUS      current
   DESCRIPTION
      "Path: efm.editConf.inboundBandwidth.correction.predefined.encapsulation.efm.idleBytes"
   ::= {er1646v2EfmIbwEntry 609550336}

er1646v2EfmIbwCorrPredefMode OBJECT-TYPE
   SYNTAX      INTEGER
               {
               routing (0),
               bridging (1)
               }
   MAX-ACCESS  read-write
   STATUS      current
   DESCRIPTION
      "Path: efm.editConf.inboundBandwidth.correction.predefined.mode

       Possibilities:
               routing   (0)
               bridging   (1)"
   ::= {er1646v2EfmIbwEntry 612368384}

er1646v2EfmIbwCorrManualOverhead OBJECT-TYPE
   SYNTAX      Integer32
   MAX-ACCESS  read-write
   STATUS      current
   DESCRIPTION
      "Path: efm.editConf.inboundBandwidth.correction.manual.overhead"
   ::= {er1646v2EfmIbwEntry 637665280}

er1646v2EfmIbwCorrManualFrameData OBJECT-TYPE
   SYNTAX      Counter32
   MAX-ACCESS  read-write
   STATUS      current
   DESCRIPTION
      "Path: efm.editConf.inboundBandwidth.correction.manual.frameData

       32 bit unsigned wrappable counter."
   ::= {er1646v2EfmIbwEntry 637796352}

er1646v2EfmIbwCorrManualFrameHeader OBJECT-TYPE
   SYNTAX      Counter32
   MAX-ACCESS  read-write
   STATUS      current
   DESCRIPTION
      "Path: efm.editConf.inboundBandwidth.correction.manual.frameHeader

       32 bit unsigned wrappable counter."
   ::= {er1646v2EfmIbwEntry 637927424}

er1646v2EfmIbwMaxFifoQLen OBJECT-TYPE
   SYNTAX      Integer32
   MAX-ACCESS  read-write
   STATUS      current
   DESCRIPTION
      "Path: efm.editConf.inboundBandwidth.maxFifoQLen"
   ::= {er1646v2EfmIbwEntry 805306368}

er1646v2EfmIbwPriorityPolicy OBJECT-TYPE
   SYNTAX      DisplayString
   MAX-ACCESS  read-write
   STATUS      current
   DESCRIPTION
      "Path: efm.editConf.inboundBandwidth.priorityPolicy"
   ::= {er1646v2EfmIbwEntry 1073741824}

er1646v2EfmIbwDeFlagCir OBJECT-TYPE
   SYNTAX      INTEGER
               {
               allowed (1),
               notAllowed (2)
               }
   MAX-ACCESS  read-write
   STATUS      current
   DESCRIPTION
      "Path: efm.editConf.inboundBandwidth.deFlag.cir

       Possibilities:
               allowed   (1)
               notAllowed   (2)"
   ::= {er1646v2EfmIbwEntry 3490709504}

er1646v2EfmIbwDeFlagEir OBJECT-TYPE
   SYNTAX      INTEGER
               {
               allowed (1),
               notAllowed (2)
               }
   MAX-ACCESS  read-write
   STATUS      current
   DESCRIPTION
      "Path: efm.editConf.inboundBandwidth.deFlag.eir

       Possibilities:
               allowed   (1)
               notAllowed   (2)"
   ::= {er1646v2EfmIbwEntry 3491758080}

er1646v2EfmIbwDeFlagViolate OBJECT-TYPE
   SYNTAX      INTEGER
               {
               allowed (1),
               notAllowed (2)
               }
   MAX-ACCESS  read-write
   STATUS      current
   DESCRIPTION
      "Path: efm.editConf.inboundBandwidth.deFlag.violate

       Possibilities:
               allowed   (1)
               notAllowed   (2)"
   ::= {er1646v2EfmIbwEntry 3492806656}

er1646v2EfmIbwActCirActNone OBJECT-TYPE
   SYNTAX      OCTET STRING
   MAX-ACCESS  read-write
   STATUS      current
   DESCRIPTION
      "Path: efm.editConf.inboundBandwidth.action.cirAction.none"
   ::= {er1646v2EfmIbwEntry 4062183424}

er1646v2EfmIbwActCirActEthCos1 OBJECT-TYPE
   SYNTAX      INTEGER
               {
               unchanged (256)
               }
   MAX-ACCESS  read-write
   STATUS      current
   DESCRIPTION
      "Path: efm.editConf.inboundBandwidth.action.cirAction.ethernet.cosDepth1

       Possibilities:
               unchanged   (256)"
   ::= {er1646v2EfmIbwEntry 4064346112}

er1646v2EfmIbwActCirActEthDei1 OBJECT-TYPE
   SYNTAX      INTEGER
               {
               unchanged (255),
               clear (0),
               set (1)
               }
   MAX-ACCESS  read-write
   STATUS      current
   DESCRIPTION
      "Path: efm.editConf.inboundBandwidth.action.cirAction.ethernet.deiDepth1

       Possibilities:
               unchanged   (255)
               clear   (0)
               set   (1)"
   ::= {er1646v2EfmIbwEntry 4065656832}

er1646v2EfmIbwActCirActEthCos2 OBJECT-TYPE
   SYNTAX      INTEGER
               {
               unchanged (256)
               }
   MAX-ACCESS  read-write
   STATUS      current
   DESCRIPTION
      "Path: efm.editConf.inboundBandwidth.action.cirAction.ethernet.cosDepth2

       Possibilities:
               unchanged   (256)"
   ::= {er1646v2EfmIbwEntry 4064411648}

er1646v2EfmIbwActCirActEthDei2 OBJECT-TYPE
   SYNTAX      INTEGER
               {
               unchanged (255),
               clear (0),
               set (1)
               }
   MAX-ACCESS  read-write
   STATUS      current
   DESCRIPTION
      "Path: efm.editConf.inboundBandwidth.action.cirAction.ethernet.deiDepth2

       Possibilities:
               unchanged   (255)
               clear   (0)
               set   (1)"
   ::= {er1646v2EfmIbwEntry 4065722368}

er1646v2EfmIbwActCirActEthCos3 OBJECT-TYPE
   SYNTAX      INTEGER
               {
               unchanged (256)
               }
   MAX-ACCESS  read-write
   STATUS      current
   DESCRIPTION
      "Path: efm.editConf.inboundBandwidth.action.cirAction.ethernet.cosDepth3

       Possibilities:
               unchanged   (256)"
   ::= {er1646v2EfmIbwEntry 4064477184}

er1646v2EfmIbwActCirActEthDei3 OBJECT-TYPE
   SYNTAX      INTEGER
               {
               unchanged (255),
               clear (0),
               set (1)
               }
   MAX-ACCESS  read-write
   STATUS      current
   DESCRIPTION
      "Path: efm.editConf.inboundBandwidth.action.cirAction.ethernet.deiDepth3

       Possibilities:
               unchanged   (255)
               clear   (0)
               set   (1)"
   ::= {er1646v2EfmIbwEntry 4065787904}

er1646v2EfmIbwActCirActEthCos4 OBJECT-TYPE
   SYNTAX      INTEGER
               {
               unchanged (256)
               }
   MAX-ACCESS  read-write
   STATUS      current
   DESCRIPTION
      "Path: efm.editConf.inboundBandwidth.action.cirAction.ethernet.cosDepth4

       Possibilities:
               unchanged   (256)"
   ::= {er1646v2EfmIbwEntry 4064542720}

er1646v2EfmIbwActCirActEthDei4 OBJECT-TYPE
   SYNTAX      INTEGER
               {
               unchanged (255),
               clear (0),
               set (1)
               }
   MAX-ACCESS  read-write
   STATUS      current
   DESCRIPTION
      "Path: efm.editConf.inboundBandwidth.action.cirAction.ethernet.deiDepth4

       Possibilities:
               unchanged   (255)
               clear   (0)
               set   (1)"
   ::= {er1646v2EfmIbwEntry 4065853440}

er1646v2EfmIbwActCirActEthCos5 OBJECT-TYPE
   SYNTAX      INTEGER
               {
               unchanged (256)
               }
   MAX-ACCESS  read-write
   STATUS      current
   DESCRIPTION
      "Path: efm.editConf.inboundBandwidth.action.cirAction.ethernet.cosDepth5

       Possibilities:
               unchanged   (256)"
   ::= {er1646v2EfmIbwEntry 4064608256}

er1646v2EfmIbwActCirActEthDei5 OBJECT-TYPE
   SYNTAX      INTEGER
               {
               unchanged (255),
               clear (0),
               set (1)
               }
   MAX-ACCESS  read-write
   STATUS      current
   DESCRIPTION
      "Path: efm.editConf.inboundBandwidth.action.cirAction.ethernet.deiDepth5

       Possibilities:
               unchanged   (255)
               clear   (0)
               set   (1)"
   ::= {er1646v2EfmIbwEntry 4065918976}

er1646v2EfmIbwActCirActEthCos6 OBJECT-TYPE
   SYNTAX      INTEGER
               {
               unchanged (256)
               }
   MAX-ACCESS  read-write
   STATUS      current
   DESCRIPTION
      "Path: efm.editConf.inboundBandwidth.action.cirAction.ethernet.cosDepth6

       Possibilities:
               unchanged   (256)"
   ::= {er1646v2EfmIbwEntry 4064673792}

er1646v2EfmIbwActCirActEthDei6 OBJECT-TYPE
   SYNTAX      INTEGER
               {
               unchanged (255),
               clear (0),
               set (1)
               }
   MAX-ACCESS  read-write
   STATUS      current
   DESCRIPTION
      "Path: efm.editConf.inboundBandwidth.action.cirAction.ethernet.deiDepth6

       Possibilities:
               unchanged   (255)
               clear   (0)
               set   (1)"
   ::= {er1646v2EfmIbwEntry 4065984512}

er1646v2EfmIbwActCirActEthCos7 OBJECT-TYPE
   SYNTAX      INTEGER
               {
               unchanged (256)
               }
   MAX-ACCESS  read-write
   STATUS      current
   DESCRIPTION
      "Path: efm.editConf.inboundBandwidth.action.cirAction.ethernet.cosDepth7

       Possibilities:
               unchanged   (256)"
   ::= {er1646v2EfmIbwEntry 4064739328}

er1646v2EfmIbwActCirActEthDei7 OBJECT-TYPE
   SYNTAX      INTEGER
               {
               unchanged (255),
               clear (0),
               set (1)
               }
   MAX-ACCESS  read-write
   STATUS      current
   DESCRIPTION
      "Path: efm.editConf.inboundBandwidth.action.cirAction.ethernet.deiDepth7

       Possibilities:
               unchanged   (255)
               clear   (0)
               set   (1)"
   ::= {er1646v2EfmIbwEntry 4066050048}

er1646v2EfmIbwActCirActEthCos8 OBJECT-TYPE
   SYNTAX      INTEGER
               {
               unchanged (256)
               }
   MAX-ACCESS  read-write
   STATUS      current
   DESCRIPTION
      "Path: efm.editConf.inboundBandwidth.action.cirAction.ethernet.cosDepth8

       Possibilities:
               unchanged   (256)"
   ::= {er1646v2EfmIbwEntry 4064804864}

er1646v2EfmIbwActCirActEthDei8 OBJECT-TYPE
   SYNTAX      INTEGER
               {
               unchanged (255),
               clear (0),
               set (1)
               }
   MAX-ACCESS  read-write
   STATUS      current
   DESCRIPTION
      "Path: efm.editConf.inboundBandwidth.action.cirAction.ethernet.deiDepth8

       Possibilities:
               unchanged   (255)
               clear   (0)
               set   (1)"
   ::= {er1646v2EfmIbwEntry 4066115584}

er1646v2EfmIbwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.inboundBandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EfmIbwEntry 4064870400}

er1646v2EfmIbwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.inboundBandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EfmIbwEntry 4064935936}

er1646v2EfmIbwActCirActEthDrpLev OBJECT-TYPE
   SYNTAX      INTEGER
               {
               unchanged (0)
               }
   MAX-ACCESS  read-write
   STATUS      current
   DESCRIPTION
      "Path: efm.editConf.inboundBandwidth.action.cirAction.ethernet.dropLevel

       Possibilities:
               unchanged   (0)"
   ::= {er1646v2EfmIbwEntry 4065001472}

er1646v2EfmIbwActCirActEthDeFlag OBJECT-TYPE
   SYNTAX      INTEGER
               {
               unchanged (255),
               clear (0),
               set (1)
               }
   MAX-ACCESS  read-write
   STATUS      current
   DESCRIPTION
      "Path: efm.editConf.inboundBandwidth.action.cirAction.ethernet.deFlag

       Possibilities:
               unchanged   (255)
               clear   (0)
               set   (1)"
   ::= {er1646v2EfmIbwEntry 4065198080}

er1646v2EfmIbwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.inboundBandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EfmIbwEntry 4071161856}

er1646v2EfmIbwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.inboundBandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EfmIbwEntry 4071227392}

er1646v2EfmIbwActCirActIpDrpLev OBJECT-TYPE
   SYNTAX      INTEGER
               {
               unchanged (0)
               }
   MAX-ACCESS  read-write
   STATUS      current
   DESCRIPTION
      "Path: efm.editConf.inboundBandwidth.action.cirAction.ip.dropLevel

       Possibilities:
               unchanged   (0)"
   ::= {er1646v2EfmIbwEntry 4071292928}

er1646v2EfmIbwActCirActIpDeFlag OBJECT-TYPE
   SYNTAX      INTEGER
               {
               unchanged (255),
               clear (0),
               set (1)
               }
   MAX-ACCESS  read-write
   STATUS      current
   DESCRIPTION
      "Path: efm.editConf.inboundBandwidth.action.cirAction.ip.deFlag

       Possibilities:
               unchanged   (255)
               clear   (0)
               set   (1)"
   ::= {er1646v2EfmIbwEntry 4071489536}

er1646v2EfmIbwActEirActNone OBJECT-TYPE
   SYNTAX      OCTET STRING
   MAX-ACCESS  read-write
   STATUS      current
   DESCRIPTION
      "Path: efm.editConf.inboundBandwidth.action.eirAction.none"
   ::= {er1646v2EfmIbwEntry 4095737856}

er1646v2EfmIbwActEirActEthCos1 OBJECT-TYPE
   SYNTAX      INTEGER
               {
               unchanged (256)
               }
   MAX-ACCESS  read-write
   STATUS      current
   DESCRIPTION
      "Path: efm.editConf.inboundBandwidth.action.eirAction.ethernet.cosDepth1

       Possibilities:
               unchanged   (256)"
   ::= {er1646v2EfmIbwEntry 4097900544}

er1646v2EfmIbwActEirActEthDei1 OBJECT-TYPE
   SYNTAX      INTEGER
               {
               unchanged (255),
               clear (0),
               set (1)
               }
   MAX-ACCESS  read-write
   STATUS      current
   DESCRIPTION
      "Path: efm.editConf.inboundBandwidth.action.eirAction.ethernet.deiDepth1

       Possibilities:
               unchanged   (255)
               clear   (0)
               set   (1)"
   ::= {er1646v2EfmIbwEntry 4099211264}

er1646v2EfmIbwActEirActEthCos2 OBJECT-TYPE
   SYNTAX      INTEGER
               {
               unchanged (256)
               }
   MAX-ACCESS  read-write
   STATUS      current
   DESCRIPTION
      "Path: efm.editConf.inboundBandwidth.action.eirAction.ethernet.cosDepth2

       Possibilities:
               unchanged   (256)"
   ::= {er1646v2EfmIbwEntry 4097966080}

er1646v2EfmIbwActEirActEthDei2 OBJECT-TYPE
   SYNTAX      INTEGER
               {
               unchanged (255),
               clear (0),
               set (1)
               }
   MAX-ACCESS  read-write
   STATUS      current
   DESCRIPTION
      "Path: efm.editConf.inboundBandwidth.action.eirAction.ethernet.deiDepth2

       Possibilities:
               unchanged   (255)
               clear   (0)
               set   (1)"
   ::= {er1646v2EfmIbwEntry 4099276800}

er1646v2EfmIbwActEirActEthCos3 OBJECT-TYPE
   SYNTAX      INTEGER
               {
               unchanged (256)
               }
   MAX-ACCESS  read-write
   STATUS      current
   DESCRIPTION
      "Path: efm.editConf.inboundBandwidth.action.eirAction.ethernet.cosDepth3

       Possibilities:
               unchanged   (256)"
   ::= {er1646v2EfmIbwEntry 4098031616}

er1646v2EfmIbwActEirActEthDei3 OBJECT-TYPE
   SYNTAX      INTEGER
               {
               unchanged (255),
               clear (0),
               set (1)
               }
   MAX-ACCESS  read-write
   STATUS      current
   DESCRIPTION
      "Path: efm.editConf.inboundBandwidth.action.eirAction.ethernet.deiDepth3

       Possibilities:
               unchanged   (255)
               clear   (0)
               set   (1)"
   ::= {er1646v2EfmIbwEntry 4099342336}

er1646v2EfmIbwActEirActEthCos4 OBJECT-TYPE
   SYNTAX      INTEGER
               {
               unchanged (256)
               }
   MAX-ACCESS  read-write
   STATUS      current
   DESCRIPTION
      "Path: efm.editConf.inboundBandwidth.action.eirAction.ethernet.cosDepth4

       Possibilities:
               unchanged   (256)"
   ::= {er1646v2EfmIbwEntry 4098097152}

er1646v2EfmIbwActEirActEthDei4 OBJECT-TYPE
   SYNTAX      INTEGER
               {
               unchanged (255),
               clear (0),
               set (1)
               }
   MAX-ACCESS  read-write
   STATUS      current
   DESCRIPTION
      "Path: efm.editConf.inboundBandwidth.action.eirAction.ethernet.deiDepth4

       Possibilities:
               unchanged   (255)
               clear   (0)
               set   (1)"
   ::= {er1646v2EfmIbwEntry 4099407872}

er1646v2EfmIbwActEirActEthCos5 OBJECT-TYPE
   SYNTAX      INTEGER
               {
               unchanged (256)
               }
   MAX-ACCESS  read-write
   STATUS      current
   DESCRIPTION
      "Path: efm.editConf.inboundBandwidth.action.eirAction.ethernet.cosDepth5

       Possibilities:
               unchanged   (256)"
   ::= {er1646v2EfmIbwEntry 4098162688}

er1646v2EfmIbwActEirActEthDei5 OBJECT-TYPE
   SYNTAX      INTEGER
               {
               unchanged (255),
               clear (0),
               set (1)
               }
   MAX-ACCESS  read-write
   STATUS      current
   DESCRIPTION
      "Path: efm.editConf.inboundBandwidth.action.eirAction.ethernet.deiDepth5

       Possibilities:
               unchanged   (255)
               clear   (0)
               set   (1)"
   ::= {er1646v2EfmIbwEntry 4099473408}

er1646v2EfmIbwActEirActEthCos6 OBJECT-TYPE
   SYNTAX      INTEGER
               {
               unchanged (256)
               }
   MAX-ACCESS  read-write
   STATUS      current
   DESCRIPTION
      "Path: efm.editConf.inboundBandwidth.action.eirAction.ethernet.cosDepth6

       Possibilities:
               unchanged   (256)"
   ::= {er1646v2EfmIbwEntry 4098228224}

er1646v2EfmIbwActEirActEthDei6 OBJECT-TYPE
   SYNTAX      INTEGER
               {
               unchanged (255),
               clear (0),
               set (1)
               }
   MAX-ACCESS  read-write
   STATUS      current
   DESCRIPTION
      "Path: efm.editConf.inboundBandwidth.action.eirAction.ethernet.deiDepth6

       Possibilities:
               unchanged   (255)
               clear   (0)
               set   (1)"
   ::= {er1646v2EfmIbwEntry 4099538944}

er1646v2EfmIbwActEirActEthCos7 OBJECT-TYPE
   SYNTAX      INTEGER
               {
               unchanged (256)
               }
   MAX-ACCESS  read-write
   STATUS      current
   DESCRIPTION
      "Path: efm.editConf.inboundBandwidth.action.eirAction.ethernet.cosDepth7

       Possibilities:
               unchanged   (256)"
   ::= {er1646v2EfmIbwEntry 4098293760}

er1646v2EfmIbwActEirActEthDei7 OBJECT-TYPE
   SYNTAX      INTEGER
               {
               unchanged (255),
               clear (0),
               set (1)
               }
   MAX-ACCESS  read-write
   STATUS      current
   DESCRIPTION
      "Path: efm.editConf.inboundBandwidth.action.eirAction.ethernet.deiDepth7

       Possibilities:
               unchanged   (255)
               clear   (0)
               set   (1)"
   ::= {er1646v2EfmIbwEntry 4099604480}

er1646v2EfmIbwActEirActEthCos8 OBJECT-TYPE
   SYNTAX      INTEGER
               {
               unchanged (256)
               }
   MAX-ACCESS  read-write
   STATUS      current
   DESCRIPTION
      "Path: efm.editConf.inboundBandwidth.action.eirAction.ethernet.cosDepth8

       Possibilities:
               unchanged   (256)"
   ::= {er1646v2EfmIbwEntry 4098359296}

er1646v2EfmIbwActEirActEthDei8 OBJECT-TYPE
   SYNTAX      INTEGER
               {
               unchanged (255),
               clear (0),
               set (1)
               }
   MAX-ACCESS  read-write
   STATUS      current
   DESCRIPTION
      "Path: efm.editConf.inboundBandwidth.action.eirAction.ethernet.deiDepth8

       Possibilities:
               unchanged   (255)
               clear   (0)
               set   (1)"
   ::= {er1646v2EfmIbwEntry 4099670016}

er1646v2EfmIbwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.inboundBandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EfmIbwEntry 4098424832}

er1646v2EfmIbwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.inboundBandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EfmIbwEntry 4098490368}

er1646v2EfmIbwActEirActEthDrpLev OBJECT-TYPE
   SYNTAX      INTEGER
               {
               unchanged (0)
               }
   MAX-ACCESS  read-write
   STATUS      current
   DESCRIPTION
      "Path: efm.editConf.inboundBandwidth.action.eirAction.ethernet.dropLevel

       Possibilities:
               unchanged   (0)"
   ::= {er1646v2EfmIbwEntry 4098555904}

er1646v2EfmIbwActEirActEthDeFlag OBJECT-TYPE
   SYNTAX      INTEGER
               {
               unchanged (255),
               clear (0),
               set (1)
               }
   MAX-ACCESS  read-write
   STATUS      current
   DESCRIPTION
      "Path: efm.editConf.inboundBandwidth.action.eirAction.ethernet.deFlag

       Possibilities:
               unchanged   (255)
               clear   (0)
               set   (1)"
   ::= {er1646v2EfmIbwEntry 4098752512}

er1646v2EfmIbwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.inboundBandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EfmIbwEntry 4104716288}

er1646v2EfmIbwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.inboundBandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EfmIbwEntry 4104781824}

er1646v2EfmIbwActEirActIpDrpLev OBJECT-TYPE
   SYNTAX      INTEGER
               {
               unchanged (0)
               }
   MAX-ACCESS  read-write
   STATUS      current
   DESCRIPTION
      "Path: efm.editConf.inboundBandwidth.action.eirAction.ip.dropLevel

       Possibilities:
               unchanged   (0)"
   ::= {er1646v2EfmIbwEntry 4104847360}

er1646v2EfmIbwActEirActIpDeFlag OBJECT-TYPE
   SYNTAX      INTEGER
               {
               unchanged (255),
               clear (0),
               set (1)
               }
   MAX-ACCESS  read-write
   STATUS      current
   DESCRIPTION
      "Path: efm.editConf.inboundBandwidth.action.eirAction.ip.deFlag

       Possibilities:
               unchanged   (255)
               clear   (0)
               set   (1)"
   ::= {er1646v2EfmIbwEntry 4105043968}

er1646v2EfmIbwActViolActNone OBJECT-TYPE
   SYNTAX      OCTET STRING
   MAX-ACCESS  read-write
   STATUS      current
   DESCRIPTION
      "Path: efm.editConf.inboundBandwidth.action.violateAction.none"
   ::= {er1646v2EfmIbwEntry 4129292288}

er1646v2EfmIbwActViolActDrop OBJECT-TYPE
   SYNTAX      OCTET STRING
   MAX-ACCESS  read-write
   STATUS      current
   DESCRIPTION
      "Path: efm.editConf.inboundBandwidth.action.violateAction.drop"
   ::= {er1646v2EfmIbwEntry 4133486592}

er1646v2EfmIbwActViolActEthCos1 OBJECT-TYPE
   SYNTAX      INTEGER
               {
               unchanged (256)
               }
   MAX-ACCESS  read-write
   STATUS      current
   DESCRIPTION
      "Path: efm.editConf.inboundBandwidth.action.violateAction.ethernet.cosDepth1

       Possibilities:
               unchanged   (256)"
   ::= {er1646v2EfmIbwEntry 4131454976}

er1646v2EfmIbwActViolActEthDei1 OBJECT-TYPE
   SYNTAX      INTEGER
               {
               unchanged (255),
               clear (0),
               set (1)
               }
   MAX-ACCESS  read-write
   STATUS      current
   DESCRIPTION
      "Path: efm.editConf.inboundBandwidth.action.violateAction.ethernet.deiDepth1

       Possibilities:
               unchanged   (255)
               clear   (0)
               set   (1)"
   ::= {er1646v2EfmIbwEntry 4132765696}

er1646v2EfmIbwActViolActEthCos2 OBJECT-TYPE
   SYNTAX      INTEGER
               {
               unchanged (256)
               }
   MAX-ACCESS  read-write
   STATUS      current
   DESCRIPTION
      "Path: efm.editConf.inboundBandwidth.action.violateAction.ethernet.cosDepth2

       Possibilities:
               unchanged   (256)"
   ::= {er1646v2EfmIbwEntry 4131520512}

er1646v2EfmIbwActViolActEthDei2 OBJECT-TYPE
   SYNTAX      INTEGER
               {
               unchanged (255),
               clear (0),
               set (1)
               }
   MAX-ACCESS  read-write
   STATUS      current
   DESCRIPTION
      "Path: efm.editConf.inboundBandwidth.action.violateAction.ethernet.deiDepth2

       Possibilities:
               unchanged   (255)
               clear   (0)
               set   (1)"
   ::= {er1646v2EfmIbwEntry 4132831232}

er1646v2EfmIbwActViolActEthCos3 OBJECT-TYPE
   SYNTAX      INTEGER
               {
               unchanged (256)
               }
   MAX-ACCESS  read-write
   STATUS      current
   DESCRIPTION
      "Path: efm.editConf.inboundBandwidth.action.violateAction.ethernet.cosDepth3

       Possibilities:
               unchanged   (256)"
   ::= {er1646v2EfmIbwEntry 4131586048}

er1646v2EfmIbwActViolActEthDei3 OBJECT-TYPE
   SYNTAX      INTEGER
               {
               unchanged (255),
               clear (0),
               set (1)
               }
   MAX-ACCESS  read-write
   STATUS      current
   DESCRIPTION
      "Path: efm.editConf.inboundBandwidth.action.violateAction.ethernet.deiDepth3

       Possibilities:
               unchanged   (255)
               clear   (0)
               set   (1)"
   ::= {er1646v2EfmIbwEntry 4132896768}

er1646v2EfmIbwActViolActEthCos4 OBJECT-TYPE
   SYNTAX      INTEGER
               {
               unchanged (256)
               }
   MAX-ACCESS  read-write
   STATUS      current
   DESCRIPTION
      "Path: efm.editConf.inboundBandwidth.action.violateAction.ethernet.cosDepth4

       Possibilities:
               unchanged   (256)"
   ::= {er1646v2EfmIbwEntry 4131651584}

er1646v2EfmIbwActViolActEthDei4 OBJECT-TYPE
   SYNTAX      INTEGER
               {
               unchanged (255),
               clear (0),
               set (1)
               }
   MAX-ACCESS  read-write
   STATUS      current
   DESCRIPTION
      "Path: efm.editConf.inboundBandwidth.action.violateAction.ethernet.deiDepth4

       Possibilities:
               unchanged   (255)
               clear   (0)
               set   (1)"
   ::= {er1646v2EfmIbwEntry 4132962304}

er1646v2EfmIbwActViolActEthCos5 OBJECT-TYPE
   SYNTAX      INTEGER
               {
               unchanged (256)
               }
   MAX-ACCESS  read-write
   STATUS      current
   DESCRIPTION
      "Path: efm.editConf.inboundBandwidth.action.violateAction.ethernet.cosDepth5

       Possibilities:
               unchanged   (256)"
   ::= {er1646v2EfmIbwEntry 4131717120}

er1646v2EfmIbwActViolActEthDei5 OBJECT-TYPE
   SYNTAX      INTEGER
               {
               unchanged (255),
               clear (0),
               set (1)
               }
   MAX-ACCESS  read-write
   STATUS      current
   DESCRIPTION
      "Path: efm.editConf.inboundBandwidth.action.violateAction.ethernet.deiDepth5

       Possibilities:
               unchanged   (255)
               clear   (0)
               set   (1)"
   ::= {er1646v2EfmIbwEntry 4133027840}

er1646v2EfmIbwActViolActEthCos6 OBJECT-TYPE
   SYNTAX      INTEGER
               {
               unchanged (256)
               }
   MAX-ACCESS  read-write
   STATUS      current
   DESCRIPTION
      "Path: efm.editConf.inboundBandwidth.action.violateAction.ethernet.cosDepth6

       Possibilities:
               unchanged   (256)"
   ::= {er1646v2EfmIbwEntry 4131782656}

er1646v2EfmIbwActViolActEthDei6 OBJECT-TYPE
   SYNTAX      INTEGER
               {
               unchanged (255),
               clear (0),
               set (1)
               }
   MAX-ACCESS  read-write
   STATUS      current
   DESCRIPTION
      "Path: efm.editConf.inboundBandwidth.action.violateAction.ethernet.deiDepth6

       Possibilities:
               unchanged   (255)
               clear   (0)
               set   (1)"
   ::= {er1646v2EfmIbwEntry 4133093376}

er1646v2EfmIbwActViolActEthCos7 OBJECT-TYPE
   SYNTAX      INTEGER
               {
               unchanged (256)
               }
   MAX-ACCESS  read-write
   STATUS      current
   DESCRIPTION
      "Path: efm.editConf.inboundBandwidth.action.violateAction.ethernet.cosDepth7

       Possibilities:
               unchanged   (256)"
   ::= {er1646v2EfmIbwEntry 4131848192}

er1646v2EfmIbwActViolActEthDei7 OBJECT-TYPE
   SYNTAX      INTEGER
               {
               unchanged (255),
               clear (0),
               set (1)
               }
   MAX-ACCESS  read-write
   STATUS      current
   DESCRIPTION
      "Path: efm.editConf.inboundBandwidth.action.violateAction.ethernet.deiDepth7

       Possibilities:
               unchanged   (255)
               clear   (0)
               set   (1)"
   ::= {er1646v2EfmIbwEntry 4133158912}

er1646v2EfmIbwActViolActEthCos8 OBJECT-TYPE
   SYNTAX      INTEGER
               {
               unchanged (256)
               }
   MAX-ACCESS  read-write
   STATUS      current
   DESCRIPTION
      "Path: efm.editConf.inboundBandwidth.action.violateAction.ethernet.cosDepth8

       Possibilities:
               unchanged   (256)"
   ::= {er1646v2EfmIbwEntry 4131913728}

er1646v2EfmIbwActViolActEthDei8 OBJECT-TYPE
   SYNTAX      INTEGER
               {
               unchanged (255),
               clear (0),
               set (1)
               }
   MAX-ACCESS  read-write
   STATUS      current
   DESCRIPTION
      "Path: efm.editConf.inboundBandwidth.action.violateAction.ethernet.deiDepth8

       Possibilities:
               unchanged   (255)
               clear   (0)
               set   (1)"
   ::= {er1646v2EfmIbwEntry 4133224448}

er1646v2EfmIbwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.inboundBandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EfmIbwEntry 4131979264}

er1646v2EfmIbwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.inboundBandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EfmIbwEntry 4132044800}

er1646v2EfmIbwActViolActEthDrpLev OBJECT-TYPE
   SYNTAX      INTEGER
               {
               unchanged (0)
               }
   MAX-ACCESS  read-write
   STATUS      current
   DESCRIPTION
      "Path: efm.editConf.inboundBandwidth.action.violateAction.ethernet.dropLevel

       Possibilities:
               unchanged   (0)"
   ::= {er1646v2EfmIbwEntry 4132110336}

er1646v2EfmIbwActViolActEthDeFlag OBJECT-TYPE
   SYNTAX      INTEGER
               {
               unchanged (255),
               clear (0),
               set (1)
               }
   MAX-ACCESS  read-write
   STATUS      current
   DESCRIPTION
      "Path: efm.editConf.inboundBandwidth.action.violateAction.ethernet.deFlag

       Possibilities:
               unchanged   (255)
               clear   (0)
               set   (1)"
   ::= {er1646v2EfmIbwEntry 4132306944}

er1646v2EfmIbwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: efm.editConf.inboundBandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EfmIbwEntry 4138270720}

er1646v2EfmIbwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: efm.editConf.inboundBandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EfmIbwEntry 4138336256}

er1646v2EfmIbwActViolActIpDrpLev OBJECT-TYPE
   SYNTAX      INTEGER
               {
               unchanged (0)
               }
   MAX-ACCESS  read-write
   STATUS      current
   DESCRIPTION
      "Path: efm.editConf.inboundBandwidth.action.violateAction.ip.dropLevel

       Possibilities:
               unchanged   (0)"
   ::= {er1646v2EfmIbwEntry 4138401792}

er1646v2EfmIbwActViolActIpDeFlag OBJECT-TYPE
   SYNTAX      INTEGER
               {
               unchanged (255),
               clear (0),
               set (1)
               }
   MAX-ACCESS  read-write
   STATUS      current
   DESCRIPTION
      "Path: efm.editConf.inboundBandwidth.action.violateAction.ip.deFlag

       Possibilities:
               unchanged   (255)
               clear   (0)
               set   (1)"
   ::= {er1646v2EfmIbwEntry 4138598400}

er1646v2EfmIbwSubInterfacesExcluded OBJECT-TYPE
   SYNTAX      INTEGER
               {
               s (1)
               }
   MAX-ACCESS  read-write
   STATUS      current
   DESCRIPTION
      "Path: efm.editConf.inboundBandwidth.subInterfaces.excluded

       Possibilities:
                  (1)"
   ::= {er1646v2EfmIbwEntry 2416967680}

er1646v2EfmIbwSubInterfacesIncludedInAccessList OBJECT-TYPE
   SYNTAX      DisplayString
   MAX-ACCESS  read-write
   STATUS      current
   DESCRIPTION
      "Path: efm.editConf.inboundBandwidth.subInterfaces.included.inAccessList"
   ::= {er1646v2EfmIbwEntry 2418020352}


er1646v2EfmMinActiveLinks OBJECT-TYPE
   SYNTAX      Integer32
   MAX-ACCESS  read-write
   STATUS      current
   DESCRIPTION
      "Path: efm.editConf.minActiveLinks
       Info: EFM minimum active links"
   ::= {er1646v2Efm 404}



sr1646v2Efm OBJECT IDENTIFIER ::= {r1646v2Efm 14}


sr1646v2EfmDescr OBJECT-TYPE
   SYNTAX      DisplayString
   MAX-ACCESS  read-only
   STATUS      current
   DESCRIPTION
      "Path: efm.status.ifDescr
       Info: ifDescr"
   ::= {sr1646v2Efm 101}


sr1646v2EfmType OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: efm.status.ifType
       Info: ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1646v2Efm 102}


sr1646v2EfmMtu OBJECT-TYPE
   SYNTAX      Integer32
   MAX-ACCESS  read-only
   STATUS      current
   DESCRIPTION
      "Path: efm.status.ifMtu
       Info: ifMtu"
   ::= {sr1646v2Efm 103}


sr1646v2EfmOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: efm.status.ifOperStatus
       Info: ifOperStatus

       Possibilities:
               up   (1)
               down   (2)
               testing   (3)
               unknown   (4)
               dormant   (5)
               notPresent   (6)
               lowerLayerDown   (7)"
   ::= {sr1646v2Efm 107}


sr1646v2EfmLastChange OBJECT-TYPE
   SYNTAX      TimeTicks
   MAX-ACCESS  read-only
   STATUS      current
   DESCRIPTION
      "Path: efm.status.ifLastChange
       Info: ifLastChange

       Time in centi-second."
   ::= {sr1646v2Efm 108}


sr1646v2EfmLastChangeD OBJECT-TYPE
   SYNTAX      DisplayString
   MAX-ACCESS  read-only
   STATUS      current
   DESCRIPTION
      "Path: efm.status.ifLastChangeDate
       Info: ifLastChangeDate"
   ::= {sr1646v2Efm 183}


sr1646v2EfmSpeed OBJECT-TYPE
   SYNTAX      Gauge32
   MAX-ACCESS  read-only
   STATUS      current
   DESCRIPTION
      "Path: efm.status.ifSpeed
       Info: ifSpeed

       32 bit unsigned gauge value."
   ::= {sr1646v2Efm 104}


sr1646v2EfmIp OBJECT IDENTIFIER ::= {sr1646v2Efm 16}

sr1646v2EfmIpSSC OBJECT IDENTIFIER ::= {sr1646v2EfmIp 1}

sr1646v2EfmIpEntry OBJECT IDENTIFIER ::= {sr1646v2EfmIpSSC 1}

sr1646v2EfmIpStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: efm.status.ip.status

       Possibilities:
               up   (1)
               down   (2)
               testing   (3)
               unknown   (4)
               dormant   (5)
               notPresent   (6)
               lowerLayerDown   (7)"
   ::= {sr1646v2EfmIpEntry 1795162112}

sr1646v2EfmIpAddress OBJECT-TYPE
   SYNTAX      IpAddress
   MAX-ACCESS  read-only
   STATUS      current
   DESCRIPTION
      "Path: efm.status.ip.address"
   ::= {sr1646v2EfmIpEntry 2030043136}

sr1646v2EfmIpNetMask OBJECT-TYPE
   SYNTAX      IpAddress
   MAX-ACCESS  read-only
   STATUS      current
   DESCRIPTION
      "Path: efm.status.ip.netMask"
   ::= {sr1646v2EfmIpEntry 2063597568}

sr1646v2EfmIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: efm.status.ip.dhcp.status

       Possibilities:
               none   (0)
               selecting   (1)
               requesting   (2)
               rebinding   (3)
               bound   (4)
               renewing   (5)
               rebooting   (6)
               initreboot   (7)"
   ::= {sr1646v2EfmIpEntry 402718720}

sr1646v2EfmIpDhcpLeaseTime OBJECT-TYPE
   SYNTAX      TimeTicks
   MAX-ACCESS  read-only
   STATUS      current
   DESCRIPTION
      "Path: efm.status.ip.dhcp.leaseTime

       Time in centi-second."
   ::= {sr1646v2EfmIpEntry 402784256}

sr1646v2EfmIpSecondaryIp OBJECT-TYPE
   SYNTAX      SEQUENCE OF Sr1646v2EfmIpSecondaryIpEntry
   MAX-ACCESS  not-accessible
   STATUS      current
   DESCRIPTION
      ""
   ::= {sr1646v2EfmIp 385875968}

sr1646v2EfmIpSecondaryIpEntry OBJECT-TYPE
   SYNTAX      Sr1646v2EfmIpSecondaryIpEntry
   MAX-ACCESS  not-accessible
   STATUS      current
   DESCRIPTION
      ""
   INDEX      { sr1646v2EfmIpSecondaryIpTableIx }
   ::= {sr1646v2EfmIpSecondaryIp 1}

Sr1646v2EfmIpSecondaryIpEntry ::=
   SEQUENCE
      {
      sr1646v2EfmIpSecondaryIpTableIx
         TableIndex,
      sr1646v2EfmIpSecondaryIpAddress
         IpAddress,
      sr1646v2EfmIpSecondaryIpNetMask
         IpAddress
      }

sr1646v2EfmIpSecondaryIpTableIx OBJECT-TYPE
   SYNTAX      TableIndex
   MAX-ACCESS  not-accessible
   STATUS      current
   DESCRIPTION
      ""
   ::= {sr1646v2EfmIpSecondaryIpEntry 11}

sr1646v2EfmIpSecondaryIpAddress OBJECT-TYPE
   SYNTAX      IpAddress
   MAX-ACCESS  read-only
   STATUS      current
   DESCRIPTION
      "Path: efm.status.ip.secondaryIp.address"
   ::= {sr1646v2EfmIpSecondaryIpEntry 2030043136}

sr1646v2EfmIpSecondaryIpNetMask OBJECT-TYPE
   SYNTAX      IpAddress
   MAX-ACCESS  read-only
   STATUS      current
   DESCRIPTION
      "Path: efm.status.ip.secondaryIp.netMask"
   ::= {sr1646v2EfmIpSecondaryIpEntry 2063597568}


sr1646v2EfmArpCache OBJECT IDENTIFIER ::= {sr1646v2Efm 11}

sr1646v2EfmArpCacheSSCTable OBJECT-TYPE
   SYNTAX      SEQUENCE OF Sr1646v2EfmArpCacheEntry
   MAX-ACCESS  not-accessible
   STATUS      current
   DESCRIPTION
      "arp cache of ethernet interface"
   ::= {sr1646v2EfmArpCache 1}

sr1646v2EfmArpCacheEntry OBJECT-TYPE
   SYNTAX      Sr1646v2EfmArpCacheEntry
   MAX-ACCESS  not-accessible
   STATUS      current
   DESCRIPTION
      ""
   INDEX      { sr1646v2EfmArpCacheTableIx }
   ::= {sr1646v2EfmArpCacheSSCTable 1}

Sr1646v2EfmArpCacheEntry ::=
   SEQUENCE
      {
      sr1646v2EfmArpCacheTableIx
         TableIndex,
      sr1646v2EfmArpCacheMacAddress
         OCTET STRING,
      sr1646v2EfmArpCacheIpAddress
         IpAddress,
      sr1646v2EfmArpCacheType
         INTEGER,
      sr1646v2EfmArpCacheTimeOut
         TimeTicks
      }

sr1646v2EfmArpCacheTableIx OBJECT-TYPE
   SYNTAX      TableIndex
   MAX-ACCESS  not-accessible
   STATUS      current
   DESCRIPTION
      ""
   ::= {sr1646v2EfmArpCacheEntry 11}

sr1646v2EfmArpCacheMacAddress OBJECT-TYPE
   SYNTAX      OCTET STRING
   MAX-ACCESS  read-only
   STATUS      current
   DESCRIPTION
      "Path: efm.status.arpCache.macAddress

       MAC address."
   ::= {sr1646v2EfmArpCacheEntry 16777216}

sr1646v2EfmArpCacheIpAddress OBJECT-TYPE
   SYNTAX      IpAddress
   MAX-ACCESS  read-only
   STATUS      current
   DESCRIPTION
      "Path: efm.status.arpCache.ipAddress"
   ::= {sr1646v2EfmArpCacheEntry 33554432}

sr1646v2EfmArpCacheType OBJECT-TYPE
   SYNTAX      INTEGER
               {
               static (0),
               dynamic (1)
               }
   MAX-ACCESS  read-only
   STATUS      current
   DESCRIPTION
      "Path: efm.status.arpCache.type

       Possibilities:
               static   (0)
               dynamic   (1)"
   ::= {sr1646v2EfmArpCacheEntry 50331648}

sr1646v2EfmArpCacheTimeOut OBJECT-TYPE
   SYNTAX      TimeTicks
   MAX-ACCESS  read-only
   STATUS      current
   DESCRIPTION
      "Path: efm.status.arpCache.timeOut

       Time in centi-second."
   ::= {sr1646v2EfmArpCacheEntry 67108864}


sr1646v2EfmBrS OBJECT IDENTIFIER ::= {sr1646v2Efm 28}

sr1646v2EfmBrSSSC OBJECT IDENTIFIER ::= {sr1646v2EfmBrS 1}

sr1646v2EfmBrSEntry OBJECT IDENTIFIER ::= {sr1646v2EfmBrSSSC 1}

sr1646v2EfmBrSStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: efm.status.bridging.status

       Possibilities:
               disabled   (0)
               discarding   (1)
               learning   (2)
               forwarding   (3)
               backupBlockedIntfDown   (256)
               backupBlockedIntfUp   (259)
               shutdown   (255)"
   ::= {sr1646v2EfmBrSEntry 16777216}

sr1646v2EfmBrSStPortRole OBJECT-TYPE
   SYNTAX      INTEGER
               {
               none (0),
               root (1),
               designated (2),
               alternate (3),
               backup (4),
               disabled (5),
               master (6)
               }
   MAX-ACCESS  read-only
   STATUS      current
   DESCRIPTION
      "Path: efm.status.bridging.spanningTree.portRole

       Possibilities:
               none   (0)
               root   (1)
               designated   (2)
               alternate   (3)
               backup   (4)
               disabled   (5)
               master   (6)"
   ::= {sr1646v2EfmBrSEntry 33619968}

sr1646v2EfmBrSStPortId OBJECT-TYPE
   SYNTAX      Integer32
   MAX-ACCESS  read-only
   STATUS      current
   DESCRIPTION
      "Path: efm.status.bridging.spanningTree.portId"
   ::= {sr1646v2EfmBrSEntry 33685504}

sr1646v2EfmBrSStPpCostExtPathCost OBJECT-TYPE
   SYNTAX      Integer32
   MAX-ACCESS  read-only
   STATUS      current
   DESCRIPTION
      "Path: efm.status.bridging.spanningTree.portPathCosts.extPathCost"
   ::= {sr1646v2EfmBrSEntry 33751296}

sr1646v2EfmBrSStPpCostIntPathCost OBJECT-TYPE
   SYNTAX      Integer32
   MAX-ACCESS  read-only
   STATUS      current
   DESCRIPTION
      "Path: efm.status.bridging.spanningTree.portPathCosts.intPathCost"
   ::= {sr1646v2EfmBrSEntry 33751552}

sr1646v2EfmBrSStExtRpCost OBJECT-TYPE
   SYNTAX      Integer32
   MAX-ACCESS  read-only
   STATUS      current
   DESCRIPTION
      "Path: efm.status.bridging.spanningTree.extRootPathCost"
   ::= {sr1646v2EfmBrSEntry 33816576}

sr1646v2EfmBrSStIntRpCost OBJECT-TYPE
   SYNTAX      Integer32
   MAX-ACCESS  read-only
   STATUS      current
   DESCRIPTION
      "Path: efm.status.bridging.spanningTree.intRootPathCost"
   ::= {sr1646v2EfmBrSEntry 33882112}

sr1646v2EfmBrSStDesBrIdPriority OBJECT-TYPE
   SYNTAX      Integer32
   MAX-ACCESS  read-only
   STATUS      current
   DESCRIPTION
      "Path: efm.status.bridging.spanningTree.designatedBridgeId.priority"
   ::= {sr1646v2EfmBrSEntry 33947904}

sr1646v2EfmBrSStDesBrIdMacAddress OBJECT-TYPE
   SYNTAX      OCTET STRING
   MAX-ACCESS  read-only
   STATUS      current
   DESCRIPTION
      "Path: efm.status.bridging.spanningTree.designatedBridgeId.macAddress

       MAC address."
   ::= {sr1646v2EfmBrSEntry 33948160}

sr1646v2EfmBrSStDesPrtId OBJECT-TYPE
   SYNTAX      Integer32
   MAX-ACCESS  read-only
   STATUS      current
   DESCRIPTION
      "Path: efm.status.bridging.spanningTree.designatedPortId"
   ::= {sr1646v2EfmBrSEntry 34013184}

sr1646v2EfmBrSStDesInt OBJECT-TYPE
   SYNTAX      INTEGER
               {
               no (0),
               yes (1)
               }
   MAX-ACCESS  read-only
   STATUS      current
   DESCRIPTION
      "Path: efm.status.bridging.spanningTree.designatedOrInternal

       Possibilities:
               no   (0)
               yes   (1)"
   ::= {sr1646v2EfmBrSEntry 34078720}

sr1646v2EfmBrSStEdgeDetection OBJECT-TYPE
   SYNTAX      INTEGER
               {
               none (0),
               edge (1),
               notEdge (2)
               }
   MAX-ACCESS  read-only
   STATUS      current
   DESCRIPTION
      "Path: efm.status.bridging.spanningTree.edgeDetection

       Possibilities:
               none   (0)
               edge   (1)
               notEdge   (2)"
   ::= {sr1646v2EfmBrSEntry 34144256}


sr1646v2EfmMacAddress OBJECT-TYPE
   SYNTAX      OCTET STRING
   MAX-ACCESS  read-only
   STATUS      current
   DESCRIPTION
      "Path: efm.status.macAddress
       Info: ifPhysAddress

       MAC address."
   ::= {sr1646v2Efm 105}


sr1646v2EfmIpAdEntBcastAddr OBJECT-TYPE
   SYNTAX      Integer32
   MAX-ACCESS  read-only
   STATUS      current
   DESCRIPTION
      "Path: efm.status.ipAdEntBcastAddr
       Info: ipAdEntBcastAddr"
   ::= {sr1646v2Efm 124}


sr1646v2EfmIpAdEntReasmMaxSize OBJECT-TYPE
   SYNTAX      Integer32
   MAX-ACCESS  read-only
   STATUS      current
   DESCRIPTION
      "Path: efm.status.ipAdEntReasmMaxSize
       Info: ipAdEntReasmMaxSize"
   ::= {sr1646v2Efm 125}


sr1646v2EfmOam OBJECT IDENTIFIER ::= {sr1646v2Efm 901}

sr1646v2EfmOamSSC OBJECT IDENTIFIER ::= {sr1646v2EfmOam 1}

sr1646v2EfmOamEntry OBJECT IDENTIFIER ::= {sr1646v2EfmOamSSC 1}

sr1646v2EfmOamDiscovery OBJECT-TYPE
   SYNTAX      INTEGER
               {
               fault (0),
               sendLocal (1),
               passiveWait (2),
               sendLocalRemote (3),
               sendLocalRemoteOk (4),
               sendAny (5)
               }
   MAX-ACCESS  read-only
   STATUS      current
   DESCRIPTION
      "Path: efm.status.oam.discovery

       Possibilities:
               fault   (0)
               sendLocal   (1)
               passiveWait   (2)
               sendLocalRemote   (3)
               sendLocalRemoteOk   (4)
               sendAny   (5)"
   ::= {sr1646v2EfmOamEntry 16777216}

sr1646v2EfmOamLoopback OBJECT-TYPE
   SYNTAX      INTEGER
               {
               idle (0),
               waiting (1),
               localRunning (2),
               remoteRunning (3)
               }
   MAX-ACCESS  read-only
   STATUS      current
   DESCRIPTION
      "Path: efm.status.oam.loopback

       Possibilities:
               idle   (0)
               waiting   (1)
               localRunning   (2)
               remoteRunning   (3)"
   ::= {sr1646v2EfmOamEntry 33554432}

sr1646v2EfmOamLocalInfoVersion OBJECT-TYPE
   SYNTAX      Integer32
   MAX-ACCESS  read-only
   STATUS      current
   DESCRIPTION
      "Path: efm.status.oam.localInfo.version"
   ::= {sr1646v2EfmOamEntry 50397184}

sr1646v2EfmOamLocalInfoRevision OBJECT-TYPE
   SYNTAX      Integer32
   MAX-ACCESS  read-only
   STATUS      current
   DESCRIPTION
      "Path: efm.status.oam.localInfo.revision"
   ::= {sr1646v2EfmOamEntry 50462720}

sr1646v2EfmOamLocalInfoStateMuxAction OBJECT-TYPE
   SYNTAX      INTEGER
               {
               forwarding (0),
               discarding (1)
               }
   MAX-ACCESS  read-only
   STATUS      current
   DESCRIPTION
      "Path: efm.status.oam.localInfo.state.muxAction

       Possibilities:
               forwarding   (0)
               discarding   (1)"
   ::= {sr1646v2EfmOamEntry 50528512}

sr1646v2EfmOamLocalInfoStateParserAction OBJECT-TYPE
   SYNTAX      INTEGER
               {
               forwarding (0),
               loopback (1),
               discarding (2),
               reserved (3)
               }
   MAX-ACCESS  read-only
   STATUS      current
   DESCRIPTION
      "Path: efm.status.oam.localInfo.state.parserAction

       Possibilities:
               forwarding   (0)
               loopback   (1)
               discarding   (2)
               reserved   (3)"
   ::= {sr1646v2EfmOamEntry 50528768}

sr1646v2EfmOamLocalInfoOui OBJECT-TYPE
   SYNTAX      OCTET STRING
   MAX-ACCESS  read-only
   STATUS      current
   DESCRIPTION
      "Path: efm.status.oam.localInfo.oui"
   ::= {sr1646v2EfmOamEntry 50593792}

sr1646v2EfmOamLocalInfoVendorInfo OBJECT-TYPE
   SYNTAX      OCTET STRING
   MAX-ACCESS  read-only
   STATUS      current
   DESCRIPTION
      "Path: efm.status.oam.localInfo.vendorInfo"
   ::= {sr1646v2EfmOamEntry 50659328}

sr1646v2EfmOamLocalInfoVarRetrieval OBJECT-TYPE
   SYNTAX      INTEGER
               {
               notSupported (0),
               supported (1)
               }
   MAX-ACCESS  read-only
   STATUS      current
   DESCRIPTION
      "Path: efm.status.oam.localInfo.varRetrieval

       Possibilities:
               notSupported   (0)
               supported   (1)"
   ::= {sr1646v2EfmOamEntry 50724864}

sr1646v2EfmOamLocalInfoLinkEvents OBJECT-TYPE
   SYNTAX      INTEGER
               {
               ignored (0),
               interpreted (1)
               }
   MAX-ACCESS  read-only
   STATUS      current
   DESCRIPTION
      "Path: efm.status.oam.localInfo.linkEvents

       Possibilities:
               ignored   (0)
               interpreted   (1)"
   ::= {sr1646v2EfmOamEntry 50790400}

sr1646v2EfmOamLocalInfoLoopback OBJECT-TYPE
   SYNTAX      INTEGER
               {
               notSupported (0),
               supported (1)
               }
   MAX-ACCESS  read-only
   STATUS      current
   DESCRIPTION
      "Path: efm.status.oam.localInfo.loopback

       Possibilities:
               notSupported   (0)
               supported   (1)"
   ::= {sr1646v2EfmOamEntry 50855936}

sr1646v2EfmOamLocalInfoUnidirectional OBJECT-TYPE
   SYNTAX      INTEGER
               {
               notSupported (0),
               supported (1)
               }
   MAX-ACCESS  read-only
   STATUS      current
   DESCRIPTION
      "Path: efm.status.oam.localInfo.unidirectional

       Possibilities:
               notSupported   (0)
               supported   (1)"
   ::= {sr1646v2EfmOamEntry 50921472}

sr1646v2EfmOamLocalInfoMode OBJECT-TYPE
   SYNTAX      INTEGER
               {
               passive (0),
               active (1)
               }
   MAX-ACCESS  read-only
   STATUS      current
   DESCRIPTION
      "Path: efm.status.oam.localInfo.mode

       Possibilities:
               passive   (0)
               active   (1)"
   ::= {sr1646v2EfmOamEntry 50987008}

sr1646v2EfmOamLocalInfoMaxPduSize OBJECT-TYPE
   SYNTAX      Integer32
   MAX-ACCESS  read-only
   STATUS      current
   DESCRIPTION
      "Path: efm.status.oam.localInfo.maxPduSize"
   ::= {sr1646v2EfmOamEntry 51052544}

sr1646v2EfmOamRemoteInfoVersion OBJECT-TYPE
   SYNTAX      Integer32
   MAX-ACCESS  read-only
   STATUS      current
   DESCRIPTION
      "Path: efm.status.oam.remoteInfo.version"
   ::= {sr1646v2EfmOamEntry 67174400}

sr1646v2EfmOamRemoteInfoRevision OBJECT-TYPE
   SYNTAX      Integer32
   MAX-ACCESS  read-only
   STATUS      current
   DESCRIPTION
      "Path: efm.status.oam.remoteInfo.revision"
   ::= {sr1646v2EfmOamEntry 67239936}

sr1646v2EfmOamRemoteInfoStateMuxAction OBJECT-TYPE
   SYNTAX      INTEGER
               {
               forwarding (0),
               discarding (1)
               }
   MAX-ACCESS  read-only
   STATUS      current
   DESCRIPTION
      "Path: efm.status.oam.remoteInfo.state.muxAction

       Possibilities:
               forwarding   (0)
               discarding   (1)"
   ::= {sr1646v2EfmOamEntry 67305728}

sr1646v2EfmOamRemoteInfoStateParserAction OBJECT-TYPE
   SYNTAX      INTEGER
               {
               forwarding (0),
               loopback (1),
               discarding (2),
               reserved (3)
               }
   MAX-ACCESS  read-only
   STATUS      current
   DESCRIPTION
      "Path: efm.status.oam.remoteInfo.state.parserAction

       Possibilities:
               forwarding   (0)
               loopback   (1)
               discarding   (2)
               reserved   (3)"
   ::= {sr1646v2EfmOamEntry 67305984}

sr1646v2EfmOamRemoteInfoOui OBJECT-TYPE
   SYNTAX      OCTET STRING
   MAX-ACCESS  read-only
   STATUS      current
   DESCRIPTION
      "Path: efm.status.oam.remoteInfo.oui"
   ::= {sr1646v2EfmOamEntry 67371008}

sr1646v2EfmOamRemoteInfoVendorInfo OBJECT-TYPE
   SYNTAX      OCTET STRING
   MAX-ACCESS  read-only
   STATUS      current
   DESCRIPTION
      "Path: efm.status.oam.remoteInfo.vendorInfo"
   ::= {sr1646v2EfmOamEntry 67436544}

sr1646v2EfmOamRemoteInfoVarRetrieval OBJECT-TYPE
   SYNTAX      INTEGER
               {
               notSupported (0),
               supported (1)
               }
   MAX-ACCESS  read-only
   STATUS      current
   DESCRIPTION
      "Path: efm.status.oam.remoteInfo.varRetrieval

       Possibilities:
               notSupported   (0)
               supported   (1)"
   ::= {sr1646v2EfmOamEntry 67502080}

sr1646v2EfmOamRemoteInfoLinkEvents OBJECT-TYPE
   SYNTAX      INTEGER
               {
               ignored (0),
               interpreted (1)
               }
   MAX-ACCESS  read-only
   STATUS      current
   DESCRIPTION
      "Path: efm.status.oam.remoteInfo.linkEvents

       Possibilities:
               ignored   (0)
               interpreted   (1)"
   ::= {sr1646v2EfmOamEntry 67567616}

sr1646v2EfmOamRemoteInfoLoopback OBJECT-TYPE
   SYNTAX      INTEGER
               {
               notSupported (0),
               supported (1)
               }
   MAX-ACCESS  read-only
   STATUS      current
   DESCRIPTION
      "Path: efm.status.oam.remoteInfo.loopback

       Possibilities:
               notSupported   (0)
               supported   (1)"
   ::= {sr1646v2EfmOamEntry 67633152}

sr1646v2EfmOamRemoteInfoUnidirectional OBJECT-TYPE
   SYNTAX      INTEGER
               {
               notSupported (0),
               supported (1)
               }
   MAX-ACCESS  read-only
   STATUS      current
   DESCRIPTION
      "Path: efm.status.oam.remoteInfo.unidirectional

       Possibilities:
               notSupported   (0)
               supported   (1)"
   ::= {sr1646v2EfmOamEntry 67698688}

sr1646v2EfmOamRemoteInfoMode OBJECT-TYPE
   SYNTAX      INTEGER
               {
               passive (0),
               active (1)
               }
   MAX-ACCESS  read-only
   STATUS      current
   DESCRIPTION
      "Path: efm.status.oam.remoteInfo.mode

       Possibilities:
               passive   (0)
               active   (1)"
   ::= {sr1646v2EfmOamEntry 67764224}

sr1646v2EfmOamRemoteInfoMaxPduSize OBJECT-TYPE
   SYNTAX      Integer32
   MAX-ACCESS  read-only
   STATUS      current
   DESCRIPTION
      "Path: efm.status.oam.remoteInfo.maxPduSize"
   ::= {sr1646v2EfmOamEntry 67829760}

sr1646v2EfmOamEventsErroredSymbolWindow OBJECT-TYPE
   SYNTAX      Integer32
   UNITS       "symbols"
   MAX-ACCESS  read-only
   STATUS      current
   DESCRIPTION
      "Path: efm.status.oam.events.erroredSymbol.window

       unit name = symbols"
   ::= {sr1646v2EfmOamEntry 83951872}

sr1646v2EfmOamEventsErroredSymbolThreshold OBJECT-TYPE
   SYNTAX      OCTET STRING
   UNITS       "symbols"
   MAX-ACCESS  read-only
   STATUS      current
   DESCRIPTION
      "Path: efm.status.oam.events.erroredSymbol.threshold

       unit name = symbols"
   ::= {sr1646v2EfmOamEntry 83952128}

sr1646v2EfmOamEventsErroredFramePeriodWindow OBJECT-TYPE
   SYNTAX      INTEGER
               {
               default (0)
               }
   UNITS       "frames"
   MAX-ACCESS  read-only
   STATUS      current
   DESCRIPTION
      "Path: efm.status.oam.events.erroredFramePeriod.window

       unit name = frames

       Possibilities:
               default   (0)"
   ::= {sr1646v2EfmOamEntry 84017408}

sr1646v2EfmOamEventsErroredFramePeriodThreshold OBJECT-TYPE
   SYNTAX      Integer32
   UNITS       "frames"
   MAX-ACCESS  read-only
   STATUS      current
   DESCRIPTION
      "Path: efm.status.oam.events.erroredFramePeriod.threshold

       unit name = frames"
   ::= {sr1646v2EfmOamEntry 84017664}

sr1646v2EfmOamEventsErroredFrameWindow OBJECT-TYPE
   SYNTAX      Integer32
   UNITS       "100msec"
   MAX-ACCESS  read-only
   STATUS      current
   DESCRIPTION
      "Path: efm.status.oam.events.erroredFrame.window

       unit name = 100msec"
   ::= {sr1646v2EfmOamEntry 84082944}

sr1646v2EfmOamEventsErroredFrameThreshold OBJECT-TYPE
   SYNTAX      Integer32
   UNITS       "frames"
   MAX-ACCESS  read-only
   STATUS      current
   DESCRIPTION
      "Path: efm.status.oam.events.erroredFrame.threshold

       unit name = frames"
   ::= {sr1646v2EfmOamEntry 84083200}

sr1646v2EfmOamEventsErroredFrameSecondsWindow OBJECT-TYPE
   SYNTAX      Integer32
   UNITS       "100msec"
   MAX-ACCESS  read-only
   STATUS      current
   DESCRIPTION
      "Path: efm.status.oam.events.erroredFrameSeconds.window

       unit name = 100msec"
   ::= {sr1646v2EfmOamEntry 84148480}

sr1646v2EfmOamEventsErroredFrameSecondsThreshold OBJECT-TYPE
   SYNTAX      Integer32
   UNITS       "frames"
   MAX-ACCESS  read-only
   STATUS      current
   DESCRIPTION
      "Path: efm.status.oam.events.erroredFrameSeconds.threshold

       unit name = frames"
   ::= {sr1646v2EfmOamEntry 84148736}


sr1646v2EfmOamEventLog OBJECT IDENTIFIER ::= {sr1646v2Efm 911}

sr1646v2EfmOamEventLogSSCTable OBJECT-TYPE
   SYNTAX      SEQUENCE OF Sr1646v2EfmOamEventLogEntry
   MAX-ACCESS  not-accessible
   STATUS      current
   DESCRIPTION
      "OAM event log"
   ::= {sr1646v2EfmOamEventLog 1}

sr1646v2EfmOamEventLogEntry OBJECT-TYPE
   SYNTAX      Sr1646v2EfmOamEventLogEntry
   MAX-ACCESS  not-accessible
   STATUS      current
   DESCRIPTION
      ""
   INDEX      { sr1646v2EfmOamEventLogTableIx }
   ::= {sr1646v2EfmOamEventLogSSCTable 1}

Sr1646v2EfmOamEventLogEntry ::=
   SEQUENCE
      {
      sr1646v2EfmOamEventLogTableIx
         TableIndex,
      sr1646v2EfmOamEventLogSysUpTime
         TimeTicks,
      sr1646v2EfmOamEventLogLocation
         INTEGER,
      sr1646v2EfmOamEventLogType
         INTEGER,
      sr1646v2EfmOamEventLogOui
         OCTET STRING,
      sr1646v2EfmOamEventLogWindow
         Counter64,
      sr1646v2EfmOamEventLogThreshold
         Counter64,
      sr1646v2EfmOamEventLogTotal
         Counter32,
      sr1646v2EfmOamEventLogValue
         Counter64,
      sr1646v2EfmOamEventLogRunningTotal
         Counter64
      }

sr1646v2EfmOamEventLogTableIx OBJECT-TYPE
   SYNTAX      TableIndex
   MAX-ACCESS  not-accessible
   STATUS      current
   DESCRIPTION
      ""
   ::= {sr1646v2EfmOamEventLogEntry 11}

sr1646v2EfmOamEventLogSysUpTime OBJECT-TYPE
   SYNTAX      TimeTicks
   MAX-ACCESS  read-only
   STATUS      current
   DESCRIPTION
      "Path: efm.status.oamEventLog.sysUpTime

       Time in centi-second."
   ::= {sr1646v2EfmOamEventLogEntry 16777216}

sr1646v2EfmOamEventLogLocation OBJECT-TYPE
   SYNTAX      INTEGER
               {
               local (1),
               remote (2)
               }
   MAX-ACCESS  read-only
   STATUS      current
   DESCRIPTION
      "Path: efm.status.oamEventLog.location

       Possibilities:
               local   (1)
               remote   (2)"
   ::= {sr1646v2EfmOamEventLogEntry 33554432}

sr1646v2EfmOamEventLogType OBJECT-TYPE
   SYNTAX      INTEGER
               {
               erroredSymbols (1),
               erroredFramePeriod (2),
               erroredFrame (3),
               erroredFrameSeconds (4),
               linkFault (256),
               dyingGasp (257),
               criticalLink (258)
               }
   MAX-ACCESS  read-only
   STATUS      current
   DESCRIPTION
      "Path: efm.status.oamEventLog.type

       Possibilities:
               erroredSymbols   (1)
               erroredFramePeriod   (2)
               erroredFrame   (3)
               erroredFrameSeconds   (4)
               linkFault   (256)
               dyingGasp   (257)
               criticalLink   (258)"
   ::= {sr1646v2EfmOamEventLogEntry 50331648}

sr1646v2EfmOamEventLogOui OBJECT-TYPE
   SYNTAX      OCTET STRING
   MAX-ACCESS  read-only
   STATUS      current
   DESCRIPTION
      "Path: efm.status.oamEventLog.oui"
   ::= {sr1646v2EfmOamEventLogEntry 67108864}

sr1646v2EfmOamEventLogWindow OBJECT-TYPE
   SYNTAX      Counter64
   MAX-ACCESS  read-only
   STATUS      current
   DESCRIPTION
      "Path: efm.status.oamEventLog.window

       64 bit unsigned wrappable counter."
   ::= {sr1646v2EfmOamEventLogEntry 83886080}

sr1646v2EfmOamEventLogThreshold OBJECT-TYPE
   SYNTAX      Counter64
   MAX-ACCESS  read-only
   STATUS      current
   DESCRIPTION
      "Path: efm.status.oamEventLog.threshold

       64 bit unsigned wrappable counter."
   ::= {sr1646v2EfmOamEventLogEntry 100663296}

sr1646v2EfmOamEventLogTotal OBJECT-TYPE
   SYNTAX      Counter32
   MAX-ACCESS  read-only
   STATUS      current
   DESCRIPTION
      "Path: efm.status.oamEventLog.total

       32 bit unsigned wrappable counter."
   ::= {sr1646v2EfmOamEventLogEntry 117440512}

sr1646v2EfmOamEventLogValue OBJECT-TYPE
   SYNTAX      Counter64
   MAX-ACCESS  read-only
   STATUS      current
   DESCRIPTION
      "Path: efm.status.oamEventLog.value

       64 bit unsigned wrappable counter."
   ::= {sr1646v2EfmOamEventLogEntry 134217728}

sr1646v2EfmOamEventLogRunningTotal OBJECT-TYPE
   SYNTAX      Counter64
   MAX-ACCESS  read-only
   STATUS      current
   DESCRIPTION
      "Path: efm.status.oamEventLog.runningTotal

       64 bit unsigned wrappable counter."
   ::= {sr1646v2EfmOamEventLogEntry 150994944}


sr1646v2EfmIpV6 OBJECT IDENTIFIER ::= {sr1646v2Efm 17}

sr1646v2EfmIpV6SSC OBJECT IDENTIFIER ::= {sr1646v2EfmIpV6 1}

sr1646v2EfmIpV6Entry OBJECT IDENTIFIER ::= {sr1646v2EfmIpV6SSC 1}

sr1646v2EfmIpV6State OBJECT-TYPE
   SYNTAX      INTEGER
               {
               disabled (0),
               enabled (1)
               }
   MAX-ACCESS  read-only
   STATUS      current
   DESCRIPTION
      "Path: efm.status.ipV6.state

       Possibilities:
               disabled   (0)
               enabled   (1)"
   ::= {sr1646v2EfmIpV6Entry 16777216}

sr1646v2EfmIpV6InterfaceId OBJECT-TYPE
   SYNTAX      OCTET STRING
   MAX-ACCESS  read-only
   STATUS      current
   DESCRIPTION
      "Path: efm.status.ipV6.interfaceId"
   ::= {sr1646v2EfmIpV6Entry 33554432}

sr1646v2EfmIpV6LinkMtu OBJECT-TYPE
   SYNTAX      Integer32
   MAX-ACCESS  read-only
   STATUS      current
   DESCRIPTION
      "Path: efm.status.ipV6.linkMtu"
   ::= {sr1646v2EfmIpV6Entry 67108864}

sr1646v2EfmIpV6HopLimit OBJECT-TYPE
   SYNTAX      Integer32
   MAX-ACCESS  read-only
   STATUS      current
   DESCRIPTION
      "Path: efm.status.ipV6.hopLimit"
   ::= {sr1646v2EfmIpV6Entry 83886080}

sr1646v2EfmIpV6DhcpIaid OBJECT-TYPE
   SYNTAX      Counter32
   MAX-ACCESS  read-only
   STATUS      current
   DESCRIPTION
      "Path: efm.status.ipV6.dhcp.iaid

       32 bit unsigned wrappable counter."
   ::= {sr1646v2EfmIpV6Entry 100728832}

sr1646v2EfmIpV6RaRcvOption OBJECT-TYPE
   SYNTAX      Integer32
   MAX-ACCESS  read-only
   STATUS      current
   DESCRIPTION
      "Path: efm.status.ipV6.raRcvOption

       Bit meanings:
               bit 0 = linkMtu,
               bit 1 = srcLinkLayer,
               bit 2 = prefixInfo,
               bit 3 = rdnss,
               bit 4 = dnssl"
   ::= {sr1646v2EfmIpV6Entry 117440512}

sr1646v2EfmIpV6Addresses OBJECT-TYPE
   SYNTAX      SEQUENCE OF Sr1646v2EfmIpV6AddressesEntry
   MAX-ACCESS  not-accessible
   STATUS      current
   DESCRIPTION
      ""
   ::= {sr1646v2EfmIpV6 50331648}

sr1646v2EfmIpV6AddressesEntry OBJECT-TYPE
   SYNTAX      Sr1646v2EfmIpV6AddressesEntry
   MAX-ACCESS  not-accessible
   STATUS      current
   DESCRIPTION
      ""
   INDEX      { sr1646v2EfmIpV6AddressesTableIx }
   ::= {sr1646v2EfmIpV6Addresses 1}

Sr1646v2EfmIpV6AddressesEntry ::=
   SEQUENCE
      {
      sr1646v2EfmIpV6AddressesTableIx
         TableIndex,
      sr1646v2EfmIpV6AddressesAddress
         Ipv6Address,
      sr1646v2EfmIpV6AddressesPrefixLength
         Integer32,
      sr1646v2EfmIpV6AddressesStatus
         INTEGER,
      sr1646v2EfmIpV6AddressesOrigin
         INTEGER,
      sr1646v2EfmIpV6AddressesFlagsInterfaceId
         INTEGER,
      sr1646v2EfmIpV6AddressesFlagsAnycast
         INTEGER,
      sr1646v2EfmIpV6AddressesTimersValidLifeTime
         TimeTicks,
      sr1646v2EfmIpV6AddressesTimersPrefLifeTime
         TimeTicks
      }

sr1646v2EfmIpV6AddressesTableIx OBJECT-TYPE
   SYNTAX      TableIndex
   MAX-ACCESS  not-accessible
   STATUS      current
   DESCRIPTION
      ""
   ::= {sr1646v2EfmIpV6AddressesEntry 11}

sr1646v2EfmIpV6AddressesAddress OBJECT-TYPE
   SYNTAX      Ipv6Address
   MAX-ACCESS  read-only
   STATUS      current
   DESCRIPTION
      "Path: efm.status.ipV6.addresses.address

       ipv6 address"
   ::= {sr1646v2EfmIpV6AddressesEntry 16777216}

sr1646v2EfmIpV6AddressesPrefixLength OBJECT-TYPE
   SYNTAX      Integer32
   MAX-ACCESS  read-only
   STATUS      current
   DESCRIPTION
      "Path: efm.status.ipV6.addresses.prefixLength"
   ::= {sr1646v2EfmIpV6AddressesEntry 33554432}

sr1646v2EfmIpV6AddressesStatus OBJECT-TYPE
   SYNTAX      INTEGER
               {
               invalid (0),
               tentative (1),
               deprecated (2),
               preferred (3)
               }
   MAX-ACCESS  read-only
   STATUS      current
   DESCRIPTION
      "Path: efm.status.ipV6.addresses.status

       Possibilities:
               invalid   (0)
               tentative   (1)
               deprecated   (2)
               preferred   (3)"
   ::= {sr1646v2EfmIpV6AddressesEntry 50331648}

sr1646v2EfmIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: efm.status.ipV6.addresses.origin

       Possibilities:
               unknown   (0)
               manual   (1)
               generalPrefix   (2)
               statelessAuto   (3)
               statefullAuto   (4)"
   ::= {sr1646v2EfmIpV6AddressesEntry 67108864}

sr1646v2EfmIpV6AddressesFlagsInterfaceId OBJECT-TYPE
   SYNTAX      INTEGER
               {
               no (0),
               yes (1)
               }
   MAX-ACCESS  read-only
   STATUS      current
   DESCRIPTION
      "Path: efm.status.ipV6.addresses.flags.interfaceId

       Possibilities:
               no   (0)
               yes   (1)"
   ::= {sr1646v2EfmIpV6AddressesEntry 83951616}

sr1646v2EfmIpV6AddressesFlagsAnycast OBJECT-TYPE
   SYNTAX      INTEGER
               {
               no (0),
               yes (1)
               }
   MAX-ACCESS  read-only
   STATUS      current
   DESCRIPTION
      "Path: efm.status.ipV6.addresses.flags.anycast

       Possibilities:
               no   (0)
               yes   (1)"
   ::= {sr1646v2EfmIpV6AddressesEntry 84017152}

sr1646v2EfmIpV6AddressesTimersValidLifeTime OBJECT-TYPE
   SYNTAX      TimeTicks
   MAX-ACCESS  read-only
   STATUS      current
   DESCRIPTION
      "Path: efm.status.ipV6.addresses.timers.validLifeTime

       Time in centi-second."
   ::= {sr1646v2EfmIpV6AddressesEntry 100794368}

sr1646v2EfmIpV6AddressesTimersPrefLifeTime OBJECT-TYPE
   SYNTAX      TimeTicks
   MAX-ACCESS  read-only
   STATUS      current
   DESCRIPTION
      "Path: efm.status.ipV6.addresses.timers.prefLifeTime

       Time in centi-second."
   ::= {sr1646v2EfmIpV6AddressesEntry 100728832}


sr1646v2EfmVlan OBJECT IDENTIFIER ::= {sr1646v2Efm 34}

sr1646v2EfmVlanSSCTable OBJECT-TYPE
   SYNTAX      SEQUENCE OF Sr1646v2EfmVlanEntry
   MAX-ACCESS  not-accessible
   STATUS      current
   DESCRIPTION
      ""
   ::= {sr1646v2EfmVlan 1}

sr1646v2EfmVlanEntry OBJECT-TYPE
   SYNTAX      Sr1646v2EfmVlanEntry
   MAX-ACCESS  not-accessible
   STATUS      current
   DESCRIPTION
      ""
   INDEX      { sr1646v2EfmVlanTableIx }
   ::= {sr1646v2EfmVlanSSCTable 1}

Sr1646v2EfmVlanEntry ::=
   SEQUENCE
      {
      sr1646v2EfmVlanTableIx
         TableIndex,
      sr1646v2EfmVlanName
         DisplayString,
      sr1646v2EfmVlanMode
         INTEGER,
      sr1646v2EfmVlanIfOperStatus
         INTEGER,
      sr1646v2EfmVlanIfLastChange
         TimeTicks,
      sr1646v2EfmVlanIfLastChangeDate
         DisplayString,
      sr1646v2EfmVlanIpAddress
         IpAddress,
      sr1646v2EfmVlanIpNetMask
         IpAddress,
      sr1646v2EfmVlanIpRemote
         IpAddress,
      sr1646v2EfmVlanIpDhcpStatus
         INTEGER,
      sr1646v2EfmVlanIpDhcpLeaseTime
         TimeTicks,
      sr1646v2EfmVlanIpV6State
         INTEGER,
      sr1646v2EfmVlanIpV6InterfaceId
         OCTET STRING,
      sr1646v2EfmVlanIpV6LinkMtu
         Integer32,
      sr1646v2EfmVlanIpV6HopLimit
         Integer32,
      sr1646v2EfmVlanIpV6DhcpIaid
         Counter32,
      sr1646v2EfmVlanIpV6RaRcvOption
         Integer32,
      sr1646v2EfmVlanBridgingStatus
         INTEGER,
      sr1646v2EfmVlanBridgingSpanningTreePortRole
         INTEGER,
      sr1646v2EfmVlanBridgingSpanningTreePortId
         Integer32,
      sr1646v2EfmVlanBridgingSpanningTreePpCostExtPathCost
         Integer32,
      sr1646v2EfmVlanBridgingSpanningTreePpCostIntPathCost
         Integer32,
      sr1646v2EfmVlanBridgingSpanningTreeExtRpCost
         Integer32,
      sr1646v2EfmVlanBridgingSpanningTreeIntRpCost
         Integer32,
      sr1646v2EfmVlanBridgingSpanningTreeDesBrIdPriority
         Integer32,
      sr1646v2EfmVlanBridgingSpanningTreeDesBrIdMacAddress
         OCTET STRING,
      sr1646v2EfmVlanBridgingSpanningTreeDesPrtId
         Integer32,
      sr1646v2EfmVlanBridgingSpanningTreeDesInt
         INTEGER,
      sr1646v2EfmVlanBridgingSpanningTreeEdgeDetection
         INTEGER,
      sr1646v2EfmVlanVlanVid
         Integer32,
      sr1646v2EfmVlanPppOEthDiscState
         INTEGER,
      sr1646v2EfmVlanPppOEthPeerMac
         OCTET STRING,
      sr1646v2EfmVlanPppOEthServiceName
         DisplayString,
      sr1646v2EfmVlanPppLcpState
         INTEGER,
      sr1646v2EfmVlanPppIpcpState
         INTEGER,
      sr1646v2EfmVlanPppIp6cpState
         INTEGER,
      sr1646v2EfmVlanPppMyAutSt
         INTEGER,
      sr1646v2EfmVlanPppHisAutSt
         INTEGER,
      sr1646v2EfmVlanPppMru
         Integer32
      }

sr1646v2EfmVlanTableIx OBJECT-TYPE
   SYNTAX      TableIndex
   MAX-ACCESS  not-accessible
   STATUS      current
   DESCRIPTION
      ""
   ::= {sr1646v2EfmVlanEntry 11}

sr1646v2EfmVlanName OBJECT-TYPE
   SYNTAX      DisplayString
   MAX-ACCESS  read-only
   STATUS      current
   DESCRIPTION
      "Path: efm.status.vlan.name"
   ::= {sr1646v2EfmVlanEntry 16777216}

sr1646v2EfmVlanMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: efm.status.vlan.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1646v2EfmVlanEntry 335544320}

sr1646v2EfmVlanIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: efm.status.vlan.ifOperStatus

       Possibilities:
               up   (1)
               down   (2)
               testing   (3)
               unknown   (4)
               dormant   (5)
               notPresent   (6)
               lowerLayerDown   (7)"
   ::= {sr1646v2EfmVlanEntry 1795162112}

sr1646v2EfmVlanIfLastChange OBJECT-TYPE
   SYNTAX      TimeTicks
   MAX-ACCESS  read-only
   STATUS      current
   DESCRIPTION
      "Path: efm.status.vlan.ifLastChange

       Time in centi-second."
   ::= {sr1646v2EfmVlanEntry 1811939328}

sr1646v2EfmVlanIfLastChangeDate OBJECT-TYPE
   SYNTAX      DisplayString
   MAX-ACCESS  read-only
   STATUS      current
   DESCRIPTION
      "Path: efm.status.vlan.ifLastChangeDate"
   ::= {sr1646v2EfmVlanEntry 3070230528}

sr1646v2EfmVlanIpAddress OBJECT-TYPE
   SYNTAX      IpAddress
   MAX-ACCESS  read-only
   STATUS      current
   DESCRIPTION
      "Path: efm.status.vlan.ip.address"
   ::= {sr1646v2EfmVlanEntry 51380224}

sr1646v2EfmVlanIpNetMask OBJECT-TYPE
   SYNTAX      IpAddress
   MAX-ACCESS  read-only
   STATUS      current
   DESCRIPTION
      "Path: efm.status.vlan.ip.netMask"
   ::= {sr1646v2EfmVlanEntry 51445760}

sr1646v2EfmVlanIpRemote OBJECT-TYPE
   SYNTAX      IpAddress
   MAX-ACCESS  read-only
   STATUS      current
   DESCRIPTION
      "Path: efm.status.vlan.ip.remote"
   ::= {sr1646v2EfmVlanEntry 51511296}

sr1646v2EfmVlanIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: efm.status.vlan.ip.dhcp.status

       Possibilities:
               none   (0)
               selecting   (1)
               requesting   (2)
               rebinding   (3)
               bound   (4)
               renewing   (5)
               rebooting   (6)
               initreboot   (7)"
   ::= {sr1646v2EfmVlanEntry 51904768}

sr1646v2EfmVlanIpDhcpLeaseTime OBJECT-TYPE
   SYNTAX      TimeTicks
   MAX-ACCESS  read-only
   STATUS      current
   DESCRIPTION
      "Path: efm.status.vlan.ip.dhcp.leaseTime

       Time in centi-second."
   ::= {sr1646v2EfmVlanEntry 51905024}

sr1646v2EfmVlanIpV6State OBJECT-TYPE
   SYNTAX      INTEGER
               {
               disabled (0),
               enabled (1)
               }
   MAX-ACCESS  read-only
   STATUS      current
   DESCRIPTION
      "Path: efm.status.vlan.ipV6.state

       Possibilities:
               disabled   (0)
               enabled   (1)"
   ::= {sr1646v2EfmVlanEntry 100728832}

sr1646v2EfmVlanIpV6InterfaceId OBJECT-TYPE
   SYNTAX      OCTET STRING
   MAX-ACCESS  read-only
   STATUS      current
   DESCRIPTION
      "Path: efm.status.vlan.ipV6.interfaceId"
   ::= {sr1646v2EfmVlanEntry 100794368}

sr1646v2EfmVlanIpV6LinkMtu OBJECT-TYPE
   SYNTAX      Integer32
   MAX-ACCESS  read-only
   STATUS      current
   DESCRIPTION
      "Path: efm.status.vlan.ipV6.linkMtu"
   ::= {sr1646v2EfmVlanEntry 100925440}

sr1646v2EfmVlanIpV6HopLimit OBJECT-TYPE
   SYNTAX      Integer32
   MAX-ACCESS  read-only
   STATUS      current
   DESCRIPTION
      "Path: efm.status.vlan.ipV6.hopLimit"
   ::= {sr1646v2EfmVlanEntry 100990976}

sr1646v2EfmVlanIpV6DhcpIaid OBJECT-TYPE
   SYNTAX      Counter32
   MAX-ACCESS  read-only
   STATUS      current
   DESCRIPTION
      "Path: efm.status.vlan.ipV6.dhcp.iaid

       32 bit unsigned wrappable counter."
   ::= {sr1646v2EfmVlanEntry 101056768}

sr1646v2EfmVlanIpV6RaRcvOption OBJECT-TYPE
   SYNTAX      Integer32
   MAX-ACCESS  read-only
   STATUS      current
   DESCRIPTION
      "Path: efm.status.vlan.ipV6.raRcvOption

       Bit meanings:
               bit 0 = linkMtu,
               bit 1 = srcLinkLayer,
               bit 2 = prefixInfo,
               bit 3 = rdnss,
               bit 4 = dnssl"
   ::= {sr1646v2EfmVlanEntry 101122048}

sr1646v2EfmVlanBridgingStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: efm.status.vlan.bridging.status

       Possibilities:
               disabled   (0)
               discarding   (1)
               learning   (2)
               forwarding   (3)
               backupBlockedIntfDown   (256)
               backupBlockedIntfUp   (259)
               shutdown   (255)"
   ::= {sr1646v2EfmVlanEntry 453050368}

sr1646v2EfmVlanBridgingSpanningTreePortRole OBJECT-TYPE
   SYNTAX      INTEGER
               {
               none (0),
               root (1),
               designated (2),
               alternate (3),
               backup (4),
               disabled (5),
               master (6)
               }
   MAX-ACCESS  read-only
   STATUS      current
   DESCRIPTION
      "Path: efm.status.vlan.bridging.spanningTree.portRole

       Possibilities:
               none   (0)
               root   (1)
               designated   (2)
               alternate   (3)
               backup   (4)
               disabled   (5)
               master   (6)"
   ::= {sr1646v2EfmVlanEntry 453116160}

sr1646v2EfmVlanBridgingSpanningTreePortId OBJECT-TYPE
   SYNTAX      Integer32
   MAX-ACCESS  read-only
   STATUS      current
   DESCRIPTION
      "Path: efm.status.vlan.bridging.spanningTree.portId"
   ::= {sr1646v2EfmVlanEntry 453116416}

sr1646v2EfmVlanBridgingSpanningTreePpCostExtPathCost OBJECT-TYPE
   SYNTAX      Integer32
   MAX-ACCESS  read-only
   STATUS      current
   DESCRIPTION
      "Path: efm.status.vlan.bridging.spanningTree.portPathCosts.extPathCost"
   ::= {sr1646v2EfmVlanEntry 453116673}

sr1646v2EfmVlanBridgingSpanningTreePpCostIntPathCost OBJECT-TYPE
   SYNTAX      Integer32
   MAX-ACCESS  read-only
   STATUS      current
   DESCRIPTION
      "Path: efm.status.vlan.bridging.spanningTree.portPathCosts.intPathCost"
   ::= {sr1646v2EfmVlanEntry 453116674}

sr1646v2EfmVlanBridgingSpanningTreeExtRpCost OBJECT-TYPE
   SYNTAX      Integer32
   MAX-ACCESS  read-only
   STATUS      current
   DESCRIPTION
      "Path: efm.status.vlan.bridging.spanningTree.extRootPathCost"
   ::= {sr1646v2EfmVlanEntry 453116928}

sr1646v2EfmVlanBridgingSpanningTreeIntRpCost OBJECT-TYPE
   SYNTAX      Integer32
   MAX-ACCESS  read-only
   STATUS      current
   DESCRIPTION
      "Path: efm.status.vlan.bridging.spanningTree.intRootPathCost"
   ::= {sr1646v2EfmVlanEntry 453117184}

sr1646v2EfmVlanBridgingSpanningTreeDesBrIdPriority OBJECT-TYPE
   SYNTAX      Integer32
   MAX-ACCESS  read-only
   STATUS      current
   DESCRIPTION
      "Path: efm.status.vlan.bridging.spanningTree.designatedBridgeId.priority"
   ::= {sr1646v2EfmVlanEntry 453117441}

sr1646v2EfmVlanBridgingSpanningTreeDesBrIdMacAddress OBJECT-TYPE
   SYNTAX      OCTET STRING
   MAX-ACCESS  read-only
   STATUS      current
   DESCRIPTION
      "Path: efm.status.vlan.bridging.spanningTree.designatedBridgeId.macAddress

       MAC address."
   ::= {sr1646v2EfmVlanEntry 453117442}

sr1646v2EfmVlanBridgingSpanningTreeDesPrtId OBJECT-TYPE
   SYNTAX      Integer32
   MAX-ACCESS  read-only
   STATUS      current
   DESCRIPTION
      "Path: efm.status.vlan.bridging.spanningTree.designatedPortId"
   ::= {sr1646v2EfmVlanEntry 453117696}

sr1646v2EfmVlanBridgingSpanningTreeDesInt OBJECT-TYPE
   SYNTAX      INTEGER
               {
               no (0),
               yes (1)
               }
   MAX-ACCESS  read-only
   STATUS      current
   DESCRIPTION
      "Path: efm.status.vlan.bridging.spanningTree.designatedOrInternal

       Possibilities:
               no   (0)
               yes   (1)"
   ::= {sr1646v2EfmVlanEntry 453117952}

sr1646v2EfmVlanBridgingSpanningTreeEdgeDetection OBJECT-TYPE
   SYNTAX      INTEGER
               {
               none (0),
               edge (1),
               notEdge (2)
               }
   MAX-ACCESS  read-only
   STATUS      current
   DESCRIPTION
      "Path: efm.status.vlan.bridging.spanningTree.edgeDetection

       Possibilities:
               none   (0)
               edge   (1)
               notEdge   (2)"
   ::= {sr1646v2EfmVlanEntry 453118208}

sr1646v2EfmVlanVlanVid OBJECT-TYPE
   SYNTAX      Integer32
   MAX-ACCESS  read-only
   STATUS      current
   DESCRIPTION
      "Path: efm.status.vlan.vlan.vid"
   ::= {sr1646v2EfmVlanEntry 234946560}

sr1646v2EfmVlanPppOEthDiscState OBJECT-TYPE
   SYNTAX      INTEGER
               {
               idle (0),
               waitForPADO (1),
               waitForPADS (2),
               established (3)
               }
   MAX-ACCESS  read-only
   STATUS      current
   DESCRIPTION
      "Path: efm.status.vlan.pppOverEth.discState

       Possibilities:
               idle   (0)
               waitForPADO   (1)
               waitForPADS   (2)
               established   (3)"
   ::= {sr1646v2EfmVlanEntry 67174400}

sr1646v2EfmVlanPppOEthPeerMac OBJECT-TYPE
   SYNTAX      OCTET STRING
   MAX-ACCESS  read-only
   STATUS      current
   DESCRIPTION
      "Path: efm.status.vlan.pppOverEth.remoteMacAddress

       MAC address."
   ::= {sr1646v2EfmVlanEntry 67239936}

sr1646v2EfmVlanPppOEthServiceName OBJECT-TYPE
   SYNTAX      DisplayString
   MAX-ACCESS  read-only
   STATUS      current
   DESCRIPTION
      "Path: efm.status.vlan.pppOverEth.serviceName"
   ::= {sr1646v2EfmVlanEntry 67305472}

sr1646v2EfmVlanPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: efm.status.vlan.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2EfmVlanEntry 83951616}

sr1646v2EfmVlanPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: efm.status.vlan.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2EfmVlanEntry 84017152}

sr1646v2EfmVlanPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: efm.status.vlan.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2EfmVlanEntry 84869120}

sr1646v2EfmVlanPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: efm.status.vlan.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1646v2EfmVlanEntry 84541440}

sr1646v2EfmVlanPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: efm.status.vlan.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1646v2EfmVlanEntry 84606976}

sr1646v2EfmVlanPppMru OBJECT-TYPE
   SYNTAX      Integer32
   MAX-ACCESS  read-only
   STATUS      current
   DESCRIPTION
      "Path: efm.status.vlan.ppp.mru"
   ::= {sr1646v2EfmVlanEntry 84934656}

sr1646v2EfmVlanIpSecondaryIp OBJECT-TYPE
   SYNTAX      SEQUENCE OF Sr1646v2EfmVlanIpSecondaryIpEntry
   MAX-ACCESS  not-accessible
   STATUS      current
   DESCRIPTION
      ""
   ::= {sr1646v2EfmVlan 51838976}

sr1646v2EfmVlanIpSecondaryIpEntry OBJECT-TYPE
   SYNTAX      Sr1646v2EfmVlanIpSecondaryIpEntry
   MAX-ACCESS  not-accessible
   STATUS      current
   DESCRIPTION
      ""
   INDEX      { sr1646v2EfmVlanTableIx,
                sr1646v2EfmVlanIpSecondaryIpTableIx }
   ::= {sr1646v2EfmVlanIpSecondaryIp 1}

Sr1646v2EfmVlanIpSecondaryIpEntry ::=
   SEQUENCE
      {
      sr1646v2EfmVlanIpSecondaryIpTableIx
         TableIndex,
      sr1646v2EfmVlanIpSecondaryIpAddress
         IpAddress,
      sr1646v2EfmVlanIpSecondaryIpNetMask
         IpAddress
      }

sr1646v2EfmVlanIpSecondaryIpTableIx OBJECT-TYPE
   SYNTAX      TableIndex
   MAX-ACCESS  not-accessible
   STATUS      current
   DESCRIPTION
      ""
   ::= {sr1646v2EfmVlanIpSecondaryIpEntry 11}

sr1646v2EfmVlanIpSecondaryIpAddress OBJECT-TYPE
   SYNTAX      IpAddress
   MAX-ACCESS  read-only
   STATUS      current
   DESCRIPTION
      "Path: efm.status.vlan.ip.secondaryIp.address"
   ::= {sr1646v2EfmVlanIpSecondaryIpEntry 2030043136}

sr1646v2EfmVlanIpSecondaryIpNetMask OBJECT-TYPE
   SYNTAX      IpAddress
   MAX-ACCESS  read-only
   STATUS      current
   DESCRIPTION
      "Path: efm.status.vlan.ip.secondaryIp.netMask"
   ::= {sr1646v2EfmVlanIpSecondaryIpEntry 2063597568}

sr1646v2EfmVlanIpV6Addresses OBJECT-TYPE
   SYNTAX      SEQUENCE OF Sr1646v2EfmVlanIpV6AddressesEntry
   MAX-ACCESS  not-accessible
   STATUS      current
   DESCRIPTION
      ""
   ::= {sr1646v2EfmVlan 100859904}

sr1646v2EfmVlanIpV6AddressesEntry OBJECT-TYPE
   SYNTAX      Sr1646v2EfmVlanIpV6AddressesEntry
   MAX-ACCESS  not-accessible
   STATUS      current
   DESCRIPTION
      ""
   INDEX      { sr1646v2EfmVlanTableIx,
                sr1646v2EfmVlanIpV6AddressesTableIx }
   ::= {sr1646v2EfmVlanIpV6Addresses 1}

Sr1646v2EfmVlanIpV6AddressesEntry ::=
   SEQUENCE
      {
      sr1646v2EfmVlanIpV6AddressesTableIx
         TableIndex,
      sr1646v2EfmVlanIpV6AddressesAddress
         Ipv6Address,
      sr1646v2EfmVlanIpV6AddressesPrefixLength
         Integer32,
      sr1646v2EfmVlanIpV6AddressesStatus
         INTEGER,
      sr1646v2EfmVlanIpV6AddressesOrigin
         INTEGER,
      sr1646v2EfmVlanIpV6AddressesFlagsInterfaceId
         INTEGER,
      sr1646v2EfmVlanIpV6AddressesFlagsAnycast
         INTEGER,
      sr1646v2EfmVlanIpV6AddressesTimersValidLifeTime
         TimeTicks,
      sr1646v2EfmVlanIpV6AddressesTimersPrefLifeTime
         TimeTicks
      }

sr1646v2EfmVlanIpV6AddressesTableIx OBJECT-TYPE
   SYNTAX      TableIndex
   MAX-ACCESS  not-accessible
   STATUS      current
   DESCRIPTION
      ""
   ::= {sr1646v2EfmVlanIpV6AddressesEntry 11}

sr1646v2EfmVlanIpV6AddressesAddress OBJECT-TYPE
   SYNTAX      Ipv6Address
   MAX-ACCESS  read-only
   STATUS      current
   DESCRIPTION
      "Path: efm.status.vlan.ipV6.addresses.address

       ipv6 address"
   ::= {sr1646v2EfmVlanIpV6AddressesEntry 16777216}

sr1646v2EfmVlanIpV6AddressesPrefixLength OBJECT-TYPE
   SYNTAX      Integer32
   MAX-ACCESS  read-only
   STATUS      current
   DESCRIPTION
      "Path: efm.status.vlan.ipV6.addresses.prefixLength"
   ::= {sr1646v2EfmVlanIpV6AddressesEntry 33554432}

sr1646v2EfmVlanIpV6AddressesStatus OBJECT-TYPE
   SYNTAX      INTEGER
               {
               invalid (0),
               tentative (1),
               deprecated (2),
               preferred (3)
               }
   MAX-ACCESS  read-only
   STATUS      current
   DESCRIPTION
      "Path: efm.status.vlan.ipV6.addresses.status

       Possibilities:
               invalid   (0)
               tentative   (1)
               deprecated   (2)
               preferred   (3)"
   ::= {sr1646v2EfmVlanIpV6AddressesEntry 50331648}

sr1646v2EfmVlanIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: efm.status.vlan.ipV6.addresses.origin

       Possibilities:
               unknown   (0)
               manual   (1)
               generalPrefix   (2)
               statelessAuto   (3)
               statefullAuto   (4)"
   ::= {sr1646v2EfmVlanIpV6AddressesEntry 67108864}

sr1646v2EfmVlanIpV6AddressesFlagsInterfaceId OBJECT-TYPE
   SYNTAX      INTEGER
               {
               no (0),
               yes (1)
               }
   MAX-ACCESS  read-only
   STATUS      current
   DESCRIPTION
      "Path: efm.status.vlan.ipV6.addresses.flags.interfaceId

       Possibilities:
               no   (0)
               yes   (1)"
   ::= {sr1646v2EfmVlanIpV6AddressesEntry 83951616}

sr1646v2EfmVlanIpV6AddressesFlagsAnycast OBJECT-TYPE
   SYNTAX      INTEGER
               {
               no (0),
               yes (1)
               }
   MAX-ACCESS  read-only
   STATUS      current
   DESCRIPTION
      "Path: efm.status.vlan.ipV6.addresses.flags.anycast

       Possibilities:
               no   (0)
               yes   (1)"
   ::= {sr1646v2EfmVlanIpV6AddressesEntry 84017152}

sr1646v2EfmVlanIpV6AddressesTimersValidLifeTime OBJECT-TYPE
   SYNTAX      TimeTicks
   MAX-ACCESS  read-only
   STATUS      current
   DESCRIPTION
      "Path: efm.status.vlan.ipV6.addresses.timers.validLifeTime

       Time in centi-second."
   ::= {sr1646v2EfmVlanIpV6AddressesEntry 100794368}

sr1646v2EfmVlanIpV6AddressesTimersPrefLifeTime OBJECT-TYPE
   SYNTAX      TimeTicks
   MAX-ACCESS  read-only
   STATUS      current
   DESCRIPTION
      "Path: efm.status.vlan.ipV6.addresses.timers.prefLifeTime

       Time in centi-second."
   ::= {sr1646v2EfmVlanIpV6AddressesEntry 100728832}

sr1646v2EfmVlanVlanArpCache OBJECT-TYPE
   SYNTAX      SEQUENCE OF Sr1646v2EfmVlanVlanArpCacheEntry
   MAX-ACCESS  not-accessible
   STATUS      current
   DESCRIPTION
      ""
   ::= {sr1646v2EfmVlan 235601920}

sr1646v2EfmVlanVlanArpCacheEntry OBJECT-TYPE
   SYNTAX      Sr1646v2EfmVlanVlanArpCacheEntry
   MAX-ACCESS  not-accessible
   STATUS      current
   DESCRIPTION
      ""
   INDEX      { sr1646v2EfmVlanTableIx,
                sr1646v2EfmVlanVlanArpCacheTableIx }
   ::= {sr1646v2EfmVlanVlanArpCache 1}

Sr1646v2EfmVlanVlanArpCacheEntry ::=
   SEQUENCE
      {
      sr1646v2EfmVlanVlanArpCacheTableIx
         TableIndex,
      sr1646v2EfmVlanVlanArpCacheMacAddress
         OCTET STRING,
      sr1646v2EfmVlanVlanArpCacheIpAddress
         IpAddress,
      sr1646v2EfmVlanVlanArpCacheType
         INTEGER,
      sr1646v2EfmVlanVlanArpCacheTimeOut
         TimeTicks
      }

sr1646v2EfmVlanVlanArpCacheTableIx OBJECT-TYPE
   SYNTAX      TableIndex
   MAX-ACCESS  not-accessible
   STATUS      current
   DESCRIPTION
      ""
   ::= {sr1646v2EfmVlanVlanArpCacheEntry 11}

sr1646v2EfmVlanVlanArpCacheMacAddress OBJECT-TYPE
   SYNTAX      OCTET STRING
   MAX-ACCESS  read-only
   STATUS      current
   DESCRIPTION
      "Path: efm.status.vlan.vlan.arpCache.macAddress

       MAC address."
   ::= {sr1646v2EfmVlanVlanArpCacheEntry 16777216}

sr1646v2EfmVlanVlanArpCacheIpAddress OBJECT-TYPE
   SYNTAX      IpAddress
   MAX-ACCESS  read-only
   STATUS      current
   DESCRIPTION
      "Path: efm.status.vlan.vlan.arpCache.ipAddress"
   ::= {sr1646v2EfmVlanVlanArpCacheEntry 33554432}

sr1646v2EfmVlanVlanArpCacheType OBJECT-TYPE
   SYNTAX      INTEGER
               {
               static (0),
               dynamic (1)
               }
   MAX-ACCESS  read-only
   STATUS      current
   DESCRIPTION
      "Path: efm.status.vlan.vlan.arpCache.type

       Possibilities:
               static   (0)
               dynamic   (1)"
   ::= {sr1646v2EfmVlanVlanArpCacheEntry 50331648}

sr1646v2EfmVlanVlanArpCacheTimeOut OBJECT-TYPE
   SYNTAX      TimeTicks
   MAX-ACCESS  read-only
   STATUS      current
   DESCRIPTION
      "Path: efm.status.vlan.vlan.arpCache.timeOut

       Time in centi-second."
   ::= {sr1646v2EfmVlanVlanArpCacheEntry 67108864}


sr1646v2EfmPppOE OBJECT IDENTIFIER ::= {sr1646v2Efm 36}

sr1646v2EfmPppOESSCTable OBJECT-TYPE
   SYNTAX      SEQUENCE OF Sr1646v2EfmPppOEEntry
   MAX-ACCESS  not-accessible
   STATUS      current
   DESCRIPTION
      ""
   ::= {sr1646v2EfmPppOE 1}

sr1646v2EfmPppOEEntry OBJECT-TYPE
   SYNTAX      Sr1646v2EfmPppOEEntry
   MAX-ACCESS  not-accessible
   STATUS      current
   DESCRIPTION
      ""
   INDEX      { sr1646v2EfmPppOETableIx }
   ::= {sr1646v2EfmPppOESSCTable 1}

Sr1646v2EfmPppOEEntry ::=
   SEQUENCE
      {
      sr1646v2EfmPppOETableIx
         TableIndex,
      sr1646v2EfmPppOEName
         DisplayString,
      sr1646v2EfmPppOEMode
         INTEGER,
      sr1646v2EfmPppOEIfOperStatus
         INTEGER,
      sr1646v2EfmPppOEIfLastChange
         TimeTicks,
      sr1646v2EfmPppOEIfLastChangeDate
         DisplayString,
      sr1646v2EfmPppOEIpAddress
         IpAddress,
      sr1646v2EfmPppOEIpNetMask
         IpAddress,
      sr1646v2EfmPppOEIpRemote
         IpAddress,
      sr1646v2EfmPppOEPppOEthDiscState
         INTEGER,
      sr1646v2EfmPppOEPppOEthPeerMac
         OCTET STRING,
      sr1646v2EfmPppOEPppOEthServiceName
         DisplayString,
      sr1646v2EfmPppOEPppLcpState
         INTEGER,
      sr1646v2EfmPppOEPppIpcpState
         INTEGER,
      sr1646v2EfmPppOEPppIp6cpState
         INTEGER,
      sr1646v2EfmPppOEPppMyAutSt
         INTEGER,
      sr1646v2EfmPppOEPppHisAutSt
         INTEGER,
      sr1646v2EfmPppOEPppMru
         Integer32,
      sr1646v2EfmPppOEIpV6State
         INTEGER,
      sr1646v2EfmPppOEIpV6InterfaceId
         OCTET STRING,
      sr1646v2EfmPppOEIpV6LinkMtu
         Integer32,
      sr1646v2EfmPppOEIpV6HopLimit
         Integer32,
      sr1646v2EfmPppOEIpV6DhcpIaid
         Counter32,
      sr1646v2EfmPppOEIpV6RaRcvOption
         Integer32
      }

sr1646v2EfmPppOETableIx OBJECT-TYPE
   SYNTAX      TableIndex
   MAX-ACCESS  not-accessible
   STATUS      current
   DESCRIPTION
      ""
   ::= {sr1646v2EfmPppOEEntry 11}

sr1646v2EfmPppOEName OBJECT-TYPE
   SYNTAX      DisplayString
   MAX-ACCESS  read-only
   STATUS      current
   DESCRIPTION
      "Path: efm.status.pppoEClient.name"
   ::= {sr1646v2EfmPppOEEntry 16777216}

sr1646v2EfmPppOEMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: efm.status.pppoEClient.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1646v2EfmPppOEEntry 335544320}

sr1646v2EfmPppOEIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: efm.status.pppoEClient.ifOperStatus

       Possibilities:
               up   (1)
               down   (2)
               testing   (3)
               unknown   (4)
               dormant   (5)
               notPresent   (6)
               lowerLayerDown   (7)"
   ::= {sr1646v2EfmPppOEEntry 1795162112}

sr1646v2EfmPppOEIfLastChange OBJECT-TYPE
   SYNTAX      TimeTicks
   MAX-ACCESS  read-only
   STATUS      current
   DESCRIPTION
      "Path: efm.status.pppoEClient.ifLastChange

       Time in centi-second."
   ::= {sr1646v2EfmPppOEEntry 1811939328}

sr1646v2EfmPppOEIfLastChangeDate OBJECT-TYPE
   SYNTAX      DisplayString
   MAX-ACCESS  read-only
   STATUS      current
   DESCRIPTION
      "Path: efm.status.pppoEClient.ifLastChangeDate"
   ::= {sr1646v2EfmPppOEEntry 3070230528}

sr1646v2EfmPppOEIpAddress OBJECT-TYPE
   SYNTAX      IpAddress
   MAX-ACCESS  read-only
   STATUS      current
   DESCRIPTION
      "Path: efm.status.pppoEClient.ip.address"
   ::= {sr1646v2EfmPppOEEntry 51380224}

sr1646v2EfmPppOEIpNetMask OBJECT-TYPE
   SYNTAX      IpAddress
   MAX-ACCESS  read-only
   STATUS      current
   DESCRIPTION
      "Path: efm.status.pppoEClient.ip.netMask"
   ::= {sr1646v2EfmPppOEEntry 51445760}

sr1646v2EfmPppOEIpRemote OBJECT-TYPE
   SYNTAX      IpAddress
   MAX-ACCESS  read-only
   STATUS      current
   DESCRIPTION
      "Path: efm.status.pppoEClient.ip.remote"
   ::= {sr1646v2EfmPppOEEntry 51511296}

sr1646v2EfmPppOEPppOEthDiscState OBJECT-TYPE
   SYNTAX      INTEGER
               {
               idle (0),
               waitForPADO (1),
               waitForPADS (2),
               established (3)
               }
   MAX-ACCESS  read-only
   STATUS      current
   DESCRIPTION
      "Path: efm.status.pppoEClient.pppOverEth.discState

       Possibilities:
               idle   (0)
               waitForPADO   (1)
               waitForPADS   (2)
               established   (3)"
   ::= {sr1646v2EfmPppOEEntry 67174400}

sr1646v2EfmPppOEPppOEthPeerMac OBJECT-TYPE
   SYNTAX      OCTET STRING
   MAX-ACCESS  read-only
   STATUS      current
   DESCRIPTION
      "Path: efm.status.pppoEClient.pppOverEth.remoteMacAddress

       MAC address."
   ::= {sr1646v2EfmPppOEEntry 67239936}

sr1646v2EfmPppOEPppOEthServiceName OBJECT-TYPE
   SYNTAX      DisplayString
   MAX-ACCESS  read-only
   STATUS      current
   DESCRIPTION
      "Path: efm.status.pppoEClient.pppOverEth.serviceName"
   ::= {sr1646v2EfmPppOEEntry 67305472}

sr1646v2EfmPppOEPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: efm.status.pppoEClient.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2EfmPppOEEntry 83951616}

sr1646v2EfmPppOEPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: efm.status.pppoEClient.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2EfmPppOEEntry 84017152}

sr1646v2EfmPppOEPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: efm.status.pppoEClient.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2EfmPppOEEntry 84869120}

sr1646v2EfmPppOEPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: efm.status.pppoEClient.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1646v2EfmPppOEEntry 84541440}

sr1646v2EfmPppOEPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: efm.status.pppoEClient.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1646v2EfmPppOEEntry 84606976}

sr1646v2EfmPppOEPppMru OBJECT-TYPE
   SYNTAX      Integer32
   MAX-ACCESS  read-only
   STATUS      current
   DESCRIPTION
      "Path: efm.status.pppoEClient.ppp.mru"
   ::= {sr1646v2EfmPppOEEntry 84934656}

sr1646v2EfmPppOEIpV6State OBJECT-TYPE
   SYNTAX      INTEGER
               {
               disabled (0),
               enabled (1)
               }
   MAX-ACCESS  read-only
   STATUS      current
   DESCRIPTION
      "Path: efm.status.pppoEClient.ipV6.state

       Possibilities:
               disabled   (0)
               enabled   (1)"
   ::= {sr1646v2EfmPppOEEntry 100728832}

sr1646v2EfmPppOEIpV6InterfaceId OBJECT-TYPE
   SYNTAX      OCTET STRING
   MAX-ACCESS  read-only
   STATUS      current
   DESCRIPTION
      "Path: efm.status.pppoEClient.ipV6.interfaceId"
   ::= {sr1646v2EfmPppOEEntry 100794368}

sr1646v2EfmPppOEIpV6LinkMtu OBJECT-TYPE
   SYNTAX      Integer32
   MAX-ACCESS  read-only
   STATUS      current
   DESCRIPTION
      "Path: efm.status.pppoEClient.ipV6.linkMtu"
   ::= {sr1646v2EfmPppOEEntry 100925440}

sr1646v2EfmPppOEIpV6HopLimit OBJECT-TYPE
   SYNTAX      Integer32
   MAX-ACCESS  read-only
   STATUS      current
   DESCRIPTION
      "Path: efm.status.pppoEClient.ipV6.hopLimit"
   ::= {sr1646v2EfmPppOEEntry 100990976}

sr1646v2EfmPppOEIpV6DhcpIaid OBJECT-TYPE
   SYNTAX      Counter32
   MAX-ACCESS  read-only
   STATUS      current
   DESCRIPTION
      "Path: efm.status.pppoEClient.ipV6.dhcp.iaid

       32 bit unsigned wrappable counter."
   ::= {sr1646v2EfmPppOEEntry 101056768}

sr1646v2EfmPppOEIpV6RaRcvOption OBJECT-TYPE
   SYNTAX      Integer32
   MAX-ACCESS  read-only
   STATUS      current
   DESCRIPTION
      "Path: efm.status.pppoEClient.ipV6.raRcvOption

       Bit meanings:
               bit 0 = linkMtu,
               bit 1 = srcLinkLayer,
               bit 2 = prefixInfo,
               bit 3 = rdnss,
               bit 4 = dnssl"
   ::= {sr1646v2EfmPppOEEntry 101122048}

sr1646v2EfmPppOEIpV6Addresses OBJECT-TYPE
   SYNTAX      SEQUENCE OF Sr1646v2EfmPppOEIpV6AddressesEntry
   MAX-ACCESS  not-accessible
   STATUS      current
   DESCRIPTION
      ""
   ::= {sr1646v2EfmPppOE 100859904}

sr1646v2EfmPppOEIpV6AddressesEntry OBJECT-TYPE
   SYNTAX      Sr1646v2EfmPppOEIpV6AddressesEntry
   MAX-ACCESS  not-accessible
   STATUS      current
   DESCRIPTION
      ""
   INDEX      { sr1646v2EfmPppOETableIx,
                sr1646v2EfmPppOEIpV6AddressesTableIx }
   ::= {sr1646v2EfmPppOEIpV6Addresses 1}

Sr1646v2EfmPppOEIpV6AddressesEntry ::=
   SEQUENCE
      {
      sr1646v2EfmPppOEIpV6AddressesTableIx
         TableIndex,
      sr1646v2EfmPppOEIpV6AddressesAddress
         Ipv6Address,
      sr1646v2EfmPppOEIpV6AddressesPrefixLength
         Integer32,
      sr1646v2EfmPppOEIpV6AddressesStatus
         INTEGER,
      sr1646v2EfmPppOEIpV6AddressesOrigin
         INTEGER,
      sr1646v2EfmPppOEIpV6AddressesFlagsInterfaceId
         INTEGER,
      sr1646v2EfmPppOEIpV6AddressesFlagsAnycast
         INTEGER,
      sr1646v2EfmPppOEIpV6AddressesTimersValidLifeTime
         TimeTicks,
      sr1646v2EfmPppOEIpV6AddressesTimersPrefLifeTime
         TimeTicks
      }

sr1646v2EfmPppOEIpV6AddressesTableIx OBJECT-TYPE
   SYNTAX      TableIndex
   MAX-ACCESS  not-accessible
   STATUS      current
   DESCRIPTION
      ""
   ::= {sr1646v2EfmPppOEIpV6AddressesEntry 11}

sr1646v2EfmPppOEIpV6AddressesAddress OBJECT-TYPE
   SYNTAX      Ipv6Address
   MAX-ACCESS  read-only
   STATUS      current
   DESCRIPTION
      "Path: efm.status.pppoEClient.ipV6.addresses.address

       ipv6 address"
   ::= {sr1646v2EfmPppOEIpV6AddressesEntry 16777216}

sr1646v2EfmPppOEIpV6AddressesPrefixLength OBJECT-TYPE
   SYNTAX      Integer32
   MAX-ACCESS  read-only
   STATUS      current
   DESCRIPTION
      "Path: efm.status.pppoEClient.ipV6.addresses.prefixLength"
   ::= {sr1646v2EfmPppOEIpV6AddressesEntry 33554432}

sr1646v2EfmPppOEIpV6AddressesStatus OBJECT-TYPE
   SYNTAX      INTEGER
               {
               invalid (0),
               tentative (1),
               deprecated (2),
               preferred (3)
               }
   MAX-ACCESS  read-only
   STATUS      current
   DESCRIPTION
      "Path: efm.status.pppoEClient.ipV6.addresses.status

       Possibilities:
               invalid   (0)
               tentative   (1)
               deprecated   (2)
               preferred   (3)"
   ::= {sr1646v2EfmPppOEIpV6AddressesEntry 50331648}

sr1646v2EfmPppOEIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: efm.status.pppoEClient.ipV6.addresses.origin

       Possibilities:
               unknown   (0)
               manual   (1)
               generalPrefix   (2)
               statelessAuto   (3)
               statefullAuto   (4)"
   ::= {sr1646v2EfmPppOEIpV6AddressesEntry 67108864}

sr1646v2EfmPppOEIpV6AddressesFlagsInterfaceId OBJECT-TYPE
   SYNTAX      INTEGER
               {
               no (0),
               yes (1)
               }
   MAX-ACCESS  read-only
   STATUS      current
   DESCRIPTION
      "Path: efm.status.pppoEClient.ipV6.addresses.flags.interfaceId

       Possibilities:
               no   (0)
               yes   (1)"
   ::= {sr1646v2EfmPppOEIpV6AddressesEntry 83951616}

sr1646v2EfmPppOEIpV6AddressesFlagsAnycast OBJECT-TYPE
   SYNTAX      INTEGER
               {
               no (0),
               yes (1)
               }
   MAX-ACCESS  read-only
   STATUS      current
   DESCRIPTION
      "Path: efm.status.pppoEClient.ipV6.addresses.flags.anycast

       Possibilities:
               no   (0)
               yes   (1)"
   ::= {sr1646v2EfmPppOEIpV6AddressesEntry 84017152}

sr1646v2EfmPppOEIpV6AddressesTimersValidLifeTime OBJECT-TYPE
   SYNTAX      TimeTicks
   MAX-ACCESS  read-only
   STATUS      current
   DESCRIPTION
      "Path: efm.status.pppoEClient.ipV6.addresses.timers.validLifeTime

       Time in centi-second."
   ::= {sr1646v2EfmPppOEIpV6AddressesEntry 100794368}

sr1646v2EfmPppOEIpV6AddressesTimersPrefLifeTime OBJECT-TYPE
   SYNTAX      TimeTicks
   MAX-ACCESS  read-only
   STATUS      current
   DESCRIPTION
      "Path: efm.status.pppoEClient.ipV6.addresses.timers.prefLifeTime

       Time in centi-second."
   ::= {sr1646v2EfmPppOEIpV6AddressesEntry 100728832}


sr1646v2EfmDot1x OBJECT IDENTIFIER ::= {sr1646v2Efm 190}

sr1646v2EfmDot1xSSCTable OBJECT-TYPE
   SYNTAX      SEQUENCE OF Sr1646v2EfmDot1xEntry
   MAX-ACCESS  not-accessible
   STATUS      current
   DESCRIPTION
      "Ethernet Switch VLAN Table"
   ::= {sr1646v2EfmDot1x 1}

sr1646v2EfmDot1xEntry OBJECT-TYPE
   SYNTAX      Sr1646v2EfmDot1xEntry
   MAX-ACCESS  not-accessible
   STATUS      current
   DESCRIPTION
      ""
   INDEX      { sr1646v2EfmDot1xTableIx }
   ::= {sr1646v2EfmDot1xSSCTable 1}

Sr1646v2EfmDot1xEntry ::=
   SEQUENCE
      {
      sr1646v2EfmDot1xTableIx
         TableIndex,
      sr1646v2EfmDot1xRemote
         OCTET STRING,
      sr1646v2EfmDot1xAuthorized
         INTEGER,
      sr1646v2EfmDot1xAuthenticator
         INTEGER,
      sr1646v2EfmDot1xBackEnd
         INTEGER,
      sr1646v2EfmDot1xRetries
         Integer32,
      sr1646v2EfmDot1xReAuthTime
         TimeTicks,
      sr1646v2EfmDot1xHoldTime
         TimeTicks
      }

sr1646v2EfmDot1xTableIx OBJECT-TYPE
   SYNTAX      TableIndex
   MAX-ACCESS  not-accessible
   STATUS      current
   DESCRIPTION
      ""
   ::= {sr1646v2EfmDot1xEntry 11}

sr1646v2EfmDot1xRemote OBJECT-TYPE
   SYNTAX      OCTET STRING
   MAX-ACCESS  read-only
   STATUS      current
   DESCRIPTION
      "Path: efm.status.dot1x.remote

       MAC address."
   ::= {sr1646v2EfmDot1xEntry 16777216}

sr1646v2EfmDot1xAuthorized OBJECT-TYPE
   SYNTAX      INTEGER
               {
               no (0),
               yes (1)
               }
   MAX-ACCESS  read-only
   STATUS      current
   DESCRIPTION
      "Path: efm.status.dot1x.authorized

       Possibilities:
               no   (0)
               yes   (1)"
   ::= {sr1646v2EfmDot1xEntry 33554432}

sr1646v2EfmDot1xAuthenticator OBJECT-TYPE
   SYNTAX      INTEGER
               {
               preInit (0),
               initialize (1),
               disconnected (2),
               restart (3),
               connecting (4),
               authenticating (5),
               authenticated (6),
               aborting (7),
               held (8),
               forceAuth (9),
               forceUnauth (10)
               }
   MAX-ACCESS  read-only
   STATUS      current
   DESCRIPTION
      "Path: efm.status.dot1x.authenticator

       Possibilities:
               preInit   (0)
               initialize   (1)
               disconnected   (2)
               restart   (3)
               connecting   (4)
               authenticating   (5)
               authenticated   (6)
               aborting   (7)
               held   (8)
               forceAuth   (9)
               forceUnauth   (10)"
   ::= {sr1646v2EfmDot1xEntry 50331648}

sr1646v2EfmDot1xBackEnd OBJECT-TYPE
   SYNTAX      INTEGER
               {
               preInit (0),
               initialize (1),
               idle (2),
               request (3),
               response (4),
               success (5),
               failure (6),
               radiusTimeout (7),
               timeout (8)
               }
   MAX-ACCESS  read-only
   STATUS      current
   DESCRIPTION
      "Path: efm.status.dot1x.backEnd

       Possibilities:
               preInit   (0)
               initialize   (1)
               idle   (2)
               request   (3)
               response   (4)
               success   (5)
               failure   (6)
               radiusTimeout   (7)
               timeout   (8)"
   ::= {sr1646v2EfmDot1xEntry 67108864}

sr1646v2EfmDot1xRetries OBJECT-TYPE
   SYNTAX      Integer32
   MAX-ACCESS  read-only
   STATUS      current
   DESCRIPTION
      "Path: efm.status.dot1x.retries"
   ::= {sr1646v2EfmDot1xEntry 83886080}

sr1646v2EfmDot1xReAuthTime OBJECT-TYPE
   SYNTAX      TimeTicks
   MAX-ACCESS  read-only
   STATUS      current
   DESCRIPTION
      "Path: efm.status.dot1x.reAuthTime

       Time in centi-second."
   ::= {sr1646v2EfmDot1xEntry 100663296}

sr1646v2EfmDot1xHoldTime OBJECT-TYPE
   SYNTAX      TimeTicks
   MAX-ACCESS  read-only
   STATUS      current
   DESCRIPTION
      "Path: efm.status.dot1x.holdTime

       Time in centi-second."
   ::= {sr1646v2EfmDot1xEntry 117440512}



pr1646v2Efm OBJECT IDENTIFIER ::= {r1646v2Efm 12}


pr1646v2EfmInOctets OBJECT-TYPE
   SYNTAX      Counter64
   MAX-ACCESS  read-only
   STATUS      current
   DESCRIPTION
      "Path: efm.performance.ifInOctets
       Info: ifInOctets

       64 bit unsigned wrappable counter."
   ::= {pr1646v2Efm 109}


pr1646v2EfmInUcast OBJECT-TYPE
   SYNTAX      Counter64
   MAX-ACCESS  read-only
   STATUS      current
   DESCRIPTION
      "Path: efm.performance.ifInUcastPkts
       Info: ifInUcastPkts

       64 bit unsigned wrappable counter."
   ::= {pr1646v2Efm 110}


pr1646v2EfmInNUcastPkts OBJECT-TYPE
   SYNTAX      Counter64
   MAX-ACCESS  read-only
   STATUS      current
   DESCRIPTION
      "Path: efm.performance.ifInNUcastPkts
       Info: ifInNUcastPkts

       64 bit unsigned wrappable counter."
   ::= {pr1646v2Efm 111}


pr1646v2EfmInBcastPkts OBJECT-TYPE
   SYNTAX      Counter64
   MAX-ACCESS  read-only
   STATUS      current
   DESCRIPTION
      "Path: efm.performance.ifInBcastPkts
       Info: ifInBcastPkts

       64 bit unsigned wrappable counter."
   ::= {pr1646v2Efm 211}


pr1646v2EfmInMcastPkts OBJECT-TYPE
   SYNTAX      Counter64
   MAX-ACCESS  read-only
   STATUS      current
   DESCRIPTION
      "Path: efm.performance.ifInMcastPkts
       Info: ifInNUcastPkts

       64 bit unsigned wrappable counter."
   ::= {pr1646v2Efm 221}


pr1646v2EfmInDiscards OBJECT-TYPE
   SYNTAX      Counter64
   MAX-ACCESS  read-only
   STATUS      current
   DESCRIPTION
      "Path: efm.performance.ifInDiscards
       Info: ifInDiscards

       64 bit unsigned wrappable counter."
   ::= {pr1646v2Efm 112}


pr1646v2EfmInErrors OBJECT-TYPE
   SYNTAX      Counter64
   MAX-ACCESS  read-only
   STATUS      current
   DESCRIPTION
      "Path: efm.performance.ifInErrors
       Info: ifInErrors

       64 bit unsigned wrappable counter."
   ::= {pr1646v2Efm 113}


pr1646v2EfmInUnknownProtos OBJECT-TYPE
   SYNTAX      Counter64
   MAX-ACCESS  read-only
   STATUS      current
   DESCRIPTION
      "Path: efm.performance.ifInUnknownProtos
       Info: ifInUnknownprotos

       64 bit unsigned wrappable counter."
   ::= {pr1646v2Efm 114}


pr1646v2EfmInQLen OBJECT-TYPE
   SYNTAX      Gauge32
   MAX-ACCESS  read-only
   STATUS      current
   DESCRIPTION
      "Path: efm.performance.ifInQLen
       Info: ifInQLen

       32 bit unsigned gauge value."
   ::= {pr1646v2Efm 128}


pr1646v2EfmInDropEx OBJECT-TYPE
   SYNTAX      Counter64
   MAX-ACCESS  read-only
   STATUS      current
   DESCRIPTION
      "Path: efm.performance.ifInDropLevelExceeded
       Info: ifInDiscards

       64 bit unsigned wrappable counter."
   ::= {pr1646v2Efm 130}


pr1646v2EfmInDropNoMac OBJECT-TYPE
   SYNTAX      Counter64
   MAX-ACCESS  read-only
   STATUS      current
   DESCRIPTION
      "Path: efm.performance.ifInDiscardsNoMacFit
       Info: ifInDiscards

       64 bit unsigned wrappable counter."
   ::= {pr1646v2Efm 133}


pr1646v2EfmInDropNUCast OBJECT-TYPE
   SYNTAX      Counter64
   MAX-ACCESS  read-only
   STATUS      current
   DESCRIPTION
      "Path: efm.performance.ifInDiscardsNUCast
       Info: ifInDiscards

       64 bit unsigned wrappable counter."
   ::= {pr1646v2Efm 136}


pr1646v2EfmInDropFilter OBJECT-TYPE
   SYNTAX      Counter64
   MAX-ACCESS  read-only
   STATUS      current
   DESCRIPTION
      "Path: efm.performance.ifInDiscardsFilter
       Info: ifInDiscards

       64 bit unsigned wrappable counter."
   ::= {pr1646v2Efm 137}


pr1646v2EfmInQueues OBJECT IDENTIFIER ::= {pr1646v2Efm 131}

pr1646v2EfmInQueuesSSCTable OBJECT-TYPE
   SYNTAX      SEQUENCE OF Pr1646v2EfmInQueuesEntry
   MAX-ACCESS  not-accessible
   STATUS      current
   DESCRIPTION
      "Queue Lengths"
   ::= {pr1646v2EfmInQueues 1}

pr1646v2EfmInQueuesEntry OBJECT-TYPE
   SYNTAX      Pr1646v2EfmInQueuesEntry
   MAX-ACCESS  not-accessible
   STATUS      current
   DESCRIPTION
      ""
   INDEX      { pr1646v2EfmInQueuesTableIx }
   ::= {pr1646v2EfmInQueuesSSCTable 1}

Pr1646v2EfmInQueuesEntry ::=
   SEQUENCE
      {
      pr1646v2EfmInQueuesTableIx
         TableIndex,
      pr1646v2EfmInQueuesName
         INTEGER,
      pr1646v2EfmInQueuesLength
         Integer32,
      pr1646v2EfmInQueuesOctetLength
         Integer32,
      pr1646v2EfmInQueuesRedLength
         Integer32,
      pr1646v2EfmInQueuesPacketsTotal
         Counter64,
      pr1646v2EfmInQueuesPacketsDirectTx
         Counter64,
      pr1646v2EfmInQueuesPacketsQueued
         Counter64,
      pr1646v2EfmInQueuesPacketsDropped
         Counter64,
      pr1646v2EfmInQueuesPacketsRedDropped
         Counter64,
      pr1646v2EfmInQueuesPacketsCirTx
         Counter64,
      pr1646v2EfmInQueuesPacketsEirTx
         Counter64,
      pr1646v2EfmInQueuesPacketsViolateTx
         Counter64,
      pr1646v2EfmInQueuesOctetsTotal
         Counter64,
      pr1646v2EfmInQueuesOctetsDirectTx
         Counter64,
      pr1646v2EfmInQueuesOctetsQueued
         Counter64,
      pr1646v2EfmInQueuesOctetsDropped
         Counter64,
      pr1646v2EfmInQueuesOctetsRedDropped
         Counter64,
      pr1646v2EfmInQueuesOctetsCirTx
         Counter64,
      pr1646v2EfmInQueuesOctetsEirTx
         Counter64,
      pr1646v2EfmInQueuesOctetsViolateTx
         Counter64,
      pr1646v2EfmInQueuesOctetsBandwidth15sec
         Integer32,
      pr1646v2EfmInQueuesOctetsBandwidth30sec
         Integer32,
      pr1646v2EfmInQueuesOctetsBandwidth1min
         Integer32,
      pr1646v2EfmInQueuesOctetsBandwidth2min
         Integer32,
      pr1646v2EfmInQueuesOctetsBandwidth5min
         Integer32
      }

pr1646v2EfmInQueuesTableIx OBJECT-TYPE
   SYNTAX      TableIndex
   MAX-ACCESS  not-accessible
   STATUS      current
   DESCRIPTION
      ""
   ::= {pr1646v2EfmInQueuesEntry 11}

pr1646v2EfmInQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: efm.performance.ifInPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2EfmInQueuesEntry 16777216}

pr1646v2EfmInQueuesLength OBJECT-TYPE
   SYNTAX      Integer32
   MAX-ACCESS  read-only
   STATUS      current
   DESCRIPTION
      "Path: efm.performance.ifInPriorityQueues.length"
   ::= {pr1646v2EfmInQueuesEntry 33554432}

pr1646v2EfmInQueuesOctetLength OBJECT-TYPE
   SYNTAX      Integer32
   MAX-ACCESS  read-only
   STATUS      current
   DESCRIPTION
      "Path: efm.performance.ifInPriorityQueues.octetLength"
   ::= {pr1646v2EfmInQueuesEntry 150994944}

pr1646v2EfmInQueuesRedLength OBJECT-TYPE
   SYNTAX      Integer32
   MAX-ACCESS  read-only
   STATUS      current
   DESCRIPTION
      "Path: efm.performance.ifInPriorityQueues.redLength"
   ::= {pr1646v2EfmInQueuesEntry 134217728}

pr1646v2EfmInQueuesPacketsTotal OBJECT-TYPE
   SYNTAX      Counter64
   MAX-ACCESS  read-only
   STATUS      current
   DESCRIPTION
      "Path: efm.performance.ifInPriorityQueues.packets.total

       64 bit unsigned wrappable counter."
   ::= {pr1646v2EfmInQueuesEntry 50790400}

pr1646v2EfmInQueuesPacketsDirectTx OBJECT-TYPE
   SYNTAX      Counter64
   MAX-ACCESS  read-only
   STATUS      current
   DESCRIPTION
      "Path: efm.performance.ifInPriorityQueues.packets.directTx

       64 bit unsigned wrappable counter."
   ::= {pr1646v2EfmInQueuesEntry 50397184}

pr1646v2EfmInQueuesPacketsQueued OBJECT-TYPE
   SYNTAX      Counter64
   MAX-ACCESS  read-only
   STATUS      current
   DESCRIPTION
      "Path: efm.performance.ifInPriorityQueues.packets.queued

       64 bit unsigned wrappable counter."
   ::= {pr1646v2EfmInQueuesEntry 50462720}

pr1646v2EfmInQueuesPacketsDropped OBJECT-TYPE
   SYNTAX      Counter64
   MAX-ACCESS  read-only
   STATUS      current
   DESCRIPTION
      "Path: efm.performance.ifInPriorityQueues.packets.dropped

       64 bit unsigned wrappable counter."
   ::= {pr1646v2EfmInQueuesEntry 50528256}

pr1646v2EfmInQueuesPacketsRedDropped OBJECT-TYPE
   SYNTAX      Counter64
   MAX-ACCESS  read-only
   STATUS      current
   DESCRIPTION
      "Path: efm.performance.ifInPriorityQueues.packets.redDropped

       64 bit unsigned wrappable counter."
   ::= {pr1646v2EfmInQueuesEntry 50724864}

pr1646v2EfmInQueuesPacketsCirTx OBJECT-TYPE
   SYNTAX      Counter64
   MAX-ACCESS  read-only
   STATUS      current
   DESCRIPTION
      "Path: efm.performance.ifInPriorityQueues.packets.cirTx

       64 bit unsigned wrappable counter."
   ::= {pr1646v2EfmInQueuesEntry 50593792}

pr1646v2EfmInQueuesPacketsEirTx OBJECT-TYPE
   SYNTAX      Counter64
   MAX-ACCESS  read-only
   STATUS      current
   DESCRIPTION
      "Path: efm.performance.ifInPriorityQueues.packets.eirTx

       64 bit unsigned wrappable counter."
   ::= {pr1646v2EfmInQueuesEntry 50659328}

pr1646v2EfmInQueuesPacketsViolateTx OBJECT-TYPE
   SYNTAX      Counter64
   MAX-ACCESS  read-only
   STATUS      current
   DESCRIPTION
      "Path: efm.performance.ifInPriorityQueues.packets.violateTx

       64 bit unsigned wrappable counter."
   ::= {pr1646v2EfmInQueuesEntry 50855936}

pr1646v2EfmInQueuesOctetsTotal OBJECT-TYPE
   SYNTAX      Counter64
   MAX-ACCESS  read-only
   STATUS      current
   DESCRIPTION
      "Path: efm.performance.ifInPriorityQueues.octets.total

       64 bit unsigned wrappable counter."
   ::= {pr1646v2EfmInQueuesEntry 67567616}

pr1646v2EfmInQueuesOctetsDirectTx OBJECT-TYPE
   SYNTAX      Counter64
   MAX-ACCESS  read-only
   STATUS      current
   DESCRIPTION
      "Path: efm.performance.ifInPriorityQueues.octets.directTx

       64 bit unsigned wrappable counter."
   ::= {pr1646v2EfmInQueuesEntry 67174400}

pr1646v2EfmInQueuesOctetsQueued OBJECT-TYPE
   SYNTAX      Counter64
   MAX-ACCESS  read-only
   STATUS      current
   DESCRIPTION
      "Path: efm.performance.ifInPriorityQueues.octets.queued

       64 bit unsigned wrappable counter."
   ::= {pr1646v2EfmInQueuesEntry 67239936}

pr1646v2EfmInQueuesOctetsDropped OBJECT-TYPE
   SYNTAX      Counter64
   MAX-ACCESS  read-only
   STATUS      current
   DESCRIPTION
      "Path: efm.performance.ifInPriorityQueues.octets.dropped

       64 bit unsigned wrappable counter."
   ::= {pr1646v2EfmInQueuesEntry 67305472}

pr1646v2EfmInQueuesOctetsRedDropped OBJECT-TYPE
   SYNTAX      Counter64
   MAX-ACCESS  read-only
   STATUS      current
   DESCRIPTION
      "Path: efm.performance.ifInPriorityQueues.octets.redDropped

       64 bit unsigned wrappable counter."
   ::= {pr1646v2EfmInQueuesEntry 67502080}

pr1646v2EfmInQueuesOctetsCirTx OBJECT-TYPE
   SYNTAX      Counter64
   MAX-ACCESS  read-only
   STATUS      current
   DESCRIPTION
      "Path: efm.performance.ifInPriorityQueues.octets.cirTx

       64 bit unsigned wrappable counter."
   ::= {pr1646v2EfmInQueuesEntry 67371008}

pr1646v2EfmInQueuesOctetsEirTx OBJECT-TYPE
   SYNTAX      Counter64
   MAX-ACCESS  read-only
   STATUS      current
   DESCRIPTION
      "Path: efm.performance.ifInPriorityQueues.octets.eirTx

       64 bit unsigned wrappable counter."
   ::= {pr1646v2EfmInQueuesEntry 67436544}

pr1646v2EfmInQueuesOctetsViolateTx OBJECT-TYPE
   SYNTAX      Counter64
   MAX-ACCESS  read-only
   STATUS      current
   DESCRIPTION
      "Path: efm.performance.ifInPriorityQueues.octets.violateTx

       64 bit unsigned wrappable counter."
   ::= {pr1646v2EfmInQueuesEntry 67633152}

pr1646v2EfmInQueuesOctetsBandwidth15sec OBJECT-TYPE
   SYNTAX      Integer32
   MAX-ACCESS  read-only
   STATUS      current
   DESCRIPTION
      "Path: efm.performance.ifInPriorityQueues.octets.bandwidth.15sec

       unit name = bps
       formula = 8 * ; 8 /"
   ::= {pr1646v2EfmInQueuesEntry 70386944}

pr1646v2EfmInQueuesOctetsBandwidth30sec OBJECT-TYPE
   SYNTAX      Integer32
   MAX-ACCESS  read-only
   STATUS      current
   DESCRIPTION
      "Path: efm.performance.ifInPriorityQueues.octets.bandwidth.30sec

       unit name = bps
       formula = 8 * ; 8 /"
   ::= {pr1646v2EfmInQueuesEntry 70388224}

pr1646v2EfmInQueuesOctetsBandwidth1min OBJECT-TYPE
   SYNTAX      Integer32
   MAX-ACCESS  read-only
   STATUS      current
   DESCRIPTION
      "Path: efm.performance.ifInPriorityQueues.octets.bandwidth.1min

       unit name = bps
       formula = 8 * ; 8 /"
   ::= {pr1646v2EfmInQueuesEntry 70390784}

pr1646v2EfmInQueuesOctetsBandwidth2min OBJECT-TYPE
   SYNTAX      Integer32
   MAX-ACCESS  read-only
   STATUS      current
   DESCRIPTION
      "Path: efm.performance.ifInPriorityQueues.octets.bandwidth.2min

       unit name = bps
       formula = 8 * ; 8 /"
   ::= {pr1646v2EfmInQueuesEntry 70395904}

pr1646v2EfmInQueuesOctetsBandwidth5min OBJECT-TYPE
   SYNTAX      Integer32
   MAX-ACCESS  read-only
   STATUS      current
   DESCRIPTION
      "Path: efm.performance.ifInPriorityQueues.octets.bandwidth.5min

       unit name = bps
       formula = 8 * ; 8 /"
   ::= {pr1646v2EfmInQueuesEntry 70411264}

pr1646v2EfmInQueuesH2Performance OBJECT-TYPE
   SYNTAX      SEQUENCE OF Pr1646v2EfmInQueuesH2PerformanceEntry
   MAX-ACCESS  not-accessible
   STATUS      current
   DESCRIPTION
      ""
   ::= {pr1646v2EfmInQueues 83886080}

pr1646v2EfmInQueuesH2PerformanceEntry OBJECT-TYPE
   SYNTAX      Pr1646v2EfmInQueuesH2PerformanceEntry
   MAX-ACCESS  not-accessible
   STATUS      current
   DESCRIPTION
      ""
   INDEX      { pr1646v2EfmInQueuesTableIx,
                pr1646v2EfmInQueuesH2PerformanceTableIx }
   ::= {pr1646v2EfmInQueuesH2Performance 1}

Pr1646v2EfmInQueuesH2PerformanceEntry ::=
   SEQUENCE
      {
      pr1646v2EfmInQueuesH2PerformanceTableIx
         TableIndex,
      pr1646v2EfmInQueuesH2PerformanceSysUpTime
         TimeTicks,
      pr1646v2EfmInQueuesH2PerformanceTotPkts
         Counter64,
      pr1646v2EfmInQueuesH2PerformanceDirTxPkts
         Counter64,
      pr1646v2EfmInQueuesH2PerformanceQdPkts
         Counter64,
      pr1646v2EfmInQueuesH2PerformanceDropPkts
         Counter64,
      pr1646v2EfmInQueuesH2PerformanceRDropPkts
         Counter64,
      pr1646v2EfmInQueuesH2PerformanceCirTxPkts
         Counter64,
      pr1646v2EfmInQueuesH2PerformanceEirTxPkts
         Counter64,
      pr1646v2EfmInQueuesH2PerformanceViolTxPkts
         Counter64,
      pr1646v2EfmInQueuesH2PerformanceTotOcts
         Counter64,
      pr1646v2EfmInQueuesH2PerformanceDirTxOcts
         Counter64,
      pr1646v2EfmInQueuesH2PerformanceQdOcts
         Counter64,
      pr1646v2EfmInQueuesH2PerformanceDropOcts
         Counter64,
      pr1646v2EfmInQueuesH2PerformanceRDropOcts
         Counter64,
      pr1646v2EfmInQueuesH2PerformanceCirTxOcts
         Counter64,
      pr1646v2EfmInQueuesH2PerformanceEirTxOcts
         Counter64,
      pr1646v2EfmInQueuesH2PerformanceViolTxOcts
         Counter64,
      pr1646v2EfmInQueuesH2PerformanceBandwidth
         Integer32
      }

pr1646v2EfmInQueuesH2PerformanceTableIx OBJECT-TYPE
   SYNTAX      TableIndex
   MAX-ACCESS  not-accessible
   STATUS      current
   DESCRIPTION
      ""
   ::= {pr1646v2EfmInQueuesH2PerformanceEntry 11}

pr1646v2EfmInQueuesH2PerformanceSysUpTime OBJECT-TYPE
   SYNTAX      TimeTicks
   MAX-ACCESS  read-only
   STATUS      current
   DESCRIPTION
      "Path: efm.performance.ifInPriorityQueues.h2Performance.sysUpTime

       Time in centi-second."
   ::= {pr1646v2EfmInQueuesH2PerformanceEntry 16777216}

pr1646v2EfmInQueuesH2PerformanceTotPkts OBJECT-TYPE
   SYNTAX      Counter64
   MAX-ACCESS  read-only
   STATUS      current
   DESCRIPTION
      "Path: efm.performance.ifInPriorityQueues.h2Performance.totalPkts

       64 bit unsigned wrappable counter."
   ::= {pr1646v2EfmInQueuesH2PerformanceEntry 234881024}

pr1646v2EfmInQueuesH2PerformanceDirTxPkts OBJECT-TYPE
   SYNTAX      Counter64
   MAX-ACCESS  read-only
   STATUS      current
   DESCRIPTION
      "Path: efm.performance.ifInPriorityQueues.h2Performance.directTxPkts

       64 bit unsigned wrappable counter."
   ::= {pr1646v2EfmInQueuesH2PerformanceEntry 33554432}

pr1646v2EfmInQueuesH2PerformanceQdPkts OBJECT-TYPE
   SYNTAX      Counter64
   MAX-ACCESS  read-only
   STATUS      current
   DESCRIPTION
      "Path: efm.performance.ifInPriorityQueues.h2Performance.queuedPkts

       64 bit unsigned wrappable counter."
   ::= {pr1646v2EfmInQueuesH2PerformanceEntry 50331648}

pr1646v2EfmInQueuesH2PerformanceDropPkts OBJECT-TYPE
   SYNTAX      Counter64
   MAX-ACCESS  read-only
   STATUS      current
   DESCRIPTION
      "Path: efm.performance.ifInPriorityQueues.h2Performance.droppedPkts

       64 bit unsigned wrappable counter."
   ::= {pr1646v2EfmInQueuesH2PerformanceEntry 67108864}

pr1646v2EfmInQueuesH2PerformanceRDropPkts OBJECT-TYPE
   SYNTAX      Counter64
   MAX-ACCESS  read-only
   STATUS      current
   DESCRIPTION
      "Path: efm.performance.ifInPriorityQueues.h2Performance.redDroppedPkts

       64 bit unsigned wrappable counter."
   ::= {pr1646v2EfmInQueuesH2PerformanceEntry 201326592}

pr1646v2EfmInQueuesH2PerformanceCirTxPkts OBJECT-TYPE
   SYNTAX      Counter64
   MAX-ACCESS  read-only
   STATUS      current
   DESCRIPTION
      "Path: efm.performance.ifInPriorityQueues.h2Performance.cirTxPkts

       64 bit unsigned wrappable counter."
   ::= {pr1646v2EfmInQueuesH2PerformanceEntry 83886080}

pr1646v2EfmInQueuesH2PerformanceEirTxPkts OBJECT-TYPE
   SYNTAX      Counter64
   MAX-ACCESS  read-only
   STATUS      current
   DESCRIPTION
      "Path: efm.performance.ifInPriorityQueues.h2Performance.eirTxPkts

       64 bit unsigned wrappable counter."
   ::= {pr1646v2EfmInQueuesH2PerformanceEntry 100663296}

pr1646v2EfmInQueuesH2PerformanceViolTxPkts OBJECT-TYPE
   SYNTAX      Counter64
   MAX-ACCESS  read-only
   STATUS      current
   DESCRIPTION
      "Path: efm.performance.ifInPriorityQueues.h2Performance.violateTxPkts

       64 bit unsigned wrappable counter."
   ::= {pr1646v2EfmInQueuesH2PerformanceEntry 301989888}

pr1646v2EfmInQueuesH2PerformanceTotOcts OBJECT-TYPE
   SYNTAX      Counter64
   MAX-ACCESS  read-only
   STATUS      current
   DESCRIPTION
      "Path: efm.performance.ifInPriorityQueues.h2Performance.totalOctets

       64 bit unsigned wrappable counter."
   ::= {pr1646v2EfmInQueuesH2PerformanceEntry 251658240}

pr1646v2EfmInQueuesH2PerformanceDirTxOcts OBJECT-TYPE
   SYNTAX      Counter64
   MAX-ACCESS  read-only
   STATUS      current
   DESCRIPTION
      "Path: efm.performance.ifInPriorityQueues.h2Performance.directTxOctets

       64 bit unsigned wrappable counter."
   ::= {pr1646v2EfmInQueuesH2PerformanceEntry 117440512}

pr1646v2EfmInQueuesH2PerformanceQdOcts OBJECT-TYPE
   SYNTAX      Counter64
   MAX-ACCESS  read-only
   STATUS      current
   DESCRIPTION
      "Path: efm.performance.ifInPriorityQueues.h2Performance.queuedOctets

       64 bit unsigned wrappable counter."
   ::= {pr1646v2EfmInQueuesH2PerformanceEntry 134217728}

pr1646v2EfmInQueuesH2PerformanceDropOcts OBJECT-TYPE
   SYNTAX      Counter64
   MAX-ACCESS  read-only
   STATUS      current
   DESCRIPTION
      "Path: efm.performance.ifInPriorityQueues.h2Performance.droppedOctets

       64 bit unsigned wrappable counter."
   ::= {pr1646v2EfmInQueuesH2PerformanceEntry 150994944}

pr1646v2EfmInQueuesH2PerformanceRDropOcts OBJECT-TYPE
   SYNTAX      Counter64
   MAX-ACCESS  read-only
   STATUS      current
   DESCRIPTION
      "Path: efm.performance.ifInPriorityQueues.h2Performance.redDroppedOctets

       64 bit unsigned wrappable counter."
   ::= {pr1646v2EfmInQueuesH2PerformanceEntry 218103808}

pr1646v2EfmInQueuesH2PerformanceCirTxOcts OBJECT-TYPE
   SYNTAX      Counter64
   MAX-ACCESS  read-only
   STATUS      current
   DESCRIPTION
      "Path: efm.performance.ifInPriorityQueues.h2Performance.cirTxOctets

       64 bit unsigned wrappable counter."
   ::= {pr1646v2EfmInQueuesH2PerformanceEntry 167772160}

pr1646v2EfmInQueuesH2PerformanceEirTxOcts OBJECT-TYPE
   SYNTAX      Counter64
   MAX-ACCESS  read-only
   STATUS      current
   DESCRIPTION
      "Path: efm.performance.ifInPriorityQueues.h2Performance.eirTxOctets

       64 bit unsigned wrappable counter."
   ::= {pr1646v2EfmInQueuesH2PerformanceEntry 184549376}

pr1646v2EfmInQueuesH2PerformanceViolTxOcts OBJECT-TYPE
   SYNTAX      Counter64
   MAX-ACCESS  read-only
   STATUS      current
   DESCRIPTION
      "Path: efm.performance.ifInPriorityQueues.h2Performance.violateTxOctets

       64 bit unsigned wrappable counter."
   ::= {pr1646v2EfmInQueuesH2PerformanceEntry 318767104}

pr1646v2EfmInQueuesH2PerformanceBandwidth OBJECT-TYPE
   SYNTAX      Integer32
   MAX-ACCESS  read-only
   STATUS      current
   DESCRIPTION
      "Path: efm.performance.ifInPriorityQueues.h2Performance.bandwidth

       unit name = bps
       formula = 8 * ; 8 /"
   ::= {pr1646v2EfmInQueuesH2PerformanceEntry 268435456}

pr1646v2EfmInQueuesH24Performance OBJECT-TYPE
   SYNTAX      SEQUENCE OF Pr1646v2EfmInQueuesH24PerformanceEntry
   MAX-ACCESS  not-accessible
   STATUS      current
   DESCRIPTION
      ""
   ::= {pr1646v2EfmInQueues 100663296}

pr1646v2EfmInQueuesH24PerformanceEntry OBJECT-TYPE
   SYNTAX      Pr1646v2EfmInQueuesH24PerformanceEntry
   MAX-ACCESS  not-accessible
   STATUS      current
   DESCRIPTION
      ""
   INDEX      { pr1646v2EfmInQueuesTableIx,
                pr1646v2EfmInQueuesH24PerformanceTableIx }
   ::= {pr1646v2EfmInQueuesH24Performance 1}

Pr1646v2EfmInQueuesH24PerformanceEntry ::=
   SEQUENCE
      {
      pr1646v2EfmInQueuesH24PerformanceTableIx
         TableIndex,
      pr1646v2EfmInQueuesH24PerformanceSysUpTime
         TimeTicks,
      pr1646v2EfmInQueuesH24PerformanceTotPkts
         Counter64,
      pr1646v2EfmInQueuesH24PerformanceDirTxPkts
         Counter64,
      pr1646v2EfmInQueuesH24PerformanceQdPkts
         Counter64,
      pr1646v2EfmInQueuesH24PerformanceDropPkts
         Counter64,
      pr1646v2EfmInQueuesH24PerformanceRDropPkts
         Counter64,
      pr1646v2EfmInQueuesH24PerformanceCirTxPkts
         Counter64,
      pr1646v2EfmInQueuesH24PerformanceEirTxPkts
         Counter64,
      pr1646v2EfmInQueuesH24PerformanceViolTxPkts
         Counter64,
      pr1646v2EfmInQueuesH24PerformanceTotOcts
         Counter64,
      pr1646v2EfmInQueuesH24PerformanceDirTxOcts
         Counter64,
      pr1646v2EfmInQueuesH24PerformanceQdOcts
         Counter64,
      pr1646v2EfmInQueuesH24PerformanceDropOcts
         Counter64,
      pr1646v2EfmInQueuesH24PerformanceRDropOcts
         Counter64,
      pr1646v2EfmInQueuesH24PerformanceCirTxOcts
         Counter64,
      pr1646v2EfmInQueuesH24PerformanceEirTxOcts
         Counter64,
      pr1646v2EfmInQueuesH24PerformanceViolTxOcts
         Counter64,
      pr1646v2EfmInQueuesH24PerformanceBandwidth
         Integer32
      }

pr1646v2EfmInQueuesH24PerformanceTableIx OBJECT-TYPE
   SYNTAX      TableIndex
   MAX-ACCESS  not-accessible
   STATUS      current
   DESCRIPTION
      ""
   ::= {pr1646v2EfmInQueuesH24PerformanceEntry 11}

pr1646v2EfmInQueuesH24PerformanceSysUpTime OBJECT-TYPE
   SYNTAX      TimeTicks
   MAX-ACCESS  read-only
   STATUS      current
   DESCRIPTION
      "Path: efm.performance.ifInPriorityQueues.h24Performance.sysUpTime

       Time in centi-second."
   ::= {pr1646v2EfmInQueuesH24PerformanceEntry 16777216}

pr1646v2EfmInQueuesH24PerformanceTotPkts OBJECT-TYPE
   SYNTAX      Counter64
   MAX-ACCESS  read-only
   STATUS      current
   DESCRIPTION
      "Path: efm.performance.ifInPriorityQueues.h24Performance.totalPkts

       64 bit unsigned wrappable counter."
   ::= {pr1646v2EfmInQueuesH24PerformanceEntry 234881024}

pr1646v2EfmInQueuesH24PerformanceDirTxPkts OBJECT-TYPE
   SYNTAX      Counter64
   MAX-ACCESS  read-only
   STATUS      current
   DESCRIPTION
      "Path: efm.performance.ifInPriorityQueues.h24Performance.directTxPkts

       64 bit unsigned wrappable counter."
   ::= {pr1646v2EfmInQueuesH24PerformanceEntry 33554432}

pr1646v2EfmInQueuesH24PerformanceQdPkts OBJECT-TYPE
   SYNTAX      Counter64
   MAX-ACCESS  read-only
   STATUS      current
   DESCRIPTION
      "Path: efm.performance.ifInPriorityQueues.h24Performance.queuedPkts

       64 bit unsigned wrappable counter."
   ::= {pr1646v2EfmInQueuesH24PerformanceEntry 50331648}

pr1646v2EfmInQueuesH24PerformanceDropPkts OBJECT-TYPE
   SYNTAX      Counter64
   MAX-ACCESS  read-only
   STATUS      current
   DESCRIPTION
      "Path: efm.performance.ifInPriorityQueues.h24Performance.droppedPkts

       64 bit unsigned wrappable counter."
   ::= {pr1646v2EfmInQueuesH24PerformanceEntry 67108864}

pr1646v2EfmInQueuesH24PerformanceRDropPkts OBJECT-TYPE
   SYNTAX      Counter64
   MAX-ACCESS  read-only
   STATUS      current
   DESCRIPTION
      "Path: efm.performance.ifInPriorityQueues.h24Performance.redDroppedPkts

       64 bit unsigned wrappable counter."
   ::= {pr1646v2EfmInQueuesH24PerformanceEntry 201326592}

pr1646v2EfmInQueuesH24PerformanceCirTxPkts OBJECT-TYPE
   SYNTAX      Counter64
   MAX-ACCESS  read-only
   STATUS      current
   DESCRIPTION
      "Path: efm.performance.ifInPriorityQueues.h24Performance.cirTxPkts

       64 bit unsigned wrappable counter."
   ::= {pr1646v2EfmInQueuesH24PerformanceEntry 83886080}

pr1646v2EfmInQueuesH24PerformanceEirTxPkts OBJECT-TYPE
   SYNTAX      Counter64
   MAX-ACCESS  read-only
   STATUS      current
   DESCRIPTION
      "Path: efm.performance.ifInPriorityQueues.h24Performance.eirTxPkts

       64 bit unsigned wrappable counter."
   ::= {pr1646v2EfmInQueuesH24PerformanceEntry 100663296}

pr1646v2EfmInQueuesH24PerformanceViolTxPkts OBJECT-TYPE
   SYNTAX      Counter64
   MAX-ACCESS  read-only
   STATUS      current
   DESCRIPTION
      "Path: efm.performance.ifInPriorityQueues.h24Performance.violateTxPkts

       64 bit unsigned wrappable counter."
   ::= {pr1646v2EfmInQueuesH24PerformanceEntry 301989888}

pr1646v2EfmInQueuesH24PerformanceTotOcts OBJECT-TYPE
   SYNTAX      Counter64
   MAX-ACCESS  read-only
   STATUS      current
   DESCRIPTION
      "Path: efm.performance.ifInPriorityQueues.h24Performance.totalOctets

       64 bit unsigned wrappable counter."
   ::= {pr1646v2EfmInQueuesH24PerformanceEntry 251658240}

pr1646v2EfmInQueuesH24PerformanceDirTxOcts OBJECT-TYPE
   SYNTAX      Counter64
   MAX-ACCESS  read-only
   STATUS      current
   DESCRIPTION
      "Path: efm.performance.ifInPriorityQueues.h24Performance.directTxOctets

       64 bit unsigned wrappable counter."
   ::= {pr1646v2EfmInQueuesH24PerformanceEntry 117440512}

pr1646v2EfmInQueuesH24PerformanceQdOcts OBJECT-TYPE
   SYNTAX      Counter64
   MAX-ACCESS  read-only
   STATUS      current
   DESCRIPTION
      "Path: efm.performance.ifInPriorityQueues.h24Performance.queuedOctets

       64 bit unsigned wrappable counter."
   ::= {pr1646v2EfmInQueuesH24PerformanceEntry 134217728}

pr1646v2EfmInQueuesH24PerformanceDropOcts OBJECT-TYPE
   SYNTAX      Counter64
   MAX-ACCESS  read-only
   STATUS      current
   DESCRIPTION
      "Path: efm.performance.ifInPriorityQueues.h24Performance.droppedOctets

       64 bit unsigned wrappable counter."
   ::= {pr1646v2EfmInQueuesH24PerformanceEntry 150994944}

pr1646v2EfmInQueuesH24PerformanceRDropOcts OBJECT-TYPE
   SYNTAX      Counter64
   MAX-ACCESS  read-only
   STATUS      current
   DESCRIPTION
      "Path: efm.performance.ifInPriorityQueues.h24Performance.redDroppedOctets

       64 bit unsigned wrappable counter."
   ::= {pr1646v2EfmInQueuesH24PerformanceEntry 218103808}

pr1646v2EfmInQueuesH24PerformanceCirTxOcts OBJECT-TYPE
   SYNTAX      Counter64
   MAX-ACCESS  read-only
   STATUS      current
   DESCRIPTION
      "Path: efm.performance.ifInPriorityQueues.h24Performance.cirTxOctets

       64 bit unsigned wrappable counter."
   ::= {pr1646v2EfmInQueuesH24PerformanceEntry 167772160}

pr1646v2EfmInQueuesH24PerformanceEirTxOcts OBJECT-TYPE
   SYNTAX      Counter64
   MAX-ACCESS  read-only
   STATUS      current
   DESCRIPTION
      "Path: efm.performance.ifInPriorityQueues.h24Performance.eirTxOctets

       64 bit unsigned wrappable counter."
   ::= {pr1646v2EfmInQueuesH24PerformanceEntry 184549376}

pr1646v2EfmInQueuesH24PerformanceViolTxOcts OBJECT-TYPE
   SYNTAX      Counter64
   MAX-ACCESS  read-only
   STATUS      current
   DESCRIPTION
      "Path: efm.performance.ifInPriorityQueues.h24Performance.violateTxOctets

       64 bit unsigned wrappable counter."
   ::= {pr1646v2EfmInQueuesH24PerformanceEntry 318767104}

pr1646v2EfmInQueuesH24PerformanceBandwidth OBJECT-TYPE
   SYNTAX      Integer32
   MAX-ACCESS  read-only
   STATUS      current
   DESCRIPTION
      "Path: efm.performance.ifInPriorityQueues.h24Performance.bandwidth

       unit name = bps
       formula = 8 * ; 8 /"
   ::= {pr1646v2EfmInQueuesH24PerformanceEntry 268435456}

pr1646v2EfmInQueuesD7Performance OBJECT-TYPE
   SYNTAX      SEQUENCE OF Pr1646v2EfmInQueuesD7PerformanceEntry
   MAX-ACCESS  not-accessible
   STATUS      current
   DESCRIPTION
      ""
   ::= {pr1646v2EfmInQueues 117440512}

pr1646v2EfmInQueuesD7PerformanceEntry OBJECT-TYPE
   SYNTAX      Pr1646v2EfmInQueuesD7PerformanceEntry
   MAX-ACCESS  not-accessible
   STATUS      current
   DESCRIPTION
      ""
   INDEX      { pr1646v2EfmInQueuesTableIx,
                pr1646v2EfmInQueuesD7PerformanceTableIx }
   ::= {pr1646v2EfmInQueuesD7Performance 1}

Pr1646v2EfmInQueuesD7PerformanceEntry ::=
   SEQUENCE
      {
      pr1646v2EfmInQueuesD7PerformanceTableIx
         TableIndex,
      pr1646v2EfmInQueuesD7PerformanceSysUpTime
         TimeTicks,
      pr1646v2EfmInQueuesD7PerformanceTotPkts
         Counter64,
      pr1646v2EfmInQueuesD7PerformanceDirTxPkts
         Counter64,
      pr1646v2EfmInQueuesD7PerformanceQdPkts
         Counter64,
      pr1646v2EfmInQueuesD7PerformanceDropPkts
         Counter64,
      pr1646v2EfmInQueuesD7PerformanceRDropPkts
         Counter64,
      pr1646v2EfmInQueuesD7PerformanceCirTxPkts
         Counter64,
      pr1646v2EfmInQueuesD7PerformanceEirTxPkts
         Counter64,
      pr1646v2EfmInQueuesD7PerformanceViolTxPkts
         Counter64,
      pr1646v2EfmInQueuesD7PerformanceTotOcts
         Counter64,
      pr1646v2EfmInQueuesD7PerformanceDirTxOcts
         Counter64,
      pr1646v2EfmInQueuesD7PerformanceQdOcts
         Counter64,
      pr1646v2EfmInQueuesD7PerformanceDropOcts
         Counter64,
      pr1646v2EfmInQueuesD7PerformanceRDropOcts
         Counter64,
      pr1646v2EfmInQueuesD7PerformanceCirTxOcts
         Counter64,
      pr1646v2EfmInQueuesD7PerformanceEirTxOcts
         Counter64,
      pr1646v2EfmInQueuesD7PerformanceViolTxOcts
         Counter64,
      pr1646v2EfmInQueuesD7PerformanceBandwidth
         Integer32
      }

pr1646v2EfmInQueuesD7PerformanceTableIx OBJECT-TYPE
   SYNTAX      TableIndex
   MAX-ACCESS  not-accessible
   STATUS      current
   DESCRIPTION
      ""
   ::= {pr1646v2EfmInQueuesD7PerformanceEntry 11}

pr1646v2EfmInQueuesD7PerformanceSysUpTime OBJECT-TYPE
   SYNTAX      TimeTicks
   MAX-ACCESS  read-only
   STATUS      current
   DESCRIPTION
      "Path: efm.performance.ifInPriorityQueues.d7Performance.sysUpTime

       Time in centi-second."
   ::= {pr1646v2EfmInQueuesD7PerformanceEntry 16777216}

pr1646v2EfmInQueuesD7PerformanceTotPkts OBJECT-TYPE
   SYNTAX      Counter64
   MAX-ACCESS  read-only
   STATUS      current
   DESCRIPTION
      "Path: efm.performance.ifInPriorityQueues.d7Performance.totalPkts

       64 bit unsigned wrappable counter."
   ::= {pr1646v2EfmInQueuesD7PerformanceEntry 234881024}

pr1646v2EfmInQueuesD7PerformanceDirTxPkts OBJECT-TYPE
   SYNTAX      Counter64
   MAX-ACCESS  read-only
   STATUS      current
   DESCRIPTION
      "Path: efm.performance.ifInPriorityQueues.d7Performance.directTxPkts

       64 bit unsigned wrappable counter."
   ::= {pr1646v2EfmInQueuesD7PerformanceEntry 33554432}

pr1646v2EfmInQueuesD7PerformanceQdPkts OBJECT-TYPE
   SYNTAX      Counter64
   MAX-ACCESS  read-only
   STATUS      current
   DESCRIPTION
      "Path: efm.performance.ifInPriorityQueues.d7Performance.queuedPkts

       64 bit unsigned wrappable counter."
   ::= {pr1646v2EfmInQueuesD7PerformanceEntry 50331648}

pr1646v2EfmInQueuesD7PerformanceDropPkts OBJECT-TYPE
   SYNTAX      Counter64
   MAX-ACCESS  read-only
   STATUS      current
   DESCRIPTION
      "Path: efm.performance.ifInPriorityQueues.d7Performance.droppedPkts

       64 bit unsigned wrappable counter."
   ::= {pr1646v2EfmInQueuesD7PerformanceEntry 67108864}

pr1646v2EfmInQueuesD7PerformanceRDropPkts OBJECT-TYPE
   SYNTAX      Counter64
   MAX-ACCESS  read-only
   STATUS      current
   DESCRIPTION
      "Path: efm.performance.ifInPriorityQueues.d7Performance.redDroppedPkts

       64 bit unsigned wrappable counter."
   ::= {pr1646v2EfmInQueuesD7PerformanceEntry 201326592}

pr1646v2EfmInQueuesD7PerformanceCirTxPkts OBJECT-TYPE
   SYNTAX      Counter64
   MAX-ACCESS  read-only
   STATUS      current
   DESCRIPTION
      "Path: efm.performance.ifInPriorityQueues.d7Performance.cirTxPkts

       64 bit unsigned wrappable counter."
   ::= {pr1646v2EfmInQueuesD7PerformanceEntry 83886080}

pr1646v2EfmInQueuesD7PerformanceEirTxPkts OBJECT-TYPE
   SYNTAX      Counter64
   MAX-ACCESS  read-only
   STATUS      current
   DESCRIPTION
      "Path: efm.performance.ifInPriorityQueues.d7Performance.eirTxPkts

       64 bit unsigned wrappable counter."
   ::= {pr1646v2EfmInQueuesD7PerformanceEntry 100663296}

pr1646v2EfmInQueuesD7PerformanceViolTxPkts OBJECT-TYPE
   SYNTAX      Counter64
   MAX-ACCESS  read-only
   STATUS      current
   DESCRIPTION
      "Path: efm.performance.ifInPriorityQueues.d7Performance.violateTxPkts

       64 bit unsigned wrappable counter."
   ::= {pr1646v2EfmInQueuesD7PerformanceEntry 301989888}

pr1646v2EfmInQueuesD7PerformanceTotOcts OBJECT-TYPE
   SYNTAX      Counter64
   MAX-ACCESS  read-only
   STATUS      current
   DESCRIPTION
      "Path: efm.performance.ifInPriorityQueues.d7Performance.totalOctets

       64 bit unsigned wrappable counter."
   ::= {pr1646v2EfmInQueuesD7PerformanceEntry 251658240}

pr1646v2EfmInQueuesD7PerformanceDirTxOcts OBJECT-TYPE
   SYNTAX      Counter64
   MAX-ACCESS  read-only
   STATUS      current
   DESCRIPTION
      "Path: efm.performance.ifInPriorityQueues.d7Performance.directTxOctets

       64 bit unsigned wrappable counter."
   ::= {pr1646v2EfmInQueuesD7PerformanceEntry 117440512}

pr1646v2EfmInQueuesD7PerformanceQdOcts OBJECT-TYPE
   SYNTAX      Counter64
   MAX-ACCESS  read-only
   STATUS      current
   DESCRIPTION
      "Path: efm.performance.ifInPriorityQueues.d7Performance.queuedOctets

       64 bit unsigned wrappable counter."
   ::= {pr1646v2EfmInQueuesD7PerformanceEntry 134217728}

pr1646v2EfmInQueuesD7PerformanceDropOcts OBJECT-TYPE
   SYNTAX      Counter64
   MAX-ACCESS  read-only
   STATUS      current
   DESCRIPTION
      "Path: efm.performance.ifInPriorityQueues.d7Performance.droppedOctets

       64 bit unsigned wrappable counter."
   ::= {pr1646v2EfmInQueuesD7PerformanceEntry 150994944}

pr1646v2EfmInQueuesD7PerformanceRDropOcts OBJECT-TYPE
   SYNTAX      Counter64
   MAX-ACCESS  read-only
   STATUS      current
   DESCRIPTION
      "Path: efm.performance.ifInPriorityQueues.d7Performance.redDroppedOctets

       64 bit unsigned wrappable counter."
   ::= {pr1646v2EfmInQueuesD7PerformanceEntry 218103808}

pr1646v2EfmInQueuesD7PerformanceCirTxOcts OBJECT-TYPE
   SYNTAX      Counter64
   MAX-ACCESS  read-only
   STATUS      current
   DESCRIPTION
      "Path: efm.performance.ifInPriorityQueues.d7Performance.cirTxOctets

       64 bit unsigned wrappable counter."
   ::= {pr1646v2EfmInQueuesD7PerformanceEntry 167772160}

pr1646v2EfmInQueuesD7PerformanceEirTxOcts OBJECT-TYPE
   SYNTAX      Counter64
   MAX-ACCESS  read-only
   STATUS      current
   DESCRIPTION
      "Path: efm.performance.ifInPriorityQueues.d7Performance.eirTxOctets

       64 bit unsigned wrappable counter."
   ::= {pr1646v2EfmInQueuesD7PerformanceEntry 184549376}

pr1646v2EfmInQueuesD7PerformanceViolTxOcts OBJECT-TYPE
   SYNTAX      Counter64
   MAX-ACCESS  read-only
   STATUS      current
   DESCRIPTION
      "Path: efm.performance.ifInPriorityQueues.d7Performance.violateTxOctets

       64 bit unsigned wrappable counter."
   ::= {pr1646v2EfmInQueuesD7PerformanceEntry 318767104}

pr1646v2EfmInQueuesD7PerformanceBandwidth OBJECT-TYPE
   SYNTAX      Integer32
   MAX-ACCESS  read-only
   STATUS      current
   DESCRIPTION
      "Path: efm.performance.ifInPriorityQueues.d7Performance.bandwidth

       unit name = bps
       formula = 8 * ; 8 /"
   ::= {pr1646v2EfmInQueuesD7PerformanceEntry 268435456}


pr1646v2EfmInBandwidth OBJECT IDENTIFIER ::= {pr1646v2Efm 181}

pr1646v2EfmInBandwidthSSC OBJECT IDENTIFIER ::= {pr1646v2EfmInBandwidth 1}

pr1646v2EfmInBandwidthEntry OBJECT IDENTIFIER ::= {pr1646v2EfmInBandwidthSSC 1}

pr1646v2EfmInBandwidth15sec OBJECT-TYPE
   SYNTAX      Integer32
   MAX-ACCESS  read-only
   STATUS      current
   DESCRIPTION
      "Path: efm.performance.ifInBandwidth.15sec

       unit name = bps
       formula = 8 * ; 8 /"
   ::= {pr1646v2EfmInBandwidthEntry 83886080}

pr1646v2EfmInBandwidth30sec OBJECT-TYPE
   SYNTAX      Integer32
   MAX-ACCESS  read-only
   STATUS      current
   DESCRIPTION
      "Path: efm.performance.ifInBandwidth.30sec

       unit name = bps
       formula = 8 * ; 8 /"
   ::= {pr1646v2EfmInBandwidthEntry 167772160}

pr1646v2EfmInBandwidth1min OBJECT-TYPE
   SYNTAX      Integer32
   MAX-ACCESS  read-only
   STATUS      current
   DESCRIPTION
      "Path: efm.performance.ifInBandwidth.1min

       unit name = bps
       formula = 8 * ; 8 /"
   ::= {pr1646v2EfmInBandwidthEntry 335544320}

pr1646v2EfmInBandwidth2min OBJECT-TYPE
   SYNTAX      Integer32
   MAX-ACCESS  read-only
   STATUS      current
   DESCRIPTION
      "Path: efm.performance.ifInBandwidth.2min

       unit name = bps
       formula = 8 * ; 8 /"
   ::= {pr1646v2EfmInBandwidthEntry 671088640}

pr1646v2EfmInBandwidth5min OBJECT-TYPE
   SYNTAX      Integer32
   MAX-ACCESS  read-only
   STATUS      current
   DESCRIPTION
      "Path: efm.performance.ifInBandwidth.5min

       unit name = bps
       formula = 8 * ; 8 /"
   ::= {pr1646v2EfmInBandwidthEntry 1677721600}


pr1646v2EfmOutOctets OBJECT-TYPE
   SYNTAX      Counter64
   MAX-ACCESS  read-only
   STATUS      current
   DESCRIPTION
      "Path: efm.performance.ifOutOctets
       Info: ifOutOctets

       64 bit unsigned wrappable counter."
   ::= {pr1646v2Efm 115}


pr1646v2EfmOutUcastPkts OBJECT-TYPE
   SYNTAX      Counter64
   MAX-ACCESS  read-only
   STATUS      current
   DESCRIPTION
      "Path: efm.performance.ifOutUcastPkts
       Info: ifOutUcastPkts

       64 bit unsigned wrappable counter."
   ::= {pr1646v2Efm 116}


pr1646v2EfmOutNUcastPkts OBJECT-TYPE
   SYNTAX      Counter64
   MAX-ACCESS  read-only
   STATUS      current
   DESCRIPTION
      "Path: efm.performance.ifOutNUcastPkts
       Info: ifOutNUcastPkts

       64 bit unsigned wrappable counter."
   ::= {pr1646v2Efm 117}


pr1646v2EfmOutBcastPkts OBJECT-TYPE
   SYNTAX      Counter64
   MAX-ACCESS  read-only
   STATUS      current
   DESCRIPTION
      "Path: efm.performance.ifOutBcastPkts
       Info: ifOutBcastPkts

       64 bit unsigned wrappable counter."
   ::= {pr1646v2Efm 217}


pr1646v2EfmOutMcastPkts OBJECT-TYPE
   SYNTAX      Counter64
   MAX-ACCESS  read-only
   STATUS      current
   DESCRIPTION
      "Path: efm.performance.ifOutMcastPkts
       Info: ifOutMcastPkts

       64 bit unsigned wrappable counter."
   ::= {pr1646v2Efm 227}


pr1646v2EfmOutDiscards OBJECT-TYPE
   SYNTAX      Counter64
   MAX-ACCESS  read-only
   STATUS      current
   DESCRIPTION
      "Path: efm.performance.ifOutDiscards
       Info: ifOutDiscards

       64 bit unsigned wrappable counter."
   ::= {pr1646v2Efm 118}


pr1646v2EfmOutErrors OBJECT-TYPE
   SYNTAX      Counter64
   MAX-ACCESS  read-only
   STATUS      current
   DESCRIPTION
      "Path: efm.performance.ifOutErrors
       Info: ifOutErrors

       64 bit unsigned wrappable counter."
   ::= {pr1646v2Efm 119}


pr1646v2EfmOutQLen OBJECT-TYPE
   SYNTAX      Gauge32
   MAX-ACCESS  read-only
   STATUS      current
   DESCRIPTION
      "Path: efm.performance.ifOutQLen
       Info: ifOutQLen

       32 bit unsigned gauge value."
   ::= {pr1646v2Efm 120}


pr1646v2EfmOutDropEx OBJECT-TYPE
   SYNTAX      Counter64
   MAX-ACCESS  read-only
   STATUS      current
   DESCRIPTION
      "Path: efm.performance.ifOutDropLevelExceeded
       Info: ifOutDiscards

       64 bit unsigned wrappable counter."
   ::= {pr1646v2Efm 127}


pr1646v2EfmOutDropNoArp OBJECT-TYPE
   SYNTAX      Counter64
   MAX-ACCESS  read-only
   STATUS      current
   DESCRIPTION
      "Path: efm.performance.ifOutDiscardsNoArp
       Info: ifOutDiscards

       64 bit unsigned wrappable counter."
   ::= {pr1646v2Efm 134}


pr1646v2EfmOutDropFilter OBJECT-TYPE
   SYNTAX      Counter64
   MAX-ACCESS  read-only
   STATUS      current
   DESCRIPTION
      "Path: efm.performance.ifOutDiscardsFilter
       Info: ifOutDiscards

       64 bit unsigned wrappable counter."
   ::= {pr1646v2Efm 138}


pr1646v2EfmOutQueues OBJECT IDENTIFIER ::= {pr1646v2Efm 129}

pr1646v2EfmOutQueuesSSCTable OBJECT-TYPE
   SYNTAX      SEQUENCE OF Pr1646v2EfmOutQueuesEntry
   MAX-ACCESS  not-accessible
   STATUS      current
   DESCRIPTION
      "Queue Lengths"
   ::= {pr1646v2EfmOutQueues 1}

pr1646v2EfmOutQueuesEntry OBJECT-TYPE
   SYNTAX      Pr1646v2EfmOutQueuesEntry
   MAX-ACCESS  not-accessible
   STATUS      current
   DESCRIPTION
      ""
   INDEX      { pr1646v2EfmOutQueuesTableIx }
   ::= {pr1646v2EfmOutQueuesSSCTable 1}

Pr1646v2EfmOutQueuesEntry ::=
   SEQUENCE
      {
      pr1646v2EfmOutQueuesTableIx
         TableIndex,
      pr1646v2EfmOutQueuesName
         INTEGER,
      pr1646v2EfmOutQueuesLength
         Integer32,
      pr1646v2EfmOutQueuesOctetLength
         Integer32,
      pr1646v2EfmOutQueuesRedLength
         Integer32,
      pr1646v2EfmOutQueuesPacketsTotal
         Counter64,
      pr1646v2EfmOutQueuesPacketsDirectTx
         Counter64,
      pr1646v2EfmOutQueuesPacketsQueued
         Counter64,
      pr1646v2EfmOutQueuesPacketsDropped
         Counter64,
      pr1646v2EfmOutQueuesPacketsRedDropped
         Counter64,
      pr1646v2EfmOutQueuesPacketsCirTx
         Counter64,
      pr1646v2EfmOutQueuesPacketsEirTx
         Counter64,
      pr1646v2EfmOutQueuesPacketsViolateTx
         Counter64,
      pr1646v2EfmOutQueuesOctetsTotal
         Counter64,
      pr1646v2EfmOutQueuesOctetsDirectTx
         Counter64,
      pr1646v2EfmOutQueuesOctetsQueued
         Counter64,
      pr1646v2EfmOutQueuesOctetsDropped
         Counter64,
      pr1646v2EfmOutQueuesOctetsRedDropped
         Counter64,
      pr1646v2EfmOutQueuesOctetsCirTx
         Counter64,
      pr1646v2EfmOutQueuesOctetsEirTx
         Counter64,
      pr1646v2EfmOutQueuesOctetsViolateTx
         Counter64,
      pr1646v2EfmOutQueuesOctetsBandwidth15sec
         Integer32,
      pr1646v2EfmOutQueuesOctetsBandwidth30sec
         Integer32,
      pr1646v2EfmOutQueuesOctetsBandwidth1min
         Integer32,
      pr1646v2EfmOutQueuesOctetsBandwidth2min
         Integer32,
      pr1646v2EfmOutQueuesOctetsBandwidth5min
         Integer32
      }

pr1646v2EfmOutQueuesTableIx OBJECT-TYPE
   SYNTAX      TableIndex
   MAX-ACCESS  not-accessible
   STATUS      current
   DESCRIPTION
      ""
   ::= {pr1646v2EfmOutQueuesEntry 11}

pr1646v2EfmOutQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: efm.performance.ifOutPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2EfmOutQueuesEntry 16777216}

pr1646v2EfmOutQueuesLength OBJECT-TYPE
   SYNTAX      Integer32
   MAX-ACCESS  read-only
   STATUS      current
   DESCRIPTION
      "Path: efm.performance.ifOutPriorityQueues.length"
   ::= {pr1646v2EfmOutQueuesEntry 33554432}

pr1646v2EfmOutQueuesOctetLength OBJECT-TYPE
   SYNTAX      Integer32
   MAX-ACCESS  read-only
   STATUS      current
   DESCRIPTION
      "Path: efm.performance.ifOutPriorityQueues.octetLength"
   ::= {pr1646v2EfmOutQueuesEntry 150994944}

pr1646v2EfmOutQueuesRedLength OBJECT-TYPE
   SYNTAX      Integer32
   MAX-ACCESS  read-only
   STATUS      current
   DESCRIPTION
      "Path: efm.performance.ifOutPriorityQueues.redLength"
   ::= {pr1646v2EfmOutQueuesEntry 134217728}

pr1646v2EfmOutQueuesPacketsTotal OBJECT-TYPE
   SYNTAX      Counter64
   MAX-ACCESS  read-only
   STATUS      current
   DESCRIPTION
      "Path: efm.performance.ifOutPriorityQueues.packets.total

       64 bit unsigned wrappable counter."
   ::= {pr1646v2EfmOutQueuesEntry 50790400}

pr1646v2EfmOutQueuesPacketsDirectTx OBJECT-TYPE
   SYNTAX      Counter64
   MAX-ACCESS  read-only
   STATUS      current
   DESCRIPTION
      "Path: efm.performance.ifOutPriorityQueues.packets.directTx

       64 bit unsigned wrappable counter."
   ::= {pr1646v2EfmOutQueuesEntry 50397184}

pr1646v2EfmOutQueuesPacketsQueued OBJECT-TYPE
   SYNTAX      Counter64
   MAX-ACCESS  read-only
   STATUS      current
   DESCRIPTION
      "Path: efm.performance.ifOutPriorityQueues.packets.queued

       64 bit unsigned wrappable counter."
   ::= {pr1646v2EfmOutQueuesEntry 50462720}

pr1646v2EfmOutQueuesPacketsDropped OBJECT-TYPE
   SYNTAX      Counter64
   MAX-ACCESS  read-only
   STATUS      current
   DESCRIPTION
      "Path: efm.performance.ifOutPriorityQueues.packets.dropped

       64 bit unsigned wrappable counter."
   ::= {pr1646v2EfmOutQueuesEntry 50528256}

pr1646v2EfmOutQueuesPacketsRedDropped OBJECT-TYPE
   SYNTAX      Counter64
   MAX-ACCESS  read-only
   STATUS      current
   DESCRIPTION
      "Path: efm.performance.ifOutPriorityQueues.packets.redDropped

       64 bit unsigned wrappable counter."
   ::= {pr1646v2EfmOutQueuesEntry 50724864}

pr1646v2EfmOutQueuesPacketsCirTx OBJECT-TYPE
   SYNTAX      Counter64
   MAX-ACCESS  read-only
   STATUS      current
   DESCRIPTION
      "Path: efm.performance.ifOutPriorityQueues.packets.cirTx

       64 bit unsigned wrappable counter."
   ::= {pr1646v2EfmOutQueuesEntry 50593792}

pr1646v2EfmOutQueuesPacketsEirTx OBJECT-TYPE
   SYNTAX      Counter64
   MAX-ACCESS  read-only
   STATUS      current
   DESCRIPTION
      "Path: efm.performance.ifOutPriorityQueues.packets.eirTx

       64 bit unsigned wrappable counter."
   ::= {pr1646v2EfmOutQueuesEntry 50659328}

pr1646v2EfmOutQueuesPacketsViolateTx OBJECT-TYPE
   SYNTAX      Counter64
   MAX-ACCESS  read-only
   STATUS      current
   DESCRIPTION
      "Path: efm.performance.ifOutPriorityQueues.packets.violateTx

       64 bit unsigned wrappable counter."
   ::= {pr1646v2EfmOutQueuesEntry 50855936}

pr1646v2EfmOutQueuesOctetsTotal OBJECT-TYPE
   SYNTAX      Counter64
   MAX-ACCESS  read-only
   STATUS      current
   DESCRIPTION
      "Path: efm.performance.ifOutPriorityQueues.octets.total

       64 bit unsigned wrappable counter."
   ::= {pr1646v2EfmOutQueuesEntry 67567616}

pr1646v2EfmOutQueuesOctetsDirectTx OBJECT-TYPE
   SYNTAX      Counter64
   MAX-ACCESS  read-only
   STATUS      current
   DESCRIPTION
      "Path: efm.performance.ifOutPriorityQueues.octets.directTx

       64 bit unsigned wrappable counter."
   ::= {pr1646v2EfmOutQueuesEntry 67174400}

pr1646v2EfmOutQueuesOctetsQueued OBJECT-TYPE
   SYNTAX      Counter64
   MAX-ACCESS  read-only
   STATUS      current
   DESCRIPTION
      "Path: efm.performance.ifOutPriorityQueues.octets.queued

       64 bit unsigned wrappable counter."
   ::= {pr1646v2EfmOutQueuesEntry 67239936}

pr1646v2EfmOutQueuesOctetsDropped OBJECT-TYPE
   SYNTAX      Counter64
   MAX-ACCESS  read-only
   STATUS      current
   DESCRIPTION
      "Path: efm.performance.ifOutPriorityQueues.octets.dropped

       64 bit unsigned wrappable counter."
   ::= {pr1646v2EfmOutQueuesEntry 67305472}

pr1646v2EfmOutQueuesOctetsRedDropped OBJECT-TYPE
   SYNTAX      Counter64
   MAX-ACCESS  read-only
   STATUS      current
   DESCRIPTION
      "Path: efm.performance.ifOutPriorityQueues.octets.redDropped

       64 bit unsigned wrappable counter."
   ::= {pr1646v2EfmOutQueuesEntry 67502080}

pr1646v2EfmOutQueuesOctetsCirTx OBJECT-TYPE
   SYNTAX      Counter64
   MAX-ACCESS  read-only
   STATUS      current
   DESCRIPTION
      "Path: efm.performance.ifOutPriorityQueues.octets.cirTx

       64 bit unsigned wrappable counter."
   ::= {pr1646v2EfmOutQueuesEntry 67371008}

pr1646v2EfmOutQueuesOctetsEirTx OBJECT-TYPE
   SYNTAX      Counter64
   MAX-ACCESS  read-only
   STATUS      current
   DESCRIPTION
      "Path: efm.performance.ifOutPriorityQueues.octets.eirTx

       64 bit unsigned wrappable counter."
   ::= {pr1646v2EfmOutQueuesEntry 67436544}

pr1646v2EfmOutQueuesOctetsViolateTx OBJECT-TYPE
   SYNTAX      Counter64
   MAX-ACCESS  read-only
   STATUS      current
   DESCRIPTION
      "Path: efm.performance.ifOutPriorityQueues.octets.violateTx

       64 bit unsigned wrappable counter."
   ::= {pr1646v2EfmOutQueuesEntry 67633152}

pr1646v2EfmOutQueuesOctetsBandwidth15sec OBJECT-TYPE
   SYNTAX      Integer32
   MAX-ACCESS  read-only
   STATUS      current
   DESCRIPTION
      "Path: efm.performance.ifOutPriorityQueues.octets.bandwidth.15sec

       unit name = bps
       formula = 8 * ; 8 /"
   ::= {pr1646v2EfmOutQueuesEntry 70386944}

pr1646v2EfmOutQueuesOctetsBandwidth30sec OBJECT-TYPE
   SYNTAX      Integer32
   MAX-ACCESS  read-only
   STATUS      current
   DESCRIPTION
      "Path: efm.performance.ifOutPriorityQueues.octets.bandwidth.30sec

       unit name = bps
       formula = 8 * ; 8 /"
   ::= {pr1646v2EfmOutQueuesEntry 70388224}

pr1646v2EfmOutQueuesOctetsBandwidth1min OBJECT-TYPE
   SYNTAX      Integer32
   MAX-ACCESS  read-only
   STATUS      current
   DESCRIPTION
      "Path: efm.performance.ifOutPriorityQueues.octets.bandwidth.1min

       unit name = bps
       formula = 8 * ; 8 /"
   ::= {pr1646v2EfmOutQueuesEntry 70390784}

pr1646v2EfmOutQueuesOctetsBandwidth2min OBJECT-TYPE
   SYNTAX      Integer32
   MAX-ACCESS  read-only
   STATUS      current
   DESCRIPTION
      "Path: efm.performance.ifOutPriorityQueues.octets.bandwidth.2min

       unit name = bps
       formula = 8 * ; 8 /"
   ::= {pr1646v2EfmOutQueuesEntry 70395904}

pr1646v2EfmOutQueuesOctetsBandwidth5min OBJECT-TYPE
   SYNTAX      Integer32
   MAX-ACCESS  read-only
   STATUS      current
   DESCRIPTION
      "Path: efm.performance.ifOutPriorityQueues.octets.bandwidth.5min

       unit name = bps
       formula = 8 * ; 8 /"
   ::= {pr1646v2EfmOutQueuesEntry 70411264}

pr1646v2EfmOutQueuesH2Performance OBJECT-TYPE
   SYNTAX      SEQUENCE OF Pr1646v2EfmOutQueuesH2PerformanceEntry
   MAX-ACCESS  not-accessible
   STATUS      current
   DESCRIPTION
      ""
   ::= {pr1646v2EfmOutQueues 83886080}

pr1646v2EfmOutQueuesH2PerformanceEntry OBJECT-TYPE
   SYNTAX      Pr1646v2EfmOutQueuesH2PerformanceEntry
   MAX-ACCESS  not-accessible
   STATUS      current
   DESCRIPTION
      ""
   INDEX      { pr1646v2EfmOutQueuesTableIx,
                pr1646v2EfmOutQueuesH2PerformanceTableIx }
   ::= {pr1646v2EfmOutQueuesH2Performance 1}

Pr1646v2EfmOutQueuesH2PerformanceEntry ::=
   SEQUENCE
      {
      pr1646v2EfmOutQueuesH2PerformanceTableIx
         TableIndex,
      pr1646v2EfmOutQueuesH2PerformanceSysUpTime
         TimeTicks,
      pr1646v2EfmOutQueuesH2PerformanceTotPkts
         Counter64,
      pr1646v2EfmOutQueuesH2PerformanceDirTxPkts
         Counter64,
      pr1646v2EfmOutQueuesH2PerformanceQdPkts
         Counter64,
      pr1646v2EfmOutQueuesH2PerformanceDropPkts
         Counter64,
      pr1646v2EfmOutQueuesH2PerformanceRDropPkts
         Counter64,
      pr1646v2EfmOutQueuesH2PerformanceCirTxPkts
         Counter64,
      pr1646v2EfmOutQueuesH2PerformanceEirTxPkts
         Counter64,
      pr1646v2EfmOutQueuesH2PerformanceViolTxPkts
         Counter64,
      pr1646v2EfmOutQueuesH2PerformanceTotOcts
         Counter64,
      pr1646v2EfmOutQueuesH2PerformanceDirTxOcts
         Counter64,
      pr1646v2EfmOutQueuesH2PerformanceQdOcts
         Counter64,
      pr1646v2EfmOutQueuesH2PerformanceDropOcts
         Counter64,
      pr1646v2EfmOutQueuesH2PerformanceRDropOcts
         Counter64,
      pr1646v2EfmOutQueuesH2PerformanceCirTxOcts
         Counter64,
      pr1646v2EfmOutQueuesH2PerformanceEirTxOcts
         Counter64,
      pr1646v2EfmOutQueuesH2PerformanceViolTxOcts
         Counter64,
      pr1646v2EfmOutQueuesH2PerformanceBandwidth
         Integer32
      }

pr1646v2EfmOutQueuesH2PerformanceTableIx OBJECT-TYPE
   SYNTAX      TableIndex
   MAX-ACCESS  not-accessible
   STATUS      current
   DESCRIPTION
      ""
   ::= {pr1646v2EfmOutQueuesH2PerformanceEntry 11}

pr1646v2EfmOutQueuesH2PerformanceSysUpTime OBJECT-TYPE
   SYNTAX      TimeTicks
   MAX-ACCESS  read-only
   STATUS      current
   DESCRIPTION
      "Path: efm.performance.ifOutPriorityQueues.h2Performance.sysUpTime

       Time in centi-second."
   ::= {pr1646v2EfmOutQueuesH2PerformanceEntry 16777216}

pr1646v2EfmOutQueuesH2PerformanceTotPkts OBJECT-TYPE
   SYNTAX      Counter64
   MAX-ACCESS  read-only
   STATUS      current
   DESCRIPTION
      "Path: efm.performance.ifOutPriorityQueues.h2Performance.totalPkts

       64 bit unsigned wrappable counter."
   ::= {pr1646v2EfmOutQueuesH2PerformanceEntry 234881024}

pr1646v2EfmOutQueuesH2PerformanceDirTxPkts OBJECT-TYPE
   SYNTAX      Counter64
   MAX-ACCESS  read-only
   STATUS      current
   DESCRIPTION
      "Path: efm.performance.ifOutPriorityQueues.h2Performance.directTxPkts

       64 bit unsigned wrappable counter."
   ::= {pr1646v2EfmOutQueuesH2PerformanceEntry 33554432}

pr1646v2EfmOutQueuesH2PerformanceQdPkts OBJECT-TYPE
   SYNTAX      Counter64
   MAX-ACCESS  read-only
   STATUS      current
   DESCRIPTION
      "Path: efm.performance.ifOutPriorityQueues.h2Performance.queuedPkts

       64 bit unsigned wrappable counter."
   ::= {pr1646v2EfmOutQueuesH2PerformanceEntry 50331648}

pr1646v2EfmOutQueuesH2PerformanceDropPkts OBJECT-TYPE
   SYNTAX      Counter64
   MAX-ACCESS  read-only
   STATUS      current
   DESCRIPTION
      "Path: efm.performance.ifOutPriorityQueues.h2Performance.droppedPkts

       64 bit unsigned wrappable counter."
   ::= {pr1646v2EfmOutQueuesH2PerformanceEntry 67108864}

pr1646v2EfmOutQueuesH2PerformanceRDropPkts OBJECT-TYPE
   SYNTAX      Counter64
   MAX-ACCESS  read-only
   STATUS      current
   DESCRIPTION
      "Path: efm.performance.ifOutPriorityQueues.h2Performance.redDroppedPkts

       64 bit unsigned wrappable counter."
   ::= {pr1646v2EfmOutQueuesH2PerformanceEntry 201326592}

pr1646v2EfmOutQueuesH2PerformanceCirTxPkts OBJECT-TYPE
   SYNTAX      Counter64
   MAX-ACCESS  read-only
   STATUS      current
   DESCRIPTION
      "Path: efm.performance.ifOutPriorityQueues.h2Performance.cirTxPkts

       64 bit unsigned wrappable counter."
   ::= {pr1646v2EfmOutQueuesH2PerformanceEntry 83886080}

pr1646v2EfmOutQueuesH2PerformanceEirTxPkts OBJECT-TYPE
   SYNTAX      Counter64
   MAX-ACCESS  read-only
   STATUS      current
   DESCRIPTION
      "Path: efm.performance.ifOutPriorityQueues.h2Performance.eirTxPkts

       64 bit unsigned wrappable counter."
   ::= {pr1646v2EfmOutQueuesH2PerformanceEntry 100663296}

pr1646v2EfmOutQueuesH2PerformanceViolTxPkts OBJECT-TYPE
   SYNTAX      Counter64
   MAX-ACCESS  read-only
   STATUS      current
   DESCRIPTION
      "Path: efm.performance.ifOutPriorityQueues.h2Performance.violateTxPkts

       64 bit unsigned wrappable counter."
   ::= {pr1646v2EfmOutQueuesH2PerformanceEntry 301989888}

pr1646v2EfmOutQueuesH2PerformanceTotOcts OBJECT-TYPE
   SYNTAX      Counter64
   MAX-ACCESS  read-only
   STATUS      current
   DESCRIPTION
      "Path: efm.performance.ifOutPriorityQueues.h2Performance.totalOctets

       64 bit unsigned wrappable counter."
   ::= {pr1646v2EfmOutQueuesH2PerformanceEntry 251658240}

pr1646v2EfmOutQueuesH2PerformanceDirTxOcts OBJECT-TYPE
   SYNTAX      Counter64
   MAX-ACCESS  read-only
   STATUS      current
   DESCRIPTION
      "Path: efm.performance.ifOutPriorityQueues.h2Performance.directTxOctets

       64 bit unsigned wrappable counter."
   ::= {pr1646v2EfmOutQueuesH2PerformanceEntry 117440512}

pr1646v2EfmOutQueuesH2PerformanceQdOcts OBJECT-TYPE
   SYNTAX      Counter64
   MAX-ACCESS  read-only
   STATUS      current
   DESCRIPTION
      "Path: efm.performance.ifOutPriorityQueues.h2Performance.queuedOctets

       64 bit unsigned wrappable counter."
   ::= {pr1646v2EfmOutQueuesH2PerformanceEntry 134217728}

pr1646v2EfmOutQueuesH2PerformanceDropOcts OBJECT-TYPE
   SYNTAX      Counter64
   MAX-ACCESS  read-only
   STATUS      current
   DESCRIPTION
      "Path: efm.performance.ifOutPriorityQueues.h2Performance.droppedOctets

       64 bit unsigned wrappable counter."
   ::= {pr1646v2EfmOutQueuesH2PerformanceEntry 150994944}

pr1646v2EfmOutQueuesH2PerformanceRDropOcts OBJECT-TYPE
   SYNTAX      Counter64
   MAX-ACCESS  read-only
   STATUS      current
   DESCRIPTION
      "Path: efm.performance.ifOutPriorityQueues.h2Performance.redDroppedOctets

       64 bit unsigned wrappable counter."
   ::= {pr1646v2EfmOutQueuesH2PerformanceEntry 218103808}

pr1646v2EfmOutQueuesH2PerformanceCirTxOcts OBJECT-TYPE
   SYNTAX      Counter64
   MAX-ACCESS  read-only
   STATUS      current
   DESCRIPTION
      "Path: efm.performance.ifOutPriorityQueues.h2Performance.cirTxOctets

       64 bit unsigned wrappable counter."
   ::= {pr1646v2EfmOutQueuesH2PerformanceEntry 167772160}

pr1646v2EfmOutQueuesH2PerformanceEirTxOcts OBJECT-TYPE
   SYNTAX      Counter64
   MAX-ACCESS  read-only
   STATUS      current
   DESCRIPTION
      "Path: efm.performance.ifOutPriorityQueues.h2Performance.eirTxOctets

       64 bit unsigned wrappable counter."
   ::= {pr1646v2EfmOutQueuesH2PerformanceEntry 184549376}

pr1646v2EfmOutQueuesH2PerformanceViolTxOcts OBJECT-TYPE
   SYNTAX      Counter64
   MAX-ACCESS  read-only
   STATUS      current
   DESCRIPTION
      "Path: efm.performance.ifOutPriorityQueues.h2Performance.violateTxOctets

       64 bit unsigned wrappable counter."
   ::= {pr1646v2EfmOutQueuesH2PerformanceEntry 318767104}

pr1646v2EfmOutQueuesH2PerformanceBandwidth OBJECT-TYPE
   SYNTAX      Integer32
   MAX-ACCESS  read-only
   STATUS      current
   DESCRIPTION
      "Path: efm.performance.ifOutPriorityQueues.h2Performance.bandwidth

       unit name = bps
       formula = 8 * ; 8 /"
   ::= {pr1646v2EfmOutQueuesH2PerformanceEntry 268435456}

pr1646v2EfmOutQueuesH24Performance OBJECT-TYPE
   SYNTAX      SEQUENCE OF Pr1646v2EfmOutQueuesH24PerformanceEntry
   MAX-ACCESS  not-accessible
   STATUS      current
   DESCRIPTION
      ""
   ::= {pr1646v2EfmOutQueues 100663296}

pr1646v2EfmOutQueuesH24PerformanceEntry OBJECT-TYPE
   SYNTAX      Pr1646v2EfmOutQueuesH24PerformanceEntry
   MAX-ACCESS  not-accessible
   STATUS      current
   DESCRIPTION
      ""
   INDEX      { pr1646v2EfmOutQueuesTableIx,
                pr1646v2EfmOutQueuesH24PerformanceTableIx }
   ::= {pr1646v2EfmOutQueuesH24Performance 1}

Pr1646v2EfmOutQueuesH24PerformanceEntry ::=
   SEQUENCE
      {
      pr1646v2EfmOutQueuesH24PerformanceTableIx
         TableIndex,
      pr1646v2EfmOutQueuesH24PerformanceSysUpTime
         TimeTicks,
      pr1646v2EfmOutQueuesH24PerformanceTotPkts
         Counter64,
      pr1646v2EfmOutQueuesH24PerformanceDirTxPkts
         Counter64,
      pr1646v2EfmOutQueuesH24PerformanceQdPkts
         Counter64,
      pr1646v2EfmOutQueuesH24PerformanceDropPkts
         Counter64,
      pr1646v2EfmOutQueuesH24PerformanceRDropPkts
         Counter64,
      pr1646v2EfmOutQueuesH24PerformanceCirTxPkts
         Counter64,
      pr1646v2EfmOutQueuesH24PerformanceEirTxPkts
         Counter64,
      pr1646v2EfmOutQueuesH24PerformanceViolTxPkts
         Counter64,
      pr1646v2EfmOutQueuesH24PerformanceTotOcts
         Counter64,
      pr1646v2EfmOutQueuesH24PerformanceDirTxOcts
         Counter64,
      pr1646v2EfmOutQueuesH24PerformanceQdOcts
         Counter64,
      pr1646v2EfmOutQueuesH24PerformanceDropOcts
         Counter64,
      pr1646v2EfmOutQueuesH24PerformanceRDropOcts
         Counter64,
      pr1646v2EfmOutQueuesH24PerformanceCirTxOcts
         Counter64,
      pr1646v2EfmOutQueuesH24PerformanceEirTxOcts
         Counter64,
      pr1646v2EfmOutQueuesH24PerformanceViolTxOcts
         Counter64,
      pr1646v2EfmOutQueuesH24PerformanceBandwidth
         Integer32
      }

pr1646v2EfmOutQueuesH24PerformanceTableIx OBJECT-TYPE
   SYNTAX      TableIndex
   MAX-ACCESS  not-accessible
   STATUS      current
   DESCRIPTION
      ""
   ::= {pr1646v2EfmOutQueuesH24PerformanceEntry 11}

pr1646v2EfmOutQueuesH24PerformanceSysUpTime OBJECT-TYPE
   SYNTAX      TimeTicks
   MAX-ACCESS  read-only
   STATUS      current
   DESCRIPTION
      "Path: efm.performance.ifOutPriorityQueues.h24Performance.sysUpTime

       Time in centi-second."
   ::= {pr1646v2EfmOutQueuesH24PerformanceEntry 16777216}

pr1646v2EfmOutQueuesH24PerformanceTotPkts OBJECT-TYPE
   SYNTAX      Counter64
   MAX-ACCESS  read-only
   STATUS      current
   DESCRIPTION
      "Path: efm.performance.ifOutPriorityQueues.h24Performance.totalPkts

       64 bit unsigned wrappable counter."
   ::= {pr1646v2EfmOutQueuesH24PerformanceEntry 234881024}

pr1646v2EfmOutQueuesH24PerformanceDirTxPkts OBJECT-TYPE
   SYNTAX      Counter64
   MAX-ACCESS  read-only
   STATUS      current
   DESCRIPTION
      "Path: efm.performance.ifOutPriorityQueues.h24Performance.directTxPkts

       64 bit unsigned wrappable counter."
   ::= {pr1646v2EfmOutQueuesH24PerformanceEntry 33554432}

pr1646v2EfmOutQueuesH24PerformanceQdPkts OBJECT-TYPE
   SYNTAX      Counter64
   MAX-ACCESS  read-only
   STATUS      current
   DESCRIPTION
      "Path: efm.performance.ifOutPriorityQueues.h24Performance.queuedPkts

       64 bit unsigned wrappable counter."
   ::= {pr1646v2EfmOutQueuesH24PerformanceEntry 50331648}

pr1646v2EfmOutQueuesH24PerformanceDropPkts OBJECT-TYPE
   SYNTAX      Counter64
   MAX-ACCESS  read-only
   STATUS      current
   DESCRIPTION
      "Path: efm.performance.ifOutPriorityQueues.h24Performance.droppedPkts

       64 bit unsigned wrappable counter."
   ::= {pr1646v2EfmOutQueuesH24PerformanceEntry 67108864}

pr1646v2EfmOutQueuesH24PerformanceRDropPkts OBJECT-TYPE
   SYNTAX      Counter64
   MAX-ACCESS  read-only
   STATUS      current
   DESCRIPTION
      "Path: efm.performance.ifOutPriorityQueues.h24Performance.redDroppedPkts

       64 bit unsigned wrappable counter."
   ::= {pr1646v2EfmOutQueuesH24PerformanceEntry 201326592}

pr1646v2EfmOutQueuesH24PerformanceCirTxPkts OBJECT-TYPE
   SYNTAX      Counter64
   MAX-ACCESS  read-only
   STATUS      current
   DESCRIPTION
      "Path: efm.performance.ifOutPriorityQueues.h24Performance.cirTxPkts

       64 bit unsigned wrappable counter."
   ::= {pr1646v2EfmOutQueuesH24PerformanceEntry 83886080}

pr1646v2EfmOutQueuesH24PerformanceEirTxPkts OBJECT-TYPE
   SYNTAX      Counter64
   MAX-ACCESS  read-only
   STATUS      current
   DESCRIPTION
      "Path: efm.performance.ifOutPriorityQueues.h24Performance.eirTxPkts

       64 bit unsigned wrappable counter."
   ::= {pr1646v2EfmOutQueuesH24PerformanceEntry 100663296}

pr1646v2EfmOutQueuesH24PerformanceViolTxPkts OBJECT-TYPE
   SYNTAX      Counter64
   MAX-ACCESS  read-only
   STATUS      current
   DESCRIPTION
      "Path: efm.performance.ifOutPriorityQueues.h24Performance.violateTxPkts

       64 bit unsigned wrappable counter."
   ::= {pr1646v2EfmOutQueuesH24PerformanceEntry 301989888}

pr1646v2EfmOutQueuesH24PerformanceTotOcts OBJECT-TYPE
   SYNTAX      Counter64
   MAX-ACCESS  read-only
   STATUS      current
   DESCRIPTION
      "Path: efm.performance.ifOutPriorityQueues.h24Performance.totalOctets

       64 bit unsigned wrappable counter."
   ::= {pr1646v2EfmOutQueuesH24PerformanceEntry 251658240}

pr1646v2EfmOutQueuesH24PerformanceDirTxOcts OBJECT-TYPE
   SYNTAX      Counter64
   MAX-ACCESS  read-only
   STATUS      current
   DESCRIPTION
      "Path: efm.performance.ifOutPriorityQueues.h24Performance.directTxOctets

       64 bit unsigned wrappable counter."
   ::= {pr1646v2EfmOutQueuesH24PerformanceEntry 117440512}

pr1646v2EfmOutQueuesH24PerformanceQdOcts OBJECT-TYPE
   SYNTAX      Counter64
   MAX-ACCESS  read-only
   STATUS      current
   DESCRIPTION
      "Path: efm.performance.ifOutPriorityQueues.h24Performance.queuedOctets

       64 bit unsigned wrappable counter."
   ::= {pr1646v2EfmOutQueuesH24PerformanceEntry 134217728}

pr1646v2EfmOutQueuesH24PerformanceDropOcts OBJECT-TYPE
   SYNTAX      Counter64
   MAX-ACCESS  read-only
   STATUS      current
   DESCRIPTION
      "Path: efm.performance.ifOutPriorityQueues.h24Performance.droppedOctets

       64 bit unsigned wrappable counter."
   ::= {pr1646v2EfmOutQueuesH24PerformanceEntry 150994944}

pr1646v2EfmOutQueuesH24PerformanceRDropOcts OBJECT-TYPE
   SYNTAX      Counter64
   MAX-ACCESS  read-only
   STATUS      current
   DESCRIPTION
      "Path: efm.performance.ifOutPriorityQueues.h24Performance.redDroppedOctets

       64 bit unsigned wrappable counter."
   ::= {pr1646v2EfmOutQueuesH24PerformanceEntry 218103808}

pr1646v2EfmOutQueuesH24PerformanceCirTxOcts OBJECT-TYPE
   SYNTAX      Counter64
   MAX-ACCESS  read-only
   STATUS      current
   DESCRIPTION
      "Path: efm.performance.ifOutPriorityQueues.h24Performance.cirTxOctets

       64 bit unsigned wrappable counter."
   ::= {pr1646v2EfmOutQueuesH24PerformanceEntry 167772160}

pr1646v2EfmOutQueuesH24PerformanceEirTxOcts OBJECT-TYPE
   SYNTAX      Counter64
   MAX-ACCESS  read-only
   STATUS      current
   DESCRIPTION
      "Path: efm.performance.ifOutPriorityQueues.h24Performance.eirTxOctets

       64 bit unsigned wrappable counter."
   ::= {pr1646v2EfmOutQueuesH24PerformanceEntry 184549376}

pr1646v2EfmOutQueuesH24PerformanceViolTxOcts OBJECT-TYPE
   SYNTAX      Counter64
   MAX-ACCESS  read-only
   STATUS      current
   DESCRIPTION
      "Path: efm.performance.ifOutPriorityQueues.h24Performance.violateTxOctets

       64 bit unsigned wrappable counter."
   ::= {pr1646v2EfmOutQueuesH24PerformanceEntry 318767104}

pr1646v2EfmOutQueuesH24PerformanceBandwidth OBJECT-TYPE
   SYNTAX      Integer32
   MAX-ACCESS  read-only
   STATUS      current
   DESCRIPTION
      "Path: efm.performance.ifOutPriorityQueues.h24Performance.bandwidth

       unit name = bps
       formula = 8 * ; 8 /"
   ::= {pr1646v2EfmOutQueuesH24PerformanceEntry 268435456}

pr1646v2EfmOutQueuesD7Performance OBJECT-TYPE
   SYNTAX      SEQUENCE OF Pr1646v2EfmOutQueuesD7PerformanceEntry
   MAX-ACCESS  not-accessible
   STATUS      current
   DESCRIPTION
      ""
   ::= {pr1646v2EfmOutQueues 117440512}

pr1646v2EfmOutQueuesD7PerformanceEntry OBJECT-TYPE
   SYNTAX      Pr1646v2EfmOutQueuesD7PerformanceEntry
   MAX-ACCESS  not-accessible
   STATUS      current
   DESCRIPTION
      ""
   INDEX      { pr1646v2EfmOutQueuesTableIx,
                pr1646v2EfmOutQueuesD7PerformanceTableIx }
   ::= {pr1646v2EfmOutQueuesD7Performance 1}

Pr1646v2EfmOutQueuesD7PerformanceEntry ::=
   SEQUENCE
      {
      pr1646v2EfmOutQueuesD7PerformanceTableIx
         TableIndex,
      pr1646v2EfmOutQueuesD7PerformanceSysUpTime
         TimeTicks,
      pr1646v2EfmOutQueuesD7PerformanceTotPkts
         Counter64,
      pr1646v2EfmOutQueuesD7PerformanceDirTxPkts
         Counter64,
      pr1646v2EfmOutQueuesD7PerformanceQdPkts
         Counter64,
      pr1646v2EfmOutQueuesD7PerformanceDropPkts
         Counter64,
      pr1646v2EfmOutQueuesD7PerformanceRDropPkts
         Counter64,
      pr1646v2EfmOutQueuesD7PerformanceCirTxPkts
         Counter64,
      pr1646v2EfmOutQueuesD7PerformanceEirTxPkts
         Counter64,
      pr1646v2EfmOutQueuesD7PerformanceViolTxPkts
         Counter64,
      pr1646v2EfmOutQueuesD7PerformanceTotOcts
         Counter64,
      pr1646v2EfmOutQueuesD7PerformanceDirTxOcts
         Counter64,
      pr1646v2EfmOutQueuesD7PerformanceQdOcts
         Counter64,
      pr1646v2EfmOutQueuesD7PerformanceDropOcts
         Counter64,
      pr1646v2EfmOutQueuesD7PerformanceRDropOcts
         Counter64,
      pr1646v2EfmOutQueuesD7PerformanceCirTxOcts
         Counter64,
      pr1646v2EfmOutQueuesD7PerformanceEirTxOcts
         Counter64,
      pr1646v2EfmOutQueuesD7PerformanceViolTxOcts
         Counter64,
      pr1646v2EfmOutQueuesD7PerformanceBandwidth
         Integer32
      }

pr1646v2EfmOutQueuesD7PerformanceTableIx OBJECT-TYPE
   SYNTAX      TableIndex
   MAX-ACCESS  not-accessible
   STATUS      current
   DESCRIPTION
      ""
   ::= {pr1646v2EfmOutQueuesD7PerformanceEntry 11}

pr1646v2EfmOutQueuesD7PerformanceSysUpTime OBJECT-TYPE
   SYNTAX      TimeTicks
   MAX-ACCESS  read-only
   STATUS      current
   DESCRIPTION
      "Path: efm.performance.ifOutPriorityQueues.d7Performance.sysUpTime

       Time in centi-second."
   ::= {pr1646v2EfmOutQueuesD7PerformanceEntry 16777216}

pr1646v2EfmOutQueuesD7PerformanceTotPkts OBJECT-TYPE
   SYNTAX      Counter64
   MAX-ACCESS  read-only
   STATUS      current
   DESCRIPTION
      "Path: efm.performance.ifOutPriorityQueues.d7Performance.totalPkts

       64 bit unsigned wrappable counter."
   ::= {pr1646v2EfmOutQueuesD7PerformanceEntry 234881024}

pr1646v2EfmOutQueuesD7PerformanceDirTxPkts OBJECT-TYPE
   SYNTAX      Counter64
   MAX-ACCESS  read-only
   STATUS      current
   DESCRIPTION
      "Path: efm.performance.ifOutPriorityQueues.d7Performance.directTxPkts

       64 bit unsigned wrappable counter."
   ::= {pr1646v2EfmOutQueuesD7PerformanceEntry 33554432}

pr1646v2EfmOutQueuesD7PerformanceQdPkts OBJECT-TYPE
   SYNTAX      Counter64
   MAX-ACCESS  read-only
   STATUS      current
   DESCRIPTION
      "Path: efm.performance.ifOutPriorityQueues.d7Performance.queuedPkts

       64 bit unsigned wrappable counter."
   ::= {pr1646v2EfmOutQueuesD7PerformanceEntry 50331648}

pr1646v2EfmOutQueuesD7PerformanceDropPkts OBJECT-TYPE
   SYNTAX      Counter64
   MAX-ACCESS  read-only
   STATUS      current
   DESCRIPTION
      "Path: efm.performance.ifOutPriorityQueues.d7Performance.droppedPkts

       64 bit unsigned wrappable counter."
   ::= {pr1646v2EfmOutQueuesD7PerformanceEntry 67108864}

pr1646v2EfmOutQueuesD7PerformanceRDropPkts OBJECT-TYPE
   SYNTAX      Counter64
   MAX-ACCESS  read-only
   STATUS      current
   DESCRIPTION
      "Path: efm.performance.ifOutPriorityQueues.d7Performance.redDroppedPkts

       64 bit unsigned wrappable counter."
   ::= {pr1646v2EfmOutQueuesD7PerformanceEntry 201326592}

pr1646v2EfmOutQueuesD7PerformanceCirTxPkts OBJECT-TYPE
   SYNTAX      Counter64
   MAX-ACCESS  read-only
   STATUS      current
   DESCRIPTION
      "Path: efm.performance.ifOutPriorityQueues.d7Performance.cirTxPkts

       64 bit unsigned wrappable counter."
   ::= {pr1646v2EfmOutQueuesD7PerformanceEntry 83886080}

pr1646v2EfmOutQueuesD7PerformanceEirTxPkts OBJECT-TYPE
   SYNTAX      Counter64
   MAX-ACCESS  read-only
   STATUS      current
   DESCRIPTION
      "Path: efm.performance.ifOutPriorityQueues.d7Performance.eirTxPkts

       64 bit unsigned wrappable counter."
   ::= {pr1646v2EfmOutQueuesD7PerformanceEntry 100663296}

pr1646v2EfmOutQueuesD7PerformanceViolTxPkts OBJECT-TYPE
   SYNTAX      Counter64
   MAX-ACCESS  read-only
   STATUS      current
   DESCRIPTION
      "Path: efm.performance.ifOutPriorityQueues.d7Performance.violateTxPkts

       64 bit unsigned wrappable counter."
   ::= {pr1646v2EfmOutQueuesD7PerformanceEntry 301989888}

pr1646v2EfmOutQueuesD7PerformanceTotOcts OBJECT-TYPE
   SYNTAX      Counter64
   MAX-ACCESS  read-only
   STATUS      current
   DESCRIPTION
      "Path: efm.performance.ifOutPriorityQueues.d7Performance.totalOctets

       64 bit unsigned wrappable counter."
   ::= {pr1646v2EfmOutQueuesD7PerformanceEntry 251658240}

pr1646v2EfmOutQueuesD7PerformanceDirTxOcts OBJECT-TYPE
   SYNTAX      Counter64
   MAX-ACCESS  read-only
   STATUS      current
   DESCRIPTION
      "Path: efm.performance.ifOutPriorityQueues.d7Performance.directTxOctets

       64 bit unsigned wrappable counter."
   ::= {pr1646v2EfmOutQueuesD7PerformanceEntry 117440512}

pr1646v2EfmOutQueuesD7PerformanceQdOcts OBJECT-TYPE
   SYNTAX      Counter64
   MAX-ACCESS  read-only
   STATUS      current
   DESCRIPTION
      "Path: efm.performance.ifOutPriorityQueues.d7Performance.queuedOctets

       64 bit unsigned wrappable counter."
   ::= {pr1646v2EfmOutQueuesD7PerformanceEntry 134217728}

pr1646v2EfmOutQueuesD7PerformanceDropOcts OBJECT-TYPE
   SYNTAX      Counter64
   MAX-ACCESS  read-only
   STATUS      current
   DESCRIPTION
      "Path: efm.performance.ifOutPriorityQueues.d7Performance.droppedOctets

       64 bit unsigned wrappable counter."
   ::= {pr1646v2EfmOutQueuesD7PerformanceEntry 150994944}

pr1646v2EfmOutQueuesD7PerformanceRDropOcts OBJECT-TYPE
   SYNTAX      Counter64
   MAX-ACCESS  read-only
   STATUS      current
   DESCRIPTION
      "Path: efm.performance.ifOutPriorityQueues.d7Performance.redDroppedOctets

       64 bit unsigned wrappable counter."
   ::= {pr1646v2EfmOutQueuesD7PerformanceEntry 218103808}

pr1646v2EfmOutQueuesD7PerformanceCirTxOcts OBJECT-TYPE
   SYNTAX      Counter64
   MAX-ACCESS  read-only
   STATUS      current
   DESCRIPTION
      "Path: efm.performance.ifOutPriorityQueues.d7Performance.cirTxOctets

       64 bit unsigned wrappable counter."
   ::= {pr1646v2EfmOutQueuesD7PerformanceEntry 167772160}

pr1646v2EfmOutQueuesD7PerformanceEirTxOcts OBJECT-TYPE
   SYNTAX      Counter64
   MAX-ACCESS  read-only
   STATUS      current
   DESCRIPTION
      "Path: efm.performance.ifOutPriorityQueues.d7Performance.eirTxOctets

       64 bit unsigned wrappable counter."
   ::= {pr1646v2EfmOutQueuesD7PerformanceEntry 184549376}

pr1646v2EfmOutQueuesD7PerformanceViolTxOcts OBJECT-TYPE
   SYNTAX      Counter64
   MAX-ACCESS  read-only
   STATUS      current
   DESCRIPTION
      "Path: efm.performance.ifOutPriorityQueues.d7Performance.violateTxOctets

       64 bit unsigned wrappable counter."
   ::= {pr1646v2EfmOutQueuesD7PerformanceEntry 318767104}

pr1646v2EfmOutQueuesD7PerformanceBandwidth OBJECT-TYPE
   SYNTAX      Integer32
   MAX-ACCESS  read-only
   STATUS      current
   DESCRIPTION
      "Path: efm.performance.ifOutPriorityQueues.d7Performance.bandwidth

       unit name = bps
       formula = 8 * ; 8 /"
   ::= {pr1646v2EfmOutQueuesD7PerformanceEntry 268435456}


pr1646v2EfmOutBandwidth OBJECT IDENTIFIER ::= {pr1646v2Efm 182}

pr1646v2EfmOutBandwidthSSC OBJECT IDENTIFIER ::= {pr1646v2EfmOutBandwidth 1}

pr1646v2EfmOutBandwidthEntry OBJECT IDENTIFIER ::= {pr1646v2EfmOutBandwidthSSC 1}

pr1646v2EfmOutBandwidth15sec OBJECT-TYPE
   SYNTAX      Integer32
   MAX-ACCESS  read-only
   STATUS      current
   DESCRIPTION
      "Path: efm.performance.ifOutBandwidth.15sec

       unit name = bps
       formula = 8 * ; 8 /"
   ::= {pr1646v2EfmOutBandwidthEntry 83886080}

pr1646v2EfmOutBandwidth30sec OBJECT-TYPE
   SYNTAX      Integer32
   MAX-ACCESS  read-only
   STATUS      current
   DESCRIPTION
      "Path: efm.performance.ifOutBandwidth.30sec

       unit name = bps
       formula = 8 * ; 8 /"
   ::= {pr1646v2EfmOutBandwidthEntry 167772160}

pr1646v2EfmOutBandwidth1min OBJECT-TYPE
   SYNTAX      Integer32
   MAX-ACCESS  read-only
   STATUS      current
   DESCRIPTION
      "Path: efm.performance.ifOutBandwidth.1min

       unit name = bps
       formula = 8 * ; 8 /"
   ::= {pr1646v2EfmOutBandwidthEntry 335544320}

pr1646v2EfmOutBandwidth2min OBJECT-TYPE
   SYNTAX      Integer32
   MAX-ACCESS  read-only
   STATUS      current
   DESCRIPTION
      "Path: efm.performance.ifOutBandwidth.2min

       unit name = bps
       formula = 8 * ; 8 /"
   ::= {pr1646v2EfmOutBandwidthEntry 671088640}

pr1646v2EfmOutBandwidth5min OBJECT-TYPE
   SYNTAX      Integer32
   MAX-ACCESS  read-only
   STATUS      current
   DESCRIPTION
      "Path: efm.performance.ifOutBandwidth.5min

       unit name = bps
       formula = 8 * ; 8 /"
   ::= {pr1646v2EfmOutBandwidthEntry 1677721600}


pr1646v2EfmInP OBJECT IDENTIFIER ::= {pr1646v2Efm 307}

pr1646v2EfmInPSSCTable OBJECT-TYPE
   SYNTAX      SEQUENCE OF Pr1646v2EfmInPEntry
   MAX-ACCESS  not-accessible
   STATUS      current
   DESCRIPTION
      "h2IfInPerformance"
   ::= {pr1646v2EfmInP 1}

pr1646v2EfmInPEntry OBJECT-TYPE
   SYNTAX      Pr1646v2EfmInPEntry
   MAX-ACCESS  not-accessible
   STATUS      current
   DESCRIPTION
      ""
   INDEX      { pr1646v2EfmInPTableIx }
   ::= {pr1646v2EfmInPSSCTable 1}

Pr1646v2EfmInPEntry ::=
   SEQUENCE
      {
      pr1646v2EfmInPTableIx
         TableIndex,
      pr1646v2EfmInPSysUpTime
         TimeTicks,
      pr1646v2EfmInPIfUpTime
         TimeTicks,
      pr1646v2EfmInPIfStatChanges
         Counter32,
      pr1646v2EfmInPIfInOctets
         Counter64,
      pr1646v2EfmInPIfInUCPkts
         Counter64,
      pr1646v2EfmInPIfInNUCPkts
         Counter64,
      pr1646v2EfmInPIfInBCPkts
         Counter64,
      pr1646v2EfmInPIfInMCPkts
         Counter64,
      pr1646v2EfmInPIfInDiscards
         Counter64,
      pr1646v2EfmInPIfInErrors
         Counter64,
      pr1646v2EfmInPIfInUnkwn
         Counter64,
      pr1646v2EfmInPInDropEx
         Counter64,
      pr1646v2EfmInPInDropNoMac
         Counter64,
      pr1646v2EfmInPInDropNUCast
         Counter64,
      pr1646v2EfmInPInDropFilter
         Counter64,
      pr1646v2EfmInPIfInBandwidth
         Integer32,
      pr1646v2EfmInPIfOutOctets
         Counter64,
      pr1646v2EfmInPIfOutUCPkts
         Counter64,
      pr1646v2EfmInPIfOutNUCPkts
         Counter64,
      pr1646v2EfmInPIfOutBCPkts
         Counter64,
      pr1646v2EfmInPIfOutMCPkts
         Counter64,
      pr1646v2EfmInPIfOutDiscards
         Counter64,
      pr1646v2EfmInPIfOutErrors
         Counter64,
      pr1646v2EfmInPOutDropEx
         Counter64,
      pr1646v2EfmInPOutDropNoArp
         Counter64,
      pr1646v2EfmInPOutDropFilter
         Counter64,
      pr1646v2EfmInPIfOutBandwidth
         Integer32,
      pr1646v2EfmInPIfErrSec
         Counter32
      }

pr1646v2EfmInPTableIx OBJECT-TYPE
   SYNTAX      TableIndex
   MAX-ACCESS  not-accessible
   STATUS      current
   DESCRIPTION
      ""
   ::= {pr1646v2EfmInPEntry 11}

pr1646v2EfmInPSysUpTime OBJECT-TYPE
   SYNTAX      TimeTicks
   MAX-ACCESS  read-only
   STATUS      current
   DESCRIPTION
      "Path: efm.performance.h2Performance.sysUpTime

       Time in centi-second."
   ::= {pr1646v2EfmInPEntry 16777216}

pr1646v2EfmInPIfUpTime OBJECT-TYPE
   SYNTAX      TimeTicks
   MAX-ACCESS  read-only
   STATUS      current
   DESCRIPTION
      "Path: efm.performance.h2Performance.ifUpTime

       Time in centi-second."
   ::= {pr1646v2EfmInPEntry 33554432}

pr1646v2EfmInPIfStatChanges OBJECT-TYPE
   SYNTAX      Counter32
   MAX-ACCESS  read-only
   STATUS      current
   DESCRIPTION
      "Path: efm.performance.h2Performance.ifStatusChanges

       32 bit unsigned wrappable counter."
   ::= {pr1646v2EfmInPEntry 50331648}

pr1646v2EfmInPIfInOctets OBJECT-TYPE
   SYNTAX      Counter64
   MAX-ACCESS  read-only
   STATUS      current
   DESCRIPTION
      "Path: efm.performance.h2Performance.ifInOctets

       64 bit unsigned wrappable counter."
   ::= {pr1646v2EfmInPEntry 67108864}

pr1646v2EfmInPIfInUCPkts OBJECT-TYPE
   SYNTAX      Counter64
   MAX-ACCESS  read-only
   STATUS      current
   DESCRIPTION
      "Path: efm.performance.h2Performance.ifInUcastPkts

       64 bit unsigned wrappable counter."
   ::= {pr1646v2EfmInPEntry 83886080}

pr1646v2EfmInPIfInNUCPkts OBJECT-TYPE
   SYNTAX      Counter64
   MAX-ACCESS  read-only
   STATUS      current
   DESCRIPTION
      "Path: efm.performance.h2Performance.ifInNUcastPkts

       64 bit unsigned wrappable counter."
   ::= {pr1646v2EfmInPEntry 100663296}

pr1646v2EfmInPIfInBCPkts OBJECT-TYPE
   SYNTAX      Counter64
   MAX-ACCESS  read-only
   STATUS      current
   DESCRIPTION
      "Path: efm.performance.h2Performance.ifInBcastPkts

       64 bit unsigned wrappable counter."
   ::= {pr1646v2EfmInPEntry 419430400}

pr1646v2EfmInPIfInMCPkts OBJECT-TYPE
   SYNTAX      Counter64
   MAX-ACCESS  read-only
   STATUS      current
   DESCRIPTION
      "Path: efm.performance.h2Performance.ifInMcastPkts

       64 bit unsigned wrappable counter."
   ::= {pr1646v2EfmInPEntry 436207616}

pr1646v2EfmInPIfInDiscards OBJECT-TYPE
   SYNTAX      Counter64
   MAX-ACCESS  read-only
   STATUS      current
   DESCRIPTION
      "Path: efm.performance.h2Performance.ifInDiscards

       64 bit unsigned wrappable counter."
   ::= {pr1646v2EfmInPEntry 117440512}

pr1646v2EfmInPIfInErrors OBJECT-TYPE
   SYNTAX      Counter64
   MAX-ACCESS  read-only
   STATUS      current
   DESCRIPTION
      "Path: efm.performance.h2Performance.ifInErrors

       64 bit unsigned wrappable counter."
   ::= {pr1646v2EfmInPEntry 134217728}

pr1646v2EfmInPIfInUnkwn OBJECT-TYPE
   SYNTAX      Counter64
   MAX-ACCESS  read-only
   STATUS      current
   DESCRIPTION
      "Path: efm.performance.h2Performance.ifInUnknownProtos

       64 bit unsigned wrappable counter."
   ::= {pr1646v2EfmInPEntry 150994944}

pr1646v2EfmInPInDropEx OBJECT-TYPE
   SYNTAX      Counter64
   MAX-ACCESS  read-only
   STATUS      current
   DESCRIPTION
      "Path: efm.performance.h2Performance.ifInDropLevelExceeded

       64 bit unsigned wrappable counter."
   ::= {pr1646v2EfmInPEntry 335544320}

pr1646v2EfmInPInDropNoMac OBJECT-TYPE
   SYNTAX      Counter64
   MAX-ACCESS  read-only
   STATUS      current
   DESCRIPTION
      "Path: efm.performance.h2Performance.fInDiscardsNoMacFit

       64 bit unsigned wrappable counter."
   ::= {pr1646v2EfmInPEntry 301989888}

pr1646v2EfmInPInDropNUCast OBJECT-TYPE
   SYNTAX      Counter64
   MAX-ACCESS  read-only
   STATUS      current
   DESCRIPTION
      "Path: efm.performance.h2Performance.fInDiscardsNUCast

       64 bit unsigned wrappable counter."
   ::= {pr1646v2EfmInPEntry 318767104}

pr1646v2EfmInPInDropFilter OBJECT-TYPE
   SYNTAX      Counter64
   MAX-ACCESS  read-only
   STATUS      current
   DESCRIPTION
      "Path: efm.performance.h2Performance.fInDiscardsFilter

       64 bit unsigned wrappable counter."
   ::= {pr1646v2EfmInPEntry 385875968}

pr1646v2EfmInPIfInBandwidth OBJECT-TYPE
   SYNTAX      Integer32
   MAX-ACCESS  read-only
   STATUS      current
   DESCRIPTION
      "Path: efm.performance.h2Performance.ifInBandwidth

       unit name = bps
       formula = 8 * ; 8 /"
   ::= {pr1646v2EfmInPEntry 268435456}

pr1646v2EfmInPIfOutOctets OBJECT-TYPE
   SYNTAX      Counter64
   MAX-ACCESS  read-only
   STATUS      current
   DESCRIPTION
      "Path: efm.performance.h2Performance.ifOutOctets

       64 bit unsigned wrappable counter."
   ::= {pr1646v2EfmInPEntry 167772160}

pr1646v2EfmInPIfOutUCPkts OBJECT-TYPE
   SYNTAX      Counter64
   MAX-ACCESS  read-only
   STATUS      current
   DESCRIPTION
      "Path: efm.performance.h2Performance.ifOutUcastPkts

       64 bit unsigned wrappable counter."
   ::= {pr1646v2EfmInPEntry 184549376}

pr1646v2EfmInPIfOutNUCPkts OBJECT-TYPE
   SYNTAX      Counter64
   MAX-ACCESS  read-only
   STATUS      current
   DESCRIPTION
      "Path: efm.performance.h2Performance.ifOutNUcastPkts

       64 bit unsigned wrappable counter."
   ::= {pr1646v2EfmInPEntry 201326592}

pr1646v2EfmInPIfOutBCPkts OBJECT-TYPE
   SYNTAX      Counter64
   MAX-ACCESS  read-only
   STATUS      current
   DESCRIPTION
      "Path: efm.performance.h2Performance.ifOutBcastPkts

       64 bit unsigned wrappable counter."
   ::= {pr1646v2EfmInPEntry 452984832}

pr1646v2EfmInPIfOutMCPkts OBJECT-TYPE
   SYNTAX      Counter64
   MAX-ACCESS  read-only
   STATUS      current
   DESCRIPTION
      "Path: efm.performance.h2Performance.ifOutMcastPkts

       64 bit unsigned wrappable counter."
   ::= {pr1646v2EfmInPEntry 469762048}

pr1646v2EfmInPIfOutDiscards OBJECT-TYPE
   SYNTAX      Counter64
   MAX-ACCESS  read-only
   STATUS      current
   DESCRIPTION
      "Path: efm.performance.h2Performance.ifOutDiscards

       64 bit unsigned wrappable counter."
   ::= {pr1646v2EfmInPEntry 218103808}

pr1646v2EfmInPIfOutErrors OBJECT-TYPE
   SYNTAX      Counter64
   MAX-ACCESS  read-only
   STATUS      current
   DESCRIPTION
      "Path: efm.performance.h2Performance.ifOutErrors

       64 bit unsigned wrappable counter."
   ::= {pr1646v2EfmInPEntry 234881024}

pr1646v2EfmInPOutDropEx OBJECT-TYPE
   SYNTAX      Counter64
   MAX-ACCESS  read-only
   STATUS      current
   DESCRIPTION
      "Path: efm.performance.h2Performance.ifOutDropLevelExceeded

       64 bit unsigned wrappable counter."
   ::= {pr1646v2EfmInPEntry 352321536}

pr1646v2EfmInPOutDropNoArp OBJECT-TYPE
   SYNTAX      Counter64
   MAX-ACCESS  read-only
   STATUS      current
   DESCRIPTION
      "Path: efm.performance.h2Performance.ifOutDiscardsNoArp

       64 bit unsigned wrappable counter."
   ::= {pr1646v2EfmInPEntry 369098752}

pr1646v2EfmInPOutDropFilter OBJECT-TYPE
   SYNTAX      Counter64
   MAX-ACCESS  read-only
   STATUS      current
   DESCRIPTION
      "Path: efm.performance.h2Performance.ifOutDiscardsFilter

       64 bit unsigned wrappable counter."
   ::= {pr1646v2EfmInPEntry 402653184}

pr1646v2EfmInPIfOutBandwidth OBJECT-TYPE
   SYNTAX      Integer32
   MAX-ACCESS  read-only
   STATUS      current
   DESCRIPTION
      "Path: efm.performance.h2Performance.ifOutBandwidth

       unit name = bps
       formula = 8 * ; 8 /"
   ::= {pr1646v2EfmInPEntry 285212672}

pr1646v2EfmInPIfErrSec OBJECT-TYPE
   SYNTAX      Counter32
   MAX-ACCESS  read-only
   STATUS      current
   DESCRIPTION
      "Path: efm.performance.h2Performance.ifErrSec

       32 bit unsigned wrappable counter."
   ::= {pr1646v2EfmInPEntry 251658240}


pr1646v2EfmH24InP OBJECT IDENTIFIER ::= {pr1646v2Efm 308}

pr1646v2EfmH24InPSSCTable OBJECT-TYPE
   SYNTAX      SEQUENCE OF Pr1646v2EfmH24InPEntry
   MAX-ACCESS  not-accessible
   STATUS      current
   DESCRIPTION
      "h24IfInPerformance"
   ::= {pr1646v2EfmH24InP 1}

pr1646v2EfmH24InPEntry OBJECT-TYPE
   SYNTAX      Pr1646v2EfmH24InPEntry
   MAX-ACCESS  not-accessible
   STATUS      current
   DESCRIPTION
      ""
   INDEX      { pr1646v2EfmH24InPTableIx }
   ::= {pr1646v2EfmH24InPSSCTable 1}

Pr1646v2EfmH24InPEntry ::=
   SEQUENCE
      {
      pr1646v2EfmH24InPTableIx
         TableIndex,
      pr1646v2EfmH24InPSysUpTime
         TimeTicks,
      pr1646v2EfmH24InPIfUpTime
         TimeTicks,
      pr1646v2EfmH24InPIfStatChanges
         Counter32,
      pr1646v2EfmH24InPIfInOctets
         Counter64,
      pr1646v2EfmH24InPIfInUCPkts
         Counter64,
      pr1646v2EfmH24InPIfInNUCPkts
         Counter64,
      pr1646v2EfmH24InPIfInBCPkts
         Counter64,
      pr1646v2EfmH24InPIfInMCPkts
         Counter64,
      pr1646v2EfmH24InPIfInDiscards
         Counter64,
      pr1646v2EfmH24InPIfInErrors
         Counter64,
      pr1646v2EfmH24InPIfInUnkwn
         Counter64,
      pr1646v2EfmH24InPInDropEx
         Counter64,
      pr1646v2EfmH24InPInDropNoMac
         Counter64,
      pr1646v2EfmH24InPInDropNUCast
         Counter64,
      pr1646v2EfmH24InPInDropFilter
         Counter64,
      pr1646v2EfmH24InPIfInBandwidth
         Integer32,
      pr1646v2EfmH24InPIfOutOctets
         Counter64,
      pr1646v2EfmH24InPIfOutUCPkts
         Counter64,
      pr1646v2EfmH24InPIfOutNUCPkts
         Counter64,
      pr1646v2EfmH24InPIfOutBCPkts
         Counter64,
      pr1646v2EfmH24InPIfOutMCPkts
         Counter64,
      pr1646v2EfmH24InPIfOutDiscards
         Counter64,
      pr1646v2EfmH24InPIfOutErrors
         Counter64,
      pr1646v2EfmH24InPOutDropEx
         Counter64,
      pr1646v2EfmH24InPOutDropNoArp
         Counter64,
      pr1646v2EfmH24InPOutDropFilter
         Counter64,
      pr1646v2EfmH24InPIfOutBandwidth
         Integer32,
      pr1646v2EfmH24InPIfErrSec
         Counter32
      }

pr1646v2EfmH24InPTableIx OBJECT-TYPE
   SYNTAX      TableIndex
   MAX-ACCESS  not-accessible
   STATUS      current
   DESCRIPTION
      ""
   ::= {pr1646v2EfmH24InPEntry 11}

pr1646v2EfmH24InPSysUpTime OBJECT-TYPE
   SYNTAX      TimeTicks
   MAX-ACCESS  read-only
   STATUS      current
   DESCRIPTION
      "Path: efm.performance.h24Performance.sysUpTime

       Time in centi-second."
   ::= {pr1646v2EfmH24InPEntry 16777216}

pr1646v2EfmH24InPIfUpTime OBJECT-TYPE
   SYNTAX      TimeTicks
   MAX-ACCESS  read-only
   STATUS      current
   DESCRIPTION
      "Path: efm.performance.h24Performance.ifUpTime

       Time in centi-second."
   ::= {pr1646v2EfmH24InPEntry 33554432}

pr1646v2EfmH24InPIfStatChanges OBJECT-TYPE
   SYNTAX      Counter32
   MAX-ACCESS  read-only
   STATUS      current
   DESCRIPTION
      "Path: efm.performance.h24Performance.ifStatusChanges

       32 bit unsigned wrappable counter."
   ::= {pr1646v2EfmH24InPEntry 50331648}

pr1646v2EfmH24InPIfInOctets OBJECT-TYPE
   SYNTAX      Counter64
   MAX-ACCESS  read-only
   STATUS      current
   DESCRIPTION
      "Path: efm.performance.h24Performance.ifInOctets

       64 bit unsigned wrappable counter."
   ::= {pr1646v2EfmH24InPEntry 67108864}

pr1646v2EfmH24InPIfInUCPkts OBJECT-TYPE
   SYNTAX      Counter64
   MAX-ACCESS  read-only
   STATUS      current
   DESCRIPTION
      "Path: efm.performance.h24Performance.ifInUcastPkts

       64 bit unsigned wrappable counter."
   ::= {pr1646v2EfmH24InPEntry 83886080}

pr1646v2EfmH24InPIfInNUCPkts OBJECT-TYPE
   SYNTAX      Counter64
   MAX-ACCESS  read-only
   STATUS      current
   DESCRIPTION
      "Path: efm.performance.h24Performance.ifInNUcastPkts

       64 bit unsigned wrappable counter."
   ::= {pr1646v2EfmH24InPEntry 100663296}

pr1646v2EfmH24InPIfInBCPkts OBJECT-TYPE
   SYNTAX      Counter64
   MAX-ACCESS  read-only
   STATUS      current
   DESCRIPTION
      "Path: efm.performance.h24Performance.ifInBcastPkts

       64 bit unsigned wrappable counter."
   ::= {pr1646v2EfmH24InPEntry 419430400}

pr1646v2EfmH24InPIfInMCPkts OBJECT-TYPE
   SYNTAX      Counter64
   MAX-ACCESS  read-only
   STATUS      current
   DESCRIPTION
      "Path: efm.performance.h24Performance.ifInMcastPkts

       64 bit unsigned wrappable counter."
   ::= {pr1646v2EfmH24InPEntry 436207616}

pr1646v2EfmH24InPIfInDiscards OBJECT-TYPE
   SYNTAX      Counter64
   MAX-ACCESS  read-only
   STATUS      current
   DESCRIPTION
      "Path: efm.performance.h24Performance.ifInDiscards

       64 bit unsigned wrappable counter."
   ::= {pr1646v2EfmH24InPEntry 117440512}

pr1646v2EfmH24InPIfInErrors OBJECT-TYPE
   SYNTAX      Counter64
   MAX-ACCESS  read-only
   STATUS      current
   DESCRIPTION
      "Path: efm.performance.h24Performance.ifInErrors

       64 bit unsigned wrappable counter."
   ::= {pr1646v2EfmH24InPEntry 134217728}

pr1646v2EfmH24InPIfInUnkwn OBJECT-TYPE
   SYNTAX      Counter64
   MAX-ACCESS  read-only
   STATUS      current
   DESCRIPTION
      "Path: efm.performance.h24Performance.ifInUnknownProtos

       64 bit unsigned wrappable counter."
   ::= {pr1646v2EfmH24InPEntry 150994944}

pr1646v2EfmH24InPInDropEx OBJECT-TYPE
   SYNTAX      Counter64
   MAX-ACCESS  read-only
   STATUS      current
   DESCRIPTION
      "Path: efm.performance.h24Performance.ifInDropLevelExceeded

       64 bit unsigned wrappable counter."
   ::= {pr1646v2EfmH24InPEntry 335544320}

pr1646v2EfmH24InPInDropNoMac OBJECT-TYPE
   SYNTAX      Counter64
   MAX-ACCESS  read-only
   STATUS      current
   DESCRIPTION
      "Path: efm.performance.h24Performance.fInDiscardsNoMacFit

       64 bit unsigned wrappable counter."
   ::= {pr1646v2EfmH24InPEntry 301989888}

pr1646v2EfmH24InPInDropNUCast OBJECT-TYPE
   SYNTAX      Counter64
   MAX-ACCESS  read-only
   STATUS      current
   DESCRIPTION
      "Path: efm.performance.h24Performance.fInDiscardsNUCast

       64 bit unsigned wrappable counter."
   ::= {pr1646v2EfmH24InPEntry 318767104}

pr1646v2EfmH24InPInDropFilter OBJECT-TYPE
   SYNTAX      Counter64
   MAX-ACCESS  read-only
   STATUS      current
   DESCRIPTION
      "Path: efm.performance.h24Performance.fInDiscardsFilter

       64 bit unsigned wrappable counter."
   ::= {pr1646v2EfmH24InPEntry 385875968}

pr1646v2EfmH24InPIfInBandwidth OBJECT-TYPE
   SYNTAX      Integer32
   MAX-ACCESS  read-only
   STATUS      current
   DESCRIPTION
      "Path: efm.performance.h24Performance.ifInBandwidth

       unit name = bps
       formula = 8 * ; 8 /"
   ::= {pr1646v2EfmH24InPEntry 268435456}

pr1646v2EfmH24InPIfOutOctets OBJECT-TYPE
   SYNTAX      Counter64
   MAX-ACCESS  read-only
   STATUS      current
   DESCRIPTION
      "Path: efm.performance.h24Performance.ifOutOctets

       64 bit unsigned wrappable counter."
   ::= {pr1646v2EfmH24InPEntry 167772160}

pr1646v2EfmH24InPIfOutUCPkts OBJECT-TYPE
   SYNTAX      Counter64
   MAX-ACCESS  read-only
   STATUS      current
   DESCRIPTION
      "Path: efm.performance.h24Performance.ifOutUcastPkts

       64 bit unsigned wrappable counter."
   ::= {pr1646v2EfmH24InPEntry 184549376}

pr1646v2EfmH24InPIfOutNUCPkts OBJECT-TYPE
   SYNTAX      Counter64
   MAX-ACCESS  read-only
   STATUS      current
   DESCRIPTION
      "Path: efm.performance.h24Performance.ifOutNUcastPkts

       64 bit unsigned wrappable counter."
   ::= {pr1646v2EfmH24InPEntry 201326592}

pr1646v2EfmH24InPIfOutBCPkts OBJECT-TYPE
   SYNTAX      Counter64
   MAX-ACCESS  read-only
   STATUS      current
   DESCRIPTION
      "Path: efm.performance.h24Performance.ifOutBcastPkts

       64 bit unsigned wrappable counter."
   ::= {pr1646v2EfmH24InPEntry 452984832}

pr1646v2EfmH24InPIfOutMCPkts OBJECT-TYPE
   SYNTAX      Counter64
   MAX-ACCESS  read-only
   STATUS      current
   DESCRIPTION
      "Path: efm.performance.h24Performance.ifOutMcastPkts

       64 bit unsigned wrappable counter."
   ::= {pr1646v2EfmH24InPEntry 469762048}

pr1646v2EfmH24InPIfOutDiscards OBJECT-TYPE
   SYNTAX      Counter64
   MAX-ACCESS  read-only
   STATUS      current
   DESCRIPTION
      "Path: efm.performance.h24Performance.ifOutDiscards

       64 bit unsigned wrappable counter."
   ::= {pr1646v2EfmH24InPEntry 218103808}

pr1646v2EfmH24InPIfOutErrors OBJECT-TYPE
   SYNTAX      Counter64
   MAX-ACCESS  read-only
   STATUS      current
   DESCRIPTION
      "Path: efm.performance.h24Performance.ifOutErrors

       64 bit unsigned wrappable counter."
   ::= {pr1646v2EfmH24InPEntry 234881024}

pr1646v2EfmH24InPOutDropEx OBJECT-TYPE
   SYNTAX      Counter64
   MAX-ACCESS  read-only
   STATUS      current
   DESCRIPTION
      "Path: efm.performance.h24Performance.ifOutDropLevelExceeded

       64 bit unsigned wrappable counter."
   ::= {pr1646v2EfmH24InPEntry 352321536}

pr1646v2EfmH24InPOutDropNoArp OBJECT-TYPE
   SYNTAX      Counter64
   MAX-ACCESS  read-only
   STATUS      current
   DESCRIPTION
      "Path: efm.performance.h24Performance.ifOutDiscardsNoArp

       64 bit unsigned wrappable counter."
   ::= {pr1646v2EfmH24InPEntry 369098752}

pr1646v2EfmH24InPOutDropFilter OBJECT-TYPE
   SYNTAX      Counter64
   MAX-ACCESS  read-only
   STATUS      current
   DESCRIPTION
      "Path: efm.performance.h24Performance.ifOutDiscardsFilter

       64 bit unsigned wrappable counter."
   ::= {pr1646v2EfmH24InPEntry 402653184}

pr1646v2EfmH24InPIfOutBandwidth OBJECT-TYPE
   SYNTAX      Integer32
   MAX-ACCESS  read-only
   STATUS      current
   DESCRIPTION
      "Path: efm.performance.h24Performance.ifOutBandwidth

       unit name = bps
       formula = 8 * ; 8 /"
   ::= {pr1646v2EfmH24InPEntry 285212672}

pr1646v2EfmH24InPIfErrSec OBJECT-TYPE
   SYNTAX      Counter32
   MAX-ACCESS  read-only
   STATUS      current
   DESCRIPTION
      "Path: efm.performance.h24Performance.ifErrSec

       32 bit unsigned wrappable counter."
   ::= {pr1646v2EfmH24InPEntry 251658240}


pr1646v2EfmD7InP OBJECT IDENTIFIER ::= {pr1646v2Efm 309}

pr1646v2EfmD7InPSSCTable OBJECT-TYPE
   SYNTAX      SEQUENCE OF Pr1646v2EfmD7InPEntry
   MAX-ACCESS  not-accessible
   STATUS      current
   DESCRIPTION
      "d7IfInPerformance"
   ::= {pr1646v2EfmD7InP 1}

pr1646v2EfmD7InPEntry OBJECT-TYPE
   SYNTAX      Pr1646v2EfmD7InPEntry
   MAX-ACCESS  not-accessible
   STATUS      current
   DESCRIPTION
      ""
   INDEX      { pr1646v2EfmD7InPTableIx }
   ::= {pr1646v2EfmD7InPSSCTable 1}

Pr1646v2EfmD7InPEntry ::=
   SEQUENCE
      {
      pr1646v2EfmD7InPTableIx
         TableIndex,
      pr1646v2EfmD7InPSysUpTime
         TimeTicks,
      pr1646v2EfmD7InPIfUpTime
         TimeTicks,
      pr1646v2EfmD7InPIfStatChanges
         Counter32,
      pr1646v2EfmD7InPIfInOctets
         Counter64,
      pr1646v2EfmD7InPIfInUCPkts
         Counter64,
      pr1646v2EfmD7InPIfInNUCPkts
         Counter64,
      pr1646v2EfmD7InPIfInBCPkts
         Counter64,
      pr1646v2EfmD7InPIfInMCPkts
         Counter64,
      pr1646v2EfmD7InPIfInDiscards
         Counter64,
      pr1646v2EfmD7InPIfInErrors
         Counter64,
      pr1646v2EfmD7InPIfInUnkwn
         Counter64,
      pr1646v2EfmD7InPInDropEx
         Counter64,
      pr1646v2EfmD7InPInDropNoMac
         Counter64,
      pr1646v2EfmD7InPInDropNUCast
         Counter64,
      pr1646v2EfmD7InPInDropFilter
         Counter64,
      pr1646v2EfmD7InPIfInBandwidth
         Integer32,
      pr1646v2EfmD7InPIfOutOctets
         Counter64,
      pr1646v2EfmD7InPIfOutUCPkts
         Counter64,
      pr1646v2EfmD7InPIfOutNUCPkts
         Counter64,
      pr1646v2EfmD7InPIfOutBCPkts
         Counter64,
      pr1646v2EfmD7InPIfOutMCPkts
         Counter64,
      pr1646v2EfmD7InPIfOutDiscards
         Counter64,
      pr1646v2EfmD7InPIfOutErrors
         Counter64,
      pr1646v2EfmD7InPOutDropEx
         Counter64,
      pr1646v2EfmD7InPOutDropNoArp
         Counter64,
      pr1646v2EfmD7InPOutDropFilter
         Counter64,
      pr1646v2EfmD7InPIfOutBandwidth
         Integer32,
      pr1646v2EfmD7InPIfErrSec
         Counter32
      }

pr1646v2EfmD7InPTableIx OBJECT-TYPE
   SYNTAX      TableIndex
   MAX-ACCESS  not-accessible
   STATUS      current
   DESCRIPTION
      ""
   ::= {pr1646v2EfmD7InPEntry 11}

pr1646v2EfmD7InPSysUpTime OBJECT-TYPE
   SYNTAX      TimeTicks
   MAX-ACCESS  read-only
   STATUS      current
   DESCRIPTION
      "Path: efm.performance.d7Performance.sysUpTime

       Time in centi-second."
   ::= {pr1646v2EfmD7InPEntry 16777216}

pr1646v2EfmD7InPIfUpTime OBJECT-TYPE
   SYNTAX      TimeTicks
   MAX-ACCESS  read-only
   STATUS      current
   DESCRIPTION
      "Path: efm.performance.d7Performance.ifUpTime

       Time in centi-second."
   ::= {pr1646v2EfmD7InPEntry 33554432}

pr1646v2EfmD7InPIfStatChanges OBJECT-TYPE
   SYNTAX      Counter32
   MAX-ACCESS  read-only
   STATUS      current
   DESCRIPTION
      "Path: efm.performance.d7Performance.ifStatusChanges

       32 bit unsigned wrappable counter."
   ::= {pr1646v2EfmD7InPEntry 50331648}

pr1646v2EfmD7InPIfInOctets OBJECT-TYPE
   SYNTAX      Counter64
   MAX-ACCESS  read-only
   STATUS      current
   DESCRIPTION
      "Path: efm.performance.d7Performance.ifInOctets

       64 bit unsigned wrappable counter."
   ::= {pr1646v2EfmD7InPEntry 67108864}

pr1646v2EfmD7InPIfInUCPkts OBJECT-TYPE
   SYNTAX      Counter64
   MAX-ACCESS  read-only
   STATUS      current
   DESCRIPTION
      "Path: efm.performance.d7Performance.ifInUcastPkts

       64 bit unsigned wrappable counter."
   ::= {pr1646v2EfmD7InPEntry 83886080}

pr1646v2EfmD7InPIfInNUCPkts OBJECT-TYPE
   SYNTAX      Counter64
   MAX-ACCESS  read-only
   STATUS      current
   DESCRIPTION
      "Path: efm.performance.d7Performance.ifInNUcastPkts

       64 bit unsigned wrappable counter."
   ::= {pr1646v2EfmD7InPEntry 100663296}

pr1646v2EfmD7InPIfInBCPkts OBJECT-TYPE
   SYNTAX      Counter64
   MAX-ACCESS  read-only
   STATUS      current
   DESCRIPTION
      "Path: efm.performance.d7Performance.ifInBcastPkts

       64 bit unsigned wrappable counter."
   ::= {pr1646v2EfmD7InPEntry 419430400}

pr1646v2EfmD7InPIfInMCPkts OBJECT-TYPE
   SYNTAX      Counter64
   MAX-ACCESS  read-only
   STATUS      current
   DESCRIPTION
      "Path: efm.performance.d7Performance.ifInMcastPkts

       64 bit unsigned wrappable counter."
   ::= {pr1646v2EfmD7InPEntry 436207616}

pr1646v2EfmD7InPIfInDiscards OBJECT-TYPE
   SYNTAX      Counter64
   MAX-ACCESS  read-only
   STATUS      current
   DESCRIPTION
      "Path: efm.performance.d7Performance.ifInDiscards

       64 bit unsigned wrappable counter."
   ::= {pr1646v2EfmD7InPEntry 117440512}

pr1646v2EfmD7InPIfInErrors OBJECT-TYPE
   SYNTAX      Counter64
   MAX-ACCESS  read-only
   STATUS      current
   DESCRIPTION
      "Path: efm.performance.d7Performance.ifInErrors

       64 bit unsigned wrappable counter."
   ::= {pr1646v2EfmD7InPEntry 134217728}

pr1646v2EfmD7InPIfInUnkwn OBJECT-TYPE
   SYNTAX      Counter64
   MAX-ACCESS  read-only
   STATUS      current
   DESCRIPTION
      "Path: efm.performance.d7Performance.ifInUnknownProtos

       64 bit unsigned wrappable counter."
   ::= {pr1646v2EfmD7InPEntry 150994944}

pr1646v2EfmD7InPInDropEx OBJECT-TYPE
   SYNTAX      Counter64
   MAX-ACCESS  read-only
   STATUS      current
   DESCRIPTION
      "Path: efm.performance.d7Performance.ifInDropLevelExceeded

       64 bit unsigned wrappable counter."
   ::= {pr1646v2EfmD7InPEntry 335544320}

pr1646v2EfmD7InPInDropNoMac OBJECT-TYPE
   SYNTAX      Counter64
   MAX-ACCESS  read-only
   STATUS      current
   DESCRIPTION
      "Path: efm.performance.d7Performance.fInDiscardsNoMacFit

       64 bit unsigned wrappable counter."
   ::= {pr1646v2EfmD7InPEntry 301989888}

pr1646v2EfmD7InPInDropNUCast OBJECT-TYPE
   SYNTAX      Counter64
   MAX-ACCESS  read-only
   STATUS      current
   DESCRIPTION
      "Path: efm.performance.d7Performance.fInDiscardsNUCast

       64 bit unsigned wrappable counter."
   ::= {pr1646v2EfmD7InPEntry 318767104}

pr1646v2EfmD7InPInDropFilter OBJECT-TYPE
   SYNTAX      Counter64
   MAX-ACCESS  read-only
   STATUS      current
   DESCRIPTION
      "Path: efm.performance.d7Performance.fInDiscardsFilter

       64 bit unsigned wrappable counter."
   ::= {pr1646v2EfmD7InPEntry 385875968}

pr1646v2EfmD7InPIfInBandwidth OBJECT-TYPE
   SYNTAX      Integer32
   MAX-ACCESS  read-only
   STATUS      current
   DESCRIPTION
      "Path: efm.performance.d7Performance.ifInBandwidth

       unit name = bps
       formula = 8 * ; 8 /"
   ::= {pr1646v2EfmD7InPEntry 268435456}

pr1646v2EfmD7InPIfOutOctets OBJECT-TYPE
   SYNTAX      Counter64
   MAX-ACCESS  read-only
   STATUS      current
   DESCRIPTION
      "Path: efm.performance.d7Performance.ifOutOctets

       64 bit unsigned wrappable counter."
   ::= {pr1646v2EfmD7InPEntry 167772160}

pr1646v2EfmD7InPIfOutUCPkts OBJECT-TYPE
   SYNTAX      Counter64
   MAX-ACCESS  read-only
   STATUS      current
   DESCRIPTION
      "Path: efm.performance.d7Performance.ifOutUcastPkts

       64 bit unsigned wrappable counter."
   ::= {pr1646v2EfmD7InPEntry 184549376}

pr1646v2EfmD7InPIfOutNUCPkts OBJECT-TYPE
   SYNTAX      Counter64
   MAX-ACCESS  read-only
   STATUS      current
   DESCRIPTION
      "Path: efm.performance.d7Performance.ifOutNUcastPkts

       64 bit unsigned wrappable counter."
   ::= {pr1646v2EfmD7InPEntry 201326592}

pr1646v2EfmD7InPIfOutBCPkts OBJECT-TYPE
   SYNTAX      Counter64
   MAX-ACCESS  read-only
   STATUS      current
   DESCRIPTION
      "Path: efm.performance.d7Performance.ifOutBcastPkts

       64 bit unsigned wrappable counter."
   ::= {pr1646v2EfmD7InPEntry 452984832}

pr1646v2EfmD7InPIfOutMCPkts OBJECT-TYPE
   SYNTAX      Counter64
   MAX-ACCESS  read-only
   STATUS      current
   DESCRIPTION
      "Path: efm.performance.d7Performance.ifOutMcastPkts

       64 bit unsigned wrappable counter."
   ::= {pr1646v2EfmD7InPEntry 469762048}

pr1646v2EfmD7InPIfOutDiscards OBJECT-TYPE
   SYNTAX      Counter64
   MAX-ACCESS  read-only
   STATUS      current
   DESCRIPTION
      "Path: efm.performance.d7Performance.ifOutDiscards

       64 bit unsigned wrappable counter."
   ::= {pr1646v2EfmD7InPEntry 218103808}

pr1646v2EfmD7InPIfOutErrors OBJECT-TYPE
   SYNTAX      Counter64
   MAX-ACCESS  read-only
   STATUS      current
   DESCRIPTION
      "Path: efm.performance.d7Performance.ifOutErrors

       64 bit unsigned wrappable counter."
   ::= {pr1646v2EfmD7InPEntry 234881024}

pr1646v2EfmD7InPOutDropEx OBJECT-TYPE
   SYNTAX      Counter64
   MAX-ACCESS  read-only
   STATUS      current
   DESCRIPTION
      "Path: efm.performance.d7Performance.ifOutDropLevelExceeded

       64 bit unsigned wrappable counter."
   ::= {pr1646v2EfmD7InPEntry 352321536}

pr1646v2EfmD7InPOutDropNoArp OBJECT-TYPE
   SYNTAX      Counter64
   MAX-ACCESS  read-only
   STATUS      current
   DESCRIPTION
      "Path: efm.performance.d7Performance.ifOutDiscardsNoArp

       64 bit unsigned wrappable counter."
   ::= {pr1646v2EfmD7InPEntry 369098752}

pr1646v2EfmD7InPOutDropFilter OBJECT-TYPE
   SYNTAX      Counter64
   MAX-ACCESS  read-only
   STATUS      current
   DESCRIPTION
      "Path: efm.performance.d7Performance.ifOutDiscardsFilter

       64 bit unsigned wrappable counter."
   ::= {pr1646v2EfmD7InPEntry 402653184}

pr1646v2EfmD7InPIfOutBandwidth OBJECT-TYPE
   SYNTAX      Integer32
   MAX-ACCESS  read-only
   STATUS      current
   DESCRIPTION
      "Path: efm.performance.d7Performance.ifOutBandwidth

       unit name = bps
       formula = 8 * ; 8 /"
   ::= {pr1646v2EfmD7InPEntry 285212672}

pr1646v2EfmD7InPIfErrSec OBJECT-TYPE
   SYNTAX      Counter32
   MAX-ACCESS  read-only
   STATUS      current
   DESCRIPTION
      "Path: efm.performance.d7Performance.ifErrSec

       32 bit unsigned wrappable counter."
   ::= {pr1646v2EfmD7InPEntry 251658240}


pr1646v2EfmOam OBJECT IDENTIFIER ::= {pr1646v2Efm 910}

pr1646v2EfmOamSSC OBJECT IDENTIFIER ::= {pr1646v2EfmOam 1}

pr1646v2EfmOamEntry OBJECT IDENTIFIER ::= {pr1646v2EfmOamSSC 1}

pr1646v2EfmOamInformationTx OBJECT-TYPE
   SYNTAX      Counter32
   MAX-ACCESS  read-only
   STATUS      current
   DESCRIPTION
      "Path: efm.performance.oam.informationTx

       32 bit unsigned wrappable counter."
   ::= {pr1646v2EfmOamEntry 16777216}

pr1646v2EfmOamInformationRx OBJECT-TYPE
   SYNTAX      Counter32
   MAX-ACCESS  read-only
   STATUS      current
   DESCRIPTION
      "Path: efm.performance.oam.informationRx

       32 bit unsigned wrappable counter."
   ::= {pr1646v2EfmOamEntry 33554432}

pr1646v2EfmOamUniqueEventNotifTx OBJECT-TYPE
   SYNTAX      Counter32
   MAX-ACCESS  read-only
   STATUS      current
   DESCRIPTION
      "Path: efm.performance.oam.uniqueEventNotifTx

       32 bit unsigned wrappable counter."
   ::= {pr1646v2EfmOamEntry 50331648}

pr1646v2EfmOamUniqueEventNotifRx OBJECT-TYPE
   SYNTAX      Counter32
   MAX-ACCESS  read-only
   STATUS      current
   DESCRIPTION
      "Path: efm.performance.oam.uniqueEventNotifRx

       32 bit unsigned wrappable counter."
   ::= {pr1646v2EfmOamEntry 67108864}

pr1646v2EfmOamLoopbackCtrlTx OBJECT-TYPE
   SYNTAX      Counter32
   MAX-ACCESS  read-only
   STATUS      current
   DESCRIPTION
      "Path: efm.performance.oam.loopbackCtrlTx

       32 bit unsigned wrappable counter."
   ::= {pr1646v2EfmOamEntry 117440512}

pr1646v2EfmOamLoopbackCtrlRx OBJECT-TYPE
   SYNTAX      Counter32
   MAX-ACCESS  read-only
   STATUS      current
   DESCRIPTION
      "Path: efm.performance.oam.loopbackCtrlRx

       32 bit unsigned wrappable counter."
   ::= {pr1646v2EfmOamEntry 134217728}

pr1646v2EfmOamVarReqTx OBJECT-TYPE
   SYNTAX      Counter32
   MAX-ACCESS  read-only
   STATUS      current
   DESCRIPTION
      "Path: efm.performance.oam.varReqTx

       32 bit unsigned wrappable counter."
   ::= {pr1646v2EfmOamEntry 150994944}

pr1646v2EfmOamVarReqRx OBJECT-TYPE
   SYNTAX      Counter32
   MAX-ACCESS  read-only
   STATUS      current
   DESCRIPTION
      "Path: efm.performance.oam.varReqRx

       32 bit unsigned wrappable counter."
   ::= {pr1646v2EfmOamEntry 167772160}

pr1646v2EfmOamVarRespTx OBJECT-TYPE
   SYNTAX      Counter32
   MAX-ACCESS  read-only
   STATUS      current
   DESCRIPTION
      "Path: efm.performance.oam.varRespTx

       32 bit unsigned wrappable counter."
   ::= {pr1646v2EfmOamEntry 184549376}

pr1646v2EfmOamVarRespRx OBJECT-TYPE
   SYNTAX      Counter32
   MAX-ACCESS  read-only
   STATUS      current
   DESCRIPTION
      "Path: efm.performance.oam.varRespRx

       32 bit unsigned wrappable counter."
   ::= {pr1646v2EfmOamEntry 201326592}

pr1646v2EfmOamOrgSpecificTx OBJECT-TYPE
   SYNTAX      Counter32
   MAX-ACCESS  read-only
   STATUS      current
   DESCRIPTION
      "Path: efm.performance.oam.orgSpecificTx

       32 bit unsigned wrappable counter."
   ::= {pr1646v2EfmOamEntry 218103808}

pr1646v2EfmOamOrgSpecificRx OBJECT-TYPE
   SYNTAX      Counter32
   MAX-ACCESS  read-only
   STATUS      current
   DESCRIPTION
      "Path: efm.performance.oam.orgSpecificRx

       32 bit unsigned wrappable counter."
   ::= {pr1646v2EfmOamEntry 234881024}

pr1646v2EfmOamUnsupportedCodesTx OBJECT-TYPE
   SYNTAX      Counter32
   MAX-ACCESS  read-only
   STATUS      current
   DESCRIPTION
      "Path: efm.performance.oam.unsupportedCodesTx

       32 bit unsigned wrappable counter."
   ::= {pr1646v2EfmOamEntry 251658240}

pr1646v2EfmOamUnsupportedCodesRx OBJECT-TYPE
   SYNTAX      Counter32
   MAX-ACCESS  read-only
   STATUS      current
   DESCRIPTION
      "Path: efm.performance.oam.unsupportedCodesRx

       32 bit unsigned wrappable counter."
   ::= {pr1646v2EfmOamEntry 268435456}

pr1646v2EfmOamPduDiscardRx OBJECT-TYPE
   SYNTAX      Counter32
   MAX-ACCESS  read-only
   STATUS      current
   DESCRIPTION
      "Path: efm.performance.oam.pduDiscardRx

       32 bit unsigned wrappable counter."
   ::= {pr1646v2EfmOamEntry 1694498816}

pr1646v2EfmOamDataDiscardTx OBJECT-TYPE
   SYNTAX      Counter32
   MAX-ACCESS  read-only
   STATUS      current
   DESCRIPTION
      "Path: efm.performance.oam.dataDiscardTx

       32 bit unsigned wrappable counter."
   ::= {pr1646v2EfmOamEntry 1711276032}

pr1646v2EfmOamDataDiscardRx OBJECT-TYPE
   SYNTAX      Counter32
   MAX-ACCESS  read-only
   STATUS      current
   DESCRIPTION
      "Path: efm.performance.oam.dataDiscardRx

       32 bit unsigned wrappable counter."
   ::= {pr1646v2EfmOamEntry 1728053248}


pr1646v2EfmVlan OBJECT IDENTIFIER ::= {pr1646v2Efm 310}

pr1646v2EfmVlanSSCTable OBJECT-TYPE
   SYNTAX      SEQUENCE OF Pr1646v2EfmVlanEntry
   MAX-ACCESS  not-accessible
   STATUS      current
   DESCRIPTION
      ""
   ::= {pr1646v2EfmVlan 1}

pr1646v2EfmVlanEntry OBJECT-TYPE
   SYNTAX      Pr1646v2EfmVlanEntry
   MAX-ACCESS  not-accessible
   STATUS      current
   DESCRIPTION
      ""
   INDEX      { pr1646v2EfmVlanTableIx }
   ::= {pr1646v2EfmVlanSSCTable 1}

Pr1646v2EfmVlanEntry ::=
   SEQUENCE
      {
      pr1646v2EfmVlanTableIx
         TableIndex,
      pr1646v2EfmVlanName
         DisplayString,
      pr1646v2EfmVlanMCInOctets
         Counter64,
      pr1646v2EfmVlanMCInUcast
         Counter64,
      pr1646v2EfmVlanMCInNUcastPkts
         Counter64,
      pr1646v2EfmVlanMCInBcastPkts
         Counter64,
      pr1646v2EfmVlanMCInMcastPkts
         Counter64,
      pr1646v2EfmVlanMCInDiscards
         Counter64,
      pr1646v2EfmVlanMCInErrors
         Counter64,
      pr1646v2EfmVlanMCInUnknownProtos
         Counter64,
      pr1646v2EfmVlanMCInDropEx
         Counter64,
      pr1646v2EfmVlanMCInDropNoMac
         Counter64,
      pr1646v2EfmVlanMCInDropNUCast
         Counter64,
      pr1646v2EfmVlanMCInDropFilter
         Counter64,
      pr1646v2EfmVlanMCInBandwidth15sec
         Integer32,
      pr1646v2EfmVlanMCInBandwidth30sec
         Integer32,
      pr1646v2EfmVlanMCInBandwidth1min
         Integer32,
      pr1646v2EfmVlanMCInBandwidth2min
         Integer32,
      pr1646v2EfmVlanMCInBandwidth5min
         Integer32,
      pr1646v2EfmVlanMCOutOctets
         Counter64,
      pr1646v2EfmVlanMCOutUcastPkts
         Counter64,
      pr1646v2EfmVlanMCOutNUcastPkts
         Counter64,
      pr1646v2EfmVlanMCOutBcastPkts
         Counter64,
      pr1646v2EfmVlanMCOutMcastPkts
         Counter64,
      pr1646v2EfmVlanMCOutDiscards
         Counter64,
      pr1646v2EfmVlanMCOutErrors
         Counter64,
      pr1646v2EfmVlanMCOutQLen
         Counter32,
      pr1646v2EfmVlanMCOutDropEx
         Counter64,
      pr1646v2EfmVlanMCOutDropNoArp
         Counter64,
      pr1646v2EfmVlanMCOutDropFilter
         Counter64,
      pr1646v2EfmVlanMCOutBandwidth15sec
         Integer32,
      pr1646v2EfmVlanMCOutBandwidth30sec
         Integer32,
      pr1646v2EfmVlanMCOutBandwidth1min
         Integer32,
      pr1646v2EfmVlanMCOutBandwidth2min
         Integer32,
      pr1646v2EfmVlanMCOutBandwidth5min
         Integer32,
      pr1646v2EfmVlanVlanVid
         Integer32,
      pr1646v2EfmVlanPppLinkMonitoringRequestsSent
         Gauge32,
      pr1646v2EfmVlanPppLinkMonitoringRepliesRcvd
         Gauge32,
      pr1646v2EfmVlanPppLinkMonitoringRequestsRcvd
         Gauge32,
      pr1646v2EfmVlanPppLinkMonitoringRepliesSent
         Gauge32
      }

pr1646v2EfmVlanTableIx OBJECT-TYPE
   SYNTAX      TableIndex
   MAX-ACCESS  not-accessible
   STATUS      current
   DESCRIPTION
      ""
   ::= {pr1646v2EfmVlanEntry 11}

pr1646v2EfmVlanName OBJECT-TYPE
   SYNTAX      DisplayString
   MAX-ACCESS  read-only
   STATUS      current
   DESCRIPTION
      "Path: efm.performance.vlan.name"
   ::= {pr1646v2EfmVlanEntry 16777216}

pr1646v2EfmVlanMCInOctets OBJECT-TYPE
   SYNTAX      Counter64
   MAX-ACCESS  read-only
   STATUS      current
   DESCRIPTION
      "Path: efm.performance.vlan.mibCounters.ifInOctets

       64 bit unsigned wrappable counter."
   ::= {pr1646v2EfmVlanEntry 40697856}

pr1646v2EfmVlanMCInUcast OBJECT-TYPE
   SYNTAX      Counter64
   MAX-ACCESS  read-only
   STATUS      current
   DESCRIPTION
      "Path: efm.performance.vlan.mibCounters.ifInUcastPkts

       64 bit unsigned wrappable counter."
   ::= {pr1646v2EfmVlanEntry 40763392}

pr1646v2EfmVlanMCInNUcastPkts OBJECT-TYPE
   SYNTAX      Counter64
   MAX-ACCESS  read-only
   STATUS      current
   DESCRIPTION
      "Path: efm.performance.vlan.mibCounters.ifInNUcastPkts

       64 bit unsigned wrappable counter."
   ::= {pr1646v2EfmVlanEntry 40828928}

pr1646v2EfmVlanMCInBcastPkts OBJECT-TYPE
   SYNTAX      Counter64
   MAX-ACCESS  read-only
   STATUS      current
   DESCRIPTION
      "Path: efm.performance.vlan.mibCounters.ifInBcastPkts

       64 bit unsigned wrappable counter."
   ::= {pr1646v2EfmVlanEntry 47382528}

pr1646v2EfmVlanMCInMcastPkts OBJECT-TYPE
   SYNTAX      Counter64
   MAX-ACCESS  read-only
   STATUS      current
   DESCRIPTION
      "Path: efm.performance.vlan.mibCounters.ifInMcastPkts

       64 bit unsigned wrappable counter."
   ::= {pr1646v2EfmVlanEntry 48037888}

pr1646v2EfmVlanMCInDiscards OBJECT-TYPE
   SYNTAX      Counter64
   MAX-ACCESS  read-only
   STATUS      current
   DESCRIPTION
      "Path: efm.performance.vlan.mibCounters.ifInDiscards

       64 bit unsigned wrappable counter."
   ::= {pr1646v2EfmVlanEntry 40894464}

pr1646v2EfmVlanMCInErrors OBJECT-TYPE
   SYNTAX      Counter64
   MAX-ACCESS  read-only
   STATUS      current
   DESCRIPTION
      "Path: efm.performance.vlan.mibCounters.ifInErrors

       64 bit unsigned wrappable counter."
   ::= {pr1646v2EfmVlanEntry 40960000}

pr1646v2EfmVlanMCInUnknownProtos OBJECT-TYPE
   SYNTAX      Counter64
   MAX-ACCESS  read-only
   STATUS      current
   DESCRIPTION
      "Path: efm.performance.vlan.mibCounters.ifInUnknownProtos

       64 bit unsigned wrappable counter."
   ::= {pr1646v2EfmVlanEntry 41025536}

pr1646v2EfmVlanMCInDropEx OBJECT-TYPE
   SYNTAX      Counter64
   MAX-ACCESS  read-only
   STATUS      current
   DESCRIPTION
      "Path: efm.performance.vlan.mibCounters.ifInDropLevelExceeded

       64 bit unsigned wrappable counter."
   ::= {pr1646v2EfmVlanEntry 42074112}

pr1646v2EfmVlanMCInDropNoMac OBJECT-TYPE
   SYNTAX      Counter64
   MAX-ACCESS  read-only
   STATUS      current
   DESCRIPTION
      "Path: efm.performance.vlan.mibCounters.ifInDiscardsNoMacFit

       64 bit unsigned wrappable counter."
   ::= {pr1646v2EfmVlanEntry 42270720}

pr1646v2EfmVlanMCInDropNUCast OBJECT-TYPE
   SYNTAX      Counter64
   MAX-ACCESS  read-only
   STATUS      current
   DESCRIPTION
      "Path: efm.performance.vlan.mibCounters.ifInDiscardsNUCast

       64 bit unsigned wrappable counter."
   ::= {pr1646v2EfmVlanEntry 42467328}

pr1646v2EfmVlanMCInDropFilter OBJECT-TYPE
   SYNTAX      Counter64
   MAX-ACCESS  read-only
   STATUS      current
   DESCRIPTION
      "Path: efm.performance.vlan.mibCounters.ifInDiscardsFilter

       64 bit unsigned wrappable counter."
   ::= {pr1646v2EfmVlanEntry 42532864}

pr1646v2EfmVlanMCInBandwidth15sec OBJECT-TYPE
   SYNTAX      Integer32
   MAX-ACCESS  read-only
   STATUS      current
   DESCRIPTION
      "Path: efm.performance.vlan.mibCounters.ifInBandwidth.15sec

       unit name = bps
       formula = 8 * ; 8 /"
   ::= {pr1646v2EfmVlanEntry 45417728}

pr1646v2EfmVlanMCInBandwidth30sec OBJECT-TYPE
   SYNTAX      Integer32
   MAX-ACCESS  read-only
   STATUS      current
   DESCRIPTION
      "Path: efm.performance.vlan.mibCounters.ifInBandwidth.30sec

       unit name = bps
       formula = 8 * ; 8 /"
   ::= {pr1646v2EfmVlanEntry 45419008}

pr1646v2EfmVlanMCInBandwidth1min OBJECT-TYPE
   SYNTAX      Integer32
   MAX-ACCESS  read-only
   STATUS      current
   DESCRIPTION
      "Path: efm.performance.vlan.mibCounters.ifInBandwidth.1min

       unit name = bps
       formula = 8 * ; 8 /"
   ::= {pr1646v2EfmVlanEntry 45421568}

pr1646v2EfmVlanMCInBandwidth2min OBJECT-TYPE
   SYNTAX      Integer32
   MAX-ACCESS  read-only
   STATUS      current
   DESCRIPTION
      "Path: efm.performance.vlan.mibCounters.ifInBandwidth.2min

       unit name = bps
       formula = 8 * ; 8 /"
   ::= {pr1646v2EfmVlanEntry 45426688}

pr1646v2EfmVlanMCInBandwidth5min OBJECT-TYPE
   SYNTAX      Integer32
   MAX-ACCESS  read-only
   STATUS      current
   DESCRIPTION
      "Path: efm.performance.vlan.mibCounters.ifInBandwidth.5min

       unit name = bps
       formula = 8 * ; 8 /"
   ::= {pr1646v2EfmVlanEntry 45442048}

pr1646v2EfmVlanMCOutOctets OBJECT-TYPE
   SYNTAX      Counter64
   MAX-ACCESS  read-only
   STATUS      current
   DESCRIPTION
      "Path: efm.performance.vlan.mibCounters.ifOutOctets

       64 bit unsigned wrappable counter."
   ::= {pr1646v2EfmVlanEntry 41091072}

pr1646v2EfmVlanMCOutUcastPkts OBJECT-TYPE
   SYNTAX      Counter64
   MAX-ACCESS  read-only
   STATUS      current
   DESCRIPTION
      "Path: efm.performance.vlan.mibCounters.ifOutUcastPkts

       64 bit unsigned wrappable counter."
   ::= {pr1646v2EfmVlanEntry 41156608}

pr1646v2EfmVlanMCOutNUcastPkts OBJECT-TYPE
   SYNTAX      Counter64
   MAX-ACCESS  read-only
   STATUS      current
   DESCRIPTION
      "Path: efm.performance.vlan.mibCounters.ifOutNUcastPkts

       64 bit unsigned wrappable counter."
   ::= {pr1646v2EfmVlanEntry 41222144}

pr1646v2EfmVlanMCOutBcastPkts OBJECT-TYPE
   SYNTAX      Counter64
   MAX-ACCESS  read-only
   STATUS      current
   DESCRIPTION
      "Path: efm.performance.vlan.mibCounters.ifOutBcastPkts

       64 bit unsigned wrappable counter."
   ::= {pr1646v2EfmVlanEntry 47775744}

pr1646v2EfmVlanMCOutMcastPkts OBJECT-TYPE
   SYNTAX      Counter64
   MAX-ACCESS  read-only
   STATUS      current
   DESCRIPTION
      "Path: efm.performance.vlan.mibCounters.ifOutMcastPkts

       64 bit unsigned wrappable counter."
   ::= {pr1646v2EfmVlanEntry 48431104}

pr1646v2EfmVlanMCOutDiscards OBJECT-TYPE
   SYNTAX      Counter64
   MAX-ACCESS  read-only
   STATUS      current
   DESCRIPTION
      "Path: efm.performance.vlan.mibCounters.ifOutDiscards

       64 bit unsigned wrappable counter."
   ::= {pr1646v2EfmVlanEntry 41287680}

pr1646v2EfmVlanMCOutErrors OBJECT-TYPE
   SYNTAX      Counter64
   MAX-ACCESS  read-only
   STATUS      current
   DESCRIPTION
      "Path: efm.performance.vlan.mibCounters.ifOutErrors

       64 bit unsigned wrappable counter."
   ::= {pr1646v2EfmVlanEntry 41353216}

pr1646v2EfmVlanMCOutQLen OBJECT-TYPE
   SYNTAX      Counter32
   MAX-ACCESS  read-only
   STATUS      current
   DESCRIPTION
      "Path: efm.performance.vlan.mibCounters.ifOutQLen

       32 bit unsigned wrappable counter."
   ::= {pr1646v2EfmVlanEntry 41418752}

pr1646v2EfmVlanMCOutDropEx OBJECT-TYPE
   SYNTAX      Counter64
   MAX-ACCESS  read-only
   STATUS      current
   DESCRIPTION
      "Path: efm.performance.vlan.mibCounters.ifOutDropLevelExceeded

       64 bit unsigned wrappable counter."
   ::= {pr1646v2EfmVlanEntry 41484288}

pr1646v2EfmVlanMCOutDropNoArp OBJECT-TYPE
   SYNTAX      Counter64
   MAX-ACCESS  read-only
   STATUS      current
   DESCRIPTION
      "Path: efm.performance.vlan.mibCounters.ifOutDiscardsNoArp

       64 bit unsigned wrappable counter."
   ::= {pr1646v2EfmVlanEntry 42336256}

pr1646v2EfmVlanMCOutDropFilter OBJECT-TYPE
   SYNTAX      Counter64
   MAX-ACCESS  read-only
   STATUS      current
   DESCRIPTION
      "Path: efm.performance.vlan.mibCounters.ifOutDiscardsFilter

       64 bit unsigned wrappable counter."
   ::= {pr1646v2EfmVlanEntry 42598400}

pr1646v2EfmVlanMCOutBandwidth15sec OBJECT-TYPE
   SYNTAX      Integer32
   MAX-ACCESS  read-only
   STATUS      current
   DESCRIPTION
      "Path: efm.performance.vlan.mibCounters.ifOutBandwidth.15sec

       unit name = bps
       formula = 8 * ; 8 /"
   ::= {pr1646v2EfmVlanEntry 45483264}

pr1646v2EfmVlanMCOutBandwidth30sec OBJECT-TYPE
   SYNTAX      Integer32
   MAX-ACCESS  read-only
   STATUS      current
   DESCRIPTION
      "Path: efm.performance.vlan.mibCounters.ifOutBandwidth.30sec

       unit name = bps
       formula = 8 * ; 8 /"
   ::= {pr1646v2EfmVlanEntry 45484544}

pr1646v2EfmVlanMCOutBandwidth1min OBJECT-TYPE
   SYNTAX      Integer32
   MAX-ACCESS  read-only
   STATUS      current
   DESCRIPTION
      "Path: efm.performance.vlan.mibCounters.ifOutBandwidth.1min

       unit name = bps
       formula = 8 * ; 8 /"
   ::= {pr1646v2EfmVlanEntry 45487104}

pr1646v2EfmVlanMCOutBandwidth2min OBJECT-TYPE
   SYNTAX      Integer32
   MAX-ACCESS  read-only
   STATUS      current
   DESCRIPTION
      "Path: efm.performance.vlan.mibCounters.ifOutBandwidth.2min

       unit name = bps
       formula = 8 * ; 8 /"
   ::= {pr1646v2EfmVlanEntry 45492224}

pr1646v2EfmVlanMCOutBandwidth5min OBJECT-TYPE
   SYNTAX      Integer32
   MAX-ACCESS  read-only
   STATUS      current
   DESCRIPTION
      "Path: efm.performance.vlan.mibCounters.ifOutBandwidth.5min

       unit name = bps
       formula = 8 * ; 8 /"
   ::= {pr1646v2EfmVlanEntry 45507584}

pr1646v2EfmVlanVlanVid OBJECT-TYPE
   SYNTAX      Integer32
   MAX-ACCESS  read-only
   STATUS      current
   DESCRIPTION
      "Path: efm.performance.vlan.vlan.vid"
   ::= {pr1646v2EfmVlanEntry 234946560}

pr1646v2EfmVlanPppLinkMonitoringRequestsSent OBJECT-TYPE
   SYNTAX      Gauge32
   MAX-ACCESS  read-only
   STATUS      current
   DESCRIPTION
      "Path: efm.performance.vlan.ppp.linkMonitoring.requestsSent

       32 bit unsigned gauge value."
   ::= {pr1646v2EfmVlanEntry 50397440}

pr1646v2EfmVlanPppLinkMonitoringRepliesRcvd OBJECT-TYPE
   SYNTAX      Gauge32
   MAX-ACCESS  read-only
   STATUS      current
   DESCRIPTION
      "Path: efm.performance.vlan.ppp.linkMonitoring.repliesRcvd

       32 bit unsigned gauge value."
   ::= {pr1646v2EfmVlanEntry 50397696}

pr1646v2EfmVlanPppLinkMonitoringRequestsRcvd OBJECT-TYPE
   SYNTAX      Gauge32
   MAX-ACCESS  read-only
   STATUS      current
   DESCRIPTION
      "Path: efm.performance.vlan.ppp.linkMonitoring.requestsRcvd

       32 bit unsigned gauge value."
   ::= {pr1646v2EfmVlanEntry 50397952}

pr1646v2EfmVlanPppLinkMonitoringRepliesSent OBJECT-TYPE
   SYNTAX      Gauge32
   MAX-ACCESS  read-only
   STATUS      current
   DESCRIPTION
      "Path: efm.performance.vlan.ppp.linkMonitoring.repliesSent

       32 bit unsigned gauge value."
   ::= {pr1646v2EfmVlanEntry 50398208}

pr1646v2EfmVlanMCH2P OBJECT-TYPE
   SYNTAX      SEQUENCE OF Pr1646v2EfmVlanMCH2PEntry
   MAX-ACCESS  not-accessible
   STATUS      current
   DESCRIPTION
      ""
   ::= {pr1646v2EfmVlan 41549824}

pr1646v2EfmVlanMCH2PEntry OBJECT-TYPE
   SYNTAX      Pr1646v2EfmVlanMCH2PEntry
   MAX-ACCESS  not-accessible
   STATUS      current
   DESCRIPTION
      ""
   INDEX      { pr1646v2EfmVlanTableIx,
                pr1646v2EfmVlanMCH2PTableIx }
   ::= {pr1646v2EfmVlanMCH2P 1}

Pr1646v2EfmVlanMCH2PEntry ::=
   SEQUENCE
      {
      pr1646v2EfmVlanMCH2PTableIx
         TableIndex,
      pr1646v2EfmVlanMCH2PSysUpTime
         TimeTicks,
      pr1646v2EfmVlanMCH2PIfUpTime
         TimeTicks,
      pr1646v2EfmVlanMCH2PIfStatChanges
         Counter32,
      pr1646v2EfmVlanMCH2PIfInOctets
         Counter64,
      pr1646v2EfmVlanMCH2PIfInUCPkts
         Counter64,
      pr1646v2EfmVlanMCH2PIfInNUCPkts
         Counter64,
      pr1646v2EfmVlanMCH2PIfInBCPkts
         Counter64,
      pr1646v2EfmVlanMCH2PIfInMCPkts
         Counter64,
      pr1646v2EfmVlanMCH2PIfInDiscards
         Counter64,
      pr1646v2EfmVlanMCH2PIfInErrors
         Counter64,
      pr1646v2EfmVlanMCH2PIfInUnkwn
         Counter64,
      pr1646v2EfmVlanMCH2PInDropEx
         Counter64,
      pr1646v2EfmVlanMCH2PInDropNoMac
         Counter64,
      pr1646v2EfmVlanMCH2PInDropNUCast
         Counter64,
      pr1646v2EfmVlanMCH2PInDropFilter
         Counter64,
      pr1646v2EfmVlanMCH2PIfInBandwidth
         Integer32,
      pr1646v2EfmVlanMCH2PIfOutOctets
         Counter64,
      pr1646v2EfmVlanMCH2PIfOutUCPkts
         Counter64,
      pr1646v2EfmVlanMCH2PIfOutNUCPkts
         Counter64,
      pr1646v2EfmVlanMCH2PIfOutBCPkts
         Counter64,
      pr1646v2EfmVlanMCH2PIfOutMCPkts
         Counter64,
      pr1646v2EfmVlanMCH2PIfOutDiscards
         Counter64,
      pr1646v2EfmVlanMCH2PIfOutErrors
         Counter64,
      pr1646v2EfmVlanMCH2POutDropEx
         Counter64,
      pr1646v2EfmVlanMCH2POutDropNoArp
         Counter64,
      pr1646v2EfmVlanMCH2POutDropFilter
         Counter64,
      pr1646v2EfmVlanMCH2PIfOutBandwidth
         Integer32,
      pr1646v2EfmVlanMCH2PIfErrSec
         Counter32
      }

pr1646v2EfmVlanMCH2PTableIx OBJECT-TYPE
   SYNTAX      TableIndex
   MAX-ACCESS  not-accessible
   STATUS      current
   DESCRIPTION
      ""
   ::= {pr1646v2EfmVlanMCH2PEntry 11}

pr1646v2EfmVlanMCH2PSysUpTime OBJECT-TYPE
   SYNTAX      TimeTicks
   MAX-ACCESS  read-only
   STATUS      current
   DESCRIPTION
      "Path: efm.performance.vlan.mibCounters.h2Performance.sysUpTime

       Time in centi-second."
   ::= {pr1646v2EfmVlanMCH2PEntry 16777216}

pr1646v2EfmVlanMCH2PIfUpTime OBJECT-TYPE
   SYNTAX      TimeTicks
   MAX-ACCESS  read-only
   STATUS      current
   DESCRIPTION
      "Path: efm.performance.vlan.mibCounters.h2Performance.ifUpTime

       Time in centi-second."
   ::= {pr1646v2EfmVlanMCH2PEntry 33554432}

pr1646v2EfmVlanMCH2PIfStatChanges OBJECT-TYPE
   SYNTAX      Counter32
   MAX-ACCESS  read-only
   STATUS      current
   DESCRIPTION
      "Path: efm.performance.vlan.mibCounters.h2Performance.ifStatusChanges

       32 bit unsigned wrappable counter."
   ::= {pr1646v2EfmVlanMCH2PEntry 50331648}

pr1646v2EfmVlanMCH2PIfInOctets OBJECT-TYPE
   SYNTAX      Counter64
   MAX-ACCESS  read-only
   STATUS      current
   DESCRIPTION
      "Path: efm.performance.vlan.mibCounters.h2Performance.ifInOctets

       64 bit unsigned wrappable counter."
   ::= {pr1646v2EfmVlanMCH2PEntry 67108864}

pr1646v2EfmVlanMCH2PIfInUCPkts OBJECT-TYPE
   SYNTAX      Counter64
   MAX-ACCESS  read-only
   STATUS      current
   DESCRIPTION
      "Path: efm.performance.vlan.mibCounters.h2Performance.ifInUcastPkts

       64 bit unsigned wrappable counter."
   ::= {pr1646v2EfmVlanMCH2PEntry 83886080}

pr1646v2EfmVlanMCH2PIfInNUCPkts OBJECT-TYPE
   SYNTAX      Counter64
   MAX-ACCESS  read-only
   STATUS      current
   DESCRIPTION
      "Path: efm.performance.vlan.mibCounters.h2Performance.ifInNUcastPkts

       64 bit unsigned wrappable counter."
   ::= {pr1646v2EfmVlanMCH2PEntry 100663296}

pr1646v2EfmVlanMCH2PIfInBCPkts OBJECT-TYPE
   SYNTAX      Counter64
   MAX-ACCESS  read-only
   STATUS      current
   DESCRIPTION
      "Path: efm.performance.vlan.mibCounters.h2Performance.ifInBcastPkts

       64 bit unsigned wrappable counter."
   ::= {pr1646v2EfmVlanMCH2PEntry 419430400}

pr1646v2EfmVlanMCH2PIfInMCPkts OBJECT-TYPE
   SYNTAX      Counter64
   MAX-ACCESS  read-only
   STATUS      current
   DESCRIPTION
      "Path: efm.performance.vlan.mibCounters.h2Performance.ifInMcastPkts

       64 bit unsigned wrappable counter."
   ::= {pr1646v2EfmVlanMCH2PEntry 436207616}

pr1646v2EfmVlanMCH2PIfInDiscards OBJECT-TYPE
   SYNTAX      Counter64
   MAX-ACCESS  read-only
   STATUS      current
   DESCRIPTION
      "Path: efm.performance.vlan.mibCounters.h2Performance.ifInDiscards

       64 bit unsigned wrappable counter."
   ::= {pr1646v2EfmVlanMCH2PEntry 117440512}

pr1646v2EfmVlanMCH2PIfInErrors OBJECT-TYPE
   SYNTAX      Counter64
   MAX-ACCESS  read-only
   STATUS      current
   DESCRIPTION
      "Path: efm.performance.vlan.mibCounters.h2Performance.ifInErrors

       64 bit unsigned wrappable counter."
   ::= {pr1646v2EfmVlanMCH2PEntry 134217728}

pr1646v2EfmVlanMCH2PIfInUnkwn OBJECT-TYPE
   SYNTAX      Counter64
   MAX-ACCESS  read-only
   STATUS      current
   DESCRIPTION
      "Path: efm.performance.vlan.mibCounters.h2Performance.ifInUnknownProtos

       64 bit unsigned wrappable counter."
   ::= {pr1646v2EfmVlanMCH2PEntry 150994944}

pr1646v2EfmVlanMCH2PInDropEx OBJECT-TYPE
   SYNTAX      Counter64
   MAX-ACCESS  read-only
   STATUS      current
   DESCRIPTION
      "Path: efm.performance.vlan.mibCounters.h2Performance.ifInDropLevelExceeded

       64 bit unsigned wrappable counter."
   ::= {pr1646v2EfmVlanMCH2PEntry 335544320}

pr1646v2EfmVlanMCH2PInDropNoMac OBJECT-TYPE
   SYNTAX      Counter64
   MAX-ACCESS  read-only
   STATUS      current
   DESCRIPTION
      "Path: efm.performance.vlan.mibCounters.h2Performance.fInDiscardsNoMacFit

       64 bit unsigned wrappable counter."
   ::= {pr1646v2EfmVlanMCH2PEntry 301989888}

pr1646v2EfmVlanMCH2PInDropNUCast OBJECT-TYPE
   SYNTAX      Counter64
   MAX-ACCESS  read-only
   STATUS      current
   DESCRIPTION
      "Path: efm.performance.vlan.mibCounters.h2Performance.fInDiscardsNUCast

       64 bit unsigned wrappable counter."
   ::= {pr1646v2EfmVlanMCH2PEntry 318767104}

pr1646v2EfmVlanMCH2PInDropFilter OBJECT-TYPE
   SYNTAX      Counter64
   MAX-ACCESS  read-only
   STATUS      current
   DESCRIPTION
      "Path: efm.performance.vlan.mibCounters.h2Performance.fInDiscardsFilter

       64 bit unsigned wrappable counter."
   ::= {pr1646v2EfmVlanMCH2PEntry 385875968}

pr1646v2EfmVlanMCH2PIfInBandwidth OBJECT-TYPE
   SYNTAX      Integer32
   MAX-ACCESS  read-only
   STATUS      current
   DESCRIPTION
      "Path: efm.performance.vlan.mibCounters.h2Performance.ifInBandwidth

       unit name = bps
       formula = 8 * ; 8 /"
   ::= {pr1646v2EfmVlanMCH2PEntry 268435456}

pr1646v2EfmVlanMCH2PIfOutOctets OBJECT-TYPE
   SYNTAX      Counter64
   MAX-ACCESS  read-only
   STATUS      current
   DESCRIPTION
      "Path: efm.performance.vlan.mibCounters.h2Performance.ifOutOctets

       64 bit unsigned wrappable counter."
   ::= {pr1646v2EfmVlanMCH2PEntry 167772160}

pr1646v2EfmVlanMCH2PIfOutUCPkts OBJECT-TYPE
   SYNTAX      Counter64
   MAX-ACCESS  read-only
   STATUS      current
   DESCRIPTION
      "Path: efm.performance.vlan.mibCounters.h2Performance.ifOutUcastPkts

       64 bit unsigned wrappable counter."
   ::= {pr1646v2EfmVlanMCH2PEntry 184549376}

pr1646v2EfmVlanMCH2PIfOutNUCPkts OBJECT-TYPE
   SYNTAX      Counter64
   MAX-ACCESS  read-only
   STATUS      current
   DESCRIPTION
      "Path: efm.performance.vlan.mibCounters.h2Performance.ifOutNUcastPkts

       64 bit unsigned wrappable counter."
   ::= {pr1646v2EfmVlanMCH2PEntry 201326592}

pr1646v2EfmVlanMCH2PIfOutBCPkts OBJECT-TYPE
   SYNTAX      Counter64
   MAX-ACCESS  read-only
   STATUS      current
   DESCRIPTION
      "Path: efm.performance.vlan.mibCounters.h2Performance.ifOutBcastPkts

       64 bit unsigned wrappable counter."
   ::= {pr1646v2EfmVlanMCH2PEntry 452984832}

pr1646v2EfmVlanMCH2PIfOutMCPkts OBJECT-TYPE
   SYNTAX      Counter64
   MAX-ACCESS  read-only
   STATUS      current
   DESCRIPTION
      "Path: efm.performance.vlan.mibCounters.h2Performance.ifOutMcastPkts

       64 bit unsigned wrappable counter."
   ::= {pr1646v2EfmVlanMCH2PEntry 469762048}

pr1646v2EfmVlanMCH2PIfOutDiscards OBJECT-TYPE
   SYNTAX      Counter64
   MAX-ACCESS  read-only
   STATUS      current
   DESCRIPTION
      "Path: efm.performance.vlan.mibCounters.h2Performance.ifOutDiscards

       64 bit unsigned wrappable counter."
   ::= {pr1646v2EfmVlanMCH2PEntry 218103808}

pr1646v2EfmVlanMCH2PIfOutErrors OBJECT-TYPE
   SYNTAX      Counter64
   MAX-ACCESS  read-only
   STATUS      current
   DESCRIPTION
      "Path: efm.performance.vlan.mibCounters.h2Performance.ifOutErrors

       64 bit unsigned wrappable counter."
   ::= {pr1646v2EfmVlanMCH2PEntry 234881024}

pr1646v2EfmVlanMCH2POutDropEx OBJECT-TYPE
   SYNTAX      Counter64
   MAX-ACCESS  read-only
   STATUS      current
   DESCRIPTION
      "Path: efm.performance.vlan.mibCounters.h2Performance.ifOutDropLevelExceeded

       64 bit unsigned wrappable counter."
   ::= {pr1646v2EfmVlanMCH2PEntry 352321536}

pr1646v2EfmVlanMCH2POutDropNoArp OBJECT-TYPE
   SYNTAX      Counter64
   MAX-ACCESS  read-only
   STATUS      current
   DESCRIPTION
      "Path: efm.performance.vlan.mibCounters.h2Performance.ifOutDiscardsNoArp

       64 bit unsigned wrappable counter."
   ::= {pr1646v2EfmVlanMCH2PEntry 369098752}

pr1646v2EfmVlanMCH2POutDropFilter OBJECT-TYPE
   SYNTAX      Counter64
   MAX-ACCESS  read-only
   STATUS      current
   DESCRIPTION
      "Path: efm.performance.vlan.mibCounters.h2Performance.ifOutDiscardsFilter

       64 bit unsigned wrappable counter."
   ::= {pr1646v2EfmVlanMCH2PEntry 402653184}

pr1646v2EfmVlanMCH2PIfOutBandwidth OBJECT-TYPE
   SYNTAX      Integer32
   MAX-ACCESS  read-only
   STATUS      current
   DESCRIPTION
      "Path: efm.performance.vlan.mibCounters.h2Performance.ifOutBandwidth

       unit name = bps
       formula = 8 * ; 8 /"
   ::= {pr1646v2EfmVlanMCH2PEntry 285212672}

pr1646v2EfmVlanMCH2PIfErrSec OBJECT-TYPE
   SYNTAX      Counter32
   MAX-ACCESS  read-only
   STATUS      current
   DESCRIPTION
      "Path: efm.performance.vlan.mibCounters.h2Performance.ifErrSec

       32 bit unsigned wrappable counter."
   ::= {pr1646v2EfmVlanMCH2PEntry 251658240}

pr1646v2EfmVlanMCH24P OBJECT-TYPE
   SYNTAX      SEQUENCE OF Pr1646v2EfmVlanMCH24PEntry
   MAX-ACCESS  not-accessible
   STATUS      current
   DESCRIPTION
      ""
   ::= {pr1646v2EfmVlan 41615360}

pr1646v2EfmVlanMCH24PEntry OBJECT-TYPE
   SYNTAX      Pr1646v2EfmVlanMCH24PEntry
   MAX-ACCESS  not-accessible
   STATUS      current
   DESCRIPTION
      ""
   INDEX      { pr1646v2EfmVlanTableIx,
                pr1646v2EfmVlanMCH24PTableIx }
   ::= {pr1646v2EfmVlanMCH24P 1}

Pr1646v2EfmVlanMCH24PEntry ::=
   SEQUENCE
      {
      pr1646v2EfmVlanMCH24PTableIx
         TableIndex,
      pr1646v2EfmVlanMCH24PSysUpTime
         TimeTicks,
      pr1646v2EfmVlanMCH24PIfUpTime
         TimeTicks,
      pr1646v2EfmVlanMCH24PIfStatChanges
         Counter32,
      pr1646v2EfmVlanMCH24PIfInOctets
         Counter64,
      pr1646v2EfmVlanMCH24PIfInUCPkts
         Counter64,
      pr1646v2EfmVlanMCH24PIfInNUCPkts
         Counter64,
      pr1646v2EfmVlanMCH24PIfInBCPkts
         Counter64,
      pr1646v2EfmVlanMCH24PIfInMCPkts
         Counter64,
      pr1646v2EfmVlanMCH24PIfInDiscards
         Counter64,
      pr1646v2EfmVlanMCH24PIfInErrors
         Counter64,
      pr1646v2EfmVlanMCH24PIfInUnkwn
         Counter64,
      pr1646v2EfmVlanMCH24PInDropEx
         Counter64,
      pr1646v2EfmVlanMCH24PInDropNoMac
         Counter64,
      pr1646v2EfmVlanMCH24PInDropNUCast
         Counter64,
      pr1646v2EfmVlanMCH24PInDropFilter
         Counter64,
      pr1646v2EfmVlanMCH24PIfInBandwidth
         Integer32,
      pr1646v2EfmVlanMCH24PIfOutOctets
         Counter64,
      pr1646v2EfmVlanMCH24PIfOutUCPkts
         Counter64,
      pr1646v2EfmVlanMCH24PIfOutNUCPkts
         Counter64,
      pr1646v2EfmVlanMCH24PIfOutBCPkts
         Counter64,
      pr1646v2EfmVlanMCH24PIfOutMCPkts
         Counter64,
      pr1646v2EfmVlanMCH24PIfOutDiscards
         Counter64,
      pr1646v2EfmVlanMCH24PIfOutErrors
         Counter64,
      pr1646v2EfmVlanMCH24POutDropEx
         Counter64,
      pr1646v2EfmVlanMCH24POutDropNoArp
         Counter64,
      pr1646v2EfmVlanMCH24POutDropFilter
         Counter64,
      pr1646v2EfmVlanMCH24PIfOutBandwidth
         Integer32,
      pr1646v2EfmVlanMCH24PIfErrSec
         Counter32
      }

pr1646v2EfmVlanMCH24PTableIx OBJECT-TYPE
   SYNTAX      TableIndex
   MAX-ACCESS  not-accessible
   STATUS      current
   DESCRIPTION
      ""
   ::= {pr1646v2EfmVlanMCH24PEntry 11}

pr1646v2EfmVlanMCH24PSysUpTime OBJECT-TYPE
   SYNTAX      TimeTicks
   MAX-ACCESS  read-only
   STATUS      current
   DESCRIPTION
      "Path: efm.performance.vlan.mibCounters.h24Performance.sysUpTime

       Time in centi-second."
   ::= {pr1646v2EfmVlanMCH24PEntry 16777216}

pr1646v2EfmVlanMCH24PIfUpTime OBJECT-TYPE
   SYNTAX      TimeTicks
   MAX-ACCESS  read-only
   STATUS      current
   DESCRIPTION
      "Path: efm.performance.vlan.mibCounters.h24Performance.ifUpTime

       Time in centi-second."
   ::= {pr1646v2EfmVlanMCH24PEntry 33554432}

pr1646v2EfmVlanMCH24PIfStatChanges OBJECT-TYPE
   SYNTAX      Counter32
   MAX-ACCESS  read-only
   STATUS      current
   DESCRIPTION
      "Path: efm.performance.vlan.mibCounters.h24Performance.ifStatusChanges

       32 bit unsigned wrappable counter."
   ::= {pr1646v2EfmVlanMCH24PEntry 50331648}

pr1646v2EfmVlanMCH24PIfInOctets OBJECT-TYPE
   SYNTAX      Counter64
   MAX-ACCESS  read-only
   STATUS      current
   DESCRIPTION
      "Path: efm.performance.vlan.mibCounters.h24Performance.ifInOctets

       64 bit unsigned wrappable counter."
   ::= {pr1646v2EfmVlanMCH24PEntry 67108864}

pr1646v2EfmVlanMCH24PIfInUCPkts OBJECT-TYPE
   SYNTAX      Counter64
   MAX-ACCESS  read-only
   STATUS      current
   DESCRIPTION
      "Path: efm.performance.vlan.mibCounters.h24Performance.ifInUcastPkts

       64 bit unsigned wrappable counter."
   ::= {pr1646v2EfmVlanMCH24PEntry 83886080}

pr1646v2EfmVlanMCH24PIfInNUCPkts OBJECT-TYPE
   SYNTAX      Counter64
   MAX-ACCESS  read-only
   STATUS      current
   DESCRIPTION
      "Path: efm.performance.vlan.mibCounters.h24Performance.ifInNUcastPkts

       64 bit unsigned wrappable counter."
   ::= {pr1646v2EfmVlanMCH24PEntry 100663296}

pr1646v2EfmVlanMCH24PIfInBCPkts OBJECT-TYPE
   SYNTAX      Counter64
   MAX-ACCESS  read-only
   STATUS      current
   DESCRIPTION
      "Path: efm.performance.vlan.mibCounters.h24Performance.ifInBcastPkts

       64 bit unsigned wrappable counter."
   ::= {pr1646v2EfmVlanMCH24PEntry 419430400}

pr1646v2EfmVlanMCH24PIfInMCPkts OBJECT-TYPE
   SYNTAX      Counter64
   MAX-ACCESS  read-only
   STATUS      current
   DESCRIPTION
      "Path: efm.performance.vlan.mibCounters.h24Performance.ifInMcastPkts

       64 bit unsigned wrappable counter."
   ::= {pr1646v2EfmVlanMCH24PEntry 436207616}

pr1646v2EfmVlanMCH24PIfInDiscards OBJECT-TYPE
   SYNTAX      Counter64
   MAX-ACCESS  read-only
   STATUS      current
   DESCRIPTION
      "Path: efm.performance.vlan.mibCounters.h24Performance.ifInDiscards

       64 bit unsigned wrappable counter."
   ::= {pr1646v2EfmVlanMCH24PEntry 117440512}

pr1646v2EfmVlanMCH24PIfInErrors OBJECT-TYPE
   SYNTAX      Counter64
   MAX-ACCESS  read-only
   STATUS      current
   DESCRIPTION
      "Path: efm.performance.vlan.mibCounters.h24Performance.ifInErrors

       64 bit unsigned wrappable counter."
   ::= {pr1646v2EfmVlanMCH24PEntry 134217728}

pr1646v2EfmVlanMCH24PIfInUnkwn OBJECT-TYPE
   SYNTAX      Counter64
   MAX-ACCESS  read-only
   STATUS      current
   DESCRIPTION
      "Path: efm.performance.vlan.mibCounters.h24Performance.ifInUnknownProtos

       64 bit unsigned wrappable counter."
   ::= {pr1646v2EfmVlanMCH24PEntry 150994944}

pr1646v2EfmVlanMCH24PInDropEx OBJECT-TYPE
   SYNTAX      Counter64
   MAX-ACCESS  read-only
   STATUS      current
   DESCRIPTION
      "Path: efm.performance.vlan.mibCounters.h24Performance.ifInDropLevelExceeded

       64 bit unsigned wrappable counter."
   ::= {pr1646v2EfmVlanMCH24PEntry 335544320}

pr1646v2EfmVlanMCH24PInDropNoMac OBJECT-TYPE
   SYNTAX      Counter64
   MAX-ACCESS  read-only
   STATUS      current
   DESCRIPTION
      "Path: efm.performance.vlan.mibCounters.h24Performance.fInDiscardsNoMacFit

       64 bit unsigned wrappable counter."
   ::= {pr1646v2EfmVlanMCH24PEntry 301989888}

pr1646v2EfmVlanMCH24PInDropNUCast OBJECT-TYPE
   SYNTAX      Counter64
   MAX-ACCESS  read-only
   STATUS      current
   DESCRIPTION
      "Path: efm.performance.vlan.mibCounters.h24Performance.fInDiscardsNUCast

       64 bit unsigned wrappable counter."
   ::= {pr1646v2EfmVlanMCH24PEntry 318767104}

pr1646v2EfmVlanMCH24PInDropFilter OBJECT-TYPE
   SYNTAX      Counter64
   MAX-ACCESS  read-only
   STATUS      current
   DESCRIPTION
      "Path: efm.performance.vlan.mibCounters.h24Performance.fInDiscardsFilter

       64 bit unsigned wrappable counter."
   ::= {pr1646v2EfmVlanMCH24PEntry 385875968}

pr1646v2EfmVlanMCH24PIfInBandwidth OBJECT-TYPE
   SYNTAX      Integer32
   MAX-ACCESS  read-only
   STATUS      current
   DESCRIPTION
      "Path: efm.performance.vlan.mibCounters.h24Performance.ifInBandwidth

       unit name = bps
       formula = 8 * ; 8 /"
   ::= {pr1646v2EfmVlanMCH24PEntry 268435456}

pr1646v2EfmVlanMCH24PIfOutOctets OBJECT-TYPE
   SYNTAX      Counter64
   MAX-ACCESS  read-only
   STATUS      current
   DESCRIPTION
      "Path: efm.performance.vlan.mibCounters.h24Performance.ifOutOctets

       64 bit unsigned wrappable counter."
   ::= {pr1646v2EfmVlanMCH24PEntry 167772160}

pr1646v2EfmVlanMCH24PIfOutUCPkts OBJECT-TYPE
   SYNTAX      Counter64
   MAX-ACCESS  read-only
   STATUS      current
   DESCRIPTION
      "Path: efm.performance.vlan.mibCounters.h24Performance.ifOutUcastPkts

       64 bit unsigned wrappable counter."
   ::= {pr1646v2EfmVlanMCH24PEntry 184549376}

pr1646v2EfmVlanMCH24PIfOutNUCPkts OBJECT-TYPE
   SYNTAX      Counter64
   MAX-ACCESS  read-only
   STATUS      current
   DESCRIPTION
      "Path: efm.performance.vlan.mibCounters.h24Performance.ifOutNUcastPkts

       64 bit unsigned wrappable counter."
   ::= {pr1646v2EfmVlanMCH24PEntry 201326592}

pr1646v2EfmVlanMCH24PIfOutBCPkts OBJECT-TYPE
   SYNTAX      Counter64
   MAX-ACCESS  read-only
   STATUS      current
   DESCRIPTION
      "Path: efm.performance.vlan.mibCounters.h24Performance.ifOutBcastPkts

       64 bit unsigned wrappable counter."
   ::= {pr1646v2EfmVlanMCH24PEntry 452984832}

pr1646v2EfmVlanMCH24PIfOutMCPkts OBJECT-TYPE
   SYNTAX      Counter64
   MAX-ACCESS  read-only
   STATUS      current
   DESCRIPTION
      "Path: efm.performance.vlan.mibCounters.h24Performance.ifOutMcastPkts

       64 bit unsigned wrappable counter."
   ::= {pr1646v2EfmVlanMCH24PEntry 469762048}

pr1646v2EfmVlanMCH24PIfOutDiscards OBJECT-TYPE
   SYNTAX      Counter64
   MAX-ACCESS  read-only
   STATUS      current
   DESCRIPTION
      "Path: efm.performance.vlan.mibCounters.h24Performance.ifOutDiscards

       64 bit unsigned wrappable counter."
   ::= {pr1646v2EfmVlanMCH24PEntry 218103808}

pr1646v2EfmVlanMCH24PIfOutErrors OBJECT-TYPE
   SYNTAX      Counter64
   MAX-ACCESS  read-only
   STATUS      current
   DESCRIPTION
      "Path: efm.performance.vlan.mibCounters.h24Performance.ifOutErrors

       64 bit unsigned wrappable counter."
   ::= {pr1646v2EfmVlanMCH24PEntry 234881024}

pr1646v2EfmVlanMCH24POutDropEx OBJECT-TYPE
   SYNTAX      Counter64
   MAX-ACCESS  read-only
   STATUS      current
   DESCRIPTION
      "Path: efm.performance.vlan.mibCounters.h24Performance.ifOutDropLevelExceeded

       64 bit unsigned wrappable counter."
   ::= {pr1646v2EfmVlanMCH24PEntry 352321536}

pr1646v2EfmVlanMCH24POutDropNoArp OBJECT-TYPE
   SYNTAX      Counter64
   MAX-ACCESS  read-only
   STATUS      current
   DESCRIPTION
      "Path: efm.performance.vlan.mibCounters.h24Performance.ifOutDiscardsNoArp

       64 bit unsigned wrappable counter."
   ::= {pr1646v2EfmVlanMCH24PEntry 369098752}

pr1646v2EfmVlanMCH24POutDropFilter OBJECT-TYPE
   SYNTAX      Counter64
   MAX-ACCESS  read-only
   STATUS      current
   DESCRIPTION
      "Path: efm.performance.vlan.mibCounters.h24Performance.ifOutDiscardsFilter

       64 bit unsigned wrappable counter."
   ::= {pr1646v2EfmVlanMCH24PEntry 402653184}

pr1646v2EfmVlanMCH24PIfOutBandwidth OBJECT-TYPE
   SYNTAX      Integer32
   MAX-ACCESS  read-only
   STATUS      current
   DESCRIPTION
      "Path: efm.performance.vlan.mibCounters.h24Performance.ifOutBandwidth

       unit name = bps
       formula = 8 * ; 8 /"
   ::= {pr1646v2EfmVlanMCH24PEntry 285212672}

pr1646v2EfmVlanMCH24PIfErrSec OBJECT-TYPE
   SYNTAX      Counter32
   MAX-ACCESS  read-only
   STATUS      current
   DESCRIPTION
      "Path: efm.performance.vlan.mibCounters.h24Performance.ifErrSec

       32 bit unsigned wrappable counter."
   ::= {pr1646v2EfmVlanMCH24PEntry 251658240}

pr1646v2EfmVlanMCD7P OBJECT-TYPE
   SYNTAX      SEQUENCE OF Pr1646v2EfmVlanMCD7PEntry
   MAX-ACCESS  not-accessible
   STATUS      current
   DESCRIPTION
      ""
   ::= {pr1646v2EfmVlan 41680896}

pr1646v2EfmVlanMCD7PEntry OBJECT-TYPE
   SYNTAX      Pr1646v2EfmVlanMCD7PEntry
   MAX-ACCESS  not-accessible
   STATUS      current
   DESCRIPTION
      ""
   INDEX      { pr1646v2EfmVlanTableIx,
                pr1646v2EfmVlanMCD7PTableIx }
   ::= {pr1646v2EfmVlanMCD7P 1}

Pr1646v2EfmVlanMCD7PEntry ::=
   SEQUENCE
      {
      pr1646v2EfmVlanMCD7PTableIx
         TableIndex,
      pr1646v2EfmVlanMCD7PSysUpTime
         TimeTicks,
      pr1646v2EfmVlanMCD7PIfUpTime
         TimeTicks,
      pr1646v2EfmVlanMCD7PIfStatChanges
         Counter32,
      pr1646v2EfmVlanMCD7PIfInOctets
         Counter64,
      pr1646v2EfmVlanMCD7PIfInUCPkts
         Counter64,
      pr1646v2EfmVlanMCD7PIfInNUCPkts
         Counter64,
      pr1646v2EfmVlanMCD7PIfInBCPkts
         Counter64,
      pr1646v2EfmVlanMCD7PIfInMCPkts
         Counter64,
      pr1646v2EfmVlanMCD7PIfInDiscards
         Counter64,
      pr1646v2EfmVlanMCD7PIfInErrors
         Counter64,
      pr1646v2EfmVlanMCD7PIfInUnkwn
         Counter64,
      pr1646v2EfmVlanMCD7PInDropEx
         Counter64,
      pr1646v2EfmVlanMCD7PInDropNoMac
         Counter64,
      pr1646v2EfmVlanMCD7PInDropNUCast
         Counter64,
      pr1646v2EfmVlanMCD7PInDropFilter
         Counter64,
      pr1646v2EfmVlanMCD7PIfInBandwidth
         Integer32,
      pr1646v2EfmVlanMCD7PIfOutOctets
         Counter64,
      pr1646v2EfmVlanMCD7PIfOutUCPkts
         Counter64,
      pr1646v2EfmVlanMCD7PIfOutNUCPkts
         Counter64,
      pr1646v2EfmVlanMCD7PIfOutBCPkts
         Counter64,
      pr1646v2EfmVlanMCD7PIfOutMCPkts
         Counter64,
      pr1646v2EfmVlanMCD7PIfOutDiscards
         Counter64,
      pr1646v2EfmVlanMCD7PIfOutErrors
         Counter64,
      pr1646v2EfmVlanMCD7POutDropEx
         Counter64,
      pr1646v2EfmVlanMCD7POutDropNoArp
         Counter64,
      pr1646v2EfmVlanMCD7POutDropFilter
         Counter64,
      pr1646v2EfmVlanMCD7PIfOutBandwidth
         Integer32,
      pr1646v2EfmVlanMCD7PIfErrSec
         Counter32
      }

pr1646v2EfmVlanMCD7PTableIx OBJECT-TYPE
   SYNTAX      TableIndex
   MAX-ACCESS  not-accessible
   STATUS      current
   DESCRIPTION
      ""
   ::= {pr1646v2EfmVlanMCD7PEntry 11}

pr1646v2EfmVlanMCD7PSysUpTime OBJECT-TYPE
   SYNTAX      TimeTicks
   MAX-ACCESS  read-only
   STATUS      current
   DESCRIPTION
      "Path: efm.performance.vlan.mibCounters.d7Performance.sysUpTime

       Time in centi-second."
   ::= {pr1646v2EfmVlanMCD7PEntry 16777216}

pr1646v2EfmVlanMCD7PIfUpTime OBJECT-TYPE
   SYNTAX      TimeTicks
   MAX-ACCESS  read-only
   STATUS      current
   DESCRIPTION
      "Path: efm.performance.vlan.mibCounters.d7Performance.ifUpTime

       Time in centi-second."
   ::= {pr1646v2EfmVlanMCD7PEntry 33554432}

pr1646v2EfmVlanMCD7PIfStatChanges OBJECT-TYPE
   SYNTAX      Counter32
   MAX-ACCESS  read-only
   STATUS      current
   DESCRIPTION
      "Path: efm.performance.vlan.mibCounters.d7Performance.ifStatusChanges

       32 bit unsigned wrappable counter."
   ::= {pr1646v2EfmVlanMCD7PEntry 50331648}

pr1646v2EfmVlanMCD7PIfInOctets OBJECT-TYPE
   SYNTAX      Counter64
   MAX-ACCESS  read-only
   STATUS      current
   DESCRIPTION
      "Path: efm.performance.vlan.mibCounters.d7Performance.ifInOctets

       64 bit unsigned wrappable counter."
   ::= {pr1646v2EfmVlanMCD7PEntry 67108864}

pr1646v2EfmVlanMCD7PIfInUCPkts OBJECT-TYPE
   SYNTAX      Counter64
   MAX-ACCESS  read-only
   STATUS      current
   DESCRIPTION
      "Path: efm.performance.vlan.mibCounters.d7Performance.ifInUcastPkts

       64 bit unsigned wrappable counter."
   ::= {pr1646v2EfmVlanMCD7PEntry 83886080}

pr1646v2EfmVlanMCD7PIfInNUCPkts OBJECT-TYPE
   SYNTAX      Counter64
   MAX-ACCESS  read-only
   STATUS      current
   DESCRIPTION
      "Path: efm.performance.vlan.mibCounters.d7Performance.ifInNUcastPkts

       64 bit unsigned wrappable counter."
   ::= {pr1646v2EfmVlanMCD7PEntry 100663296}

pr1646v2EfmVlanMCD7PIfInBCPkts OBJECT-TYPE
   SYNTAX      Counter64
   MAX-ACCESS  read-only
   STATUS      current
   DESCRIPTION
      "Path: efm.performance.vlan.mibCounters.d7Performance.ifInBcastPkts

       64 bit unsigned wrappable counter."
   ::= {pr1646v2EfmVlanMCD7PEntry 419430400}

pr1646v2EfmVlanMCD7PIfInMCPkts OBJECT-TYPE
   SYNTAX      Counter64
   MAX-ACCESS  read-only
   STATUS      current
   DESCRIPTION
      "Path: efm.performance.vlan.mibCounters.d7Performance.ifInMcastPkts

       64 bit unsigned wrappable counter."
   ::= {pr1646v2EfmVlanMCD7PEntry 436207616}

pr1646v2EfmVlanMCD7PIfInDiscards OBJECT-TYPE
   SYNTAX      Counter64
   MAX-ACCESS  read-only
   STATUS      current
   DESCRIPTION
      "Path: efm.performance.vlan.mibCounters.d7Performance.ifInDiscards

       64 bit unsigned wrappable counter."
   ::= {pr1646v2EfmVlanMCD7PEntry 117440512}

pr1646v2EfmVlanMCD7PIfInErrors OBJECT-TYPE
   SYNTAX      Counter64
   MAX-ACCESS  read-only
   STATUS      current
   DESCRIPTION
      "Path: efm.performance.vlan.mibCounters.d7Performance.ifInErrors

       64 bit unsigned wrappable counter."
   ::= {pr1646v2EfmVlanMCD7PEntry 134217728}

pr1646v2EfmVlanMCD7PIfInUnkwn OBJECT-TYPE
   SYNTAX      Counter64
   MAX-ACCESS  read-only
   STATUS      current
   DESCRIPTION
      "Path: efm.performance.vlan.mibCounters.d7Performance.ifInUnknownProtos

       64 bit unsigned wrappable counter."
   ::= {pr1646v2EfmVlanMCD7PEntry 150994944}

pr1646v2EfmVlanMCD7PInDropEx OBJECT-TYPE
   SYNTAX      Counter64
   MAX-ACCESS  read-only
   STATUS      current
   DESCRIPTION
      "Path: efm.performance.vlan.mibCounters.d7Performance.ifInDropLevelExceeded

       64 bit unsigned wrappable counter."
   ::= {pr1646v2EfmVlanMCD7PEntry 335544320}

pr1646v2EfmVlanMCD7PInDropNoMac OBJECT-TYPE
   SYNTAX      Counter64
   MAX-ACCESS  read-only
   STATUS      current
   DESCRIPTION
      "Path: efm.performance.vlan.mibCounters.d7Performance.fInDiscardsNoMacFit

       64 bit unsigned wrappable counter."
   ::= {pr1646v2EfmVlanMCD7PEntry 301989888}

pr1646v2EfmVlanMCD7PInDropNUCast OBJECT-TYPE
   SYNTAX      Counter64
   MAX-ACCESS  read-only
   STATUS      current
   DESCRIPTION
      "Path: efm.performance.vlan.mibCounters.d7Performance.fInDiscardsNUCast

       64 bit unsigned wrappable counter."
   ::= {pr1646v2EfmVlanMCD7PEntry 318767104}

pr1646v2EfmVlanMCD7PInDropFilter OBJECT-TYPE
   SYNTAX      Counter64
   MAX-ACCESS  read-only
   STATUS      current
   DESCRIPTION
      "Path: efm.performance.vlan.mibCounters.d7Performance.fInDiscardsFilter

       64 bit unsigned wrappable counter."
   ::= {pr1646v2EfmVlanMCD7PEntry 385875968}

pr1646v2EfmVlanMCD7PIfInBandwidth OBJECT-TYPE
   SYNTAX      Integer32
   MAX-ACCESS  read-only
   STATUS      current
   DESCRIPTION
      "Path: efm.performance.vlan.mibCounters.d7Performance.ifInBandwidth

       unit name = bps
       formula = 8 * ; 8 /"
   ::= {pr1646v2EfmVlanMCD7PEntry 268435456}

pr1646v2EfmVlanMCD7PIfOutOctets OBJECT-TYPE
   SYNTAX      Counter64
   MAX-ACCESS  read-only
   STATUS      current
   DESCRIPTION
      "Path: efm.performance.vlan.mibCounters.d7Performance.ifOutOctets

       64 bit unsigned wrappable counter."
   ::= {pr1646v2EfmVlanMCD7PEntry 167772160}

pr1646v2EfmVlanMCD7PIfOutUCPkts OBJECT-TYPE
   SYNTAX      Counter64
   MAX-ACCESS  read-only
   STATUS      current
   DESCRIPTION
      "Path: efm.performance.vlan.mibCounters.d7Performance.ifOutUcastPkts

       64 bit unsigned wrappable counter."
   ::= {pr1646v2EfmVlanMCD7PEntry 184549376}

pr1646v2EfmVlanMCD7PIfOutNUCPkts OBJECT-TYPE
   SYNTAX      Counter64
   MAX-ACCESS  read-only
   STATUS      current
   DESCRIPTION
      "Path: efm.performance.vlan.mibCounters.d7Performance.ifOutNUcastPkts

       64 bit unsigned wrappable counter."
   ::= {pr1646v2EfmVlanMCD7PEntry 201326592}

pr1646v2EfmVlanMCD7PIfOutBCPkts OBJECT-TYPE
   SYNTAX      Counter64
   MAX-ACCESS  read-only
   STATUS      current
   DESCRIPTION
      "Path: efm.performance.vlan.mibCounters.d7Performance.ifOutBcastPkts

       64 bit unsigned wrappable counter."
   ::= {pr1646v2EfmVlanMCD7PEntry 452984832}

pr1646v2EfmVlanMCD7PIfOutMCPkts OBJECT-TYPE
   SYNTAX      Counter64
   MAX-ACCESS  read-only
   STATUS      current
   DESCRIPTION
      "Path: efm.performance.vlan.mibCounters.d7Performance.ifOutMcastPkts

       64 bit unsigned wrappable counter."
   ::= {pr1646v2EfmVlanMCD7PEntry 469762048}

pr1646v2EfmVlanMCD7PIfOutDiscards OBJECT-TYPE
   SYNTAX      Counter64
   MAX-ACCESS  read-only
   STATUS      current
   DESCRIPTION
      "Path: efm.performance.vlan.mibCounters.d7Performance.ifOutDiscards

       64 bit unsigned wrappable counter."
   ::= {pr1646v2EfmVlanMCD7PEntry 218103808}

pr1646v2EfmVlanMCD7PIfOutErrors OBJECT-TYPE
   SYNTAX      Counter64
   MAX-ACCESS  read-only
   STATUS      current
   DESCRIPTION
      "Path: efm.performance.vlan.mibCounters.d7Performance.ifOutErrors

       64 bit unsigned wrappable counter."
   ::= {pr1646v2EfmVlanMCD7PEntry 234881024}

pr1646v2EfmVlanMCD7POutDropEx OBJECT-TYPE
   SYNTAX      Counter64
   MAX-ACCESS  read-only
   STATUS      current
   DESCRIPTION
      "Path: efm.performance.vlan.mibCounters.d7Performance.ifOutDropLevelExceeded

       64 bit unsigned wrappable counter."
   ::= {pr1646v2EfmVlanMCD7PEntry 352321536}

pr1646v2EfmVlanMCD7POutDropNoArp OBJECT-TYPE
   SYNTAX      Counter64
   MAX-ACCESS  read-only
   STATUS      current
   DESCRIPTION
      "Path: efm.performance.vlan.mibCounters.d7Performance.ifOutDiscardsNoArp

       64 bit unsigned wrappable counter."
   ::= {pr1646v2EfmVlanMCD7PEntry 369098752}

pr1646v2EfmVlanMCD7POutDropFilter OBJECT-TYPE
   SYNTAX      Counter64
   MAX-ACCESS  read-only
   STATUS      current
   DESCRIPTION
      "Path: efm.performance.vlan.mibCounters.d7Performance.ifOutDiscardsFilter

       64 bit unsigned wrappable counter."
   ::= {pr1646v2EfmVlanMCD7PEntry 402653184}

pr1646v2EfmVlanMCD7PIfOutBandwidth OBJECT-TYPE
   SYNTAX      Integer32
   MAX-ACCESS  read-only
   STATUS      current
   DESCRIPTION
      "Path: efm.performance.vlan.mibCounters.d7Performance.ifOutBandwidth

       unit name = bps
       formula = 8 * ; 8 /"
   ::= {pr1646v2EfmVlanMCD7PEntry 285212672}

pr1646v2EfmVlanMCD7PIfErrSec OBJECT-TYPE
   SYNTAX      Counter32
   MAX-ACCESS  read-only
   STATUS      current
   DESCRIPTION
      "Path: efm.performance.vlan.mibCounters.d7Performance.ifErrSec

       32 bit unsigned wrappable counter."
   ::= {pr1646v2EfmVlanMCD7PEntry 251658240}

pr1646v2EfmVlanInPQs OBJECT-TYPE
   SYNTAX      SEQUENCE OF Pr1646v2EfmVlanInPQsEntry
   MAX-ACCESS  not-accessible
   STATUS      current
   DESCRIPTION
      ""
   ::= {pr1646v2EfmVlan 100663296}

pr1646v2EfmVlanInPQsEntry OBJECT-TYPE
   SYNTAX      Pr1646v2EfmVlanInPQsEntry
   MAX-ACCESS  not-accessible
   STATUS      current
   DESCRIPTION
      ""
   INDEX      { pr1646v2EfmVlanTableIx,
                pr1646v2EfmVlanInPQsTableIx }
   ::= {pr1646v2EfmVlanInPQs 1}

Pr1646v2EfmVlanInPQsEntry ::=
   SEQUENCE
      {
      pr1646v2EfmVlanInPQsTableIx
         TableIndex,
      pr1646v2EfmVlanInPQsName
         INTEGER,
      pr1646v2EfmVlanInPQsLength
         Integer32,
      pr1646v2EfmVlanInPQsOctetLength
         Integer32,
      pr1646v2EfmVlanInPQsRedLength
         Integer32,
      pr1646v2EfmVlanInPQsPacketsTotal
         Counter64,
      pr1646v2EfmVlanInPQsPacketsDirectTx
         Counter64,
      pr1646v2EfmVlanInPQsPacketsQueued
         Counter64,
      pr1646v2EfmVlanInPQsPacketsDropped
         Counter64,
      pr1646v2EfmVlanInPQsPacketsRedDropped
         Counter64,
      pr1646v2EfmVlanInPQsPacketsCirTx
         Counter64,
      pr1646v2EfmVlanInPQsPacketsEirTx
         Counter64,
      pr1646v2EfmVlanInPQsPacketsViolateTx
         Counter64,
      pr1646v2EfmVlanInPQsOctetsTotal
         Counter64,
      pr1646v2EfmVlanInPQsOctetsDirectTx
         Counter64,
      pr1646v2EfmVlanInPQsOctetsQueued
         Counter64,
      pr1646v2EfmVlanInPQsOctetsDropped
         Counter64,
      pr1646v2EfmVlanInPQsOctetsRedDropped
         Counter64,
      pr1646v2EfmVlanInPQsOctetsCirTx
         Counter64,
      pr1646v2EfmVlanInPQsOctetsEirTx
         Counter64,
      pr1646v2EfmVlanInPQsOctetsViolateTx
         Counter64,
      pr1646v2EfmVlanInPQsOctetsBandwidth15sec
         Integer32,
      pr1646v2EfmVlanInPQsOctetsBandwidth30sec
         Integer32,
      pr1646v2EfmVlanInPQsOctetsBandwidth1min
         Integer32,
      pr1646v2EfmVlanInPQsOctetsBandwidth2min
         Integer32,
      pr1646v2EfmVlanInPQsOctetsBandwidth5min
         Integer32
      }

pr1646v2EfmVlanInPQsTableIx OBJECT-TYPE
   SYNTAX      TableIndex
   MAX-ACCESS  not-accessible
   STATUS      current
   DESCRIPTION
      ""
   ::= {pr1646v2EfmVlanInPQsEntry 11}

pr1646v2EfmVlanInPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: efm.performance.vlan.inPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2EfmVlanInPQsEntry 16777216}

pr1646v2EfmVlanInPQsLength OBJECT-TYPE
   SYNTAX      Integer32
   MAX-ACCESS  read-only
   STATUS      current
   DESCRIPTION
      "Path: efm.performance.vlan.inPriorityQueues.length"
   ::= {pr1646v2EfmVlanInPQsEntry 33554432}

pr1646v2EfmVlanInPQsOctetLength OBJECT-TYPE
   SYNTAX      Integer32
   MAX-ACCESS  read-only
   STATUS      current
   DESCRIPTION
      "Path: efm.performance.vlan.inPriorityQueues.octetLength"
   ::= {pr1646v2EfmVlanInPQsEntry 150994944}

pr1646v2EfmVlanInPQsRedLength OBJECT-TYPE
   SYNTAX      Integer32
   MAX-ACCESS  read-only
   STATUS      current
   DESCRIPTION
      "Path: efm.performance.vlan.inPriorityQueues.redLength"
   ::= {pr1646v2EfmVlanInPQsEntry 134217728}

pr1646v2EfmVlanInPQsPacketsTotal OBJECT-TYPE
   SYNTAX      Counter64
   MAX-ACCESS  read-only
   STATUS      current
   DESCRIPTION
      "Path: efm.performance.vlan.inPriorityQueues.packets.total

       64 bit unsigned wrappable counter."
   ::= {pr1646v2EfmVlanInPQsEntry 50790400}

pr1646v2EfmVlanInPQsPacketsDirectTx OBJECT-TYPE
   SYNTAX      Counter64
   MAX-ACCESS  read-only
   STATUS      current
   DESCRIPTION
      "Path: efm.performance.vlan.inPriorityQueues.packets.directTx

       64 bit unsigned wrappable counter."
   ::= {pr1646v2EfmVlanInPQsEntry 50397184}

pr1646v2EfmVlanInPQsPacketsQueued OBJECT-TYPE
   SYNTAX      Counter64
   MAX-ACCESS  read-only
   STATUS      current
   DESCRIPTION
      "Path: efm.performance.vlan.inPriorityQueues.packets.queued

       64 bit unsigned wrappable counter."
   ::= {pr1646v2EfmVlanInPQsEntry 50462720}

pr1646v2EfmVlanInPQsPacketsDropped OBJECT-TYPE
   SYNTAX      Counter64
   MAX-ACCESS  read-only
   STATUS      current
   DESCRIPTION
      "Path: efm.performance.vlan.inPriorityQueues.packets.dropped

       64 bit unsigned wrappable counter."
   ::= {pr1646v2EfmVlanInPQsEntry 50528256}

pr1646v2EfmVlanInPQsPacketsRedDropped OBJECT-TYPE
   SYNTAX      Counter64
   MAX-ACCESS  read-only
   STATUS      current
   DESCRIPTION
      "Path: efm.performance.vlan.inPriorityQueues.packets.redDropped

       64 bit unsigned wrappable counter."
   ::= {pr1646v2EfmVlanInPQsEntry 50724864}

pr1646v2EfmVlanInPQsPacketsCirTx OBJECT-TYPE
   SYNTAX      Counter64
   MAX-ACCESS  read-only
   STATUS      current
   DESCRIPTION
      "Path: efm.performance.vlan.inPriorityQueues.packets.cirTx

       64 bit unsigned wrappable counter."
   ::= {pr1646v2EfmVlanInPQsEntry 50593792}

pr1646v2EfmVlanInPQsPacketsEirTx OBJECT-TYPE
   SYNTAX      Counter64
   MAX-ACCESS  read-only
   STATUS      current
   DESCRIPTION
      "Path: efm.performance.vlan.inPriorityQueues.packets.eirTx

       64 bit unsigned wrappable counter."
   ::= {pr1646v2EfmVlanInPQsEntry 50659328}

pr1646v2EfmVlanInPQsPacketsViolateTx OBJECT-TYPE
   SYNTAX      Counter64
   MAX-ACCESS  read-only
   STATUS      current
   DESCRIPTION
      "Path: efm.performance.vlan.inPriorityQueues.packets.violateTx

       64 bit unsigned wrappable counter."
   ::= {pr1646v2EfmVlanInPQsEntry 50855936}

pr1646v2EfmVlanInPQsOctetsTotal OBJECT-TYPE
   SYNTAX      Counter64
   MAX-ACCESS  read-only
   STATUS      current
   DESCRIPTION
      "Path: efm.performance.vlan.inPriorityQueues.octets.total

       64 bit unsigned wrappable counter."
   ::= {pr1646v2EfmVlanInPQsEntry 67567616}

pr1646v2EfmVlanInPQsOctetsDirectTx OBJECT-TYPE
   SYNTAX      Counter64
   MAX-ACCESS  read-only
   STATUS      current
   DESCRIPTION
      "Path: efm.performance.vlan.inPriorityQueues.octets.directTx

       64 bit unsigned wrappable counter."
   ::= {pr1646v2EfmVlanInPQsEntry 67174400}

pr1646v2EfmVlanInPQsOctetsQueued OBJECT-TYPE
   SYNTAX      Counter64
   MAX-ACCESS  read-only
   STATUS      current
   DESCRIPTION
      "Path: efm.performance.vlan.inPriorityQueues.octets.queued

       64 bit unsigned wrappable counter."
   ::= {pr1646v2EfmVlanInPQsEntry 67239936}

pr1646v2EfmVlanInPQsOctetsDropped OBJECT-TYPE
   SYNTAX      Counter64
   MAX-ACCESS  read-only
   STATUS      current
   DESCRIPTION
      "Path: efm.performance.vlan.inPriorityQueues.octets.dropped

       64 bit unsigned wrappable counter."
   ::= {pr1646v2EfmVlanInPQsEntry 67305472}

pr1646v2EfmVlanInPQsOctetsRedDropped OBJECT-TYPE
   SYNTAX      Counter64
   MAX-ACCESS  read-only
   STATUS      current
   DESCRIPTION
      "Path: efm.performance.vlan.inPriorityQueues.octets.redDropped

       64 bit unsigned wrappable counter."
   ::= {pr1646v2EfmVlanInPQsEntry 67502080}

pr1646v2EfmVlanInPQsOctetsCirTx OBJECT-TYPE
   SYNTAX      Counter64
   MAX-ACCESS  read-only
   STATUS      current
   DESCRIPTION
      "Path: efm.performance.vlan.inPriorityQueues.octets.cirTx

       64 bit unsigned wrappable counter."
   ::= {pr1646v2EfmVlanInPQsEntry 67371008}

pr1646v2EfmVlanInPQsOctetsEirTx OBJECT-TYPE
   SYNTAX      Counter64
   MAX-ACCESS  read-only
   STATUS      current
   DESCRIPTION
      "Path: efm.performance.vlan.inPriorityQueues.octets.eirTx

       64 bit unsigned wrappable counter."
   ::= {pr1646v2EfmVlanInPQsEntry 67436544}

pr1646v2EfmVlanInPQsOctetsViolateTx OBJECT-TYPE
   SYNTAX      Counter64
   MAX-ACCESS  read-only
   STATUS      current
   DESCRIPTION
      "Path: efm.performance.vlan.inPriorityQueues.octets.violateTx

       64 bit unsigned wrappable counter."
   ::= {pr1646v2EfmVlanInPQsEntry 67633152}

pr1646v2EfmVlanInPQsOctetsBandwidth15sec OBJECT-TYPE
   SYNTAX      Integer32
   MAX-ACCESS  read-only
   STATUS      current
   DESCRIPTION
      "Path: efm.performance.vlan.inPriorityQueues.octets.bandwidth.15sec

       unit name = bps
       formula = 8 * ; 8 /"
   ::= {pr1646v2EfmVlanInPQsEntry 70386944}

pr1646v2EfmVlanInPQsOctetsBandwidth30sec OBJECT-TYPE
   SYNTAX      Integer32
   MAX-ACCESS  read-only
   STATUS      current
   DESCRIPTION
      "Path: efm.performance.vlan.inPriorityQueues.octets.bandwidth.30sec

       unit name = bps
       formula = 8 * ; 8 /"
   ::= {pr1646v2EfmVlanInPQsEntry 70388224}

pr1646v2EfmVlanInPQsOctetsBandwidth1min OBJECT-TYPE
   SYNTAX      Integer32
   MAX-ACCESS  read-only
   STATUS      current
   DESCRIPTION
      "Path: efm.performance.vlan.inPriorityQueues.octets.bandwidth.1min

       unit name = bps
       formula = 8 * ; 8 /"
   ::= {pr1646v2EfmVlanInPQsEntry 70390784}

pr1646v2EfmVlanInPQsOctetsBandwidth2min OBJECT-TYPE
   SYNTAX      Integer32
   MAX-ACCESS  read-only
   STATUS      current
   DESCRIPTION
      "Path: efm.performance.vlan.inPriorityQueues.octets.bandwidth.2min

       unit name = bps
       formula = 8 * ; 8 /"
   ::= {pr1646v2EfmVlanInPQsEntry 70395904}

pr1646v2EfmVlanInPQsOctetsBandwidth5min OBJECT-TYPE
   SYNTAX      Integer32
   MAX-ACCESS  read-only
   STATUS      current
   DESCRIPTION
      "Path: efm.performance.vlan.inPriorityQueues.octets.bandwidth.5min

       unit name = bps
       formula = 8 * ; 8 /"
   ::= {pr1646v2EfmVlanInPQsEntry 70411264}

pr1646v2EfmVlanInPQsH2Performance OBJECT-TYPE
   SYNTAX      SEQUENCE OF Pr1646v2EfmVlanInPQsH2PerformanceEntry
   MAX-ACCESS  not-accessible
   STATUS      current
   DESCRIPTION
      ""
   ::= {pr1646v2EfmVlan 100990976}

pr1646v2EfmVlanInPQsH2PerformanceEntry OBJECT-TYPE
   SYNTAX      Pr1646v2EfmVlanInPQsH2PerformanceEntry
   MAX-ACCESS  not-accessible
   STATUS      current
   DESCRIPTION
      ""
   INDEX      { pr1646v2EfmVlanTableIx,
                pr1646v2EfmVlanInPQsTableIx,
                pr1646v2EfmVlanInPQsH2PerformanceTableIx }
   ::= {pr1646v2EfmVlanInPQsH2Performance 1}

Pr1646v2EfmVlanInPQsH2PerformanceEntry ::=
   SEQUENCE
      {
      pr1646v2EfmVlanInPQsH2PerformanceTableIx
         TableIndex,
      pr1646v2EfmVlanInPQsH2PerformanceSysUpTime
         TimeTicks,
      pr1646v2EfmVlanInPQsH2PerformanceTotPkts
         Counter64,
      pr1646v2EfmVlanInPQsH2PerformanceDirTxPkts
         Counter64,
      pr1646v2EfmVlanInPQsH2PerformanceQdPkts
         Counter64,
      pr1646v2EfmVlanInPQsH2PerformanceDropPkts
         Counter64,
      pr1646v2EfmVlanInPQsH2PerformanceRDropPkts
         Counter64,
      pr1646v2EfmVlanInPQsH2PerformanceCirTxPkts
         Counter64,
      pr1646v2EfmVlanInPQsH2PerformanceEirTxPkts
         Counter64,
      pr1646v2EfmVlanInPQsH2PerformanceViolTxPkts
         Counter64,
      pr1646v2EfmVlanInPQsH2PerformanceTotOcts
         Counter64,
      pr1646v2EfmVlanInPQsH2PerformanceDirTxOcts
         Counter64,
      pr1646v2EfmVlanInPQsH2PerformanceQdOcts
         Counter64,
      pr1646v2EfmVlanInPQsH2PerformanceDropOcts
         Counter64,
      pr1646v2EfmVlanInPQsH2PerformanceRDropOcts
         Counter64,
      pr1646v2EfmVlanInPQsH2PerformanceCirTxOcts
         Counter64,
      pr1646v2EfmVlanInPQsH2PerformanceEirTxOcts
         Counter64,
      pr1646v2EfmVlanInPQsH2PerformanceViolTxOcts
         Counter64,
      pr1646v2EfmVlanInPQsH2PerformanceBandwidth
         Integer32
      }

pr1646v2EfmVlanInPQsH2PerformanceTableIx OBJECT-TYPE
   SYNTAX      TableIndex
   MAX-ACCESS  not-accessible
   STATUS      current
   DESCRIPTION
      ""
   ::= {pr1646v2EfmVlanInPQsH2PerformanceEntry 11}

pr1646v2EfmVlanInPQsH2PerformanceSysUpTime OBJECT-TYPE
   SYNTAX      TimeTicks
   MAX-ACCESS  read-only
   STATUS      current
   DESCRIPTION
      "Path: efm.performance.vlan.inPriorityQueues.h2Performance.sysUpTime

       Time in centi-second."
   ::= {pr1646v2EfmVlanInPQsH2PerformanceEntry 16777216}

pr1646v2EfmVlanInPQsH2PerformanceTotPkts OBJECT-TYPE
   SYNTAX      Counter64
   MAX-ACCESS  read-only
   STATUS      current
   DESCRIPTION
      "Path: efm.performance.vlan.inPriorityQueues.h2Performance.totalPkts

       64 bit unsigned wrappable counter."
   ::= {pr1646v2EfmVlanInPQsH2PerformanceEntry 234881024}

pr1646v2EfmVlanInPQsH2PerformanceDirTxPkts OBJECT-TYPE
   SYNTAX      Counter64
   MAX-ACCESS  read-only
   STATUS      current
   DESCRIPTION
      "Path: efm.performance.vlan.inPriorityQueues.h2Performance.directTxPkts

       64 bit unsigned wrappable counter."
   ::= {pr1646v2EfmVlanInPQsH2PerformanceEntry 33554432}

pr1646v2EfmVlanInPQsH2PerformanceQdPkts OBJECT-TYPE
   SYNTAX      Counter64
   MAX-ACCESS  read-only
   STATUS      current
   DESCRIPTION
      "Path: efm.performance.vlan.inPriorityQueues.h2Performance.queuedPkts

       64 bit unsigned wrappable counter."
   ::= {pr1646v2EfmVlanInPQsH2PerformanceEntry 50331648}

pr1646v2EfmVlanInPQsH2PerformanceDropPkts OBJECT-TYPE
   SYNTAX      Counter64
   MAX-ACCESS  read-only
   STATUS      current
   DESCRIPTION
      "Path: efm.performance.vlan.inPriorityQueues.h2Performance.droppedPkts

       64 bit unsigned wrappable counter."
   ::= {pr1646v2EfmVlanInPQsH2PerformanceEntry 67108864}

pr1646v2EfmVlanInPQsH2PerformanceRDropPkts OBJECT-TYPE
   SYNTAX      Counter64
   MAX-ACCESS  read-only
   STATUS      current
   DESCRIPTION
      "Path: efm.performance.vlan.inPriorityQueues.h2Performance.redDroppedPkts

       64 bit unsigned wrappable counter."
   ::= {pr1646v2EfmVlanInPQsH2PerformanceEntry 201326592}

pr1646v2EfmVlanInPQsH2PerformanceCirTxPkts OBJECT-TYPE
   SYNTAX      Counter64
   MAX-ACCESS  read-only
   STATUS      current
   DESCRIPTION
      "Path: efm.performance.vlan.inPriorityQueues.h2Performance.cirTxPkts

       64 bit unsigned wrappable counter."
   ::= {pr1646v2EfmVlanInPQsH2PerformanceEntry 83886080}

pr1646v2EfmVlanInPQsH2PerformanceEirTxPkts OBJECT-TYPE
   SYNTAX      Counter64
   MAX-ACCESS  read-only
   STATUS      current
   DESCRIPTION
      "Path: efm.performance.vlan.inPriorityQueues.h2Performance.eirTxPkts

       64 bit unsigned wrappable counter."
   ::= {pr1646v2EfmVlanInPQsH2PerformanceEntry 100663296}

pr1646v2EfmVlanInPQsH2PerformanceViolTxPkts OBJECT-TYPE
   SYNTAX      Counter64
   MAX-ACCESS  read-only
   STATUS      current
   DESCRIPTION
      "Path: efm.performance.vlan.inPriorityQueues.h2Performance.violateTxPkts

       64 bit unsigned wrappable counter."
   ::= {pr1646v2EfmVlanInPQsH2PerformanceEntry 301989888}

pr1646v2EfmVlanInPQsH2PerformanceTotOcts OBJECT-TYPE
   SYNTAX      Counter64
   MAX-ACCESS  read-only
   STATUS      current
   DESCRIPTION
      "Path: efm.performance.vlan.inPriorityQueues.h2Performance.totalOctets

       64 bit unsigned wrappable counter."
   ::= {pr1646v2EfmVlanInPQsH2PerformanceEntry 251658240}

pr1646v2EfmVlanInPQsH2PerformanceDirTxOcts OBJECT-TYPE
   SYNTAX      Counter64
   MAX-ACCESS  read-only
   STATUS      current
   DESCRIPTION
      "Path: efm.performance.vlan.inPriorityQueues.h2Performance.directTxOctets

       64 bit unsigned wrappable counter."
   ::= {pr1646v2EfmVlanInPQsH2PerformanceEntry 117440512}

pr1646v2EfmVlanInPQsH2PerformanceQdOcts OBJECT-TYPE
   SYNTAX      Counter64
   MAX-ACCESS  read-only
   STATUS      current
   DESCRIPTION
      "Path: efm.performance.vlan.inPriorityQueues.h2Performance.queuedOctets

       64 bit unsigned wrappable counter."
   ::= {pr1646v2EfmVlanInPQsH2PerformanceEntry 134217728}

pr1646v2EfmVlanInPQsH2PerformanceDropOcts OBJECT-TYPE
   SYNTAX      Counter64
   MAX-ACCESS  read-only
   STATUS      current
   DESCRIPTION
      "Path: efm.performance.vlan.inPriorityQueues.h2Performance.droppedOctets

       64 bit unsigned wrappable counter."
   ::= {pr1646v2EfmVlanInPQsH2PerformanceEntry 150994944}

pr1646v2EfmVlanInPQsH2PerformanceRDropOcts OBJECT-TYPE
   SYNTAX      Counter64
   MAX-ACCESS  read-only
   STATUS      current
   DESCRIPTION
      "Path: efm.performance.vlan.inPriorityQueues.h2Performance.redDroppedOctets

       64 bit unsigned wrappable counter."
   ::= {pr1646v2EfmVlanInPQsH2PerformanceEntry 218103808}

pr1646v2EfmVlanInPQsH2PerformanceCirTxOcts OBJECT-TYPE
   SYNTAX      Counter64
   MAX-ACCESS  read-only
   STATUS      current
   DESCRIPTION
      "Path: efm.performance.vlan.inPriorityQueues.h2Performance.cirTxOctets

       64 bit unsigned wrappable counter."
   ::= {pr1646v2EfmVlanInPQsH2PerformanceEntry 167772160}

pr1646v2EfmVlanInPQsH2PerformanceEirTxOcts OBJECT-TYPE
   SYNTAX      Counter64
   MAX-ACCESS  read-only
   STATUS      current
   DESCRIPTION
      "Path: efm.performance.vlan.inPriorityQueues.h2Performance.eirTxOctets

       64 bit unsigned wrappable counter."
   ::= {pr1646v2EfmVlanInPQsH2PerformanceEntry 184549376}

pr1646v2EfmVlanInPQsH2PerformanceViolTxOcts OBJECT-TYPE
   SYNTAX      Counter64
   MAX-ACCESS  read-only
   STATUS      current
   DESCRIPTION
      "Path: efm.performance.vlan.inPriorityQueues.h2Performance.violateTxOctets

       64 bit unsigned wrappable counter."
   ::= {pr1646v2EfmVlanInPQsH2PerformanceEntry 318767104}

pr1646v2EfmVlanInPQsH2PerformanceBandwidth OBJECT-TYPE
   SYNTAX      Integer32
   MAX-ACCESS  read-only
   STATUS      current
   DESCRIPTION
      "Path: efm.performance.vlan.inPriorityQueues.h2Performance.bandwidth

       unit name = bps
       formula = 8 * ; 8 /"
   ::= {pr1646v2EfmVlanInPQsH2PerformanceEntry 268435456}

pr1646v2EfmVlanInPQsH24Performance OBJECT-TYPE
   SYNTAX      SEQUENCE OF Pr1646v2EfmVlanInPQsH24PerformanceEntry
   MAX-ACCESS  not-accessible
   STATUS      current
   DESCRIPTION
      ""
   ::= {pr1646v2EfmVlan 101056512}

pr1646v2EfmVlanInPQsH24PerformanceEntry OBJECT-TYPE
   SYNTAX      Pr1646v2EfmVlanInPQsH24PerformanceEntry
   MAX-ACCESS  not-accessible
   STATUS      current
   DESCRIPTION
      ""
   INDEX      { pr1646v2EfmVlanTableIx,
                pr1646v2EfmVlanInPQsTableIx,
                pr1646v2EfmVlanInPQsH24PerformanceTableIx }
   ::= {pr1646v2EfmVlanInPQsH24Performance 1}

Pr1646v2EfmVlanInPQsH24PerformanceEntry ::=
   SEQUENCE
      {
      pr1646v2EfmVlanInPQsH24PerformanceTableIx
         TableIndex,
      pr1646v2EfmVlanInPQsH24PerformanceSysUpTime
         TimeTicks,
      pr1646v2EfmVlanInPQsH24PerformanceTotPkts
         Counter64,
      pr1646v2EfmVlanInPQsH24PerformanceDirTxPkts
         Counter64,
      pr1646v2EfmVlanInPQsH24PerformanceQdPkts
         Counter64,
      pr1646v2EfmVlanInPQsH24PerformanceDropPkts
         Counter64,
      pr1646v2EfmVlanInPQsH24PerformanceRDropPkts
         Counter64,
      pr1646v2EfmVlanInPQsH24PerformanceCirTxPkts
         Counter64,
      pr1646v2EfmVlanInPQsH24PerformanceEirTxPkts
         Counter64,
      pr1646v2EfmVlanInPQsH24PerformanceViolTxPkts
         Counter64,
      pr1646v2EfmVlanInPQsH24PerformanceTotOcts
         Counter64,
      pr1646v2EfmVlanInPQsH24PerformanceDirTxOcts
         Counter64,
      pr1646v2EfmVlanInPQsH24PerformanceQdOcts
         Counter64,
      pr1646v2EfmVlanInPQsH24PerformanceDropOcts
         Counter64,
      pr1646v2EfmVlanInPQsH24PerformanceRDropOcts
         Counter64,
      pr1646v2EfmVlanInPQsH24PerformanceCirTxOcts
         Counter64,
      pr1646v2EfmVlanInPQsH24PerformanceEirTxOcts
         Counter64,
      pr1646v2EfmVlanInPQsH24PerformanceViolTxOcts
         Counter64,
      pr1646v2EfmVlanInPQsH24PerformanceBandwidth
         Integer32
      }

pr1646v2EfmVlanInPQsH24PerformanceTableIx OBJECT-TYPE
   SYNTAX      TableIndex
   MAX-ACCESS  not-accessible
   STATUS      current
   DESCRIPTION
      ""
   ::= {pr1646v2EfmVlanInPQsH24PerformanceEntry 11}

pr1646v2EfmVlanInPQsH24PerformanceSysUpTime OBJECT-TYPE
   SYNTAX      TimeTicks
   MAX-ACCESS  read-only
   STATUS      current
   DESCRIPTION
      "Path: efm.performance.vlan.inPriorityQueues.h24Performance.sysUpTime

       Time in centi-second."
   ::= {pr1646v2EfmVlanInPQsH24PerformanceEntry 16777216}

pr1646v2EfmVlanInPQsH24PerformanceTotPkts OBJECT-TYPE
   SYNTAX      Counter64
   MAX-ACCESS  read-only
   STATUS      current
   DESCRIPTION
      "Path: efm.performance.vlan.inPriorityQueues.h24Performance.totalPkts

       64 bit unsigned wrappable counter."
   ::= {pr1646v2EfmVlanInPQsH24PerformanceEntry 234881024}

pr1646v2EfmVlanInPQsH24PerformanceDirTxPkts OBJECT-TYPE
   SYNTAX      Counter64
   MAX-ACCESS  read-only
   STATUS      current
   DESCRIPTION
      "Path: efm.performance.vlan.inPriorityQueues.h24Performance.directTxPkts

       64 bit unsigned wrappable counter."
   ::= {pr1646v2EfmVlanInPQsH24PerformanceEntry 33554432}

pr1646v2EfmVlanInPQsH24PerformanceQdPkts OBJECT-TYPE
   SYNTAX      Counter64
   MAX-ACCESS  read-only
   STATUS      current
   DESCRIPTION
      "Path: efm.performance.vlan.inPriorityQueues.h24Performance.queuedPkts

       64 bit unsigned wrappable counter."
   ::= {pr1646v2EfmVlanInPQsH24PerformanceEntry 50331648}

pr1646v2EfmVlanInPQsH24PerformanceDropPkts OBJECT-TYPE
   SYNTAX      Counter64
   MAX-ACCESS  read-only
   STATUS      current
   DESCRIPTION
      "Path: efm.performance.vlan.inPriorityQueues.h24Performance.droppedPkts

       64 bit unsigned wrappable counter."
   ::= {pr1646v2EfmVlanInPQsH24PerformanceEntry 67108864}

pr1646v2EfmVlanInPQsH24PerformanceRDropPkts OBJECT-TYPE
   SYNTAX      Counter64
   MAX-ACCESS  read-only
   STATUS      current
   DESCRIPTION
      "Path: efm.performance.vlan.inPriorityQueues.h24Performance.redDroppedPkts

       64 bit unsigned wrappable counter."
   ::= {pr1646v2EfmVlanInPQsH24PerformanceEntry 201326592}

pr1646v2EfmVlanInPQsH24PerformanceCirTxPkts OBJECT-TYPE
   SYNTAX      Counter64
   MAX-ACCESS  read-only
   STATUS      current
   DESCRIPTION
      "Path: efm.performance.vlan.inPriorityQueues.h24Performance.cirTxPkts

       64 bit unsigned wrappable counter."
   ::= {pr1646v2EfmVlanInPQsH24PerformanceEntry 83886080}

pr1646v2EfmVlanInPQsH24PerformanceEirTxPkts OBJECT-TYPE
   SYNTAX      Counter64
   MAX-ACCESS  read-only
   STATUS      current
   DESCRIPTION
      "Path: efm.performance.vlan.inPriorityQueues.h24Performance.eirTxPkts

       64 bit unsigned wrappable counter."
   ::= {pr1646v2EfmVlanInPQsH24PerformanceEntry 100663296}

pr1646v2EfmVlanInPQsH24PerformanceViolTxPkts OBJECT-TYPE
   SYNTAX      Counter64
   MAX-ACCESS  read-only
   STATUS      current
   DESCRIPTION
      "Path: efm.performance.vlan.inPriorityQueues.h24Performance.violateTxPkts

       64 bit unsigned wrappable counter."
   ::= {pr1646v2EfmVlanInPQsH24PerformanceEntry 301989888}

pr1646v2EfmVlanInPQsH24PerformanceTotOcts OBJECT-TYPE
   SYNTAX      Counter64
   MAX-ACCESS  read-only
   STATUS      current
   DESCRIPTION
      "Path: efm.performance.vlan.inPriorityQueues.h24Performance.totalOctets

       64 bit unsigned wrappable counter."
   ::= {pr1646v2EfmVlanInPQsH24PerformanceEntry 251658240}

pr1646v2EfmVlanInPQsH24PerformanceDirTxOcts OBJECT-TYPE
   SYNTAX      Counter64
   MAX-ACCESS  read-only
   STATUS      current
   DESCRIPTION
      "Path: efm.performance.vlan.inPriorityQueues.h24Performance.directTxOctets

       64 bit unsigned wrappable counter."
   ::= {pr1646v2EfmVlanInPQsH24PerformanceEntry 117440512}

pr1646v2EfmVlanInPQsH24PerformanceQdOcts OBJECT-TYPE
   SYNTAX      Counter64
   MAX-ACCESS  read-only
   STATUS      current
   DESCRIPTION
      "Path: efm.performance.vlan.inPriorityQueues.h24Performance.queuedOctets

       64 bit unsigned wrappable counter."
   ::= {pr1646v2EfmVlanInPQsH24PerformanceEntry 134217728}

pr1646v2EfmVlanInPQsH24PerformanceDropOcts OBJECT-TYPE
   SYNTAX      Counter64
   MAX-ACCESS  read-only
   STATUS      current
   DESCRIPTION
      "Path: efm.performance.vlan.inPriorityQueues.h24Performance.droppedOctets

       64 bit unsigned wrappable counter."
   ::= {pr1646v2EfmVlanInPQsH24PerformanceEntry 150994944}

pr1646v2EfmVlanInPQsH24PerformanceRDropOcts OBJECT-TYPE
   SYNTAX      Counter64
   MAX-ACCESS  read-only
   STATUS      current
   DESCRIPTION
      "Path: efm.performance.vlan.inPriorityQueues.h24Performance.redDroppedOctets

       64 bit unsigned wrappable counter."
   ::= {pr1646v2EfmVlanInPQsH24PerformanceEntry 218103808}

pr1646v2EfmVlanInPQsH24PerformanceCirTxOcts OBJECT-TYPE
   SYNTAX      Counter64
   MAX-ACCESS  read-only
   STATUS      current
   DESCRIPTION
      "Path: efm.performance.vlan.inPriorityQueues.h24Performance.cirTxOctets

       64 bit unsigned wrappable counter."
   ::= {pr1646v2EfmVlanInPQsH24PerformanceEntry 167772160}

pr1646v2EfmVlanInPQsH24PerformanceEirTxOcts OBJECT-TYPE
   SYNTAX      Counter64
   MAX-ACCESS  read-only
   STATUS      current
   DESCRIPTION
      "Path: efm.performance.vlan.inPriorityQueues.h24Performance.eirTxOctets

       64 bit unsigned wrappable counter."
   ::= {pr1646v2EfmVlanInPQsH24PerformanceEntry 184549376}

pr1646v2EfmVlanInPQsH24PerformanceViolTxOcts OBJECT-TYPE
   SYNTAX      Counter64
   MAX-ACCESS  read-only
   STATUS      current
   DESCRIPTION
      "Path: efm.performance.vlan.inPriorityQueues.h24Performance.violateTxOctets

       64 bit unsigned wrappable counter."
   ::= {pr1646v2EfmVlanInPQsH24PerformanceEntry 318767104}

pr1646v2EfmVlanInPQsH24PerformanceBandwidth OBJECT-TYPE
   SYNTAX      Integer32
   MAX-ACCESS  read-only
   STATUS      current
   DESCRIPTION
      "Path: efm.performance.vlan.inPriorityQueues.h24Performance.bandwidth

       unit name = bps
       formula = 8 * ; 8 /"
   ::= {pr1646v2EfmVlanInPQsH24PerformanceEntry 268435456}

pr1646v2EfmVlanInPQsD7Performance OBJECT-TYPE
   SYNTAX      SEQUENCE OF Pr1646v2EfmVlanInPQsD7PerformanceEntry
   MAX-ACCESS  not-accessible
   STATUS      current
   DESCRIPTION
      ""
   ::= {pr1646v2EfmVlan 101122048}

pr1646v2EfmVlanInPQsD7PerformanceEntry OBJECT-TYPE
   SYNTAX      Pr1646v2EfmVlanInPQsD7PerformanceEntry
   MAX-ACCESS  not-accessible
   STATUS      current
   DESCRIPTION
      ""
   INDEX      { pr1646v2EfmVlanTableIx,
                pr1646v2EfmVlanInPQsTableIx,
                pr1646v2EfmVlanInPQsD7PerformanceTableIx }
   ::= {pr1646v2EfmVlanInPQsD7Performance 1}

Pr1646v2EfmVlanInPQsD7PerformanceEntry ::=
   SEQUENCE
      {
      pr1646v2EfmVlanInPQsD7PerformanceTableIx
         TableIndex,
      pr1646v2EfmVlanInPQsD7PerformanceSysUpTime
         TimeTicks,
      pr1646v2EfmVlanInPQsD7PerformanceTotPkts
         Counter64,
      pr1646v2EfmVlanInPQsD7PerformanceDirTxPkts
         Counter64,
      pr1646v2EfmVlanInPQsD7PerformanceQdPkts
         Counter64,
      pr1646v2EfmVlanInPQsD7PerformanceDropPkts
         Counter64,
      pr1646v2EfmVlanInPQsD7PerformanceRDropPkts
         Counter64,
      pr1646v2EfmVlanInPQsD7PerformanceCirTxPkts
         Counter64,
      pr1646v2EfmVlanInPQsD7PerformanceEirTxPkts
         Counter64,
      pr1646v2EfmVlanInPQsD7PerformanceViolTxPkts
         Counter64,
      pr1646v2EfmVlanInPQsD7PerformanceTotOcts
         Counter64,
      pr1646v2EfmVlanInPQsD7PerformanceDirTxOcts
         Counter64,
      pr1646v2EfmVlanInPQsD7PerformanceQdOcts
         Counter64,
      pr1646v2EfmVlanInPQsD7PerformanceDropOcts
         Counter64,
      pr1646v2EfmVlanInPQsD7PerformanceRDropOcts
         Counter64,
      pr1646v2EfmVlanInPQsD7PerformanceCirTxOcts
         Counter64,
      pr1646v2EfmVlanInPQsD7PerformanceEirTxOcts
         Counter64,
      pr1646v2EfmVlanInPQsD7PerformanceViolTxOcts
         Counter64,
      pr1646v2EfmVlanInPQsD7PerformanceBandwidth
         Integer32
      }

pr1646v2EfmVlanInPQsD7PerformanceTableIx OBJECT-TYPE
   SYNTAX      TableIndex
   MAX-ACCESS  not-accessible
   STATUS      current
   DESCRIPTION
      ""
   ::= {pr1646v2EfmVlanInPQsD7PerformanceEntry 11}

pr1646v2EfmVlanInPQsD7PerformanceSysUpTime OBJECT-TYPE
   SYNTAX      TimeTicks
   MAX-ACCESS  read-only
   STATUS      current
   DESCRIPTION
      "Path: efm.performance.vlan.inPriorityQueues.d7Performance.sysUpTime

       Time in centi-second."
   ::= {pr1646v2EfmVlanInPQsD7PerformanceEntry 16777216}

pr1646v2EfmVlanInPQsD7PerformanceTotPkts OBJECT-TYPE
   SYNTAX      Counter64
   MAX-ACCESS  read-only
   STATUS      current
   DESCRIPTION
      "Path: efm.performance.vlan.inPriorityQueues.d7Performance.totalPkts

       64 bit unsigned wrappable counter."
   ::= {pr1646v2EfmVlanInPQsD7PerformanceEntry 234881024}

pr1646v2EfmVlanInPQsD7PerformanceDirTxPkts OBJECT-TYPE
   SYNTAX      Counter64
   MAX-ACCESS  read-only
   STATUS      current
   DESCRIPTION
      "Path: efm.performance.vlan.inPriorityQueues.d7Performance.directTxPkts

       64 bit unsigned wrappable counter."
   ::= {pr1646v2EfmVlanInPQsD7PerformanceEntry 33554432}

pr1646v2EfmVlanInPQsD7PerformanceQdPkts OBJECT-TYPE
   SYNTAX      Counter64
   MAX-ACCESS  read-only
   STATUS      current
   DESCRIPTION
      "Path: efm.performance.vlan.inPriorityQueues.d7Performance.queuedPkts

       64 bit unsigned wrappable counter."
   ::= {pr1646v2EfmVlanInPQsD7PerformanceEntry 50331648}

pr1646v2EfmVlanInPQsD7PerformanceDropPkts OBJECT-TYPE
   SYNTAX      Counter64
   MAX-ACCESS  read-only
   STATUS      current
   DESCRIPTION
      "Path: efm.performance.vlan.inPriorityQueues.d7Performance.droppedPkts

       64 bit unsigned wrappable counter."
   ::= {pr1646v2EfmVlanInPQsD7PerformanceEntry 67108864}

pr1646v2EfmVlanInPQsD7PerformanceRDropPkts OBJECT-TYPE
   SYNTAX      Counter64
   MAX-ACCESS  read-only
   STATUS      current
   DESCRIPTION
      "Path: efm.performance.vlan.inPriorityQueues.d7Performance.redDroppedPkts

       64 bit unsigned wrappable counter."
   ::= {pr1646v2EfmVlanInPQsD7PerformanceEntry 201326592}

pr1646v2EfmVlanInPQsD7PerformanceCirTxPkts OBJECT-TYPE
   SYNTAX      Counter64
   MAX-ACCESS  read-only
   STATUS      current
   DESCRIPTION
      "Path: efm.performance.vlan.inPriorityQueues.d7Performance.cirTxPkts

       64 bit unsigned wrappable counter."
   ::= {pr1646v2EfmVlanInPQsD7PerformanceEntry 83886080}

pr1646v2EfmVlanInPQsD7PerformanceEirTxPkts OBJECT-TYPE
   SYNTAX      Counter64
   MAX-ACCESS  read-only
   STATUS      current
   DESCRIPTION
      "Path: efm.performance.vlan.inPriorityQueues.d7Performance.eirTxPkts

       64 bit unsigned wrappable counter."
   ::= {pr1646v2EfmVlanInPQsD7PerformanceEntry 100663296}

pr1646v2EfmVlanInPQsD7PerformanceViolTxPkts OBJECT-TYPE
   SYNTAX      Counter64
   MAX-ACCESS  read-only
   STATUS      current
   DESCRIPTION
      "Path: efm.performance.vlan.inPriorityQueues.d7Performance.violateTxPkts

       64 bit unsigned wrappable counter."
   ::= {pr1646v2EfmVlanInPQsD7PerformanceEntry 301989888}

pr1646v2EfmVlanInPQsD7PerformanceTotOcts OBJECT-TYPE
   SYNTAX      Counter64
   MAX-ACCESS  read-only
   STATUS      current
   DESCRIPTION
      "Path: efm.performance.vlan.inPriorityQueues.d7Performance.totalOctets

       64 bit unsigned wrappable counter."
   ::= {pr1646v2EfmVlanInPQsD7PerformanceEntry 251658240}

pr1646v2EfmVlanInPQsD7PerformanceDirTxOcts OBJECT-TYPE
   SYNTAX      Counter64
   MAX-ACCESS  read-only
   STATUS      current
   DESCRIPTION
      "Path: efm.performance.vlan.inPriorityQueues.d7Performance.directTxOctets

       64 bit unsigned wrappable counter."
   ::= {pr1646v2EfmVlanInPQsD7PerformanceEntry 117440512}

pr1646v2EfmVlanInPQsD7PerformanceQdOcts OBJECT-TYPE
   SYNTAX      Counter64
   MAX-ACCESS  read-only
   STATUS      current
   DESCRIPTION
      "Path: efm.performance.vlan.inPriorityQueues.d7Performance.queuedOctets

       64 bit unsigned wrappable counter."
   ::= {pr1646v2EfmVlanInPQsD7PerformanceEntry 134217728}

pr1646v2EfmVlanInPQsD7PerformanceDropOcts OBJECT-TYPE
   SYNTAX      Counter64
   MAX-ACCESS  read-only
   STATUS      current
   DESCRIPTION
      "Path: efm.performance.vlan.inPriorityQueues.d7Performance.droppedOctets

       64 bit unsigned wrappable counter."
   ::= {pr1646v2EfmVlanInPQsD7PerformanceEntry 150994944}

pr1646v2EfmVlanInPQsD7PerformanceRDropOcts OBJECT-TYPE
   SYNTAX      Counter64
   MAX-ACCESS  read-only
   STATUS      current
   DESCRIPTION
      "Path: efm.performance.vlan.inPriorityQueues.d7Performance.redDroppedOctets

       64 bit unsigned wrappable counter."
   ::= {pr1646v2EfmVlanInPQsD7PerformanceEntry 218103808}

pr1646v2EfmVlanInPQsD7PerformanceCirTxOcts OBJECT-TYPE
   SYNTAX      Counter64
   MAX-ACCESS  read-only
   STATUS      current
   DESCRIPTION
      "Path: efm.performance.vlan.inPriorityQueues.d7Performance.cirTxOctets

       64 bit unsigned wrappable counter."
   ::= {pr1646v2EfmVlanInPQsD7PerformanceEntry 167772160}

pr1646v2EfmVlanInPQsD7PerformanceEirTxOcts OBJECT-TYPE
   SYNTAX      Counter64
   MAX-ACCESS  read-only
   STATUS      current
   DESCRIPTION
      "Path: efm.performance.vlan.inPriorityQueues.d7Performance.eirTxOctets

       64 bit unsigned wrappable counter."
   ::= {pr1646v2EfmVlanInPQsD7PerformanceEntry 184549376}

pr1646v2EfmVlanInPQsD7PerformanceViolTxOcts OBJECT-TYPE
   SYNTAX      Counter64
   MAX-ACCESS  read-only
   STATUS      current
   DESCRIPTION
      "Path: efm.performance.vlan.inPriorityQueues.d7Performance.violateTxOctets

       64 bit unsigned wrappable counter."
   ::= {pr1646v2EfmVlanInPQsD7PerformanceEntry 318767104}

pr1646v2EfmVlanInPQsD7PerformanceBandwidth OBJECT-TYPE
   SYNTAX      Integer32
   MAX-ACCESS  read-only
   STATUS      current
   DESCRIPTION
      "Path: efm.performance.vlan.inPriorityQueues.d7Performance.bandwidth

       unit name = bps
       formula = 8 * ; 8 /"
   ::= {pr1646v2EfmVlanInPQsD7PerformanceEntry 268435456}

pr1646v2EfmVlanOutPQs OBJECT-TYPE
   SYNTAX      SEQUENCE OF Pr1646v2EfmVlanOutPQsEntry
   MAX-ACCESS  not-accessible
   STATUS      current
   DESCRIPTION
      ""
   ::= {pr1646v2EfmVlan 83886080}

pr1646v2EfmVlanOutPQsEntry OBJECT-TYPE
   SYNTAX      Pr1646v2EfmVlanOutPQsEntry
   MAX-ACCESS  not-accessible
   STATUS      current
   DESCRIPTION
      ""
   INDEX      { pr1646v2EfmVlanTableIx,
                pr1646v2EfmVlanOutPQsTableIx }
   ::= {pr1646v2EfmVlanOutPQs 1}

Pr1646v2EfmVlanOutPQsEntry ::=
   SEQUENCE
      {
      pr1646v2EfmVlanOutPQsTableIx
         TableIndex,
      pr1646v2EfmVlanOutPQsName
         INTEGER,
      pr1646v2EfmVlanOutPQsLength
         Integer32,
      pr1646v2EfmVlanOutPQsOctetLength
         Integer32,
      pr1646v2EfmVlanOutPQsRedLength
         Integer32,
      pr1646v2EfmVlanOutPQsPacketsTotal
         Counter64,
      pr1646v2EfmVlanOutPQsPacketsDirectTx
         Counter64,
      pr1646v2EfmVlanOutPQsPacketsQueued
         Counter64,
      pr1646v2EfmVlanOutPQsPacketsDropped
         Counter64,
      pr1646v2EfmVlanOutPQsPacketsRedDropped
         Counter64,
      pr1646v2EfmVlanOutPQsPacketsCirTx
         Counter64,
      pr1646v2EfmVlanOutPQsPacketsEirTx
         Counter64,
      pr1646v2EfmVlanOutPQsPacketsViolateTx
         Counter64,
      pr1646v2EfmVlanOutPQsOctetsTotal
         Counter64,
      pr1646v2EfmVlanOutPQsOctetsDirectTx
         Counter64,
      pr1646v2EfmVlanOutPQsOctetsQueued
         Counter64,
      pr1646v2EfmVlanOutPQsOctetsDropped
         Counter64,
      pr1646v2EfmVlanOutPQsOctetsRedDropped
         Counter64,
      pr1646v2EfmVlanOutPQsOctetsCirTx
         Counter64,
      pr1646v2EfmVlanOutPQsOctetsEirTx
         Counter64,
      pr1646v2EfmVlanOutPQsOctetsViolateTx
         Counter64,
      pr1646v2EfmVlanOutPQsOctetsBandwidth15sec
         Integer32,
      pr1646v2EfmVlanOutPQsOctetsBandwidth30sec
         Integer32,
      pr1646v2EfmVlanOutPQsOctetsBandwidth1min
         Integer32,
      pr1646v2EfmVlanOutPQsOctetsBandwidth2min
         Integer32,
      pr1646v2EfmVlanOutPQsOctetsBandwidth5min
         Integer32
      }

pr1646v2EfmVlanOutPQsTableIx OBJECT-TYPE
   SYNTAX      TableIndex
   MAX-ACCESS  not-accessible
   STATUS      current
   DESCRIPTION
      ""
   ::= {pr1646v2EfmVlanOutPQsEntry 11}

pr1646v2EfmVlanOutPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: efm.performance.vlan.outPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2EfmVlanOutPQsEntry 16777216}

pr1646v2EfmVlanOutPQsLength OBJECT-TYPE
   SYNTAX      Integer32
   MAX-ACCESS  read-only
   STATUS      current
   DESCRIPTION
      "Path: efm.performance.vlan.outPriorityQueues.length"
   ::= {pr1646v2EfmVlanOutPQsEntry 33554432}

pr1646v2EfmVlanOutPQsOctetLength OBJECT-TYPE
   SYNTAX      Integer32
   MAX-ACCESS  read-only
   STATUS      current
   DESCRIPTION
      "Path: efm.performance.vlan.outPriorityQueues.octetLength"
   ::= {pr1646v2EfmVlanOutPQsEntry 150994944}

pr1646v2EfmVlanOutPQsRedLength OBJECT-TYPE
   SYNTAX      Integer32
   MAX-ACCESS  read-only
   STATUS      current
   DESCRIPTION
      "Path: efm.performance.vlan.outPriorityQueues.redLength"
   ::= {pr1646v2EfmVlanOutPQsEntry 134217728}

pr1646v2EfmVlanOutPQsPacketsTotal OBJECT-TYPE
   SYNTAX      Counter64
   MAX-ACCESS  read-only
   STATUS      current
   DESCRIPTION
      "Path: efm.performance.vlan.outPriorityQueues.packets.total

       64 bit unsigned wrappable counter."
   ::= {pr1646v2EfmVlanOutPQsEntry 50790400}

pr1646v2EfmVlanOutPQsPacketsDirectTx OBJECT-TYPE
   SYNTAX      Counter64
   MAX-ACCESS  read-only
   STATUS      current
   DESCRIPTION
      "Path: efm.performance.vlan.outPriorityQueues.packets.directTx

       64 bit unsigned wrappable counter."
   ::= {pr1646v2EfmVlanOutPQsEntry 50397184}

pr1646v2EfmVlanOutPQsPacketsQueued OBJECT-TYPE
   SYNTAX      Counter64
   MAX-ACCESS  read-only
   STATUS      current
   DESCRIPTION
      "Path: efm.performance.vlan.outPriorityQueues.packets.queued

       64 bit unsigned wrappable counter."
   ::= {pr1646v2EfmVlanOutPQsEntry 50462720}

pr1646v2EfmVlanOutPQsPacketsDropped OBJECT-TYPE
   SYNTAX      Counter64
   MAX-ACCESS  read-only
   STATUS      current
   DESCRIPTION
      "Path: efm.performance.vlan.outPriorityQueues.packets.dropped

       64 bit unsigned wrappable counter."
   ::= {pr1646v2EfmVlanOutPQsEntry 50528256}

pr1646v2EfmVlanOutPQsPacketsRedDropped OBJECT-TYPE
   SYNTAX      Counter64
   MAX-ACCESS  read-only
   STATUS      current
   DESCRIPTION
      "Path: efm.performance.vlan.outPriorityQueues.packets.redDropped

       64 bit unsigned wrappable counter."
   ::= {pr1646v2EfmVlanOutPQsEntry 50724864}

pr1646v2EfmVlanOutPQsPacketsCirTx OBJECT-TYPE
   SYNTAX      Counter64
   MAX-ACCESS  read-only
   STATUS      current
   DESCRIPTION
      "Path: efm.performance.vlan.outPriorityQueues.packets.cirTx

       64 bit unsigned wrappable counter."
   ::= {pr1646v2EfmVlanOutPQsEntry 50593792}

pr1646v2EfmVlanOutPQsPacketsEirTx OBJECT-TYPE
   SYNTAX      Counter64
   MAX-ACCESS  read-only
   STATUS      current
   DESCRIPTION
      "Path: efm.performance.vlan.outPriorityQueues.packets.eirTx

       64 bit unsigned wrappable counter."
   ::= {pr1646v2EfmVlanOutPQsEntry 50659328}

pr1646v2EfmVlanOutPQsPacketsViolateTx OBJECT-TYPE
   SYNTAX      Counter64
   MAX-ACCESS  read-only
   STATUS      current
   DESCRIPTION
      "Path: efm.performance.vlan.outPriorityQueues.packets.violateTx

       64 bit unsigned wrappable counter."
   ::= {pr1646v2EfmVlanOutPQsEntry 50855936}

pr1646v2EfmVlanOutPQsOctetsTotal OBJECT-TYPE
   SYNTAX      Counter64
   MAX-ACCESS  read-only
   STATUS      current
   DESCRIPTION
      "Path: efm.performance.vlan.outPriorityQueues.octets.total

       64 bit unsigned wrappable counter."
   ::= {pr1646v2EfmVlanOutPQsEntry 67567616}

pr1646v2EfmVlanOutPQsOctetsDirectTx OBJECT-TYPE
   SYNTAX      Counter64
   MAX-ACCESS  read-only
   STATUS      current
   DESCRIPTION
      "Path: efm.performance.vlan.outPriorityQueues.octets.directTx

       64 bit unsigned wrappable counter."
   ::= {pr1646v2EfmVlanOutPQsEntry 67174400}

pr1646v2EfmVlanOutPQsOctetsQueued OBJECT-TYPE
   SYNTAX      Counter64
   MAX-ACCESS  read-only
   STATUS      current
   DESCRIPTION
      "Path: efm.performance.vlan.outPriorityQueues.octets.queued

       64 bit unsigned wrappable counter."
   ::= {pr1646v2EfmVlanOutPQsEntry 67239936}

pr1646v2EfmVlanOutPQsOctetsDropped OBJECT-TYPE
   SYNTAX      Counter64
   MAX-ACCESS  read-only
   STATUS      current
   DESCRIPTION
      "Path: efm.performance.vlan.outPriorityQueues.octets.dropped

       64 bit unsigned wrappable counter."
   ::= {pr1646v2EfmVlanOutPQsEntry 67305472}

pr1646v2EfmVlanOutPQsOctetsRedDropped OBJECT-TYPE
   SYNTAX      Counter64
   MAX-ACCESS  read-only
   STATUS      current
   DESCRIPTION
      "Path: efm.performance.vlan.outPriorityQueues.octets.redDropped

       64 bit unsigned wrappable counter."
   ::= {pr1646v2EfmVlanOutPQsEntry 67502080}

pr1646v2EfmVlanOutPQsOctetsCirTx OBJECT-TYPE
   SYNTAX      Counter64
   MAX-ACCESS  read-only
   STATUS      current
   DESCRIPTION
      "Path: efm.performance.vlan.outPriorityQueues.octets.cirTx

       64 bit unsigned wrappable counter."
   ::= {pr1646v2EfmVlanOutPQsEntry 67371008}

pr1646v2EfmVlanOutPQsOctetsEirTx OBJECT-TYPE
   SYNTAX      Counter64
   MAX-ACCESS  read-only
   STATUS      current
   DESCRIPTION
      "Path: efm.performance.vlan.outPriorityQueues.octets.eirTx

       64 bit unsigned wrappable counter."
   ::= {pr1646v2EfmVlanOutPQsEntry 67436544}

pr1646v2EfmVlanOutPQsOctetsViolateTx OBJECT-TYPE
   SYNTAX      Counter64
   MAX-ACCESS  read-only
   STATUS      current
   DESCRIPTION
      "Path: efm.performance.vlan.outPriorityQueues.octets.violateTx

       64 bit unsigned wrappable counter."
   ::= {pr1646v2EfmVlanOutPQsEntry 67633152}

pr1646v2EfmVlanOutPQsOctetsBandwidth15sec OBJECT-TYPE
   SYNTAX      Integer32
   MAX-ACCESS  read-only
   STATUS      current
   DESCRIPTION
      "Path: efm.performance.vlan.outPriorityQueues.octets.bandwidth.15sec

       unit name = bps
       formula = 8 * ; 8 /"
   ::= {pr1646v2EfmVlanOutPQsEntry 70386944}

pr1646v2EfmVlanOutPQsOctetsBandwidth30sec OBJECT-TYPE
   SYNTAX      Integer32
   MAX-ACCESS  read-only
   STATUS      current
   DESCRIPTION
      "Path: efm.performance.vlan.outPriorityQueues.octets.bandwidth.30sec

       unit name = bps
       formula = 8 * ; 8 /"
   ::= {pr1646v2EfmVlanOutPQsEntry 70388224}

pr1646v2EfmVlanOutPQsOctetsBandwidth1min OBJECT-TYPE
   SYNTAX      Integer32
   MAX-ACCESS  read-only
   STATUS      current
   DESCRIPTION
      "Path: efm.performance.vlan.outPriorityQueues.octets.bandwidth.1min

       unit name = bps
       formula = 8 * ; 8 /"
   ::= {pr1646v2EfmVlanOutPQsEntry 70390784}

pr1646v2EfmVlanOutPQsOctetsBandwidth2min OBJECT-TYPE
   SYNTAX      Integer32
   MAX-ACCESS  read-only
   STATUS      current
   DESCRIPTION
      "Path: efm.performance.vlan.outPriorityQueues.octets.bandwidth.2min

       unit name = bps
       formula = 8 * ; 8 /"
   ::= {pr1646v2EfmVlanOutPQsEntry 70395904}

pr1646v2EfmVlanOutPQsOctetsBandwidth5min OBJECT-TYPE
   SYNTAX      Integer32
   MAX-ACCESS  read-only
   STATUS      current
   DESCRIPTION
      "Path: efm.performance.vlan.outPriorityQueues.octets.bandwidth.5min

       unit name = bps
       formula = 8 * ; 8 /"
   ::= {pr1646v2EfmVlanOutPQsEntry 70411264}

pr1646v2EfmVlanOutPQsH2Performance OBJECT-TYPE
   SYNTAX      SEQUENCE OF Pr1646v2EfmVlanOutPQsH2PerformanceEntry
   MAX-ACCESS  not-accessible
   STATUS      current
   DESCRIPTION
      ""
   ::= {pr1646v2EfmVlan 84213760}

pr1646v2EfmVlanOutPQsH2PerformanceEntry OBJECT-TYPE
   SYNTAX      Pr1646v2EfmVlanOutPQsH2PerformanceEntry
   MAX-ACCESS  not-accessible
   STATUS      current
   DESCRIPTION
      ""
   INDEX      { pr1646v2EfmVlanTableIx,
                pr1646v2EfmVlanOutPQsTableIx,
                pr1646v2EfmVlanOutPQsH2PerformanceTableIx }
   ::= {pr1646v2EfmVlanOutPQsH2Performance 1}

Pr1646v2EfmVlanOutPQsH2PerformanceEntry ::=
   SEQUENCE
      {
      pr1646v2EfmVlanOutPQsH2PerformanceTableIx
         TableIndex,
      pr1646v2EfmVlanOutPQsH2PerformanceSysUpTime
         TimeTicks,
      pr1646v2EfmVlanOutPQsH2PerformanceTotPkts
         Counter64,
      pr1646v2EfmVlanOutPQsH2PerformanceDirTxPkts
         Counter64,
      pr1646v2EfmVlanOutPQsH2PerformanceQdPkts
         Counter64,
      pr1646v2EfmVlanOutPQsH2PerformanceDropPkts
         Counter64,
      pr1646v2EfmVlanOutPQsH2PerformanceRDropPkts
         Counter64,
      pr1646v2EfmVlanOutPQsH2PerformanceCirTxPkts
         Counter64,
      pr1646v2EfmVlanOutPQsH2PerformanceEirTxPkts
         Counter64,
      pr1646v2EfmVlanOutPQsH2PerformanceViolTxPkts
         Counter64,
      pr1646v2EfmVlanOutPQsH2PerformanceTotOcts
         Counter64,
      pr1646v2EfmVlanOutPQsH2PerformanceDirTxOcts
         Counter64,
      pr1646v2EfmVlanOutPQsH2PerformanceQdOcts
         Counter64,
      pr1646v2EfmVlanOutPQsH2PerformanceDropOcts
         Counter64,
      pr1646v2EfmVlanOutPQsH2PerformanceRDropOcts
         Counter64,
      pr1646v2EfmVlanOutPQsH2PerformanceCirTxOcts
         Counter64,
      pr1646v2EfmVlanOutPQsH2PerformanceEirTxOcts
         Counter64,
      pr1646v2EfmVlanOutPQsH2PerformanceViolTxOcts
         Counter64,
      pr1646v2EfmVlanOutPQsH2PerformanceBandwidth
         Integer32
      }

pr1646v2EfmVlanOutPQsH2PerformanceTableIx OBJECT-TYPE
   SYNTAX      TableIndex
   MAX-ACCESS  not-accessible
   STATUS      current
   DESCRIPTION
      ""
   ::= {pr1646v2EfmVlanOutPQsH2PerformanceEntry 11}

pr1646v2EfmVlanOutPQsH2PerformanceSysUpTime OBJECT-TYPE
   SYNTAX      TimeTicks
   MAX-ACCESS  read-only
   STATUS      current
   DESCRIPTION
      "Path: efm.performance.vlan.outPriorityQueues.h2Performance.sysUpTime

       Time in centi-second."
   ::= {pr1646v2EfmVlanOutPQsH2PerformanceEntry 16777216}

pr1646v2EfmVlanOutPQsH2PerformanceTotPkts OBJECT-TYPE
   SYNTAX      Counter64
   MAX-ACCESS  read-only
   STATUS      current
   DESCRIPTION
      "Path: efm.performance.vlan.outPriorityQueues.h2Performance.totalPkts

       64 bit unsigned wrappable counter."
   ::= {pr1646v2EfmVlanOutPQsH2PerformanceEntry 234881024}

pr1646v2EfmVlanOutPQsH2PerformanceDirTxPkts OBJECT-TYPE
   SYNTAX      Counter64
   MAX-ACCESS  read-only
   STATUS      current
   DESCRIPTION
      "Path: efm.performance.vlan.outPriorityQueues.h2Performance.directTxPkts

       64 bit unsigned wrappable counter."
   ::= {pr1646v2EfmVlanOutPQsH2PerformanceEntry 33554432}

pr1646v2EfmVlanOutPQsH2PerformanceQdPkts OBJECT-TYPE
   SYNTAX      Counter64
   MAX-ACCESS  read-only
   STATUS      current
   DESCRIPTION
      "Path: efm.performance.vlan.outPriorityQueues.h2Performance.queuedPkts

       64 bit unsigned wrappable counter."
   ::= {pr1646v2EfmVlanOutPQsH2PerformanceEntry 50331648}

pr1646v2EfmVlanOutPQsH2PerformanceDropPkts OBJECT-TYPE
   SYNTAX      Counter64
   MAX-ACCESS  read-only
   STATUS      current
   DESCRIPTION
      "Path: efm.performance.vlan.outPriorityQueues.h2Performance.droppedPkts

       64 bit unsigned wrappable counter."
   ::= {pr1646v2EfmVlanOutPQsH2PerformanceEntry 67108864}

pr1646v2EfmVlanOutPQsH2PerformanceRDropPkts OBJECT-TYPE
   SYNTAX      Counter64
   MAX-ACCESS  read-only
   STATUS      current
   DESCRIPTION
      "Path: efm.performance.vlan.outPriorityQueues.h2Performance.redDroppedPkts

       64 bit unsigned wrappable counter."
   ::= {pr1646v2EfmVlanOutPQsH2PerformanceEntry 201326592}

pr1646v2EfmVlanOutPQsH2PerformanceCirTxPkts OBJECT-TYPE
   SYNTAX      Counter64
   MAX-ACCESS  read-only
   STATUS      current
   DESCRIPTION
      "Path: efm.performance.vlan.outPriorityQueues.h2Performance.cirTxPkts

       64 bit unsigned wrappable counter."
   ::= {pr1646v2EfmVlanOutPQsH2PerformanceEntry 83886080}

pr1646v2EfmVlanOutPQsH2PerformanceEirTxPkts OBJECT-TYPE
   SYNTAX      Counter64
   MAX-ACCESS  read-only
   STATUS      current
   DESCRIPTION
      "Path: efm.performance.vlan.outPriorityQueues.h2Performance.eirTxPkts

       64 bit unsigned wrappable counter."
   ::= {pr1646v2EfmVlanOutPQsH2PerformanceEntry 100663296}

pr1646v2EfmVlanOutPQsH2PerformanceViolTxPkts OBJECT-TYPE
   SYNTAX      Counter64
   MAX-ACCESS  read-only
   STATUS      current
   DESCRIPTION
      "Path: efm.performance.vlan.outPriorityQueues.h2Performance.violateTxPkts

       64 bit unsigned wrappable counter."
   ::= {pr1646v2EfmVlanOutPQsH2PerformanceEntry 301989888}

pr1646v2EfmVlanOutPQsH2PerformanceTotOcts OBJECT-TYPE
   SYNTAX      Counter64
   MAX-ACCESS  read-only
   STATUS      current
   DESCRIPTION
      "Path: efm.performance.vlan.outPriorityQueues.h2Performance.totalOctets

       64 bit unsigned wrappable counter."
   ::= {pr1646v2EfmVlanOutPQsH2PerformanceEntry 251658240}

pr1646v2EfmVlanOutPQsH2PerformanceDirTxOcts OBJECT-TYPE
   SYNTAX      Counter64
   MAX-ACCESS  read-only
   STATUS      current
   DESCRIPTION
      "Path: efm.performance.vlan.outPriorityQueues.h2Performance.directTxOctets

       64 bit unsigned wrappable counter."
   ::= {pr1646v2EfmVlanOutPQsH2PerformanceEntry 117440512}

pr1646v2EfmVlanOutPQsH2PerformanceQdOcts OBJECT-TYPE
   SYNTAX      Counter64
   MAX-ACCESS  read-only
   STATUS      current
   DESCRIPTION
      "Path: efm.performance.vlan.outPriorityQueues.h2Performance.queuedOctets

       64 bit unsigned wrappable counter."
   ::= {pr1646v2EfmVlanOutPQsH2PerformanceEntry 134217728}

pr1646v2EfmVlanOutPQsH2PerformanceDropOcts OBJECT-TYPE
   SYNTAX      Counter64
   MAX-ACCESS  read-only
   STATUS      current
   DESCRIPTION
      "Path: efm.performance.vlan.outPriorityQueues.h2Performance.droppedOctets

       64 bit unsigned wrappable counter."
   ::= {pr1646v2EfmVlanOutPQsH2PerformanceEntry 150994944}

pr1646v2EfmVlanOutPQsH2PerformanceRDropOcts OBJECT-TYPE
   SYNTAX      Counter64
   MAX-ACCESS  read-only
   STATUS      current
   DESCRIPTION
      "Path: efm.performance.vlan.outPriorityQueues.h2Performance.redDroppedOctets

       64 bit unsigned wrappable counter."
   ::= {pr1646v2EfmVlanOutPQsH2PerformanceEntry 218103808}

pr1646v2EfmVlanOutPQsH2PerformanceCirTxOcts OBJECT-TYPE
   SYNTAX      Counter64
   MAX-ACCESS  read-only
   STATUS      current
   DESCRIPTION
      "Path: efm.performance.vlan.outPriorityQueues.h2Performance.cirTxOctets

       64 bit unsigned wrappable counter."
   ::= {pr1646v2EfmVlanOutPQsH2PerformanceEntry 167772160}

pr1646v2EfmVlanOutPQsH2PerformanceEirTxOcts OBJECT-TYPE
   SYNTAX      Counter64
   MAX-ACCESS  read-only
   STATUS      current
   DESCRIPTION
      "Path: efm.performance.vlan.outPriorityQueues.h2Performance.eirTxOctets

       64 bit unsigned wrappable counter."
   ::= {pr1646v2EfmVlanOutPQsH2PerformanceEntry 184549376}

pr1646v2EfmVlanOutPQsH2PerformanceViolTxOcts OBJECT-TYPE
   SYNTAX      Counter64
   MAX-ACCESS  read-only
   STATUS      current
   DESCRIPTION
      "Path: efm.performance.vlan.outPriorityQueues.h2Performance.violateTxOctets

       64 bit unsigned wrappable counter."
   ::= {pr1646v2EfmVlanOutPQsH2PerformanceEntry 318767104}

pr1646v2EfmVlanOutPQsH2PerformanceBandwidth OBJECT-TYPE
   SYNTAX      Integer32
   MAX-ACCESS  read-only
   STATUS      current
   DESCRIPTION
      "Path: efm.performance.vlan.outPriorityQueues.h2Performance.bandwidth

       unit name = bps
       formula = 8 * ; 8 /"
   ::= {pr1646v2EfmVlanOutPQsH2PerformanceEntry 268435456}

pr1646v2EfmVlanOutPQsH24Performance OBJECT-TYPE
   SYNTAX      SEQUENCE OF Pr1646v2EfmVlanOutPQsH24PerformanceEntry
   MAX-ACCESS  not-accessible
   STATUS      current
   DESCRIPTION
      ""
   ::= {pr1646v2EfmVlan 84279296}

pr1646v2EfmVlanOutPQsH24PerformanceEntry OBJECT-TYPE
   SYNTAX      Pr1646v2EfmVlanOutPQsH24PerformanceEntry
   MAX-ACCESS  not-accessible
   STATUS      current
   DESCRIPTION
      ""
   INDEX      { pr1646v2EfmVlanTableIx,
                pr1646v2EfmVlanOutPQsTableIx,
                pr1646v2EfmVlanOutPQsH24PerformanceTableIx }
   ::= {pr1646v2EfmVlanOutPQsH24Performance 1}

Pr1646v2EfmVlanOutPQsH24PerformanceEntry ::=
   SEQUENCE
      {
      pr1646v2EfmVlanOutPQsH24PerformanceTableIx
         TableIndex,
      pr1646v2EfmVlanOutPQsH24PerformanceSysUpTime
         TimeTicks,
      pr1646v2EfmVlanOutPQsH24PerformanceTotPkts
         Counter64,
      pr1646v2EfmVlanOutPQsH24PerformanceDirTxPkts
         Counter64,
      pr1646v2EfmVlanOutPQsH24PerformanceQdPkts
         Counter64,
      pr1646v2EfmVlanOutPQsH24PerformanceDropPkts
         Counter64,
      pr1646v2EfmVlanOutPQsH24PerformanceRDropPkts
         Counter64,
      pr1646v2EfmVlanOutPQsH24PerformanceCirTxPkts
         Counter64,
      pr1646v2EfmVlanOutPQsH24PerformanceEirTxPkts
         Counter64,
      pr1646v2EfmVlanOutPQsH24PerformanceViolTxPkts
         Counter64,
      pr1646v2EfmVlanOutPQsH24PerformanceTotOcts
         Counter64,
      pr1646v2EfmVlanOutPQsH24PerformanceDirTxOcts
         Counter64,
      pr1646v2EfmVlanOutPQsH24PerformanceQdOcts
         Counter64,
      pr1646v2EfmVlanOutPQsH24PerformanceDropOcts
         Counter64,
      pr1646v2EfmVlanOutPQsH24PerformanceRDropOcts
         Counter64,
      pr1646v2EfmVlanOutPQsH24PerformanceCirTxOcts
         Counter64,
      pr1646v2EfmVlanOutPQsH24PerformanceEirTxOcts
         Counter64,
      pr1646v2EfmVlanOutPQsH24PerformanceViolTxOcts
         Counter64,
      pr1646v2EfmVlanOutPQsH24PerformanceBandwidth
         Integer32
      }

pr1646v2EfmVlanOutPQsH24PerformanceTableIx OBJECT-TYPE
   SYNTAX      TableIndex
   MAX-ACCESS  not-accessible
   STATUS      current
   DESCRIPTION
      ""
   ::= {pr1646v2EfmVlanOutPQsH24PerformanceEntry 11}

pr1646v2EfmVlanOutPQsH24PerformanceSysUpTime OBJECT-TYPE
   SYNTAX      TimeTicks
   MAX-ACCESS  read-only
   STATUS      current
   DESCRIPTION
      "Path: efm.performance.vlan.outPriorityQueues.h24Performance.sysUpTime

       Time in centi-second."
   ::= {pr1646v2EfmVlanOutPQsH24PerformanceEntry 16777216}

pr1646v2EfmVlanOutPQsH24PerformanceTotPkts OBJECT-TYPE
   SYNTAX      Counter64
   MAX-ACCESS  read-only
   STATUS      current
   DESCRIPTION
      "Path: efm.performance.vlan.outPriorityQueues.h24Performance.totalPkts

       64 bit unsigned wrappable counter."
   ::= {pr1646v2EfmVlanOutPQsH24PerformanceEntry 234881024}

pr1646v2EfmVlanOutPQsH24PerformanceDirTxPkts OBJECT-TYPE
   SYNTAX      Counter64
   MAX-ACCESS  read-only
   STATUS      current
   DESCRIPTION
      "Path: efm.performance.vlan.outPriorityQueues.h24Performance.directTxPkts

       64 bit unsigned wrappable counter."
   ::= {pr1646v2EfmVlanOutPQsH24PerformanceEntry 33554432}

pr1646v2EfmVlanOutPQsH24PerformanceQdPkts OBJECT-TYPE
   SYNTAX      Counter64
   MAX-ACCESS  read-only
   STATUS      current
   DESCRIPTION
      "Path: efm.performance.vlan.outPriorityQueues.h24Performance.queuedPkts

       64 bit unsigned wrappable counter."
   ::= {pr1646v2EfmVlanOutPQsH24PerformanceEntry 50331648}

pr1646v2EfmVlanOutPQsH24PerformanceDropPkts OBJECT-TYPE
   SYNTAX      Counter64
   MAX-ACCESS  read-only
   STATUS      current
   DESCRIPTION
      "Path: efm.performance.vlan.outPriorityQueues.h24Performance.droppedPkts

       64 bit unsigned wrappable counter."
   ::= {pr1646v2EfmVlanOutPQsH24PerformanceEntry 67108864}

pr1646v2EfmVlanOutPQsH24PerformanceRDropPkts OBJECT-TYPE
   SYNTAX      Counter64
   MAX-ACCESS  read-only
   STATUS      current
   DESCRIPTION
      "Path: efm.performance.vlan.outPriorityQueues.h24Performance.redDroppedPkts

       64 bit unsigned wrappable counter."
   ::= {pr1646v2EfmVlanOutPQsH24PerformanceEntry 201326592}

pr1646v2EfmVlanOutPQsH24PerformanceCirTxPkts OBJECT-TYPE
   SYNTAX      Counter64
   MAX-ACCESS  read-only
   STATUS      current
   DESCRIPTION
      "Path: efm.performance.vlan.outPriorityQueues.h24Performance.cirTxPkts

       64 bit unsigned wrappable counter."
   ::= {pr1646v2EfmVlanOutPQsH24PerformanceEntry 83886080}

pr1646v2EfmVlanOutPQsH24PerformanceEirTxPkts OBJECT-TYPE
   SYNTAX      Counter64
   MAX-ACCESS  read-only
   STATUS      current
   DESCRIPTION
      "Path: efm.performance.vlan.outPriorityQueues.h24Performance.eirTxPkts

       64 bit unsigned wrappable counter."
   ::= {pr1646v2EfmVlanOutPQsH24PerformanceEntry 100663296}

pr1646v2EfmVlanOutPQsH24PerformanceViolTxPkts OBJECT-TYPE
   SYNTAX      Counter64
   MAX-ACCESS  read-only
   STATUS      current
   DESCRIPTION
      "Path: efm.performance.vlan.outPriorityQueues.h24Performance.violateTxPkts

       64 bit unsigned wrappable counter."
   ::= {pr1646v2EfmVlanOutPQsH24PerformanceEntry 301989888}

pr1646v2EfmVlanOutPQsH24PerformanceTotOcts OBJECT-TYPE
   SYNTAX      Counter64
   MAX-ACCESS  read-only
   STATUS      current
   DESCRIPTION
      "Path: efm.performance.vlan.outPriorityQueues.h24Performance.totalOctets

       64 bit unsigned wrappable counter."
   ::= {pr1646v2EfmVlanOutPQsH24PerformanceEntry 251658240}

pr1646v2EfmVlanOutPQsH24PerformanceDirTxOcts OBJECT-TYPE
   SYNTAX      Counter64
   MAX-ACCESS  read-only
   STATUS      current
   DESCRIPTION
      "Path: efm.performance.vlan.outPriorityQueues.h24Performance.directTxOctets

       64 bit unsigned wrappable counter."
   ::= {pr1646v2EfmVlanOutPQsH24PerformanceEntry 117440512}

pr1646v2EfmVlanOutPQsH24PerformanceQdOcts OBJECT-TYPE
   SYNTAX      Counter64
   MAX-ACCESS  read-only
   STATUS      current
   DESCRIPTION
      "Path: efm.performance.vlan.outPriorityQueues.h24Performance.queuedOctets

       64 bit unsigned wrappable counter."
   ::= {pr1646v2EfmVlanOutPQsH24PerformanceEntry 134217728}

pr1646v2EfmVlanOutPQsH24PerformanceDropOcts OBJECT-TYPE
   SYNTAX      Counter64
   MAX-ACCESS  read-only
   STATUS      current
   DESCRIPTION
      "Path: efm.performance.vlan.outPriorityQueues.h24Performance.droppedOctets

       64 bit unsigned wrappable counter."
   ::= {pr1646v2EfmVlanOutPQsH24PerformanceEntry 150994944}

pr1646v2EfmVlanOutPQsH24PerformanceRDropOcts OBJECT-TYPE
   SYNTAX      Counter64
   MAX-ACCESS  read-only
   STATUS      current
   DESCRIPTION
      "Path: efm.performance.vlan.outPriorityQueues.h24Performance.redDroppedOctets

       64 bit unsigned wrappable counter."
   ::= {pr1646v2EfmVlanOutPQsH24PerformanceEntry 218103808}

pr1646v2EfmVlanOutPQsH24PerformanceCirTxOcts OBJECT-TYPE
   SYNTAX      Counter64
   MAX-ACCESS  read-only
   STATUS      current
   DESCRIPTION
      "Path: efm.performance.vlan.outPriorityQueues.h24Performance.cirTxOctets

       64 bit unsigned wrappable counter."
   ::= {pr1646v2EfmVlanOutPQsH24PerformanceEntry 167772160}

pr1646v2EfmVlanOutPQsH24PerformanceEirTxOcts OBJECT-TYPE
   SYNTAX      Counter64
   MAX-ACCESS  read-only
   STATUS      current
   DESCRIPTION
      "Path: efm.performance.vlan.outPriorityQueues.h24Performance.eirTxOctets

       64 bit unsigned wrappable counter."
   ::= {pr1646v2EfmVlanOutPQsH24PerformanceEntry 184549376}

pr1646v2EfmVlanOutPQsH24PerformanceViolTxOcts OBJECT-TYPE
   SYNTAX      Counter64
   MAX-ACCESS  read-only
   STATUS      current
   DESCRIPTION
      "Path: efm.performance.vlan.outPriorityQueues.h24Performance.violateTxOctets

       64 bit unsigned wrappable counter."
   ::= {pr1646v2EfmVlanOutPQsH24PerformanceEntry 318767104}

pr1646v2EfmVlanOutPQsH24PerformanceBandwidth OBJECT-TYPE
   SYNTAX      Integer32
   MAX-ACCESS  read-only
   STATUS      current
   DESCRIPTION
      "Path: efm.performance.vlan.outPriorityQueues.h24Performance.bandwidth

       unit name = bps
       formula = 8 * ; 8 /"
   ::= {pr1646v2EfmVlanOutPQsH24PerformanceEntry 268435456}

pr1646v2EfmVlanOutPQsD7Performance OBJECT-TYPE
   SYNTAX      SEQUENCE OF Pr1646v2EfmVlanOutPQsD7PerformanceEntry
   MAX-ACCESS  not-accessible
   STATUS      current
   DESCRIPTION
      ""
   ::= {pr1646v2EfmVlan 84344832}

pr1646v2EfmVlanOutPQsD7PerformanceEntry OBJECT-TYPE
   SYNTAX      Pr1646v2EfmVlanOutPQsD7PerformanceEntry
   MAX-ACCESS  not-accessible
   STATUS      current
   DESCRIPTION
      ""
   INDEX      { pr1646v2EfmVlanTableIx,
                pr1646v2EfmVlanOutPQsTableIx,
                pr1646v2EfmVlanOutPQsD7PerformanceTableIx }
   ::= {pr1646v2EfmVlanOutPQsD7Performance 1}

Pr1646v2EfmVlanOutPQsD7PerformanceEntry ::=
   SEQUENCE
      {
      pr1646v2EfmVlanOutPQsD7PerformanceTableIx
         TableIndex,
      pr1646v2EfmVlanOutPQsD7PerformanceSysUpTime
         TimeTicks,
      pr1646v2EfmVlanOutPQsD7PerformanceTotPkts
         Counter64,
      pr1646v2EfmVlanOutPQsD7PerformanceDirTxPkts
         Counter64,
      pr1646v2EfmVlanOutPQsD7PerformanceQdPkts
         Counter64,
      pr1646v2EfmVlanOutPQsD7PerformanceDropPkts
         Counter64,
      pr1646v2EfmVlanOutPQsD7PerformanceRDropPkts
         Counter64,
      pr1646v2EfmVlanOutPQsD7PerformanceCirTxPkts
         Counter64,
      pr1646v2EfmVlanOutPQsD7PerformanceEirTxPkts
         Counter64,
      pr1646v2EfmVlanOutPQsD7PerformanceViolTxPkts
         Counter64,
      pr1646v2EfmVlanOutPQsD7PerformanceTotOcts
         Counter64,
      pr1646v2EfmVlanOutPQsD7PerformanceDirTxOcts
         Counter64,
      pr1646v2EfmVlanOutPQsD7PerformanceQdOcts
         Counter64,
      pr1646v2EfmVlanOutPQsD7PerformanceDropOcts
         Counter64,
      pr1646v2EfmVlanOutPQsD7PerformanceRDropOcts
         Counter64,
      pr1646v2EfmVlanOutPQsD7PerformanceCirTxOcts
         Counter64,
      pr1646v2EfmVlanOutPQsD7PerformanceEirTxOcts
         Counter64,
      pr1646v2EfmVlanOutPQsD7PerformanceViolTxOcts
         Counter64,
      pr1646v2EfmVlanOutPQsD7PerformanceBandwidth
         Integer32
      }

pr1646v2EfmVlanOutPQsD7PerformanceTableIx OBJECT-TYPE
   SYNTAX      TableIndex
   MAX-ACCESS  not-accessible
   STATUS      current
   DESCRIPTION
      ""
   ::= {pr1646v2EfmVlanOutPQsD7PerformanceEntry 11}

pr1646v2EfmVlanOutPQsD7PerformanceSysUpTime OBJECT-TYPE
   SYNTAX      TimeTicks
   MAX-ACCESS  read-only
   STATUS      current
   DESCRIPTION
      "Path: efm.performance.vlan.outPriorityQueues.d7Performance.sysUpTime

       Time in centi-second."
   ::= {pr1646v2EfmVlanOutPQsD7PerformanceEntry 16777216}

pr1646v2EfmVlanOutPQsD7PerformanceTotPkts OBJECT-TYPE
   SYNTAX      Counter64
   MAX-ACCESS  read-only
   STATUS      current
   DESCRIPTION
      "Path: efm.performance.vlan.outPriorityQueues.d7Performance.totalPkts

       64 bit unsigned wrappable counter."
   ::= {pr1646v2EfmVlanOutPQsD7PerformanceEntry 234881024}

pr1646v2EfmVlanOutPQsD7PerformanceDirTxPkts OBJECT-TYPE
   SYNTAX      Counter64
   MAX-ACCESS  read-only
   STATUS      current
   DESCRIPTION
      "Path: efm.performance.vlan.outPriorityQueues.d7Performance.directTxPkts

       64 bit unsigned wrappable counter."
   ::= {pr1646v2EfmVlanOutPQsD7PerformanceEntry 33554432}

pr1646v2EfmVlanOutPQsD7PerformanceQdPkts OBJECT-TYPE
   SYNTAX      Counter64
   MAX-ACCESS  read-only
   STATUS      current
   DESCRIPTION
      "Path: efm.performance.vlan.outPriorityQueues.d7Performance.queuedPkts

       64 bit unsigned wrappable counter."
   ::= {pr1646v2EfmVlanOutPQsD7PerformanceEntry 50331648}

pr1646v2EfmVlanOutPQsD7PerformanceDropPkts OBJECT-TYPE
   SYNTAX      Counter64
   MAX-ACCESS  read-only
   STATUS      current
   DESCRIPTION
      "Path: efm.performance.vlan.outPriorityQueues.d7Performance.droppedPkts

       64 bit unsigned wrappable counter."
   ::= {pr1646v2EfmVlanOutPQsD7PerformanceEntry 67108864}

pr1646v2EfmVlanOutPQsD7PerformanceRDropPkts OBJECT-TYPE
   SYNTAX      Counter64
   MAX-ACCESS  read-only
   STATUS      current
   DESCRIPTION
      "Path: efm.performance.vlan.outPriorityQueues.d7Performance.redDroppedPkts

       64 bit unsigned wrappable counter."
   ::= {pr1646v2EfmVlanOutPQsD7PerformanceEntry 201326592}

pr1646v2EfmVlanOutPQsD7PerformanceCirTxPkts OBJECT-TYPE
   SYNTAX      Counter64
   MAX-ACCESS  read-only
   STATUS      current
   DESCRIPTION
      "Path: efm.performance.vlan.outPriorityQueues.d7Performance.cirTxPkts

       64 bit unsigned wrappable counter."
   ::= {pr1646v2EfmVlanOutPQsD7PerformanceEntry 83886080}

pr1646v2EfmVlanOutPQsD7PerformanceEirTxPkts OBJECT-TYPE
   SYNTAX      Counter64
   MAX-ACCESS  read-only
   STATUS      current
   DESCRIPTION
      "Path: efm.performance.vlan.outPriorityQueues.d7Performance.eirTxPkts

       64 bit unsigned wrappable counter."
   ::= {pr1646v2EfmVlanOutPQsD7PerformanceEntry 100663296}

pr1646v2EfmVlanOutPQsD7PerformanceViolTxPkts OBJECT-TYPE
   SYNTAX      Counter64
   MAX-ACCESS  read-only
   STATUS      current
   DESCRIPTION
      "Path: efm.performance.vlan.outPriorityQueues.d7Performance.violateTxPkts

       64 bit unsigned wrappable counter."
   ::= {pr1646v2EfmVlanOutPQsD7PerformanceEntry 301989888}

pr1646v2EfmVlanOutPQsD7PerformanceTotOcts OBJECT-TYPE
   SYNTAX      Counter64
   MAX-ACCESS  read-only
   STATUS      current
   DESCRIPTION
      "Path: efm.performance.vlan.outPriorityQueues.d7Performance.totalOctets

       64 bit unsigned wrappable counter."
   ::= {pr1646v2EfmVlanOutPQsD7PerformanceEntry 251658240}

pr1646v2EfmVlanOutPQsD7PerformanceDirTxOcts OBJECT-TYPE
   SYNTAX      Counter64
   MAX-ACCESS  read-only
   STATUS      current
   DESCRIPTION
      "Path: efm.performance.vlan.outPriorityQueues.d7Performance.directTxOctets

       64 bit unsigned wrappable counter."
   ::= {pr1646v2EfmVlanOutPQsD7PerformanceEntry 117440512}

pr1646v2EfmVlanOutPQsD7PerformanceQdOcts OBJECT-TYPE
   SYNTAX      Counter64
   MAX-ACCESS  read-only
   STATUS      current
   DESCRIPTION
      "Path: efm.performance.vlan.outPriorityQueues.d7Performance.queuedOctets

       64 bit unsigned wrappable counter."
   ::= {pr1646v2EfmVlanOutPQsD7PerformanceEntry 134217728}

pr1646v2EfmVlanOutPQsD7PerformanceDropOcts OBJECT-TYPE
   SYNTAX      Counter64
   MAX-ACCESS  read-only
   STATUS      current
   DESCRIPTION
      "Path: efm.performance.vlan.outPriorityQueues.d7Performance.droppedOctets

       64 bit unsigned wrappable counter."
   ::= {pr1646v2EfmVlanOutPQsD7PerformanceEntry 150994944}

pr1646v2EfmVlanOutPQsD7PerformanceRDropOcts OBJECT-TYPE
   SYNTAX      Counter64
   MAX-ACCESS  read-only
   STATUS      current
   DESCRIPTION
      "Path: efm.performance.vlan.outPriorityQueues.d7Performance.redDroppedOctets

       64 bit unsigned wrappable counter."
   ::= {pr1646v2EfmVlanOutPQsD7PerformanceEntry 218103808}

pr1646v2EfmVlanOutPQsD7PerformanceCirTxOcts OBJECT-TYPE
   SYNTAX      Counter64
   MAX-ACCESS  read-only
   STATUS      current
   DESCRIPTION
      "Path: efm.performance.vlan.outPriorityQueues.d7Performance.cirTxOctets

       64 bit unsigned wrappable counter."
   ::= {pr1646v2EfmVlanOutPQsD7PerformanceEntry 167772160}

pr1646v2EfmVlanOutPQsD7PerformanceEirTxOcts OBJECT-TYPE
   SYNTAX      Counter64
   MAX-ACCESS  read-only
   STATUS      current
   DESCRIPTION
      "Path: efm.performance.vlan.outPriorityQueues.d7Performance.eirTxOctets

       64 bit unsigned wrappable counter."
   ::= {pr1646v2EfmVlanOutPQsD7PerformanceEntry 184549376}

pr1646v2EfmVlanOutPQsD7PerformanceViolTxOcts OBJECT-TYPE
   SYNTAX      Counter64
   MAX-ACCESS  read-only
   STATUS      current
   DESCRIPTION
      "Path: efm.performance.vlan.outPriorityQueues.d7Performance.violateTxOctets

       64 bit unsigned wrappable counter."
   ::= {pr1646v2EfmVlanOutPQsD7PerformanceEntry 318767104}

pr1646v2EfmVlanOutPQsD7PerformanceBandwidth OBJECT-TYPE
   SYNTAX      Integer32
   MAX-ACCESS  read-only
   STATUS      current
   DESCRIPTION
      "Path: efm.performance.vlan.outPriorityQueues.d7Performance.bandwidth

       unit name = bps
       formula = 8 * ; 8 /"
   ::= {pr1646v2EfmVlanOutPQsD7PerformanceEntry 268435456}


pr1646v2EfmPPPoE OBJECT IDENTIFIER ::= {pr1646v2Efm 53}

pr1646v2EfmPPPoESSCTable OBJECT-TYPE
   SYNTAX      SEQUENCE OF Pr1646v2EfmPPPoEEntry
   MAX-ACCESS  not-accessible
   STATUS      current
   DESCRIPTION
      ""
   ::= {pr1646v2EfmPPPoE 1}

pr1646v2EfmPPPoEEntry OBJECT-TYPE
   SYNTAX      Pr1646v2EfmPPPoEEntry
   MAX-ACCESS  not-accessible
   STATUS      current
   DESCRIPTION
      ""
   INDEX      { pr1646v2EfmPPPoETableIx }
   ::= {pr1646v2EfmPPPoESSCTable 1}

Pr1646v2EfmPPPoEEntry ::=
   SEQUENCE
      {
      pr1646v2EfmPPPoETableIx
         TableIndex,
      pr1646v2EfmPPPoEName
         DisplayString,
      pr1646v2EfmPPPoEMCInOctets
         Counter64,
      pr1646v2EfmPPPoEMCInUcast
         Counter64,
      pr1646v2EfmPPPoEMCInNUcastPkts
         Counter64,
      pr1646v2EfmPPPoEMCInBcastPkts
         Counter64,
      pr1646v2EfmPPPoEMCInMcastPkts
         Counter64,
      pr1646v2EfmPPPoEMCInDiscards
         Counter64,
      pr1646v2EfmPPPoEMCInErrors
         Counter64,
      pr1646v2EfmPPPoEMCInUnknownProtos
         Counter64,
      pr1646v2EfmPPPoEMCInDropEx
         Counter64,
      pr1646v2EfmPPPoEMCInDropNoMac
         Counter64,
      pr1646v2EfmPPPoEMCInDropNUCast
         Counter64,
      pr1646v2EfmPPPoEMCInDropFilter
         Counter64,
      pr1646v2EfmPPPoEMCInBandwidth15sec
         Integer32,
      pr1646v2EfmPPPoEMCInBandwidth30sec
         Integer32,
      pr1646v2EfmPPPoEMCInBandwidth1min
         Integer32,
      pr1646v2EfmPPPoEMCInBandwidth2min
         Integer32,
      pr1646v2EfmPPPoEMCInBandwidth5min
         Integer32,
      pr1646v2EfmPPPoEMCOutOctets
         Counter64,
      pr1646v2EfmPPPoEMCOutUcastPkts
         Counter64,
      pr1646v2EfmPPPoEMCOutNUcastPkts
         Counter64,
      pr1646v2EfmPPPoEMCOutBcastPkts
         Counter64,
      pr1646v2EfmPPPoEMCOutMcastPkts
         Counter64,
      pr1646v2EfmPPPoEMCOutDiscards
         Counter64,
      pr1646v2EfmPPPoEMCOutErrors
         Counter64,
      pr1646v2EfmPPPoEMCOutQLen
         Counter32,
      pr1646v2EfmPPPoEMCOutDropEx
         Counter64,
      pr1646v2EfmPPPoEMCOutDropNoArp
         Counter64,
      pr1646v2EfmPPPoEMCOutDropFilter
         Counter64,
      pr1646v2EfmPPPoEMCOutBandwidth15sec
         Integer32,
      pr1646v2EfmPPPoEMCOutBandwidth30sec
         Integer32,
      pr1646v2EfmPPPoEMCOutBandwidth1min
         Integer32,
      pr1646v2EfmPPPoEMCOutBandwidth2min
         Integer32,
      pr1646v2EfmPPPoEMCOutBandwidth5min
         Integer32,
      pr1646v2EfmPPPoEPppLinkMonitoringRequestsSent
         Gauge32,
      pr1646v2EfmPPPoEPppLinkMonitoringRepliesRcvd
         Gauge32,
      pr1646v2EfmPPPoEPppLinkMonitoringRequestsRcvd
         Gauge32,
      pr1646v2EfmPPPoEPppLinkMonitoringRepliesSent
         Gauge32
      }

pr1646v2EfmPPPoETableIx OBJECT-TYPE
   SYNTAX      TableIndex
   MAX-ACCESS  not-accessible
   STATUS      current
   DESCRIPTION
      ""
   ::= {pr1646v2EfmPPPoEEntry 11}

pr1646v2EfmPPPoEName OBJECT-TYPE
   SYNTAX      DisplayString
   MAX-ACCESS  read-only
   STATUS      current
   DESCRIPTION
      "Path: efm.performance.pppoEClient.name"
   ::= {pr1646v2EfmPPPoEEntry 16777216}

pr1646v2EfmPPPoEMCInOctets OBJECT-TYPE
   SYNTAX      Counter64
   MAX-ACCESS  read-only
   STATUS      current
   DESCRIPTION
      "Path: efm.performance.pppoEClient.mibCounters.ifInOctets

       64 bit unsigned wrappable counter."
   ::= {pr1646v2EfmPPPoEEntry 40697856}

pr1646v2EfmPPPoEMCInUcast OBJECT-TYPE
   SYNTAX      Counter64
   MAX-ACCESS  read-only
   STATUS      current
   DESCRIPTION
      "Path: efm.performance.pppoEClient.mibCounters.ifInUcastPkts

       64 bit unsigned wrappable counter."
   ::= {pr1646v2EfmPPPoEEntry 40763392}

pr1646v2EfmPPPoEMCInNUcastPkts OBJECT-TYPE
   SYNTAX      Counter64
   MAX-ACCESS  read-only
   STATUS      current
   DESCRIPTION
      "Path: efm.performance.pppoEClient.mibCounters.ifInNUcastPkts

       64 bit unsigned wrappable counter."
   ::= {pr1646v2EfmPPPoEEntry 40828928}

pr1646v2EfmPPPoEMCInBcastPkts OBJECT-TYPE
   SYNTAX      Counter64
   MAX-ACCESS  read-only
   STATUS      current
   DESCRIPTION
      "Path: efm.performance.pppoEClient.mibCounters.ifInBcastPkts

       64 bit unsigned wrappable counter."
   ::= {pr1646v2EfmPPPoEEntry 47382528}

pr1646v2EfmPPPoEMCInMcastPkts OBJECT-TYPE
   SYNTAX      Counter64
   MAX-ACCESS  read-only
   STATUS      current
   DESCRIPTION
      "Path: efm.performance.pppoEClient.mibCounters.ifInMcastPkts

       64 bit unsigned wrappable counter."
   ::= {pr1646v2EfmPPPoEEntry 48037888}

pr1646v2EfmPPPoEMCInDiscards OBJECT-TYPE
   SYNTAX      Counter64
   MAX-ACCESS  read-only
   STATUS      current
   DESCRIPTION
      "Path: efm.performance.pppoEClient.mibCounters.ifInDiscards

       64 bit unsigned wrappable counter."
   ::= {pr1646v2EfmPPPoEEntry 40894464}

pr1646v2EfmPPPoEMCInErrors OBJECT-TYPE
   SYNTAX      Counter64
   MAX-ACCESS  read-only
   STATUS      current
   DESCRIPTION
      "Path: efm.performance.pppoEClient.mibCounters.ifInErrors

       64 bit unsigned wrappable counter."
   ::= {pr1646v2EfmPPPoEEntry 40960000}

pr1646v2EfmPPPoEMCInUnknownProtos OBJECT-TYPE
   SYNTAX      Counter64
   MAX-ACCESS  read-only
   STATUS      current
   DESCRIPTION
      "Path: efm.performance.pppoEClient.mibCounters.ifInUnknownProtos

       64 bit unsigned wrappable counter."
   ::= {pr1646v2EfmPPPoEEntry 41025536}

pr1646v2EfmPPPoEMCInDropEx OBJECT-TYPE
   SYNTAX      Counter64
   MAX-ACCESS  read-only
   STATUS      current
   DESCRIPTION
      "Path: efm.performance.pppoEClient.mibCounters.ifInDropLevelExceeded

       64 bit unsigned wrappable counter."
   ::= {pr1646v2EfmPPPoEEntry 42074112}

pr1646v2EfmPPPoEMCInDropNoMac OBJECT-TYPE
   SYNTAX      Counter64
   MAX-ACCESS  read-only
   STATUS      current
   DESCRIPTION
      "Path: efm.performance.pppoEClient.mibCounters.ifInDiscardsNoMacFit

       64 bit unsigned wrappable counter."
   ::= {pr1646v2EfmPPPoEEntry 42270720}

pr1646v2EfmPPPoEMCInDropNUCast OBJECT-TYPE
   SYNTAX      Counter64
   MAX-ACCESS  read-only
   STATUS      current
   DESCRIPTION
      "Path: efm.performance.pppoEClient.mibCounters.ifInDiscardsNUCast

       64 bit unsigned wrappable counter."
   ::= {pr1646v2EfmPPPoEEntry 42467328}

pr1646v2EfmPPPoEMCInDropFilter OBJECT-TYPE
   SYNTAX      Counter64
   MAX-ACCESS  read-only
   STATUS      current
   DESCRIPTION
      "Path: efm.performance.pppoEClient.mibCounters.ifInDiscardsFilter

       64 bit unsigned wrappable counter."
   ::= {pr1646v2EfmPPPoEEntry 42532864}

pr1646v2EfmPPPoEMCInBandwidth15sec OBJECT-TYPE
   SYNTAX      Integer32
   MAX-ACCESS  read-only
   STATUS      current
   DESCRIPTION
      "Path: efm.performance.pppoEClient.mibCounters.ifInBandwidth.15sec

       unit name = bps
       formula = 8 * ; 8 /"
   ::= {pr1646v2EfmPPPoEEntry 45417728}

pr1646v2EfmPPPoEMCInBandwidth30sec OBJECT-TYPE
   SYNTAX      Integer32
   MAX-ACCESS  read-only
   STATUS      current
   DESCRIPTION
      "Path: efm.performance.pppoEClient.mibCounters.ifInBandwidth.30sec

       unit name = bps
       formula = 8 * ; 8 /"
   ::= {pr1646v2EfmPPPoEEntry 45419008}

pr1646v2EfmPPPoEMCInBandwidth1min OBJECT-TYPE
   SYNTAX      Integer32
   MAX-ACCESS  read-only
   STATUS      current
   DESCRIPTION
      "Path: efm.performance.pppoEClient.mibCounters.ifInBandwidth.1min

       unit name = bps
       formula = 8 * ; 8 /"
   ::= {pr1646v2EfmPPPoEEntry 45421568}

pr1646v2EfmPPPoEMCInBandwidth2min OBJECT-TYPE
   SYNTAX      Integer32
   MAX-ACCESS  read-only
   STATUS      current
   DESCRIPTION
      "Path: efm.performance.pppoEClient.mibCounters.ifInBandwidth.2min

       unit name = bps
       formula = 8 * ; 8 /"
   ::= {pr1646v2EfmPPPoEEntry 45426688}

pr1646v2EfmPPPoEMCInBandwidth5min OBJECT-TYPE
   SYNTAX      Integer32
   MAX-ACCESS  read-only
   STATUS      current
   DESCRIPTION
      "Path: efm.performance.pppoEClient.mibCounters.ifInBandwidth.5min

       unit name = bps
       formula = 8 * ; 8 /"
   ::= {pr1646v2EfmPPPoEEntry 45442048}

pr1646v2EfmPPPoEMCOutOctets OBJECT-TYPE
   SYNTAX      Counter64
   MAX-ACCESS  read-only
   STATUS      current
   DESCRIPTION
      "Path: efm.performance.pppoEClient.mibCounters.ifOutOctets

       64 bit unsigned wrappable counter."
   ::= {pr1646v2EfmPPPoEEntry 41091072}

pr1646v2EfmPPPoEMCOutUcastPkts OBJECT-TYPE
   SYNTAX      Counter64
   MAX-ACCESS  read-only
   STATUS      current
   DESCRIPTION
      "Path: efm.performance.pppoEClient.mibCounters.ifOutUcastPkts

       64 bit unsigned wrappable counter."
   ::= {pr1646v2EfmPPPoEEntry 41156608}

pr1646v2EfmPPPoEMCOutNUcastPkts OBJECT-TYPE
   SYNTAX      Counter64
   MAX-ACCESS  read-only
   STATUS      current
   DESCRIPTION
      "Path: efm.performance.pppoEClient.mibCounters.ifOutNUcastPkts

       64 bit unsigned wrappable counter."
   ::= {pr1646v2EfmPPPoEEntry 41222144}

pr1646v2EfmPPPoEMCOutBcastPkts OBJECT-TYPE
   SYNTAX      Counter64
   MAX-ACCESS  read-only
   STATUS      current
   DESCRIPTION
      "Path: efm.performance.pppoEClient.mibCounters.ifOutBcastPkts

       64 bit unsigned wrappable counter."
   ::= {pr1646v2EfmPPPoEEntry 47775744}

pr1646v2EfmPPPoEMCOutMcastPkts OBJECT-TYPE
   SYNTAX      Counter64
   MAX-ACCESS  read-only
   STATUS      current
   DESCRIPTION
      "Path: efm.performance.pppoEClient.mibCounters.ifOutMcastPkts

       64 bit unsigned wrappable counter."
   ::= {pr1646v2EfmPPPoEEntry 48431104}

pr1646v2EfmPPPoEMCOutDiscards OBJECT-TYPE
   SYNTAX      Counter64
   MAX-ACCESS  read-only
   STATUS      current
   DESCRIPTION
      "Path: efm.performance.pppoEClient.mibCounters.ifOutDiscards

       64 bit unsigned wrappable counter."
   ::= {pr1646v2EfmPPPoEEntry 41287680}

pr1646v2EfmPPPoEMCOutErrors OBJECT-TYPE
   SYNTAX      Counter64
   MAX-ACCESS  read-only
   STATUS      current
   DESCRIPTION
      "Path: efm.performance.pppoEClient.mibCounters.ifOutErrors

       64 bit unsigned wrappable counter."
   ::= {pr1646v2EfmPPPoEEntry 41353216}

pr1646v2EfmPPPoEMCOutQLen OBJECT-TYPE
   SYNTAX      Counter32
   MAX-ACCESS  read-only
   STATUS      current
   DESCRIPTION
      "Path: efm.performance.pppoEClient.mibCounters.ifOutQLen

       32 bit unsigned wrappable counter."
   ::= {pr1646v2EfmPPPoEEntry 41418752}

pr1646v2EfmPPPoEMCOutDropEx OBJECT-TYPE
   SYNTAX      Counter64
   MAX-ACCESS  read-only
   STATUS      current
   DESCRIPTION
      "Path: efm.performance.pppoEClient.mibCounters.ifOutDropLevelExceeded

       64 bit unsigned wrappable counter."
   ::= {pr1646v2EfmPPPoEEntry 41484288}

pr1646v2EfmPPPoEMCOutDropNoArp OBJECT-TYPE
   SYNTAX      Counter64
   MAX-ACCESS  read-only
   STATUS      current
   DESCRIPTION
      "Path: efm.performance.pppoEClient.mibCounters.ifOutDiscardsNoArp

       64 bit unsigned wrappable counter."
   ::= {pr1646v2EfmPPPoEEntry 42336256}

pr1646v2EfmPPPoEMCOutDropFilter OBJECT-TYPE
   SYNTAX      Counter64
   MAX-ACCESS  read-only
   STATUS      current
   DESCRIPTION
      "Path: efm.performance.pppoEClient.mibCounters.ifOutDiscardsFilter

       64 bit unsigned wrappable counter."
   ::= {pr1646v2EfmPPPoEEntry 42598400}

pr1646v2EfmPPPoEMCOutBandwidth15sec OBJECT-TYPE
   SYNTAX      Integer32
   MAX-ACCESS  read-only
   STATUS      current
   DESCRIPTION
      "Path: efm.performance.pppoEClient.mibCounters.ifOutBandwidth.15sec

       unit name = bps
       formula = 8 * ; 8 /"
   ::= {pr1646v2EfmPPPoEEntry 45483264}

pr1646v2EfmPPPoEMCOutBandwidth30sec OBJECT-TYPE
   SYNTAX      Integer32
   MAX-ACCESS  read-only
   STATUS      current
   DESCRIPTION
      "Path: efm.performance.pppoEClient.mibCounters.ifOutBandwidth.30sec

       unit name = bps
       formula = 8 * ; 8 /"
   ::= {pr1646v2EfmPPPoEEntry 45484544}

pr1646v2EfmPPPoEMCOutBandwidth1min OBJECT-TYPE
   SYNTAX      Integer32
   MAX-ACCESS  read-only
   STATUS      current
   DESCRIPTION
      "Path: efm.performance.pppoEClient.mibCounters.ifOutBandwidth.1min

       unit name = bps
       formula = 8 * ; 8 /"
   ::= {pr1646v2EfmPPPoEEntry 45487104}

pr1646v2EfmPPPoEMCOutBandwidth2min OBJECT-TYPE
   SYNTAX      Integer32
   MAX-ACCESS  read-only
   STATUS      current
   DESCRIPTION
      "Path: efm.performance.pppoEClient.mibCounters.ifOutBandwidth.2min

       unit name = bps
       formula = 8 * ; 8 /"
   ::= {pr1646v2EfmPPPoEEntry 45492224}

pr1646v2EfmPPPoEMCOutBandwidth5min OBJECT-TYPE
   SYNTAX      Integer32
   MAX-ACCESS  read-only
   STATUS      current
   DESCRIPTION
      "Path: efm.performance.pppoEClient.mibCounters.ifOutBandwidth.5min

       unit name = bps
       formula = 8 * ; 8 /"
   ::= {pr1646v2EfmPPPoEEntry 45507584}

pr1646v2EfmPPPoEPppLinkMonitoringRequestsSent OBJECT-TYPE
   SYNTAX      Gauge32
   MAX-ACCESS  read-only
   STATUS      current
   DESCRIPTION
      "Path: efm.performance.pppoEClient.ppp.linkMonitoring.requestsSent

       32 bit unsigned gauge value."
   ::= {pr1646v2EfmPPPoEEntry 50397440}

pr1646v2EfmPPPoEPppLinkMonitoringRepliesRcvd OBJECT-TYPE
   SYNTAX      Gauge32
   MAX-ACCESS  read-only
   STATUS      current
   DESCRIPTION
      "Path: efm.performance.pppoEClient.ppp.linkMonitoring.repliesRcvd

       32 bit unsigned gauge value."
   ::= {pr1646v2EfmPPPoEEntry 50397696}

pr1646v2EfmPPPoEPppLinkMonitoringRequestsRcvd OBJECT-TYPE
   SYNTAX      Gauge32
   MAX-ACCESS  read-only
   STATUS      current
   DESCRIPTION
      "Path: efm.performance.pppoEClient.ppp.linkMonitoring.requestsRcvd

       32 bit unsigned gauge value."
   ::= {pr1646v2EfmPPPoEEntry 50397952}

pr1646v2EfmPPPoEPppLinkMonitoringRepliesSent OBJECT-TYPE
   SYNTAX      Gauge32
   MAX-ACCESS  read-only
   STATUS      current
   DESCRIPTION
      "Path: efm.performance.pppoEClient.ppp.linkMonitoring.repliesSent

       32 bit unsigned gauge value."
   ::= {pr1646v2EfmPPPoEEntry 50398208}

pr1646v2EfmPPPoEMCH2P OBJECT-TYPE
   SYNTAX      SEQUENCE OF Pr1646v2EfmPPPoEMCH2PEntry
   MAX-ACCESS  not-accessible
   STATUS      current
   DESCRIPTION
      ""
   ::= {pr1646v2EfmPPPoE 41549824}

pr1646v2EfmPPPoEMCH2PEntry OBJECT-TYPE
   SYNTAX      Pr1646v2EfmPPPoEMCH2PEntry
   MAX-ACCESS  not-accessible
   STATUS      current
   DESCRIPTION
      ""
   INDEX      { pr1646v2EfmPPPoETableIx,
                pr1646v2EfmPPPoEMCH2PTableIx }
   ::= {pr1646v2EfmPPPoEMCH2P 1}

Pr1646v2EfmPPPoEMCH2PEntry ::=
   SEQUENCE
      {
      pr1646v2EfmPPPoEMCH2PTableIx
         TableIndex,
      pr1646v2EfmPPPoEMCH2PSysUpTime
         TimeTicks,
      pr1646v2EfmPPPoEMCH2PIfUpTime
         TimeTicks,
      pr1646v2EfmPPPoEMCH2PIfStatChanges
         Counter32,
      pr1646v2EfmPPPoEMCH2PIfInOctets
         Counter64,
      pr1646v2EfmPPPoEMCH2PIfInUCPkts
         Counter64,
      pr1646v2EfmPPPoEMCH2PIfInNUCPkts
         Counter64,
      pr1646v2EfmPPPoEMCH2PIfInBCPkts
         Counter64,
      pr1646v2EfmPPPoEMCH2PIfInMCPkts
         Counter64,
      pr1646v2EfmPPPoEMCH2PIfInDiscards
         Counter64,
      pr1646v2EfmPPPoEMCH2PIfInErrors
         Counter64,
      pr1646v2EfmPPPoEMCH2PIfInUnkwn
         Counter64,
      pr1646v2EfmPPPoEMCH2PInDropEx
         Counter64,
      pr1646v2EfmPPPoEMCH2PInDropNoMac
         Counter64,
      pr1646v2EfmPPPoEMCH2PInDropNUCast
         Counter64,
      pr1646v2EfmPPPoEMCH2PInDropFilter
         Counter64,
      pr1646v2EfmPPPoEMCH2PIfInBandwidth
         Integer32,
      pr1646v2EfmPPPoEMCH2PIfOutOctets
         Counter64,
      pr1646v2EfmPPPoEMCH2PIfOutUCPkts
         Counter64,
      pr1646v2EfmPPPoEMCH2PIfOutNUCPkts
         Counter64,
      pr1646v2EfmPPPoEMCH2PIfOutBCPkts
         Counter64,
      pr1646v2EfmPPPoEMCH2PIfOutMCPkts
         Counter64,
      pr1646v2EfmPPPoEMCH2PIfOutDiscards
         Counter64,
      pr1646v2EfmPPPoEMCH2PIfOutErrors
         Counter64,
      pr1646v2EfmPPPoEMCH2POutDropEx
         Counter64,
      pr1646v2EfmPPPoEMCH2POutDropNoArp
         Counter64,
      pr1646v2EfmPPPoEMCH2POutDropFilter
         Counter64,
      pr1646v2EfmPPPoEMCH2PIfOutBandwidth
         Integer32,
      pr1646v2EfmPPPoEMCH2PIfErrSec
         Counter32
      }

pr1646v2EfmPPPoEMCH2PTableIx OBJECT-TYPE
   SYNTAX      TableIndex
   MAX-ACCESS  not-accessible
   STATUS      current
   DESCRIPTION
      ""
   ::= {pr1646v2EfmPPPoEMCH2PEntry 11}

pr1646v2EfmPPPoEMCH2PSysUpTime OBJECT-TYPE
   SYNTAX      TimeTicks
   MAX-ACCESS  read-only
   STATUS      current
   DESCRIPTION
      "Path: efm.performance.pppoEClient.mibCounters.h2Performance.sysUpTime

       Time in centi-second."
   ::= {pr1646v2EfmPPPoEMCH2PEntry 16777216}

pr1646v2EfmPPPoEMCH2PIfUpTime OBJECT-TYPE
   SYNTAX      TimeTicks
   MAX-ACCESS  read-only
   STATUS      current
   DESCRIPTION
      "Path: efm.performance.pppoEClient.mibCounters.h2Performance.ifUpTime

       Time in centi-second."
   ::= {pr1646v2EfmPPPoEMCH2PEntry 33554432}

pr1646v2EfmPPPoEMCH2PIfStatChanges OBJECT-TYPE
   SYNTAX      Counter32
   MAX-ACCESS  read-only
   STATUS      current
   DESCRIPTION
      "Path: efm.performance.pppoEClient.mibCounters.h2Performance.ifStatusChanges

       32 bit unsigned wrappable counter."
   ::= {pr1646v2EfmPPPoEMCH2PEntry 50331648}

pr1646v2EfmPPPoEMCH2PIfInOctets OBJECT-TYPE
   SYNTAX      Counter64
   MAX-ACCESS  read-only
   STATUS      current
   DESCRIPTION
      "Path: efm.performance.pppoEClient.mibCounters.h2Performance.ifInOctets

       64 bit unsigned wrappable counter."
   ::= {pr1646v2EfmPPPoEMCH2PEntry 67108864}

pr1646v2EfmPPPoEMCH2PIfInUCPkts OBJECT-TYPE
   SYNTAX      Counter64
   MAX-ACCESS  read-only
   STATUS      current
   DESCRIPTION
      "Path: efm.performance.pppoEClient.mibCounters.h2Performance.ifInUcastPkts

       64 bit unsigned wrappable counter."
   ::= {pr1646v2EfmPPPoEMCH2PEntry 83886080}

pr1646v2EfmPPPoEMCH2PIfInNUCPkts OBJECT-TYPE
   SYNTAX      Counter64
   MAX-ACCESS  read-only
   STATUS      current
   DESCRIPTION
      "Path: efm.performance.pppoEClient.mibCounters.h2Performance.ifInNUcastPkts

       64 bit unsigned wrappable counter."
   ::= {pr1646v2EfmPPPoEMCH2PEntry 100663296}

pr1646v2EfmPPPoEMCH2PIfInBCPkts OBJECT-TYPE
   SYNTAX      Counter64
   MAX-ACCESS  read-only
   STATUS      current
   DESCRIPTION
      "Path: efm.performance.pppoEClient.mibCounters.h2Performance.ifInBcastPkts

       64 bit unsigned wrappable counter."
   ::= {pr1646v2EfmPPPoEMCH2PEntry 419430400}

pr1646v2EfmPPPoEMCH2PIfInMCPkts OBJECT-TYPE
   SYNTAX      Counter64
   MAX-ACCESS  read-only
   STATUS      current
   DESCRIPTION
      "Path: efm.performance.pppoEClient.mibCounters.h2Performance.ifInMcastPkts

       64 bit unsigned wrappable counter."
   ::= {pr1646v2EfmPPPoEMCH2PEntry 436207616}

pr1646v2EfmPPPoEMCH2PIfInDiscards OBJECT-TYPE
   SYNTAX      Counter64
   MAX-ACCESS  read-only
   STATUS      current
   DESCRIPTION
      "Path: efm.performance.pppoEClient.mibCounters.h2Performance.ifInDiscards

       64 bit unsigned wrappable counter."
   ::= {pr1646v2EfmPPPoEMCH2PEntry 117440512}

pr1646v2EfmPPPoEMCH2PIfInErrors OBJECT-TYPE
   SYNTAX      Counter64
   MAX-ACCESS  read-only
   STATUS      current
   DESCRIPTION
      "Path: efm.performance.pppoEClient.mibCounters.h2Performance.ifInErrors

       64 bit unsigned wrappable counter."
   ::= {pr1646v2EfmPPPoEMCH2PEntry 134217728}

pr1646v2EfmPPPoEMCH2PIfInUnkwn OBJECT-TYPE
   SYNTAX      Counter64
   MAX-ACCESS  read-only
   STATUS      current
   DESCRIPTION
      "Path: efm.performance.pppoEClient.mibCounters.h2Performance.ifInUnknownProtos

       64 bit unsigned wrappable counter."
   ::= {pr1646v2EfmPPPoEMCH2PEntry 150994944}

pr1646v2EfmPPPoEMCH2PInDropEx OBJECT-TYPE
   SYNTAX      Counter64
   MAX-ACCESS  read-only
   STATUS      current
   DESCRIPTION
      "Path: efm.performance.pppoEClient.mibCounters.h2Performance.ifInDropLevelExceeded

       64 bit unsigned wrappable counter."
   ::= {pr1646v2EfmPPPoEMCH2PEntry 335544320}

pr1646v2EfmPPPoEMCH2PInDropNoMac OBJECT-TYPE
   SYNTAX      Counter64
   MAX-ACCESS  read-only
   STATUS      current
   DESCRIPTION
      "Path: efm.performance.pppoEClient.mibCounters.h2Performance.fInDiscardsNoMacFit

       64 bit unsigned wrappable counter."
   ::= {pr1646v2EfmPPPoEMCH2PEntry 301989888}

pr1646v2EfmPPPoEMCH2PInDropNUCast OBJECT-TYPE
   SYNTAX      Counter64
   MAX-ACCESS  read-only
   STATUS      current
   DESCRIPTION
      "Path: efm.performance.pppoEClient.mibCounters.h2Performance.fInDiscardsNUCast

       64 bit unsigned wrappable counter."
   ::= {pr1646v2EfmPPPoEMCH2PEntry 318767104}

pr1646v2EfmPPPoEMCH2PInDropFilter OBJECT-TYPE
   SYNTAX      Counter64
   MAX-ACCESS  read-only
   STATUS      current
   DESCRIPTION
      "Path: efm.performance.pppoEClient.mibCounters.h2Performance.fInDiscardsFilter

       64 bit unsigned wrappable counter."
   ::= {pr1646v2EfmPPPoEMCH2PEntry 385875968}

pr1646v2EfmPPPoEMCH2PIfInBandwidth OBJECT-TYPE
   SYNTAX      Integer32
   MAX-ACCESS  read-only
   STATUS      current
   DESCRIPTION
      "Path: efm.performance.pppoEClient.mibCounters.h2Performance.ifInBandwidth

       unit name = bps
       formula = 8 * ; 8 /"
   ::= {pr1646v2EfmPPPoEMCH2PEntry 268435456}

pr1646v2EfmPPPoEMCH2PIfOutOctets OBJECT-TYPE
   SYNTAX      Counter64
   MAX-ACCESS  read-only
   STATUS      current
   DESCRIPTION
      "Path: efm.performance.pppoEClient.mibCounters.h2Performance.ifOutOctets

       64 bit unsigned wrappable counter."
   ::= {pr1646v2EfmPPPoEMCH2PEntry 167772160}

pr1646v2EfmPPPoEMCH2PIfOutUCPkts OBJECT-TYPE
   SYNTAX      Counter64
   MAX-ACCESS  read-only
   STATUS      current
   DESCRIPTION
      "Path: efm.performance.pppoEClient.mibCounters.h2Performance.ifOutUcastPkts

       64 bit unsigned wrappable counter."
   ::= {pr1646v2EfmPPPoEMCH2PEntry 184549376}

pr1646v2EfmPPPoEMCH2PIfOutNUCPkts OBJECT-TYPE
   SYNTAX      Counter64
   MAX-ACCESS  read-only
   STATUS      current
   DESCRIPTION
      "Path: efm.performance.pppoEClient.mibCounters.h2Performance.ifOutNUcastPkts

       64 bit unsigned wrappable counter."
   ::= {pr1646v2EfmPPPoEMCH2PEntry 201326592}

pr1646v2EfmPPPoEMCH2PIfOutBCPkts OBJECT-TYPE
   SYNTAX      Counter64
   MAX-ACCESS  read-only
   STATUS      current
   DESCRIPTION
      "Path: efm.performance.pppoEClient.mibCounters.h2Performance.ifOutBcastPkts

       64 bit unsigned wrappable counter."
   ::= {pr1646v2EfmPPPoEMCH2PEntry 452984832}

pr1646v2EfmPPPoEMCH2PIfOutMCPkts OBJECT-TYPE
   SYNTAX      Counter64
   MAX-ACCESS  read-only
   STATUS      current
   DESCRIPTION
      "Path: efm.performance.pppoEClient.mibCounters.h2Performance.ifOutMcastPkts

       64 bit unsigned wrappable counter."
   ::= {pr1646v2EfmPPPoEMCH2PEntry 469762048}

pr1646v2EfmPPPoEMCH2PIfOutDiscards OBJECT-TYPE
   SYNTAX      Counter64
   MAX-ACCESS  read-only
   STATUS      current
   DESCRIPTION
      "Path: efm.performance.pppoEClient.mibCounters.h2Performance.ifOutDiscards

       64 bit unsigned wrappable counter."
   ::= {pr1646v2EfmPPPoEMCH2PEntry 218103808}

pr1646v2EfmPPPoEMCH2PIfOutErrors OBJECT-TYPE
   SYNTAX      Counter64
   MAX-ACCESS  read-only
   STATUS      current
   DESCRIPTION
      "Path: efm.performance.pppoEClient.mibCounters.h2Performance.ifOutErrors

       64 bit unsigned wrappable counter."
   ::= {pr1646v2EfmPPPoEMCH2PEntry 234881024}

pr1646v2EfmPPPoEMCH2POutDropEx OBJECT-TYPE
   SYNTAX      Counter64
   MAX-ACCESS  read-only
   STATUS      current
   DESCRIPTION
      "Path: efm.performance.pppoEClient.mibCounters.h2Performance.ifOutDropLevelExceeded

       64 bit unsigned wrappable counter."
   ::= {pr1646v2EfmPPPoEMCH2PEntry 352321536}

pr1646v2EfmPPPoEMCH2POutDropNoArp OBJECT-TYPE
   SYNTAX      Counter64
   MAX-ACCESS  read-only
   STATUS      current
   DESCRIPTION
      "Path: efm.performance.pppoEClient.mibCounters.h2Performance.ifOutDiscardsNoArp

       64 bit unsigned wrappable counter."
   ::= {pr1646v2EfmPPPoEMCH2PEntry 369098752}

pr1646v2EfmPPPoEMCH2POutDropFilter OBJECT-TYPE
   SYNTAX      Counter64
   MAX-ACCESS  read-only
   STATUS      current
   DESCRIPTION
      "Path: efm.performance.pppoEClient.mibCounters.h2Performance.ifOutDiscardsFilter

       64 bit unsigned wrappable counter."
   ::= {pr1646v2EfmPPPoEMCH2PEntry 402653184}

pr1646v2EfmPPPoEMCH2PIfOutBandwidth OBJECT-TYPE
   SYNTAX      Integer32
   MAX-ACCESS  read-only
   STATUS      current
   DESCRIPTION
      "Path: efm.performance.pppoEClient.mibCounters.h2Performance.ifOutBandwidth

       unit name = bps
       formula = 8 * ; 8 /"
   ::= {pr1646v2EfmPPPoEMCH2PEntry 285212672}

pr1646v2EfmPPPoEMCH2PIfErrSec OBJECT-TYPE
   SYNTAX      Counter32
   MAX-ACCESS  read-only
   STATUS      current
   DESCRIPTION
      "Path: efm.performance.pppoEClient.mibCounters.h2Performance.ifErrSec

       32 bit unsigned wrappable counter."
   ::= {pr1646v2EfmPPPoEMCH2PEntry 251658240}

pr1646v2EfmPPPoEMCH24P OBJECT-TYPE
   SYNTAX      SEQUENCE OF Pr1646v2EfmPPPoEMCH24PEntry
   MAX-ACCESS  not-accessible
   STATUS      current
   DESCRIPTION
      ""
   ::= {pr1646v2EfmPPPoE 41615360}

pr1646v2EfmPPPoEMCH24PEntry OBJECT-TYPE
   SYNTAX      Pr1646v2EfmPPPoEMCH24PEntry
   MAX-ACCESS  not-accessible
   STATUS      current
   DESCRIPTION
      ""
   INDEX      { pr1646v2EfmPPPoETableIx,
                pr1646v2EfmPPPoEMCH24PTableIx }
   ::= {pr1646v2EfmPPPoEMCH24P 1}

Pr1646v2EfmPPPoEMCH24PEntry ::=
   SEQUENCE
      {
      pr1646v2EfmPPPoEMCH24PTableIx
         TableIndex,
      pr1646v2EfmPPPoEMCH24PSysUpTime
         TimeTicks,
      pr1646v2EfmPPPoEMCH24PIfUpTime
         TimeTicks,
      pr1646v2EfmPPPoEMCH24PIfStatChanges
         Counter32,
      pr1646v2EfmPPPoEMCH24PIfInOctets
         Counter64,
      pr1646v2EfmPPPoEMCH24PIfInUCPkts
         Counter64,
      pr1646v2EfmPPPoEMCH24PIfInNUCPkts
         Counter64,
      pr1646v2EfmPPPoEMCH24PIfInBCPkts
         Counter64,
      pr1646v2EfmPPPoEMCH24PIfInMCPkts
         Counter64,
      pr1646v2EfmPPPoEMCH24PIfInDiscards
         Counter64,
      pr1646v2EfmPPPoEMCH24PIfInErrors
         Counter64,
      pr1646v2EfmPPPoEMCH24PIfInUnkwn
         Counter64,
      pr1646v2EfmPPPoEMCH24PInDropEx
         Counter64,
      pr1646v2EfmPPPoEMCH24PInDropNoMac
         Counter64,
      pr1646v2EfmPPPoEMCH24PInDropNUCast
         Counter64,
      pr1646v2EfmPPPoEMCH24PInDropFilter
         Counter64,
      pr1646v2EfmPPPoEMCH24PIfInBandwidth
         Integer32,
      pr1646v2EfmPPPoEMCH24PIfOutOctets
         Counter64,
      pr1646v2EfmPPPoEMCH24PIfOutUCPkts
         Counter64,
      pr1646v2EfmPPPoEMCH24PIfOutNUCPkts
         Counter64,
      pr1646v2EfmPPPoEMCH24PIfOutBCPkts
         Counter64,
      pr1646v2EfmPPPoEMCH24PIfOutMCPkts
         Counter64,
      pr1646v2EfmPPPoEMCH24PIfOutDiscards
         Counter64,
      pr1646v2EfmPPPoEMCH24PIfOutErrors
         Counter64,
      pr1646v2EfmPPPoEMCH24POutDropEx
         Counter64,
      pr1646v2EfmPPPoEMCH24POutDropNoArp
         Counter64,
      pr1646v2EfmPPPoEMCH24POutDropFilter
         Counter64,
      pr1646v2EfmPPPoEMCH24PIfOutBandwidth
         Integer32,
      pr1646v2EfmPPPoEMCH24PIfErrSec
         Counter32
      }

pr1646v2EfmPPPoEMCH24PTableIx OBJECT-TYPE
   SYNTAX      TableIndex
   MAX-ACCESS  not-accessible
   STATUS      current
   DESCRIPTION
      ""
   ::= {pr1646v2EfmPPPoEMCH24PEntry 11}

pr1646v2EfmPPPoEMCH24PSysUpTime OBJECT-TYPE
   SYNTAX      TimeTicks
   MAX-ACCESS  read-only
   STATUS      current
   DESCRIPTION
      "Path: efm.performance.pppoEClient.mibCounters.h24Performance.sysUpTime

       Time in centi-second."
   ::= {pr1646v2EfmPPPoEMCH24PEntry 16777216}

pr1646v2EfmPPPoEMCH24PIfUpTime OBJECT-TYPE
   SYNTAX      TimeTicks
   MAX-ACCESS  read-only
   STATUS      current
   DESCRIPTION
      "Path: efm.performance.pppoEClient.mibCounters.h24Performance.ifUpTime

       Time in centi-second."
   ::= {pr1646v2EfmPPPoEMCH24PEntry 33554432}

pr1646v2EfmPPPoEMCH24PIfStatChanges OBJECT-TYPE
   SYNTAX      Counter32
   MAX-ACCESS  read-only
   STATUS      current
   DESCRIPTION
      "Path: efm.performance.pppoEClient.mibCounters.h24Performance.ifStatusChanges

       32 bit unsigned wrappable counter."
   ::= {pr1646v2EfmPPPoEMCH24PEntry 50331648}

pr1646v2EfmPPPoEMCH24PIfInOctets OBJECT-TYPE
   SYNTAX      Counter64
   MAX-ACCESS  read-only
   STATUS      current
   DESCRIPTION
      "Path: efm.performance.pppoEClient.mibCounters.h24Performance.ifInOctets

       64 bit unsigned wrappable counter."
   ::= {pr1646v2EfmPPPoEMCH24PEntry 67108864}

pr1646v2EfmPPPoEMCH24PIfInUCPkts OBJECT-TYPE
   SYNTAX      Counter64
   MAX-ACCESS  read-only
   STATUS      current
   DESCRIPTION
      "Path: efm.performance.pppoEClient.mibCounters.h24Performance.ifInUcastPkts

       64 bit unsigned wrappable counter."
   ::= {pr1646v2EfmPPPoEMCH24PEntry 83886080}

pr1646v2EfmPPPoEMCH24PIfInNUCPkts OBJECT-TYPE
   SYNTAX      Counter64
   MAX-ACCESS  read-only
   STATUS      current
   DESCRIPTION
      "Path: efm.performance.pppoEClient.mibCounters.h24Performance.ifInNUcastPkts

       64 bit unsigned wrappable counter."
   ::= {pr1646v2EfmPPPoEMCH24PEntry 100663296}

pr1646v2EfmPPPoEMCH24PIfInBCPkts OBJECT-TYPE
   SYNTAX      Counter64
   MAX-ACCESS  read-only
   STATUS      current
   DESCRIPTION
      "Path: efm.performance.pppoEClient.mibCounters.h24Performance.ifInBcastPkts

       64 bit unsigned wrappable counter."
   ::= {pr1646v2EfmPPPoEMCH24PEntry 419430400}

pr1646v2EfmPPPoEMCH24PIfInMCPkts OBJECT-TYPE
   SYNTAX      Counter64
   MAX-ACCESS  read-only
   STATUS      current
   DESCRIPTION
      "Path: efm.performance.pppoEClient.mibCounters.h24Performance.ifInMcastPkts

       64 bit unsigned wrappable counter."
   ::= {pr1646v2EfmPPPoEMCH24PEntry 436207616}

pr1646v2EfmPPPoEMCH24PIfInDiscards OBJECT-TYPE
   SYNTAX      Counter64
   MAX-ACCESS  read-only
   STATUS      current
   DESCRIPTION
      "Path: efm.performance.pppoEClient.mibCounters.h24Performance.ifInDiscards

       64 bit unsigned wrappable counter."
   ::= {pr1646v2EfmPPPoEMCH24PEntry 117440512}

pr1646v2EfmPPPoEMCH24PIfInErrors OBJECT-TYPE
   SYNTAX      Counter64
   MAX-ACCESS  read-only
   STATUS      current
   DESCRIPTION
      "Path: efm.performance.pppoEClient.mibCounters.h24Performance.ifInErrors

       64 bit unsigned wrappable counter."
   ::= {pr1646v2EfmPPPoEMCH24PEntry 134217728}

pr1646v2EfmPPPoEMCH24PIfInUnkwn OBJECT-TYPE
   SYNTAX      Counter64
   MAX-ACCESS  read-only
   STATUS      current
   DESCRIPTION
      "Path: efm.performance.pppoEClient.mibCounters.h24Performance.ifInUnknownProtos

       64 bit unsigned wrappable counter."
   ::= {pr1646v2EfmPPPoEMCH24PEntry 150994944}

pr1646v2EfmPPPoEMCH24PInDropEx OBJECT-TYPE
   SYNTAX      Counter64
   MAX-ACCESS  read-only
   STATUS      current
   DESCRIPTION
      "Path: efm.performance.pppoEClient.mibCounters.h24Performance.ifInDropLevelExceeded

       64 bit unsigned wrappable counter."
   ::= {pr1646v2EfmPPPoEMCH24PEntry 335544320}

pr1646v2EfmPPPoEMCH24PInDropNoMac OBJECT-TYPE
   SYNTAX      Counter64
   MAX-ACCESS  read-only
   STATUS      current
   DESCRIPTION
      "Path: efm.performance.pppoEClient.mibCounters.h24Performance.fInDiscardsNoMacFit

       64 bit unsigned wrappable counter."
   ::= {pr1646v2EfmPPPoEMCH24PEntry 301989888}

pr1646v2EfmPPPoEMCH24PInDropNUCast OBJECT-TYPE
   SYNTAX      Counter64
   MAX-ACCESS  read-only
   STATUS      current
   DESCRIPTION
      "Path: efm.performance.pppoEClient.mibCounters.h24Performance.fInDiscardsNUCast

       64 bit unsigned wrappable counter."
   ::= {pr1646v2EfmPPPoEMCH24PEntry 318767104}

pr1646v2EfmPPPoEMCH24PInDropFilter OBJECT-TYPE
   SYNTAX      Counter64
   MAX-ACCESS  read-only
   STATUS      current
   DESCRIPTION
      "Path: efm.performance.pppoEClient.mibCounters.h24Performance.fInDiscardsFilter

       64 bit unsigned wrappable counter."
   ::= {pr1646v2EfmPPPoEMCH24PEntry 385875968}

pr1646v2EfmPPPoEMCH24PIfInBandwidth OBJECT-TYPE
   SYNTAX      Integer32
   MAX-ACCESS  read-only
   STATUS      current
   DESCRIPTION
      "Path: efm.performance.pppoEClient.mibCounters.h24Performance.ifInBandwidth

       unit name = bps
       formula = 8 * ; 8 /"
   ::= {pr1646v2EfmPPPoEMCH24PEntry 268435456}

pr1646v2EfmPPPoEMCH24PIfOutOctets OBJECT-TYPE
   SYNTAX      Counter64
   MAX-ACCESS  read-only
   STATUS      current
   DESCRIPTION
      "Path: efm.performance.pppoEClient.mibCounters.h24Performance.ifOutOctets

       64 bit unsigned wrappable counter."
   ::= {pr1646v2EfmPPPoEMCH24PEntry 167772160}

pr1646v2EfmPPPoEMCH24PIfOutUCPkts OBJECT-TYPE
   SYNTAX      Counter64
   MAX-ACCESS  read-only
   STATUS      current
   DESCRIPTION
      "Path: efm.performance.pppoEClient.mibCounters.h24Performance.ifOutUcastPkts

       64 bit unsigned wrappable counter."
   ::= {pr1646v2EfmPPPoEMCH24PEntry 184549376}

pr1646v2EfmPPPoEMCH24PIfOutNUCPkts OBJECT-TYPE
   SYNTAX      Counter64
   MAX-ACCESS  read-only
   STATUS      current
   DESCRIPTION
      "Path: efm.performance.pppoEClient.mibCounters.h24Performance.ifOutNUcastPkts

       64 bit unsigned wrappable counter."
   ::= {pr1646v2EfmPPPoEMCH24PEntry 201326592}

pr1646v2EfmPPPoEMCH24PIfOutBCPkts OBJECT-TYPE
   SYNTAX      Counter64
   MAX-ACCESS  read-only
   STATUS      current
   DESCRIPTION
      "Path: efm.performance.pppoEClient.mibCounters.h24Performance.ifOutBcastPkts

       64 bit unsigned wrappable counter."
   ::= {pr1646v2EfmPPPoEMCH24PEntry 452984832}

pr1646v2EfmPPPoEMCH24PIfOutMCPkts OBJECT-TYPE
   SYNTAX      Counter64
   MAX-ACCESS  read-only
   STATUS      current
   DESCRIPTION
      "Path: efm.performance.pppoEClient.mibCounters.h24Performance.ifOutMcastPkts

       64 bit unsigned wrappable counter."
   ::= {pr1646v2EfmPPPoEMCH24PEntry 469762048}

pr1646v2EfmPPPoEMCH24PIfOutDiscards OBJECT-TYPE
   SYNTAX      Counter64
   MAX-ACCESS  read-only
   STATUS      current
   DESCRIPTION
      "Path: efm.performance.pppoEClient.mibCounters.h24Performance.ifOutDiscards

       64 bit unsigned wrappable counter."
   ::= {pr1646v2EfmPPPoEMCH24PEntry 218103808}

pr1646v2EfmPPPoEMCH24PIfOutErrors OBJECT-TYPE
   SYNTAX      Counter64
   MAX-ACCESS  read-only
   STATUS      current
   DESCRIPTION
      "Path: efm.performance.pppoEClient.mibCounters.h24Performance.ifOutErrors

       64 bit unsigned wrappable counter."
   ::= {pr1646v2EfmPPPoEMCH24PEntry 234881024}

pr1646v2EfmPPPoEMCH24POutDropEx OBJECT-TYPE
   SYNTAX      Counter64
   MAX-ACCESS  read-only
   STATUS      current
   DESCRIPTION
      "Path: efm.performance.pppoEClient.mibCounters.h24Performance.ifOutDropLevelExceeded

       64 bit unsigned wrappable counter."
   ::= {pr1646v2EfmPPPoEMCH24PEntry 352321536}

pr1646v2EfmPPPoEMCH24POutDropNoArp OBJECT-TYPE
   SYNTAX      Counter64
   MAX-ACCESS  read-only
   STATUS      current
   DESCRIPTION
      "Path: efm.performance.pppoEClient.mibCounters.h24Performance.ifOutDiscardsNoArp

       64 bit unsigned wrappable counter."
   ::= {pr1646v2EfmPPPoEMCH24PEntry 369098752}

pr1646v2EfmPPPoEMCH24POutDropFilter OBJECT-TYPE
   SYNTAX      Counter64
   MAX-ACCESS  read-only
   STATUS      current
   DESCRIPTION
      "Path: efm.performance.pppoEClient.mibCounters.h24Performance.ifOutDiscardsFilter

       64 bit unsigned wrappable counter."
   ::= {pr1646v2EfmPPPoEMCH24PEntry 402653184}

pr1646v2EfmPPPoEMCH24PIfOutBandwidth OBJECT-TYPE
   SYNTAX      Integer32
   MAX-ACCESS  read-only
   STATUS      current
   DESCRIPTION
      "Path: efm.performance.pppoEClient.mibCounters.h24Performance.ifOutBandwidth

       unit name = bps
       formula = 8 * ; 8 /"
   ::= {pr1646v2EfmPPPoEMCH24PEntry 285212672}

pr1646v2EfmPPPoEMCH24PIfErrSec OBJECT-TYPE
   SYNTAX      Counter32
   MAX-ACCESS  read-only
   STATUS      current
   DESCRIPTION
      "Path: efm.performance.pppoEClient.mibCounters.h24Performance.ifErrSec

       32 bit unsigned wrappable counter."
   ::= {pr1646v2EfmPPPoEMCH24PEntry 251658240}

pr1646v2EfmPPPoEMCD7P OBJECT-TYPE
   SYNTAX      SEQUENCE OF Pr1646v2EfmPPPoEMCD7PEntry
   MAX-ACCESS  not-accessible
   STATUS      current
   DESCRIPTION
      ""
   ::= {pr1646v2EfmPPPoE 41680896}

pr1646v2EfmPPPoEMCD7PEntry OBJECT-TYPE
   SYNTAX      Pr1646v2EfmPPPoEMCD7PEntry
   MAX-ACCESS  not-accessible
   STATUS      current
   DESCRIPTION
      ""
   INDEX      { pr1646v2EfmPPPoETableIx,
                pr1646v2EfmPPPoEMCD7PTableIx }
   ::= {pr1646v2EfmPPPoEMCD7P 1}

Pr1646v2EfmPPPoEMCD7PEntry ::=
   SEQUENCE
      {
      pr1646v2EfmPPPoEMCD7PTableIx
         TableIndex,
      pr1646v2EfmPPPoEMCD7PSysUpTime
         TimeTicks,
      pr1646v2EfmPPPoEMCD7PIfUpTime
         TimeTicks,
      pr1646v2EfmPPPoEMCD7PIfStatChanges
         Counter32,
      pr1646v2EfmPPPoEMCD7PIfInOctets
         Counter64,
      pr1646v2EfmPPPoEMCD7PIfInUCPkts
         Counter64,
      pr1646v2EfmPPPoEMCD7PIfInNUCPkts
         Counter64,
      pr1646v2EfmPPPoEMCD7PIfInBCPkts
         Counter64,
      pr1646v2EfmPPPoEMCD7PIfInMCPkts
         Counter64,
      pr1646v2EfmPPPoEMCD7PIfInDiscards
         Counter64,
      pr1646v2EfmPPPoEMCD7PIfInErrors
         Counter64,
      pr1646v2EfmPPPoEMCD7PIfInUnkwn
         Counter64,
      pr1646v2EfmPPPoEMCD7PInDropEx
         Counter64,
      pr1646v2EfmPPPoEMCD7PInDropNoMac
         Counter64,
      pr1646v2EfmPPPoEMCD7PInDropNUCast
         Counter64,
      pr1646v2EfmPPPoEMCD7PInDropFilter
         Counter64,
      pr1646v2EfmPPPoEMCD7PIfInBandwidth
         Integer32,
      pr1646v2EfmPPPoEMCD7PIfOutOctets
         Counter64,
      pr1646v2EfmPPPoEMCD7PIfOutUCPkts
         Counter64,
      pr1646v2EfmPPPoEMCD7PIfOutNUCPkts
         Counter64,
      pr1646v2EfmPPPoEMCD7PIfOutBCPkts
         Counter64,
      pr1646v2EfmPPPoEMCD7PIfOutMCPkts
         Counter64,
      pr1646v2EfmPPPoEMCD7PIfOutDiscards
         Counter64,
      pr1646v2EfmPPPoEMCD7PIfOutErrors
         Counter64,
      pr1646v2EfmPPPoEMCD7POutDropEx
         Counter64,
      pr1646v2EfmPPPoEMCD7POutDropNoArp
         Counter64,
      pr1646v2EfmPPPoEMCD7POutDropFilter
         Counter64,
      pr1646v2EfmPPPoEMCD7PIfOutBandwidth
         Integer32,
      pr1646v2EfmPPPoEMCD7PIfErrSec
         Counter32
      }

pr1646v2EfmPPPoEMCD7PTableIx OBJECT-TYPE
   SYNTAX      TableIndex
   MAX-ACCESS  not-accessible
   STATUS      current
   DESCRIPTION
      ""
   ::= {pr1646v2EfmPPPoEMCD7PEntry 11}

pr1646v2EfmPPPoEMCD7PSysUpTime OBJECT-TYPE
   SYNTAX      TimeTicks
   MAX-ACCESS  read-only
   STATUS      current
   DESCRIPTION
      "Path: efm.performance.pppoEClient.mibCounters.d7Performance.sysUpTime

       Time in centi-second."
   ::= {pr1646v2EfmPPPoEMCD7PEntry 16777216}

pr1646v2EfmPPPoEMCD7PIfUpTime OBJECT-TYPE
   SYNTAX      TimeTicks
   MAX-ACCESS  read-only
   STATUS      current
   DESCRIPTION
      "Path: efm.performance.pppoEClient.mibCounters.d7Performance.ifUpTime

       Time in centi-second."
   ::= {pr1646v2EfmPPPoEMCD7PEntry 33554432}

pr1646v2EfmPPPoEMCD7PIfStatChanges OBJECT-TYPE
   SYNTAX      Counter32
   MAX-ACCESS  read-only
   STATUS      current
   DESCRIPTION
      "Path: efm.performance.pppoEClient.mibCounters.d7Performance.ifStatusChanges

       32 bit unsigned wrappable counter."
   ::= {pr1646v2EfmPPPoEMCD7PEntry 50331648}

pr1646v2EfmPPPoEMCD7PIfInOctets OBJECT-TYPE
   SYNTAX      Counter64
   MAX-ACCESS  read-only
   STATUS      current
   DESCRIPTION
      "Path: efm.performance.pppoEClient.mibCounters.d7Performance.ifInOctets

       64 bit unsigned wrappable counter."
   ::= {pr1646v2EfmPPPoEMCD7PEntry 67108864}

pr1646v2EfmPPPoEMCD7PIfInUCPkts OBJECT-TYPE
   SYNTAX      Counter64
   MAX-ACCESS  read-only
   STATUS      current
   DESCRIPTION
      "Path: efm.performance.pppoEClient.mibCounters.d7Performance.ifInUcastPkts

       64 bit unsigned wrappable counter."
   ::= {pr1646v2EfmPPPoEMCD7PEntry 83886080}

pr1646v2EfmPPPoEMCD7PIfInNUCPkts OBJECT-TYPE
   SYNTAX      Counter64
   MAX-ACCESS  read-only
   STATUS      current
   DESCRIPTION
      "Path: efm.performance.pppoEClient.mibCounters.d7Performance.ifInNUcastPkts

       64 bit unsigned wrappable counter."
   ::= {pr1646v2EfmPPPoEMCD7PEntry 100663296}

pr1646v2EfmPPPoEMCD7PIfInBCPkts OBJECT-TYPE
   SYNTAX      Counter64
   MAX-ACCESS  read-only
   STATUS      current
   DESCRIPTION
      "Path: efm.performance.pppoEClient.mibCounters.d7Performance.ifInBcastPkts

       64 bit unsigned wrappable counter."
   ::= {pr1646v2EfmPPPoEMCD7PEntry 419430400}

pr1646v2EfmPPPoEMCD7PIfInMCPkts OBJECT-TYPE
   SYNTAX      Counter64
   MAX-ACCESS  read-only
   STATUS      current
   DESCRIPTION
      "Path: efm.performance.pppoEClient.mibCounters.d7Performance.ifInMcastPkts

       64 bit unsigned wrappable counter."
   ::= {pr1646v2EfmPPPoEMCD7PEntry 436207616}

pr1646v2EfmPPPoEMCD7PIfInDiscards OBJECT-TYPE
   SYNTAX      Counter64
   MAX-ACCESS  read-only
   STATUS      current
   DESCRIPTION
      "Path: efm.performance.pppoEClient.mibCounters.d7Performance.ifInDiscards

       64 bit unsigned wrappable counter."
   ::= {pr1646v2EfmPPPoEMCD7PEntry 117440512}

pr1646v2EfmPPPoEMCD7PIfInErrors OBJECT-TYPE
   SYNTAX      Counter64
   MAX-ACCESS  read-only
   STATUS      current
   DESCRIPTION
      "Path: efm.performance.pppoEClient.mibCounters.d7Performance.ifInErrors

       64 bit unsigned wrappable counter."
   ::= {pr1646v2EfmPPPoEMCD7PEntry 134217728}

pr1646v2EfmPPPoEMCD7PIfInUnkwn OBJECT-TYPE
   SYNTAX      Counter64
   MAX-ACCESS  read-only
   STATUS      current
   DESCRIPTION
      "Path: efm.performance.pppoEClient.mibCounters.d7Performance.ifInUnknownProtos

       64 bit unsigned wrappable counter."
   ::= {pr1646v2EfmPPPoEMCD7PEntry 150994944}

pr1646v2EfmPPPoEMCD7PInDropEx OBJECT-TYPE
   SYNTAX      Counter64
   MAX-ACCESS  read-only
   STATUS      current
   DESCRIPTION
      "Path: efm.performance.pppoEClient.mibCounters.d7Performance.ifInDropLevelExceeded

       64 bit unsigned wrappable counter."
   ::= {pr1646v2EfmPPPoEMCD7PEntry 335544320}

pr1646v2EfmPPPoEMCD7PInDropNoMac OBJECT-TYPE
   SYNTAX      Counter64
   MAX-ACCESS  read-only
   STATUS      current
   DESCRIPTION
      "Path: efm.performance.pppoEClient.mibCounters.d7Performance.fInDiscardsNoMacFit

       64 bit unsigned wrappable counter."
   ::= {pr1646v2EfmPPPoEMCD7PEntry 301989888}

pr1646v2EfmPPPoEMCD7PInDropNUCast OBJECT-TYPE
   SYNTAX      Counter64
   MAX-ACCESS  read-only
   STATUS      current
   DESCRIPTION
      "Path: efm.performance.pppoEClient.mibCounters.d7Performance.fInDiscardsNUCast

       64 bit unsigned wrappable counter."
   ::= {pr1646v2EfmPPPoEMCD7PEntry 318767104}

pr1646v2EfmPPPoEMCD7PInDropFilter OBJECT-TYPE
   SYNTAX      Counter64
   MAX-ACCESS  read-only
   STATUS      current
   DESCRIPTION
      "Path: efm.performance.pppoEClient.mibCounters.d7Performance.fInDiscardsFilter

       64 bit unsigned wrappable counter."
   ::= {pr1646v2EfmPPPoEMCD7PEntry 385875968}

pr1646v2EfmPPPoEMCD7PIfInBandwidth OBJECT-TYPE
   SYNTAX      Integer32
   MAX-ACCESS  read-only
   STATUS      current
   DESCRIPTION
      "Path: efm.performance.pppoEClient.mibCounters.d7Performance.ifInBandwidth

       unit name = bps
       formula = 8 * ; 8 /"
   ::= {pr1646v2EfmPPPoEMCD7PEntry 268435456}

pr1646v2EfmPPPoEMCD7PIfOutOctets OBJECT-TYPE
   SYNTAX      Counter64
   MAX-ACCESS  read-only
   STATUS      current
   DESCRIPTION
      "Path: efm.performance.pppoEClient.mibCounters.d7Performance.ifOutOctets

       64 bit unsigned wrappable counter."
   ::= {pr1646v2EfmPPPoEMCD7PEntry 167772160}

pr1646v2EfmPPPoEMCD7PIfOutUCPkts OBJECT-TYPE
   SYNTAX      Counter64
   MAX-ACCESS  read-only
   STATUS      current
   DESCRIPTION
      "Path: efm.performance.pppoEClient.mibCounters.d7Performance.ifOutUcastPkts

       64 bit unsigned wrappable counter."
   ::= {pr1646v2EfmPPPoEMCD7PEntry 184549376}

pr1646v2EfmPPPoEMCD7PIfOutNUCPkts OBJECT-TYPE
   SYNTAX      Counter64
   MAX-ACCESS  read-only
   STATUS      current
   DESCRIPTION
      "Path: efm.performance.pppoEClient.mibCounters.d7Performance.ifOutNUcastPkts

       64 bit unsigned wrappable counter."
   ::= {pr1646v2EfmPPPoEMCD7PEntry 201326592}

pr1646v2EfmPPPoEMCD7PIfOutBCPkts OBJECT-TYPE
   SYNTAX      Counter64
   MAX-ACCESS  read-only
   STATUS      current
   DESCRIPTION
      "Path: efm.performance.pppoEClient.mibCounters.d7Performance.ifOutBcastPkts

       64 bit unsigned wrappable counter."
   ::= {pr1646v2EfmPPPoEMCD7PEntry 452984832}

pr1646v2EfmPPPoEMCD7PIfOutMCPkts OBJECT-TYPE
   SYNTAX      Counter64
   MAX-ACCESS  read-only
   STATUS      current
   DESCRIPTION
      "Path: efm.performance.pppoEClient.mibCounters.d7Performance.ifOutMcastPkts

       64 bit unsigned wrappable counter."
   ::= {pr1646v2EfmPPPoEMCD7PEntry 469762048}

pr1646v2EfmPPPoEMCD7PIfOutDiscards OBJECT-TYPE
   SYNTAX      Counter64
   MAX-ACCESS  read-only
   STATUS      current
   DESCRIPTION
      "Path: efm.performance.pppoEClient.mibCounters.d7Performance.ifOutDiscards

       64 bit unsigned wrappable counter."
   ::= {pr1646v2EfmPPPoEMCD7PEntry 218103808}

pr1646v2EfmPPPoEMCD7PIfOutErrors OBJECT-TYPE
   SYNTAX      Counter64
   MAX-ACCESS  read-only
   STATUS      current
   DESCRIPTION
      "Path: efm.performance.pppoEClient.mibCounters.d7Performance.ifOutErrors

       64 bit unsigned wrappable counter."
   ::= {pr1646v2EfmPPPoEMCD7PEntry 234881024}

pr1646v2EfmPPPoEMCD7POutDropEx OBJECT-TYPE
   SYNTAX      Counter64
   MAX-ACCESS  read-only
   STATUS      current
   DESCRIPTION
      "Path: efm.performance.pppoEClient.mibCounters.d7Performance.ifOutDropLevelExceeded

       64 bit unsigned wrappable counter."
   ::= {pr1646v2EfmPPPoEMCD7PEntry 352321536}

pr1646v2EfmPPPoEMCD7POutDropNoArp OBJECT-TYPE
   SYNTAX      Counter64
   MAX-ACCESS  read-only
   STATUS      current
   DESCRIPTION
      "Path: efm.performance.pppoEClient.mibCounters.d7Performance.ifOutDiscardsNoArp

       64 bit unsigned wrappable counter."
   ::= {pr1646v2EfmPPPoEMCD7PEntry 369098752}

pr1646v2EfmPPPoEMCD7POutDropFilter OBJECT-TYPE
   SYNTAX      Counter64
   MAX-ACCESS  read-only
   STATUS      current
   DESCRIPTION
      "Path: efm.performance.pppoEClient.mibCounters.d7Performance.ifOutDiscardsFilter

       64 bit unsigned wrappable counter."
   ::= {pr1646v2EfmPPPoEMCD7PEntry 402653184}

pr1646v2EfmPPPoEMCD7PIfOutBandwidth OBJECT-TYPE
   SYNTAX      Integer32
   MAX-ACCESS  read-only
   STATUS      current
   DESCRIPTION
      "Path: efm.performance.pppoEClient.mibCounters.d7Performance.ifOutBandwidth

       unit name = bps
       formula = 8 * ; 8 /"
   ::= {pr1646v2EfmPPPoEMCD7PEntry 285212672}

pr1646v2EfmPPPoEMCD7PIfErrSec OBJECT-TYPE
   SYNTAX      Counter32
   MAX-ACCESS  read-only
   STATUS      current
   DESCRIPTION
      "Path: efm.performance.pppoEClient.mibCounters.d7Performance.ifErrSec

       32 bit unsigned wrappable counter."
   ::= {pr1646v2EfmPPPoEMCD7PEntry 251658240}



ar1646v2Efm OBJECT IDENTIFIER ::= {r1646v2Efm 16}


ar1646v2EfmClearCounters OBJECT-TYPE
   SYNTAX      Integer32
   MAX-ACCESS  read-write
   STATUS      current
   DESCRIPTION
      "Path: efm.actions.clearCounters
       Info: reset counters"
   ::= {ar1646v2Efm 263}


ar1646v2EfmPowerToggle OBJECT-TYPE
   SYNTAX      Integer32
   MAX-ACCESS  read-write
   STATUS      current
   DESCRIPTION
      "Path: efm.actions.powerToggle
       Info: action in the debug group"
   ::= {ar1646v2Efm 68}


ar1646v2EfmStopAutoNeg OBJECT-TYPE
   SYNTAX      Integer32
   MAX-ACCESS  read-write
   STATUS      current
   DESCRIPTION
      "Path: efm.actions.stopAutoNeg
       Info: action in the debug group"
   ::= {ar1646v2Efm 79}


ar1646v2EfmRestartIntf OBJECT-TYPE
   SYNTAX      Integer32
   MAX-ACCESS  read-write
   STATUS      current
   DESCRIPTION
      "Path: efm.actions.restartIntf
       Info: action in the debug group"
   ::= {ar1646v2Efm 67}


ar1646v2EfmClearOamEventLog OBJECT-TYPE
   SYNTAX      Integer32
   MAX-ACCESS  read-write
   STATUS      current
   DESCRIPTION
      "Path: efm.actions.clearOamEventLog
       Info: clear the OAM event log"
   ::= {ar1646v2Efm 916}


ar1646v2EfmLoopback OBJECT-TYPE
   SYNTAX      Integer32
   MAX-ACCESS  read-write
   STATUS      current
   DESCRIPTION
      "Path: efm.actions.loopback
       Info: ethernet loopback"
   ::= {ar1646v2Efm 914}


ar1646v2EfmLoop OBJECT IDENTIFIER ::= {ar1646v2Efm 915}

ar1646v2EfmLoopSSC OBJECT IDENTIFIER ::= {ar1646v2EfmLoop 1}

ar1646v2EfmLoopEntry OBJECT IDENTIFIER ::= {ar1646v2EfmLoopSSC 1}

ar1646v2EfmLoopAction OBJECT-TYPE
   SYNTAX      INTEGER
               {
               start (1),
               stop (2)
               }
   MAX-ACCESS  read-write
   STATUS      current
   DESCRIPTION
      "Path: efm.actions.loop.action

       Possibilities:
               start   (1)
               stop   (2)"
   ::= {ar1646v2EfmLoopEntry 16777216}

ar1646v2EfmLoopTime OBJECT-TYPE
   SYNTAX      TimeTicks
   MAX-ACCESS  read-write
   STATUS      current
   DESCRIPTION
      "Path: efm.actions.loop.time

       Time in centi-second."
   ::= {ar1646v2EfmLoopEntry 50331648}

ar1646v2EfmLoopIntfName OBJECT-TYPE
   SYNTAX      DisplayString
   MAX-ACCESS  read-write
   STATUS      current
   DESCRIPTION
      "Path: efm.actions.loop.intfName"
   ::= {ar1646v2EfmLoopEntry 67108864}


ar1646v2EfmOamRemLoopback OBJECT-TYPE
   SYNTAX      Integer32
   MAX-ACCESS  read-write
   STATUS      current
   DESCRIPTION
      "Path: efm.actions.oamRemLoopback
       Info: OAM Remote Loopback"
   ::= {ar1646v2Efm 912}


ar1646v2EfmType OBJECT-TYPE
   SYNTAX      INTEGER
               {
               start (0),
               stop (1)
               }
   MAX-ACCESS  read-write
   STATUS      current
   DESCRIPTION
      "Path: efm.actions.type
       Info: OAM Remote Loopback type

       Possibilities:
               start   (0)
               stop   (1)"
   ::= {ar1646v2Efm 913}


ar1646v2EfmSendWOL OBJECT-TYPE
   SYNTAX      Integer32
   MAX-ACCESS  read-write
   STATUS      current
   DESCRIPTION
      "Path: efm.actions.sendWOL
       Info: send a WakeOnLan message on this interface"
   ::= {ar1646v2Efm 333}


ar1646v2EfmWolInfo OBJECT IDENTIFIER ::= {ar1646v2Efm 332}

ar1646v2EfmWolInfoSSC OBJECT IDENTIFIER ::= {ar1646v2EfmWolInfo 1}

ar1646v2EfmWolInfoEntry OBJECT IDENTIFIER ::= {ar1646v2EfmWolInfoSSC 1}

ar1646v2EfmWolInfoTargetMAC OBJECT-TYPE
   SYNTAX      OCTET STRING
   MAX-ACCESS  read-write
   STATUS      current
   DESCRIPTION
      "Path: efm.actions.wolInfo.targetMAC

       MAC address."
   ::= {ar1646v2EfmWolInfoEntry 16777216}

ar1646v2EfmWolInfoPassword OBJECT-TYPE
   SYNTAX      OCTET STRING
   MAX-ACCESS  read-write
   STATUS      current
   DESCRIPTION
      "Path: efm.actions.wolInfo.password"
   ::= {ar1646v2EfmWolInfoEntry 33554432}


ar1646v2EfmClearArpCache OBJECT-TYPE
   SYNTAX      Integer32
   MAX-ACCESS  read-write
   STATUS      current
   DESCRIPTION
      "Path: efm.actions.clearArpCache
       Info: clear all dynamic enties in ARP cache table"
   ::= {ar1646v2Efm 25}



END
