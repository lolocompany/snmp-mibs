OneAccess-R1645v2-4618-Ethpdp DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2Ethpdp OBJECT IDENTIFIER ::= {r1645Rootv2 4618}

r1645v2EthpdpMOProp OBJECT-TYPE
   SYNTAX      SEQUENCE OF R1645v2EthpdpMOPropEntry
   MAX-ACCESS  not-accessible
   STATUS      current
   DESCRIPTION
      ""
   ::= {r1645v2Ethpdp 1}

r1645v2EthpdpMOPropEntry OBJECT-TYPE
   SYNTAX      R1645v2EthpdpMOPropEntry
   MAX-ACCESS  not-accessible
   STATUS      current
   DESCRIPTION
      ""
   INDEX      { r1645v2EthpdpMOPropGlobalIx }
   ::= {r1645v2EthpdpMOProp 1}

R1645v2EthpdpMOPropEntry ::=
   SEQUENCE
      {
      r1645v2EthpdpMOPropPath
         ContainmentPath,
      r1645v2EthpdpMOPropRev
         ObjectRevision,
      r1645v2EthpdpMOPropGlobalIx
         GlobalIndex
      }

r1645v2EthpdpMOPropPath OBJECT-TYPE
   SYNTAX      ContainmentPath
   MAX-ACCESS  read-only
   STATUS      current
   DESCRIPTION
      "Textual description of the containment tree from the instance of
       the root object down to the instance of the current object."
   ::= {r1645v2EthpdpMOPropEntry 3}

r1645v2EthpdpMOPropRev OBJECT-TYPE
   SYNTAX      ObjectRevision
   MAX-ACCESS  read-only
   STATUS      current
   DESCRIPTION
      "This value corresponds with the revision of the MANAGED OBJECT."
   ::= {r1645v2EthpdpMOPropEntry 4}

r1645v2EthpdpMOPropGlobalIx OBJECT-TYPE
   SYNTAX      GlobalIndex
   MAX-ACCESS  read-only
   STATUS      current
   DESCRIPTION
      "The value of the tlsCntTreeGlobalIndex of the MANAGED OBJECT."
   ::= {r1645v2EthpdpMOPropEntry 10}



er1645v2Ethpdp OBJECT IDENTIFIER ::= {r1645v2Ethpdp 11}


er1645v2EthpdpName OBJECT IDENTIFIER ::= {er1645v2Ethpdp 2}

er1645v2EthpdpNameTable OBJECT-TYPE
   SYNTAX      SEQUENCE OF Er1645v2EthpdpNameEntry
   MAX-ACCESS  not-accessible
   STATUS      current
   DESCRIPTION
      "config interface name"
   ::= {er1645v2EthpdpName 1}

er1645v2EthpdpNameEntry OBJECT-TYPE
   SYNTAX      Er1645v2EthpdpNameEntry
   MAX-ACCESS  not-accessible
   STATUS      current
   DESCRIPTION
      ""
   INDEX      { er1645v2EthpdpNameGlobalIx }
   ::= {er1645v2EthpdpNameTable 1}

Er1645v2EthpdpNameEntry ::=
   SEQUENCE
      {
      er1645v2EthpdpNameGlobalIx
         GlobalIndex,
      er1645v2EthpdpNameValue
         DisplayString
      }

er1645v2EthpdpNameGlobalIx OBJECT-TYPE
   SYNTAX      GlobalIndex
   MAX-ACCESS  not-accessible
   STATUS      current
   DESCRIPTION
      "The value of the tlsCntTreeGlobalIndex of the MANAGED OBJECT."
   ::= {er1645v2EthpdpNameEntry 10}

er1645v2EthpdpNameValue OBJECT-TYPE
   SYNTAX      DisplayString
   MAX-ACCESS  read-write
   STATUS      current
   DESCRIPTION
      "Path: ethernetPdp.editConf.name"
   ::= {er1645v2EthpdpNameEntry 2147483648}


er1645v2EthpdpRemark OBJECT IDENTIFIER ::= {er1645v2Ethpdp 321}

er1645v2EthpdpRemarkTable OBJECT-TYPE
   SYNTAX      SEQUENCE OF Er1645v2EthpdpRemarkEntry
   MAX-ACCESS  not-accessible
   STATUS      current
   DESCRIPTION
      "intfRemark"
   ::= {er1645v2EthpdpRemark 1}

er1645v2EthpdpRemarkEntry OBJECT-TYPE
   SYNTAX      Er1645v2EthpdpRemarkEntry
   MAX-ACCESS  not-accessible
   STATUS      current
   DESCRIPTION
      ""
   INDEX      { er1645v2EthpdpRemarkGlobalIx }
   ::= {er1645v2EthpdpRemarkTable 1}

Er1645v2EthpdpRemarkEntry ::=
   SEQUENCE
      {
      er1645v2EthpdpRemarkGlobalIx
         GlobalIndex,
      er1645v2EthpdpRemarkValue
         DisplayString
      }

er1645v2EthpdpRemarkGlobalIx OBJECT-TYPE
   SYNTAX      GlobalIndex
   MAX-ACCESS  not-accessible
   STATUS      current
   DESCRIPTION
      "The value of the tlsCntTreeGlobalIndex of the MANAGED OBJECT."
   ::= {er1645v2EthpdpRemarkEntry 10}

er1645v2EthpdpRemarkValue OBJECT-TYPE
   SYNTAX      DisplayString
   MAX-ACCESS  read-write
   STATUS      current
   DESCRIPTION
      "Path: ethernetPdp.editConf.remark"
   ::= {er1645v2EthpdpRemarkEntry 2147483648}


er1645v2EthpdpDataProfile OBJECT IDENTIFIER ::= {er1645v2Ethpdp 8}

er1645v2EthpdpDataProfileTable OBJECT-TYPE
   SYNTAX      SEQUENCE OF Er1645v2EthpdpDataProfileEntry
   MAX-ACCESS  not-accessible
   STATUS      current
   DESCRIPTION
      "cellular profile"
   ::= {er1645v2EthpdpDataProfile 1}

er1645v2EthpdpDataProfileEntry OBJECT-TYPE
   SYNTAX      Er1645v2EthpdpDataProfileEntry
   MAX-ACCESS  not-accessible
   STATUS      current
   DESCRIPTION
      ""
   INDEX      { er1645v2EthpdpDataProfileGlobalIx }
   ::= {er1645v2EthpdpDataProfileTable 1}

Er1645v2EthpdpDataProfileEntry ::=
   SEQUENCE
      {
      er1645v2EthpdpDataProfileGlobalIx
         GlobalIndex,
      er1645v2EthpdpDataProfileValue
         DisplayString
      }

er1645v2EthpdpDataProfileGlobalIx OBJECT-TYPE
   SYNTAX      GlobalIndex
   MAX-ACCESS  not-accessible
   STATUS      current
   DESCRIPTION
      "The value of the tlsCntTreeGlobalIndex of the MANAGED OBJECT."
   ::= {er1645v2EthpdpDataProfileEntry 10}

er1645v2EthpdpDataProfileValue OBJECT-TYPE
   SYNTAX      DisplayString
   MAX-ACCESS  read-write
   STATUS      current
   DESCRIPTION
      "Path: ethernetPdp.editConf.dataProfile"
   ::= {er1645v2EthpdpDataProfileEntry 2147483648}


er1645v2EthpdpAdminStatus OBJECT IDENTIFIER ::= {er1645v2Ethpdp 106}

er1645v2EthpdpAdminStatusTable OBJECT-TYPE
   SYNTAX      SEQUENCE OF Er1645v2EthpdpAdminStatusEntry
   MAX-ACCESS  not-accessible
   STATUS      current
   DESCRIPTION
      "admin status"
   ::= {er1645v2EthpdpAdminStatus 1}

er1645v2EthpdpAdminStatusEntry OBJECT-TYPE
   SYNTAX      Er1645v2EthpdpAdminStatusEntry
   MAX-ACCESS  not-accessible
   STATUS      current
   DESCRIPTION
      ""
   INDEX      { er1645v2EthpdpAdminStatusGlobalIx }
   ::= {er1645v2EthpdpAdminStatusTable 1}

Er1645v2EthpdpAdminStatusEntry ::=
   SEQUENCE
      {
      er1645v2EthpdpAdminStatusGlobalIx
         GlobalIndex,
      er1645v2EthpdpAdminStatusValue
         INTEGER
      }

er1645v2EthpdpAdminStatusGlobalIx OBJECT-TYPE
   SYNTAX      GlobalIndex
   MAX-ACCESS  not-accessible
   STATUS      current
   DESCRIPTION
      "The value of the tlsCntTreeGlobalIndex of the MANAGED OBJECT."
   ::= {er1645v2EthpdpAdminStatusEntry 10}

er1645v2EthpdpAdminStatusValue OBJECT-TYPE
   SYNTAX      INTEGER
               {
               up (1),
               down (2)
               }
   MAX-ACCESS  read-write
   STATUS      current
   DESCRIPTION
      "Path: ethernetPdp.editConf.adminStatus

       Possibilities:
               up   (1)
               down   (2)"
   ::= {er1645v2EthpdpAdminStatusEntry 2147483648}


er1645v2EthpdpVirtEthernet OBJECT IDENTIFIER ::= {er1645v2Ethpdp 5}

er1645v2EthpdpVirtEthernetSSCTable OBJECT-TYPE
   SYNTAX      SEQUENCE OF Er1645v2EthpdpVirtEthernetEntry
   MAX-ACCESS  not-accessible
   STATUS      current
   DESCRIPTION
      ""
   ::= {er1645v2EthpdpVirtEthernet 1}

er1645v2EthpdpVirtEthernetEntry OBJECT-TYPE
   SYNTAX      Er1645v2EthpdpVirtEthernetEntry
   MAX-ACCESS  not-accessible
   STATUS      current
   DESCRIPTION
      ""
   INDEX      { er1645v2EthpdpVirtEthernetGlobalIx }
   ::= {er1645v2EthpdpVirtEthernetSSCTable 1}

Er1645v2EthpdpVirtEthernetEntry ::=
   SEQUENCE
      {
      er1645v2EthpdpVirtEthernetGlobalIx
         GlobalIndex,
      er1645v2EthpdpVirtEthernetVirtualEthernet
         DisplayString
      }

er1645v2EthpdpVirtEthernetGlobalIx OBJECT-TYPE
   SYNTAX      GlobalIndex
   MAX-ACCESS  not-accessible
   STATUS      current
   DESCRIPTION
      "The value of the tlsCntTreeGlobalIndex of the MANAGED OBJECT."
   ::= {er1645v2EthpdpVirtEthernetEntry 10}

er1645v2EthpdpVirtEthernetVirtualEthernet OBJECT-TYPE
   SYNTAX      DisplayString
   MAX-ACCESS  read-write
   STATUS      current
   DESCRIPTION
      "Path: ethernetPdp.editConf.virtEthernet.virtualEthernet"
   ::= {er1645v2EthpdpVirtEthernetEntry 16777216}


er1645v2EthpdpStartDelay OBJECT IDENTIFIER ::= {er1645v2Ethpdp 7}

er1645v2EthpdpStartDelayTable OBJECT-TYPE
   SYNTAX      SEQUENCE OF Er1645v2EthpdpStartDelayEntry
   MAX-ACCESS  not-accessible
   STATUS      current
   DESCRIPTION
      "the amount of time the ethernetPdp module starts after network registration"
   ::= {er1645v2EthpdpStartDelay 1}

er1645v2EthpdpStartDelayEntry OBJECT-TYPE
   SYNTAX      Er1645v2EthpdpStartDelayEntry
   MAX-ACCESS  not-accessible
   STATUS      current
   DESCRIPTION
      ""
   INDEX      { er1645v2EthpdpStartDelayGlobalIx }
   ::= {er1645v2EthpdpStartDelayTable 1}

Er1645v2EthpdpStartDelayEntry ::=
   SEQUENCE
      {
      er1645v2EthpdpStartDelayGlobalIx
         GlobalIndex,
      er1645v2EthpdpStartDelayValue
         INTEGER
      }

er1645v2EthpdpStartDelayGlobalIx OBJECT-TYPE
   SYNTAX      GlobalIndex
   MAX-ACCESS  not-accessible
   STATUS      current
   DESCRIPTION
      "The value of the tlsCntTreeGlobalIndex of the MANAGED OBJECT."
   ::= {er1645v2EthpdpStartDelayEntry 10}

er1645v2EthpdpStartDelayValue OBJECT-TYPE
   SYNTAX      INTEGER
               {
               disabled (0)
               }
   MAX-ACCESS  read-write
   STATUS      current
   DESCRIPTION
      "Path: ethernetPdp.editConf.startDelay

       Possibilities:
               disabled   (0)"
   ::= {er1645v2EthpdpStartDelayEntry 2147483648}


er1645v2EthpdpBw OBJECT IDENTIFIER ::= {er1645v2Ethpdp 37}

er1645v2EthpdpBwSSCTable OBJECT-TYPE
   SYNTAX      SEQUENCE OF Er1645v2EthpdpBwEntry
   MAX-ACCESS  not-accessible
   STATUS      current
   DESCRIPTION
      ""
   ::= {er1645v2EthpdpBw 1}

er1645v2EthpdpBwEntry OBJECT-TYPE
   SYNTAX      Er1645v2EthpdpBwEntry
   MAX-ACCESS  not-accessible
   STATUS      current
   DESCRIPTION
      ""
   INDEX      { er1645v2EthpdpBwGlobalIx }
   ::= {er1645v2EthpdpBwSSCTable 1}

Er1645v2EthpdpBwEntry ::=
   SEQUENCE
      {
      er1645v2EthpdpBwGlobalIx
         GlobalIndex,
      er1645v2EthpdpBwMode
         INTEGER,
      er1645v2EthpdpBwCir
         Integer32,
      er1645v2EthpdpBwEir
         Integer32,
      er1645v2EthpdpBwUnit
         INTEGER,
      er1645v2EthpdpBwTc
         INTEGER,
      er1645v2EthpdpBwTcFactor
         INTEGER,
      er1645v2EthpdpBwCorrType
         INTEGER,
      er1645v2EthpdpBwCorrPredefEncapsFrameRelay
         DisplayString,
      er1645v2EthpdpBwCorrPredefEncapsPpp
         DisplayString,
      er1645v2EthpdpBwCorrPredefEncapsAtmHl
         INTEGER,
      er1645v2EthpdpBwCorrPredefEncapsAtmMp
         INTEGER,
      er1645v2EthpdpBwCorrPredefEncapsHdlc
         DisplayString,
      er1645v2EthpdpBwCorrPredefEncapsEfmFs
         Integer32,
      er1645v2EthpdpBwCorrPredefEncapsEfmIb
         Integer32,
      er1645v2EthpdpBwCorrPredefMode
         INTEGER,
      er1645v2EthpdpBwCorrManualOverhead
         Integer32,
      er1645v2EthpdpBwCorrManualFrameData
         Counter32,
      er1645v2EthpdpBwCorrManualFrameHeader
         Counter32,
      er1645v2EthpdpBwMaxFifoQLen
         Integer32,
      er1645v2EthpdpBwDeFlagCir
         INTEGER,
      er1645v2EthpdpBwDeFlagEir
         INTEGER,
      er1645v2EthpdpBwDeFlagViolate
         INTEGER,
      er1645v2EthpdpBwActCirActNone
         OCTET STRING,
      er1645v2EthpdpBwActCirActEthCos1
         INTEGER,
      er1645v2EthpdpBwActCirActEthDei1
         INTEGER,
      er1645v2EthpdpBwActCirActEthCos2
         INTEGER,
      er1645v2EthpdpBwActCirActEthDei2
         INTEGER,
      er1645v2EthpdpBwActCirActEthCos3
         INTEGER,
      er1645v2EthpdpBwActCirActEthDei3
         INTEGER,
      er1645v2EthpdpBwActCirActEthCos4
         INTEGER,
      er1645v2EthpdpBwActCirActEthDei4
         INTEGER,
      er1645v2EthpdpBwActCirActEthCos5
         INTEGER,
      er1645v2EthpdpBwActCirActEthDei5
         INTEGER,
      er1645v2EthpdpBwActCirActEthCos6
         INTEGER,
      er1645v2EthpdpBwActCirActEthDei6
         INTEGER,
      er1645v2EthpdpBwActCirActEthCos7
         INTEGER,
      er1645v2EthpdpBwActCirActEthDei7
         INTEGER,
      er1645v2EthpdpBwActCirActEthCos8
         INTEGER,
      er1645v2EthpdpBwActCirActEthDei8
         INTEGER,
      er1645v2EthpdpBwActCirActEthTos
         INTEGER,
      er1645v2EthpdpBwActCirActEthQueue
         INTEGER,
      er1645v2EthpdpBwActCirActEthDrpLev
         INTEGER,
      er1645v2EthpdpBwActCirActEthDeFlag
         INTEGER,
      er1645v2EthpdpBwActCirActIpTos
         INTEGER,
      er1645v2EthpdpBwActCirActIpQueue
         INTEGER,
      er1645v2EthpdpBwActCirActIpDrpLev
         INTEGER,
      er1645v2EthpdpBwActCirActIpDeFlag
         INTEGER,
      er1645v2EthpdpBwActEirActNone
         OCTET STRING,
      er1645v2EthpdpBwActEirActEthCos1
         INTEGER,
      er1645v2EthpdpBwActEirActEthDei1
         INTEGER,
      er1645v2EthpdpBwActEirActEthCos2
         INTEGER,
      er1645v2EthpdpBwActEirActEthDei2
         INTEGER,
      er1645v2EthpdpBwActEirActEthCos3
         INTEGER,
      er1645v2EthpdpBwActEirActEthDei3
         INTEGER,
      er1645v2EthpdpBwActEirActEthCos4
         INTEGER,
      er1645v2EthpdpBwActEirActEthDei4
         INTEGER,
      er1645v2EthpdpBwActEirActEthCos5
         INTEGER,
      er1645v2EthpdpBwActEirActEthDei5
         INTEGER,
      er1645v2EthpdpBwActEirActEthCos6
         INTEGER,
      er1645v2EthpdpBwActEirActEthDei6
         INTEGER,
      er1645v2EthpdpBwActEirActEthCos7
         INTEGER,
      er1645v2EthpdpBwActEirActEthDei7
         INTEGER,
      er1645v2EthpdpBwActEirActEthCos8
         INTEGER,
      er1645v2EthpdpBwActEirActEthDei8
         INTEGER,
      er1645v2EthpdpBwActEirActEthTos
         INTEGER,
      er1645v2EthpdpBwActEirActEthQueue
         INTEGER,
      er1645v2EthpdpBwActEirActEthDrpLev
         INTEGER,
      er1645v2EthpdpBwActEirActEthDeFlag
         INTEGER,
      er1645v2EthpdpBwActEirActIpTos
         INTEGER,
      er1645v2EthpdpBwActEirActIpQueue
         INTEGER,
      er1645v2EthpdpBwActEirActIpDrpLev
         INTEGER,
      er1645v2EthpdpBwActEirActIpDeFlag
         INTEGER,
      er1645v2EthpdpBwActViolActNone
         OCTET STRING,
      er1645v2EthpdpBwActViolActDrop
         OCTET STRING,
      er1645v2EthpdpBwActViolActEthCos1
         INTEGER,
      er1645v2EthpdpBwActViolActEthDei1
         INTEGER,
      er1645v2EthpdpBwActViolActEthCos2
         INTEGER,
      er1645v2EthpdpBwActViolActEthDei2
         INTEGER,
      er1645v2EthpdpBwActViolActEthCos3
         INTEGER,
      er1645v2EthpdpBwActViolActEthDei3
         INTEGER,
      er1645v2EthpdpBwActViolActEthCos4
         INTEGER,
      er1645v2EthpdpBwActViolActEthDei4
         INTEGER,
      er1645v2EthpdpBwActViolActEthCos5
         INTEGER,
      er1645v2EthpdpBwActViolActEthDei5
         INTEGER,
      er1645v2EthpdpBwActViolActEthCos6
         INTEGER,
      er1645v2EthpdpBwActViolActEthDei6
         INTEGER,
      er1645v2EthpdpBwActViolActEthCos7
         INTEGER,
      er1645v2EthpdpBwActViolActEthDei7
         INTEGER,
      er1645v2EthpdpBwActViolActEthCos8
         INTEGER,
      er1645v2EthpdpBwActViolActEthDei8
         INTEGER,
      er1645v2EthpdpBwActViolActEthTos
         INTEGER,
      er1645v2EthpdpBwActViolActEthQueue
         INTEGER,
      er1645v2EthpdpBwActViolActEthDrpLev
         INTEGER,
      er1645v2EthpdpBwActViolActEthDeFlag
         INTEGER,
      er1645v2EthpdpBwActViolActIpTos
         INTEGER,
      er1645v2EthpdpBwActViolActIpQueue
         INTEGER,
      er1645v2EthpdpBwActViolActIpDrpLev
         INTEGER,
      er1645v2EthpdpBwActViolActIpDeFlag
         INTEGER
      }

er1645v2EthpdpBwGlobalIx OBJECT-TYPE
   SYNTAX      GlobalIndex
   MAX-ACCESS  not-accessible
   STATUS      current
   DESCRIPTION
      "The value of the tlsCntTreeGlobalIndex of the MANAGED OBJECT."
   ::= {er1645v2EthpdpBwEntry 10}

er1645v2EthpdpBwMode OBJECT-TYPE
   SYNTAX      INTEGER
               {
               reshaping (1),
               policing (2),
               policingReshape (3)
               }
   MAX-ACCESS  read-write
   STATUS      current
   DESCRIPTION
      "Path: ethernetPdp.editConf.bandwidth.mode

       Possibilities:
               reshaping   (1)
               policing   (2)
               policingReshape   (3)"
   ::= {er1645v2EthpdpBwEntry 3758096384}

er1645v2EthpdpBwCir OBJECT-TYPE
   SYNTAX      Integer32
   MAX-ACCESS  read-write
   STATUS      current
   DESCRIPTION
      "Path: ethernetPdp.editConf.bandwidth.cir"
   ::= {er1645v2EthpdpBwEntry 268435456}

er1645v2EthpdpBwEir OBJECT-TYPE
   SYNTAX      Integer32
   MAX-ACCESS  read-write
   STATUS      current
   DESCRIPTION
      "Path: ethernetPdp.editConf.bandwidth.eir"
   ::= {er1645v2EthpdpBwEntry 1879048192}

er1645v2EthpdpBwUnit OBJECT-TYPE
   SYNTAX      INTEGER
               {
               bitssec (1),
               percent (2)
               }
   MAX-ACCESS  read-write
   STATUS      current
   DESCRIPTION
      "Path: ethernetPdp.editConf.bandwidth.unit

       Possibilities:
               bits/sec   (1)
               percent   (2)"
   ::= {er1645v2EthpdpBwEntry 1342177280}

er1645v2EthpdpBwTc OBJECT-TYPE
   SYNTAX      INTEGER
               {
               auto (0)
               }
   MAX-ACCESS  read-write
   STATUS      current
   DESCRIPTION
      "Path: ethernetPdp.editConf.bandwidth.tc

       Possibilities:
               auto   (0)"
   ::= {er1645v2EthpdpBwEntry 1610612736}

er1645v2EthpdpBwTcFactor OBJECT-TYPE
   SYNTAX      INTEGER
               {
               ms (10),
               s100us (1)
               }
   MAX-ACCESS  read-write
   STATUS      current
   DESCRIPTION
      "Path: ethernetPdp.editConf.bandwidth.tcFactor

       Possibilities:
               ms   (10)
               *100us   (1)"
   ::= {er1645v2EthpdpBwEntry 2147483648}

er1645v2EthpdpBwCorrType OBJECT-TYPE
   SYNTAX      INTEGER
               {
               noCorrection (0),
               predefined (1),
               manual (2)
               }
   MAX-ACCESS  read-write
   STATUS      current
   DESCRIPTION
      "Path: ethernetPdp.editConf.bandwidth.correction.type

       Possibilities:
               noCorrection   (0)
               predefined   (1)
               manual   (2)"
   ::= {er1645v2EthpdpBwEntry 570425344}

er1645v2EthpdpBwCorrPredefEncapsFrameRelay OBJECT-TYPE
   SYNTAX      DisplayString
   MAX-ACCESS  read-write
   STATUS      current
   DESCRIPTION
      "Path: ethernetPdp.editConf.bandwidth.correction.predefined.encapsulation.frameRelay"
   ::= {er1645v2EthpdpBwEntry 608436224}

er1645v2EthpdpBwCorrPredefEncapsPpp OBJECT-TYPE
   SYNTAX      DisplayString
   MAX-ACCESS  read-write
   STATUS      current
   DESCRIPTION
      "Path: ethernetPdp.editConf.bandwidth.correction.predefined.encapsulation.ppp"
   ::= {er1645v2EthpdpBwEntry 608698368}

er1645v2EthpdpBwCorrPredefEncapsAtmHl OBJECT-TYPE
   SYNTAX      INTEGER
               {
               rfc2684 (0),
               ppp (1),
               pppOverEthernet (2)
               }
   MAX-ACCESS  read-write
   STATUS      current
   DESCRIPTION
      "Path: ethernetPdp.editConf.bandwidth.correction.predefined.encapsulation.atm.higherLayer

       Possibilities:
               rfc2684   (0)
               ppp   (1)
               pppOverEthernet   (2)"
   ::= {er1645v2EthpdpBwEntry 608993280}

er1645v2EthpdpBwCorrPredefEncapsAtmMp OBJECT-TYPE
   SYNTAX      INTEGER
               {
               llcEncapsulation (0),
               vcMultiplexing (1)
               }
   MAX-ACCESS  read-write
   STATUS      current
   DESCRIPTION
      "Path: ethernetPdp.editConf.bandwidth.correction.predefined.encapsulation.atm.multiProtocol

       Possibilities:
               llcEncapsulation   (0)
               vcMultiplexing   (1)"
   ::= {er1645v2EthpdpBwEntry 609026048}

er1645v2EthpdpBwCorrPredefEncapsHdlc OBJECT-TYPE
   SYNTAX      DisplayString
   MAX-ACCESS  read-write
   STATUS      current
   DESCRIPTION
      "Path: ethernetPdp.editConf.bandwidth.correction.predefined.encapsulation.hdlc"
   ::= {er1645v2EthpdpBwEntry 609222656}

er1645v2EthpdpBwCorrPredefEncapsEfmFs OBJECT-TYPE
   SYNTAX      Integer32
   MAX-ACCESS  read-write
   STATUS      current
   DESCRIPTION
      "Path: ethernetPdp.editConf.bandwidth.correction.predefined.encapsulation.efm.fragmentSize"
   ::= {er1645v2EthpdpBwEntry 609517568}

er1645v2EthpdpBwCorrPredefEncapsEfmIb OBJECT-TYPE
   SYNTAX      Integer32
   MAX-ACCESS  read-write
   STATUS      current
   DESCRIPTION
      "Path: ethernetPdp.editConf.bandwidth.correction.predefined.encapsulation.efm.idleBytes"
   ::= {er1645v2EthpdpBwEntry 609550336}

er1645v2EthpdpBwCorrPredefMode OBJECT-TYPE
   SYNTAX      INTEGER
               {
               routing (0),
               bridging (1)
               }
   MAX-ACCESS  read-write
   STATUS      current
   DESCRIPTION
      "Path: ethernetPdp.editConf.bandwidth.correction.predefined.mode

       Possibilities:
               routing   (0)
               bridging   (1)"
   ::= {er1645v2EthpdpBwEntry 612368384}

er1645v2EthpdpBwCorrManualOverhead OBJECT-TYPE
   SYNTAX      Integer32
   MAX-ACCESS  read-write
   STATUS      current
   DESCRIPTION
      "Path: ethernetPdp.editConf.bandwidth.correction.manual.overhead"
   ::= {er1645v2EthpdpBwEntry 637665280}

er1645v2EthpdpBwCorrManualFrameData OBJECT-TYPE
   SYNTAX      Counter32
   MAX-ACCESS  read-write
   STATUS      current
   DESCRIPTION
      "Path: ethernetPdp.editConf.bandwidth.correction.manual.frameData

       32 bit unsigned wrappable counter."
   ::= {er1645v2EthpdpBwEntry 637796352}

er1645v2EthpdpBwCorrManualFrameHeader OBJECT-TYPE
   SYNTAX      Counter32
   MAX-ACCESS  read-write
   STATUS      current
   DESCRIPTION
      "Path: ethernetPdp.editConf.bandwidth.correction.manual.frameHeader

       32 bit unsigned wrappable counter."
   ::= {er1645v2EthpdpBwEntry 637927424}

er1645v2EthpdpBwMaxFifoQLen OBJECT-TYPE
   SYNTAX      Integer32
   MAX-ACCESS  read-write
   STATUS      current
   DESCRIPTION
      "Path: ethernetPdp.editConf.bandwidth.maxFifoQLen"
   ::= {er1645v2EthpdpBwEntry 805306368}

er1645v2EthpdpBwDeFlagCir OBJECT-TYPE
   SYNTAX      INTEGER
               {
               allowed (1),
               notAllowed (2)
               }
   MAX-ACCESS  read-write
   STATUS      current
   DESCRIPTION
      "Path: ethernetPdp.editConf.bandwidth.deFlag.cir

       Possibilities:
               allowed   (1)
               notAllowed   (2)"
   ::= {er1645v2EthpdpBwEntry 3490709504}

er1645v2EthpdpBwDeFlagEir OBJECT-TYPE
   SYNTAX      INTEGER
               {
               allowed (1),
               notAllowed (2)
               }
   MAX-ACCESS  read-write
   STATUS      current
   DESCRIPTION
      "Path: ethernetPdp.editConf.bandwidth.deFlag.eir

       Possibilities:
               allowed   (1)
               notAllowed   (2)"
   ::= {er1645v2EthpdpBwEntry 3491758080}

er1645v2EthpdpBwDeFlagViolate OBJECT-TYPE
   SYNTAX      INTEGER
               {
               allowed (1),
               notAllowed (2)
               }
   MAX-ACCESS  read-write
   STATUS      current
   DESCRIPTION
      "Path: ethernetPdp.editConf.bandwidth.deFlag.violate

       Possibilities:
               allowed   (1)
               notAllowed   (2)"
   ::= {er1645v2EthpdpBwEntry 3492806656}

er1645v2EthpdpBwActCirActNone OBJECT-TYPE
   SYNTAX      OCTET STRING
   MAX-ACCESS  read-write
   STATUS      current
   DESCRIPTION
      "Path: ethernetPdp.editConf.bandwidth.action.cirAction.none"
   ::= {er1645v2EthpdpBwEntry 4062183424}

er1645v2EthpdpBwActCirActEthCos1 OBJECT-TYPE
   SYNTAX      INTEGER
               {
               unchanged (256)
               }
   MAX-ACCESS  read-write
   STATUS      current
   DESCRIPTION
      "Path: ethernetPdp.editConf.bandwidth.action.cirAction.ethernet.cosDepth1

       Possibilities:
               unchanged   (256)"
   ::= {er1645v2EthpdpBwEntry 4064346112}

er1645v2EthpdpBwActCirActEthDei1 OBJECT-TYPE
   SYNTAX      INTEGER
               {
               unchanged (255),
               clear (0),
               set (1)
               }
   MAX-ACCESS  read-write
   STATUS      current
   DESCRIPTION
      "Path: ethernetPdp.editConf.bandwidth.action.cirAction.ethernet.deiDepth1

       Possibilities:
               unchanged   (255)
               clear   (0)
               set   (1)"
   ::= {er1645v2EthpdpBwEntry 4065656832}

er1645v2EthpdpBwActCirActEthCos2 OBJECT-TYPE
   SYNTAX      INTEGER
               {
               unchanged (256)
               }
   MAX-ACCESS  read-write
   STATUS      current
   DESCRIPTION
      "Path: ethernetPdp.editConf.bandwidth.action.cirAction.ethernet.cosDepth2

       Possibilities:
               unchanged   (256)"
   ::= {er1645v2EthpdpBwEntry 4064411648}

er1645v2EthpdpBwActCirActEthDei2 OBJECT-TYPE
   SYNTAX      INTEGER
               {
               unchanged (255),
               clear (0),
               set (1)
               }
   MAX-ACCESS  read-write
   STATUS      current
   DESCRIPTION
      "Path: ethernetPdp.editConf.bandwidth.action.cirAction.ethernet.deiDepth2

       Possibilities:
               unchanged   (255)
               clear   (0)
               set   (1)"
   ::= {er1645v2EthpdpBwEntry 4065722368}

er1645v2EthpdpBwActCirActEthCos3 OBJECT-TYPE
   SYNTAX      INTEGER
               {
               unchanged (256)
               }
   MAX-ACCESS  read-write
   STATUS      current
   DESCRIPTION
      "Path: ethernetPdp.editConf.bandwidth.action.cirAction.ethernet.cosDepth3

       Possibilities:
               unchanged   (256)"
   ::= {er1645v2EthpdpBwEntry 4064477184}

er1645v2EthpdpBwActCirActEthDei3 OBJECT-TYPE
   SYNTAX      INTEGER
               {
               unchanged (255),
               clear (0),
               set (1)
               }
   MAX-ACCESS  read-write
   STATUS      current
   DESCRIPTION
      "Path: ethernetPdp.editConf.bandwidth.action.cirAction.ethernet.deiDepth3

       Possibilities:
               unchanged   (255)
               clear   (0)
               set   (1)"
   ::= {er1645v2EthpdpBwEntry 4065787904}

er1645v2EthpdpBwActCirActEthCos4 OBJECT-TYPE
   SYNTAX      INTEGER
               {
               unchanged (256)
               }
   MAX-ACCESS  read-write
   STATUS      current
   DESCRIPTION
      "Path: ethernetPdp.editConf.bandwidth.action.cirAction.ethernet.cosDepth4

       Possibilities:
               unchanged   (256)"
   ::= {er1645v2EthpdpBwEntry 4064542720}

er1645v2EthpdpBwActCirActEthDei4 OBJECT-TYPE
   SYNTAX      INTEGER
               {
               unchanged (255),
               clear (0),
               set (1)
               }
   MAX-ACCESS  read-write
   STATUS      current
   DESCRIPTION
      "Path: ethernetPdp.editConf.bandwidth.action.cirAction.ethernet.deiDepth4

       Possibilities:
               unchanged   (255)
               clear   (0)
               set   (1)"
   ::= {er1645v2EthpdpBwEntry 4065853440}

er1645v2EthpdpBwActCirActEthCos5 OBJECT-TYPE
   SYNTAX      INTEGER
               {
               unchanged (256)
               }
   MAX-ACCESS  read-write
   STATUS      current
   DESCRIPTION
      "Path: ethernetPdp.editConf.bandwidth.action.cirAction.ethernet.cosDepth5

       Possibilities:
               unchanged   (256)"
   ::= {er1645v2EthpdpBwEntry 4064608256}

er1645v2EthpdpBwActCirActEthDei5 OBJECT-TYPE
   SYNTAX      INTEGER
               {
               unchanged (255),
               clear (0),
               set (1)
               }
   MAX-ACCESS  read-write
   STATUS      current
   DESCRIPTION
      "Path: ethernetPdp.editConf.bandwidth.action.cirAction.ethernet.deiDepth5

       Possibilities:
               unchanged   (255)
               clear   (0)
               set   (1)"
   ::= {er1645v2EthpdpBwEntry 4065918976}

er1645v2EthpdpBwActCirActEthCos6 OBJECT-TYPE
   SYNTAX      INTEGER
               {
               unchanged (256)
               }
   MAX-ACCESS  read-write
   STATUS      current
   DESCRIPTION
      "Path: ethernetPdp.editConf.bandwidth.action.cirAction.ethernet.cosDepth6

       Possibilities:
               unchanged   (256)"
   ::= {er1645v2EthpdpBwEntry 4064673792}

er1645v2EthpdpBwActCirActEthDei6 OBJECT-TYPE
   SYNTAX      INTEGER
               {
               unchanged (255),
               clear (0),
               set (1)
               }
   MAX-ACCESS  read-write
   STATUS      current
   DESCRIPTION
      "Path: ethernetPdp.editConf.bandwidth.action.cirAction.ethernet.deiDepth6

       Possibilities:
               unchanged   (255)
               clear   (0)
               set   (1)"
   ::= {er1645v2EthpdpBwEntry 4065984512}

er1645v2EthpdpBwActCirActEthCos7 OBJECT-TYPE
   SYNTAX      INTEGER
               {
               unchanged (256)
               }
   MAX-ACCESS  read-write
   STATUS      current
   DESCRIPTION
      "Path: ethernetPdp.editConf.bandwidth.action.cirAction.ethernet.cosDepth7

       Possibilities:
               unchanged   (256)"
   ::= {er1645v2EthpdpBwEntry 4064739328}

er1645v2EthpdpBwActCirActEthDei7 OBJECT-TYPE
   SYNTAX      INTEGER
               {
               unchanged (255),
               clear (0),
               set (1)
               }
   MAX-ACCESS  read-write
   STATUS      current
   DESCRIPTION
      "Path: ethernetPdp.editConf.bandwidth.action.cirAction.ethernet.deiDepth7

       Possibilities:
               unchanged   (255)
               clear   (0)
               set   (1)"
   ::= {er1645v2EthpdpBwEntry 4066050048}

er1645v2EthpdpBwActCirActEthCos8 OBJECT-TYPE
   SYNTAX      INTEGER
               {
               unchanged (256)
               }
   MAX-ACCESS  read-write
   STATUS      current
   DESCRIPTION
      "Path: ethernetPdp.editConf.bandwidth.action.cirAction.ethernet.cosDepth8

       Possibilities:
               unchanged   (256)"
   ::= {er1645v2EthpdpBwEntry 4064804864}

er1645v2EthpdpBwActCirActEthDei8 OBJECT-TYPE
   SYNTAX      INTEGER
               {
               unchanged (255),
               clear (0),
               set (1)
               }
   MAX-ACCESS  read-write
   STATUS      current
   DESCRIPTION
      "Path: ethernetPdp.editConf.bandwidth.action.cirAction.ethernet.deiDepth8

       Possibilities:
               unchanged   (255)
               clear   (0)
               set   (1)"
   ::= {er1645v2EthpdpBwEntry 4066115584}

er1645v2EthpdpBwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernetPdp.editConf.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthpdpBwEntry 4064870400}

er1645v2EthpdpBwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernetPdp.editConf.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2EthpdpBwEntry 4064935936}

er1645v2EthpdpBwActCirActEthDrpLev OBJECT-TYPE
   SYNTAX      INTEGER
               {
               unchanged (0)
               }
   MAX-ACCESS  read-write
   STATUS      current
   DESCRIPTION
      "Path: ethernetPdp.editConf.bandwidth.action.cirAction.ethernet.dropLevel

       Possibilities:
               unchanged   (0)"
   ::= {er1645v2EthpdpBwEntry 4065001472}

er1645v2EthpdpBwActCirActEthDeFlag OBJECT-TYPE
   SYNTAX      INTEGER
               {
               unchanged (255),
               clear (0),
               set (1)
               }
   MAX-ACCESS  read-write
   STATUS      current
   DESCRIPTION
      "Path: ethernetPdp.editConf.bandwidth.action.cirAction.ethernet.deFlag

       Possibilities:
               unchanged   (255)
               clear   (0)
               set   (1)"
   ::= {er1645v2EthpdpBwEntry 4065198080}

er1645v2EthpdpBwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernetPdp.editConf.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthpdpBwEntry 4071161856}

er1645v2EthpdpBwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernetPdp.editConf.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2EthpdpBwEntry 4071227392}

er1645v2EthpdpBwActCirActIpDrpLev OBJECT-TYPE
   SYNTAX      INTEGER
               {
               unchanged (0)
               }
   MAX-ACCESS  read-write
   STATUS      current
   DESCRIPTION
      "Path: ethernetPdp.editConf.bandwidth.action.cirAction.ip.dropLevel

       Possibilities:
               unchanged   (0)"
   ::= {er1645v2EthpdpBwEntry 4071292928}

er1645v2EthpdpBwActCirActIpDeFlag OBJECT-TYPE
   SYNTAX      INTEGER
               {
               unchanged (255),
               clear (0),
               set (1)
               }
   MAX-ACCESS  read-write
   STATUS      current
   DESCRIPTION
      "Path: ethernetPdp.editConf.bandwidth.action.cirAction.ip.deFlag

       Possibilities:
               unchanged   (255)
               clear   (0)
               set   (1)"
   ::= {er1645v2EthpdpBwEntry 4071489536}

er1645v2EthpdpBwActEirActNone OBJECT-TYPE
   SYNTAX      OCTET STRING
   MAX-ACCESS  read-write
   STATUS      current
   DESCRIPTION
      "Path: ethernetPdp.editConf.bandwidth.action.eirAction.none"
   ::= {er1645v2EthpdpBwEntry 4095737856}

er1645v2EthpdpBwActEirActEthCos1 OBJECT-TYPE
   SYNTAX      INTEGER
               {
               unchanged (256)
               }
   MAX-ACCESS  read-write
   STATUS      current
   DESCRIPTION
      "Path: ethernetPdp.editConf.bandwidth.action.eirAction.ethernet.cosDepth1

       Possibilities:
               unchanged   (256)"
   ::= {er1645v2EthpdpBwEntry 4097900544}

er1645v2EthpdpBwActEirActEthDei1 OBJECT-TYPE
   SYNTAX      INTEGER
               {
               unchanged (255),
               clear (0),
               set (1)
               }
   MAX-ACCESS  read-write
   STATUS      current
   DESCRIPTION
      "Path: ethernetPdp.editConf.bandwidth.action.eirAction.ethernet.deiDepth1

       Possibilities:
               unchanged   (255)
               clear   (0)
               set   (1)"
   ::= {er1645v2EthpdpBwEntry 4099211264}

er1645v2EthpdpBwActEirActEthCos2 OBJECT-TYPE
   SYNTAX      INTEGER
               {
               unchanged (256)
               }
   MAX-ACCESS  read-write
   STATUS      current
   DESCRIPTION
      "Path: ethernetPdp.editConf.bandwidth.action.eirAction.ethernet.cosDepth2

       Possibilities:
               unchanged   (256)"
   ::= {er1645v2EthpdpBwEntry 4097966080}

er1645v2EthpdpBwActEirActEthDei2 OBJECT-TYPE
   SYNTAX      INTEGER
               {
               unchanged (255),
               clear (0),
               set (1)
               }
   MAX-ACCESS  read-write
   STATUS      current
   DESCRIPTION
      "Path: ethernetPdp.editConf.bandwidth.action.eirAction.ethernet.deiDepth2

       Possibilities:
               unchanged   (255)
               clear   (0)
               set   (1)"
   ::= {er1645v2EthpdpBwEntry 4099276800}

er1645v2EthpdpBwActEirActEthCos3 OBJECT-TYPE
   SYNTAX      INTEGER
               {
               unchanged (256)
               }
   MAX-ACCESS  read-write
   STATUS      current
   DESCRIPTION
      "Path: ethernetPdp.editConf.bandwidth.action.eirAction.ethernet.cosDepth3

       Possibilities:
               unchanged   (256)"
   ::= {er1645v2EthpdpBwEntry 4098031616}

er1645v2EthpdpBwActEirActEthDei3 OBJECT-TYPE
   SYNTAX      INTEGER
               {
               unchanged (255),
               clear (0),
               set (1)
               }
   MAX-ACCESS  read-write
   STATUS      current
   DESCRIPTION
      "Path: ethernetPdp.editConf.bandwidth.action.eirAction.ethernet.deiDepth3

       Possibilities:
               unchanged   (255)
               clear   (0)
               set   (1)"
   ::= {er1645v2EthpdpBwEntry 4099342336}

er1645v2EthpdpBwActEirActEthCos4 OBJECT-TYPE
   SYNTAX      INTEGER
               {
               unchanged (256)
               }
   MAX-ACCESS  read-write
   STATUS      current
   DESCRIPTION
      "Path: ethernetPdp.editConf.bandwidth.action.eirAction.ethernet.cosDepth4

       Possibilities:
               unchanged   (256)"
   ::= {er1645v2EthpdpBwEntry 4098097152}

er1645v2EthpdpBwActEirActEthDei4 OBJECT-TYPE
   SYNTAX      INTEGER
               {
               unchanged (255),
               clear (0),
               set (1)
               }
   MAX-ACCESS  read-write
   STATUS      current
   DESCRIPTION
      "Path: ethernetPdp.editConf.bandwidth.action.eirAction.ethernet.deiDepth4

       Possibilities:
               unchanged   (255)
               clear   (0)
               set   (1)"
   ::= {er1645v2EthpdpBwEntry 4099407872}

er1645v2EthpdpBwActEirActEthCos5 OBJECT-TYPE
   SYNTAX      INTEGER
               {
               unchanged (256)
               }
   MAX-ACCESS  read-write
   STATUS      current
   DESCRIPTION
      "Path: ethernetPdp.editConf.bandwidth.action.eirAction.ethernet.cosDepth5

       Possibilities:
               unchanged   (256)"
   ::= {er1645v2EthpdpBwEntry 4098162688}

er1645v2EthpdpBwActEirActEthDei5 OBJECT-TYPE
   SYNTAX      INTEGER
               {
               unchanged (255),
               clear (0),
               set (1)
               }
   MAX-ACCESS  read-write
   STATUS      current
   DESCRIPTION
      "Path: ethernetPdp.editConf.bandwidth.action.eirAction.ethernet.deiDepth5

       Possibilities:
               unchanged   (255)
               clear   (0)
               set   (1)"
   ::= {er1645v2EthpdpBwEntry 4099473408}

er1645v2EthpdpBwActEirActEthCos6 OBJECT-TYPE
   SYNTAX      INTEGER
               {
               unchanged (256)
               }
   MAX-ACCESS  read-write
   STATUS      current
   DESCRIPTION
      "Path: ethernetPdp.editConf.bandwidth.action.eirAction.ethernet.cosDepth6

       Possibilities:
               unchanged   (256)"
   ::= {er1645v2EthpdpBwEntry 4098228224}

er1645v2EthpdpBwActEirActEthDei6 OBJECT-TYPE
   SYNTAX      INTEGER
               {
               unchanged (255),
               clear (0),
               set (1)
               }
   MAX-ACCESS  read-write
   STATUS      current
   DESCRIPTION
      "Path: ethernetPdp.editConf.bandwidth.action.eirAction.ethernet.deiDepth6

       Possibilities:
               unchanged   (255)
               clear   (0)
               set   (1)"
   ::= {er1645v2EthpdpBwEntry 4099538944}

er1645v2EthpdpBwActEirActEthCos7 OBJECT-TYPE
   SYNTAX      INTEGER
               {
               unchanged (256)
               }
   MAX-ACCESS  read-write
   STATUS      current
   DESCRIPTION
      "Path: ethernetPdp.editConf.bandwidth.action.eirAction.ethernet.cosDepth7

       Possibilities:
               unchanged   (256)"
   ::= {er1645v2EthpdpBwEntry 4098293760}

er1645v2EthpdpBwActEirActEthDei7 OBJECT-TYPE
   SYNTAX      INTEGER
               {
               unchanged (255),
               clear (0),
               set (1)
               }
   MAX-ACCESS  read-write
   STATUS      current
   DESCRIPTION
      "Path: ethernetPdp.editConf.bandwidth.action.eirAction.ethernet.deiDepth7

       Possibilities:
               unchanged   (255)
               clear   (0)
               set   (1)"
   ::= {er1645v2EthpdpBwEntry 4099604480}

er1645v2EthpdpBwActEirActEthCos8 OBJECT-TYPE
   SYNTAX      INTEGER
               {
               unchanged (256)
               }
   MAX-ACCESS  read-write
   STATUS      current
   DESCRIPTION
      "Path: ethernetPdp.editConf.bandwidth.action.eirAction.ethernet.cosDepth8

       Possibilities:
               unchanged   (256)"
   ::= {er1645v2EthpdpBwEntry 4098359296}

er1645v2EthpdpBwActEirActEthDei8 OBJECT-TYPE
   SYNTAX      INTEGER
               {
               unchanged (255),
               clear (0),
               set (1)
               }
   MAX-ACCESS  read-write
   STATUS      current
   DESCRIPTION
      "Path: ethernetPdp.editConf.bandwidth.action.eirAction.ethernet.deiDepth8

       Possibilities:
               unchanged   (255)
               clear   (0)
               set   (1)"
   ::= {er1645v2EthpdpBwEntry 4099670016}

er1645v2EthpdpBwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernetPdp.editConf.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthpdpBwEntry 4098424832}

er1645v2EthpdpBwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernetPdp.editConf.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2EthpdpBwEntry 4098490368}

er1645v2EthpdpBwActEirActEthDrpLev OBJECT-TYPE
   SYNTAX      INTEGER
               {
               unchanged (0)
               }
   MAX-ACCESS  read-write
   STATUS      current
   DESCRIPTION
      "Path: ethernetPdp.editConf.bandwidth.action.eirAction.ethernet.dropLevel

       Possibilities:
               unchanged   (0)"
   ::= {er1645v2EthpdpBwEntry 4098555904}

er1645v2EthpdpBwActEirActEthDeFlag OBJECT-TYPE
   SYNTAX      INTEGER
               {
               unchanged (255),
               clear (0),
               set (1)
               }
   MAX-ACCESS  read-write
   STATUS      current
   DESCRIPTION
      "Path: ethernetPdp.editConf.bandwidth.action.eirAction.ethernet.deFlag

       Possibilities:
               unchanged   (255)
               clear   (0)
               set   (1)"
   ::= {er1645v2EthpdpBwEntry 4098752512}

er1645v2EthpdpBwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernetPdp.editConf.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthpdpBwEntry 4104716288}

er1645v2EthpdpBwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernetPdp.editConf.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2EthpdpBwEntry 4104781824}

er1645v2EthpdpBwActEirActIpDrpLev OBJECT-TYPE
   SYNTAX      INTEGER
               {
               unchanged (0)
               }
   MAX-ACCESS  read-write
   STATUS      current
   DESCRIPTION
      "Path: ethernetPdp.editConf.bandwidth.action.eirAction.ip.dropLevel

       Possibilities:
               unchanged   (0)"
   ::= {er1645v2EthpdpBwEntry 4104847360}

er1645v2EthpdpBwActEirActIpDeFlag OBJECT-TYPE
   SYNTAX      INTEGER
               {
               unchanged (255),
               clear (0),
               set (1)
               }
   MAX-ACCESS  read-write
   STATUS      current
   DESCRIPTION
      "Path: ethernetPdp.editConf.bandwidth.action.eirAction.ip.deFlag

       Possibilities:
               unchanged   (255)
               clear   (0)
               set   (1)"
   ::= {er1645v2EthpdpBwEntry 4105043968}

er1645v2EthpdpBwActViolActNone OBJECT-TYPE
   SYNTAX      OCTET STRING
   MAX-ACCESS  read-write
   STATUS      current
   DESCRIPTION
      "Path: ethernetPdp.editConf.bandwidth.action.violateAction.none"
   ::= {er1645v2EthpdpBwEntry 4129292288}

er1645v2EthpdpBwActViolActDrop OBJECT-TYPE
   SYNTAX      OCTET STRING
   MAX-ACCESS  read-write
   STATUS      current
   DESCRIPTION
      "Path: ethernetPdp.editConf.bandwidth.action.violateAction.drop"
   ::= {er1645v2EthpdpBwEntry 4133486592}

er1645v2EthpdpBwActViolActEthCos1 OBJECT-TYPE
   SYNTAX      INTEGER
               {
               unchanged (256)
               }
   MAX-ACCESS  read-write
   STATUS      current
   DESCRIPTION
      "Path: ethernetPdp.editConf.bandwidth.action.violateAction.ethernet.cosDepth1

       Possibilities:
               unchanged   (256)"
   ::= {er1645v2EthpdpBwEntry 4131454976}

er1645v2EthpdpBwActViolActEthDei1 OBJECT-TYPE
   SYNTAX      INTEGER
               {
               unchanged (255),
               clear (0),
               set (1)
               }
   MAX-ACCESS  read-write
   STATUS      current
   DESCRIPTION
      "Path: ethernetPdp.editConf.bandwidth.action.violateAction.ethernet.deiDepth1

       Possibilities:
               unchanged   (255)
               clear   (0)
               set   (1)"
   ::= {er1645v2EthpdpBwEntry 4132765696}

er1645v2EthpdpBwActViolActEthCos2 OBJECT-TYPE
   SYNTAX      INTEGER
               {
               unchanged (256)
               }
   MAX-ACCESS  read-write
   STATUS      current
   DESCRIPTION
      "Path: ethernetPdp.editConf.bandwidth.action.violateAction.ethernet.cosDepth2

       Possibilities:
               unchanged   (256)"
   ::= {er1645v2EthpdpBwEntry 4131520512}

er1645v2EthpdpBwActViolActEthDei2 OBJECT-TYPE
   SYNTAX      INTEGER
               {
               unchanged (255),
               clear (0),
               set (1)
               }
   MAX-ACCESS  read-write
   STATUS      current
   DESCRIPTION
      "Path: ethernetPdp.editConf.bandwidth.action.violateAction.ethernet.deiDepth2

       Possibilities:
               unchanged   (255)
               clear   (0)
               set   (1)"
   ::= {er1645v2EthpdpBwEntry 4132831232}

er1645v2EthpdpBwActViolActEthCos3 OBJECT-TYPE
   SYNTAX      INTEGER
               {
               unchanged (256)
               }
   MAX-ACCESS  read-write
   STATUS      current
   DESCRIPTION
      "Path: ethernetPdp.editConf.bandwidth.action.violateAction.ethernet.cosDepth3

       Possibilities:
               unchanged   (256)"
   ::= {er1645v2EthpdpBwEntry 4131586048}

er1645v2EthpdpBwActViolActEthDei3 OBJECT-TYPE
   SYNTAX      INTEGER
               {
               unchanged (255),
               clear (0),
               set (1)
               }
   MAX-ACCESS  read-write
   STATUS      current
   DESCRIPTION
      "Path: ethernetPdp.editConf.bandwidth.action.violateAction.ethernet.deiDepth3

       Possibilities:
               unchanged   (255)
               clear   (0)
               set   (1)"
   ::= {er1645v2EthpdpBwEntry 4132896768}

er1645v2EthpdpBwActViolActEthCos4 OBJECT-TYPE
   SYNTAX      INTEGER
               {
               unchanged (256)
               }
   MAX-ACCESS  read-write
   STATUS      current
   DESCRIPTION
      "Path: ethernetPdp.editConf.bandwidth.action.violateAction.ethernet.cosDepth4

       Possibilities:
               unchanged   (256)"
   ::= {er1645v2EthpdpBwEntry 4131651584}

er1645v2EthpdpBwActViolActEthDei4 OBJECT-TYPE
   SYNTAX      INTEGER
               {
               unchanged (255),
               clear (0),
               set (1)
               }
   MAX-ACCESS  read-write
   STATUS      current
   DESCRIPTION
      "Path: ethernetPdp.editConf.bandwidth.action.violateAction.ethernet.deiDepth4

       Possibilities:
               unchanged   (255)
               clear   (0)
               set   (1)"
   ::= {er1645v2EthpdpBwEntry 4132962304}

er1645v2EthpdpBwActViolActEthCos5 OBJECT-TYPE
   SYNTAX      INTEGER
               {
               unchanged (256)
               }
   MAX-ACCESS  read-write
   STATUS      current
   DESCRIPTION
      "Path: ethernetPdp.editConf.bandwidth.action.violateAction.ethernet.cosDepth5

       Possibilities:
               unchanged   (256)"
   ::= {er1645v2EthpdpBwEntry 4131717120}

er1645v2EthpdpBwActViolActEthDei5 OBJECT-TYPE
   SYNTAX      INTEGER
               {
               unchanged (255),
               clear (0),
               set (1)
               }
   MAX-ACCESS  read-write
   STATUS      current
   DESCRIPTION
      "Path: ethernetPdp.editConf.bandwidth.action.violateAction.ethernet.deiDepth5

       Possibilities:
               unchanged   (255)
               clear   (0)
               set   (1)"
   ::= {er1645v2EthpdpBwEntry 4133027840}

er1645v2EthpdpBwActViolActEthCos6 OBJECT-TYPE
   SYNTAX      INTEGER
               {
               unchanged (256)
               }
   MAX-ACCESS  read-write
   STATUS      current
   DESCRIPTION
      "Path: ethernetPdp.editConf.bandwidth.action.violateAction.ethernet.cosDepth6

       Possibilities:
               unchanged   (256)"
   ::= {er1645v2EthpdpBwEntry 4131782656}

er1645v2EthpdpBwActViolActEthDei6 OBJECT-TYPE
   SYNTAX      INTEGER
               {
               unchanged (255),
               clear (0),
               set (1)
               }
   MAX-ACCESS  read-write
   STATUS      current
   DESCRIPTION
      "Path: ethernetPdp.editConf.bandwidth.action.violateAction.ethernet.deiDepth6

       Possibilities:
               unchanged   (255)
               clear   (0)
               set   (1)"
   ::= {er1645v2EthpdpBwEntry 4133093376}

er1645v2EthpdpBwActViolActEthCos7 OBJECT-TYPE
   SYNTAX      INTEGER
               {
               unchanged (256)
               }
   MAX-ACCESS  read-write
   STATUS      current
   DESCRIPTION
      "Path: ethernetPdp.editConf.bandwidth.action.violateAction.ethernet.cosDepth7

       Possibilities:
               unchanged   (256)"
   ::= {er1645v2EthpdpBwEntry 4131848192}

er1645v2EthpdpBwActViolActEthDei7 OBJECT-TYPE
   SYNTAX      INTEGER
               {
               unchanged (255),
               clear (0),
               set (1)
               }
   MAX-ACCESS  read-write
   STATUS      current
   DESCRIPTION
      "Path: ethernetPdp.editConf.bandwidth.action.violateAction.ethernet.deiDepth7

       Possibilities:
               unchanged   (255)
               clear   (0)
               set   (1)"
   ::= {er1645v2EthpdpBwEntry 4133158912}

er1645v2EthpdpBwActViolActEthCos8 OBJECT-TYPE
   SYNTAX      INTEGER
               {
               unchanged (256)
               }
   MAX-ACCESS  read-write
   STATUS      current
   DESCRIPTION
      "Path: ethernetPdp.editConf.bandwidth.action.violateAction.ethernet.cosDepth8

       Possibilities:
               unchanged   (256)"
   ::= {er1645v2EthpdpBwEntry 4131913728}

er1645v2EthpdpBwActViolActEthDei8 OBJECT-TYPE
   SYNTAX      INTEGER
               {
               unchanged (255),
               clear (0),
               set (1)
               }
   MAX-ACCESS  read-write
   STATUS      current
   DESCRIPTION
      "Path: ethernetPdp.editConf.bandwidth.action.violateAction.ethernet.deiDepth8

       Possibilities:
               unchanged   (255)
               clear   (0)
               set   (1)"
   ::= {er1645v2EthpdpBwEntry 4133224448}

er1645v2EthpdpBwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernetPdp.editConf.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthpdpBwEntry 4131979264}

er1645v2EthpdpBwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernetPdp.editConf.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2EthpdpBwEntry 4132044800}

er1645v2EthpdpBwActViolActEthDrpLev OBJECT-TYPE
   SYNTAX      INTEGER
               {
               unchanged (0)
               }
   MAX-ACCESS  read-write
   STATUS      current
   DESCRIPTION
      "Path: ethernetPdp.editConf.bandwidth.action.violateAction.ethernet.dropLevel

       Possibilities:
               unchanged   (0)"
   ::= {er1645v2EthpdpBwEntry 4132110336}

er1645v2EthpdpBwActViolActEthDeFlag OBJECT-TYPE
   SYNTAX      INTEGER
               {
               unchanged (255),
               clear (0),
               set (1)
               }
   MAX-ACCESS  read-write
   STATUS      current
   DESCRIPTION
      "Path: ethernetPdp.editConf.bandwidth.action.violateAction.ethernet.deFlag

       Possibilities:
               unchanged   (255)
               clear   (0)
               set   (1)"
   ::= {er1645v2EthpdpBwEntry 4132306944}

er1645v2EthpdpBwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernetPdp.editConf.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthpdpBwEntry 4138270720}

er1645v2EthpdpBwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernetPdp.editConf.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2EthpdpBwEntry 4138336256}

er1645v2EthpdpBwActViolActIpDrpLev OBJECT-TYPE
   SYNTAX      INTEGER
               {
               unchanged (0)
               }
   MAX-ACCESS  read-write
   STATUS      current
   DESCRIPTION
      "Path: ethernetPdp.editConf.bandwidth.action.violateAction.ip.dropLevel

       Possibilities:
               unchanged   (0)"
   ::= {er1645v2EthpdpBwEntry 4138401792}

er1645v2EthpdpBwActViolActIpDeFlag OBJECT-TYPE
   SYNTAX      INTEGER
               {
               unchanged (255),
               clear (0),
               set (1)
               }
   MAX-ACCESS  read-write
   STATUS      current
   DESCRIPTION
      "Path: ethernetPdp.editConf.bandwidth.action.violateAction.ip.deFlag

       Possibilities:
               unchanged   (255)
               clear   (0)
               set   (1)"
   ::= {er1645v2EthpdpBwEntry 4138598400}


er1645v2EthpdpPriorityPolicy OBJECT IDENTIFIER ::= {er1645v2Ethpdp 39}

er1645v2EthpdpPriorityPolicyTable OBJECT-TYPE
   SYNTAX      SEQUENCE OF Er1645v2EthpdpPriorityPolicyEntry
   MAX-ACCESS  not-accessible
   STATUS      current
   DESCRIPTION
      "Preferred Policy"
   ::= {er1645v2EthpdpPriorityPolicy 1}

er1645v2EthpdpPriorityPolicyEntry OBJECT-TYPE
   SYNTAX      Er1645v2EthpdpPriorityPolicyEntry
   MAX-ACCESS  not-accessible
   STATUS      current
   DESCRIPTION
      ""
   INDEX      { er1645v2EthpdpPriorityPolicyGlobalIx }
   ::= {er1645v2EthpdpPriorityPolicyTable 1}

Er1645v2EthpdpPriorityPolicyEntry ::=
   SEQUENCE
      {
      er1645v2EthpdpPriorityPolicyGlobalIx
         GlobalIndex,
      er1645v2EthpdpPriorityPolicyValue
         DisplayString
      }

er1645v2EthpdpPriorityPolicyGlobalIx OBJECT-TYPE
   SYNTAX      GlobalIndex
   MAX-ACCESS  not-accessible
   STATUS      current
   DESCRIPTION
      "The value of the tlsCntTreeGlobalIndex of the MANAGED OBJECT."
   ::= {er1645v2EthpdpPriorityPolicyEntry 10}

er1645v2EthpdpPriorityPolicyValue OBJECT-TYPE
   SYNTAX      DisplayString
   MAX-ACCESS  read-write
   STATUS      current
   DESCRIPTION
      "Path: ethernetPdp.editConf.priorityPolicy"
   ::= {er1645v2EthpdpPriorityPolicyEntry 2147483648}


er1645v2EthpdpSnmpIndexOffset OBJECT IDENTIFIER ::= {er1645v2Ethpdp 268}

er1645v2EthpdpSnmpIndexOffsetTable OBJECT-TYPE
   SYNTAX      SEQUENCE OF Er1645v2EthpdpSnmpIndexOffsetEntry
   MAX-ACCESS  not-accessible
   STATUS      current
   DESCRIPTION
      "Preferred offset in the range of SNMP indices for this SWinst, 0 means automatic"
   ::= {er1645v2EthpdpSnmpIndexOffset 1}

er1645v2EthpdpSnmpIndexOffsetEntry OBJECT-TYPE
   SYNTAX      Er1645v2EthpdpSnmpIndexOffsetEntry
   MAX-ACCESS  not-accessible
   STATUS      current
   DESCRIPTION
      ""
   INDEX      { er1645v2EthpdpSnmpIndexOffsetGlobalIx }
   ::= {er1645v2EthpdpSnmpIndexOffsetTable 1}

Er1645v2EthpdpSnmpIndexOffsetEntry ::=
   SEQUENCE
      {
      er1645v2EthpdpSnmpIndexOffsetGlobalIx
         GlobalIndex,
      er1645v2EthpdpSnmpIndexOffsetValue
         Integer32
      }

er1645v2EthpdpSnmpIndexOffsetGlobalIx OBJECT-TYPE
   SYNTAX      GlobalIndex
   MAX-ACCESS  not-accessible
   STATUS      current
   DESCRIPTION
      "The value of the tlsCntTreeGlobalIndex of the MANAGED OBJECT."
   ::= {er1645v2EthpdpSnmpIndexOffsetEntry 10}

er1645v2EthpdpSnmpIndexOffsetValue OBJECT-TYPE
   SYNTAX      Integer32
   MAX-ACCESS  read-write
   STATUS      current
   DESCRIPTION
      "Path: ethernetPdp.editConf.snmpIndexOffset"
   ::= {er1645v2EthpdpSnmpIndexOffsetEntry 2147483648}



sr1645v2Ethpdp OBJECT IDENTIFIER ::= {r1645v2Ethpdp 14}


sr1645v2EthpdpDescr OBJECT IDENTIFIER ::= {sr1645v2Ethpdp 101}

sr1645v2EthpdpDescrTable OBJECT-TYPE
   SYNTAX      SEQUENCE OF Sr1645v2EthpdpDescrEntry
   MAX-ACCESS  not-accessible
   STATUS      current
   DESCRIPTION
      "ifDescr"
   ::= {sr1645v2EthpdpDescr 1}

sr1645v2EthpdpDescrEntry OBJECT-TYPE
   SYNTAX      Sr1645v2EthpdpDescrEntry
   MAX-ACCESS  not-accessible
   STATUS      current
   DESCRIPTION
      ""
   INDEX      { sr1645v2EthpdpDescrGlobalIx }
   ::= {sr1645v2EthpdpDescrTable 1}

Sr1645v2EthpdpDescrEntry ::=
   SEQUENCE
      {
      sr1645v2EthpdpDescrGlobalIx
         GlobalIndex,
      sr1645v2EthpdpDescrValue
         DisplayString
      }

sr1645v2EthpdpDescrGlobalIx OBJECT-TYPE
   SYNTAX      GlobalIndex
   MAX-ACCESS  not-accessible
   STATUS      current
   DESCRIPTION
      "The value of the tlsCntTreeGlobalIndex of the MANAGED OBJECT."
   ::= {sr1645v2EthpdpDescrEntry 10}

sr1645v2EthpdpDescrValue OBJECT-TYPE
   SYNTAX      DisplayString
   MAX-ACCESS  read-only
   STATUS      current
   DESCRIPTION
      "Path: ethernetPdp.status.ifDescr"
   ::= {sr1645v2EthpdpDescrEntry 2147483648}


sr1645v2EthpdpState OBJECT IDENTIFIER ::= {sr1645v2Ethpdp 47}

sr1645v2EthpdpStateTable OBJECT-TYPE
   SYNTAX      SEQUENCE OF Sr1645v2EthpdpStateEntry
   MAX-ACCESS  not-accessible
   STATUS      current
   DESCRIPTION
      "call state"
   ::= {sr1645v2EthpdpState 1}

sr1645v2EthpdpStateEntry OBJECT-TYPE
   SYNTAX      Sr1645v2EthpdpStateEntry
   MAX-ACCESS  not-accessible
   STATUS      current
   DESCRIPTION
      ""
   INDEX      { sr1645v2EthpdpStateGlobalIx }
   ::= {sr1645v2EthpdpStateTable 1}

Sr1645v2EthpdpStateEntry ::=
   SEQUENCE
      {
      sr1645v2EthpdpStateGlobalIx
         GlobalIndex,
      sr1645v2EthpdpStateValue
         INTEGER
      }

sr1645v2EthpdpStateGlobalIx OBJECT-TYPE
   SYNTAX      GlobalIndex
   MAX-ACCESS  not-accessible
   STATUS      current
   DESCRIPTION
      "The value of the tlsCntTreeGlobalIndex of the MANAGED OBJECT."
   ::= {sr1645v2EthpdpStateEntry 10}

sr1645v2EthpdpStateValue OBJECT-TYPE
   SYNTAX      INTEGER
               {
               init (0),
               l1Down (1),
               ready (2),
               dialing (3),
               up (4),
               releasing (5)
               }
   MAX-ACCESS  read-only
   STATUS      current
   DESCRIPTION
      "Path: ethernetPdp.status.state

       Possibilities:
               init   (0)
               l1Down   (1)
               ready   (2)
               dialing   (3)
               up   (4)
               releasing   (5)"
   ::= {sr1645v2EthpdpStateEntry 2147483648}


sr1645v2EthpdpIfMtu OBJECT IDENTIFIER ::= {sr1645v2Ethpdp 103}

sr1645v2EthpdpIfMtuTable OBJECT-TYPE
   SYNTAX      SEQUENCE OF Sr1645v2EthpdpIfMtuEntry
   MAX-ACCESS  not-accessible
   STATUS      current
   DESCRIPTION
      "ifMtu"
   ::= {sr1645v2EthpdpIfMtu 1}

sr1645v2EthpdpIfMtuEntry OBJECT-TYPE
   SYNTAX      Sr1645v2EthpdpIfMtuEntry
   MAX-ACCESS  not-accessible
   STATUS      current
   DESCRIPTION
      ""
   INDEX      { sr1645v2EthpdpIfMtuGlobalIx }
   ::= {sr1645v2EthpdpIfMtuTable 1}

Sr1645v2EthpdpIfMtuEntry ::=
   SEQUENCE
      {
      sr1645v2EthpdpIfMtuGlobalIx
         GlobalIndex,
      sr1645v2EthpdpIfMtuValue
         Integer32
      }

sr1645v2EthpdpIfMtuGlobalIx OBJECT-TYPE
   SYNTAX      GlobalIndex
   MAX-ACCESS  not-accessible
   STATUS      current
   DESCRIPTION
      "The value of the tlsCntTreeGlobalIndex of the MANAGED OBJECT."
   ::= {sr1645v2EthpdpIfMtuEntry 10}

sr1645v2EthpdpIfMtuValue OBJECT-TYPE
   SYNTAX      Integer32
   MAX-ACCESS  read-only
   STATUS      current
   DESCRIPTION
      "Path: ethernetPdp.status.ifMtu"
   ::= {sr1645v2EthpdpIfMtuEntry 2147483648}


sr1645v2EthpdpSnmpIndex OBJECT IDENTIFIER ::= {sr1645v2Ethpdp 269}

sr1645v2EthpdpSnmpIndexTable OBJECT-TYPE
   SYNTAX      SEQUENCE OF Sr1645v2EthpdpSnmpIndexEntry
   MAX-ACCESS  not-accessible
   STATUS      current
   DESCRIPTION
      "SNMP index assigned to this object"
   ::= {sr1645v2EthpdpSnmpIndex 1}

sr1645v2EthpdpSnmpIndexEntry OBJECT-TYPE
   SYNTAX      Sr1645v2EthpdpSnmpIndexEntry
   MAX-ACCESS  not-accessible
   STATUS      current
   DESCRIPTION
      ""
   INDEX      { sr1645v2EthpdpSnmpIndexGlobalIx }
   ::= {sr1645v2EthpdpSnmpIndexTable 1}

Sr1645v2EthpdpSnmpIndexEntry ::=
   SEQUENCE
      {
      sr1645v2EthpdpSnmpIndexGlobalIx
         GlobalIndex,
      sr1645v2EthpdpSnmpIndexValue
         Integer32
      }

sr1645v2EthpdpSnmpIndexGlobalIx OBJECT-TYPE
   SYNTAX      GlobalIndex
   MAX-ACCESS  not-accessible
   STATUS      current
   DESCRIPTION
      "The value of the tlsCntTreeGlobalIndex of the MANAGED OBJECT."
   ::= {sr1645v2EthpdpSnmpIndexEntry 10}

sr1645v2EthpdpSnmpIndexValue OBJECT-TYPE
   SYNTAX      Integer32
   MAX-ACCESS  read-only
   STATUS      current
   DESCRIPTION
      "Path: ethernetPdp.status.snmpIndex"
   ::= {sr1645v2EthpdpSnmpIndexEntry 2147483648}



pr1645v2Ethpdp OBJECT IDENTIFIER ::= {r1645v2Ethpdp 12}


pr1645v2EthpdpInOctets OBJECT IDENTIFIER ::= {pr1645v2Ethpdp 109}

pr1645v2EthpdpInOctetsTable OBJECT-TYPE
   SYNTAX      SEQUENCE OF Pr1645v2EthpdpInOctetsEntry
   MAX-ACCESS  not-accessible
   STATUS      current
   DESCRIPTION
      "ifInOctets"
   ::= {pr1645v2EthpdpInOctets 1}

pr1645v2EthpdpInOctetsEntry OBJECT-TYPE
   SYNTAX      Pr1645v2EthpdpInOctetsEntry
   MAX-ACCESS  not-accessible
   STATUS      current
   DESCRIPTION
      ""
   INDEX      { pr1645v2EthpdpInOctetsGlobalIx }
   ::= {pr1645v2EthpdpInOctetsTable 1}

Pr1645v2EthpdpInOctetsEntry ::=
   SEQUENCE
      {
      pr1645v2EthpdpInOctetsGlobalIx
         GlobalIndex,
      pr1645v2EthpdpInOctetsValue
         Counter64
      }

pr1645v2EthpdpInOctetsGlobalIx OBJECT-TYPE
   SYNTAX      GlobalIndex
   MAX-ACCESS  not-accessible
   STATUS      current
   DESCRIPTION
      "The value of the tlsCntTreeGlobalIndex of the MANAGED OBJECT."
   ::= {pr1645v2EthpdpInOctetsEntry 10}

pr1645v2EthpdpInOctetsValue OBJECT-TYPE
   SYNTAX      Counter64
   MAX-ACCESS  read-only
   STATUS      current
   DESCRIPTION
      "Path: ethernetPdp.performance.ifInOctets

       64 bit unsigned wrappable counter."
   ::= {pr1645v2EthpdpInOctetsEntry 2147483648}


pr1645v2EthpdpInUcast OBJECT IDENTIFIER ::= {pr1645v2Ethpdp 110}

pr1645v2EthpdpInUcastTable OBJECT-TYPE
   SYNTAX      SEQUENCE OF Pr1645v2EthpdpInUcastEntry
   MAX-ACCESS  not-accessible
   STATUS      current
   DESCRIPTION
      "ifInUcastPkts"
   ::= {pr1645v2EthpdpInUcast 1}

pr1645v2EthpdpInUcastEntry OBJECT-TYPE
   SYNTAX      Pr1645v2EthpdpInUcastEntry
   MAX-ACCESS  not-accessible
   STATUS      current
   DESCRIPTION
      ""
   INDEX      { pr1645v2EthpdpInUcastGlobalIx }
   ::= {pr1645v2EthpdpInUcastTable 1}

Pr1645v2EthpdpInUcastEntry ::=
   SEQUENCE
      {
      pr1645v2EthpdpInUcastGlobalIx
         GlobalIndex,
      pr1645v2EthpdpInUcastValue
         Counter64
      }

pr1645v2EthpdpInUcastGlobalIx OBJECT-TYPE
   SYNTAX      GlobalIndex
   MAX-ACCESS  not-accessible
   STATUS      current
   DESCRIPTION
      "The value of the tlsCntTreeGlobalIndex of the MANAGED OBJECT."
   ::= {pr1645v2EthpdpInUcastEntry 10}

pr1645v2EthpdpInUcastValue OBJECT-TYPE
   SYNTAX      Counter64
   MAX-ACCESS  read-only
   STATUS      current
   DESCRIPTION
      "Path: ethernetPdp.performance.ifInUcastPkts

       64 bit unsigned wrappable counter."
   ::= {pr1645v2EthpdpInUcastEntry 2147483648}


pr1645v2EthpdpInNUcastPkts OBJECT IDENTIFIER ::= {pr1645v2Ethpdp 111}

pr1645v2EthpdpInNUcastPktsTable OBJECT-TYPE
   SYNTAX      SEQUENCE OF Pr1645v2EthpdpInNUcastPktsEntry
   MAX-ACCESS  not-accessible
   STATUS      current
   DESCRIPTION
      "ifInNUcastPkts"
   ::= {pr1645v2EthpdpInNUcastPkts 1}

pr1645v2EthpdpInNUcastPktsEntry OBJECT-TYPE
   SYNTAX      Pr1645v2EthpdpInNUcastPktsEntry
   MAX-ACCESS  not-accessible
   STATUS      current
   DESCRIPTION
      ""
   INDEX      { pr1645v2EthpdpInNUcastPktsGlobalIx }
   ::= {pr1645v2EthpdpInNUcastPktsTable 1}

Pr1645v2EthpdpInNUcastPktsEntry ::=
   SEQUENCE
      {
      pr1645v2EthpdpInNUcastPktsGlobalIx
         GlobalIndex,
      pr1645v2EthpdpInNUcastPktsValue
         Counter64
      }

pr1645v2EthpdpInNUcastPktsGlobalIx OBJECT-TYPE
   SYNTAX      GlobalIndex
   MAX-ACCESS  not-accessible
   STATUS      current
   DESCRIPTION
      "The value of the tlsCntTreeGlobalIndex of the MANAGED OBJECT."
   ::= {pr1645v2EthpdpInNUcastPktsEntry 10}

pr1645v2EthpdpInNUcastPktsValue OBJECT-TYPE
   SYNTAX      Counter64
   MAX-ACCESS  read-only
   STATUS      current
   DESCRIPTION
      "Path: ethernetPdp.performance.ifInNUcastPkts

       64 bit unsigned wrappable counter."
   ::= {pr1645v2EthpdpInNUcastPktsEntry 2147483648}


pr1645v2EthpdpInDiscards OBJECT IDENTIFIER ::= {pr1645v2Ethpdp 112}

pr1645v2EthpdpInDiscardsTable OBJECT-TYPE
   SYNTAX      SEQUENCE OF Pr1645v2EthpdpInDiscardsEntry
   MAX-ACCESS  not-accessible
   STATUS      current
   DESCRIPTION
      "ifInDiscards"
   ::= {pr1645v2EthpdpInDiscards 1}

pr1645v2EthpdpInDiscardsEntry OBJECT-TYPE
   SYNTAX      Pr1645v2EthpdpInDiscardsEntry
   MAX-ACCESS  not-accessible
   STATUS      current
   DESCRIPTION
      ""
   INDEX      { pr1645v2EthpdpInDiscardsGlobalIx }
   ::= {pr1645v2EthpdpInDiscardsTable 1}

Pr1645v2EthpdpInDiscardsEntry ::=
   SEQUENCE
      {
      pr1645v2EthpdpInDiscardsGlobalIx
         GlobalIndex,
      pr1645v2EthpdpInDiscardsValue
         Counter64
      }

pr1645v2EthpdpInDiscardsGlobalIx OBJECT-TYPE
   SYNTAX      GlobalIndex
   MAX-ACCESS  not-accessible
   STATUS      current
   DESCRIPTION
      "The value of the tlsCntTreeGlobalIndex of the MANAGED OBJECT."
   ::= {pr1645v2EthpdpInDiscardsEntry 10}

pr1645v2EthpdpInDiscardsValue OBJECT-TYPE
   SYNTAX      Counter64
   MAX-ACCESS  read-only
   STATUS      current
   DESCRIPTION
      "Path: ethernetPdp.performance.ifInDiscards

       64 bit unsigned wrappable counter."
   ::= {pr1645v2EthpdpInDiscardsEntry 2147483648}


pr1645v2EthpdpInErrors OBJECT IDENTIFIER ::= {pr1645v2Ethpdp 113}

pr1645v2EthpdpInErrorsTable OBJECT-TYPE
   SYNTAX      SEQUENCE OF Pr1645v2EthpdpInErrorsEntry
   MAX-ACCESS  not-accessible
   STATUS      current
   DESCRIPTION
      "ifInErrors"
   ::= {pr1645v2EthpdpInErrors 1}

pr1645v2EthpdpInErrorsEntry OBJECT-TYPE
   SYNTAX      Pr1645v2EthpdpInErrorsEntry
   MAX-ACCESS  not-accessible
   STATUS      current
   DESCRIPTION
      ""
   INDEX      { pr1645v2EthpdpInErrorsGlobalIx }
   ::= {pr1645v2EthpdpInErrorsTable 1}

Pr1645v2EthpdpInErrorsEntry ::=
   SEQUENCE
      {
      pr1645v2EthpdpInErrorsGlobalIx
         GlobalIndex,
      pr1645v2EthpdpInErrorsValue
         Counter64
      }

pr1645v2EthpdpInErrorsGlobalIx OBJECT-TYPE
   SYNTAX      GlobalIndex
   MAX-ACCESS  not-accessible
   STATUS      current
   DESCRIPTION
      "The value of the tlsCntTreeGlobalIndex of the MANAGED OBJECT."
   ::= {pr1645v2EthpdpInErrorsEntry 10}

pr1645v2EthpdpInErrorsValue OBJECT-TYPE
   SYNTAX      Counter64
   MAX-ACCESS  read-only
   STATUS      current
   DESCRIPTION
      "Path: ethernetPdp.performance.ifInErrors

       64 bit unsigned wrappable counter."
   ::= {pr1645v2EthpdpInErrorsEntry 2147483648}


pr1645v2EthpdpInUnknownProtos OBJECT IDENTIFIER ::= {pr1645v2Ethpdp 114}

pr1645v2EthpdpInUnknownProtosTable OBJECT-TYPE
   SYNTAX      SEQUENCE OF Pr1645v2EthpdpInUnknownProtosEntry
   MAX-ACCESS  not-accessible
   STATUS      current
   DESCRIPTION
      "ifInUnknownprotos"
   ::= {pr1645v2EthpdpInUnknownProtos 1}

pr1645v2EthpdpInUnknownProtosEntry OBJECT-TYPE
   SYNTAX      Pr1645v2EthpdpInUnknownProtosEntry
   MAX-ACCESS  not-accessible
   STATUS      current
   DESCRIPTION
      ""
   INDEX      { pr1645v2EthpdpInUnknownProtosGlobalIx }
   ::= {pr1645v2EthpdpInUnknownProtosTable 1}

Pr1645v2EthpdpInUnknownProtosEntry ::=
   SEQUENCE
      {
      pr1645v2EthpdpInUnknownProtosGlobalIx
         GlobalIndex,
      pr1645v2EthpdpInUnknownProtosValue
         Counter64
      }

pr1645v2EthpdpInUnknownProtosGlobalIx OBJECT-TYPE
   SYNTAX      GlobalIndex
   MAX-ACCESS  not-accessible
   STATUS      current
   DESCRIPTION
      "The value of the tlsCntTreeGlobalIndex of the MANAGED OBJECT."
   ::= {pr1645v2EthpdpInUnknownProtosEntry 10}

pr1645v2EthpdpInUnknownProtosValue OBJECT-TYPE
   SYNTAX      Counter64
   MAX-ACCESS  read-only
   STATUS      current
   DESCRIPTION
      "Path: ethernetPdp.performance.ifInUnknownProtos

       64 bit unsigned wrappable counter."
   ::= {pr1645v2EthpdpInUnknownProtosEntry 2147483648}


pr1645v2EthpdpInQLen OBJECT IDENTIFIER ::= {pr1645v2Ethpdp 128}

pr1645v2EthpdpInQLenTable OBJECT-TYPE
   SYNTAX      SEQUENCE OF Pr1645v2EthpdpInQLenEntry
   MAX-ACCESS  not-accessible
   STATUS      current
   DESCRIPTION
      "ifInQLen"
   ::= {pr1645v2EthpdpInQLen 1}

pr1645v2EthpdpInQLenEntry OBJECT-TYPE
   SYNTAX      Pr1645v2EthpdpInQLenEntry
   MAX-ACCESS  not-accessible
   STATUS      current
   DESCRIPTION
      ""
   INDEX      { pr1645v2EthpdpInQLenGlobalIx }
   ::= {pr1645v2EthpdpInQLenTable 1}

Pr1645v2EthpdpInQLenEntry ::=
   SEQUENCE
      {
      pr1645v2EthpdpInQLenGlobalIx
         GlobalIndex,
      pr1645v2EthpdpInQLenValue
         Gauge32
      }

pr1645v2EthpdpInQLenGlobalIx OBJECT-TYPE
   SYNTAX      GlobalIndex
   MAX-ACCESS  not-accessible
   STATUS      current
   DESCRIPTION
      "The value of the tlsCntTreeGlobalIndex of the MANAGED OBJECT."
   ::= {pr1645v2EthpdpInQLenEntry 10}

pr1645v2EthpdpInQLenValue OBJECT-TYPE
   SYNTAX      Gauge32
   MAX-ACCESS  read-only
   STATUS      current
   DESCRIPTION
      "Path: ethernetPdp.performance.ifInQLen

       32 bit unsigned gauge value."
   ::= {pr1645v2EthpdpInQLenEntry 2147483648}


pr1645v2EthpdpInDropEx OBJECT IDENTIFIER ::= {pr1645v2Ethpdp 130}

pr1645v2EthpdpInDropExTable OBJECT-TYPE
   SYNTAX      SEQUENCE OF Pr1645v2EthpdpInDropExEntry
   MAX-ACCESS  not-accessible
   STATUS      current
   DESCRIPTION
      "ifInDiscards"
   ::= {pr1645v2EthpdpInDropEx 1}

pr1645v2EthpdpInDropExEntry OBJECT-TYPE
   SYNTAX      Pr1645v2EthpdpInDropExEntry
   MAX-ACCESS  not-accessible
   STATUS      current
   DESCRIPTION
      ""
   INDEX      { pr1645v2EthpdpInDropExGlobalIx }
   ::= {pr1645v2EthpdpInDropExTable 1}

Pr1645v2EthpdpInDropExEntry ::=
   SEQUENCE
      {
      pr1645v2EthpdpInDropExGlobalIx
         GlobalIndex,
      pr1645v2EthpdpInDropExValue
         Counter64
      }

pr1645v2EthpdpInDropExGlobalIx OBJECT-TYPE
   SYNTAX      GlobalIndex
   MAX-ACCESS  not-accessible
   STATUS      current
   DESCRIPTION
      "The value of the tlsCntTreeGlobalIndex of the MANAGED OBJECT."
   ::= {pr1645v2EthpdpInDropExEntry 10}

pr1645v2EthpdpInDropExValue OBJECT-TYPE
   SYNTAX      Counter64
   MAX-ACCESS  read-only
   STATUS      current
   DESCRIPTION
      "Path: ethernetPdp.performance.ifInDropLevelExceeded

       64 bit unsigned wrappable counter."
   ::= {pr1645v2EthpdpInDropExEntry 2147483648}


pr1645v2EthpdpInDropNoMac OBJECT IDENTIFIER ::= {pr1645v2Ethpdp 133}

pr1645v2EthpdpInDropNoMacTable OBJECT-TYPE
   SYNTAX      SEQUENCE OF Pr1645v2EthpdpInDropNoMacEntry
   MAX-ACCESS  not-accessible
   STATUS      current
   DESCRIPTION
      "ifInDiscards"
   ::= {pr1645v2EthpdpInDropNoMac 1}

pr1645v2EthpdpInDropNoMacEntry OBJECT-TYPE
   SYNTAX      Pr1645v2EthpdpInDropNoMacEntry
   MAX-ACCESS  not-accessible
   STATUS      current
   DESCRIPTION
      ""
   INDEX      { pr1645v2EthpdpInDropNoMacGlobalIx }
   ::= {pr1645v2EthpdpInDropNoMacTable 1}

Pr1645v2EthpdpInDropNoMacEntry ::=
   SEQUENCE
      {
      pr1645v2EthpdpInDropNoMacGlobalIx
         GlobalIndex,
      pr1645v2EthpdpInDropNoMacValue
         Counter64
      }

pr1645v2EthpdpInDropNoMacGlobalIx OBJECT-TYPE
   SYNTAX      GlobalIndex
   MAX-ACCESS  not-accessible
   STATUS      current
   DESCRIPTION
      "The value of the tlsCntTreeGlobalIndex of the MANAGED OBJECT."
   ::= {pr1645v2EthpdpInDropNoMacEntry 10}

pr1645v2EthpdpInDropNoMacValue OBJECT-TYPE
   SYNTAX      Counter64
   MAX-ACCESS  read-only
   STATUS      current
   DESCRIPTION
      "Path: ethernetPdp.performance.ifInDiscardsNoMacFit

       64 bit unsigned wrappable counter."
   ::= {pr1645v2EthpdpInDropNoMacEntry 2147483648}


pr1645v2EthpdpInDropNUCast OBJECT IDENTIFIER ::= {pr1645v2Ethpdp 136}

pr1645v2EthpdpInDropNUCastTable OBJECT-TYPE
   SYNTAX      SEQUENCE OF Pr1645v2EthpdpInDropNUCastEntry
   MAX-ACCESS  not-accessible
   STATUS      current
   DESCRIPTION
      "ifInDiscards"
   ::= {pr1645v2EthpdpInDropNUCast 1}

pr1645v2EthpdpInDropNUCastEntry OBJECT-TYPE
   SYNTAX      Pr1645v2EthpdpInDropNUCastEntry
   MAX-ACCESS  not-accessible
   STATUS      current
   DESCRIPTION
      ""
   INDEX      { pr1645v2EthpdpInDropNUCastGlobalIx }
   ::= {pr1645v2EthpdpInDropNUCastTable 1}

Pr1645v2EthpdpInDropNUCastEntry ::=
   SEQUENCE
      {
      pr1645v2EthpdpInDropNUCastGlobalIx
         GlobalIndex,
      pr1645v2EthpdpInDropNUCastValue
         Counter64
      }

pr1645v2EthpdpInDropNUCastGlobalIx OBJECT-TYPE
   SYNTAX      GlobalIndex
   MAX-ACCESS  not-accessible
   STATUS      current
   DESCRIPTION
      "The value of the tlsCntTreeGlobalIndex of the MANAGED OBJECT."
   ::= {pr1645v2EthpdpInDropNUCastEntry 10}

pr1645v2EthpdpInDropNUCastValue OBJECT-TYPE
   SYNTAX      Counter64
   MAX-ACCESS  read-only
   STATUS      current
   DESCRIPTION
      "Path: ethernetPdp.performance.ifInDiscardsNUCast

       64 bit unsigned wrappable counter."
   ::= {pr1645v2EthpdpInDropNUCastEntry 2147483648}


pr1645v2EthpdpInDropFilter OBJECT IDENTIFIER ::= {pr1645v2Ethpdp 137}

pr1645v2EthpdpInDropFilterTable OBJECT-TYPE
   SYNTAX      SEQUENCE OF Pr1645v2EthpdpInDropFilterEntry
   MAX-ACCESS  not-accessible
   STATUS      current
   DESCRIPTION
      "ifInDiscards"
   ::= {pr1645v2EthpdpInDropFilter 1}

pr1645v2EthpdpInDropFilterEntry OBJECT-TYPE
   SYNTAX      Pr1645v2EthpdpInDropFilterEntry
   MAX-ACCESS  not-accessible
   STATUS      current
   DESCRIPTION
      ""
   INDEX      { pr1645v2EthpdpInDropFilterGlobalIx }
   ::= {pr1645v2EthpdpInDropFilterTable 1}

Pr1645v2EthpdpInDropFilterEntry ::=
   SEQUENCE
      {
      pr1645v2EthpdpInDropFilterGlobalIx
         GlobalIndex,
      pr1645v2EthpdpInDropFilterValue
         Counter64
      }

pr1645v2EthpdpInDropFilterGlobalIx OBJECT-TYPE
   SYNTAX      GlobalIndex
   MAX-ACCESS  not-accessible
   STATUS      current
   DESCRIPTION
      "The value of the tlsCntTreeGlobalIndex of the MANAGED OBJECT."
   ::= {pr1645v2EthpdpInDropFilterEntry 10}

pr1645v2EthpdpInDropFilterValue OBJECT-TYPE
   SYNTAX      Counter64
   MAX-ACCESS  read-only
   STATUS      current
   DESCRIPTION
      "Path: ethernetPdp.performance.ifInDiscardsFilter

       64 bit unsigned wrappable counter."
   ::= {pr1645v2EthpdpInDropFilterEntry 2147483648}


pr1645v2EthpdpInQueues OBJECT IDENTIFIER ::= {pr1645v2Ethpdp 131}

pr1645v2EthpdpInQueuesSSCTable OBJECT-TYPE
   SYNTAX      SEQUENCE OF Pr1645v2EthpdpInQueuesEntry
   MAX-ACCESS  not-accessible
   STATUS      current
   DESCRIPTION
      "Queue Lengths"
   ::= {pr1645v2EthpdpInQueues 1}

pr1645v2EthpdpInQueuesEntry OBJECT-TYPE
   SYNTAX      Pr1645v2EthpdpInQueuesEntry
   MAX-ACCESS  not-accessible
   STATUS      current
   DESCRIPTION
      ""
   INDEX      { pr1645v2EthpdpInQueuesGlobalIx,
                pr1645v2EthpdpInQueuesTableIx }
   ::= {pr1645v2EthpdpInQueuesSSCTable 1}

Pr1645v2EthpdpInQueuesEntry ::=
   SEQUENCE
      {
      pr1645v2EthpdpInQueuesGlobalIx
         GlobalIndex,
      pr1645v2EthpdpInQueuesTableIx
         TableIndex,
      pr1645v2EthpdpInQueuesName
         INTEGER,
      pr1645v2EthpdpInQueuesLength
         Integer32,
      pr1645v2EthpdpInQueuesOctetLength
         Integer32,
      pr1645v2EthpdpInQueuesRedLength
         Integer32,
      pr1645v2EthpdpInQueuesPacketsTotal
         Counter64,
      pr1645v2EthpdpInQueuesPacketsDirectTx
         Counter64,
      pr1645v2EthpdpInQueuesPacketsQueued
         Counter64,
      pr1645v2EthpdpInQueuesPacketsDropped
         Counter64,
      pr1645v2EthpdpInQueuesPacketsRedDropped
         Counter64,
      pr1645v2EthpdpInQueuesPacketsCirTx
         Counter64,
      pr1645v2EthpdpInQueuesPacketsEirTx
         Counter64,
      pr1645v2EthpdpInQueuesPacketsViolateTx
         Counter64,
      pr1645v2EthpdpInQueuesOctetsTotal
         Counter64,
      pr1645v2EthpdpInQueuesOctetsDirectTx
         Counter64,
      pr1645v2EthpdpInQueuesOctetsQueued
         Counter64,
      pr1645v2EthpdpInQueuesOctetsDropped
         Counter64,
      pr1645v2EthpdpInQueuesOctetsRedDropped
         Counter64,
      pr1645v2EthpdpInQueuesOctetsCirTx
         Counter64,
      pr1645v2EthpdpInQueuesOctetsEirTx
         Counter64,
      pr1645v2EthpdpInQueuesOctetsViolateTx
         Counter64,
      pr1645v2EthpdpInQueuesOctetsBandwidth15sec
         Integer32,
      pr1645v2EthpdpInQueuesOctetsBandwidth30sec
         Integer32,
      pr1645v2EthpdpInQueuesOctetsBandwidth1min
         Integer32,
      pr1645v2EthpdpInQueuesOctetsBandwidth2min
         Integer32,
      pr1645v2EthpdpInQueuesOctetsBandwidth5min
         Integer32
      }

pr1645v2EthpdpInQueuesGlobalIx OBJECT-TYPE
   SYNTAX      GlobalIndex
   MAX-ACCESS  not-accessible
   STATUS      current
   DESCRIPTION
      "The value of the tlsCntTreeGlobalIndex of the MANAGED OBJECT."
   ::= {pr1645v2EthpdpInQueuesEntry 10}

pr1645v2EthpdpInQueuesTableIx OBJECT-TYPE
   SYNTAX      TableIndex
   MAX-ACCESS  not-accessible
   STATUS      current
   DESCRIPTION
      ""
   ::= {pr1645v2EthpdpInQueuesEntry 11}

pr1645v2EthpdpInQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernetPdp.performance.ifInPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2EthpdpInQueuesEntry 16777216}

pr1645v2EthpdpInQueuesLength OBJECT-TYPE
   SYNTAX      Integer32
   MAX-ACCESS  read-only
   STATUS      current
   DESCRIPTION
      "Path: ethernetPdp.performance.ifInPriorityQueues.length"
   ::= {pr1645v2EthpdpInQueuesEntry 33554432}

pr1645v2EthpdpInQueuesOctetLength OBJECT-TYPE
   SYNTAX      Integer32
   MAX-ACCESS  read-only
   STATUS      current
   DESCRIPTION
      "Path: ethernetPdp.performance.ifInPriorityQueues.octetLength"
   ::= {pr1645v2EthpdpInQueuesEntry 150994944}

pr1645v2EthpdpInQueuesRedLength OBJECT-TYPE
   SYNTAX      Integer32
   MAX-ACCESS  read-only
   STATUS      current
   DESCRIPTION
      "Path: ethernetPdp.performance.ifInPriorityQueues.redLength"
   ::= {pr1645v2EthpdpInQueuesEntry 134217728}

pr1645v2EthpdpInQueuesPacketsTotal OBJECT-TYPE
   SYNTAX      Counter64
   MAX-ACCESS  read-only
   STATUS      current
   DESCRIPTION
      "Path: ethernetPdp.performance.ifInPriorityQueues.packets.total

       64 bit unsigned wrappable counter."
   ::= {pr1645v2EthpdpInQueuesEntry 50790400}

pr1645v2EthpdpInQueuesPacketsDirectTx OBJECT-TYPE
   SYNTAX      Counter64
   MAX-ACCESS  read-only
   STATUS      current
   DESCRIPTION
      "Path: ethernetPdp.performance.ifInPriorityQueues.packets.directTx

       64 bit unsigned wrappable counter."
   ::= {pr1645v2EthpdpInQueuesEntry 50397184}

pr1645v2EthpdpInQueuesPacketsQueued OBJECT-TYPE
   SYNTAX      Counter64
   MAX-ACCESS  read-only
   STATUS      current
   DESCRIPTION
      "Path: ethernetPdp.performance.ifInPriorityQueues.packets.queued

       64 bit unsigned wrappable counter."
   ::= {pr1645v2EthpdpInQueuesEntry 50462720}

pr1645v2EthpdpInQueuesPacketsDropped OBJECT-TYPE
   SYNTAX      Counter64
   MAX-ACCESS  read-only
   STATUS      current
   DESCRIPTION
      "Path: ethernetPdp.performance.ifInPriorityQueues.packets.dropped

       64 bit unsigned wrappable counter."
   ::= {pr1645v2EthpdpInQueuesEntry 50528256}

pr1645v2EthpdpInQueuesPacketsRedDropped OBJECT-TYPE
   SYNTAX      Counter64
   MAX-ACCESS  read-only
   STATUS      current
   DESCRIPTION
      "Path: ethernetPdp.performance.ifInPriorityQueues.packets.redDropped

       64 bit unsigned wrappable counter."
   ::= {pr1645v2EthpdpInQueuesEntry 50724864}

pr1645v2EthpdpInQueuesPacketsCirTx OBJECT-TYPE
   SYNTAX      Counter64
   MAX-ACCESS  read-only
   STATUS      current
   DESCRIPTION
      "Path: ethernetPdp.performance.ifInPriorityQueues.packets.cirTx

       64 bit unsigned wrappable counter."
   ::= {pr1645v2EthpdpInQueuesEntry 50593792}

pr1645v2EthpdpInQueuesPacketsEirTx OBJECT-TYPE
   SYNTAX      Counter64
   MAX-ACCESS  read-only
   STATUS      current
   DESCRIPTION
      "Path: ethernetPdp.performance.ifInPriorityQueues.packets.eirTx

       64 bit unsigned wrappable counter."
   ::= {pr1645v2EthpdpInQueuesEntry 50659328}

pr1645v2EthpdpInQueuesPacketsViolateTx OBJECT-TYPE
   SYNTAX      Counter64
   MAX-ACCESS  read-only
   STATUS      current
   DESCRIPTION
      "Path: ethernetPdp.performance.ifInPriorityQueues.packets.violateTx

       64 bit unsigned wrappable counter."
   ::= {pr1645v2EthpdpInQueuesEntry 50855936}

pr1645v2EthpdpInQueuesOctetsTotal OBJECT-TYPE
   SYNTAX      Counter64
   MAX-ACCESS  read-only
   STATUS      current
   DESCRIPTION
      "Path: ethernetPdp.performance.ifInPriorityQueues.octets.total

       64 bit unsigned wrappable counter."
   ::= {pr1645v2EthpdpInQueuesEntry 67567616}

pr1645v2EthpdpInQueuesOctetsDirectTx OBJECT-TYPE
   SYNTAX      Counter64
   MAX-ACCESS  read-only
   STATUS      current
   DESCRIPTION
      "Path: ethernetPdp.performance.ifInPriorityQueues.octets.directTx

       64 bit unsigned wrappable counter."
   ::= {pr1645v2EthpdpInQueuesEntry 67174400}

pr1645v2EthpdpInQueuesOctetsQueued OBJECT-TYPE
   SYNTAX      Counter64
   MAX-ACCESS  read-only
   STATUS      current
   DESCRIPTION
      "Path: ethernetPdp.performance.ifInPriorityQueues.octets.queued

       64 bit unsigned wrappable counter."
   ::= {pr1645v2EthpdpInQueuesEntry 67239936}

pr1645v2EthpdpInQueuesOctetsDropped OBJECT-TYPE
   SYNTAX      Counter64
   MAX-ACCESS  read-only
   STATUS      current
   DESCRIPTION
      "Path: ethernetPdp.performance.ifInPriorityQueues.octets.dropped

       64 bit unsigned wrappable counter."
   ::= {pr1645v2EthpdpInQueuesEntry 67305472}

pr1645v2EthpdpInQueuesOctetsRedDropped OBJECT-TYPE
   SYNTAX      Counter64
   MAX-ACCESS  read-only
   STATUS      current
   DESCRIPTION
      "Path: ethernetPdp.performance.ifInPriorityQueues.octets.redDropped

       64 bit unsigned wrappable counter."
   ::= {pr1645v2EthpdpInQueuesEntry 67502080}

pr1645v2EthpdpInQueuesOctetsCirTx OBJECT-TYPE
   SYNTAX      Counter64
   MAX-ACCESS  read-only
   STATUS      current
   DESCRIPTION
      "Path: ethernetPdp.performance.ifInPriorityQueues.octets.cirTx

       64 bit unsigned wrappable counter."
   ::= {pr1645v2EthpdpInQueuesEntry 67371008}

pr1645v2EthpdpInQueuesOctetsEirTx OBJECT-TYPE
   SYNTAX      Counter64
   MAX-ACCESS  read-only
   STATUS      current
   DESCRIPTION
      "Path: ethernetPdp.performance.ifInPriorityQueues.octets.eirTx

       64 bit unsigned wrappable counter."
   ::= {pr1645v2EthpdpInQueuesEntry 67436544}

pr1645v2EthpdpInQueuesOctetsViolateTx OBJECT-TYPE
   SYNTAX      Counter64
   MAX-ACCESS  read-only
   STATUS      current
   DESCRIPTION
      "Path: ethernetPdp.performance.ifInPriorityQueues.octets.violateTx

       64 bit unsigned wrappable counter."
   ::= {pr1645v2EthpdpInQueuesEntry 67633152}

pr1645v2EthpdpInQueuesOctetsBandwidth15sec OBJECT-TYPE
   SYNTAX      Integer32
   MAX-ACCESS  read-only
   STATUS      current
   DESCRIPTION
      "Path: ethernetPdp.performance.ifInPriorityQueues.octets.bandwidth.15sec

       unit name = bps
       formula = 8 * ; 8 /"
   ::= {pr1645v2EthpdpInQueuesEntry 70386944}

pr1645v2EthpdpInQueuesOctetsBandwidth30sec OBJECT-TYPE
   SYNTAX      Integer32
   MAX-ACCESS  read-only
   STATUS      current
   DESCRIPTION
      "Path: ethernetPdp.performance.ifInPriorityQueues.octets.bandwidth.30sec

       unit name = bps
       formula = 8 * ; 8 /"
   ::= {pr1645v2EthpdpInQueuesEntry 70388224}

pr1645v2EthpdpInQueuesOctetsBandwidth1min OBJECT-TYPE
   SYNTAX      Integer32
   MAX-ACCESS  read-only
   STATUS      current
   DESCRIPTION
      "Path: ethernetPdp.performance.ifInPriorityQueues.octets.bandwidth.1min

       unit name = bps
       formula = 8 * ; 8 /"
   ::= {pr1645v2EthpdpInQueuesEntry 70390784}

pr1645v2EthpdpInQueuesOctetsBandwidth2min OBJECT-TYPE
   SYNTAX      Integer32
   MAX-ACCESS  read-only
   STATUS      current
   DESCRIPTION
      "Path: ethernetPdp.performance.ifInPriorityQueues.octets.bandwidth.2min

       unit name = bps
       formula = 8 * ; 8 /"
   ::= {pr1645v2EthpdpInQueuesEntry 70395904}

pr1645v2EthpdpInQueuesOctetsBandwidth5min OBJECT-TYPE
   SYNTAX      Integer32
   MAX-ACCESS  read-only
   STATUS      current
   DESCRIPTION
      "Path: ethernetPdp.performance.ifInPriorityQueues.octets.bandwidth.5min

       unit name = bps
       formula = 8 * ; 8 /"
   ::= {pr1645v2EthpdpInQueuesEntry 70411264}

pr1645v2EthpdpInQueuesH2Performance OBJECT-TYPE
   SYNTAX      SEQUENCE OF Pr1645v2EthpdpInQueuesH2PerformanceEntry
   MAX-ACCESS  not-accessible
   STATUS      current
   DESCRIPTION
      ""
   ::= {pr1645v2EthpdpInQueues 83886080}

pr1645v2EthpdpInQueuesH2PerformanceEntry OBJECT-TYPE
   SYNTAX      Pr1645v2EthpdpInQueuesH2PerformanceEntry
   MAX-ACCESS  not-accessible
   STATUS      current
   DESCRIPTION
      ""
   INDEX      { pr1645v2EthpdpInQueuesH2PerformanceGlobalIx,
                pr1645v2EthpdpInQueuesTableIx,
                pr1645v2EthpdpInQueuesH2PerformanceTableIx }
   ::= {pr1645v2EthpdpInQueuesH2Performance 1}

Pr1645v2EthpdpInQueuesH2PerformanceEntry ::=
   SEQUENCE
      {
      pr1645v2EthpdpInQueuesH2PerformanceGlobalIx
         GlobalIndex,
      pr1645v2EthpdpInQueuesH2PerformanceTableIx
         TableIndex,
      pr1645v2EthpdpInQueuesH2PerformanceSysUpTime
         TimeTicks,
      pr1645v2EthpdpInQueuesH2PerformanceTotPkts
         Counter64,
      pr1645v2EthpdpInQueuesH2PerformanceDirTxPkts
         Counter64,
      pr1645v2EthpdpInQueuesH2PerformanceQdPkts
         Counter64,
      pr1645v2EthpdpInQueuesH2PerformanceDropPkts
         Counter64,
      pr1645v2EthpdpInQueuesH2PerformanceRDropPkts
         Counter64,
      pr1645v2EthpdpInQueuesH2PerformanceCirTxPkts
         Counter64,
      pr1645v2EthpdpInQueuesH2PerformanceEirTxPkts
         Counter64,
      pr1645v2EthpdpInQueuesH2PerformanceViolTxPkts
         Counter64,
      pr1645v2EthpdpInQueuesH2PerformanceTotOcts
         Counter64,
      pr1645v2EthpdpInQueuesH2PerformanceDirTxOcts
         Counter64,
      pr1645v2EthpdpInQueuesH2PerformanceQdOcts
         Counter64,
      pr1645v2EthpdpInQueuesH2PerformanceDropOcts
         Counter64,
      pr1645v2EthpdpInQueuesH2PerformanceRDropOcts
         Counter64,
      pr1645v2EthpdpInQueuesH2PerformanceCirTxOcts
         Counter64,
      pr1645v2EthpdpInQueuesH2PerformanceEirTxOcts
         Counter64,
      pr1645v2EthpdpInQueuesH2PerformanceViolTxOcts
         Counter64,
      pr1645v2EthpdpInQueuesH2PerformanceBandwidth
         Integer32
      }

pr1645v2EthpdpInQueuesH2PerformanceGlobalIx OBJECT-TYPE
   SYNTAX      GlobalIndex
   MAX-ACCESS  not-accessible
   STATUS      current
   DESCRIPTION
      "The value of the tlsCntTreeGlobalIndex of the MANAGED OBJECT."
   ::= {pr1645v2EthpdpInQueuesH2PerformanceEntry 10}

pr1645v2EthpdpInQueuesH2PerformanceTableIx OBJECT-TYPE
   SYNTAX      TableIndex
   MAX-ACCESS  not-accessible
   STATUS      current
   DESCRIPTION
      ""
   ::= {pr1645v2EthpdpInQueuesH2PerformanceEntry 11}

pr1645v2EthpdpInQueuesH2PerformanceSysUpTime OBJECT-TYPE
   SYNTAX      TimeTicks
   MAX-ACCESS  read-only
   STATUS      current
   DESCRIPTION
      "Path: ethernetPdp.performance.ifInPriorityQueues.h2Performance.sysUpTime

       Time in centi-second."
   ::= {pr1645v2EthpdpInQueuesH2PerformanceEntry 16777216}

pr1645v2EthpdpInQueuesH2PerformanceTotPkts OBJECT-TYPE
   SYNTAX      Counter64
   MAX-ACCESS  read-only
   STATUS      current
   DESCRIPTION
      "Path: ethernetPdp.performance.ifInPriorityQueues.h2Performance.totalPkts

       64 bit unsigned wrappable counter."
   ::= {pr1645v2EthpdpInQueuesH2PerformanceEntry 234881024}

pr1645v2EthpdpInQueuesH2PerformanceDirTxPkts OBJECT-TYPE
   SYNTAX      Counter64
   MAX-ACCESS  read-only
   STATUS      current
   DESCRIPTION
      "Path: ethernetPdp.performance.ifInPriorityQueues.h2Performance.directTxPkts

       64 bit unsigned wrappable counter."
   ::= {pr1645v2EthpdpInQueuesH2PerformanceEntry 33554432}

pr1645v2EthpdpInQueuesH2PerformanceQdPkts OBJECT-TYPE
   SYNTAX      Counter64
   MAX-ACCESS  read-only
   STATUS      current
   DESCRIPTION
      "Path: ethernetPdp.performance.ifInPriorityQueues.h2Performance.queuedPkts

       64 bit unsigned wrappable counter."
   ::= {pr1645v2EthpdpInQueuesH2PerformanceEntry 50331648}

pr1645v2EthpdpInQueuesH2PerformanceDropPkts OBJECT-TYPE
   SYNTAX      Counter64
   MAX-ACCESS  read-only
   STATUS      current
   DESCRIPTION
      "Path: ethernetPdp.performance.ifInPriorityQueues.h2Performance.droppedPkts

       64 bit unsigned wrappable counter."
   ::= {pr1645v2EthpdpInQueuesH2PerformanceEntry 67108864}

pr1645v2EthpdpInQueuesH2PerformanceRDropPkts OBJECT-TYPE
   SYNTAX      Counter64
   MAX-ACCESS  read-only
   STATUS      current
   DESCRIPTION
      "Path: ethernetPdp.performance.ifInPriorityQueues.h2Performance.redDroppedPkts

       64 bit unsigned wrappable counter."
   ::= {pr1645v2EthpdpInQueuesH2PerformanceEntry 201326592}

pr1645v2EthpdpInQueuesH2PerformanceCirTxPkts OBJECT-TYPE
   SYNTAX      Counter64
   MAX-ACCESS  read-only
   STATUS      current
   DESCRIPTION
      "Path: ethernetPdp.performance.ifInPriorityQueues.h2Performance.cirTxPkts

       64 bit unsigned wrappable counter."
   ::= {pr1645v2EthpdpInQueuesH2PerformanceEntry 83886080}

pr1645v2EthpdpInQueuesH2PerformanceEirTxPkts OBJECT-TYPE
   SYNTAX      Counter64
   MAX-ACCESS  read-only
   STATUS      current
   DESCRIPTION
      "Path: ethernetPdp.performance.ifInPriorityQueues.h2Performance.eirTxPkts

       64 bit unsigned wrappable counter."
   ::= {pr1645v2EthpdpInQueuesH2PerformanceEntry 100663296}

pr1645v2EthpdpInQueuesH2PerformanceViolTxPkts OBJECT-TYPE
   SYNTAX      Counter64
   MAX-ACCESS  read-only
   STATUS      current
   DESCRIPTION
      "Path: ethernetPdp.performance.ifInPriorityQueues.h2Performance.violateTxPkts

       64 bit unsigned wrappable counter."
   ::= {pr1645v2EthpdpInQueuesH2PerformanceEntry 301989888}

pr1645v2EthpdpInQueuesH2PerformanceTotOcts OBJECT-TYPE
   SYNTAX      Counter64
   MAX-ACCESS  read-only
   STATUS      current
   DESCRIPTION
      "Path: ethernetPdp.performance.ifInPriorityQueues.h2Performance.totalOctets

       64 bit unsigned wrappable counter."
   ::= {pr1645v2EthpdpInQueuesH2PerformanceEntry 251658240}

pr1645v2EthpdpInQueuesH2PerformanceDirTxOcts OBJECT-TYPE
   SYNTAX      Counter64
   MAX-ACCESS  read-only
   STATUS      current
   DESCRIPTION
      "Path: ethernetPdp.performance.ifInPriorityQueues.h2Performance.directTxOctets

       64 bit unsigned wrappable counter."
   ::= {pr1645v2EthpdpInQueuesH2PerformanceEntry 117440512}

pr1645v2EthpdpInQueuesH2PerformanceQdOcts OBJECT-TYPE
   SYNTAX      Counter64
   MAX-ACCESS  read-only
   STATUS      current
   DESCRIPTION
      "Path: ethernetPdp.performance.ifInPriorityQueues.h2Performance.queuedOctets

       64 bit unsigned wrappable counter."
   ::= {pr1645v2EthpdpInQueuesH2PerformanceEntry 134217728}

pr1645v2EthpdpInQueuesH2PerformanceDropOcts OBJECT-TYPE
   SYNTAX      Counter64
   MAX-ACCESS  read-only
   STATUS      current
   DESCRIPTION
      "Path: ethernetPdp.performance.ifInPriorityQueues.h2Performance.droppedOctets

       64 bit unsigned wrappable counter."
   ::= {pr1645v2EthpdpInQueuesH2PerformanceEntry 150994944}

pr1645v2EthpdpInQueuesH2PerformanceRDropOcts OBJECT-TYPE
   SYNTAX      Counter64
   MAX-ACCESS  read-only
   STATUS      current
   DESCRIPTION
      "Path: ethernetPdp.performance.ifInPriorityQueues.h2Performance.redDroppedOctets

       64 bit unsigned wrappable counter."
   ::= {pr1645v2EthpdpInQueuesH2PerformanceEntry 218103808}

pr1645v2EthpdpInQueuesH2PerformanceCirTxOcts OBJECT-TYPE
   SYNTAX      Counter64
   MAX-ACCESS  read-only
   STATUS      current
   DESCRIPTION
      "Path: ethernetPdp.performance.ifInPriorityQueues.h2Performance.cirTxOctets

       64 bit unsigned wrappable counter."
   ::= {pr1645v2EthpdpInQueuesH2PerformanceEntry 167772160}

pr1645v2EthpdpInQueuesH2PerformanceEirTxOcts OBJECT-TYPE
   SYNTAX      Counter64
   MAX-ACCESS  read-only
   STATUS      current
   DESCRIPTION
      "Path: ethernetPdp.performance.ifInPriorityQueues.h2Performance.eirTxOctets

       64 bit unsigned wrappable counter."
   ::= {pr1645v2EthpdpInQueuesH2PerformanceEntry 184549376}

pr1645v2EthpdpInQueuesH2PerformanceViolTxOcts OBJECT-TYPE
   SYNTAX      Counter64
   MAX-ACCESS  read-only
   STATUS      current
   DESCRIPTION
      "Path: ethernetPdp.performance.ifInPriorityQueues.h2Performance.violateTxOctets

       64 bit unsigned wrappable counter."
   ::= {pr1645v2EthpdpInQueuesH2PerformanceEntry 318767104}

pr1645v2EthpdpInQueuesH2PerformanceBandwidth OBJECT-TYPE
   SYNTAX      Integer32
   MAX-ACCESS  read-only
   STATUS      current
   DESCRIPTION
      "Path: ethernetPdp.performance.ifInPriorityQueues.h2Performance.bandwidth

       unit name = bps
       formula = 8 * ; 8 /"
   ::= {pr1645v2EthpdpInQueuesH2PerformanceEntry 268435456}

pr1645v2EthpdpInQueuesH24Performance OBJECT-TYPE
   SYNTAX      SEQUENCE OF Pr1645v2EthpdpInQueuesH24PerformanceEntry
   MAX-ACCESS  not-accessible
   STATUS      current
   DESCRIPTION
      ""
   ::= {pr1645v2EthpdpInQueues 100663296}

pr1645v2EthpdpInQueuesH24PerformanceEntry OBJECT-TYPE
   SYNTAX      Pr1645v2EthpdpInQueuesH24PerformanceEntry
   MAX-ACCESS  not-accessible
   STATUS      current
   DESCRIPTION
      ""
   INDEX      { pr1645v2EthpdpInQueuesH24PerformanceGlobalIx,
                pr1645v2EthpdpInQueuesTableIx,
                pr1645v2EthpdpInQueuesH24PerformanceTableIx }
   ::= {pr1645v2EthpdpInQueuesH24Performance 1}

Pr1645v2EthpdpInQueuesH24PerformanceEntry ::=
   SEQUENCE
      {
      pr1645v2EthpdpInQueuesH24PerformanceGlobalIx
         GlobalIndex,
      pr1645v2EthpdpInQueuesH24PerformanceTableIx
         TableIndex,
      pr1645v2EthpdpInQueuesH24PerformanceSysUpTime
         TimeTicks,
      pr1645v2EthpdpInQueuesH24PerformanceTotPkts
         Counter64,
      pr1645v2EthpdpInQueuesH24PerformanceDirTxPkts
         Counter64,
      pr1645v2EthpdpInQueuesH24PerformanceQdPkts
         Counter64,
      pr1645v2EthpdpInQueuesH24PerformanceDropPkts
         Counter64,
      pr1645v2EthpdpInQueuesH24PerformanceRDropPkts
         Counter64,
      pr1645v2EthpdpInQueuesH24PerformanceCirTxPkts
         Counter64,
      pr1645v2EthpdpInQueuesH24PerformanceEirTxPkts
         Counter64,
      pr1645v2EthpdpInQueuesH24PerformanceViolTxPkts
         Counter64,
      pr1645v2EthpdpInQueuesH24PerformanceTotOcts
         Counter64,
      pr1645v2EthpdpInQueuesH24PerformanceDirTxOcts
         Counter64,
      pr1645v2EthpdpInQueuesH24PerformanceQdOcts
         Counter64,
      pr1645v2EthpdpInQueuesH24PerformanceDropOcts
         Counter64,
      pr1645v2EthpdpInQueuesH24PerformanceRDropOcts
         Counter64,
      pr1645v2EthpdpInQueuesH24PerformanceCirTxOcts
         Counter64,
      pr1645v2EthpdpInQueuesH24PerformanceEirTxOcts
         Counter64,
      pr1645v2EthpdpInQueuesH24PerformanceViolTxOcts
         Counter64,
      pr1645v2EthpdpInQueuesH24PerformanceBandwidth
         Integer32
      }

pr1645v2EthpdpInQueuesH24PerformanceGlobalIx OBJECT-TYPE
   SYNTAX      GlobalIndex
   MAX-ACCESS  not-accessible
   STATUS      current
   DESCRIPTION
      "The value of the tlsCntTreeGlobalIndex of the MANAGED OBJECT."
   ::= {pr1645v2EthpdpInQueuesH24PerformanceEntry 10}

pr1645v2EthpdpInQueuesH24PerformanceTableIx OBJECT-TYPE
   SYNTAX      TableIndex
   MAX-ACCESS  not-accessible
   STATUS      current
   DESCRIPTION
      ""
   ::= {pr1645v2EthpdpInQueuesH24PerformanceEntry 11}

pr1645v2EthpdpInQueuesH24PerformanceSysUpTime OBJECT-TYPE
   SYNTAX      TimeTicks
   MAX-ACCESS  read-only
   STATUS      current
   DESCRIPTION
      "Path: ethernetPdp.performance.ifInPriorityQueues.h24Performance.sysUpTime

       Time in centi-second."
   ::= {pr1645v2EthpdpInQueuesH24PerformanceEntry 16777216}

pr1645v2EthpdpInQueuesH24PerformanceTotPkts OBJECT-TYPE
   SYNTAX      Counter64
   MAX-ACCESS  read-only
   STATUS      current
   DESCRIPTION
      "Path: ethernetPdp.performance.ifInPriorityQueues.h24Performance.totalPkts

       64 bit unsigned wrappable counter."
   ::= {pr1645v2EthpdpInQueuesH24PerformanceEntry 234881024}

pr1645v2EthpdpInQueuesH24PerformanceDirTxPkts OBJECT-TYPE
   SYNTAX      Counter64
   MAX-ACCESS  read-only
   STATUS      current
   DESCRIPTION
      "Path: ethernetPdp.performance.ifInPriorityQueues.h24Performance.directTxPkts

       64 bit unsigned wrappable counter."
   ::= {pr1645v2EthpdpInQueuesH24PerformanceEntry 33554432}

pr1645v2EthpdpInQueuesH24PerformanceQdPkts OBJECT-TYPE
   SYNTAX      Counter64
   MAX-ACCESS  read-only
   STATUS      current
   DESCRIPTION
      "Path: ethernetPdp.performance.ifInPriorityQueues.h24Performance.queuedPkts

       64 bit unsigned wrappable counter."
   ::= {pr1645v2EthpdpInQueuesH24PerformanceEntry 50331648}

pr1645v2EthpdpInQueuesH24PerformanceDropPkts OBJECT-TYPE
   SYNTAX      Counter64
   MAX-ACCESS  read-only
   STATUS      current
   DESCRIPTION
      "Path: ethernetPdp.performance.ifInPriorityQueues.h24Performance.droppedPkts

       64 bit unsigned wrappable counter."
   ::= {pr1645v2EthpdpInQueuesH24PerformanceEntry 67108864}

pr1645v2EthpdpInQueuesH24PerformanceRDropPkts OBJECT-TYPE
   SYNTAX      Counter64
   MAX-ACCESS  read-only
   STATUS      current
   DESCRIPTION
      "Path: ethernetPdp.performance.ifInPriorityQueues.h24Performance.redDroppedPkts

       64 bit unsigned wrappable counter."
   ::= {pr1645v2EthpdpInQueuesH24PerformanceEntry 201326592}

pr1645v2EthpdpInQueuesH24PerformanceCirTxPkts OBJECT-TYPE
   SYNTAX      Counter64
   MAX-ACCESS  read-only
   STATUS      current
   DESCRIPTION
      "Path: ethernetPdp.performance.ifInPriorityQueues.h24Performance.cirTxPkts

       64 bit unsigned wrappable counter."
   ::= {pr1645v2EthpdpInQueuesH24PerformanceEntry 83886080}

pr1645v2EthpdpInQueuesH24PerformanceEirTxPkts OBJECT-TYPE
   SYNTAX      Counter64
   MAX-ACCESS  read-only
   STATUS      current
   DESCRIPTION
      "Path: ethernetPdp.performance.ifInPriorityQueues.h24Performance.eirTxPkts

       64 bit unsigned wrappable counter."
   ::= {pr1645v2EthpdpInQueuesH24PerformanceEntry 100663296}

pr1645v2EthpdpInQueuesH24PerformanceViolTxPkts OBJECT-TYPE
   SYNTAX      Counter64
   MAX-ACCESS  read-only
   STATUS      current
   DESCRIPTION
      "Path: ethernetPdp.performance.ifInPriorityQueues.h24Performance.violateTxPkts

       64 bit unsigned wrappable counter."
   ::= {pr1645v2EthpdpInQueuesH24PerformanceEntry 301989888}

pr1645v2EthpdpInQueuesH24PerformanceTotOcts OBJECT-TYPE
   SYNTAX      Counter64
   MAX-ACCESS  read-only
   STATUS      current
   DESCRIPTION
      "Path: ethernetPdp.performance.ifInPriorityQueues.h24Performance.totalOctets

       64 bit unsigned wrappable counter."
   ::= {pr1645v2EthpdpInQueuesH24PerformanceEntry 251658240}

pr1645v2EthpdpInQueuesH24PerformanceDirTxOcts OBJECT-TYPE
   SYNTAX      Counter64
   MAX-ACCESS  read-only
   STATUS      current
   DESCRIPTION
      "Path: ethernetPdp.performance.ifInPriorityQueues.h24Performance.directTxOctets

       64 bit unsigned wrappable counter."
   ::= {pr1645v2EthpdpInQueuesH24PerformanceEntry 117440512}

pr1645v2EthpdpInQueuesH24PerformanceQdOcts OBJECT-TYPE
   SYNTAX      Counter64
   MAX-ACCESS  read-only
   STATUS      current
   DESCRIPTION
      "Path: ethernetPdp.performance.ifInPriorityQueues.h24Performance.queuedOctets

       64 bit unsigned wrappable counter."
   ::= {pr1645v2EthpdpInQueuesH24PerformanceEntry 134217728}

pr1645v2EthpdpInQueuesH24PerformanceDropOcts OBJECT-TYPE
   SYNTAX      Counter64
   MAX-ACCESS  read-only
   STATUS      current
   DESCRIPTION
      "Path: ethernetPdp.performance.ifInPriorityQueues.h24Performance.droppedOctets

       64 bit unsigned wrappable counter."
   ::= {pr1645v2EthpdpInQueuesH24PerformanceEntry 150994944}

pr1645v2EthpdpInQueuesH24PerformanceRDropOcts OBJECT-TYPE
   SYNTAX      Counter64
   MAX-ACCESS  read-only
   STATUS      current
   DESCRIPTION
      "Path: ethernetPdp.performance.ifInPriorityQueues.h24Performance.redDroppedOctets

       64 bit unsigned wrappable counter."
   ::= {pr1645v2EthpdpInQueuesH24PerformanceEntry 218103808}

pr1645v2EthpdpInQueuesH24PerformanceCirTxOcts OBJECT-TYPE
   SYNTAX      Counter64
   MAX-ACCESS  read-only
   STATUS      current
   DESCRIPTION
      "Path: ethernetPdp.performance.ifInPriorityQueues.h24Performance.cirTxOctets

       64 bit unsigned wrappable counter."
   ::= {pr1645v2EthpdpInQueuesH24PerformanceEntry 167772160}

pr1645v2EthpdpInQueuesH24PerformanceEirTxOcts OBJECT-TYPE
   SYNTAX      Counter64
   MAX-ACCESS  read-only
   STATUS      current
   DESCRIPTION
      "Path: ethernetPdp.performance.ifInPriorityQueues.h24Performance.eirTxOctets

       64 bit unsigned wrappable counter."
   ::= {pr1645v2EthpdpInQueuesH24PerformanceEntry 184549376}

pr1645v2EthpdpInQueuesH24PerformanceViolTxOcts OBJECT-TYPE
   SYNTAX      Counter64
   MAX-ACCESS  read-only
   STATUS      current
   DESCRIPTION
      "Path: ethernetPdp.performance.ifInPriorityQueues.h24Performance.violateTxOctets

       64 bit unsigned wrappable counter."
   ::= {pr1645v2EthpdpInQueuesH24PerformanceEntry 318767104}

pr1645v2EthpdpInQueuesH24PerformanceBandwidth OBJECT-TYPE
   SYNTAX      Integer32
   MAX-ACCESS  read-only
   STATUS      current
   DESCRIPTION
      "Path: ethernetPdp.performance.ifInPriorityQueues.h24Performance.bandwidth

       unit name = bps
       formula = 8 * ; 8 /"
   ::= {pr1645v2EthpdpInQueuesH24PerformanceEntry 268435456}

pr1645v2EthpdpInQueuesD7Performance OBJECT-TYPE
   SYNTAX      SEQUENCE OF Pr1645v2EthpdpInQueuesD7PerformanceEntry
   MAX-ACCESS  not-accessible
   STATUS      current
   DESCRIPTION
      ""
   ::= {pr1645v2EthpdpInQueues 117440512}

pr1645v2EthpdpInQueuesD7PerformanceEntry OBJECT-TYPE
   SYNTAX      Pr1645v2EthpdpInQueuesD7PerformanceEntry
   MAX-ACCESS  not-accessible
   STATUS      current
   DESCRIPTION
      ""
   INDEX      { pr1645v2EthpdpInQueuesD7PerformanceGlobalIx,
                pr1645v2EthpdpInQueuesTableIx,
                pr1645v2EthpdpInQueuesD7PerformanceTableIx }
   ::= {pr1645v2EthpdpInQueuesD7Performance 1}

Pr1645v2EthpdpInQueuesD7PerformanceEntry ::=
   SEQUENCE
      {
      pr1645v2EthpdpInQueuesD7PerformanceGlobalIx
         GlobalIndex,
      pr1645v2EthpdpInQueuesD7PerformanceTableIx
         TableIndex,
      pr1645v2EthpdpInQueuesD7PerformanceSysUpTime
         TimeTicks,
      pr1645v2EthpdpInQueuesD7PerformanceTotPkts
         Counter64,
      pr1645v2EthpdpInQueuesD7PerformanceDirTxPkts
         Counter64,
      pr1645v2EthpdpInQueuesD7PerformanceQdPkts
         Counter64,
      pr1645v2EthpdpInQueuesD7PerformanceDropPkts
         Counter64,
      pr1645v2EthpdpInQueuesD7PerformanceRDropPkts
         Counter64,
      pr1645v2EthpdpInQueuesD7PerformanceCirTxPkts
         Counter64,
      pr1645v2EthpdpInQueuesD7PerformanceEirTxPkts
         Counter64,
      pr1645v2EthpdpInQueuesD7PerformanceViolTxPkts
         Counter64,
      pr1645v2EthpdpInQueuesD7PerformanceTotOcts
         Counter64,
      pr1645v2EthpdpInQueuesD7PerformanceDirTxOcts
         Counter64,
      pr1645v2EthpdpInQueuesD7PerformanceQdOcts
         Counter64,
      pr1645v2EthpdpInQueuesD7PerformanceDropOcts
         Counter64,
      pr1645v2EthpdpInQueuesD7PerformanceRDropOcts
         Counter64,
      pr1645v2EthpdpInQueuesD7PerformanceCirTxOcts
         Counter64,
      pr1645v2EthpdpInQueuesD7PerformanceEirTxOcts
         Counter64,
      pr1645v2EthpdpInQueuesD7PerformanceViolTxOcts
         Counter64,
      pr1645v2EthpdpInQueuesD7PerformanceBandwidth
         Integer32
      }

pr1645v2EthpdpInQueuesD7PerformanceGlobalIx OBJECT-TYPE
   SYNTAX      GlobalIndex
   MAX-ACCESS  not-accessible
   STATUS      current
   DESCRIPTION
      "The value of the tlsCntTreeGlobalIndex of the MANAGED OBJECT."
   ::= {pr1645v2EthpdpInQueuesD7PerformanceEntry 10}

pr1645v2EthpdpInQueuesD7PerformanceTableIx OBJECT-TYPE
   SYNTAX      TableIndex
   MAX-ACCESS  not-accessible
   STATUS      current
   DESCRIPTION
      ""
   ::= {pr1645v2EthpdpInQueuesD7PerformanceEntry 11}

pr1645v2EthpdpInQueuesD7PerformanceSysUpTime OBJECT-TYPE
   SYNTAX      TimeTicks
   MAX-ACCESS  read-only
   STATUS      current
   DESCRIPTION
      "Path: ethernetPdp.performance.ifInPriorityQueues.d7Performance.sysUpTime

       Time in centi-second."
   ::= {pr1645v2EthpdpInQueuesD7PerformanceEntry 16777216}

pr1645v2EthpdpInQueuesD7PerformanceTotPkts OBJECT-TYPE
   SYNTAX      Counter64
   MAX-ACCESS  read-only
   STATUS      current
   DESCRIPTION
      "Path: ethernetPdp.performance.ifInPriorityQueues.d7Performance.totalPkts

       64 bit unsigned wrappable counter."
   ::= {pr1645v2EthpdpInQueuesD7PerformanceEntry 234881024}

pr1645v2EthpdpInQueuesD7PerformanceDirTxPkts OBJECT-TYPE
   SYNTAX      Counter64
   MAX-ACCESS  read-only
   STATUS      current
   DESCRIPTION
      "Path: ethernetPdp.performance.ifInPriorityQueues.d7Performance.directTxPkts

       64 bit unsigned wrappable counter."
   ::= {pr1645v2EthpdpInQueuesD7PerformanceEntry 33554432}

pr1645v2EthpdpInQueuesD7PerformanceQdPkts OBJECT-TYPE
   SYNTAX      Counter64
   MAX-ACCESS  read-only
   STATUS      current
   DESCRIPTION
      "Path: ethernetPdp.performance.ifInPriorityQueues.d7Performance.queuedPkts

       64 bit unsigned wrappable counter."
   ::= {pr1645v2EthpdpInQueuesD7PerformanceEntry 50331648}

pr1645v2EthpdpInQueuesD7PerformanceDropPkts OBJECT-TYPE
   SYNTAX      Counter64
   MAX-ACCESS  read-only
   STATUS      current
   DESCRIPTION
      "Path: ethernetPdp.performance.ifInPriorityQueues.d7Performance.droppedPkts

       64 bit unsigned wrappable counter."
   ::= {pr1645v2EthpdpInQueuesD7PerformanceEntry 67108864}

pr1645v2EthpdpInQueuesD7PerformanceRDropPkts OBJECT-TYPE
   SYNTAX      Counter64
   MAX-ACCESS  read-only
   STATUS      current
   DESCRIPTION
      "Path: ethernetPdp.performance.ifInPriorityQueues.d7Performance.redDroppedPkts

       64 bit unsigned wrappable counter."
   ::= {pr1645v2EthpdpInQueuesD7PerformanceEntry 201326592}

pr1645v2EthpdpInQueuesD7PerformanceCirTxPkts OBJECT-TYPE
   SYNTAX      Counter64
   MAX-ACCESS  read-only
   STATUS      current
   DESCRIPTION
      "Path: ethernetPdp.performance.ifInPriorityQueues.d7Performance.cirTxPkts

       64 bit unsigned wrappable counter."
   ::= {pr1645v2EthpdpInQueuesD7PerformanceEntry 83886080}

pr1645v2EthpdpInQueuesD7PerformanceEirTxPkts OBJECT-TYPE
   SYNTAX      Counter64
   MAX-ACCESS  read-only
   STATUS      current
   DESCRIPTION
      "Path: ethernetPdp.performance.ifInPriorityQueues.d7Performance.eirTxPkts

       64 bit unsigned wrappable counter."
   ::= {pr1645v2EthpdpInQueuesD7PerformanceEntry 100663296}

pr1645v2EthpdpInQueuesD7PerformanceViolTxPkts OBJECT-TYPE
   SYNTAX      Counter64
   MAX-ACCESS  read-only
   STATUS      current
   DESCRIPTION
      "Path: ethernetPdp.performance.ifInPriorityQueues.d7Performance.violateTxPkts

       64 bit unsigned wrappable counter."
   ::= {pr1645v2EthpdpInQueuesD7PerformanceEntry 301989888}

pr1645v2EthpdpInQueuesD7PerformanceTotOcts OBJECT-TYPE
   SYNTAX      Counter64
   MAX-ACCESS  read-only
   STATUS      current
   DESCRIPTION
      "Path: ethernetPdp.performance.ifInPriorityQueues.d7Performance.totalOctets

       64 bit unsigned wrappable counter."
   ::= {pr1645v2EthpdpInQueuesD7PerformanceEntry 251658240}

pr1645v2EthpdpInQueuesD7PerformanceDirTxOcts OBJECT-TYPE
   SYNTAX      Counter64
   MAX-ACCESS  read-only
   STATUS      current
   DESCRIPTION
      "Path: ethernetPdp.performance.ifInPriorityQueues.d7Performance.directTxOctets

       64 bit unsigned wrappable counter."
   ::= {pr1645v2EthpdpInQueuesD7PerformanceEntry 117440512}

pr1645v2EthpdpInQueuesD7PerformanceQdOcts OBJECT-TYPE
   SYNTAX      Counter64
   MAX-ACCESS  read-only
   STATUS      current
   DESCRIPTION
      "Path: ethernetPdp.performance.ifInPriorityQueues.d7Performance.queuedOctets

       64 bit unsigned wrappable counter."
   ::= {pr1645v2EthpdpInQueuesD7PerformanceEntry 134217728}

pr1645v2EthpdpInQueuesD7PerformanceDropOcts OBJECT-TYPE
   SYNTAX      Counter64
   MAX-ACCESS  read-only
   STATUS      current
   DESCRIPTION
      "Path: ethernetPdp.performance.ifInPriorityQueues.d7Performance.droppedOctets

       64 bit unsigned wrappable counter."
   ::= {pr1645v2EthpdpInQueuesD7PerformanceEntry 150994944}

pr1645v2EthpdpInQueuesD7PerformanceRDropOcts OBJECT-TYPE
   SYNTAX      Counter64
   MAX-ACCESS  read-only
   STATUS      current
   DESCRIPTION
      "Path: ethernetPdp.performance.ifInPriorityQueues.d7Performance.redDroppedOctets

       64 bit unsigned wrappable counter."
   ::= {pr1645v2EthpdpInQueuesD7PerformanceEntry 218103808}

pr1645v2EthpdpInQueuesD7PerformanceCirTxOcts OBJECT-TYPE
   SYNTAX      Counter64
   MAX-ACCESS  read-only
   STATUS      current
   DESCRIPTION
      "Path: ethernetPdp.performance.ifInPriorityQueues.d7Performance.cirTxOctets

       64 bit unsigned wrappable counter."
   ::= {pr1645v2EthpdpInQueuesD7PerformanceEntry 167772160}

pr1645v2EthpdpInQueuesD7PerformanceEirTxOcts OBJECT-TYPE
   SYNTAX      Counter64
   MAX-ACCESS  read-only
   STATUS      current
   DESCRIPTION
      "Path: ethernetPdp.performance.ifInPriorityQueues.d7Performance.eirTxOctets

       64 bit unsigned wrappable counter."
   ::= {pr1645v2EthpdpInQueuesD7PerformanceEntry 184549376}

pr1645v2EthpdpInQueuesD7PerformanceViolTxOcts OBJECT-TYPE
   SYNTAX      Counter64
   MAX-ACCESS  read-only
   STATUS      current
   DESCRIPTION
      "Path: ethernetPdp.performance.ifInPriorityQueues.d7Performance.violateTxOctets

       64 bit unsigned wrappable counter."
   ::= {pr1645v2EthpdpInQueuesD7PerformanceEntry 318767104}

pr1645v2EthpdpInQueuesD7PerformanceBandwidth OBJECT-TYPE
   SYNTAX      Integer32
   MAX-ACCESS  read-only
   STATUS      current
   DESCRIPTION
      "Path: ethernetPdp.performance.ifInPriorityQueues.d7Performance.bandwidth

       unit name = bps
       formula = 8 * ; 8 /"
   ::= {pr1645v2EthpdpInQueuesD7PerformanceEntry 268435456}


pr1645v2EthpdpInBandwidth OBJECT IDENTIFIER ::= {pr1645v2Ethpdp 181}

pr1645v2EthpdpInBandwidthSSCTable OBJECT-TYPE
   SYNTAX      SEQUENCE OF Pr1645v2EthpdpInBandwidthEntry
   MAX-ACCESS  not-accessible
   STATUS      current
   DESCRIPTION
      "bandwidth"
   ::= {pr1645v2EthpdpInBandwidth 1}

pr1645v2EthpdpInBandwidthEntry OBJECT-TYPE
   SYNTAX      Pr1645v2EthpdpInBandwidthEntry
   MAX-ACCESS  not-accessible
   STATUS      current
   DESCRIPTION
      ""
   INDEX      { pr1645v2EthpdpInBandwidthGlobalIx }
   ::= {pr1645v2EthpdpInBandwidthSSCTable 1}

Pr1645v2EthpdpInBandwidthEntry ::=
   SEQUENCE
      {
      pr1645v2EthpdpInBandwidthGlobalIx
         GlobalIndex,
      pr1645v2EthpdpInBandwidth15sec
         Integer32,
      pr1645v2EthpdpInBandwidth30sec
         Integer32,
      pr1645v2EthpdpInBandwidth1min
         Integer32,
      pr1645v2EthpdpInBandwidth2min
         Integer32,
      pr1645v2EthpdpInBandwidth5min
         Integer32
      }

pr1645v2EthpdpInBandwidthGlobalIx OBJECT-TYPE
   SYNTAX      GlobalIndex
   MAX-ACCESS  not-accessible
   STATUS      current
   DESCRIPTION
      "The value of the tlsCntTreeGlobalIndex of the MANAGED OBJECT."
   ::= {pr1645v2EthpdpInBandwidthEntry 10}

pr1645v2EthpdpInBandwidth15sec OBJECT-TYPE
   SYNTAX      Integer32
   MAX-ACCESS  read-only
   STATUS      current
   DESCRIPTION
      "Path: ethernetPdp.performance.ifInBandwidth.15sec

       unit name = bps
       formula = 8 * ; 8 /"
   ::= {pr1645v2EthpdpInBandwidthEntry 83886080}

pr1645v2EthpdpInBandwidth30sec OBJECT-TYPE
   SYNTAX      Integer32
   MAX-ACCESS  read-only
   STATUS      current
   DESCRIPTION
      "Path: ethernetPdp.performance.ifInBandwidth.30sec

       unit name = bps
       formula = 8 * ; 8 /"
   ::= {pr1645v2EthpdpInBandwidthEntry 167772160}

pr1645v2EthpdpInBandwidth1min OBJECT-TYPE
   SYNTAX      Integer32
   MAX-ACCESS  read-only
   STATUS      current
   DESCRIPTION
      "Path: ethernetPdp.performance.ifInBandwidth.1min

       unit name = bps
       formula = 8 * ; 8 /"
   ::= {pr1645v2EthpdpInBandwidthEntry 335544320}

pr1645v2EthpdpInBandwidth2min OBJECT-TYPE
   SYNTAX      Integer32
   MAX-ACCESS  read-only
   STATUS      current
   DESCRIPTION
      "Path: ethernetPdp.performance.ifInBandwidth.2min

       unit name = bps
       formula = 8 * ; 8 /"
   ::= {pr1645v2EthpdpInBandwidthEntry 671088640}

pr1645v2EthpdpInBandwidth5min OBJECT-TYPE
   SYNTAX      Integer32
   MAX-ACCESS  read-only
   STATUS      current
   DESCRIPTION
      "Path: ethernetPdp.performance.ifInBandwidth.5min

       unit name = bps
       formula = 8 * ; 8 /"
   ::= {pr1645v2EthpdpInBandwidthEntry 1677721600}


pr1645v2EthpdpOutOctets OBJECT IDENTIFIER ::= {pr1645v2Ethpdp 115}

pr1645v2EthpdpOutOctetsTable OBJECT-TYPE
   SYNTAX      SEQUENCE OF Pr1645v2EthpdpOutOctetsEntry
   MAX-ACCESS  not-accessible
   STATUS      current
   DESCRIPTION
      "ifOutOctets"
   ::= {pr1645v2EthpdpOutOctets 1}

pr1645v2EthpdpOutOctetsEntry OBJECT-TYPE
   SYNTAX      Pr1645v2EthpdpOutOctetsEntry
   MAX-ACCESS  not-accessible
   STATUS      current
   DESCRIPTION
      ""
   INDEX      { pr1645v2EthpdpOutOctetsGlobalIx }
   ::= {pr1645v2EthpdpOutOctetsTable 1}

Pr1645v2EthpdpOutOctetsEntry ::=
   SEQUENCE
      {
      pr1645v2EthpdpOutOctetsGlobalIx
         GlobalIndex,
      pr1645v2EthpdpOutOctetsValue
         Counter64
      }

pr1645v2EthpdpOutOctetsGlobalIx OBJECT-TYPE
   SYNTAX      GlobalIndex
   MAX-ACCESS  not-accessible
   STATUS      current
   DESCRIPTION
      "The value of the tlsCntTreeGlobalIndex of the MANAGED OBJECT."
   ::= {pr1645v2EthpdpOutOctetsEntry 10}

pr1645v2EthpdpOutOctetsValue OBJECT-TYPE
   SYNTAX      Counter64
   MAX-ACCESS  read-only
   STATUS      current
   DESCRIPTION
      "Path: ethernetPdp.performance.ifOutOctets

       64 bit unsigned wrappable counter."
   ::= {pr1645v2EthpdpOutOctetsEntry 2147483648}


pr1645v2EthpdpOutUcastPkts OBJECT IDENTIFIER ::= {pr1645v2Ethpdp 116}

pr1645v2EthpdpOutUcastPktsTable OBJECT-TYPE
   SYNTAX      SEQUENCE OF Pr1645v2EthpdpOutUcastPktsEntry
   MAX-ACCESS  not-accessible
   STATUS      current
   DESCRIPTION
      "ifOutUcastPkts"
   ::= {pr1645v2EthpdpOutUcastPkts 1}

pr1645v2EthpdpOutUcastPktsEntry OBJECT-TYPE
   SYNTAX      Pr1645v2EthpdpOutUcastPktsEntry
   MAX-ACCESS  not-accessible
   STATUS      current
   DESCRIPTION
      ""
   INDEX      { pr1645v2EthpdpOutUcastPktsGlobalIx }
   ::= {pr1645v2EthpdpOutUcastPktsTable 1}

Pr1645v2EthpdpOutUcastPktsEntry ::=
   SEQUENCE
      {
      pr1645v2EthpdpOutUcastPktsGlobalIx
         GlobalIndex,
      pr1645v2EthpdpOutUcastPktsValue
         Counter64
      }

pr1645v2EthpdpOutUcastPktsGlobalIx OBJECT-TYPE
   SYNTAX      GlobalIndex
   MAX-ACCESS  not-accessible
   STATUS      current
   DESCRIPTION
      "The value of the tlsCntTreeGlobalIndex of the MANAGED OBJECT."
   ::= {pr1645v2EthpdpOutUcastPktsEntry 10}

pr1645v2EthpdpOutUcastPktsValue OBJECT-TYPE
   SYNTAX      Counter64
   MAX-ACCESS  read-only
   STATUS      current
   DESCRIPTION
      "Path: ethernetPdp.performance.ifOutUcastPkts

       64 bit unsigned wrappable counter."
   ::= {pr1645v2EthpdpOutUcastPktsEntry 2147483648}


pr1645v2EthpdpOutNUcastPkts OBJECT IDENTIFIER ::= {pr1645v2Ethpdp 117}

pr1645v2EthpdpOutNUcastPktsTable OBJECT-TYPE
   SYNTAX      SEQUENCE OF Pr1645v2EthpdpOutNUcastPktsEntry
   MAX-ACCESS  not-accessible
   STATUS      current
   DESCRIPTION
      "ifOutNUcastPkts"
   ::= {pr1645v2EthpdpOutNUcastPkts 1}

pr1645v2EthpdpOutNUcastPktsEntry OBJECT-TYPE
   SYNTAX      Pr1645v2EthpdpOutNUcastPktsEntry
   MAX-ACCESS  not-accessible
   STATUS      current
   DESCRIPTION
      ""
   INDEX      { pr1645v2EthpdpOutNUcastPktsGlobalIx }
   ::= {pr1645v2EthpdpOutNUcastPktsTable 1}

Pr1645v2EthpdpOutNUcastPktsEntry ::=
   SEQUENCE
      {
      pr1645v2EthpdpOutNUcastPktsGlobalIx
         GlobalIndex,
      pr1645v2EthpdpOutNUcastPktsValue
         Counter64
      }

pr1645v2EthpdpOutNUcastPktsGlobalIx OBJECT-TYPE
   SYNTAX      GlobalIndex
   MAX-ACCESS  not-accessible
   STATUS      current
   DESCRIPTION
      "The value of the tlsCntTreeGlobalIndex of the MANAGED OBJECT."
   ::= {pr1645v2EthpdpOutNUcastPktsEntry 10}

pr1645v2EthpdpOutNUcastPktsValue OBJECT-TYPE
   SYNTAX      Counter64
   MAX-ACCESS  read-only
   STATUS      current
   DESCRIPTION
      "Path: ethernetPdp.performance.ifOutNUcastPkts

       64 bit unsigned wrappable counter."
   ::= {pr1645v2EthpdpOutNUcastPktsEntry 2147483648}


pr1645v2EthpdpOutDiscards OBJECT IDENTIFIER ::= {pr1645v2Ethpdp 118}

pr1645v2EthpdpOutDiscardsTable OBJECT-TYPE
   SYNTAX      SEQUENCE OF Pr1645v2EthpdpOutDiscardsEntry
   MAX-ACCESS  not-accessible
   STATUS      current
   DESCRIPTION
      "ifOutDiscards"
   ::= {pr1645v2EthpdpOutDiscards 1}

pr1645v2EthpdpOutDiscardsEntry OBJECT-TYPE
   SYNTAX      Pr1645v2EthpdpOutDiscardsEntry
   MAX-ACCESS  not-accessible
   STATUS      current
   DESCRIPTION
      ""
   INDEX      { pr1645v2EthpdpOutDiscardsGlobalIx }
   ::= {pr1645v2EthpdpOutDiscardsTable 1}

Pr1645v2EthpdpOutDiscardsEntry ::=
   SEQUENCE
      {
      pr1645v2EthpdpOutDiscardsGlobalIx
         GlobalIndex,
      pr1645v2EthpdpOutDiscardsValue
         Counter64
      }

pr1645v2EthpdpOutDiscardsGlobalIx OBJECT-TYPE
   SYNTAX      GlobalIndex
   MAX-ACCESS  not-accessible
   STATUS      current
   DESCRIPTION
      "The value of the tlsCntTreeGlobalIndex of the MANAGED OBJECT."
   ::= {pr1645v2EthpdpOutDiscardsEntry 10}

pr1645v2EthpdpOutDiscardsValue OBJECT-TYPE
   SYNTAX      Counter64
   MAX-ACCESS  read-only
   STATUS      current
   DESCRIPTION
      "Path: ethernetPdp.performance.ifOutDiscards

       64 bit unsigned wrappable counter."
   ::= {pr1645v2EthpdpOutDiscardsEntry 2147483648}


pr1645v2EthpdpOutErrors OBJECT IDENTIFIER ::= {pr1645v2Ethpdp 119}

pr1645v2EthpdpOutErrorsTable OBJECT-TYPE
   SYNTAX      SEQUENCE OF Pr1645v2EthpdpOutErrorsEntry
   MAX-ACCESS  not-accessible
   STATUS      current
   DESCRIPTION
      "ifOutErrors"
   ::= {pr1645v2EthpdpOutErrors 1}

pr1645v2EthpdpOutErrorsEntry OBJECT-TYPE
   SYNTAX      Pr1645v2EthpdpOutErrorsEntry
   MAX-ACCESS  not-accessible
   STATUS      current
   DESCRIPTION
      ""
   INDEX      { pr1645v2EthpdpOutErrorsGlobalIx }
   ::= {pr1645v2EthpdpOutErrorsTable 1}

Pr1645v2EthpdpOutErrorsEntry ::=
   SEQUENCE
      {
      pr1645v2EthpdpOutErrorsGlobalIx
         GlobalIndex,
      pr1645v2EthpdpOutErrorsValue
         Counter64
      }

pr1645v2EthpdpOutErrorsGlobalIx OBJECT-TYPE
   SYNTAX      GlobalIndex
   MAX-ACCESS  not-accessible
   STATUS      current
   DESCRIPTION
      "The value of the tlsCntTreeGlobalIndex of the MANAGED OBJECT."
   ::= {pr1645v2EthpdpOutErrorsEntry 10}

pr1645v2EthpdpOutErrorsValue OBJECT-TYPE
   SYNTAX      Counter64
   MAX-ACCESS  read-only
   STATUS      current
   DESCRIPTION
      "Path: ethernetPdp.performance.ifOutErrors

       64 bit unsigned wrappable counter."
   ::= {pr1645v2EthpdpOutErrorsEntry 2147483648}


pr1645v2EthpdpOutQLen OBJECT IDENTIFIER ::= {pr1645v2Ethpdp 120}

pr1645v2EthpdpOutQLenTable OBJECT-TYPE
   SYNTAX      SEQUENCE OF Pr1645v2EthpdpOutQLenEntry
   MAX-ACCESS  not-accessible
   STATUS      current
   DESCRIPTION
      "ifOutQLen"
   ::= {pr1645v2EthpdpOutQLen 1}

pr1645v2EthpdpOutQLenEntry OBJECT-TYPE
   SYNTAX      Pr1645v2EthpdpOutQLenEntry
   MAX-ACCESS  not-accessible
   STATUS      current
   DESCRIPTION
      ""
   INDEX      { pr1645v2EthpdpOutQLenGlobalIx }
   ::= {pr1645v2EthpdpOutQLenTable 1}

Pr1645v2EthpdpOutQLenEntry ::=
   SEQUENCE
      {
      pr1645v2EthpdpOutQLenGlobalIx
         GlobalIndex,
      pr1645v2EthpdpOutQLenValue
         Gauge32
      }

pr1645v2EthpdpOutQLenGlobalIx OBJECT-TYPE
   SYNTAX      GlobalIndex
   MAX-ACCESS  not-accessible
   STATUS      current
   DESCRIPTION
      "The value of the tlsCntTreeGlobalIndex of the MANAGED OBJECT."
   ::= {pr1645v2EthpdpOutQLenEntry 10}

pr1645v2EthpdpOutQLenValue OBJECT-TYPE
   SYNTAX      Gauge32
   MAX-ACCESS  read-only
   STATUS      current
   DESCRIPTION
      "Path: ethernetPdp.performance.ifOutQLen

       32 bit unsigned gauge value."
   ::= {pr1645v2EthpdpOutQLenEntry 2147483648}


pr1645v2EthpdpOutDropEx OBJECT IDENTIFIER ::= {pr1645v2Ethpdp 127}

pr1645v2EthpdpOutDropExTable OBJECT-TYPE
   SYNTAX      SEQUENCE OF Pr1645v2EthpdpOutDropExEntry
   MAX-ACCESS  not-accessible
   STATUS      current
   DESCRIPTION
      "ifOutDiscards"
   ::= {pr1645v2EthpdpOutDropEx 1}

pr1645v2EthpdpOutDropExEntry OBJECT-TYPE
   SYNTAX      Pr1645v2EthpdpOutDropExEntry
   MAX-ACCESS  not-accessible
   STATUS      current
   DESCRIPTION
      ""
   INDEX      { pr1645v2EthpdpOutDropExGlobalIx }
   ::= {pr1645v2EthpdpOutDropExTable 1}

Pr1645v2EthpdpOutDropExEntry ::=
   SEQUENCE
      {
      pr1645v2EthpdpOutDropExGlobalIx
         GlobalIndex,
      pr1645v2EthpdpOutDropExValue
         Counter64
      }

pr1645v2EthpdpOutDropExGlobalIx OBJECT-TYPE
   SYNTAX      GlobalIndex
   MAX-ACCESS  not-accessible
   STATUS      current
   DESCRIPTION
      "The value of the tlsCntTreeGlobalIndex of the MANAGED OBJECT."
   ::= {pr1645v2EthpdpOutDropExEntry 10}

pr1645v2EthpdpOutDropExValue OBJECT-TYPE
   SYNTAX      Counter64
   MAX-ACCESS  read-only
   STATUS      current
   DESCRIPTION
      "Path: ethernetPdp.performance.ifOutDropLevelExceeded

       64 bit unsigned wrappable counter."
   ::= {pr1645v2EthpdpOutDropExEntry 2147483648}


pr1645v2EthpdpOutDropNoArp OBJECT IDENTIFIER ::= {pr1645v2Ethpdp 134}

pr1645v2EthpdpOutDropNoArpTable OBJECT-TYPE
   SYNTAX      SEQUENCE OF Pr1645v2EthpdpOutDropNoArpEntry
   MAX-ACCESS  not-accessible
   STATUS      current
   DESCRIPTION
      "ifOutDiscards"
   ::= {pr1645v2EthpdpOutDropNoArp 1}

pr1645v2EthpdpOutDropNoArpEntry OBJECT-TYPE
   SYNTAX      Pr1645v2EthpdpOutDropNoArpEntry
   MAX-ACCESS  not-accessible
   STATUS      current
   DESCRIPTION
      ""
   INDEX      { pr1645v2EthpdpOutDropNoArpGlobalIx }
   ::= {pr1645v2EthpdpOutDropNoArpTable 1}

Pr1645v2EthpdpOutDropNoArpEntry ::=
   SEQUENCE
      {
      pr1645v2EthpdpOutDropNoArpGlobalIx
         GlobalIndex,
      pr1645v2EthpdpOutDropNoArpValue
         Counter64
      }

pr1645v2EthpdpOutDropNoArpGlobalIx OBJECT-TYPE
   SYNTAX      GlobalIndex
   MAX-ACCESS  not-accessible
   STATUS      current
   DESCRIPTION
      "The value of the tlsCntTreeGlobalIndex of the MANAGED OBJECT."
   ::= {pr1645v2EthpdpOutDropNoArpEntry 10}

pr1645v2EthpdpOutDropNoArpValue OBJECT-TYPE
   SYNTAX      Counter64
   MAX-ACCESS  read-only
   STATUS      current
   DESCRIPTION
      "Path: ethernetPdp.performance.ifOutDiscardsNoArp

       64 bit unsigned wrappable counter."
   ::= {pr1645v2EthpdpOutDropNoArpEntry 2147483648}


pr1645v2EthpdpOutDropFilter OBJECT IDENTIFIER ::= {pr1645v2Ethpdp 138}

pr1645v2EthpdpOutDropFilterTable OBJECT-TYPE
   SYNTAX      SEQUENCE OF Pr1645v2EthpdpOutDropFilterEntry
   MAX-ACCESS  not-accessible
   STATUS      current
   DESCRIPTION
      "ifOutDiscards"
   ::= {pr1645v2EthpdpOutDropFilter 1}

pr1645v2EthpdpOutDropFilterEntry OBJECT-TYPE
   SYNTAX      Pr1645v2EthpdpOutDropFilterEntry
   MAX-ACCESS  not-accessible
   STATUS      current
   DESCRIPTION
      ""
   INDEX      { pr1645v2EthpdpOutDropFilterGlobalIx }
   ::= {pr1645v2EthpdpOutDropFilterTable 1}

Pr1645v2EthpdpOutDropFilterEntry ::=
   SEQUENCE
      {
      pr1645v2EthpdpOutDropFilterGlobalIx
         GlobalIndex,
      pr1645v2EthpdpOutDropFilterValue
         Counter64
      }

pr1645v2EthpdpOutDropFilterGlobalIx OBJECT-TYPE
   SYNTAX      GlobalIndex
   MAX-ACCESS  not-accessible
   STATUS      current
   DESCRIPTION
      "The value of the tlsCntTreeGlobalIndex of the MANAGED OBJECT."
   ::= {pr1645v2EthpdpOutDropFilterEntry 10}

pr1645v2EthpdpOutDropFilterValue OBJECT-TYPE
   SYNTAX      Counter64
   MAX-ACCESS  read-only
   STATUS      current
   DESCRIPTION
      "Path: ethernetPdp.performance.ifOutDiscardsFilter

       64 bit unsigned wrappable counter."
   ::= {pr1645v2EthpdpOutDropFilterEntry 2147483648}


pr1645v2EthpdpOutQueues OBJECT IDENTIFIER ::= {pr1645v2Ethpdp 129}

pr1645v2EthpdpOutQueuesSSCTable OBJECT-TYPE
   SYNTAX      SEQUENCE OF Pr1645v2EthpdpOutQueuesEntry
   MAX-ACCESS  not-accessible
   STATUS      current
   DESCRIPTION
      "Queue Lengths"
   ::= {pr1645v2EthpdpOutQueues 1}

pr1645v2EthpdpOutQueuesEntry OBJECT-TYPE
   SYNTAX      Pr1645v2EthpdpOutQueuesEntry
   MAX-ACCESS  not-accessible
   STATUS      current
   DESCRIPTION
      ""
   INDEX      { pr1645v2EthpdpOutQueuesGlobalIx,
                pr1645v2EthpdpOutQueuesTableIx }
   ::= {pr1645v2EthpdpOutQueuesSSCTable 1}

Pr1645v2EthpdpOutQueuesEntry ::=
   SEQUENCE
      {
      pr1645v2EthpdpOutQueuesGlobalIx
         GlobalIndex,
      pr1645v2EthpdpOutQueuesTableIx
         TableIndex,
      pr1645v2EthpdpOutQueuesName
         INTEGER,
      pr1645v2EthpdpOutQueuesLength
         Integer32,
      pr1645v2EthpdpOutQueuesOctetLength
         Integer32,
      pr1645v2EthpdpOutQueuesRedLength
         Integer32,
      pr1645v2EthpdpOutQueuesPacketsTotal
         Counter64,
      pr1645v2EthpdpOutQueuesPacketsDirectTx
         Counter64,
      pr1645v2EthpdpOutQueuesPacketsQueued
         Counter64,
      pr1645v2EthpdpOutQueuesPacketsDropped
         Counter64,
      pr1645v2EthpdpOutQueuesPacketsRedDropped
         Counter64,
      pr1645v2EthpdpOutQueuesPacketsCirTx
         Counter64,
      pr1645v2EthpdpOutQueuesPacketsEirTx
         Counter64,
      pr1645v2EthpdpOutQueuesPacketsViolateTx
         Counter64,
      pr1645v2EthpdpOutQueuesOctetsTotal
         Counter64,
      pr1645v2EthpdpOutQueuesOctetsDirectTx
         Counter64,
      pr1645v2EthpdpOutQueuesOctetsQueued
         Counter64,
      pr1645v2EthpdpOutQueuesOctetsDropped
         Counter64,
      pr1645v2EthpdpOutQueuesOctetsRedDropped
         Counter64,
      pr1645v2EthpdpOutQueuesOctetsCirTx
         Counter64,
      pr1645v2EthpdpOutQueuesOctetsEirTx
         Counter64,
      pr1645v2EthpdpOutQueuesOctetsViolateTx
         Counter64,
      pr1645v2EthpdpOutQueuesOctetsBandwidth15sec
         Integer32,
      pr1645v2EthpdpOutQueuesOctetsBandwidth30sec
         Integer32,
      pr1645v2EthpdpOutQueuesOctetsBandwidth1min
         Integer32,
      pr1645v2EthpdpOutQueuesOctetsBandwidth2min
         Integer32,
      pr1645v2EthpdpOutQueuesOctetsBandwidth5min
         Integer32
      }

pr1645v2EthpdpOutQueuesGlobalIx OBJECT-TYPE
   SYNTAX      GlobalIndex
   MAX-ACCESS  not-accessible
   STATUS      current
   DESCRIPTION
      "The value of the tlsCntTreeGlobalIndex of the MANAGED OBJECT."
   ::= {pr1645v2EthpdpOutQueuesEntry 10}

pr1645v2EthpdpOutQueuesTableIx OBJECT-TYPE
   SYNTAX      TableIndex
   MAX-ACCESS  not-accessible
   STATUS      current
   DESCRIPTION
      ""
   ::= {pr1645v2EthpdpOutQueuesEntry 11}

pr1645v2EthpdpOutQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernetPdp.performance.ifOutPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2EthpdpOutQueuesEntry 16777216}

pr1645v2EthpdpOutQueuesLength OBJECT-TYPE
   SYNTAX      Integer32
   MAX-ACCESS  read-only
   STATUS      current
   DESCRIPTION
      "Path: ethernetPdp.performance.ifOutPriorityQueues.length"
   ::= {pr1645v2EthpdpOutQueuesEntry 33554432}

pr1645v2EthpdpOutQueuesOctetLength OBJECT-TYPE
   SYNTAX      Integer32
   MAX-ACCESS  read-only
   STATUS      current
   DESCRIPTION
      "Path: ethernetPdp.performance.ifOutPriorityQueues.octetLength"
   ::= {pr1645v2EthpdpOutQueuesEntry 150994944}

pr1645v2EthpdpOutQueuesRedLength OBJECT-TYPE
   SYNTAX      Integer32
   MAX-ACCESS  read-only
   STATUS      current
   DESCRIPTION
      "Path: ethernetPdp.performance.ifOutPriorityQueues.redLength"
   ::= {pr1645v2EthpdpOutQueuesEntry 134217728}

pr1645v2EthpdpOutQueuesPacketsTotal OBJECT-TYPE
   SYNTAX      Counter64
   MAX-ACCESS  read-only
   STATUS      current
   DESCRIPTION
      "Path: ethernetPdp.performance.ifOutPriorityQueues.packets.total

       64 bit unsigned wrappable counter."
   ::= {pr1645v2EthpdpOutQueuesEntry 50790400}

pr1645v2EthpdpOutQueuesPacketsDirectTx OBJECT-TYPE
   SYNTAX      Counter64
   MAX-ACCESS  read-only
   STATUS      current
   DESCRIPTION
      "Path: ethernetPdp.performance.ifOutPriorityQueues.packets.directTx

       64 bit unsigned wrappable counter."
   ::= {pr1645v2EthpdpOutQueuesEntry 50397184}

pr1645v2EthpdpOutQueuesPacketsQueued OBJECT-TYPE
   SYNTAX      Counter64
   MAX-ACCESS  read-only
   STATUS      current
   DESCRIPTION
      "Path: ethernetPdp.performance.ifOutPriorityQueues.packets.queued

       64 bit unsigned wrappable counter."
   ::= {pr1645v2EthpdpOutQueuesEntry 50462720}

pr1645v2EthpdpOutQueuesPacketsDropped OBJECT-TYPE
   SYNTAX      Counter64
   MAX-ACCESS  read-only
   STATUS      current
   DESCRIPTION
      "Path: ethernetPdp.performance.ifOutPriorityQueues.packets.dropped

       64 bit unsigned wrappable counter."
   ::= {pr1645v2EthpdpOutQueuesEntry 50528256}

pr1645v2EthpdpOutQueuesPacketsRedDropped OBJECT-TYPE
   SYNTAX      Counter64
   MAX-ACCESS  read-only
   STATUS      current
   DESCRIPTION
      "Path: ethernetPdp.performance.ifOutPriorityQueues.packets.redDropped

       64 bit unsigned wrappable counter."
   ::= {pr1645v2EthpdpOutQueuesEntry 50724864}

pr1645v2EthpdpOutQueuesPacketsCirTx OBJECT-TYPE
   SYNTAX      Counter64
   MAX-ACCESS  read-only
   STATUS      current
   DESCRIPTION
      "Path: ethernetPdp.performance.ifOutPriorityQueues.packets.cirTx

       64 bit unsigned wrappable counter."
   ::= {pr1645v2EthpdpOutQueuesEntry 50593792}

pr1645v2EthpdpOutQueuesPacketsEirTx OBJECT-TYPE
   SYNTAX      Counter64
   MAX-ACCESS  read-only
   STATUS      current
   DESCRIPTION
      "Path: ethernetPdp.performance.ifOutPriorityQueues.packets.eirTx

       64 bit unsigned wrappable counter."
   ::= {pr1645v2EthpdpOutQueuesEntry 50659328}

pr1645v2EthpdpOutQueuesPacketsViolateTx OBJECT-TYPE
   SYNTAX      Counter64
   MAX-ACCESS  read-only
   STATUS      current
   DESCRIPTION
      "Path: ethernetPdp.performance.ifOutPriorityQueues.packets.violateTx

       64 bit unsigned wrappable counter."
   ::= {pr1645v2EthpdpOutQueuesEntry 50855936}

pr1645v2EthpdpOutQueuesOctetsTotal OBJECT-TYPE
   SYNTAX      Counter64
   MAX-ACCESS  read-only
   STATUS      current
   DESCRIPTION
      "Path: ethernetPdp.performance.ifOutPriorityQueues.octets.total

       64 bit unsigned wrappable counter."
   ::= {pr1645v2EthpdpOutQueuesEntry 67567616}

pr1645v2EthpdpOutQueuesOctetsDirectTx OBJECT-TYPE
   SYNTAX      Counter64
   MAX-ACCESS  read-only
   STATUS      current
   DESCRIPTION
      "Path: ethernetPdp.performance.ifOutPriorityQueues.octets.directTx

       64 bit unsigned wrappable counter."
   ::= {pr1645v2EthpdpOutQueuesEntry 67174400}

pr1645v2EthpdpOutQueuesOctetsQueued OBJECT-TYPE
   SYNTAX      Counter64
   MAX-ACCESS  read-only
   STATUS      current
   DESCRIPTION
      "Path: ethernetPdp.performance.ifOutPriorityQueues.octets.queued

       64 bit unsigned wrappable counter."
   ::= {pr1645v2EthpdpOutQueuesEntry 67239936}

pr1645v2EthpdpOutQueuesOctetsDropped OBJECT-TYPE
   SYNTAX      Counter64
   MAX-ACCESS  read-only
   STATUS      current
   DESCRIPTION
      "Path: ethernetPdp.performance.ifOutPriorityQueues.octets.dropped

       64 bit unsigned wrappable counter."
   ::= {pr1645v2EthpdpOutQueuesEntry 67305472}

pr1645v2EthpdpOutQueuesOctetsRedDropped OBJECT-TYPE
   SYNTAX      Counter64
   MAX-ACCESS  read-only
   STATUS      current
   DESCRIPTION
      "Path: ethernetPdp.performance.ifOutPriorityQueues.octets.redDropped

       64 bit unsigned wrappable counter."
   ::= {pr1645v2EthpdpOutQueuesEntry 67502080}

pr1645v2EthpdpOutQueuesOctetsCirTx OBJECT-TYPE
   SYNTAX      Counter64
   MAX-ACCESS  read-only
   STATUS      current
   DESCRIPTION
      "Path: ethernetPdp.performance.ifOutPriorityQueues.octets.cirTx

       64 bit unsigned wrappable counter."
   ::= {pr1645v2EthpdpOutQueuesEntry 67371008}

pr1645v2EthpdpOutQueuesOctetsEirTx OBJECT-TYPE
   SYNTAX      Counter64
   MAX-ACCESS  read-only
   STATUS      current
   DESCRIPTION
      "Path: ethernetPdp.performance.ifOutPriorityQueues.octets.eirTx

       64 bit unsigned wrappable counter."
   ::= {pr1645v2EthpdpOutQueuesEntry 67436544}

pr1645v2EthpdpOutQueuesOctetsViolateTx OBJECT-TYPE
   SYNTAX      Counter64
   MAX-ACCESS  read-only
   STATUS      current
   DESCRIPTION
      "Path: ethernetPdp.performance.ifOutPriorityQueues.octets.violateTx

       64 bit unsigned wrappable counter."
   ::= {pr1645v2EthpdpOutQueuesEntry 67633152}

pr1645v2EthpdpOutQueuesOctetsBandwidth15sec OBJECT-TYPE
   SYNTAX      Integer32
   MAX-ACCESS  read-only
   STATUS      current
   DESCRIPTION
      "Path: ethernetPdp.performance.ifOutPriorityQueues.octets.bandwidth.15sec

       unit name = bps
       formula = 8 * ; 8 /"
   ::= {pr1645v2EthpdpOutQueuesEntry 70386944}

pr1645v2EthpdpOutQueuesOctetsBandwidth30sec OBJECT-TYPE
   SYNTAX      Integer32
   MAX-ACCESS  read-only
   STATUS      current
   DESCRIPTION
      "Path: ethernetPdp.performance.ifOutPriorityQueues.octets.bandwidth.30sec

       unit name = bps
       formula = 8 * ; 8 /"
   ::= {pr1645v2EthpdpOutQueuesEntry 70388224}

pr1645v2EthpdpOutQueuesOctetsBandwidth1min OBJECT-TYPE
   SYNTAX      Integer32
   MAX-ACCESS  read-only
   STATUS      current
   DESCRIPTION
      "Path: ethernetPdp.performance.ifOutPriorityQueues.octets.bandwidth.1min

       unit name = bps
       formula = 8 * ; 8 /"
   ::= {pr1645v2EthpdpOutQueuesEntry 70390784}

pr1645v2EthpdpOutQueuesOctetsBandwidth2min OBJECT-TYPE
   SYNTAX      Integer32
   MAX-ACCESS  read-only
   STATUS      current
   DESCRIPTION
      "Path: ethernetPdp.performance.ifOutPriorityQueues.octets.bandwidth.2min

       unit name = bps
       formula = 8 * ; 8 /"
   ::= {pr1645v2EthpdpOutQueuesEntry 70395904}

pr1645v2EthpdpOutQueuesOctetsBandwidth5min OBJECT-TYPE
   SYNTAX      Integer32
   MAX-ACCESS  read-only
   STATUS      current
   DESCRIPTION
      "Path: ethernetPdp.performance.ifOutPriorityQueues.octets.bandwidth.5min

       unit name = bps
       formula = 8 * ; 8 /"
   ::= {pr1645v2EthpdpOutQueuesEntry 70411264}

pr1645v2EthpdpOutQueuesH2Performance OBJECT-TYPE
   SYNTAX      SEQUENCE OF Pr1645v2EthpdpOutQueuesH2PerformanceEntry
   MAX-ACCESS  not-accessible
   STATUS      current
   DESCRIPTION
      ""
   ::= {pr1645v2EthpdpOutQueues 83886080}

pr1645v2EthpdpOutQueuesH2PerformanceEntry OBJECT-TYPE
   SYNTAX      Pr1645v2EthpdpOutQueuesH2PerformanceEntry
   MAX-ACCESS  not-accessible
   STATUS      current
   DESCRIPTION
      ""
   INDEX      { pr1645v2EthpdpOutQueuesH2PerformanceGlobalIx,
                pr1645v2EthpdpOutQueuesTableIx,
                pr1645v2EthpdpOutQueuesH2PerformanceTableIx }
   ::= {pr1645v2EthpdpOutQueuesH2Performance 1}

Pr1645v2EthpdpOutQueuesH2PerformanceEntry ::=
   SEQUENCE
      {
      pr1645v2EthpdpOutQueuesH2PerformanceGlobalIx
         GlobalIndex,
      pr1645v2EthpdpOutQueuesH2PerformanceTableIx
         TableIndex,
      pr1645v2EthpdpOutQueuesH2PerformanceSysUpTime
         TimeTicks,
      pr1645v2EthpdpOutQueuesH2PerformanceTotPkts
         Counter64,
      pr1645v2EthpdpOutQueuesH2PerformanceDirTxPkts
         Counter64,
      pr1645v2EthpdpOutQueuesH2PerformanceQdPkts
         Counter64,
      pr1645v2EthpdpOutQueuesH2PerformanceDropPkts
         Counter64,
      pr1645v2EthpdpOutQueuesH2PerformanceRDropPkts
         Counter64,
      pr1645v2EthpdpOutQueuesH2PerformanceCirTxPkts
         Counter64,
      pr1645v2EthpdpOutQueuesH2PerformanceEirTxPkts
         Counter64,
      pr1645v2EthpdpOutQueuesH2PerformanceViolTxPkts
         Counter64,
      pr1645v2EthpdpOutQueuesH2PerformanceTotOcts
         Counter64,
      pr1645v2EthpdpOutQueuesH2PerformanceDirTxOcts
         Counter64,
      pr1645v2EthpdpOutQueuesH2PerformanceQdOcts
         Counter64,
      pr1645v2EthpdpOutQueuesH2PerformanceDropOcts
         Counter64,
      pr1645v2EthpdpOutQueuesH2PerformanceRDropOcts
         Counter64,
      pr1645v2EthpdpOutQueuesH2PerformanceCirTxOcts
         Counter64,
      pr1645v2EthpdpOutQueuesH2PerformanceEirTxOcts
         Counter64,
      pr1645v2EthpdpOutQueuesH2PerformanceViolTxOcts
         Counter64,
      pr1645v2EthpdpOutQueuesH2PerformanceBandwidth
         Integer32
      }

pr1645v2EthpdpOutQueuesH2PerformanceGlobalIx OBJECT-TYPE
   SYNTAX      GlobalIndex
   MAX-ACCESS  not-accessible
   STATUS      current
   DESCRIPTION
      "The value of the tlsCntTreeGlobalIndex of the MANAGED OBJECT."
   ::= {pr1645v2EthpdpOutQueuesH2PerformanceEntry 10}

pr1645v2EthpdpOutQueuesH2PerformanceTableIx OBJECT-TYPE
   SYNTAX      TableIndex
   MAX-ACCESS  not-accessible
   STATUS      current
   DESCRIPTION
      ""
   ::= {pr1645v2EthpdpOutQueuesH2PerformanceEntry 11}

pr1645v2EthpdpOutQueuesH2PerformanceSysUpTime OBJECT-TYPE
   SYNTAX      TimeTicks
   MAX-ACCESS  read-only
   STATUS      current
   DESCRIPTION
      "Path: ethernetPdp.performance.ifOutPriorityQueues.h2Performance.sysUpTime

       Time in centi-second."
   ::= {pr1645v2EthpdpOutQueuesH2PerformanceEntry 16777216}

pr1645v2EthpdpOutQueuesH2PerformanceTotPkts OBJECT-TYPE
   SYNTAX      Counter64
   MAX-ACCESS  read-only
   STATUS      current
   DESCRIPTION
      "Path: ethernetPdp.performance.ifOutPriorityQueues.h2Performance.totalPkts

       64 bit unsigned wrappable counter."
   ::= {pr1645v2EthpdpOutQueuesH2PerformanceEntry 234881024}

pr1645v2EthpdpOutQueuesH2PerformanceDirTxPkts OBJECT-TYPE
   SYNTAX      Counter64
   MAX-ACCESS  read-only
   STATUS      current
   DESCRIPTION
      "Path: ethernetPdp.performance.ifOutPriorityQueues.h2Performance.directTxPkts

       64 bit unsigned wrappable counter."
   ::= {pr1645v2EthpdpOutQueuesH2PerformanceEntry 33554432}

pr1645v2EthpdpOutQueuesH2PerformanceQdPkts OBJECT-TYPE
   SYNTAX      Counter64
   MAX-ACCESS  read-only
   STATUS      current
   DESCRIPTION
      "Path: ethernetPdp.performance.ifOutPriorityQueues.h2Performance.queuedPkts

       64 bit unsigned wrappable counter."
   ::= {pr1645v2EthpdpOutQueuesH2PerformanceEntry 50331648}

pr1645v2EthpdpOutQueuesH2PerformanceDropPkts OBJECT-TYPE
   SYNTAX      Counter64
   MAX-ACCESS  read-only
   STATUS      current
   DESCRIPTION
      "Path: ethernetPdp.performance.ifOutPriorityQueues.h2Performance.droppedPkts

       64 bit unsigned wrappable counter."
   ::= {pr1645v2EthpdpOutQueuesH2PerformanceEntry 67108864}

pr1645v2EthpdpOutQueuesH2PerformanceRDropPkts OBJECT-TYPE
   SYNTAX      Counter64
   MAX-ACCESS  read-only
   STATUS      current
   DESCRIPTION
      "Path: ethernetPdp.performance.ifOutPriorityQueues.h2Performance.redDroppedPkts

       64 bit unsigned wrappable counter."
   ::= {pr1645v2EthpdpOutQueuesH2PerformanceEntry 201326592}

pr1645v2EthpdpOutQueuesH2PerformanceCirTxPkts OBJECT-TYPE
   SYNTAX      Counter64
   MAX-ACCESS  read-only
   STATUS      current
   DESCRIPTION
      "Path: ethernetPdp.performance.ifOutPriorityQueues.h2Performance.cirTxPkts

       64 bit unsigned wrappable counter."
   ::= {pr1645v2EthpdpOutQueuesH2PerformanceEntry 83886080}

pr1645v2EthpdpOutQueuesH2PerformanceEirTxPkts OBJECT-TYPE
   SYNTAX      Counter64
   MAX-ACCESS  read-only
   STATUS      current
   DESCRIPTION
      "Path: ethernetPdp.performance.ifOutPriorityQueues.h2Performance.eirTxPkts

       64 bit unsigned wrappable counter."
   ::= {pr1645v2EthpdpOutQueuesH2PerformanceEntry 100663296}

pr1645v2EthpdpOutQueuesH2PerformanceViolTxPkts OBJECT-TYPE
   SYNTAX      Counter64
   MAX-ACCESS  read-only
   STATUS      current
   DESCRIPTION
      "Path: ethernetPdp.performance.ifOutPriorityQueues.h2Performance.violateTxPkts

       64 bit unsigned wrappable counter."
   ::= {pr1645v2EthpdpOutQueuesH2PerformanceEntry 301989888}

pr1645v2EthpdpOutQueuesH2PerformanceTotOcts OBJECT-TYPE
   SYNTAX      Counter64
   MAX-ACCESS  read-only
   STATUS      current
   DESCRIPTION
      "Path: ethernetPdp.performance.ifOutPriorityQueues.h2Performance.totalOctets

       64 bit unsigned wrappable counter."
   ::= {pr1645v2EthpdpOutQueuesH2PerformanceEntry 251658240}

pr1645v2EthpdpOutQueuesH2PerformanceDirTxOcts OBJECT-TYPE
   SYNTAX      Counter64
   MAX-ACCESS  read-only
   STATUS      current
   DESCRIPTION
      "Path: ethernetPdp.performance.ifOutPriorityQueues.h2Performance.directTxOctets

       64 bit unsigned wrappable counter."
   ::= {pr1645v2EthpdpOutQueuesH2PerformanceEntry 117440512}

pr1645v2EthpdpOutQueuesH2PerformanceQdOcts OBJECT-TYPE
   SYNTAX      Counter64
   MAX-ACCESS  read-only
   STATUS      current
   DESCRIPTION
      "Path: ethernetPdp.performance.ifOutPriorityQueues.h2Performance.queuedOctets

       64 bit unsigned wrappable counter."
   ::= {pr1645v2EthpdpOutQueuesH2PerformanceEntry 134217728}

pr1645v2EthpdpOutQueuesH2PerformanceDropOcts OBJECT-TYPE
   SYNTAX      Counter64
   MAX-ACCESS  read-only
   STATUS      current
   DESCRIPTION
      "Path: ethernetPdp.performance.ifOutPriorityQueues.h2Performance.droppedOctets

       64 bit unsigned wrappable counter."
   ::= {pr1645v2EthpdpOutQueuesH2PerformanceEntry 150994944}

pr1645v2EthpdpOutQueuesH2PerformanceRDropOcts OBJECT-TYPE
   SYNTAX      Counter64
   MAX-ACCESS  read-only
   STATUS      current
   DESCRIPTION
      "Path: ethernetPdp.performance.ifOutPriorityQueues.h2Performance.redDroppedOctets

       64 bit unsigned wrappable counter."
   ::= {pr1645v2EthpdpOutQueuesH2PerformanceEntry 218103808}

pr1645v2EthpdpOutQueuesH2PerformanceCirTxOcts OBJECT-TYPE
   SYNTAX      Counter64
   MAX-ACCESS  read-only
   STATUS      current
   DESCRIPTION
      "Path: ethernetPdp.performance.ifOutPriorityQueues.h2Performance.cirTxOctets

       64 bit unsigned wrappable counter."
   ::= {pr1645v2EthpdpOutQueuesH2PerformanceEntry 167772160}

pr1645v2EthpdpOutQueuesH2PerformanceEirTxOcts OBJECT-TYPE
   SYNTAX      Counter64
   MAX-ACCESS  read-only
   STATUS      current
   DESCRIPTION
      "Path: ethernetPdp.performance.ifOutPriorityQueues.h2Performance.eirTxOctets

       64 bit unsigned wrappable counter."
   ::= {pr1645v2EthpdpOutQueuesH2PerformanceEntry 184549376}

pr1645v2EthpdpOutQueuesH2PerformanceViolTxOcts OBJECT-TYPE
   SYNTAX      Counter64
   MAX-ACCESS  read-only
   STATUS      current
   DESCRIPTION
      "Path: ethernetPdp.performance.ifOutPriorityQueues.h2Performance.violateTxOctets

       64 bit unsigned wrappable counter."
   ::= {pr1645v2EthpdpOutQueuesH2PerformanceEntry 318767104}

pr1645v2EthpdpOutQueuesH2PerformanceBandwidth OBJECT-TYPE
   SYNTAX      Integer32
   MAX-ACCESS  read-only
   STATUS      current
   DESCRIPTION
      "Path: ethernetPdp.performance.ifOutPriorityQueues.h2Performance.bandwidth

       unit name = bps
       formula = 8 * ; 8 /"
   ::= {pr1645v2EthpdpOutQueuesH2PerformanceEntry 268435456}

pr1645v2EthpdpOutQueuesH24Performance OBJECT-TYPE
   SYNTAX      SEQUENCE OF Pr1645v2EthpdpOutQueuesH24PerformanceEntry
   MAX-ACCESS  not-accessible
   STATUS      current
   DESCRIPTION
      ""
   ::= {pr1645v2EthpdpOutQueues 100663296}

pr1645v2EthpdpOutQueuesH24PerformanceEntry OBJECT-TYPE
   SYNTAX      Pr1645v2EthpdpOutQueuesH24PerformanceEntry
   MAX-ACCESS  not-accessible
   STATUS      current
   DESCRIPTION
      ""
   INDEX      { pr1645v2EthpdpOutQueuesH24PerformanceGlobalIx,
                pr1645v2EthpdpOutQueuesTableIx,
                pr1645v2EthpdpOutQueuesH24PerformanceTableIx }
   ::= {pr1645v2EthpdpOutQueuesH24Performance 1}

Pr1645v2EthpdpOutQueuesH24PerformanceEntry ::=
   SEQUENCE
      {
      pr1645v2EthpdpOutQueuesH24PerformanceGlobalIx
         GlobalIndex,
      pr1645v2EthpdpOutQueuesH24PerformanceTableIx
         TableIndex,
      pr1645v2EthpdpOutQueuesH24PerformanceSysUpTime
         TimeTicks,
      pr1645v2EthpdpOutQueuesH24PerformanceTotPkts
         Counter64,
      pr1645v2EthpdpOutQueuesH24PerformanceDirTxPkts
         Counter64,
      pr1645v2EthpdpOutQueuesH24PerformanceQdPkts
         Counter64,
      pr1645v2EthpdpOutQueuesH24PerformanceDropPkts
         Counter64,
      pr1645v2EthpdpOutQueuesH24PerformanceRDropPkts
         Counter64,
      pr1645v2EthpdpOutQueuesH24PerformanceCirTxPkts
         Counter64,
      pr1645v2EthpdpOutQueuesH24PerformanceEirTxPkts
         Counter64,
      pr1645v2EthpdpOutQueuesH24PerformanceViolTxPkts
         Counter64,
      pr1645v2EthpdpOutQueuesH24PerformanceTotOcts
         Counter64,
      pr1645v2EthpdpOutQueuesH24PerformanceDirTxOcts
         Counter64,
      pr1645v2EthpdpOutQueuesH24PerformanceQdOcts
         Counter64,
      pr1645v2EthpdpOutQueuesH24PerformanceDropOcts
         Counter64,
      pr1645v2EthpdpOutQueuesH24PerformanceRDropOcts
         Counter64,
      pr1645v2EthpdpOutQueuesH24PerformanceCirTxOcts
         Counter64,
      pr1645v2EthpdpOutQueuesH24PerformanceEirTxOcts
         Counter64,
      pr1645v2EthpdpOutQueuesH24PerformanceViolTxOcts
         Counter64,
      pr1645v2EthpdpOutQueuesH24PerformanceBandwidth
         Integer32
      }

pr1645v2EthpdpOutQueuesH24PerformanceGlobalIx OBJECT-TYPE
   SYNTAX      GlobalIndex
   MAX-ACCESS  not-accessible
   STATUS      current
   DESCRIPTION
      "The value of the tlsCntTreeGlobalIndex of the MANAGED OBJECT."
   ::= {pr1645v2EthpdpOutQueuesH24PerformanceEntry 10}

pr1645v2EthpdpOutQueuesH24PerformanceTableIx OBJECT-TYPE
   SYNTAX      TableIndex
   MAX-ACCESS  not-accessible
   STATUS      current
   DESCRIPTION
      ""
   ::= {pr1645v2EthpdpOutQueuesH24PerformanceEntry 11}

pr1645v2EthpdpOutQueuesH24PerformanceSysUpTime OBJECT-TYPE
   SYNTAX      TimeTicks
   MAX-ACCESS  read-only
   STATUS      current
   DESCRIPTION
      "Path: ethernetPdp.performance.ifOutPriorityQueues.h24Performance.sysUpTime

       Time in centi-second."
   ::= {pr1645v2EthpdpOutQueuesH24PerformanceEntry 16777216}

pr1645v2EthpdpOutQueuesH24PerformanceTotPkts OBJECT-TYPE
   SYNTAX      Counter64
   MAX-ACCESS  read-only
   STATUS      current
   DESCRIPTION
      "Path: ethernetPdp.performance.ifOutPriorityQueues.h24Performance.totalPkts

       64 bit unsigned wrappable counter."
   ::= {pr1645v2EthpdpOutQueuesH24PerformanceEntry 234881024}

pr1645v2EthpdpOutQueuesH24PerformanceDirTxPkts OBJECT-TYPE
   SYNTAX      Counter64
   MAX-ACCESS  read-only
   STATUS      current
   DESCRIPTION
      "Path: ethernetPdp.performance.ifOutPriorityQueues.h24Performance.directTxPkts

       64 bit unsigned wrappable counter."
   ::= {pr1645v2EthpdpOutQueuesH24PerformanceEntry 33554432}

pr1645v2EthpdpOutQueuesH24PerformanceQdPkts OBJECT-TYPE
   SYNTAX      Counter64
   MAX-ACCESS  read-only
   STATUS      current
   DESCRIPTION
      "Path: ethernetPdp.performance.ifOutPriorityQueues.h24Performance.queuedPkts

       64 bit unsigned wrappable counter."
   ::= {pr1645v2EthpdpOutQueuesH24PerformanceEntry 50331648}

pr1645v2EthpdpOutQueuesH24PerformanceDropPkts OBJECT-TYPE
   SYNTAX      Counter64
   MAX-ACCESS  read-only
   STATUS      current
   DESCRIPTION
      "Path: ethernetPdp.performance.ifOutPriorityQueues.h24Performance.droppedPkts

       64 bit unsigned wrappable counter."
   ::= {pr1645v2EthpdpOutQueuesH24PerformanceEntry 67108864}

pr1645v2EthpdpOutQueuesH24PerformanceRDropPkts OBJECT-TYPE
   SYNTAX      Counter64
   MAX-ACCESS  read-only
   STATUS      current
   DESCRIPTION
      "Path: ethernetPdp.performance.ifOutPriorityQueues.h24Performance.redDroppedPkts

       64 bit unsigned wrappable counter."
   ::= {pr1645v2EthpdpOutQueuesH24PerformanceEntry 201326592}

pr1645v2EthpdpOutQueuesH24PerformanceCirTxPkts OBJECT-TYPE
   SYNTAX      Counter64
   MAX-ACCESS  read-only
   STATUS      current
   DESCRIPTION
      "Path: ethernetPdp.performance.ifOutPriorityQueues.h24Performance.cirTxPkts

       64 bit unsigned wrappable counter."
   ::= {pr1645v2EthpdpOutQueuesH24PerformanceEntry 83886080}

pr1645v2EthpdpOutQueuesH24PerformanceEirTxPkts OBJECT-TYPE
   SYNTAX      Counter64
   MAX-ACCESS  read-only
   STATUS      current
   DESCRIPTION
      "Path: ethernetPdp.performance.ifOutPriorityQueues.h24Performance.eirTxPkts

       64 bit unsigned wrappable counter."
   ::= {pr1645v2EthpdpOutQueuesH24PerformanceEntry 100663296}

pr1645v2EthpdpOutQueuesH24PerformanceViolTxPkts OBJECT-TYPE
   SYNTAX      Counter64
   MAX-ACCESS  read-only
   STATUS      current
   DESCRIPTION
      "Path: ethernetPdp.performance.ifOutPriorityQueues.h24Performance.violateTxPkts

       64 bit unsigned wrappable counter."
   ::= {pr1645v2EthpdpOutQueuesH24PerformanceEntry 301989888}

pr1645v2EthpdpOutQueuesH24PerformanceTotOcts OBJECT-TYPE
   SYNTAX      Counter64
   MAX-ACCESS  read-only
   STATUS      current
   DESCRIPTION
      "Path: ethernetPdp.performance.ifOutPriorityQueues.h24Performance.totalOctets

       64 bit unsigned wrappable counter."
   ::= {pr1645v2EthpdpOutQueuesH24PerformanceEntry 251658240}

pr1645v2EthpdpOutQueuesH24PerformanceDirTxOcts OBJECT-TYPE
   SYNTAX      Counter64
   MAX-ACCESS  read-only
   STATUS      current
   DESCRIPTION
      "Path: ethernetPdp.performance.ifOutPriorityQueues.h24Performance.directTxOctets

       64 bit unsigned wrappable counter."
   ::= {pr1645v2EthpdpOutQueuesH24PerformanceEntry 117440512}

pr1645v2EthpdpOutQueuesH24PerformanceQdOcts OBJECT-TYPE
   SYNTAX      Counter64
   MAX-ACCESS  read-only
   STATUS      current
   DESCRIPTION
      "Path: ethernetPdp.performance.ifOutPriorityQueues.h24Performance.queuedOctets

       64 bit unsigned wrappable counter."
   ::= {pr1645v2EthpdpOutQueuesH24PerformanceEntry 134217728}

pr1645v2EthpdpOutQueuesH24PerformanceDropOcts OBJECT-TYPE
   SYNTAX      Counter64
   MAX-ACCESS  read-only
   STATUS      current
   DESCRIPTION
      "Path: ethernetPdp.performance.ifOutPriorityQueues.h24Performance.droppedOctets

       64 bit unsigned wrappable counter."
   ::= {pr1645v2EthpdpOutQueuesH24PerformanceEntry 150994944}

pr1645v2EthpdpOutQueuesH24PerformanceRDropOcts OBJECT-TYPE
   SYNTAX      Counter64
   MAX-ACCESS  read-only
   STATUS      current
   DESCRIPTION
      "Path: ethernetPdp.performance.ifOutPriorityQueues.h24Performance.redDroppedOctets

       64 bit unsigned wrappable counter."
   ::= {pr1645v2EthpdpOutQueuesH24PerformanceEntry 218103808}

pr1645v2EthpdpOutQueuesH24PerformanceCirTxOcts OBJECT-TYPE
   SYNTAX      Counter64
   MAX-ACCESS  read-only
   STATUS      current
   DESCRIPTION
      "Path: ethernetPdp.performance.ifOutPriorityQueues.h24Performance.cirTxOctets

       64 bit unsigned wrappable counter."
   ::= {pr1645v2EthpdpOutQueuesH24PerformanceEntry 167772160}

pr1645v2EthpdpOutQueuesH24PerformanceEirTxOcts OBJECT-TYPE
   SYNTAX      Counter64
   MAX-ACCESS  read-only
   STATUS      current
   DESCRIPTION
      "Path: ethernetPdp.performance.ifOutPriorityQueues.h24Performance.eirTxOctets

       64 bit unsigned wrappable counter."
   ::= {pr1645v2EthpdpOutQueuesH24PerformanceEntry 184549376}

pr1645v2EthpdpOutQueuesH24PerformanceViolTxOcts OBJECT-TYPE
   SYNTAX      Counter64
   MAX-ACCESS  read-only
   STATUS      current
   DESCRIPTION
      "Path: ethernetPdp.performance.ifOutPriorityQueues.h24Performance.violateTxOctets

       64 bit unsigned wrappable counter."
   ::= {pr1645v2EthpdpOutQueuesH24PerformanceEntry 318767104}

pr1645v2EthpdpOutQueuesH24PerformanceBandwidth OBJECT-TYPE
   SYNTAX      Integer32
   MAX-ACCESS  read-only
   STATUS      current
   DESCRIPTION
      "Path: ethernetPdp.performance.ifOutPriorityQueues.h24Performance.bandwidth

       unit name = bps
       formula = 8 * ; 8 /"
   ::= {pr1645v2EthpdpOutQueuesH24PerformanceEntry 268435456}

pr1645v2EthpdpOutQueuesD7Performance OBJECT-TYPE
   SYNTAX      SEQUENCE OF Pr1645v2EthpdpOutQueuesD7PerformanceEntry
   MAX-ACCESS  not-accessible
   STATUS      current
   DESCRIPTION
      ""
   ::= {pr1645v2EthpdpOutQueues 117440512}

pr1645v2EthpdpOutQueuesD7PerformanceEntry OBJECT-TYPE
   SYNTAX      Pr1645v2EthpdpOutQueuesD7PerformanceEntry
   MAX-ACCESS  not-accessible
   STATUS      current
   DESCRIPTION
      ""
   INDEX      { pr1645v2EthpdpOutQueuesD7PerformanceGlobalIx,
                pr1645v2EthpdpOutQueuesTableIx,
                pr1645v2EthpdpOutQueuesD7PerformanceTableIx }
   ::= {pr1645v2EthpdpOutQueuesD7Performance 1}

Pr1645v2EthpdpOutQueuesD7PerformanceEntry ::=
   SEQUENCE
      {
      pr1645v2EthpdpOutQueuesD7PerformanceGlobalIx
         GlobalIndex,
      pr1645v2EthpdpOutQueuesD7PerformanceTableIx
         TableIndex,
      pr1645v2EthpdpOutQueuesD7PerformanceSysUpTime
         TimeTicks,
      pr1645v2EthpdpOutQueuesD7PerformanceTotPkts
         Counter64,
      pr1645v2EthpdpOutQueuesD7PerformanceDirTxPkts
         Counter64,
      pr1645v2EthpdpOutQueuesD7PerformanceQdPkts
         Counter64,
      pr1645v2EthpdpOutQueuesD7PerformanceDropPkts
         Counter64,
      pr1645v2EthpdpOutQueuesD7PerformanceRDropPkts
         Counter64,
      pr1645v2EthpdpOutQueuesD7PerformanceCirTxPkts
         Counter64,
      pr1645v2EthpdpOutQueuesD7PerformanceEirTxPkts
         Counter64,
      pr1645v2EthpdpOutQueuesD7PerformanceViolTxPkts
         Counter64,
      pr1645v2EthpdpOutQueuesD7PerformanceTotOcts
         Counter64,
      pr1645v2EthpdpOutQueuesD7PerformanceDirTxOcts
         Counter64,
      pr1645v2EthpdpOutQueuesD7PerformanceQdOcts
         Counter64,
      pr1645v2EthpdpOutQueuesD7PerformanceDropOcts
         Counter64,
      pr1645v2EthpdpOutQueuesD7PerformanceRDropOcts
         Counter64,
      pr1645v2EthpdpOutQueuesD7PerformanceCirTxOcts
         Counter64,
      pr1645v2EthpdpOutQueuesD7PerformanceEirTxOcts
         Counter64,
      pr1645v2EthpdpOutQueuesD7PerformanceViolTxOcts
         Counter64,
      pr1645v2EthpdpOutQueuesD7PerformanceBandwidth
         Integer32
      }

pr1645v2EthpdpOutQueuesD7PerformanceGlobalIx OBJECT-TYPE
   SYNTAX      GlobalIndex
   MAX-ACCESS  not-accessible
   STATUS      current
   DESCRIPTION
      "The value of the tlsCntTreeGlobalIndex of the MANAGED OBJECT."
   ::= {pr1645v2EthpdpOutQueuesD7PerformanceEntry 10}

pr1645v2EthpdpOutQueuesD7PerformanceTableIx OBJECT-TYPE
   SYNTAX      TableIndex
   MAX-ACCESS  not-accessible
   STATUS      current
   DESCRIPTION
      ""
   ::= {pr1645v2EthpdpOutQueuesD7PerformanceEntry 11}

pr1645v2EthpdpOutQueuesD7PerformanceSysUpTime OBJECT-TYPE
   SYNTAX      TimeTicks
   MAX-ACCESS  read-only
   STATUS      current
   DESCRIPTION
      "Path: ethernetPdp.performance.ifOutPriorityQueues.d7Performance.sysUpTime

       Time in centi-second."
   ::= {pr1645v2EthpdpOutQueuesD7PerformanceEntry 16777216}

pr1645v2EthpdpOutQueuesD7PerformanceTotPkts OBJECT-TYPE
   SYNTAX      Counter64
   MAX-ACCESS  read-only
   STATUS      current
   DESCRIPTION
      "Path: ethernetPdp.performance.ifOutPriorityQueues.d7Performance.totalPkts

       64 bit unsigned wrappable counter."
   ::= {pr1645v2EthpdpOutQueuesD7PerformanceEntry 234881024}

pr1645v2EthpdpOutQueuesD7PerformanceDirTxPkts OBJECT-TYPE
   SYNTAX      Counter64
   MAX-ACCESS  read-only
   STATUS      current
   DESCRIPTION
      "Path: ethernetPdp.performance.ifOutPriorityQueues.d7Performance.directTxPkts

       64 bit unsigned wrappable counter."
   ::= {pr1645v2EthpdpOutQueuesD7PerformanceEntry 33554432}

pr1645v2EthpdpOutQueuesD7PerformanceQdPkts OBJECT-TYPE
   SYNTAX      Counter64
   MAX-ACCESS  read-only
   STATUS      current
   DESCRIPTION
      "Path: ethernetPdp.performance.ifOutPriorityQueues.d7Performance.queuedPkts

       64 bit unsigned wrappable counter."
   ::= {pr1645v2EthpdpOutQueuesD7PerformanceEntry 50331648}

pr1645v2EthpdpOutQueuesD7PerformanceDropPkts OBJECT-TYPE
   SYNTAX      Counter64
   MAX-ACCESS  read-only
   STATUS      current
   DESCRIPTION
      "Path: ethernetPdp.performance.ifOutPriorityQueues.d7Performance.droppedPkts

       64 bit unsigned wrappable counter."
   ::= {pr1645v2EthpdpOutQueuesD7PerformanceEntry 67108864}

pr1645v2EthpdpOutQueuesD7PerformanceRDropPkts OBJECT-TYPE
   SYNTAX      Counter64
   MAX-ACCESS  read-only
   STATUS      current
   DESCRIPTION
      "Path: ethernetPdp.performance.ifOutPriorityQueues.d7Performance.redDroppedPkts

       64 bit unsigned wrappable counter."
   ::= {pr1645v2EthpdpOutQueuesD7PerformanceEntry 201326592}

pr1645v2EthpdpOutQueuesD7PerformanceCirTxPkts OBJECT-TYPE
   SYNTAX      Counter64
   MAX-ACCESS  read-only
   STATUS      current
   DESCRIPTION
      "Path: ethernetPdp.performance.ifOutPriorityQueues.d7Performance.cirTxPkts

       64 bit unsigned wrappable counter."
   ::= {pr1645v2EthpdpOutQueuesD7PerformanceEntry 83886080}

pr1645v2EthpdpOutQueuesD7PerformanceEirTxPkts OBJECT-TYPE
   SYNTAX      Counter64
   MAX-ACCESS  read-only
   STATUS      current
   DESCRIPTION
      "Path: ethernetPdp.performance.ifOutPriorityQueues.d7Performance.eirTxPkts

       64 bit unsigned wrappable counter."
   ::= {pr1645v2EthpdpOutQueuesD7PerformanceEntry 100663296}

pr1645v2EthpdpOutQueuesD7PerformanceViolTxPkts OBJECT-TYPE
   SYNTAX      Counter64
   MAX-ACCESS  read-only
   STATUS      current
   DESCRIPTION
      "Path: ethernetPdp.performance.ifOutPriorityQueues.d7Performance.violateTxPkts

       64 bit unsigned wrappable counter."
   ::= {pr1645v2EthpdpOutQueuesD7PerformanceEntry 301989888}

pr1645v2EthpdpOutQueuesD7PerformanceTotOcts OBJECT-TYPE
   SYNTAX      Counter64
   MAX-ACCESS  read-only
   STATUS      current
   DESCRIPTION
      "Path: ethernetPdp.performance.ifOutPriorityQueues.d7Performance.totalOctets

       64 bit unsigned wrappable counter."
   ::= {pr1645v2EthpdpOutQueuesD7PerformanceEntry 251658240}

pr1645v2EthpdpOutQueuesD7PerformanceDirTxOcts OBJECT-TYPE
   SYNTAX      Counter64
   MAX-ACCESS  read-only
   STATUS      current
   DESCRIPTION
      "Path: ethernetPdp.performance.ifOutPriorityQueues.d7Performance.directTxOctets

       64 bit unsigned wrappable counter."
   ::= {pr1645v2EthpdpOutQueuesD7PerformanceEntry 117440512}

pr1645v2EthpdpOutQueuesD7PerformanceQdOcts OBJECT-TYPE
   SYNTAX      Counter64
   MAX-ACCESS  read-only
   STATUS      current
   DESCRIPTION
      "Path: ethernetPdp.performance.ifOutPriorityQueues.d7Performance.queuedOctets

       64 bit unsigned wrappable counter."
   ::= {pr1645v2EthpdpOutQueuesD7PerformanceEntry 134217728}

pr1645v2EthpdpOutQueuesD7PerformanceDropOcts OBJECT-TYPE
   SYNTAX      Counter64
   MAX-ACCESS  read-only
   STATUS      current
   DESCRIPTION
      "Path: ethernetPdp.performance.ifOutPriorityQueues.d7Performance.droppedOctets

       64 bit unsigned wrappable counter."
   ::= {pr1645v2EthpdpOutQueuesD7PerformanceEntry 150994944}

pr1645v2EthpdpOutQueuesD7PerformanceRDropOcts OBJECT-TYPE
   SYNTAX      Counter64
   MAX-ACCESS  read-only
   STATUS      current
   DESCRIPTION
      "Path: ethernetPdp.performance.ifOutPriorityQueues.d7Performance.redDroppedOctets

       64 bit unsigned wrappable counter."
   ::= {pr1645v2EthpdpOutQueuesD7PerformanceEntry 218103808}

pr1645v2EthpdpOutQueuesD7PerformanceCirTxOcts OBJECT-TYPE
   SYNTAX      Counter64
   MAX-ACCESS  read-only
   STATUS      current
   DESCRIPTION
      "Path: ethernetPdp.performance.ifOutPriorityQueues.d7Performance.cirTxOctets

       64 bit unsigned wrappable counter."
   ::= {pr1645v2EthpdpOutQueuesD7PerformanceEntry 167772160}

pr1645v2EthpdpOutQueuesD7PerformanceEirTxOcts OBJECT-TYPE
   SYNTAX      Counter64
   MAX-ACCESS  read-only
   STATUS      current
   DESCRIPTION
      "Path: ethernetPdp.performance.ifOutPriorityQueues.d7Performance.eirTxOctets

       64 bit unsigned wrappable counter."
   ::= {pr1645v2EthpdpOutQueuesD7PerformanceEntry 184549376}

pr1645v2EthpdpOutQueuesD7PerformanceViolTxOcts OBJECT-TYPE
   SYNTAX      Counter64
   MAX-ACCESS  read-only
   STATUS      current
   DESCRIPTION
      "Path: ethernetPdp.performance.ifOutPriorityQueues.d7Performance.violateTxOctets

       64 bit unsigned wrappable counter."
   ::= {pr1645v2EthpdpOutQueuesD7PerformanceEntry 318767104}

pr1645v2EthpdpOutQueuesD7PerformanceBandwidth OBJECT-TYPE
   SYNTAX      Integer32
   MAX-ACCESS  read-only
   STATUS      current
   DESCRIPTION
      "Path: ethernetPdp.performance.ifOutPriorityQueues.d7Performance.bandwidth

       unit name = bps
       formula = 8 * ; 8 /"
   ::= {pr1645v2EthpdpOutQueuesD7PerformanceEntry 268435456}


pr1645v2EthpdpOutBandwidth OBJECT IDENTIFIER ::= {pr1645v2Ethpdp 182}

pr1645v2EthpdpOutBandwidthSSCTable OBJECT-TYPE
   SYNTAX      SEQUENCE OF Pr1645v2EthpdpOutBandwidthEntry
   MAX-ACCESS  not-accessible
   STATUS      current
   DESCRIPTION
      "bandwidth"
   ::= {pr1645v2EthpdpOutBandwidth 1}

pr1645v2EthpdpOutBandwidthEntry OBJECT-TYPE
   SYNTAX      Pr1645v2EthpdpOutBandwidthEntry
   MAX-ACCESS  not-accessible
   STATUS      current
   DESCRIPTION
      ""
   INDEX      { pr1645v2EthpdpOutBandwidthGlobalIx }
   ::= {pr1645v2EthpdpOutBandwidthSSCTable 1}

Pr1645v2EthpdpOutBandwidthEntry ::=
   SEQUENCE
      {
      pr1645v2EthpdpOutBandwidthGlobalIx
         GlobalIndex,
      pr1645v2EthpdpOutBandwidth15sec
         Integer32,
      pr1645v2EthpdpOutBandwidth30sec
         Integer32,
      pr1645v2EthpdpOutBandwidth1min
         Integer32,
      pr1645v2EthpdpOutBandwidth2min
         Integer32,
      pr1645v2EthpdpOutBandwidth5min
         Integer32
      }

pr1645v2EthpdpOutBandwidthGlobalIx OBJECT-TYPE
   SYNTAX      GlobalIndex
   MAX-ACCESS  not-accessible
   STATUS      current
   DESCRIPTION
      "The value of the tlsCntTreeGlobalIndex of the MANAGED OBJECT."
   ::= {pr1645v2EthpdpOutBandwidthEntry 10}

pr1645v2EthpdpOutBandwidth15sec OBJECT-TYPE
   SYNTAX      Integer32
   MAX-ACCESS  read-only
   STATUS      current
   DESCRIPTION
      "Path: ethernetPdp.performance.ifOutBandwidth.15sec

       unit name = bps
       formula = 8 * ; 8 /"
   ::= {pr1645v2EthpdpOutBandwidthEntry 83886080}

pr1645v2EthpdpOutBandwidth30sec OBJECT-TYPE
   SYNTAX      Integer32
   MAX-ACCESS  read-only
   STATUS      current
   DESCRIPTION
      "Path: ethernetPdp.performance.ifOutBandwidth.30sec

       unit name = bps
       formula = 8 * ; 8 /"
   ::= {pr1645v2EthpdpOutBandwidthEntry 167772160}

pr1645v2EthpdpOutBandwidth1min OBJECT-TYPE
   SYNTAX      Integer32
   MAX-ACCESS  read-only
   STATUS      current
   DESCRIPTION
      "Path: ethernetPdp.performance.ifOutBandwidth.1min

       unit name = bps
       formula = 8 * ; 8 /"
   ::= {pr1645v2EthpdpOutBandwidthEntry 335544320}

pr1645v2EthpdpOutBandwidth2min OBJECT-TYPE
   SYNTAX      Integer32
   MAX-ACCESS  read-only
   STATUS      current
   DESCRIPTION
      "Path: ethernetPdp.performance.ifOutBandwidth.2min

       unit name = bps
       formula = 8 * ; 8 /"
   ::= {pr1645v2EthpdpOutBandwidthEntry 671088640}

pr1645v2EthpdpOutBandwidth5min OBJECT-TYPE
   SYNTAX      Integer32
   MAX-ACCESS  read-only
   STATUS      current
   DESCRIPTION
      "Path: ethernetPdp.performance.ifOutBandwidth.5min

       unit name = bps
       formula = 8 * ; 8 /"
   ::= {pr1645v2EthpdpOutBandwidthEntry 1677721600}


pr1645v2EthpdpInP OBJECT IDENTIFIER ::= {pr1645v2Ethpdp 307}

pr1645v2EthpdpInPSSCTable OBJECT-TYPE
   SYNTAX      SEQUENCE OF Pr1645v2EthpdpInPEntry
   MAX-ACCESS  not-accessible
   STATUS      current
   DESCRIPTION
      "h2IfInPerformance"
   ::= {pr1645v2EthpdpInP 1}

pr1645v2EthpdpInPEntry OBJECT-TYPE
   SYNTAX      Pr1645v2EthpdpInPEntry
   MAX-ACCESS  not-accessible
   STATUS      current
   DESCRIPTION
      ""
   INDEX      { pr1645v2EthpdpInPGlobalIx,
                pr1645v2EthpdpInPTableIx }
   ::= {pr1645v2EthpdpInPSSCTable 1}

Pr1645v2EthpdpInPEntry ::=
   SEQUENCE
      {
      pr1645v2EthpdpInPGlobalIx
         GlobalIndex,
      pr1645v2EthpdpInPTableIx
         TableIndex,
      pr1645v2EthpdpInPSysUpTime
         TimeTicks,
      pr1645v2EthpdpInPIfUpTime
         TimeTicks,
      pr1645v2EthpdpInPIfStatChanges
         Counter32,
      pr1645v2EthpdpInPIfInOctets
         Counter64,
      pr1645v2EthpdpInPIfInUCPkts
         Counter64,
      pr1645v2EthpdpInPIfInNUCPkts
         Counter64,
      pr1645v2EthpdpInPIfInBCPkts
         Counter64,
      pr1645v2EthpdpInPIfInMCPkts
         Counter64,
      pr1645v2EthpdpInPIfInDiscards
         Counter64,
      pr1645v2EthpdpInPIfInErrors
         Counter64,
      pr1645v2EthpdpInPIfInUnkwn
         Counter64,
      pr1645v2EthpdpInPInDropEx
         Counter64,
      pr1645v2EthpdpInPInDropNoMac
         Counter64,
      pr1645v2EthpdpInPInDropNUCast
         Counter64,
      pr1645v2EthpdpInPInDropFilter
         Counter64,
      pr1645v2EthpdpInPIfInBandwidth
         Integer32,
      pr1645v2EthpdpInPIfOutOctets
         Counter64,
      pr1645v2EthpdpInPIfOutUCPkts
         Counter64,
      pr1645v2EthpdpInPIfOutNUCPkts
         Counter64,
      pr1645v2EthpdpInPIfOutBCPkts
         Counter64,
      pr1645v2EthpdpInPIfOutMCPkts
         Counter64,
      pr1645v2EthpdpInPIfOutDiscards
         Counter64,
      pr1645v2EthpdpInPIfOutErrors
         Counter64,
      pr1645v2EthpdpInPOutDropEx
         Counter64,
      pr1645v2EthpdpInPOutDropNoArp
         Counter64,
      pr1645v2EthpdpInPOutDropFilter
         Counter64,
      pr1645v2EthpdpInPIfOutBandwidth
         Integer32,
      pr1645v2EthpdpInPIfErrSec
         Counter32
      }

pr1645v2EthpdpInPGlobalIx OBJECT-TYPE
   SYNTAX      GlobalIndex
   MAX-ACCESS  not-accessible
   STATUS      current
   DESCRIPTION
      "The value of the tlsCntTreeGlobalIndex of the MANAGED OBJECT."
   ::= {pr1645v2EthpdpInPEntry 10}

pr1645v2EthpdpInPTableIx OBJECT-TYPE
   SYNTAX      TableIndex
   MAX-ACCESS  not-accessible
   STATUS      current
   DESCRIPTION
      ""
   ::= {pr1645v2EthpdpInPEntry 11}

pr1645v2EthpdpInPSysUpTime OBJECT-TYPE
   SYNTAX      TimeTicks
   MAX-ACCESS  read-only
   STATUS      current
   DESCRIPTION
      "Path: ethernetPdp.performance.h2Performance.sysUpTime

       Time in centi-second."
   ::= {pr1645v2EthpdpInPEntry 16777216}

pr1645v2EthpdpInPIfUpTime OBJECT-TYPE
   SYNTAX      TimeTicks
   MAX-ACCESS  read-only
   STATUS      current
   DESCRIPTION
      "Path: ethernetPdp.performance.h2Performance.ifUpTime

       Time in centi-second."
   ::= {pr1645v2EthpdpInPEntry 33554432}

pr1645v2EthpdpInPIfStatChanges OBJECT-TYPE
   SYNTAX      Counter32
   MAX-ACCESS  read-only
   STATUS      current
   DESCRIPTION
      "Path: ethernetPdp.performance.h2Performance.ifStatusChanges

       32 bit unsigned wrappable counter."
   ::= {pr1645v2EthpdpInPEntry 50331648}

pr1645v2EthpdpInPIfInOctets OBJECT-TYPE
   SYNTAX      Counter64
   MAX-ACCESS  read-only
   STATUS      current
   DESCRIPTION
      "Path: ethernetPdp.performance.h2Performance.ifInOctets

       64 bit unsigned wrappable counter."
   ::= {pr1645v2EthpdpInPEntry 67108864}

pr1645v2EthpdpInPIfInUCPkts OBJECT-TYPE
   SYNTAX      Counter64
   MAX-ACCESS  read-only
   STATUS      current
   DESCRIPTION
      "Path: ethernetPdp.performance.h2Performance.ifInUcastPkts

       64 bit unsigned wrappable counter."
   ::= {pr1645v2EthpdpInPEntry 83886080}

pr1645v2EthpdpInPIfInNUCPkts OBJECT-TYPE
   SYNTAX      Counter64
   MAX-ACCESS  read-only
   STATUS      current
   DESCRIPTION
      "Path: ethernetPdp.performance.h2Performance.ifInNUcastPkts

       64 bit unsigned wrappable counter."
   ::= {pr1645v2EthpdpInPEntry 100663296}

pr1645v2EthpdpInPIfInBCPkts OBJECT-TYPE
   SYNTAX      Counter64
   MAX-ACCESS  read-only
   STATUS      current
   DESCRIPTION
      "Path: ethernetPdp.performance.h2Performance.ifInBcastPkts

       64 bit unsigned wrappable counter."
   ::= {pr1645v2EthpdpInPEntry 419430400}

pr1645v2EthpdpInPIfInMCPkts OBJECT-TYPE
   SYNTAX      Counter64
   MAX-ACCESS  read-only
   STATUS      current
   DESCRIPTION
      "Path: ethernetPdp.performance.h2Performance.ifInMcastPkts

       64 bit unsigned wrappable counter."
   ::= {pr1645v2EthpdpInPEntry 436207616}

pr1645v2EthpdpInPIfInDiscards OBJECT-TYPE
   SYNTAX      Counter64
   MAX-ACCESS  read-only
   STATUS      current
   DESCRIPTION
      "Path: ethernetPdp.performance.h2Performance.ifInDiscards

       64 bit unsigned wrappable counter."
   ::= {pr1645v2EthpdpInPEntry 117440512}

pr1645v2EthpdpInPIfInErrors OBJECT-TYPE
   SYNTAX      Counter64
   MAX-ACCESS  read-only
   STATUS      current
   DESCRIPTION
      "Path: ethernetPdp.performance.h2Performance.ifInErrors

       64 bit unsigned wrappable counter."
   ::= {pr1645v2EthpdpInPEntry 134217728}

pr1645v2EthpdpInPIfInUnkwn OBJECT-TYPE
   SYNTAX      Counter64
   MAX-ACCESS  read-only
   STATUS      current
   DESCRIPTION
      "Path: ethernetPdp.performance.h2Performance.ifInUnknownProtos

       64 bit unsigned wrappable counter."
   ::= {pr1645v2EthpdpInPEntry 150994944}

pr1645v2EthpdpInPInDropEx OBJECT-TYPE
   SYNTAX      Counter64
   MAX-ACCESS  read-only
   STATUS      current
   DESCRIPTION
      "Path: ethernetPdp.performance.h2Performance.ifInDropLevelExceeded

       64 bit unsigned wrappable counter."
   ::= {pr1645v2EthpdpInPEntry 335544320}

pr1645v2EthpdpInPInDropNoMac OBJECT-TYPE
   SYNTAX      Counter64
   MAX-ACCESS  read-only
   STATUS      current
   DESCRIPTION
      "Path: ethernetPdp.performance.h2Performance.fInDiscardsNoMacFit

       64 bit unsigned wrappable counter."
   ::= {pr1645v2EthpdpInPEntry 301989888}

pr1645v2EthpdpInPInDropNUCast OBJECT-TYPE
   SYNTAX      Counter64
   MAX-ACCESS  read-only
   STATUS      current
   DESCRIPTION
      "Path: ethernetPdp.performance.h2Performance.fInDiscardsNUCast

       64 bit unsigned wrappable counter."
   ::= {pr1645v2EthpdpInPEntry 318767104}

pr1645v2EthpdpInPInDropFilter OBJECT-TYPE
   SYNTAX      Counter64
   MAX-ACCESS  read-only
   STATUS      current
   DESCRIPTION
      "Path: ethernetPdp.performance.h2Performance.fInDiscardsFilter

       64 bit unsigned wrappable counter."
   ::= {pr1645v2EthpdpInPEntry 385875968}

pr1645v2EthpdpInPIfInBandwidth OBJECT-TYPE
   SYNTAX      Integer32
   MAX-ACCESS  read-only
   STATUS      current
   DESCRIPTION
      "Path: ethernetPdp.performance.h2Performance.ifInBandwidth

       unit name = bps
       formula = 8 * ; 8 /"
   ::= {pr1645v2EthpdpInPEntry 268435456}

pr1645v2EthpdpInPIfOutOctets OBJECT-TYPE
   SYNTAX      Counter64
   MAX-ACCESS  read-only
   STATUS      current
   DESCRIPTION
      "Path: ethernetPdp.performance.h2Performance.ifOutOctets

       64 bit unsigned wrappable counter."
   ::= {pr1645v2EthpdpInPEntry 167772160}

pr1645v2EthpdpInPIfOutUCPkts OBJECT-TYPE
   SYNTAX      Counter64
   MAX-ACCESS  read-only
   STATUS      current
   DESCRIPTION
      "Path: ethernetPdp.performance.h2Performance.ifOutUcastPkts

       64 bit unsigned wrappable counter."
   ::= {pr1645v2EthpdpInPEntry 184549376}

pr1645v2EthpdpInPIfOutNUCPkts OBJECT-TYPE
   SYNTAX      Counter64
   MAX-ACCESS  read-only
   STATUS      current
   DESCRIPTION
      "Path: ethernetPdp.performance.h2Performance.ifOutNUcastPkts

       64 bit unsigned wrappable counter."
   ::= {pr1645v2EthpdpInPEntry 201326592}

pr1645v2EthpdpInPIfOutBCPkts OBJECT-TYPE
   SYNTAX      Counter64
   MAX-ACCESS  read-only
   STATUS      current
   DESCRIPTION
      "Path: ethernetPdp.performance.h2Performance.ifOutBcastPkts

       64 bit unsigned wrappable counter."
   ::= {pr1645v2EthpdpInPEntry 452984832}

pr1645v2EthpdpInPIfOutMCPkts OBJECT-TYPE
   SYNTAX      Counter64
   MAX-ACCESS  read-only
   STATUS      current
   DESCRIPTION
      "Path: ethernetPdp.performance.h2Performance.ifOutMcastPkts

       64 bit unsigned wrappable counter."
   ::= {pr1645v2EthpdpInPEntry 469762048}

pr1645v2EthpdpInPIfOutDiscards OBJECT-TYPE
   SYNTAX      Counter64
   MAX-ACCESS  read-only
   STATUS      current
   DESCRIPTION
      "Path: ethernetPdp.performance.h2Performance.ifOutDiscards

       64 bit unsigned wrappable counter."
   ::= {pr1645v2EthpdpInPEntry 218103808}

pr1645v2EthpdpInPIfOutErrors OBJECT-TYPE
   SYNTAX      Counter64
   MAX-ACCESS  read-only
   STATUS      current
   DESCRIPTION
      "Path: ethernetPdp.performance.h2Performance.ifOutErrors

       64 bit unsigned wrappable counter."
   ::= {pr1645v2EthpdpInPEntry 234881024}

pr1645v2EthpdpInPOutDropEx OBJECT-TYPE
   SYNTAX      Counter64
   MAX-ACCESS  read-only
   STATUS      current
   DESCRIPTION
      "Path: ethernetPdp.performance.h2Performance.ifOutDropLevelExceeded

       64 bit unsigned wrappable counter."
   ::= {pr1645v2EthpdpInPEntry 352321536}

pr1645v2EthpdpInPOutDropNoArp OBJECT-TYPE
   SYNTAX      Counter64
   MAX-ACCESS  read-only
   STATUS      current
   DESCRIPTION
      "Path: ethernetPdp.performance.h2Performance.ifOutDiscardsNoArp

       64 bit unsigned wrappable counter."
   ::= {pr1645v2EthpdpInPEntry 369098752}

pr1645v2EthpdpInPOutDropFilter OBJECT-TYPE
   SYNTAX      Counter64
   MAX-ACCESS  read-only
   STATUS      current
   DESCRIPTION
      "Path: ethernetPdp.performance.h2Performance.ifOutDiscardsFilter

       64 bit unsigned wrappable counter."
   ::= {pr1645v2EthpdpInPEntry 402653184}

pr1645v2EthpdpInPIfOutBandwidth OBJECT-TYPE
   SYNTAX      Integer32
   MAX-ACCESS  read-only
   STATUS      current
   DESCRIPTION
      "Path: ethernetPdp.performance.h2Performance.ifOutBandwidth

       unit name = bps
       formula = 8 * ; 8 /"
   ::= {pr1645v2EthpdpInPEntry 285212672}

pr1645v2EthpdpInPIfErrSec OBJECT-TYPE
   SYNTAX      Counter32
   MAX-ACCESS  read-only
   STATUS      current
   DESCRIPTION
      "Path: ethernetPdp.performance.h2Performance.ifErrSec

       32 bit unsigned wrappable counter."
   ::= {pr1645v2EthpdpInPEntry 251658240}


pr1645v2EthpdpH24InP OBJECT IDENTIFIER ::= {pr1645v2Ethpdp 308}

pr1645v2EthpdpH24InPSSCTable OBJECT-TYPE
   SYNTAX      SEQUENCE OF Pr1645v2EthpdpH24InPEntry
   MAX-ACCESS  not-accessible
   STATUS      current
   DESCRIPTION
      "h24IfInPerformance"
   ::= {pr1645v2EthpdpH24InP 1}

pr1645v2EthpdpH24InPEntry OBJECT-TYPE
   SYNTAX      Pr1645v2EthpdpH24InPEntry
   MAX-ACCESS  not-accessible
   STATUS      current
   DESCRIPTION
      ""
   INDEX      { pr1645v2EthpdpH24InPGlobalIx,
                pr1645v2EthpdpH24InPTableIx }
   ::= {pr1645v2EthpdpH24InPSSCTable 1}

Pr1645v2EthpdpH24InPEntry ::=
   SEQUENCE
      {
      pr1645v2EthpdpH24InPGlobalIx
         GlobalIndex,
      pr1645v2EthpdpH24InPTableIx
         TableIndex,
      pr1645v2EthpdpH24InPSysUpTime
         TimeTicks,
      pr1645v2EthpdpH24InPIfUpTime
         TimeTicks,
      pr1645v2EthpdpH24InPIfStatChanges
         Counter32,
      pr1645v2EthpdpH24InPIfInOctets
         Counter64,
      pr1645v2EthpdpH24InPIfInUCPkts
         Counter64,
      pr1645v2EthpdpH24InPIfInNUCPkts
         Counter64,
      pr1645v2EthpdpH24InPIfInBCPkts
         Counter64,
      pr1645v2EthpdpH24InPIfInMCPkts
         Counter64,
      pr1645v2EthpdpH24InPIfInDiscards
         Counter64,
      pr1645v2EthpdpH24InPIfInErrors
         Counter64,
      pr1645v2EthpdpH24InPIfInUnkwn
         Counter64,
      pr1645v2EthpdpH24InPInDropEx
         Counter64,
      pr1645v2EthpdpH24InPInDropNoMac
         Counter64,
      pr1645v2EthpdpH24InPInDropNUCast
         Counter64,
      pr1645v2EthpdpH24InPInDropFilter
         Counter64,
      pr1645v2EthpdpH24InPIfInBandwidth
         Integer32,
      pr1645v2EthpdpH24InPIfOutOctets
         Counter64,
      pr1645v2EthpdpH24InPIfOutUCPkts
         Counter64,
      pr1645v2EthpdpH24InPIfOutNUCPkts
         Counter64,
      pr1645v2EthpdpH24InPIfOutBCPkts
         Counter64,
      pr1645v2EthpdpH24InPIfOutMCPkts
         Counter64,
      pr1645v2EthpdpH24InPIfOutDiscards
         Counter64,
      pr1645v2EthpdpH24InPIfOutErrors
         Counter64,
      pr1645v2EthpdpH24InPOutDropEx
         Counter64,
      pr1645v2EthpdpH24InPOutDropNoArp
         Counter64,
      pr1645v2EthpdpH24InPOutDropFilter
         Counter64,
      pr1645v2EthpdpH24InPIfOutBandwidth
         Integer32,
      pr1645v2EthpdpH24InPIfErrSec
         Counter32
      }

pr1645v2EthpdpH24InPGlobalIx OBJECT-TYPE
   SYNTAX      GlobalIndex
   MAX-ACCESS  not-accessible
   STATUS      current
   DESCRIPTION
      "The value of the tlsCntTreeGlobalIndex of the MANAGED OBJECT."
   ::= {pr1645v2EthpdpH24InPEntry 10}

pr1645v2EthpdpH24InPTableIx OBJECT-TYPE
   SYNTAX      TableIndex
   MAX-ACCESS  not-accessible
   STATUS      current
   DESCRIPTION
      ""
   ::= {pr1645v2EthpdpH24InPEntry 11}

pr1645v2EthpdpH24InPSysUpTime OBJECT-TYPE
   SYNTAX      TimeTicks
   MAX-ACCESS  read-only
   STATUS      current
   DESCRIPTION
      "Path: ethernetPdp.performance.h24Performance.sysUpTime

       Time in centi-second."
   ::= {pr1645v2EthpdpH24InPEntry 16777216}

pr1645v2EthpdpH24InPIfUpTime OBJECT-TYPE
   SYNTAX      TimeTicks
   MAX-ACCESS  read-only
   STATUS      current
   DESCRIPTION
      "Path: ethernetPdp.performance.h24Performance.ifUpTime

       Time in centi-second."
   ::= {pr1645v2EthpdpH24InPEntry 33554432}

pr1645v2EthpdpH24InPIfStatChanges OBJECT-TYPE
   SYNTAX      Counter32
   MAX-ACCESS  read-only
   STATUS      current
   DESCRIPTION
      "Path: ethernetPdp.performance.h24Performance.ifStatusChanges

       32 bit unsigned wrappable counter."
   ::= {pr1645v2EthpdpH24InPEntry 50331648}

pr1645v2EthpdpH24InPIfInOctets OBJECT-TYPE
   SYNTAX      Counter64
   MAX-ACCESS  read-only
   STATUS      current
   DESCRIPTION
      "Path: ethernetPdp.performance.h24Performance.ifInOctets

       64 bit unsigned wrappable counter."
   ::= {pr1645v2EthpdpH24InPEntry 67108864}

pr1645v2EthpdpH24InPIfInUCPkts OBJECT-TYPE
   SYNTAX      Counter64
   MAX-ACCESS  read-only
   STATUS      current
   DESCRIPTION
      "Path: ethernetPdp.performance.h24Performance.ifInUcastPkts

       64 bit unsigned wrappable counter."
   ::= {pr1645v2EthpdpH24InPEntry 83886080}

pr1645v2EthpdpH24InPIfInNUCPkts OBJECT-TYPE
   SYNTAX      Counter64
   MAX-ACCESS  read-only
   STATUS      current
   DESCRIPTION
      "Path: ethernetPdp.performance.h24Performance.ifInNUcastPkts

       64 bit unsigned wrappable counter."
   ::= {pr1645v2EthpdpH24InPEntry 100663296}

pr1645v2EthpdpH24InPIfInBCPkts OBJECT-TYPE
   SYNTAX      Counter64
   MAX-ACCESS  read-only
   STATUS      current
   DESCRIPTION
      "Path: ethernetPdp.performance.h24Performance.ifInBcastPkts

       64 bit unsigned wrappable counter."
   ::= {pr1645v2EthpdpH24InPEntry 419430400}

pr1645v2EthpdpH24InPIfInMCPkts OBJECT-TYPE
   SYNTAX      Counter64
   MAX-ACCESS  read-only
   STATUS      current
   DESCRIPTION
      "Path: ethernetPdp.performance.h24Performance.ifInMcastPkts

       64 bit unsigned wrappable counter."
   ::= {pr1645v2EthpdpH24InPEntry 436207616}

pr1645v2EthpdpH24InPIfInDiscards OBJECT-TYPE
   SYNTAX      Counter64
   MAX-ACCESS  read-only
   STATUS      current
   DESCRIPTION
      "Path: ethernetPdp.performance.h24Performance.ifInDiscards

       64 bit unsigned wrappable counter."
   ::= {pr1645v2EthpdpH24InPEntry 117440512}

pr1645v2EthpdpH24InPIfInErrors OBJECT-TYPE
   SYNTAX      Counter64
   MAX-ACCESS  read-only
   STATUS      current
   DESCRIPTION
      "Path: ethernetPdp.performance.h24Performance.ifInErrors

       64 bit unsigned wrappable counter."
   ::= {pr1645v2EthpdpH24InPEntry 134217728}

pr1645v2EthpdpH24InPIfInUnkwn OBJECT-TYPE
   SYNTAX      Counter64
   MAX-ACCESS  read-only
   STATUS      current
   DESCRIPTION
      "Path: ethernetPdp.performance.h24Performance.ifInUnknownProtos

       64 bit unsigned wrappable counter."
   ::= {pr1645v2EthpdpH24InPEntry 150994944}

pr1645v2EthpdpH24InPInDropEx OBJECT-TYPE
   SYNTAX      Counter64
   MAX-ACCESS  read-only
   STATUS      current
   DESCRIPTION
      "Path: ethernetPdp.performance.h24Performance.ifInDropLevelExceeded

       64 bit unsigned wrappable counter."
   ::= {pr1645v2EthpdpH24InPEntry 335544320}

pr1645v2EthpdpH24InPInDropNoMac OBJECT-TYPE
   SYNTAX      Counter64
   MAX-ACCESS  read-only
   STATUS      current
   DESCRIPTION
      "Path: ethernetPdp.performance.h24Performance.fInDiscardsNoMacFit

       64 bit unsigned wrappable counter."
   ::= {pr1645v2EthpdpH24InPEntry 301989888}

pr1645v2EthpdpH24InPInDropNUCast OBJECT-TYPE
   SYNTAX      Counter64
   MAX-ACCESS  read-only
   STATUS      current
   DESCRIPTION
      "Path: ethernetPdp.performance.h24Performance.fInDiscardsNUCast

       64 bit unsigned wrappable counter."
   ::= {pr1645v2EthpdpH24InPEntry 318767104}

pr1645v2EthpdpH24InPInDropFilter OBJECT-TYPE
   SYNTAX      Counter64
   MAX-ACCESS  read-only
   STATUS      current
   DESCRIPTION
      "Path: ethernetPdp.performance.h24Performance.fInDiscardsFilter

       64 bit unsigned wrappable counter."
   ::= {pr1645v2EthpdpH24InPEntry 385875968}

pr1645v2EthpdpH24InPIfInBandwidth OBJECT-TYPE
   SYNTAX      Integer32
   MAX-ACCESS  read-only
   STATUS      current
   DESCRIPTION
      "Path: ethernetPdp.performance.h24Performance.ifInBandwidth

       unit name = bps
       formula = 8 * ; 8 /"
   ::= {pr1645v2EthpdpH24InPEntry 268435456}

pr1645v2EthpdpH24InPIfOutOctets OBJECT-TYPE
   SYNTAX      Counter64
   MAX-ACCESS  read-only
   STATUS      current
   DESCRIPTION
      "Path: ethernetPdp.performance.h24Performance.ifOutOctets

       64 bit unsigned wrappable counter."
   ::= {pr1645v2EthpdpH24InPEntry 167772160}

pr1645v2EthpdpH24InPIfOutUCPkts OBJECT-TYPE
   SYNTAX      Counter64
   MAX-ACCESS  read-only
   STATUS      current
   DESCRIPTION
      "Path: ethernetPdp.performance.h24Performance.ifOutUcastPkts

       64 bit unsigned wrappable counter."
   ::= {pr1645v2EthpdpH24InPEntry 184549376}

pr1645v2EthpdpH24InPIfOutNUCPkts OBJECT-TYPE
   SYNTAX      Counter64
   MAX-ACCESS  read-only
   STATUS      current
   DESCRIPTION
      "Path: ethernetPdp.performance.h24Performance.ifOutNUcastPkts

       64 bit unsigned wrappable counter."
   ::= {pr1645v2EthpdpH24InPEntry 201326592}

pr1645v2EthpdpH24InPIfOutBCPkts OBJECT-TYPE
   SYNTAX      Counter64
   MAX-ACCESS  read-only
   STATUS      current
   DESCRIPTION
      "Path: ethernetPdp.performance.h24Performance.ifOutBcastPkts

       64 bit unsigned wrappable counter."
   ::= {pr1645v2EthpdpH24InPEntry 452984832}

pr1645v2EthpdpH24InPIfOutMCPkts OBJECT-TYPE
   SYNTAX      Counter64
   MAX-ACCESS  read-only
   STATUS      current
   DESCRIPTION
      "Path: ethernetPdp.performance.h24Performance.ifOutMcastPkts

       64 bit unsigned wrappable counter."
   ::= {pr1645v2EthpdpH24InPEntry 469762048}

pr1645v2EthpdpH24InPIfOutDiscards OBJECT-TYPE
   SYNTAX      Counter64
   MAX-ACCESS  read-only
   STATUS      current
   DESCRIPTION
      "Path: ethernetPdp.performance.h24Performance.ifOutDiscards

       64 bit unsigned wrappable counter."
   ::= {pr1645v2EthpdpH24InPEntry 218103808}

pr1645v2EthpdpH24InPIfOutErrors OBJECT-TYPE
   SYNTAX      Counter64
   MAX-ACCESS  read-only
   STATUS      current
   DESCRIPTION
      "Path: ethernetPdp.performance.h24Performance.ifOutErrors

       64 bit unsigned wrappable counter."
   ::= {pr1645v2EthpdpH24InPEntry 234881024}

pr1645v2EthpdpH24InPOutDropEx OBJECT-TYPE
   SYNTAX      Counter64
   MAX-ACCESS  read-only
   STATUS      current
   DESCRIPTION
      "Path: ethernetPdp.performance.h24Performance.ifOutDropLevelExceeded

       64 bit unsigned wrappable counter."
   ::= {pr1645v2EthpdpH24InPEntry 352321536}

pr1645v2EthpdpH24InPOutDropNoArp OBJECT-TYPE
   SYNTAX      Counter64
   MAX-ACCESS  read-only
   STATUS      current
   DESCRIPTION
      "Path: ethernetPdp.performance.h24Performance.ifOutDiscardsNoArp

       64 bit unsigned wrappable counter."
   ::= {pr1645v2EthpdpH24InPEntry 369098752}

pr1645v2EthpdpH24InPOutDropFilter OBJECT-TYPE
   SYNTAX      Counter64
   MAX-ACCESS  read-only
   STATUS      current
   DESCRIPTION
      "Path: ethernetPdp.performance.h24Performance.ifOutDiscardsFilter

       64 bit unsigned wrappable counter."
   ::= {pr1645v2EthpdpH24InPEntry 402653184}

pr1645v2EthpdpH24InPIfOutBandwidth OBJECT-TYPE
   SYNTAX      Integer32
   MAX-ACCESS  read-only
   STATUS      current
   DESCRIPTION
      "Path: ethernetPdp.performance.h24Performance.ifOutBandwidth

       unit name = bps
       formula = 8 * ; 8 /"
   ::= {pr1645v2EthpdpH24InPEntry 285212672}

pr1645v2EthpdpH24InPIfErrSec OBJECT-TYPE
   SYNTAX      Counter32
   MAX-ACCESS  read-only
   STATUS      current
   DESCRIPTION
      "Path: ethernetPdp.performance.h24Performance.ifErrSec

       32 bit unsigned wrappable counter."
   ::= {pr1645v2EthpdpH24InPEntry 251658240}


pr1645v2EthpdpD7InP OBJECT IDENTIFIER ::= {pr1645v2Ethpdp 309}

pr1645v2EthpdpD7InPSSCTable OBJECT-TYPE
   SYNTAX      SEQUENCE OF Pr1645v2EthpdpD7InPEntry
   MAX-ACCESS  not-accessible
   STATUS      current
   DESCRIPTION
      "d7IfInPerformance"
   ::= {pr1645v2EthpdpD7InP 1}

pr1645v2EthpdpD7InPEntry OBJECT-TYPE
   SYNTAX      Pr1645v2EthpdpD7InPEntry
   MAX-ACCESS  not-accessible
   STATUS      current
   DESCRIPTION
      ""
   INDEX      { pr1645v2EthpdpD7InPGlobalIx,
                pr1645v2EthpdpD7InPTableIx }
   ::= {pr1645v2EthpdpD7InPSSCTable 1}

Pr1645v2EthpdpD7InPEntry ::=
   SEQUENCE
      {
      pr1645v2EthpdpD7InPGlobalIx
         GlobalIndex,
      pr1645v2EthpdpD7InPTableIx
         TableIndex,
      pr1645v2EthpdpD7InPSysUpTime
         TimeTicks,
      pr1645v2EthpdpD7InPIfUpTime
         TimeTicks,
      pr1645v2EthpdpD7InPIfStatChanges
         Counter32,
      pr1645v2EthpdpD7InPIfInOctets
         Counter64,
      pr1645v2EthpdpD7InPIfInUCPkts
         Counter64,
      pr1645v2EthpdpD7InPIfInNUCPkts
         Counter64,
      pr1645v2EthpdpD7InPIfInBCPkts
         Counter64,
      pr1645v2EthpdpD7InPIfInMCPkts
         Counter64,
      pr1645v2EthpdpD7InPIfInDiscards
         Counter64,
      pr1645v2EthpdpD7InPIfInErrors
         Counter64,
      pr1645v2EthpdpD7InPIfInUnkwn
         Counter64,
      pr1645v2EthpdpD7InPInDropEx
         Counter64,
      pr1645v2EthpdpD7InPInDropNoMac
         Counter64,
      pr1645v2EthpdpD7InPInDropNUCast
         Counter64,
      pr1645v2EthpdpD7InPInDropFilter
         Counter64,
      pr1645v2EthpdpD7InPIfInBandwidth
         Integer32,
      pr1645v2EthpdpD7InPIfOutOctets
         Counter64,
      pr1645v2EthpdpD7InPIfOutUCPkts
         Counter64,
      pr1645v2EthpdpD7InPIfOutNUCPkts
         Counter64,
      pr1645v2EthpdpD7InPIfOutBCPkts
         Counter64,
      pr1645v2EthpdpD7InPIfOutMCPkts
         Counter64,
      pr1645v2EthpdpD7InPIfOutDiscards
         Counter64,
      pr1645v2EthpdpD7InPIfOutErrors
         Counter64,
      pr1645v2EthpdpD7InPOutDropEx
         Counter64,
      pr1645v2EthpdpD7InPOutDropNoArp
         Counter64,
      pr1645v2EthpdpD7InPOutDropFilter
         Counter64,
      pr1645v2EthpdpD7InPIfOutBandwidth
         Integer32,
      pr1645v2EthpdpD7InPIfErrSec
         Counter32
      }

pr1645v2EthpdpD7InPGlobalIx OBJECT-TYPE
   SYNTAX      GlobalIndex
   MAX-ACCESS  not-accessible
   STATUS      current
   DESCRIPTION
      "The value of the tlsCntTreeGlobalIndex of the MANAGED OBJECT."
   ::= {pr1645v2EthpdpD7InPEntry 10}

pr1645v2EthpdpD7InPTableIx OBJECT-TYPE
   SYNTAX      TableIndex
   MAX-ACCESS  not-accessible
   STATUS      current
   DESCRIPTION
      ""
   ::= {pr1645v2EthpdpD7InPEntry 11}

pr1645v2EthpdpD7InPSysUpTime OBJECT-TYPE
   SYNTAX      TimeTicks
   MAX-ACCESS  read-only
   STATUS      current
   DESCRIPTION
      "Path: ethernetPdp.performance.d7Performance.sysUpTime

       Time in centi-second."
   ::= {pr1645v2EthpdpD7InPEntry 16777216}

pr1645v2EthpdpD7InPIfUpTime OBJECT-TYPE
   SYNTAX      TimeTicks
   MAX-ACCESS  read-only
   STATUS      current
   DESCRIPTION
      "Path: ethernetPdp.performance.d7Performance.ifUpTime

       Time in centi-second."
   ::= {pr1645v2EthpdpD7InPEntry 33554432}

pr1645v2EthpdpD7InPIfStatChanges OBJECT-TYPE
   SYNTAX      Counter32
   MAX-ACCESS  read-only
   STATUS      current
   DESCRIPTION
      "Path: ethernetPdp.performance.d7Performance.ifStatusChanges

       32 bit unsigned wrappable counter."
   ::= {pr1645v2EthpdpD7InPEntry 50331648}

pr1645v2EthpdpD7InPIfInOctets OBJECT-TYPE
   SYNTAX      Counter64
   MAX-ACCESS  read-only
   STATUS      current
   DESCRIPTION
      "Path: ethernetPdp.performance.d7Performance.ifInOctets

       64 bit unsigned wrappable counter."
   ::= {pr1645v2EthpdpD7InPEntry 67108864}

pr1645v2EthpdpD7InPIfInUCPkts OBJECT-TYPE
   SYNTAX      Counter64
   MAX-ACCESS  read-only
   STATUS      current
   DESCRIPTION
      "Path: ethernetPdp.performance.d7Performance.ifInUcastPkts

       64 bit unsigned wrappable counter."
   ::= {pr1645v2EthpdpD7InPEntry 83886080}

pr1645v2EthpdpD7InPIfInNUCPkts OBJECT-TYPE
   SYNTAX      Counter64
   MAX-ACCESS  read-only
   STATUS      current
   DESCRIPTION
      "Path: ethernetPdp.performance.d7Performance.ifInNUcastPkts

       64 bit unsigned wrappable counter."
   ::= {pr1645v2EthpdpD7InPEntry 100663296}

pr1645v2EthpdpD7InPIfInBCPkts OBJECT-TYPE
   SYNTAX      Counter64
   MAX-ACCESS  read-only
   STATUS      current
   DESCRIPTION
      "Path: ethernetPdp.performance.d7Performance.ifInBcastPkts

       64 bit unsigned wrappable counter."
   ::= {pr1645v2EthpdpD7InPEntry 419430400}

pr1645v2EthpdpD7InPIfInMCPkts OBJECT-TYPE
   SYNTAX      Counter64
   MAX-ACCESS  read-only
   STATUS      current
   DESCRIPTION
      "Path: ethernetPdp.performance.d7Performance.ifInMcastPkts

       64 bit unsigned wrappable counter."
   ::= {pr1645v2EthpdpD7InPEntry 436207616}

pr1645v2EthpdpD7InPIfInDiscards OBJECT-TYPE
   SYNTAX      Counter64
   MAX-ACCESS  read-only
   STATUS      current
   DESCRIPTION
      "Path: ethernetPdp.performance.d7Performance.ifInDiscards

       64 bit unsigned wrappable counter."
   ::= {pr1645v2EthpdpD7InPEntry 117440512}

pr1645v2EthpdpD7InPIfInErrors OBJECT-TYPE
   SYNTAX      Counter64
   MAX-ACCESS  read-only
   STATUS      current
   DESCRIPTION
      "Path: ethernetPdp.performance.d7Performance.ifInErrors

       64 bit unsigned wrappable counter."
   ::= {pr1645v2EthpdpD7InPEntry 134217728}

pr1645v2EthpdpD7InPIfInUnkwn OBJECT-TYPE
   SYNTAX      Counter64
   MAX-ACCESS  read-only
   STATUS      current
   DESCRIPTION
      "Path: ethernetPdp.performance.d7Performance.ifInUnknownProtos

       64 bit unsigned wrappable counter."
   ::= {pr1645v2EthpdpD7InPEntry 150994944}

pr1645v2EthpdpD7InPInDropEx OBJECT-TYPE
   SYNTAX      Counter64
   MAX-ACCESS  read-only
   STATUS      current
   DESCRIPTION
      "Path: ethernetPdp.performance.d7Performance.ifInDropLevelExceeded

       64 bit unsigned wrappable counter."
   ::= {pr1645v2EthpdpD7InPEntry 335544320}

pr1645v2EthpdpD7InPInDropNoMac OBJECT-TYPE
   SYNTAX      Counter64
   MAX-ACCESS  read-only
   STATUS      current
   DESCRIPTION
      "Path: ethernetPdp.performance.d7Performance.fInDiscardsNoMacFit

       64 bit unsigned wrappable counter."
   ::= {pr1645v2EthpdpD7InPEntry 301989888}

pr1645v2EthpdpD7InPInDropNUCast OBJECT-TYPE
   SYNTAX      Counter64
   MAX-ACCESS  read-only
   STATUS      current
   DESCRIPTION
      "Path: ethernetPdp.performance.d7Performance.fInDiscardsNUCast

       64 bit unsigned wrappable counter."
   ::= {pr1645v2EthpdpD7InPEntry 318767104}

pr1645v2EthpdpD7InPInDropFilter OBJECT-TYPE
   SYNTAX      Counter64
   MAX-ACCESS  read-only
   STATUS      current
   DESCRIPTION
      "Path: ethernetPdp.performance.d7Performance.fInDiscardsFilter

       64 bit unsigned wrappable counter."
   ::= {pr1645v2EthpdpD7InPEntry 385875968}

pr1645v2EthpdpD7InPIfInBandwidth OBJECT-TYPE
   SYNTAX      Integer32
   MAX-ACCESS  read-only
   STATUS      current
   DESCRIPTION
      "Path: ethernetPdp.performance.d7Performance.ifInBandwidth

       unit name = bps
       formula = 8 * ; 8 /"
   ::= {pr1645v2EthpdpD7InPEntry 268435456}

pr1645v2EthpdpD7InPIfOutOctets OBJECT-TYPE
   SYNTAX      Counter64
   MAX-ACCESS  read-only
   STATUS      current
   DESCRIPTION
      "Path: ethernetPdp.performance.d7Performance.ifOutOctets

       64 bit unsigned wrappable counter."
   ::= {pr1645v2EthpdpD7InPEntry 167772160}

pr1645v2EthpdpD7InPIfOutUCPkts OBJECT-TYPE
   SYNTAX      Counter64
   MAX-ACCESS  read-only
   STATUS      current
   DESCRIPTION
      "Path: ethernetPdp.performance.d7Performance.ifOutUcastPkts

       64 bit unsigned wrappable counter."
   ::= {pr1645v2EthpdpD7InPEntry 184549376}

pr1645v2EthpdpD7InPIfOutNUCPkts OBJECT-TYPE
   SYNTAX      Counter64
   MAX-ACCESS  read-only
   STATUS      current
   DESCRIPTION
      "Path: ethernetPdp.performance.d7Performance.ifOutNUcastPkts

       64 bit unsigned wrappable counter."
   ::= {pr1645v2EthpdpD7InPEntry 201326592}

pr1645v2EthpdpD7InPIfOutBCPkts OBJECT-TYPE
   SYNTAX      Counter64
   MAX-ACCESS  read-only
   STATUS      current
   DESCRIPTION
      "Path: ethernetPdp.performance.d7Performance.ifOutBcastPkts

       64 bit unsigned wrappable counter."
   ::= {pr1645v2EthpdpD7InPEntry 452984832}

pr1645v2EthpdpD7InPIfOutMCPkts OBJECT-TYPE
   SYNTAX      Counter64
   MAX-ACCESS  read-only
   STATUS      current
   DESCRIPTION
      "Path: ethernetPdp.performance.d7Performance.ifOutMcastPkts

       64 bit unsigned wrappable counter."
   ::= {pr1645v2EthpdpD7InPEntry 469762048}

pr1645v2EthpdpD7InPIfOutDiscards OBJECT-TYPE
   SYNTAX      Counter64
   MAX-ACCESS  read-only
   STATUS      current
   DESCRIPTION
      "Path: ethernetPdp.performance.d7Performance.ifOutDiscards

       64 bit unsigned wrappable counter."
   ::= {pr1645v2EthpdpD7InPEntry 218103808}

pr1645v2EthpdpD7InPIfOutErrors OBJECT-TYPE
   SYNTAX      Counter64
   MAX-ACCESS  read-only
   STATUS      current
   DESCRIPTION
      "Path: ethernetPdp.performance.d7Performance.ifOutErrors

       64 bit unsigned wrappable counter."
   ::= {pr1645v2EthpdpD7InPEntry 234881024}

pr1645v2EthpdpD7InPOutDropEx OBJECT-TYPE
   SYNTAX      Counter64
   MAX-ACCESS  read-only
   STATUS      current
   DESCRIPTION
      "Path: ethernetPdp.performance.d7Performance.ifOutDropLevelExceeded

       64 bit unsigned wrappable counter."
   ::= {pr1645v2EthpdpD7InPEntry 352321536}

pr1645v2EthpdpD7InPOutDropNoArp OBJECT-TYPE
   SYNTAX      Counter64
   MAX-ACCESS  read-only
   STATUS      current
   DESCRIPTION
      "Path: ethernetPdp.performance.d7Performance.ifOutDiscardsNoArp

       64 bit unsigned wrappable counter."
   ::= {pr1645v2EthpdpD7InPEntry 369098752}

pr1645v2EthpdpD7InPOutDropFilter OBJECT-TYPE
   SYNTAX      Counter64
   MAX-ACCESS  read-only
   STATUS      current
   DESCRIPTION
      "Path: ethernetPdp.performance.d7Performance.ifOutDiscardsFilter

       64 bit unsigned wrappable counter."
   ::= {pr1645v2EthpdpD7InPEntry 402653184}

pr1645v2EthpdpD7InPIfOutBandwidth OBJECT-TYPE
   SYNTAX      Integer32
   MAX-ACCESS  read-only
   STATUS      current
   DESCRIPTION
      "Path: ethernetPdp.performance.d7Performance.ifOutBandwidth

       unit name = bps
       formula = 8 * ; 8 /"
   ::= {pr1645v2EthpdpD7InPEntry 285212672}

pr1645v2EthpdpD7InPIfErrSec OBJECT-TYPE
   SYNTAX      Counter32
   MAX-ACCESS  read-only
   STATUS      current
   DESCRIPTION
      "Path: ethernetPdp.performance.d7Performance.ifErrSec

       32 bit unsigned wrappable counter."
   ::= {pr1645v2EthpdpD7InPEntry 251658240}



ar1645v2Ethpdp OBJECT IDENTIFIER ::= {r1645v2Ethpdp 16}


ar1645v2EthpdpClearCounters OBJECT IDENTIFIER ::= {ar1645v2Ethpdp 263}

ar1645v2EthpdpClearCountersTable OBJECT-TYPE
   SYNTAX      SEQUENCE OF Ar1645v2EthpdpClearCountersEntry
   MAX-ACCESS  not-accessible
   STATUS      current
   DESCRIPTION
      "reset counters"
   ::= {ar1645v2EthpdpClearCounters 1}

ar1645v2EthpdpClearCountersEntry OBJECT-TYPE
   SYNTAX      Ar1645v2EthpdpClearCountersEntry
   MAX-ACCESS  not-accessible
   STATUS      current
   DESCRIPTION
      ""
   INDEX      { ar1645v2EthpdpClearCountersGlobalIx }
   ::= {ar1645v2EthpdpClearCountersTable 1}

Ar1645v2EthpdpClearCountersEntry ::=
   SEQUENCE
      {
      ar1645v2EthpdpClearCountersGlobalIx
         GlobalIndex,
      ar1645v2EthpdpClearCountersValue
         Integer32
      }

ar1645v2EthpdpClearCountersGlobalIx OBJECT-TYPE
   SYNTAX      GlobalIndex
   MAX-ACCESS  not-accessible
   STATUS      current
   DESCRIPTION
      "The value of the tlsCntTreeGlobalIndex of the MANAGED OBJECT."
   ::= {ar1645v2EthpdpClearCountersEntry 10}

ar1645v2EthpdpClearCountersValue OBJECT-TYPE
   SYNTAX      Integer32
   MAX-ACCESS  read-write
   STATUS      current
   DESCRIPTION
      "Path: ethernetPdp.actions.clearCounters"
   ::= {ar1645v2EthpdpClearCountersEntry 2147483648}



END
