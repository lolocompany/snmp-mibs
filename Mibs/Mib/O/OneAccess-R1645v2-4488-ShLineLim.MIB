OneAccess-R1645v2-4488-ShLineLim DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2ShLineLim OBJECT IDENTIFIER ::= {r1645Rootv2 4488}

r1645v2ShLineLimMOProp OBJECT-TYPE
   SYNTAX      SEQUENCE OF R1645v2ShLineLimMOPropEntry
   MAX-ACCESS  not-accessible
   STATUS      current
   DESCRIPTION
      ""
   ::= {r1645v2ShLineLim 1}

r1645v2ShLineLimMOPropEntry OBJECT-TYPE
   SYNTAX      R1645v2ShLineLimMOPropEntry
   MAX-ACCESS  not-accessible
   STATUS      current
   DESCRIPTION
      ""
   INDEX      { r1645v2ShLineLimMOPropGlobalIx }
   ::= {r1645v2ShLineLimMOProp 1}

R1645v2ShLineLimMOPropEntry ::=
   SEQUENCE
      {
      r1645v2ShLineLimMOPropPath
         ContainmentPath,
      r1645v2ShLineLimMOPropRev
         ObjectRevision,
      r1645v2ShLineLimMOPropGlobalIx
         GlobalIndex
      }

r1645v2ShLineLimMOPropPath OBJECT-TYPE
   SYNTAX      ContainmentPath
   MAX-ACCESS  read-only
   STATUS      current
   DESCRIPTION
      "Textual description of the containment tree from the instance of
       the root object down to the instance of the current object."
   ::= {r1645v2ShLineLimMOPropEntry 3}

r1645v2ShLineLimMOPropRev OBJECT-TYPE
   SYNTAX      ObjectRevision
   MAX-ACCESS  read-only
   STATUS      current
   DESCRIPTION
      "This value corresponds with the revision of the MANAGED OBJECT."
   ::= {r1645v2ShLineLimMOPropEntry 4}

r1645v2ShLineLimMOPropGlobalIx OBJECT-TYPE
   SYNTAX      GlobalIndex
   MAX-ACCESS  read-only
   STATUS      current
   DESCRIPTION
      "The value of the tlsCntTreeGlobalIndex of the MANAGED OBJECT."
   ::= {r1645v2ShLineLimMOPropEntry 10}



sr1645v2ShLineLim OBJECT IDENTIFIER ::= {r1645v2ShLineLim 14}


sr1645v2ShLineLimIfDescr OBJECT IDENTIFIER ::= {sr1645v2ShLineLim 101}

sr1645v2ShLineLimIfDescrTable OBJECT-TYPE
   SYNTAX      SEQUENCE OF Sr1645v2ShLineLimIfDescrEntry
   MAX-ACCESS  not-accessible
   STATUS      current
   DESCRIPTION
      "ifDescr"
   ::= {sr1645v2ShLineLimIfDescr 1}

sr1645v2ShLineLimIfDescrEntry OBJECT-TYPE
   SYNTAX      Sr1645v2ShLineLimIfDescrEntry
   MAX-ACCESS  not-accessible
   STATUS      current
   DESCRIPTION
      ""
   INDEX      { sr1645v2ShLineLimIfDescrGlobalIx }
   ::= {sr1645v2ShLineLimIfDescrTable 1}

Sr1645v2ShLineLimIfDescrEntry ::=
   SEQUENCE
      {
      sr1645v2ShLineLimIfDescrGlobalIx
         GlobalIndex,
      sr1645v2ShLineLimIfDescrValue
         DisplayString
      }

sr1645v2ShLineLimIfDescrGlobalIx OBJECT-TYPE
   SYNTAX      GlobalIndex
   MAX-ACCESS  not-accessible
   STATUS      current
   DESCRIPTION
      "The value of the tlsCntTreeGlobalIndex of the MANAGED OBJECT."
   ::= {sr1645v2ShLineLimIfDescrEntry 10}

sr1645v2ShLineLimIfDescrValue OBJECT-TYPE
   SYNTAX      DisplayString
   MAX-ACCESS  read-only
   STATUS      current
   DESCRIPTION
      "Path: line.status.ifDescr"
   ::= {sr1645v2ShLineLimIfDescrEntry 2147483648}


sr1645v2ShLineLimIfType OBJECT IDENTIFIER ::= {sr1645v2ShLineLim 102}

sr1645v2ShLineLimIfTypeTable OBJECT-TYPE
   SYNTAX      SEQUENCE OF Sr1645v2ShLineLimIfTypeEntry
   MAX-ACCESS  not-accessible
   STATUS      current
   DESCRIPTION
      "ifType"
   ::= {sr1645v2ShLineLimIfType 1}

sr1645v2ShLineLimIfTypeEntry OBJECT-TYPE
   SYNTAX      Sr1645v2ShLineLimIfTypeEntry
   MAX-ACCESS  not-accessible
   STATUS      current
   DESCRIPTION
      ""
   INDEX      { sr1645v2ShLineLimIfTypeGlobalIx }
   ::= {sr1645v2ShLineLimIfTypeTable 1}

Sr1645v2ShLineLimIfTypeEntry ::=
   SEQUENCE
      {
      sr1645v2ShLineLimIfTypeGlobalIx
         GlobalIndex,
      sr1645v2ShLineLimIfTypeValue
         INTEGER
      }

sr1645v2ShLineLimIfTypeGlobalIx OBJECT-TYPE
   SYNTAX      GlobalIndex
   MAX-ACCESS  not-accessible
   STATUS      current
   DESCRIPTION
      "The value of the tlsCntTreeGlobalIndex of the MANAGED OBJECT."
   ::= {sr1645v2ShLineLimIfTypeEntry 10}

sr1645v2ShLineLimIfTypeValue OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: line.status.ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1645v2ShLineLimIfTypeEntry 2147483648}


sr1645v2ShLineLimIfSpeed OBJECT IDENTIFIER ::= {sr1645v2ShLineLim 104}

sr1645v2ShLineLimIfSpeedTable OBJECT-TYPE
   SYNTAX      SEQUENCE OF Sr1645v2ShLineLimIfSpeedEntry
   MAX-ACCESS  not-accessible
   STATUS      current
   DESCRIPTION
      "ifSpeed"
   ::= {sr1645v2ShLineLimIfSpeed 1}

sr1645v2ShLineLimIfSpeedEntry OBJECT-TYPE
   SYNTAX      Sr1645v2ShLineLimIfSpeedEntry
   MAX-ACCESS  not-accessible
   STATUS      current
   DESCRIPTION
      ""
   INDEX      { sr1645v2ShLineLimIfSpeedGlobalIx }
   ::= {sr1645v2ShLineLimIfSpeedTable 1}

Sr1645v2ShLineLimIfSpeedEntry ::=
   SEQUENCE
      {
      sr1645v2ShLineLimIfSpeedGlobalIx
         GlobalIndex,
      sr1645v2ShLineLimIfSpeedValue
         Gauge32
      }

sr1645v2ShLineLimIfSpeedGlobalIx OBJECT-TYPE
   SYNTAX      GlobalIndex
   MAX-ACCESS  not-accessible
   STATUS      current
   DESCRIPTION
      "The value of the tlsCntTreeGlobalIndex of the MANAGED OBJECT."
   ::= {sr1645v2ShLineLimIfSpeedEntry 10}

sr1645v2ShLineLimIfSpeedValue OBJECT-TYPE
   SYNTAX      Gauge32
   MAX-ACCESS  read-only
   STATUS      current
   DESCRIPTION
      "Path: line.status.ifSpeed

       32 bit unsigned gauge value."
   ::= {sr1645v2ShLineLimIfSpeedEntry 2147483648}


sr1645v2ShLineLimIfOperStatus OBJECT IDENTIFIER ::= {sr1645v2ShLineLim 107}

sr1645v2ShLineLimIfOperStatusTable OBJECT-TYPE
   SYNTAX      SEQUENCE OF Sr1645v2ShLineLimIfOperStatusEntry
   MAX-ACCESS  not-accessible
   STATUS      current
   DESCRIPTION
      "ifOperStatus"
   ::= {sr1645v2ShLineLimIfOperStatus 1}

sr1645v2ShLineLimIfOperStatusEntry OBJECT-TYPE
   SYNTAX      Sr1645v2ShLineLimIfOperStatusEntry
   MAX-ACCESS  not-accessible
   STATUS      current
   DESCRIPTION
      ""
   INDEX      { sr1645v2ShLineLimIfOperStatusGlobalIx }
   ::= {sr1645v2ShLineLimIfOperStatusTable 1}

Sr1645v2ShLineLimIfOperStatusEntry ::=
   SEQUENCE
      {
      sr1645v2ShLineLimIfOperStatusGlobalIx
         GlobalIndex,
      sr1645v2ShLineLimIfOperStatusValue
         INTEGER
      }

sr1645v2ShLineLimIfOperStatusGlobalIx OBJECT-TYPE
   SYNTAX      GlobalIndex
   MAX-ACCESS  not-accessible
   STATUS      current
   DESCRIPTION
      "The value of the tlsCntTreeGlobalIndex of the MANAGED OBJECT."
   ::= {sr1645v2ShLineLimIfOperStatusEntry 10}

sr1645v2ShLineLimIfOperStatusValue OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: line.status.ifOperStatus

       Possibilities:
               up   (1)
               down   (2)
               testing   (3)
               unknown   (4)
               dormant   (5)
               notPresent   (6)
               lowerLayerDown   (7)"
   ::= {sr1645v2ShLineLimIfOperStatusEntry 2147483648}


sr1645v2ShLineLimMinLpSpeed OBJECT IDENTIFIER ::= {sr1645v2ShLineLim 91}

sr1645v2ShLineLimMinLpSpeedTable OBJECT-TYPE
   SYNTAX      SEQUENCE OF Sr1645v2ShLineLimMinLpSpeedEntry
   MAX-ACCESS  not-accessible
   STATUS      current
   DESCRIPTION
      "line pair speed status"
   ::= {sr1645v2ShLineLimMinLpSpeed 1}

sr1645v2ShLineLimMinLpSpeedEntry OBJECT-TYPE
   SYNTAX      Sr1645v2ShLineLimMinLpSpeedEntry
   MAX-ACCESS  not-accessible
   STATUS      current
   DESCRIPTION
      ""
   INDEX      { sr1645v2ShLineLimMinLpSpeedGlobalIx }
   ::= {sr1645v2ShLineLimMinLpSpeedTable 1}

Sr1645v2ShLineLimMinLpSpeedEntry ::=
   SEQUENCE
      {
      sr1645v2ShLineLimMinLpSpeedGlobalIx
         GlobalIndex,
      sr1645v2ShLineLimMinLpSpeedValue
         Gauge32
      }

sr1645v2ShLineLimMinLpSpeedGlobalIx OBJECT-TYPE
   SYNTAX      GlobalIndex
   MAX-ACCESS  not-accessible
   STATUS      current
   DESCRIPTION
      "The value of the tlsCntTreeGlobalIndex of the MANAGED OBJECT."
   ::= {sr1645v2ShLineLimMinLpSpeedEntry 10}

sr1645v2ShLineLimMinLpSpeedValue OBJECT-TYPE
   SYNTAX      Gauge32
   MAX-ACCESS  read-only
   STATUS      current
   DESCRIPTION
      "Path: line.status.minLinePairSpeed

       32 bit unsigned gauge value."
   ::= {sr1645v2ShLineLimMinLpSpeedEntry 2147483648}


sr1645v2ShLineLimMaxLpSpeed OBJECT IDENTIFIER ::= {sr1645v2ShLineLim 92}

sr1645v2ShLineLimMaxLpSpeedTable OBJECT-TYPE
   SYNTAX      SEQUENCE OF Sr1645v2ShLineLimMaxLpSpeedEntry
   MAX-ACCESS  not-accessible
   STATUS      current
   DESCRIPTION
      "line pair speed status"
   ::= {sr1645v2ShLineLimMaxLpSpeed 1}

sr1645v2ShLineLimMaxLpSpeedEntry OBJECT-TYPE
   SYNTAX      Sr1645v2ShLineLimMaxLpSpeedEntry
   MAX-ACCESS  not-accessible
   STATUS      current
   DESCRIPTION
      ""
   INDEX      { sr1645v2ShLineLimMaxLpSpeedGlobalIx }
   ::= {sr1645v2ShLineLimMaxLpSpeedTable 1}

Sr1645v2ShLineLimMaxLpSpeedEntry ::=
   SEQUENCE
      {
      sr1645v2ShLineLimMaxLpSpeedGlobalIx
         GlobalIndex,
      sr1645v2ShLineLimMaxLpSpeedValue
         Gauge32
      }

sr1645v2ShLineLimMaxLpSpeedGlobalIx OBJECT-TYPE
   SYNTAX      GlobalIndex
   MAX-ACCESS  not-accessible
   STATUS      current
   DESCRIPTION
      "The value of the tlsCntTreeGlobalIndex of the MANAGED OBJECT."
   ::= {sr1645v2ShLineLimMaxLpSpeedEntry 10}

sr1645v2ShLineLimMaxLpSpeedValue OBJECT-TYPE
   SYNTAX      Gauge32
   MAX-ACCESS  read-only
   STATUS      current
   DESCRIPTION
      "Path: line.status.maxLinePairSpeed

       32 bit unsigned gauge value."
   ::= {sr1645v2ShLineLimMaxLpSpeedEntry 2147483648}


sr1645v2ShLineLimEocAlThr OBJECT IDENTIFIER ::= {sr1645v2ShLineLim 130}

sr1645v2ShLineLimEocAlThrSSCTable OBJECT-TYPE
   SYNTAX      SEQUENCE OF Sr1645v2ShLineLimEocAlThrEntry
   MAX-ACCESS  not-accessible
   STATUS      current
   DESCRIPTION
      "on threshold values transmittted by the eoc channel"
   ::= {sr1645v2ShLineLimEocAlThr 1}

sr1645v2ShLineLimEocAlThrEntry OBJECT-TYPE
   SYNTAX      Sr1645v2ShLineLimEocAlThrEntry
   MAX-ACCESS  not-accessible
   STATUS      current
   DESCRIPTION
      ""
   INDEX      { sr1645v2ShLineLimEocAlThrGlobalIx }
   ::= {sr1645v2ShLineLimEocAlThrSSCTable 1}

Sr1645v2ShLineLimEocAlThrEntry ::=
   SEQUENCE
      {
      sr1645v2ShLineLimEocAlThrGlobalIx
         GlobalIndex,
      sr1645v2ShLineLimEocAlThrLineAtt
         Integer32,
      sr1645v2ShLineLimEocAlThrNoiseMargin
         Integer32
      }

sr1645v2ShLineLimEocAlThrGlobalIx OBJECT-TYPE
   SYNTAX      GlobalIndex
   MAX-ACCESS  not-accessible
   STATUS      current
   DESCRIPTION
      "The value of the tlsCntTreeGlobalIndex of the MANAGED OBJECT."
   ::= {sr1645v2ShLineLimEocAlThrEntry 10}

sr1645v2ShLineLimEocAlThrLineAtt OBJECT-TYPE
   SYNTAX      Integer32
   MAX-ACCESS  read-only
   STATUS      current
   DESCRIPTION
      "Path: line.status.eocAlarmThresholds.lineAttenuation

       unit name = dB
       formula = 10 / ; 10 *"
   ::= {sr1645v2ShLineLimEocAlThrEntry 16777216}

sr1645v2ShLineLimEocAlThrNoiseMargin OBJECT-TYPE
   SYNTAX      Integer32
   MAX-ACCESS  read-only
   STATUS      current
   DESCRIPTION
      "Path: line.status.eocAlarmThresholds.noiseMargin

       unit name = dB
       formula = 10 / ; 10 *"
   ::= {sr1645v2ShLineLimEocAlThrEntry 33554432}


sr1645v2ShLineLimSnmpIndex OBJECT IDENTIFIER ::= {sr1645v2ShLineLim 269}

sr1645v2ShLineLimSnmpIndexTable OBJECT-TYPE
   SYNTAX      SEQUENCE OF Sr1645v2ShLineLimSnmpIndexEntry
   MAX-ACCESS  not-accessible
   STATUS      current
   DESCRIPTION
      "SNMP index assigned to this object"
   ::= {sr1645v2ShLineLimSnmpIndex 1}

sr1645v2ShLineLimSnmpIndexEntry OBJECT-TYPE
   SYNTAX      Sr1645v2ShLineLimSnmpIndexEntry
   MAX-ACCESS  not-accessible
   STATUS      current
   DESCRIPTION
      ""
   INDEX      { sr1645v2ShLineLimSnmpIndexGlobalIx }
   ::= {sr1645v2ShLineLimSnmpIndexTable 1}

Sr1645v2ShLineLimSnmpIndexEntry ::=
   SEQUENCE
      {
      sr1645v2ShLineLimSnmpIndexGlobalIx
         GlobalIndex,
      sr1645v2ShLineLimSnmpIndexValue
         Integer32
      }

sr1645v2ShLineLimSnmpIndexGlobalIx OBJECT-TYPE
   SYNTAX      GlobalIndex
   MAX-ACCESS  not-accessible
   STATUS      current
   DESCRIPTION
      "The value of the tlsCntTreeGlobalIndex of the MANAGED OBJECT."
   ::= {sr1645v2ShLineLimSnmpIndexEntry 10}

sr1645v2ShLineLimSnmpIndexValue OBJECT-TYPE
   SYNTAX      Integer32
   MAX-ACCESS  read-only
   STATUS      current
   DESCRIPTION
      "Path: line.status.snmpIndex"
   ::= {sr1645v2ShLineLimSnmpIndexEntry 2147483648}


sr1645v2ShLineLimRegion OBJECT IDENTIFIER ::= {sr1645v2ShLineLim 80}

sr1645v2ShLineLimRegionTable OBJECT-TYPE
   SYNTAX      SEQUENCE OF Sr1645v2ShLineLimRegionEntry
   MAX-ACCESS  not-accessible
   STATUS      current
   DESCRIPTION
      "Region Status"
   ::= {sr1645v2ShLineLimRegion 1}

sr1645v2ShLineLimRegionEntry OBJECT-TYPE
   SYNTAX      Sr1645v2ShLineLimRegionEntry
   MAX-ACCESS  not-accessible
   STATUS      current
   DESCRIPTION
      ""
   INDEX      { sr1645v2ShLineLimRegionGlobalIx }
   ::= {sr1645v2ShLineLimRegionTable 1}

Sr1645v2ShLineLimRegionEntry ::=
   SEQUENCE
      {
      sr1645v2ShLineLimRegionGlobalIx
         GlobalIndex,
      sr1645v2ShLineLimRegionValue
         INTEGER
      }

sr1645v2ShLineLimRegionGlobalIx OBJECT-TYPE
   SYNTAX      GlobalIndex
   MAX-ACCESS  not-accessible
   STATUS      current
   DESCRIPTION
      "The value of the tlsCntTreeGlobalIndex of the MANAGED OBJECT."
   ::= {sr1645v2ShLineLimRegionEntry 10}

sr1645v2ShLineLimRegionValue OBJECT-TYPE
   SYNTAX      INTEGER
               {
               annexAuF (1),
               annexBuG (2),
               auto (3)
               }
   MAX-ACCESS  read-only
   STATUS      current
   DESCRIPTION
      "Path: line.status.region

       Possibilities:
               annexA_F   (1)
               annexB_G   (2)
               auto   (3)"
   ::= {sr1645v2ShLineLimRegionEntry 2147483648}


sr1645v2ShLineLimFramerType OBJECT IDENTIFIER ::= {sr1645v2ShLineLim 93}

sr1645v2ShLineLimFramerTypeTable OBJECT-TYPE
   SYNTAX      SEQUENCE OF Sr1645v2ShLineLimFramerTypeEntry
   MAX-ACCESS  not-accessible
   STATUS      current
   DESCRIPTION
      "Framer Type status"
   ::= {sr1645v2ShLineLimFramerType 1}

sr1645v2ShLineLimFramerTypeEntry OBJECT-TYPE
   SYNTAX      Sr1645v2ShLineLimFramerTypeEntry
   MAX-ACCESS  not-accessible
   STATUS      current
   DESCRIPTION
      ""
   INDEX      { sr1645v2ShLineLimFramerTypeGlobalIx }
   ::= {sr1645v2ShLineLimFramerTypeTable 1}

Sr1645v2ShLineLimFramerTypeEntry ::=
   SEQUENCE
      {
      sr1645v2ShLineLimFramerTypeGlobalIx
         GlobalIndex,
      sr1645v2ShLineLimFramerTypeValue
         INTEGER
      }

sr1645v2ShLineLimFramerTypeGlobalIx OBJECT-TYPE
   SYNTAX      GlobalIndex
   MAX-ACCESS  not-accessible
   STATUS      current
   DESCRIPTION
      "The value of the tlsCntTreeGlobalIndex of the MANAGED OBJECT."
   ::= {sr1645v2ShLineLimFramerTypeEntry 10}

sr1645v2ShLineLimFramerTypeValue OBJECT-TYPE
   SYNTAX      INTEGER
               {
               efm (5),
               atm (6)
               }
   MAX-ACCESS  read-only
   STATUS      current
   DESCRIPTION
      "Path: line.status.framerType

       Possibilities:
               efm   (5)
               atm   (6)"
   ::= {sr1645v2ShLineLimFramerTypeEntry 2147483648}


sr1645v2ShLineLimWireMode OBJECT IDENTIFIER ::= {sr1645v2ShLineLim 411}

sr1645v2ShLineLimWireModeTable OBJECT-TYPE
   SYNTAX      SEQUENCE OF Sr1645v2ShLineLimWireModeEntry
   MAX-ACCESS  not-accessible
   STATUS      current
   DESCRIPTION
      ""
   ::= {sr1645v2ShLineLimWireMode 1}

sr1645v2ShLineLimWireModeEntry OBJECT-TYPE
   SYNTAX      Sr1645v2ShLineLimWireModeEntry
   MAX-ACCESS  not-accessible
   STATUS      current
   DESCRIPTION
      ""
   INDEX      { sr1645v2ShLineLimWireModeGlobalIx }
   ::= {sr1645v2ShLineLimWireModeTable 1}

Sr1645v2ShLineLimWireModeEntry ::=
   SEQUENCE
      {
      sr1645v2ShLineLimWireModeGlobalIx
         GlobalIndex,
      sr1645v2ShLineLimWireModeValue
         INTEGER
      }

sr1645v2ShLineLimWireModeGlobalIx OBJECT-TYPE
   SYNTAX      GlobalIndex
   MAX-ACCESS  not-accessible
   STATUS      current
   DESCRIPTION
      "The value of the tlsCntTreeGlobalIndex of the MANAGED OBJECT."
   ::= {sr1645v2ShLineLimWireModeEntry 10}

sr1645v2ShLineLimWireModeValue OBJECT-TYPE
   SYNTAX      INTEGER
               {
               singlePair (1),
               multiPair (2)
               }
   MAX-ACCESS  read-only
   STATUS      current
   DESCRIPTION
      "Path: line.status.wireMode

       Possibilities:
               singlePair   (1)
               multiPair   (2)"
   ::= {sr1645v2ShLineLimWireModeEntry 2147483648}


sr1645v2ShLineLimNrOfActivePairs OBJECT IDENTIFIER ::= {sr1645v2ShLineLim 413}

sr1645v2ShLineLimNrOfActivePairsTable OBJECT-TYPE
   SYNTAX      SEQUENCE OF Sr1645v2ShLineLimNrOfActivePairsEntry
   MAX-ACCESS  not-accessible
   STATUS      current
   DESCRIPTION
      ""
   ::= {sr1645v2ShLineLimNrOfActivePairs 1}

sr1645v2ShLineLimNrOfActivePairsEntry OBJECT-TYPE
   SYNTAX      Sr1645v2ShLineLimNrOfActivePairsEntry
   MAX-ACCESS  not-accessible
   STATUS      current
   DESCRIPTION
      ""
   INDEX      { sr1645v2ShLineLimNrOfActivePairsGlobalIx }
   ::= {sr1645v2ShLineLimNrOfActivePairsTable 1}

Sr1645v2ShLineLimNrOfActivePairsEntry ::=
   SEQUENCE
      {
      sr1645v2ShLineLimNrOfActivePairsGlobalIx
         GlobalIndex,
      sr1645v2ShLineLimNrOfActivePairsValue
         Integer32
      }

sr1645v2ShLineLimNrOfActivePairsGlobalIx OBJECT-TYPE
   SYNTAX      GlobalIndex
   MAX-ACCESS  not-accessible
   STATUS      current
   DESCRIPTION
      "The value of the tlsCntTreeGlobalIndex of the MANAGED OBJECT."
   ::= {sr1645v2ShLineLimNrOfActivePairsEntry 10}

sr1645v2ShLineLimNrOfActivePairsValue OBJECT-TYPE
   SYNTAX      Integer32
   MAX-ACCESS  read-only
   STATUS      current
   DESCRIPTION
      "Path: line.status.nrOfActivePairs"
   ::= {sr1645v2ShLineLimNrOfActivePairsEntry 2147483648}


sr1645v2ShLineLimPairOrder OBJECT IDENTIFIER ::= {sr1645v2ShLineLim 414}

sr1645v2ShLineLimPairOrderSSCTable OBJECT-TYPE
   SYNTAX      SEQUENCE OF Sr1645v2ShLineLimPairOrderEntry
   MAX-ACCESS  not-accessible
   STATUS      current
   DESCRIPTION
      ""
   ::= {sr1645v2ShLineLimPairOrder 1}

sr1645v2ShLineLimPairOrderEntry OBJECT-TYPE
   SYNTAX      Sr1645v2ShLineLimPairOrderEntry
   MAX-ACCESS  not-accessible
   STATUS      current
   DESCRIPTION
      ""
   INDEX      { sr1645v2ShLineLimPairOrderGlobalIx }
   ::= {sr1645v2ShLineLimPairOrderSSCTable 1}

Sr1645v2ShLineLimPairOrderEntry ::=
   SEQUENCE
      {
      sr1645v2ShLineLimPairOrderGlobalIx
         GlobalIndex,
      sr1645v2ShLineLimPairOrderMaster
         INTEGER,
      sr1645v2ShLineLimPairOrderSlave1
         INTEGER,
      sr1645v2ShLineLimPairOrderSlave2
         INTEGER,
      sr1645v2ShLineLimPairOrderSlave3
         INTEGER
      }

sr1645v2ShLineLimPairOrderGlobalIx OBJECT-TYPE
   SYNTAX      GlobalIndex
   MAX-ACCESS  not-accessible
   STATUS      current
   DESCRIPTION
      "The value of the tlsCntTreeGlobalIndex of the MANAGED OBJECT."
   ::= {sr1645v2ShLineLimPairOrderEntry 10}

sr1645v2ShLineLimPairOrderMaster OBJECT-TYPE
   SYNTAX      INTEGER
               {
               slOPTg (0),
               linePair1 (1),
               linePair2 (2),
               linePair3 (3),
               linePair4 (4)
               }
   MAX-ACCESS  read-only
   STATUS      current
   DESCRIPTION
      "Path: line.status.pairOrder.master

       Possibilities:
               <OPT>   (0)
               linePair[1]   (1)
               linePair[2]   (2)
               linePair[3]   (3)
               linePair[4]   (4)"
   ::= {sr1645v2ShLineLimPairOrderEntry 16777216}

sr1645v2ShLineLimPairOrderSlave1 OBJECT-TYPE
   SYNTAX      INTEGER
               {
               slOPTg (0),
               linePair1 (1),
               linePair2 (2),
               linePair3 (3),
               linePair4 (4)
               }
   MAX-ACCESS  read-only
   STATUS      current
   DESCRIPTION
      "Path: line.status.pairOrder.slave1

       Possibilities:
               <OPT>   (0)
               linePair[1]   (1)
               linePair[2]   (2)
               linePair[3]   (3)
               linePair[4]   (4)"
   ::= {sr1645v2ShLineLimPairOrderEntry 33554432}

sr1645v2ShLineLimPairOrderSlave2 OBJECT-TYPE
   SYNTAX      INTEGER
               {
               slOPTg (0),
               linePair1 (1),
               linePair2 (2),
               linePair3 (3),
               linePair4 (4)
               }
   MAX-ACCESS  read-only
   STATUS      current
   DESCRIPTION
      "Path: line.status.pairOrder.slave2

       Possibilities:
               <OPT>   (0)
               linePair[1]   (1)
               linePair[2]   (2)
               linePair[3]   (3)
               linePair[4]   (4)"
   ::= {sr1645v2ShLineLimPairOrderEntry 50331648}

sr1645v2ShLineLimPairOrderSlave3 OBJECT-TYPE
   SYNTAX      INTEGER
               {
               slOPTg (0),
               linePair1 (1),
               linePair2 (2),
               linePair3 (3),
               linePair4 (4)
               }
   MAX-ACCESS  read-only
   STATUS      current
   DESCRIPTION
      "Path: line.status.pairOrder.slave3

       Possibilities:
               <OPT>   (0)
               linePair[1]   (1)
               linePair[2]   (2)
               linePair[3]   (3)
               linePair[4]   (4)"
   ::= {sr1645v2ShLineLimPairOrderEntry 67108864}


sr1645v2ShLineLimVendorName OBJECT IDENTIFIER ::= {sr1645v2ShLineLim 417}

sr1645v2ShLineLimVendorNameTable OBJECT-TYPE
   SYNTAX      SEQUENCE OF Sr1645v2ShLineLimVendorNameEntry
   MAX-ACCESS  not-accessible
   STATUS      current
   DESCRIPTION
      "Selected Vendor Name"
   ::= {sr1645v2ShLineLimVendorName 1}

sr1645v2ShLineLimVendorNameEntry OBJECT-TYPE
   SYNTAX      Sr1645v2ShLineLimVendorNameEntry
   MAX-ACCESS  not-accessible
   STATUS      current
   DESCRIPTION
      ""
   INDEX      { sr1645v2ShLineLimVendorNameGlobalIx }
   ::= {sr1645v2ShLineLimVendorNameTable 1}

Sr1645v2ShLineLimVendorNameEntry ::=
   SEQUENCE
      {
      sr1645v2ShLineLimVendorNameGlobalIx
         GlobalIndex,
      sr1645v2ShLineLimVendorNameValue
         INTEGER
      }

sr1645v2ShLineLimVendorNameGlobalIx OBJECT-TYPE
   SYNTAX      GlobalIndex
   MAX-ACCESS  not-accessible
   STATUS      current
   DESCRIPTION
      "The value of the tlsCntTreeGlobalIndex of the MANAGED OBJECT."
   ::= {sr1645v2ShLineLimVendorNameEntry 10}

sr1645v2ShLineLimVendorNameValue OBJECT-TYPE
   SYNTAX      INTEGER
               {
               iFTN (0),
               gSPN (1)
               }
   MAX-ACCESS  read-only
   STATUS      current
   DESCRIPTION
      "Path: line.status.vendorName

       Possibilities:
               IFTN   (0)
               GSPN   (1)"
   ::= {sr1645v2ShLineLimVendorNameEntry 2147483648}


sr1645v2ShLineLimIdcFwVersion OBJECT IDENTIFIER ::= {sr1645v2ShLineLim 434}

sr1645v2ShLineLimIdcFwVersionTable OBJECT-TYPE
   SYNTAX      SEQUENCE OF Sr1645v2ShLineLimIdcFwVersionEntry
   MAX-ACCESS  not-accessible
   STATUS      current
   DESCRIPTION
      "Selected IDC version"
   ::= {sr1645v2ShLineLimIdcFwVersion 1}

sr1645v2ShLineLimIdcFwVersionEntry OBJECT-TYPE
   SYNTAX      Sr1645v2ShLineLimIdcFwVersionEntry
   MAX-ACCESS  not-accessible
   STATUS      current
   DESCRIPTION
      ""
   INDEX      { sr1645v2ShLineLimIdcFwVersionGlobalIx }
   ::= {sr1645v2ShLineLimIdcFwVersionTable 1}

Sr1645v2ShLineLimIdcFwVersionEntry ::=
   SEQUENCE
      {
      sr1645v2ShLineLimIdcFwVersionGlobalIx
         GlobalIndex,
      sr1645v2ShLineLimIdcFwVersionValue
         DisplayString
      }

sr1645v2ShLineLimIdcFwVersionGlobalIx OBJECT-TYPE
   SYNTAX      GlobalIndex
   MAX-ACCESS  not-accessible
   STATUS      current
   DESCRIPTION
      "The value of the tlsCntTreeGlobalIndex of the MANAGED OBJECT."
   ::= {sr1645v2ShLineLimIdcFwVersionEntry 10}

sr1645v2ShLineLimIdcFwVersionValue OBJECT-TYPE
   SYNTAX      DisplayString
   MAX-ACCESS  read-only
   STATUS      current
   DESCRIPTION
      "Path: line.status.idcFwVersion"
   ::= {sr1645v2ShLineLimIdcFwVersionEntry 2147483648}


sr1645v2ShLineLimSdfeFwVersion OBJECT IDENTIFIER ::= {sr1645v2ShLineLim 435}

sr1645v2ShLineLimSdfeFwVersionTable OBJECT-TYPE
   SYNTAX      SEQUENCE OF Sr1645v2ShLineLimSdfeFwVersionEntry
   MAX-ACCESS  not-accessible
   STATUS      current
   DESCRIPTION
      "Selected SDFE version"
   ::= {sr1645v2ShLineLimSdfeFwVersion 1}

sr1645v2ShLineLimSdfeFwVersionEntry OBJECT-TYPE
   SYNTAX      Sr1645v2ShLineLimSdfeFwVersionEntry
   MAX-ACCESS  not-accessible
   STATUS      current
   DESCRIPTION
      ""
   INDEX      { sr1645v2ShLineLimSdfeFwVersionGlobalIx }
   ::= {sr1645v2ShLineLimSdfeFwVersionTable 1}

Sr1645v2ShLineLimSdfeFwVersionEntry ::=
   SEQUENCE
      {
      sr1645v2ShLineLimSdfeFwVersionGlobalIx
         GlobalIndex,
      sr1645v2ShLineLimSdfeFwVersionValue
         DisplayString
      }

sr1645v2ShLineLimSdfeFwVersionGlobalIx OBJECT-TYPE
   SYNTAX      GlobalIndex
   MAX-ACCESS  not-accessible
   STATUS      current
   DESCRIPTION
      "The value of the tlsCntTreeGlobalIndex of the MANAGED OBJECT."
   ::= {sr1645v2ShLineLimSdfeFwVersionEntry 10}

sr1645v2ShLineLimSdfeFwVersionValue OBJECT-TYPE
   SYNTAX      DisplayString
   MAX-ACCESS  read-only
   STATUS      current
   DESCRIPTION
      "Path: line.status.sdfeFwVersion"
   ::= {sr1645v2ShLineLimSdfeFwVersionEntry 2147483648}


sr1645v2ShLineLimExtendedRates OBJECT IDENTIFIER ::= {sr1645v2ShLineLim 701}

sr1645v2ShLineLimExtendedRatesSSCTable OBJECT-TYPE
   SYNTAX      SEQUENCE OF Sr1645v2ShLineLimExtendedRatesEntry
   MAX-ACCESS  not-accessible
   STATUS      current
   DESCRIPTION
      "Extended rates status"
   ::= {sr1645v2ShLineLimExtendedRates 1}

sr1645v2ShLineLimExtendedRatesEntry OBJECT-TYPE
   SYNTAX      Sr1645v2ShLineLimExtendedRatesEntry
   MAX-ACCESS  not-accessible
   STATUS      current
   DESCRIPTION
      ""
   INDEX      { sr1645v2ShLineLimExtendedRatesGlobalIx }
   ::= {sr1645v2ShLineLimExtendedRatesSSCTable 1}

Sr1645v2ShLineLimExtendedRatesEntry ::=
   SEQUENCE
      {
      sr1645v2ShLineLimExtendedRatesGlobalIx
         GlobalIndex,
      sr1645v2ShLineLimExtendedRatesMode
         INTEGER,
      sr1645v2ShLineLimExtendedRatesFixedRate
         Integer32,
      sr1645v2ShLineLimExtendedRatesFixedModulation
         INTEGER,
      sr1645v2ShLineLimExtendedRatesAdaptiveMaxmrate
         Integer32,
      sr1645v2ShLineLimExtendedRatesAdaptiveModulation
         Integer32,
      sr1645v2ShLineLimExtendedRatesAdaptiveMaxmbaudrate
         Integer32
      }

sr1645v2ShLineLimExtendedRatesGlobalIx OBJECT-TYPE
   SYNTAX      GlobalIndex
   MAX-ACCESS  not-accessible
   STATUS      current
   DESCRIPTION
      "The value of the tlsCntTreeGlobalIndex of the MANAGED OBJECT."
   ::= {sr1645v2ShLineLimExtendedRatesEntry 10}

sr1645v2ShLineLimExtendedRatesMode OBJECT-TYPE
   SYNTAX      INTEGER
               {
               disabled (0),
               fixed (1),
               adaptive (2)
               }
   MAX-ACCESS  read-only
   STATUS      current
   DESCRIPTION
      "Path: line.status.extendedRates.mode

       Possibilities:
               disabled   (0)
               fixed   (1)
               adaptive   (2)"
   ::= {sr1645v2ShLineLimExtendedRatesEntry 16777216}

sr1645v2ShLineLimExtendedRatesFixedRate OBJECT-TYPE
   SYNTAX      Integer32
   UNITS       "kbps"
   MAX-ACCESS  read-only
   STATUS      current
   DESCRIPTION
      "Path: line.status.extendedRates.fixed.rate

       unit name = kbps"
   ::= {sr1645v2ShLineLimExtendedRatesEntry 33619968}

sr1645v2ShLineLimExtendedRatesFixedModulation OBJECT-TYPE
   SYNTAX      INTEGER
               {
               tcmpam4 (1),
               tcmpam8 (2),
               tcmpam16 (3),
               tcmpam32 (4),
               tcmpam64 (5),
               tcmpam128 (6)
               }
   MAX-ACCESS  read-only
   STATUS      current
   DESCRIPTION
      "Path: line.status.extendedRates.fixed.modulation

       Possibilities:
               tc-pam4   (1)
               tc-pam8   (2)
               tc-pam16   (3)
               tc-pam32   (4)
               tc-pam64   (5)
               tc-pam128   (6)"
   ::= {sr1645v2ShLineLimExtendedRatesEntry 33685504}

sr1645v2ShLineLimExtendedRatesAdaptiveMaxmrate OBJECT-TYPE
   SYNTAX      Integer32
   UNITS       "kbps"
   MAX-ACCESS  read-only
   STATUS      current
   DESCRIPTION
      "Path: line.status.extendedRates.adaptive.max-rate

       unit name = kbps"
   ::= {sr1645v2ShLineLimExtendedRatesEntry 50397184}

sr1645v2ShLineLimExtendedRatesAdaptiveModulation OBJECT-TYPE
   SYNTAX      Integer32
   MAX-ACCESS  read-only
   STATUS      current
   DESCRIPTION
      "Path: line.status.extendedRates.adaptive.modulation

       Bit meanings:
               bit 0 = tc-pam4,
               bit 1 = tc-pam8,
               bit 2 = tc-pam16,
               bit 3 = tc-pam32,
               bit 4 = tc-pam64,
               bit 5 = tc-pam128"
   ::= {sr1645v2ShLineLimExtendedRatesEntry 50462720}

sr1645v2ShLineLimExtendedRatesAdaptiveMaxmbaudrate OBJECT-TYPE
   SYNTAX      Integer32
   UNITS       "ksyms/s"
   MAX-ACCESS  read-only
   STATUS      current
   DESCRIPTION
      "Path: line.status.extendedRates.adaptive.max-baudrate

       unit name = ksyms/s"
   ::= {sr1645v2ShLineLimExtendedRatesEntry 50528256}



er1645v2ShLineLim OBJECT IDENTIFIER ::= {r1645v2ShLineLim 11}


er1645v2ShLineLimRemark OBJECT IDENTIFIER ::= {er1645v2ShLineLim 321}

er1645v2ShLineLimRemarkTable OBJECT-TYPE
   SYNTAX      SEQUENCE OF Er1645v2ShLineLimRemarkEntry
   MAX-ACCESS  not-accessible
   STATUS      current
   DESCRIPTION
      "intfRemark"
   ::= {er1645v2ShLineLimRemark 1}

er1645v2ShLineLimRemarkEntry OBJECT-TYPE
   SYNTAX      Er1645v2ShLineLimRemarkEntry
   MAX-ACCESS  not-accessible
   STATUS      current
   DESCRIPTION
      ""
   INDEX      { er1645v2ShLineLimRemarkGlobalIx }
   ::= {er1645v2ShLineLimRemarkTable 1}

Er1645v2ShLineLimRemarkEntry ::=
   SEQUENCE
      {
      er1645v2ShLineLimRemarkGlobalIx
         GlobalIndex,
      er1645v2ShLineLimRemarkValue
         DisplayString
      }

er1645v2ShLineLimRemarkGlobalIx OBJECT-TYPE
   SYNTAX      GlobalIndex
   MAX-ACCESS  not-accessible
   STATUS      current
   DESCRIPTION
      "The value of the tlsCntTreeGlobalIndex of the MANAGED OBJECT."
   ::= {er1645v2ShLineLimRemarkEntry 10}

er1645v2ShLineLimRemarkValue OBJECT-TYPE
   SYNTAX      DisplayString
   MAX-ACCESS  read-write
   STATUS      current
   DESCRIPTION
      "Path: line.editConf.remark"
   ::= {er1645v2ShLineLimRemarkEntry 2147483648}


er1645v2ShLineLimManagement OBJECT IDENTIFIER ::= {er1645v2ShLineLim 29}

er1645v2ShLineLimManagementTable OBJECT-TYPE
   SYNTAX      SEQUENCE OF Er1645v2ShLineLimManagementEntry
   MAX-ACCESS  not-accessible
   STATUS      current
   DESCRIPTION
      "mgmntBits use"
   ::= {er1645v2ShLineLimManagement 1}

er1645v2ShLineLimManagementEntry OBJECT-TYPE
   SYNTAX      Er1645v2ShLineLimManagementEntry
   MAX-ACCESS  not-accessible
   STATUS      current
   DESCRIPTION
      ""
   INDEX      { er1645v2ShLineLimManagementGlobalIx }
   ::= {er1645v2ShLineLimManagementTable 1}

Er1645v2ShLineLimManagementEntry ::=
   SEQUENCE
      {
      er1645v2ShLineLimManagementGlobalIx
         GlobalIndex,
      er1645v2ShLineLimManagementValue
         INTEGER
      }

er1645v2ShLineLimManagementGlobalIx OBJECT-TYPE
   SYNTAX      GlobalIndex
   MAX-ACCESS  not-accessible
   STATUS      current
   DESCRIPTION
      "The value of the tlsCntTreeGlobalIndex of the MANAGED OBJECT."
   ::= {er1645v2ShLineLimManagementEntry 10}

er1645v2ShLineLimManagementValue OBJECT-TYPE
   SYNTAX      INTEGER
               {
               transp (0),
               o10 (2),
               path (3),
               o10path (4)
               }
   MAX-ACCESS  read-write
   STATUS      current
   DESCRIPTION
      "Path: line.editConf.management

       Possibilities:
               transparent   (0)
               o10Management   (2)
               pathManagement   (3)
               o10-PathManagement   (4)"
   ::= {er1645v2ShLineLimManagementEntry 2147483648}


er1645v2ShLineLimEndAlmMsk OBJECT IDENTIFIER ::= {er1645v2ShLineLim 83}

er1645v2ShLineLimEndAlmMskTable OBJECT-TYPE
   SYNTAX      SEQUENCE OF Er1645v2ShLineLimEndAlmMskEntry
   MAX-ACCESS  not-accessible
   STATUS      current
   DESCRIPTION
      "lineAlarmMask"
   ::= {er1645v2ShLineLimEndAlmMsk 1}

er1645v2ShLineLimEndAlmMskEntry OBJECT-TYPE
   SYNTAX      Er1645v2ShLineLimEndAlmMskEntry
   MAX-ACCESS  not-accessible
   STATUS      current
   DESCRIPTION
      ""
   INDEX      { er1645v2ShLineLimEndAlmMskGlobalIx }
   ::= {er1645v2ShLineLimEndAlmMskTable 1}

Er1645v2ShLineLimEndAlmMskEntry ::=
   SEQUENCE
      {
      er1645v2ShLineLimEndAlmMskGlobalIx
         GlobalIndex,
      er1645v2ShLineLimEndAlmMskValue
         Integer32
      }

er1645v2ShLineLimEndAlmMskGlobalIx OBJECT-TYPE
   SYNTAX      GlobalIndex
   MAX-ACCESS  not-accessible
   STATUS      current
   DESCRIPTION
      "The value of the tlsCntTreeGlobalIndex of the MANAGED OBJECT."
   ::= {er1645v2ShLineLimEndAlmMskEntry 10}

er1645v2ShLineLimEndAlmMskValue OBJECT-TYPE
   SYNTAX      Integer32
   MAX-ACCESS  read-write
   STATUS      current
   DESCRIPTION
      "Path: line.editConf.endAlarmMask

       Bit meanings:
               bit 0 = linkDown"
   ::= {er1645v2ShLineLimEndAlmMskEntry 2147483648}


er1645v2ShLineLimEndAlmLev OBJECT IDENTIFIER ::= {er1645v2ShLineLim 82}

er1645v2ShLineLimEndAlmLevSSCTable OBJECT-TYPE
   SYNTAX      SEQUENCE OF Er1645v2ShLineLimEndAlmLevEntry
   MAX-ACCESS  not-accessible
   STATUS      current
   DESCRIPTION
      "lineAlarmLevel"
   ::= {er1645v2ShLineLimEndAlmLev 1}

er1645v2ShLineLimEndAlmLevEntry OBJECT-TYPE
   SYNTAX      Er1645v2ShLineLimEndAlmLevEntry
   MAX-ACCESS  not-accessible
   STATUS      current
   DESCRIPTION
      ""
   INDEX      { er1645v2ShLineLimEndAlmLevGlobalIx }
   ::= {er1645v2ShLineLimEndAlmLevSSCTable 1}

Er1645v2ShLineLimEndAlmLevEntry ::=
   SEQUENCE
      {
      er1645v2ShLineLimEndAlmLevGlobalIx
         GlobalIndex,
      er1645v2ShLineLimEndAlmLevLnkDwn
         Integer32
      }

er1645v2ShLineLimEndAlmLevGlobalIx OBJECT-TYPE
   SYNTAX      GlobalIndex
   MAX-ACCESS  not-accessible
   STATUS      current
   DESCRIPTION
      "The value of the tlsCntTreeGlobalIndex of the MANAGED OBJECT."
   ::= {er1645v2ShLineLimEndAlmLevEntry 10}

er1645v2ShLineLimEndAlmLevLnkDwn OBJECT-TYPE
   SYNTAX      Integer32
   MAX-ACCESS  read-write
   STATUS      current
   DESCRIPTION
      "Path: line.editConf.endAlarmLevel.linkDown"
   ::= {er1645v2ShLineLimEndAlmLevEntry 16777216}


er1645v2ShLineLimRepAlmMsk OBJECT IDENTIFIER ::= {er1645v2ShLineLim 85}

er1645v2ShLineLimRepAlmMskTable OBJECT-TYPE
   SYNTAX      SEQUENCE OF Er1645v2ShLineLimRepAlmMskEntry
   MAX-ACCESS  not-accessible
   STATUS      current
   DESCRIPTION
      "lineAlarmMask"
   ::= {er1645v2ShLineLimRepAlmMsk 1}

er1645v2ShLineLimRepAlmMskEntry OBJECT-TYPE
   SYNTAX      Er1645v2ShLineLimRepAlmMskEntry
   MAX-ACCESS  not-accessible
   STATUS      current
   DESCRIPTION
      ""
   INDEX      { er1645v2ShLineLimRepAlmMskGlobalIx }
   ::= {er1645v2ShLineLimRepAlmMskTable 1}

Er1645v2ShLineLimRepAlmMskEntry ::=
   SEQUENCE
      {
      er1645v2ShLineLimRepAlmMskGlobalIx
         GlobalIndex,
      er1645v2ShLineLimRepAlmMskValue
         Integer32
      }

er1645v2ShLineLimRepAlmMskGlobalIx OBJECT-TYPE
   SYNTAX      GlobalIndex
   MAX-ACCESS  not-accessible
   STATUS      current
   DESCRIPTION
      "The value of the tlsCntTreeGlobalIndex of the MANAGED OBJECT."
   ::= {er1645v2ShLineLimRepAlmMskEntry 10}

er1645v2ShLineLimRepAlmMskValue OBJECT-TYPE
   SYNTAX      Integer32
   MAX-ACCESS  read-write
   STATUS      current
   DESCRIPTION
      "Path: line.editConf.repeaterAlarmMask

       Bit meanings:
               bit 0 = linkDown"
   ::= {er1645v2ShLineLimRepAlmMskEntry 2147483648}


er1645v2ShLineLimRepAlmLev OBJECT IDENTIFIER ::= {er1645v2ShLineLim 84}

er1645v2ShLineLimRepAlmLevSSCTable OBJECT-TYPE
   SYNTAX      SEQUENCE OF Er1645v2ShLineLimRepAlmLevEntry
   MAX-ACCESS  not-accessible
   STATUS      current
   DESCRIPTION
      "lineAlarmLevel"
   ::= {er1645v2ShLineLimRepAlmLev 1}

er1645v2ShLineLimRepAlmLevEntry OBJECT-TYPE
   SYNTAX      Er1645v2ShLineLimRepAlmLevEntry
   MAX-ACCESS  not-accessible
   STATUS      current
   DESCRIPTION
      ""
   INDEX      { er1645v2ShLineLimRepAlmLevGlobalIx }
   ::= {er1645v2ShLineLimRepAlmLevSSCTable 1}

Er1645v2ShLineLimRepAlmLevEntry ::=
   SEQUENCE
      {
      er1645v2ShLineLimRepAlmLevGlobalIx
         GlobalIndex,
      er1645v2ShLineLimRepAlmLevLnkDwn
         Integer32
      }

er1645v2ShLineLimRepAlmLevGlobalIx OBJECT-TYPE
   SYNTAX      GlobalIndex
   MAX-ACCESS  not-accessible
   STATUS      current
   DESCRIPTION
      "The value of the tlsCntTreeGlobalIndex of the MANAGED OBJECT."
   ::= {er1645v2ShLineLimRepAlmLevEntry 10}

er1645v2ShLineLimRepAlmLevLnkDwn OBJECT-TYPE
   SYNTAX      Integer32
   MAX-ACCESS  read-write
   STATUS      current
   DESCRIPTION
      "Path: line.editConf.repeaterAlarmLevel.linkDown"
   ::= {er1645v2ShLineLimRepAlmLevEntry 16777216}


er1645v2ShLineLimName OBJECT IDENTIFIER ::= {er1645v2ShLineLim 262}

er1645v2ShLineLimNameTable OBJECT-TYPE
   SYNTAX      SEQUENCE OF Er1645v2ShLineLimNameEntry
   MAX-ACCESS  not-accessible
   STATUS      current
   DESCRIPTION
      "config interface name"
   ::= {er1645v2ShLineLimName 1}

er1645v2ShLineLimNameEntry OBJECT-TYPE
   SYNTAX      Er1645v2ShLineLimNameEntry
   MAX-ACCESS  not-accessible
   STATUS      current
   DESCRIPTION
      ""
   INDEX      { er1645v2ShLineLimNameGlobalIx }
   ::= {er1645v2ShLineLimNameTable 1}

Er1645v2ShLineLimNameEntry ::=
   SEQUENCE
      {
      er1645v2ShLineLimNameGlobalIx
         GlobalIndex,
      er1645v2ShLineLimNameValue
         DisplayString
      }

er1645v2ShLineLimNameGlobalIx OBJECT-TYPE
   SYNTAX      GlobalIndex
   MAX-ACCESS  not-accessible
   STATUS      current
   DESCRIPTION
      "The value of the tlsCntTreeGlobalIndex of the MANAGED OBJECT."
   ::= {er1645v2ShLineLimNameEntry 10}

er1645v2ShLineLimNameValue OBJECT-TYPE
   SYNTAX      DisplayString
   MAX-ACCESS  read-write
   STATUS      current
   DESCRIPTION
      "Path: line.editConf.name"
   ::= {er1645v2ShLineLimNameEntry 2147483648}


er1645v2ShLineLimChannel OBJECT IDENTIFIER ::= {er1645v2ShLineLim 1}

er1645v2ShLineLimChannelTable OBJECT-TYPE
   SYNTAX      SEQUENCE OF Er1645v2ShLineLimChannelEntry
   MAX-ACCESS  not-accessible
   STATUS      current
   DESCRIPTION
      "channel"
   ::= {er1645v2ShLineLimChannel 1}

er1645v2ShLineLimChannelEntry OBJECT-TYPE
   SYNTAX      Er1645v2ShLineLimChannelEntry
   MAX-ACCESS  not-accessible
   STATUS      current
   DESCRIPTION
      ""
   INDEX      { er1645v2ShLineLimChannelGlobalIx }
   ::= {er1645v2ShLineLimChannelTable 1}

Er1645v2ShLineLimChannelEntry ::=
   SEQUENCE
      {
      er1645v2ShLineLimChannelGlobalIx
         GlobalIndex,
      er1645v2ShLineLimChannelValue
         INTEGER
      }

er1645v2ShLineLimChannelGlobalIx OBJECT-TYPE
   SYNTAX      GlobalIndex
   MAX-ACCESS  not-accessible
   STATUS      current
   DESCRIPTION
      "The value of the tlsCntTreeGlobalIndex of the MANAGED OBJECT."
   ::= {er1645v2ShLineLimChannelEntry 10}

er1645v2ShLineLimChannelValue OBJECT-TYPE
   SYNTAX      INTEGER
               {
               central (0),
               remote (1)
               }
   MAX-ACCESS  read-write
   STATUS      current
   DESCRIPTION
      "Path: line.editConf.channel

       Possibilities:
               central   (0)
               remote   (1)"
   ::= {er1645v2ShLineLimChannelEntry 2147483648}


er1645v2ShLineLimStartupMargin OBJECT IDENTIFIER ::= {er1645v2ShLineLim 7}

er1645v2ShLineLimStartupMarginTable OBJECT-TYPE
   SYNTAX      SEQUENCE OF Er1645v2ShLineLimStartupMarginEntry
   MAX-ACCESS  not-accessible
   STATUS      current
   DESCRIPTION
      "startupMargin"
   ::= {er1645v2ShLineLimStartupMargin 1}

er1645v2ShLineLimStartupMarginEntry OBJECT-TYPE
   SYNTAX      Er1645v2ShLineLimStartupMarginEntry
   MAX-ACCESS  not-accessible
   STATUS      current
   DESCRIPTION
      ""
   INDEX      { er1645v2ShLineLimStartupMarginGlobalIx }
   ::= {er1645v2ShLineLimStartupMarginTable 1}

Er1645v2ShLineLimStartupMarginEntry ::=
   SEQUENCE
      {
      er1645v2ShLineLimStartupMarginGlobalIx
         GlobalIndex,
      er1645v2ShLineLimStartupMarginValue
         INTEGER
      }

er1645v2ShLineLimStartupMarginGlobalIx OBJECT-TYPE
   SYNTAX      GlobalIndex
   MAX-ACCESS  not-accessible
   STATUS      current
   DESCRIPTION
      "The value of the tlsCntTreeGlobalIndex of the MANAGED OBJECT."
   ::= {er1645v2ShLineLimStartupMarginEntry 10}

er1645v2ShLineLimStartupMarginValue OBJECT-TYPE
   SYNTAX      INTEGER
               {
               disabled (0),
               sm10dB (1),
               sm9dB (2),
               sm8dB (3),
               sm7dB (4),
               sm6dB (5),
               sm5dB (6),
               sm4dB (7),
               sm3dB (8),
               sm2dB (9),
               sm1dB (10),
               s0dB (11),
               s1dB (12),
               s2dB (13),
               s3dB (14),
               s4dB (15),
               s5dB (16),
               s6dB (17),
               s7dB (18),
               s8dB (19),
               s9dB (20),
               s10dB (21)
               }
   MAX-ACCESS  read-write
   STATUS      current
   DESCRIPTION
      "Path: line.editConf.startupMargin

       Possibilities:
               disabled   (0)
               -10dB   (1)
               -9dB   (2)
               -8dB   (3)
               -7dB   (4)
               -6dB   (5)
               -5dB   (6)
               -4dB   (7)
               -3dB   (8)
               -2dB   (9)
               -1dB   (10)
               0dB   (11)
               1dB   (12)
               2dB   (13)
               3dB   (14)
               4dB   (15)
               5dB   (16)
               6dB   (17)
               7dB   (18)
               8dB   (19)
               9dB   (20)
               10dB   (21)"
   ::= {er1645v2ShLineLimStartupMarginEntry 2147483648}


er1645v2ShLineLimSmm OBJECT IDENTIFIER ::= {er1645v2ShLineLim 430}

er1645v2ShLineLimSmmTable OBJECT-TYPE
   SYNTAX      SEQUENCE OF Er1645v2ShLineLimSmmEntry
   MAX-ACCESS  not-accessible
   STATUS      current
   DESCRIPTION
      ""
   ::= {er1645v2ShLineLimSmm 1}

er1645v2ShLineLimSmmEntry OBJECT-TYPE
   SYNTAX      Er1645v2ShLineLimSmmEntry
   MAX-ACCESS  not-accessible
   STATUS      current
   DESCRIPTION
      ""
   INDEX      { er1645v2ShLineLimSmmGlobalIx }
   ::= {er1645v2ShLineLimSmmTable 1}

Er1645v2ShLineLimSmmEntry ::=
   SEQUENCE
      {
      er1645v2ShLineLimSmmGlobalIx
         GlobalIndex,
      er1645v2ShLineLimSmmValue
         INTEGER
      }

er1645v2ShLineLimSmmGlobalIx OBJECT-TYPE
   SYNTAX      GlobalIndex
   MAX-ACCESS  not-accessible
   STATUS      current
   DESCRIPTION
      "The value of the tlsCntTreeGlobalIndex of the MANAGED OBJECT."
   ::= {er1645v2ShLineLimSmmEntry 10}

er1645v2ShLineLimSmmValue OBJECT-TYPE
   SYNTAX      INTEGER
               {
               normal (1),
               forced (2)
               }
   MAX-ACCESS  read-write
   STATUS      current
   DESCRIPTION
      "Path: line.editConf.startupMarginMode

       Possibilities:
               normal   (1)
               forced   (2)"
   ::= {er1645v2ShLineLimSmmEntry 2147483648}


er1645v2ShLineLimAlThr OBJECT IDENTIFIER ::= {er1645v2ShLineLim 11}

er1645v2ShLineLimAlThrSSCTable OBJECT-TYPE
   SYNTAX      SEQUENCE OF Er1645v2ShLineLimAlThrEntry
   MAX-ACCESS  not-accessible
   STATUS      current
   DESCRIPTION
      "on/off threshold values for alarm generation"
   ::= {er1645v2ShLineLimAlThr 1}

er1645v2ShLineLimAlThrEntry OBJECT-TYPE
   SYNTAX      Er1645v2ShLineLimAlThrEntry
   MAX-ACCESS  not-accessible
   STATUS      current
   DESCRIPTION
      ""
   INDEX      { er1645v2ShLineLimAlThrGlobalIx }
   ::= {er1645v2ShLineLimAlThrSSCTable 1}

Er1645v2ShLineLimAlThrEntry ::=
   SEQUENCE
      {
      er1645v2ShLineLimAlThrGlobalIx
         GlobalIndex,
      er1645v2ShLineLimAlThrLineAtt
         Integer32,
      er1645v2ShLineLimAlThrNoiseMargin
         Integer32,
      er1645v2ShLineLimAlThrEsrExc
         Integer32,
      er1645v2ShLineLimAlThrSesrExc
         Integer32,
      er1645v2ShLineLimAlThrBberExc
         Integer32,
      er1645v2ShLineLimAlThrIfSpeed
         INTEGER,
      er1645v2ShLineLimAlThrAggregatedIfSpeed
         INTEGER
      }

er1645v2ShLineLimAlThrGlobalIx OBJECT-TYPE
   SYNTAX      GlobalIndex
   MAX-ACCESS  not-accessible
   STATUS      current
   DESCRIPTION
      "The value of the tlsCntTreeGlobalIndex of the MANAGED OBJECT."
   ::= {er1645v2ShLineLimAlThrEntry 10}

er1645v2ShLineLimAlThrLineAtt OBJECT-TYPE
   SYNTAX      Integer32
   MAX-ACCESS  read-write
   STATUS      current
   DESCRIPTION
      "Path: line.editConf.linkAlarmThresholds.lineAttenuation

       unit name = dB
       formula = 10 / ; 10 *"
   ::= {er1645v2ShLineLimAlThrEntry 16777216}

er1645v2ShLineLimAlThrNoiseMargin OBJECT-TYPE
   SYNTAX      Integer32
   MAX-ACCESS  read-write
   STATUS      current
   DESCRIPTION
      "Path: line.editConf.linkAlarmThresholds.noiseMargin

       unit name = dB
       formula = 10 / ; 10 *"
   ::= {er1645v2ShLineLimAlThrEntry 33554432}

er1645v2ShLineLimAlThrEsrExc OBJECT-TYPE
   SYNTAX      Integer32
   MAX-ACCESS  read-write
   STATUS      current
   DESCRIPTION
      "Path: line.editConf.linkAlarmThresholds.errSecRatioExceeded

       unit name = ratio
       formula = 1000 / ; 1000 *"
   ::= {er1645v2ShLineLimAlThrEntry 100663296}

er1645v2ShLineLimAlThrSesrExc OBJECT-TYPE
   SYNTAX      Integer32
   MAX-ACCESS  read-write
   STATUS      current
   DESCRIPTION
      "Path: line.editConf.linkAlarmThresholds.sevErrSecRatioExceeded

       unit name = ratio
       formula = 1000 / ; 1000 *"
   ::= {er1645v2ShLineLimAlThrEntry 117440512}

er1645v2ShLineLimAlThrBberExc OBJECT-TYPE
   SYNTAX      Integer32
   MAX-ACCESS  read-write
   STATUS      current
   DESCRIPTION
      "Path: line.editConf.linkAlarmThresholds.bBErrRatioExceeded

       unit name = ratio
       formula = 1000000 / ; 1000000 *"
   ::= {er1645v2ShLineLimAlThrEntry 134217728}

er1645v2ShLineLimAlThrIfSpeed OBJECT-TYPE
   SYNTAX      INTEGER
               {
               disabled (0)
               }
   UNITS       "bps"
   MAX-ACCESS  read-write
   STATUS      current
   DESCRIPTION
      "Path: line.editConf.linkAlarmThresholds.ifSpeed

       unit name = bps

       Possibilities:
               disabled   (0)"
   ::= {er1645v2ShLineLimAlThrEntry 150994944}

er1645v2ShLineLimAlThrAggregatedIfSpeed OBJECT-TYPE
   SYNTAX      INTEGER
               {
               disabled (0)
               }
   UNITS       "bps"
   MAX-ACCESS  read-write
   STATUS      current
   DESCRIPTION
      "Path: line.editConf.linkAlarmThresholds.aggregatedIfSpeed

       unit name = bps

       Possibilities:
               disabled   (0)"
   ::= {er1645v2ShLineLimAlThrEntry 167772160}


er1645v2ShLineLimNbERep OBJECT IDENTIFIER ::= {er1645v2ShLineLim 160}

er1645v2ShLineLimNbERepTable OBJECT-TYPE
   SYNTAX      SEQUENCE OF Er1645v2ShLineLimNbERepEntry
   MAX-ACCESS  not-accessible
   STATUS      current
   DESCRIPTION
      "Number of expected repeaters"
   ::= {er1645v2ShLineLimNbERep 1}

er1645v2ShLineLimNbERepEntry OBJECT-TYPE
   SYNTAX      Er1645v2ShLineLimNbERepEntry
   MAX-ACCESS  not-accessible
   STATUS      current
   DESCRIPTION
      ""
   INDEX      { er1645v2ShLineLimNbERepGlobalIx }
   ::= {er1645v2ShLineLimNbERepTable 1}

Er1645v2ShLineLimNbERepEntry ::=
   SEQUENCE
      {
      er1645v2ShLineLimNbERepGlobalIx
         GlobalIndex,
      er1645v2ShLineLimNbERepValue
         Integer32
      }

er1645v2ShLineLimNbERepGlobalIx OBJECT-TYPE
   SYNTAX      GlobalIndex
   MAX-ACCESS  not-accessible
   STATUS      current
   DESCRIPTION
      "The value of the tlsCntTreeGlobalIndex of the MANAGED OBJECT."
   ::= {er1645v2ShLineLimNbERepEntry 10}

er1645v2ShLineLimNbERepValue OBJECT-TYPE
   SYNTAX      Integer32
   MAX-ACCESS  read-write
   STATUS      current
   DESCRIPTION
      "Path: line.editConf.numExpectedRepeaters"
   ::= {er1645v2ShLineLimNbERepEntry 2147483648}


er1645v2ShLineLimEocHandling OBJECT IDENTIFIER ::= {er1645v2ShLineLim 162}

er1645v2ShLineLimEocHandlingTable OBJECT-TYPE
   SYNTAX      SEQUENCE OF Er1645v2ShLineLimEocHandlingEntry
   MAX-ACCESS  not-accessible
   STATUS      current
   DESCRIPTION
      "define the eoc handling level"
   ::= {er1645v2ShLineLimEocHandling 1}

er1645v2ShLineLimEocHandlingEntry OBJECT-TYPE
   SYNTAX      Er1645v2ShLineLimEocHandlingEntry
   MAX-ACCESS  not-accessible
   STATUS      current
   DESCRIPTION
      ""
   INDEX      { er1645v2ShLineLimEocHandlingGlobalIx }
   ::= {er1645v2ShLineLimEocHandlingTable 1}

Er1645v2ShLineLimEocHandlingEntry ::=
   SEQUENCE
      {
      er1645v2ShLineLimEocHandlingGlobalIx
         GlobalIndex,
      er1645v2ShLineLimEocHandlingValue
         INTEGER
      }

er1645v2ShLineLimEocHandlingGlobalIx OBJECT-TYPE
   SYNTAX      GlobalIndex
   MAX-ACCESS  not-accessible
   STATUS      current
   DESCRIPTION
      "The value of the tlsCntTreeGlobalIndex of the MANAGED OBJECT."
   ::= {er1645v2ShLineLimEocHandlingEntry 10}

er1645v2ShLineLimEocHandlingValue OBJECT-TYPE
   SYNTAX      INTEGER
               {
               passive (10),
               none (0),
               discovery (1),
               inventory (2),
               info (3),
               alarmConfiguration (4)
               }
   MAX-ACCESS  read-write
   STATUS      current
   DESCRIPTION
      "Path: line.editConf.eocHandling

       Possibilities:
               passive   (10)
               none   (0)
               discovery   (1)
               inventory   (2)
               info   (3)
               alarmConfiguration   (4)"
   ::= {er1645v2ShLineLimEocHandlingEntry 2147483648}


er1645v2ShLineLimEocPerfCounters OBJECT IDENTIFIER ::= {er1645v2ShLineLim 416}

er1645v2ShLineLimEocPerfCountersTable OBJECT-TYPE
   SYNTAX      SEQUENCE OF Er1645v2ShLineLimEocPerfCountersEntry
   MAX-ACCESS  not-accessible
   STATUS      current
   DESCRIPTION
      ""
   ::= {er1645v2ShLineLimEocPerfCounters 1}

er1645v2ShLineLimEocPerfCountersEntry OBJECT-TYPE
   SYNTAX      Er1645v2ShLineLimEocPerfCountersEntry
   MAX-ACCESS  not-accessible
   STATUS      current
   DESCRIPTION
      ""
   INDEX      { er1645v2ShLineLimEocPerfCountersGlobalIx }
   ::= {er1645v2ShLineLimEocPerfCountersTable 1}

Er1645v2ShLineLimEocPerfCountersEntry ::=
   SEQUENCE
      {
      er1645v2ShLineLimEocPerfCountersGlobalIx
         GlobalIndex,
      er1645v2ShLineLimEocPerfCountersValue
         INTEGER
      }

er1645v2ShLineLimEocPerfCountersGlobalIx OBJECT-TYPE
   SYNTAX      GlobalIndex
   MAX-ACCESS  not-accessible
   STATUS      current
   DESCRIPTION
      "The value of the tlsCntTreeGlobalIndex of the MANAGED OBJECT."
   ::= {er1645v2ShLineLimEocPerfCountersEntry 10}

er1645v2ShLineLimEocPerfCountersValue OBJECT-TYPE
   SYNTAX      INTEGER
               {
               absolute (1),
               differential (2),
               auto (3)
               }
   MAX-ACCESS  read-write
   STATUS      current
   DESCRIPTION
      "Path: line.editConf.eocPerfCounters

       Possibilities:
               absolute   (1)
               differential   (2)
               auto   (3)"
   ::= {er1645v2ShLineLimEocPerfCountersEntry 2147483648}


er1645v2ShLineLimWcStartupMargin OBJECT IDENTIFIER ::= {er1645v2ShLineLim 8}

er1645v2ShLineLimWcStartupMarginTable OBJECT-TYPE
   SYNTAX      SEQUENCE OF Er1645v2ShLineLimWcStartupMarginEntry
   MAX-ACCESS  not-accessible
   STATUS      current
   DESCRIPTION
      "startupMargin"
   ::= {er1645v2ShLineLimWcStartupMargin 1}

er1645v2ShLineLimWcStartupMarginEntry OBJECT-TYPE
   SYNTAX      Er1645v2ShLineLimWcStartupMarginEntry
   MAX-ACCESS  not-accessible
   STATUS      current
   DESCRIPTION
      ""
   INDEX      { er1645v2ShLineLimWcStartupMarginGlobalIx }
   ::= {er1645v2ShLineLimWcStartupMarginTable 1}

Er1645v2ShLineLimWcStartupMarginEntry ::=
   SEQUENCE
      {
      er1645v2ShLineLimWcStartupMarginGlobalIx
         GlobalIndex,
      er1645v2ShLineLimWcStartupMarginValue
         INTEGER
      }

er1645v2ShLineLimWcStartupMarginGlobalIx OBJECT-TYPE
   SYNTAX      GlobalIndex
   MAX-ACCESS  not-accessible
   STATUS      current
   DESCRIPTION
      "The value of the tlsCntTreeGlobalIndex of the MANAGED OBJECT."
   ::= {er1645v2ShLineLimWcStartupMarginEntry 10}

er1645v2ShLineLimWcStartupMarginValue OBJECT-TYPE
   SYNTAX      INTEGER
               {
               disabled (0),
               sm10dB (1),
               sm9dB (2),
               sm8dB (3),
               sm7dB (4),
               sm6dB (5),
               sm5dB (6),
               sm4dB (7),
               sm3dB (8),
               sm2dB (9),
               sm1dB (10),
               s0dB (11),
               s1dB (12),
               s2dB (13),
               s3dB (14),
               s4dB (15),
               s5dB (16),
               s6dB (17),
               s7dB (18),
               s8dB (19),
               s9dB (20),
               s10dB (21)
               }
   MAX-ACCESS  read-write
   STATUS      current
   DESCRIPTION
      "Path: line.editConf.wcStartupMargin

       Possibilities:
               disabled   (0)
               -10dB   (1)
               -9dB   (2)
               -8dB   (3)
               -7dB   (4)
               -6dB   (5)
               -5dB   (6)
               -4dB   (7)
               -3dB   (8)
               -2dB   (9)
               -1dB   (10)
               0dB   (11)
               1dB   (12)
               2dB   (13)
               3dB   (14)
               4dB   (15)
               5dB   (16)
               6dB   (17)
               7dB   (18)
               8dB   (19)
               9dB   (20)
               10dB   (21)"
   ::= {er1645v2ShLineLimWcStartupMarginEntry 2147483648}


er1645v2ShLineLimRegion OBJECT IDENTIFIER ::= {er1645v2ShLineLim 6}

er1645v2ShLineLimRegionTable OBJECT-TYPE
   SYNTAX      SEQUENCE OF Er1645v2ShLineLimRegionEntry
   MAX-ACCESS  not-accessible
   STATUS      current
   DESCRIPTION
      "Region Selection"
   ::= {er1645v2ShLineLimRegion 1}

er1645v2ShLineLimRegionEntry OBJECT-TYPE
   SYNTAX      Er1645v2ShLineLimRegionEntry
   MAX-ACCESS  not-accessible
   STATUS      current
   DESCRIPTION
      ""
   INDEX      { er1645v2ShLineLimRegionGlobalIx }
   ::= {er1645v2ShLineLimRegionTable 1}

Er1645v2ShLineLimRegionEntry ::=
   SEQUENCE
      {
      er1645v2ShLineLimRegionGlobalIx
         GlobalIndex,
      er1645v2ShLineLimRegionValue
         INTEGER
      }

er1645v2ShLineLimRegionGlobalIx OBJECT-TYPE
   SYNTAX      GlobalIndex
   MAX-ACCESS  not-accessible
   STATUS      current
   DESCRIPTION
      "The value of the tlsCntTreeGlobalIndex of the MANAGED OBJECT."
   ::= {er1645v2ShLineLimRegionEntry 10}

er1645v2ShLineLimRegionValue OBJECT-TYPE
   SYNTAX      INTEGER
               {
               annexAuF (1),
               annexBuG (2)
               }
   MAX-ACCESS  read-write
   STATUS      current
   DESCRIPTION
      "Path: line.editConf.region

       Possibilities:
               annexA_F   (1)
               annexB_G   (2)"
   ::= {er1645v2ShLineLimRegionEntry 2147483648}


er1645v2ShLineLimRetrain OBJECT IDENTIFIER ::= {er1645v2ShLineLim 5}

er1645v2ShLineLimRetrainSSCTable OBJECT-TYPE
   SYNTAX      SEQUENCE OF Er1645v2ShLineLimRetrainEntry
   MAX-ACCESS  not-accessible
   STATUS      current
   DESCRIPTION
      "retrain"
   ::= {er1645v2ShLineLimRetrain 1}

er1645v2ShLineLimRetrainEntry OBJECT-TYPE
   SYNTAX      Er1645v2ShLineLimRetrainEntry
   MAX-ACCESS  not-accessible
   STATUS      current
   DESCRIPTION
      ""
   INDEX      { er1645v2ShLineLimRetrainGlobalIx }
   ::= {er1645v2ShLineLimRetrainSSCTable 1}

Er1645v2ShLineLimRetrainEntry ::=
   SEQUENCE
      {
      er1645v2ShLineLimRetrainGlobalIx
         GlobalIndex,
      er1645v2ShLineLimRetrainEnabled
         INTEGER,
      er1645v2ShLineLimRetrainLayer2Check
         INTEGER,
      er1645v2ShLineLimRetrainErrPersistT
         Integer32,
      er1645v2ShLineLimRetrainErrThresh
         Integer32,
      er1645v2ShLineLimRetrainNmThresh
         INTEGER,
      er1645v2ShLineLimRetrainStepupMg
         INTEGER
      }

er1645v2ShLineLimRetrainGlobalIx OBJECT-TYPE
   SYNTAX      GlobalIndex
   MAX-ACCESS  not-accessible
   STATUS      current
   DESCRIPTION
      "The value of the tlsCntTreeGlobalIndex of the MANAGED OBJECT."
   ::= {er1645v2ShLineLimRetrainEntry 10}

er1645v2ShLineLimRetrainEnabled OBJECT-TYPE
   SYNTAX      INTEGER
               {
               no (0),
               yes (1)
               }
   MAX-ACCESS  read-write
   STATUS      current
   DESCRIPTION
      "Path: line.editConf.retrain.enabled

       Possibilities:
               no   (0)
               yes   (1)"
   ::= {er1645v2ShLineLimRetrainEntry 16777216}

er1645v2ShLineLimRetrainLayer2Check OBJECT-TYPE
   SYNTAX      INTEGER
               {
               disabled (0),
               enabled (1)
               }
   MAX-ACCESS  read-write
   STATUS      current
   DESCRIPTION
      "Path: line.editConf.retrain.layer2Check

       Possibilities:
               disabled   (0)
               enabled   (1)"
   ::= {er1645v2ShLineLimRetrainEntry 117440512}

er1645v2ShLineLimRetrainErrPersistT OBJECT-TYPE
   SYNTAX      Integer32
   UNITS       "seconds"
   MAX-ACCESS  read-write
   STATUS      current
   DESCRIPTION
      "Path: line.editConf.retrain.errorPersistenceTime

       unit name = seconds"
   ::= {er1645v2ShLineLimRetrainEntry 33554432}

er1645v2ShLineLimRetrainErrThresh OBJECT-TYPE
   SYNTAX      Integer32
   UNITS       "proMille"
   MAX-ACCESS  read-write
   STATUS      current
   DESCRIPTION
      "Path: line.editConf.retrain.errorThreshold

       unit name = proMille"
   ::= {er1645v2ShLineLimRetrainEntry 50331648}

er1645v2ShLineLimRetrainNmThresh OBJECT-TYPE
   SYNTAX      INTEGER
               {
               sm2dB (-2),
               sm1dB (-1),
               s0dB (0),
               s1dB (1),
               s2dB (2),
               s3dB (3),
               s4dB (4),
               s5dB (5),
               s6dB (6),
               s7dB (7),
               s8dB (8),
               s9dB (9),
               s10dB (10),
               s11dB (11),
               s12dB (12),
               s13dB (13),
               s14dB (14),
               s15dB (15)
               }
   MAX-ACCESS  read-write
   STATUS      current
   DESCRIPTION
      "Path: line.editConf.retrain.noiseMarginThreshold

       Possibilities:
               -2dB   (-2)
               -1dB   (-1)
               0dB   (0)
               1dB   (1)
               2dB   (2)
               3dB   (3)
               4dB   (4)
               5dB   (5)
               6dB   (6)
               7dB   (7)
               8dB   (8)
               9dB   (9)
               10dB   (10)
               11dB   (11)
               12dB   (12)
               13dB   (13)
               14dB   (14)
               15dB   (15)"
   ::= {er1645v2ShLineLimRetrainEntry 67108864}

er1645v2ShLineLimRetrainStepupMg OBJECT-TYPE
   SYNTAX      INTEGER
               {
               disabled (0),
               s3d0dB (6),
               s3d5dB (7),
               s4d0dB (8),
               s4d5dB (9),
               s5d0dB (10),
               s5d5dB (11),
               s6d0dB (12),
               s6d5dB (13),
               s7d0dB (14),
               s7d5dB (15),
               s8d0dB (16),
               s8d5dB (17),
               s9d0dB (18),
               s9d5dB (19),
               s10d0dB (20),
               s10d5dB (21),
               s11d0dB (22),
               s11d5dB (23),
               s12d0dB (24),
               s12d5dB (25),
               s13d0dB (26),
               s13d5dB (27),
               s14d0dB (28),
               s14d5dB (29),
               s15d0dB (30)
               }
   MAX-ACCESS  read-write
   STATUS      current
   DESCRIPTION
      "Path: line.editConf.retrain.stepupMargin

       Possibilities:
               disabled   (0)
               3.0dB   (6)
               3.5dB   (7)
               4.0dB   (8)
               4.5dB   (9)
               5.0dB   (10)
               5.5dB   (11)
               6.0dB   (12)
               6.5dB   (13)
               7.0dB   (14)
               7.5dB   (15)
               8.0dB   (16)
               8.5dB   (17)
               9.0dB   (18)
               9.5dB   (19)
               10.0dB   (20)
               10.5dB   (21)
               11.0dB   (22)
               11.5dB   (23)
               12.0dB   (24)
               12.5dB   (25)
               13.0dB   (26)
               13.5dB   (27)
               14.0dB   (28)
               14.5dB   (29)
               15.0dB   (30)"
   ::= {er1645v2ShLineLimRetrainEntry 83886080}


er1645v2ShLineLimMinLpSpeed OBJECT IDENTIFIER ::= {er1645v2ShLineLim 14}

er1645v2ShLineLimMinLpSpeedTable OBJECT-TYPE
   SYNTAX      SEQUENCE OF Er1645v2ShLineLimMinLpSpeedEntry
   MAX-ACCESS  not-accessible
   STATUS      current
   DESCRIPTION
      "min speed which should be used by each linepair"
   ::= {er1645v2ShLineLimMinLpSpeed 1}

er1645v2ShLineLimMinLpSpeedEntry OBJECT-TYPE
   SYNTAX      Er1645v2ShLineLimMinLpSpeedEntry
   MAX-ACCESS  not-accessible
   STATUS      current
   DESCRIPTION
      ""
   INDEX      { er1645v2ShLineLimMinLpSpeedGlobalIx }
   ::= {er1645v2ShLineLimMinLpSpeedTable 1}

Er1645v2ShLineLimMinLpSpeedEntry ::=
   SEQUENCE
      {
      er1645v2ShLineLimMinLpSpeedGlobalIx
         GlobalIndex,
      er1645v2ShLineLimMinLpSpeedValue
         INTEGER
      }

er1645v2ShLineLimMinLpSpeedGlobalIx OBJECT-TYPE
   SYNTAX      GlobalIndex
   MAX-ACCESS  not-accessible
   STATUS      current
   DESCRIPTION
      "The value of the tlsCntTreeGlobalIndex of the MANAGED OBJECT."
   ::= {er1645v2ShLineLimMinLpSpeedEntry 10}

er1645v2ShLineLimMinLpSpeedValue OBJECT-TYPE
   SYNTAX      INTEGER
               {
               s192kbps (3),
               s256kbps (4),
               s320kbps (5),
               s384kbps (6),
               s448kbps (7),
               s512kbps (8),
               s576kbps (9),
               s640kbps (10),
               s704kbps (11),
               s768kbps (12),
               s832kbps (13),
               s896kbps (14),
               s960kbps (15),
               s1024kbps (16),
               s1088kbps (17),
               s1152kbps (18),
               s1216kbps (19),
               s1280kbps (20),
               s1344kbps (21),
               s1408kbps (22),
               s1472kbps (23),
               s1536kbps (24),
               s1600kbps (25),
               s1664kbps (26),
               s1728kbps (27),
               s1792kbps (28),
               s1856kbps (29),
               s1920kbps (30),
               s1984kbps (31),
               s2048kbps (32),
               s2112kbps (33),
               s2176kbps (34),
               s2240kbps (35),
               s2304kbps (36),
               s2368kbps (37),
               s2432kbps (38),
               s2496kbps (39),
               s2560kbps (40),
               s2624kbps (41),
               s2688kbps (42),
               s2752kbps (43),
               s2816kbps (44),
               s2880kbps (45),
               s2944kbps (46),
               s3008kbps (47),
               s3072kbps (48),
               s3136kbps (49),
               s3200kbps (50),
               s3264kbps (51),
               s3328kbps (52),
               s3392kbps (53),
               s3456kbps (54),
               s3520kbps (55),
               s3584kbps (56),
               s3648kbps (57),
               s3712kbps (58),
               s3776kbps (59),
               s3840kbps (60),
               s3904kbps (61),
               s3968kbps (62),
               s4032kbps (63),
               s4096kbps (64),
               s4160kbps (65),
               s4224kbps (66),
               s4288kbps (67),
               s4352kbps (68),
               s4416kbps (69),
               s4480kbps (70),
               s4544kbps (71),
               s4608kbps (72),
               s4672kbps (73),
               s4736kbps (74),
               s4800kbps (75),
               s4864kbps (76),
               s4928kbps (77),
               s4992kbps (78),
               s5056kbps (79),
               s5120kbps (80),
               s5184kbps (81),
               s5248kbps (82),
               s5312kbps (83),
               s5376kbps (84),
               s5440kbps (85),
               s5504kbps (86),
               s5568kbps (87),
               s5632kbps (88),
               s5696kbps (89)
               }
   MAX-ACCESS  read-write
   STATUS      current
   DESCRIPTION
      "Path: line.editConf.minLinePairSpeed

       Possibilities:
               192kbps   (3)
               256kbps   (4)
               320kbps   (5)
               384kbps   (6)
               448kbps   (7)
               512kbps   (8)
               576kbps   (9)
               640kbps   (10)
               704kbps   (11)
               768kbps   (12)
               832kbps   (13)
               896kbps   (14)
               960kbps   (15)
               1024kbps   (16)
               1088kbps   (17)
               1152kbps   (18)
               1216kbps   (19)
               1280kbps   (20)
               1344kbps   (21)
               1408kbps   (22)
               1472kbps   (23)
               1536kbps   (24)
               1600kbps   (25)
               1664kbps   (26)
               1728kbps   (27)
               1792kbps   (28)
               1856kbps   (29)
               1920kbps   (30)
               1984kbps   (31)
               2048kbps   (32)
               2112kbps   (33)
               2176kbps   (34)
               2240kbps   (35)
               2304kbps   (36)
               2368kbps   (37)
               2432kbps   (38)
               2496kbps   (39)
               2560kbps   (40)
               2624kbps   (41)
               2688kbps   (42)
               2752kbps   (43)
               2816kbps   (44)
               2880kbps   (45)
               2944kbps   (46)
               3008kbps   (47)
               3072kbps   (48)
               3136kbps   (49)
               3200kbps   (50)
               3264kbps   (51)
               3328kbps   (52)
               3392kbps   (53)
               3456kbps   (54)
               3520kbps   (55)
               3584kbps   (56)
               3648kbps   (57)
               3712kbps   (58)
               3776kbps   (59)
               3840kbps   (60)
               3904kbps   (61)
               3968kbps   (62)
               4032kbps   (63)
               4096kbps   (64)
               4160kbps   (65)
               4224kbps   (66)
               4288kbps   (67)
               4352kbps   (68)
               4416kbps   (69)
               4480kbps   (70)
               4544kbps   (71)
               4608kbps   (72)
               4672kbps   (73)
               4736kbps   (74)
               4800kbps   (75)
               4864kbps   (76)
               4928kbps   (77)
               4992kbps   (78)
               5056kbps   (79)
               5120kbps   (80)
               5184kbps   (81)
               5248kbps   (82)
               5312kbps   (83)
               5376kbps   (84)
               5440kbps   (85)
               5504kbps   (86)
               5568kbps   (87)
               5632kbps   (88)
               5696kbps   (89)"
   ::= {er1645v2ShLineLimMinLpSpeedEntry 2147483648}


er1645v2ShLineLimMaxLpSpeed OBJECT IDENTIFIER ::= {er1645v2ShLineLim 402}

er1645v2ShLineLimMaxLpSpeedTable OBJECT-TYPE
   SYNTAX      SEQUENCE OF Er1645v2ShLineLimMaxLpSpeedEntry
   MAX-ACCESS  not-accessible
   STATUS      current
   DESCRIPTION
      "min speed which should be used by each linepair"
   ::= {er1645v2ShLineLimMaxLpSpeed 1}

er1645v2ShLineLimMaxLpSpeedEntry OBJECT-TYPE
   SYNTAX      Er1645v2ShLineLimMaxLpSpeedEntry
   MAX-ACCESS  not-accessible
   STATUS      current
   DESCRIPTION
      ""
   INDEX      { er1645v2ShLineLimMaxLpSpeedGlobalIx }
   ::= {er1645v2ShLineLimMaxLpSpeedTable 1}

Er1645v2ShLineLimMaxLpSpeedEntry ::=
   SEQUENCE
      {
      er1645v2ShLineLimMaxLpSpeedGlobalIx
         GlobalIndex,
      er1645v2ShLineLimMaxLpSpeedValue
         INTEGER
      }

er1645v2ShLineLimMaxLpSpeedGlobalIx OBJECT-TYPE
   SYNTAX      GlobalIndex
   MAX-ACCESS  not-accessible
   STATUS      current
   DESCRIPTION
      "The value of the tlsCntTreeGlobalIndex of the MANAGED OBJECT."
   ::= {er1645v2ShLineLimMaxLpSpeedEntry 10}

er1645v2ShLineLimMaxLpSpeedValue OBJECT-TYPE
   SYNTAX      INTEGER
               {
               s192kbps (3),
               s256kbps (4),
               s320kbps (5),
               s384kbps (6),
               s448kbps (7),
               s512kbps (8),
               s576kbps (9),
               s640kbps (10),
               s704kbps (11),
               s768kbps (12),
               s832kbps (13),
               s896kbps (14),
               s960kbps (15),
               s1024kbps (16),
               s1088kbps (17),
               s1152kbps (18),
               s1216kbps (19),
               s1280kbps (20),
               s1344kbps (21),
               s1408kbps (22),
               s1472kbps (23),
               s1536kbps (24),
               s1600kbps (25),
               s1664kbps (26),
               s1728kbps (27),
               s1792kbps (28),
               s1856kbps (29),
               s1920kbps (30),
               s1984kbps (31),
               s2048kbps (32),
               s2112kbps (33),
               s2176kbps (34),
               s2240kbps (35),
               s2304kbps (36),
               s2368kbps (37),
               s2432kbps (38),
               s2496kbps (39),
               s2560kbps (40),
               s2624kbps (41),
               s2688kbps (42),
               s2752kbps (43),
               s2816kbps (44),
               s2880kbps (45),
               s2944kbps (46),
               s3008kbps (47),
               s3072kbps (48),
               s3136kbps (49),
               s3200kbps (50),
               s3264kbps (51),
               s3328kbps (52),
               s3392kbps (53),
               s3456kbps (54),
               s3520kbps (55),
               s3584kbps (56),
               s3648kbps (57),
               s3712kbps (58),
               s3776kbps (59),
               s3840kbps (60),
               s3904kbps (61),
               s3968kbps (62),
               s4032kbps (63),
               s4096kbps (64),
               s4160kbps (65),
               s4224kbps (66),
               s4288kbps (67),
               s4352kbps (68),
               s4416kbps (69),
               s4480kbps (70),
               s4544kbps (71),
               s4608kbps (72),
               s4672kbps (73),
               s4736kbps (74),
               s4800kbps (75),
               s4864kbps (76),
               s4928kbps (77),
               s4992kbps (78),
               s5056kbps (79),
               s5120kbps (80),
               s5184kbps (81),
               s5248kbps (82),
               s5312kbps (83),
               s5376kbps (84),
               s5440kbps (85),
               s5504kbps (86),
               s5568kbps (87),
               s5632kbps (88),
               s5696kbps (89)
               }
   MAX-ACCESS  read-write
   STATUS      current
   DESCRIPTION
      "Path: line.editConf.maxLinePairSpeed

       Possibilities:
               192kbps   (3)
               256kbps   (4)
               320kbps   (5)
               384kbps   (6)
               448kbps   (7)
               512kbps   (8)
               576kbps   (9)
               640kbps   (10)
               704kbps   (11)
               768kbps   (12)
               832kbps   (13)
               896kbps   (14)
               960kbps   (15)
               1024kbps   (16)
               1088kbps   (17)
               1152kbps   (18)
               1216kbps   (19)
               1280kbps   (20)
               1344kbps   (21)
               1408kbps   (22)
               1472kbps   (23)
               1536kbps   (24)
               1600kbps   (25)
               1664kbps   (26)
               1728kbps   (27)
               1792kbps   (28)
               1856kbps   (29)
               1920kbps   (30)
               1984kbps   (31)
               2048kbps   (32)
               2112kbps   (33)
               2176kbps   (34)
               2240kbps   (35)
               2304kbps   (36)
               2368kbps   (37)
               2432kbps   (38)
               2496kbps   (39)
               2560kbps   (40)
               2624kbps   (41)
               2688kbps   (42)
               2752kbps   (43)
               2816kbps   (44)
               2880kbps   (45)
               2944kbps   (46)
               3008kbps   (47)
               3072kbps   (48)
               3136kbps   (49)
               3200kbps   (50)
               3264kbps   (51)
               3328kbps   (52)
               3392kbps   (53)
               3456kbps   (54)
               3520kbps   (55)
               3584kbps   (56)
               3648kbps   (57)
               3712kbps   (58)
               3776kbps   (59)
               3840kbps   (60)
               3904kbps   (61)
               3968kbps   (62)
               4032kbps   (63)
               4096kbps   (64)
               4160kbps   (65)
               4224kbps   (66)
               4288kbps   (67)
               4352kbps   (68)
               4416kbps   (69)
               4480kbps   (70)
               4544kbps   (71)
               4608kbps   (72)
               4672kbps   (73)
               4736kbps   (74)
               4800kbps   (75)
               4864kbps   (76)
               4928kbps   (77)
               4992kbps   (78)
               5056kbps   (79)
               5120kbps   (80)
               5184kbps   (81)
               5248kbps   (82)
               5312kbps   (83)
               5376kbps   (84)
               5440kbps   (85)
               5504kbps   (86)
               5568kbps   (87)
               5632kbps   (88)
               5696kbps   (89)"
   ::= {er1645v2ShLineLimMaxLpSpeedEntry 2147483648}


er1645v2ShLineLimAutoConfig OBJECT IDENTIFIER ::= {er1645v2ShLineLim 412}

er1645v2ShLineLimAutoConfigSSCTable OBJECT-TYPE
   SYNTAX      SEQUENCE OF Er1645v2ShLineLimAutoConfigEntry
   MAX-ACCESS  not-accessible
   STATUS      current
   DESCRIPTION
      "autoConfig "
   ::= {er1645v2ShLineLimAutoConfig 1}

er1645v2ShLineLimAutoConfigEntry OBJECT-TYPE
   SYNTAX      Er1645v2ShLineLimAutoConfigEntry
   MAX-ACCESS  not-accessible
   STATUS      current
   DESCRIPTION
      ""
   INDEX      { er1645v2ShLineLimAutoConfigGlobalIx }
   ::= {er1645v2ShLineLimAutoConfigSSCTable 1}

Er1645v2ShLineLimAutoConfigEntry ::=
   SEQUENCE
      {
      er1645v2ShLineLimAutoConfigGlobalIx
         GlobalIndex,
      er1645v2ShLineLimAutoConfigOperation
         INTEGER,
      er1645v2ShLineLimAutoConfigInitialWireMode
         INTEGER
      }

er1645v2ShLineLimAutoConfigGlobalIx OBJECT-TYPE
   SYNTAX      GlobalIndex
   MAX-ACCESS  not-accessible
   STATUS      current
   DESCRIPTION
      "The value of the tlsCntTreeGlobalIndex of the MANAGED OBJECT."
   ::= {er1645v2ShLineLimAutoConfigEntry 10}

er1645v2ShLineLimAutoConfigOperation OBJECT-TYPE
   SYNTAX      INTEGER
               {
               disabled (0),
               enabled (1)
               }
   MAX-ACCESS  read-write
   STATUS      current
   DESCRIPTION
      "Path: line.editConf.autoConfig.operation

       Possibilities:
               disabled   (0)
               enabled   (1)"
   ::= {er1645v2ShLineLimAutoConfigEntry 16777216}

er1645v2ShLineLimAutoConfigInitialWireMode OBJECT-TYPE
   SYNTAX      INTEGER
               {
               singlePair (1),
               multiPair (2)
               }
   MAX-ACCESS  read-write
   STATUS      current
   DESCRIPTION
      "Path: line.editConf.autoConfig.initialWireMode

       Possibilities:
               singlePair   (1)
               multiPair   (2)"
   ::= {er1645v2ShLineLimAutoConfigEntry 33554432}


er1645v2ShLineLimModulation OBJECT IDENTIFIER ::= {er1645v2ShLineLim 401}

er1645v2ShLineLimModulationTable OBJECT-TYPE
   SYNTAX      SEQUENCE OF Er1645v2ShLineLimModulationEntry
   MAX-ACCESS  not-accessible
   STATUS      current
   DESCRIPTION
      "modulation selection"
   ::= {er1645v2ShLineLimModulation 1}

er1645v2ShLineLimModulationEntry OBJECT-TYPE
   SYNTAX      Er1645v2ShLineLimModulationEntry
   MAX-ACCESS  not-accessible
   STATUS      current
   DESCRIPTION
      ""
   INDEX      { er1645v2ShLineLimModulationGlobalIx }
   ::= {er1645v2ShLineLimModulationTable 1}

Er1645v2ShLineLimModulationEntry ::=
   SEQUENCE
      {
      er1645v2ShLineLimModulationGlobalIx
         GlobalIndex,
      er1645v2ShLineLimModulationValue
         INTEGER
      }

er1645v2ShLineLimModulationGlobalIx OBJECT-TYPE
   SYNTAX      GlobalIndex
   MAX-ACCESS  not-accessible
   STATUS      current
   DESCRIPTION
      "The value of the tlsCntTreeGlobalIndex of the MANAGED OBJECT."
   ::= {er1645v2ShLineLimModulationEntry 10}

er1645v2ShLineLimModulationValue OBJECT-TYPE
   SYNTAX      INTEGER
               {
               auto (0),
               tcmpam16 (1),
               tcmpam32 (2)
               }
   MAX-ACCESS  read-write
   STATUS      current
   DESCRIPTION
      "Path: line.editConf.modulation

       Possibilities:
               auto   (0)
               tc-pam16   (1)
               tc-pam32   (2)"
   ::= {er1645v2ShLineLimModulationEntry 2147483648}


er1645v2ShLineLimLineProbing OBJECT IDENTIFIER ::= {er1645v2ShLineLim 415}

er1645v2ShLineLimLineProbingTable OBJECT-TYPE
   SYNTAX      SEQUENCE OF Er1645v2ShLineLimLineProbingEntry
   MAX-ACCESS  not-accessible
   STATUS      current
   DESCRIPTION
      "Line Probing"
   ::= {er1645v2ShLineLimLineProbing 1}

er1645v2ShLineLimLineProbingEntry OBJECT-TYPE
   SYNTAX      Er1645v2ShLineLimLineProbingEntry
   MAX-ACCESS  not-accessible
   STATUS      current
   DESCRIPTION
      ""
   INDEX      { er1645v2ShLineLimLineProbingGlobalIx }
   ::= {er1645v2ShLineLimLineProbingTable 1}

Er1645v2ShLineLimLineProbingEntry ::=
   SEQUENCE
      {
      er1645v2ShLineLimLineProbingGlobalIx
         GlobalIndex,
      er1645v2ShLineLimLineProbingValue
         INTEGER
      }

er1645v2ShLineLimLineProbingGlobalIx OBJECT-TYPE
   SYNTAX      GlobalIndex
   MAX-ACCESS  not-accessible
   STATUS      current
   DESCRIPTION
      "The value of the tlsCntTreeGlobalIndex of the MANAGED OBJECT."
   ::= {er1645v2ShLineLimLineProbingEntry 10}

er1645v2ShLineLimLineProbingValue OBJECT-TYPE
   SYNTAX      INTEGER
               {
               normal (0),
               adaptive (1),
               simulated (2)
               }
   MAX-ACCESS  read-write
   STATUS      current
   DESCRIPTION
      "Path: line.editConf.lineProbing

       Possibilities:
               normal   (0)
               adaptive   (1)
               simulated   (2)"
   ::= {er1645v2ShLineLimLineProbingEntry 2147483648}


er1645v2ShLineLimAlarmMask OBJECT IDENTIFIER ::= {er1645v2ShLineLim 10}

er1645v2ShLineLimAlarmMaskTable OBJECT-TYPE
   SYNTAX      SEQUENCE OF Er1645v2ShLineLimAlarmMaskEntry
   MAX-ACCESS  not-accessible
   STATUS      current
   DESCRIPTION
      "lineAlarmMask"
   ::= {er1645v2ShLineLimAlarmMask 1}

er1645v2ShLineLimAlarmMaskEntry OBJECT-TYPE
   SYNTAX      Er1645v2ShLineLimAlarmMaskEntry
   MAX-ACCESS  not-accessible
   STATUS      current
   DESCRIPTION
      ""
   INDEX      { er1645v2ShLineLimAlarmMaskGlobalIx }
   ::= {er1645v2ShLineLimAlarmMaskTable 1}

Er1645v2ShLineLimAlarmMaskEntry ::=
   SEQUENCE
      {
      er1645v2ShLineLimAlarmMaskGlobalIx
         GlobalIndex,
      er1645v2ShLineLimAlarmMaskValue
         Integer32
      }

er1645v2ShLineLimAlarmMaskGlobalIx OBJECT-TYPE
   SYNTAX      GlobalIndex
   MAX-ACCESS  not-accessible
   STATUS      current
   DESCRIPTION
      "The value of the tlsCntTreeGlobalIndex of the MANAGED OBJECT."
   ::= {er1645v2ShLineLimAlarmMaskEntry 10}

er1645v2ShLineLimAlarmMaskValue OBJECT-TYPE
   SYNTAX      Integer32
   MAX-ACCESS  read-write
   STATUS      current
   DESCRIPTION
      "Path: line.editConf.alarmMask

       Bit meanings:
               bit 0 = linkDown,
               bit 1 = invalidNumRepeaters,
               bit 11 = remotePowerFail,
               bit 12 = aggregatedIfSpeed"
   ::= {er1645v2ShLineLimAlarmMaskEntry 2147483648}


er1645v2ShLineLimAlarmLevel OBJECT IDENTIFIER ::= {er1645v2ShLineLim 61}

er1645v2ShLineLimAlarmLevelSSCTable OBJECT-TYPE
   SYNTAX      SEQUENCE OF Er1645v2ShLineLimAlarmLevelEntry
   MAX-ACCESS  not-accessible
   STATUS      current
   DESCRIPTION
      "lineAlarmLevel"
   ::= {er1645v2ShLineLimAlarmLevel 1}

er1645v2ShLineLimAlarmLevelEntry OBJECT-TYPE
   SYNTAX      Er1645v2ShLineLimAlarmLevelEntry
   MAX-ACCESS  not-accessible
   STATUS      current
   DESCRIPTION
      ""
   INDEX      { er1645v2ShLineLimAlarmLevelGlobalIx }
   ::= {er1645v2ShLineLimAlarmLevelSSCTable 1}

Er1645v2ShLineLimAlarmLevelEntry ::=
   SEQUENCE
      {
      er1645v2ShLineLimAlarmLevelGlobalIx
         GlobalIndex,
      er1645v2ShLineLimAlarmLevelLnkDwn
         Integer32,
      er1645v2ShLineLimAlarmLevelInvNRep
         Integer32,
      er1645v2ShLineLimAlarmLevelRemPowFl
         Integer32,
      er1645v2ShLineLimAlarmLevelAggSpd
         Integer32
      }

er1645v2ShLineLimAlarmLevelGlobalIx OBJECT-TYPE
   SYNTAX      GlobalIndex
   MAX-ACCESS  not-accessible
   STATUS      current
   DESCRIPTION
      "The value of the tlsCntTreeGlobalIndex of the MANAGED OBJECT."
   ::= {er1645v2ShLineLimAlarmLevelEntry 10}

er1645v2ShLineLimAlarmLevelLnkDwn OBJECT-TYPE
   SYNTAX      Integer32
   MAX-ACCESS  read-write
   STATUS      current
   DESCRIPTION
      "Path: line.editConf.alarmLevel.linkDown"
   ::= {er1645v2ShLineLimAlarmLevelEntry 16777216}

er1645v2ShLineLimAlarmLevelInvNRep OBJECT-TYPE
   SYNTAX      Integer32
   MAX-ACCESS  read-write
   STATUS      current
   DESCRIPTION
      "Path: line.editConf.alarmLevel.invalidNumRepeaters"
   ::= {er1645v2ShLineLimAlarmLevelEntry 33554432}

er1645v2ShLineLimAlarmLevelRemPowFl OBJECT-TYPE
   SYNTAX      Integer32
   MAX-ACCESS  read-write
   STATUS      current
   DESCRIPTION
      "Path: line.editConf.alarmLevel.remotePowerFail"
   ::= {er1645v2ShLineLimAlarmLevelEntry 201326592}

er1645v2ShLineLimAlarmLevelAggSpd OBJECT-TYPE
   SYNTAX      Integer32
   MAX-ACCESS  read-write
   STATUS      current
   DESCRIPTION
      "Path: line.editConf.alarmLevel.aggregatedIfSpeed"
   ::= {er1645v2ShLineLimAlarmLevelEntry 218103808}


er1645v2ShLineLimELpAlmMsk OBJECT IDENTIFIER ::= {er1645v2ShLineLim 89}

er1645v2ShLineLimELpAlmMskTable OBJECT-TYPE
   SYNTAX      SEQUENCE OF Er1645v2ShLineLimELpAlmMskEntry
   MAX-ACCESS  not-accessible
   STATUS      current
   DESCRIPTION
      "linePairAlarmMask"
   ::= {er1645v2ShLineLimELpAlmMsk 1}

er1645v2ShLineLimELpAlmMskEntry OBJECT-TYPE
   SYNTAX      Er1645v2ShLineLimELpAlmMskEntry
   MAX-ACCESS  not-accessible
   STATUS      current
   DESCRIPTION
      ""
   INDEX      { er1645v2ShLineLimELpAlmMskGlobalIx }
   ::= {er1645v2ShLineLimELpAlmMskTable 1}

Er1645v2ShLineLimELpAlmMskEntry ::=
   SEQUENCE
      {
      er1645v2ShLineLimELpAlmMskGlobalIx
         GlobalIndex,
      er1645v2ShLineLimELpAlmMskValue
         Integer32
      }

er1645v2ShLineLimELpAlmMskGlobalIx OBJECT-TYPE
   SYNTAX      GlobalIndex
   MAX-ACCESS  not-accessible
   STATUS      current
   DESCRIPTION
      "The value of the tlsCntTreeGlobalIndex of the MANAGED OBJECT."
   ::= {er1645v2ShLineLimELpAlmMskEntry 10}

er1645v2ShLineLimELpAlmMskValue OBJECT-TYPE
   SYNTAX      Integer32
   MAX-ACCESS  read-write
   STATUS      current
   DESCRIPTION
      "Path: line.editConf.endLinePairAlarmMask

       Bit meanings:
               bit 1 = lineAttenuation,
               bit 2 = noiseMargin,
               bit 3 = errSecRatioExceeded,
               bit 4 = sevErrSecRatioExceeded,
               bit 5 = bBErrRatioExceeded"
   ::= {er1645v2ShLineLimELpAlmMskEntry 2147483648}


er1645v2ShLineLimELpAlmLev OBJECT IDENTIFIER ::= {er1645v2ShLineLim 88}

er1645v2ShLineLimELpAlmLevSSCTable OBJECT-TYPE
   SYNTAX      SEQUENCE OF Er1645v2ShLineLimELpAlmLevEntry
   MAX-ACCESS  not-accessible
   STATUS      current
   DESCRIPTION
      "linePairAlarmLevel"
   ::= {er1645v2ShLineLimELpAlmLev 1}

er1645v2ShLineLimELpAlmLevEntry OBJECT-TYPE
   SYNTAX      Er1645v2ShLineLimELpAlmLevEntry
   MAX-ACCESS  not-accessible
   STATUS      current
   DESCRIPTION
      ""
   INDEX      { er1645v2ShLineLimELpAlmLevGlobalIx }
   ::= {er1645v2ShLineLimELpAlmLevSSCTable 1}

Er1645v2ShLineLimELpAlmLevEntry ::=
   SEQUENCE
      {
      er1645v2ShLineLimELpAlmLevGlobalIx
         GlobalIndex,
      er1645v2ShLineLimELpAlmLevLpatt
         Integer32,
      er1645v2ShLineLimELpAlmLevNm
         Integer32,
      er1645v2ShLineLimELpAlmLevEsrExc
         Integer32,
      er1645v2ShLineLimELpAlmLevSesrExc
         Integer32,
      er1645v2ShLineLimELpAlmLevBberExc
         Integer32
      }

er1645v2ShLineLimELpAlmLevGlobalIx OBJECT-TYPE
   SYNTAX      GlobalIndex
   MAX-ACCESS  not-accessible
   STATUS      current
   DESCRIPTION
      "The value of the tlsCntTreeGlobalIndex of the MANAGED OBJECT."
   ::= {er1645v2ShLineLimELpAlmLevEntry 10}

er1645v2ShLineLimELpAlmLevLpatt OBJECT-TYPE
   SYNTAX      Integer32
   MAX-ACCESS  read-write
   STATUS      current
   DESCRIPTION
      "Path: line.editConf.endLinePairAlarmLevel.lineAttenuation"
   ::= {er1645v2ShLineLimELpAlmLevEntry 33554432}

er1645v2ShLineLimELpAlmLevNm OBJECT-TYPE
   SYNTAX      Integer32
   MAX-ACCESS  read-write
   STATUS      current
   DESCRIPTION
      "Path: line.editConf.endLinePairAlarmLevel.noiseMargin"
   ::= {er1645v2ShLineLimELpAlmLevEntry 50331648}

er1645v2ShLineLimELpAlmLevEsrExc OBJECT-TYPE
   SYNTAX      Integer32
   MAX-ACCESS  read-write
   STATUS      current
   DESCRIPTION
      "Path: line.editConf.endLinePairAlarmLevel.errSecRatioExceeded"
   ::= {er1645v2ShLineLimELpAlmLevEntry 67108864}

er1645v2ShLineLimELpAlmLevSesrExc OBJECT-TYPE
   SYNTAX      Integer32
   MAX-ACCESS  read-write
   STATUS      current
   DESCRIPTION
      "Path: line.editConf.endLinePairAlarmLevel.sevErrSecRatioExceeded"
   ::= {er1645v2ShLineLimELpAlmLevEntry 83886080}

er1645v2ShLineLimELpAlmLevBberExc OBJECT-TYPE
   SYNTAX      Integer32
   MAX-ACCESS  read-write
   STATUS      current
   DESCRIPTION
      "Path: line.editConf.endLinePairAlarmLevel.bBErrRatioExceeded"
   ::= {er1645v2ShLineLimELpAlmLevEntry 100663296}


er1645v2ShLineLimRpLpAlmMsk OBJECT IDENTIFIER ::= {er1645v2ShLineLim 87}

er1645v2ShLineLimRpLpAlmMskTable OBJECT-TYPE
   SYNTAX      SEQUENCE OF Er1645v2ShLineLimRpLpAlmMskEntry
   MAX-ACCESS  not-accessible
   STATUS      current
   DESCRIPTION
      "linePairAlarmMask"
   ::= {er1645v2ShLineLimRpLpAlmMsk 1}

er1645v2ShLineLimRpLpAlmMskEntry OBJECT-TYPE
   SYNTAX      Er1645v2ShLineLimRpLpAlmMskEntry
   MAX-ACCESS  not-accessible
   STATUS      current
   DESCRIPTION
      ""
   INDEX      { er1645v2ShLineLimRpLpAlmMskGlobalIx }
   ::= {er1645v2ShLineLimRpLpAlmMskTable 1}

Er1645v2ShLineLimRpLpAlmMskEntry ::=
   SEQUENCE
      {
      er1645v2ShLineLimRpLpAlmMskGlobalIx
         GlobalIndex,
      er1645v2ShLineLimRpLpAlmMskValue
         Integer32
      }

er1645v2ShLineLimRpLpAlmMskGlobalIx OBJECT-TYPE
   SYNTAX      GlobalIndex
   MAX-ACCESS  not-accessible
   STATUS      current
   DESCRIPTION
      "The value of the tlsCntTreeGlobalIndex of the MANAGED OBJECT."
   ::= {er1645v2ShLineLimRpLpAlmMskEntry 10}

er1645v2ShLineLimRpLpAlmMskValue OBJECT-TYPE
   SYNTAX      Integer32
   MAX-ACCESS  read-write
   STATUS      current
   DESCRIPTION
      "Path: line.editConf.repeaterLinePairAlarmMask

       Bit meanings:
               bit 1 = lineAttenuation,
               bit 2 = noiseMargin,
               bit 3 = errSecRatioExceeded,
               bit 4 = sevErrSecRatioExceeded,
               bit 5 = bBErrRatioExceeded"
   ::= {er1645v2ShLineLimRpLpAlmMskEntry 2147483648}


er1645v2ShLineLimRpLpAlmLev OBJECT IDENTIFIER ::= {er1645v2ShLineLim 86}

er1645v2ShLineLimRpLpAlmLevSSCTable OBJECT-TYPE
   SYNTAX      SEQUENCE OF Er1645v2ShLineLimRpLpAlmLevEntry
   MAX-ACCESS  not-accessible
   STATUS      current
   DESCRIPTION
      "linePairAlarmLevel"
   ::= {er1645v2ShLineLimRpLpAlmLev 1}

er1645v2ShLineLimRpLpAlmLevEntry OBJECT-TYPE
   SYNTAX      Er1645v2ShLineLimRpLpAlmLevEntry
   MAX-ACCESS  not-accessible
   STATUS      current
   DESCRIPTION
      ""
   INDEX      { er1645v2ShLineLimRpLpAlmLevGlobalIx }
   ::= {er1645v2ShLineLimRpLpAlmLevSSCTable 1}

Er1645v2ShLineLimRpLpAlmLevEntry ::=
   SEQUENCE
      {
      er1645v2ShLineLimRpLpAlmLevGlobalIx
         GlobalIndex,
      er1645v2ShLineLimRpLpAlmLevLpatt
         Integer32,
      er1645v2ShLineLimRpLpAlmLevNm
         Integer32,
      er1645v2ShLineLimRpLpAlmLevEsrExc
         Integer32,
      er1645v2ShLineLimRpLpAlmLevSesrExc
         Integer32,
      er1645v2ShLineLimRpLpAlmLevBberExc
         Integer32
      }

er1645v2ShLineLimRpLpAlmLevGlobalIx OBJECT-TYPE
   SYNTAX      GlobalIndex
   MAX-ACCESS  not-accessible
   STATUS      current
   DESCRIPTION
      "The value of the tlsCntTreeGlobalIndex of the MANAGED OBJECT."
   ::= {er1645v2ShLineLimRpLpAlmLevEntry 10}

er1645v2ShLineLimRpLpAlmLevLpatt OBJECT-TYPE
   SYNTAX      Integer32
   MAX-ACCESS  read-write
   STATUS      current
   DESCRIPTION
      "Path: line.editConf.repeaterLinePairAlarmLevel.lineAttenuation"
   ::= {er1645v2ShLineLimRpLpAlmLevEntry 33554432}

er1645v2ShLineLimRpLpAlmLevNm OBJECT-TYPE
   SYNTAX      Integer32
   MAX-ACCESS  read-write
   STATUS      current
   DESCRIPTION
      "Path: line.editConf.repeaterLinePairAlarmLevel.noiseMargin"
   ::= {er1645v2ShLineLimRpLpAlmLevEntry 50331648}

er1645v2ShLineLimRpLpAlmLevEsrExc OBJECT-TYPE
   SYNTAX      Integer32
   MAX-ACCESS  read-write
   STATUS      current
   DESCRIPTION
      "Path: line.editConf.repeaterLinePairAlarmLevel.errSecRatioExceeded"
   ::= {er1645v2ShLineLimRpLpAlmLevEntry 67108864}

er1645v2ShLineLimRpLpAlmLevSesrExc OBJECT-TYPE
   SYNTAX      Integer32
   MAX-ACCESS  read-write
   STATUS      current
   DESCRIPTION
      "Path: line.editConf.repeaterLinePairAlarmLevel.sevErrSecRatioExceeded"
   ::= {er1645v2ShLineLimRpLpAlmLevEntry 83886080}

er1645v2ShLineLimRpLpAlmLevBberExc OBJECT-TYPE
   SYNTAX      Integer32
   MAX-ACCESS  read-write
   STATUS      current
   DESCRIPTION
      "Path: line.editConf.repeaterLinePairAlarmLevel.bBErrRatioExceeded"
   ::= {er1645v2ShLineLimRpLpAlmLevEntry 100663296}


er1645v2ShLineLimExtendedRates OBJECT IDENTIFIER ::= {er1645v2ShLineLim 700}

er1645v2ShLineLimExtendedRatesSSCTable OBJECT-TYPE
   SYNTAX      SEQUENCE OF Er1645v2ShLineLimExtendedRatesEntry
   MAX-ACCESS  not-accessible
   STATUS      current
   DESCRIPTION
      "Extended rates configuration"
   ::= {er1645v2ShLineLimExtendedRates 1}

er1645v2ShLineLimExtendedRatesEntry OBJECT-TYPE
   SYNTAX      Er1645v2ShLineLimExtendedRatesEntry
   MAX-ACCESS  not-accessible
   STATUS      current
   DESCRIPTION
      ""
   INDEX      { er1645v2ShLineLimExtendedRatesGlobalIx }
   ::= {er1645v2ShLineLimExtendedRatesSSCTable 1}

Er1645v2ShLineLimExtendedRatesEntry ::=
   SEQUENCE
      {
      er1645v2ShLineLimExtendedRatesGlobalIx
         GlobalIndex,
      er1645v2ShLineLimExtendedRatesMode
         INTEGER,
      er1645v2ShLineLimExtendedRatesFixedRate
         Integer32,
      er1645v2ShLineLimExtendedRatesFixedModulation
         INTEGER,
      er1645v2ShLineLimExtendedRatesAdaptiveMaxmrate
         Integer32,
      er1645v2ShLineLimExtendedRatesAdaptiveModulation
         Integer32,
      er1645v2ShLineLimExtendedRatesAdaptiveMaxmbaudrate
         Integer32
      }

er1645v2ShLineLimExtendedRatesGlobalIx OBJECT-TYPE
   SYNTAX      GlobalIndex
   MAX-ACCESS  not-accessible
   STATUS      current
   DESCRIPTION
      "The value of the tlsCntTreeGlobalIndex of the MANAGED OBJECT."
   ::= {er1645v2ShLineLimExtendedRatesEntry 10}

er1645v2ShLineLimExtendedRatesMode OBJECT-TYPE
   SYNTAX      INTEGER
               {
               disabled (0),
               fixed (1),
               adaptive (2)
               }
   MAX-ACCESS  read-write
   STATUS      current
   DESCRIPTION
      "Path: line.editConf.extendedRates.mode

       Possibilities:
               disabled   (0)
               fixed   (1)
               adaptive   (2)"
   ::= {er1645v2ShLineLimExtendedRatesEntry 16777216}

er1645v2ShLineLimExtendedRatesFixedRate OBJECT-TYPE
   SYNTAX      Integer32
   UNITS       "kbps"
   MAX-ACCESS  read-write
   STATUS      current
   DESCRIPTION
      "Path: line.editConf.extendedRates.fixed.rate

       unit name = kbps"
   ::= {er1645v2ShLineLimExtendedRatesEntry 33619968}

er1645v2ShLineLimExtendedRatesFixedModulation OBJECT-TYPE
   SYNTAX      INTEGER
               {
               tcmpam4 (1),
               tcmpam8 (2),
               tcmpam16 (3),
               tcmpam32 (4),
               tcmpam64 (5),
               tcmpam128 (6)
               }
   MAX-ACCESS  read-write
   STATUS      current
   DESCRIPTION
      "Path: line.editConf.extendedRates.fixed.modulation

       Possibilities:
               tc-pam4   (1)
               tc-pam8   (2)
               tc-pam16   (3)
               tc-pam32   (4)
               tc-pam64   (5)
               tc-pam128   (6)"
   ::= {er1645v2ShLineLimExtendedRatesEntry 33685504}

er1645v2ShLineLimExtendedRatesAdaptiveMaxmrate OBJECT-TYPE
   SYNTAX      Integer32
   UNITS       "kbps"
   MAX-ACCESS  read-write
   STATUS      current
   DESCRIPTION
      "Path: line.editConf.extendedRates.adaptive.max-rate

       unit name = kbps"
   ::= {er1645v2ShLineLimExtendedRatesEntry 50397184}

er1645v2ShLineLimExtendedRatesAdaptiveModulation OBJECT-TYPE
   SYNTAX      Integer32
   MAX-ACCESS  read-write
   STATUS      current
   DESCRIPTION
      "Path: line.editConf.extendedRates.adaptive.modulation

       Bit meanings:
               bit 0 = tc-pam4,
               bit 1 = tc-pam8,
               bit 2 = tc-pam16,
               bit 3 = tc-pam32,
               bit 4 = tc-pam64,
               bit 5 = tc-pam128"
   ::= {er1645v2ShLineLimExtendedRatesEntry 50462720}

er1645v2ShLineLimExtendedRatesAdaptiveMaxmbaudrate OBJECT-TYPE
   SYNTAX      Integer32
   UNITS       "ksyms/s"
   MAX-ACCESS  read-write
   STATUS      current
   DESCRIPTION
      "Path: line.editConf.extendedRates.adaptive.max-baudrate

       unit name = ksyms/s"
   ::= {er1645v2ShLineLimExtendedRatesEntry 50528256}


er1645v2ShLineLimCompatibility OBJECT IDENTIFIER ::= {er1645v2ShLineLim 407}

er1645v2ShLineLimCompatibilitySSCTable OBJECT-TYPE
   SYNTAX      SEQUENCE OF Er1645v2ShLineLimCompatibilityEntry
   MAX-ACCESS  not-accessible
   STATUS      current
   DESCRIPTION
      "Line Compatibility"
   ::= {er1645v2ShLineLimCompatibility 1}

er1645v2ShLineLimCompatibilityEntry OBJECT-TYPE
   SYNTAX      Er1645v2ShLineLimCompatibilityEntry
   MAX-ACCESS  not-accessible
   STATUS      current
   DESCRIPTION
      ""
   INDEX      { er1645v2ShLineLimCompatibilityGlobalIx }
   ::= {er1645v2ShLineLimCompatibilitySSCTable 1}

Er1645v2ShLineLimCompatibilityEntry ::=
   SEQUENCE
      {
      er1645v2ShLineLimCompatibilityGlobalIx
         GlobalIndex,
      er1645v2ShLineLimCompatibilityCapList
         INTEGER,
      er1645v2ShLineLimCompatibilityPmmsMode
         INTEGER,
      er1645v2ShLineLimCompatibilityFourWireMode
         INTEGER,
      er1645v2ShLineLimCompatibilityVendorSpecOctets
         OCTET STRING,
      er1645v2ShLineLimCompatibilityAutoWireMode
         INTEGER
      }

er1645v2ShLineLimCompatibilityGlobalIx OBJECT-TYPE
   SYNTAX      GlobalIndex
   MAX-ACCESS  not-accessible
   STATUS      current
   DESCRIPTION
      "The value of the tlsCntTreeGlobalIndex of the MANAGED OBJECT."
   ::= {er1645v2ShLineLimCompatibilityEntry 10}

er1645v2ShLineLimCompatibilityCapList OBJECT-TYPE
   SYNTAX      INTEGER
               {
               auto (2),
               newStyle (0),
               oldStyle (1)
               }
   MAX-ACCESS  read-write
   STATUS      current
   DESCRIPTION
      "Path: line.editConf.compatibility.capList

       Possibilities:
               auto   (2)
               newStyle   (0)
               oldStyle   (1)"
   ::= {er1645v2ShLineLimCompatibilityEntry 16777216}

er1645v2ShLineLimCompatibilityPmmsMode OBJECT-TYPE
   SYNTAX      INTEGER
               {
               normal (0),
               globespan (1)
               }
   MAX-ACCESS  read-write
   STATUS      current
   DESCRIPTION
      "Path: line.editConf.compatibility.pmmsMode

       Possibilities:
               normal   (0)
               globespan   (1)"
   ::= {er1645v2ShLineLimCompatibilityEntry 33554432}

er1645v2ShLineLimCompatibilityFourWireMode OBJECT-TYPE
   SYNTAX      INTEGER
               {
               auto (0),
               enhanced (1),
               standard (2)
               }
   MAX-ACCESS  read-write
   STATUS      current
   DESCRIPTION
      "Path: line.editConf.compatibility.fourWireMode

       Possibilities:
               auto   (0)
               enhanced   (1)
               standard   (2)"
   ::= {er1645v2ShLineLimCompatibilityEntry 50331648}

er1645v2ShLineLimCompatibilityVendorSpecOctets OBJECT-TYPE
   SYNTAX      OCTET STRING
   MAX-ACCESS  read-write
   STATUS      current
   DESCRIPTION
      "Path: line.editConf.compatibility.vendorSpecOctets"
   ::= {er1645v2ShLineLimCompatibilityEntry 67108864}

er1645v2ShLineLimCompatibilityAutoWireMode OBJECT-TYPE
   SYNTAX      INTEGER
               {
               mode0 (0),
               mode1 (1),
               mode2 (2)
               }
   MAX-ACCESS  read-write
   STATUS      current
   DESCRIPTION
      "Path: line.editConf.compatibility.autoWireMode

       Possibilities:
               mode0   (0)
               mode1   (1)
               mode2   (2)"
   ::= {er1645v2ShLineLimCompatibilityEntry 134217728}



pr1645v2ShLineLim OBJECT IDENTIFIER ::= {r1645v2ShLineLim 12}


pr1645v2ShLineLimH2 OBJECT IDENTIFIER ::= {pr1645v2ShLineLim 21}

pr1645v2ShLineLimH2SSCTable OBJECT-TYPE
   SYNTAX      SEQUENCE OF Pr1645v2ShLineLimH2Entry
   MAX-ACCESS  not-accessible
   STATUS      current
   DESCRIPTION
      "h2Line"
   ::= {pr1645v2ShLineLimH2 1}

pr1645v2ShLineLimH2Entry OBJECT-TYPE
   SYNTAX      Pr1645v2ShLineLimH2Entry
   MAX-ACCESS  not-accessible
   STATUS      current
   DESCRIPTION
      ""
   INDEX      { pr1645v2ShLineLimH2GlobalIx,
                pr1645v2ShLineLimH2TableIx }
   ::= {pr1645v2ShLineLimH2SSCTable 1}

Pr1645v2ShLineLimH2Entry ::=
   SEQUENCE
      {
      pr1645v2ShLineLimH2GlobalIx
         GlobalIndex,
      pr1645v2ShLineLimH2TableIx
         TableIndex,
      pr1645v2ShLineLimH2SysUpTime
         TimeTicks,
      pr1645v2ShLineLimH2LDownCnt
         Counter32,
      pr1645v2ShLineLimH2LDownTme
         TimeTicks
      }

pr1645v2ShLineLimH2GlobalIx OBJECT-TYPE
   SYNTAX      GlobalIndex
   MAX-ACCESS  not-accessible
   STATUS      current
   DESCRIPTION
      "The value of the tlsCntTreeGlobalIndex of the MANAGED OBJECT."
   ::= {pr1645v2ShLineLimH2Entry 10}

pr1645v2ShLineLimH2TableIx OBJECT-TYPE
   SYNTAX      TableIndex
   MAX-ACCESS  not-accessible
   STATUS      current
   DESCRIPTION
      ""
   ::= {pr1645v2ShLineLimH2Entry 11}

pr1645v2ShLineLimH2SysUpTime OBJECT-TYPE
   SYNTAX      TimeTicks
   MAX-ACCESS  read-only
   STATUS      current
   DESCRIPTION
      "Path: line.performance.h2Line.sysUpTime

       Time in centi-second."
   ::= {pr1645v2ShLineLimH2Entry 16777216}

pr1645v2ShLineLimH2LDownCnt OBJECT-TYPE
   SYNTAX      Counter32
   MAX-ACCESS  read-only
   STATUS      current
   DESCRIPTION
      "Path: line.performance.h2Line.linkDownCount

       32 bit unsigned wrappable counter."
   ::= {pr1645v2ShLineLimH2Entry 33554432}

pr1645v2ShLineLimH2LDownTme OBJECT-TYPE
   SYNTAX      TimeTicks
   MAX-ACCESS  read-only
   STATUS      current
   DESCRIPTION
      "Path: line.performance.h2Line.linkDownTime

       Time in centi-second."
   ::= {pr1645v2ShLineLimH2Entry 50331648}


pr1645v2ShLineLimH24 OBJECT IDENTIFIER ::= {pr1645v2ShLineLim 23}

pr1645v2ShLineLimH24SSCTable OBJECT-TYPE
   SYNTAX      SEQUENCE OF Pr1645v2ShLineLimH24Entry
   MAX-ACCESS  not-accessible
   STATUS      current
   DESCRIPTION
      "h24Line"
   ::= {pr1645v2ShLineLimH24 1}

pr1645v2ShLineLimH24Entry OBJECT-TYPE
   SYNTAX      Pr1645v2ShLineLimH24Entry
   MAX-ACCESS  not-accessible
   STATUS      current
   DESCRIPTION
      ""
   INDEX      { pr1645v2ShLineLimH24GlobalIx,
                pr1645v2ShLineLimH24TableIx }
   ::= {pr1645v2ShLineLimH24SSCTable 1}

Pr1645v2ShLineLimH24Entry ::=
   SEQUENCE
      {
      pr1645v2ShLineLimH24GlobalIx
         GlobalIndex,
      pr1645v2ShLineLimH24TableIx
         TableIndex,
      pr1645v2ShLineLimH24SysUpTime
         TimeTicks,
      pr1645v2ShLineLimH24LDownCnt
         Counter32,
      pr1645v2ShLineLimH24LDownTme
         TimeTicks
      }

pr1645v2ShLineLimH24GlobalIx OBJECT-TYPE
   SYNTAX      GlobalIndex
   MAX-ACCESS  not-accessible
   STATUS      current
   DESCRIPTION
      "The value of the tlsCntTreeGlobalIndex of the MANAGED OBJECT."
   ::= {pr1645v2ShLineLimH24Entry 10}

pr1645v2ShLineLimH24TableIx OBJECT-TYPE
   SYNTAX      TableIndex
   MAX-ACCESS  not-accessible
   STATUS      current
   DESCRIPTION
      ""
   ::= {pr1645v2ShLineLimH24Entry 11}

pr1645v2ShLineLimH24SysUpTime OBJECT-TYPE
   SYNTAX      TimeTicks
   MAX-ACCESS  read-only
   STATUS      current
   DESCRIPTION
      "Path: line.performance.h24Line.sysUpTime

       Time in centi-second."
   ::= {pr1645v2ShLineLimH24Entry 16777216}

pr1645v2ShLineLimH24LDownCnt OBJECT-TYPE
   SYNTAX      Counter32
   MAX-ACCESS  read-only
   STATUS      current
   DESCRIPTION
      "Path: line.performance.h24Line.linkDownCount

       32 bit unsigned wrappable counter."
   ::= {pr1645v2ShLineLimH24Entry 33554432}

pr1645v2ShLineLimH24LDownTme OBJECT-TYPE
   SYNTAX      TimeTicks
   MAX-ACCESS  read-only
   STATUS      current
   DESCRIPTION
      "Path: line.performance.h24Line.linkDownTime

       Time in centi-second."
   ::= {pr1645v2ShLineLimH24Entry 50331648}


pr1645v2ShLineLimD7 OBJECT IDENTIFIER ::= {pr1645v2ShLineLim 26}

pr1645v2ShLineLimD7SSCTable OBJECT-TYPE
   SYNTAX      SEQUENCE OF Pr1645v2ShLineLimD7Entry
   MAX-ACCESS  not-accessible
   STATUS      current
   DESCRIPTION
      "d7Line"
   ::= {pr1645v2ShLineLimD7 1}

pr1645v2ShLineLimD7Entry OBJECT-TYPE
   SYNTAX      Pr1645v2ShLineLimD7Entry
   MAX-ACCESS  not-accessible
   STATUS      current
   DESCRIPTION
      ""
   INDEX      { pr1645v2ShLineLimD7GlobalIx,
                pr1645v2ShLineLimD7TableIx }
   ::= {pr1645v2ShLineLimD7SSCTable 1}

Pr1645v2ShLineLimD7Entry ::=
   SEQUENCE
      {
      pr1645v2ShLineLimD7GlobalIx
         GlobalIndex,
      pr1645v2ShLineLimD7TableIx
         TableIndex,
      pr1645v2ShLineLimD7SysUpTime
         TimeTicks,
      pr1645v2ShLineLimD7LDownCnt
         Counter32,
      pr1645v2ShLineLimD7LDownTme
         TimeTicks
      }

pr1645v2ShLineLimD7GlobalIx OBJECT-TYPE
   SYNTAX      GlobalIndex
   MAX-ACCESS  not-accessible
   STATUS      current
   DESCRIPTION
      "The value of the tlsCntTreeGlobalIndex of the MANAGED OBJECT."
   ::= {pr1645v2ShLineLimD7Entry 10}

pr1645v2ShLineLimD7TableIx OBJECT-TYPE
   SYNTAX      TableIndex
   MAX-ACCESS  not-accessible
   STATUS      current
   DESCRIPTION
      ""
   ::= {pr1645v2ShLineLimD7Entry 11}

pr1645v2ShLineLimD7SysUpTime OBJECT-TYPE
   SYNTAX      TimeTicks
   MAX-ACCESS  read-only
   STATUS      current
   DESCRIPTION
      "Path: line.performance.d7Line.sysUpTime

       Time in centi-second."
   ::= {pr1645v2ShLineLimD7Entry 16777216}

pr1645v2ShLineLimD7LDownCnt OBJECT-TYPE
   SYNTAX      Counter32
   MAX-ACCESS  read-only
   STATUS      current
   DESCRIPTION
      "Path: line.performance.d7Line.linkDownCount

       32 bit unsigned wrappable counter."
   ::= {pr1645v2ShLineLimD7Entry 33554432}

pr1645v2ShLineLimD7LDownTme OBJECT-TYPE
   SYNTAX      TimeTicks
   MAX-ACCESS  read-only
   STATUS      current
   DESCRIPTION
      "Path: line.performance.d7Line.linkDownTime

       Time in centi-second."
   ::= {pr1645v2ShLineLimD7Entry 50331648}


pr1645v2ShLineLimRel OBJECT IDENTIFIER ::= {pr1645v2ShLineLim 30}

pr1645v2ShLineLimRelSSCTable OBJECT-TYPE
   SYNTAX      SEQUENCE OF Pr1645v2ShLineLimRelEntry
   MAX-ACCESS  not-accessible
   STATUS      current
   DESCRIPTION
      "relLine"
   ::= {pr1645v2ShLineLimRel 1}

pr1645v2ShLineLimRelEntry OBJECT-TYPE
   SYNTAX      Pr1645v2ShLineLimRelEntry
   MAX-ACCESS  not-accessible
   STATUS      current
   DESCRIPTION
      ""
   INDEX      { pr1645v2ShLineLimRelGlobalIx }
   ::= {pr1645v2ShLineLimRelSSCTable 1}

Pr1645v2ShLineLimRelEntry ::=
   SEQUENCE
      {
      pr1645v2ShLineLimRelGlobalIx
         GlobalIndex,
      pr1645v2ShLineLimRelLDownCnt
         Counter32,
      pr1645v2ShLineLimRelLDownTme
         TimeTicks
      }

pr1645v2ShLineLimRelGlobalIx OBJECT-TYPE
   SYNTAX      GlobalIndex
   MAX-ACCESS  not-accessible
   STATUS      current
   DESCRIPTION
      "The value of the tlsCntTreeGlobalIndex of the MANAGED OBJECT."
   ::= {pr1645v2ShLineLimRelEntry 10}

pr1645v2ShLineLimRelLDownCnt OBJECT-TYPE
   SYNTAX      Counter32
   MAX-ACCESS  read-only
   STATUS      current
   DESCRIPTION
      "Path: line.performance.line.linkDownCount

       32 bit unsigned wrappable counter."
   ::= {pr1645v2ShLineLimRelEntry 16777216}

pr1645v2ShLineLimRelLDownTme OBJECT-TYPE
   SYNTAX      TimeTicks
   MAX-ACCESS  read-only
   STATUS      current
   DESCRIPTION
      "Path: line.performance.line.linkDownTime

       Time in centi-second."
   ::= {pr1645v2ShLineLimRelEntry 33554432}



ar1645v2ShLineLim OBJECT IDENTIFIER ::= {r1645v2ShLineLim 16}


ar1645v2ShLineLimResetEOCCounters OBJECT IDENTIFIER ::= {ar1645v2ShLineLim 685}

ar1645v2ShLineLimResetEOCCountersTable OBJECT-TYPE
   SYNTAX      SEQUENCE OF Ar1645v2ShLineLimResetEOCCountersEntry
   MAX-ACCESS  not-accessible
   STATUS      current
   DESCRIPTION
      "action in the debug group"
   ::= {ar1645v2ShLineLimResetEOCCounters 1}

ar1645v2ShLineLimResetEOCCountersEntry OBJECT-TYPE
   SYNTAX      Ar1645v2ShLineLimResetEOCCountersEntry
   MAX-ACCESS  not-accessible
   STATUS      current
   DESCRIPTION
      ""
   INDEX      { ar1645v2ShLineLimResetEOCCountersGlobalIx }
   ::= {ar1645v2ShLineLimResetEOCCountersTable 1}

Ar1645v2ShLineLimResetEOCCountersEntry ::=
   SEQUENCE
      {
      ar1645v2ShLineLimResetEOCCountersGlobalIx
         GlobalIndex,
      ar1645v2ShLineLimResetEOCCountersValue
         Integer32
      }

ar1645v2ShLineLimResetEOCCountersGlobalIx OBJECT-TYPE
   SYNTAX      GlobalIndex
   MAX-ACCESS  not-accessible
   STATUS      current
   DESCRIPTION
      "The value of the tlsCntTreeGlobalIndex of the MANAGED OBJECT."
   ::= {ar1645v2ShLineLimResetEOCCountersEntry 10}

ar1645v2ShLineLimResetEOCCountersValue OBJECT-TYPE
   SYNTAX      Integer32
   MAX-ACCESS  read-write
   STATUS      current
   DESCRIPTION
      "Path: line.actions.resetEOCCounters"
   ::= {ar1645v2ShLineLimResetEOCCountersEntry 2147483648}


ar1645v2ShLineLimClearCounters OBJECT IDENTIFIER ::= {ar1645v2ShLineLim 263}

ar1645v2ShLineLimClearCountersTable OBJECT-TYPE
   SYNTAX      SEQUENCE OF Ar1645v2ShLineLimClearCountersEntry
   MAX-ACCESS  not-accessible
   STATUS      current
   DESCRIPTION
      "reset counters"
   ::= {ar1645v2ShLineLimClearCounters 1}

ar1645v2ShLineLimClearCountersEntry OBJECT-TYPE
   SYNTAX      Ar1645v2ShLineLimClearCountersEntry
   MAX-ACCESS  not-accessible
   STATUS      current
   DESCRIPTION
      ""
   INDEX      { ar1645v2ShLineLimClearCountersGlobalIx }
   ::= {ar1645v2ShLineLimClearCountersTable 1}

Ar1645v2ShLineLimClearCountersEntry ::=
   SEQUENCE
      {
      ar1645v2ShLineLimClearCountersGlobalIx
         GlobalIndex,
      ar1645v2ShLineLimClearCountersValue
         Integer32
      }

ar1645v2ShLineLimClearCountersGlobalIx OBJECT-TYPE
   SYNTAX      GlobalIndex
   MAX-ACCESS  not-accessible
   STATUS      current
   DESCRIPTION
      "The value of the tlsCntTreeGlobalIndex of the MANAGED OBJECT."
   ::= {ar1645v2ShLineLimClearCountersEntry 10}

ar1645v2ShLineLimClearCountersValue OBJECT-TYPE
   SYNTAX      Integer32
   MAX-ACCESS  read-write
   STATUS      current
   DESCRIPTION
      "Path: line.actions.clearCounters"
   ::= {ar1645v2ShLineLimClearCountersEntry 2147483648}


ar1645v2ShLineLimForceRetrain OBJECT IDENTIFIER ::= {ar1645v2ShLineLim 131}

ar1645v2ShLineLimForceRetrainTable OBJECT-TYPE
   SYNTAX      SEQUENCE OF Ar1645v2ShLineLimForceRetrainEntry
   MAX-ACCESS  not-accessible
   STATUS      current
   DESCRIPTION
      "forceRetrain"
   ::= {ar1645v2ShLineLimForceRetrain 1}

ar1645v2ShLineLimForceRetrainEntry OBJECT-TYPE
   SYNTAX      Ar1645v2ShLineLimForceRetrainEntry
   MAX-ACCESS  not-accessible
   STATUS      current
   DESCRIPTION
      ""
   INDEX      { ar1645v2ShLineLimForceRetrainGlobalIx }
   ::= {ar1645v2ShLineLimForceRetrainTable 1}

Ar1645v2ShLineLimForceRetrainEntry ::=
   SEQUENCE
      {
      ar1645v2ShLineLimForceRetrainGlobalIx
         GlobalIndex,
      ar1645v2ShLineLimForceRetrainValue
         Integer32
      }

ar1645v2ShLineLimForceRetrainGlobalIx OBJECT-TYPE
   SYNTAX      GlobalIndex
   MAX-ACCESS  not-accessible
   STATUS      current
   DESCRIPTION
      "The value of the tlsCntTreeGlobalIndex of the MANAGED OBJECT."
   ::= {ar1645v2ShLineLimForceRetrainEntry 10}

ar1645v2ShLineLimForceRetrainValue OBJECT-TYPE
   SYNTAX      Integer32
   MAX-ACCESS  read-write
   STATUS      current
   DESCRIPTION
      "Path: line.actions.forceRetrain"
   ::= {ar1645v2ShLineLimForceRetrainEntry 2147483648}


ar1645v2ShLineLimResetSdfe4 OBJECT IDENTIFIER ::= {ar1645v2ShLineLim 277}

ar1645v2ShLineLimResetSdfe4Table OBJECT-TYPE
   SYNTAX      SEQUENCE OF Ar1645v2ShLineLimResetSdfe4Entry
   MAX-ACCESS  not-accessible
   STATUS      current
   DESCRIPTION
      "reset Sdfe4"
   ::= {ar1645v2ShLineLimResetSdfe4 1}

ar1645v2ShLineLimResetSdfe4Entry OBJECT-TYPE
   SYNTAX      Ar1645v2ShLineLimResetSdfe4Entry
   MAX-ACCESS  not-accessible
   STATUS      current
   DESCRIPTION
      ""
   INDEX      { ar1645v2ShLineLimResetSdfe4GlobalIx }
   ::= {ar1645v2ShLineLimResetSdfe4Table 1}

Ar1645v2ShLineLimResetSdfe4Entry ::=
   SEQUENCE
      {
      ar1645v2ShLineLimResetSdfe4GlobalIx
         GlobalIndex,
      ar1645v2ShLineLimResetSdfe4Value
         Integer32
      }

ar1645v2ShLineLimResetSdfe4GlobalIx OBJECT-TYPE
   SYNTAX      GlobalIndex
   MAX-ACCESS  not-accessible
   STATUS      current
   DESCRIPTION
      "The value of the tlsCntTreeGlobalIndex of the MANAGED OBJECT."
   ::= {ar1645v2ShLineLimResetSdfe4Entry 10}

ar1645v2ShLineLimResetSdfe4Value OBJECT-TYPE
   SYNTAX      Integer32
   MAX-ACCESS  read-write
   STATUS      current
   DESCRIPTION
      "Path: line.actions.resetSdfe4"
   ::= {ar1645v2ShLineLimResetSdfe4Entry 2147483648}


ar1645v2ShLineLimPsdMeasurement OBJECT IDENTIFIER ::= {ar1645v2ShLineLim 431}

ar1645v2ShLineLimPsdMeasurementTable OBJECT-TYPE
   SYNTAX      SEQUENCE OF Ar1645v2ShLineLimPsdMeasurementEntry
   MAX-ACCESS  not-accessible
   STATUS      current
   DESCRIPTION
      "PSDMeasurement"
   ::= {ar1645v2ShLineLimPsdMeasurement 1}

ar1645v2ShLineLimPsdMeasurementEntry OBJECT-TYPE
   SYNTAX      Ar1645v2ShLineLimPsdMeasurementEntry
   MAX-ACCESS  not-accessible
   STATUS      current
   DESCRIPTION
      ""
   INDEX      { ar1645v2ShLineLimPsdMeasurementGlobalIx }
   ::= {ar1645v2ShLineLimPsdMeasurementTable 1}

Ar1645v2ShLineLimPsdMeasurementEntry ::=
   SEQUENCE
      {
      ar1645v2ShLineLimPsdMeasurementGlobalIx
         GlobalIndex,
      ar1645v2ShLineLimPsdMeasurementValue
         Integer32
      }

ar1645v2ShLineLimPsdMeasurementGlobalIx OBJECT-TYPE
   SYNTAX      GlobalIndex
   MAX-ACCESS  not-accessible
   STATUS      current
   DESCRIPTION
      "The value of the tlsCntTreeGlobalIndex of the MANAGED OBJECT."
   ::= {ar1645v2ShLineLimPsdMeasurementEntry 10}

ar1645v2ShLineLimPsdMeasurementValue OBJECT-TYPE
   SYNTAX      Integer32
   MAX-ACCESS  read-write
   STATUS      current
   DESCRIPTION
      "Path: line.actions.psdMeasurement"
   ::= {ar1645v2ShLineLimPsdMeasurementEntry 2147483648}


ar1645v2ShLineLimPsdMeasurementType OBJECT IDENTIFIER ::= {ar1645v2ShLineLim 432}

ar1645v2ShLineLimPsdMeasurementTypeTable OBJECT-TYPE
   SYNTAX      SEQUENCE OF Ar1645v2ShLineLimPsdMeasurementTypeEntry
   MAX-ACCESS  not-accessible
   STATUS      current
   DESCRIPTION
      "PSDMeasurementType"
   ::= {ar1645v2ShLineLimPsdMeasurementType 1}

ar1645v2ShLineLimPsdMeasurementTypeEntry OBJECT-TYPE
   SYNTAX      Ar1645v2ShLineLimPsdMeasurementTypeEntry
   MAX-ACCESS  not-accessible
   STATUS      current
   DESCRIPTION
      ""
   INDEX      { ar1645v2ShLineLimPsdMeasurementTypeGlobalIx }
   ::= {ar1645v2ShLineLimPsdMeasurementTypeTable 1}

Ar1645v2ShLineLimPsdMeasurementTypeEntry ::=
   SEQUENCE
      {
      ar1645v2ShLineLimPsdMeasurementTypeGlobalIx
         GlobalIndex,
      ar1645v2ShLineLimPsdMeasurementTypeValue
         INTEGER
      }

ar1645v2ShLineLimPsdMeasurementTypeGlobalIx OBJECT-TYPE
   SYNTAX      GlobalIndex
   MAX-ACCESS  not-accessible
   STATUS      current
   DESCRIPTION
      "The value of the tlsCntTreeGlobalIndex of the MANAGED OBJECT."
   ::= {ar1645v2ShLineLimPsdMeasurementTypeEntry 10}

ar1645v2ShLineLimPsdMeasurementTypeValue OBJECT-TYPE
   SYNTAX      INTEGER
               {
               start (0),
               stop (1)
               }
   MAX-ACCESS  read-write
   STATUS      current
   DESCRIPTION
      "Path: line.actions.psdMeasurementType

       Possibilities:
               start   (0)
               stop   (1)"
   ::= {ar1645v2ShLineLimPsdMeasurementTypeEntry 2147483648}


ar1645v2ShLineLimPowerScaleValue OBJECT IDENTIFIER ::= {ar1645v2ShLineLim 154}

ar1645v2ShLineLimPowerScaleValueTable OBJECT-TYPE
   SYNTAX      SEQUENCE OF Ar1645v2ShLineLimPowerScaleValueEntry
   MAX-ACCESS  not-accessible
   STATUS      current
   DESCRIPTION
      "powerScaleValue"
   ::= {ar1645v2ShLineLimPowerScaleValue 1}

ar1645v2ShLineLimPowerScaleValueEntry OBJECT-TYPE
   SYNTAX      Ar1645v2ShLineLimPowerScaleValueEntry
   MAX-ACCESS  not-accessible
   STATUS      current
   DESCRIPTION
      ""
   INDEX      { ar1645v2ShLineLimPowerScaleValueGlobalIx }
   ::= {ar1645v2ShLineLimPowerScaleValueTable 1}

Ar1645v2ShLineLimPowerScaleValueEntry ::=
   SEQUENCE
      {
      ar1645v2ShLineLimPowerScaleValueGlobalIx
         GlobalIndex,
      ar1645v2ShLineLimPowerScaleValueValue
         INTEGER
      }

ar1645v2ShLineLimPowerScaleValueGlobalIx OBJECT-TYPE
   SYNTAX      GlobalIndex
   MAX-ACCESS  not-accessible
   STATUS      current
   DESCRIPTION
      "The value of the tlsCntTreeGlobalIndex of the MANAGED OBJECT."
   ::= {ar1645v2ShLineLimPowerScaleValueEntry 10}

ar1645v2ShLineLimPowerScaleValueValue OBJECT-TYPE
   SYNTAX      INTEGER
               {
               sp0d5dB (27659),
               sp0d4dB (27342),
               sp0d3dB (27029),
               sp0d2dB (26720),
               sp0d1dB (26414),
               s0dB (26112),
               sm0d1dB (25813),
               sm0d2dB (25517),
               sm0d3dB (25225),
               sm0d4dB (24936),
               sm0d5dB (24651),
               sm0d6dB (24369),
               sm0d7dB (24090),
               sm0d8dB (23814),
               sm0d9dB (23541),
               sm1d0dB (23272),
               sm1d1dB (23005),
               sm1d2dB (22742),
               sm1d3dB (22482),
               sm1d4dB (22224),
               sm1d5dB (21970),
               sm1d6dB (21719),
               sm1d7dB (21470),
               sm1d8dB (21224),
               sm1d9dB (20981),
               sm2dB (20741),
               sm3dB (18485),
               sm4dB (16475),
               sm5dB (14683),
               sm6dB (13087),
               sm7dB (11663),
               sm8dB (10395),
               sm9dB (9264),
               sm10dB (8257),
               sm11dB (7359),
               sm12dB (6559),
               sm13dB (5845),
               sm14dB (5210),
               sm15dB (4643)
               }
   MAX-ACCESS  read-write
   STATUS      current
   DESCRIPTION
      "Path: line.actions.powerScaleValue

       Possibilities:
               +0.5dB   (27659)
               +0.4dB   (27342)
               +0.3dB   (27029)
               +0.2dB   (26720)
               +0.1dB   (26414)
               0dB   (26112)
               -0.1dB   (25813)
               -0.2dB   (25517)
               -0.3dB   (25225)
               -0.4dB   (24936)
               -0.5dB   (24651)
               -0.6dB   (24369)
               -0.7dB   (24090)
               -0.8dB   (23814)
               -0.9dB   (23541)
               -1.0dB   (23272)
               -1.1dB   (23005)
               -1.2dB   (22742)
               -1.3dB   (22482)
               -1.4dB   (22224)
               -1.5dB   (21970)
               -1.6dB   (21719)
               -1.7dB   (21470)
               -1.8dB   (21224)
               -1.9dB   (20981)
               -2dB   (20741)
               -3dB   (18485)
               -4dB   (16475)
               -5dB   (14683)
               -6dB   (13087)
               -7dB   (11663)
               -8dB   (10395)
               -9dB   (9264)
               -10dB   (8257)
               -11dB   (7359)
               -12dB   (6559)
               -13dB   (5845)
               -14dB   (5210)
               -15dB   (4643)"
   ::= {ar1645v2ShLineLimPowerScaleValueEntry 2147483648}


ar1645v2ShLineLimReadDebugRegAction OBJECT IDENTIFIER ::= {ar1645v2ShLineLim 690}

ar1645v2ShLineLimReadDebugRegActionTable OBJECT-TYPE
   SYNTAX      SEQUENCE OF Ar1645v2ShLineLimReadDebugRegActionEntry
   MAX-ACCESS  not-accessible
   STATUS      current
   DESCRIPTION
      "reads Soc4e Debug registers"
   ::= {ar1645v2ShLineLimReadDebugRegAction 1}

ar1645v2ShLineLimReadDebugRegActionEntry OBJECT-TYPE
   SYNTAX      Ar1645v2ShLineLimReadDebugRegActionEntry
   MAX-ACCESS  not-accessible
   STATUS      current
   DESCRIPTION
      ""
   INDEX      { ar1645v2ShLineLimReadDebugRegActionGlobalIx }
   ::= {ar1645v2ShLineLimReadDebugRegActionTable 1}

Ar1645v2ShLineLimReadDebugRegActionEntry ::=
   SEQUENCE
      {
      ar1645v2ShLineLimReadDebugRegActionGlobalIx
         GlobalIndex,
      ar1645v2ShLineLimReadDebugRegActionValue
         Integer32
      }

ar1645v2ShLineLimReadDebugRegActionGlobalIx OBJECT-TYPE
   SYNTAX      GlobalIndex
   MAX-ACCESS  not-accessible
   STATUS      current
   DESCRIPTION
      "The value of the tlsCntTreeGlobalIndex of the MANAGED OBJECT."
   ::= {ar1645v2ShLineLimReadDebugRegActionEntry 10}

ar1645v2ShLineLimReadDebugRegActionValue OBJECT-TYPE
   SYNTAX      Integer32
   MAX-ACCESS  read-write
   STATUS      current
   DESCRIPTION
      "Path: line.actions.readDebugRegAction"
   ::= {ar1645v2ShLineLimReadDebugRegActionEntry 2147483648}


ar1645v2ShLineLimSetDebugRegAction OBJECT IDENTIFIER ::= {ar1645v2ShLineLim 688}

ar1645v2ShLineLimSetDebugRegActionTable OBJECT-TYPE
   SYNTAX      SEQUENCE OF Ar1645v2ShLineLimSetDebugRegActionEntry
   MAX-ACCESS  not-accessible
   STATUS      current
   DESCRIPTION
      "generic action attribute"
   ::= {ar1645v2ShLineLimSetDebugRegAction 1}

ar1645v2ShLineLimSetDebugRegActionEntry OBJECT-TYPE
   SYNTAX      Ar1645v2ShLineLimSetDebugRegActionEntry
   MAX-ACCESS  not-accessible
   STATUS      current
   DESCRIPTION
      ""
   INDEX      { ar1645v2ShLineLimSetDebugRegActionGlobalIx }
   ::= {ar1645v2ShLineLimSetDebugRegActionTable 1}

Ar1645v2ShLineLimSetDebugRegActionEntry ::=
   SEQUENCE
      {
      ar1645v2ShLineLimSetDebugRegActionGlobalIx
         GlobalIndex,
      ar1645v2ShLineLimSetDebugRegActionValue
         Integer32
      }

ar1645v2ShLineLimSetDebugRegActionGlobalIx OBJECT-TYPE
   SYNTAX      GlobalIndex
   MAX-ACCESS  not-accessible
   STATUS      current
   DESCRIPTION
      "The value of the tlsCntTreeGlobalIndex of the MANAGED OBJECT."
   ::= {ar1645v2ShLineLimSetDebugRegActionEntry 10}

ar1645v2ShLineLimSetDebugRegActionValue OBJECT-TYPE
   SYNTAX      Integer32
   MAX-ACCESS  read-write
   STATUS      current
   DESCRIPTION
      "Path: line.actions.setDebugRegAction"
   ::= {ar1645v2ShLineLimSetDebugRegActionEntry 2147483648}


ar1645v2ShLineLimSetDebugRegValue OBJECT IDENTIFIER ::= {ar1645v2ShLineLim 689}

ar1645v2ShLineLimSetDebugRegValueSSCTable OBJECT-TYPE
   SYNTAX      SEQUENCE OF Ar1645v2ShLineLimSetDebugRegValueEntry
   MAX-ACCESS  not-accessible
   STATUS      current
   DESCRIPTION
      "Writes Soc4e Debug register"
   ::= {ar1645v2ShLineLimSetDebugRegValue 1}

ar1645v2ShLineLimSetDebugRegValueEntry OBJECT-TYPE
   SYNTAX      Ar1645v2ShLineLimSetDebugRegValueEntry
   MAX-ACCESS  not-accessible
   STATUS      current
   DESCRIPTION
      ""
   INDEX      { ar1645v2ShLineLimSetDebugRegValueGlobalIx }
   ::= {ar1645v2ShLineLimSetDebugRegValueSSCTable 1}

Ar1645v2ShLineLimSetDebugRegValueEntry ::=
   SEQUENCE
      {
      ar1645v2ShLineLimSetDebugRegValueGlobalIx
         GlobalIndex,
      ar1645v2ShLineLimSetDebugRegValueModule
         INTEGER,
      ar1645v2ShLineLimSetDebugRegValueSlice
         INTEGER,
      ar1645v2ShLineLimSetDebugRegValueBlock
         INTEGER,
      ar1645v2ShLineLimSetDebugRegValueRegister
         Integer32,
      ar1645v2ShLineLimSetDebugRegValueValue
         Integer32
      }

ar1645v2ShLineLimSetDebugRegValueGlobalIx OBJECT-TYPE
   SYNTAX      GlobalIndex
   MAX-ACCESS  not-accessible
   STATUS      current
   DESCRIPTION
      "The value of the tlsCntTreeGlobalIndex of the MANAGED OBJECT."
   ::= {ar1645v2ShLineLimSetDebugRegValueEntry 10}

ar1645v2ShLineLimSetDebugRegValueModule OBJECT-TYPE
   SYNTAX      INTEGER
               {
               dBGuModuleuATMuTC (0),
               dBGuModuleuATMuOAM (1),
               dBGuModuleuSAR (2),
               dBGuModuleuTCuFIFO (3),
               dBGuModuleuHDLC (4),
               dBGuModuleuxMII (5),
               dBGuModuleuMAC (6),
               dBGuModuleuEFMuTC (10),
               dBGuModuleuMDIO (11),
               dBGuModuleuCntMem1 (12),
               dBGuModuleuPAF (13),
               dBGuModuleuPAFuQueue (14),
               dBGuModuleuPDI (15),
               dBGuModuleuCntMem2 (16)
               }
   MAX-ACCESS  read-write
   STATUS      current
   DESCRIPTION
      "Path: line.actions.setDebugRegValue.module

       Possibilities:
               DBG_Module_ATM_TC   (0)
               DBG_Module_ATM_OAM   (1)
               DBG_Module_SAR   (2)
               DBG_Module_TC_FIFO   (3)
               DBG_Module_HDLC   (4)
               DBG_Module_xMII   (5)
               DBG_Module_MAC   (6)
               DBG_Module_EFM_TC   (10)
               DBG_Module_MDIO   (11)
               DBG_Module_CntMem1   (12)
               DBG_Module_PAF   (13)
               DBG_Module_PAF_Queue   (14)
               DBG_Module_PDI   (15)
               DBG_Module_CntMem2   (16)"
   ::= {ar1645v2ShLineLimSetDebugRegValueEntry 16777216}

ar1645v2ShLineLimSetDebugRegValueSlice OBJECT-TYPE
   SYNTAX      INTEGER
               {
               dBGuSliceu0 (0),
               dBGuSliceu1 (1),
               dBGuSliceu2 (2),
               dBGuSliceu3 (3),
               dBGuPSI (32),
               dBGuEFMuOAM (33),
               dBGuxTCuTop (63)
               }
   MAX-ACCESS  read-write
   STATUS      current
   DESCRIPTION
      "Path: line.actions.setDebugRegValue.slice

       Possibilities:
               DBG_Slice_0   (0)
               DBG_Slice_1   (1)
               DBG_Slice_2   (2)
               DBG_Slice_3   (3)
               DBG_PSI   (32)
               DBG_EFM_OAM   (33)
               DBG_xTC_Top   (63)"
   ::= {ar1645v2ShLineLimSetDebugRegValueEntry 33554432}

ar1645v2ShLineLimSetDebugRegValueBlock OBJECT-TYPE
   SYNTAX      INTEGER
               {
               dBGuBlockuxTC (1),
               dBGuBlockuxSwitch (2),
               dBGuBlockuBoot (3)
               }
   MAX-ACCESS  read-write
   STATUS      current
   DESCRIPTION
      "Path: line.actions.setDebugRegValue.block

       Possibilities:
               DBG_Block_xTC   (1)
               DBG_Block_xSwitch   (2)
               DBG_Block_Boot   (3)"
   ::= {ar1645v2ShLineLimSetDebugRegValueEntry 50331648}

ar1645v2ShLineLimSetDebugRegValueRegister OBJECT-TYPE
   SYNTAX      Integer32
   MAX-ACCESS  read-write
   STATUS      current
   DESCRIPTION
      "Path: line.actions.setDebugRegValue.register"
   ::= {ar1645v2ShLineLimSetDebugRegValueEntry 67108864}

ar1645v2ShLineLimSetDebugRegValueValue OBJECT-TYPE
   SYNTAX      Integer32
   MAX-ACCESS  read-write
   STATUS      current
   DESCRIPTION
      "Path: line.actions.setDebugRegValue.value"
   ::= {ar1645v2ShLineLimSetDebugRegValueEntry 83886080}


ar1645v2ShLineLimResetDebugCounters OBJECT IDENTIFIER ::= {ar1645v2ShLineLim 601}

ar1645v2ShLineLimResetDebugCountersTable OBJECT-TYPE
   SYNTAX      SEQUENCE OF Ar1645v2ShLineLimResetDebugCountersEntry
   MAX-ACCESS  not-accessible
   STATUS      current
   DESCRIPTION
      "resetDebugCounters"
   ::= {ar1645v2ShLineLimResetDebugCounters 1}

ar1645v2ShLineLimResetDebugCountersEntry OBJECT-TYPE
   SYNTAX      Ar1645v2ShLineLimResetDebugCountersEntry
   MAX-ACCESS  not-accessible
   STATUS      current
   DESCRIPTION
      ""
   INDEX      { ar1645v2ShLineLimResetDebugCountersGlobalIx }
   ::= {ar1645v2ShLineLimResetDebugCountersTable 1}

Ar1645v2ShLineLimResetDebugCountersEntry ::=
   SEQUENCE
      {
      ar1645v2ShLineLimResetDebugCountersGlobalIx
         GlobalIndex,
      ar1645v2ShLineLimResetDebugCountersValue
         Integer32
      }

ar1645v2ShLineLimResetDebugCountersGlobalIx OBJECT-TYPE
   SYNTAX      GlobalIndex
   MAX-ACCESS  not-accessible
   STATUS      current
   DESCRIPTION
      "The value of the tlsCntTreeGlobalIndex of the MANAGED OBJECT."
   ::= {ar1645v2ShLineLimResetDebugCountersEntry 10}

ar1645v2ShLineLimResetDebugCountersValue OBJECT-TYPE
   SYNTAX      Integer32
   MAX-ACCESS  read-write
   STATUS      current
   DESCRIPTION
      "Path: line.actions.resetDebugCounters"
   ::= {ar1645v2ShLineLimResetDebugCountersEntry 2147483648}



fr1645v2ShLineLim OBJECT IDENTIFIER ::= {r1645v2ShLineLim 13}


fr1645v2ShLineLimAlInfo OBJECT IDENTIFIER ::= {fr1645v2ShLineLim 207}

fr1645v2ShLineLimAlInfoSSCTable OBJECT-TYPE
   SYNTAX      SEQUENCE OF Fr1645v2ShLineLimAlInfoEntry
   MAX-ACCESS  not-accessible
   STATUS      current
   DESCRIPTION
      "lineAlarmInfo"
   ::= {fr1645v2ShLineLimAlInfo 1}

fr1645v2ShLineLimAlInfoEntry OBJECT-TYPE
   SYNTAX      Fr1645v2ShLineLimAlInfoEntry
   MAX-ACCESS  not-accessible
   STATUS      current
   DESCRIPTION
      ""
   INDEX      { fr1645v2ShLineLimAlInfoGlobalIx }
   ::= {fr1645v2ShLineLimAlInfoSSCTable 1}

Fr1645v2ShLineLimAlInfoEntry ::=
   SEQUENCE
      {
      fr1645v2ShLineLimAlInfoGlobalIx
         GlobalIndex,
      fr1645v2ShLineLimAlInfoDiscr
         Integer32,
      fr1645v2ShLineLimAlInfoCurrAlms
         Integer32,
      fr1645v2ShLineLimAlInfoPrevAlms
         Integer32,
      fr1645v2ShLineLimAlInfoAlMask
         Integer32,
      fr1645v2ShLineLimAlInfoAlLvlLnkDwn
         Integer32,
      fr1645v2ShLineLimAlInfoAlLvlInvNRep
         Integer32,
      fr1645v2ShLineLimAlInfoAlLvlRemPowFl
         Integer32,
      fr1645v2ShLineLimAlInfoAlLvlAggSpd
         Integer32
      }

fr1645v2ShLineLimAlInfoGlobalIx OBJECT-TYPE
   SYNTAX      GlobalIndex
   MAX-ACCESS  not-accessible
   STATUS      current
   DESCRIPTION
      "The value of the tlsCntTreeGlobalIndex of the MANAGED OBJECT."
   ::= {fr1645v2ShLineLimAlInfoEntry 10}

fr1645v2ShLineLimAlInfoDiscr OBJECT-TYPE
   SYNTAX      Integer32
   MAX-ACCESS  read-only
   STATUS      current
   DESCRIPTION
      "Path: line.alarms.alarmInfo.discriminator"
   ::= {fr1645v2ShLineLimAlInfoEntry 16777216}

fr1645v2ShLineLimAlInfoCurrAlms OBJECT-TYPE
   SYNTAX      Integer32
   MAX-ACCESS  read-only
   STATUS      current
   DESCRIPTION
      "Path: line.alarms.alarmInfo.currentAlarms

       Bit meanings:
               bit 0 = linkDown,
               bit 1 = invalidNumRepeaters,
               bit 11 = remotePowerFail,
               bit 12 = aggregatedIfSpeed"
   ::= {fr1645v2ShLineLimAlInfoEntry 33554432}

fr1645v2ShLineLimAlInfoPrevAlms OBJECT-TYPE
   SYNTAX      Integer32
   MAX-ACCESS  read-only
   STATUS      current
   DESCRIPTION
      "Path: line.alarms.alarmInfo.previousAlarms

       Bit meanings:
               bit 0 = linkDown,
               bit 1 = invalidNumRepeaters,
               bit 11 = remotePowerFail,
               bit 12 = aggregatedIfSpeed"
   ::= {fr1645v2ShLineLimAlInfoEntry 50331648}

fr1645v2ShLineLimAlInfoAlMask OBJECT-TYPE
   SYNTAX      Integer32
   MAX-ACCESS  read-only
   STATUS      current
   DESCRIPTION
      "Path: line.alarms.alarmInfo.alarmMask

       Bit meanings:
               bit 0 = linkDown,
               bit 1 = invalidNumRepeaters,
               bit 11 = remotePowerFail,
               bit 12 = aggregatedIfSpeed"
   ::= {fr1645v2ShLineLimAlInfoEntry 67108864}

fr1645v2ShLineLimAlInfoAlLvlLnkDwn OBJECT-TYPE
   SYNTAX      Integer32
   MAX-ACCESS  read-only
   STATUS      current
   DESCRIPTION
      "Path: line.alarms.alarmInfo.alarmLevel.linkDown"
   ::= {fr1645v2ShLineLimAlInfoEntry 83951616}

fr1645v2ShLineLimAlInfoAlLvlInvNRep OBJECT-TYPE
   SYNTAX      Integer32
   MAX-ACCESS  read-only
   STATUS      current
   DESCRIPTION
      "Path: line.alarms.alarmInfo.alarmLevel.invalidNumRepeaters"
   ::= {fr1645v2ShLineLimAlInfoEntry 84017152}

fr1645v2ShLineLimAlInfoAlLvlRemPowFl OBJECT-TYPE
   SYNTAX      Integer32
   MAX-ACCESS  read-only
   STATUS      current
   DESCRIPTION
      "Path: line.alarms.alarmInfo.alarmLevel.remotePowerFail"
   ::= {fr1645v2ShLineLimAlInfoEntry 84672512}

fr1645v2ShLineLimAlInfoAlLvlAggSpd OBJECT-TYPE
   SYNTAX      Integer32
   MAX-ACCESS  read-only
   STATUS      current
   DESCRIPTION
      "Path: line.alarms.alarmInfo.alarmLevel.aggregatedIfSpeed"
   ::= {fr1645v2ShLineLimAlInfoEntry 84738048}


fr1645v2ShLineLimAlInfoE2 OBJECT IDENTIFIER ::= {fr1645v2ShLineLimAlInfo 2}

fr1645v2ShLineLimAlInfoE2Entry OBJECT IDENTIFIER ::= {fr1645v2ShLineLimAlInfoE2 1}

fr1645v2ShLineLimAlInfoE2LnkDwn OBJECT IDENTIFIER ::= {fr1645v2ShLineLimAlInfoE2Entry 10}

fr1645v2ShLineLimAlInfoE2LnkDwnPfx OBJECT IDENTIFIER ::= {fr1645v2ShLineLimAlInfoE2LnkDwn 0}

fr1645v2ShLineLimAlInfoE2LnkDwnOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'socratesLineLimited'
                (root='router1645') has changed from the ON to the OFF state."
   ::= {fr1645v2ShLineLimAlInfoE2LnkDwnPfx 1}

fr1645v2ShLineLimAlInfoE2LnkDwnOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'socratesLineLimited'
                (root='router1645') has changed from the OFF to the ON state."
   ::= {fr1645v2ShLineLimAlInfoE2LnkDwnPfx 2}

fr1645v2ShLineLimAlInfoE2InvNRep OBJECT IDENTIFIER ::= {fr1645v2ShLineLimAlInfoE2Entry 11}

fr1645v2ShLineLimAlInfoE2InvNRepPfx OBJECT IDENTIFIER ::= {fr1645v2ShLineLimAlInfoE2InvNRep 0}

fr1645v2ShLineLimAlInfoE2InvNRepOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'invalidNumRepeaters'
                representing an alarm condition in the alarm word
                of attribute 'alarmInfo' of managed object 'socratesLineLimited'
                (root='router1645') has changed from the ON to the OFF state."
   ::= {fr1645v2ShLineLimAlInfoE2InvNRepPfx 1}

fr1645v2ShLineLimAlInfoE2InvNRepOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'invalidNumRepeaters'
                representing an alarm condition in the alarm word
                of attribute 'alarmInfo' of managed object 'socratesLineLimited'
                (root='router1645') has changed from the OFF to the ON state."
   ::= {fr1645v2ShLineLimAlInfoE2InvNRepPfx 2}

fr1645v2ShLineLimAlInfoE2RemPowFl OBJECT IDENTIFIER ::= {fr1645v2ShLineLimAlInfoE2Entry 21}

fr1645v2ShLineLimAlInfoE2RemPowFlPfx OBJECT IDENTIFIER ::= {fr1645v2ShLineLimAlInfoE2RemPowFl 0}

fr1645v2ShLineLimAlInfoE2RemPowFlOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'remotePowerFail'
                representing an alarm condition in the alarm word
                of attribute 'alarmInfo' of managed object 'socratesLineLimited'
                (root='router1645') has changed from the ON to the OFF state."
   ::= {fr1645v2ShLineLimAlInfoE2RemPowFlPfx 1}

fr1645v2ShLineLimAlInfoE2RemPowFlOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'remotePowerFail'
                representing an alarm condition in the alarm word
                of attribute 'alarmInfo' of managed object 'socratesLineLimited'
                (root='router1645') has changed from the OFF to the ON state."
   ::= {fr1645v2ShLineLimAlInfoE2RemPowFlPfx 2}

fr1645v2ShLineLimAlInfoE2AggSpd OBJECT IDENTIFIER ::= {fr1645v2ShLineLimAlInfoE2Entry 22}

fr1645v2ShLineLimAlInfoE2AggSpdPfx OBJECT IDENTIFIER ::= {fr1645v2ShLineLimAlInfoE2AggSpd 0}

fr1645v2ShLineLimAlInfoE2AggSpdOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'aggregatedIfSpeed'
                representing an alarm condition in the alarm word
                of attribute 'alarmInfo' of managed object 'socratesLineLimited'
                (root='router1645') has changed from the ON to the OFF state."
   ::= {fr1645v2ShLineLimAlInfoE2AggSpdPfx 1}

fr1645v2ShLineLimAlInfoE2AggSpdOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'aggregatedIfSpeed'
                representing an alarm condition in the alarm word
                of attribute 'alarmInfo' of managed object 'socratesLineLimited'
                (root='router1645') has changed from the OFF to the ON state."
   ::= {fr1645v2ShLineLimAlInfoE2AggSpdPfx 2}



END
