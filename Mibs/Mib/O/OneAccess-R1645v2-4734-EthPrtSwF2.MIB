OneAccess-R1645v2-4734-EthPrtSwF2 DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2EthPrtSwF2 OBJECT IDENTIFIER ::= {r1645Rootv2 4734}

r1645v2EthPrtSwF2MOProp OBJECT-TYPE
   SYNTAX      SEQUENCE OF R1645v2EthPrtSwF2MOPropEntry
   MAX-ACCESS  not-accessible
   STATUS      current
   DESCRIPTION
      ""
   ::= {r1645v2EthPrtSwF2 1}

r1645v2EthPrtSwF2MOPropEntry OBJECT-TYPE
   SYNTAX      R1645v2EthPrtSwF2MOPropEntry
   MAX-ACCESS  not-accessible
   STATUS      current
   DESCRIPTION
      ""
   INDEX      { r1645v2EthPrtSwF2MOPropGlobalIx }
   ::= {r1645v2EthPrtSwF2MOProp 1}

R1645v2EthPrtSwF2MOPropEntry ::=
   SEQUENCE
      {
      r1645v2EthPrtSwF2MOPropPath
         ContainmentPath,
      r1645v2EthPrtSwF2MOPropRev
         ObjectRevision,
      r1645v2EthPrtSwF2MOPropGlobalIx
         GlobalIndex
      }

r1645v2EthPrtSwF2MOPropPath OBJECT-TYPE
   SYNTAX      ContainmentPath
   MAX-ACCESS  read-only
   STATUS      current
   DESCRIPTION
      "Textual description of the containment tree from the instance of
       the root object down to the instance of the current object."
   ::= {r1645v2EthPrtSwF2MOPropEntry 3}

r1645v2EthPrtSwF2MOPropRev OBJECT-TYPE
   SYNTAX      ObjectRevision
   MAX-ACCESS  read-only
   STATUS      current
   DESCRIPTION
      "This value corresponds with the revision of the MANAGED OBJECT."
   ::= {r1645v2EthPrtSwF2MOPropEntry 4}

r1645v2EthPrtSwF2MOPropGlobalIx OBJECT-TYPE
   SYNTAX      GlobalIndex
   MAX-ACCESS  read-only
   STATUS      current
   DESCRIPTION
      "The value of the tlsCntTreeGlobalIndex of the MANAGED OBJECT."
   ::= {r1645v2EthPrtSwF2MOPropEntry 10}



er1645v2EthPrtSwF2 OBJECT IDENTIFIER ::= {r1645v2EthPrtSwF2 11}


er1645v2EthPrtSwF2Remark OBJECT IDENTIFIER ::= {er1645v2EthPrtSwF2 321}

er1645v2EthPrtSwF2RemarkTable OBJECT-TYPE
   SYNTAX      SEQUENCE OF Er1645v2EthPrtSwF2RemarkEntry
   MAX-ACCESS  not-accessible
   STATUS      current
   DESCRIPTION
      "intfRemark"
   ::= {er1645v2EthPrtSwF2Remark 1}

er1645v2EthPrtSwF2RemarkEntry OBJECT-TYPE
   SYNTAX      Er1645v2EthPrtSwF2RemarkEntry
   MAX-ACCESS  not-accessible
   STATUS      current
   DESCRIPTION
      ""
   INDEX      { er1645v2EthPrtSwF2RemarkGlobalIx }
   ::= {er1645v2EthPrtSwF2RemarkTable 1}

Er1645v2EthPrtSwF2RemarkEntry ::=
   SEQUENCE
      {
      er1645v2EthPrtSwF2RemarkGlobalIx
         GlobalIndex,
      er1645v2EthPrtSwF2RemarkValue
         DisplayString
      }

er1645v2EthPrtSwF2RemarkGlobalIx OBJECT-TYPE
   SYNTAX      GlobalIndex
   MAX-ACCESS  not-accessible
   STATUS      current
   DESCRIPTION
      "The value of the tlsCntTreeGlobalIndex of the MANAGED OBJECT."
   ::= {er1645v2EthPrtSwF2RemarkEntry 10}

er1645v2EthPrtSwF2RemarkValue OBJECT-TYPE
   SYNTAX      DisplayString
   MAX-ACCESS  read-write
   STATUS      current
   DESCRIPTION
      "Path: swPort.editConf.remark"
   ::= {er1645v2EthPrtSwF2RemarkEntry 2147483648}


er1645v2EthPrtSwF2Arp OBJECT IDENTIFIER ::= {er1645v2EthPrtSwF2 19}

er1645v2EthPrtSwF2ArpSSCTable OBJECT-TYPE
   SYNTAX      SEQUENCE OF Er1645v2EthPrtSwF2ArpEntry
   MAX-ACCESS  not-accessible
   STATUS      current
   DESCRIPTION
      "ethernet related config parameters"
   ::= {er1645v2EthPrtSwF2Arp 1}

er1645v2EthPrtSwF2ArpEntry OBJECT-TYPE
   SYNTAX      Er1645v2EthPrtSwF2ArpEntry
   MAX-ACCESS  not-accessible
   STATUS      current
   DESCRIPTION
      ""
   INDEX      { er1645v2EthPrtSwF2ArpGlobalIx }
   ::= {er1645v2EthPrtSwF2ArpSSCTable 1}

Er1645v2EthPrtSwF2ArpEntry ::=
   SEQUENCE
      {
      er1645v2EthPrtSwF2ArpGlobalIx
         GlobalIndex,
      er1645v2EthPrtSwF2ArpTimeOut
         TimeTicks,
      er1645v2EthPrtSwF2ArpProxyArp
         INTEGER
      }

er1645v2EthPrtSwF2ArpGlobalIx OBJECT-TYPE
   SYNTAX      GlobalIndex
   MAX-ACCESS  not-accessible
   STATUS      current
   DESCRIPTION
      "The value of the tlsCntTreeGlobalIndex of the MANAGED OBJECT."
   ::= {er1645v2EthPrtSwF2ArpEntry 10}

er1645v2EthPrtSwF2ArpTimeOut OBJECT-TYPE
   SYNTAX      TimeTicks
   MAX-ACCESS  read-write
   STATUS      current
   DESCRIPTION
      "Path: swPort.editConf.arp.timeOut

       Time in centi-second."
   ::= {er1645v2EthPrtSwF2ArpEntry 201326592}

er1645v2EthPrtSwF2ArpProxyArp OBJECT-TYPE
   SYNTAX      INTEGER
               {
               disabled (0),
               enabled (1)
               }
   MAX-ACCESS  read-write
   STATUS      current
   DESCRIPTION
      "Path: swPort.editConf.arp.proxyArp

       Possibilities:
               disabled   (0)
               enabled   (1)"
   ::= {er1645v2EthPrtSwF2ArpEntry 838860800}

er1645v2EthPrtSwF2ArpStaticArp OBJECT-TYPE
   SYNTAX      SEQUENCE OF Er1645v2EthPrtSwF2ArpStaticArpEntry
   MAX-ACCESS  not-accessible
   STATUS      current
   DESCRIPTION
      ""
   ::= {er1645v2EthPrtSwF2Arp 50331648}

er1645v2EthPrtSwF2ArpStaticArpEntry OBJECT-TYPE
   SYNTAX      Er1645v2EthPrtSwF2ArpStaticArpEntry
   MAX-ACCESS  not-accessible
   STATUS      current
   DESCRIPTION
      ""
   INDEX      { er1645v2EthPrtSwF2ArpStaticArpGlobalIx,
                er1645v2EthPrtSwF2ArpStaticArpTableIx }
   ::= {er1645v2EthPrtSwF2ArpStaticArp 1}

Er1645v2EthPrtSwF2ArpStaticArpEntry ::=
   SEQUENCE
      {
      er1645v2EthPrtSwF2ArpStaticArpActions
         VariableLengthTableActions,
      er1645v2EthPrtSwF2ArpStaticArpGlobalIx
         GlobalIndex,
      er1645v2EthPrtSwF2ArpStaticArpTableIx
         TableIndex,
      er1645v2EthPrtSwF2ArpStaticArpMacAddress
         OCTET STRING,
      er1645v2EthPrtSwF2ArpStaticArpIpAddress
         IpAddress
      }

er1645v2EthPrtSwF2ArpStaticArpActions OBJECT-TYPE
   SYNTAX      VariableLengthTableActions
   MAX-ACCESS  read-write
   STATUS      current
   DESCRIPTION
      "By way of this field, some manipulations
       on this table may be performed."
   ::= {er1645v2EthPrtSwF2ArpStaticArpEntry 2}

er1645v2EthPrtSwF2ArpStaticArpGlobalIx OBJECT-TYPE
   SYNTAX      GlobalIndex
   MAX-ACCESS  not-accessible
   STATUS      current
   DESCRIPTION
      "The value of the tlsCntTreeGlobalIndex of the MANAGED OBJECT."
   ::= {er1645v2EthPrtSwF2ArpStaticArpEntry 10}

er1645v2EthPrtSwF2ArpStaticArpTableIx OBJECT-TYPE
   SYNTAX      TableIndex
   MAX-ACCESS  not-accessible
   STATUS      current
   DESCRIPTION
      ""
   ::= {er1645v2EthPrtSwF2ArpStaticArpEntry 11}

er1645v2EthPrtSwF2ArpStaticArpMacAddress OBJECT-TYPE
   SYNTAX      OCTET STRING
   MAX-ACCESS  read-write
   STATUS      current
   DESCRIPTION
      "Path: swPort.editConf.arp.staticArp.macAddress

       MAC address."
   ::= {er1645v2EthPrtSwF2ArpStaticArpEntry 16777216}

er1645v2EthPrtSwF2ArpStaticArpIpAddress OBJECT-TYPE
   SYNTAX      IpAddress
   MAX-ACCESS  read-write
   STATUS      current
   DESCRIPTION
      "Path: swPort.editConf.arp.staticArp.ipAddress"
   ::= {er1645v2EthPrtSwF2ArpStaticArpEntry 33554432}


er1645v2EthPrtSwF2BrC OBJECT IDENTIFIER ::= {er1645v2EthPrtSwF2 27}

er1645v2EthPrtSwF2BrCSSCTable OBJECT-TYPE
   SYNTAX      SEQUENCE OF Er1645v2EthPrtSwF2BrCEntry
   MAX-ACCESS  not-accessible
   STATUS      current
   DESCRIPTION
      "Set bridging parameters"
   ::= {er1645v2EthPrtSwF2BrC 1}

er1645v2EthPrtSwF2BrCEntry OBJECT-TYPE
   SYNTAX      Er1645v2EthPrtSwF2BrCEntry
   MAX-ACCESS  not-accessible
   STATUS      current
   DESCRIPTION
      ""
   INDEX      { er1645v2EthPrtSwF2BrCGlobalIx }
   ::= {er1645v2EthPrtSwF2BrCSSCTable 1}

Er1645v2EthPrtSwF2BrCEntry ::=
   SEQUENCE
      {
      er1645v2EthPrtSwF2BrCGlobalIx
         GlobalIndex,
      er1645v2EthPrtSwF2BrCAccessList
         DisplayString,
      er1645v2EthPrtSwF2BrCInAccessList
         DisplayString,
      er1645v2EthPrtSwF2BrCTp
         DisplayString,
      er1645v2EthPrtSwF2BrCBridgeGroup
         DisplayString,
      er1645v2EthPrtSwF2BrCLimBC
         INTEGER,
      er1645v2EthPrtSwF2BrCPrivateMode
         INTEGER,
      er1645v2EthPrtSwF2BrCLearning
         INTEGER,
      er1645v2EthPrtSwF2BrCMaxCacheSize
         INTEGER,
      er1645v2EthPrtSwF2BrCRelearnDropOnRelearn
         INTEGER,
      er1645v2EthPrtSwF2BrCRelearnShutdownThreshold
         Integer32,
      er1645v2EthPrtSwF2BrCRelearnShutdownTime
         TimeTicks,
      er1645v2EthPrtSwF2BrCRelearnLoopDetection
         INTEGER,
      er1645v2EthPrtSwF2BrCRelearnLoopDetectionInterval
         TimeTicks,
      er1645v2EthPrtSwF2BrCVlanMemberShip
         INTEGER,
      er1645v2EthPrtSwF2BrCDot1adType
         INTEGER,
      er1645v2EthPrtSwF2BrCPriority
         Integer32,
      er1645v2EthPrtSwF2BrCPathCost
         Integer32,
      er1645v2EthPrtSwF2BrCInternalPathCost
         Integer32,
      er1645v2EthPrtSwF2BrCTCD
         INTEGER,
      er1645v2EthPrtSwF2BrCRestrictedRole
         INTEGER,
      er1645v2EthPrtSwF2BrCAdminEdge
         INTEGER,
      er1645v2EthPrtSwF2BrCMgmtInline
         INTEGER,
      er1645v2EthPrtSwF2BrCL2ptMode
         INTEGER,
      er1645v2EthPrtSwF2BrCL2ptProtocols
         Integer32,
      er1645v2EthPrtSwF2BrCL2ptDestMac
         OCTET STRING,
      er1645v2EthPrtSwF2BrCL2ptCos
         INTEGER,
      er1645v2EthPrtSwF2BrCL2ptDropThrStp
         INTEGER,
      er1645v2EthPrtSwF2BrCL2ptDropThrLldp
         INTEGER,
      er1645v2EthPrtSwF2BrCL2ptDropThrOam
         INTEGER,
      er1645v2EthPrtSwF2BrCL2ptDropThrCdp
         INTEGER,
      er1645v2EthPrtSwF2BrCL2ptDropThrVtp
         INTEGER,
      er1645v2EthPrtSwF2BrCL2ptDropThrLacp
         INTEGER,
      er1645v2EthPrtSwF2BrCL2ptDropThrEfmOam
         INTEGER,
      er1645v2EthPrtSwF2BrCL2ptDropThrPvst
         INTEGER,
      er1645v2EthPrtSwF2BrCL2ptDropThrMmrp
         INTEGER,
      er1645v2EthPrtSwF2BrCL2ptDropThrMvrp
         INTEGER,
      er1645v2EthPrtSwF2BrCL2ptDropThrGvrp
         INTEGER,
      er1645v2EthPrtSwF2BrCL2ptDropThrGmrp
         INTEGER,
      er1645v2EthPrtSwF2BrCL2ptDropThrDtp
         INTEGER,
      er1645v2EthPrtSwF2BrCL2ptDropThrPagp
         INTEGER,
      er1645v2EthPrtSwF2BrCL2ptDropThrUdld
         INTEGER
      }

er1645v2EthPrtSwF2BrCGlobalIx OBJECT-TYPE
   SYNTAX      GlobalIndex
   MAX-ACCESS  not-accessible
   STATUS      current
   DESCRIPTION
      "The value of the tlsCntTreeGlobalIndex of the MANAGED OBJECT."
   ::= {er1645v2EthPrtSwF2BrCEntry 10}

er1645v2EthPrtSwF2BrCAccessList OBJECT-TYPE
   SYNTAX      DisplayString
   MAX-ACCESS  read-write
   STATUS      current
   DESCRIPTION
      "Path: swPort.editConf.bridging.accessList"
   ::= {er1645v2EthPrtSwF2BrCEntry 83886080}

er1645v2EthPrtSwF2BrCInAccessList OBJECT-TYPE
   SYNTAX      DisplayString
   MAX-ACCESS  read-write
   STATUS      current
   DESCRIPTION
      "Path: swPort.editConf.bridging.inAccessList"
   ::= {er1645v2EthPrtSwF2BrCEntry 251658240}

er1645v2EthPrtSwF2BrCTp OBJECT-TYPE
   SYNTAX      DisplayString
   MAX-ACCESS  read-write
   STATUS      current
   DESCRIPTION
      "Path: swPort.editConf.bridging.trafficPolicy"
   ::= {er1645v2EthPrtSwF2BrCEntry 100663296}

er1645v2EthPrtSwF2BrCBridgeGroup OBJECT-TYPE
   SYNTAX      DisplayString
   MAX-ACCESS  read-write
   STATUS      current
   DESCRIPTION
      "Path: swPort.editConf.bridging.bridgeGroup"
   ::= {er1645v2EthPrtSwF2BrCEntry 117440512}

er1645v2EthPrtSwF2BrCLimBC OBJECT-TYPE
   SYNTAX      INTEGER
               {
               disabled (0),
               enabled (1)
               }
   MAX-ACCESS  read-write
   STATUS      current
   DESCRIPTION
      "Path: swPort.editConf.bridging.limitBroadcasts

       Possibilities:
               disabled   (0)
               enabled   (1)"
   ::= {er1645v2EthPrtSwF2BrCEntry 134217728}

er1645v2EthPrtSwF2BrCPrivateMode OBJECT-TYPE
   SYNTAX      INTEGER
               {
               disabled (0),
               enabled (1)
               }
   MAX-ACCESS  read-write
   STATUS      current
   DESCRIPTION
      "Path: swPort.editConf.bridging.privateMode

       Possibilities:
               disabled   (0)
               enabled   (1)"
   ::= {er1645v2EthPrtSwF2BrCEntry 419430400}

er1645v2EthPrtSwF2BrCLearning OBJECT-TYPE
   SYNTAX      INTEGER
               {
               disabled (0),
               enabled (1)
               }
   MAX-ACCESS  read-write
   STATUS      current
   DESCRIPTION
      "Path: swPort.editConf.bridging.learning

       Possibilities:
               disabled   (0)
               enabled   (1)"
   ::= {er1645v2EthPrtSwF2BrCEntry 201326592}

er1645v2EthPrtSwF2BrCMaxCacheSize OBJECT-TYPE
   SYNTAX      INTEGER
               {
               unlimited (0)
               }
   MAX-ACCESS  read-write
   STATUS      current
   DESCRIPTION
      "Path: swPort.editConf.bridging.maxCacheSize

       Possibilities:
               unlimited   (0)"
   ::= {er1645v2EthPrtSwF2BrCEntry 218103808}

er1645v2EthPrtSwF2BrCRelearnDropOnRelearn OBJECT-TYPE
   SYNTAX      INTEGER
               {
               disabled (0),
               enabled (1)
               }
   MAX-ACCESS  read-write
   STATUS      current
   DESCRIPTION
      "Path: swPort.editConf.bridging.relearn.dropOnRelearn

       Possibilities:
               disabled   (0)
               enabled   (1)"
   ::= {er1645v2EthPrtSwF2BrCEntry 234946560}

er1645v2EthPrtSwF2BrCRelearnShutdownThreshold OBJECT-TYPE
   SYNTAX      Integer32
   MAX-ACCESS  read-write
   STATUS      current
   DESCRIPTION
      "Path: swPort.editConf.bridging.relearn.shutdownThreshold"
   ::= {er1645v2EthPrtSwF2BrCEntry 235012096}

er1645v2EthPrtSwF2BrCRelearnShutdownTime OBJECT-TYPE
   SYNTAX      TimeTicks
   MAX-ACCESS  read-write
   STATUS      current
   DESCRIPTION
      "Path: swPort.editConf.bridging.relearn.shutdownTime

       Time in centi-second."
   ::= {er1645v2EthPrtSwF2BrCEntry 235077632}

er1645v2EthPrtSwF2BrCRelearnLoopDetection OBJECT-TYPE
   SYNTAX      INTEGER
               {
               disabled (0),
               passive (1),
               active (2)
               }
   MAX-ACCESS  read-write
   STATUS      current
   DESCRIPTION
      "Path: swPort.editConf.bridging.relearn.loopDetection

       Possibilities:
               disabled   (0)
               passive   (1)
               active   (2)"
   ::= {er1645v2EthPrtSwF2BrCEntry 235143168}

er1645v2EthPrtSwF2BrCRelearnLoopDetectionInterval OBJECT-TYPE
   SYNTAX      TimeTicks
   MAX-ACCESS  read-write
   STATUS      current
   DESCRIPTION
      "Path: swPort.editConf.bridging.relearn.loopDetectionInterval

       Time in centi-second."
   ::= {er1645v2EthPrtSwF2BrCEntry 235208704}

er1645v2EthPrtSwF2BrCVlanMemberShip OBJECT-TYPE
   SYNTAX      INTEGER
               {
               all (0),
               none (1),
               grouped (2)
               }
   MAX-ACCESS  read-write
   STATUS      current
   DESCRIPTION
      "Path: swPort.editConf.bridging.vlanMemberShip

       Possibilities:
               all   (0)
               none   (1)
               grouped   (2)"
   ::= {er1645v2EthPrtSwF2BrCEntry 318767104}

er1645v2EthPrtSwF2BrCDot1adType OBJECT-TYPE
   SYNTAX      INTEGER
               {
               slOPTg (0),
               cPort (4),
               sPort (1),
               nni (2)
               }
   MAX-ACCESS  read-write
   STATUS      current
   DESCRIPTION
      "Path: swPort.editConf.bridging.dot1ad.type

       Possibilities:
               <OPT>   (0)
               cPort   (4)
               sPort   (1)
               nni   (2)"
   ::= {er1645v2EthPrtSwF2BrCEntry 503382016}

er1645v2EthPrtSwF2BrCPriority OBJECT-TYPE
   SYNTAX      Integer32
   MAX-ACCESS  read-write
   STATUS      current
   DESCRIPTION
      "Path: swPort.editConf.bridging.priority"
   ::= {er1645v2EthPrtSwF2BrCEntry 33554432}

er1645v2EthPrtSwF2BrCPathCost OBJECT-TYPE
   SYNTAX      Integer32
   MAX-ACCESS  read-write
   STATUS      current
   DESCRIPTION
      "Path: swPort.editConf.bridging.pathCost"
   ::= {er1645v2EthPrtSwF2BrCEntry 50331648}

er1645v2EthPrtSwF2BrCInternalPathCost OBJECT-TYPE
   SYNTAX      Integer32
   MAX-ACCESS  read-write
   STATUS      current
   DESCRIPTION
      "Path: swPort.editConf.bridging.internalPathCost"
   ::= {er1645v2EthPrtSwF2BrCEntry 301989888}

er1645v2EthPrtSwF2BrCTCD OBJECT-TYPE
   SYNTAX      INTEGER
               {
               disabled (0),
               enabled (1)
               }
   MAX-ACCESS  read-write
   STATUS      current
   DESCRIPTION
      "Path: swPort.editConf.bridging.topologyChangeDetection

       Possibilities:
               disabled   (0)
               enabled   (1)"
   ::= {er1645v2EthPrtSwF2BrCEntry 67108864}

er1645v2EthPrtSwF2BrCRestrictedRole OBJECT-TYPE
   SYNTAX      INTEGER
               {
               disabled (0),
               enabled (1)
               }
   MAX-ACCESS  read-write
   STATUS      current
   DESCRIPTION
      "Path: swPort.editConf.bridging.restrictedRole

       Possibilities:
               disabled   (0)
               enabled   (1)"
   ::= {er1645v2EthPrtSwF2BrCEntry 335544320}

er1645v2EthPrtSwF2BrCAdminEdge OBJECT-TYPE
   SYNTAX      INTEGER
               {
               disabled (0),
               enabled (1)
               }
   MAX-ACCESS  read-write
   STATUS      current
   DESCRIPTION
      "Path: swPort.editConf.bridging.adminEdge

       Possibilities:
               disabled   (0)
               enabled   (1)"
   ::= {er1645v2EthPrtSwF2BrCEntry 268435456}

er1645v2EthPrtSwF2BrCMgmtInline OBJECT-TYPE
   SYNTAX      INTEGER
               {
               disabled (0),
               enabled (1)
               }
   MAX-ACCESS  read-write
   STATUS      current
   DESCRIPTION
      "Path: swPort.editConf.bridging.mgmtInline

       Possibilities:
               disabled   (0)
               enabled   (1)"
   ::= {er1645v2EthPrtSwF2BrCEntry 369098752}

er1645v2EthPrtSwF2BrCL2ptMode OBJECT-TYPE
   SYNTAX      INTEGER
               {
               disabled (0),
               enabled (1)
               }
   MAX-ACCESS  read-write
   STATUS      current
   DESCRIPTION
      "Path: swPort.editConf.bridging.l2ProtTunnel.mode

       Possibilities:
               disabled   (0)
               enabled   (1)"
   ::= {er1645v2EthPrtSwF2BrCEntry 403701760}

er1645v2EthPrtSwF2BrCL2ptProtocols OBJECT-TYPE
   SYNTAX      Integer32
   MAX-ACCESS  read-write
   STATUS      current
   DESCRIPTION
      "Path: swPort.editConf.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1645v2EthPrtSwF2BrCEntry 404750336}

er1645v2EthPrtSwF2BrCL2ptDestMac OBJECT-TYPE
   SYNTAX      OCTET STRING
   MAX-ACCESS  read-write
   STATUS      current
   DESCRIPTION
      "Path: swPort.editConf.bridging.l2ProtTunnel.destinationMac

       MAC address."
   ::= {er1645v2EthPrtSwF2BrCEntry 405798912}

er1645v2EthPrtSwF2BrCL2ptCos OBJECT-TYPE
   SYNTAX      INTEGER
               {
               unchanged (255)
               }
   MAX-ACCESS  read-write
   STATUS      current
   DESCRIPTION
      "Path: swPort.editConf.bridging.l2ProtTunnel.cos

       Possibilities:
               unchanged   (255)"
   ::= {er1645v2EthPrtSwF2BrCEntry 406847488}

er1645v2EthPrtSwF2BrCL2ptDropThrStp OBJECT-TYPE
   SYNTAX      INTEGER
               {
               unlimited (0)
               }
   UNITS       "packets/sec"
   MAX-ACCESS  read-write
   STATUS      current
   DESCRIPTION
      "Path: swPort.editConf.bridging.l2ProtTunnel.dropThresholds.stp

       unit name = packets/sec

       Possibilities:
               unlimited   (0)"
   ::= {er1645v2EthPrtSwF2BrCEntry 407900160}

er1645v2EthPrtSwF2BrCL2ptDropThrLldp OBJECT-TYPE
   SYNTAX      INTEGER
               {
               unlimited (0)
               }
   UNITS       "packets/sec"
   MAX-ACCESS  read-write
   STATUS      current
   DESCRIPTION
      "Path: swPort.editConf.bridging.l2ProtTunnel.dropThresholds.lldp

       unit name = packets/sec

       Possibilities:
               unlimited   (0)"
   ::= {er1645v2EthPrtSwF2BrCEntry 407904256}

er1645v2EthPrtSwF2BrCL2ptDropThrOam OBJECT-TYPE
   SYNTAX      INTEGER
               {
               unlimited (0)
               }
   UNITS       "packets/sec"
   MAX-ACCESS  read-write
   STATUS      current
   DESCRIPTION
      "Path: swPort.editConf.bridging.l2ProtTunnel.dropThresholds.oam

       unit name = packets/sec

       Possibilities:
               unlimited   (0)"
   ::= {er1645v2EthPrtSwF2BrCEntry 407908352}

er1645v2EthPrtSwF2BrCL2ptDropThrCdp OBJECT-TYPE
   SYNTAX      INTEGER
               {
               unlimited (0)
               }
   UNITS       "packets/sec"
   MAX-ACCESS  read-write
   STATUS      current
   DESCRIPTION
      "Path: swPort.editConf.bridging.l2ProtTunnel.dropThresholds.cdp

       unit name = packets/sec

       Possibilities:
               unlimited   (0)"
   ::= {er1645v2EthPrtSwF2BrCEntry 407912448}

er1645v2EthPrtSwF2BrCL2ptDropThrVtp OBJECT-TYPE
   SYNTAX      INTEGER
               {
               unlimited (0)
               }
   UNITS       "packets/sec"
   MAX-ACCESS  read-write
   STATUS      current
   DESCRIPTION
      "Path: swPort.editConf.bridging.l2ProtTunnel.dropThresholds.vtp

       unit name = packets/sec

       Possibilities:
               unlimited   (0)"
   ::= {er1645v2EthPrtSwF2BrCEntry 407916544}

er1645v2EthPrtSwF2BrCL2ptDropThrLacp OBJECT-TYPE
   SYNTAX      INTEGER
               {
               unlimited (0)
               }
   UNITS       "packets/sec"
   MAX-ACCESS  read-write
   STATUS      current
   DESCRIPTION
      "Path: swPort.editConf.bridging.l2ProtTunnel.dropThresholds.lacp

       unit name = packets/sec

       Possibilities:
               unlimited   (0)"
   ::= {er1645v2EthPrtSwF2BrCEntry 407920640}

er1645v2EthPrtSwF2BrCL2ptDropThrEfmOam OBJECT-TYPE
   SYNTAX      INTEGER
               {
               unlimited (0)
               }
   UNITS       "packets/sec"
   MAX-ACCESS  read-write
   STATUS      current
   DESCRIPTION
      "Path: swPort.editConf.bridging.l2ProtTunnel.dropThresholds.efmOam

       unit name = packets/sec

       Possibilities:
               unlimited   (0)"
   ::= {er1645v2EthPrtSwF2BrCEntry 407924736}

er1645v2EthPrtSwF2BrCL2ptDropThrPvst OBJECT-TYPE
   SYNTAX      INTEGER
               {
               unlimited (0)
               }
   UNITS       "packets/sec"
   MAX-ACCESS  read-write
   STATUS      current
   DESCRIPTION
      "Path: swPort.editConf.bridging.l2ProtTunnel.dropThresholds.pvst

       unit name = packets/sec

       Possibilities:
               unlimited   (0)"
   ::= {er1645v2EthPrtSwF2BrCEntry 407928832}

er1645v2EthPrtSwF2BrCL2ptDropThrMmrp OBJECT-TYPE
   SYNTAX      INTEGER
               {
               unlimited (0)
               }
   UNITS       "packets/sec"
   MAX-ACCESS  read-write
   STATUS      current
   DESCRIPTION
      "Path: swPort.editConf.bridging.l2ProtTunnel.dropThresholds.mmrp

       unit name = packets/sec

       Possibilities:
               unlimited   (0)"
   ::= {er1645v2EthPrtSwF2BrCEntry 407932928}

er1645v2EthPrtSwF2BrCL2ptDropThrMvrp OBJECT-TYPE
   SYNTAX      INTEGER
               {
               unlimited (0)
               }
   UNITS       "packets/sec"
   MAX-ACCESS  read-write
   STATUS      current
   DESCRIPTION
      "Path: swPort.editConf.bridging.l2ProtTunnel.dropThresholds.mvrp

       unit name = packets/sec

       Possibilities:
               unlimited   (0)"
   ::= {er1645v2EthPrtSwF2BrCEntry 407937024}

er1645v2EthPrtSwF2BrCL2ptDropThrGvrp OBJECT-TYPE
   SYNTAX      INTEGER
               {
               unlimited (0)
               }
   UNITS       "packets/sec"
   MAX-ACCESS  read-write
   STATUS      current
   DESCRIPTION
      "Path: swPort.editConf.bridging.l2ProtTunnel.dropThresholds.gvrp

       unit name = packets/sec

       Possibilities:
               unlimited   (0)"
   ::= {er1645v2EthPrtSwF2BrCEntry 407941120}

er1645v2EthPrtSwF2BrCL2ptDropThrGmrp OBJECT-TYPE
   SYNTAX      INTEGER
               {
               unlimited (0)
               }
   UNITS       "packets/sec"
   MAX-ACCESS  read-write
   STATUS      current
   DESCRIPTION
      "Path: swPort.editConf.bridging.l2ProtTunnel.dropThresholds.gmrp

       unit name = packets/sec

       Possibilities:
               unlimited   (0)"
   ::= {er1645v2EthPrtSwF2BrCEntry 407945216}

er1645v2EthPrtSwF2BrCL2ptDropThrDtp OBJECT-TYPE
   SYNTAX      INTEGER
               {
               unlimited (0)
               }
   UNITS       "packets/sec"
   MAX-ACCESS  read-write
   STATUS      current
   DESCRIPTION
      "Path: swPort.editConf.bridging.l2ProtTunnel.dropThresholds.dtp

       unit name = packets/sec

       Possibilities:
               unlimited   (0)"
   ::= {er1645v2EthPrtSwF2BrCEntry 407949312}

er1645v2EthPrtSwF2BrCL2ptDropThrPagp OBJECT-TYPE
   SYNTAX      INTEGER
               {
               unlimited (0)
               }
   UNITS       "packets/sec"
   MAX-ACCESS  read-write
   STATUS      current
   DESCRIPTION
      "Path: swPort.editConf.bridging.l2ProtTunnel.dropThresholds.pagp

       unit name = packets/sec

       Possibilities:
               unlimited   (0)"
   ::= {er1645v2EthPrtSwF2BrCEntry 407953408}

er1645v2EthPrtSwF2BrCL2ptDropThrUdld OBJECT-TYPE
   SYNTAX      INTEGER
               {
               unlimited (0)
               }
   UNITS       "packets/sec"
   MAX-ACCESS  read-write
   STATUS      current
   DESCRIPTION
      "Path: swPort.editConf.bridging.l2ProtTunnel.dropThresholds.udld

       unit name = packets/sec

       Possibilities:
               unlimited   (0)"
   ::= {er1645v2EthPrtSwF2BrCEntry 407957504}


er1645v2EthPrtSwF2VlanTagging OBJECT IDENTIFIER ::= {er1645v2EthPrtSwF2 14}

er1645v2EthPrtSwF2VlanTaggingSSCTable OBJECT-TYPE
   SYNTAX      SEQUENCE OF Er1645v2EthPrtSwF2VlanTaggingEntry
   MAX-ACCESS  not-accessible
   STATUS      current
   DESCRIPTION
      "vlan tagging config"
   ::= {er1645v2EthPrtSwF2VlanTagging 1}

er1645v2EthPrtSwF2VlanTaggingEntry OBJECT-TYPE
   SYNTAX      Er1645v2EthPrtSwF2VlanTaggingEntry
   MAX-ACCESS  not-accessible
   STATUS      current
   DESCRIPTION
      ""
   INDEX      { er1645v2EthPrtSwF2VlanTaggingGlobalIx }
   ::= {er1645v2EthPrtSwF2VlanTaggingSSCTable 1}

Er1645v2EthPrtSwF2VlanTaggingEntry ::=
   SEQUENCE
      {
      er1645v2EthPrtSwF2VlanTaggingGlobalIx
         GlobalIndex,
      er1645v2EthPrtSwF2VlanTaggingUntaggedAction
         INTEGER,
      er1645v2EthPrtSwF2VlanTaggingUntaggedTagInfoTpid
         INTEGER,
      er1645v2EthPrtSwF2VlanTaggingUntaggedTagInfoVid
         Integer32,
      er1645v2EthPrtSwF2VlanTaggingUnknownVlansAction
         INTEGER,
      er1645v2EthPrtSwF2VlanTaggingUnknownVlansTagInfoTpid
         INTEGER,
      er1645v2EthPrtSwF2VlanTaggingUnknownVlansTagInfoVid
         Integer32
      }

er1645v2EthPrtSwF2VlanTaggingGlobalIx OBJECT-TYPE
   SYNTAX      GlobalIndex
   MAX-ACCESS  not-accessible
   STATUS      current
   DESCRIPTION
      "The value of the tlsCntTreeGlobalIndex of the MANAGED OBJECT."
   ::= {er1645v2EthPrtSwF2VlanTaggingEntry 10}

er1645v2EthPrtSwF2VlanTaggingUntaggedAction OBJECT-TYPE
   SYNTAX      INTEGER
               {
               discard (0),
               accept (1),
               tag (2)
               }
   MAX-ACCESS  read-write
   STATUS      current
   DESCRIPTION
      "Path: swPort.editConf.vlanTagging.untagged.action

       Possibilities:
               discard   (0)
               accept   (1)
               tag   (2)"
   ::= {er1645v2EthPrtSwF2VlanTaggingEntry 671088640}

er1645v2EthPrtSwF2VlanTaggingUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlanTagging.untagged.tagInfo.tpid

       Possibilities:
               dot1Q   (33024)
               dot1ad   (34984)
               0x9100   (37120)
               0x9200   (37376)
               0x9300   (37632)"
   ::= {er1645v2EthPrtSwF2VlanTaggingEntry 746586112}

er1645v2EthPrtSwF2VlanTaggingUntaggedTagInfoVid OBJECT-TYPE
   SYNTAX      Integer32
   MAX-ACCESS  read-write
   STATUS      current
   DESCRIPTION
      "Path: swPort.editConf.vlanTagging.untagged.tagInfo.vid"
   ::= {er1645v2EthPrtSwF2VlanTaggingEntry 754974720}

er1645v2EthPrtSwF2VlanTaggingUnknownVlansAction OBJECT-TYPE
   SYNTAX      INTEGER
               {
               discard (0),
               accept (1),
               tag (2)
               }
   MAX-ACCESS  read-write
   STATUS      current
   DESCRIPTION
      "Path: swPort.editConf.vlanTagging.unknownVlans.action

       Possibilities:
               discard   (0)
               accept   (1)
               tag   (2)"
   ::= {er1645v2EthPrtSwF2VlanTaggingEntry 1744830464}

er1645v2EthPrtSwF2VlanTaggingUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlanTagging.unknownVlans.tagInfo.tpid

       Possibilities:
               dot1Q   (33024)
               dot1ad   (34984)
               0x9100   (37120)
               0x9200   (37376)
               0x9300   (37632)"
   ::= {er1645v2EthPrtSwF2VlanTaggingEntry 1820327936}

er1645v2EthPrtSwF2VlanTaggingUnknownVlansTagInfoVid OBJECT-TYPE
   SYNTAX      Integer32
   MAX-ACCESS  read-write
   STATUS      current
   DESCRIPTION
      "Path: swPort.editConf.vlanTagging.unknownVlans.tagInfo.vid"
   ::= {er1645v2EthPrtSwF2VlanTaggingEntry 1828716544}

er1645v2EthPrtSwF2VlanTaggingVlans OBJECT-TYPE
   SYNTAX      SEQUENCE OF Er1645v2EthPrtSwF2VlanTaggingVlansEntry
   MAX-ACCESS  not-accessible
   STATUS      current
   DESCRIPTION
      ""
   ::= {er1645v2EthPrtSwF2VlanTagging 1073741824}

er1645v2EthPrtSwF2VlanTaggingVlansEntry OBJECT-TYPE
   SYNTAX      Er1645v2EthPrtSwF2VlanTaggingVlansEntry
   MAX-ACCESS  not-accessible
   STATUS      current
   DESCRIPTION
      ""
   INDEX      { er1645v2EthPrtSwF2VlanTaggingVlansGlobalIx,
                er1645v2EthPrtSwF2VlanTaggingVlansTableIx }
   ::= {er1645v2EthPrtSwF2VlanTaggingVlans 1}

Er1645v2EthPrtSwF2VlanTaggingVlansEntry ::=
   SEQUENCE
      {
      er1645v2EthPrtSwF2VlanTaggingVlansActions
         VariableLengthTableActions,
      er1645v2EthPrtSwF2VlanTaggingVlansGlobalIx
         GlobalIndex,
      er1645v2EthPrtSwF2VlanTaggingVlansTableIx
         TableIndex,
      er1645v2EthPrtSwF2VlanTaggingVlansVid
         Integer32,
      er1645v2EthPrtSwF2VlanTaggingVlansEndVid
         Integer32,
      er1645v2EthPrtSwF2VlanTaggingVlansAction
         INTEGER,
      er1645v2EthPrtSwF2VlanTaggingVlansTagInfoTpid
         INTEGER,
      er1645v2EthPrtSwF2VlanTaggingVlansTagInfoVid
         Integer32
      }

er1645v2EthPrtSwF2VlanTaggingVlansActions OBJECT-TYPE
   SYNTAX      VariableLengthTableActions
   MAX-ACCESS  read-write
   STATUS      current
   DESCRIPTION
      "By way of this field, some manipulations
       on this table may be performed."
   ::= {er1645v2EthPrtSwF2VlanTaggingVlansEntry 2}

er1645v2EthPrtSwF2VlanTaggingVlansGlobalIx OBJECT-TYPE
   SYNTAX      GlobalIndex
   MAX-ACCESS  not-accessible
   STATUS      current
   DESCRIPTION
      "The value of the tlsCntTreeGlobalIndex of the MANAGED OBJECT."
   ::= {er1645v2EthPrtSwF2VlanTaggingVlansEntry 10}

er1645v2EthPrtSwF2VlanTaggingVlansTableIx OBJECT-TYPE
   SYNTAX      TableIndex
   MAX-ACCESS  not-accessible
   STATUS      current
   DESCRIPTION
      ""
   ::= {er1645v2EthPrtSwF2VlanTaggingVlansEntry 11}

er1645v2EthPrtSwF2VlanTaggingVlansVid OBJECT-TYPE
   SYNTAX      Integer32
   MAX-ACCESS  read-write
   STATUS      current
   DESCRIPTION
      "Path: swPort.editConf.vlanTagging.vlans.vid"
   ::= {er1645v2EthPrtSwF2VlanTaggingVlansEntry 536870912}

er1645v2EthPrtSwF2VlanTaggingVlansEndVid OBJECT-TYPE
   SYNTAX      Integer32
   MAX-ACCESS  read-write
   STATUS      current
   DESCRIPTION
      "Path: swPort.editConf.vlanTagging.vlans.endVid"
   ::= {er1645v2EthPrtSwF2VlanTaggingVlansEntry 2147483648}

er1645v2EthPrtSwF2VlanTaggingVlansAction OBJECT-TYPE
   SYNTAX      INTEGER
               {
               discard (0),
               accept (1),
               tag (2)
               }
   MAX-ACCESS  read-write
   STATUS      current
   DESCRIPTION
      "Path: swPort.editConf.vlanTagging.vlans.action

       Possibilities:
               discard   (0)
               accept   (1)
               tag   (2)"
   ::= {er1645v2EthPrtSwF2VlanTaggingVlansEntry 1073741824}

er1645v2EthPrtSwF2VlanTaggingVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlanTagging.vlans.tagInfo.tpid

       Possibilities:
               dot1Q   (33024)
               dot1ad   (34984)
               0x9100   (37120)
               0x9200   (37376)
               0x9300   (37632)"
   ::= {er1645v2EthPrtSwF2VlanTaggingVlansEntry 1677721600}

er1645v2EthPrtSwF2VlanTaggingVlansTagInfoVid OBJECT-TYPE
   SYNTAX      Integer32
   MAX-ACCESS  read-write
   STATUS      current
   DESCRIPTION
      "Path: swPort.editConf.vlanTagging.vlans.tagInfo.vid"
   ::= {er1645v2EthPrtSwF2VlanTaggingVlansEntry 1744830464}


er1645v2EthPrtSwF2Oam OBJECT IDENTIFIER ::= {er1645v2EthPrtSwF2 900}

er1645v2EthPrtSwF2OamSSCTable OBJECT-TYPE
   SYNTAX      SEQUENCE OF Er1645v2EthPrtSwF2OamEntry
   MAX-ACCESS  not-accessible
   STATUS      current
   DESCRIPTION
      "OAM mode"
   ::= {er1645v2EthPrtSwF2Oam 1}

er1645v2EthPrtSwF2OamEntry OBJECT-TYPE
   SYNTAX      Er1645v2EthPrtSwF2OamEntry
   MAX-ACCESS  not-accessible
   STATUS      current
   DESCRIPTION
      ""
   INDEX      { er1645v2EthPrtSwF2OamGlobalIx }
   ::= {er1645v2EthPrtSwF2OamSSCTable 1}

Er1645v2EthPrtSwF2OamEntry ::=
   SEQUENCE
      {
      er1645v2EthPrtSwF2OamGlobalIx
         GlobalIndex,
      er1645v2EthPrtSwF2OamMode
         INTEGER,
      er1645v2EthPrtSwF2OamLpbkLocalParAction
         INTEGER,
      er1645v2EthPrtSwF2OamLpbkSwapMacAddr
         INTEGER,
      er1645v2EthPrtSwF2OamLoopbackIgnoreRx
         INTEGER,
      er1645v2EthPrtSwF2OamEventsErroredSymbolEnabled
         INTEGER,
      er1645v2EthPrtSwF2OamEventsErroredSymbolWindowHi
         INTEGER,
      er1645v2EthPrtSwF2OamEventsErroredSymbolWindowLo
         INTEGER,
      er1645v2EthPrtSwF2OamEventsErroredSymbolThresholdHi
         Integer32,
      er1645v2EthPrtSwF2OamEventsErroredSymbolThresholdLo
         Integer32,
      er1645v2EthPrtSwF2OamEventsErroredFramePeriodEnabled
         INTEGER,
      er1645v2EthPrtSwF2OamEventsErroredFramePeriodWindow
         INTEGER,
      er1645v2EthPrtSwF2OamEventsErroredFramePeriodThreshold
         Integer32,
      er1645v2EthPrtSwF2OamEventsErroredFrameEnabled
         INTEGER,
      er1645v2EthPrtSwF2OamEventsErroredFrameWindow
         Integer32,
      er1645v2EthPrtSwF2OamEventsErroredFrameThreshold
         Integer32,
      er1645v2EthPrtSwF2OamEventsErroredFrameSecondsEnabled
         INTEGER,
      er1645v2EthPrtSwF2OamEventsErroredFrameSecondsWindow
         Integer32,
      er1645v2EthPrtSwF2OamEventsErroredFrameSecondsThreshold
         Integer32,
      er1645v2EthPrtSwF2OamEventsDyingGasp
         INTEGER,
      er1645v2EthPrtSwF2OamEventsCriticalEvent
         INTEGER
      }

er1645v2EthPrtSwF2OamGlobalIx OBJECT-TYPE
   SYNTAX      GlobalIndex
   MAX-ACCESS  not-accessible
   STATUS      current
   DESCRIPTION
      "The value of the tlsCntTreeGlobalIndex of the MANAGED OBJECT."
   ::= {er1645v2EthPrtSwF2OamEntry 10}

er1645v2EthPrtSwF2OamMode OBJECT-TYPE
   SYNTAX      INTEGER
               {
               disabled (0),
               passive (3),
               active (2)
               }
   MAX-ACCESS  read-write
   STATUS      current
   DESCRIPTION
      "Path: swPort.editConf.oam.mode

       Possibilities:
               disabled   (0)
               passive   (3)
               active   (2)"
   ::= {er1645v2EthPrtSwF2OamEntry 16777216}

er1645v2EthPrtSwF2OamLpbkLocalParAction OBJECT-TYPE
   SYNTAX      INTEGER
               {
               discard (0),
               forward (1)
               }
   MAX-ACCESS  read-write
   STATUS      current
   DESCRIPTION
      "Path: swPort.editConf.oam.loopbackLocalParserAction

       Possibilities:
               discard   (0)
               forward   (1)"
   ::= {er1645v2EthPrtSwF2OamEntry 33554432}

er1645v2EthPrtSwF2OamLpbkSwapMacAddr OBJECT-TYPE
   SYNTAX      INTEGER
               {
               disabled (0),
               enabled (1)
               }
   MAX-ACCESS  read-write
   STATUS      current
   DESCRIPTION
      "Path: swPort.editConf.oam.loopbackSwapMacAddresses

       Possibilities:
               disabled   (0)
               enabled   (1)"
   ::= {er1645v2EthPrtSwF2OamEntry 50331648}

er1645v2EthPrtSwF2OamLoopbackIgnoreRx OBJECT-TYPE
   SYNTAX      INTEGER
               {
               no (0),
               yes (1)
               }
   MAX-ACCESS  read-write
   STATUS      current
   DESCRIPTION
      "Path: swPort.editConf.oam.loopbackIgnoreRx

       Possibilities:
               no   (0)
               yes   (1)"
   ::= {er1645v2EthPrtSwF2OamEntry 67108864}

er1645v2EthPrtSwF2OamEventsErroredSymbolEnabled OBJECT-TYPE
   SYNTAX      INTEGER
               {
               no (0),
               yes (1)
               }
   MAX-ACCESS  read-write
   STATUS      current
   DESCRIPTION
      "Path: swPort.editConf.oam.events.erroredSymbol.enabled

       Possibilities:
               no   (0)
               yes   (1)"
   ::= {er1645v2EthPrtSwF2OamEntry 83951872}

er1645v2EthPrtSwF2OamEventsErroredSymbolWindowHi OBJECT-TYPE
   SYNTAX      INTEGER
               {
               default (0)
               }
   UNITS       "symbols"
   MAX-ACCESS  read-write
   STATUS      current
   DESCRIPTION
      "Path: swPort.editConf.oam.events.erroredSymbol.windowHi

       unit name = symbols

       Possibilities:
               default   (0)"
   ::= {er1645v2EthPrtSwF2OamEntry 83952128}

er1645v2EthPrtSwF2OamEventsErroredSymbolWindowLo OBJECT-TYPE
   SYNTAX      INTEGER
               {
               default (0)
               }
   UNITS       "symbols"
   MAX-ACCESS  read-write
   STATUS      current
   DESCRIPTION
      "Path: swPort.editConf.oam.events.erroredSymbol.windowLo

       unit name = symbols

       Possibilities:
               default   (0)"
   ::= {er1645v2EthPrtSwF2OamEntry 83952384}

er1645v2EthPrtSwF2OamEventsErroredSymbolThresholdHi OBJECT-TYPE
   SYNTAX      Integer32
   UNITS       "symbols"
   MAX-ACCESS  read-write
   STATUS      current
   DESCRIPTION
      "Path: swPort.editConf.oam.events.erroredSymbol.thresholdHi

       unit name = symbols"
   ::= {er1645v2EthPrtSwF2OamEntry 83952640}

er1645v2EthPrtSwF2OamEventsErroredSymbolThresholdLo OBJECT-TYPE
   SYNTAX      Integer32
   UNITS       "symbols"
   MAX-ACCESS  read-write
   STATUS      current
   DESCRIPTION
      "Path: swPort.editConf.oam.events.erroredSymbol.thresholdLo

       unit name = symbols"
   ::= {er1645v2EthPrtSwF2OamEntry 83952896}

er1645v2EthPrtSwF2OamEventsErroredFramePeriodEnabled OBJECT-TYPE
   SYNTAX      INTEGER
               {
               no (0),
               yes (1)
               }
   MAX-ACCESS  read-write
   STATUS      current
   DESCRIPTION
      "Path: swPort.editConf.oam.events.erroredFramePeriod.enabled

       Possibilities:
               no   (0)
               yes   (1)"
   ::= {er1645v2EthPrtSwF2OamEntry 84017408}

er1645v2EthPrtSwF2OamEventsErroredFramePeriodWindow OBJECT-TYPE
   SYNTAX      INTEGER
               {
               default (0)
               }
   UNITS       "frames"
   MAX-ACCESS  read-write
   STATUS      current
   DESCRIPTION
      "Path: swPort.editConf.oam.events.erroredFramePeriod.window

       unit name = frames

       Possibilities:
               default   (0)"
   ::= {er1645v2EthPrtSwF2OamEntry 84017664}

er1645v2EthPrtSwF2OamEventsErroredFramePeriodThreshold OBJECT-TYPE
   SYNTAX      Integer32
   UNITS       "frames"
   MAX-ACCESS  read-write
   STATUS      current
   DESCRIPTION
      "Path: swPort.editConf.oam.events.erroredFramePeriod.threshold

       unit name = frames"
   ::= {er1645v2EthPrtSwF2OamEntry 84017920}

er1645v2EthPrtSwF2OamEventsErroredFrameEnabled OBJECT-TYPE
   SYNTAX      INTEGER
               {
               no (0),
               yes (1)
               }
   MAX-ACCESS  read-write
   STATUS      current
   DESCRIPTION
      "Path: swPort.editConf.oam.events.erroredFrame.enabled

       Possibilities:
               no   (0)
               yes   (1)"
   ::= {er1645v2EthPrtSwF2OamEntry 84082944}

er1645v2EthPrtSwF2OamEventsErroredFrameWindow OBJECT-TYPE
   SYNTAX      Integer32
   UNITS       "100msec"
   MAX-ACCESS  read-write
   STATUS      current
   DESCRIPTION
      "Path: swPort.editConf.oam.events.erroredFrame.window

       unit name = 100msec"
   ::= {er1645v2EthPrtSwF2OamEntry 84083200}

er1645v2EthPrtSwF2OamEventsErroredFrameThreshold OBJECT-TYPE
   SYNTAX      Integer32
   UNITS       "frames"
   MAX-ACCESS  read-write
   STATUS      current
   DESCRIPTION
      "Path: swPort.editConf.oam.events.erroredFrame.threshold

       unit name = frames"
   ::= {er1645v2EthPrtSwF2OamEntry 84083456}

er1645v2EthPrtSwF2OamEventsErroredFrameSecondsEnabled OBJECT-TYPE
   SYNTAX      INTEGER
               {
               no (0),
               yes (1)
               }
   MAX-ACCESS  read-write
   STATUS      current
   DESCRIPTION
      "Path: swPort.editConf.oam.events.erroredFrameSeconds.enabled

       Possibilities:
               no   (0)
               yes   (1)"
   ::= {er1645v2EthPrtSwF2OamEntry 84148480}

er1645v2EthPrtSwF2OamEventsErroredFrameSecondsWindow OBJECT-TYPE
   SYNTAX      Integer32
   UNITS       "100msec"
   MAX-ACCESS  read-write
   STATUS      current
   DESCRIPTION
      "Path: swPort.editConf.oam.events.erroredFrameSeconds.window

       unit name = 100msec"
   ::= {er1645v2EthPrtSwF2OamEntry 84148736}

er1645v2EthPrtSwF2OamEventsErroredFrameSecondsThreshold OBJECT-TYPE
   SYNTAX      Integer32
   UNITS       "frames"
   MAX-ACCESS  read-write
   STATUS      current
   DESCRIPTION
      "Path: swPort.editConf.oam.events.erroredFrameSeconds.threshold

       unit name = frames"
   ::= {er1645v2EthPrtSwF2OamEntry 84148992}

er1645v2EthPrtSwF2OamEventsDyingGasp OBJECT-TYPE
   SYNTAX      INTEGER
               {
               disabled (0),
               enabled (1)
               }
   MAX-ACCESS  read-write
   STATUS      current
   DESCRIPTION
      "Path: swPort.editConf.oam.events.dyingGasp

       Possibilities:
               disabled   (0)
               enabled   (1)"
   ::= {er1645v2EthPrtSwF2OamEntry 84213760}

er1645v2EthPrtSwF2OamEventsCriticalEvent OBJECT-TYPE
   SYNTAX      INTEGER
               {
               disabled (0),
               enabled (1)
               }
   MAX-ACCESS  read-write
   STATUS      current
   DESCRIPTION
      "Path: swPort.editConf.oam.events.criticalEvent

       Possibilities:
               disabled   (0)
               enabled   (1)"
   ::= {er1645v2EthPrtSwF2OamEntry 84279296}


er1645v2EthPrtSwF2Dot1x OBJECT IDENTIFIER ::= {er1645v2EthPrtSwF2 191}

er1645v2EthPrtSwF2Dot1xSSCTable OBJECT-TYPE
   SYNTAX      SEQUENCE OF Er1645v2EthPrtSwF2Dot1xEntry
   MAX-ACCESS  not-accessible
   STATUS      current
   DESCRIPTION
      "ppp server name on interface"
   ::= {er1645v2EthPrtSwF2Dot1x 1}

er1645v2EthPrtSwF2Dot1xEntry OBJECT-TYPE
   SYNTAX      Er1645v2EthPrtSwF2Dot1xEntry
   MAX-ACCESS  not-accessible
   STATUS      current
   DESCRIPTION
      ""
   INDEX      { er1645v2EthPrtSwF2Dot1xGlobalIx }
   ::= {er1645v2EthPrtSwF2Dot1xSSCTable 1}

Er1645v2EthPrtSwF2Dot1xEntry ::=
   SEQUENCE
      {
      er1645v2EthPrtSwF2Dot1xGlobalIx
         GlobalIndex,
      er1645v2EthPrtSwF2Dot1xMode
         INTEGER,
      er1645v2EthPrtSwF2Dot1xMaxHosts
         Integer32,
      er1645v2EthPrtSwF2Dot1xReAuthentication
         INTEGER,
      er1645v2EthPrtSwF2Dot1xReAuthPeriod
         TimeTicks,
      er1645v2EthPrtSwF2Dot1xQuietPeriod
         TimeTicks,
      er1645v2EthPrtSwF2Dot1xSupplTimeout
         TimeTicks,
      er1645v2EthPrtSwF2Dot1xServerTimeout
         TimeTicks,
      er1645v2EthPrtSwF2Dot1xMaxReqCount
         Integer32
      }

er1645v2EthPrtSwF2Dot1xGlobalIx OBJECT-TYPE
   SYNTAX      GlobalIndex
   MAX-ACCESS  not-accessible
   STATUS      current
   DESCRIPTION
      "The value of the tlsCntTreeGlobalIndex of the MANAGED OBJECT."
   ::= {er1645v2EthPrtSwF2Dot1xEntry 10}

er1645v2EthPrtSwF2Dot1xMode OBJECT-TYPE
   SYNTAX      INTEGER
               {
               inactive (0),
               auto (1)
               }
   MAX-ACCESS  read-write
   STATUS      current
   DESCRIPTION
      "Path: swPort.editConf.dot1x.mode

       Possibilities:
               inactive   (0)
               auto   (1)"
   ::= {er1645v2EthPrtSwF2Dot1xEntry 16777216}

er1645v2EthPrtSwF2Dot1xMaxHosts OBJECT-TYPE
   SYNTAX      Integer32
   MAX-ACCESS  read-write
   STATUS      current
   DESCRIPTION
      "Path: swPort.editConf.dot1x.maxHosts"
   ::= {er1645v2EthPrtSwF2Dot1xEntry 33554432}

er1645v2EthPrtSwF2Dot1xReAuthentication OBJECT-TYPE
   SYNTAX      INTEGER
               {
               disabled (0),
               enabled (1)
               }
   MAX-ACCESS  read-write
   STATUS      current
   DESCRIPTION
      "Path: swPort.editConf.dot1x.reAuthentication

       Possibilities:
               disabled   (0)
               enabled   (1)"
   ::= {er1645v2EthPrtSwF2Dot1xEntry 50331648}

er1645v2EthPrtSwF2Dot1xReAuthPeriod OBJECT-TYPE
   SYNTAX      TimeTicks
   MAX-ACCESS  read-write
   STATUS      current
   DESCRIPTION
      "Path: swPort.editConf.dot1x.reAuthPeriod

       Time in centi-second."
   ::= {er1645v2EthPrtSwF2Dot1xEntry 67108864}

er1645v2EthPrtSwF2Dot1xQuietPeriod OBJECT-TYPE
   SYNTAX      TimeTicks
   MAX-ACCESS  read-write
   STATUS      current
   DESCRIPTION
      "Path: swPort.editConf.dot1x.quietPeriod

       Time in centi-second."
   ::= {er1645v2EthPrtSwF2Dot1xEntry 83886080}

er1645v2EthPrtSwF2Dot1xSupplTimeout OBJECT-TYPE
   SYNTAX      TimeTicks
   MAX-ACCESS  read-write
   STATUS      current
   DESCRIPTION
      "Path: swPort.editConf.dot1x.supplTimeout

       Time in centi-second."
   ::= {er1645v2EthPrtSwF2Dot1xEntry 100663296}

er1645v2EthPrtSwF2Dot1xServerTimeout OBJECT-TYPE
   SYNTAX      TimeTicks
   MAX-ACCESS  read-write
   STATUS      current
   DESCRIPTION
      "Path: swPort.editConf.dot1x.serverTimeout

       Time in centi-second."
   ::= {er1645v2EthPrtSwF2Dot1xEntry 117440512}

er1645v2EthPrtSwF2Dot1xMaxReqCount OBJECT-TYPE
   SYNTAX      Integer32
   MAX-ACCESS  read-write
   STATUS      current
   DESCRIPTION
      "Path: swPort.editConf.dot1x.maxReqCount"
   ::= {er1645v2EthPrtSwF2Dot1xEntry 134217728}


er1645v2EthPrtSwF2IpV6 OBJECT IDENTIFIER ::= {er1645v2EthPrtSwF2 15}

er1645v2EthPrtSwF2IpV6SSCTable OBJECT-TYPE
   SYNTAX      SEQUENCE OF Er1645v2EthPrtSwF2IpV6Entry
   MAX-ACCESS  not-accessible
   STATUS      current
   DESCRIPTION
      "IPv6 interface config parameters"
   ::= {er1645v2EthPrtSwF2IpV6 1}

er1645v2EthPrtSwF2IpV6Entry OBJECT-TYPE
   SYNTAX      Er1645v2EthPrtSwF2IpV6Entry
   MAX-ACCESS  not-accessible
   STATUS      current
   DESCRIPTION
      ""
   INDEX      { er1645v2EthPrtSwF2IpV6GlobalIx }
   ::= {er1645v2EthPrtSwF2IpV6SSCTable 1}

Er1645v2EthPrtSwF2IpV6Entry ::=
   SEQUENCE
      {
      er1645v2EthPrtSwF2IpV6GlobalIx
         GlobalIndex,
      er1645v2EthPrtSwF2IpV6VrfRouter
         DisplayString,
      er1645v2EthPrtSwF2IpV6AddrAutoConfigNrDupAddrDetects
         Integer32,
      er1645v2EthPrtSwF2IpV6AddrAutoConfigAcceptRa
         INTEGER,
      er1645v2EthPrtSwF2IpV6AddrAutoConfigAcceptRaRdnss
         INTEGER,
      er1645v2EthPrtSwF2IpV6AddrAutoConfigAcceptRaDnssl
         INTEGER,
      er1645v2EthPrtSwF2IpV6DefaultRoute
         INTEGER,
      er1645v2EthPrtSwF2IpV6RaSend
         INTEGER,
      er1645v2EthPrtSwF2IpV6RaMinInterval
         TimeTicks,
      er1645v2EthPrtSwF2IpV6RaMaxInterval
         TimeTicks,
      er1645v2EthPrtSwF2IpV6RaManagedFlag
         INTEGER,
      er1645v2EthPrtSwF2IpV6RaOtherConfFlag
         INTEGER,
      er1645v2EthPrtSwF2IpV6RaLinkMtu
         Integer32,
      er1645v2EthPrtSwF2IpV6RaReachableTime
         TimeTicks,
      er1645v2EthPrtSwF2IpV6RaRetransmitTime
         TimeTicks,
      er1645v2EthPrtSwF2IpV6RaHopLimit
         Integer32,
      er1645v2EthPrtSwF2IpV6RaDefaultLifeTime
         TimeTicks,
      er1645v2EthPrtSwF2IpV6RaDnsOptionsRdnssLifeTime
         TimeTicks,
      er1645v2EthPrtSwF2IpV6RaDnsOptionsRdnssImportServers
         INTEGER,
      er1645v2EthPrtSwF2IpV6RaDnsOptionsDnsslLifeTime
         TimeTicks,
      er1645v2EthPrtSwF2IpV6RaDnsOptionsDnsslImportDomains
         INTEGER,
      er1645v2EthPrtSwF2IpV6RsSend
         INTEGER,
      er1645v2EthPrtSwF2IpV6RsMaxRandomDelay
         TimeTicks,
      er1645v2EthPrtSwF2IpV6RsInterval
         TimeTicks,
      er1645v2EthPrtSwF2IpV6RsMaxSolicitations
         Integer32,
      er1645v2EthPrtSwF2IpV6TrafficPolicyInbound
         DisplayString,
      er1645v2EthPrtSwF2IpV6TrafficPolicyOutbound
         DisplayString,
      er1645v2EthPrtSwF2IpV6FirewallZone
         DisplayString,
      er1645v2EthPrtSwF2IpV6DhcpClientAddrAC
         INTEGER,
      er1645v2EthPrtSwF2IpV6DhcpClientPrDelMode
         INTEGER,
      er1645v2EthPrtSwF2IpV6DhcpClientPrDelPool
         DisplayString,
      er1645v2EthPrtSwF2IpV6DhcpClientPrDelPdExclOpt
         INTEGER,
      er1645v2EthPrtSwF2IpV6DhcpClientDnsServerPref
         Integer32,
      er1645v2EthPrtSwF2IpV6DhcpClientRapidCommit
         INTEGER,
      er1645v2EthPrtSwF2IpV6DhcpClientTimersSolTimeOut
         TimeTicks,
      er1645v2EthPrtSwF2IpV6DhcpClientTimersSolMaxRt
         TimeTicks,
      er1645v2EthPrtSwF2IpV6DhcpClientTimersInfoRefresh
         TimeTicks,
      er1645v2EthPrtSwF2IpV6DhcpServerMode
         INTEGER,
      er1645v2EthPrtSwF2IpV6DhcpServerPreference
         Integer32,
      er1645v2EthPrtSwF2IpV6DhcpServerPool
         DisplayString,
      er1645v2EthPrtSwF2IpV6DhcpServerRapidCommit
         INTEGER,
      er1645v2EthPrtSwF2IpV6DhcpServerTimersInfoRefresh
         TimeTicks,
      er1645v2EthPrtSwF2IpV6DhcpRelayMode
         INTEGER,
      er1645v2EthPrtSwF2IpV6SendRedirect
         INTEGER,
      er1645v2EthPrtSwF2IpV6LinkMtu
         Integer32,
      er1645v2EthPrtSwF2IpV6InterfaceId
         OCTET STRING,
      er1645v2EthPrtSwF2IpV6MF
         Integer32,
      er1645v2EthPrtSwF2IpV6IcmpMessagesNoRoute
         INTEGER,
      er1645v2EthPrtSwF2IpV6IcmpMessagesBeyondScope
         INTEGER,
      er1645v2EthPrtSwF2IpV6IcmpMessagesAddressUnreachable
         INTEGER,
      er1645v2EthPrtSwF2IpV6IcmpMessagesPortUnreachable
         INTEGER,
      er1645v2EthPrtSwF2IpV6IcmpMessagesPacketTooBig
         INTEGER,
      er1645v2EthPrtSwF2IpV6IcmpMessagesHopLimitExceeded
         INTEGER,
      er1645v2EthPrtSwF2IpV6IcmpMessagesFragTimeExceeded
         INTEGER,
      er1645v2EthPrtSwF2IpV6IcmpMessagesHeaderFieldErr
         INTEGER,
      er1645v2EthPrtSwF2IpV6IcmpMessagesOptionUnrecognized
         INTEGER,
      er1645v2EthPrtSwF2IpV6IcmpMessagesRedirect
         INTEGER
      }

er1645v2EthPrtSwF2IpV6GlobalIx OBJECT-TYPE
   SYNTAX      GlobalIndex
   MAX-ACCESS  not-accessible
   STATUS      current
   DESCRIPTION
      "The value of the tlsCntTreeGlobalIndex of the MANAGED OBJECT."
   ::= {er1645v2EthPrtSwF2IpV6Entry 10}

er1645v2EthPrtSwF2IpV6VrfRouter OBJECT-TYPE
   SYNTAX      DisplayString
   MAX-ACCESS  read-write
   STATUS      current
   DESCRIPTION
      "Path: swPort.editConf.ipV6.vrfRouter"
   ::= {er1645v2EthPrtSwF2IpV6Entry 16777216}

er1645v2EthPrtSwF2IpV6AddrAutoConfigNrDupAddrDetects OBJECT-TYPE
   SYNTAX      Integer32
   MAX-ACCESS  read-write
   STATUS      current
   DESCRIPTION
      "Path: swPort.editConf.ipV6.addrAutoConfig.nrDupAddrDetects"
   ::= {er1645v2EthPrtSwF2IpV6Entry 67174400}

er1645v2EthPrtSwF2IpV6AddrAutoConfigAcceptRa OBJECT-TYPE
   SYNTAX      INTEGER
               {
               disabled (0),
               enabled (1)
               }
   MAX-ACCESS  read-write
   STATUS      current
   DESCRIPTION
      "Path: swPort.editConf.ipV6.addrAutoConfig.acceptRa

       Possibilities:
               disabled   (0)
               enabled   (1)"
   ::= {er1645v2EthPrtSwF2IpV6Entry 67239936}

er1645v2EthPrtSwF2IpV6AddrAutoConfigAcceptRaRdnss OBJECT-TYPE
   SYNTAX      INTEGER
               {
               disabled (0),
               enabled (1)
               }
   MAX-ACCESS  read-write
   STATUS      current
   DESCRIPTION
      "Path: swPort.editConf.ipV6.addrAutoConfig.acceptRaRdnss

       Possibilities:
               disabled   (0)
               enabled   (1)"
   ::= {er1645v2EthPrtSwF2IpV6Entry 67305472}

er1645v2EthPrtSwF2IpV6AddrAutoConfigAcceptRaDnssl OBJECT-TYPE
   SYNTAX      INTEGER
               {
               disabled (0),
               enabled (1)
               }
   MAX-ACCESS  read-write
   STATUS      current
   DESCRIPTION
      "Path: swPort.editConf.ipV6.addrAutoConfig.acceptRaDnssl

       Possibilities:
               disabled   (0)
               enabled   (1)"
   ::= {er1645v2EthPrtSwF2IpV6Entry 67371008}

er1645v2EthPrtSwF2IpV6DefaultRoute OBJECT-TYPE
   SYNTAX      INTEGER
               {
               disabled (0),
               enabled (1)
               }
   MAX-ACCESS  read-write
   STATUS      current
   DESCRIPTION
      "Path: swPort.editConf.ipV6.defaultRoute

       Possibilities:
               disabled   (0)
               enabled   (1)"
   ::= {er1645v2EthPrtSwF2IpV6Entry 83886080}

er1645v2EthPrtSwF2IpV6RaSend OBJECT-TYPE
   SYNTAX      INTEGER
               {
               disabled (0),
               enabled (1)
               }
   MAX-ACCESS  read-write
   STATUS      current
   DESCRIPTION
      "Path: swPort.editConf.ipV6.ra.send

       Possibilities:
               disabled   (0)
               enabled   (1)"
   ::= {er1645v2EthPrtSwF2IpV6Entry 100728832}

er1645v2EthPrtSwF2IpV6RaMinInterval OBJECT-TYPE
   SYNTAX      TimeTicks
   MAX-ACCESS  read-write
   STATUS      current
   DESCRIPTION
      "Path: swPort.editConf.ipV6.ra.minInterval

       Time in centi-second."
   ::= {er1645v2EthPrtSwF2IpV6Entry 100794368}

er1645v2EthPrtSwF2IpV6RaMaxInterval OBJECT-TYPE
   SYNTAX      TimeTicks
   MAX-ACCESS  read-write
   STATUS      current
   DESCRIPTION
      "Path: swPort.editConf.ipV6.ra.maxInterval

       Time in centi-second."
   ::= {er1645v2EthPrtSwF2IpV6Entry 100859904}

er1645v2EthPrtSwF2IpV6RaManagedFlag OBJECT-TYPE
   SYNTAX      INTEGER
               {
               disabled (0),
               enabled (1)
               }
   MAX-ACCESS  read-write
   STATUS      current
   DESCRIPTION
      "Path: swPort.editConf.ipV6.ra.managedFlag

       Possibilities:
               disabled   (0)
               enabled   (1)"
   ::= {er1645v2EthPrtSwF2IpV6Entry 100925440}

er1645v2EthPrtSwF2IpV6RaOtherConfFlag OBJECT-TYPE
   SYNTAX      INTEGER
               {
               disabled (0),
               enabled (1)
               }
   MAX-ACCESS  read-write
   STATUS      current
   DESCRIPTION
      "Path: swPort.editConf.ipV6.ra.otherConfFlag

       Possibilities:
               disabled   (0)
               enabled   (1)"
   ::= {er1645v2EthPrtSwF2IpV6Entry 100990976}

er1645v2EthPrtSwF2IpV6RaLinkMtu OBJECT-TYPE
   SYNTAX      Integer32
   MAX-ACCESS  read-write
   STATUS      current
   DESCRIPTION
      "Path: swPort.editConf.ipV6.ra.linkMtu"
   ::= {er1645v2EthPrtSwF2IpV6Entry 101056512}

er1645v2EthPrtSwF2IpV6RaReachableTime OBJECT-TYPE
   SYNTAX      TimeTicks
   MAX-ACCESS  read-write
   STATUS      current
   DESCRIPTION
      "Path: swPort.editConf.ipV6.ra.reachableTime

       Time in centi-second."
   ::= {er1645v2EthPrtSwF2IpV6Entry 101122048}

er1645v2EthPrtSwF2IpV6RaRetransmitTime OBJECT-TYPE
   SYNTAX      TimeTicks
   MAX-ACCESS  read-write
   STATUS      current
   DESCRIPTION
      "Path: swPort.editConf.ipV6.ra.retransmitTime

       Time in centi-second."
   ::= {er1645v2EthPrtSwF2IpV6Entry 101187584}

er1645v2EthPrtSwF2IpV6RaHopLimit OBJECT-TYPE
   SYNTAX      Integer32
   MAX-ACCESS  read-write
   STATUS      current
   DESCRIPTION
      "Path: swPort.editConf.ipV6.ra.hopLimit"
   ::= {er1645v2EthPrtSwF2IpV6Entry 101253120}

er1645v2EthPrtSwF2IpV6RaDefaultLifeTime OBJECT-TYPE
   SYNTAX      TimeTicks
   MAX-ACCESS  read-write
   STATUS      current
   DESCRIPTION
      "Path: swPort.editConf.ipV6.ra.defaultLifeTime

       Time in centi-second."
   ::= {er1645v2EthPrtSwF2IpV6Entry 101318656}

er1645v2EthPrtSwF2IpV6RaDnsOptionsRdnssLifeTime OBJECT-TYPE
   SYNTAX      TimeTicks
   MAX-ACCESS  read-write
   STATUS      current
   DESCRIPTION
      "Path: swPort.editConf.ipV6.ra.dnsOptions.rdnss.lifeTime

       Time in centi-second."
   ::= {er1645v2EthPrtSwF2IpV6Entry 101393408}

er1645v2EthPrtSwF2IpV6RaDnsOptionsRdnssImportServers OBJECT-TYPE
   SYNTAX      INTEGER
               {
               disabled (0),
               enabled (1)
               }
   MAX-ACCESS  read-write
   STATUS      current
   DESCRIPTION
      "Path: swPort.editConf.ipV6.ra.dnsOptions.rdnss.importServers

       Possibilities:
               disabled   (0)
               enabled   (1)"
   ::= {er1645v2EthPrtSwF2IpV6Entry 101395456}

er1645v2EthPrtSwF2IpV6RaDnsOptionsDnsslLifeTime OBJECT-TYPE
   SYNTAX      TimeTicks
   MAX-ACCESS  read-write
   STATUS      current
   DESCRIPTION
      "Path: swPort.editConf.ipV6.ra.dnsOptions.dnssl.lifeTime

       Time in centi-second."
   ::= {er1645v2EthPrtSwF2IpV6Entry 101401600}

er1645v2EthPrtSwF2IpV6RaDnsOptionsDnsslImportDomains OBJECT-TYPE
   SYNTAX      INTEGER
               {
               disabled (0),
               enabled (1)
               }
   MAX-ACCESS  read-write
   STATUS      current
   DESCRIPTION
      "Path: swPort.editConf.ipV6.ra.dnsOptions.dnssl.importDomains

       Possibilities:
               disabled   (0)
               enabled   (1)"
   ::= {er1645v2EthPrtSwF2IpV6Entry 101403648}

er1645v2EthPrtSwF2IpV6RsSend OBJECT-TYPE
   SYNTAX      INTEGER
               {
               disabled (0),
               enabled (1)
               }
   MAX-ACCESS  read-write
   STATUS      current
   DESCRIPTION
      "Path: swPort.editConf.ipV6.rs.send

       Possibilities:
               disabled   (0)
               enabled   (1)"
   ::= {er1645v2EthPrtSwF2IpV6Entry 335609856}

er1645v2EthPrtSwF2IpV6RsMaxRandomDelay OBJECT-TYPE
   SYNTAX      TimeTicks
   MAX-ACCESS  read-write
   STATUS      current
   DESCRIPTION
      "Path: swPort.editConf.ipV6.rs.maxRandomDelay

       Time in centi-second."
   ::= {er1645v2EthPrtSwF2IpV6Entry 335675392}

er1645v2EthPrtSwF2IpV6RsInterval OBJECT-TYPE
   SYNTAX      TimeTicks
   MAX-ACCESS  read-write
   STATUS      current
   DESCRIPTION
      "Path: swPort.editConf.ipV6.rs.interval

       Time in centi-second."
   ::= {er1645v2EthPrtSwF2IpV6Entry 335740928}

er1645v2EthPrtSwF2IpV6RsMaxSolicitations OBJECT-TYPE
   SYNTAX      Integer32
   MAX-ACCESS  read-write
   STATUS      current
   DESCRIPTION
      "Path: swPort.editConf.ipV6.rs.maxSolicitations"
   ::= {er1645v2EthPrtSwF2IpV6Entry 335806464}

er1645v2EthPrtSwF2IpV6TrafficPolicyInbound OBJECT-TYPE
   SYNTAX      DisplayString
   MAX-ACCESS  read-write
   STATUS      current
   DESCRIPTION
      "Path: swPort.editConf.ipV6.trafficPolicy.inbound"
   ::= {er1645v2EthPrtSwF2IpV6Entry 184614912}

er1645v2EthPrtSwF2IpV6TrafficPolicyOutbound OBJECT-TYPE
   SYNTAX      DisplayString
   MAX-ACCESS  read-write
   STATUS      current
   DESCRIPTION
      "Path: swPort.editConf.ipV6.trafficPolicy.outbound"
   ::= {er1645v2EthPrtSwF2IpV6Entry 184680448}

er1645v2EthPrtSwF2IpV6FirewallZone OBJECT-TYPE
   SYNTAX      DisplayString
   MAX-ACCESS  read-write
   STATUS      current
   DESCRIPTION
      "Path: swPort.editConf.ipV6.firewall.zone"
   ::= {er1645v2EthPrtSwF2IpV6Entry 201392128}

er1645v2EthPrtSwF2IpV6DhcpClientAddrAC OBJECT-TYPE
   SYNTAX      INTEGER
               {
               disabled (0),
               enabled (1)
               }
   MAX-ACCESS  read-write
   STATUS      current
   DESCRIPTION
      "Path: swPort.editConf.ipV6.dhcp.client.addrAutoConfig

       Possibilities:
               disabled   (0)
               enabled   (1)"
   ::= {er1645v2EthPrtSwF2IpV6Entry 170131456}

er1645v2EthPrtSwF2IpV6DhcpClientPrDelMode OBJECT-TYPE
   SYNTAX      INTEGER
               {
               disabled (0),
               enabled (1)
               }
   MAX-ACCESS  read-write
   STATUS      current
   DESCRIPTION
      "Path: swPort.editConf.ipV6.dhcp.client.pd.mode

       Possibilities:
               disabled   (0)
               enabled   (1)"
   ::= {er1645v2EthPrtSwF2IpV6Entry 170394624}

er1645v2EthPrtSwF2IpV6DhcpClientPrDelPool OBJECT-TYPE
   SYNTAX      DisplayString
   MAX-ACCESS  read-write
   STATUS      current
   DESCRIPTION
      "Path: swPort.editConf.ipV6.dhcp.client.pd.pool"
   ::= {er1645v2EthPrtSwF2IpV6Entry 170395648}

er1645v2EthPrtSwF2IpV6DhcpClientPrDelPdExclOpt OBJECT-TYPE
   SYNTAX      INTEGER
               {
               disabled (0),
               enabled (1)
               }
   MAX-ACCESS  read-write
   STATUS      current
   DESCRIPTION
      "Path: swPort.editConf.ipV6.dhcp.client.pd.pdExclOpt

       Possibilities:
               disabled   (0)
               enabled   (1)"
   ::= {er1645v2EthPrtSwF2IpV6Entry 170396672}

er1645v2EthPrtSwF2IpV6DhcpClientDnsServerPref OBJECT-TYPE
   SYNTAX      Integer32
   MAX-ACCESS  read-write
   STATUS      current
   DESCRIPTION
      "Path: swPort.editConf.ipV6.dhcp.client.dns.serverPref"
   ::= {er1645v2EthPrtSwF2IpV6Entry 170918912}

er1645v2EthPrtSwF2IpV6DhcpClientRapidCommit OBJECT-TYPE
   SYNTAX      INTEGER
               {
               disabled (0),
               enabled (1)
               }
   MAX-ACCESS  read-write
   STATUS      current
   DESCRIPTION
      "Path: swPort.editConf.ipV6.dhcp.client.rapidCommit

       Possibilities:
               disabled   (0)
               enabled   (1)"
   ::= {er1645v2EthPrtSwF2IpV6Entry 170655744}

er1645v2EthPrtSwF2IpV6DhcpClientTimersSolTimeOut OBJECT-TYPE
   SYNTAX      TimeTicks
   MAX-ACCESS  read-write
   STATUS      current
   DESCRIPTION
      "Path: swPort.editConf.ipV6.dhcp.client.timers.solTimeOut

       Time in centi-second."
   ::= {er1645v2EthPrtSwF2IpV6Entry 171181056}

er1645v2EthPrtSwF2IpV6DhcpClientTimersSolMaxRt OBJECT-TYPE
   SYNTAX      TimeTicks
   MAX-ACCESS  read-write
   STATUS      current
   DESCRIPTION
      "Path: swPort.editConf.ipV6.dhcp.client.timers.solMaxRt

       Time in centi-second."
   ::= {er1645v2EthPrtSwF2IpV6Entry 171182080}

er1645v2EthPrtSwF2IpV6DhcpClientTimersInfoRefresh OBJECT-TYPE
   SYNTAX      TimeTicks
   MAX-ACCESS  read-write
   STATUS      current
   DESCRIPTION
      "Path: swPort.editConf.ipV6.dhcp.client.timers.infoRefresh

       Time in centi-second."
   ::= {er1645v2EthPrtSwF2IpV6Entry 171183104}

er1645v2EthPrtSwF2IpV6DhcpServerMode OBJECT-TYPE
   SYNTAX      INTEGER
               {
               disabled (0),
               enabled (1)
               }
   MAX-ACCESS  read-write
   STATUS      current
   DESCRIPTION
      "Path: swPort.editConf.ipV6.dhcp.server.mode

       Possibilities:
               disabled   (0)
               enabled   (1)"
   ::= {er1645v2EthPrtSwF2IpV6Entry 172228608}

er1645v2EthPrtSwF2IpV6DhcpServerPreference OBJECT-TYPE
   SYNTAX      Integer32
   MAX-ACCESS  read-write
   STATUS      current
   DESCRIPTION
      "Path: swPort.editConf.ipV6.dhcp.server.preference"
   ::= {er1645v2EthPrtSwF2IpV6Entry 172490752}

er1645v2EthPrtSwF2IpV6DhcpServerPool OBJECT-TYPE
   SYNTAX      DisplayString
   MAX-ACCESS  read-write
   STATUS      current
   DESCRIPTION
      "Path: swPort.editConf.ipV6.dhcp.server.pool"
   ::= {er1645v2EthPrtSwF2IpV6Entry 172752896}

er1645v2EthPrtSwF2IpV6DhcpServerRapidCommit OBJECT-TYPE
   SYNTAX      INTEGER
               {
               disabled (0),
               enabled (1)
               }
   MAX-ACCESS  read-write
   STATUS      current
   DESCRIPTION
      "Path: swPort.editConf.ipV6.dhcp.server.rapidCommit

       Possibilities:
               disabled   (0)
               enabled   (1)"
   ::= {er1645v2EthPrtSwF2IpV6Entry 173015040}

er1645v2EthPrtSwF2IpV6DhcpServerTimersInfoRefresh OBJECT-TYPE
   SYNTAX      TimeTicks
   MAX-ACCESS  read-write
   STATUS      current
   DESCRIPTION
      "Path: swPort.editConf.ipV6.dhcp.server.timers.infoRefresh

       Time in centi-second."
   ::= {er1645v2EthPrtSwF2IpV6Entry 173278208}

er1645v2EthPrtSwF2IpV6DhcpRelayMode OBJECT-TYPE
   SYNTAX      INTEGER
               {
               disabled (0),
               enabled (1)
               }
   MAX-ACCESS  read-write
   STATUS      current
   DESCRIPTION
      "Path: swPort.editConf.ipV6.dhcp.relay.mode

       Possibilities:
               disabled   (0)
               enabled   (1)"
   ::= {er1645v2EthPrtSwF2IpV6Entry 174071808}

er1645v2EthPrtSwF2IpV6SendRedirect OBJECT-TYPE
   SYNTAX      INTEGER
               {
               disabled (0),
               enabled (1)
               }
   MAX-ACCESS  read-write
   STATUS      current
   DESCRIPTION
      "Path: swPort.editConf.ipV6.sendRedirect

       Possibilities:
               disabled   (0)
               enabled   (1)"
   ::= {er1645v2EthPrtSwF2IpV6Entry 117440512}

er1645v2EthPrtSwF2IpV6LinkMtu OBJECT-TYPE
   SYNTAX      Integer32
   MAX-ACCESS  read-write
   STATUS      current
   DESCRIPTION
      "Path: swPort.editConf.ipV6.linkMtu"
   ::= {er1645v2EthPrtSwF2IpV6Entry 134217728}

er1645v2EthPrtSwF2IpV6InterfaceId OBJECT-TYPE
   SYNTAX      OCTET STRING
   MAX-ACCESS  read-write
   STATUS      current
   DESCRIPTION
      "Path: swPort.editConf.ipV6.interfaceId"
   ::= {er1645v2EthPrtSwF2IpV6Entry 150994944}

er1645v2EthPrtSwF2IpV6MF OBJECT-TYPE
   SYNTAX      Integer32
   MAX-ACCESS  read-write
   STATUS      current
   DESCRIPTION
      "Path: swPort.editConf.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1645v2EthPrtSwF2IpV6Entry 285212672}

er1645v2EthPrtSwF2IpV6IcmpMessagesNoRoute OBJECT-TYPE
   SYNTAX      INTEGER
               {
               disabled (0),
               enabled (1)
               }
   MAX-ACCESS  read-write
   STATUS      current
   DESCRIPTION
      "Path: swPort.editConf.ipV6.icmpMessages.noRoute

       Possibilities:
               disabled   (0)
               enabled   (1)"
   ::= {er1645v2EthPrtSwF2IpV6Entry 302055424}

er1645v2EthPrtSwF2IpV6IcmpMessagesBeyondScope OBJECT-TYPE
   SYNTAX      INTEGER
               {
               disabled (0),
               enabled (1)
               }
   MAX-ACCESS  read-write
   STATUS      current
   DESCRIPTION
      "Path: swPort.editConf.ipV6.icmpMessages.beyondScope

       Possibilities:
               disabled   (0)
               enabled   (1)"
   ::= {er1645v2EthPrtSwF2IpV6Entry 302186496}

er1645v2EthPrtSwF2IpV6IcmpMessagesAddressUnreachable OBJECT-TYPE
   SYNTAX      INTEGER
               {
               disabled (0),
               enabled (1)
               }
   MAX-ACCESS  read-write
   STATUS      current
   DESCRIPTION
      "Path: swPort.editConf.ipV6.icmpMessages.addressUnreachable

       Possibilities:
               disabled   (0)
               enabled   (1)"
   ::= {er1645v2EthPrtSwF2IpV6Entry 302252032}

er1645v2EthPrtSwF2IpV6IcmpMessagesPortUnreachable OBJECT-TYPE
   SYNTAX      INTEGER
               {
               disabled (0),
               enabled (1)
               }
   MAX-ACCESS  read-write
   STATUS      current
   DESCRIPTION
      "Path: swPort.editConf.ipV6.icmpMessages.portUnreachable

       Possibilities:
               disabled   (0)
               enabled   (1)"
   ::= {er1645v2EthPrtSwF2IpV6Entry 302317568}

er1645v2EthPrtSwF2IpV6IcmpMessagesPacketTooBig OBJECT-TYPE
   SYNTAX      INTEGER
               {
               disabled (0),
               enabled (1)
               }
   MAX-ACCESS  read-write
   STATUS      current
   DESCRIPTION
      "Path: swPort.editConf.ipV6.icmpMessages.packetTooBig

       Possibilities:
               disabled   (0)
               enabled   (1)"
   ::= {er1645v2EthPrtSwF2IpV6Entry 302645248}

er1645v2EthPrtSwF2IpV6IcmpMessagesHopLimitExceeded OBJECT-TYPE
   SYNTAX      INTEGER
               {
               disabled (0),
               enabled (1)
               }
   MAX-ACCESS  read-write
   STATUS      current
   DESCRIPTION
      "Path: swPort.editConf.ipV6.icmpMessages.hopLimitExceeded

       Possibilities:
               disabled   (0)
               enabled   (1)"
   ::= {er1645v2EthPrtSwF2IpV6Entry 303300608}

er1645v2EthPrtSwF2IpV6IcmpMessagesFragTimeExceeded OBJECT-TYPE
   SYNTAX      INTEGER
               {
               disabled (0),
               enabled (1)
               }
   MAX-ACCESS  read-write
   STATUS      current
   DESCRIPTION
      "Path: swPort.editConf.ipV6.icmpMessages.fragTimeExceeded

       Possibilities:
               disabled   (0)
               enabled   (1)"
   ::= {er1645v2EthPrtSwF2IpV6Entry 303366144}

er1645v2EthPrtSwF2IpV6IcmpMessagesHeaderFieldErr OBJECT-TYPE
   SYNTAX      INTEGER
               {
               disabled (0),
               enabled (1)
               }
   MAX-ACCESS  read-write
   STATUS      current
   DESCRIPTION
      "Path: swPort.editConf.ipV6.icmpMessages.headerFieldErr

       Possibilities:
               disabled   (0)
               enabled   (1)"
   ::= {er1645v2EthPrtSwF2IpV6Entry 303955968}

er1645v2EthPrtSwF2IpV6IcmpMessagesOptionUnrecognized OBJECT-TYPE
   SYNTAX      INTEGER
               {
               disabled (0),
               enabled (1)
               }
   MAX-ACCESS  read-write
   STATUS      current
   DESCRIPTION
      "Path: swPort.editConf.ipV6.icmpMessages.optionUnrecognized

       Possibilities:
               disabled   (0)
               enabled   (1)"
   ::= {er1645v2EthPrtSwF2IpV6Entry 304087040}

er1645v2EthPrtSwF2IpV6IcmpMessagesRedirect OBJECT-TYPE
   SYNTAX      INTEGER
               {
               disabled (0),
               enabled (1)
               }
   MAX-ACCESS  read-write
   STATUS      current
   DESCRIPTION
      "Path: swPort.editConf.ipV6.icmpMessages.redirect

       Possibilities:
               disabled   (0)
               enabled   (1)"
   ::= {er1645v2EthPrtSwF2IpV6Entry 304611328}

er1645v2EthPrtSwF2IpV6Addresses OBJECT-TYPE
   SYNTAX      SEQUENCE OF Er1645v2EthPrtSwF2IpV6AddressesEntry
   MAX-ACCESS  not-accessible
   STATUS      current
   DESCRIPTION
      ""
   ::= {er1645v2EthPrtSwF2IpV6 50331648}

er1645v2EthPrtSwF2IpV6AddressesEntry OBJECT-TYPE
   SYNTAX      Er1645v2EthPrtSwF2IpV6AddressesEntry
   MAX-ACCESS  not-accessible
   STATUS      current
   DESCRIPTION
      ""
   INDEX      { er1645v2EthPrtSwF2IpV6AddressesGlobalIx,
                er1645v2EthPrtSwF2IpV6AddressesTableIx }
   ::= {er1645v2EthPrtSwF2IpV6Addresses 1}

Er1645v2EthPrtSwF2IpV6AddressesEntry ::=
   SEQUENCE
      {
      er1645v2EthPrtSwF2IpV6AddressesActions
         VariableLengthTableActions,
      er1645v2EthPrtSwF2IpV6AddressesGlobalIx
         GlobalIndex,
      er1645v2EthPrtSwF2IpV6AddressesTableIx
         TableIndex,
      er1645v2EthPrtSwF2IpV6AddressesType
         INTEGER,
      er1645v2EthPrtSwF2IpV6AddressesAddress
         Ipv6Address,
      er1645v2EthPrtSwF2IpV6AddressesPrefixLength
         Integer32,
      er1645v2EthPrtSwF2IpV6AddressesGeneralPrefix
         DisplayString,
      er1645v2EthPrtSwF2IpV6AddressesRaSend
         INTEGER,
      er1645v2EthPrtSwF2IpV6AddressesRaOnLinkFlag
         INTEGER,
      er1645v2EthPrtSwF2IpV6AddressesRaAutoFlag
         INTEGER,
      er1645v2EthPrtSwF2IpV6AddressesRaValidLifeTime
         TimeTicks,
      er1645v2EthPrtSwF2IpV6AddressesRaValidLTMode
         INTEGER,
      er1645v2EthPrtSwF2IpV6AddressesRaPrefLifeTime
         TimeTicks,
      er1645v2EthPrtSwF2IpV6AddressesRaPrefLTMode
         INTEGER
      }

er1645v2EthPrtSwF2IpV6AddressesActions OBJECT-TYPE
   SYNTAX      VariableLengthTableActions
   MAX-ACCESS  read-write
   STATUS      current
   DESCRIPTION
      "By way of this field, some manipulations
       on this table may be performed."
   ::= {er1645v2EthPrtSwF2IpV6AddressesEntry 2}

er1645v2EthPrtSwF2IpV6AddressesGlobalIx OBJECT-TYPE
   SYNTAX      GlobalIndex
   MAX-ACCESS  not-accessible
   STATUS      current
   DESCRIPTION
      "The value of the tlsCntTreeGlobalIndex of the MANAGED OBJECT."
   ::= {er1645v2EthPrtSwF2IpV6AddressesEntry 10}

er1645v2EthPrtSwF2IpV6AddressesTableIx OBJECT-TYPE
   SYNTAX      TableIndex
   MAX-ACCESS  not-accessible
   STATUS      current
   DESCRIPTION
      ""
   ::= {er1645v2EthPrtSwF2IpV6AddressesEntry 11}

er1645v2EthPrtSwF2IpV6AddressesType OBJECT-TYPE
   SYNTAX      INTEGER
               {
               unicast (0),
               eui64 (1),
               anycast (2),
               linkLocal (3),
               generalPrefix (4)
               }
   MAX-ACCESS  read-write
   STATUS      current
   DESCRIPTION
      "Path: swPort.editConf.ipV6.addresses.type

       Possibilities:
               unicast   (0)
               eui64   (1)
               anycast   (2)
               linkLocal   (3)
               generalPrefix   (4)"
   ::= {er1645v2EthPrtSwF2IpV6AddressesEntry 50331648}

er1645v2EthPrtSwF2IpV6AddressesAddress OBJECT-TYPE
   SYNTAX      Ipv6Address
   MAX-ACCESS  read-write
   STATUS      current
   DESCRIPTION
      "Path: swPort.editConf.ipV6.addresses.address

       ipv6 address"
   ::= {er1645v2EthPrtSwF2IpV6AddressesEntry 16777216}

er1645v2EthPrtSwF2IpV6AddressesPrefixLength OBJECT-TYPE
   SYNTAX      Integer32
   MAX-ACCESS  read-write
   STATUS      current
   DESCRIPTION
      "Path: swPort.editConf.ipV6.addresses.prefixLength"
   ::= {er1645v2EthPrtSwF2IpV6AddressesEntry 33554432}

er1645v2EthPrtSwF2IpV6AddressesGeneralPrefix OBJECT-TYPE
   SYNTAX      DisplayString
   MAX-ACCESS  read-write
   STATUS      current
   DESCRIPTION
      "Path: swPort.editConf.ipV6.addresses.generalPrefix"
   ::= {er1645v2EthPrtSwF2IpV6AddressesEntry 83886080}

er1645v2EthPrtSwF2IpV6AddressesRaSend OBJECT-TYPE
   SYNTAX      INTEGER
               {
               disabled (0),
               enabled (1)
               }
   MAX-ACCESS  read-write
   STATUS      current
   DESCRIPTION
      "Path: swPort.editConf.ipV6.addresses.ra.send

       Possibilities:
               disabled   (0)
               enabled   (1)"
   ::= {er1645v2EthPrtSwF2IpV6AddressesEntry 67174400}

er1645v2EthPrtSwF2IpV6AddressesRaOnLinkFlag OBJECT-TYPE
   SYNTAX      INTEGER
               {
               disabled (0),
               enabled (1)
               }
   MAX-ACCESS  read-write
   STATUS      current
   DESCRIPTION
      "Path: swPort.editConf.ipV6.addresses.ra.onLinkFlag

       Possibilities:
               disabled   (0)
               enabled   (1)"
   ::= {er1645v2EthPrtSwF2IpV6AddressesEntry 67371008}

er1645v2EthPrtSwF2IpV6AddressesRaAutoFlag OBJECT-TYPE
   SYNTAX      INTEGER
               {
               disabled (0),
               enabled (1)
               }
   MAX-ACCESS  read-write
   STATUS      current
   DESCRIPTION
      "Path: swPort.editConf.ipV6.addresses.ra.autonomousFlag

       Possibilities:
               disabled   (0)
               enabled   (1)"
   ::= {er1645v2EthPrtSwF2IpV6AddressesEntry 67567616}

er1645v2EthPrtSwF2IpV6AddressesRaValidLifeTime OBJECT-TYPE
   SYNTAX      TimeTicks
   MAX-ACCESS  read-write
   STATUS      current
   DESCRIPTION
      "Path: swPort.editConf.ipV6.addresses.ra.validLifeTime

       Time in centi-second."
   ::= {er1645v2EthPrtSwF2IpV6AddressesEntry 67239936}

er1645v2EthPrtSwF2IpV6AddressesRaValidLTMode OBJECT-TYPE
   SYNTAX      INTEGER
               {
               fixed (0),
               infinite (2)
               }
   MAX-ACCESS  read-write
   STATUS      current
   DESCRIPTION
      "Path: swPort.editConf.ipV6.addresses.ra.validLifeTimeMode

       Possibilities:
               fixed   (0)
               infinite   (2)"
   ::= {er1645v2EthPrtSwF2IpV6AddressesEntry 67305472}

er1645v2EthPrtSwF2IpV6AddressesRaPrefLifeTime OBJECT-TYPE
   SYNTAX      TimeTicks
   MAX-ACCESS  read-write
   STATUS      current
   DESCRIPTION
      "Path: swPort.editConf.ipV6.addresses.ra.prefLifeTime

       Time in centi-second."
   ::= {er1645v2EthPrtSwF2IpV6AddressesEntry 67436544}

er1645v2EthPrtSwF2IpV6AddressesRaPrefLTMode OBJECT-TYPE
   SYNTAX      INTEGER
               {
               fixed (0),
               infinite (2)
               }
   MAX-ACCESS  read-write
   STATUS      current
   DESCRIPTION
      "Path: swPort.editConf.ipV6.addresses.ra.prefLifeTimeMode

       Possibilities:
               fixed   (0)
               infinite   (2)"
   ::= {er1645v2EthPrtSwF2IpV6AddressesEntry 67502080}

er1645v2EthPrtSwF2IpV6RaDnsOptionsRdnssServers OBJECT-TYPE
   SYNTAX      SEQUENCE OF Er1645v2EthPrtSwF2IpV6RaDnsOptionsRdnssServersEntry
   MAX-ACCESS  not-accessible
   STATUS      current
   DESCRIPTION
      ""
   ::= {er1645v2EthPrtSwF2IpV6 101394432}

er1645v2EthPrtSwF2IpV6RaDnsOptionsRdnssServersEntry OBJECT-TYPE
   SYNTAX      Er1645v2EthPrtSwF2IpV6RaDnsOptionsRdnssServersEntry
   MAX-ACCESS  not-accessible
   STATUS      current
   DESCRIPTION
      ""
   INDEX      { er1645v2EthPrtSwF2IpV6RaDnsOptionsRdnssServersGlobalIx,
                er1645v2EthPrtSwF2IpV6RaDnsOptionsRdnssServersTableIx }
   ::= {er1645v2EthPrtSwF2IpV6RaDnsOptionsRdnssServers 1}

Er1645v2EthPrtSwF2IpV6RaDnsOptionsRdnssServersEntry ::=
   SEQUENCE
      {
      er1645v2EthPrtSwF2IpV6RaDnsOptionsRdnssServersActions
         VariableLengthTableActions,
      er1645v2EthPrtSwF2IpV6RaDnsOptionsRdnssServersGlobalIx
         GlobalIndex,
      er1645v2EthPrtSwF2IpV6RaDnsOptionsRdnssServersTableIx
         TableIndex,
      er1645v2EthPrtSwF2IpV6RaDnsOptionsRdnssServersAddress
         Ipv6Address
      }

er1645v2EthPrtSwF2IpV6RaDnsOptionsRdnssServersActions OBJECT-TYPE
   SYNTAX      VariableLengthTableActions
   MAX-ACCESS  read-write
   STATUS      current
   DESCRIPTION
      "By way of this field, some manipulations
       on this table may be performed."
   ::= {er1645v2EthPrtSwF2IpV6RaDnsOptionsRdnssServersEntry 2}

er1645v2EthPrtSwF2IpV6RaDnsOptionsRdnssServersGlobalIx OBJECT-TYPE
   SYNTAX      GlobalIndex
   MAX-ACCESS  not-accessible
   STATUS      current
   DESCRIPTION
      "The value of the tlsCntTreeGlobalIndex of the MANAGED OBJECT."
   ::= {er1645v2EthPrtSwF2IpV6RaDnsOptionsRdnssServersEntry 10}

er1645v2EthPrtSwF2IpV6RaDnsOptionsRdnssServersTableIx OBJECT-TYPE
   SYNTAX      TableIndex
   MAX-ACCESS  not-accessible
   STATUS      current
   DESCRIPTION
      ""
   ::= {er1645v2EthPrtSwF2IpV6RaDnsOptionsRdnssServersEntry 11}

er1645v2EthPrtSwF2IpV6RaDnsOptionsRdnssServersAddress OBJECT-TYPE
   SYNTAX      Ipv6Address
   MAX-ACCESS  read-write
   STATUS      current
   DESCRIPTION
      "Path: swPort.editConf.ipV6.ra.dnsOptions.rdnss.servers.address

       ipv6 address"
   ::= {er1645v2EthPrtSwF2IpV6RaDnsOptionsRdnssServersEntry 16777216}

er1645v2EthPrtSwF2IpV6RaDnsOptionsDnsslDomains OBJECT-TYPE
   SYNTAX      SEQUENCE OF Er1645v2EthPrtSwF2IpV6RaDnsOptionsDnsslDomainsEntry
   MAX-ACCESS  not-accessible
   STATUS      current
   DESCRIPTION
      ""
   ::= {er1645v2EthPrtSwF2IpV6 101402624}

er1645v2EthPrtSwF2IpV6RaDnsOptionsDnsslDomainsEntry OBJECT-TYPE
   SYNTAX      Er1645v2EthPrtSwF2IpV6RaDnsOptionsDnsslDomainsEntry
   MAX-ACCESS  not-accessible
   STATUS      current
   DESCRIPTION
      ""
   INDEX      { er1645v2EthPrtSwF2IpV6RaDnsOptionsDnsslDomainsGlobalIx,
                er1645v2EthPrtSwF2IpV6RaDnsOptionsDnsslDomainsTableIx }
   ::= {er1645v2EthPrtSwF2IpV6RaDnsOptionsDnsslDomains 1}

Er1645v2EthPrtSwF2IpV6RaDnsOptionsDnsslDomainsEntry ::=
   SEQUENCE
      {
      er1645v2EthPrtSwF2IpV6RaDnsOptionsDnsslDomainsActions
         VariableLengthTableActions,
      er1645v2EthPrtSwF2IpV6RaDnsOptionsDnsslDomainsGlobalIx
         GlobalIndex,
      er1645v2EthPrtSwF2IpV6RaDnsOptionsDnsslDomainsTableIx
         TableIndex,
      er1645v2EthPrtSwF2IpV6RaDnsOptionsDnsslDomainsName
         DisplayString
      }

er1645v2EthPrtSwF2IpV6RaDnsOptionsDnsslDomainsActions OBJECT-TYPE
   SYNTAX      VariableLengthTableActions
   MAX-ACCESS  read-write
   STATUS      current
   DESCRIPTION
      "By way of this field, some manipulations
       on this table may be performed."
   ::= {er1645v2EthPrtSwF2IpV6RaDnsOptionsDnsslDomainsEntry 2}

er1645v2EthPrtSwF2IpV6RaDnsOptionsDnsslDomainsGlobalIx OBJECT-TYPE
   SYNTAX      GlobalIndex
   MAX-ACCESS  not-accessible
   STATUS      current
   DESCRIPTION
      "The value of the tlsCntTreeGlobalIndex of the MANAGED OBJECT."
   ::= {er1645v2EthPrtSwF2IpV6RaDnsOptionsDnsslDomainsEntry 10}

er1645v2EthPrtSwF2IpV6RaDnsOptionsDnsslDomainsTableIx OBJECT-TYPE
   SYNTAX      TableIndex
   MAX-ACCESS  not-accessible
   STATUS      current
   DESCRIPTION
      ""
   ::= {er1645v2EthPrtSwF2IpV6RaDnsOptionsDnsslDomainsEntry 11}

er1645v2EthPrtSwF2IpV6RaDnsOptionsDnsslDomainsName OBJECT-TYPE
   SYNTAX      DisplayString
   MAX-ACCESS  read-write
   STATUS      current
   DESCRIPTION
      "Path: swPort.editConf.ipV6.ra.dnsOptions.dnssl.domains.name"
   ::= {er1645v2EthPrtSwF2IpV6RaDnsOptionsDnsslDomainsEntry 16777216}

er1645v2EthPrtSwF2IpV6DhcpClientUserClassOpt OBJECT-TYPE
   SYNTAX      SEQUENCE OF Er1645v2EthPrtSwF2IpV6DhcpClientUserClassOptEntry
   MAX-ACCESS  not-accessible
   STATUS      current
   DESCRIPTION
      ""
   ::= {er1645v2EthPrtSwF2IpV6 171442176}

er1645v2EthPrtSwF2IpV6DhcpClientUserClassOptEntry OBJECT-TYPE
   SYNTAX      Er1645v2EthPrtSwF2IpV6DhcpClientUserClassOptEntry
   MAX-ACCESS  not-accessible
   STATUS      current
   DESCRIPTION
      ""
   INDEX      { er1645v2EthPrtSwF2IpV6DhcpClientUserClassOptGlobalIx,
                er1645v2EthPrtSwF2IpV6DhcpClientUserClassOptTableIx }
   ::= {er1645v2EthPrtSwF2IpV6DhcpClientUserClassOpt 1}

Er1645v2EthPrtSwF2IpV6DhcpClientUserClassOptEntry ::=
   SEQUENCE
      {
      er1645v2EthPrtSwF2IpV6DhcpClientUserClassOptActions
         VariableLengthTableActions,
      er1645v2EthPrtSwF2IpV6DhcpClientUserClassOptGlobalIx
         GlobalIndex,
      er1645v2EthPrtSwF2IpV6DhcpClientUserClassOptTableIx
         TableIndex,
      er1645v2EthPrtSwF2IpV6DhcpClientUserClassOptValueAscii
         DisplayString,
      er1645v2EthPrtSwF2IpV6DhcpClientUserClassOptValueDecimal
         Integer32,
      er1645v2EthPrtSwF2IpV6DhcpClientUserClassOptValueHexData
         OCTET STRING
      }

er1645v2EthPrtSwF2IpV6DhcpClientUserClassOptActions OBJECT-TYPE
   SYNTAX      VariableLengthTableActions
   MAX-ACCESS  read-write
   STATUS      current
   DESCRIPTION
      "By way of this field, some manipulations
       on this table may be performed."
   ::= {er1645v2EthPrtSwF2IpV6DhcpClientUserClassOptEntry 2}

er1645v2EthPrtSwF2IpV6DhcpClientUserClassOptGlobalIx OBJECT-TYPE
   SYNTAX      GlobalIndex
   MAX-ACCESS  not-accessible
   STATUS      current
   DESCRIPTION
      "The value of the tlsCntTreeGlobalIndex of the MANAGED OBJECT."
   ::= {er1645v2EthPrtSwF2IpV6DhcpClientUserClassOptEntry 10}

er1645v2EthPrtSwF2IpV6DhcpClientUserClassOptTableIx OBJECT-TYPE
   SYNTAX      TableIndex
   MAX-ACCESS  not-accessible
   STATUS      current
   DESCRIPTION
      ""
   ::= {er1645v2EthPrtSwF2IpV6DhcpClientUserClassOptEntry 11}

er1645v2EthPrtSwF2IpV6DhcpClientUserClassOptValueAscii OBJECT-TYPE
   SYNTAX      DisplayString
   MAX-ACCESS  read-write
   STATUS      current
   DESCRIPTION
      "Path: swPort.editConf.ipV6.dhcp.client.userClassOpt.value.ascii"
   ::= {er1645v2EthPrtSwF2IpV6DhcpClientUserClassOptEntry 16842752}

er1645v2EthPrtSwF2IpV6DhcpClientUserClassOptValueDecimal OBJECT-TYPE
   SYNTAX      Integer32
   MAX-ACCESS  read-write
   STATUS      current
   DESCRIPTION
      "Path: swPort.editConf.ipV6.dhcp.client.userClassOpt.value.decimal"
   ::= {er1645v2EthPrtSwF2IpV6DhcpClientUserClassOptEntry 16908288}

er1645v2EthPrtSwF2IpV6DhcpClientUserClassOptValueHexData OBJECT-TYPE
   SYNTAX      OCTET STRING
   MAX-ACCESS  read-write
   STATUS      current
   DESCRIPTION
      "Path: swPort.editConf.ipV6.dhcp.client.userClassOpt.value.hexData"
   ::= {er1645v2EthPrtSwF2IpV6DhcpClientUserClassOptEntry 16973824}

er1645v2EthPrtSwF2IpV6DhcpClientVendorCl OBJECT-TYPE
   SYNTAX      SEQUENCE OF Er1645v2EthPrtSwF2IpV6DhcpClientVendorClEntry
   MAX-ACCESS  not-accessible
   STATUS      current
   DESCRIPTION
      ""
   ::= {er1645v2EthPrtSwF2IpV6 171704320}

er1645v2EthPrtSwF2IpV6DhcpClientVendorClEntry OBJECT-TYPE
   SYNTAX      Er1645v2EthPrtSwF2IpV6DhcpClientVendorClEntry
   MAX-ACCESS  not-accessible
   STATUS      current
   DESCRIPTION
      ""
   INDEX      { er1645v2EthPrtSwF2IpV6DhcpClientVendorClGlobalIx,
                er1645v2EthPrtSwF2IpV6DhcpClientVendorClTableIx }
   ::= {er1645v2EthPrtSwF2IpV6DhcpClientVendorCl 1}

Er1645v2EthPrtSwF2IpV6DhcpClientVendorClEntry ::=
   SEQUENCE
      {
      er1645v2EthPrtSwF2IpV6DhcpClientVendorClActions
         VariableLengthTableActions,
      er1645v2EthPrtSwF2IpV6DhcpClientVendorClGlobalIx
         GlobalIndex,
      er1645v2EthPrtSwF2IpV6DhcpClientVendorClTableIx
         TableIndex,
      er1645v2EthPrtSwF2IpV6DhcpClientVendorClValueAscii
         DisplayString,
      er1645v2EthPrtSwF2IpV6DhcpClientVendorClValueDecimal
         Integer32,
      er1645v2EthPrtSwF2IpV6DhcpClientVendorClValueHexData
         OCTET STRING
      }

er1645v2EthPrtSwF2IpV6DhcpClientVendorClActions OBJECT-TYPE
   SYNTAX      VariableLengthTableActions
   MAX-ACCESS  read-write
   STATUS      current
   DESCRIPTION
      "By way of this field, some manipulations
       on this table may be performed."
   ::= {er1645v2EthPrtSwF2IpV6DhcpClientVendorClEntry 2}

er1645v2EthPrtSwF2IpV6DhcpClientVendorClGlobalIx OBJECT-TYPE
   SYNTAX      GlobalIndex
   MAX-ACCESS  not-accessible
   STATUS      current
   DESCRIPTION
      "The value of the tlsCntTreeGlobalIndex of the MANAGED OBJECT."
   ::= {er1645v2EthPrtSwF2IpV6DhcpClientVendorClEntry 10}

er1645v2EthPrtSwF2IpV6DhcpClientVendorClTableIx OBJECT-TYPE
   SYNTAX      TableIndex
   MAX-ACCESS  not-accessible
   STATUS      current
   DESCRIPTION
      ""
   ::= {er1645v2EthPrtSwF2IpV6DhcpClientVendorClEntry 11}

er1645v2EthPrtSwF2IpV6DhcpClientVendorClValueAscii OBJECT-TYPE
   SYNTAX      DisplayString
   MAX-ACCESS  read-write
   STATUS      current
   DESCRIPTION
      "Path: swPort.editConf.ipV6.dhcp.client.vendorClassOpt.value.ascii"
   ::= {er1645v2EthPrtSwF2IpV6DhcpClientVendorClEntry 16842752}

er1645v2EthPrtSwF2IpV6DhcpClientVendorClValueDecimal OBJECT-TYPE
   SYNTAX      Integer32
   MAX-ACCESS  read-write
   STATUS      current
   DESCRIPTION
      "Path: swPort.editConf.ipV6.dhcp.client.vendorClassOpt.value.decimal"
   ::= {er1645v2EthPrtSwF2IpV6DhcpClientVendorClEntry 16908288}

er1645v2EthPrtSwF2IpV6DhcpClientVendorClValueHexData OBJECT-TYPE
   SYNTAX      OCTET STRING
   MAX-ACCESS  read-write
   STATUS      current
   DESCRIPTION
      "Path: swPort.editConf.ipV6.dhcp.client.vendorClassOpt.value.hexData"
   ::= {er1645v2EthPrtSwF2IpV6DhcpClientVendorClEntry 16973824}

er1645v2EthPrtSwF2IpV6DhcpRelayDestinations OBJECT-TYPE
   SYNTAX      SEQUENCE OF Er1645v2EthPrtSwF2IpV6DhcpRelayDestinationsEntry
   MAX-ACCESS  not-accessible
   STATUS      current
   DESCRIPTION
      ""
   ::= {er1645v2EthPrtSwF2IpV6 174080000}

er1645v2EthPrtSwF2IpV6DhcpRelayDestinationsEntry OBJECT-TYPE
   SYNTAX      Er1645v2EthPrtSwF2IpV6DhcpRelayDestinationsEntry
   MAX-ACCESS  not-accessible
   STATUS      current
   DESCRIPTION
      ""
   INDEX      { er1645v2EthPrtSwF2IpV6DhcpRelayDestinationsGlobalIx,
                er1645v2EthPrtSwF2IpV6DhcpRelayDestinationsTableIx }
   ::= {er1645v2EthPrtSwF2IpV6DhcpRelayDestinations 1}

Er1645v2EthPrtSwF2IpV6DhcpRelayDestinationsEntry ::=
   SEQUENCE
      {
      er1645v2EthPrtSwF2IpV6DhcpRelayDestinationsActions
         VariableLengthTableActions,
      er1645v2EthPrtSwF2IpV6DhcpRelayDestinationsGlobalIx
         GlobalIndex,
      er1645v2EthPrtSwF2IpV6DhcpRelayDestinationsTableIx
         TableIndex,
      er1645v2EthPrtSwF2IpV6DhcpRelayDestinationsAddress
         Ipv6Address,
      er1645v2EthPrtSwF2IpV6DhcpRelayDestinationsInterface
         DisplayString
      }

er1645v2EthPrtSwF2IpV6DhcpRelayDestinationsActions OBJECT-TYPE
   SYNTAX      VariableLengthTableActions
   MAX-ACCESS  read-write
   STATUS      current
   DESCRIPTION
      "By way of this field, some manipulations
       on this table may be performed."
   ::= {er1645v2EthPrtSwF2IpV6DhcpRelayDestinationsEntry 2}

er1645v2EthPrtSwF2IpV6DhcpRelayDestinationsGlobalIx OBJECT-TYPE
   SYNTAX      GlobalIndex
   MAX-ACCESS  not-accessible
   STATUS      current
   DESCRIPTION
      "The value of the tlsCntTreeGlobalIndex of the MANAGED OBJECT."
   ::= {er1645v2EthPrtSwF2IpV6DhcpRelayDestinationsEntry 10}

er1645v2EthPrtSwF2IpV6DhcpRelayDestinationsTableIx OBJECT-TYPE
   SYNTAX      TableIndex
   MAX-ACCESS  not-accessible
   STATUS      current
   DESCRIPTION
      ""
   ::= {er1645v2EthPrtSwF2IpV6DhcpRelayDestinationsEntry 11}

er1645v2EthPrtSwF2IpV6DhcpRelayDestinationsAddress OBJECT-TYPE
   SYNTAX      Ipv6Address
   MAX-ACCESS  read-write
   STATUS      current
   DESCRIPTION
      "Path: swPort.editConf.ipV6.dhcp.relay.destinations.address

       ipv6 address"
   ::= {er1645v2EthPrtSwF2IpV6DhcpRelayDestinationsEntry 16777216}

er1645v2EthPrtSwF2IpV6DhcpRelayDestinationsInterface OBJECT-TYPE
   SYNTAX      DisplayString
   MAX-ACCESS  read-write
   STATUS      current
   DESCRIPTION
      "Path: swPort.editConf.ipV6.dhcp.relay.destinations.interface"
   ::= {er1645v2EthPrtSwF2IpV6DhcpRelayDestinationsEntry 33554432}


er1645v2EthPrtSwF2Mode OBJECT IDENTIFIER ::= {er1645v2EthPrtSwF2 29}

er1645v2EthPrtSwF2ModeTable OBJECT-TYPE
   SYNTAX      SEQUENCE OF Er1645v2EthPrtSwF2ModeEntry
   MAX-ACCESS  not-accessible
   STATUS      current
   DESCRIPTION
      "routing and/or bridging or ipV6 or multilink selection"
   ::= {er1645v2EthPrtSwF2Mode 1}

er1645v2EthPrtSwF2ModeEntry OBJECT-TYPE
   SYNTAX      Er1645v2EthPrtSwF2ModeEntry
   MAX-ACCESS  not-accessible
   STATUS      current
   DESCRIPTION
      ""
   INDEX      { er1645v2EthPrtSwF2ModeGlobalIx }
   ::= {er1645v2EthPrtSwF2ModeTable 1}

Er1645v2EthPrtSwF2ModeEntry ::=
   SEQUENCE
      {
      er1645v2EthPrtSwF2ModeGlobalIx
         GlobalIndex,
      er1645v2EthPrtSwF2ModeValue
         INTEGER
      }

er1645v2EthPrtSwF2ModeGlobalIx OBJECT-TYPE
   SYNTAX      GlobalIndex
   MAX-ACCESS  not-accessible
   STATUS      current
   DESCRIPTION
      "The value of the tlsCntTreeGlobalIndex of the MANAGED OBJECT."
   ::= {er1645v2EthPrtSwF2ModeEntry 10}

er1645v2EthPrtSwF2ModeValue OBJECT-TYPE
   SYNTAX      INTEGER
               {
               bridging (0),
               routing (1),
               routingAndBridging (2),
               ipV6 (3),
               ipV6ipV4 (4),
               multilink (5)
               }
   MAX-ACCESS  read-write
   STATUS      current
   DESCRIPTION
      "Path: swPort.editConf.mode

       Possibilities:
               bridging   (0)
               routing   (1)
               routingAndBridging   (2)
               ipV6   (3)
               ipV6/ipV4   (4)
               multilink   (5)"
   ::= {er1645v2EthPrtSwF2ModeEntry 2147483648}


er1645v2EthPrtSwF2Ip OBJECT IDENTIFIER ::= {er1645v2EthPrtSwF2 1}

er1645v2EthPrtSwF2IpSSCTable OBJECT-TYPE
   SYNTAX      SEQUENCE OF Er1645v2EthPrtSwF2IpEntry
   MAX-ACCESS  not-accessible
   STATUS      current
   DESCRIPTION
      "ip interface config parameters"
   ::= {er1645v2EthPrtSwF2Ip 1}

er1645v2EthPrtSwF2IpEntry OBJECT-TYPE
   SYNTAX      Er1645v2EthPrtSwF2IpEntry
   MAX-ACCESS  not-accessible
   STATUS      current
   DESCRIPTION
      ""
   INDEX      { er1645v2EthPrtSwF2IpGlobalIx }
   ::= {er1645v2EthPrtSwF2IpSSCTable 1}

Er1645v2EthPrtSwF2IpEntry ::=
   SEQUENCE
      {
      er1645v2EthPrtSwF2IpGlobalIx
         GlobalIndex,
      er1645v2EthPrtSwF2IpVrfRouter
         DisplayString,
      er1645v2EthPrtSwF2IpAdr
         IpAddress,
      er1645v2EthPrtSwF2IpNetm
         IpAddress,
      er1645v2EthPrtSwF2IpSNetName
         INTEGER,
      er1645v2EthPrtSwF2IpSNetCust
         DisplayString,
      er1645v2EthPrtSwF2IpDhcpC
         INTEGER,
      er1645v2EthPrtSwF2IpDhcpGatewayPreference
         Integer32,
      er1645v2EthPrtSwF2IpDhcpRoutePreference
         Integer32,
      er1645v2EthPrtSwF2IpDhcpDnsPreference
         Integer32,
      er1645v2EthPrtSwF2IpMtu
         Integer32,
      er1645v2EthPrtSwF2IpMssAdjust
         INTEGER,
      er1645v2EthPrtSwF2IpRipMetric
         Integer32,
      er1645v2EthPrtSwF2IpRipMetricOut
         Integer32,
      er1645v2EthPrtSwF2IpRipMode
         INTEGER,
      er1645v2EthPrtSwF2IpRipTxVer
         INTEGER,
      er1645v2EthPrtSwF2IpRipRxVer
         INTEGER,
      er1645v2EthPrtSwF2IpRipSplitH
         INTEGER,
      er1645v2EthPrtSwF2IpRipAuth
         INTEGER,
      er1645v2EthPrtSwF2IpRipFilter
         DisplayString,
      er1645v2EthPrtSwF2IpRipFilterIn
         DisplayString,
      er1645v2EthPrtSwF2IpRipClearNextHop
         INTEGER,
      er1645v2EthPrtSwF2IpAccPol
         DisplayString,
      er1645v2EthPrtSwF2IpAB
         DisplayString,
      er1645v2EthPrtSwF2IpMA
         INTEGER,
      er1645v2EthPrtSwF2IpMF
         Integer32,
      er1645v2EthPrtSwF2IpDB
         INTEGER,
      er1645v2EthPrtSwF2IpIR
         INTEGER,
      er1645v2EthPrtSwF2IpIgmp
         INTEGER,
      er1645v2EthPrtSwF2IpNN
         DisplayString,
      er1645v2EthPrtSwF2IpVrrp
         INTEGER,
      er1645v2EthPrtSwF2IpPimMode
         INTEGER,
      er1645v2EthPrtSwF2IpPimDrPriority
         Counter32,
      er1645v2EthPrtSwF2IpPimHelloTime
         TimeTicks,
      er1645v2EthPrtSwF2IpPimPropagationDelay
         TimeTicks,
      er1645v2EthPrtSwF2IpPimOverrideInterval
         TimeTicks,
      er1645v2EthPrtSwF2IpPimBsrBorder
         INTEGER,
      er1645v2EthPrtSwF2IpPimTtlThreshold
         Integer32,
      er1645v2EthPrtSwF2IpIMNetworkUnreachable
         INTEGER,
      er1645v2EthPrtSwF2IpIMHostUnreachable
         INTEGER,
      er1645v2EthPrtSwF2IpIMProtocolUnreachable
         INTEGER,
      er1645v2EthPrtSwF2IpIMPortUnreachable
         INTEGER,
      er1645v2EthPrtSwF2IpIMMtuExceeded
         INTEGER,
      er1645v2EthPrtSwF2IpIMAdminProhibited
         INTEGER,
      er1645v2EthPrtSwF2IpIMTtlExceeded
         INTEGER,
      er1645v2EthPrtSwF2IpIMRedirect
         INTEGER
      }

er1645v2EthPrtSwF2IpGlobalIx OBJECT-TYPE
   SYNTAX      GlobalIndex
   MAX-ACCESS  not-accessible
   STATUS      current
   DESCRIPTION
      "The value of the tlsCntTreeGlobalIndex of the MANAGED OBJECT."
   ::= {er1645v2EthPrtSwF2IpEntry 10}

er1645v2EthPrtSwF2IpVrfRouter OBJECT-TYPE
   SYNTAX      DisplayString
   MAX-ACCESS  read-write
   STATUS      current
   DESCRIPTION
      "Path: swPort.editConf.ip.vrfRouter"
   ::= {er1645v2EthPrtSwF2IpEntry 738197504}

er1645v2EthPrtSwF2IpAdr OBJECT-TYPE
   SYNTAX      IpAddress
   MAX-ACCESS  read-write
   STATUS      current
   DESCRIPTION
      "Path: swPort.editConf.ip.address"
   ::= {er1645v2EthPrtSwF2IpEntry 2030043136}

er1645v2EthPrtSwF2IpNetm OBJECT-TYPE
   SYNTAX      IpAddress
   MAX-ACCESS  read-write
   STATUS      current
   DESCRIPTION
      "Path: swPort.editConf.ip.netMask"
   ::= {er1645v2EthPrtSwF2IpEntry 2063597568}

er1645v2EthPrtSwF2IpSNetName OBJECT-TYPE
   SYNTAX      INTEGER
               {
               slOPTg (0),
               corp (2),
               dmz (3),
               internet (1)
               }
   MAX-ACCESS  read-write
   STATUS      current
   DESCRIPTION
      "Path: swPort.editConf.ip.sNet.name

       Possibilities:
               <OPT>   (0)
               corp   (2)
               dmz   (3)
               internet   (1)"
   ::= {er1645v2EthPrtSwF2IpEntry 855703552}

er1645v2EthPrtSwF2IpSNetCust OBJECT-TYPE
   SYNTAX      DisplayString
   MAX-ACCESS  read-write
   STATUS      current
   DESCRIPTION
      "Path: swPort.editConf.ip.sNet.custom"
   ::= {er1645v2EthPrtSwF2IpEntry 855769088}

er1645v2EthPrtSwF2IpDhcpC OBJECT-TYPE
   SYNTAX      INTEGER
               {
               disabled (0),
               enabled (1)
               }
   MAX-ACCESS  read-write
   STATUS      current
   DESCRIPTION
      "Path: swPort.editConf.ip.dhcpClient

       Possibilities:
               disabled   (0)
               enabled   (1)"
   ::= {er1645v2EthPrtSwF2IpEntry 838860800}

er1645v2EthPrtSwF2IpDhcpGatewayPreference OBJECT-TYPE
   SYNTAX      Integer32
   MAX-ACCESS  read-write
   STATUS      current
   DESCRIPTION
      "Path: swPort.editConf.ip.dhcp.gatewayPreference"
   ::= {er1645v2EthPrtSwF2IpEntry 872480768}

er1645v2EthPrtSwF2IpDhcpRoutePreference OBJECT-TYPE
   SYNTAX      Integer32
   MAX-ACCESS  read-write
   STATUS      current
   DESCRIPTION
      "Path: swPort.editConf.ip.dhcp.routePreference"
   ::= {er1645v2EthPrtSwF2IpEntry 872546304}

er1645v2EthPrtSwF2IpDhcpDnsPreference OBJECT-TYPE
   SYNTAX      Integer32
   MAX-ACCESS  read-write
   STATUS      current
   DESCRIPTION
      "Path: swPort.editConf.ip.dhcp.dnsPreference"
   ::= {er1645v2EthPrtSwF2IpEntry 872611840}

er1645v2EthPrtSwF2IpMtu OBJECT-TYPE
   SYNTAX      Integer32
   MAX-ACCESS  read-write
   STATUS      current
   DESCRIPTION
      "Path: swPort.editConf.ip.mtu"
   ::= {er1645v2EthPrtSwF2IpEntry 671088640}

er1645v2EthPrtSwF2IpMssAdjust OBJECT-TYPE
   SYNTAX      INTEGER
               {
               disabled (0),
               auto (65536)
               }
   MAX-ACCESS  read-write
   STATUS      current
   DESCRIPTION
      "Path: swPort.editConf.ip.mssAdjust

       Possibilities:
               disabled   (0)
               auto   (65536)"
   ::= {er1645v2EthPrtSwF2IpEntry 754974720}

er1645v2EthPrtSwF2IpRipMetric OBJECT-TYPE
   SYNTAX      Integer32
   MAX-ACCESS  read-write
   STATUS      current
   DESCRIPTION
      "Path: swPort.editConf.ip.rip.metric"
   ::= {er1645v2EthPrtSwF2IpEntry 353566720}

er1645v2EthPrtSwF2IpRipMetricOut OBJECT-TYPE
   SYNTAX      Integer32
   MAX-ACCESS  read-write
   STATUS      current
   DESCRIPTION
      "Path: swPort.editConf.ip.rip.metricOut"
   ::= {er1645v2EthPrtSwF2IpEntry 353632256}

er1645v2EthPrtSwF2IpRipMode OBJECT-TYPE
   SYNTAX      INTEGER
               {
               disabled (0),
               passive (1),
               active (2)
               }
   MAX-ACCESS  read-write
   STATUS      current
   DESCRIPTION
      "Path: swPort.editConf.ip.rip.mode

       Possibilities:
               disabled   (0)
               passive   (1)
               active   (2)"
   ::= {er1645v2EthPrtSwF2IpEntry 353697792}

er1645v2EthPrtSwF2IpRipTxVer OBJECT-TYPE
   SYNTAX      INTEGER
               {
               rip1 (0),
               rip2 (1),
               rip1mcompatible (2)
               }
   MAX-ACCESS  read-write
   STATUS      current
   DESCRIPTION
      "Path: swPort.editConf.ip.rip.txVersion

       Possibilities:
               rip1   (0)
               rip2   (1)
               rip1-compatible   (2)"
   ::= {er1645v2EthPrtSwF2IpEntry 354615296}

er1645v2EthPrtSwF2IpRipRxVer OBJECT-TYPE
   SYNTAX      INTEGER
               {
               rip1only (0),
               rip2only (1),
               rip12 (2)
               }
   MAX-ACCESS  read-write
   STATUS      current
   DESCRIPTION
      "Path: swPort.editConf.ip.rip.rxVersion

       Possibilities:
               rip1only   (0)
               rip2only   (1)
               rip1&2   (2)"
   ::= {er1645v2EthPrtSwF2IpEntry 354680832}

er1645v2EthPrtSwF2IpRipSplitH OBJECT-TYPE
   SYNTAX      INTEGER
               {
               disabled (0),
               enabled (1),
               poisonedReverse (2)
               }
   MAX-ACCESS  read-write
   STATUS      current
   DESCRIPTION
      "Path: swPort.editConf.ip.rip.splitHorizon

       Possibilities:
               disabled   (0)
               enabled   (1)
               poisonedReverse   (2)"
   ::= {er1645v2EthPrtSwF2IpEntry 353828864}

er1645v2EthPrtSwF2IpRipAuth OBJECT-TYPE
   SYNTAX      INTEGER
               {
               disabled (0),
               texts (1),
               md5 (2)
               }
   MAX-ACCESS  read-write
   STATUS      current
   DESCRIPTION
      "Path: swPort.editConf.ip.rip.authentication

       Possibilities:
               disabled   (0)
               text    (1)
               md5   (2)"
   ::= {er1645v2EthPrtSwF2IpEntry 353501184}

er1645v2EthPrtSwF2IpRipFilter OBJECT-TYPE
   SYNTAX      DisplayString
   MAX-ACCESS  read-write
   STATUS      current
   DESCRIPTION
      "Path: swPort.editConf.ip.rip.filter"
   ::= {er1645v2EthPrtSwF2IpEntry 354418688}

er1645v2EthPrtSwF2IpRipFilterIn OBJECT-TYPE
   SYNTAX      DisplayString
   MAX-ACCESS  read-write
   STATUS      current
   DESCRIPTION
      "Path: swPort.editConf.ip.rip.filterIn"
   ::= {er1645v2EthPrtSwF2IpEntry 354484224}

er1645v2EthPrtSwF2IpRipClearNextHop OBJECT-TYPE
   SYNTAX      INTEGER
               {
               disabled (0),
               enabled (1)
               }
   MAX-ACCESS  read-write
   STATUS      current
   DESCRIPTION
      "Path: swPort.editConf.ip.rip.clearNextHop

       Possibilities:
               disabled   (0)
               enabled   (1)"
   ::= {er1645v2EthPrtSwF2IpEntry 352452608}

er1645v2EthPrtSwF2IpAccPol OBJECT-TYPE
   SYNTAX      DisplayString
   MAX-ACCESS  read-write
   STATUS      current
   DESCRIPTION
      "Path: swPort.editConf.ip.accessPolicy"
   ::= {er1645v2EthPrtSwF2IpEntry 704643072}

er1645v2EthPrtSwF2IpAB OBJECT-TYPE
   SYNTAX      DisplayString
   MAX-ACCESS  read-write
   STATUS      current
   DESCRIPTION
      "Path: swPort.editConf.ip.trafficPolicy"
   ::= {er1645v2EthPrtSwF2IpEntry 234881024}

er1645v2EthPrtSwF2IpMA OBJECT-TYPE
   SYNTAX      INTEGER
               {
               disabled (0),
               enabled (1)
               }
   MAX-ACCESS  read-write
   STATUS      current
   DESCRIPTION
      "Path: swPort.editConf.ip.mgmtAccess

       Possibilities:
               disabled   (0)
               enabled   (1)"
   ::= {er1645v2EthPrtSwF2IpEntry 268435456}

er1645v2EthPrtSwF2IpMF OBJECT-TYPE
   SYNTAX      Integer32
   MAX-ACCESS  read-write
   STATUS      current
   DESCRIPTION
      "Path: swPort.editConf.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2EthPrtSwF2IpEntry 285212672}

er1645v2EthPrtSwF2IpDB OBJECT-TYPE
   SYNTAX      INTEGER
               {
               disabled (0),
               enabled (1)
               }
   MAX-ACCESS  read-write
   STATUS      current
   DESCRIPTION
      "Path: swPort.editConf.ip.directedBroadcasts

       Possibilities:
               disabled   (0)
               enabled   (1)"
   ::= {er1645v2EthPrtSwF2IpEntry 369098752}

er1645v2EthPrtSwF2IpIR OBJECT-TYPE
   SYNTAX      INTEGER
               {
               disabled (0),
               enabled (1)
               }
   MAX-ACCESS  read-write
   STATUS      current
   DESCRIPTION
      "Path: swPort.editConf.ip.icmpRedirects

       Possibilities:
               disabled   (0)
               enabled   (1)"
   ::= {er1645v2EthPrtSwF2IpEntry 436207616}

er1645v2EthPrtSwF2IpIgmp OBJECT-TYPE
   SYNTAX      INTEGER
               {
               disabled (0),
               proxy (1),
               router (2),
               v3Router (5)
               }
   MAX-ACCESS  read-write
   STATUS      current
   DESCRIPTION
      "Path: swPort.editConf.ip.igmp

       Possibilities:
               disabled   (0)
               proxy   (1)
               router   (2)
               v3Router   (5)"
   ::= {er1645v2EthPrtSwF2IpEntry 536870912}

er1645v2EthPrtSwF2IpNN OBJECT-TYPE
   SYNTAX      DisplayString
   MAX-ACCESS  read-write
   STATUS      current
   DESCRIPTION
      "Path: swPort.editConf.ip.nat"
   ::= {er1645v2EthPrtSwF2IpEntry 452984832}

er1645v2EthPrtSwF2IpVrrp OBJECT-TYPE
   SYNTAX      INTEGER
               {
               disabled (0),
               enabled (1)
               }
   MAX-ACCESS  read-write
   STATUS      current
   DESCRIPTION
      "Path: swPort.editConf.ip.vrrp

       Possibilities:
               disabled   (0)
               enabled   (1)"
   ::= {er1645v2EthPrtSwF2IpEntry 721420288}

er1645v2EthPrtSwF2IpPimMode OBJECT-TYPE
   SYNTAX      INTEGER
               {
               disabled (0),
               sparse (1),
               passive (2)
               }
   MAX-ACCESS  read-write
   STATUS      current
   DESCRIPTION
      "Path: swPort.editConf.ip.pim.mode

       Possibilities:
               disabled   (0)
               sparse   (1)
               passive   (2)"
   ::= {er1645v2EthPrtSwF2IpEntry 771817472}

er1645v2EthPrtSwF2IpPimDrPriority OBJECT-TYPE
   SYNTAX      Counter32
   MAX-ACCESS  read-write
   STATUS      current
   DESCRIPTION
      "Path: swPort.editConf.ip.pim.drPriority

       32 bit unsigned wrappable counter."
   ::= {er1645v2EthPrtSwF2IpEntry 771883008}

er1645v2EthPrtSwF2IpPimHelloTime OBJECT-TYPE
   SYNTAX      TimeTicks
   MAX-ACCESS  read-write
   STATUS      current
   DESCRIPTION
      "Path: swPort.editConf.ip.pim.helloTime

       Time in centi-second."
   ::= {er1645v2EthPrtSwF2IpEntry 771948544}

er1645v2EthPrtSwF2IpPimPropagationDelay OBJECT-TYPE
   SYNTAX      TimeTicks
   MAX-ACCESS  read-write
   STATUS      current
   DESCRIPTION
      "Path: swPort.editConf.ip.pim.propagationDelay

       Time in centi-second."
   ::= {er1645v2EthPrtSwF2IpEntry 772014080}

er1645v2EthPrtSwF2IpPimOverrideInterval OBJECT-TYPE
   SYNTAX      TimeTicks
   MAX-ACCESS  read-write
   STATUS      current
   DESCRIPTION
      "Path: swPort.editConf.ip.pim.overrideInterval

       Time in centi-second."
   ::= {er1645v2EthPrtSwF2IpEntry 772079616}

er1645v2EthPrtSwF2IpPimBsrBorder OBJECT-TYPE
   SYNTAX      INTEGER
               {
               disabled (0),
               enabled (1)
               }
   MAX-ACCESS  read-write
   STATUS      current
   DESCRIPTION
      "Path: swPort.editConf.ip.pim.bsrBorder

       Possibilities:
               disabled   (0)
               enabled   (1)"
   ::= {er1645v2EthPrtSwF2IpEntry 772145152}

er1645v2EthPrtSwF2IpPimTtlThreshold OBJECT-TYPE
   SYNTAX      Integer32
   MAX-ACCESS  read-write
   STATUS      current
   DESCRIPTION
      "Path: swPort.editConf.ip.pim.ttlThreshold"
   ::= {er1645v2EthPrtSwF2IpEntry 772210688}

er1645v2EthPrtSwF2IpIMNetworkUnreachable OBJECT-TYPE
   SYNTAX      INTEGER
               {
               disabled (0),
               enabled (1)
               }
   MAX-ACCESS  read-write
   STATUS      current
   DESCRIPTION
      "Path: swPort.editConf.ip.icmpMessages.networkUnreachable

       Possibilities:
               disabled   (0)
               enabled   (1)"
   ::= {er1645v2EthPrtSwF2IpEntry 788594688}

er1645v2EthPrtSwF2IpIMHostUnreachable OBJECT-TYPE
   SYNTAX      INTEGER
               {
               disabled (0),
               enabled (1)
               }
   MAX-ACCESS  read-write
   STATUS      current
   DESCRIPTION
      "Path: swPort.editConf.ip.icmpMessages.hostUnreachable

       Possibilities:
               disabled   (0)
               enabled   (1)"
   ::= {er1645v2EthPrtSwF2IpEntry 788660224}

er1645v2EthPrtSwF2IpIMProtocolUnreachable OBJECT-TYPE
   SYNTAX      INTEGER
               {
               disabled (0),
               enabled (1)
               }
   MAX-ACCESS  read-write
   STATUS      current
   DESCRIPTION
      "Path: swPort.editConf.ip.icmpMessages.protocolUnreachable

       Possibilities:
               disabled   (0)
               enabled   (1)"
   ::= {er1645v2EthPrtSwF2IpEntry 788725760}

er1645v2EthPrtSwF2IpIMPortUnreachable OBJECT-TYPE
   SYNTAX      INTEGER
               {
               disabled (0),
               enabled (1)
               }
   MAX-ACCESS  read-write
   STATUS      current
   DESCRIPTION
      "Path: swPort.editConf.ip.icmpMessages.portUnreachable

       Possibilities:
               disabled   (0)
               enabled   (1)"
   ::= {er1645v2EthPrtSwF2IpEntry 788791296}

er1645v2EthPrtSwF2IpIMMtuExceeded OBJECT-TYPE
   SYNTAX      INTEGER
               {
               disabled (0),
               enabled (1)
               }
   MAX-ACCESS  read-write
   STATUS      current
   DESCRIPTION
      "Path: swPort.editConf.ip.icmpMessages.mtuExceeded

       Possibilities:
               disabled   (0)
               enabled   (1)"
   ::= {er1645v2EthPrtSwF2IpEntry 788856832}

er1645v2EthPrtSwF2IpIMAdminProhibited OBJECT-TYPE
   SYNTAX      INTEGER
               {
               disabled (0),
               enabled (1)
               }
   MAX-ACCESS  read-write
   STATUS      current
   DESCRIPTION
      "Path: swPort.editConf.ip.icmpMessages.adminProhibited

       Possibilities:
               disabled   (0)
               enabled   (1)"
   ::= {er1645v2EthPrtSwF2IpEntry 788922368}

er1645v2EthPrtSwF2IpIMTtlExceeded OBJECT-TYPE
   SYNTAX      INTEGER
               {
               disabled (0),
               enabled (1)
               }
   MAX-ACCESS  read-write
   STATUS      current
   DESCRIPTION
      "Path: swPort.editConf.ip.icmpMessages.ttlExceeded

       Possibilities:
               disabled   (0)
               enabled   (1)"
   ::= {er1645v2EthPrtSwF2IpEntry 788987904}

er1645v2EthPrtSwF2IpIMRedirect OBJECT-TYPE
   SYNTAX      INTEGER
               {
               disabled (0),
               enabled (1)
               }
   MAX-ACCESS  read-write
   STATUS      current
   DESCRIPTION
      "Path: swPort.editConf.ip.icmpMessages.redirect

       Possibilities:
               disabled   (0)
               enabled   (1)"
   ::= {er1645v2EthPrtSwF2IpEntry 789053440}

er1645v2EthPrtSwF2IpSaddr OBJECT-TYPE
   SYNTAX      SEQUENCE OF Er1645v2EthPrtSwF2IpSaddrEntry
   MAX-ACCESS  not-accessible
   STATUS      current
   DESCRIPTION
      ""
   ::= {er1645v2EthPrtSwF2Ip 385875968}

er1645v2EthPrtSwF2IpSaddrEntry OBJECT-TYPE
   SYNTAX      Er1645v2EthPrtSwF2IpSaddrEntry
   MAX-ACCESS  not-accessible
   STATUS      current
   DESCRIPTION
      ""
   INDEX      { er1645v2EthPrtSwF2IpSaddrGlobalIx,
                er1645v2EthPrtSwF2IpSaddrTableIx }
   ::= {er1645v2EthPrtSwF2IpSaddr 1}

Er1645v2EthPrtSwF2IpSaddrEntry ::=
   SEQUENCE
      {
      er1645v2EthPrtSwF2IpSaddrActions
         VariableLengthTableActions,
      er1645v2EthPrtSwF2IpSaddrGlobalIx
         GlobalIndex,
      er1645v2EthPrtSwF2IpSaddrTableIx
         TableIndex,
      er1645v2EthPrtSwF2IpSaddrAddress
         IpAddress,
      er1645v2EthPrtSwF2IpSaddrNetMask
         IpAddress
      }

er1645v2EthPrtSwF2IpSaddrActions OBJECT-TYPE
   SYNTAX      VariableLengthTableActions
   MAX-ACCESS  read-write
   STATUS      current
   DESCRIPTION
      "By way of this field, some manipulations
       on this table may be performed."
   ::= {er1645v2EthPrtSwF2IpSaddrEntry 2}

er1645v2EthPrtSwF2IpSaddrGlobalIx OBJECT-TYPE
   SYNTAX      GlobalIndex
   MAX-ACCESS  not-accessible
   STATUS      current
   DESCRIPTION
      "The value of the tlsCntTreeGlobalIndex of the MANAGED OBJECT."
   ::= {er1645v2EthPrtSwF2IpSaddrEntry 10}

er1645v2EthPrtSwF2IpSaddrTableIx OBJECT-TYPE
   SYNTAX      TableIndex
   MAX-ACCESS  not-accessible
   STATUS      current
   DESCRIPTION
      ""
   ::= {er1645v2EthPrtSwF2IpSaddrEntry 11}

er1645v2EthPrtSwF2IpSaddrAddress OBJECT-TYPE
   SYNTAX      IpAddress
   MAX-ACCESS  read-write
   STATUS      current
   DESCRIPTION
      "Path: swPort.editConf.ip.secondaryIp.address"
   ::= {er1645v2EthPrtSwF2IpSaddrEntry 2030043136}

er1645v2EthPrtSwF2IpSaddrNetMask OBJECT-TYPE
   SYNTAX      IpAddress
   MAX-ACCESS  read-write
   STATUS      current
   DESCRIPTION
      "Path: swPort.editConf.ip.secondaryIp.netMask"
   ::= {er1645v2EthPrtSwF2IpSaddrEntry 2063597568}

er1645v2EthPrtSwF2IpH OBJECT-TYPE
   SYNTAX      SEQUENCE OF Er1645v2EthPrtSwF2IpHEntry
   MAX-ACCESS  not-accessible
   STATUS      current
   DESCRIPTION
      ""
   ::= {er1645v2EthPrtSwF2Ip 251658240}

er1645v2EthPrtSwF2IpHEntry OBJECT-TYPE
   SYNTAX      Er1645v2EthPrtSwF2IpHEntry
   MAX-ACCESS  not-accessible
   STATUS      current
   DESCRIPTION
      ""
   INDEX      { er1645v2EthPrtSwF2IpHGlobalIx,
                er1645v2EthPrtSwF2IpHTableIx }
   ::= {er1645v2EthPrtSwF2IpH 1}

Er1645v2EthPrtSwF2IpHEntry ::=
   SEQUENCE
      {
      er1645v2EthPrtSwF2IpHActions
         VariableLengthTableActions,
      er1645v2EthPrtSwF2IpHGlobalIx
         GlobalIndex,
      er1645v2EthPrtSwF2IpHTableIx
         TableIndex,
      er1645v2EthPrtSwF2IpHAddress
         IpAddress,
      er1645v2EthPrtSwF2IpHDhcpRelayOptionSubscriberId
         DisplayString
      }

er1645v2EthPrtSwF2IpHActions OBJECT-TYPE
   SYNTAX      VariableLengthTableActions
   MAX-ACCESS  read-write
   STATUS      current
   DESCRIPTION
      "By way of this field, some manipulations
       on this table may be performed."
   ::= {er1645v2EthPrtSwF2IpHEntry 2}

er1645v2EthPrtSwF2IpHGlobalIx OBJECT-TYPE
   SYNTAX      GlobalIndex
   MAX-ACCESS  not-accessible
   STATUS      current
   DESCRIPTION
      "The value of the tlsCntTreeGlobalIndex of the MANAGED OBJECT."
   ::= {er1645v2EthPrtSwF2IpHEntry 10}

er1645v2EthPrtSwF2IpHTableIx OBJECT-TYPE
   SYNTAX      TableIndex
   MAX-ACCESS  not-accessible
   STATUS      current
   DESCRIPTION
      ""
   ::= {er1645v2EthPrtSwF2IpHEntry 11}

er1645v2EthPrtSwF2IpHAddress OBJECT-TYPE
   SYNTAX      IpAddress
   MAX-ACCESS  read-write
   STATUS      current
   DESCRIPTION
      "Path: swPort.editConf.ip.helpers.address"
   ::= {er1645v2EthPrtSwF2IpHEntry 16777216}

er1645v2EthPrtSwF2IpHDhcpRelayOptionSubscriberId OBJECT-TYPE
   SYNTAX      DisplayString
   MAX-ACCESS  read-write
   STATUS      current
   DESCRIPTION
      "Path: swPort.editConf.ip.helpers.dhcpRelayOption.subscriberId"
   ::= {er1645v2EthPrtSwF2IpHEntry 33947648}


er1645v2EthPrtSwF2Name OBJECT IDENTIFIER ::= {er1645v2EthPrtSwF2 2}

er1645v2EthPrtSwF2NameTable OBJECT-TYPE
   SYNTAX      SEQUENCE OF Er1645v2EthPrtSwF2NameEntry
   MAX-ACCESS  not-accessible
   STATUS      current
   DESCRIPTION
      "config interface name"
   ::= {er1645v2EthPrtSwF2Name 1}

er1645v2EthPrtSwF2NameEntry OBJECT-TYPE
   SYNTAX      Er1645v2EthPrtSwF2NameEntry
   MAX-ACCESS  not-accessible
   STATUS      current
   DESCRIPTION
      ""
   INDEX      { er1645v2EthPrtSwF2NameGlobalIx }
   ::= {er1645v2EthPrtSwF2NameTable 1}

Er1645v2EthPrtSwF2NameEntry ::=
   SEQUENCE
      {
      er1645v2EthPrtSwF2NameGlobalIx
         GlobalIndex,
      er1645v2EthPrtSwF2NameValue
         DisplayString
      }

er1645v2EthPrtSwF2NameGlobalIx OBJECT-TYPE
   SYNTAX      GlobalIndex
   MAX-ACCESS  not-accessible
   STATUS      current
   DESCRIPTION
      "The value of the tlsCntTreeGlobalIndex of the MANAGED OBJECT."
   ::= {er1645v2EthPrtSwF2NameEntry 10}

er1645v2EthPrtSwF2NameValue OBJECT-TYPE
   SYNTAX      DisplayString
   MAX-ACCESS  read-write
   STATUS      current
   DESCRIPTION
      "Path: swPort.editConf.name"
   ::= {er1645v2EthPrtSwF2NameEntry 2147483648}


er1645v2EthPrtSwF2Bw OBJECT IDENTIFIER ::= {er1645v2EthPrtSwF2 5}

er1645v2EthPrtSwF2BwSSCTable OBJECT-TYPE
   SYNTAX      SEQUENCE OF Er1645v2EthPrtSwF2BwEntry
   MAX-ACCESS  not-accessible
   STATUS      current
   DESCRIPTION
      ""
   ::= {er1645v2EthPrtSwF2Bw 1}

er1645v2EthPrtSwF2BwEntry OBJECT-TYPE
   SYNTAX      Er1645v2EthPrtSwF2BwEntry
   MAX-ACCESS  not-accessible
   STATUS      current
   DESCRIPTION
      ""
   INDEX      { er1645v2EthPrtSwF2BwGlobalIx }
   ::= {er1645v2EthPrtSwF2BwSSCTable 1}

Er1645v2EthPrtSwF2BwEntry ::=
   SEQUENCE
      {
      er1645v2EthPrtSwF2BwGlobalIx
         GlobalIndex,
      er1645v2EthPrtSwF2BwMode
         INTEGER,
      er1645v2EthPrtSwF2BwCir
         Integer32,
      er1645v2EthPrtSwF2BwEir
         Integer32,
      er1645v2EthPrtSwF2BwUnit
         INTEGER,
      er1645v2EthPrtSwF2BwTc
         INTEGER,
      er1645v2EthPrtSwF2BwTcFactor
         INTEGER,
      er1645v2EthPrtSwF2BwCorrType
         INTEGER,
      er1645v2EthPrtSwF2BwCorrPredefEncapsFrameRelay
         DisplayString,
      er1645v2EthPrtSwF2BwCorrPredefEncapsPpp
         DisplayString,
      er1645v2EthPrtSwF2BwCorrPredefEncapsAtmHl
         INTEGER,
      er1645v2EthPrtSwF2BwCorrPredefEncapsAtmMp
         INTEGER,
      er1645v2EthPrtSwF2BwCorrPredefEncapsHdlc
         DisplayString,
      er1645v2EthPrtSwF2BwCorrPredefEncapsEfmFs
         Integer32,
      er1645v2EthPrtSwF2BwCorrPredefEncapsEfmIb
         Integer32,
      er1645v2EthPrtSwF2BwCorrPredefMode
         INTEGER,
      er1645v2EthPrtSwF2BwCorrManualOverhead
         Integer32,
      er1645v2EthPrtSwF2BwCorrManualFrameData
         Counter32,
      er1645v2EthPrtSwF2BwCorrManualFrameHeader
         Counter32,
      er1645v2EthPrtSwF2BwMaxFifoQLen
         Integer32,
      er1645v2EthPrtSwF2BwDeFlagCir
         INTEGER,
      er1645v2EthPrtSwF2BwDeFlagEir
         INTEGER,
      er1645v2EthPrtSwF2BwDeFlagViolate
         INTEGER,
      er1645v2EthPrtSwF2BwActCirActNone
         OCTET STRING,
      er1645v2EthPrtSwF2BwActCirActEthCos1
         INTEGER,
      er1645v2EthPrtSwF2BwActCirActEthDei1
         INTEGER,
      er1645v2EthPrtSwF2BwActCirActEthCos2
         INTEGER,
      er1645v2EthPrtSwF2BwActCirActEthDei2
         INTEGER,
      er1645v2EthPrtSwF2BwActCirActEthCos3
         INTEGER,
      er1645v2EthPrtSwF2BwActCirActEthDei3
         INTEGER,
      er1645v2EthPrtSwF2BwActCirActEthCos4
         INTEGER,
      er1645v2EthPrtSwF2BwActCirActEthDei4
         INTEGER,
      er1645v2EthPrtSwF2BwActCirActEthCos5
         INTEGER,
      er1645v2EthPrtSwF2BwActCirActEthDei5
         INTEGER,
      er1645v2EthPrtSwF2BwActCirActEthCos6
         INTEGER,
      er1645v2EthPrtSwF2BwActCirActEthDei6
         INTEGER,
      er1645v2EthPrtSwF2BwActCirActEthCos7
         INTEGER,
      er1645v2EthPrtSwF2BwActCirActEthDei7
         INTEGER,
      er1645v2EthPrtSwF2BwActCirActEthCos8
         INTEGER,
      er1645v2EthPrtSwF2BwActCirActEthDei8
         INTEGER,
      er1645v2EthPrtSwF2BwActCirActEthTos
         INTEGER,
      er1645v2EthPrtSwF2BwActCirActEthQueue
         INTEGER,
      er1645v2EthPrtSwF2BwActCirActEthDrpLev
         INTEGER,
      er1645v2EthPrtSwF2BwActCirActEthDeFlag
         INTEGER,
      er1645v2EthPrtSwF2BwActCirActIpTos
         INTEGER,
      er1645v2EthPrtSwF2BwActCirActIpQueue
         INTEGER,
      er1645v2EthPrtSwF2BwActCirActIpDrpLev
         INTEGER,
      er1645v2EthPrtSwF2BwActCirActIpDeFlag
         INTEGER,
      er1645v2EthPrtSwF2BwActEirActNone
         OCTET STRING,
      er1645v2EthPrtSwF2BwActEirActEthCos1
         INTEGER,
      er1645v2EthPrtSwF2BwActEirActEthDei1
         INTEGER,
      er1645v2EthPrtSwF2BwActEirActEthCos2
         INTEGER,
      er1645v2EthPrtSwF2BwActEirActEthDei2
         INTEGER,
      er1645v2EthPrtSwF2BwActEirActEthCos3
         INTEGER,
      er1645v2EthPrtSwF2BwActEirActEthDei3
         INTEGER,
      er1645v2EthPrtSwF2BwActEirActEthCos4
         INTEGER,
      er1645v2EthPrtSwF2BwActEirActEthDei4
         INTEGER,
      er1645v2EthPrtSwF2BwActEirActEthCos5
         INTEGER,
      er1645v2EthPrtSwF2BwActEirActEthDei5
         INTEGER,
      er1645v2EthPrtSwF2BwActEirActEthCos6
         INTEGER,
      er1645v2EthPrtSwF2BwActEirActEthDei6
         INTEGER,
      er1645v2EthPrtSwF2BwActEirActEthCos7
         INTEGER,
      er1645v2EthPrtSwF2BwActEirActEthDei7
         INTEGER,
      er1645v2EthPrtSwF2BwActEirActEthCos8
         INTEGER,
      er1645v2EthPrtSwF2BwActEirActEthDei8
         INTEGER,
      er1645v2EthPrtSwF2BwActEirActEthTos
         INTEGER,
      er1645v2EthPrtSwF2BwActEirActEthQueue
         INTEGER,
      er1645v2EthPrtSwF2BwActEirActEthDrpLev
         INTEGER,
      er1645v2EthPrtSwF2BwActEirActEthDeFlag
         INTEGER,
      er1645v2EthPrtSwF2BwActEirActIpTos
         INTEGER,
      er1645v2EthPrtSwF2BwActEirActIpQueue
         INTEGER,
      er1645v2EthPrtSwF2BwActEirActIpDrpLev
         INTEGER,
      er1645v2EthPrtSwF2BwActEirActIpDeFlag
         INTEGER,
      er1645v2EthPrtSwF2BwActViolActNone
         OCTET STRING,
      er1645v2EthPrtSwF2BwActViolActDrop
         OCTET STRING,
      er1645v2EthPrtSwF2BwActViolActEthCos1
         INTEGER,
      er1645v2EthPrtSwF2BwActViolActEthDei1
         INTEGER,
      er1645v2EthPrtSwF2BwActViolActEthCos2
         INTEGER,
      er1645v2EthPrtSwF2BwActViolActEthDei2
         INTEGER,
      er1645v2EthPrtSwF2BwActViolActEthCos3
         INTEGER,
      er1645v2EthPrtSwF2BwActViolActEthDei3
         INTEGER,
      er1645v2EthPrtSwF2BwActViolActEthCos4
         INTEGER,
      er1645v2EthPrtSwF2BwActViolActEthDei4
         INTEGER,
      er1645v2EthPrtSwF2BwActViolActEthCos5
         INTEGER,
      er1645v2EthPrtSwF2BwActViolActEthDei5
         INTEGER,
      er1645v2EthPrtSwF2BwActViolActEthCos6
         INTEGER,
      er1645v2EthPrtSwF2BwActViolActEthDei6
         INTEGER,
      er1645v2EthPrtSwF2BwActViolActEthCos7
         INTEGER,
      er1645v2EthPrtSwF2BwActViolActEthDei7
         INTEGER,
      er1645v2EthPrtSwF2BwActViolActEthCos8
         INTEGER,
      er1645v2EthPrtSwF2BwActViolActEthDei8
         INTEGER,
      er1645v2EthPrtSwF2BwActViolActEthTos
         INTEGER,
      er1645v2EthPrtSwF2BwActViolActEthQueue
         INTEGER,
      er1645v2EthPrtSwF2BwActViolActEthDrpLev
         INTEGER,
      er1645v2EthPrtSwF2BwActViolActEthDeFlag
         INTEGER,
      er1645v2EthPrtSwF2BwActViolActIpTos
         INTEGER,
      er1645v2EthPrtSwF2BwActViolActIpQueue
         INTEGER,
      er1645v2EthPrtSwF2BwActViolActIpDrpLev
         INTEGER,
      er1645v2EthPrtSwF2BwActViolActIpDeFlag
         INTEGER
      }

er1645v2EthPrtSwF2BwGlobalIx OBJECT-TYPE
   SYNTAX      GlobalIndex
   MAX-ACCESS  not-accessible
   STATUS      current
   DESCRIPTION
      "The value of the tlsCntTreeGlobalIndex of the MANAGED OBJECT."
   ::= {er1645v2EthPrtSwF2BwEntry 10}

er1645v2EthPrtSwF2BwMode OBJECT-TYPE
   SYNTAX      INTEGER
               {
               reshaping (1),
               policing (2),
               policingReshape (3)
               }
   MAX-ACCESS  read-write
   STATUS      current
   DESCRIPTION
      "Path: swPort.editConf.bandwidth.mode

       Possibilities:
               reshaping   (1)
               policing   (2)
               policingReshape   (3)"
   ::= {er1645v2EthPrtSwF2BwEntry 3758096384}

er1645v2EthPrtSwF2BwCir OBJECT-TYPE
   SYNTAX      Integer32
   MAX-ACCESS  read-write
   STATUS      current
   DESCRIPTION
      "Path: swPort.editConf.bandwidth.cir"
   ::= {er1645v2EthPrtSwF2BwEntry 268435456}

er1645v2EthPrtSwF2BwEir OBJECT-TYPE
   SYNTAX      Integer32
   MAX-ACCESS  read-write
   STATUS      current
   DESCRIPTION
      "Path: swPort.editConf.bandwidth.eir"
   ::= {er1645v2EthPrtSwF2BwEntry 1879048192}

er1645v2EthPrtSwF2BwUnit OBJECT-TYPE
   SYNTAX      INTEGER
               {
               bitssec (1),
               percent (2)
               }
   MAX-ACCESS  read-write
   STATUS      current
   DESCRIPTION
      "Path: swPort.editConf.bandwidth.unit

       Possibilities:
               bits/sec   (1)
               percent   (2)"
   ::= {er1645v2EthPrtSwF2BwEntry 1342177280}

er1645v2EthPrtSwF2BwTc OBJECT-TYPE
   SYNTAX      INTEGER
               {
               auto (0)
               }
   MAX-ACCESS  read-write
   STATUS      current
   DESCRIPTION
      "Path: swPort.editConf.bandwidth.tc

       Possibilities:
               auto   (0)"
   ::= {er1645v2EthPrtSwF2BwEntry 1610612736}

er1645v2EthPrtSwF2BwTcFactor OBJECT-TYPE
   SYNTAX      INTEGER
               {
               ms (10),
               s100us (1)
               }
   MAX-ACCESS  read-write
   STATUS      current
   DESCRIPTION
      "Path: swPort.editConf.bandwidth.tcFactor

       Possibilities:
               ms   (10)
               *100us   (1)"
   ::= {er1645v2EthPrtSwF2BwEntry 2147483648}

er1645v2EthPrtSwF2BwCorrType OBJECT-TYPE
   SYNTAX      INTEGER
               {
               noCorrection (0),
               predefined (1),
               manual (2)
               }
   MAX-ACCESS  read-write
   STATUS      current
   DESCRIPTION
      "Path: swPort.editConf.bandwidth.correction.type

       Possibilities:
               noCorrection   (0)
               predefined   (1)
               manual   (2)"
   ::= {er1645v2EthPrtSwF2BwEntry 570425344}

er1645v2EthPrtSwF2BwCorrPredefEncapsFrameRelay OBJECT-TYPE
   SYNTAX      DisplayString
   MAX-ACCESS  read-write
   STATUS      current
   DESCRIPTION
      "Path: swPort.editConf.bandwidth.correction.predefined.encapsulation.frameRelay"
   ::= {er1645v2EthPrtSwF2BwEntry 608436224}

er1645v2EthPrtSwF2BwCorrPredefEncapsPpp OBJECT-TYPE
   SYNTAX      DisplayString
   MAX-ACCESS  read-write
   STATUS      current
   DESCRIPTION
      "Path: swPort.editConf.bandwidth.correction.predefined.encapsulation.ppp"
   ::= {er1645v2EthPrtSwF2BwEntry 608698368}

er1645v2EthPrtSwF2BwCorrPredefEncapsAtmHl OBJECT-TYPE
   SYNTAX      INTEGER
               {
               rfc2684 (0),
               ppp (1),
               pppOverEthernet (2)
               }
   MAX-ACCESS  read-write
   STATUS      current
   DESCRIPTION
      "Path: swPort.editConf.bandwidth.correction.predefined.encapsulation.atm.higherLayer

       Possibilities:
               rfc2684   (0)
               ppp   (1)
               pppOverEthernet   (2)"
   ::= {er1645v2EthPrtSwF2BwEntry 608993280}

er1645v2EthPrtSwF2BwCorrPredefEncapsAtmMp OBJECT-TYPE
   SYNTAX      INTEGER
               {
               llcEncapsulation (0),
               vcMultiplexing (1)
               }
   MAX-ACCESS  read-write
   STATUS      current
   DESCRIPTION
      "Path: swPort.editConf.bandwidth.correction.predefined.encapsulation.atm.multiProtocol

       Possibilities:
               llcEncapsulation   (0)
               vcMultiplexing   (1)"
   ::= {er1645v2EthPrtSwF2BwEntry 609026048}

er1645v2EthPrtSwF2BwCorrPredefEncapsHdlc OBJECT-TYPE
   SYNTAX      DisplayString
   MAX-ACCESS  read-write
   STATUS      current
   DESCRIPTION
      "Path: swPort.editConf.bandwidth.correction.predefined.encapsulation.hdlc"
   ::= {er1645v2EthPrtSwF2BwEntry 609222656}

er1645v2EthPrtSwF2BwCorrPredefEncapsEfmFs OBJECT-TYPE
   SYNTAX      Integer32
   MAX-ACCESS  read-write
   STATUS      current
   DESCRIPTION
      "Path: swPort.editConf.bandwidth.correction.predefined.encapsulation.efm.fragmentSize"
   ::= {er1645v2EthPrtSwF2BwEntry 609517568}

er1645v2EthPrtSwF2BwCorrPredefEncapsEfmIb OBJECT-TYPE
   SYNTAX      Integer32
   MAX-ACCESS  read-write
   STATUS      current
   DESCRIPTION
      "Path: swPort.editConf.bandwidth.correction.predefined.encapsulation.efm.idleBytes"
   ::= {er1645v2EthPrtSwF2BwEntry 609550336}

er1645v2EthPrtSwF2BwCorrPredefMode OBJECT-TYPE
   SYNTAX      INTEGER
               {
               routing (0),
               bridging (1)
               }
   MAX-ACCESS  read-write
   STATUS      current
   DESCRIPTION
      "Path: swPort.editConf.bandwidth.correction.predefined.mode

       Possibilities:
               routing   (0)
               bridging   (1)"
   ::= {er1645v2EthPrtSwF2BwEntry 612368384}

er1645v2EthPrtSwF2BwCorrManualOverhead OBJECT-TYPE
   SYNTAX      Integer32
   MAX-ACCESS  read-write
   STATUS      current
   DESCRIPTION
      "Path: swPort.editConf.bandwidth.correction.manual.overhead"
   ::= {er1645v2EthPrtSwF2BwEntry 637665280}

er1645v2EthPrtSwF2BwCorrManualFrameData OBJECT-TYPE
   SYNTAX      Counter32
   MAX-ACCESS  read-write
   STATUS      current
   DESCRIPTION
      "Path: swPort.editConf.bandwidth.correction.manual.frameData

       32 bit unsigned wrappable counter."
   ::= {er1645v2EthPrtSwF2BwEntry 637796352}

er1645v2EthPrtSwF2BwCorrManualFrameHeader OBJECT-TYPE
   SYNTAX      Counter32
   MAX-ACCESS  read-write
   STATUS      current
   DESCRIPTION
      "Path: swPort.editConf.bandwidth.correction.manual.frameHeader

       32 bit unsigned wrappable counter."
   ::= {er1645v2EthPrtSwF2BwEntry 637927424}

er1645v2EthPrtSwF2BwMaxFifoQLen OBJECT-TYPE
   SYNTAX      Integer32
   MAX-ACCESS  read-write
   STATUS      current
   DESCRIPTION
      "Path: swPort.editConf.bandwidth.maxFifoQLen"
   ::= {er1645v2EthPrtSwF2BwEntry 805306368}

er1645v2EthPrtSwF2BwDeFlagCir OBJECT-TYPE
   SYNTAX      INTEGER
               {
               allowed (1),
               notAllowed (2)
               }
   MAX-ACCESS  read-write
   STATUS      current
   DESCRIPTION
      "Path: swPort.editConf.bandwidth.deFlag.cir

       Possibilities:
               allowed   (1)
               notAllowed   (2)"
   ::= {er1645v2EthPrtSwF2BwEntry 3490709504}

er1645v2EthPrtSwF2BwDeFlagEir OBJECT-TYPE
   SYNTAX      INTEGER
               {
               allowed (1),
               notAllowed (2)
               }
   MAX-ACCESS  read-write
   STATUS      current
   DESCRIPTION
      "Path: swPort.editConf.bandwidth.deFlag.eir

       Possibilities:
               allowed   (1)
               notAllowed   (2)"
   ::= {er1645v2EthPrtSwF2BwEntry 3491758080}

er1645v2EthPrtSwF2BwDeFlagViolate OBJECT-TYPE
   SYNTAX      INTEGER
               {
               allowed (1),
               notAllowed (2)
               }
   MAX-ACCESS  read-write
   STATUS      current
   DESCRIPTION
      "Path: swPort.editConf.bandwidth.deFlag.violate

       Possibilities:
               allowed   (1)
               notAllowed   (2)"
   ::= {er1645v2EthPrtSwF2BwEntry 3492806656}

er1645v2EthPrtSwF2BwActCirActNone OBJECT-TYPE
   SYNTAX      OCTET STRING
   MAX-ACCESS  read-write
   STATUS      current
   DESCRIPTION
      "Path: swPort.editConf.bandwidth.action.cirAction.none"
   ::= {er1645v2EthPrtSwF2BwEntry 4062183424}

er1645v2EthPrtSwF2BwActCirActEthCos1 OBJECT-TYPE
   SYNTAX      INTEGER
               {
               unchanged (256)
               }
   MAX-ACCESS  read-write
   STATUS      current
   DESCRIPTION
      "Path: swPort.editConf.bandwidth.action.cirAction.ethernet.cosDepth1

       Possibilities:
               unchanged   (256)"
   ::= {er1645v2EthPrtSwF2BwEntry 4064346112}

er1645v2EthPrtSwF2BwActCirActEthDei1 OBJECT-TYPE
   SYNTAX      INTEGER
               {
               unchanged (255),
               clear (0),
               set (1)
               }
   MAX-ACCESS  read-write
   STATUS      current
   DESCRIPTION
      "Path: swPort.editConf.bandwidth.action.cirAction.ethernet.deiDepth1

       Possibilities:
               unchanged   (255)
               clear   (0)
               set   (1)"
   ::= {er1645v2EthPrtSwF2BwEntry 4065656832}

er1645v2EthPrtSwF2BwActCirActEthCos2 OBJECT-TYPE
   SYNTAX      INTEGER
               {
               unchanged (256)
               }
   MAX-ACCESS  read-write
   STATUS      current
   DESCRIPTION
      "Path: swPort.editConf.bandwidth.action.cirAction.ethernet.cosDepth2

       Possibilities:
               unchanged   (256)"
   ::= {er1645v2EthPrtSwF2BwEntry 4064411648}

er1645v2EthPrtSwF2BwActCirActEthDei2 OBJECT-TYPE
   SYNTAX      INTEGER
               {
               unchanged (255),
               clear (0),
               set (1)
               }
   MAX-ACCESS  read-write
   STATUS      current
   DESCRIPTION
      "Path: swPort.editConf.bandwidth.action.cirAction.ethernet.deiDepth2

       Possibilities:
               unchanged   (255)
               clear   (0)
               set   (1)"
   ::= {er1645v2EthPrtSwF2BwEntry 4065722368}

er1645v2EthPrtSwF2BwActCirActEthCos3 OBJECT-TYPE
   SYNTAX      INTEGER
               {
               unchanged (256)
               }
   MAX-ACCESS  read-write
   STATUS      current
   DESCRIPTION
      "Path: swPort.editConf.bandwidth.action.cirAction.ethernet.cosDepth3

       Possibilities:
               unchanged   (256)"
   ::= {er1645v2EthPrtSwF2BwEntry 4064477184}

er1645v2EthPrtSwF2BwActCirActEthDei3 OBJECT-TYPE
   SYNTAX      INTEGER
               {
               unchanged (255),
               clear (0),
               set (1)
               }
   MAX-ACCESS  read-write
   STATUS      current
   DESCRIPTION
      "Path: swPort.editConf.bandwidth.action.cirAction.ethernet.deiDepth3

       Possibilities:
               unchanged   (255)
               clear   (0)
               set   (1)"
   ::= {er1645v2EthPrtSwF2BwEntry 4065787904}

er1645v2EthPrtSwF2BwActCirActEthCos4 OBJECT-TYPE
   SYNTAX      INTEGER
               {
               unchanged (256)
               }
   MAX-ACCESS  read-write
   STATUS      current
   DESCRIPTION
      "Path: swPort.editConf.bandwidth.action.cirAction.ethernet.cosDepth4

       Possibilities:
               unchanged   (256)"
   ::= {er1645v2EthPrtSwF2BwEntry 4064542720}

er1645v2EthPrtSwF2BwActCirActEthDei4 OBJECT-TYPE
   SYNTAX      INTEGER
               {
               unchanged (255),
               clear (0),
               set (1)
               }
   MAX-ACCESS  read-write
   STATUS      current
   DESCRIPTION
      "Path: swPort.editConf.bandwidth.action.cirAction.ethernet.deiDepth4

       Possibilities:
               unchanged   (255)
               clear   (0)
               set   (1)"
   ::= {er1645v2EthPrtSwF2BwEntry 4065853440}

er1645v2EthPrtSwF2BwActCirActEthCos5 OBJECT-TYPE
   SYNTAX      INTEGER
               {
               unchanged (256)
               }
   MAX-ACCESS  read-write
   STATUS      current
   DESCRIPTION
      "Path: swPort.editConf.bandwidth.action.cirAction.ethernet.cosDepth5

       Possibilities:
               unchanged   (256)"
   ::= {er1645v2EthPrtSwF2BwEntry 4064608256}

er1645v2EthPrtSwF2BwActCirActEthDei5 OBJECT-TYPE
   SYNTAX      INTEGER
               {
               unchanged (255),
               clear (0),
               set (1)
               }
   MAX-ACCESS  read-write
   STATUS      current
   DESCRIPTION
      "Path: swPort.editConf.bandwidth.action.cirAction.ethernet.deiDepth5

       Possibilities:
               unchanged   (255)
               clear   (0)
               set   (1)"
   ::= {er1645v2EthPrtSwF2BwEntry 4065918976}

er1645v2EthPrtSwF2BwActCirActEthCos6 OBJECT-TYPE
   SYNTAX      INTEGER
               {
               unchanged (256)
               }
   MAX-ACCESS  read-write
   STATUS      current
   DESCRIPTION
      "Path: swPort.editConf.bandwidth.action.cirAction.ethernet.cosDepth6

       Possibilities:
               unchanged   (256)"
   ::= {er1645v2EthPrtSwF2BwEntry 4064673792}

er1645v2EthPrtSwF2BwActCirActEthDei6 OBJECT-TYPE
   SYNTAX      INTEGER
               {
               unchanged (255),
               clear (0),
               set (1)
               }
   MAX-ACCESS  read-write
   STATUS      current
   DESCRIPTION
      "Path: swPort.editConf.bandwidth.action.cirAction.ethernet.deiDepth6

       Possibilities:
               unchanged   (255)
               clear   (0)
               set   (1)"
   ::= {er1645v2EthPrtSwF2BwEntry 4065984512}

er1645v2EthPrtSwF2BwActCirActEthCos7 OBJECT-TYPE
   SYNTAX      INTEGER
               {
               unchanged (256)
               }
   MAX-ACCESS  read-write
   STATUS      current
   DESCRIPTION
      "Path: swPort.editConf.bandwidth.action.cirAction.ethernet.cosDepth7

       Possibilities:
               unchanged   (256)"
   ::= {er1645v2EthPrtSwF2BwEntry 4064739328}

er1645v2EthPrtSwF2BwActCirActEthDei7 OBJECT-TYPE
   SYNTAX      INTEGER
               {
               unchanged (255),
               clear (0),
               set (1)
               }
   MAX-ACCESS  read-write
   STATUS      current
   DESCRIPTION
      "Path: swPort.editConf.bandwidth.action.cirAction.ethernet.deiDepth7

       Possibilities:
               unchanged   (255)
               clear   (0)
               set   (1)"
   ::= {er1645v2EthPrtSwF2BwEntry 4066050048}

er1645v2EthPrtSwF2BwActCirActEthCos8 OBJECT-TYPE
   SYNTAX      INTEGER
               {
               unchanged (256)
               }
   MAX-ACCESS  read-write
   STATUS      current
   DESCRIPTION
      "Path: swPort.editConf.bandwidth.action.cirAction.ethernet.cosDepth8

       Possibilities:
               unchanged   (256)"
   ::= {er1645v2EthPrtSwF2BwEntry 4064804864}

er1645v2EthPrtSwF2BwActCirActEthDei8 OBJECT-TYPE
   SYNTAX      INTEGER
               {
               unchanged (255),
               clear (0),
               set (1)
               }
   MAX-ACCESS  read-write
   STATUS      current
   DESCRIPTION
      "Path: swPort.editConf.bandwidth.action.cirAction.ethernet.deiDepth8

       Possibilities:
               unchanged   (255)
               clear   (0)
               set   (1)"
   ::= {er1645v2EthPrtSwF2BwEntry 4066115584}

er1645v2EthPrtSwF2BwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPrtSwF2BwEntry 4064870400}

er1645v2EthPrtSwF2BwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2EthPrtSwF2BwEntry 4064935936}

er1645v2EthPrtSwF2BwActCirActEthDrpLev OBJECT-TYPE
   SYNTAX      INTEGER
               {
               unchanged (0)
               }
   MAX-ACCESS  read-write
   STATUS      current
   DESCRIPTION
      "Path: swPort.editConf.bandwidth.action.cirAction.ethernet.dropLevel

       Possibilities:
               unchanged   (0)"
   ::= {er1645v2EthPrtSwF2BwEntry 4065001472}

er1645v2EthPrtSwF2BwActCirActEthDeFlag OBJECT-TYPE
   SYNTAX      INTEGER
               {
               unchanged (255),
               clear (0),
               set (1)
               }
   MAX-ACCESS  read-write
   STATUS      current
   DESCRIPTION
      "Path: swPort.editConf.bandwidth.action.cirAction.ethernet.deFlag

       Possibilities:
               unchanged   (255)
               clear   (0)
               set   (1)"
   ::= {er1645v2EthPrtSwF2BwEntry 4065198080}

er1645v2EthPrtSwF2BwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPrtSwF2BwEntry 4071161856}

er1645v2EthPrtSwF2BwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2EthPrtSwF2BwEntry 4071227392}

er1645v2EthPrtSwF2BwActCirActIpDrpLev OBJECT-TYPE
   SYNTAX      INTEGER
               {
               unchanged (0)
               }
   MAX-ACCESS  read-write
   STATUS      current
   DESCRIPTION
      "Path: swPort.editConf.bandwidth.action.cirAction.ip.dropLevel

       Possibilities:
               unchanged   (0)"
   ::= {er1645v2EthPrtSwF2BwEntry 4071292928}

er1645v2EthPrtSwF2BwActCirActIpDeFlag OBJECT-TYPE
   SYNTAX      INTEGER
               {
               unchanged (255),
               clear (0),
               set (1)
               }
   MAX-ACCESS  read-write
   STATUS      current
   DESCRIPTION
      "Path: swPort.editConf.bandwidth.action.cirAction.ip.deFlag

       Possibilities:
               unchanged   (255)
               clear   (0)
               set   (1)"
   ::= {er1645v2EthPrtSwF2BwEntry 4071489536}

er1645v2EthPrtSwF2BwActEirActNone OBJECT-TYPE
   SYNTAX      OCTET STRING
   MAX-ACCESS  read-write
   STATUS      current
   DESCRIPTION
      "Path: swPort.editConf.bandwidth.action.eirAction.none"
   ::= {er1645v2EthPrtSwF2BwEntry 4095737856}

er1645v2EthPrtSwF2BwActEirActEthCos1 OBJECT-TYPE
   SYNTAX      INTEGER
               {
               unchanged (256)
               }
   MAX-ACCESS  read-write
   STATUS      current
   DESCRIPTION
      "Path: swPort.editConf.bandwidth.action.eirAction.ethernet.cosDepth1

       Possibilities:
               unchanged   (256)"
   ::= {er1645v2EthPrtSwF2BwEntry 4097900544}

er1645v2EthPrtSwF2BwActEirActEthDei1 OBJECT-TYPE
   SYNTAX      INTEGER
               {
               unchanged (255),
               clear (0),
               set (1)
               }
   MAX-ACCESS  read-write
   STATUS      current
   DESCRIPTION
      "Path: swPort.editConf.bandwidth.action.eirAction.ethernet.deiDepth1

       Possibilities:
               unchanged   (255)
               clear   (0)
               set   (1)"
   ::= {er1645v2EthPrtSwF2BwEntry 4099211264}

er1645v2EthPrtSwF2BwActEirActEthCos2 OBJECT-TYPE
   SYNTAX      INTEGER
               {
               unchanged (256)
               }
   MAX-ACCESS  read-write
   STATUS      current
   DESCRIPTION
      "Path: swPort.editConf.bandwidth.action.eirAction.ethernet.cosDepth2

       Possibilities:
               unchanged   (256)"
   ::= {er1645v2EthPrtSwF2BwEntry 4097966080}

er1645v2EthPrtSwF2BwActEirActEthDei2 OBJECT-TYPE
   SYNTAX      INTEGER
               {
               unchanged (255),
               clear (0),
               set (1)
               }
   MAX-ACCESS  read-write
   STATUS      current
   DESCRIPTION
      "Path: swPort.editConf.bandwidth.action.eirAction.ethernet.deiDepth2

       Possibilities:
               unchanged   (255)
               clear   (0)
               set   (1)"
   ::= {er1645v2EthPrtSwF2BwEntry 4099276800}

er1645v2EthPrtSwF2BwActEirActEthCos3 OBJECT-TYPE
   SYNTAX      INTEGER
               {
               unchanged (256)
               }
   MAX-ACCESS  read-write
   STATUS      current
   DESCRIPTION
      "Path: swPort.editConf.bandwidth.action.eirAction.ethernet.cosDepth3

       Possibilities:
               unchanged   (256)"
   ::= {er1645v2EthPrtSwF2BwEntry 4098031616}

er1645v2EthPrtSwF2BwActEirActEthDei3 OBJECT-TYPE
   SYNTAX      INTEGER
               {
               unchanged (255),
               clear (0),
               set (1)
               }
   MAX-ACCESS  read-write
   STATUS      current
   DESCRIPTION
      "Path: swPort.editConf.bandwidth.action.eirAction.ethernet.deiDepth3

       Possibilities:
               unchanged   (255)
               clear   (0)
               set   (1)"
   ::= {er1645v2EthPrtSwF2BwEntry 4099342336}

er1645v2EthPrtSwF2BwActEirActEthCos4 OBJECT-TYPE
   SYNTAX      INTEGER
               {
               unchanged (256)
               }
   MAX-ACCESS  read-write
   STATUS      current
   DESCRIPTION
      "Path: swPort.editConf.bandwidth.action.eirAction.ethernet.cosDepth4

       Possibilities:
               unchanged   (256)"
   ::= {er1645v2EthPrtSwF2BwEntry 4098097152}

er1645v2EthPrtSwF2BwActEirActEthDei4 OBJECT-TYPE
   SYNTAX      INTEGER
               {
               unchanged (255),
               clear (0),
               set (1)
               }
   MAX-ACCESS  read-write
   STATUS      current
   DESCRIPTION
      "Path: swPort.editConf.bandwidth.action.eirAction.ethernet.deiDepth4

       Possibilities:
               unchanged   (255)
               clear   (0)
               set   (1)"
   ::= {er1645v2EthPrtSwF2BwEntry 4099407872}

er1645v2EthPrtSwF2BwActEirActEthCos5 OBJECT-TYPE
   SYNTAX      INTEGER
               {
               unchanged (256)
               }
   MAX-ACCESS  read-write
   STATUS      current
   DESCRIPTION
      "Path: swPort.editConf.bandwidth.action.eirAction.ethernet.cosDepth5

       Possibilities:
               unchanged   (256)"
   ::= {er1645v2EthPrtSwF2BwEntry 4098162688}

er1645v2EthPrtSwF2BwActEirActEthDei5 OBJECT-TYPE
   SYNTAX      INTEGER
               {
               unchanged (255),
               clear (0),
               set (1)
               }
   MAX-ACCESS  read-write
   STATUS      current
   DESCRIPTION
      "Path: swPort.editConf.bandwidth.action.eirAction.ethernet.deiDepth5

       Possibilities:
               unchanged   (255)
               clear   (0)
               set   (1)"
   ::= {er1645v2EthPrtSwF2BwEntry 4099473408}

er1645v2EthPrtSwF2BwActEirActEthCos6 OBJECT-TYPE
   SYNTAX      INTEGER
               {
               unchanged (256)
               }
   MAX-ACCESS  read-write
   STATUS      current
   DESCRIPTION
      "Path: swPort.editConf.bandwidth.action.eirAction.ethernet.cosDepth6

       Possibilities:
               unchanged   (256)"
   ::= {er1645v2EthPrtSwF2BwEntry 4098228224}

er1645v2EthPrtSwF2BwActEirActEthDei6 OBJECT-TYPE
   SYNTAX      INTEGER
               {
               unchanged (255),
               clear (0),
               set (1)
               }
   MAX-ACCESS  read-write
   STATUS      current
   DESCRIPTION
      "Path: swPort.editConf.bandwidth.action.eirAction.ethernet.deiDepth6

       Possibilities:
               unchanged   (255)
               clear   (0)
               set   (1)"
   ::= {er1645v2EthPrtSwF2BwEntry 4099538944}

er1645v2EthPrtSwF2BwActEirActEthCos7 OBJECT-TYPE
   SYNTAX      INTEGER
               {
               unchanged (256)
               }
   MAX-ACCESS  read-write
   STATUS      current
   DESCRIPTION
      "Path: swPort.editConf.bandwidth.action.eirAction.ethernet.cosDepth7

       Possibilities:
               unchanged   (256)"
   ::= {er1645v2EthPrtSwF2BwEntry 4098293760}

er1645v2EthPrtSwF2BwActEirActEthDei7 OBJECT-TYPE
   SYNTAX      INTEGER
               {
               unchanged (255),
               clear (0),
               set (1)
               }
   MAX-ACCESS  read-write
   STATUS      current
   DESCRIPTION
      "Path: swPort.editConf.bandwidth.action.eirAction.ethernet.deiDepth7

       Possibilities:
               unchanged   (255)
               clear   (0)
               set   (1)"
   ::= {er1645v2EthPrtSwF2BwEntry 4099604480}

er1645v2EthPrtSwF2BwActEirActEthCos8 OBJECT-TYPE
   SYNTAX      INTEGER
               {
               unchanged (256)
               }
   MAX-ACCESS  read-write
   STATUS      current
   DESCRIPTION
      "Path: swPort.editConf.bandwidth.action.eirAction.ethernet.cosDepth8

       Possibilities:
               unchanged   (256)"
   ::= {er1645v2EthPrtSwF2BwEntry 4098359296}

er1645v2EthPrtSwF2BwActEirActEthDei8 OBJECT-TYPE
   SYNTAX      INTEGER
               {
               unchanged (255),
               clear (0),
               set (1)
               }
   MAX-ACCESS  read-write
   STATUS      current
   DESCRIPTION
      "Path: swPort.editConf.bandwidth.action.eirAction.ethernet.deiDepth8

       Possibilities:
               unchanged   (255)
               clear   (0)
               set   (1)"
   ::= {er1645v2EthPrtSwF2BwEntry 4099670016}

er1645v2EthPrtSwF2BwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPrtSwF2BwEntry 4098424832}

er1645v2EthPrtSwF2BwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2EthPrtSwF2BwEntry 4098490368}

er1645v2EthPrtSwF2BwActEirActEthDrpLev OBJECT-TYPE
   SYNTAX      INTEGER
               {
               unchanged (0)
               }
   MAX-ACCESS  read-write
   STATUS      current
   DESCRIPTION
      "Path: swPort.editConf.bandwidth.action.eirAction.ethernet.dropLevel

       Possibilities:
               unchanged   (0)"
   ::= {er1645v2EthPrtSwF2BwEntry 4098555904}

er1645v2EthPrtSwF2BwActEirActEthDeFlag OBJECT-TYPE
   SYNTAX      INTEGER
               {
               unchanged (255),
               clear (0),
               set (1)
               }
   MAX-ACCESS  read-write
   STATUS      current
   DESCRIPTION
      "Path: swPort.editConf.bandwidth.action.eirAction.ethernet.deFlag

       Possibilities:
               unchanged   (255)
               clear   (0)
               set   (1)"
   ::= {er1645v2EthPrtSwF2BwEntry 4098752512}

er1645v2EthPrtSwF2BwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPrtSwF2BwEntry 4104716288}

er1645v2EthPrtSwF2BwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2EthPrtSwF2BwEntry 4104781824}

er1645v2EthPrtSwF2BwActEirActIpDrpLev OBJECT-TYPE
   SYNTAX      INTEGER
               {
               unchanged (0)
               }
   MAX-ACCESS  read-write
   STATUS      current
   DESCRIPTION
      "Path: swPort.editConf.bandwidth.action.eirAction.ip.dropLevel

       Possibilities:
               unchanged   (0)"
   ::= {er1645v2EthPrtSwF2BwEntry 4104847360}

er1645v2EthPrtSwF2BwActEirActIpDeFlag OBJECT-TYPE
   SYNTAX      INTEGER
               {
               unchanged (255),
               clear (0),
               set (1)
               }
   MAX-ACCESS  read-write
   STATUS      current
   DESCRIPTION
      "Path: swPort.editConf.bandwidth.action.eirAction.ip.deFlag

       Possibilities:
               unchanged   (255)
               clear   (0)
               set   (1)"
   ::= {er1645v2EthPrtSwF2BwEntry 4105043968}

er1645v2EthPrtSwF2BwActViolActNone OBJECT-TYPE
   SYNTAX      OCTET STRING
   MAX-ACCESS  read-write
   STATUS      current
   DESCRIPTION
      "Path: swPort.editConf.bandwidth.action.violateAction.none"
   ::= {er1645v2EthPrtSwF2BwEntry 4129292288}

er1645v2EthPrtSwF2BwActViolActDrop OBJECT-TYPE
   SYNTAX      OCTET STRING
   MAX-ACCESS  read-write
   STATUS      current
   DESCRIPTION
      "Path: swPort.editConf.bandwidth.action.violateAction.drop"
   ::= {er1645v2EthPrtSwF2BwEntry 4133486592}

er1645v2EthPrtSwF2BwActViolActEthCos1 OBJECT-TYPE
   SYNTAX      INTEGER
               {
               unchanged (256)
               }
   MAX-ACCESS  read-write
   STATUS      current
   DESCRIPTION
      "Path: swPort.editConf.bandwidth.action.violateAction.ethernet.cosDepth1

       Possibilities:
               unchanged   (256)"
   ::= {er1645v2EthPrtSwF2BwEntry 4131454976}

er1645v2EthPrtSwF2BwActViolActEthDei1 OBJECT-TYPE
   SYNTAX      INTEGER
               {
               unchanged (255),
               clear (0),
               set (1)
               }
   MAX-ACCESS  read-write
   STATUS      current
   DESCRIPTION
      "Path: swPort.editConf.bandwidth.action.violateAction.ethernet.deiDepth1

       Possibilities:
               unchanged   (255)
               clear   (0)
               set   (1)"
   ::= {er1645v2EthPrtSwF2BwEntry 4132765696}

er1645v2EthPrtSwF2BwActViolActEthCos2 OBJECT-TYPE
   SYNTAX      INTEGER
               {
               unchanged (256)
               }
   MAX-ACCESS  read-write
   STATUS      current
   DESCRIPTION
      "Path: swPort.editConf.bandwidth.action.violateAction.ethernet.cosDepth2

       Possibilities:
               unchanged   (256)"
   ::= {er1645v2EthPrtSwF2BwEntry 4131520512}

er1645v2EthPrtSwF2BwActViolActEthDei2 OBJECT-TYPE
   SYNTAX      INTEGER
               {
               unchanged (255),
               clear (0),
               set (1)
               }
   MAX-ACCESS  read-write
   STATUS      current
   DESCRIPTION
      "Path: swPort.editConf.bandwidth.action.violateAction.ethernet.deiDepth2

       Possibilities:
               unchanged   (255)
               clear   (0)
               set   (1)"
   ::= {er1645v2EthPrtSwF2BwEntry 4132831232}

er1645v2EthPrtSwF2BwActViolActEthCos3 OBJECT-TYPE
   SYNTAX      INTEGER
               {
               unchanged (256)
               }
   MAX-ACCESS  read-write
   STATUS      current
   DESCRIPTION
      "Path: swPort.editConf.bandwidth.action.violateAction.ethernet.cosDepth3

       Possibilities:
               unchanged   (256)"
   ::= {er1645v2EthPrtSwF2BwEntry 4131586048}

er1645v2EthPrtSwF2BwActViolActEthDei3 OBJECT-TYPE
   SYNTAX      INTEGER
               {
               unchanged (255),
               clear (0),
               set (1)
               }
   MAX-ACCESS  read-write
   STATUS      current
   DESCRIPTION
      "Path: swPort.editConf.bandwidth.action.violateAction.ethernet.deiDepth3

       Possibilities:
               unchanged   (255)
               clear   (0)
               set   (1)"
   ::= {er1645v2EthPrtSwF2BwEntry 4132896768}

er1645v2EthPrtSwF2BwActViolActEthCos4 OBJECT-TYPE
   SYNTAX      INTEGER
               {
               unchanged (256)
               }
   MAX-ACCESS  read-write
   STATUS      current
   DESCRIPTION
      "Path: swPort.editConf.bandwidth.action.violateAction.ethernet.cosDepth4

       Possibilities:
               unchanged   (256)"
   ::= {er1645v2EthPrtSwF2BwEntry 4131651584}

er1645v2EthPrtSwF2BwActViolActEthDei4 OBJECT-TYPE
   SYNTAX      INTEGER
               {
               unchanged (255),
               clear (0),
               set (1)
               }
   MAX-ACCESS  read-write
   STATUS      current
   DESCRIPTION
      "Path: swPort.editConf.bandwidth.action.violateAction.ethernet.deiDepth4

       Possibilities:
               unchanged   (255)
               clear   (0)
               set   (1)"
   ::= {er1645v2EthPrtSwF2BwEntry 4132962304}

er1645v2EthPrtSwF2BwActViolActEthCos5 OBJECT-TYPE
   SYNTAX      INTEGER
               {
               unchanged (256)
               }
   MAX-ACCESS  read-write
   STATUS      current
   DESCRIPTION
      "Path: swPort.editConf.bandwidth.action.violateAction.ethernet.cosDepth5

       Possibilities:
               unchanged   (256)"
   ::= {er1645v2EthPrtSwF2BwEntry 4131717120}

er1645v2EthPrtSwF2BwActViolActEthDei5 OBJECT-TYPE
   SYNTAX      INTEGER
               {
               unchanged (255),
               clear (0),
               set (1)
               }
   MAX-ACCESS  read-write
   STATUS      current
   DESCRIPTION
      "Path: swPort.editConf.bandwidth.action.violateAction.ethernet.deiDepth5

       Possibilities:
               unchanged   (255)
               clear   (0)
               set   (1)"
   ::= {er1645v2EthPrtSwF2BwEntry 4133027840}

er1645v2EthPrtSwF2BwActViolActEthCos6 OBJECT-TYPE
   SYNTAX      INTEGER
               {
               unchanged (256)
               }
   MAX-ACCESS  read-write
   STATUS      current
   DESCRIPTION
      "Path: swPort.editConf.bandwidth.action.violateAction.ethernet.cosDepth6

       Possibilities:
               unchanged   (256)"
   ::= {er1645v2EthPrtSwF2BwEntry 4131782656}

er1645v2EthPrtSwF2BwActViolActEthDei6 OBJECT-TYPE
   SYNTAX      INTEGER
               {
               unchanged (255),
               clear (0),
               set (1)
               }
   MAX-ACCESS  read-write
   STATUS      current
   DESCRIPTION
      "Path: swPort.editConf.bandwidth.action.violateAction.ethernet.deiDepth6

       Possibilities:
               unchanged   (255)
               clear   (0)
               set   (1)"
   ::= {er1645v2EthPrtSwF2BwEntry 4133093376}

er1645v2EthPrtSwF2BwActViolActEthCos7 OBJECT-TYPE
   SYNTAX      INTEGER
               {
               unchanged (256)
               }
   MAX-ACCESS  read-write
   STATUS      current
   DESCRIPTION
      "Path: swPort.editConf.bandwidth.action.violateAction.ethernet.cosDepth7

       Possibilities:
               unchanged   (256)"
   ::= {er1645v2EthPrtSwF2BwEntry 4131848192}

er1645v2EthPrtSwF2BwActViolActEthDei7 OBJECT-TYPE
   SYNTAX      INTEGER
               {
               unchanged (255),
               clear (0),
               set (1)
               }
   MAX-ACCESS  read-write
   STATUS      current
   DESCRIPTION
      "Path: swPort.editConf.bandwidth.action.violateAction.ethernet.deiDepth7

       Possibilities:
               unchanged   (255)
               clear   (0)
               set   (1)"
   ::= {er1645v2EthPrtSwF2BwEntry 4133158912}

er1645v2EthPrtSwF2BwActViolActEthCos8 OBJECT-TYPE
   SYNTAX      INTEGER
               {
               unchanged (256)
               }
   MAX-ACCESS  read-write
   STATUS      current
   DESCRIPTION
      "Path: swPort.editConf.bandwidth.action.violateAction.ethernet.cosDepth8

       Possibilities:
               unchanged   (256)"
   ::= {er1645v2EthPrtSwF2BwEntry 4131913728}

er1645v2EthPrtSwF2BwActViolActEthDei8 OBJECT-TYPE
   SYNTAX      INTEGER
               {
               unchanged (255),
               clear (0),
               set (1)
               }
   MAX-ACCESS  read-write
   STATUS      current
   DESCRIPTION
      "Path: swPort.editConf.bandwidth.action.violateAction.ethernet.deiDepth8

       Possibilities:
               unchanged   (255)
               clear   (0)
               set   (1)"
   ::= {er1645v2EthPrtSwF2BwEntry 4133224448}

er1645v2EthPrtSwF2BwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPrtSwF2BwEntry 4131979264}

er1645v2EthPrtSwF2BwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2EthPrtSwF2BwEntry 4132044800}

er1645v2EthPrtSwF2BwActViolActEthDrpLev OBJECT-TYPE
   SYNTAX      INTEGER
               {
               unchanged (0)
               }
   MAX-ACCESS  read-write
   STATUS      current
   DESCRIPTION
      "Path: swPort.editConf.bandwidth.action.violateAction.ethernet.dropLevel

       Possibilities:
               unchanged   (0)"
   ::= {er1645v2EthPrtSwF2BwEntry 4132110336}

er1645v2EthPrtSwF2BwActViolActEthDeFlag OBJECT-TYPE
   SYNTAX      INTEGER
               {
               unchanged (255),
               clear (0),
               set (1)
               }
   MAX-ACCESS  read-write
   STATUS      current
   DESCRIPTION
      "Path: swPort.editConf.bandwidth.action.violateAction.ethernet.deFlag

       Possibilities:
               unchanged   (255)
               clear   (0)
               set   (1)"
   ::= {er1645v2EthPrtSwF2BwEntry 4132306944}

er1645v2EthPrtSwF2BwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPrtSwF2BwEntry 4138270720}

er1645v2EthPrtSwF2BwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2EthPrtSwF2BwEntry 4138336256}

er1645v2EthPrtSwF2BwActViolActIpDrpLev OBJECT-TYPE
   SYNTAX      INTEGER
               {
               unchanged (0)
               }
   MAX-ACCESS  read-write
   STATUS      current
   DESCRIPTION
      "Path: swPort.editConf.bandwidth.action.violateAction.ip.dropLevel

       Possibilities:
               unchanged   (0)"
   ::= {er1645v2EthPrtSwF2BwEntry 4138401792}

er1645v2EthPrtSwF2BwActViolActIpDeFlag OBJECT-TYPE
   SYNTAX      INTEGER
               {
               unchanged (255),
               clear (0),
               set (1)
               }
   MAX-ACCESS  read-write
   STATUS      current
   DESCRIPTION
      "Path: swPort.editConf.bandwidth.action.violateAction.ip.deFlag

       Possibilities:
               unchanged   (255)
               clear   (0)
               set   (1)"
   ::= {er1645v2EthPrtSwF2BwEntry 4138598400}


er1645v2EthPrtSwF2Ibw OBJECT IDENTIFIER ::= {er1645v2EthPrtSwF2 13}

er1645v2EthPrtSwF2IbwSSCTable OBJECT-TYPE
   SYNTAX      SEQUENCE OF Er1645v2EthPrtSwF2IbwEntry
   MAX-ACCESS  not-accessible
   STATUS      current
   DESCRIPTION
      ""
   ::= {er1645v2EthPrtSwF2Ibw 1}

er1645v2EthPrtSwF2IbwEntry OBJECT-TYPE
   SYNTAX      Er1645v2EthPrtSwF2IbwEntry
   MAX-ACCESS  not-accessible
   STATUS      current
   DESCRIPTION
      ""
   INDEX      { er1645v2EthPrtSwF2IbwGlobalIx }
   ::= {er1645v2EthPrtSwF2IbwSSCTable 1}

Er1645v2EthPrtSwF2IbwEntry ::=
   SEQUENCE
      {
      er1645v2EthPrtSwF2IbwGlobalIx
         GlobalIndex,
      er1645v2EthPrtSwF2IbwMode
         INTEGER,
      er1645v2EthPrtSwF2IbwCir
         Integer32,
      er1645v2EthPrtSwF2IbwEir
         Integer32,
      er1645v2EthPrtSwF2IbwUnit
         INTEGER,
      er1645v2EthPrtSwF2IbwTc
         INTEGER,
      er1645v2EthPrtSwF2IbwTcFactor
         INTEGER,
      er1645v2EthPrtSwF2IbwCorrType
         INTEGER,
      er1645v2EthPrtSwF2IbwCorrPredefEncapsFrameRelay
         DisplayString,
      er1645v2EthPrtSwF2IbwCorrPredefEncapsPpp
         DisplayString,
      er1645v2EthPrtSwF2IbwCorrPredefEncapsAtmHl
         INTEGER,
      er1645v2EthPrtSwF2IbwCorrPredefEncapsAtmMp
         INTEGER,
      er1645v2EthPrtSwF2IbwCorrPredefEncapsHdlc
         DisplayString,
      er1645v2EthPrtSwF2IbwCorrPredefEncapsEfmFs
         Integer32,
      er1645v2EthPrtSwF2IbwCorrPredefEncapsEfmIb
         Integer32,
      er1645v2EthPrtSwF2IbwCorrPredefMode
         INTEGER,
      er1645v2EthPrtSwF2IbwCorrManualOverhead
         Integer32,
      er1645v2EthPrtSwF2IbwCorrManualFrameData
         Counter32,
      er1645v2EthPrtSwF2IbwCorrManualFrameHeader
         Counter32,
      er1645v2EthPrtSwF2IbwMaxFifoQLen
         Integer32,
      er1645v2EthPrtSwF2IbwPriorityPolicy
         DisplayString,
      er1645v2EthPrtSwF2IbwDeFlagCir
         INTEGER,
      er1645v2EthPrtSwF2IbwDeFlagEir
         INTEGER,
      er1645v2EthPrtSwF2IbwDeFlagViolate
         INTEGER,
      er1645v2EthPrtSwF2IbwActCirActNone
         OCTET STRING,
      er1645v2EthPrtSwF2IbwActCirActEthCos1
         INTEGER,
      er1645v2EthPrtSwF2IbwActCirActEthDei1
         INTEGER,
      er1645v2EthPrtSwF2IbwActCirActEthCos2
         INTEGER,
      er1645v2EthPrtSwF2IbwActCirActEthDei2
         INTEGER,
      er1645v2EthPrtSwF2IbwActCirActEthCos3
         INTEGER,
      er1645v2EthPrtSwF2IbwActCirActEthDei3
         INTEGER,
      er1645v2EthPrtSwF2IbwActCirActEthCos4
         INTEGER,
      er1645v2EthPrtSwF2IbwActCirActEthDei4
         INTEGER,
      er1645v2EthPrtSwF2IbwActCirActEthCos5
         INTEGER,
      er1645v2EthPrtSwF2IbwActCirActEthDei5
         INTEGER,
      er1645v2EthPrtSwF2IbwActCirActEthCos6
         INTEGER,
      er1645v2EthPrtSwF2IbwActCirActEthDei6
         INTEGER,
      er1645v2EthPrtSwF2IbwActCirActEthCos7
         INTEGER,
      er1645v2EthPrtSwF2IbwActCirActEthDei7
         INTEGER,
      er1645v2EthPrtSwF2IbwActCirActEthCos8
         INTEGER,
      er1645v2EthPrtSwF2IbwActCirActEthDei8
         INTEGER,
      er1645v2EthPrtSwF2IbwActCirActEthTos
         INTEGER,
      er1645v2EthPrtSwF2IbwActCirActEthQueue
         INTEGER,
      er1645v2EthPrtSwF2IbwActCirActEthDrpLev
         INTEGER,
      er1645v2EthPrtSwF2IbwActCirActEthDeFlag
         INTEGER,
      er1645v2EthPrtSwF2IbwActCirActIpTos
         INTEGER,
      er1645v2EthPrtSwF2IbwActCirActIpQueue
         INTEGER,
      er1645v2EthPrtSwF2IbwActCirActIpDrpLev
         INTEGER,
      er1645v2EthPrtSwF2IbwActCirActIpDeFlag
         INTEGER,
      er1645v2EthPrtSwF2IbwActEirActNone
         OCTET STRING,
      er1645v2EthPrtSwF2IbwActEirActEthCos1
         INTEGER,
      er1645v2EthPrtSwF2IbwActEirActEthDei1
         INTEGER,
      er1645v2EthPrtSwF2IbwActEirActEthCos2
         INTEGER,
      er1645v2EthPrtSwF2IbwActEirActEthDei2
         INTEGER,
      er1645v2EthPrtSwF2IbwActEirActEthCos3
         INTEGER,
      er1645v2EthPrtSwF2IbwActEirActEthDei3
         INTEGER,
      er1645v2EthPrtSwF2IbwActEirActEthCos4
         INTEGER,
      er1645v2EthPrtSwF2IbwActEirActEthDei4
         INTEGER,
      er1645v2EthPrtSwF2IbwActEirActEthCos5
         INTEGER,
      er1645v2EthPrtSwF2IbwActEirActEthDei5
         INTEGER,
      er1645v2EthPrtSwF2IbwActEirActEthCos6
         INTEGER,
      er1645v2EthPrtSwF2IbwActEirActEthDei6
         INTEGER,
      er1645v2EthPrtSwF2IbwActEirActEthCos7
         INTEGER,
      er1645v2EthPrtSwF2IbwActEirActEthDei7
         INTEGER,
      er1645v2EthPrtSwF2IbwActEirActEthCos8
         INTEGER,
      er1645v2EthPrtSwF2IbwActEirActEthDei8
         INTEGER,
      er1645v2EthPrtSwF2IbwActEirActEthTos
         INTEGER,
      er1645v2EthPrtSwF2IbwActEirActEthQueue
         INTEGER,
      er1645v2EthPrtSwF2IbwActEirActEthDrpLev
         INTEGER,
      er1645v2EthPrtSwF2IbwActEirActEthDeFlag
         INTEGER,
      er1645v2EthPrtSwF2IbwActEirActIpTos
         INTEGER,
      er1645v2EthPrtSwF2IbwActEirActIpQueue
         INTEGER,
      er1645v2EthPrtSwF2IbwActEirActIpDrpLev
         INTEGER,
      er1645v2EthPrtSwF2IbwActEirActIpDeFlag
         INTEGER,
      er1645v2EthPrtSwF2IbwActViolActNone
         OCTET STRING,
      er1645v2EthPrtSwF2IbwActViolActDrop
         OCTET STRING,
      er1645v2EthPrtSwF2IbwActViolActEthCos1
         INTEGER,
      er1645v2EthPrtSwF2IbwActViolActEthDei1
         INTEGER,
      er1645v2EthPrtSwF2IbwActViolActEthCos2
         INTEGER,
      er1645v2EthPrtSwF2IbwActViolActEthDei2
         INTEGER,
      er1645v2EthPrtSwF2IbwActViolActEthCos3
         INTEGER,
      er1645v2EthPrtSwF2IbwActViolActEthDei3
         INTEGER,
      er1645v2EthPrtSwF2IbwActViolActEthCos4
         INTEGER,
      er1645v2EthPrtSwF2IbwActViolActEthDei4
         INTEGER,
      er1645v2EthPrtSwF2IbwActViolActEthCos5
         INTEGER,
      er1645v2EthPrtSwF2IbwActViolActEthDei5
         INTEGER,
      er1645v2EthPrtSwF2IbwActViolActEthCos6
         INTEGER,
      er1645v2EthPrtSwF2IbwActViolActEthDei6
         INTEGER,
      er1645v2EthPrtSwF2IbwActViolActEthCos7
         INTEGER,
      er1645v2EthPrtSwF2IbwActViolActEthDei7
         INTEGER,
      er1645v2EthPrtSwF2IbwActViolActEthCos8
         INTEGER,
      er1645v2EthPrtSwF2IbwActViolActEthDei8
         INTEGER,
      er1645v2EthPrtSwF2IbwActViolActEthTos
         INTEGER,
      er1645v2EthPrtSwF2IbwActViolActEthQueue
         INTEGER,
      er1645v2EthPrtSwF2IbwActViolActEthDrpLev
         INTEGER,
      er1645v2EthPrtSwF2IbwActViolActEthDeFlag
         INTEGER,
      er1645v2EthPrtSwF2IbwActViolActIpTos
         INTEGER,
      er1645v2EthPrtSwF2IbwActViolActIpQueue
         INTEGER,
      er1645v2EthPrtSwF2IbwActViolActIpDrpLev
         INTEGER,
      er1645v2EthPrtSwF2IbwActViolActIpDeFlag
         INTEGER,
      er1645v2EthPrtSwF2IbwSubInterfacesExcluded
         INTEGER,
      er1645v2EthPrtSwF2IbwSubInterfacesIncludedInAccessList
         DisplayString
      }

er1645v2EthPrtSwF2IbwGlobalIx OBJECT-TYPE
   SYNTAX      GlobalIndex
   MAX-ACCESS  not-accessible
   STATUS      current
   DESCRIPTION
      "The value of the tlsCntTreeGlobalIndex of the MANAGED OBJECT."
   ::= {er1645v2EthPrtSwF2IbwEntry 10}

er1645v2EthPrtSwF2IbwMode OBJECT-TYPE
   SYNTAX      INTEGER
               {
               reshaping (1),
               policing (2)
               }
   MAX-ACCESS  read-write
   STATUS      current
   DESCRIPTION
      "Path: swPort.editConf.inboundBandwidth.mode

       Possibilities:
               reshaping   (1)
               policing   (2)"
   ::= {er1645v2EthPrtSwF2IbwEntry 3758096384}

er1645v2EthPrtSwF2IbwCir OBJECT-TYPE
   SYNTAX      Integer32
   MAX-ACCESS  read-write
   STATUS      current
   DESCRIPTION
      "Path: swPort.editConf.inboundBandwidth.cir"
   ::= {er1645v2EthPrtSwF2IbwEntry 268435456}

er1645v2EthPrtSwF2IbwEir OBJECT-TYPE
   SYNTAX      Integer32
   MAX-ACCESS  read-write
   STATUS      current
   DESCRIPTION
      "Path: swPort.editConf.inboundBandwidth.eir"
   ::= {er1645v2EthPrtSwF2IbwEntry 1879048192}

er1645v2EthPrtSwF2IbwUnit OBJECT-TYPE
   SYNTAX      INTEGER
               {
               bitssec (1),
               percent (2)
               }
   MAX-ACCESS  read-write
   STATUS      current
   DESCRIPTION
      "Path: swPort.editConf.inboundBandwidth.unit

       Possibilities:
               bits/sec   (1)
               percent   (2)"
   ::= {er1645v2EthPrtSwF2IbwEntry 1342177280}

er1645v2EthPrtSwF2IbwTc OBJECT-TYPE
   SYNTAX      INTEGER
               {
               auto (0)
               }
   MAX-ACCESS  read-write
   STATUS      current
   DESCRIPTION
      "Path: swPort.editConf.inboundBandwidth.tc

       Possibilities:
               auto   (0)"
   ::= {er1645v2EthPrtSwF2IbwEntry 1610612736}

er1645v2EthPrtSwF2IbwTcFactor OBJECT-TYPE
   SYNTAX      INTEGER
               {
               ms (10),
               s100us (1)
               }
   MAX-ACCESS  read-write
   STATUS      current
   DESCRIPTION
      "Path: swPort.editConf.inboundBandwidth.tcFactor

       Possibilities:
               ms   (10)
               *100us   (1)"
   ::= {er1645v2EthPrtSwF2IbwEntry 2147483648}

er1645v2EthPrtSwF2IbwCorrType OBJECT-TYPE
   SYNTAX      INTEGER
               {
               noCorrection (0),
               predefined (1),
               manual (2)
               }
   MAX-ACCESS  read-write
   STATUS      current
   DESCRIPTION
      "Path: swPort.editConf.inboundBandwidth.correction.type

       Possibilities:
               noCorrection   (0)
               predefined   (1)
               manual   (2)"
   ::= {er1645v2EthPrtSwF2IbwEntry 570425344}

er1645v2EthPrtSwF2IbwCorrPredefEncapsFrameRelay OBJECT-TYPE
   SYNTAX      DisplayString
   MAX-ACCESS  read-write
   STATUS      current
   DESCRIPTION
      "Path: swPort.editConf.inboundBandwidth.correction.predefined.encapsulation.frameRelay"
   ::= {er1645v2EthPrtSwF2IbwEntry 608436224}

er1645v2EthPrtSwF2IbwCorrPredefEncapsPpp OBJECT-TYPE
   SYNTAX      DisplayString
   MAX-ACCESS  read-write
   STATUS      current
   DESCRIPTION
      "Path: swPort.editConf.inboundBandwidth.correction.predefined.encapsulation.ppp"
   ::= {er1645v2EthPrtSwF2IbwEntry 608698368}

er1645v2EthPrtSwF2IbwCorrPredefEncapsAtmHl OBJECT-TYPE
   SYNTAX      INTEGER
               {
               rfc2684 (0),
               ppp (1),
               pppOverEthernet (2)
               }
   MAX-ACCESS  read-write
   STATUS      current
   DESCRIPTION
      "Path: swPort.editConf.inboundBandwidth.correction.predefined.encapsulation.atm.higherLayer

       Possibilities:
               rfc2684   (0)
               ppp   (1)
               pppOverEthernet   (2)"
   ::= {er1645v2EthPrtSwF2IbwEntry 608993280}

er1645v2EthPrtSwF2IbwCorrPredefEncapsAtmMp OBJECT-TYPE
   SYNTAX      INTEGER
               {
               llcEncapsulation (0),
               vcMultiplexing (1)
               }
   MAX-ACCESS  read-write
   STATUS      current
   DESCRIPTION
      "Path: swPort.editConf.inboundBandwidth.correction.predefined.encapsulation.atm.multiProtocol

       Possibilities:
               llcEncapsulation   (0)
               vcMultiplexing   (1)"
   ::= {er1645v2EthPrtSwF2IbwEntry 609026048}

er1645v2EthPrtSwF2IbwCorrPredefEncapsHdlc OBJECT-TYPE
   SYNTAX      DisplayString
   MAX-ACCESS  read-write
   STATUS      current
   DESCRIPTION
      "Path: swPort.editConf.inboundBandwidth.correction.predefined.encapsulation.hdlc"
   ::= {er1645v2EthPrtSwF2IbwEntry 609222656}

er1645v2EthPrtSwF2IbwCorrPredefEncapsEfmFs OBJECT-TYPE
   SYNTAX      Integer32
   MAX-ACCESS  read-write
   STATUS      current
   DESCRIPTION
      "Path: swPort.editConf.inboundBandwidth.correction.predefined.encapsulation.efm.fragmentSize"
   ::= {er1645v2EthPrtSwF2IbwEntry 609517568}

er1645v2EthPrtSwF2IbwCorrPredefEncapsEfmIb OBJECT-TYPE
   SYNTAX      Integer32
   MAX-ACCESS  read-write
   STATUS      current
   DESCRIPTION
      "Path: swPort.editConf.inboundBandwidth.correction.predefined.encapsulation.efm.idleBytes"
   ::= {er1645v2EthPrtSwF2IbwEntry 609550336}

er1645v2EthPrtSwF2IbwCorrPredefMode OBJECT-TYPE
   SYNTAX      INTEGER
               {
               routing (0),
               bridging (1)
               }
   MAX-ACCESS  read-write
   STATUS      current
   DESCRIPTION
      "Path: swPort.editConf.inboundBandwidth.correction.predefined.mode

       Possibilities:
               routing   (0)
               bridging   (1)"
   ::= {er1645v2EthPrtSwF2IbwEntry 612368384}

er1645v2EthPrtSwF2IbwCorrManualOverhead OBJECT-TYPE
   SYNTAX      Integer32
   MAX-ACCESS  read-write
   STATUS      current
   DESCRIPTION
      "Path: swPort.editConf.inboundBandwidth.correction.manual.overhead"
   ::= {er1645v2EthPrtSwF2IbwEntry 637665280}

er1645v2EthPrtSwF2IbwCorrManualFrameData OBJECT-TYPE
   SYNTAX      Counter32
   MAX-ACCESS  read-write
   STATUS      current
   DESCRIPTION
      "Path: swPort.editConf.inboundBandwidth.correction.manual.frameData

       32 bit unsigned wrappable counter."
   ::= {er1645v2EthPrtSwF2IbwEntry 637796352}

er1645v2EthPrtSwF2IbwCorrManualFrameHeader OBJECT-TYPE
   SYNTAX      Counter32
   MAX-ACCESS  read-write
   STATUS      current
   DESCRIPTION
      "Path: swPort.editConf.inboundBandwidth.correction.manual.frameHeader

       32 bit unsigned wrappable counter."
   ::= {er1645v2EthPrtSwF2IbwEntry 637927424}

er1645v2EthPrtSwF2IbwMaxFifoQLen OBJECT-TYPE
   SYNTAX      Integer32
   MAX-ACCESS  read-write
   STATUS      current
   DESCRIPTION
      "Path: swPort.editConf.inboundBandwidth.maxFifoQLen"
   ::= {er1645v2EthPrtSwF2IbwEntry 805306368}

er1645v2EthPrtSwF2IbwPriorityPolicy OBJECT-TYPE
   SYNTAX      DisplayString
   MAX-ACCESS  read-write
   STATUS      current
   DESCRIPTION
      "Path: swPort.editConf.inboundBandwidth.priorityPolicy"
   ::= {er1645v2EthPrtSwF2IbwEntry 1073741824}

er1645v2EthPrtSwF2IbwDeFlagCir OBJECT-TYPE
   SYNTAX      INTEGER
               {
               allowed (1),
               notAllowed (2)
               }
   MAX-ACCESS  read-write
   STATUS      current
   DESCRIPTION
      "Path: swPort.editConf.inboundBandwidth.deFlag.cir

       Possibilities:
               allowed   (1)
               notAllowed   (2)"
   ::= {er1645v2EthPrtSwF2IbwEntry 3490709504}

er1645v2EthPrtSwF2IbwDeFlagEir OBJECT-TYPE
   SYNTAX      INTEGER
               {
               allowed (1),
               notAllowed (2)
               }
   MAX-ACCESS  read-write
   STATUS      current
   DESCRIPTION
      "Path: swPort.editConf.inboundBandwidth.deFlag.eir

       Possibilities:
               allowed   (1)
               notAllowed   (2)"
   ::= {er1645v2EthPrtSwF2IbwEntry 3491758080}

er1645v2EthPrtSwF2IbwDeFlagViolate OBJECT-TYPE
   SYNTAX      INTEGER
               {
               allowed (1),
               notAllowed (2)
               }
   MAX-ACCESS  read-write
   STATUS      current
   DESCRIPTION
      "Path: swPort.editConf.inboundBandwidth.deFlag.violate

       Possibilities:
               allowed   (1)
               notAllowed   (2)"
   ::= {er1645v2EthPrtSwF2IbwEntry 3492806656}

er1645v2EthPrtSwF2IbwActCirActNone OBJECT-TYPE
   SYNTAX      OCTET STRING
   MAX-ACCESS  read-write
   STATUS      current
   DESCRIPTION
      "Path: swPort.editConf.inboundBandwidth.action.cirAction.none"
   ::= {er1645v2EthPrtSwF2IbwEntry 4062183424}

er1645v2EthPrtSwF2IbwActCirActEthCos1 OBJECT-TYPE
   SYNTAX      INTEGER
               {
               unchanged (256)
               }
   MAX-ACCESS  read-write
   STATUS      current
   DESCRIPTION
      "Path: swPort.editConf.inboundBandwidth.action.cirAction.ethernet.cosDepth1

       Possibilities:
               unchanged   (256)"
   ::= {er1645v2EthPrtSwF2IbwEntry 4064346112}

er1645v2EthPrtSwF2IbwActCirActEthDei1 OBJECT-TYPE
   SYNTAX      INTEGER
               {
               unchanged (255),
               clear (0),
               set (1)
               }
   MAX-ACCESS  read-write
   STATUS      current
   DESCRIPTION
      "Path: swPort.editConf.inboundBandwidth.action.cirAction.ethernet.deiDepth1

       Possibilities:
               unchanged   (255)
               clear   (0)
               set   (1)"
   ::= {er1645v2EthPrtSwF2IbwEntry 4065656832}

er1645v2EthPrtSwF2IbwActCirActEthCos2 OBJECT-TYPE
   SYNTAX      INTEGER
               {
               unchanged (256)
               }
   MAX-ACCESS  read-write
   STATUS      current
   DESCRIPTION
      "Path: swPort.editConf.inboundBandwidth.action.cirAction.ethernet.cosDepth2

       Possibilities:
               unchanged   (256)"
   ::= {er1645v2EthPrtSwF2IbwEntry 4064411648}

er1645v2EthPrtSwF2IbwActCirActEthDei2 OBJECT-TYPE
   SYNTAX      INTEGER
               {
               unchanged (255),
               clear (0),
               set (1)
               }
   MAX-ACCESS  read-write
   STATUS      current
   DESCRIPTION
      "Path: swPort.editConf.inboundBandwidth.action.cirAction.ethernet.deiDepth2

       Possibilities:
               unchanged   (255)
               clear   (0)
               set   (1)"
   ::= {er1645v2EthPrtSwF2IbwEntry 4065722368}

er1645v2EthPrtSwF2IbwActCirActEthCos3 OBJECT-TYPE
   SYNTAX      INTEGER
               {
               unchanged (256)
               }
   MAX-ACCESS  read-write
   STATUS      current
   DESCRIPTION
      "Path: swPort.editConf.inboundBandwidth.action.cirAction.ethernet.cosDepth3

       Possibilities:
               unchanged   (256)"
   ::= {er1645v2EthPrtSwF2IbwEntry 4064477184}

er1645v2EthPrtSwF2IbwActCirActEthDei3 OBJECT-TYPE
   SYNTAX      INTEGER
               {
               unchanged (255),
               clear (0),
               set (1)
               }
   MAX-ACCESS  read-write
   STATUS      current
   DESCRIPTION
      "Path: swPort.editConf.inboundBandwidth.action.cirAction.ethernet.deiDepth3

       Possibilities:
               unchanged   (255)
               clear   (0)
               set   (1)"
   ::= {er1645v2EthPrtSwF2IbwEntry 4065787904}

er1645v2EthPrtSwF2IbwActCirActEthCos4 OBJECT-TYPE
   SYNTAX      INTEGER
               {
               unchanged (256)
               }
   MAX-ACCESS  read-write
   STATUS      current
   DESCRIPTION
      "Path: swPort.editConf.inboundBandwidth.action.cirAction.ethernet.cosDepth4

       Possibilities:
               unchanged   (256)"
   ::= {er1645v2EthPrtSwF2IbwEntry 4064542720}

er1645v2EthPrtSwF2IbwActCirActEthDei4 OBJECT-TYPE
   SYNTAX      INTEGER
               {
               unchanged (255),
               clear (0),
               set (1)
               }
   MAX-ACCESS  read-write
   STATUS      current
   DESCRIPTION
      "Path: swPort.editConf.inboundBandwidth.action.cirAction.ethernet.deiDepth4

       Possibilities:
               unchanged   (255)
               clear   (0)
               set   (1)"
   ::= {er1645v2EthPrtSwF2IbwEntry 4065853440}

er1645v2EthPrtSwF2IbwActCirActEthCos5 OBJECT-TYPE
   SYNTAX      INTEGER
               {
               unchanged (256)
               }
   MAX-ACCESS  read-write
   STATUS      current
   DESCRIPTION
      "Path: swPort.editConf.inboundBandwidth.action.cirAction.ethernet.cosDepth5

       Possibilities:
               unchanged   (256)"
   ::= {er1645v2EthPrtSwF2IbwEntry 4064608256}

er1645v2EthPrtSwF2IbwActCirActEthDei5 OBJECT-TYPE
   SYNTAX      INTEGER
               {
               unchanged (255),
               clear (0),
               set (1)
               }
   MAX-ACCESS  read-write
   STATUS      current
   DESCRIPTION
      "Path: swPort.editConf.inboundBandwidth.action.cirAction.ethernet.deiDepth5

       Possibilities:
               unchanged   (255)
               clear   (0)
               set   (1)"
   ::= {er1645v2EthPrtSwF2IbwEntry 4065918976}

er1645v2EthPrtSwF2IbwActCirActEthCos6 OBJECT-TYPE
   SYNTAX      INTEGER
               {
               unchanged (256)
               }
   MAX-ACCESS  read-write
   STATUS      current
   DESCRIPTION
      "Path: swPort.editConf.inboundBandwidth.action.cirAction.ethernet.cosDepth6

       Possibilities:
               unchanged   (256)"
   ::= {er1645v2EthPrtSwF2IbwEntry 4064673792}

er1645v2EthPrtSwF2IbwActCirActEthDei6 OBJECT-TYPE
   SYNTAX      INTEGER
               {
               unchanged (255),
               clear (0),
               set (1)
               }
   MAX-ACCESS  read-write
   STATUS      current
   DESCRIPTION
      "Path: swPort.editConf.inboundBandwidth.action.cirAction.ethernet.deiDepth6

       Possibilities:
               unchanged   (255)
               clear   (0)
               set   (1)"
   ::= {er1645v2EthPrtSwF2IbwEntry 4065984512}

er1645v2EthPrtSwF2IbwActCirActEthCos7 OBJECT-TYPE
   SYNTAX      INTEGER
               {
               unchanged (256)
               }
   MAX-ACCESS  read-write
   STATUS      current
   DESCRIPTION
      "Path: swPort.editConf.inboundBandwidth.action.cirAction.ethernet.cosDepth7

       Possibilities:
               unchanged   (256)"
   ::= {er1645v2EthPrtSwF2IbwEntry 4064739328}

er1645v2EthPrtSwF2IbwActCirActEthDei7 OBJECT-TYPE
   SYNTAX      INTEGER
               {
               unchanged (255),
               clear (0),
               set (1)
               }
   MAX-ACCESS  read-write
   STATUS      current
   DESCRIPTION
      "Path: swPort.editConf.inboundBandwidth.action.cirAction.ethernet.deiDepth7

       Possibilities:
               unchanged   (255)
               clear   (0)
               set   (1)"
   ::= {er1645v2EthPrtSwF2IbwEntry 4066050048}

er1645v2EthPrtSwF2IbwActCirActEthCos8 OBJECT-TYPE
   SYNTAX      INTEGER
               {
               unchanged (256)
               }
   MAX-ACCESS  read-write
   STATUS      current
   DESCRIPTION
      "Path: swPort.editConf.inboundBandwidth.action.cirAction.ethernet.cosDepth8

       Possibilities:
               unchanged   (256)"
   ::= {er1645v2EthPrtSwF2IbwEntry 4064804864}

er1645v2EthPrtSwF2IbwActCirActEthDei8 OBJECT-TYPE
   SYNTAX      INTEGER
               {
               unchanged (255),
               clear (0),
               set (1)
               }
   MAX-ACCESS  read-write
   STATUS      current
   DESCRIPTION
      "Path: swPort.editConf.inboundBandwidth.action.cirAction.ethernet.deiDepth8

       Possibilities:
               unchanged   (255)
               clear   (0)
               set   (1)"
   ::= {er1645v2EthPrtSwF2IbwEntry 4066115584}

er1645v2EthPrtSwF2IbwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.inboundBandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPrtSwF2IbwEntry 4064870400}

er1645v2EthPrtSwF2IbwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.inboundBandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2EthPrtSwF2IbwEntry 4064935936}

er1645v2EthPrtSwF2IbwActCirActEthDrpLev OBJECT-TYPE
   SYNTAX      INTEGER
               {
               unchanged (0)
               }
   MAX-ACCESS  read-write
   STATUS      current
   DESCRIPTION
      "Path: swPort.editConf.inboundBandwidth.action.cirAction.ethernet.dropLevel

       Possibilities:
               unchanged   (0)"
   ::= {er1645v2EthPrtSwF2IbwEntry 4065001472}

er1645v2EthPrtSwF2IbwActCirActEthDeFlag OBJECT-TYPE
   SYNTAX      INTEGER
               {
               unchanged (255),
               clear (0),
               set (1)
               }
   MAX-ACCESS  read-write
   STATUS      current
   DESCRIPTION
      "Path: swPort.editConf.inboundBandwidth.action.cirAction.ethernet.deFlag

       Possibilities:
               unchanged   (255)
               clear   (0)
               set   (1)"
   ::= {er1645v2EthPrtSwF2IbwEntry 4065198080}

er1645v2EthPrtSwF2IbwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.inboundBandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPrtSwF2IbwEntry 4071161856}

er1645v2EthPrtSwF2IbwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.inboundBandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2EthPrtSwF2IbwEntry 4071227392}

er1645v2EthPrtSwF2IbwActCirActIpDrpLev OBJECT-TYPE
   SYNTAX      INTEGER
               {
               unchanged (0)
               }
   MAX-ACCESS  read-write
   STATUS      current
   DESCRIPTION
      "Path: swPort.editConf.inboundBandwidth.action.cirAction.ip.dropLevel

       Possibilities:
               unchanged   (0)"
   ::= {er1645v2EthPrtSwF2IbwEntry 4071292928}

er1645v2EthPrtSwF2IbwActCirActIpDeFlag OBJECT-TYPE
   SYNTAX      INTEGER
               {
               unchanged (255),
               clear (0),
               set (1)
               }
   MAX-ACCESS  read-write
   STATUS      current
   DESCRIPTION
      "Path: swPort.editConf.inboundBandwidth.action.cirAction.ip.deFlag

       Possibilities:
               unchanged   (255)
               clear   (0)
               set   (1)"
   ::= {er1645v2EthPrtSwF2IbwEntry 4071489536}

er1645v2EthPrtSwF2IbwActEirActNone OBJECT-TYPE
   SYNTAX      OCTET STRING
   MAX-ACCESS  read-write
   STATUS      current
   DESCRIPTION
      "Path: swPort.editConf.inboundBandwidth.action.eirAction.none"
   ::= {er1645v2EthPrtSwF2IbwEntry 4095737856}

er1645v2EthPrtSwF2IbwActEirActEthCos1 OBJECT-TYPE
   SYNTAX      INTEGER
               {
               unchanged (256)
               }
   MAX-ACCESS  read-write
   STATUS      current
   DESCRIPTION
      "Path: swPort.editConf.inboundBandwidth.action.eirAction.ethernet.cosDepth1

       Possibilities:
               unchanged   (256)"
   ::= {er1645v2EthPrtSwF2IbwEntry 4097900544}

er1645v2EthPrtSwF2IbwActEirActEthDei1 OBJECT-TYPE
   SYNTAX      INTEGER
               {
               unchanged (255),
               clear (0),
               set (1)
               }
   MAX-ACCESS  read-write
   STATUS      current
   DESCRIPTION
      "Path: swPort.editConf.inboundBandwidth.action.eirAction.ethernet.deiDepth1

       Possibilities:
               unchanged   (255)
               clear   (0)
               set   (1)"
   ::= {er1645v2EthPrtSwF2IbwEntry 4099211264}

er1645v2EthPrtSwF2IbwActEirActEthCos2 OBJECT-TYPE
   SYNTAX      INTEGER
               {
               unchanged (256)
               }
   MAX-ACCESS  read-write
   STATUS      current
   DESCRIPTION
      "Path: swPort.editConf.inboundBandwidth.action.eirAction.ethernet.cosDepth2

       Possibilities:
               unchanged   (256)"
   ::= {er1645v2EthPrtSwF2IbwEntry 4097966080}

er1645v2EthPrtSwF2IbwActEirActEthDei2 OBJECT-TYPE
   SYNTAX      INTEGER
               {
               unchanged (255),
               clear (0),
               set (1)
               }
   MAX-ACCESS  read-write
   STATUS      current
   DESCRIPTION
      "Path: swPort.editConf.inboundBandwidth.action.eirAction.ethernet.deiDepth2

       Possibilities:
               unchanged   (255)
               clear   (0)
               set   (1)"
   ::= {er1645v2EthPrtSwF2IbwEntry 4099276800}

er1645v2EthPrtSwF2IbwActEirActEthCos3 OBJECT-TYPE
   SYNTAX      INTEGER
               {
               unchanged (256)
               }
   MAX-ACCESS  read-write
   STATUS      current
   DESCRIPTION
      "Path: swPort.editConf.inboundBandwidth.action.eirAction.ethernet.cosDepth3

       Possibilities:
               unchanged   (256)"
   ::= {er1645v2EthPrtSwF2IbwEntry 4098031616}

er1645v2EthPrtSwF2IbwActEirActEthDei3 OBJECT-TYPE
   SYNTAX      INTEGER
               {
               unchanged (255),
               clear (0),
               set (1)
               }
   MAX-ACCESS  read-write
   STATUS      current
   DESCRIPTION
      "Path: swPort.editConf.inboundBandwidth.action.eirAction.ethernet.deiDepth3

       Possibilities:
               unchanged   (255)
               clear   (0)
               set   (1)"
   ::= {er1645v2EthPrtSwF2IbwEntry 4099342336}

er1645v2EthPrtSwF2IbwActEirActEthCos4 OBJECT-TYPE
   SYNTAX      INTEGER
               {
               unchanged (256)
               }
   MAX-ACCESS  read-write
   STATUS      current
   DESCRIPTION
      "Path: swPort.editConf.inboundBandwidth.action.eirAction.ethernet.cosDepth4

       Possibilities:
               unchanged   (256)"
   ::= {er1645v2EthPrtSwF2IbwEntry 4098097152}

er1645v2EthPrtSwF2IbwActEirActEthDei4 OBJECT-TYPE
   SYNTAX      INTEGER
               {
               unchanged (255),
               clear (0),
               set (1)
               }
   MAX-ACCESS  read-write
   STATUS      current
   DESCRIPTION
      "Path: swPort.editConf.inboundBandwidth.action.eirAction.ethernet.deiDepth4

       Possibilities:
               unchanged   (255)
               clear   (0)
               set   (1)"
   ::= {er1645v2EthPrtSwF2IbwEntry 4099407872}

er1645v2EthPrtSwF2IbwActEirActEthCos5 OBJECT-TYPE
   SYNTAX      INTEGER
               {
               unchanged (256)
               }
   MAX-ACCESS  read-write
   STATUS      current
   DESCRIPTION
      "Path: swPort.editConf.inboundBandwidth.action.eirAction.ethernet.cosDepth5

       Possibilities:
               unchanged   (256)"
   ::= {er1645v2EthPrtSwF2IbwEntry 4098162688}

er1645v2EthPrtSwF2IbwActEirActEthDei5 OBJECT-TYPE
   SYNTAX      INTEGER
               {
               unchanged (255),
               clear (0),
               set (1)
               }
   MAX-ACCESS  read-write
   STATUS      current
   DESCRIPTION
      "Path: swPort.editConf.inboundBandwidth.action.eirAction.ethernet.deiDepth5

       Possibilities:
               unchanged   (255)
               clear   (0)
               set   (1)"
   ::= {er1645v2EthPrtSwF2IbwEntry 4099473408}

er1645v2EthPrtSwF2IbwActEirActEthCos6 OBJECT-TYPE
   SYNTAX      INTEGER
               {
               unchanged (256)
               }
   MAX-ACCESS  read-write
   STATUS      current
   DESCRIPTION
      "Path: swPort.editConf.inboundBandwidth.action.eirAction.ethernet.cosDepth6

       Possibilities:
               unchanged   (256)"
   ::= {er1645v2EthPrtSwF2IbwEntry 4098228224}

er1645v2EthPrtSwF2IbwActEirActEthDei6 OBJECT-TYPE
   SYNTAX      INTEGER
               {
               unchanged (255),
               clear (0),
               set (1)
               }
   MAX-ACCESS  read-write
   STATUS      current
   DESCRIPTION
      "Path: swPort.editConf.inboundBandwidth.action.eirAction.ethernet.deiDepth6

       Possibilities:
               unchanged   (255)
               clear   (0)
               set   (1)"
   ::= {er1645v2EthPrtSwF2IbwEntry 4099538944}

er1645v2EthPrtSwF2IbwActEirActEthCos7 OBJECT-TYPE
   SYNTAX      INTEGER
               {
               unchanged (256)
               }
   MAX-ACCESS  read-write
   STATUS      current
   DESCRIPTION
      "Path: swPort.editConf.inboundBandwidth.action.eirAction.ethernet.cosDepth7

       Possibilities:
               unchanged   (256)"
   ::= {er1645v2EthPrtSwF2IbwEntry 4098293760}

er1645v2EthPrtSwF2IbwActEirActEthDei7 OBJECT-TYPE
   SYNTAX      INTEGER
               {
               unchanged (255),
               clear (0),
               set (1)
               }
   MAX-ACCESS  read-write
   STATUS      current
   DESCRIPTION
      "Path: swPort.editConf.inboundBandwidth.action.eirAction.ethernet.deiDepth7

       Possibilities:
               unchanged   (255)
               clear   (0)
               set   (1)"
   ::= {er1645v2EthPrtSwF2IbwEntry 4099604480}

er1645v2EthPrtSwF2IbwActEirActEthCos8 OBJECT-TYPE
   SYNTAX      INTEGER
               {
               unchanged (256)
               }
   MAX-ACCESS  read-write
   STATUS      current
   DESCRIPTION
      "Path: swPort.editConf.inboundBandwidth.action.eirAction.ethernet.cosDepth8

       Possibilities:
               unchanged   (256)"
   ::= {er1645v2EthPrtSwF2IbwEntry 4098359296}

er1645v2EthPrtSwF2IbwActEirActEthDei8 OBJECT-TYPE
   SYNTAX      INTEGER
               {
               unchanged (255),
               clear (0),
               set (1)
               }
   MAX-ACCESS  read-write
   STATUS      current
   DESCRIPTION
      "Path: swPort.editConf.inboundBandwidth.action.eirAction.ethernet.deiDepth8

       Possibilities:
               unchanged   (255)
               clear   (0)
               set   (1)"
   ::= {er1645v2EthPrtSwF2IbwEntry 4099670016}

er1645v2EthPrtSwF2IbwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.inboundBandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPrtSwF2IbwEntry 4098424832}

er1645v2EthPrtSwF2IbwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.inboundBandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2EthPrtSwF2IbwEntry 4098490368}

er1645v2EthPrtSwF2IbwActEirActEthDrpLev OBJECT-TYPE
   SYNTAX      INTEGER
               {
               unchanged (0)
               }
   MAX-ACCESS  read-write
   STATUS      current
   DESCRIPTION
      "Path: swPort.editConf.inboundBandwidth.action.eirAction.ethernet.dropLevel

       Possibilities:
               unchanged   (0)"
   ::= {er1645v2EthPrtSwF2IbwEntry 4098555904}

er1645v2EthPrtSwF2IbwActEirActEthDeFlag OBJECT-TYPE
   SYNTAX      INTEGER
               {
               unchanged (255),
               clear (0),
               set (1)
               }
   MAX-ACCESS  read-write
   STATUS      current
   DESCRIPTION
      "Path: swPort.editConf.inboundBandwidth.action.eirAction.ethernet.deFlag

       Possibilities:
               unchanged   (255)
               clear   (0)
               set   (1)"
   ::= {er1645v2EthPrtSwF2IbwEntry 4098752512}

er1645v2EthPrtSwF2IbwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.inboundBandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPrtSwF2IbwEntry 4104716288}

er1645v2EthPrtSwF2IbwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.inboundBandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2EthPrtSwF2IbwEntry 4104781824}

er1645v2EthPrtSwF2IbwActEirActIpDrpLev OBJECT-TYPE
   SYNTAX      INTEGER
               {
               unchanged (0)
               }
   MAX-ACCESS  read-write
   STATUS      current
   DESCRIPTION
      "Path: swPort.editConf.inboundBandwidth.action.eirAction.ip.dropLevel

       Possibilities:
               unchanged   (0)"
   ::= {er1645v2EthPrtSwF2IbwEntry 4104847360}

er1645v2EthPrtSwF2IbwActEirActIpDeFlag OBJECT-TYPE
   SYNTAX      INTEGER
               {
               unchanged (255),
               clear (0),
               set (1)
               }
   MAX-ACCESS  read-write
   STATUS      current
   DESCRIPTION
      "Path: swPort.editConf.inboundBandwidth.action.eirAction.ip.deFlag

       Possibilities:
               unchanged   (255)
               clear   (0)
               set   (1)"
   ::= {er1645v2EthPrtSwF2IbwEntry 4105043968}

er1645v2EthPrtSwF2IbwActViolActNone OBJECT-TYPE
   SYNTAX      OCTET STRING
   MAX-ACCESS  read-write
   STATUS      current
   DESCRIPTION
      "Path: swPort.editConf.inboundBandwidth.action.violateAction.none"
   ::= {er1645v2EthPrtSwF2IbwEntry 4129292288}

er1645v2EthPrtSwF2IbwActViolActDrop OBJECT-TYPE
   SYNTAX      OCTET STRING
   MAX-ACCESS  read-write
   STATUS      current
   DESCRIPTION
      "Path: swPort.editConf.inboundBandwidth.action.violateAction.drop"
   ::= {er1645v2EthPrtSwF2IbwEntry 4133486592}

er1645v2EthPrtSwF2IbwActViolActEthCos1 OBJECT-TYPE
   SYNTAX      INTEGER
               {
               unchanged (256)
               }
   MAX-ACCESS  read-write
   STATUS      current
   DESCRIPTION
      "Path: swPort.editConf.inboundBandwidth.action.violateAction.ethernet.cosDepth1

       Possibilities:
               unchanged   (256)"
   ::= {er1645v2EthPrtSwF2IbwEntry 4131454976}

er1645v2EthPrtSwF2IbwActViolActEthDei1 OBJECT-TYPE
   SYNTAX      INTEGER
               {
               unchanged (255),
               clear (0),
               set (1)
               }
   MAX-ACCESS  read-write
   STATUS      current
   DESCRIPTION
      "Path: swPort.editConf.inboundBandwidth.action.violateAction.ethernet.deiDepth1

       Possibilities:
               unchanged   (255)
               clear   (0)
               set   (1)"
   ::= {er1645v2EthPrtSwF2IbwEntry 4132765696}

er1645v2EthPrtSwF2IbwActViolActEthCos2 OBJECT-TYPE
   SYNTAX      INTEGER
               {
               unchanged (256)
               }
   MAX-ACCESS  read-write
   STATUS      current
   DESCRIPTION
      "Path: swPort.editConf.inboundBandwidth.action.violateAction.ethernet.cosDepth2

       Possibilities:
               unchanged   (256)"
   ::= {er1645v2EthPrtSwF2IbwEntry 4131520512}

er1645v2EthPrtSwF2IbwActViolActEthDei2 OBJECT-TYPE
   SYNTAX      INTEGER
               {
               unchanged (255),
               clear (0),
               set (1)
               }
   MAX-ACCESS  read-write
   STATUS      current
   DESCRIPTION
      "Path: swPort.editConf.inboundBandwidth.action.violateAction.ethernet.deiDepth2

       Possibilities:
               unchanged   (255)
               clear   (0)
               set   (1)"
   ::= {er1645v2EthPrtSwF2IbwEntry 4132831232}

er1645v2EthPrtSwF2IbwActViolActEthCos3 OBJECT-TYPE
   SYNTAX      INTEGER
               {
               unchanged (256)
               }
   MAX-ACCESS  read-write
   STATUS      current
   DESCRIPTION
      "Path: swPort.editConf.inboundBandwidth.action.violateAction.ethernet.cosDepth3

       Possibilities:
               unchanged   (256)"
   ::= {er1645v2EthPrtSwF2IbwEntry 4131586048}

er1645v2EthPrtSwF2IbwActViolActEthDei3 OBJECT-TYPE
   SYNTAX      INTEGER
               {
               unchanged (255),
               clear (0),
               set (1)
               }
   MAX-ACCESS  read-write
   STATUS      current
   DESCRIPTION
      "Path: swPort.editConf.inboundBandwidth.action.violateAction.ethernet.deiDepth3

       Possibilities:
               unchanged   (255)
               clear   (0)
               set   (1)"
   ::= {er1645v2EthPrtSwF2IbwEntry 4132896768}

er1645v2EthPrtSwF2IbwActViolActEthCos4 OBJECT-TYPE
   SYNTAX      INTEGER
               {
               unchanged (256)
               }
   MAX-ACCESS  read-write
   STATUS      current
   DESCRIPTION
      "Path: swPort.editConf.inboundBandwidth.action.violateAction.ethernet.cosDepth4

       Possibilities:
               unchanged   (256)"
   ::= {er1645v2EthPrtSwF2IbwEntry 4131651584}

er1645v2EthPrtSwF2IbwActViolActEthDei4 OBJECT-TYPE
   SYNTAX      INTEGER
               {
               unchanged (255),
               clear (0),
               set (1)
               }
   MAX-ACCESS  read-write
   STATUS      current
   DESCRIPTION
      "Path: swPort.editConf.inboundBandwidth.action.violateAction.ethernet.deiDepth4

       Possibilities:
               unchanged   (255)
               clear   (0)
               set   (1)"
   ::= {er1645v2EthPrtSwF2IbwEntry 4132962304}

er1645v2EthPrtSwF2IbwActViolActEthCos5 OBJECT-TYPE
   SYNTAX      INTEGER
               {
               unchanged (256)
               }
   MAX-ACCESS  read-write
   STATUS      current
   DESCRIPTION
      "Path: swPort.editConf.inboundBandwidth.action.violateAction.ethernet.cosDepth5

       Possibilities:
               unchanged   (256)"
   ::= {er1645v2EthPrtSwF2IbwEntry 4131717120}

er1645v2EthPrtSwF2IbwActViolActEthDei5 OBJECT-TYPE
   SYNTAX      INTEGER
               {
               unchanged (255),
               clear (0),
               set (1)
               }
   MAX-ACCESS  read-write
   STATUS      current
   DESCRIPTION
      "Path: swPort.editConf.inboundBandwidth.action.violateAction.ethernet.deiDepth5

       Possibilities:
               unchanged   (255)
               clear   (0)
               set   (1)"
   ::= {er1645v2EthPrtSwF2IbwEntry 4133027840}

er1645v2EthPrtSwF2IbwActViolActEthCos6 OBJECT-TYPE
   SYNTAX      INTEGER
               {
               unchanged (256)
               }
   MAX-ACCESS  read-write
   STATUS      current
   DESCRIPTION
      "Path: swPort.editConf.inboundBandwidth.action.violateAction.ethernet.cosDepth6

       Possibilities:
               unchanged   (256)"
   ::= {er1645v2EthPrtSwF2IbwEntry 4131782656}

er1645v2EthPrtSwF2IbwActViolActEthDei6 OBJECT-TYPE
   SYNTAX      INTEGER
               {
               unchanged (255),
               clear (0),
               set (1)
               }
   MAX-ACCESS  read-write
   STATUS      current
   DESCRIPTION
      "Path: swPort.editConf.inboundBandwidth.action.violateAction.ethernet.deiDepth6

       Possibilities:
               unchanged   (255)
               clear   (0)
               set   (1)"
   ::= {er1645v2EthPrtSwF2IbwEntry 4133093376}

er1645v2EthPrtSwF2IbwActViolActEthCos7 OBJECT-TYPE
   SYNTAX      INTEGER
               {
               unchanged (256)
               }
   MAX-ACCESS  read-write
   STATUS      current
   DESCRIPTION
      "Path: swPort.editConf.inboundBandwidth.action.violateAction.ethernet.cosDepth7

       Possibilities:
               unchanged   (256)"
   ::= {er1645v2EthPrtSwF2IbwEntry 4131848192}

er1645v2EthPrtSwF2IbwActViolActEthDei7 OBJECT-TYPE
   SYNTAX      INTEGER
               {
               unchanged (255),
               clear (0),
               set (1)
               }
   MAX-ACCESS  read-write
   STATUS      current
   DESCRIPTION
      "Path: swPort.editConf.inboundBandwidth.action.violateAction.ethernet.deiDepth7

       Possibilities:
               unchanged   (255)
               clear   (0)
               set   (1)"
   ::= {er1645v2EthPrtSwF2IbwEntry 4133158912}

er1645v2EthPrtSwF2IbwActViolActEthCos8 OBJECT-TYPE
   SYNTAX      INTEGER
               {
               unchanged (256)
               }
   MAX-ACCESS  read-write
   STATUS      current
   DESCRIPTION
      "Path: swPort.editConf.inboundBandwidth.action.violateAction.ethernet.cosDepth8

       Possibilities:
               unchanged   (256)"
   ::= {er1645v2EthPrtSwF2IbwEntry 4131913728}

er1645v2EthPrtSwF2IbwActViolActEthDei8 OBJECT-TYPE
   SYNTAX      INTEGER
               {
               unchanged (255),
               clear (0),
               set (1)
               }
   MAX-ACCESS  read-write
   STATUS      current
   DESCRIPTION
      "Path: swPort.editConf.inboundBandwidth.action.violateAction.ethernet.deiDepth8

       Possibilities:
               unchanged   (255)
               clear   (0)
               set   (1)"
   ::= {er1645v2EthPrtSwF2IbwEntry 4133224448}

er1645v2EthPrtSwF2IbwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.inboundBandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPrtSwF2IbwEntry 4131979264}

er1645v2EthPrtSwF2IbwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.inboundBandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2EthPrtSwF2IbwEntry 4132044800}

er1645v2EthPrtSwF2IbwActViolActEthDrpLev OBJECT-TYPE
   SYNTAX      INTEGER
               {
               unchanged (0)
               }
   MAX-ACCESS  read-write
   STATUS      current
   DESCRIPTION
      "Path: swPort.editConf.inboundBandwidth.action.violateAction.ethernet.dropLevel

       Possibilities:
               unchanged   (0)"
   ::= {er1645v2EthPrtSwF2IbwEntry 4132110336}

er1645v2EthPrtSwF2IbwActViolActEthDeFlag OBJECT-TYPE
   SYNTAX      INTEGER
               {
               unchanged (255),
               clear (0),
               set (1)
               }
   MAX-ACCESS  read-write
   STATUS      current
   DESCRIPTION
      "Path: swPort.editConf.inboundBandwidth.action.violateAction.ethernet.deFlag

       Possibilities:
               unchanged   (255)
               clear   (0)
               set   (1)"
   ::= {er1645v2EthPrtSwF2IbwEntry 4132306944}

er1645v2EthPrtSwF2IbwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.inboundBandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPrtSwF2IbwEntry 4138270720}

er1645v2EthPrtSwF2IbwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.inboundBandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2EthPrtSwF2IbwEntry 4138336256}

er1645v2EthPrtSwF2IbwActViolActIpDrpLev OBJECT-TYPE
   SYNTAX      INTEGER
               {
               unchanged (0)
               }
   MAX-ACCESS  read-write
   STATUS      current
   DESCRIPTION
      "Path: swPort.editConf.inboundBandwidth.action.violateAction.ip.dropLevel

       Possibilities:
               unchanged   (0)"
   ::= {er1645v2EthPrtSwF2IbwEntry 4138401792}

er1645v2EthPrtSwF2IbwActViolActIpDeFlag OBJECT-TYPE
   SYNTAX      INTEGER
               {
               unchanged (255),
               clear (0),
               set (1)
               }
   MAX-ACCESS  read-write
   STATUS      current
   DESCRIPTION
      "Path: swPort.editConf.inboundBandwidth.action.violateAction.ip.deFlag

       Possibilities:
               unchanged   (255)
               clear   (0)
               set   (1)"
   ::= {er1645v2EthPrtSwF2IbwEntry 4138598400}

er1645v2EthPrtSwF2IbwSubInterfacesExcluded OBJECT-TYPE
   SYNTAX      INTEGER
               {
               s (1)
               }
   MAX-ACCESS  read-write
   STATUS      current
   DESCRIPTION
      "Path: swPort.editConf.inboundBandwidth.subInterfaces.excluded

       Possibilities:
                  (1)"
   ::= {er1645v2EthPrtSwF2IbwEntry 2416967680}

er1645v2EthPrtSwF2IbwSubInterfacesIncludedInAccessList OBJECT-TYPE
   SYNTAX      DisplayString
   MAX-ACCESS  read-write
   STATUS      current
   DESCRIPTION
      "Path: swPort.editConf.inboundBandwidth.subInterfaces.included.inAccessList"
   ::= {er1645v2EthPrtSwF2IbwEntry 2418020352}


er1645v2EthPrtSwF2Vlan OBJECT IDENTIFIER ::= {er1645v2EthPrtSwF2 33}

er1645v2EthPrtSwF2VlanSSCTable OBJECT-TYPE
   SYNTAX      SEQUENCE OF Er1645v2EthPrtSwF2VlanEntry
   MAX-ACCESS  not-accessible
   STATUS      current
   DESCRIPTION
      ""
   ::= {er1645v2EthPrtSwF2Vlan 1}

er1645v2EthPrtSwF2VlanEntry OBJECT-TYPE
   SYNTAX      Er1645v2EthPrtSwF2VlanEntry
   MAX-ACCESS  not-accessible
   STATUS      current
   DESCRIPTION
      ""
   INDEX      { er1645v2EthPrtSwF2VlanGlobalIx,
                er1645v2EthPrtSwF2VlanTableIx }
   ::= {er1645v2EthPrtSwF2VlanSSCTable 1}

Er1645v2EthPrtSwF2VlanEntry ::=
   SEQUENCE
      {
      er1645v2EthPrtSwF2VlanActions
         VariableLengthTableActions,
      er1645v2EthPrtSwF2VlanGlobalIx
         GlobalIndex,
      er1645v2EthPrtSwF2VlanTableIx
         TableIndex,
      er1645v2EthPrtSwF2VlanName
         DisplayString,
      er1645v2EthPrtSwF2VlanRemark
         DisplayString,
      er1645v2EthPrtSwF2VlanAdminStatus
         INTEGER,
      er1645v2EthPrtSwF2VlanMode
         INTEGER,
      er1645v2EthPrtSwF2VlanPriorityPolicy
         DisplayString,
      er1645v2EthPrtSwF2VlanIpVrfRouter
         DisplayString,
      er1645v2EthPrtSwF2VlanIpAdr
         IpAddress,
      er1645v2EthPrtSwF2VlanIpNetm
         IpAddress,
      er1645v2EthPrtSwF2VlanIpSNetName
         INTEGER,
      er1645v2EthPrtSwF2VlanIpSNetCust
         DisplayString,
      er1645v2EthPrtSwF2VlanIpDhcpC
         INTEGER,
      er1645v2EthPrtSwF2VlanIpDhcpGatewayPreference
         Integer32,
      er1645v2EthPrtSwF2VlanIpDhcpRoutePreference
         Integer32,
      er1645v2EthPrtSwF2VlanIpDhcpDnsPreference
         Integer32,
      er1645v2EthPrtSwF2VlanIpMtu
         Integer32,
      er1645v2EthPrtSwF2VlanIpMssAdjust
         INTEGER,
      er1645v2EthPrtSwF2VlanIpRipMetric
         Integer32,
      er1645v2EthPrtSwF2VlanIpRipMetricOut
         Integer32,
      er1645v2EthPrtSwF2VlanIpRipMode
         INTEGER,
      er1645v2EthPrtSwF2VlanIpRipTxVer
         INTEGER,
      er1645v2EthPrtSwF2VlanIpRipRxVer
         INTEGER,
      er1645v2EthPrtSwF2VlanIpRipSplitH
         INTEGER,
      er1645v2EthPrtSwF2VlanIpRipAuth
         INTEGER,
      er1645v2EthPrtSwF2VlanIpRipFilter
         DisplayString,
      er1645v2EthPrtSwF2VlanIpRipFilterIn
         DisplayString,
      er1645v2EthPrtSwF2VlanIpRipClearNextHop
         INTEGER,
      er1645v2EthPrtSwF2VlanIpAccPol
         DisplayString,
      er1645v2EthPrtSwF2VlanIpAB
         DisplayString,
      er1645v2EthPrtSwF2VlanIpMA
         INTEGER,
      er1645v2EthPrtSwF2VlanIpMF
         Integer32,
      er1645v2EthPrtSwF2VlanIpDB
         INTEGER,
      er1645v2EthPrtSwF2VlanIpIR
         INTEGER,
      er1645v2EthPrtSwF2VlanIpIgmp
         INTEGER,
      er1645v2EthPrtSwF2VlanIpNN
         DisplayString,
      er1645v2EthPrtSwF2VlanIpVrrp
         INTEGER,
      er1645v2EthPrtSwF2VlanIpPimMode
         INTEGER,
      er1645v2EthPrtSwF2VlanIpPimDrPriority
         Counter32,
      er1645v2EthPrtSwF2VlanIpPimHelloTime
         TimeTicks,
      er1645v2EthPrtSwF2VlanIpPimPropagationDelay
         TimeTicks,
      er1645v2EthPrtSwF2VlanIpPimOverrideInterval
         TimeTicks,
      er1645v2EthPrtSwF2VlanIpPimBsrBorder
         INTEGER,
      er1645v2EthPrtSwF2VlanIpPimTtlThreshold
         Integer32,
      er1645v2EthPrtSwF2VlanIpIMNetworkUnreachable
         INTEGER,
      er1645v2EthPrtSwF2VlanIpIMHostUnreachable
         INTEGER,
      er1645v2EthPrtSwF2VlanIpIMProtocolUnreachable
         INTEGER,
      er1645v2EthPrtSwF2VlanIpIMPortUnreachable
         INTEGER,
      er1645v2EthPrtSwF2VlanIpIMMtuExceeded
         INTEGER,
      er1645v2EthPrtSwF2VlanIpIMAdminProhibited
         INTEGER,
      er1645v2EthPrtSwF2VlanIpIMTtlExceeded
         INTEGER,
      er1645v2EthPrtSwF2VlanIpIMRedirect
         INTEGER,
      er1645v2EthPrtSwF2VlanIpV6VrfRouter
         DisplayString,
      er1645v2EthPrtSwF2VlanIpV6AddrAutoConfigNrDupAddrDetects
         Integer32,
      er1645v2EthPrtSwF2VlanIpV6AddrAutoConfigAcceptRa
         INTEGER,
      er1645v2EthPrtSwF2VlanIpV6AddrAutoConfigAcceptRaRdnss
         INTEGER,
      er1645v2EthPrtSwF2VlanIpV6AddrAutoConfigAcceptRaDnssl
         INTEGER,
      er1645v2EthPrtSwF2VlanIpV6DefaultRoute
         INTEGER,
      er1645v2EthPrtSwF2VlanIpV6RaSend
         INTEGER,
      er1645v2EthPrtSwF2VlanIpV6RaMinInterval
         TimeTicks,
      er1645v2EthPrtSwF2VlanIpV6RaMaxInterval
         TimeTicks,
      er1645v2EthPrtSwF2VlanIpV6RaManagedFlag
         INTEGER,
      er1645v2EthPrtSwF2VlanIpV6RaOtherConfFlag
         INTEGER,
      er1645v2EthPrtSwF2VlanIpV6RaLinkMtu
         Integer32,
      er1645v2EthPrtSwF2VlanIpV6RaReachableTime
         TimeTicks,
      er1645v2EthPrtSwF2VlanIpV6RaRetransmitTime
         TimeTicks,
      er1645v2EthPrtSwF2VlanIpV6RaHopLimit
         Integer32,
      er1645v2EthPrtSwF2VlanIpV6RaDefaultLifeTime
         TimeTicks,
      er1645v2EthPrtSwF2VlanIpV6RaDnsOptionsRdnssLifeTime
         TimeTicks,
      er1645v2EthPrtSwF2VlanIpV6RaDnsOptionsRdnssImportServers
         INTEGER,
      er1645v2EthPrtSwF2VlanIpV6RaDnsOptionsDnsslLifeTime
         TimeTicks,
      er1645v2EthPrtSwF2VlanIpV6RaDnsOptionsDnsslImportDomains
         INTEGER,
      er1645v2EthPrtSwF2VlanIpV6RsSend
         INTEGER,
      er1645v2EthPrtSwF2VlanIpV6RsMaxRandomDelay
         TimeTicks,
      er1645v2EthPrtSwF2VlanIpV6RsInterval
         TimeTicks,
      er1645v2EthPrtSwF2VlanIpV6RsMaxSolicitations
         Integer32,
      er1645v2EthPrtSwF2VlanIpV6TrafficPolicyInbound
         DisplayString,
      er1645v2EthPrtSwF2VlanIpV6TrafficPolicyOutbound
         DisplayString,
      er1645v2EthPrtSwF2VlanIpV6FirewallZone
         DisplayString,
      er1645v2EthPrtSwF2VlanIpV6DhcpClientAddrAC
         INTEGER,
      er1645v2EthPrtSwF2VlanIpV6DhcpClientPrDelMode
         INTEGER,
      er1645v2EthPrtSwF2VlanIpV6DhcpClientPrDelPool
         DisplayString,
      er1645v2EthPrtSwF2VlanIpV6DhcpClientPrDelPdExclOpt
         INTEGER,
      er1645v2EthPrtSwF2VlanIpV6DhcpClientDnsServerPref
         Integer32,
      er1645v2EthPrtSwF2VlanIpV6DhcpClientRapidCommit
         INTEGER,
      er1645v2EthPrtSwF2VlanIpV6DhcpClientTimersSolTimeOut
         TimeTicks,
      er1645v2EthPrtSwF2VlanIpV6DhcpClientTimersSolMaxRt
         TimeTicks,
      er1645v2EthPrtSwF2VlanIpV6DhcpClientTimersInfoRefresh
         TimeTicks,
      er1645v2EthPrtSwF2VlanIpV6DhcpServerMode
         INTEGER,
      er1645v2EthPrtSwF2VlanIpV6DhcpServerPreference
         Integer32,
      er1645v2EthPrtSwF2VlanIpV6DhcpServerPool
         DisplayString,
      er1645v2EthPrtSwF2VlanIpV6DhcpServerRapidCommit
         INTEGER,
      er1645v2EthPrtSwF2VlanIpV6DhcpServerTimersInfoRefresh
         TimeTicks,
      er1645v2EthPrtSwF2VlanIpV6DhcpRelayMode
         INTEGER,
      er1645v2EthPrtSwF2VlanIpV6SendRedirect
         INTEGER,
      er1645v2EthPrtSwF2VlanIpV6LinkMtu
         Integer32,
      er1645v2EthPrtSwF2VlanIpV6InterfaceId
         OCTET STRING,
      er1645v2EthPrtSwF2VlanIpV6MF
         Integer32,
      er1645v2EthPrtSwF2VlanIpV6IcmpMessagesNoRoute
         INTEGER,
      er1645v2EthPrtSwF2VlanIpV6IcmpMessagesBeyondScope
         INTEGER,
      er1645v2EthPrtSwF2VlanIpV6IcmpMessagesAddressUnreachable
         INTEGER,
      er1645v2EthPrtSwF2VlanIpV6IcmpMessagesPortUnreachable
         INTEGER,
      er1645v2EthPrtSwF2VlanIpV6IcmpMessagesPacketTooBig
         INTEGER,
      er1645v2EthPrtSwF2VlanIpV6IcmpMessagesHopLimitExceeded
         INTEGER,
      er1645v2EthPrtSwF2VlanIpV6IcmpMessagesFragTimeExceeded
         INTEGER,
      er1645v2EthPrtSwF2VlanIpV6IcmpMessagesHeaderFieldErr
         INTEGER,
      er1645v2EthPrtSwF2VlanIpV6IcmpMessagesOptionUnrecognized
         INTEGER,
      er1645v2EthPrtSwF2VlanIpV6IcmpMessagesRedirect
         INTEGER,
      er1645v2EthPrtSwF2VlanBridgingAccList
         DisplayString,
      er1645v2EthPrtSwF2VlanBridgingInACL
         DisplayString,
      er1645v2EthPrtSwF2VlanBridgingTp
         DisplayString,
      er1645v2EthPrtSwF2VlanBridgingBrGrp
         DisplayString,
      er1645v2EthPrtSwF2VlanBridgingLimBC
         INTEGER,
      er1645v2EthPrtSwF2VlanBridgingPrivateMode
         INTEGER,
      er1645v2EthPrtSwF2VlanBridgingLearning
         INTEGER,
      er1645v2EthPrtSwF2VlanBridgingMaxCacheSize
         INTEGER,
      er1645v2EthPrtSwF2VlanBridgingRelearnDropOnRelearn
         INTEGER,
      er1645v2EthPrtSwF2VlanBridgingRelearnShutdownThreshold
         Integer32,
      er1645v2EthPrtSwF2VlanBridgingRelearnShutdownTime
         TimeTicks,
      er1645v2EthPrtSwF2VlanBridgingRelearnLoopDetection
         INTEGER,
      er1645v2EthPrtSwF2VlanBridgingRelearnLoopDetectionInterval
         TimeTicks,
      er1645v2EthPrtSwF2VlanBridgingVlanMemberShip
         INTEGER,
      er1645v2EthPrtSwF2VlanBridgingVlTUntaggedAction
         INTEGER,
      er1645v2EthPrtSwF2VlanBridgingVlTUntaggedTagInfoTpid
         INTEGER,
      er1645v2EthPrtSwF2VlanBridgingVlTUntaggedTagInfoVid
         Integer32,
      er1645v2EthPrtSwF2VlanBridgingVlTUnknownVlansAction
         INTEGER,
      er1645v2EthPrtSwF2VlanBridgingVlTUnknownVlansTagInfoTpid
         INTEGER,
      er1645v2EthPrtSwF2VlanBridgingVlTUnknownVlansTagInfoVid
         Integer32,
      er1645v2EthPrtSwF2VlanBridgingDot1adType
         INTEGER,
      er1645v2EthPrtSwF2VlanBridgingPriority
         Integer32,
      er1645v2EthPrtSwF2VlanBridgingPathCost
         Integer32,
      er1645v2EthPrtSwF2VlanBridgingInternalPathCost
         Integer32,
      er1645v2EthPrtSwF2VlanBridgingTCD
         INTEGER,
      er1645v2EthPrtSwF2VlanBridgingRestrictedRole
         INTEGER,
      er1645v2EthPrtSwF2VlanBridgingAdminEdge
         INTEGER,
      er1645v2EthPrtSwF2VlanBridgingOamMacDeviceMac
         DisplayString,
      er1645v2EthPrtSwF2VlanBridgingOamMacUserMac
         OCTET STRING,
      er1645v2EthPrtSwF2VlanBridgingOamMacBridgeMac
         DisplayString,
      er1645v2EthPrtSwF2VlanBridgingMgmtInline
         INTEGER,
      er1645v2EthPrtSwF2VlanBridgingL2ptMode
         INTEGER,
      er1645v2EthPrtSwF2VlanBridgingL2ptProtocols
         Integer32,
      er1645v2EthPrtSwF2VlanBridgingL2ptDestMac
         OCTET STRING,
      er1645v2EthPrtSwF2VlanBridgingL2ptCos
         INTEGER,
      er1645v2EthPrtSwF2VlanBridgingL2ptDropThrStp
         INTEGER,
      er1645v2EthPrtSwF2VlanBridgingL2ptDropThrLldp
         INTEGER,
      er1645v2EthPrtSwF2VlanBridgingL2ptDropThrOam
         INTEGER,
      er1645v2EthPrtSwF2VlanBridgingL2ptDropThrCdp
         INTEGER,
      er1645v2EthPrtSwF2VlanBridgingL2ptDropThrVtp
         INTEGER,
      er1645v2EthPrtSwF2VlanBridgingL2ptDropThrLacp
         INTEGER,
      er1645v2EthPrtSwF2VlanBridgingL2ptDropThrEfmOam
         INTEGER,
      er1645v2EthPrtSwF2VlanBridgingL2ptDropThrPvst
         INTEGER,
      er1645v2EthPrtSwF2VlanBridgingL2ptDropThrMmrp
         INTEGER,
      er1645v2EthPrtSwF2VlanBridgingL2ptDropThrMvrp
         INTEGER,
      er1645v2EthPrtSwF2VlanBridgingL2ptDropThrGvrp
         INTEGER,
      er1645v2EthPrtSwF2VlanBridgingL2ptDropThrGmrp
         INTEGER,
      er1645v2EthPrtSwF2VlanBridgingL2ptDropThrDtp
         INTEGER,
      er1645v2EthPrtSwF2VlanBridgingL2ptDropThrPagp
         INTEGER,
      er1645v2EthPrtSwF2VlanBridgingL2ptDropThrUdld
         INTEGER,
      er1645v2EthPrtSwF2VlanVlanVid
         INTEGER,
      er1645v2EthPrtSwF2VlanVlanVidExtensionSingle
         OCTET STRING,
      er1645v2EthPrtSwF2VlanVlanVidExtensionEndVid
         Integer32,
      er1645v2EthPrtSwF2VlanVlanTpid
         INTEGER,
      er1645v2EthPrtSwF2VlanVlanTagSign
         INTEGER,
      er1645v2EthPrtSwF2VlanVlanChTos
         INTEGER,
      er1645v2EthPrtSwF2VlanVlanCTMapP0
         INTEGER,
      er1645v2EthPrtSwF2VlanVlanCTMapP1
         INTEGER,
      er1645v2EthPrtSwF2VlanVlanCTMapP2
         INTEGER,
      er1645v2EthPrtSwF2VlanVlanCTMapP3
         INTEGER,
      er1645v2EthPrtSwF2VlanVlanCTMapP4
         INTEGER,
      er1645v2EthPrtSwF2VlanVlanCTMapP5
         INTEGER,
      er1645v2EthPrtSwF2VlanVlanCTMapP6
         INTEGER,
      er1645v2EthPrtSwF2VlanVlanCTMapP7
         INTEGER,
      er1645v2EthPrtSwF2VlanVlanTxCos
         INTEGER,
      er1645v2EthPrtSwF2VlanVlanCCMapP0
         Integer32,
      er1645v2EthPrtSwF2VlanVlanCCMapP1
         Integer32,
      er1645v2EthPrtSwF2VlanVlanCCMapP2
         Integer32,
      er1645v2EthPrtSwF2VlanVlanCCMapP3
         Integer32,
      er1645v2EthPrtSwF2VlanVlanCCMapP4
         Integer32,
      er1645v2EthPrtSwF2VlanVlanCCMapP5
         Integer32,
      er1645v2EthPrtSwF2VlanVlanCCMapP6
         Integer32,
      er1645v2EthPrtSwF2VlanVlanCCMapP7
         Integer32,
      er1645v2EthPrtSwF2VlanVlanQCMapQueue1
         Integer32,
      er1645v2EthPrtSwF2VlanVlanQCMapQueue2
         Integer32,
      er1645v2EthPrtSwF2VlanVlanQCMapQueue3
         Integer32,
      er1645v2EthPrtSwF2VlanVlanQCMapQueue4
         Integer32,
      er1645v2EthPrtSwF2VlanVlanQCMapQueue5
         Integer32,
      er1645v2EthPrtSwF2VlanVlanQCMapLowDelayQueue
         Integer32,
      er1645v2EthPrtSwF2VlanVlanQCMapLowDelay2Queue
         Integer32,
      er1645v2EthPrtSwF2VlanVlanQCMapSystemQueue
         Integer32,
      er1645v2EthPrtSwF2VlanVlanQinQSVid
         Integer32,
      er1645v2EthPrtSwF2VlanVlanQinQSTpid
         INTEGER,
      er1645v2EthPrtSwF2VlanVlanArpTimeOut
         TimeTicks,
      er1645v2EthPrtSwF2VlanVlanArpProxyArp
         INTEGER,
      er1645v2EthPrtSwF2VlanBandwidthMode
         INTEGER,
      er1645v2EthPrtSwF2VlanBandwidthCir
         Integer32,
      er1645v2EthPrtSwF2VlanBandwidthEir
         Integer32,
      er1645v2EthPrtSwF2VlanBandwidthUnit
         INTEGER,
      er1645v2EthPrtSwF2VlanBandwidthTc
         INTEGER,
      er1645v2EthPrtSwF2VlanBandwidthTcFactor
         INTEGER,
      er1645v2EthPrtSwF2VlanBandwidthCorrType
         INTEGER,
      er1645v2EthPrtSwF2VlanBandwidthCorrPredefEncapsFrameRelay
         DisplayString,
      er1645v2EthPrtSwF2VlanBandwidthCorrPredefEncapsPpp
         DisplayString,
      er1645v2EthPrtSwF2VlanBandwidthCorrPredefEncapsAtmHl
         INTEGER,
      er1645v2EthPrtSwF2VlanBandwidthCorrPredefEncapsAtmMp
         INTEGER,
      er1645v2EthPrtSwF2VlanBandwidthCorrPredefEncapsHdlc
         DisplayString,
      er1645v2EthPrtSwF2VlanBandwidthCorrPredefEncapsEfmFs
         Integer32,
      er1645v2EthPrtSwF2VlanBandwidthCorrPredefEncapsEfmIb
         Integer32,
      er1645v2EthPrtSwF2VlanBandwidthCorrPredefMode
         INTEGER,
      er1645v2EthPrtSwF2VlanBandwidthCorrManualOverhead
         Integer32,
      er1645v2EthPrtSwF2VlanBandwidthCorrManualFrameData
         Counter32,
      er1645v2EthPrtSwF2VlanBandwidthCorrManualFrameHeader
         Counter32,
      er1645v2EthPrtSwF2VlanBandwidthMaxFifoQLen
         Integer32,
      er1645v2EthPrtSwF2VlanBandwidthDeFlagCir
         INTEGER,
      er1645v2EthPrtSwF2VlanBandwidthDeFlagEir
         INTEGER,
      er1645v2EthPrtSwF2VlanBandwidthDeFlagViolate
         INTEGER,
      er1645v2EthPrtSwF2VlanBandwidthActCirActNone
         OCTET STRING,
      er1645v2EthPrtSwF2VlanBandwidthActCirActEthCos1
         INTEGER,
      er1645v2EthPrtSwF2VlanBandwidthActCirActEthDei1
         INTEGER,
      er1645v2EthPrtSwF2VlanBandwidthActCirActEthCos2
         INTEGER,
      er1645v2EthPrtSwF2VlanBandwidthActCirActEthDei2
         INTEGER,
      er1645v2EthPrtSwF2VlanBandwidthActCirActEthCos3
         INTEGER,
      er1645v2EthPrtSwF2VlanBandwidthActCirActEthDei3
         INTEGER,
      er1645v2EthPrtSwF2VlanBandwidthActCirActEthCos4
         INTEGER,
      er1645v2EthPrtSwF2VlanBandwidthActCirActEthDei4
         INTEGER,
      er1645v2EthPrtSwF2VlanBandwidthActCirActEthCos5
         INTEGER,
      er1645v2EthPrtSwF2VlanBandwidthActCirActEthDei5
         INTEGER,
      er1645v2EthPrtSwF2VlanBandwidthActCirActEthCos6
         INTEGER,
      er1645v2EthPrtSwF2VlanBandwidthActCirActEthDei6
         INTEGER,
      er1645v2EthPrtSwF2VlanBandwidthActCirActEthCos7
         INTEGER,
      er1645v2EthPrtSwF2VlanBandwidthActCirActEthDei7
         INTEGER,
      er1645v2EthPrtSwF2VlanBandwidthActCirActEthCos8
         INTEGER,
      er1645v2EthPrtSwF2VlanBandwidthActCirActEthDei8
         INTEGER,
      er1645v2EthPrtSwF2VlanBandwidthActCirActEthTos
         INTEGER,
      er1645v2EthPrtSwF2VlanBandwidthActCirActEthQueue
         INTEGER,
      er1645v2EthPrtSwF2VlanBandwidthActCirActEthDrpLev
         INTEGER,
      er1645v2EthPrtSwF2VlanBandwidthActCirActEthDeFlag
         INTEGER,
      er1645v2EthPrtSwF2VlanBandwidthActCirActIpTos
         INTEGER,
      er1645v2EthPrtSwF2VlanBandwidthActCirActIpQueue
         INTEGER,
      er1645v2EthPrtSwF2VlanBandwidthActCirActIpDrpLev
         INTEGER,
      er1645v2EthPrtSwF2VlanBandwidthActCirActIpDeFlag
         INTEGER,
      er1645v2EthPrtSwF2VlanBandwidthActEirActNone
         OCTET STRING,
      er1645v2EthPrtSwF2VlanBandwidthActEirActEthCos1
         INTEGER,
      er1645v2EthPrtSwF2VlanBandwidthActEirActEthDei1
         INTEGER,
      er1645v2EthPrtSwF2VlanBandwidthActEirActEthCos2
         INTEGER,
      er1645v2EthPrtSwF2VlanBandwidthActEirActEthDei2
         INTEGER,
      er1645v2EthPrtSwF2VlanBandwidthActEirActEthCos3
         INTEGER,
      er1645v2EthPrtSwF2VlanBandwidthActEirActEthDei3
         INTEGER,
      er1645v2EthPrtSwF2VlanBandwidthActEirActEthCos4
         INTEGER,
      er1645v2EthPrtSwF2VlanBandwidthActEirActEthDei4
         INTEGER,
      er1645v2EthPrtSwF2VlanBandwidthActEirActEthCos5
         INTEGER,
      er1645v2EthPrtSwF2VlanBandwidthActEirActEthDei5
         INTEGER,
      er1645v2EthPrtSwF2VlanBandwidthActEirActEthCos6
         INTEGER,
      er1645v2EthPrtSwF2VlanBandwidthActEirActEthDei6
         INTEGER,
      er1645v2EthPrtSwF2VlanBandwidthActEirActEthCos7
         INTEGER,
      er1645v2EthPrtSwF2VlanBandwidthActEirActEthDei7
         INTEGER,
      er1645v2EthPrtSwF2VlanBandwidthActEirActEthCos8
         INTEGER,
      er1645v2EthPrtSwF2VlanBandwidthActEirActEthDei8
         INTEGER,
      er1645v2EthPrtSwF2VlanBandwidthActEirActEthTos
         INTEGER,
      er1645v2EthPrtSwF2VlanBandwidthActEirActEthQueue
         INTEGER,
      er1645v2EthPrtSwF2VlanBandwidthActEirActEthDrpLev
         INTEGER,
      er1645v2EthPrtSwF2VlanBandwidthActEirActEthDeFlag
         INTEGER,
      er1645v2EthPrtSwF2VlanBandwidthActEirActIpTos
         INTEGER,
      er1645v2EthPrtSwF2VlanBandwidthActEirActIpQueue
         INTEGER,
      er1645v2EthPrtSwF2VlanBandwidthActEirActIpDrpLev
         INTEGER,
      er1645v2EthPrtSwF2VlanBandwidthActEirActIpDeFlag
         INTEGER,
      er1645v2EthPrtSwF2VlanBandwidthActViolActNone
         OCTET STRING,
      er1645v2EthPrtSwF2VlanBandwidthActViolActDrop
         OCTET STRING,
      er1645v2EthPrtSwF2VlanBandwidthActViolActEthCos1
         INTEGER,
      er1645v2EthPrtSwF2VlanBandwidthActViolActEthDei1
         INTEGER,
      er1645v2EthPrtSwF2VlanBandwidthActViolActEthCos2
         INTEGER,
      er1645v2EthPrtSwF2VlanBandwidthActViolActEthDei2
         INTEGER,
      er1645v2EthPrtSwF2VlanBandwidthActViolActEthCos3
         INTEGER,
      er1645v2EthPrtSwF2VlanBandwidthActViolActEthDei3
         INTEGER,
      er1645v2EthPrtSwF2VlanBandwidthActViolActEthCos4
         INTEGER,
      er1645v2EthPrtSwF2VlanBandwidthActViolActEthDei4
         INTEGER,
      er1645v2EthPrtSwF2VlanBandwidthActViolActEthCos5
         INTEGER,
      er1645v2EthPrtSwF2VlanBandwidthActViolActEthDei5
         INTEGER,
      er1645v2EthPrtSwF2VlanBandwidthActViolActEthCos6
         INTEGER,
      er1645v2EthPrtSwF2VlanBandwidthActViolActEthDei6
         INTEGER,
      er1645v2EthPrtSwF2VlanBandwidthActViolActEthCos7
         INTEGER,
      er1645v2EthPrtSwF2VlanBandwidthActViolActEthDei7
         INTEGER,
      er1645v2EthPrtSwF2VlanBandwidthActViolActEthCos8
         INTEGER,
      er1645v2EthPrtSwF2VlanBandwidthActViolActEthDei8
         INTEGER,
      er1645v2EthPrtSwF2VlanBandwidthActViolActEthTos
         INTEGER,
      er1645v2EthPrtSwF2VlanBandwidthActViolActEthQueue
         INTEGER,
      er1645v2EthPrtSwF2VlanBandwidthActViolActEthDrpLev
         INTEGER,
      er1645v2EthPrtSwF2VlanBandwidthActViolActEthDeFlag
         INTEGER,
      er1645v2EthPrtSwF2VlanBandwidthActViolActIpTos
         INTEGER,
      er1645v2EthPrtSwF2VlanBandwidthActViolActIpQueue
         INTEGER,
      er1645v2EthPrtSwF2VlanBandwidthActViolActIpDrpLev
         INTEGER,
      er1645v2EthPrtSwF2VlanBandwidthActViolActIpDeFlag
         INTEGER,
      er1645v2EthPrtSwF2VlanInbBwMode
         INTEGER,
      er1645v2EthPrtSwF2VlanInbBwCir
         Integer32,
      er1645v2EthPrtSwF2VlanInbBwEir
         Integer32,
      er1645v2EthPrtSwF2VlanInbBwUnit
         INTEGER,
      er1645v2EthPrtSwF2VlanInbBwTc
         INTEGER,
      er1645v2EthPrtSwF2VlanInbBwTcFactor
         INTEGER,
      er1645v2EthPrtSwF2VlanInbBwCorrType
         INTEGER,
      er1645v2EthPrtSwF2VlanInbBwCorrPredefEncapsFrameRelay
         DisplayString,
      er1645v2EthPrtSwF2VlanInbBwCorrPredefEncapsPpp
         DisplayString,
      er1645v2EthPrtSwF2VlanInbBwCorrPredefEncapsAtmHl
         INTEGER,
      er1645v2EthPrtSwF2VlanInbBwCorrPredefEncapsAtmMp
         INTEGER,
      er1645v2EthPrtSwF2VlanInbBwCorrPredefEncapsHdlc
         DisplayString,
      er1645v2EthPrtSwF2VlanInbBwCorrPredefEncapsEfmFs
         Integer32,
      er1645v2EthPrtSwF2VlanInbBwCorrPredefEncapsEfmIb
         Integer32,
      er1645v2EthPrtSwF2VlanInbBwCorrPredefMode
         INTEGER,
      er1645v2EthPrtSwF2VlanInbBwCorrManualOverhead
         Integer32,
      er1645v2EthPrtSwF2VlanInbBwCorrManualFrameData
         Counter32,
      er1645v2EthPrtSwF2VlanInbBwCorrManualFrameHeader
         Counter32,
      er1645v2EthPrtSwF2VlanInbBwMaxFifoQLen
         Integer32,
      er1645v2EthPrtSwF2VlanInbBwPriorityPolicy
         DisplayString,
      er1645v2EthPrtSwF2VlanInbBwDeFlagCir
         INTEGER,
      er1645v2EthPrtSwF2VlanInbBwDeFlagEir
         INTEGER,
      er1645v2EthPrtSwF2VlanInbBwDeFlagViolate
         INTEGER,
      er1645v2EthPrtSwF2VlanInbBwActCirActNone
         OCTET STRING,
      er1645v2EthPrtSwF2VlanInbBwActCirActEthCos1
         INTEGER,
      er1645v2EthPrtSwF2VlanInbBwActCirActEthDei1
         INTEGER,
      er1645v2EthPrtSwF2VlanInbBwActCirActEthCos2
         INTEGER,
      er1645v2EthPrtSwF2VlanInbBwActCirActEthDei2
         INTEGER,
      er1645v2EthPrtSwF2VlanInbBwActCirActEthCos3
         INTEGER,
      er1645v2EthPrtSwF2VlanInbBwActCirActEthDei3
         INTEGER,
      er1645v2EthPrtSwF2VlanInbBwActCirActEthCos4
         INTEGER,
      er1645v2EthPrtSwF2VlanInbBwActCirActEthDei4
         INTEGER,
      er1645v2EthPrtSwF2VlanInbBwActCirActEthCos5
         INTEGER,
      er1645v2EthPrtSwF2VlanInbBwActCirActEthDei5
         INTEGER,
      er1645v2EthPrtSwF2VlanInbBwActCirActEthCos6
         INTEGER,
      er1645v2EthPrtSwF2VlanInbBwActCirActEthDei6
         INTEGER,
      er1645v2EthPrtSwF2VlanInbBwActCirActEthCos7
         INTEGER,
      er1645v2EthPrtSwF2VlanInbBwActCirActEthDei7
         INTEGER,
      er1645v2EthPrtSwF2VlanInbBwActCirActEthCos8
         INTEGER,
      er1645v2EthPrtSwF2VlanInbBwActCirActEthDei8
         INTEGER,
      er1645v2EthPrtSwF2VlanInbBwActCirActEthTos
         INTEGER,
      er1645v2EthPrtSwF2VlanInbBwActCirActEthQueue
         INTEGER,
      er1645v2EthPrtSwF2VlanInbBwActCirActEthDrpLev
         INTEGER,
      er1645v2EthPrtSwF2VlanInbBwActCirActEthDeFlag
         INTEGER,
      er1645v2EthPrtSwF2VlanInbBwActCirActIpTos
         INTEGER,
      er1645v2EthPrtSwF2VlanInbBwActCirActIpQueue
         INTEGER,
      er1645v2EthPrtSwF2VlanInbBwActCirActIpDrpLev
         INTEGER,
      er1645v2EthPrtSwF2VlanInbBwActCirActIpDeFlag
         INTEGER,
      er1645v2EthPrtSwF2VlanInbBwActEirActNone
         OCTET STRING,
      er1645v2EthPrtSwF2VlanInbBwActEirActEthCos1
         INTEGER,
      er1645v2EthPrtSwF2VlanInbBwActEirActEthDei1
         INTEGER,
      er1645v2EthPrtSwF2VlanInbBwActEirActEthCos2
         INTEGER,
      er1645v2EthPrtSwF2VlanInbBwActEirActEthDei2
         INTEGER,
      er1645v2EthPrtSwF2VlanInbBwActEirActEthCos3
         INTEGER,
      er1645v2EthPrtSwF2VlanInbBwActEirActEthDei3
         INTEGER,
      er1645v2EthPrtSwF2VlanInbBwActEirActEthCos4
         INTEGER,
      er1645v2EthPrtSwF2VlanInbBwActEirActEthDei4
         INTEGER,
      er1645v2EthPrtSwF2VlanInbBwActEirActEthCos5
         INTEGER,
      er1645v2EthPrtSwF2VlanInbBwActEirActEthDei5
         INTEGER,
      er1645v2EthPrtSwF2VlanInbBwActEirActEthCos6
         INTEGER,
      er1645v2EthPrtSwF2VlanInbBwActEirActEthDei6
         INTEGER,
      er1645v2EthPrtSwF2VlanInbBwActEirActEthCos7
         INTEGER,
      er1645v2EthPrtSwF2VlanInbBwActEirActEthDei7
         INTEGER,
      er1645v2EthPrtSwF2VlanInbBwActEirActEthCos8
         INTEGER,
      er1645v2EthPrtSwF2VlanInbBwActEirActEthDei8
         INTEGER,
      er1645v2EthPrtSwF2VlanInbBwActEirActEthTos
         INTEGER,
      er1645v2EthPrtSwF2VlanInbBwActEirActEthQueue
         INTEGER,
      er1645v2EthPrtSwF2VlanInbBwActEirActEthDrpLev
         INTEGER,
      er1645v2EthPrtSwF2VlanInbBwActEirActEthDeFlag
         INTEGER,
      er1645v2EthPrtSwF2VlanInbBwActEirActIpTos
         INTEGER,
      er1645v2EthPrtSwF2VlanInbBwActEirActIpQueue
         INTEGER,
      er1645v2EthPrtSwF2VlanInbBwActEirActIpDrpLev
         INTEGER,
      er1645v2EthPrtSwF2VlanInbBwActEirActIpDeFlag
         INTEGER,
      er1645v2EthPrtSwF2VlanInbBwActViolActNone
         OCTET STRING,
      er1645v2EthPrtSwF2VlanInbBwActViolActDrop
         OCTET STRING,
      er1645v2EthPrtSwF2VlanInbBwActViolActEthCos1
         INTEGER,
      er1645v2EthPrtSwF2VlanInbBwActViolActEthDei1
         INTEGER,
      er1645v2EthPrtSwF2VlanInbBwActViolActEthCos2
         INTEGER,
      er1645v2EthPrtSwF2VlanInbBwActViolActEthDei2
         INTEGER,
      er1645v2EthPrtSwF2VlanInbBwActViolActEthCos3
         INTEGER,
      er1645v2EthPrtSwF2VlanInbBwActViolActEthDei3
         INTEGER,
      er1645v2EthPrtSwF2VlanInbBwActViolActEthCos4
         INTEGER,
      er1645v2EthPrtSwF2VlanInbBwActViolActEthDei4
         INTEGER,
      er1645v2EthPrtSwF2VlanInbBwActViolActEthCos5
         INTEGER,
      er1645v2EthPrtSwF2VlanInbBwActViolActEthDei5
         INTEGER,
      er1645v2EthPrtSwF2VlanInbBwActViolActEthCos6
         INTEGER,
      er1645v2EthPrtSwF2VlanInbBwActViolActEthDei6
         INTEGER,
      er1645v2EthPrtSwF2VlanInbBwActViolActEthCos7
         INTEGER,
      er1645v2EthPrtSwF2VlanInbBwActViolActEthDei7
         INTEGER,
      er1645v2EthPrtSwF2VlanInbBwActViolActEthCos8
         INTEGER,
      er1645v2EthPrtSwF2VlanInbBwActViolActEthDei8
         INTEGER,
      er1645v2EthPrtSwF2VlanInbBwActViolActEthTos
         INTEGER,
      er1645v2EthPrtSwF2VlanInbBwActViolActEthQueue
         INTEGER,
      er1645v2EthPrtSwF2VlanInbBwActViolActEthDrpLev
         INTEGER,
      er1645v2EthPrtSwF2VlanInbBwActViolActEthDeFlag
         INTEGER,
      er1645v2EthPrtSwF2VlanInbBwActViolActIpTos
         INTEGER,
      er1645v2EthPrtSwF2VlanInbBwActViolActIpQueue
         INTEGER,
      er1645v2EthPrtSwF2VlanInbBwActViolActIpDrpLev
         INTEGER,
      er1645v2EthPrtSwF2VlanInbBwActViolActIpDeFlag
         INTEGER,
      er1645v2EthPrtSwF2VlanPppoE
         INTEGER,
      er1645v2EthPrtSwF2VlanPppLnkMOperation
         INTEGER,
      er1645v2EthPrtSwF2VlanPppLnkMInterval
         TimeTicks,
      er1645v2EthPrtSwF2VlanPppLnkMRepTimeOut
         TimeTicks,
      er1645v2EthPrtSwF2VlanPppLnkMFailsPrmt
         Integer32,
      er1645v2EthPrtSwF2VlanPppAuthentication
         INTEGER,
      er1645v2EthPrtSwF2VlanPppAuthenPeriod
         TimeTicks,
      er1645v2EthPrtSwF2VlanPppSessionName
         DisplayString,
      er1645v2EthPrtSwF2VlanPppSessionSecret
         DisplayString,
      er1645v2EthPrtSwF2VlanPppEncModeSessionSecret
         INTEGER,
      er1645v2EthPrtSwF2VlanPppEncSessionSecret
         DisplayString,
      er1645v2EthPrtSwF2VlanPppServiceName
         DisplayString,
      er1645v2EthPrtSwF2VlanPbbMode
         INTEGER,
      er1645v2EthPrtSwF2VlanPbbTxCos
         Integer32,
      er1645v2EthPrtSwF2VlanPbbIsid
         Integer32,
      er1645v2EthPrtSwF2VlanPbbDestMac
         OCTET STRING,
      er1645v2EthPrtSwF2VlanPbbCustomGroupMac
         OCTET STRING
      }

er1645v2EthPrtSwF2VlanActions OBJECT-TYPE
   SYNTAX      VariableLengthTableActions
   MAX-ACCESS  read-write
   STATUS      current
   DESCRIPTION
      "By way of this field, some manipulations
       on this table may be performed."
   ::= {er1645v2EthPrtSwF2VlanEntry 2}

er1645v2EthPrtSwF2VlanGlobalIx OBJECT-TYPE
   SYNTAX      GlobalIndex
   MAX-ACCESS  not-accessible
   STATUS      current
   DESCRIPTION
      "The value of the tlsCntTreeGlobalIndex of the MANAGED OBJECT."
   ::= {er1645v2EthPrtSwF2VlanEntry 10}

er1645v2EthPrtSwF2VlanTableIx OBJECT-TYPE
   SYNTAX      TableIndex
   MAX-ACCESS  not-accessible
   STATUS      current
   DESCRIPTION
      ""
   ::= {er1645v2EthPrtSwF2VlanEntry 11}

er1645v2EthPrtSwF2VlanName OBJECT-TYPE
   SYNTAX      DisplayString
   MAX-ACCESS  read-write
   STATUS      current
   DESCRIPTION
      "Path: swPort.editConf.vlan.name"
   ::= {er1645v2EthPrtSwF2VlanEntry 16777216}

er1645v2EthPrtSwF2VlanRemark OBJECT-TYPE
   SYNTAX      DisplayString
   MAX-ACCESS  read-write
   STATUS      current
   DESCRIPTION
      "Path: swPort.editConf.vlan.remark"
   ::= {er1645v2EthPrtSwF2VlanEntry 1157627904}

er1645v2EthPrtSwF2VlanAdminStatus OBJECT-TYPE
   SYNTAX      INTEGER
               {
               up (1),
               down (2)
               }
   MAX-ACCESS  read-write
   STATUS      current
   DESCRIPTION
      "Path: swPort.editConf.vlan.adminStatus

       Possibilities:
               up   (1)
               down   (2)"
   ::= {er1645v2EthPrtSwF2VlanEntry 33554432}

er1645v2EthPrtSwF2VlanMode OBJECT-TYPE
   SYNTAX      INTEGER
               {
               routing (1),
               bridging (2),
               ipV6 (16),
               ipV6ipV4 (17),
               multilink (8)
               }
   MAX-ACCESS  read-write
   STATUS      current
   DESCRIPTION
      "Path: swPort.editConf.vlan.mode

       Possibilities:
               routing   (1)
               bridging   (2)
               ipV6   (16)
               ipV6/ipV4   (17)
               multilink   (8)"
   ::= {er1645v2EthPrtSwF2VlanEntry 67108864}

er1645v2EthPrtSwF2VlanPriorityPolicy OBJECT-TYPE
   SYNTAX      DisplayString
   MAX-ACCESS  read-write
   STATUS      current
   DESCRIPTION
      "Path: swPort.editConf.vlan.priorityPolicy"
   ::= {er1645v2EthPrtSwF2VlanEntry 83886080}

er1645v2EthPrtSwF2VlanIpVrfRouter OBJECT-TYPE
   SYNTAX      DisplayString
   MAX-ACCESS  read-write
   STATUS      current
   DESCRIPTION
      "Path: swPort.editConf.vlan.ip.vrfRouter"
   ::= {er1645v2EthPrtSwF2VlanEntry 53215232}

er1645v2EthPrtSwF2VlanIpAdr OBJECT-TYPE
   SYNTAX      IpAddress
   MAX-ACCESS  read-write
   STATUS      current
   DESCRIPTION
      "Path: swPort.editConf.vlan.ip.address"
   ::= {er1645v2EthPrtSwF2VlanEntry 58261504}

er1645v2EthPrtSwF2VlanIpNetm OBJECT-TYPE
   SYNTAX      IpAddress
   MAX-ACCESS  read-write
   STATUS      current
   DESCRIPTION
      "Path: swPort.editConf.vlan.ip.netMask"
   ::= {er1645v2EthPrtSwF2VlanEntry 58392576}

er1645v2EthPrtSwF2VlanIpSNetName OBJECT-TYPE
   SYNTAX      INTEGER
               {
               slOPTg (0),
               corp (2),
               dmz (3),
               internet (1)
               }
   MAX-ACCESS  read-write
   STATUS      current
   DESCRIPTION
      "Path: swPort.editConf.vlan.ip.sNet.name

       Possibilities:
               <OPT>   (0)
               corp   (2)
               dmz   (3)
               internet   (1)"
   ::= {er1645v2EthPrtSwF2VlanEntry 53674240}

er1645v2EthPrtSwF2VlanIpSNetCust OBJECT-TYPE
   SYNTAX      DisplayString
   MAX-ACCESS  read-write
   STATUS      current
   DESCRIPTION
      "Path: swPort.editConf.vlan.ip.sNet.custom"
   ::= {er1645v2EthPrtSwF2VlanEntry 53674496}

er1645v2EthPrtSwF2VlanIpDhcpC OBJECT-TYPE
   SYNTAX      INTEGER
               {
               disabled (0),
               enabled (1)
               }
   MAX-ACCESS  read-write
   STATUS      current
   DESCRIPTION
      "Path: swPort.editConf.vlan.ip.dhcpClient

       Possibilities:
               disabled   (0)
               enabled   (1)"
   ::= {er1645v2EthPrtSwF2VlanEntry 53608448}

er1645v2EthPrtSwF2VlanIpDhcpGatewayPreference OBJECT-TYPE
   SYNTAX      Integer32
   MAX-ACCESS  read-write
   STATUS      current
   DESCRIPTION
      "Path: swPort.editConf.vlan.ip.dhcp.gatewayPreference"
   ::= {er1645v2EthPrtSwF2VlanEntry 53739776}

er1645v2EthPrtSwF2VlanIpDhcpRoutePreference OBJECT-TYPE
   SYNTAX      Integer32
   MAX-ACCESS  read-write
   STATUS      current
   DESCRIPTION
      "Path: swPort.editConf.vlan.ip.dhcp.routePreference"
   ::= {er1645v2EthPrtSwF2VlanEntry 53740032}

er1645v2EthPrtSwF2VlanIpDhcpDnsPreference OBJECT-TYPE
   SYNTAX      Integer32
   MAX-ACCESS  read-write
   STATUS      current
   DESCRIPTION
      "Path: swPort.editConf.vlan.ip.dhcp.dnsPreference"
   ::= {er1645v2EthPrtSwF2VlanEntry 53740288}

er1645v2EthPrtSwF2VlanIpMtu OBJECT-TYPE
   SYNTAX      Integer32
   MAX-ACCESS  read-write
   STATUS      current
   DESCRIPTION
      "Path: swPort.editConf.vlan.ip.mtu"
   ::= {er1645v2EthPrtSwF2VlanEntry 52953088}

er1645v2EthPrtSwF2VlanIpMssAdjust OBJECT-TYPE
   SYNTAX      INTEGER
               {
               disabled (0),
               auto (65536)
               }
   MAX-ACCESS  read-write
   STATUS      current
   DESCRIPTION
      "Path: swPort.editConf.vlan.ip.mssAdjust

       Possibilities:
               disabled   (0)
               auto   (65536)"
   ::= {er1645v2EthPrtSwF2VlanEntry 53280768}

er1645v2EthPrtSwF2VlanIpRipMetric OBJECT-TYPE
   SYNTAX      Integer32
   MAX-ACCESS  read-write
   STATUS      current
   DESCRIPTION
      "Path: swPort.editConf.vlan.ip.rip.metric"
   ::= {er1645v2EthPrtSwF2VlanEntry 51712768}

er1645v2EthPrtSwF2VlanIpRipMetricOut OBJECT-TYPE
   SYNTAX      Integer32
   MAX-ACCESS  read-write
   STATUS      current
   DESCRIPTION
      "Path: swPort.editConf.vlan.ip.rip.metricOut"
   ::= {er1645v2EthPrtSwF2VlanEntry 51713024}

er1645v2EthPrtSwF2VlanIpRipMode OBJECT-TYPE
   SYNTAX      INTEGER
               {
               disabled (0),
               passive (1),
               active (2)
               }
   MAX-ACCESS  read-write
   STATUS      current
   DESCRIPTION
      "Path: swPort.editConf.vlan.ip.rip.mode

       Possibilities:
               disabled   (0)
               passive   (1)
               active   (2)"
   ::= {er1645v2EthPrtSwF2VlanEntry 51713280}

er1645v2EthPrtSwF2VlanIpRipTxVer OBJECT-TYPE
   SYNTAX      INTEGER
               {
               rip1 (0),
               rip2 (1),
               rip1mcompatible (2)
               }
   MAX-ACCESS  read-write
   STATUS      current
   DESCRIPTION
      "Path: swPort.editConf.vlan.ip.rip.txVersion

       Possibilities:
               rip1   (0)
               rip2   (1)
               rip1-compatible   (2)"
   ::= {er1645v2EthPrtSwF2VlanEntry 51716864}

er1645v2EthPrtSwF2VlanIpRipRxVer OBJECT-TYPE
   SYNTAX      INTEGER
               {
               rip1only (0),
               rip2only (1),
               rip12 (2)
               }
   MAX-ACCESS  read-write
   STATUS      current
   DESCRIPTION
      "Path: swPort.editConf.vlan.ip.rip.rxVersion

       Possibilities:
               rip1only   (0)
               rip2only   (1)
               rip1&2   (2)"
   ::= {er1645v2EthPrtSwF2VlanEntry 51717120}

er1645v2EthPrtSwF2VlanIpRipSplitH OBJECT-TYPE
   SYNTAX      INTEGER
               {
               disabled (0),
               enabled (1),
               poisonedReverse (2)
               }
   MAX-ACCESS  read-write
   STATUS      current
   DESCRIPTION
      "Path: swPort.editConf.vlan.ip.rip.splitHorizon

       Possibilities:
               disabled   (0)
               enabled   (1)
               poisonedReverse   (2)"
   ::= {er1645v2EthPrtSwF2VlanEntry 51713792}

er1645v2EthPrtSwF2VlanIpRipAuth OBJECT-TYPE
   SYNTAX      INTEGER
               {
               disabled (0),
               texts (1),
               md5 (2)
               }
   MAX-ACCESS  read-write
   STATUS      current
   DESCRIPTION
      "Path: swPort.editConf.vlan.ip.rip.authentication

       Possibilities:
               disabled   (0)
               text    (1)
               md5   (2)"
   ::= {er1645v2EthPrtSwF2VlanEntry 51712512}

er1645v2EthPrtSwF2VlanIpRipFilter OBJECT-TYPE
   SYNTAX      DisplayString
   MAX-ACCESS  read-write
   STATUS      current
   DESCRIPTION
      "Path: swPort.editConf.vlan.ip.rip.filter"
   ::= {er1645v2EthPrtSwF2VlanEntry 51716096}

er1645v2EthPrtSwF2VlanIpRipFilterIn OBJECT-TYPE
   SYNTAX      DisplayString
   MAX-ACCESS  read-write
   STATUS      current
   DESCRIPTION
      "Path: swPort.editConf.vlan.ip.rip.filterIn"
   ::= {er1645v2EthPrtSwF2VlanEntry 51716352}

er1645v2EthPrtSwF2VlanIpRipClearNextHop OBJECT-TYPE
   SYNTAX      INTEGER
               {
               disabled (0),
               enabled (1)
               }
   MAX-ACCESS  read-write
   STATUS      current
   DESCRIPTION
      "Path: swPort.editConf.vlan.ip.rip.clearNextHop

       Possibilities:
               disabled   (0)
               enabled   (1)"
   ::= {er1645v2EthPrtSwF2VlanEntry 51708416}

er1645v2EthPrtSwF2VlanIpAccPol OBJECT-TYPE
   SYNTAX      DisplayString
   MAX-ACCESS  read-write
   STATUS      current
   DESCRIPTION
      "Path: swPort.editConf.vlan.ip.accessPolicy"
   ::= {er1645v2EthPrtSwF2VlanEntry 53084160}

er1645v2EthPrtSwF2VlanIpAB OBJECT-TYPE
   SYNTAX      DisplayString
   MAX-ACCESS  read-write
   STATUS      current
   DESCRIPTION
      "Path: swPort.editConf.vlan.ip.trafficPolicy"
   ::= {er1645v2EthPrtSwF2VlanEntry 51249152}

er1645v2EthPrtSwF2VlanIpMA OBJECT-TYPE
   SYNTAX      INTEGER
               {
               disabled (0),
               enabled (1)
               }
   MAX-ACCESS  read-write
   STATUS      current
   DESCRIPTION
      "Path: swPort.editConf.vlan.ip.mgmtAccess

       Possibilities:
               disabled   (0)
               enabled   (1)"
   ::= {er1645v2EthPrtSwF2VlanEntry 51380224}

er1645v2EthPrtSwF2VlanIpMF OBJECT-TYPE
   SYNTAX      Integer32
   MAX-ACCESS  read-write
   STATUS      current
   DESCRIPTION
      "Path: swPort.editConf.vlan.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2EthPrtSwF2VlanEntry 51445760}

er1645v2EthPrtSwF2VlanIpDB OBJECT-TYPE
   SYNTAX      INTEGER
               {
               disabled (0),
               enabled (1)
               }
   MAX-ACCESS  read-write
   STATUS      current
   DESCRIPTION
      "Path: swPort.editConf.vlan.ip.directedBroadcasts

       Possibilities:
               disabled   (0)
               enabled   (1)"
   ::= {er1645v2EthPrtSwF2VlanEntry 51773440}

er1645v2EthPrtSwF2VlanIpIR OBJECT-TYPE
   SYNTAX      INTEGER
               {
               disabled (0),
               enabled (1)
               }
   MAX-ACCESS  read-write
   STATUS      current
   DESCRIPTION
      "Path: swPort.editConf.vlan.ip.icmpRedirects

       Possibilities:
               disabled   (0)
               enabled   (1)"
   ::= {er1645v2EthPrtSwF2VlanEntry 52035584}

er1645v2EthPrtSwF2VlanIpIgmp OBJECT-TYPE
   SYNTAX      INTEGER
               {
               disabled (0),
               proxy (1),
               router (2),
               v3Router (5)
               }
   MAX-ACCESS  read-write
   STATUS      current
   DESCRIPTION
      "Path: swPort.editConf.vlan.ip.igmp

       Possibilities:
               disabled   (0)
               proxy   (1)
               router   (2)
               v3Router   (5)"
   ::= {er1645v2EthPrtSwF2VlanEntry 52428800}

er1645v2EthPrtSwF2VlanIpNN OBJECT-TYPE
   SYNTAX      DisplayString
   MAX-ACCESS  read-write
   STATUS      current
   DESCRIPTION
      "Path: swPort.editConf.vlan.ip.nat"
   ::= {er1645v2EthPrtSwF2VlanEntry 52101120}

er1645v2EthPrtSwF2VlanIpVrrp OBJECT-TYPE
   SYNTAX      INTEGER
               {
               disabled (0),
               enabled (1)
               }
   MAX-ACCESS  read-write
   STATUS      current
   DESCRIPTION
      "Path: swPort.editConf.vlan.ip.vrrp

       Possibilities:
               disabled   (0)
               enabled   (1)"
   ::= {er1645v2EthPrtSwF2VlanEntry 53149696}

er1645v2EthPrtSwF2VlanIpPimMode OBJECT-TYPE
   SYNTAX      INTEGER
               {
               disabled (0),
               sparse (1),
               passive (2)
               }
   MAX-ACCESS  read-write
   STATUS      current
   DESCRIPTION
      "Path: swPort.editConf.vlan.ip.pim.mode

       Possibilities:
               disabled   (0)
               sparse   (1)
               passive   (2)"
   ::= {er1645v2EthPrtSwF2VlanEntry 53346560}

er1645v2EthPrtSwF2VlanIpPimDrPriority OBJECT-TYPE
   SYNTAX      Counter32
   MAX-ACCESS  read-write
   STATUS      current
   DESCRIPTION
      "Path: swPort.editConf.vlan.ip.pim.drPriority

       32 bit unsigned wrappable counter."
   ::= {er1645v2EthPrtSwF2VlanEntry 53346816}

er1645v2EthPrtSwF2VlanIpPimHelloTime OBJECT-TYPE
   SYNTAX      TimeTicks
   MAX-ACCESS  read-write
   STATUS      current
   DESCRIPTION
      "Path: swPort.editConf.vlan.ip.pim.helloTime

       Time in centi-second."
   ::= {er1645v2EthPrtSwF2VlanEntry 53347072}

er1645v2EthPrtSwF2VlanIpPimPropagationDelay OBJECT-TYPE
   SYNTAX      TimeTicks
   MAX-ACCESS  read-write
   STATUS      current
   DESCRIPTION
      "Path: swPort.editConf.vlan.ip.pim.propagationDelay

       Time in centi-second."
   ::= {er1645v2EthPrtSwF2VlanEntry 53347328}

er1645v2EthPrtSwF2VlanIpPimOverrideInterval OBJECT-TYPE
   SYNTAX      TimeTicks
   MAX-ACCESS  read-write
   STATUS      current
   DESCRIPTION
      "Path: swPort.editConf.vlan.ip.pim.overrideInterval

       Time in centi-second."
   ::= {er1645v2EthPrtSwF2VlanEntry 53347584}

er1645v2EthPrtSwF2VlanIpPimBsrBorder OBJECT-TYPE
   SYNTAX      INTEGER
               {
               disabled (0),
               enabled (1)
               }
   MAX-ACCESS  read-write
   STATUS      current
   DESCRIPTION
      "Path: swPort.editConf.vlan.ip.pim.bsrBorder

       Possibilities:
               disabled   (0)
               enabled   (1)"
   ::= {er1645v2EthPrtSwF2VlanEntry 53347840}

er1645v2EthPrtSwF2VlanIpPimTtlThreshold OBJECT-TYPE
   SYNTAX      Integer32
   MAX-ACCESS  read-write
   STATUS      current
   DESCRIPTION
      "Path: swPort.editConf.vlan.ip.pim.ttlThreshold"
   ::= {er1645v2EthPrtSwF2VlanEntry 53348096}

er1645v2EthPrtSwF2VlanIpIMNetworkUnreachable OBJECT-TYPE
   SYNTAX      INTEGER
               {
               disabled (0),
               enabled (1)
               }
   MAX-ACCESS  read-write
   STATUS      current
   DESCRIPTION
      "Path: swPort.editConf.vlan.ip.icmpMessages.networkUnreachable

       Possibilities:
               disabled   (0)
               enabled   (1)"
   ::= {er1645v2EthPrtSwF2VlanEntry 53412096}

er1645v2EthPrtSwF2VlanIpIMHostUnreachable OBJECT-TYPE
   SYNTAX      INTEGER
               {
               disabled (0),
               enabled (1)
               }
   MAX-ACCESS  read-write
   STATUS      current
   DESCRIPTION
      "Path: swPort.editConf.vlan.ip.icmpMessages.hostUnreachable

       Possibilities:
               disabled   (0)
               enabled   (1)"
   ::= {er1645v2EthPrtSwF2VlanEntry 53412352}

er1645v2EthPrtSwF2VlanIpIMProtocolUnreachable OBJECT-TYPE
   SYNTAX      INTEGER
               {
               disabled (0),
               enabled (1)
               }
   MAX-ACCESS  read-write
   STATUS      current
   DESCRIPTION
      "Path: swPort.editConf.vlan.ip.icmpMessages.protocolUnreachable

       Possibilities:
               disabled   (0)
               enabled   (1)"
   ::= {er1645v2EthPrtSwF2VlanEntry 53412608}

er1645v2EthPrtSwF2VlanIpIMPortUnreachable OBJECT-TYPE
   SYNTAX      INTEGER
               {
               disabled (0),
               enabled (1)
               }
   MAX-ACCESS  read-write
   STATUS      current
   DESCRIPTION
      "Path: swPort.editConf.vlan.ip.icmpMessages.portUnreachable

       Possibilities:
               disabled   (0)
               enabled   (1)"
   ::= {er1645v2EthPrtSwF2VlanEntry 53412864}

er1645v2EthPrtSwF2VlanIpIMMtuExceeded OBJECT-TYPE
   SYNTAX      INTEGER
               {
               disabled (0),
               enabled (1)
               }
   MAX-ACCESS  read-write
   STATUS      current
   DESCRIPTION
      "Path: swPort.editConf.vlan.ip.icmpMessages.mtuExceeded

       Possibilities:
               disabled   (0)
               enabled   (1)"
   ::= {er1645v2EthPrtSwF2VlanEntry 53413120}

er1645v2EthPrtSwF2VlanIpIMAdminProhibited OBJECT-TYPE
   SYNTAX      INTEGER
               {
               disabled (0),
               enabled (1)
               }
   MAX-ACCESS  read-write
   STATUS      current
   DESCRIPTION
      "Path: swPort.editConf.vlan.ip.icmpMessages.adminProhibited

       Possibilities:
               disabled   (0)
               enabled   (1)"
   ::= {er1645v2EthPrtSwF2VlanEntry 53413376}

er1645v2EthPrtSwF2VlanIpIMTtlExceeded OBJECT-TYPE
   SYNTAX      INTEGER
               {
               disabled (0),
               enabled (1)
               }
   MAX-ACCESS  read-write
   STATUS      current
   DESCRIPTION
      "Path: swPort.editConf.vlan.ip.icmpMessages.ttlExceeded

       Possibilities:
               disabled   (0)
               enabled   (1)"
   ::= {er1645v2EthPrtSwF2VlanEntry 53413632}

er1645v2EthPrtSwF2VlanIpIMRedirect OBJECT-TYPE
   SYNTAX      INTEGER
               {
               disabled (0),
               enabled (1)
               }
   MAX-ACCESS  read-write
   STATUS      current
   DESCRIPTION
      "Path: swPort.editConf.vlan.ip.icmpMessages.redirect

       Possibilities:
               disabled   (0)
               enabled   (1)"
   ::= {er1645v2EthPrtSwF2VlanEntry 53413888}

er1645v2EthPrtSwF2VlanIpV6VrfRouter OBJECT-TYPE
   SYNTAX      DisplayString
   MAX-ACCESS  read-write
   STATUS      current
   DESCRIPTION
      "Path: swPort.editConf.vlan.ipV6.vrfRouter"
   ::= {er1645v2EthPrtSwF2VlanEntry 704708608}

er1645v2EthPrtSwF2VlanIpV6AddrAutoConfigNrDupAddrDetects OBJECT-TYPE
   SYNTAX      Integer32
   MAX-ACCESS  read-write
   STATUS      current
   DESCRIPTION
      "Path: swPort.editConf.vlan.ipV6.addrAutoConfig.nrDupAddrDetects"
   ::= {er1645v2EthPrtSwF2VlanEntry 704905472}

er1645v2EthPrtSwF2VlanIpV6AddrAutoConfigAcceptRa OBJECT-TYPE
   SYNTAX      INTEGER
               {
               disabled (0),
               enabled (1)
               }
   MAX-ACCESS  read-write
   STATUS      current
   DESCRIPTION
      "Path: swPort.editConf.vlan.ipV6.addrAutoConfig.acceptRa

       Possibilities:
               disabled   (0)
               enabled   (1)"
   ::= {er1645v2EthPrtSwF2VlanEntry 704905728}

er1645v2EthPrtSwF2VlanIpV6AddrAutoConfigAcceptRaRdnss OBJECT-TYPE
   SYNTAX      INTEGER
               {
               disabled (0),
               enabled (1)
               }
   MAX-ACCESS  read-write
   STATUS      current
   DESCRIPTION
      "Path: swPort.editConf.vlan.ipV6.addrAutoConfig.acceptRaRdnss

       Possibilities:
               disabled   (0)
               enabled   (1)"
   ::= {er1645v2EthPrtSwF2VlanEntry 704905984}

er1645v2EthPrtSwF2VlanIpV6AddrAutoConfigAcceptRaDnssl OBJECT-TYPE
   SYNTAX      INTEGER
               {
               disabled (0),
               enabled (1)
               }
   MAX-ACCESS  read-write
   STATUS      current
   DESCRIPTION
      "Path: swPort.editConf.vlan.ipV6.addrAutoConfig.acceptRaDnssl

       Possibilities:
               disabled   (0)
               enabled   (1)"
   ::= {er1645v2EthPrtSwF2VlanEntry 704906240}

er1645v2EthPrtSwF2VlanIpV6DefaultRoute OBJECT-TYPE
   SYNTAX      INTEGER
               {
               disabled (0),
               enabled (1)
               }
   MAX-ACCESS  read-write
   STATUS      current
   DESCRIPTION
      "Path: swPort.editConf.vlan.ipV6.defaultRoute

       Possibilities:
               disabled   (0)
               enabled   (1)"
   ::= {er1645v2EthPrtSwF2VlanEntry 704970752}

er1645v2EthPrtSwF2VlanIpV6RaSend OBJECT-TYPE
   SYNTAX      INTEGER
               {
               disabled (0),
               enabled (1)
               }
   MAX-ACCESS  read-write
   STATUS      current
   DESCRIPTION
      "Path: swPort.editConf.vlan.ipV6.ra.send

       Possibilities:
               disabled   (0)
               enabled   (1)"
   ::= {er1645v2EthPrtSwF2VlanEntry 705036544}

er1645v2EthPrtSwF2VlanIpV6RaMinInterval OBJECT-TYPE
   SYNTAX      TimeTicks
   MAX-ACCESS  read-write
   STATUS      current
   DESCRIPTION
      "Path: swPort.editConf.vlan.ipV6.ra.minInterval

       Time in centi-second."
   ::= {er1645v2EthPrtSwF2VlanEntry 705036800}

er1645v2EthPrtSwF2VlanIpV6RaMaxInterval OBJECT-TYPE
   SYNTAX      TimeTicks
   MAX-ACCESS  read-write
   STATUS      current
   DESCRIPTION
      "Path: swPort.editConf.vlan.ipV6.ra.maxInterval

       Time in centi-second."
   ::= {er1645v2EthPrtSwF2VlanEntry 705037056}

er1645v2EthPrtSwF2VlanIpV6RaManagedFlag OBJECT-TYPE
   SYNTAX      INTEGER
               {
               disabled (0),
               enabled (1)
               }
   MAX-ACCESS  read-write
   STATUS      current
   DESCRIPTION
      "Path: swPort.editConf.vlan.ipV6.ra.managedFlag

       Possibilities:
               disabled   (0)
               enabled   (1)"
   ::= {er1645v2EthPrtSwF2VlanEntry 705037312}

er1645v2EthPrtSwF2VlanIpV6RaOtherConfFlag OBJECT-TYPE
   SYNTAX      INTEGER
               {
               disabled (0),
               enabled (1)
               }
   MAX-ACCESS  read-write
   STATUS      current
   DESCRIPTION
      "Path: swPort.editConf.vlan.ipV6.ra.otherConfFlag

       Possibilities:
               disabled   (0)
               enabled   (1)"
   ::= {er1645v2EthPrtSwF2VlanEntry 705037568}

er1645v2EthPrtSwF2VlanIpV6RaLinkMtu OBJECT-TYPE
   SYNTAX      Integer32
   MAX-ACCESS  read-write
   STATUS      current
   DESCRIPTION
      "Path: swPort.editConf.vlan.ipV6.ra.linkMtu"
   ::= {er1645v2EthPrtSwF2VlanEntry 705037824}

er1645v2EthPrtSwF2VlanIpV6RaReachableTime OBJECT-TYPE
   SYNTAX      TimeTicks
   MAX-ACCESS  read-write
   STATUS      current
   DESCRIPTION
      "Path: swPort.editConf.vlan.ipV6.ra.reachableTime

       Time in centi-second."
   ::= {er1645v2EthPrtSwF2VlanEntry 705038080}

er1645v2EthPrtSwF2VlanIpV6RaRetransmitTime OBJECT-TYPE
   SYNTAX      TimeTicks
   MAX-ACCESS  read-write
   STATUS      current
   DESCRIPTION
      "Path: swPort.editConf.vlan.ipV6.ra.retransmitTime

       Time in centi-second."
   ::= {er1645v2EthPrtSwF2VlanEntry 705038336}

er1645v2EthPrtSwF2VlanIpV6RaHopLimit OBJECT-TYPE
   SYNTAX      Integer32
   MAX-ACCESS  read-write
   STATUS      current
   DESCRIPTION
      "Path: swPort.editConf.vlan.ipV6.ra.hopLimit"
   ::= {er1645v2EthPrtSwF2VlanEntry 705038592}

er1645v2EthPrtSwF2VlanIpV6RaDefaultLifeTime OBJECT-TYPE
   SYNTAX      TimeTicks
   MAX-ACCESS  read-write
   STATUS      current
   DESCRIPTION
      "Path: swPort.editConf.vlan.ipV6.ra.defaultLifeTime

       Time in centi-second."
   ::= {er1645v2EthPrtSwF2VlanEntry 705038848}

er1645v2EthPrtSwF2VlanIpV6RaDnsOptionsRdnssLifeTime OBJECT-TYPE
   SYNTAX      TimeTicks
   MAX-ACCESS  read-write
   STATUS      current
   DESCRIPTION
      "Path: swPort.editConf.vlan.ipV6.ra.dnsOptions.rdnss.lifeTime

       Time in centi-second."
   ::= {er1645v2EthPrtSwF2VlanEntry 705039140}

er1645v2EthPrtSwF2VlanIpV6RaDnsOptionsRdnssImportServers OBJECT-TYPE
   SYNTAX      INTEGER
               {
               disabled (0),
               enabled (1)
               }
   MAX-ACCESS  read-write
   STATUS      current
   DESCRIPTION
      "Path: swPort.editConf.vlan.ipV6.ra.dnsOptions.rdnss.importServers

       Possibilities:
               disabled   (0)
               enabled   (1)"
   ::= {er1645v2EthPrtSwF2VlanEntry 705039148}

er1645v2EthPrtSwF2VlanIpV6RaDnsOptionsDnsslLifeTime OBJECT-TYPE
   SYNTAX      TimeTicks
   MAX-ACCESS  read-write
   STATUS      current
   DESCRIPTION
      "Path: swPort.editConf.vlan.ipV6.ra.dnsOptions.dnssl.lifeTime

       Time in centi-second."
   ::= {er1645v2EthPrtSwF2VlanEntry 705039172}

er1645v2EthPrtSwF2VlanIpV6RaDnsOptionsDnsslImportDomains OBJECT-TYPE
   SYNTAX      INTEGER
               {
               disabled (0),
               enabled (1)
               }
   MAX-ACCESS  read-write
   STATUS      current
   DESCRIPTION
      "Path: swPort.editConf.vlan.ipV6.ra.dnsOptions.dnssl.importDomains

       Possibilities:
               disabled   (0)
               enabled   (1)"
   ::= {er1645v2EthPrtSwF2VlanEntry 705039180}

er1645v2EthPrtSwF2VlanIpV6RsSend OBJECT-TYPE
   SYNTAX      INTEGER
               {
               disabled (0),
               enabled (1)
               }
   MAX-ACCESS  read-write
   STATUS      current
   DESCRIPTION
      "Path: swPort.editConf.vlan.ipV6.rs.send

       Possibilities:
               disabled   (0)
               enabled   (1)"
   ::= {er1645v2EthPrtSwF2VlanEntry 705954048}

er1645v2EthPrtSwF2VlanIpV6RsMaxRandomDelay OBJECT-TYPE
   SYNTAX      TimeTicks
   MAX-ACCESS  read-write
   STATUS      current
   DESCRIPTION
      "Path: swPort.editConf.vlan.ipV6.rs.maxRandomDelay

       Time in centi-second."
   ::= {er1645v2EthPrtSwF2VlanEntry 705954304}

er1645v2EthPrtSwF2VlanIpV6RsInterval OBJECT-TYPE
   SYNTAX      TimeTicks
   MAX-ACCESS  read-write
   STATUS      current
   DESCRIPTION
      "Path: swPort.editConf.vlan.ipV6.rs.interval

       Time in centi-second."
   ::= {er1645v2EthPrtSwF2VlanEntry 705954560}

er1645v2EthPrtSwF2VlanIpV6RsMaxSolicitations OBJECT-TYPE
   SYNTAX      Integer32
   MAX-ACCESS  read-write
   STATUS      current
   DESCRIPTION
      "Path: swPort.editConf.vlan.ipV6.rs.maxSolicitations"
   ::= {er1645v2EthPrtSwF2VlanEntry 705954816}

er1645v2EthPrtSwF2VlanIpV6TrafficPolicyInbound OBJECT-TYPE
   SYNTAX      DisplayString
   MAX-ACCESS  read-write
   STATUS      current
   DESCRIPTION
      "Path: swPort.editConf.vlan.ipV6.trafficPolicy.inbound"
   ::= {er1645v2EthPrtSwF2VlanEntry 705364224}

er1645v2EthPrtSwF2VlanIpV6TrafficPolicyOutbound OBJECT-TYPE
   SYNTAX      DisplayString
   MAX-ACCESS  read-write
   STATUS      current
   DESCRIPTION
      "Path: swPort.editConf.vlan.ipV6.trafficPolicy.outbound"
   ::= {er1645v2EthPrtSwF2VlanEntry 705364480}

er1645v2EthPrtSwF2VlanIpV6FirewallZone OBJECT-TYPE
   SYNTAX      DisplayString
   MAX-ACCESS  read-write
   STATUS      current
   DESCRIPTION
      "Path: swPort.editConf.vlan.ipV6.firewall.zone"
   ::= {er1645v2EthPrtSwF2VlanEntry 705429760}

er1645v2EthPrtSwF2VlanIpV6DhcpClientAddrAC OBJECT-TYPE
   SYNTAX      INTEGER
               {
               disabled (0),
               enabled (1)
               }
   MAX-ACCESS  read-write
   STATUS      current
   DESCRIPTION
      "Path: swPort.editConf.vlan.ipV6.dhcp.client.addrAutoConfig

       Possibilities:
               disabled   (0)
               enabled   (1)"
   ::= {er1645v2EthPrtSwF2VlanEntry 705307648}

er1645v2EthPrtSwF2VlanIpV6DhcpClientPrDelMode OBJECT-TYPE
   SYNTAX      INTEGER
               {
               disabled (0),
               enabled (1)
               }
   MAX-ACCESS  read-write
   STATUS      current
   DESCRIPTION
      "Path: swPort.editConf.vlan.ipV6.dhcp.client.pd.mode

       Possibilities:
               disabled   (0)
               enabled   (1)"
   ::= {er1645v2EthPrtSwF2VlanEntry 705308676}

er1645v2EthPrtSwF2VlanIpV6DhcpClientPrDelPool OBJECT-TYPE
   SYNTAX      DisplayString
   MAX-ACCESS  read-write
   STATUS      current
   DESCRIPTION
      "Path: swPort.editConf.vlan.ipV6.dhcp.client.pd.pool"
   ::= {er1645v2EthPrtSwF2VlanEntry 705308680}

er1645v2EthPrtSwF2VlanIpV6DhcpClientPrDelPdExclOpt OBJECT-TYPE
   SYNTAX      INTEGER
               {
               disabled (0),
               enabled (1)
               }
   MAX-ACCESS  read-write
   STATUS      current
   DESCRIPTION
      "Path: swPort.editConf.vlan.ipV6.dhcp.client.pd.pdExclOpt

       Possibilities:
               disabled   (0)
               enabled   (1)"
   ::= {er1645v2EthPrtSwF2VlanEntry 705308684}

er1645v2EthPrtSwF2VlanIpV6DhcpClientDnsServerPref OBJECT-TYPE
   SYNTAX      Integer32
   MAX-ACCESS  read-write
   STATUS      current
   DESCRIPTION
      "Path: swPort.editConf.vlan.ipV6.dhcp.client.dns.serverPref"
   ::= {er1645v2EthPrtSwF2VlanEntry 705310724}

er1645v2EthPrtSwF2VlanIpV6DhcpClientRapidCommit OBJECT-TYPE
   SYNTAX      INTEGER
               {
               disabled (0),
               enabled (1)
               }
   MAX-ACCESS  read-write
   STATUS      current
   DESCRIPTION
      "Path: swPort.editConf.vlan.ipV6.dhcp.client.rapidCommit

       Possibilities:
               disabled   (0)
               enabled   (1)"
   ::= {er1645v2EthPrtSwF2VlanEntry 705309696}

er1645v2EthPrtSwF2VlanIpV6DhcpClientTimersSolTimeOut OBJECT-TYPE
   SYNTAX      TimeTicks
   MAX-ACCESS  read-write
   STATUS      current
   DESCRIPTION
      "Path: swPort.editConf.vlan.ipV6.dhcp.client.timers.solTimeOut

       Time in centi-second."
   ::= {er1645v2EthPrtSwF2VlanEntry 705311748}

er1645v2EthPrtSwF2VlanIpV6DhcpClientTimersSolMaxRt OBJECT-TYPE
   SYNTAX      TimeTicks
   MAX-ACCESS  read-write
   STATUS      current
   DESCRIPTION
      "Path: swPort.editConf.vlan.ipV6.dhcp.client.timers.solMaxRt

       Time in centi-second."
   ::= {er1645v2EthPrtSwF2VlanEntry 705311752}

er1645v2EthPrtSwF2VlanIpV6DhcpClientTimersInfoRefresh OBJECT-TYPE
   SYNTAX      TimeTicks
   MAX-ACCESS  read-write
   STATUS      current
   DESCRIPTION
      "Path: swPort.editConf.vlan.ipV6.dhcp.client.timers.infoRefresh

       Time in centi-second."
   ::= {er1645v2EthPrtSwF2VlanEntry 705311756}

er1645v2EthPrtSwF2VlanIpV6DhcpServerMode OBJECT-TYPE
   SYNTAX      INTEGER
               {
               disabled (0),
               enabled (1)
               }
   MAX-ACCESS  read-write
   STATUS      current
   DESCRIPTION
      "Path: swPort.editConf.vlan.ipV6.dhcp.server.mode

       Possibilities:
               disabled   (0)
               enabled   (1)"
   ::= {er1645v2EthPrtSwF2VlanEntry 705315840}

er1645v2EthPrtSwF2VlanIpV6DhcpServerPreference OBJECT-TYPE
   SYNTAX      Integer32
   MAX-ACCESS  read-write
   STATUS      current
   DESCRIPTION
      "Path: swPort.editConf.vlan.ipV6.dhcp.server.preference"
   ::= {er1645v2EthPrtSwF2VlanEntry 705316864}

er1645v2EthPrtSwF2VlanIpV6DhcpServerPool OBJECT-TYPE
   SYNTAX      DisplayString
   MAX-ACCESS  read-write
   STATUS      current
   DESCRIPTION
      "Path: swPort.editConf.vlan.ipV6.dhcp.server.pool"
   ::= {er1645v2EthPrtSwF2VlanEntry 705317888}

er1645v2EthPrtSwF2VlanIpV6DhcpServerRapidCommit OBJECT-TYPE
   SYNTAX      INTEGER
               {
               disabled (0),
               enabled (1)
               }
   MAX-ACCESS  read-write
   STATUS      current
   DESCRIPTION
      "Path: swPort.editConf.vlan.ipV6.dhcp.server.rapidCommit

       Possibilities:
               disabled   (0)
               enabled   (1)"
   ::= {er1645v2EthPrtSwF2VlanEntry 705318912}

er1645v2EthPrtSwF2VlanIpV6DhcpServerTimersInfoRefresh OBJECT-TYPE
   SYNTAX      TimeTicks
   MAX-ACCESS  read-write
   STATUS      current
   DESCRIPTION
      "Path: swPort.editConf.vlan.ipV6.dhcp.server.timers.infoRefresh

       Time in centi-second."
   ::= {er1645v2EthPrtSwF2VlanEntry 705319940}

er1645v2EthPrtSwF2VlanIpV6DhcpRelayMode OBJECT-TYPE
   SYNTAX      INTEGER
               {
               disabled (0),
               enabled (1)
               }
   MAX-ACCESS  read-write
   STATUS      current
   DESCRIPTION
      "Path: swPort.editConf.vlan.ipV6.dhcp.relay.mode

       Possibilities:
               disabled   (0)
               enabled   (1)"
   ::= {er1645v2EthPrtSwF2VlanEntry 705323040}

er1645v2EthPrtSwF2VlanIpV6SendRedirect OBJECT-TYPE
   SYNTAX      INTEGER
               {
               disabled (0),
               enabled (1)
               }
   MAX-ACCESS  read-write
   STATUS      current
   DESCRIPTION
      "Path: swPort.editConf.vlan.ipV6.sendRedirect

       Possibilities:
               disabled   (0)
               enabled   (1)"
   ::= {er1645v2EthPrtSwF2VlanEntry 705101824}

er1645v2EthPrtSwF2VlanIpV6LinkMtu OBJECT-TYPE
   SYNTAX      Integer32
   MAX-ACCESS  read-write
   STATUS      current
   DESCRIPTION
      "Path: swPort.editConf.vlan.ipV6.linkMtu"
   ::= {er1645v2EthPrtSwF2VlanEntry 705167360}

er1645v2EthPrtSwF2VlanIpV6InterfaceId OBJECT-TYPE
   SYNTAX      OCTET STRING
   MAX-ACCESS  read-write
   STATUS      current
   DESCRIPTION
      "Path: swPort.editConf.vlan.ipV6.interfaceId"
   ::= {er1645v2EthPrtSwF2VlanEntry 705232896}

er1645v2EthPrtSwF2VlanIpV6MF OBJECT-TYPE
   SYNTAX      Integer32
   MAX-ACCESS  read-write
   STATUS      current
   DESCRIPTION
      "Path: swPort.editConf.vlan.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1645v2EthPrtSwF2VlanEntry 705757184}

er1645v2EthPrtSwF2VlanIpV6IcmpMessagesNoRoute OBJECT-TYPE
   SYNTAX      INTEGER
               {
               disabled (0),
               enabled (1)
               }
   MAX-ACCESS  read-write
   STATUS      current
   DESCRIPTION
      "Path: swPort.editConf.vlan.ipV6.icmpMessages.noRoute

       Possibilities:
               disabled   (0)
               enabled   (1)"
   ::= {er1645v2EthPrtSwF2VlanEntry 705822976}

er1645v2EthPrtSwF2VlanIpV6IcmpMessagesBeyondScope OBJECT-TYPE
   SYNTAX      INTEGER
               {
               disabled (0),
               enabled (1)
               }
   MAX-ACCESS  read-write
   STATUS      current
   DESCRIPTION
      "Path: swPort.editConf.vlan.ipV6.icmpMessages.beyondScope

       Possibilities:
               disabled   (0)
               enabled   (1)"
   ::= {er1645v2EthPrtSwF2VlanEntry 705823488}

er1645v2EthPrtSwF2VlanIpV6IcmpMessagesAddressUnreachable OBJECT-TYPE
   SYNTAX      INTEGER
               {
               disabled (0),
               enabled (1)
               }
   MAX-ACCESS  read-write
   STATUS      current
   DESCRIPTION
      "Path: swPort.editConf.vlan.ipV6.icmpMessages.addressUnreachable

       Possibilities:
               disabled   (0)
               enabled   (1)"
   ::= {er1645v2EthPrtSwF2VlanEntry 705823744}

er1645v2EthPrtSwF2VlanIpV6IcmpMessagesPortUnreachable OBJECT-TYPE
   SYNTAX      INTEGER
               {
               disabled (0),
               enabled (1)
               }
   MAX-ACCESS  read-write
   STATUS      current
   DESCRIPTION
      "Path: swPort.editConf.vlan.ipV6.icmpMessages.portUnreachable

       Possibilities:
               disabled   (0)
               enabled   (1)"
   ::= {er1645v2EthPrtSwF2VlanEntry 705824000}

er1645v2EthPrtSwF2VlanIpV6IcmpMessagesPacketTooBig OBJECT-TYPE
   SYNTAX      INTEGER
               {
               disabled (0),
               enabled (1)
               }
   MAX-ACCESS  read-write
   STATUS      current
   DESCRIPTION
      "Path: swPort.editConf.vlan.ipV6.icmpMessages.packetTooBig

       Possibilities:
               disabled   (0)
               enabled   (1)"
   ::= {er1645v2EthPrtSwF2VlanEntry 705825280}

er1645v2EthPrtSwF2VlanIpV6IcmpMessagesHopLimitExceeded OBJECT-TYPE
   SYNTAX      INTEGER
               {
               disabled (0),
               enabled (1)
               }
   MAX-ACCESS  read-write
   STATUS      current
   DESCRIPTION
      "Path: swPort.editConf.vlan.ipV6.icmpMessages.hopLimitExceeded

       Possibilities:
               disabled   (0)
               enabled   (1)"
   ::= {er1645v2EthPrtSwF2VlanEntry 705827840}

er1645v2EthPrtSwF2VlanIpV6IcmpMessagesFragTimeExceeded OBJECT-TYPE
   SYNTAX      INTEGER
               {
               disabled (0),
               enabled (1)
               }
   MAX-ACCESS  read-write
   STATUS      current
   DESCRIPTION
      "Path: swPort.editConf.vlan.ipV6.icmpMessages.fragTimeExceeded

       Possibilities:
               disabled   (0)
               enabled   (1)"
   ::= {er1645v2EthPrtSwF2VlanEntry 705828096}

er1645v2EthPrtSwF2VlanIpV6IcmpMessagesHeaderFieldErr OBJECT-TYPE
   SYNTAX      INTEGER
               {
               disabled (0),
               enabled (1)
               }
   MAX-ACCESS  read-write
   STATUS      current
   DESCRIPTION
      "Path: swPort.editConf.vlan.ipV6.icmpMessages.headerFieldErr

       Possibilities:
               disabled   (0)
               enabled   (1)"
   ::= {er1645v2EthPrtSwF2VlanEntry 705830400}

er1645v2EthPrtSwF2VlanIpV6IcmpMessagesOptionUnrecognized OBJECT-TYPE
   SYNTAX      INTEGER
               {
               disabled (0),
               enabled (1)
               }
   MAX-ACCESS  read-write
   STATUS      current
   DESCRIPTION
      "Path: swPort.editConf.vlan.ipV6.icmpMessages.optionUnrecognized

       Possibilities:
               disabled   (0)
               enabled   (1)"
   ::= {er1645v2EthPrtSwF2VlanEntry 705830912}

er1645v2EthPrtSwF2VlanIpV6IcmpMessagesRedirect OBJECT-TYPE
   SYNTAX      INTEGER
               {
               disabled (0),
               enabled (1)
               }
   MAX-ACCESS  read-write
   STATUS      current
   DESCRIPTION
      "Path: swPort.editConf.vlan.ipV6.icmpMessages.redirect

       Possibilities:
               disabled   (0)
               enabled   (1)"
   ::= {er1645v2EthPrtSwF2VlanEntry 705832960}

er1645v2EthPrtSwF2VlanBridgingAccList OBJECT-TYPE
   SYNTAX      DisplayString
   MAX-ACCESS  read-write
   STATUS      current
   DESCRIPTION
      "Path: swPort.editConf.vlan.bridging.accessList"
   ::= {er1645v2EthPrtSwF2VlanEntry 453246976}

er1645v2EthPrtSwF2VlanBridgingInACL OBJECT-TYPE
   SYNTAX      DisplayString
   MAX-ACCESS  read-write
   STATUS      current
   DESCRIPTION
      "Path: swPort.editConf.vlan.bridging.inAccessList"
   ::= {er1645v2EthPrtSwF2VlanEntry 456916992}

er1645v2EthPrtSwF2VlanBridgingTp OBJECT-TYPE
   SYNTAX      DisplayString
   MAX-ACCESS  read-write
   STATUS      current
   DESCRIPTION
      "Path: swPort.editConf.vlan.bridging.trafficPolicy"
   ::= {er1645v2EthPrtSwF2VlanEntry 454295552}

er1645v2EthPrtSwF2VlanBridgingBrGrp OBJECT-TYPE
   SYNTAX      DisplayString
   MAX-ACCESS  read-write
   STATUS      current
   DESCRIPTION
      "Path: swPort.editConf.vlan.bridging.bridgeGroup"
   ::= {er1645v2EthPrtSwF2VlanEntry 454819840}

er1645v2EthPrtSwF2VlanBridgingLimBC OBJECT-TYPE
   SYNTAX      INTEGER
               {
               disabled (0),
               enabled (1)
               }
   MAX-ACCESS  read-write
   STATUS      current
   DESCRIPTION
      "Path: swPort.editConf.vlan.bridging.limitBroadcasts

       Possibilities:
               disabled   (0)
               enabled   (1)"
   ::= {er1645v2EthPrtSwF2VlanEntry 455081984}

er1645v2EthPrtSwF2VlanBridgingPrivateMode OBJECT-TYPE
   SYNTAX      INTEGER
               {
               disabled (0),
               enabled (1)
               }
   MAX-ACCESS  read-write
   STATUS      current
   DESCRIPTION
      "Path: swPort.editConf.vlan.bridging.privateMode

       Possibilities:
               disabled   (0)
               enabled   (1)"
   ::= {er1645v2EthPrtSwF2VlanEntry 459538432}

er1645v2EthPrtSwF2VlanBridgingLearning OBJECT-TYPE
   SYNTAX      INTEGER
               {
               disabled (0),
               enabled (1)
               }
   MAX-ACCESS  read-write
   STATUS      current
   DESCRIPTION
      "Path: swPort.editConf.vlan.bridging.learning

       Possibilities:
               disabled   (0)
               enabled   (1)"
   ::= {er1645v2EthPrtSwF2VlanEntry 456130560}

er1645v2EthPrtSwF2VlanBridgingMaxCacheSize OBJECT-TYPE
   SYNTAX      INTEGER
               {
               unlimited (0)
               }
   MAX-ACCESS  read-write
   STATUS      current
   DESCRIPTION
      "Path: swPort.editConf.vlan.bridging.maxCacheSize

       Possibilities:
               unlimited   (0)"
   ::= {er1645v2EthPrtSwF2VlanEntry 456392704}

er1645v2EthPrtSwF2VlanBridgingRelearnDropOnRelearn OBJECT-TYPE
   SYNTAX      INTEGER
               {
               disabled (0),
               enabled (1)
               }
   MAX-ACCESS  read-write
   STATUS      current
   DESCRIPTION
      "Path: swPort.editConf.vlan.bridging.relearn.dropOnRelearn

       Possibilities:
               disabled   (0)
               enabled   (1)"
   ::= {er1645v2EthPrtSwF2VlanEntry 456655872}

er1645v2EthPrtSwF2VlanBridgingRelearnShutdownThreshold OBJECT-TYPE
   SYNTAX      Integer32
   MAX-ACCESS  read-write
   STATUS      current
   DESCRIPTION
      "Path: swPort.editConf.vlan.bridging.relearn.shutdownThreshold"
   ::= {er1645v2EthPrtSwF2VlanEntry 456656896}

er1645v2EthPrtSwF2VlanBridgingRelearnShutdownTime OBJECT-TYPE
   SYNTAX      TimeTicks
   MAX-ACCESS  read-write
   STATUS      current
   DESCRIPTION
      "Path: swPort.editConf.vlan.bridging.relearn.shutdownTime

       Time in centi-second."
   ::= {er1645v2EthPrtSwF2VlanEntry 456657920}

er1645v2EthPrtSwF2VlanBridgingRelearnLoopDetection OBJECT-TYPE
   SYNTAX      INTEGER
               {
               disabled (0),
               passive (1),
               active (2)
               }
   MAX-ACCESS  read-write
   STATUS      current
   DESCRIPTION
      "Path: swPort.editConf.vlan.bridging.relearn.loopDetection

       Possibilities:
               disabled   (0)
               passive   (1)
               active   (2)"
   ::= {er1645v2EthPrtSwF2VlanEntry 456658944}

er1645v2EthPrtSwF2VlanBridgingRelearnLoopDetectionInterval OBJECT-TYPE
   SYNTAX      TimeTicks
   MAX-ACCESS  read-write
   STATUS      current
   DESCRIPTION
      "Path: swPort.editConf.vlan.bridging.relearn.loopDetectionInterval

       Time in centi-second."
   ::= {er1645v2EthPrtSwF2VlanEntry 456659968}

er1645v2EthPrtSwF2VlanBridgingVlanMemberShip OBJECT-TYPE
   SYNTAX      INTEGER
               {
               all (0),
               none (1),
               grouped (2)
               }
   MAX-ACCESS  read-write
   STATUS      current
   DESCRIPTION
      "Path: swPort.editConf.vlan.bridging.vlanMemberShip

       Possibilities:
               all   (0)
               none   (1)
               grouped   (2)"
   ::= {er1645v2EthPrtSwF2VlanEntry 457965568}

er1645v2EthPrtSwF2VlanBridgingVlTUntaggedAction OBJECT-TYPE
   SYNTAX      INTEGER
               {
               discard (0),
               accept (1),
               tag (2)
               }
   MAX-ACCESS  read-write
   STATUS      current
   DESCRIPTION
      "Path: swPort.editConf.vlan.bridging.vlanTagging.untagged.action

       Possibilities:
               discard   (0)
               accept   (1)
               tag   (2)"
   ::= {er1645v2EthPrtSwF2VlanEntry 459055104}

er1645v2EthPrtSwF2VlanBridgingVlTUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlan.bridging.vlanTagging.untagged.tagInfo.tpid

       Possibilities:
               dot1Q   (33024)
               dot1ad   (34984)
               0x9100   (37120)
               0x9200   (37376)
               0x9300   (37632)"
   ::= {er1645v2EthPrtSwF2VlanEntry 459059712}

er1645v2EthPrtSwF2VlanBridgingVlTUntaggedTagInfoVid OBJECT-TYPE
   SYNTAX      Integer32
   MAX-ACCESS  read-write
   STATUS      current
   DESCRIPTION
      "Path: swPort.editConf.vlan.bridging.vlanTagging.untagged.tagInfo.vid"
   ::= {er1645v2EthPrtSwF2VlanEntry 459060224}

er1645v2EthPrtSwF2VlanBridgingVlTUnknownVlansAction OBJECT-TYPE
   SYNTAX      INTEGER
               {
               discard (0),
               accept (1),
               tag (2)
               }
   MAX-ACCESS  read-write
   STATUS      current
   DESCRIPTION
      "Path: swPort.editConf.vlan.bridging.vlanTagging.unknownVlans.action

       Possibilities:
               discard   (0)
               accept   (1)
               tag   (2)"
   ::= {er1645v2EthPrtSwF2VlanEntry 459120640}

er1645v2EthPrtSwF2VlanBridgingVlTUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlan.bridging.vlanTagging.unknownVlans.tagInfo.tpid

       Possibilities:
               dot1Q   (33024)
               dot1ad   (34984)
               0x9100   (37120)
               0x9200   (37376)
               0x9300   (37632)"
   ::= {er1645v2EthPrtSwF2VlanEntry 459125248}

er1645v2EthPrtSwF2VlanBridgingVlTUnknownVlansTagInfoVid OBJECT-TYPE
   SYNTAX      Integer32
   MAX-ACCESS  read-write
   STATUS      current
   DESCRIPTION
      "Path: swPort.editConf.vlan.bridging.vlanTagging.unknownVlans.tagInfo.vid"
   ::= {er1645v2EthPrtSwF2VlanEntry 459125760}

er1645v2EthPrtSwF2VlanBridgingDot1adType OBJECT-TYPE
   SYNTAX      INTEGER
               {
               slOPTg (0),
               cPort (4),
               sPort (1),
               nni (2)
               }
   MAX-ACCESS  read-write
   STATUS      current
   DESCRIPTION
      "Path: swPort.editConf.vlan.bridging.dot1ad.type

       Possibilities:
               <OPT>   (0)
               cPort   (4)
               sPort   (1)
               nni   (2)"
   ::= {er1645v2EthPrtSwF2VlanEntry 460850176}

er1645v2EthPrtSwF2VlanBridgingPriority OBJECT-TYPE
   SYNTAX      Integer32
   MAX-ACCESS  read-write
   STATUS      current
   DESCRIPTION
      "Path: swPort.editConf.vlan.bridging.priority"
   ::= {er1645v2EthPrtSwF2VlanEntry 453509120}

er1645v2EthPrtSwF2VlanBridgingPathCost OBJECT-TYPE
   SYNTAX      Integer32
   MAX-ACCESS  read-write
   STATUS      current
   DESCRIPTION
      "Path: swPort.editConf.vlan.bridging.pathCost"
   ::= {er1645v2EthPrtSwF2VlanEntry 453771264}

er1645v2EthPrtSwF2VlanBridgingInternalPathCost OBJECT-TYPE
   SYNTAX      Integer32
   MAX-ACCESS  read-write
   STATUS      current
   DESCRIPTION
      "Path: swPort.editConf.vlan.bridging.internalPathCost"
   ::= {er1645v2EthPrtSwF2VlanEntry 457703424}

er1645v2EthPrtSwF2VlanBridgingTCD OBJECT-TYPE
   SYNTAX      INTEGER
               {
               disabled (0),
               enabled (1)
               }
   MAX-ACCESS  read-write
   STATUS      current
   DESCRIPTION
      "Path: swPort.editConf.vlan.bridging.topologyChangeDetection

       Possibilities:
               disabled   (0)
               enabled   (1)"
   ::= {er1645v2EthPrtSwF2VlanEntry 454033408}

er1645v2EthPrtSwF2VlanBridgingRestrictedRole OBJECT-TYPE
   SYNTAX      INTEGER
               {
               disabled (0),
               enabled (1)
               }
   MAX-ACCESS  read-write
   STATUS      current
   DESCRIPTION
      "Path: swPort.editConf.vlan.bridging.restrictedRole

       Possibilities:
               disabled   (0)
               enabled   (1)"
   ::= {er1645v2EthPrtSwF2VlanEntry 458227712}

er1645v2EthPrtSwF2VlanBridgingAdminEdge OBJECT-TYPE
   SYNTAX      INTEGER
               {
               disabled (0),
               enabled (1)
               }
   MAX-ACCESS  read-write
   STATUS      current
   DESCRIPTION
      "Path: swPort.editConf.vlan.bridging.adminEdge

       Possibilities:
               disabled   (0)
               enabled   (1)"
   ::= {er1645v2EthPrtSwF2VlanEntry 457179136}

er1645v2EthPrtSwF2VlanBridgingOamMacDeviceMac OBJECT-TYPE
   SYNTAX      DisplayString
   MAX-ACCESS  read-write
   STATUS      current
   DESCRIPTION
      "Path: swPort.editConf.vlan.bridging.ethOam.macAddress.deviceMac"
   ::= {er1645v2EthPrtSwF2VlanEntry 458506496}

er1645v2EthPrtSwF2VlanBridgingOamMacUserMac OBJECT-TYPE
   SYNTAX      OCTET STRING
   MAX-ACCESS  read-write
   STATUS      current
   DESCRIPTION
      "Path: swPort.editConf.vlan.bridging.ethOam.macAddress.userMac

       MAC address."
   ::= {er1645v2EthPrtSwF2VlanEntry 458506368}

er1645v2EthPrtSwF2VlanBridgingOamMacBridgeMac OBJECT-TYPE
   SYNTAX      DisplayString
   MAX-ACCESS  read-write
   STATUS      current
   DESCRIPTION
      "Path: swPort.editConf.vlan.bridging.ethOam.macAddress.bridgeMac"
   ::= {er1645v2EthPrtSwF2VlanEntry 458506432}

er1645v2EthPrtSwF2VlanBridgingMgmtInline OBJECT-TYPE
   SYNTAX      INTEGER
               {
               disabled (0),
               enabled (1)
               }
   MAX-ACCESS  read-write
   STATUS      current
   DESCRIPTION
      "Path: swPort.editConf.vlan.bridging.mgmtInline

       Possibilities:
               disabled   (0)
               enabled   (1)"
   ::= {er1645v2EthPrtSwF2VlanEntry 458752000}

er1645v2EthPrtSwF2VlanBridgingL2ptMode OBJECT-TYPE
   SYNTAX      INTEGER
               {
               disabled (0),
               enabled (1)
               }
   MAX-ACCESS  read-write
   STATUS      current
   DESCRIPTION
      "Path: swPort.editConf.vlan.bridging.l2ProtTunnel.mode

       Possibilities:
               disabled   (0)
               enabled   (1)"
   ::= {er1645v2EthPrtSwF2VlanEntry 459292672}

er1645v2EthPrtSwF2VlanBridgingL2ptProtocols OBJECT-TYPE
   SYNTAX      Integer32
   MAX-ACCESS  read-write
   STATUS      current
   DESCRIPTION
      "Path: swPort.editConf.vlan.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1645v2EthPrtSwF2VlanEntry 459309056}

er1645v2EthPrtSwF2VlanBridgingL2ptDestMac OBJECT-TYPE
   SYNTAX      OCTET STRING
   MAX-ACCESS  read-write
   STATUS      current
   DESCRIPTION
      "Path: swPort.editConf.vlan.bridging.l2ProtTunnel.destinationMac

       MAC address."
   ::= {er1645v2EthPrtSwF2VlanEntry 459325440}

er1645v2EthPrtSwF2VlanBridgingL2ptCos OBJECT-TYPE
   SYNTAX      INTEGER
               {
               unchanged (255)
               }
   MAX-ACCESS  read-write
   STATUS      current
   DESCRIPTION
      "Path: swPort.editConf.vlan.bridging.l2ProtTunnel.cos

       Possibilities:
               unchanged   (255)"
   ::= {er1645v2EthPrtSwF2VlanEntry 459341824}

er1645v2EthPrtSwF2VlanBridgingL2ptDropThrStp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.stp

       unit name = packets/sec

       Possibilities:
               unlimited   (0)"
   ::= {er1645v2EthPrtSwF2VlanEntry 459358272}

er1645v2EthPrtSwF2VlanBridgingL2ptDropThrLldp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.lldp

       unit name = packets/sec

       Possibilities:
               unlimited   (0)"
   ::= {er1645v2EthPrtSwF2VlanEntry 459358336}

er1645v2EthPrtSwF2VlanBridgingL2ptDropThrOam OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.oam

       unit name = packets/sec

       Possibilities:
               unlimited   (0)"
   ::= {er1645v2EthPrtSwF2VlanEntry 459358400}

er1645v2EthPrtSwF2VlanBridgingL2ptDropThrCdp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.cdp

       unit name = packets/sec

       Possibilities:
               unlimited   (0)"
   ::= {er1645v2EthPrtSwF2VlanEntry 459358464}

er1645v2EthPrtSwF2VlanBridgingL2ptDropThrVtp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.vtp

       unit name = packets/sec

       Possibilities:
               unlimited   (0)"
   ::= {er1645v2EthPrtSwF2VlanEntry 459358528}

er1645v2EthPrtSwF2VlanBridgingL2ptDropThrLacp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.lacp

       unit name = packets/sec

       Possibilities:
               unlimited   (0)"
   ::= {er1645v2EthPrtSwF2VlanEntry 459358592}

er1645v2EthPrtSwF2VlanBridgingL2ptDropThrEfmOam OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.efmOam

       unit name = packets/sec

       Possibilities:
               unlimited   (0)"
   ::= {er1645v2EthPrtSwF2VlanEntry 459358656}

er1645v2EthPrtSwF2VlanBridgingL2ptDropThrPvst OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.pvst

       unit name = packets/sec

       Possibilities:
               unlimited   (0)"
   ::= {er1645v2EthPrtSwF2VlanEntry 459358720}

er1645v2EthPrtSwF2VlanBridgingL2ptDropThrMmrp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.mmrp

       unit name = packets/sec

       Possibilities:
               unlimited   (0)"
   ::= {er1645v2EthPrtSwF2VlanEntry 459358784}

er1645v2EthPrtSwF2VlanBridgingL2ptDropThrMvrp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.mvrp

       unit name = packets/sec

       Possibilities:
               unlimited   (0)"
   ::= {er1645v2EthPrtSwF2VlanEntry 459358848}

er1645v2EthPrtSwF2VlanBridgingL2ptDropThrGvrp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.gvrp

       unit name = packets/sec

       Possibilities:
               unlimited   (0)"
   ::= {er1645v2EthPrtSwF2VlanEntry 459358912}

er1645v2EthPrtSwF2VlanBridgingL2ptDropThrGmrp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.gmrp

       unit name = packets/sec

       Possibilities:
               unlimited   (0)"
   ::= {er1645v2EthPrtSwF2VlanEntry 459358976}

er1645v2EthPrtSwF2VlanBridgingL2ptDropThrDtp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.dtp

       unit name = packets/sec

       Possibilities:
               unlimited   (0)"
   ::= {er1645v2EthPrtSwF2VlanEntry 459359040}

er1645v2EthPrtSwF2VlanBridgingL2ptDropThrPagp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.pagp

       unit name = packets/sec

       Possibilities:
               unlimited   (0)"
   ::= {er1645v2EthPrtSwF2VlanEntry 459359104}

er1645v2EthPrtSwF2VlanBridgingL2ptDropThrUdld OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.udld

       unit name = packets/sec

       Possibilities:
               unlimited   (0)"
   ::= {er1645v2EthPrtSwF2VlanEntry 459359168}

er1645v2EthPrtSwF2VlanVlanVid OBJECT-TYPE
   SYNTAX      INTEGER
               {
               untagged (0),
               prioTagged (4096),
               notUsed (4097)
               }
   MAX-ACCESS  read-write
   STATUS      current
   DESCRIPTION
      "Path: swPort.editConf.vlan.vlan.vid

       Possibilities:
               untagged   (0)
               prioTagged   (4096)
               notUsed   (4097)"
   ::= {er1645v2EthPrtSwF2VlanEntry 234946560}

er1645v2EthPrtSwF2VlanVlanVidExtensionSingle OBJECT-TYPE
   SYNTAX      OCTET STRING
   MAX-ACCESS  read-write
   STATUS      current
   DESCRIPTION
      "Path: swPort.editConf.vlan.vlan.vidExtension.single"
   ::= {er1645v2EthPrtSwF2VlanEntry 235340032}

er1645v2EthPrtSwF2VlanVlanVidExtensionEndVid OBJECT-TYPE
   SYNTAX      Integer32
   MAX-ACCESS  read-write
   STATUS      current
   DESCRIPTION
      "Path: swPort.editConf.vlan.vlan.vidExtension.endVid"
   ::= {er1645v2EthPrtSwF2VlanEntry 235340288}

er1645v2EthPrtSwF2VlanVlanTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlan.vlan.tpid

       Possibilities:
               dot1Q   (33024)
               dot1ad   (34984)
               0x9100   (37120)
               0x9200   (37376)
               0x9300   (37632)"
   ::= {er1645v2EthPrtSwF2VlanEntry 241238016}

er1645v2EthPrtSwF2VlanVlanTagSign OBJECT-TYPE
   SYNTAX      INTEGER
               {
               global (0),
               local (1),
               sVlan (2),
               sVlanGlobal (6),
               cVlan (3),
               scVlan (5),
               cVlanLocal (4)
               }
   MAX-ACCESS  read-write
   STATUS      current
   DESCRIPTION
      "Path: swPort.editConf.vlan.vlan.tagSignificance

       Possibilities:
               global   (0)
               local   (1)
               sVlan   (2)
               sVlanGlobal   (6)
               cVlan   (3)
               scVlan   (5)
               cVlanLocal   (4)"
   ::= {er1645v2EthPrtSwF2VlanEntry 235012096}

er1645v2EthPrtSwF2VlanVlanChTos OBJECT-TYPE
   SYNTAX      INTEGER
               {
               disabled (0),
               enabled (1)
               }
   MAX-ACCESS  read-write
   STATUS      current
   DESCRIPTION
      "Path: swPort.editConf.vlan.vlan.changeTos

       Possibilities:
               disabled   (0)
               enabled   (1)"
   ::= {er1645v2EthPrtSwF2VlanEntry 235208704}

er1645v2EthPrtSwF2VlanVlanCTMapP0 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: swPort.editConf.vlan.vlan.cosTosMap.p0

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2EthPrtSwF2VlanEntry 235143424}

er1645v2EthPrtSwF2VlanVlanCTMapP1 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: swPort.editConf.vlan.vlan.cosTosMap.p1

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2EthPrtSwF2VlanEntry 235143680}

er1645v2EthPrtSwF2VlanVlanCTMapP2 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: swPort.editConf.vlan.vlan.cosTosMap.p2

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2EthPrtSwF2VlanEntry 235143936}

er1645v2EthPrtSwF2VlanVlanCTMapP3 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: swPort.editConf.vlan.vlan.cosTosMap.p3

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2EthPrtSwF2VlanEntry 235144192}

er1645v2EthPrtSwF2VlanVlanCTMapP4 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: swPort.editConf.vlan.vlan.cosTosMap.p4

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2EthPrtSwF2VlanEntry 235144448}

er1645v2EthPrtSwF2VlanVlanCTMapP5 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: swPort.editConf.vlan.vlan.cosTosMap.p5

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2EthPrtSwF2VlanEntry 235144704}

er1645v2EthPrtSwF2VlanVlanCTMapP6 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: swPort.editConf.vlan.vlan.cosTosMap.p6

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2EthPrtSwF2VlanEntry 235144960}

er1645v2EthPrtSwF2VlanVlanCTMapP7 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: swPort.editConf.vlan.vlan.cosTosMap.p7

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2EthPrtSwF2VlanEntry 235145216}

er1645v2EthPrtSwF2VlanVlanTxCos OBJECT-TYPE
   SYNTAX      INTEGER
               {
               tosCosMap (8),
               queueCosMap (16)
               }
   MAX-ACCESS  read-write
   STATUS      current
   DESCRIPTION
      "Path: swPort.editConf.vlan.vlan.txCos

       Possibilities:
               tosCosMap   (8)
               queueCosMap   (16)"
   ::= {er1645v2EthPrtSwF2VlanEntry 235077632}

er1645v2EthPrtSwF2VlanVlanCCMapP0 OBJECT-TYPE
   SYNTAX      Integer32
   MAX-ACCESS  read-write
   STATUS      current
   DESCRIPTION
      "Path: swPort.editConf.vlan.vlan.cosCosMap.p0"
   ::= {er1645v2EthPrtSwF2VlanEntry 241303808}

er1645v2EthPrtSwF2VlanVlanCCMapP1 OBJECT-TYPE
   SYNTAX      Integer32
   MAX-ACCESS  read-write
   STATUS      current
   DESCRIPTION
      "Path: swPort.editConf.vlan.vlan.cosCosMap.p1"
   ::= {er1645v2EthPrtSwF2VlanEntry 241304064}

er1645v2EthPrtSwF2VlanVlanCCMapP2 OBJECT-TYPE
   SYNTAX      Integer32
   MAX-ACCESS  read-write
   STATUS      current
   DESCRIPTION
      "Path: swPort.editConf.vlan.vlan.cosCosMap.p2"
   ::= {er1645v2EthPrtSwF2VlanEntry 241304320}

er1645v2EthPrtSwF2VlanVlanCCMapP3 OBJECT-TYPE
   SYNTAX      Integer32
   MAX-ACCESS  read-write
   STATUS      current
   DESCRIPTION
      "Path: swPort.editConf.vlan.vlan.cosCosMap.p3"
   ::= {er1645v2EthPrtSwF2VlanEntry 241304576}

er1645v2EthPrtSwF2VlanVlanCCMapP4 OBJECT-TYPE
   SYNTAX      Integer32
   MAX-ACCESS  read-write
   STATUS      current
   DESCRIPTION
      "Path: swPort.editConf.vlan.vlan.cosCosMap.p4"
   ::= {er1645v2EthPrtSwF2VlanEntry 241304832}

er1645v2EthPrtSwF2VlanVlanCCMapP5 OBJECT-TYPE
   SYNTAX      Integer32
   MAX-ACCESS  read-write
   STATUS      current
   DESCRIPTION
      "Path: swPort.editConf.vlan.vlan.cosCosMap.p5"
   ::= {er1645v2EthPrtSwF2VlanEntry 241305088}

er1645v2EthPrtSwF2VlanVlanCCMapP6 OBJECT-TYPE
   SYNTAX      Integer32
   MAX-ACCESS  read-write
   STATUS      current
   DESCRIPTION
      "Path: swPort.editConf.vlan.vlan.cosCosMap.p6"
   ::= {er1645v2EthPrtSwF2VlanEntry 241305344}

er1645v2EthPrtSwF2VlanVlanCCMapP7 OBJECT-TYPE
   SYNTAX      Integer32
   MAX-ACCESS  read-write
   STATUS      current
   DESCRIPTION
      "Path: swPort.editConf.vlan.vlan.cosCosMap.p7"
   ::= {er1645v2EthPrtSwF2VlanEntry 241305600}

er1645v2EthPrtSwF2VlanVlanQCMapQueue1 OBJECT-TYPE
   SYNTAX      Integer32
   MAX-ACCESS  read-write
   STATUS      current
   DESCRIPTION
      "Path: swPort.editConf.vlan.vlan.queueCosMap.queue1"
   ::= {er1645v2EthPrtSwF2VlanEntry 241434880}

er1645v2EthPrtSwF2VlanVlanQCMapQueue2 OBJECT-TYPE
   SYNTAX      Integer32
   MAX-ACCESS  read-write
   STATUS      current
   DESCRIPTION
      "Path: swPort.editConf.vlan.vlan.queueCosMap.queue2"
   ::= {er1645v2EthPrtSwF2VlanEntry 241435136}

er1645v2EthPrtSwF2VlanVlanQCMapQueue3 OBJECT-TYPE
   SYNTAX      Integer32
   MAX-ACCESS  read-write
   STATUS      current
   DESCRIPTION
      "Path: swPort.editConf.vlan.vlan.queueCosMap.queue3"
   ::= {er1645v2EthPrtSwF2VlanEntry 241435392}

er1645v2EthPrtSwF2VlanVlanQCMapQueue4 OBJECT-TYPE
   SYNTAX      Integer32
   MAX-ACCESS  read-write
   STATUS      current
   DESCRIPTION
      "Path: swPort.editConf.vlan.vlan.queueCosMap.queue4"
   ::= {er1645v2EthPrtSwF2VlanEntry 241435648}

er1645v2EthPrtSwF2VlanVlanQCMapQueue5 OBJECT-TYPE
   SYNTAX      Integer32
   MAX-ACCESS  read-write
   STATUS      current
   DESCRIPTION
      "Path: swPort.editConf.vlan.vlan.queueCosMap.queue5"
   ::= {er1645v2EthPrtSwF2VlanEntry 241435904}

er1645v2EthPrtSwF2VlanVlanQCMapLowDelayQueue OBJECT-TYPE
   SYNTAX      Integer32
   MAX-ACCESS  read-write
   STATUS      current
   DESCRIPTION
      "Path: swPort.editConf.vlan.vlan.queueCosMap.lowDelayQueue"
   ::= {er1645v2EthPrtSwF2VlanEntry 241436160}

er1645v2EthPrtSwF2VlanVlanQCMapLowDelay2Queue OBJECT-TYPE
   SYNTAX      Integer32
   MAX-ACCESS  read-write
   STATUS      current
   DESCRIPTION
      "Path: swPort.editConf.vlan.vlan.queueCosMap.lowDelay2Queue"
   ::= {er1645v2EthPrtSwF2VlanEntry 241436416}

er1645v2EthPrtSwF2VlanVlanQCMapSystemQueue OBJECT-TYPE
   SYNTAX      Integer32
   MAX-ACCESS  read-write
   STATUS      current
   DESCRIPTION
      "Path: swPort.editConf.vlan.vlan.queueCosMap.systemQueue"
   ::= {er1645v2EthPrtSwF2VlanEntry 241436672}

er1645v2EthPrtSwF2VlanVlanQinQSVid OBJECT-TYPE
   SYNTAX      Integer32
   MAX-ACCESS  read-write
   STATUS      current
   DESCRIPTION
      "Path: swPort.editConf.vlan.vlan.tunnel.sVid"
   ::= {er1645v2EthPrtSwF2VlanEntry 241172736}

er1645v2EthPrtSwF2VlanVlanQinQSTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlan.vlan.tunnel.sTpid

       Possibilities:
               dot1Q   (33024)
               dot1ad   (34984)
               0x9100   (37120)
               0x9200   (37376)
               0x9300   (37632)"
   ::= {er1645v2EthPrtSwF2VlanEntry 241172992}

er1645v2EthPrtSwF2VlanVlanArpTimeOut OBJECT-TYPE
   SYNTAX      TimeTicks
   MAX-ACCESS  read-write
   STATUS      current
   DESCRIPTION
      "Path: swPort.editConf.vlan.vlan.arp.timeOut

       Time in centi-second."
   ::= {er1645v2EthPrtSwF2VlanEntry 235277312}

er1645v2EthPrtSwF2VlanVlanArpProxyArp OBJECT-TYPE
   SYNTAX      INTEGER
               {
               disabled (0),
               enabled (1)
               }
   MAX-ACCESS  read-write
   STATUS      current
   DESCRIPTION
      "Path: swPort.editConf.vlan.vlan.arp.proxyArp

       Possibilities:
               disabled   (0)
               enabled   (1)"
   ::= {er1645v2EthPrtSwF2VlanEntry 235287040}

er1645v2EthPrtSwF2VlanBandwidthMode OBJECT-TYPE
   SYNTAX      INTEGER
               {
               reshaping (1),
               policing (2),
               policingReshape (3)
               }
   MAX-ACCESS  read-write
   STATUS      current
   DESCRIPTION
      "Path: swPort.editConf.vlan.bandwidth.mode

       Possibilities:
               reshaping   (1)
               policing   (2)
               policingReshape   (3)"
   ::= {er1645v2EthPrtSwF2VlanEntry 148897792}

er1645v2EthPrtSwF2VlanBandwidthCir OBJECT-TYPE
   SYNTAX      Integer32
   MAX-ACCESS  read-write
   STATUS      current
   DESCRIPTION
      "Path: swPort.editConf.vlan.bandwidth.cir"
   ::= {er1645v2EthPrtSwF2VlanEntry 135266304}

er1645v2EthPrtSwF2VlanBandwidthEir OBJECT-TYPE
   SYNTAX      Integer32
   MAX-ACCESS  read-write
   STATUS      current
   DESCRIPTION
      "Path: swPort.editConf.vlan.bandwidth.eir"
   ::= {er1645v2EthPrtSwF2VlanEntry 141557760}

er1645v2EthPrtSwF2VlanBandwidthUnit OBJECT-TYPE
   SYNTAX      INTEGER
               {
               bitssec (1),
               percent (2)
               }
   MAX-ACCESS  read-write
   STATUS      current
   DESCRIPTION
      "Path: swPort.editConf.vlan.bandwidth.unit

       Possibilities:
               bits/sec   (1)
               percent   (2)"
   ::= {er1645v2EthPrtSwF2VlanEntry 139460608}

er1645v2EthPrtSwF2VlanBandwidthTc OBJECT-TYPE
   SYNTAX      INTEGER
               {
               auto (0)
               }
   MAX-ACCESS  read-write
   STATUS      current
   DESCRIPTION
      "Path: swPort.editConf.vlan.bandwidth.tc

       Possibilities:
               auto   (0)"
   ::= {er1645v2EthPrtSwF2VlanEntry 140509184}

er1645v2EthPrtSwF2VlanBandwidthTcFactor OBJECT-TYPE
   SYNTAX      INTEGER
               {
               ms (10),
               s100us (1)
               }
   MAX-ACCESS  read-write
   STATUS      current
   DESCRIPTION
      "Path: swPort.editConf.vlan.bandwidth.tcFactor

       Possibilities:
               ms   (10)
               *100us   (1)"
   ::= {er1645v2EthPrtSwF2VlanEntry 142606336}

er1645v2EthPrtSwF2VlanBandwidthCorrType OBJECT-TYPE
   SYNTAX      INTEGER
               {
               noCorrection (0),
               predefined (1),
               manual (2)
               }
   MAX-ACCESS  read-write
   STATUS      current
   DESCRIPTION
      "Path: swPort.editConf.vlan.bandwidth.correction.type

       Possibilities:
               noCorrection   (0)
               predefined   (1)
               manual   (2)"
   ::= {er1645v2EthPrtSwF2VlanEntry 136445952}

er1645v2EthPrtSwF2VlanBandwidthCorrPredefEncapsFrameRelay OBJECT-TYPE
   SYNTAX      DisplayString
   MAX-ACCESS  read-write
   STATUS      current
   DESCRIPTION
      "Path: swPort.editConf.vlan.bandwidth.correction.predefined.encapsulation.frameRelay"
   ::= {er1645v2EthPrtSwF2VlanEntry 136594432}

er1645v2EthPrtSwF2VlanBandwidthCorrPredefEncapsPpp OBJECT-TYPE
   SYNTAX      DisplayString
   MAX-ACCESS  read-write
   STATUS      current
   DESCRIPTION
      "Path: swPort.editConf.vlan.bandwidth.correction.predefined.encapsulation.ppp"
   ::= {er1645v2EthPrtSwF2VlanEntry 136595456}

er1645v2EthPrtSwF2VlanBandwidthCorrPredefEncapsAtmHl OBJECT-TYPE
   SYNTAX      INTEGER
               {
               rfc2684 (0),
               ppp (1),
               pppOverEthernet (2)
               }
   MAX-ACCESS  read-write
   STATUS      current
   DESCRIPTION
      "Path: swPort.editConf.vlan.bandwidth.correction.predefined.encapsulation.atm.higherLayer

       Possibilities:
               rfc2684   (0)
               ppp   (1)
               pppOverEthernet   (2)"
   ::= {er1645v2EthPrtSwF2VlanEntry 136596608}

er1645v2EthPrtSwF2VlanBandwidthCorrPredefEncapsAtmMp OBJECT-TYPE
   SYNTAX      INTEGER
               {
               llcEncapsulation (0),
               vcMultiplexing (1)
               }
   MAX-ACCESS  read-write
   STATUS      current
   DESCRIPTION
      "Path: swPort.editConf.vlan.bandwidth.correction.predefined.encapsulation.atm.multiProtocol

       Possibilities:
               llcEncapsulation   (0)
               vcMultiplexing   (1)"
   ::= {er1645v2EthPrtSwF2VlanEntry 136596736}

er1645v2EthPrtSwF2VlanBandwidthCorrPredefEncapsHdlc OBJECT-TYPE
   SYNTAX      DisplayString
   MAX-ACCESS  read-write
   STATUS      current
   DESCRIPTION
      "Path: swPort.editConf.vlan.bandwidth.correction.predefined.encapsulation.hdlc"
   ::= {er1645v2EthPrtSwF2VlanEntry 136597504}

er1645v2EthPrtSwF2VlanBandwidthCorrPredefEncapsEfmFs OBJECT-TYPE
   SYNTAX      Integer32
   MAX-ACCESS  read-write
   STATUS      current
   DESCRIPTION
      "Path: swPort.editConf.vlan.bandwidth.correction.predefined.encapsulation.efm.fragmentSize"
   ::= {er1645v2EthPrtSwF2VlanEntry 136598656}

er1645v2EthPrtSwF2VlanBandwidthCorrPredefEncapsEfmIb OBJECT-TYPE
   SYNTAX      Integer32
   MAX-ACCESS  read-write
   STATUS      current
   DESCRIPTION
      "Path: swPort.editConf.vlan.bandwidth.correction.predefined.encapsulation.efm.idleBytes"
   ::= {er1645v2EthPrtSwF2VlanEntry 136598784}

er1645v2EthPrtSwF2VlanBandwidthCorrPredefMode OBJECT-TYPE
   SYNTAX      INTEGER
               {
               routing (0),
               bridging (1)
               }
   MAX-ACCESS  read-write
   STATUS      current
   DESCRIPTION
      "Path: swPort.editConf.vlan.bandwidth.correction.predefined.mode

       Possibilities:
               routing   (0)
               bridging   (1)"
   ::= {er1645v2EthPrtSwF2VlanEntry 136609792}

er1645v2EthPrtSwF2VlanBandwidthCorrManualOverhead OBJECT-TYPE
   SYNTAX      Integer32
   MAX-ACCESS  read-write
   STATUS      current
   DESCRIPTION
      "Path: swPort.editConf.vlan.bandwidth.correction.manual.overhead"
   ::= {er1645v2EthPrtSwF2VlanEntry 136708608}

er1645v2EthPrtSwF2VlanBandwidthCorrManualFrameData OBJECT-TYPE
   SYNTAX      Counter32
   MAX-ACCESS  read-write
   STATUS      current
   DESCRIPTION
      "Path: swPort.editConf.vlan.bandwidth.correction.manual.frameData

       32 bit unsigned wrappable counter."
   ::= {er1645v2EthPrtSwF2VlanEntry 136709120}

er1645v2EthPrtSwF2VlanBandwidthCorrManualFrameHeader OBJECT-TYPE
   SYNTAX      Counter32
   MAX-ACCESS  read-write
   STATUS      current
   DESCRIPTION
      "Path: swPort.editConf.vlan.bandwidth.correction.manual.frameHeader

       32 bit unsigned wrappable counter."
   ::= {er1645v2EthPrtSwF2VlanEntry 136709632}

er1645v2EthPrtSwF2VlanBandwidthMaxFifoQLen OBJECT-TYPE
   SYNTAX      Integer32
   MAX-ACCESS  read-write
   STATUS      current
   DESCRIPTION
      "Path: swPort.editConf.vlan.bandwidth.maxFifoQLen"
   ::= {er1645v2EthPrtSwF2VlanEntry 137363456}

er1645v2EthPrtSwF2VlanBandwidthDeFlagCir OBJECT-TYPE
   SYNTAX      INTEGER
               {
               allowed (1),
               notAllowed (2)
               }
   MAX-ACCESS  read-write
   STATUS      current
   DESCRIPTION
      "Path: swPort.editConf.vlan.bandwidth.deFlag.cir

       Possibilities:
               allowed   (1)
               notAllowed   (2)"
   ::= {er1645v2EthPrtSwF2VlanEntry 147853312}

er1645v2EthPrtSwF2VlanBandwidthDeFlagEir OBJECT-TYPE
   SYNTAX      INTEGER
               {
               allowed (1),
               notAllowed (2)
               }
   MAX-ACCESS  read-write
   STATUS      current
   DESCRIPTION
      "Path: swPort.editConf.vlan.bandwidth.deFlag.eir

       Possibilities:
               allowed   (1)
               notAllowed   (2)"
   ::= {er1645v2EthPrtSwF2VlanEntry 147857408}

er1645v2EthPrtSwF2VlanBandwidthDeFlagViolate OBJECT-TYPE
   SYNTAX      INTEGER
               {
               allowed (1),
               notAllowed (2)
               }
   MAX-ACCESS  read-write
   STATUS      current
   DESCRIPTION
      "Path: swPort.editConf.vlan.bandwidth.deFlag.violate

       Possibilities:
               allowed   (1)
               notAllowed   (2)"
   ::= {er1645v2EthPrtSwF2VlanEntry 147861504}

er1645v2EthPrtSwF2VlanBandwidthActCirActNone OBJECT-TYPE
   SYNTAX      OCTET STRING
   MAX-ACCESS  read-write
   STATUS      current
   DESCRIPTION
      "Path: swPort.editConf.vlan.bandwidth.action.cirAction.none"
   ::= {er1645v2EthPrtSwF2VlanEntry 150085632}

er1645v2EthPrtSwF2VlanBandwidthActCirActEthCos1 OBJECT-TYPE
   SYNTAX      INTEGER
               {
               unchanged (256)
               }
   MAX-ACCESS  read-write
   STATUS      current
   DESCRIPTION
      "Path: swPort.editConf.vlan.bandwidth.action.cirAction.ethernet.cosDepth1

       Possibilities:
               unchanged   (256)"
   ::= {er1645v2EthPrtSwF2VlanEntry 150094080}

er1645v2EthPrtSwF2VlanBandwidthActCirActEthDei1 OBJECT-TYPE
   SYNTAX      INTEGER
               {
               unchanged (255),
               clear (0),
               set (1)
               }
   MAX-ACCESS  read-write
   STATUS      current
   DESCRIPTION
      "Path: swPort.editConf.vlan.bandwidth.action.cirAction.ethernet.deiDepth1

       Possibilities:
               unchanged   (255)
               clear   (0)
               set   (1)"
   ::= {er1645v2EthPrtSwF2VlanEntry 150099200}

er1645v2EthPrtSwF2VlanBandwidthActCirActEthCos2 OBJECT-TYPE
   SYNTAX      INTEGER
               {
               unchanged (256)
               }
   MAX-ACCESS  read-write
   STATUS      current
   DESCRIPTION
      "Path: swPort.editConf.vlan.bandwidth.action.cirAction.ethernet.cosDepth2

       Possibilities:
               unchanged   (256)"
   ::= {er1645v2EthPrtSwF2VlanEntry 150094336}

er1645v2EthPrtSwF2VlanBandwidthActCirActEthDei2 OBJECT-TYPE
   SYNTAX      INTEGER
               {
               unchanged (255),
               clear (0),
               set (1)
               }
   MAX-ACCESS  read-write
   STATUS      current
   DESCRIPTION
      "Path: swPort.editConf.vlan.bandwidth.action.cirAction.ethernet.deiDepth2

       Possibilities:
               unchanged   (255)
               clear   (0)
               set   (1)"
   ::= {er1645v2EthPrtSwF2VlanEntry 150099456}

er1645v2EthPrtSwF2VlanBandwidthActCirActEthCos3 OBJECT-TYPE
   SYNTAX      INTEGER
               {
               unchanged (256)
               }
   MAX-ACCESS  read-write
   STATUS      current
   DESCRIPTION
      "Path: swPort.editConf.vlan.bandwidth.action.cirAction.ethernet.cosDepth3

       Possibilities:
               unchanged   (256)"
   ::= {er1645v2EthPrtSwF2VlanEntry 150094592}

er1645v2EthPrtSwF2VlanBandwidthActCirActEthDei3 OBJECT-TYPE
   SYNTAX      INTEGER
               {
               unchanged (255),
               clear (0),
               set (1)
               }
   MAX-ACCESS  read-write
   STATUS      current
   DESCRIPTION
      "Path: swPort.editConf.vlan.bandwidth.action.cirAction.ethernet.deiDepth3

       Possibilities:
               unchanged   (255)
               clear   (0)
               set   (1)"
   ::= {er1645v2EthPrtSwF2VlanEntry 150099712}

er1645v2EthPrtSwF2VlanBandwidthActCirActEthCos4 OBJECT-TYPE
   SYNTAX      INTEGER
               {
               unchanged (256)
               }
   MAX-ACCESS  read-write
   STATUS      current
   DESCRIPTION
      "Path: swPort.editConf.vlan.bandwidth.action.cirAction.ethernet.cosDepth4

       Possibilities:
               unchanged   (256)"
   ::= {er1645v2EthPrtSwF2VlanEntry 150094848}

er1645v2EthPrtSwF2VlanBandwidthActCirActEthDei4 OBJECT-TYPE
   SYNTAX      INTEGER
               {
               unchanged (255),
               clear (0),
               set (1)
               }
   MAX-ACCESS  read-write
   STATUS      current
   DESCRIPTION
      "Path: swPort.editConf.vlan.bandwidth.action.cirAction.ethernet.deiDepth4

       Possibilities:
               unchanged   (255)
               clear   (0)
               set   (1)"
   ::= {er1645v2EthPrtSwF2VlanEntry 150099968}

er1645v2EthPrtSwF2VlanBandwidthActCirActEthCos5 OBJECT-TYPE
   SYNTAX      INTEGER
               {
               unchanged (256)
               }
   MAX-ACCESS  read-write
   STATUS      current
   DESCRIPTION
      "Path: swPort.editConf.vlan.bandwidth.action.cirAction.ethernet.cosDepth5

       Possibilities:
               unchanged   (256)"
   ::= {er1645v2EthPrtSwF2VlanEntry 150095104}

er1645v2EthPrtSwF2VlanBandwidthActCirActEthDei5 OBJECT-TYPE
   SYNTAX      INTEGER
               {
               unchanged (255),
               clear (0),
               set (1)
               }
   MAX-ACCESS  read-write
   STATUS      current
   DESCRIPTION
      "Path: swPort.editConf.vlan.bandwidth.action.cirAction.ethernet.deiDepth5

       Possibilities:
               unchanged   (255)
               clear   (0)
               set   (1)"
   ::= {er1645v2EthPrtSwF2VlanEntry 150100224}

er1645v2EthPrtSwF2VlanBandwidthActCirActEthCos6 OBJECT-TYPE
   SYNTAX      INTEGER
               {
               unchanged (256)
               }
   MAX-ACCESS  read-write
   STATUS      current
   DESCRIPTION
      "Path: swPort.editConf.vlan.bandwidth.action.cirAction.ethernet.cosDepth6

       Possibilities:
               unchanged   (256)"
   ::= {er1645v2EthPrtSwF2VlanEntry 150095360}

er1645v2EthPrtSwF2VlanBandwidthActCirActEthDei6 OBJECT-TYPE
   SYNTAX      INTEGER
               {
               unchanged (255),
               clear (0),
               set (1)
               }
   MAX-ACCESS  read-write
   STATUS      current
   DESCRIPTION
      "Path: swPort.editConf.vlan.bandwidth.action.cirAction.ethernet.deiDepth6

       Possibilities:
               unchanged   (255)
               clear   (0)
               set   (1)"
   ::= {er1645v2EthPrtSwF2VlanEntry 150100480}

er1645v2EthPrtSwF2VlanBandwidthActCirActEthCos7 OBJECT-TYPE
   SYNTAX      INTEGER
               {
               unchanged (256)
               }
   MAX-ACCESS  read-write
   STATUS      current
   DESCRIPTION
      "Path: swPort.editConf.vlan.bandwidth.action.cirAction.ethernet.cosDepth7

       Possibilities:
               unchanged   (256)"
   ::= {er1645v2EthPrtSwF2VlanEntry 150095616}

er1645v2EthPrtSwF2VlanBandwidthActCirActEthDei7 OBJECT-TYPE
   SYNTAX      INTEGER
               {
               unchanged (255),
               clear (0),
               set (1)
               }
   MAX-ACCESS  read-write
   STATUS      current
   DESCRIPTION
      "Path: swPort.editConf.vlan.bandwidth.action.cirAction.ethernet.deiDepth7

       Possibilities:
               unchanged   (255)
               clear   (0)
               set   (1)"
   ::= {er1645v2EthPrtSwF2VlanEntry 150100736}

er1645v2EthPrtSwF2VlanBandwidthActCirActEthCos8 OBJECT-TYPE
   SYNTAX      INTEGER
               {
               unchanged (256)
               }
   MAX-ACCESS  read-write
   STATUS      current
   DESCRIPTION
      "Path: swPort.editConf.vlan.bandwidth.action.cirAction.ethernet.cosDepth8

       Possibilities:
               unchanged   (256)"
   ::= {er1645v2EthPrtSwF2VlanEntry 150095872}

er1645v2EthPrtSwF2VlanBandwidthActCirActEthDei8 OBJECT-TYPE
   SYNTAX      INTEGER
               {
               unchanged (255),
               clear (0),
               set (1)
               }
   MAX-ACCESS  read-write
   STATUS      current
   DESCRIPTION
      "Path: swPort.editConf.vlan.bandwidth.action.cirAction.ethernet.deiDepth8

       Possibilities:
               unchanged   (255)
               clear   (0)
               set   (1)"
   ::= {er1645v2EthPrtSwF2VlanEntry 150100992}

er1645v2EthPrtSwF2VlanBandwidthActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPrtSwF2VlanEntry 150096128}

er1645v2EthPrtSwF2VlanBandwidthActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2EthPrtSwF2VlanEntry 150096384}

er1645v2EthPrtSwF2VlanBandwidthActCirActEthDrpLev OBJECT-TYPE
   SYNTAX      INTEGER
               {
               unchanged (0)
               }
   MAX-ACCESS  read-write
   STATUS      current
   DESCRIPTION
      "Path: swPort.editConf.vlan.bandwidth.action.cirAction.ethernet.dropLevel

       Possibilities:
               unchanged   (0)"
   ::= {er1645v2EthPrtSwF2VlanEntry 150096640}

er1645v2EthPrtSwF2VlanBandwidthActCirActEthDeFlag OBJECT-TYPE
   SYNTAX      INTEGER
               {
               unchanged (255),
               clear (0),
               set (1)
               }
   MAX-ACCESS  read-write
   STATUS      current
   DESCRIPTION
      "Path: swPort.editConf.vlan.bandwidth.action.cirAction.ethernet.deFlag

       Possibilities:
               unchanged   (255)
               clear   (0)
               set   (1)"
   ::= {er1645v2EthPrtSwF2VlanEntry 150097408}

er1645v2EthPrtSwF2VlanBandwidthActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPrtSwF2VlanEntry 150120704}

er1645v2EthPrtSwF2VlanBandwidthActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2EthPrtSwF2VlanEntry 150120960}

er1645v2EthPrtSwF2VlanBandwidthActCirActIpDrpLev OBJECT-TYPE
   SYNTAX      INTEGER
               {
               unchanged (0)
               }
   MAX-ACCESS  read-write
   STATUS      current
   DESCRIPTION
      "Path: swPort.editConf.vlan.bandwidth.action.cirAction.ip.dropLevel

       Possibilities:
               unchanged   (0)"
   ::= {er1645v2EthPrtSwF2VlanEntry 150121216}

er1645v2EthPrtSwF2VlanBandwidthActCirActIpDeFlag OBJECT-TYPE
   SYNTAX      INTEGER
               {
               unchanged (255),
               clear (0),
               set (1)
               }
   MAX-ACCESS  read-write
   STATUS      current
   DESCRIPTION
      "Path: swPort.editConf.vlan.bandwidth.action.cirAction.ip.deFlag

       Possibilities:
               unchanged   (255)
               clear   (0)
               set   (1)"
   ::= {er1645v2EthPrtSwF2VlanEntry 150121984}

er1645v2EthPrtSwF2VlanBandwidthActEirActNone OBJECT-TYPE
   SYNTAX      OCTET STRING
   MAX-ACCESS  read-write
   STATUS      current
   DESCRIPTION
      "Path: swPort.editConf.vlan.bandwidth.action.eirAction.none"
   ::= {er1645v2EthPrtSwF2VlanEntry 150216704}

er1645v2EthPrtSwF2VlanBandwidthActEirActEthCos1 OBJECT-TYPE
   SYNTAX      INTEGER
               {
               unchanged (256)
               }
   MAX-ACCESS  read-write
   STATUS      current
   DESCRIPTION
      "Path: swPort.editConf.vlan.bandwidth.action.eirAction.ethernet.cosDepth1

       Possibilities:
               unchanged   (256)"
   ::= {er1645v2EthPrtSwF2VlanEntry 150225152}

er1645v2EthPrtSwF2VlanBandwidthActEirActEthDei1 OBJECT-TYPE
   SYNTAX      INTEGER
               {
               unchanged (255),
               clear (0),
               set (1)
               }
   MAX-ACCESS  read-write
   STATUS      current
   DESCRIPTION
      "Path: swPort.editConf.vlan.bandwidth.action.eirAction.ethernet.deiDepth1

       Possibilities:
               unchanged   (255)
               clear   (0)
               set   (1)"
   ::= {er1645v2EthPrtSwF2VlanEntry 150230272}

er1645v2EthPrtSwF2VlanBandwidthActEirActEthCos2 OBJECT-TYPE
   SYNTAX      INTEGER
               {
               unchanged (256)
               }
   MAX-ACCESS  read-write
   STATUS      current
   DESCRIPTION
      "Path: swPort.editConf.vlan.bandwidth.action.eirAction.ethernet.cosDepth2

       Possibilities:
               unchanged   (256)"
   ::= {er1645v2EthPrtSwF2VlanEntry 150225408}

er1645v2EthPrtSwF2VlanBandwidthActEirActEthDei2 OBJECT-TYPE
   SYNTAX      INTEGER
               {
               unchanged (255),
               clear (0),
               set (1)
               }
   MAX-ACCESS  read-write
   STATUS      current
   DESCRIPTION
      "Path: swPort.editConf.vlan.bandwidth.action.eirAction.ethernet.deiDepth2

       Possibilities:
               unchanged   (255)
               clear   (0)
               set   (1)"
   ::= {er1645v2EthPrtSwF2VlanEntry 150230528}

er1645v2EthPrtSwF2VlanBandwidthActEirActEthCos3 OBJECT-TYPE
   SYNTAX      INTEGER
               {
               unchanged (256)
               }
   MAX-ACCESS  read-write
   STATUS      current
   DESCRIPTION
      "Path: swPort.editConf.vlan.bandwidth.action.eirAction.ethernet.cosDepth3

       Possibilities:
               unchanged   (256)"
   ::= {er1645v2EthPrtSwF2VlanEntry 150225664}

er1645v2EthPrtSwF2VlanBandwidthActEirActEthDei3 OBJECT-TYPE
   SYNTAX      INTEGER
               {
               unchanged (255),
               clear (0),
               set (1)
               }
   MAX-ACCESS  read-write
   STATUS      current
   DESCRIPTION
      "Path: swPort.editConf.vlan.bandwidth.action.eirAction.ethernet.deiDepth3

       Possibilities:
               unchanged   (255)
               clear   (0)
               set   (1)"
   ::= {er1645v2EthPrtSwF2VlanEntry 150230784}

er1645v2EthPrtSwF2VlanBandwidthActEirActEthCos4 OBJECT-TYPE
   SYNTAX      INTEGER
               {
               unchanged (256)
               }
   MAX-ACCESS  read-write
   STATUS      current
   DESCRIPTION
      "Path: swPort.editConf.vlan.bandwidth.action.eirAction.ethernet.cosDepth4

       Possibilities:
               unchanged   (256)"
   ::= {er1645v2EthPrtSwF2VlanEntry 150225920}

er1645v2EthPrtSwF2VlanBandwidthActEirActEthDei4 OBJECT-TYPE
   SYNTAX      INTEGER
               {
               unchanged (255),
               clear (0),
               set (1)
               }
   MAX-ACCESS  read-write
   STATUS      current
   DESCRIPTION
      "Path: swPort.editConf.vlan.bandwidth.action.eirAction.ethernet.deiDepth4

       Possibilities:
               unchanged   (255)
               clear   (0)
               set   (1)"
   ::= {er1645v2EthPrtSwF2VlanEntry 150231040}

er1645v2EthPrtSwF2VlanBandwidthActEirActEthCos5 OBJECT-TYPE
   SYNTAX      INTEGER
               {
               unchanged (256)
               }
   MAX-ACCESS  read-write
   STATUS      current
   DESCRIPTION
      "Path: swPort.editConf.vlan.bandwidth.action.eirAction.ethernet.cosDepth5

       Possibilities:
               unchanged   (256)"
   ::= {er1645v2EthPrtSwF2VlanEntry 150226176}

er1645v2EthPrtSwF2VlanBandwidthActEirActEthDei5 OBJECT-TYPE
   SYNTAX      INTEGER
               {
               unchanged (255),
               clear (0),
               set (1)
               }
   MAX-ACCESS  read-write
   STATUS      current
   DESCRIPTION
      "Path: swPort.editConf.vlan.bandwidth.action.eirAction.ethernet.deiDepth5

       Possibilities:
               unchanged   (255)
               clear   (0)
               set   (1)"
   ::= {er1645v2EthPrtSwF2VlanEntry 150231296}

er1645v2EthPrtSwF2VlanBandwidthActEirActEthCos6 OBJECT-TYPE
   SYNTAX      INTEGER
               {
               unchanged (256)
               }
   MAX-ACCESS  read-write
   STATUS      current
   DESCRIPTION
      "Path: swPort.editConf.vlan.bandwidth.action.eirAction.ethernet.cosDepth6

       Possibilities:
               unchanged   (256)"
   ::= {er1645v2EthPrtSwF2VlanEntry 150226432}

er1645v2EthPrtSwF2VlanBandwidthActEirActEthDei6 OBJECT-TYPE
   SYNTAX      INTEGER
               {
               unchanged (255),
               clear (0),
               set (1)
               }
   MAX-ACCESS  read-write
   STATUS      current
   DESCRIPTION
      "Path: swPort.editConf.vlan.bandwidth.action.eirAction.ethernet.deiDepth6

       Possibilities:
               unchanged   (255)
               clear   (0)
               set   (1)"
   ::= {er1645v2EthPrtSwF2VlanEntry 150231552}

er1645v2EthPrtSwF2VlanBandwidthActEirActEthCos7 OBJECT-TYPE
   SYNTAX      INTEGER
               {
               unchanged (256)
               }
   MAX-ACCESS  read-write
   STATUS      current
   DESCRIPTION
      "Path: swPort.editConf.vlan.bandwidth.action.eirAction.ethernet.cosDepth7

       Possibilities:
               unchanged   (256)"
   ::= {er1645v2EthPrtSwF2VlanEntry 150226688}

er1645v2EthPrtSwF2VlanBandwidthActEirActEthDei7 OBJECT-TYPE
   SYNTAX      INTEGER
               {
               unchanged (255),
               clear (0),
               set (1)
               }
   MAX-ACCESS  read-write
   STATUS      current
   DESCRIPTION
      "Path: swPort.editConf.vlan.bandwidth.action.eirAction.ethernet.deiDepth7

       Possibilities:
               unchanged   (255)
               clear   (0)
               set   (1)"
   ::= {er1645v2EthPrtSwF2VlanEntry 150231808}

er1645v2EthPrtSwF2VlanBandwidthActEirActEthCos8 OBJECT-TYPE
   SYNTAX      INTEGER
               {
               unchanged (256)
               }
   MAX-ACCESS  read-write
   STATUS      current
   DESCRIPTION
      "Path: swPort.editConf.vlan.bandwidth.action.eirAction.ethernet.cosDepth8

       Possibilities:
               unchanged   (256)"
   ::= {er1645v2EthPrtSwF2VlanEntry 150226944}

er1645v2EthPrtSwF2VlanBandwidthActEirActEthDei8 OBJECT-TYPE
   SYNTAX      INTEGER
               {
               unchanged (255),
               clear (0),
               set (1)
               }
   MAX-ACCESS  read-write
   STATUS      current
   DESCRIPTION
      "Path: swPort.editConf.vlan.bandwidth.action.eirAction.ethernet.deiDepth8

       Possibilities:
               unchanged   (255)
               clear   (0)
               set   (1)"
   ::= {er1645v2EthPrtSwF2VlanEntry 150232064}

er1645v2EthPrtSwF2VlanBandwidthActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPrtSwF2VlanEntry 150227200}

er1645v2EthPrtSwF2VlanBandwidthActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2EthPrtSwF2VlanEntry 150227456}

er1645v2EthPrtSwF2VlanBandwidthActEirActEthDrpLev OBJECT-TYPE
   SYNTAX      INTEGER
               {
               unchanged (0)
               }
   MAX-ACCESS  read-write
   STATUS      current
   DESCRIPTION
      "Path: swPort.editConf.vlan.bandwidth.action.eirAction.ethernet.dropLevel

       Possibilities:
               unchanged   (0)"
   ::= {er1645v2EthPrtSwF2VlanEntry 150227712}

er1645v2EthPrtSwF2VlanBandwidthActEirActEthDeFlag OBJECT-TYPE
   SYNTAX      INTEGER
               {
               unchanged (255),
               clear (0),
               set (1)
               }
   MAX-ACCESS  read-write
   STATUS      current
   DESCRIPTION
      "Path: swPort.editConf.vlan.bandwidth.action.eirAction.ethernet.deFlag

       Possibilities:
               unchanged   (255)
               clear   (0)
               set   (1)"
   ::= {er1645v2EthPrtSwF2VlanEntry 150228480}

er1645v2EthPrtSwF2VlanBandwidthActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPrtSwF2VlanEntry 150251776}

er1645v2EthPrtSwF2VlanBandwidthActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2EthPrtSwF2VlanEntry 150252032}

er1645v2EthPrtSwF2VlanBandwidthActEirActIpDrpLev OBJECT-TYPE
   SYNTAX      INTEGER
               {
               unchanged (0)
               }
   MAX-ACCESS  read-write
   STATUS      current
   DESCRIPTION
      "Path: swPort.editConf.vlan.bandwidth.action.eirAction.ip.dropLevel

       Possibilities:
               unchanged   (0)"
   ::= {er1645v2EthPrtSwF2VlanEntry 150252288}

er1645v2EthPrtSwF2VlanBandwidthActEirActIpDeFlag OBJECT-TYPE
   SYNTAX      INTEGER
               {
               unchanged (255),
               clear (0),
               set (1)
               }
   MAX-ACCESS  read-write
   STATUS      current
   DESCRIPTION
      "Path: swPort.editConf.vlan.bandwidth.action.eirAction.ip.deFlag

       Possibilities:
               unchanged   (255)
               clear   (0)
               set   (1)"
   ::= {er1645v2EthPrtSwF2VlanEntry 150253056}

er1645v2EthPrtSwF2VlanBandwidthActViolActNone OBJECT-TYPE
   SYNTAX      OCTET STRING
   MAX-ACCESS  read-write
   STATUS      current
   DESCRIPTION
      "Path: swPort.editConf.vlan.bandwidth.action.violateAction.none"
   ::= {er1645v2EthPrtSwF2VlanEntry 150347776}

er1645v2EthPrtSwF2VlanBandwidthActViolActDrop OBJECT-TYPE
   SYNTAX      OCTET STRING
   MAX-ACCESS  read-write
   STATUS      current
   DESCRIPTION
      "Path: swPort.editConf.vlan.bandwidth.action.violateAction.drop"
   ::= {er1645v2EthPrtSwF2VlanEntry 150364160}

er1645v2EthPrtSwF2VlanBandwidthActViolActEthCos1 OBJECT-TYPE
   SYNTAX      INTEGER
               {
               unchanged (256)
               }
   MAX-ACCESS  read-write
   STATUS      current
   DESCRIPTION
      "Path: swPort.editConf.vlan.bandwidth.action.violateAction.ethernet.cosDepth1

       Possibilities:
               unchanged   (256)"
   ::= {er1645v2EthPrtSwF2VlanEntry 150356224}

er1645v2EthPrtSwF2VlanBandwidthActViolActEthDei1 OBJECT-TYPE
   SYNTAX      INTEGER
               {
               unchanged (255),
               clear (0),
               set (1)
               }
   MAX-ACCESS  read-write
   STATUS      current
   DESCRIPTION
      "Path: swPort.editConf.vlan.bandwidth.action.violateAction.ethernet.deiDepth1

       Possibilities:
               unchanged   (255)
               clear   (0)
               set   (1)"
   ::= {er1645v2EthPrtSwF2VlanEntry 150361344}

er1645v2EthPrtSwF2VlanBandwidthActViolActEthCos2 OBJECT-TYPE
   SYNTAX      INTEGER
               {
               unchanged (256)
               }
   MAX-ACCESS  read-write
   STATUS      current
   DESCRIPTION
      "Path: swPort.editConf.vlan.bandwidth.action.violateAction.ethernet.cosDepth2

       Possibilities:
               unchanged   (256)"
   ::= {er1645v2EthPrtSwF2VlanEntry 150356480}

er1645v2EthPrtSwF2VlanBandwidthActViolActEthDei2 OBJECT-TYPE
   SYNTAX      INTEGER
               {
               unchanged (255),
               clear (0),
               set (1)
               }
   MAX-ACCESS  read-write
   STATUS      current
   DESCRIPTION
      "Path: swPort.editConf.vlan.bandwidth.action.violateAction.ethernet.deiDepth2

       Possibilities:
               unchanged   (255)
               clear   (0)
               set   (1)"
   ::= {er1645v2EthPrtSwF2VlanEntry 150361600}

er1645v2EthPrtSwF2VlanBandwidthActViolActEthCos3 OBJECT-TYPE
   SYNTAX      INTEGER
               {
               unchanged (256)
               }
   MAX-ACCESS  read-write
   STATUS      current
   DESCRIPTION
      "Path: swPort.editConf.vlan.bandwidth.action.violateAction.ethernet.cosDepth3

       Possibilities:
               unchanged   (256)"
   ::= {er1645v2EthPrtSwF2VlanEntry 150356736}

er1645v2EthPrtSwF2VlanBandwidthActViolActEthDei3 OBJECT-TYPE
   SYNTAX      INTEGER
               {
               unchanged (255),
               clear (0),
               set (1)
               }
   MAX-ACCESS  read-write
   STATUS      current
   DESCRIPTION
      "Path: swPort.editConf.vlan.bandwidth.action.violateAction.ethernet.deiDepth3

       Possibilities:
               unchanged   (255)
               clear   (0)
               set   (1)"
   ::= {er1645v2EthPrtSwF2VlanEntry 150361856}

er1645v2EthPrtSwF2VlanBandwidthActViolActEthCos4 OBJECT-TYPE
   SYNTAX      INTEGER
               {
               unchanged (256)
               }
   MAX-ACCESS  read-write
   STATUS      current
   DESCRIPTION
      "Path: swPort.editConf.vlan.bandwidth.action.violateAction.ethernet.cosDepth4

       Possibilities:
               unchanged   (256)"
   ::= {er1645v2EthPrtSwF2VlanEntry 150356992}

er1645v2EthPrtSwF2VlanBandwidthActViolActEthDei4 OBJECT-TYPE
   SYNTAX      INTEGER
               {
               unchanged (255),
               clear (0),
               set (1)
               }
   MAX-ACCESS  read-write
   STATUS      current
   DESCRIPTION
      "Path: swPort.editConf.vlan.bandwidth.action.violateAction.ethernet.deiDepth4

       Possibilities:
               unchanged   (255)
               clear   (0)
               set   (1)"
   ::= {er1645v2EthPrtSwF2VlanEntry 150362112}

er1645v2EthPrtSwF2VlanBandwidthActViolActEthCos5 OBJECT-TYPE
   SYNTAX      INTEGER
               {
               unchanged (256)
               }
   MAX-ACCESS  read-write
   STATUS      current
   DESCRIPTION
      "Path: swPort.editConf.vlan.bandwidth.action.violateAction.ethernet.cosDepth5

       Possibilities:
               unchanged   (256)"
   ::= {er1645v2EthPrtSwF2VlanEntry 150357248}

er1645v2EthPrtSwF2VlanBandwidthActViolActEthDei5 OBJECT-TYPE
   SYNTAX      INTEGER
               {
               unchanged (255),
               clear (0),
               set (1)
               }
   MAX-ACCESS  read-write
   STATUS      current
   DESCRIPTION
      "Path: swPort.editConf.vlan.bandwidth.action.violateAction.ethernet.deiDepth5

       Possibilities:
               unchanged   (255)
               clear   (0)
               set   (1)"
   ::= {er1645v2EthPrtSwF2VlanEntry 150362368}

er1645v2EthPrtSwF2VlanBandwidthActViolActEthCos6 OBJECT-TYPE
   SYNTAX      INTEGER
               {
               unchanged (256)
               }
   MAX-ACCESS  read-write
   STATUS      current
   DESCRIPTION
      "Path: swPort.editConf.vlan.bandwidth.action.violateAction.ethernet.cosDepth6

       Possibilities:
               unchanged   (256)"
   ::= {er1645v2EthPrtSwF2VlanEntry 150357504}

er1645v2EthPrtSwF2VlanBandwidthActViolActEthDei6 OBJECT-TYPE
   SYNTAX      INTEGER
               {
               unchanged (255),
               clear (0),
               set (1)
               }
   MAX-ACCESS  read-write
   STATUS      current
   DESCRIPTION
      "Path: swPort.editConf.vlan.bandwidth.action.violateAction.ethernet.deiDepth6

       Possibilities:
               unchanged   (255)
               clear   (0)
               set   (1)"
   ::= {er1645v2EthPrtSwF2VlanEntry 150362624}

er1645v2EthPrtSwF2VlanBandwidthActViolActEthCos7 OBJECT-TYPE
   SYNTAX      INTEGER
               {
               unchanged (256)
               }
   MAX-ACCESS  read-write
   STATUS      current
   DESCRIPTION
      "Path: swPort.editConf.vlan.bandwidth.action.violateAction.ethernet.cosDepth7

       Possibilities:
               unchanged   (256)"
   ::= {er1645v2EthPrtSwF2VlanEntry 150357760}

er1645v2EthPrtSwF2VlanBandwidthActViolActEthDei7 OBJECT-TYPE
   SYNTAX      INTEGER
               {
               unchanged (255),
               clear (0),
               set (1)
               }
   MAX-ACCESS  read-write
   STATUS      current
   DESCRIPTION
      "Path: swPort.editConf.vlan.bandwidth.action.violateAction.ethernet.deiDepth7

       Possibilities:
               unchanged   (255)
               clear   (0)
               set   (1)"
   ::= {er1645v2EthPrtSwF2VlanEntry 150362880}

er1645v2EthPrtSwF2VlanBandwidthActViolActEthCos8 OBJECT-TYPE
   SYNTAX      INTEGER
               {
               unchanged (256)
               }
   MAX-ACCESS  read-write
   STATUS      current
   DESCRIPTION
      "Path: swPort.editConf.vlan.bandwidth.action.violateAction.ethernet.cosDepth8

       Possibilities:
               unchanged   (256)"
   ::= {er1645v2EthPrtSwF2VlanEntry 150358016}

er1645v2EthPrtSwF2VlanBandwidthActViolActEthDei8 OBJECT-TYPE
   SYNTAX      INTEGER
               {
               unchanged (255),
               clear (0),
               set (1)
               }
   MAX-ACCESS  read-write
   STATUS      current
   DESCRIPTION
      "Path: swPort.editConf.vlan.bandwidth.action.violateAction.ethernet.deiDepth8

       Possibilities:
               unchanged   (255)
               clear   (0)
               set   (1)"
   ::= {er1645v2EthPrtSwF2VlanEntry 150363136}

er1645v2EthPrtSwF2VlanBandwidthActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPrtSwF2VlanEntry 150358272}

er1645v2EthPrtSwF2VlanBandwidthActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2EthPrtSwF2VlanEntry 150358528}

er1645v2EthPrtSwF2VlanBandwidthActViolActEthDrpLev OBJECT-TYPE
   SYNTAX      INTEGER
               {
               unchanged (0)
               }
   MAX-ACCESS  read-write
   STATUS      current
   DESCRIPTION
      "Path: swPort.editConf.vlan.bandwidth.action.violateAction.ethernet.dropLevel

       Possibilities:
               unchanged   (0)"
   ::= {er1645v2EthPrtSwF2VlanEntry 150358784}

er1645v2EthPrtSwF2VlanBandwidthActViolActEthDeFlag OBJECT-TYPE
   SYNTAX      INTEGER
               {
               unchanged (255),
               clear (0),
               set (1)
               }
   MAX-ACCESS  read-write
   STATUS      current
   DESCRIPTION
      "Path: swPort.editConf.vlan.bandwidth.action.violateAction.ethernet.deFlag

       Possibilities:
               unchanged   (255)
               clear   (0)
               set   (1)"
   ::= {er1645v2EthPrtSwF2VlanEntry 150359552}

er1645v2EthPrtSwF2VlanBandwidthActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPrtSwF2VlanEntry 150382848}

er1645v2EthPrtSwF2VlanBandwidthActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2EthPrtSwF2VlanEntry 150383104}

er1645v2EthPrtSwF2VlanBandwidthActViolActIpDrpLev OBJECT-TYPE
   SYNTAX      INTEGER
               {
               unchanged (0)
               }
   MAX-ACCESS  read-write
   STATUS      current
   DESCRIPTION
      "Path: swPort.editConf.vlan.bandwidth.action.violateAction.ip.dropLevel

       Possibilities:
               unchanged   (0)"
   ::= {er1645v2EthPrtSwF2VlanEntry 150383360}

er1645v2EthPrtSwF2VlanBandwidthActViolActIpDeFlag OBJECT-TYPE
   SYNTAX      INTEGER
               {
               unchanged (255),
               clear (0),
               set (1)
               }
   MAX-ACCESS  read-write
   STATUS      current
   DESCRIPTION
      "Path: swPort.editConf.vlan.bandwidth.action.violateAction.ip.deFlag

       Possibilities:
               unchanged   (255)
               clear   (0)
               set   (1)"
   ::= {er1645v2EthPrtSwF2VlanEntry 150384128}

er1645v2EthPrtSwF2VlanInbBwMode OBJECT-TYPE
   SYNTAX      INTEGER
               {
               reshaping (1),
               policing (2)
               }
   MAX-ACCESS  read-write
   STATUS      current
   DESCRIPTION
      "Path: swPort.editConf.vlan.inboundBandwidth.mode

       Possibilities:
               reshaping   (1)
               policing   (2)"
   ::= {er1645v2EthPrtSwF2VlanEntry 132120576}

er1645v2EthPrtSwF2VlanInbBwCir OBJECT-TYPE
   SYNTAX      Integer32
   MAX-ACCESS  read-write
   STATUS      current
   DESCRIPTION
      "Path: swPort.editConf.vlan.inboundBandwidth.cir"
   ::= {er1645v2EthPrtSwF2VlanEntry 118489088}

er1645v2EthPrtSwF2VlanInbBwEir OBJECT-TYPE
   SYNTAX      Integer32
   MAX-ACCESS  read-write
   STATUS      current
   DESCRIPTION
      "Path: swPort.editConf.vlan.inboundBandwidth.eir"
   ::= {er1645v2EthPrtSwF2VlanEntry 124780544}

er1645v2EthPrtSwF2VlanInbBwUnit OBJECT-TYPE
   SYNTAX      INTEGER
               {
               bitssec (1),
               percent (2)
               }
   MAX-ACCESS  read-write
   STATUS      current
   DESCRIPTION
      "Path: swPort.editConf.vlan.inboundBandwidth.unit

       Possibilities:
               bits/sec   (1)
               percent   (2)"
   ::= {er1645v2EthPrtSwF2VlanEntry 122683392}

er1645v2EthPrtSwF2VlanInbBwTc OBJECT-TYPE
   SYNTAX      INTEGER
               {
               auto (0)
               }
   MAX-ACCESS  read-write
   STATUS      current
   DESCRIPTION
      "Path: swPort.editConf.vlan.inboundBandwidth.tc

       Possibilities:
               auto   (0)"
   ::= {er1645v2EthPrtSwF2VlanEntry 123731968}

er1645v2EthPrtSwF2VlanInbBwTcFactor OBJECT-TYPE
   SYNTAX      INTEGER
               {
               ms (10),
               s100us (1)
               }
   MAX-ACCESS  read-write
   STATUS      current
   DESCRIPTION
      "Path: swPort.editConf.vlan.inboundBandwidth.tcFactor

       Possibilities:
               ms   (10)
               *100us   (1)"
   ::= {er1645v2EthPrtSwF2VlanEntry 125829120}

er1645v2EthPrtSwF2VlanInbBwCorrType OBJECT-TYPE
   SYNTAX      INTEGER
               {
               noCorrection (0),
               predefined (1),
               manual (2)
               }
   MAX-ACCESS  read-write
   STATUS      current
   DESCRIPTION
      "Path: swPort.editConf.vlan.inboundBandwidth.correction.type

       Possibilities:
               noCorrection   (0)
               predefined   (1)
               manual   (2)"
   ::= {er1645v2EthPrtSwF2VlanEntry 119668736}

er1645v2EthPrtSwF2VlanInbBwCorrPredefEncapsFrameRelay OBJECT-TYPE
   SYNTAX      DisplayString
   MAX-ACCESS  read-write
   STATUS      current
   DESCRIPTION
      "Path: swPort.editConf.vlan.inboundBandwidth.correction.predefined.encapsulation.frameRelay"
   ::= {er1645v2EthPrtSwF2VlanEntry 119817216}

er1645v2EthPrtSwF2VlanInbBwCorrPredefEncapsPpp OBJECT-TYPE
   SYNTAX      DisplayString
   MAX-ACCESS  read-write
   STATUS      current
   DESCRIPTION
      "Path: swPort.editConf.vlan.inboundBandwidth.correction.predefined.encapsulation.ppp"
   ::= {er1645v2EthPrtSwF2VlanEntry 119818240}

er1645v2EthPrtSwF2VlanInbBwCorrPredefEncapsAtmHl OBJECT-TYPE
   SYNTAX      INTEGER
               {
               rfc2684 (0),
               ppp (1),
               pppOverEthernet (2)
               }
   MAX-ACCESS  read-write
   STATUS      current
   DESCRIPTION
      "Path: swPort.editConf.vlan.inboundBandwidth.correction.predefined.encapsulation.atm.higherLayer

       Possibilities:
               rfc2684   (0)
               ppp   (1)
               pppOverEthernet   (2)"
   ::= {er1645v2EthPrtSwF2VlanEntry 119819392}

er1645v2EthPrtSwF2VlanInbBwCorrPredefEncapsAtmMp OBJECT-TYPE
   SYNTAX      INTEGER
               {
               llcEncapsulation (0),
               vcMultiplexing (1)
               }
   MAX-ACCESS  read-write
   STATUS      current
   DESCRIPTION
      "Path: swPort.editConf.vlan.inboundBandwidth.correction.predefined.encapsulation.atm.multiProtocol

       Possibilities:
               llcEncapsulation   (0)
               vcMultiplexing   (1)"
   ::= {er1645v2EthPrtSwF2VlanEntry 119819520}

er1645v2EthPrtSwF2VlanInbBwCorrPredefEncapsHdlc OBJECT-TYPE
   SYNTAX      DisplayString
   MAX-ACCESS  read-write
   STATUS      current
   DESCRIPTION
      "Path: swPort.editConf.vlan.inboundBandwidth.correction.predefined.encapsulation.hdlc"
   ::= {er1645v2EthPrtSwF2VlanEntry 119820288}

er1645v2EthPrtSwF2VlanInbBwCorrPredefEncapsEfmFs OBJECT-TYPE
   SYNTAX      Integer32
   MAX-ACCESS  read-write
   STATUS      current
   DESCRIPTION
      "Path: swPort.editConf.vlan.inboundBandwidth.correction.predefined.encapsulation.efm.fragmentSize"
   ::= {er1645v2EthPrtSwF2VlanEntry 119821440}

er1645v2EthPrtSwF2VlanInbBwCorrPredefEncapsEfmIb OBJECT-TYPE
   SYNTAX      Integer32
   MAX-ACCESS  read-write
   STATUS      current
   DESCRIPTION
      "Path: swPort.editConf.vlan.inboundBandwidth.correction.predefined.encapsulation.efm.idleBytes"
   ::= {er1645v2EthPrtSwF2VlanEntry 119821568}

er1645v2EthPrtSwF2VlanInbBwCorrPredefMode OBJECT-TYPE
   SYNTAX      INTEGER
               {
               routing (0),
               bridging (1)
               }
   MAX-ACCESS  read-write
   STATUS      current
   DESCRIPTION
      "Path: swPort.editConf.vlan.inboundBandwidth.correction.predefined.mode

       Possibilities:
               routing   (0)
               bridging   (1)"
   ::= {er1645v2EthPrtSwF2VlanEntry 119832576}

er1645v2EthPrtSwF2VlanInbBwCorrManualOverhead OBJECT-TYPE
   SYNTAX      Integer32
   MAX-ACCESS  read-write
   STATUS      current
   DESCRIPTION
      "Path: swPort.editConf.vlan.inboundBandwidth.correction.manual.overhead"
   ::= {er1645v2EthPrtSwF2VlanEntry 119931392}

er1645v2EthPrtSwF2VlanInbBwCorrManualFrameData OBJECT-TYPE
   SYNTAX      Counter32
   MAX-ACCESS  read-write
   STATUS      current
   DESCRIPTION
      "Path: swPort.editConf.vlan.inboundBandwidth.correction.manual.frameData

       32 bit unsigned wrappable counter."
   ::= {er1645v2EthPrtSwF2VlanEntry 119931904}

er1645v2EthPrtSwF2VlanInbBwCorrManualFrameHeader OBJECT-TYPE
   SYNTAX      Counter32
   MAX-ACCESS  read-write
   STATUS      current
   DESCRIPTION
      "Path: swPort.editConf.vlan.inboundBandwidth.correction.manual.frameHeader

       32 bit unsigned wrappable counter."
   ::= {er1645v2EthPrtSwF2VlanEntry 119932416}

er1645v2EthPrtSwF2VlanInbBwMaxFifoQLen OBJECT-TYPE
   SYNTAX      Integer32
   MAX-ACCESS  read-write
   STATUS      current
   DESCRIPTION
      "Path: swPort.editConf.vlan.inboundBandwidth.maxFifoQLen"
   ::= {er1645v2EthPrtSwF2VlanEntry 120586240}

er1645v2EthPrtSwF2VlanInbBwPriorityPolicy OBJECT-TYPE
   SYNTAX      DisplayString
   MAX-ACCESS  read-write
   STATUS      current
   DESCRIPTION
      "Path: swPort.editConf.vlan.inboundBandwidth.priorityPolicy"
   ::= {er1645v2EthPrtSwF2VlanEntry 121634816}

er1645v2EthPrtSwF2VlanInbBwDeFlagCir OBJECT-TYPE
   SYNTAX      INTEGER
               {
               allowed (1),
               notAllowed (2)
               }
   MAX-ACCESS  read-write
   STATUS      current
   DESCRIPTION
      "Path: swPort.editConf.vlan.inboundBandwidth.deFlag.cir

       Possibilities:
               allowed   (1)
               notAllowed   (2)"
   ::= {er1645v2EthPrtSwF2VlanEntry 131076096}

er1645v2EthPrtSwF2VlanInbBwDeFlagEir OBJECT-TYPE
   SYNTAX      INTEGER
               {
               allowed (1),
               notAllowed (2)
               }
   MAX-ACCESS  read-write
   STATUS      current
   DESCRIPTION
      "Path: swPort.editConf.vlan.inboundBandwidth.deFlag.eir

       Possibilities:
               allowed   (1)
               notAllowed   (2)"
   ::= {er1645v2EthPrtSwF2VlanEntry 131080192}

er1645v2EthPrtSwF2VlanInbBwDeFlagViolate OBJECT-TYPE
   SYNTAX      INTEGER
               {
               allowed (1),
               notAllowed (2)
               }
   MAX-ACCESS  read-write
   STATUS      current
   DESCRIPTION
      "Path: swPort.editConf.vlan.inboundBandwidth.deFlag.violate

       Possibilities:
               allowed   (1)
               notAllowed   (2)"
   ::= {er1645v2EthPrtSwF2VlanEntry 131084288}

er1645v2EthPrtSwF2VlanInbBwActCirActNone OBJECT-TYPE
   SYNTAX      OCTET STRING
   MAX-ACCESS  read-write
   STATUS      current
   DESCRIPTION
      "Path: swPort.editConf.vlan.inboundBandwidth.action.cirAction.none"
   ::= {er1645v2EthPrtSwF2VlanEntry 133308416}

er1645v2EthPrtSwF2VlanInbBwActCirActEthCos1 OBJECT-TYPE
   SYNTAX      INTEGER
               {
               unchanged (256)
               }
   MAX-ACCESS  read-write
   STATUS      current
   DESCRIPTION
      "Path: swPort.editConf.vlan.inboundBandwidth.action.cirAction.ethernet.cosDepth1

       Possibilities:
               unchanged   (256)"
   ::= {er1645v2EthPrtSwF2VlanEntry 133316864}

er1645v2EthPrtSwF2VlanInbBwActCirActEthDei1 OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deiDepth1

       Possibilities:
               unchanged   (255)
               clear   (0)
               set   (1)"
   ::= {er1645v2EthPrtSwF2VlanEntry 133321984}

er1645v2EthPrtSwF2VlanInbBwActCirActEthCos2 OBJECT-TYPE
   SYNTAX      INTEGER
               {
               unchanged (256)
               }
   MAX-ACCESS  read-write
   STATUS      current
   DESCRIPTION
      "Path: swPort.editConf.vlan.inboundBandwidth.action.cirAction.ethernet.cosDepth2

       Possibilities:
               unchanged   (256)"
   ::= {er1645v2EthPrtSwF2VlanEntry 133317120}

er1645v2EthPrtSwF2VlanInbBwActCirActEthDei2 OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deiDepth2

       Possibilities:
               unchanged   (255)
               clear   (0)
               set   (1)"
   ::= {er1645v2EthPrtSwF2VlanEntry 133322240}

er1645v2EthPrtSwF2VlanInbBwActCirActEthCos3 OBJECT-TYPE
   SYNTAX      INTEGER
               {
               unchanged (256)
               }
   MAX-ACCESS  read-write
   STATUS      current
   DESCRIPTION
      "Path: swPort.editConf.vlan.inboundBandwidth.action.cirAction.ethernet.cosDepth3

       Possibilities:
               unchanged   (256)"
   ::= {er1645v2EthPrtSwF2VlanEntry 133317376}

er1645v2EthPrtSwF2VlanInbBwActCirActEthDei3 OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deiDepth3

       Possibilities:
               unchanged   (255)
               clear   (0)
               set   (1)"
   ::= {er1645v2EthPrtSwF2VlanEntry 133322496}

er1645v2EthPrtSwF2VlanInbBwActCirActEthCos4 OBJECT-TYPE
   SYNTAX      INTEGER
               {
               unchanged (256)
               }
   MAX-ACCESS  read-write
   STATUS      current
   DESCRIPTION
      "Path: swPort.editConf.vlan.inboundBandwidth.action.cirAction.ethernet.cosDepth4

       Possibilities:
               unchanged   (256)"
   ::= {er1645v2EthPrtSwF2VlanEntry 133317632}

er1645v2EthPrtSwF2VlanInbBwActCirActEthDei4 OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deiDepth4

       Possibilities:
               unchanged   (255)
               clear   (0)
               set   (1)"
   ::= {er1645v2EthPrtSwF2VlanEntry 133322752}

er1645v2EthPrtSwF2VlanInbBwActCirActEthCos5 OBJECT-TYPE
   SYNTAX      INTEGER
               {
               unchanged (256)
               }
   MAX-ACCESS  read-write
   STATUS      current
   DESCRIPTION
      "Path: swPort.editConf.vlan.inboundBandwidth.action.cirAction.ethernet.cosDepth5

       Possibilities:
               unchanged   (256)"
   ::= {er1645v2EthPrtSwF2VlanEntry 133317888}

er1645v2EthPrtSwF2VlanInbBwActCirActEthDei5 OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deiDepth5

       Possibilities:
               unchanged   (255)
               clear   (0)
               set   (1)"
   ::= {er1645v2EthPrtSwF2VlanEntry 133323008}

er1645v2EthPrtSwF2VlanInbBwActCirActEthCos6 OBJECT-TYPE
   SYNTAX      INTEGER
               {
               unchanged (256)
               }
   MAX-ACCESS  read-write
   STATUS      current
   DESCRIPTION
      "Path: swPort.editConf.vlan.inboundBandwidth.action.cirAction.ethernet.cosDepth6

       Possibilities:
               unchanged   (256)"
   ::= {er1645v2EthPrtSwF2VlanEntry 133318144}

er1645v2EthPrtSwF2VlanInbBwActCirActEthDei6 OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deiDepth6

       Possibilities:
               unchanged   (255)
               clear   (0)
               set   (1)"
   ::= {er1645v2EthPrtSwF2VlanEntry 133323264}

er1645v2EthPrtSwF2VlanInbBwActCirActEthCos7 OBJECT-TYPE
   SYNTAX      INTEGER
               {
               unchanged (256)
               }
   MAX-ACCESS  read-write
   STATUS      current
   DESCRIPTION
      "Path: swPort.editConf.vlan.inboundBandwidth.action.cirAction.ethernet.cosDepth7

       Possibilities:
               unchanged   (256)"
   ::= {er1645v2EthPrtSwF2VlanEntry 133318400}

er1645v2EthPrtSwF2VlanInbBwActCirActEthDei7 OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deiDepth7

       Possibilities:
               unchanged   (255)
               clear   (0)
               set   (1)"
   ::= {er1645v2EthPrtSwF2VlanEntry 133323520}

er1645v2EthPrtSwF2VlanInbBwActCirActEthCos8 OBJECT-TYPE
   SYNTAX      INTEGER
               {
               unchanged (256)
               }
   MAX-ACCESS  read-write
   STATUS      current
   DESCRIPTION
      "Path: swPort.editConf.vlan.inboundBandwidth.action.cirAction.ethernet.cosDepth8

       Possibilities:
               unchanged   (256)"
   ::= {er1645v2EthPrtSwF2VlanEntry 133318656}

er1645v2EthPrtSwF2VlanInbBwActCirActEthDei8 OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deiDepth8

       Possibilities:
               unchanged   (255)
               clear   (0)
               set   (1)"
   ::= {er1645v2EthPrtSwF2VlanEntry 133323776}

er1645v2EthPrtSwF2VlanInbBwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.inboundBandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPrtSwF2VlanEntry 133318912}

er1645v2EthPrtSwF2VlanInbBwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.inboundBandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2EthPrtSwF2VlanEntry 133319168}

er1645v2EthPrtSwF2VlanInbBwActCirActEthDrpLev OBJECT-TYPE
   SYNTAX      INTEGER
               {
               unchanged (0)
               }
   MAX-ACCESS  read-write
   STATUS      current
   DESCRIPTION
      "Path: swPort.editConf.vlan.inboundBandwidth.action.cirAction.ethernet.dropLevel

       Possibilities:
               unchanged   (0)"
   ::= {er1645v2EthPrtSwF2VlanEntry 133319424}

er1645v2EthPrtSwF2VlanInbBwActCirActEthDeFlag OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deFlag

       Possibilities:
               unchanged   (255)
               clear   (0)
               set   (1)"
   ::= {er1645v2EthPrtSwF2VlanEntry 133320192}

er1645v2EthPrtSwF2VlanInbBwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.inboundBandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPrtSwF2VlanEntry 133343488}

er1645v2EthPrtSwF2VlanInbBwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.inboundBandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2EthPrtSwF2VlanEntry 133343744}

er1645v2EthPrtSwF2VlanInbBwActCirActIpDrpLev OBJECT-TYPE
   SYNTAX      INTEGER
               {
               unchanged (0)
               }
   MAX-ACCESS  read-write
   STATUS      current
   DESCRIPTION
      "Path: swPort.editConf.vlan.inboundBandwidth.action.cirAction.ip.dropLevel

       Possibilities:
               unchanged   (0)"
   ::= {er1645v2EthPrtSwF2VlanEntry 133344000}

er1645v2EthPrtSwF2VlanInbBwActCirActIpDeFlag OBJECT-TYPE
   SYNTAX      INTEGER
               {
               unchanged (255),
               clear (0),
               set (1)
               }
   MAX-ACCESS  read-write
   STATUS      current
   DESCRIPTION
      "Path: swPort.editConf.vlan.inboundBandwidth.action.cirAction.ip.deFlag

       Possibilities:
               unchanged   (255)
               clear   (0)
               set   (1)"
   ::= {er1645v2EthPrtSwF2VlanEntry 133344768}

er1645v2EthPrtSwF2VlanInbBwActEirActNone OBJECT-TYPE
   SYNTAX      OCTET STRING
   MAX-ACCESS  read-write
   STATUS      current
   DESCRIPTION
      "Path: swPort.editConf.vlan.inboundBandwidth.action.eirAction.none"
   ::= {er1645v2EthPrtSwF2VlanEntry 133439488}

er1645v2EthPrtSwF2VlanInbBwActEirActEthCos1 OBJECT-TYPE
   SYNTAX      INTEGER
               {
               unchanged (256)
               }
   MAX-ACCESS  read-write
   STATUS      current
   DESCRIPTION
      "Path: swPort.editConf.vlan.inboundBandwidth.action.eirAction.ethernet.cosDepth1

       Possibilities:
               unchanged   (256)"
   ::= {er1645v2EthPrtSwF2VlanEntry 133447936}

er1645v2EthPrtSwF2VlanInbBwActEirActEthDei1 OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deiDepth1

       Possibilities:
               unchanged   (255)
               clear   (0)
               set   (1)"
   ::= {er1645v2EthPrtSwF2VlanEntry 133453056}

er1645v2EthPrtSwF2VlanInbBwActEirActEthCos2 OBJECT-TYPE
   SYNTAX      INTEGER
               {
               unchanged (256)
               }
   MAX-ACCESS  read-write
   STATUS      current
   DESCRIPTION
      "Path: swPort.editConf.vlan.inboundBandwidth.action.eirAction.ethernet.cosDepth2

       Possibilities:
               unchanged   (256)"
   ::= {er1645v2EthPrtSwF2VlanEntry 133448192}

er1645v2EthPrtSwF2VlanInbBwActEirActEthDei2 OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deiDepth2

       Possibilities:
               unchanged   (255)
               clear   (0)
               set   (1)"
   ::= {er1645v2EthPrtSwF2VlanEntry 133453312}

er1645v2EthPrtSwF2VlanInbBwActEirActEthCos3 OBJECT-TYPE
   SYNTAX      INTEGER
               {
               unchanged (256)
               }
   MAX-ACCESS  read-write
   STATUS      current
   DESCRIPTION
      "Path: swPort.editConf.vlan.inboundBandwidth.action.eirAction.ethernet.cosDepth3

       Possibilities:
               unchanged   (256)"
   ::= {er1645v2EthPrtSwF2VlanEntry 133448448}

er1645v2EthPrtSwF2VlanInbBwActEirActEthDei3 OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deiDepth3

       Possibilities:
               unchanged   (255)
               clear   (0)
               set   (1)"
   ::= {er1645v2EthPrtSwF2VlanEntry 133453568}

er1645v2EthPrtSwF2VlanInbBwActEirActEthCos4 OBJECT-TYPE
   SYNTAX      INTEGER
               {
               unchanged (256)
               }
   MAX-ACCESS  read-write
   STATUS      current
   DESCRIPTION
      "Path: swPort.editConf.vlan.inboundBandwidth.action.eirAction.ethernet.cosDepth4

       Possibilities:
               unchanged   (256)"
   ::= {er1645v2EthPrtSwF2VlanEntry 133448704}

er1645v2EthPrtSwF2VlanInbBwActEirActEthDei4 OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deiDepth4

       Possibilities:
               unchanged   (255)
               clear   (0)
               set   (1)"
   ::= {er1645v2EthPrtSwF2VlanEntry 133453824}

er1645v2EthPrtSwF2VlanInbBwActEirActEthCos5 OBJECT-TYPE
   SYNTAX      INTEGER
               {
               unchanged (256)
               }
   MAX-ACCESS  read-write
   STATUS      current
   DESCRIPTION
      "Path: swPort.editConf.vlan.inboundBandwidth.action.eirAction.ethernet.cosDepth5

       Possibilities:
               unchanged   (256)"
   ::= {er1645v2EthPrtSwF2VlanEntry 133448960}

er1645v2EthPrtSwF2VlanInbBwActEirActEthDei5 OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deiDepth5

       Possibilities:
               unchanged   (255)
               clear   (0)
               set   (1)"
   ::= {er1645v2EthPrtSwF2VlanEntry 133454080}

er1645v2EthPrtSwF2VlanInbBwActEirActEthCos6 OBJECT-TYPE
   SYNTAX      INTEGER
               {
               unchanged (256)
               }
   MAX-ACCESS  read-write
   STATUS      current
   DESCRIPTION
      "Path: swPort.editConf.vlan.inboundBandwidth.action.eirAction.ethernet.cosDepth6

       Possibilities:
               unchanged   (256)"
   ::= {er1645v2EthPrtSwF2VlanEntry 133449216}

er1645v2EthPrtSwF2VlanInbBwActEirActEthDei6 OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deiDepth6

       Possibilities:
               unchanged   (255)
               clear   (0)
               set   (1)"
   ::= {er1645v2EthPrtSwF2VlanEntry 133454336}

er1645v2EthPrtSwF2VlanInbBwActEirActEthCos7 OBJECT-TYPE
   SYNTAX      INTEGER
               {
               unchanged (256)
               }
   MAX-ACCESS  read-write
   STATUS      current
   DESCRIPTION
      "Path: swPort.editConf.vlan.inboundBandwidth.action.eirAction.ethernet.cosDepth7

       Possibilities:
               unchanged   (256)"
   ::= {er1645v2EthPrtSwF2VlanEntry 133449472}

er1645v2EthPrtSwF2VlanInbBwActEirActEthDei7 OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deiDepth7

       Possibilities:
               unchanged   (255)
               clear   (0)
               set   (1)"
   ::= {er1645v2EthPrtSwF2VlanEntry 133454592}

er1645v2EthPrtSwF2VlanInbBwActEirActEthCos8 OBJECT-TYPE
   SYNTAX      INTEGER
               {
               unchanged (256)
               }
   MAX-ACCESS  read-write
   STATUS      current
   DESCRIPTION
      "Path: swPort.editConf.vlan.inboundBandwidth.action.eirAction.ethernet.cosDepth8

       Possibilities:
               unchanged   (256)"
   ::= {er1645v2EthPrtSwF2VlanEntry 133449728}

er1645v2EthPrtSwF2VlanInbBwActEirActEthDei8 OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deiDepth8

       Possibilities:
               unchanged   (255)
               clear   (0)
               set   (1)"
   ::= {er1645v2EthPrtSwF2VlanEntry 133454848}

er1645v2EthPrtSwF2VlanInbBwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.inboundBandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPrtSwF2VlanEntry 133449984}

er1645v2EthPrtSwF2VlanInbBwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.inboundBandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2EthPrtSwF2VlanEntry 133450240}

er1645v2EthPrtSwF2VlanInbBwActEirActEthDrpLev OBJECT-TYPE
   SYNTAX      INTEGER
               {
               unchanged (0)
               }
   MAX-ACCESS  read-write
   STATUS      current
   DESCRIPTION
      "Path: swPort.editConf.vlan.inboundBandwidth.action.eirAction.ethernet.dropLevel

       Possibilities:
               unchanged   (0)"
   ::= {er1645v2EthPrtSwF2VlanEntry 133450496}

er1645v2EthPrtSwF2VlanInbBwActEirActEthDeFlag OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deFlag

       Possibilities:
               unchanged   (255)
               clear   (0)
               set   (1)"
   ::= {er1645v2EthPrtSwF2VlanEntry 133451264}

er1645v2EthPrtSwF2VlanInbBwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.inboundBandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPrtSwF2VlanEntry 133474560}

er1645v2EthPrtSwF2VlanInbBwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.inboundBandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2EthPrtSwF2VlanEntry 133474816}

er1645v2EthPrtSwF2VlanInbBwActEirActIpDrpLev OBJECT-TYPE
   SYNTAX      INTEGER
               {
               unchanged (0)
               }
   MAX-ACCESS  read-write
   STATUS      current
   DESCRIPTION
      "Path: swPort.editConf.vlan.inboundBandwidth.action.eirAction.ip.dropLevel

       Possibilities:
               unchanged   (0)"
   ::= {er1645v2EthPrtSwF2VlanEntry 133475072}

er1645v2EthPrtSwF2VlanInbBwActEirActIpDeFlag OBJECT-TYPE
   SYNTAX      INTEGER
               {
               unchanged (255),
               clear (0),
               set (1)
               }
   MAX-ACCESS  read-write
   STATUS      current
   DESCRIPTION
      "Path: swPort.editConf.vlan.inboundBandwidth.action.eirAction.ip.deFlag

       Possibilities:
               unchanged   (255)
               clear   (0)
               set   (1)"
   ::= {er1645v2EthPrtSwF2VlanEntry 133475840}

er1645v2EthPrtSwF2VlanInbBwActViolActNone OBJECT-TYPE
   SYNTAX      OCTET STRING
   MAX-ACCESS  read-write
   STATUS      current
   DESCRIPTION
      "Path: swPort.editConf.vlan.inboundBandwidth.action.violateAction.none"
   ::= {er1645v2EthPrtSwF2VlanEntry 133570560}

er1645v2EthPrtSwF2VlanInbBwActViolActDrop OBJECT-TYPE
   SYNTAX      OCTET STRING
   MAX-ACCESS  read-write
   STATUS      current
   DESCRIPTION
      "Path: swPort.editConf.vlan.inboundBandwidth.action.violateAction.drop"
   ::= {er1645v2EthPrtSwF2VlanEntry 133586944}

er1645v2EthPrtSwF2VlanInbBwActViolActEthCos1 OBJECT-TYPE
   SYNTAX      INTEGER
               {
               unchanged (256)
               }
   MAX-ACCESS  read-write
   STATUS      current
   DESCRIPTION
      "Path: swPort.editConf.vlan.inboundBandwidth.action.violateAction.ethernet.cosDepth1

       Possibilities:
               unchanged   (256)"
   ::= {er1645v2EthPrtSwF2VlanEntry 133579008}

er1645v2EthPrtSwF2VlanInbBwActViolActEthDei1 OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deiDepth1

       Possibilities:
               unchanged   (255)
               clear   (0)
               set   (1)"
   ::= {er1645v2EthPrtSwF2VlanEntry 133584128}

er1645v2EthPrtSwF2VlanInbBwActViolActEthCos2 OBJECT-TYPE
   SYNTAX      INTEGER
               {
               unchanged (256)
               }
   MAX-ACCESS  read-write
   STATUS      current
   DESCRIPTION
      "Path: swPort.editConf.vlan.inboundBandwidth.action.violateAction.ethernet.cosDepth2

       Possibilities:
               unchanged   (256)"
   ::= {er1645v2EthPrtSwF2VlanEntry 133579264}

er1645v2EthPrtSwF2VlanInbBwActViolActEthDei2 OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deiDepth2

       Possibilities:
               unchanged   (255)
               clear   (0)
               set   (1)"
   ::= {er1645v2EthPrtSwF2VlanEntry 133584384}

er1645v2EthPrtSwF2VlanInbBwActViolActEthCos3 OBJECT-TYPE
   SYNTAX      INTEGER
               {
               unchanged (256)
               }
   MAX-ACCESS  read-write
   STATUS      current
   DESCRIPTION
      "Path: swPort.editConf.vlan.inboundBandwidth.action.violateAction.ethernet.cosDepth3

       Possibilities:
               unchanged   (256)"
   ::= {er1645v2EthPrtSwF2VlanEntry 133579520}

er1645v2EthPrtSwF2VlanInbBwActViolActEthDei3 OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deiDepth3

       Possibilities:
               unchanged   (255)
               clear   (0)
               set   (1)"
   ::= {er1645v2EthPrtSwF2VlanEntry 133584640}

er1645v2EthPrtSwF2VlanInbBwActViolActEthCos4 OBJECT-TYPE
   SYNTAX      INTEGER
               {
               unchanged (256)
               }
   MAX-ACCESS  read-write
   STATUS      current
   DESCRIPTION
      "Path: swPort.editConf.vlan.inboundBandwidth.action.violateAction.ethernet.cosDepth4

       Possibilities:
               unchanged   (256)"
   ::= {er1645v2EthPrtSwF2VlanEntry 133579776}

er1645v2EthPrtSwF2VlanInbBwActViolActEthDei4 OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deiDepth4

       Possibilities:
               unchanged   (255)
               clear   (0)
               set   (1)"
   ::= {er1645v2EthPrtSwF2VlanEntry 133584896}

er1645v2EthPrtSwF2VlanInbBwActViolActEthCos5 OBJECT-TYPE
   SYNTAX      INTEGER
               {
               unchanged (256)
               }
   MAX-ACCESS  read-write
   STATUS      current
   DESCRIPTION
      "Path: swPort.editConf.vlan.inboundBandwidth.action.violateAction.ethernet.cosDepth5

       Possibilities:
               unchanged   (256)"
   ::= {er1645v2EthPrtSwF2VlanEntry 133580032}

er1645v2EthPrtSwF2VlanInbBwActViolActEthDei5 OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deiDepth5

       Possibilities:
               unchanged   (255)
               clear   (0)
               set   (1)"
   ::= {er1645v2EthPrtSwF2VlanEntry 133585152}

er1645v2EthPrtSwF2VlanInbBwActViolActEthCos6 OBJECT-TYPE
   SYNTAX      INTEGER
               {
               unchanged (256)
               }
   MAX-ACCESS  read-write
   STATUS      current
   DESCRIPTION
      "Path: swPort.editConf.vlan.inboundBandwidth.action.violateAction.ethernet.cosDepth6

       Possibilities:
               unchanged   (256)"
   ::= {er1645v2EthPrtSwF2VlanEntry 133580288}

er1645v2EthPrtSwF2VlanInbBwActViolActEthDei6 OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deiDepth6

       Possibilities:
               unchanged   (255)
               clear   (0)
               set   (1)"
   ::= {er1645v2EthPrtSwF2VlanEntry 133585408}

er1645v2EthPrtSwF2VlanInbBwActViolActEthCos7 OBJECT-TYPE
   SYNTAX      INTEGER
               {
               unchanged (256)
               }
   MAX-ACCESS  read-write
   STATUS      current
   DESCRIPTION
      "Path: swPort.editConf.vlan.inboundBandwidth.action.violateAction.ethernet.cosDepth7

       Possibilities:
               unchanged   (256)"
   ::= {er1645v2EthPrtSwF2VlanEntry 133580544}

er1645v2EthPrtSwF2VlanInbBwActViolActEthDei7 OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deiDepth7

       Possibilities:
               unchanged   (255)
               clear   (0)
               set   (1)"
   ::= {er1645v2EthPrtSwF2VlanEntry 133585664}

er1645v2EthPrtSwF2VlanInbBwActViolActEthCos8 OBJECT-TYPE
   SYNTAX      INTEGER
               {
               unchanged (256)
               }
   MAX-ACCESS  read-write
   STATUS      current
   DESCRIPTION
      "Path: swPort.editConf.vlan.inboundBandwidth.action.violateAction.ethernet.cosDepth8

       Possibilities:
               unchanged   (256)"
   ::= {er1645v2EthPrtSwF2VlanEntry 133580800}

er1645v2EthPrtSwF2VlanInbBwActViolActEthDei8 OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deiDepth8

       Possibilities:
               unchanged   (255)
               clear   (0)
               set   (1)"
   ::= {er1645v2EthPrtSwF2VlanEntry 133585920}

er1645v2EthPrtSwF2VlanInbBwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.inboundBandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPrtSwF2VlanEntry 133581056}

er1645v2EthPrtSwF2VlanInbBwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.inboundBandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2EthPrtSwF2VlanEntry 133581312}

er1645v2EthPrtSwF2VlanInbBwActViolActEthDrpLev OBJECT-TYPE
   SYNTAX      INTEGER
               {
               unchanged (0)
               }
   MAX-ACCESS  read-write
   STATUS      current
   DESCRIPTION
      "Path: swPort.editConf.vlan.inboundBandwidth.action.violateAction.ethernet.dropLevel

       Possibilities:
               unchanged   (0)"
   ::= {er1645v2EthPrtSwF2VlanEntry 133581568}

er1645v2EthPrtSwF2VlanInbBwActViolActEthDeFlag OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deFlag

       Possibilities:
               unchanged   (255)
               clear   (0)
               set   (1)"
   ::= {er1645v2EthPrtSwF2VlanEntry 133582336}

er1645v2EthPrtSwF2VlanInbBwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.inboundBandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPrtSwF2VlanEntry 133605632}

er1645v2EthPrtSwF2VlanInbBwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.inboundBandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2EthPrtSwF2VlanEntry 133605888}

er1645v2EthPrtSwF2VlanInbBwActViolActIpDrpLev OBJECT-TYPE
   SYNTAX      INTEGER
               {
               unchanged (0)
               }
   MAX-ACCESS  read-write
   STATUS      current
   DESCRIPTION
      "Path: swPort.editConf.vlan.inboundBandwidth.action.violateAction.ip.dropLevel

       Possibilities:
               unchanged   (0)"
   ::= {er1645v2EthPrtSwF2VlanEntry 133606144}

er1645v2EthPrtSwF2VlanInbBwActViolActIpDeFlag OBJECT-TYPE
   SYNTAX      INTEGER
               {
               unchanged (255),
               clear (0),
               set (1)
               }
   MAX-ACCESS  read-write
   STATUS      current
   DESCRIPTION
      "Path: swPort.editConf.vlan.inboundBandwidth.action.violateAction.ip.deFlag

       Possibilities:
               unchanged   (255)
               clear   (0)
               set   (1)"
   ::= {er1645v2EthPrtSwF2VlanEntry 133606912}

er1645v2EthPrtSwF2VlanPppoE OBJECT-TYPE
   SYNTAX      INTEGER
               {
               disabled (0),
               enabled (1)
               }
   MAX-ACCESS  read-write
   STATUS      current
   DESCRIPTION
      "Path: swPort.editConf.vlan.pppoE

       Possibilities:
               disabled   (0)
               enabled   (1)"
   ::= {er1645v2EthPrtSwF2VlanEntry 838860800}

er1645v2EthPrtSwF2VlanPppLnkMOperation OBJECT-TYPE
   SYNTAX      INTEGER
               {
               disabled (0),
               enabled (1)
               }
   MAX-ACCESS  read-write
   STATUS      current
   DESCRIPTION
      "Path: swPort.editConf.vlan.ppp.linkMonitoring.operation

       Possibilities:
               disabled   (0)
               enabled   (1)"
   ::= {er1645v2EthPrtSwF2VlanEntry 251724032}

er1645v2EthPrtSwF2VlanPppLnkMInterval OBJECT-TYPE
   SYNTAX      TimeTicks
   MAX-ACCESS  read-write
   STATUS      current
   DESCRIPTION
      "Path: swPort.editConf.vlan.ppp.linkMonitoring.interval

       Time in centi-second."
   ::= {er1645v2EthPrtSwF2VlanEntry 251724288}

er1645v2EthPrtSwF2VlanPppLnkMRepTimeOut OBJECT-TYPE
   SYNTAX      TimeTicks
   MAX-ACCESS  read-write
   STATUS      current
   DESCRIPTION
      "Path: swPort.editConf.vlan.ppp.linkMonitoring.replyTimeOut

       Time in centi-second."
   ::= {er1645v2EthPrtSwF2VlanEntry 251724544}

er1645v2EthPrtSwF2VlanPppLnkMFailsPrmt OBJECT-TYPE
   SYNTAX      Integer32
   MAX-ACCESS  read-write
   STATUS      current
   DESCRIPTION
      "Path: swPort.editConf.vlan.ppp.linkMonitoring.failsPermitted"
   ::= {er1645v2EthPrtSwF2VlanEntry 251724800}

er1645v2EthPrtSwF2VlanPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: swPort.editConf.vlan.ppp.authentication

       Possibilities:
               disabled   (0)
               chap   (1)
               pap   (2)
               chapOrPap   (3)
               msChap   (4)
               msChapV2   (5)"
   ::= {er1645v2EthPrtSwF2VlanEntry 251789312}

er1645v2EthPrtSwF2VlanPppAuthenPeriod OBJECT-TYPE
   SYNTAX      TimeTicks
   MAX-ACCESS  read-write
   STATUS      current
   DESCRIPTION
      "Path: swPort.editConf.vlan.ppp.authenPeriod

       Time in centi-second."
   ::= {er1645v2EthPrtSwF2VlanEntry 251854848}

er1645v2EthPrtSwF2VlanPppSessionName OBJECT-TYPE
   SYNTAX      DisplayString
   MAX-ACCESS  read-write
   STATUS      current
   DESCRIPTION
      "Path: swPort.editConf.vlan.ppp.sessionName"
   ::= {er1645v2EthPrtSwF2VlanEntry 251985920}

er1645v2EthPrtSwF2VlanPppSessionSecret OBJECT-TYPE
   SYNTAX      DisplayString
   MAX-ACCESS  read-write
   STATUS      current
   DESCRIPTION
      "Path: swPort.editConf.vlan.ppp.sessionSecret"
   ::= {er1645v2EthPrtSwF2VlanEntry 252051456}

er1645v2EthPrtSwF2VlanPppEncModeSessionSecret OBJECT-TYPE
   SYNTAX      INTEGER
               {
               none (1),
               encrypt (2),
               encType1 (3),
               invalid (128)
               }
   MAX-ACCESS  read-write
   STATUS      current
   DESCRIPTION
      "Path: swPort.editConf.vlan.ppp.encModeSessionSecret

       Possibilities:
               none   (1)
               encrypt   (2)
               encType1   (3)
               invalid   (128)"
   ::= {er1645v2EthPrtSwF2VlanEntry 252182528}

er1645v2EthPrtSwF2VlanPppEncSessionSecret OBJECT-TYPE
   SYNTAX      DisplayString
   MAX-ACCESS  read-write
   STATUS      current
   DESCRIPTION
      "Path: swPort.editConf.vlan.ppp.encSessionSecret"
   ::= {er1645v2EthPrtSwF2VlanEntry 252248064}

er1645v2EthPrtSwF2VlanPppServiceName OBJECT-TYPE
   SYNTAX      DisplayString
   MAX-ACCESS  read-write
   STATUS      current
   DESCRIPTION
      "Path: swPort.editConf.vlan.ppp.serviceName"
   ::= {er1645v2EthPrtSwF2VlanEntry 252116992}

er1645v2EthPrtSwF2VlanPbbMode OBJECT-TYPE
   SYNTAX      INTEGER
               {
               disabled (0),
               static (1),
               dynamicPtp (2),
               dynamicPtmp (3)
               }
   MAX-ACCESS  read-write
   STATUS      current
   DESCRIPTION
      "Path: swPort.editConf.vlan.pbb.mode

       Possibilities:
               disabled   (0)
               static   (1)
               dynamicPtp   (2)
               dynamicPtmp   (3)"
   ::= {er1645v2EthPrtSwF2VlanEntry 1174667264}

er1645v2EthPrtSwF2VlanPbbTxCos OBJECT-TYPE
   SYNTAX      Integer32
   MAX-ACCESS  read-write
   STATUS      current
   DESCRIPTION
      "Path: swPort.editConf.vlan.pbb.txCos"
   ::= {er1645v2EthPrtSwF2VlanEntry 1175191552}

er1645v2EthPrtSwF2VlanPbbIsid OBJECT-TYPE
   SYNTAX      Integer32
   MAX-ACCESS  read-write
   STATUS      current
   DESCRIPTION
      "Path: swPort.editConf.vlan.pbb.isid"
   ::= {er1645v2EthPrtSwF2VlanEntry 1175453696}

er1645v2EthPrtSwF2VlanPbbDestMac OBJECT-TYPE
   SYNTAX      OCTET STRING
   MAX-ACCESS  read-write
   STATUS      current
   DESCRIPTION
      "Path: swPort.editConf.vlan.pbb.destMac

       MAC address."
   ::= {er1645v2EthPrtSwF2VlanEntry 1175715840}

er1645v2EthPrtSwF2VlanPbbCustomGroupMac OBJECT-TYPE
   SYNTAX      OCTET STRING
   MAX-ACCESS  read-write
   STATUS      current
   DESCRIPTION
      "Path: swPort.editConf.vlan.pbb.customGroupMac

       MAC address."
   ::= {er1645v2EthPrtSwF2VlanEntry 1175977984}

er1645v2EthPrtSwF2VlanIpSaddr OBJECT-TYPE
   SYNTAX      SEQUENCE OF Er1645v2EthPrtSwF2VlanIpSaddrEntry
   MAX-ACCESS  not-accessible
   STATUS      current
   DESCRIPTION
      ""
   ::= {er1645v2EthPrtSwF2Vlan 51838976}

er1645v2EthPrtSwF2VlanIpSaddrEntry OBJECT-TYPE
   SYNTAX      Er1645v2EthPrtSwF2VlanIpSaddrEntry
   MAX-ACCESS  not-accessible
   STATUS      current
   DESCRIPTION
      ""
   INDEX      { er1645v2EthPrtSwF2VlanIpSaddrGlobalIx,
                er1645v2EthPrtSwF2VlanTableIx,
                er1645v2EthPrtSwF2VlanIpSaddrTableIx }
   ::= {er1645v2EthPrtSwF2VlanIpSaddr 1}

Er1645v2EthPrtSwF2VlanIpSaddrEntry ::=
   SEQUENCE
      {
      er1645v2EthPrtSwF2VlanIpSaddrActions
         VariableLengthTableActions,
      er1645v2EthPrtSwF2VlanIpSaddrGlobalIx
         GlobalIndex,
      er1645v2EthPrtSwF2VlanIpSaddrTableIx
         TableIndex,
      er1645v2EthPrtSwF2VlanIpSaddrAddress
         IpAddress,
      er1645v2EthPrtSwF2VlanIpSaddrNetMask
         IpAddress
      }

er1645v2EthPrtSwF2VlanIpSaddrActions OBJECT-TYPE
   SYNTAX      VariableLengthTableActions
   MAX-ACCESS  read-write
   STATUS      current
   DESCRIPTION
      "By way of this field, some manipulations
       on this table may be performed."
   ::= {er1645v2EthPrtSwF2VlanIpSaddrEntry 2}

er1645v2EthPrtSwF2VlanIpSaddrGlobalIx OBJECT-TYPE
   SYNTAX      GlobalIndex
   MAX-ACCESS  not-accessible
   STATUS      current
   DESCRIPTION
      "The value of the tlsCntTreeGlobalIndex of the MANAGED OBJECT."
   ::= {er1645v2EthPrtSwF2VlanIpSaddrEntry 10}

er1645v2EthPrtSwF2VlanIpSaddrTableIx OBJECT-TYPE
   SYNTAX      TableIndex
   MAX-ACCESS  not-accessible
   STATUS      current
   DESCRIPTION
      ""
   ::= {er1645v2EthPrtSwF2VlanIpSaddrEntry 11}

er1645v2EthPrtSwF2VlanIpSaddrAddress OBJECT-TYPE
   SYNTAX      IpAddress
   MAX-ACCESS  read-write
   STATUS      current
   DESCRIPTION
      "Path: swPort.editConf.vlan.ip.secondaryIp.address"
   ::= {er1645v2EthPrtSwF2VlanIpSaddrEntry 2030043136}

er1645v2EthPrtSwF2VlanIpSaddrNetMask OBJECT-TYPE
   SYNTAX      IpAddress
   MAX-ACCESS  read-write
   STATUS      current
   DESCRIPTION
      "Path: swPort.editConf.vlan.ip.secondaryIp.netMask"
   ::= {er1645v2EthPrtSwF2VlanIpSaddrEntry 2063597568}

er1645v2EthPrtSwF2VlanIpH OBJECT-TYPE
   SYNTAX      SEQUENCE OF Er1645v2EthPrtSwF2VlanIpHEntry
   MAX-ACCESS  not-accessible
   STATUS      current
   DESCRIPTION
      ""
   ::= {er1645v2EthPrtSwF2Vlan 51314688}

er1645v2EthPrtSwF2VlanIpHEntry OBJECT-TYPE
   SYNTAX      Er1645v2EthPrtSwF2VlanIpHEntry
   MAX-ACCESS  not-accessible
   STATUS      current
   DESCRIPTION
      ""
   INDEX      { er1645v2EthPrtSwF2VlanIpHGlobalIx,
                er1645v2EthPrtSwF2VlanTableIx,
                er1645v2EthPrtSwF2VlanIpHTableIx }
   ::= {er1645v2EthPrtSwF2VlanIpH 1}

Er1645v2EthPrtSwF2VlanIpHEntry ::=
   SEQUENCE
      {
      er1645v2EthPrtSwF2VlanIpHActions
         VariableLengthTableActions,
      er1645v2EthPrtSwF2VlanIpHGlobalIx
         GlobalIndex,
      er1645v2EthPrtSwF2VlanIpHTableIx
         TableIndex,
      er1645v2EthPrtSwF2VlanIpHAddress
         IpAddress,
      er1645v2EthPrtSwF2VlanIpHDhcpRelayOptionSubscriberId
         DisplayString
      }

er1645v2EthPrtSwF2VlanIpHActions OBJECT-TYPE
   SYNTAX      VariableLengthTableActions
   MAX-ACCESS  read-write
   STATUS      current
   DESCRIPTION
      "By way of this field, some manipulations
       on this table may be performed."
   ::= {er1645v2EthPrtSwF2VlanIpHEntry 2}

er1645v2EthPrtSwF2VlanIpHGlobalIx OBJECT-TYPE
   SYNTAX      GlobalIndex
   MAX-ACCESS  not-accessible
   STATUS      current
   DESCRIPTION
      "The value of the tlsCntTreeGlobalIndex of the MANAGED OBJECT."
   ::= {er1645v2EthPrtSwF2VlanIpHEntry 10}

er1645v2EthPrtSwF2VlanIpHTableIx OBJECT-TYPE
   SYNTAX      TableIndex
   MAX-ACCESS  not-accessible
   STATUS      current
   DESCRIPTION
      ""
   ::= {er1645v2EthPrtSwF2VlanIpHEntry 11}

er1645v2EthPrtSwF2VlanIpHAddress OBJECT-TYPE
   SYNTAX      IpAddress
   MAX-ACCESS  read-write
   STATUS      current
   DESCRIPTION
      "Path: swPort.editConf.vlan.ip.helpers.address"
   ::= {er1645v2EthPrtSwF2VlanIpHEntry 16777216}

er1645v2EthPrtSwF2VlanIpHDhcpRelayOptionSubscriberId OBJECT-TYPE
   SYNTAX      DisplayString
   MAX-ACCESS  read-write
   STATUS      current
   DESCRIPTION
      "Path: swPort.editConf.vlan.ip.helpers.dhcpRelayOption.subscriberId"
   ::= {er1645v2EthPrtSwF2VlanIpHEntry 33947648}

er1645v2EthPrtSwF2VlanIpV6Addresses OBJECT-TYPE
   SYNTAX      SEQUENCE OF Er1645v2EthPrtSwF2VlanIpV6AddressesEntry
   MAX-ACCESS  not-accessible
   STATUS      current
   DESCRIPTION
      ""
   ::= {er1645v2EthPrtSwF2Vlan 704839680}

er1645v2EthPrtSwF2VlanIpV6AddressesEntry OBJECT-TYPE
   SYNTAX      Er1645v2EthPrtSwF2VlanIpV6AddressesEntry
   MAX-ACCESS  not-accessible
   STATUS      current
   DESCRIPTION
      ""
   INDEX      { er1645v2EthPrtSwF2VlanIpV6AddressesGlobalIx,
                er1645v2EthPrtSwF2VlanTableIx,
                er1645v2EthPrtSwF2VlanIpV6AddressesTableIx }
   ::= {er1645v2EthPrtSwF2VlanIpV6Addresses 1}

Er1645v2EthPrtSwF2VlanIpV6AddressesEntry ::=
   SEQUENCE
      {
      er1645v2EthPrtSwF2VlanIpV6AddressesActions
         VariableLengthTableActions,
      er1645v2EthPrtSwF2VlanIpV6AddressesGlobalIx
         GlobalIndex,
      er1645v2EthPrtSwF2VlanIpV6AddressesTableIx
         TableIndex,
      er1645v2EthPrtSwF2VlanIpV6AddressesType
         INTEGER,
      er1645v2EthPrtSwF2VlanIpV6AddressesAddress
         Ipv6Address,
      er1645v2EthPrtSwF2VlanIpV6AddressesPrefixLength
         Integer32,
      er1645v2EthPrtSwF2VlanIpV6AddressesGeneralPrefix
         DisplayString,
      er1645v2EthPrtSwF2VlanIpV6AddressesRaSend
         INTEGER,
      er1645v2EthPrtSwF2VlanIpV6AddressesRaOnLinkFlag
         INTEGER,
      er1645v2EthPrtSwF2VlanIpV6AddressesRaAutoFlag
         INTEGER,
      er1645v2EthPrtSwF2VlanIpV6AddressesRaValidLifeTime
         TimeTicks,
      er1645v2EthPrtSwF2VlanIpV6AddressesRaValidLTMode
         INTEGER,
      er1645v2EthPrtSwF2VlanIpV6AddressesRaPrefLifeTime
         TimeTicks,
      er1645v2EthPrtSwF2VlanIpV6AddressesRaPrefLTMode
         INTEGER
      }

er1645v2EthPrtSwF2VlanIpV6AddressesActions OBJECT-TYPE
   SYNTAX      VariableLengthTableActions
   MAX-ACCESS  read-write
   STATUS      current
   DESCRIPTION
      "By way of this field, some manipulations
       on this table may be performed."
   ::= {er1645v2EthPrtSwF2VlanIpV6AddressesEntry 2}

er1645v2EthPrtSwF2VlanIpV6AddressesGlobalIx OBJECT-TYPE
   SYNTAX      GlobalIndex
   MAX-ACCESS  not-accessible
   STATUS      current
   DESCRIPTION
      "The value of the tlsCntTreeGlobalIndex of the MANAGED OBJECT."
   ::= {er1645v2EthPrtSwF2VlanIpV6AddressesEntry 10}

er1645v2EthPrtSwF2VlanIpV6AddressesTableIx OBJECT-TYPE
   SYNTAX      TableIndex
   MAX-ACCESS  not-accessible
   STATUS      current
   DESCRIPTION
      ""
   ::= {er1645v2EthPrtSwF2VlanIpV6AddressesEntry 11}

er1645v2EthPrtSwF2VlanIpV6AddressesType OBJECT-TYPE
   SYNTAX      INTEGER
               {
               unicast (0),
               eui64 (1),
               anycast (2),
               linkLocal (3),
               generalPrefix (4)
               }
   MAX-ACCESS  read-write
   STATUS      current
   DESCRIPTION
      "Path: swPort.editConf.vlan.ipV6.addresses.type

       Possibilities:
               unicast   (0)
               eui64   (1)
               anycast   (2)
               linkLocal   (3)
               generalPrefix   (4)"
   ::= {er1645v2EthPrtSwF2VlanIpV6AddressesEntry 50331648}

er1645v2EthPrtSwF2VlanIpV6AddressesAddress OBJECT-TYPE
   SYNTAX      Ipv6Address
   MAX-ACCESS  read-write
   STATUS      current
   DESCRIPTION
      "Path: swPort.editConf.vlan.ipV6.addresses.address

       ipv6 address"
   ::= {er1645v2EthPrtSwF2VlanIpV6AddressesEntry 16777216}

er1645v2EthPrtSwF2VlanIpV6AddressesPrefixLength OBJECT-TYPE
   SYNTAX      Integer32
   MAX-ACCESS  read-write
   STATUS      current
   DESCRIPTION
      "Path: swPort.editConf.vlan.ipV6.addresses.prefixLength"
   ::= {er1645v2EthPrtSwF2VlanIpV6AddressesEntry 33554432}

er1645v2EthPrtSwF2VlanIpV6AddressesGeneralPrefix OBJECT-TYPE
   SYNTAX      DisplayString
   MAX-ACCESS  read-write
   STATUS      current
   DESCRIPTION
      "Path: swPort.editConf.vlan.ipV6.addresses.generalPrefix"
   ::= {er1645v2EthPrtSwF2VlanIpV6AddressesEntry 83886080}

er1645v2EthPrtSwF2VlanIpV6AddressesRaSend OBJECT-TYPE
   SYNTAX      INTEGER
               {
               disabled (0),
               enabled (1)
               }
   MAX-ACCESS  read-write
   STATUS      current
   DESCRIPTION
      "Path: swPort.editConf.vlan.ipV6.addresses.ra.send

       Possibilities:
               disabled   (0)
               enabled   (1)"
   ::= {er1645v2EthPrtSwF2VlanIpV6AddressesEntry 67174400}

er1645v2EthPrtSwF2VlanIpV6AddressesRaOnLinkFlag OBJECT-TYPE
   SYNTAX      INTEGER
               {
               disabled (0),
               enabled (1)
               }
   MAX-ACCESS  read-write
   STATUS      current
   DESCRIPTION
      "Path: swPort.editConf.vlan.ipV6.addresses.ra.onLinkFlag

       Possibilities:
               disabled   (0)
               enabled   (1)"
   ::= {er1645v2EthPrtSwF2VlanIpV6AddressesEntry 67371008}

er1645v2EthPrtSwF2VlanIpV6AddressesRaAutoFlag OBJECT-TYPE
   SYNTAX      INTEGER
               {
               disabled (0),
               enabled (1)
               }
   MAX-ACCESS  read-write
   STATUS      current
   DESCRIPTION
      "Path: swPort.editConf.vlan.ipV6.addresses.ra.autonomousFlag

       Possibilities:
               disabled   (0)
               enabled   (1)"
   ::= {er1645v2EthPrtSwF2VlanIpV6AddressesEntry 67567616}

er1645v2EthPrtSwF2VlanIpV6AddressesRaValidLifeTime OBJECT-TYPE
   SYNTAX      TimeTicks
   MAX-ACCESS  read-write
   STATUS      current
   DESCRIPTION
      "Path: swPort.editConf.vlan.ipV6.addresses.ra.validLifeTime

       Time in centi-second."
   ::= {er1645v2EthPrtSwF2VlanIpV6AddressesEntry 67239936}

er1645v2EthPrtSwF2VlanIpV6AddressesRaValidLTMode OBJECT-TYPE
   SYNTAX      INTEGER
               {
               fixed (0),
               infinite (2)
               }
   MAX-ACCESS  read-write
   STATUS      current
   DESCRIPTION
      "Path: swPort.editConf.vlan.ipV6.addresses.ra.validLifeTimeMode

       Possibilities:
               fixed   (0)
               infinite   (2)"
   ::= {er1645v2EthPrtSwF2VlanIpV6AddressesEntry 67305472}

er1645v2EthPrtSwF2VlanIpV6AddressesRaPrefLifeTime OBJECT-TYPE
   SYNTAX      TimeTicks
   MAX-ACCESS  read-write
   STATUS      current
   DESCRIPTION
      "Path: swPort.editConf.vlan.ipV6.addresses.ra.prefLifeTime

       Time in centi-second."
   ::= {er1645v2EthPrtSwF2VlanIpV6AddressesEntry 67436544}

er1645v2EthPrtSwF2VlanIpV6AddressesRaPrefLTMode OBJECT-TYPE
   SYNTAX      INTEGER
               {
               fixed (0),
               infinite (2)
               }
   MAX-ACCESS  read-write
   STATUS      current
   DESCRIPTION
      "Path: swPort.editConf.vlan.ipV6.addresses.ra.prefLifeTimeMode

       Possibilities:
               fixed   (0)
               infinite   (2)"
   ::= {er1645v2EthPrtSwF2VlanIpV6AddressesEntry 67502080}

er1645v2EthPrtSwF2VlanIpV6RaDnsOptionsRdnssServers OBJECT-TYPE
   SYNTAX      SEQUENCE OF Er1645v2EthPrtSwF2VlanIpV6RaDnsOptionsRdnssServersEntry
   MAX-ACCESS  not-accessible
   STATUS      current
   DESCRIPTION
      ""
   ::= {er1645v2EthPrtSwF2Vlan 705039144}

er1645v2EthPrtSwF2VlanIpV6RaDnsOptionsRdnssServersEntry OBJECT-TYPE
   SYNTAX      Er1645v2EthPrtSwF2VlanIpV6RaDnsOptionsRdnssServersEntry
   MAX-ACCESS  not-accessible
   STATUS      current
   DESCRIPTION
      ""
   INDEX      { er1645v2EthPrtSwF2VlanIpV6RaDnsOptionsRdnssServersGlobalIx,
                er1645v2EthPrtSwF2VlanTableIx,
                er1645v2EthPrtSwF2VlanIpV6RaDnsOptionsRdnssServersTableIx }
   ::= {er1645v2EthPrtSwF2VlanIpV6RaDnsOptionsRdnssServers 1}

Er1645v2EthPrtSwF2VlanIpV6RaDnsOptionsRdnssServersEntry ::=
   SEQUENCE
      {
      er1645v2EthPrtSwF2VlanIpV6RaDnsOptionsRdnssServersActions
         VariableLengthTableActions,
      er1645v2EthPrtSwF2VlanIpV6RaDnsOptionsRdnssServersGlobalIx
         GlobalIndex,
      er1645v2EthPrtSwF2VlanIpV6RaDnsOptionsRdnssServersTableIx
         TableIndex,
      er1645v2EthPrtSwF2VlanIpV6RaDnsOptionsRdnssServersAddress
         Ipv6Address
      }

er1645v2EthPrtSwF2VlanIpV6RaDnsOptionsRdnssServersActions OBJECT-TYPE
   SYNTAX      VariableLengthTableActions
   MAX-ACCESS  read-write
   STATUS      current
   DESCRIPTION
      "By way of this field, some manipulations
       on this table may be performed."
   ::= {er1645v2EthPrtSwF2VlanIpV6RaDnsOptionsRdnssServersEntry 2}

er1645v2EthPrtSwF2VlanIpV6RaDnsOptionsRdnssServersGlobalIx OBJECT-TYPE
   SYNTAX      GlobalIndex
   MAX-ACCESS  not-accessible
   STATUS      current
   DESCRIPTION
      "The value of the tlsCntTreeGlobalIndex of the MANAGED OBJECT."
   ::= {er1645v2EthPrtSwF2VlanIpV6RaDnsOptionsRdnssServersEntry 10}

er1645v2EthPrtSwF2VlanIpV6RaDnsOptionsRdnssServersTableIx OBJECT-TYPE
   SYNTAX      TableIndex
   MAX-ACCESS  not-accessible
   STATUS      current
   DESCRIPTION
      ""
   ::= {er1645v2EthPrtSwF2VlanIpV6RaDnsOptionsRdnssServersEntry 11}

er1645v2EthPrtSwF2VlanIpV6RaDnsOptionsRdnssServersAddress OBJECT-TYPE
   SYNTAX      Ipv6Address
   MAX-ACCESS  read-write
   STATUS      current
   DESCRIPTION
      "Path: swPort.editConf.vlan.ipV6.ra.dnsOptions.rdnss.servers.address

       ipv6 address"
   ::= {er1645v2EthPrtSwF2VlanIpV6RaDnsOptionsRdnssServersEntry 16777216}

er1645v2EthPrtSwF2VlanIpV6RaDnsOptionsDnsslDomains OBJECT-TYPE
   SYNTAX      SEQUENCE OF Er1645v2EthPrtSwF2VlanIpV6RaDnsOptionsDnsslDomainsEntry
   MAX-ACCESS  not-accessible
   STATUS      current
   DESCRIPTION
      ""
   ::= {er1645v2EthPrtSwF2Vlan 705039176}

er1645v2EthPrtSwF2VlanIpV6RaDnsOptionsDnsslDomainsEntry OBJECT-TYPE
   SYNTAX      Er1645v2EthPrtSwF2VlanIpV6RaDnsOptionsDnsslDomainsEntry
   MAX-ACCESS  not-accessible
   STATUS      current
   DESCRIPTION
      ""
   INDEX      { er1645v2EthPrtSwF2VlanIpV6RaDnsOptionsDnsslDomainsGlobalIx,
                er1645v2EthPrtSwF2VlanTableIx,
                er1645v2EthPrtSwF2VlanIpV6RaDnsOptionsDnsslDomainsTableIx }
   ::= {er1645v2EthPrtSwF2VlanIpV6RaDnsOptionsDnsslDomains 1}

Er1645v2EthPrtSwF2VlanIpV6RaDnsOptionsDnsslDomainsEntry ::=
   SEQUENCE
      {
      er1645v2EthPrtSwF2VlanIpV6RaDnsOptionsDnsslDomainsActions
         VariableLengthTableActions,
      er1645v2EthPrtSwF2VlanIpV6RaDnsOptionsDnsslDomainsGlobalIx
         GlobalIndex,
      er1645v2EthPrtSwF2VlanIpV6RaDnsOptionsDnsslDomainsTableIx
         TableIndex,
      er1645v2EthPrtSwF2VlanIpV6RaDnsOptionsDnsslDomainsName
         DisplayString
      }

er1645v2EthPrtSwF2VlanIpV6RaDnsOptionsDnsslDomainsActions OBJECT-TYPE
   SYNTAX      VariableLengthTableActions
   MAX-ACCESS  read-write
   STATUS      current
   DESCRIPTION
      "By way of this field, some manipulations
       on this table may be performed."
   ::= {er1645v2EthPrtSwF2VlanIpV6RaDnsOptionsDnsslDomainsEntry 2}

er1645v2EthPrtSwF2VlanIpV6RaDnsOptionsDnsslDomainsGlobalIx OBJECT-TYPE
   SYNTAX      GlobalIndex
   MAX-ACCESS  not-accessible
   STATUS      current
   DESCRIPTION
      "The value of the tlsCntTreeGlobalIndex of the MANAGED OBJECT."
   ::= {er1645v2EthPrtSwF2VlanIpV6RaDnsOptionsDnsslDomainsEntry 10}

er1645v2EthPrtSwF2VlanIpV6RaDnsOptionsDnsslDomainsTableIx OBJECT-TYPE
   SYNTAX      TableIndex
   MAX-ACCESS  not-accessible
   STATUS      current
   DESCRIPTION
      ""
   ::= {er1645v2EthPrtSwF2VlanIpV6RaDnsOptionsDnsslDomainsEntry 11}

er1645v2EthPrtSwF2VlanIpV6RaDnsOptionsDnsslDomainsName OBJECT-TYPE
   SYNTAX      DisplayString
   MAX-ACCESS  read-write
   STATUS      current
   DESCRIPTION
      "Path: swPort.editConf.vlan.ipV6.ra.dnsOptions.dnssl.domains.name"
   ::= {er1645v2EthPrtSwF2VlanIpV6RaDnsOptionsDnsslDomainsEntry 16777216}

er1645v2EthPrtSwF2VlanIpV6DhcpClientUserClassOpt OBJECT-TYPE
   SYNTAX      SEQUENCE OF Er1645v2EthPrtSwF2VlanIpV6DhcpClientUserClassOptEntry
   MAX-ACCESS  not-accessible
   STATUS      current
   DESCRIPTION
      ""
   ::= {er1645v2EthPrtSwF2Vlan 705312768}

er1645v2EthPrtSwF2VlanIpV6DhcpClientUserClassOptEntry OBJECT-TYPE
   SYNTAX      Er1645v2EthPrtSwF2VlanIpV6DhcpClientUserClassOptEntry
   MAX-ACCESS  not-accessible
   STATUS      current
   DESCRIPTION
      ""
   INDEX      { er1645v2EthPrtSwF2VlanIpV6DhcpClientUserClassOptGlobalIx,
                er1645v2EthPrtSwF2VlanTableIx,
                er1645v2EthPrtSwF2VlanIpV6DhcpClientUserClassOptTableIx }
   ::= {er1645v2EthPrtSwF2VlanIpV6DhcpClientUserClassOpt 1}

Er1645v2EthPrtSwF2VlanIpV6DhcpClientUserClassOptEntry ::=
   SEQUENCE
      {
      er1645v2EthPrtSwF2VlanIpV6DhcpClientUserClassOptActions
         VariableLengthTableActions,
      er1645v2EthPrtSwF2VlanIpV6DhcpClientUserClassOptGlobalIx
         GlobalIndex,
      er1645v2EthPrtSwF2VlanIpV6DhcpClientUserClassOptTableIx
         TableIndex,
      er1645v2EthPrtSwF2VlanIpV6DhcpClientUserClassOptValueAscii
         DisplayString,
      er1645v2EthPrtSwF2VlanIpV6DhcpClientUserClassOptValueDecimal
         Integer32,
      er1645v2EthPrtSwF2VlanIpV6DhcpClientUserClassOptValueHexData
         OCTET STRING
      }

er1645v2EthPrtSwF2VlanIpV6DhcpClientUserClassOptActions OBJECT-TYPE
   SYNTAX      VariableLengthTableActions
   MAX-ACCESS  read-write
   STATUS      current
   DESCRIPTION
      "By way of this field, some manipulations
       on this table may be performed."
   ::= {er1645v2EthPrtSwF2VlanIpV6DhcpClientUserClassOptEntry 2}

er1645v2EthPrtSwF2VlanIpV6DhcpClientUserClassOptGlobalIx OBJECT-TYPE
   SYNTAX      GlobalIndex
   MAX-ACCESS  not-accessible
   STATUS      current
   DESCRIPTION
      "The value of the tlsCntTreeGlobalIndex of the MANAGED OBJECT."
   ::= {er1645v2EthPrtSwF2VlanIpV6DhcpClientUserClassOptEntry 10}

er1645v2EthPrtSwF2VlanIpV6DhcpClientUserClassOptTableIx OBJECT-TYPE
   SYNTAX      TableIndex
   MAX-ACCESS  not-accessible
   STATUS      current
   DESCRIPTION
      ""
   ::= {er1645v2EthPrtSwF2VlanIpV6DhcpClientUserClassOptEntry 11}

er1645v2EthPrtSwF2VlanIpV6DhcpClientUserClassOptValueAscii OBJECT-TYPE
   SYNTAX      DisplayString
   MAX-ACCESS  read-write
   STATUS      current
   DESCRIPTION
      "Path: swPort.editConf.vlan.ipV6.dhcp.client.userClassOpt.value.ascii"
   ::= {er1645v2EthPrtSwF2VlanIpV6DhcpClientUserClassOptEntry 16842752}

er1645v2EthPrtSwF2VlanIpV6DhcpClientUserClassOptValueDecimal OBJECT-TYPE
   SYNTAX      Integer32
   MAX-ACCESS  read-write
   STATUS      current
   DESCRIPTION
      "Path: swPort.editConf.vlan.ipV6.dhcp.client.userClassOpt.value.decimal"
   ::= {er1645v2EthPrtSwF2VlanIpV6DhcpClientUserClassOptEntry 16908288}

er1645v2EthPrtSwF2VlanIpV6DhcpClientUserClassOptValueHexData OBJECT-TYPE
   SYNTAX      OCTET STRING
   MAX-ACCESS  read-write
   STATUS      current
   DESCRIPTION
      "Path: swPort.editConf.vlan.ipV6.dhcp.client.userClassOpt.value.hexData"
   ::= {er1645v2EthPrtSwF2VlanIpV6DhcpClientUserClassOptEntry 16973824}

er1645v2EthPrtSwF2VlanIpV6DhcpClientVendorCl OBJECT-TYPE
   SYNTAX      SEQUENCE OF Er1645v2EthPrtSwF2VlanIpV6DhcpClientVendorClEntry
   MAX-ACCESS  not-accessible
   STATUS      current
   DESCRIPTION
      ""
   ::= {er1645v2EthPrtSwF2Vlan 705313792}

er1645v2EthPrtSwF2VlanIpV6DhcpClientVendorClEntry OBJECT-TYPE
   SYNTAX      Er1645v2EthPrtSwF2VlanIpV6DhcpClientVendorClEntry
   MAX-ACCESS  not-accessible
   STATUS      current
   DESCRIPTION
      ""
   INDEX      { er1645v2EthPrtSwF2VlanIpV6DhcpClientVendorClGlobalIx,
                er1645v2EthPrtSwF2VlanTableIx,
                er1645v2EthPrtSwF2VlanIpV6DhcpClientVendorClTableIx }
   ::= {er1645v2EthPrtSwF2VlanIpV6DhcpClientVendorCl 1}

Er1645v2EthPrtSwF2VlanIpV6DhcpClientVendorClEntry ::=
   SEQUENCE
      {
      er1645v2EthPrtSwF2VlanIpV6DhcpClientVendorClActions
         VariableLengthTableActions,
      er1645v2EthPrtSwF2VlanIpV6DhcpClientVendorClGlobalIx
         GlobalIndex,
      er1645v2EthPrtSwF2VlanIpV6DhcpClientVendorClTableIx
         TableIndex,
      er1645v2EthPrtSwF2VlanIpV6DhcpClientVendorClValueAscii
         DisplayString,
      er1645v2EthPrtSwF2VlanIpV6DhcpClientVendorClValueDecimal
         Integer32,
      er1645v2EthPrtSwF2VlanIpV6DhcpClientVendorClValueHexData
         OCTET STRING
      }

er1645v2EthPrtSwF2VlanIpV6DhcpClientVendorClActions OBJECT-TYPE
   SYNTAX      VariableLengthTableActions
   MAX-ACCESS  read-write
   STATUS      current
   DESCRIPTION
      "By way of this field, some manipulations
       on this table may be performed."
   ::= {er1645v2EthPrtSwF2VlanIpV6DhcpClientVendorClEntry 2}

er1645v2EthPrtSwF2VlanIpV6DhcpClientVendorClGlobalIx OBJECT-TYPE
   SYNTAX      GlobalIndex
   MAX-ACCESS  not-accessible
   STATUS      current
   DESCRIPTION
      "The value of the tlsCntTreeGlobalIndex of the MANAGED OBJECT."
   ::= {er1645v2EthPrtSwF2VlanIpV6DhcpClientVendorClEntry 10}

er1645v2EthPrtSwF2VlanIpV6DhcpClientVendorClTableIx OBJECT-TYPE
   SYNTAX      TableIndex
   MAX-ACCESS  not-accessible
   STATUS      current
   DESCRIPTION
      ""
   ::= {er1645v2EthPrtSwF2VlanIpV6DhcpClientVendorClEntry 11}

er1645v2EthPrtSwF2VlanIpV6DhcpClientVendorClValueAscii OBJECT-TYPE
   SYNTAX      DisplayString
   MAX-ACCESS  read-write
   STATUS      current
   DESCRIPTION
      "Path: swPort.editConf.vlan.ipV6.dhcp.client.vendorClassOpt.value.ascii"
   ::= {er1645v2EthPrtSwF2VlanIpV6DhcpClientVendorClEntry 16842752}

er1645v2EthPrtSwF2VlanIpV6DhcpClientVendorClValueDecimal OBJECT-TYPE
   SYNTAX      Integer32
   MAX-ACCESS  read-write
   STATUS      current
   DESCRIPTION
      "Path: swPort.editConf.vlan.ipV6.dhcp.client.vendorClassOpt.value.decimal"
   ::= {er1645v2EthPrtSwF2VlanIpV6DhcpClientVendorClEntry 16908288}

er1645v2EthPrtSwF2VlanIpV6DhcpClientVendorClValueHexData OBJECT-TYPE
   SYNTAX      OCTET STRING
   MAX-ACCESS  read-write
   STATUS      current
   DESCRIPTION
      "Path: swPort.editConf.vlan.ipV6.dhcp.client.vendorClassOpt.value.hexData"
   ::= {er1645v2EthPrtSwF2VlanIpV6DhcpClientVendorClEntry 16973824}

er1645v2EthPrtSwF2VlanIpV6DhcpRelayDestinations OBJECT-TYPE
   SYNTAX      SEQUENCE OF Er1645v2EthPrtSwF2VlanIpV6DhcpRelayDestinationsEntry
   MAX-ACCESS  not-accessible
   STATUS      current
   DESCRIPTION
      ""
   ::= {er1645v2EthPrtSwF2Vlan 705323072}

er1645v2EthPrtSwF2VlanIpV6DhcpRelayDestinationsEntry OBJECT-TYPE
   SYNTAX      Er1645v2EthPrtSwF2VlanIpV6DhcpRelayDestinationsEntry
   MAX-ACCESS  not-accessible
   STATUS      current
   DESCRIPTION
      ""
   INDEX      { er1645v2EthPrtSwF2VlanIpV6DhcpRelayDestinationsGlobalIx,
                er1645v2EthPrtSwF2VlanTableIx,
                er1645v2EthPrtSwF2VlanIpV6DhcpRelayDestinationsTableIx }
   ::= {er1645v2EthPrtSwF2VlanIpV6DhcpRelayDestinations 1}

Er1645v2EthPrtSwF2VlanIpV6DhcpRelayDestinationsEntry ::=
   SEQUENCE
      {
      er1645v2EthPrtSwF2VlanIpV6DhcpRelayDestinationsActions
         VariableLengthTableActions,
      er1645v2EthPrtSwF2VlanIpV6DhcpRelayDestinationsGlobalIx
         GlobalIndex,
      er1645v2EthPrtSwF2VlanIpV6DhcpRelayDestinationsTableIx
         TableIndex,
      er1645v2EthPrtSwF2VlanIpV6DhcpRelayDestinationsAddress
         Ipv6Address,
      er1645v2EthPrtSwF2VlanIpV6DhcpRelayDestinationsInterface
         DisplayString
      }

er1645v2EthPrtSwF2VlanIpV6DhcpRelayDestinationsActions OBJECT-TYPE
   SYNTAX      VariableLengthTableActions
   MAX-ACCESS  read-write
   STATUS      current
   DESCRIPTION
      "By way of this field, some manipulations
       on this table may be performed."
   ::= {er1645v2EthPrtSwF2VlanIpV6DhcpRelayDestinationsEntry 2}

er1645v2EthPrtSwF2VlanIpV6DhcpRelayDestinationsGlobalIx OBJECT-TYPE
   SYNTAX      GlobalIndex
   MAX-ACCESS  not-accessible
   STATUS      current
   DESCRIPTION
      "The value of the tlsCntTreeGlobalIndex of the MANAGED OBJECT."
   ::= {er1645v2EthPrtSwF2VlanIpV6DhcpRelayDestinationsEntry 10}

er1645v2EthPrtSwF2VlanIpV6DhcpRelayDestinationsTableIx OBJECT-TYPE
   SYNTAX      TableIndex
   MAX-ACCESS  not-accessible
   STATUS      current
   DESCRIPTION
      ""
   ::= {er1645v2EthPrtSwF2VlanIpV6DhcpRelayDestinationsEntry 11}

er1645v2EthPrtSwF2VlanIpV6DhcpRelayDestinationsAddress OBJECT-TYPE
   SYNTAX      Ipv6Address
   MAX-ACCESS  read-write
   STATUS      current
   DESCRIPTION
      "Path: swPort.editConf.vlan.ipV6.dhcp.relay.destinations.address

       ipv6 address"
   ::= {er1645v2EthPrtSwF2VlanIpV6DhcpRelayDestinationsEntry 16777216}

er1645v2EthPrtSwF2VlanIpV6DhcpRelayDestinationsInterface OBJECT-TYPE
   SYNTAX      DisplayString
   MAX-ACCESS  read-write
   STATUS      current
   DESCRIPTION
      "Path: swPort.editConf.vlan.ipV6.dhcp.relay.destinations.interface"
   ::= {er1645v2EthPrtSwF2VlanIpV6DhcpRelayDestinationsEntry 33554432}

er1645v2EthPrtSwF2VlanBridgingVlTVlans OBJECT-TYPE
   SYNTAX      SEQUENCE OF Er1645v2EthPrtSwF2VlanBridgingVlTVlansEntry
   MAX-ACCESS  not-accessible
   STATUS      current
   DESCRIPTION
      ""
   ::= {er1645v2EthPrtSwF2Vlan 459079680}

er1645v2EthPrtSwF2VlanBridgingVlTVlansEntry OBJECT-TYPE
   SYNTAX      Er1645v2EthPrtSwF2VlanBridgingVlTVlansEntry
   MAX-ACCESS  not-accessible
   STATUS      current
   DESCRIPTION
      ""
   INDEX      { er1645v2EthPrtSwF2VlanBridgingVlTVlansGlobalIx,
                er1645v2EthPrtSwF2VlanTableIx,
                er1645v2EthPrtSwF2VlanBridgingVlTVlansTableIx }
   ::= {er1645v2EthPrtSwF2VlanBridgingVlTVlans 1}

Er1645v2EthPrtSwF2VlanBridgingVlTVlansEntry ::=
   SEQUENCE
      {
      er1645v2EthPrtSwF2VlanBridgingVlTVlansActions
         VariableLengthTableActions,
      er1645v2EthPrtSwF2VlanBridgingVlTVlansGlobalIx
         GlobalIndex,
      er1645v2EthPrtSwF2VlanBridgingVlTVlansTableIx
         TableIndex,
      er1645v2EthPrtSwF2VlanBridgingVlTVlansVid
         Integer32,
      er1645v2EthPrtSwF2VlanBridgingVlTVlansEndVid
         Integer32,
      er1645v2EthPrtSwF2VlanBridgingVlTVlansAction
         INTEGER,
      er1645v2EthPrtSwF2VlanBridgingVlTVlansTagInfoTpid
         INTEGER,
      er1645v2EthPrtSwF2VlanBridgingVlTVlansTagInfoVid
         Integer32
      }

er1645v2EthPrtSwF2VlanBridgingVlTVlansActions OBJECT-TYPE
   SYNTAX      VariableLengthTableActions
   MAX-ACCESS  read-write
   STATUS      current
   DESCRIPTION
      "By way of this field, some manipulations
       on this table may be performed."
   ::= {er1645v2EthPrtSwF2VlanBridgingVlTVlansEntry 2}

er1645v2EthPrtSwF2VlanBridgingVlTVlansGlobalIx OBJECT-TYPE
   SYNTAX      GlobalIndex
   MAX-ACCESS  not-accessible
   STATUS      current
   DESCRIPTION
      "The value of the tlsCntTreeGlobalIndex of the MANAGED OBJECT."
   ::= {er1645v2EthPrtSwF2VlanBridgingVlTVlansEntry 10}

er1645v2EthPrtSwF2VlanBridgingVlTVlansTableIx OBJECT-TYPE
   SYNTAX      TableIndex
   MAX-ACCESS  not-accessible
   STATUS      current
   DESCRIPTION
      ""
   ::= {er1645v2EthPrtSwF2VlanBridgingVlTVlansEntry 11}

er1645v2EthPrtSwF2VlanBridgingVlTVlansVid OBJECT-TYPE
   SYNTAX      Integer32
   MAX-ACCESS  read-write
   STATUS      current
   DESCRIPTION
      "Path: swPort.editConf.vlan.bridging.vlanTagging.vlans.vid"
   ::= {er1645v2EthPrtSwF2VlanBridgingVlTVlansEntry 536870912}

er1645v2EthPrtSwF2VlanBridgingVlTVlansEndVid OBJECT-TYPE
   SYNTAX      Integer32
   MAX-ACCESS  read-write
   STATUS      current
   DESCRIPTION
      "Path: swPort.editConf.vlan.bridging.vlanTagging.vlans.endVid"
   ::= {er1645v2EthPrtSwF2VlanBridgingVlTVlansEntry 2147483648}

er1645v2EthPrtSwF2VlanBridgingVlTVlansAction OBJECT-TYPE
   SYNTAX      INTEGER
               {
               discard (0),
               accept (1),
               tag (2)
               }
   MAX-ACCESS  read-write
   STATUS      current
   DESCRIPTION
      "Path: swPort.editConf.vlan.bridging.vlanTagging.vlans.action

       Possibilities:
               discard   (0)
               accept   (1)
               tag   (2)"
   ::= {er1645v2EthPrtSwF2VlanBridgingVlTVlansEntry 1073741824}

er1645v2EthPrtSwF2VlanBridgingVlTVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlan.bridging.vlanTagging.vlans.tagInfo.tpid

       Possibilities:
               dot1Q   (33024)
               dot1ad   (34984)
               0x9100   (37120)
               0x9200   (37376)
               0x9300   (37632)"
   ::= {er1645v2EthPrtSwF2VlanBridgingVlTVlansEntry 1677721600}

er1645v2EthPrtSwF2VlanBridgingVlTVlansTagInfoVid OBJECT-TYPE
   SYNTAX      Integer32
   MAX-ACCESS  read-write
   STATUS      current
   DESCRIPTION
      "Path: swPort.editConf.vlan.bridging.vlanTagging.vlans.tagInfo.vid"
   ::= {er1645v2EthPrtSwF2VlanBridgingVlTVlansEntry 1744830464}

er1645v2EthPrtSwF2VlanVlanVidExtensionTable OBJECT-TYPE
   SYNTAX      SEQUENCE OF Er1645v2EthPrtSwF2VlanVlanVidExtensionTableEntry
   MAX-ACCESS  not-accessible
   STATUS      current
   DESCRIPTION
      ""
   ::= {er1645v2EthPrtSwF2Vlan 235340544}

er1645v2EthPrtSwF2VlanVlanVidExtensionTableEntry OBJECT-TYPE
   SYNTAX      Er1645v2EthPrtSwF2VlanVlanVidExtensionTableEntry
   MAX-ACCESS  not-accessible
   STATUS      current
   DESCRIPTION
      ""
   INDEX      { er1645v2EthPrtSwF2VlanVlanVidExtensionTableGlobalIx,
                er1645v2EthPrtSwF2VlanTableIx,
                er1645v2EthPrtSwF2VlanVlanVidExtensionTableTableIx }
   ::= {er1645v2EthPrtSwF2VlanVlanVidExtensionTable 1}

Er1645v2EthPrtSwF2VlanVlanVidExtensionTableEntry ::=
   SEQUENCE
      {
      er1645v2EthPrtSwF2VlanVlanVidExtensionTableActions
         VariableLengthTableActions,
      er1645v2EthPrtSwF2VlanVlanVidExtensionTableGlobalIx
         GlobalIndex,
      er1645v2EthPrtSwF2VlanVlanVidExtensionTableTableIx
         TableIndex,
      er1645v2EthPrtSwF2VlanVlanVidExtensionTableTpid
         INTEGER,
      er1645v2EthPrtSwF2VlanVlanVidExtensionTableVid
         Integer32,
      er1645v2EthPrtSwF2VlanVlanVidExtensionTableEndVid
         Integer32
      }

er1645v2EthPrtSwF2VlanVlanVidExtensionTableActions OBJECT-TYPE
   SYNTAX      VariableLengthTableActions
   MAX-ACCESS  read-write
   STATUS      current
   DESCRIPTION
      "By way of this field, some manipulations
       on this table may be performed."
   ::= {er1645v2EthPrtSwF2VlanVlanVidExtensionTableEntry 2}

er1645v2EthPrtSwF2VlanVlanVidExtensionTableGlobalIx OBJECT-TYPE
   SYNTAX      GlobalIndex
   MAX-ACCESS  not-accessible
   STATUS      current
   DESCRIPTION
      "The value of the tlsCntTreeGlobalIndex of the MANAGED OBJECT."
   ::= {er1645v2EthPrtSwF2VlanVlanVidExtensionTableEntry 10}

er1645v2EthPrtSwF2VlanVlanVidExtensionTableTableIx OBJECT-TYPE
   SYNTAX      TableIndex
   MAX-ACCESS  not-accessible
   STATUS      current
   DESCRIPTION
      ""
   ::= {er1645v2EthPrtSwF2VlanVlanVidExtensionTableEntry 11}

er1645v2EthPrtSwF2VlanVlanVidExtensionTableTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlan.vlan.vidExtension.table.tpid

       Possibilities:
               dot1Q   (33024)
               dot1ad   (34984)
               0x9100   (37120)
               0x9200   (37376)
               0x9300   (37632)"
   ::= {er1645v2EthPrtSwF2VlanVlanVidExtensionTableEntry 16777216}

er1645v2EthPrtSwF2VlanVlanVidExtensionTableVid OBJECT-TYPE
   SYNTAX      Integer32
   MAX-ACCESS  read-write
   STATUS      current
   DESCRIPTION
      "Path: swPort.editConf.vlan.vlan.vidExtension.table.vid"
   ::= {er1645v2EthPrtSwF2VlanVlanVidExtensionTableEntry 33554432}

er1645v2EthPrtSwF2VlanVlanVidExtensionTableEndVid OBJECT-TYPE
   SYNTAX      Integer32
   MAX-ACCESS  read-write
   STATUS      current
   DESCRIPTION
      "Path: swPort.editConf.vlan.vlan.vidExtension.table.endVid"
   ::= {er1645v2EthPrtSwF2VlanVlanVidExtensionTableEntry 50331648}

er1645v2EthPrtSwF2VlanVlanCSMap OBJECT-TYPE
   SYNTAX      SEQUENCE OF Er1645v2EthPrtSwF2VlanVlanCSMapEntry
   MAX-ACCESS  not-accessible
   STATUS      current
   DESCRIPTION
      ""
   ::= {er1645v2EthPrtSwF2Vlan 235405312}

er1645v2EthPrtSwF2VlanVlanCSMapEntry OBJECT-TYPE
   SYNTAX      Er1645v2EthPrtSwF2VlanVlanCSMapEntry
   MAX-ACCESS  not-accessible
   STATUS      current
   DESCRIPTION
      ""
   INDEX      { er1645v2EthPrtSwF2VlanVlanCSMapGlobalIx,
                er1645v2EthPrtSwF2VlanTableIx,
                er1645v2EthPrtSwF2VlanVlanCSMapTableIx }
   ::= {er1645v2EthPrtSwF2VlanVlanCSMap 1}

Er1645v2EthPrtSwF2VlanVlanCSMapEntry ::=
   SEQUENCE
      {
      er1645v2EthPrtSwF2VlanVlanCSMapActions
         VariableLengthTableActions,
      er1645v2EthPrtSwF2VlanVlanCSMapGlobalIx
         GlobalIndex,
      er1645v2EthPrtSwF2VlanVlanCSMapTableIx
         TableIndex,
      er1645v2EthPrtSwF2VlanVlanCSMapCos
         INTEGER,
      er1645v2EthPrtSwF2VlanVlanCSMapDei
         INTEGER,
      er1645v2EthPrtSwF2VlanVlanCSMapTos
         INTEGER,
      er1645v2EthPrtSwF2VlanVlanCSMapQueue
         INTEGER,
      er1645v2EthPrtSwF2VlanVlanCSMapDropLevel
         INTEGER,
      er1645v2EthPrtSwF2VlanVlanCSMapDeFlag
         INTEGER
      }

er1645v2EthPrtSwF2VlanVlanCSMapActions OBJECT-TYPE
   SYNTAX      VariableLengthTableActions
   MAX-ACCESS  read-write
   STATUS      current
   DESCRIPTION
      "By way of this field, some manipulations
       on this table may be performed."
   ::= {er1645v2EthPrtSwF2VlanVlanCSMapEntry 2}

er1645v2EthPrtSwF2VlanVlanCSMapGlobalIx OBJECT-TYPE
   SYNTAX      GlobalIndex
   MAX-ACCESS  not-accessible
   STATUS      current
   DESCRIPTION
      "The value of the tlsCntTreeGlobalIndex of the MANAGED OBJECT."
   ::= {er1645v2EthPrtSwF2VlanVlanCSMapEntry 10}

er1645v2EthPrtSwF2VlanVlanCSMapTableIx OBJECT-TYPE
   SYNTAX      TableIndex
   MAX-ACCESS  not-accessible
   STATUS      current
   DESCRIPTION
      ""
   ::= {er1645v2EthPrtSwF2VlanVlanCSMapEntry 11}

er1645v2EthPrtSwF2VlanVlanCSMapCos OBJECT-TYPE
   SYNTAX      INTEGER
               {
               any (8)
               }
   MAX-ACCESS  read-write
   STATUS      current
   DESCRIPTION
      "Path: swPort.editConf.vlan.vlan.cosMap.cos

       Possibilities:
               any   (8)"
   ::= {er1645v2EthPrtSwF2VlanVlanCSMapEntry 16777216}

er1645v2EthPrtSwF2VlanVlanCSMapDei OBJECT-TYPE
   SYNTAX      INTEGER
               {
               clear (0),
               set (1),
               any (2)
               }
   MAX-ACCESS  read-write
   STATUS      current
   DESCRIPTION
      "Path: swPort.editConf.vlan.vlan.cosMap.dei

       Possibilities:
               clear   (0)
               set   (1)
               any   (2)"
   ::= {er1645v2EthPrtSwF2VlanVlanCSMapEntry 33554432}

er1645v2EthPrtSwF2VlanVlanCSMapTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.vlan.cosMap.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2EthPrtSwF2VlanVlanCSMapEntry 50331648}

er1645v2EthPrtSwF2VlanVlanCSMapQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.vlan.cosMap.queue

       Possibilities:
               unchanged   (-1)
               queue1   (0)
               queue2   (1)
               queue3   (2)
               queue4   (3)
               queue5   (4)
               lowDelayQueue   (5)
               lowDelay2Queue   (6)
               systemQueue   (7)"
   ::= {er1645v2EthPrtSwF2VlanVlanCSMapEntry 67108864}

er1645v2EthPrtSwF2VlanVlanCSMapDropLevel OBJECT-TYPE
   SYNTAX      INTEGER
               {
               unchanged (-1),
               dropOnQueue (0)
               }
   MAX-ACCESS  read-write
   STATUS      current
   DESCRIPTION
      "Path: swPort.editConf.vlan.vlan.cosMap.dropLevel

       Possibilities:
               unchanged   (-1)
               dropOnQueue   (0)"
   ::= {er1645v2EthPrtSwF2VlanVlanCSMapEntry 83886080}

er1645v2EthPrtSwF2VlanVlanCSMapDeFlag OBJECT-TYPE
   SYNTAX      INTEGER
               {
               unchanged (255),
               clear (0),
               set (1)
               }
   MAX-ACCESS  read-write
   STATUS      current
   DESCRIPTION
      "Path: swPort.editConf.vlan.vlan.cosMap.deFlag

       Possibilities:
               unchanged   (255)
               clear   (0)
               set   (1)"
   ::= {er1645v2EthPrtSwF2VlanVlanCSMapEntry 117440512}

er1645v2EthPrtSwF2VlanVlanTCMap OBJECT-TYPE
   SYNTAX      SEQUENCE OF Er1645v2EthPrtSwF2VlanVlanTCMapEntry
   MAX-ACCESS  not-accessible
   STATUS      current
   DESCRIPTION
      ""
   ::= {er1645v2EthPrtSwF2Vlan 241369088}

er1645v2EthPrtSwF2VlanVlanTCMapEntry OBJECT-TYPE
   SYNTAX      Er1645v2EthPrtSwF2VlanVlanTCMapEntry
   MAX-ACCESS  not-accessible
   STATUS      current
   DESCRIPTION
      ""
   INDEX      { er1645v2EthPrtSwF2VlanVlanTCMapGlobalIx,
                er1645v2EthPrtSwF2VlanTableIx,
                er1645v2EthPrtSwF2VlanVlanTCMapTableIx }
   ::= {er1645v2EthPrtSwF2VlanVlanTCMap 1}

Er1645v2EthPrtSwF2VlanVlanTCMapEntry ::=
   SEQUENCE
      {
      er1645v2EthPrtSwF2VlanVlanTCMapActions
         VariableLengthTableActions,
      er1645v2EthPrtSwF2VlanVlanTCMapGlobalIx
         GlobalIndex,
      er1645v2EthPrtSwF2VlanVlanTCMapTableIx
         TableIndex,
      er1645v2EthPrtSwF2VlanVlanTCMapStartTos
         INTEGER,
      er1645v2EthPrtSwF2VlanVlanTCMapEndTos
         INTEGER,
      er1645v2EthPrtSwF2VlanVlanTCMapCos
         INTEGER
      }

er1645v2EthPrtSwF2VlanVlanTCMapActions OBJECT-TYPE
   SYNTAX      VariableLengthTableActions
   MAX-ACCESS  read-write
   STATUS      current
   DESCRIPTION
      "By way of this field, some manipulations
       on this table may be performed."
   ::= {er1645v2EthPrtSwF2VlanVlanTCMapEntry 2}

er1645v2EthPrtSwF2VlanVlanTCMapGlobalIx OBJECT-TYPE
   SYNTAX      GlobalIndex
   MAX-ACCESS  not-accessible
   STATUS      current
   DESCRIPTION
      "The value of the tlsCntTreeGlobalIndex of the MANAGED OBJECT."
   ::= {er1645v2EthPrtSwF2VlanVlanTCMapEntry 10}

er1645v2EthPrtSwF2VlanVlanTCMapTableIx OBJECT-TYPE
   SYNTAX      TableIndex
   MAX-ACCESS  not-accessible
   STATUS      current
   DESCRIPTION
      ""
   ::= {er1645v2EthPrtSwF2VlanVlanTCMapEntry 11}

er1645v2EthPrtSwF2VlanVlanTCMapStartTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: swPort.editConf.vlan.vlan.tosCosMap.startTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1645v2EthPrtSwF2VlanVlanTCMapEntry 16777216}

er1645v2EthPrtSwF2VlanVlanTCMapEndTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: swPort.editConf.vlan.vlan.tosCosMap.endTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1645v2EthPrtSwF2VlanVlanTCMapEntry 33554432}

er1645v2EthPrtSwF2VlanVlanTCMapCos OBJECT-TYPE
   SYNTAX      INTEGER
               {
               queueCosMap (8)
               }
   MAX-ACCESS  read-write
   STATUS      current
   DESCRIPTION
      "Path: swPort.editConf.vlan.vlan.tosCosMap.cos

       Possibilities:
               queueCosMap   (8)"
   ::= {er1645v2EthPrtSwF2VlanVlanTCMapEntry 50331648}

er1645v2EthPrtSwF2VlanVlanArpStaticArp OBJECT-TYPE
   SYNTAX      SEQUENCE OF Er1645v2EthPrtSwF2VlanVlanArpStaticArpEntry
   MAX-ACCESS  not-accessible
   STATUS      current
   DESCRIPTION
      ""
   ::= {er1645v2EthPrtSwF2Vlan 235275008}

er1645v2EthPrtSwF2VlanVlanArpStaticArpEntry OBJECT-TYPE
   SYNTAX      Er1645v2EthPrtSwF2VlanVlanArpStaticArpEntry
   MAX-ACCESS  not-accessible
   STATUS      current
   DESCRIPTION
      ""
   INDEX      { er1645v2EthPrtSwF2VlanVlanArpStaticArpGlobalIx,
                er1645v2EthPrtSwF2VlanTableIx,
                er1645v2EthPrtSwF2VlanVlanArpStaticArpTableIx }
   ::= {er1645v2EthPrtSwF2VlanVlanArpStaticArp 1}

Er1645v2EthPrtSwF2VlanVlanArpStaticArpEntry ::=
   SEQUENCE
      {
      er1645v2EthPrtSwF2VlanVlanArpStaticArpActions
         VariableLengthTableActions,
      er1645v2EthPrtSwF2VlanVlanArpStaticArpGlobalIx
         GlobalIndex,
      er1645v2EthPrtSwF2VlanVlanArpStaticArpTableIx
         TableIndex,
      er1645v2EthPrtSwF2VlanVlanArpStaticArpMacAddress
         OCTET STRING,
      er1645v2EthPrtSwF2VlanVlanArpStaticArpIpAddress
         IpAddress
      }

er1645v2EthPrtSwF2VlanVlanArpStaticArpActions OBJECT-TYPE
   SYNTAX      VariableLengthTableActions
   MAX-ACCESS  read-write
   STATUS      current
   DESCRIPTION
      "By way of this field, some manipulations
       on this table may be performed."
   ::= {er1645v2EthPrtSwF2VlanVlanArpStaticArpEntry 2}

er1645v2EthPrtSwF2VlanVlanArpStaticArpGlobalIx OBJECT-TYPE
   SYNTAX      GlobalIndex
   MAX-ACCESS  not-accessible
   STATUS      current
   DESCRIPTION
      "The value of the tlsCntTreeGlobalIndex of the MANAGED OBJECT."
   ::= {er1645v2EthPrtSwF2VlanVlanArpStaticArpEntry 10}

er1645v2EthPrtSwF2VlanVlanArpStaticArpTableIx OBJECT-TYPE
   SYNTAX      TableIndex
   MAX-ACCESS  not-accessible
   STATUS      current
   DESCRIPTION
      ""
   ::= {er1645v2EthPrtSwF2VlanVlanArpStaticArpEntry 11}

er1645v2EthPrtSwF2VlanVlanArpStaticArpMacAddress OBJECT-TYPE
   SYNTAX      OCTET STRING
   MAX-ACCESS  read-write
   STATUS      current
   DESCRIPTION
      "Path: swPort.editConf.vlan.vlan.arp.staticArp.macAddress

       MAC address."
   ::= {er1645v2EthPrtSwF2VlanVlanArpStaticArpEntry 16777216}

er1645v2EthPrtSwF2VlanVlanArpStaticArpIpAddress OBJECT-TYPE
   SYNTAX      IpAddress
   MAX-ACCESS  read-write
   STATUS      current
   DESCRIPTION
      "Path: swPort.editConf.vlan.vlan.arp.staticArp.ipAddress"
   ::= {er1645v2EthPrtSwF2VlanVlanArpStaticArpEntry 33554432}


er1645v2EthPrtSwF2PppOE OBJECT IDENTIFIER ::= {er1645v2EthPrtSwF2 35}

er1645v2EthPrtSwF2PppOESSCTable OBJECT-TYPE
   SYNTAX      SEQUENCE OF Er1645v2EthPrtSwF2PppOEEntry
   MAX-ACCESS  not-accessible
   STATUS      current
   DESCRIPTION
      ""
   ::= {er1645v2EthPrtSwF2PppOE 1}

er1645v2EthPrtSwF2PppOEEntry OBJECT-TYPE
   SYNTAX      Er1645v2EthPrtSwF2PppOEEntry
   MAX-ACCESS  not-accessible
   STATUS      current
   DESCRIPTION
      ""
   INDEX      { er1645v2EthPrtSwF2PppOEGlobalIx,
                er1645v2EthPrtSwF2PppOETableIx }
   ::= {er1645v2EthPrtSwF2PppOESSCTable 1}

Er1645v2EthPrtSwF2PppOEEntry ::=
   SEQUENCE
      {
      er1645v2EthPrtSwF2PppOEActions
         VariableLengthTableActions,
      er1645v2EthPrtSwF2PppOEGlobalIx
         GlobalIndex,
      er1645v2EthPrtSwF2PppOETableIx
         TableIndex,
      er1645v2EthPrtSwF2PppOEName
         DisplayString,
      er1645v2EthPrtSwF2PppOERemark
         DisplayString,
      er1645v2EthPrtSwF2PppOEAdminStatus
         INTEGER,
      er1645v2EthPrtSwF2PppOEMode
         INTEGER,
      er1645v2EthPrtSwF2PppOEIpVrfRouter
         DisplayString,
      er1645v2EthPrtSwF2PppOEIpAdr
         IpAddress,
      er1645v2EthPrtSwF2PppOEIpNetm
         IpAddress,
      er1645v2EthPrtSwF2PppOEIpSNetName
         INTEGER,
      er1645v2EthPrtSwF2PppOEIpSNetCust
         DisplayString,
      er1645v2EthPrtSwF2PppOEIpRem
         IpAddress,
      er1645v2EthPrtSwF2PppOEIpUnnumbered
         DisplayString,
      er1645v2EthPrtSwF2PppOEIpGwPref
         Integer32,
      er1645v2EthPrtSwF2PppOEIpRsn
         INTEGER,
      er1645v2EthPrtSwF2PppOEIpMtu
         Integer32,
      er1645v2EthPrtSwF2PppOEIpMssAdjust
         INTEGER,
      er1645v2EthPrtSwF2PppOEIpRipMetric
         Integer32,
      er1645v2EthPrtSwF2PppOEIpRipMetricOut
         Integer32,
      er1645v2EthPrtSwF2PppOEIpRipMode
         INTEGER,
      er1645v2EthPrtSwF2PppOEIpRipTxVer
         INTEGER,
      er1645v2EthPrtSwF2PppOEIpRipRxVer
         INTEGER,
      er1645v2EthPrtSwF2PppOEIpRipSplitH
         INTEGER,
      er1645v2EthPrtSwF2PppOEIpRipAuth
         INTEGER,
      er1645v2EthPrtSwF2PppOEIpRipFilter
         DisplayString,
      er1645v2EthPrtSwF2PppOEIpRipFilterIn
         DisplayString,
      er1645v2EthPrtSwF2PppOEIpRipClearNextHop
         INTEGER,
      er1645v2EthPrtSwF2PppOEIpAccPol
         DisplayString,
      er1645v2EthPrtSwF2PppOEIpAB
         DisplayString,
      er1645v2EthPrtSwF2PppOEIpMA
         INTEGER,
      er1645v2EthPrtSwF2PppOEIpMF
         Integer32,
      er1645v2EthPrtSwF2PppOEIpDB
         INTEGER,
      er1645v2EthPrtSwF2PppOEIpIR
         INTEGER,
      er1645v2EthPrtSwF2PppOEIpIgmp
         INTEGER,
      er1645v2EthPrtSwF2PppOEIpNN
         DisplayString,
      er1645v2EthPrtSwF2PppOEIpPimMode
         INTEGER,
      er1645v2EthPrtSwF2PppOEIpPimDrPriority
         Counter32,
      er1645v2EthPrtSwF2PppOEIpPimHelloTime
         TimeTicks,
      er1645v2EthPrtSwF2PppOEIpPimPropagationDelay
         TimeTicks,
      er1645v2EthPrtSwF2PppOEIpPimOverrideInterval
         TimeTicks,
      er1645v2EthPrtSwF2PppOEIpPimBsrBorder
         INTEGER,
      er1645v2EthPrtSwF2PppOEIpPimTtlThreshold
         Integer32,
      er1645v2EthPrtSwF2PppOEIpIMNetworkUnreachable
         INTEGER,
      er1645v2EthPrtSwF2PppOEIpIMHostUnreachable
         INTEGER,
      er1645v2EthPrtSwF2PppOEIpIMProtocolUnreachable
         INTEGER,
      er1645v2EthPrtSwF2PppOEIpIMPortUnreachable
         INTEGER,
      er1645v2EthPrtSwF2PppOEIpIMMtuExceeded
         INTEGER,
      er1645v2EthPrtSwF2PppOEIpIMAdminProhibited
         INTEGER,
      er1645v2EthPrtSwF2PppOEIpIMTtlExceeded
         INTEGER,
      er1645v2EthPrtSwF2PppOEIpIMRedirect
         INTEGER,
      er1645v2EthPrtSwF2PppOEIpV6VrfRouter
         DisplayString,
      er1645v2EthPrtSwF2PppOEIpV6AddrAutoConfigNrDupAddrDetects
         Integer32,
      er1645v2EthPrtSwF2PppOEIpV6AddrAutoConfigAcceptRa
         INTEGER,
      er1645v2EthPrtSwF2PppOEIpV6AddrAutoConfigAcceptRaRdnss
         INTEGER,
      er1645v2EthPrtSwF2PppOEIpV6AddrAutoConfigAcceptRaDnssl
         INTEGER,
      er1645v2EthPrtSwF2PppOEIpV6DefaultRoute
         INTEGER,
      er1645v2EthPrtSwF2PppOEIpV6RaSend
         INTEGER,
      er1645v2EthPrtSwF2PppOEIpV6RaMinInterval
         TimeTicks,
      er1645v2EthPrtSwF2PppOEIpV6RaMaxInterval
         TimeTicks,
      er1645v2EthPrtSwF2PppOEIpV6RaManagedFlag
         INTEGER,
      er1645v2EthPrtSwF2PppOEIpV6RaOtherConfFlag
         INTEGER,
      er1645v2EthPrtSwF2PppOEIpV6RaLinkMtu
         Integer32,
      er1645v2EthPrtSwF2PppOEIpV6RaReachableTime
         TimeTicks,
      er1645v2EthPrtSwF2PppOEIpV6RaRetransmitTime
         TimeTicks,
      er1645v2EthPrtSwF2PppOEIpV6RaHopLimit
         Integer32,
      er1645v2EthPrtSwF2PppOEIpV6RaDefaultLifeTime
         TimeTicks,
      er1645v2EthPrtSwF2PppOEIpV6RaDnsOptionsRdnssLifeTime
         TimeTicks,
      er1645v2EthPrtSwF2PppOEIpV6RaDnsOptionsRdnssImportServers
         INTEGER,
      er1645v2EthPrtSwF2PppOEIpV6RaDnsOptionsDnsslLifeTime
         TimeTicks,
      er1645v2EthPrtSwF2PppOEIpV6RaDnsOptionsDnsslImportDomains
         INTEGER,
      er1645v2EthPrtSwF2PppOEIpV6RsSend
         INTEGER,
      er1645v2EthPrtSwF2PppOEIpV6RsMaxRandomDelay
         TimeTicks,
      er1645v2EthPrtSwF2PppOEIpV6RsInterval
         TimeTicks,
      er1645v2EthPrtSwF2PppOEIpV6RsMaxSolicitations
         Integer32,
      er1645v2EthPrtSwF2PppOEIpV6TrafficPolicyInbound
         DisplayString,
      er1645v2EthPrtSwF2PppOEIpV6TrafficPolicyOutbound
         DisplayString,
      er1645v2EthPrtSwF2PppOEIpV6FirewallZone
         DisplayString,
      er1645v2EthPrtSwF2PppOEIpV6DhcpClientAddrAC
         INTEGER,
      er1645v2EthPrtSwF2PppOEIpV6DhcpClientPrDelMode
         INTEGER,
      er1645v2EthPrtSwF2PppOEIpV6DhcpClientPrDelPool
         DisplayString,
      er1645v2EthPrtSwF2PppOEIpV6DhcpClientPrDelPdExclOpt
         INTEGER,
      er1645v2EthPrtSwF2PppOEIpV6DhcpClientDnsServerPref
         Integer32,
      er1645v2EthPrtSwF2PppOEIpV6DhcpClientRapidCommit
         INTEGER,
      er1645v2EthPrtSwF2PppOEIpV6DhcpClientTimersSolTimeOut
         TimeTicks,
      er1645v2EthPrtSwF2PppOEIpV6DhcpClientTimersSolMaxRt
         TimeTicks,
      er1645v2EthPrtSwF2PppOEIpV6DhcpClientTimersInfoRefresh
         TimeTicks,
      er1645v2EthPrtSwF2PppOEIpV6DhcpServerMode
         INTEGER,
      er1645v2EthPrtSwF2PppOEIpV6DhcpServerPreference
         Integer32,
      er1645v2EthPrtSwF2PppOEIpV6DhcpServerPool
         DisplayString,
      er1645v2EthPrtSwF2PppOEIpV6DhcpServerRapidCommit
         INTEGER,
      er1645v2EthPrtSwF2PppOEIpV6DhcpServerTimersInfoRefresh
         TimeTicks,
      er1645v2EthPrtSwF2PppOEIpV6DhcpRelayMode
         INTEGER,
      er1645v2EthPrtSwF2PppOEIpV6SendRedirect
         INTEGER,
      er1645v2EthPrtSwF2PppOEIpV6LinkMtu
         Integer32,
      er1645v2EthPrtSwF2PppOEIpV6InterfaceId
         OCTET STRING,
      er1645v2EthPrtSwF2PppOEIpV6MF
         Integer32,
      er1645v2EthPrtSwF2PppOEIpV6IcmpMessagesNoRoute
         INTEGER,
      er1645v2EthPrtSwF2PppOEIpV6IcmpMessagesBeyondScope
         INTEGER,
      er1645v2EthPrtSwF2PppOEIpV6IcmpMessagesAddressUnreachable
         INTEGER,
      er1645v2EthPrtSwF2PppOEIpV6IcmpMessagesPortUnreachable
         INTEGER,
      er1645v2EthPrtSwF2PppOEIpV6IcmpMessagesPacketTooBig
         INTEGER,
      er1645v2EthPrtSwF2PppOEIpV6IcmpMessagesHopLimitExceeded
         INTEGER,
      er1645v2EthPrtSwF2PppOEIpV6IcmpMessagesFragTimeExceeded
         INTEGER,
      er1645v2EthPrtSwF2PppOEIpV6IcmpMessagesHeaderFieldErr
         INTEGER,
      er1645v2EthPrtSwF2PppOEIpV6IcmpMessagesOptionUnrecognized
         INTEGER,
      er1645v2EthPrtSwF2PppOEIpV6IcmpMessagesRedirect
         INTEGER,
      er1645v2EthPrtSwF2PppOEPppLnkMOperation
         INTEGER,
      er1645v2EthPrtSwF2PppOEPppLnkMInterval
         TimeTicks,
      er1645v2EthPrtSwF2PppOEPppLnkMRepTimeOut
         TimeTicks,
      er1645v2EthPrtSwF2PppOEPppLnkMFailsPrmt
         Integer32,
      er1645v2EthPrtSwF2PppOEPppAuthentication
         INTEGER,
      er1645v2EthPrtSwF2PppOEPppAuthenPeriod
         TimeTicks,
      er1645v2EthPrtSwF2PppOEPppSessionName
         DisplayString,
      er1645v2EthPrtSwF2PppOEPppSessionSecret
         DisplayString,
      er1645v2EthPrtSwF2PppOEPppEncModeSessionSecret
         INTEGER,
      er1645v2EthPrtSwF2PppOEPppEncSessionSecret
         DisplayString,
      er1645v2EthPrtSwF2PppOEPppServiceName
         DisplayString
      }

er1645v2EthPrtSwF2PppOEActions OBJECT-TYPE
   SYNTAX      VariableLengthTableActions
   MAX-ACCESS  read-write
   STATUS      current
   DESCRIPTION
      "By way of this field, some manipulations
       on this table may be performed."
   ::= {er1645v2EthPrtSwF2PppOEEntry 2}

er1645v2EthPrtSwF2PppOEGlobalIx OBJECT-TYPE
   SYNTAX      GlobalIndex
   MAX-ACCESS  not-accessible
   STATUS      current
   DESCRIPTION
      "The value of the tlsCntTreeGlobalIndex of the MANAGED OBJECT."
   ::= {er1645v2EthPrtSwF2PppOEEntry 10}

er1645v2EthPrtSwF2PppOETableIx OBJECT-TYPE
   SYNTAX      TableIndex
   MAX-ACCESS  not-accessible
   STATUS      current
   DESCRIPTION
      ""
   ::= {er1645v2EthPrtSwF2PppOEEntry 11}

er1645v2EthPrtSwF2PppOEName OBJECT-TYPE
   SYNTAX      DisplayString
   MAX-ACCESS  read-write
   STATUS      current
   DESCRIPTION
      "Path: swPort.editConf.pppoEClient.name"
   ::= {er1645v2EthPrtSwF2PppOEEntry 16777216}

er1645v2EthPrtSwF2PppOERemark OBJECT-TYPE
   SYNTAX      DisplayString
   MAX-ACCESS  read-write
   STATUS      current
   DESCRIPTION
      "Path: swPort.editConf.pppoEClient.remark"
   ::= {er1645v2EthPrtSwF2PppOEEntry 1157627904}

er1645v2EthPrtSwF2PppOEAdminStatus OBJECT-TYPE
   SYNTAX      INTEGER
               {
               up (1),
               down (2)
               }
   MAX-ACCESS  read-write
   STATUS      current
   DESCRIPTION
      "Path: swPort.editConf.pppoEClient.adminStatus

       Possibilities:
               up   (1)
               down   (2)"
   ::= {er1645v2EthPrtSwF2PppOEEntry 33554432}

er1645v2EthPrtSwF2PppOEMode OBJECT-TYPE
   SYNTAX      INTEGER
               {
               routing (1),
               multilink (8),
               ipV6 (16),
               ipV6ipV4 (17)
               }
   MAX-ACCESS  read-write
   STATUS      current
   DESCRIPTION
      "Path: swPort.editConf.pppoEClient.mode

       Possibilities:
               routing   (1)
               multilink   (8)
               ipV6   (16)
               ipV6/ipV4   (17)"
   ::= {er1645v2EthPrtSwF2PppOEEntry 67108864}

er1645v2EthPrtSwF2PppOEIpVrfRouter OBJECT-TYPE
   SYNTAX      DisplayString
   MAX-ACCESS  read-write
   STATUS      current
   DESCRIPTION
      "Path: swPort.editConf.pppoEClient.ip.vrfRouter"
   ::= {er1645v2EthPrtSwF2PppOEEntry 53215232}

er1645v2EthPrtSwF2PppOEIpAdr OBJECT-TYPE
   SYNTAX      IpAddress
   MAX-ACCESS  read-write
   STATUS      current
   DESCRIPTION
      "Path: swPort.editConf.pppoEClient.ip.address"
   ::= {er1645v2EthPrtSwF2PppOEEntry 58261504}

er1645v2EthPrtSwF2PppOEIpNetm OBJECT-TYPE
   SYNTAX      IpAddress
   MAX-ACCESS  read-write
   STATUS      current
   DESCRIPTION
      "Path: swPort.editConf.pppoEClient.ip.netMask"
   ::= {er1645v2EthPrtSwF2PppOEEntry 58392576}

er1645v2EthPrtSwF2PppOEIpSNetName OBJECT-TYPE
   SYNTAX      INTEGER
               {
               slOPTg (0),
               corp (2),
               dmz (3),
               internet (1)
               }
   MAX-ACCESS  read-write
   STATUS      current
   DESCRIPTION
      "Path: swPort.editConf.pppoEClient.ip.sNet.name

       Possibilities:
               <OPT>   (0)
               corp   (2)
               dmz   (3)
               internet   (1)"
   ::= {er1645v2EthPrtSwF2PppOEEntry 53674240}

er1645v2EthPrtSwF2PppOEIpSNetCust OBJECT-TYPE
   SYNTAX      DisplayString
   MAX-ACCESS  read-write
   STATUS      current
   DESCRIPTION
      "Path: swPort.editConf.pppoEClient.ip.sNet.custom"
   ::= {er1645v2EthPrtSwF2PppOEEntry 53674496}

er1645v2EthPrtSwF2PppOEIpRem OBJECT-TYPE
   SYNTAX      IpAddress
   MAX-ACCESS  read-write
   STATUS      current
   DESCRIPTION
      "Path: swPort.editConf.pppoEClient.ip.remote"
   ::= {er1645v2EthPrtSwF2PppOEEntry 58458112}

er1645v2EthPrtSwF2PppOEIpUnnumbered OBJECT-TYPE
   SYNTAX      DisplayString
   MAX-ACCESS  read-write
   STATUS      current
   DESCRIPTION
      "Path: swPort.editConf.pppoEClient.ip.unnumbered"
   ::= {er1645v2EthPrtSwF2PppOEEntry 52625408}

er1645v2EthPrtSwF2PppOEIpGwPref OBJECT-TYPE
   SYNTAX      Integer32
   MAX-ACCESS  read-write
   STATUS      current
   DESCRIPTION
      "Path: swPort.editConf.pppoEClient.ip.gatewayPreference"
   ::= {er1645v2EthPrtSwF2PppOEEntry 52690944}

er1645v2EthPrtSwF2PppOEIpRsn OBJECT-TYPE
   SYNTAX      INTEGER
               {
               disabled (0),
               enabled (1)
               }
   MAX-ACCESS  read-write
   STATUS      current
   DESCRIPTION
      "Path: swPort.editConf.pppoEClient.ip.requestSubnet

       Possibilities:
               disabled   (0)
               enabled   (1)"
   ::= {er1645v2EthPrtSwF2PppOEEntry 56688640}

er1645v2EthPrtSwF2PppOEIpMtu OBJECT-TYPE
   SYNTAX      Integer32
   MAX-ACCESS  read-write
   STATUS      current
   DESCRIPTION
      "Path: swPort.editConf.pppoEClient.ip.mtu"
   ::= {er1645v2EthPrtSwF2PppOEEntry 52953088}

er1645v2EthPrtSwF2PppOEIpMssAdjust OBJECT-TYPE
   SYNTAX      INTEGER
               {
               disabled (0),
               auto (65536)
               }
   MAX-ACCESS  read-write
   STATUS      current
   DESCRIPTION
      "Path: swPort.editConf.pppoEClient.ip.mssAdjust

       Possibilities:
               disabled   (0)
               auto   (65536)"
   ::= {er1645v2EthPrtSwF2PppOEEntry 53280768}

er1645v2EthPrtSwF2PppOEIpRipMetric OBJECT-TYPE
   SYNTAX      Integer32
   MAX-ACCESS  read-write
   STATUS      current
   DESCRIPTION
      "Path: swPort.editConf.pppoEClient.ip.rip.metric"
   ::= {er1645v2EthPrtSwF2PppOEEntry 51712768}

er1645v2EthPrtSwF2PppOEIpRipMetricOut OBJECT-TYPE
   SYNTAX      Integer32
   MAX-ACCESS  read-write
   STATUS      current
   DESCRIPTION
      "Path: swPort.editConf.pppoEClient.ip.rip.metricOut"
   ::= {er1645v2EthPrtSwF2PppOEEntry 51713024}

er1645v2EthPrtSwF2PppOEIpRipMode OBJECT-TYPE
   SYNTAX      INTEGER
               {
               disabled (0),
               passive (1),
               active (2)
               }
   MAX-ACCESS  read-write
   STATUS      current
   DESCRIPTION
      "Path: swPort.editConf.pppoEClient.ip.rip.mode

       Possibilities:
               disabled   (0)
               passive   (1)
               active   (2)"
   ::= {er1645v2EthPrtSwF2PppOEEntry 51713280}

er1645v2EthPrtSwF2PppOEIpRipTxVer OBJECT-TYPE
   SYNTAX      INTEGER
               {
               rip1 (0),
               rip2 (1),
               rip1mcompatible (2)
               }
   MAX-ACCESS  read-write
   STATUS      current
   DESCRIPTION
      "Path: swPort.editConf.pppoEClient.ip.rip.txVersion

       Possibilities:
               rip1   (0)
               rip2   (1)
               rip1-compatible   (2)"
   ::= {er1645v2EthPrtSwF2PppOEEntry 51716864}

er1645v2EthPrtSwF2PppOEIpRipRxVer OBJECT-TYPE
   SYNTAX      INTEGER
               {
               rip1only (0),
               rip2only (1),
               rip12 (2)
               }
   MAX-ACCESS  read-write
   STATUS      current
   DESCRIPTION
      "Path: swPort.editConf.pppoEClient.ip.rip.rxVersion

       Possibilities:
               rip1only   (0)
               rip2only   (1)
               rip1&2   (2)"
   ::= {er1645v2EthPrtSwF2PppOEEntry 51717120}

er1645v2EthPrtSwF2PppOEIpRipSplitH OBJECT-TYPE
   SYNTAX      INTEGER
               {
               disabled (0),
               enabled (1),
               poisonedReverse (2)
               }
   MAX-ACCESS  read-write
   STATUS      current
   DESCRIPTION
      "Path: swPort.editConf.pppoEClient.ip.rip.splitHorizon

       Possibilities:
               disabled   (0)
               enabled   (1)
               poisonedReverse   (2)"
   ::= {er1645v2EthPrtSwF2PppOEEntry 51713792}

er1645v2EthPrtSwF2PppOEIpRipAuth OBJECT-TYPE
   SYNTAX      INTEGER
               {
               disabled (0),
               texts (1),
               md5 (2)
               }
   MAX-ACCESS  read-write
   STATUS      current
   DESCRIPTION
      "Path: swPort.editConf.pppoEClient.ip.rip.authentication

       Possibilities:
               disabled   (0)
               text    (1)
               md5   (2)"
   ::= {er1645v2EthPrtSwF2PppOEEntry 51712512}

er1645v2EthPrtSwF2PppOEIpRipFilter OBJECT-TYPE
   SYNTAX      DisplayString
   MAX-ACCESS  read-write
   STATUS      current
   DESCRIPTION
      "Path: swPort.editConf.pppoEClient.ip.rip.filter"
   ::= {er1645v2EthPrtSwF2PppOEEntry 51716096}

er1645v2EthPrtSwF2PppOEIpRipFilterIn OBJECT-TYPE
   SYNTAX      DisplayString
   MAX-ACCESS  read-write
   STATUS      current
   DESCRIPTION
      "Path: swPort.editConf.pppoEClient.ip.rip.filterIn"
   ::= {er1645v2EthPrtSwF2PppOEEntry 51716352}

er1645v2EthPrtSwF2PppOEIpRipClearNextHop OBJECT-TYPE
   SYNTAX      INTEGER
               {
               disabled (0),
               enabled (1)
               }
   MAX-ACCESS  read-write
   STATUS      current
   DESCRIPTION
      "Path: swPort.editConf.pppoEClient.ip.rip.clearNextHop

       Possibilities:
               disabled   (0)
               enabled   (1)"
   ::= {er1645v2EthPrtSwF2PppOEEntry 51708416}

er1645v2EthPrtSwF2PppOEIpAccPol OBJECT-TYPE
   SYNTAX      DisplayString
   MAX-ACCESS  read-write
   STATUS      current
   DESCRIPTION
      "Path: swPort.editConf.pppoEClient.ip.accessPolicy"
   ::= {er1645v2EthPrtSwF2PppOEEntry 53084160}

er1645v2EthPrtSwF2PppOEIpAB OBJECT-TYPE
   SYNTAX      DisplayString
   MAX-ACCESS  read-write
   STATUS      current
   DESCRIPTION
      "Path: swPort.editConf.pppoEClient.ip.trafficPolicy"
   ::= {er1645v2EthPrtSwF2PppOEEntry 51249152}

er1645v2EthPrtSwF2PppOEIpMA OBJECT-TYPE
   SYNTAX      INTEGER
               {
               disabled (0),
               enabled (1)
               }
   MAX-ACCESS  read-write
   STATUS      current
   DESCRIPTION
      "Path: swPort.editConf.pppoEClient.ip.mgmtAccess

       Possibilities:
               disabled   (0)
               enabled   (1)"
   ::= {er1645v2EthPrtSwF2PppOEEntry 51380224}

er1645v2EthPrtSwF2PppOEIpMF OBJECT-TYPE
   SYNTAX      Integer32
   MAX-ACCESS  read-write
   STATUS      current
   DESCRIPTION
      "Path: swPort.editConf.pppoEClient.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2EthPrtSwF2PppOEEntry 51445760}

er1645v2EthPrtSwF2PppOEIpDB OBJECT-TYPE
   SYNTAX      INTEGER
               {
               disabled (0),
               enabled (1)
               }
   MAX-ACCESS  read-write
   STATUS      current
   DESCRIPTION
      "Path: swPort.editConf.pppoEClient.ip.directedBroadcasts

       Possibilities:
               disabled   (0)
               enabled   (1)"
   ::= {er1645v2EthPrtSwF2PppOEEntry 51773440}

er1645v2EthPrtSwF2PppOEIpIR OBJECT-TYPE
   SYNTAX      INTEGER
               {
               disabled (0),
               enabled (1)
               }
   MAX-ACCESS  read-write
   STATUS      current
   DESCRIPTION
      "Path: swPort.editConf.pppoEClient.ip.icmpRedirects

       Possibilities:
               disabled   (0)
               enabled   (1)"
   ::= {er1645v2EthPrtSwF2PppOEEntry 52035584}

er1645v2EthPrtSwF2PppOEIpIgmp OBJECT-TYPE
   SYNTAX      INTEGER
               {
               disabled (0),
               proxy (1),
               router (2),
               v3Router (5)
               }
   MAX-ACCESS  read-write
   STATUS      current
   DESCRIPTION
      "Path: swPort.editConf.pppoEClient.ip.igmp

       Possibilities:
               disabled   (0)
               proxy   (1)
               router   (2)
               v3Router   (5)"
   ::= {er1645v2EthPrtSwF2PppOEEntry 52428800}

er1645v2EthPrtSwF2PppOEIpNN OBJECT-TYPE
   SYNTAX      DisplayString
   MAX-ACCESS  read-write
   STATUS      current
   DESCRIPTION
      "Path: swPort.editConf.pppoEClient.ip.nat"
   ::= {er1645v2EthPrtSwF2PppOEEntry 52101120}

er1645v2EthPrtSwF2PppOEIpPimMode OBJECT-TYPE
   SYNTAX      INTEGER
               {
               disabled (0),
               sparse (1),
               passive (2)
               }
   MAX-ACCESS  read-write
   STATUS      current
   DESCRIPTION
      "Path: swPort.editConf.pppoEClient.ip.pim.mode

       Possibilities:
               disabled   (0)
               sparse   (1)
               passive   (2)"
   ::= {er1645v2EthPrtSwF2PppOEEntry 53346560}

er1645v2EthPrtSwF2PppOEIpPimDrPriority OBJECT-TYPE
   SYNTAX      Counter32
   MAX-ACCESS  read-write
   STATUS      current
   DESCRIPTION
      "Path: swPort.editConf.pppoEClient.ip.pim.drPriority

       32 bit unsigned wrappable counter."
   ::= {er1645v2EthPrtSwF2PppOEEntry 53346816}

er1645v2EthPrtSwF2PppOEIpPimHelloTime OBJECT-TYPE
   SYNTAX      TimeTicks
   MAX-ACCESS  read-write
   STATUS      current
   DESCRIPTION
      "Path: swPort.editConf.pppoEClient.ip.pim.helloTime

       Time in centi-second."
   ::= {er1645v2EthPrtSwF2PppOEEntry 53347072}

er1645v2EthPrtSwF2PppOEIpPimPropagationDelay OBJECT-TYPE
   SYNTAX      TimeTicks
   MAX-ACCESS  read-write
   STATUS      current
   DESCRIPTION
      "Path: swPort.editConf.pppoEClient.ip.pim.propagationDelay

       Time in centi-second."
   ::= {er1645v2EthPrtSwF2PppOEEntry 53347328}

er1645v2EthPrtSwF2PppOEIpPimOverrideInterval OBJECT-TYPE
   SYNTAX      TimeTicks
   MAX-ACCESS  read-write
   STATUS      current
   DESCRIPTION
      "Path: swPort.editConf.pppoEClient.ip.pim.overrideInterval

       Time in centi-second."
   ::= {er1645v2EthPrtSwF2PppOEEntry 53347584}

er1645v2EthPrtSwF2PppOEIpPimBsrBorder OBJECT-TYPE
   SYNTAX      INTEGER
               {
               disabled (0),
               enabled (1)
               }
   MAX-ACCESS  read-write
   STATUS      current
   DESCRIPTION
      "Path: swPort.editConf.pppoEClient.ip.pim.bsrBorder

       Possibilities:
               disabled   (0)
               enabled   (1)"
   ::= {er1645v2EthPrtSwF2PppOEEntry 53347840}

er1645v2EthPrtSwF2PppOEIpPimTtlThreshold OBJECT-TYPE
   SYNTAX      Integer32
   MAX-ACCESS  read-write
   STATUS      current
   DESCRIPTION
      "Path: swPort.editConf.pppoEClient.ip.pim.ttlThreshold"
   ::= {er1645v2EthPrtSwF2PppOEEntry 53348096}

er1645v2EthPrtSwF2PppOEIpIMNetworkUnreachable OBJECT-TYPE
   SYNTAX      INTEGER
               {
               disabled (0),
               enabled (1)
               }
   MAX-ACCESS  read-write
   STATUS      current
   DESCRIPTION
      "Path: swPort.editConf.pppoEClient.ip.icmpMessages.networkUnreachable

       Possibilities:
               disabled   (0)
               enabled   (1)"
   ::= {er1645v2EthPrtSwF2PppOEEntry 53412096}

er1645v2EthPrtSwF2PppOEIpIMHostUnreachable OBJECT-TYPE
   SYNTAX      INTEGER
               {
               disabled (0),
               enabled (1)
               }
   MAX-ACCESS  read-write
   STATUS      current
   DESCRIPTION
      "Path: swPort.editConf.pppoEClient.ip.icmpMessages.hostUnreachable

       Possibilities:
               disabled   (0)
               enabled   (1)"
   ::= {er1645v2EthPrtSwF2PppOEEntry 53412352}

er1645v2EthPrtSwF2PppOEIpIMProtocolUnreachable OBJECT-TYPE
   SYNTAX      INTEGER
               {
               disabled (0),
               enabled (1)
               }
   MAX-ACCESS  read-write
   STATUS      current
   DESCRIPTION
      "Path: swPort.editConf.pppoEClient.ip.icmpMessages.protocolUnreachable

       Possibilities:
               disabled   (0)
               enabled   (1)"
   ::= {er1645v2EthPrtSwF2PppOEEntry 53412608}

er1645v2EthPrtSwF2PppOEIpIMPortUnreachable OBJECT-TYPE
   SYNTAX      INTEGER
               {
               disabled (0),
               enabled (1)
               }
   MAX-ACCESS  read-write
   STATUS      current
   DESCRIPTION
      "Path: swPort.editConf.pppoEClient.ip.icmpMessages.portUnreachable

       Possibilities:
               disabled   (0)
               enabled   (1)"
   ::= {er1645v2EthPrtSwF2PppOEEntry 53412864}

er1645v2EthPrtSwF2PppOEIpIMMtuExceeded OBJECT-TYPE
   SYNTAX      INTEGER
               {
               disabled (0),
               enabled (1)
               }
   MAX-ACCESS  read-write
   STATUS      current
   DESCRIPTION
      "Path: swPort.editConf.pppoEClient.ip.icmpMessages.mtuExceeded

       Possibilities:
               disabled   (0)
               enabled   (1)"
   ::= {er1645v2EthPrtSwF2PppOEEntry 53413120}

er1645v2EthPrtSwF2PppOEIpIMAdminProhibited OBJECT-TYPE
   SYNTAX      INTEGER
               {
               disabled (0),
               enabled (1)
               }
   MAX-ACCESS  read-write
   STATUS      current
   DESCRIPTION
      "Path: swPort.editConf.pppoEClient.ip.icmpMessages.adminProhibited

       Possibilities:
               disabled   (0)
               enabled   (1)"
   ::= {er1645v2EthPrtSwF2PppOEEntry 53413376}

er1645v2EthPrtSwF2PppOEIpIMTtlExceeded OBJECT-TYPE
   SYNTAX      INTEGER
               {
               disabled (0),
               enabled (1)
               }
   MAX-ACCESS  read-write
   STATUS      current
   DESCRIPTION
      "Path: swPort.editConf.pppoEClient.ip.icmpMessages.ttlExceeded

       Possibilities:
               disabled   (0)
               enabled   (1)"
   ::= {er1645v2EthPrtSwF2PppOEEntry 53413632}

er1645v2EthPrtSwF2PppOEIpIMRedirect OBJECT-TYPE
   SYNTAX      INTEGER
               {
               disabled (0),
               enabled (1)
               }
   MAX-ACCESS  read-write
   STATUS      current
   DESCRIPTION
      "Path: swPort.editConf.pppoEClient.ip.icmpMessages.redirect

       Possibilities:
               disabled   (0)
               enabled   (1)"
   ::= {er1645v2EthPrtSwF2PppOEEntry 53413888}

er1645v2EthPrtSwF2PppOEIpV6VrfRouter OBJECT-TYPE
   SYNTAX      DisplayString
   MAX-ACCESS  read-write
   STATUS      current
   DESCRIPTION
      "Path: swPort.editConf.pppoEClient.ipV6.vrfRouter"
   ::= {er1645v2EthPrtSwF2PppOEEntry 704708608}

er1645v2EthPrtSwF2PppOEIpV6AddrAutoConfigNrDupAddrDetects OBJECT-TYPE
   SYNTAX      Integer32
   MAX-ACCESS  read-write
   STATUS      current
   DESCRIPTION
      "Path: swPort.editConf.pppoEClient.ipV6.addrAutoConfig.nrDupAddrDetects"
   ::= {er1645v2EthPrtSwF2PppOEEntry 704905472}

er1645v2EthPrtSwF2PppOEIpV6AddrAutoConfigAcceptRa OBJECT-TYPE
   SYNTAX      INTEGER
               {
               disabled (0),
               enabled (1)
               }
   MAX-ACCESS  read-write
   STATUS      current
   DESCRIPTION
      "Path: swPort.editConf.pppoEClient.ipV6.addrAutoConfig.acceptRa

       Possibilities:
               disabled   (0)
               enabled   (1)"
   ::= {er1645v2EthPrtSwF2PppOEEntry 704905728}

er1645v2EthPrtSwF2PppOEIpV6AddrAutoConfigAcceptRaRdnss OBJECT-TYPE
   SYNTAX      INTEGER
               {
               disabled (0),
               enabled (1)
               }
   MAX-ACCESS  read-write
   STATUS      current
   DESCRIPTION
      "Path: swPort.editConf.pppoEClient.ipV6.addrAutoConfig.acceptRaRdnss

       Possibilities:
               disabled   (0)
               enabled   (1)"
   ::= {er1645v2EthPrtSwF2PppOEEntry 704905984}

er1645v2EthPrtSwF2PppOEIpV6AddrAutoConfigAcceptRaDnssl OBJECT-TYPE
   SYNTAX      INTEGER
               {
               disabled (0),
               enabled (1)
               }
   MAX-ACCESS  read-write
   STATUS      current
   DESCRIPTION
      "Path: swPort.editConf.pppoEClient.ipV6.addrAutoConfig.acceptRaDnssl

       Possibilities:
               disabled   (0)
               enabled   (1)"
   ::= {er1645v2EthPrtSwF2PppOEEntry 704906240}

er1645v2EthPrtSwF2PppOEIpV6DefaultRoute OBJECT-TYPE
   SYNTAX      INTEGER
               {
               disabled (0),
               enabled (1)
               }
   MAX-ACCESS  read-write
   STATUS      current
   DESCRIPTION
      "Path: swPort.editConf.pppoEClient.ipV6.defaultRoute

       Possibilities:
               disabled   (0)
               enabled   (1)"
   ::= {er1645v2EthPrtSwF2PppOEEntry 704970752}

er1645v2EthPrtSwF2PppOEIpV6RaSend OBJECT-TYPE
   SYNTAX      INTEGER
               {
               disabled (0),
               enabled (1)
               }
   MAX-ACCESS  read-write
   STATUS      current
   DESCRIPTION
      "Path: swPort.editConf.pppoEClient.ipV6.ra.send

       Possibilities:
               disabled   (0)
               enabled   (1)"
   ::= {er1645v2EthPrtSwF2PppOEEntry 705036544}

er1645v2EthPrtSwF2PppOEIpV6RaMinInterval OBJECT-TYPE
   SYNTAX      TimeTicks
   MAX-ACCESS  read-write
   STATUS      current
   DESCRIPTION
      "Path: swPort.editConf.pppoEClient.ipV6.ra.minInterval

       Time in centi-second."
   ::= {er1645v2EthPrtSwF2PppOEEntry 705036800}

er1645v2EthPrtSwF2PppOEIpV6RaMaxInterval OBJECT-TYPE
   SYNTAX      TimeTicks
   MAX-ACCESS  read-write
   STATUS      current
   DESCRIPTION
      "Path: swPort.editConf.pppoEClient.ipV6.ra.maxInterval

       Time in centi-second."
   ::= {er1645v2EthPrtSwF2PppOEEntry 705037056}

er1645v2EthPrtSwF2PppOEIpV6RaManagedFlag OBJECT-TYPE
   SYNTAX      INTEGER
               {
               disabled (0),
               enabled (1)
               }
   MAX-ACCESS  read-write
   STATUS      current
   DESCRIPTION
      "Path: swPort.editConf.pppoEClient.ipV6.ra.managedFlag

       Possibilities:
               disabled   (0)
               enabled   (1)"
   ::= {er1645v2EthPrtSwF2PppOEEntry 705037312}

er1645v2EthPrtSwF2PppOEIpV6RaOtherConfFlag OBJECT-TYPE
   SYNTAX      INTEGER
               {
               disabled (0),
               enabled (1)
               }
   MAX-ACCESS  read-write
   STATUS      current
   DESCRIPTION
      "Path: swPort.editConf.pppoEClient.ipV6.ra.otherConfFlag

       Possibilities:
               disabled   (0)
               enabled   (1)"
   ::= {er1645v2EthPrtSwF2PppOEEntry 705037568}

er1645v2EthPrtSwF2PppOEIpV6RaLinkMtu OBJECT-TYPE
   SYNTAX      Integer32
   MAX-ACCESS  read-write
   STATUS      current
   DESCRIPTION
      "Path: swPort.editConf.pppoEClient.ipV6.ra.linkMtu"
   ::= {er1645v2EthPrtSwF2PppOEEntry 705037824}

er1645v2EthPrtSwF2PppOEIpV6RaReachableTime OBJECT-TYPE
   SYNTAX      TimeTicks
   MAX-ACCESS  read-write
   STATUS      current
   DESCRIPTION
      "Path: swPort.editConf.pppoEClient.ipV6.ra.reachableTime

       Time in centi-second."
   ::= {er1645v2EthPrtSwF2PppOEEntry 705038080}

er1645v2EthPrtSwF2PppOEIpV6RaRetransmitTime OBJECT-TYPE
   SYNTAX      TimeTicks
   MAX-ACCESS  read-write
   STATUS      current
   DESCRIPTION
      "Path: swPort.editConf.pppoEClient.ipV6.ra.retransmitTime

       Time in centi-second."
   ::= {er1645v2EthPrtSwF2PppOEEntry 705038336}

er1645v2EthPrtSwF2PppOEIpV6RaHopLimit OBJECT-TYPE
   SYNTAX      Integer32
   MAX-ACCESS  read-write
   STATUS      current
   DESCRIPTION
      "Path: swPort.editConf.pppoEClient.ipV6.ra.hopLimit"
   ::= {er1645v2EthPrtSwF2PppOEEntry 705038592}

er1645v2EthPrtSwF2PppOEIpV6RaDefaultLifeTime OBJECT-TYPE
   SYNTAX      TimeTicks
   MAX-ACCESS  read-write
   STATUS      current
   DESCRIPTION
      "Path: swPort.editConf.pppoEClient.ipV6.ra.defaultLifeTime

       Time in centi-second."
   ::= {er1645v2EthPrtSwF2PppOEEntry 705038848}

er1645v2EthPrtSwF2PppOEIpV6RaDnsOptionsRdnssLifeTime OBJECT-TYPE
   SYNTAX      TimeTicks
   MAX-ACCESS  read-write
   STATUS      current
   DESCRIPTION
      "Path: swPort.editConf.pppoEClient.ipV6.ra.dnsOptions.rdnss.lifeTime

       Time in centi-second."
   ::= {er1645v2EthPrtSwF2PppOEEntry 705039140}

er1645v2EthPrtSwF2PppOEIpV6RaDnsOptionsRdnssImportServers OBJECT-TYPE
   SYNTAX      INTEGER
               {
               disabled (0),
               enabled (1)
               }
   MAX-ACCESS  read-write
   STATUS      current
   DESCRIPTION
      "Path: swPort.editConf.pppoEClient.ipV6.ra.dnsOptions.rdnss.importServers

       Possibilities:
               disabled   (0)
               enabled   (1)"
   ::= {er1645v2EthPrtSwF2PppOEEntry 705039148}

er1645v2EthPrtSwF2PppOEIpV6RaDnsOptionsDnsslLifeTime OBJECT-TYPE
   SYNTAX      TimeTicks
   MAX-ACCESS  read-write
   STATUS      current
   DESCRIPTION
      "Path: swPort.editConf.pppoEClient.ipV6.ra.dnsOptions.dnssl.lifeTime

       Time in centi-second."
   ::= {er1645v2EthPrtSwF2PppOEEntry 705039172}

er1645v2EthPrtSwF2PppOEIpV6RaDnsOptionsDnsslImportDomains OBJECT-TYPE
   SYNTAX      INTEGER
               {
               disabled (0),
               enabled (1)
               }
   MAX-ACCESS  read-write
   STATUS      current
   DESCRIPTION
      "Path: swPort.editConf.pppoEClient.ipV6.ra.dnsOptions.dnssl.importDomains

       Possibilities:
               disabled   (0)
               enabled   (1)"
   ::= {er1645v2EthPrtSwF2PppOEEntry 705039180}

er1645v2EthPrtSwF2PppOEIpV6RsSend OBJECT-TYPE
   SYNTAX      INTEGER
               {
               disabled (0),
               enabled (1)
               }
   MAX-ACCESS  read-write
   STATUS      current
   DESCRIPTION
      "Path: swPort.editConf.pppoEClient.ipV6.rs.send

       Possibilities:
               disabled   (0)
               enabled   (1)"
   ::= {er1645v2EthPrtSwF2PppOEEntry 705954048}

er1645v2EthPrtSwF2PppOEIpV6RsMaxRandomDelay OBJECT-TYPE
   SYNTAX      TimeTicks
   MAX-ACCESS  read-write
   STATUS      current
   DESCRIPTION
      "Path: swPort.editConf.pppoEClient.ipV6.rs.maxRandomDelay

       Time in centi-second."
   ::= {er1645v2EthPrtSwF2PppOEEntry 705954304}

er1645v2EthPrtSwF2PppOEIpV6RsInterval OBJECT-TYPE
   SYNTAX      TimeTicks
   MAX-ACCESS  read-write
   STATUS      current
   DESCRIPTION
      "Path: swPort.editConf.pppoEClient.ipV6.rs.interval

       Time in centi-second."
   ::= {er1645v2EthPrtSwF2PppOEEntry 705954560}

er1645v2EthPrtSwF2PppOEIpV6RsMaxSolicitations OBJECT-TYPE
   SYNTAX      Integer32
   MAX-ACCESS  read-write
   STATUS      current
   DESCRIPTION
      "Path: swPort.editConf.pppoEClient.ipV6.rs.maxSolicitations"
   ::= {er1645v2EthPrtSwF2PppOEEntry 705954816}

er1645v2EthPrtSwF2PppOEIpV6TrafficPolicyInbound OBJECT-TYPE
   SYNTAX      DisplayString
   MAX-ACCESS  read-write
   STATUS      current
   DESCRIPTION
      "Path: swPort.editConf.pppoEClient.ipV6.trafficPolicy.inbound"
   ::= {er1645v2EthPrtSwF2PppOEEntry 705364224}

er1645v2EthPrtSwF2PppOEIpV6TrafficPolicyOutbound OBJECT-TYPE
   SYNTAX      DisplayString
   MAX-ACCESS  read-write
   STATUS      current
   DESCRIPTION
      "Path: swPort.editConf.pppoEClient.ipV6.trafficPolicy.outbound"
   ::= {er1645v2EthPrtSwF2PppOEEntry 705364480}

er1645v2EthPrtSwF2PppOEIpV6FirewallZone OBJECT-TYPE
   SYNTAX      DisplayString
   MAX-ACCESS  read-write
   STATUS      current
   DESCRIPTION
      "Path: swPort.editConf.pppoEClient.ipV6.firewall.zone"
   ::= {er1645v2EthPrtSwF2PppOEEntry 705429760}

er1645v2EthPrtSwF2PppOEIpV6DhcpClientAddrAC OBJECT-TYPE
   SYNTAX      INTEGER
               {
               disabled (0),
               enabled (1)
               }
   MAX-ACCESS  read-write
   STATUS      current
   DESCRIPTION
      "Path: swPort.editConf.pppoEClient.ipV6.dhcp.client.addrAutoConfig

       Possibilities:
               disabled   (0)
               enabled   (1)"
   ::= {er1645v2EthPrtSwF2PppOEEntry 705307648}

er1645v2EthPrtSwF2PppOEIpV6DhcpClientPrDelMode OBJECT-TYPE
   SYNTAX      INTEGER
               {
               disabled (0),
               enabled (1)
               }
   MAX-ACCESS  read-write
   STATUS      current
   DESCRIPTION
      "Path: swPort.editConf.pppoEClient.ipV6.dhcp.client.pd.mode

       Possibilities:
               disabled   (0)
               enabled   (1)"
   ::= {er1645v2EthPrtSwF2PppOEEntry 705308676}

er1645v2EthPrtSwF2PppOEIpV6DhcpClientPrDelPool OBJECT-TYPE
   SYNTAX      DisplayString
   MAX-ACCESS  read-write
   STATUS      current
   DESCRIPTION
      "Path: swPort.editConf.pppoEClient.ipV6.dhcp.client.pd.pool"
   ::= {er1645v2EthPrtSwF2PppOEEntry 705308680}

er1645v2EthPrtSwF2PppOEIpV6DhcpClientPrDelPdExclOpt OBJECT-TYPE
   SYNTAX      INTEGER
               {
               disabled (0),
               enabled (1)
               }
   MAX-ACCESS  read-write
   STATUS      current
   DESCRIPTION
      "Path: swPort.editConf.pppoEClient.ipV6.dhcp.client.pd.pdExclOpt

       Possibilities:
               disabled   (0)
               enabled   (1)"
   ::= {er1645v2EthPrtSwF2PppOEEntry 705308684}

er1645v2EthPrtSwF2PppOEIpV6DhcpClientDnsServerPref OBJECT-TYPE
   SYNTAX      Integer32
   MAX-ACCESS  read-write
   STATUS      current
   DESCRIPTION
      "Path: swPort.editConf.pppoEClient.ipV6.dhcp.client.dns.serverPref"
   ::= {er1645v2EthPrtSwF2PppOEEntry 705310724}

er1645v2EthPrtSwF2PppOEIpV6DhcpClientRapidCommit OBJECT-TYPE
   SYNTAX      INTEGER
               {
               disabled (0),
               enabled (1)
               }
   MAX-ACCESS  read-write
   STATUS      current
   DESCRIPTION
      "Path: swPort.editConf.pppoEClient.ipV6.dhcp.client.rapidCommit

       Possibilities:
               disabled   (0)
               enabled   (1)"
   ::= {er1645v2EthPrtSwF2PppOEEntry 705309696}

er1645v2EthPrtSwF2PppOEIpV6DhcpClientTimersSolTimeOut OBJECT-TYPE
   SYNTAX      TimeTicks
   MAX-ACCESS  read-write
   STATUS      current
   DESCRIPTION
      "Path: swPort.editConf.pppoEClient.ipV6.dhcp.client.timers.solTimeOut

       Time in centi-second."
   ::= {er1645v2EthPrtSwF2PppOEEntry 705311748}

er1645v2EthPrtSwF2PppOEIpV6DhcpClientTimersSolMaxRt OBJECT-TYPE
   SYNTAX      TimeTicks
   MAX-ACCESS  read-write
   STATUS      current
   DESCRIPTION
      "Path: swPort.editConf.pppoEClient.ipV6.dhcp.client.timers.solMaxRt

       Time in centi-second."
   ::= {er1645v2EthPrtSwF2PppOEEntry 705311752}

er1645v2EthPrtSwF2PppOEIpV6DhcpClientTimersInfoRefresh OBJECT-TYPE
   SYNTAX      TimeTicks
   MAX-ACCESS  read-write
   STATUS      current
   DESCRIPTION
      "Path: swPort.editConf.pppoEClient.ipV6.dhcp.client.timers.infoRefresh

       Time in centi-second."
   ::= {er1645v2EthPrtSwF2PppOEEntry 705311756}

er1645v2EthPrtSwF2PppOEIpV6DhcpServerMode OBJECT-TYPE
   SYNTAX      INTEGER
               {
               disabled (0),
               enabled (1)
               }
   MAX-ACCESS  read-write
   STATUS      current
   DESCRIPTION
      "Path: swPort.editConf.pppoEClient.ipV6.dhcp.server.mode

       Possibilities:
               disabled   (0)
               enabled   (1)"
   ::= {er1645v2EthPrtSwF2PppOEEntry 705315840}

er1645v2EthPrtSwF2PppOEIpV6DhcpServerPreference OBJECT-TYPE
   SYNTAX      Integer32
   MAX-ACCESS  read-write
   STATUS      current
   DESCRIPTION
      "Path: swPort.editConf.pppoEClient.ipV6.dhcp.server.preference"
   ::= {er1645v2EthPrtSwF2PppOEEntry 705316864}

er1645v2EthPrtSwF2PppOEIpV6DhcpServerPool OBJECT-TYPE
   SYNTAX      DisplayString
   MAX-ACCESS  read-write
   STATUS      current
   DESCRIPTION
      "Path: swPort.editConf.pppoEClient.ipV6.dhcp.server.pool"
   ::= {er1645v2EthPrtSwF2PppOEEntry 705317888}

er1645v2EthPrtSwF2PppOEIpV6DhcpServerRapidCommit OBJECT-TYPE
   SYNTAX      INTEGER
               {
               disabled (0),
               enabled (1)
               }
   MAX-ACCESS  read-write
   STATUS      current
   DESCRIPTION
      "Path: swPort.editConf.pppoEClient.ipV6.dhcp.server.rapidCommit

       Possibilities:
               disabled   (0)
               enabled   (1)"
   ::= {er1645v2EthPrtSwF2PppOEEntry 705318912}

er1645v2EthPrtSwF2PppOEIpV6DhcpServerTimersInfoRefresh OBJECT-TYPE
   SYNTAX      TimeTicks
   MAX-ACCESS  read-write
   STATUS      current
   DESCRIPTION
      "Path: swPort.editConf.pppoEClient.ipV6.dhcp.server.timers.infoRefresh

       Time in centi-second."
   ::= {er1645v2EthPrtSwF2PppOEEntry 705319940}

er1645v2EthPrtSwF2PppOEIpV6DhcpRelayMode OBJECT-TYPE
   SYNTAX      INTEGER
               {
               disabled (0),
               enabled (1)
               }
   MAX-ACCESS  read-write
   STATUS      current
   DESCRIPTION
      "Path: swPort.editConf.pppoEClient.ipV6.dhcp.relay.mode

       Possibilities:
               disabled   (0)
               enabled   (1)"
   ::= {er1645v2EthPrtSwF2PppOEEntry 705323040}

er1645v2EthPrtSwF2PppOEIpV6SendRedirect OBJECT-TYPE
   SYNTAX      INTEGER
               {
               disabled (0),
               enabled (1)
               }
   MAX-ACCESS  read-write
   STATUS      current
   DESCRIPTION
      "Path: swPort.editConf.pppoEClient.ipV6.sendRedirect

       Possibilities:
               disabled   (0)
               enabled   (1)"
   ::= {er1645v2EthPrtSwF2PppOEEntry 705101824}

er1645v2EthPrtSwF2PppOEIpV6LinkMtu OBJECT-TYPE
   SYNTAX      Integer32
   MAX-ACCESS  read-write
   STATUS      current
   DESCRIPTION
      "Path: swPort.editConf.pppoEClient.ipV6.linkMtu"
   ::= {er1645v2EthPrtSwF2PppOEEntry 705167360}

er1645v2EthPrtSwF2PppOEIpV6InterfaceId OBJECT-TYPE
   SYNTAX      OCTET STRING
   MAX-ACCESS  read-write
   STATUS      current
   DESCRIPTION
      "Path: swPort.editConf.pppoEClient.ipV6.interfaceId"
   ::= {er1645v2EthPrtSwF2PppOEEntry 705232896}

er1645v2EthPrtSwF2PppOEIpV6MF OBJECT-TYPE
   SYNTAX      Integer32
   MAX-ACCESS  read-write
   STATUS      current
   DESCRIPTION
      "Path: swPort.editConf.pppoEClient.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1645v2EthPrtSwF2PppOEEntry 705757184}

er1645v2EthPrtSwF2PppOEIpV6IcmpMessagesNoRoute OBJECT-TYPE
   SYNTAX      INTEGER
               {
               disabled (0),
               enabled (1)
               }
   MAX-ACCESS  read-write
   STATUS      current
   DESCRIPTION
      "Path: swPort.editConf.pppoEClient.ipV6.icmpMessages.noRoute

       Possibilities:
               disabled   (0)
               enabled   (1)"
   ::= {er1645v2EthPrtSwF2PppOEEntry 705822976}

er1645v2EthPrtSwF2PppOEIpV6IcmpMessagesBeyondScope OBJECT-TYPE
   SYNTAX      INTEGER
               {
               disabled (0),
               enabled (1)
               }
   MAX-ACCESS  read-write
   STATUS      current
   DESCRIPTION
      "Path: swPort.editConf.pppoEClient.ipV6.icmpMessages.beyondScope

       Possibilities:
               disabled   (0)
               enabled   (1)"
   ::= {er1645v2EthPrtSwF2PppOEEntry 705823488}

er1645v2EthPrtSwF2PppOEIpV6IcmpMessagesAddressUnreachable OBJECT-TYPE
   SYNTAX      INTEGER
               {
               disabled (0),
               enabled (1)
               }
   MAX-ACCESS  read-write
   STATUS      current
   DESCRIPTION
      "Path: swPort.editConf.pppoEClient.ipV6.icmpMessages.addressUnreachable

       Possibilities:
               disabled   (0)
               enabled   (1)"
   ::= {er1645v2EthPrtSwF2PppOEEntry 705823744}

er1645v2EthPrtSwF2PppOEIpV6IcmpMessagesPortUnreachable OBJECT-TYPE
   SYNTAX      INTEGER
               {
               disabled (0),
               enabled (1)
               }
   MAX-ACCESS  read-write
   STATUS      current
   DESCRIPTION
      "Path: swPort.editConf.pppoEClient.ipV6.icmpMessages.portUnreachable

       Possibilities:
               disabled   (0)
               enabled   (1)"
   ::= {er1645v2EthPrtSwF2PppOEEntry 705824000}

er1645v2EthPrtSwF2PppOEIpV6IcmpMessagesPacketTooBig OBJECT-TYPE
   SYNTAX      INTEGER
               {
               disabled (0),
               enabled (1)
               }
   MAX-ACCESS  read-write
   STATUS      current
   DESCRIPTION
      "Path: swPort.editConf.pppoEClient.ipV6.icmpMessages.packetTooBig

       Possibilities:
               disabled   (0)
               enabled   (1)"
   ::= {er1645v2EthPrtSwF2PppOEEntry 705825280}

er1645v2EthPrtSwF2PppOEIpV6IcmpMessagesHopLimitExceeded OBJECT-TYPE
   SYNTAX      INTEGER
               {
               disabled (0),
               enabled (1)
               }
   MAX-ACCESS  read-write
   STATUS      current
   DESCRIPTION
      "Path: swPort.editConf.pppoEClient.ipV6.icmpMessages.hopLimitExceeded

       Possibilities:
               disabled   (0)
               enabled   (1)"
   ::= {er1645v2EthPrtSwF2PppOEEntry 705827840}

er1645v2EthPrtSwF2PppOEIpV6IcmpMessagesFragTimeExceeded OBJECT-TYPE
   SYNTAX      INTEGER
               {
               disabled (0),
               enabled (1)
               }
   MAX-ACCESS  read-write
   STATUS      current
   DESCRIPTION
      "Path: swPort.editConf.pppoEClient.ipV6.icmpMessages.fragTimeExceeded

       Possibilities:
               disabled   (0)
               enabled   (1)"
   ::= {er1645v2EthPrtSwF2PppOEEntry 705828096}

er1645v2EthPrtSwF2PppOEIpV6IcmpMessagesHeaderFieldErr OBJECT-TYPE
   SYNTAX      INTEGER
               {
               disabled (0),
               enabled (1)
               }
   MAX-ACCESS  read-write
   STATUS      current
   DESCRIPTION
      "Path: swPort.editConf.pppoEClient.ipV6.icmpMessages.headerFieldErr

       Possibilities:
               disabled   (0)
               enabled   (1)"
   ::= {er1645v2EthPrtSwF2PppOEEntry 705830400}

er1645v2EthPrtSwF2PppOEIpV6IcmpMessagesOptionUnrecognized OBJECT-TYPE
   SYNTAX      INTEGER
               {
               disabled (0),
               enabled (1)
               }
   MAX-ACCESS  read-write
   STATUS      current
   DESCRIPTION
      "Path: swPort.editConf.pppoEClient.ipV6.icmpMessages.optionUnrecognized

       Possibilities:
               disabled   (0)
               enabled   (1)"
   ::= {er1645v2EthPrtSwF2PppOEEntry 705830912}

er1645v2EthPrtSwF2PppOEIpV6IcmpMessagesRedirect OBJECT-TYPE
   SYNTAX      INTEGER
               {
               disabled (0),
               enabled (1)
               }
   MAX-ACCESS  read-write
   STATUS      current
   DESCRIPTION
      "Path: swPort.editConf.pppoEClient.ipV6.icmpMessages.redirect

       Possibilities:
               disabled   (0)
               enabled   (1)"
   ::= {er1645v2EthPrtSwF2PppOEEntry 705832960}

er1645v2EthPrtSwF2PppOEPppLnkMOperation OBJECT-TYPE
   SYNTAX      INTEGER
               {
               disabled (0),
               enabled (1)
               }
   MAX-ACCESS  read-write
   STATUS      current
   DESCRIPTION
      "Path: swPort.editConf.pppoEClient.ppp.linkMonitoring.operation

       Possibilities:
               disabled   (0)
               enabled   (1)"
   ::= {er1645v2EthPrtSwF2PppOEEntry 251724032}

er1645v2EthPrtSwF2PppOEPppLnkMInterval OBJECT-TYPE
   SYNTAX      TimeTicks
   MAX-ACCESS  read-write
   STATUS      current
   DESCRIPTION
      "Path: swPort.editConf.pppoEClient.ppp.linkMonitoring.interval

       Time in centi-second."
   ::= {er1645v2EthPrtSwF2PppOEEntry 251724288}

er1645v2EthPrtSwF2PppOEPppLnkMRepTimeOut OBJECT-TYPE
   SYNTAX      TimeTicks
   MAX-ACCESS  read-write
   STATUS      current
   DESCRIPTION
      "Path: swPort.editConf.pppoEClient.ppp.linkMonitoring.replyTimeOut

       Time in centi-second."
   ::= {er1645v2EthPrtSwF2PppOEEntry 251724544}

er1645v2EthPrtSwF2PppOEPppLnkMFailsPrmt OBJECT-TYPE
   SYNTAX      Integer32
   MAX-ACCESS  read-write
   STATUS      current
   DESCRIPTION
      "Path: swPort.editConf.pppoEClient.ppp.linkMonitoring.failsPermitted"
   ::= {er1645v2EthPrtSwF2PppOEEntry 251724800}

er1645v2EthPrtSwF2PppOEPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: swPort.editConf.pppoEClient.ppp.authentication

       Possibilities:
               disabled   (0)
               chap   (1)
               pap   (2)
               chapOrPap   (3)
               msChap   (4)
               msChapV2   (5)"
   ::= {er1645v2EthPrtSwF2PppOEEntry 251789312}

er1645v2EthPrtSwF2PppOEPppAuthenPeriod OBJECT-TYPE
   SYNTAX      TimeTicks
   MAX-ACCESS  read-write
   STATUS      current
   DESCRIPTION
      "Path: swPort.editConf.pppoEClient.ppp.authenPeriod

       Time in centi-second."
   ::= {er1645v2EthPrtSwF2PppOEEntry 251854848}

er1645v2EthPrtSwF2PppOEPppSessionName OBJECT-TYPE
   SYNTAX      DisplayString
   MAX-ACCESS  read-write
   STATUS      current
   DESCRIPTION
      "Path: swPort.editConf.pppoEClient.ppp.sessionName"
   ::= {er1645v2EthPrtSwF2PppOEEntry 251985920}

er1645v2EthPrtSwF2PppOEPppSessionSecret OBJECT-TYPE
   SYNTAX      DisplayString
   MAX-ACCESS  read-write
   STATUS      current
   DESCRIPTION
      "Path: swPort.editConf.pppoEClient.ppp.sessionSecret"
   ::= {er1645v2EthPrtSwF2PppOEEntry 252051456}

er1645v2EthPrtSwF2PppOEPppEncModeSessionSecret OBJECT-TYPE
   SYNTAX      INTEGER
               {
               none (1),
               encrypt (2),
               encType1 (3),
               invalid (128)
               }
   MAX-ACCESS  read-write
   STATUS      current
   DESCRIPTION
      "Path: swPort.editConf.pppoEClient.ppp.encModeSessionSecret

       Possibilities:
               none   (1)
               encrypt   (2)
               encType1   (3)
               invalid   (128)"
   ::= {er1645v2EthPrtSwF2PppOEEntry 252182528}

er1645v2EthPrtSwF2PppOEPppEncSessionSecret OBJECT-TYPE
   SYNTAX      DisplayString
   MAX-ACCESS  read-write
   STATUS      current
   DESCRIPTION
      "Path: swPort.editConf.pppoEClient.ppp.encSessionSecret"
   ::= {er1645v2EthPrtSwF2PppOEEntry 252248064}

er1645v2EthPrtSwF2PppOEPppServiceName OBJECT-TYPE
   SYNTAX      DisplayString
   MAX-ACCESS  read-write
   STATUS      current
   DESCRIPTION
      "Path: swPort.editConf.pppoEClient.ppp.serviceName"
   ::= {er1645v2EthPrtSwF2PppOEEntry 252116992}

er1645v2EthPrtSwF2PppOEIpH OBJECT-TYPE
   SYNTAX      SEQUENCE OF Er1645v2EthPrtSwF2PppOEIpHEntry
   MAX-ACCESS  not-accessible
   STATUS      current
   DESCRIPTION
      ""
   ::= {er1645v2EthPrtSwF2PppOE 51314688}

er1645v2EthPrtSwF2PppOEIpHEntry OBJECT-TYPE
   SYNTAX      Er1645v2EthPrtSwF2PppOEIpHEntry
   MAX-ACCESS  not-accessible
   STATUS      current
   DESCRIPTION
      ""
   INDEX      { er1645v2EthPrtSwF2PppOEIpHGlobalIx,
                er1645v2EthPrtSwF2PppOETableIx,
                er1645v2EthPrtSwF2PppOEIpHTableIx }
   ::= {er1645v2EthPrtSwF2PppOEIpH 1}

Er1645v2EthPrtSwF2PppOEIpHEntry ::=
   SEQUENCE
      {
      er1645v2EthPrtSwF2PppOEIpHActions
         VariableLengthTableActions,
      er1645v2EthPrtSwF2PppOEIpHGlobalIx
         GlobalIndex,
      er1645v2EthPrtSwF2PppOEIpHTableIx
         TableIndex,
      er1645v2EthPrtSwF2PppOEIpHAddress
         IpAddress,
      er1645v2EthPrtSwF2PppOEIpHDhcpRelayOptionSubscriberId
         DisplayString
      }

er1645v2EthPrtSwF2PppOEIpHActions OBJECT-TYPE
   SYNTAX      VariableLengthTableActions
   MAX-ACCESS  read-write
   STATUS      current
   DESCRIPTION
      "By way of this field, some manipulations
       on this table may be performed."
   ::= {er1645v2EthPrtSwF2PppOEIpHEntry 2}

er1645v2EthPrtSwF2PppOEIpHGlobalIx OBJECT-TYPE
   SYNTAX      GlobalIndex
   MAX-ACCESS  not-accessible
   STATUS      current
   DESCRIPTION
      "The value of the tlsCntTreeGlobalIndex of the MANAGED OBJECT."
   ::= {er1645v2EthPrtSwF2PppOEIpHEntry 10}

er1645v2EthPrtSwF2PppOEIpHTableIx OBJECT-TYPE
   SYNTAX      TableIndex
   MAX-ACCESS  not-accessible
   STATUS      current
   DESCRIPTION
      ""
   ::= {er1645v2EthPrtSwF2PppOEIpHEntry 11}

er1645v2EthPrtSwF2PppOEIpHAddress OBJECT-TYPE
   SYNTAX      IpAddress
   MAX-ACCESS  read-write
   STATUS      current
   DESCRIPTION
      "Path: swPort.editConf.pppoEClient.ip.helpers.address"
   ::= {er1645v2EthPrtSwF2PppOEIpHEntry 16777216}

er1645v2EthPrtSwF2PppOEIpHDhcpRelayOptionSubscriberId OBJECT-TYPE
   SYNTAX      DisplayString
   MAX-ACCESS  read-write
   STATUS      current
   DESCRIPTION
      "Path: swPort.editConf.pppoEClient.ip.helpers.dhcpRelayOption.subscriberId"
   ::= {er1645v2EthPrtSwF2PppOEIpHEntry 33947648}

er1645v2EthPrtSwF2PppOEIpV6Addresses OBJECT-TYPE
   SYNTAX      SEQUENCE OF Er1645v2EthPrtSwF2PppOEIpV6AddressesEntry
   MAX-ACCESS  not-accessible
   STATUS      current
   DESCRIPTION
      ""
   ::= {er1645v2EthPrtSwF2PppOE 704839680}

er1645v2EthPrtSwF2PppOEIpV6AddressesEntry OBJECT-TYPE
   SYNTAX      Er1645v2EthPrtSwF2PppOEIpV6AddressesEntry
   MAX-ACCESS  not-accessible
   STATUS      current
   DESCRIPTION
      ""
   INDEX      { er1645v2EthPrtSwF2PppOEIpV6AddressesGlobalIx,
                er1645v2EthPrtSwF2PppOETableIx,
                er1645v2EthPrtSwF2PppOEIpV6AddressesTableIx }
   ::= {er1645v2EthPrtSwF2PppOEIpV6Addresses 1}

Er1645v2EthPrtSwF2PppOEIpV6AddressesEntry ::=
   SEQUENCE
      {
      er1645v2EthPrtSwF2PppOEIpV6AddressesActions
         VariableLengthTableActions,
      er1645v2EthPrtSwF2PppOEIpV6AddressesGlobalIx
         GlobalIndex,
      er1645v2EthPrtSwF2PppOEIpV6AddressesTableIx
         TableIndex,
      er1645v2EthPrtSwF2PppOEIpV6AddressesType
         INTEGER,
      er1645v2EthPrtSwF2PppOEIpV6AddressesAddress
         Ipv6Address,
      er1645v2EthPrtSwF2PppOEIpV6AddressesPrefixLength
         Integer32,
      er1645v2EthPrtSwF2PppOEIpV6AddressesGeneralPrefix
         DisplayString,
      er1645v2EthPrtSwF2PppOEIpV6AddressesRaSend
         INTEGER,
      er1645v2EthPrtSwF2PppOEIpV6AddressesRaOnLinkFlag
         INTEGER,
      er1645v2EthPrtSwF2PppOEIpV6AddressesRaAutoFlag
         INTEGER,
      er1645v2EthPrtSwF2PppOEIpV6AddressesRaValidLifeTime
         TimeTicks,
      er1645v2EthPrtSwF2PppOEIpV6AddressesRaValidLTMode
         INTEGER,
      er1645v2EthPrtSwF2PppOEIpV6AddressesRaPrefLifeTime
         TimeTicks,
      er1645v2EthPrtSwF2PppOEIpV6AddressesRaPrefLTMode
         INTEGER
      }

er1645v2EthPrtSwF2PppOEIpV6AddressesActions OBJECT-TYPE
   SYNTAX      VariableLengthTableActions
   MAX-ACCESS  read-write
   STATUS      current
   DESCRIPTION
      "By way of this field, some manipulations
       on this table may be performed."
   ::= {er1645v2EthPrtSwF2PppOEIpV6AddressesEntry 2}

er1645v2EthPrtSwF2PppOEIpV6AddressesGlobalIx OBJECT-TYPE
   SYNTAX      GlobalIndex
   MAX-ACCESS  not-accessible
   STATUS      current
   DESCRIPTION
      "The value of the tlsCntTreeGlobalIndex of the MANAGED OBJECT."
   ::= {er1645v2EthPrtSwF2PppOEIpV6AddressesEntry 10}

er1645v2EthPrtSwF2PppOEIpV6AddressesTableIx OBJECT-TYPE
   SYNTAX      TableIndex
   MAX-ACCESS  not-accessible
   STATUS      current
   DESCRIPTION
      ""
   ::= {er1645v2EthPrtSwF2PppOEIpV6AddressesEntry 11}

er1645v2EthPrtSwF2PppOEIpV6AddressesType OBJECT-TYPE
   SYNTAX      INTEGER
               {
               unicast (0),
               eui64 (1),
               anycast (2),
               linkLocal (3),
               generalPrefix (4)
               }
   MAX-ACCESS  read-write
   STATUS      current
   DESCRIPTION
      "Path: swPort.editConf.pppoEClient.ipV6.addresses.type

       Possibilities:
               unicast   (0)
               eui64   (1)
               anycast   (2)
               linkLocal   (3)
               generalPrefix   (4)"
   ::= {er1645v2EthPrtSwF2PppOEIpV6AddressesEntry 50331648}

er1645v2EthPrtSwF2PppOEIpV6AddressesAddress OBJECT-TYPE
   SYNTAX      Ipv6Address
   MAX-ACCESS  read-write
   STATUS      current
   DESCRIPTION
      "Path: swPort.editConf.pppoEClient.ipV6.addresses.address

       ipv6 address"
   ::= {er1645v2EthPrtSwF2PppOEIpV6AddressesEntry 16777216}

er1645v2EthPrtSwF2PppOEIpV6AddressesPrefixLength OBJECT-TYPE
   SYNTAX      Integer32
   MAX-ACCESS  read-write
   STATUS      current
   DESCRIPTION
      "Path: swPort.editConf.pppoEClient.ipV6.addresses.prefixLength"
   ::= {er1645v2EthPrtSwF2PppOEIpV6AddressesEntry 33554432}

er1645v2EthPrtSwF2PppOEIpV6AddressesGeneralPrefix OBJECT-TYPE
   SYNTAX      DisplayString
   MAX-ACCESS  read-write
   STATUS      current
   DESCRIPTION
      "Path: swPort.editConf.pppoEClient.ipV6.addresses.generalPrefix"
   ::= {er1645v2EthPrtSwF2PppOEIpV6AddressesEntry 83886080}

er1645v2EthPrtSwF2PppOEIpV6AddressesRaSend OBJECT-TYPE
   SYNTAX      INTEGER
               {
               disabled (0),
               enabled (1)
               }
   MAX-ACCESS  read-write
   STATUS      current
   DESCRIPTION
      "Path: swPort.editConf.pppoEClient.ipV6.addresses.ra.send

       Possibilities:
               disabled   (0)
               enabled   (1)"
   ::= {er1645v2EthPrtSwF2PppOEIpV6AddressesEntry 67174400}

er1645v2EthPrtSwF2PppOEIpV6AddressesRaOnLinkFlag OBJECT-TYPE
   SYNTAX      INTEGER
               {
               disabled (0),
               enabled (1)
               }
   MAX-ACCESS  read-write
   STATUS      current
   DESCRIPTION
      "Path: swPort.editConf.pppoEClient.ipV6.addresses.ra.onLinkFlag

       Possibilities:
               disabled   (0)
               enabled   (1)"
   ::= {er1645v2EthPrtSwF2PppOEIpV6AddressesEntry 67371008}

er1645v2EthPrtSwF2PppOEIpV6AddressesRaAutoFlag OBJECT-TYPE
   SYNTAX      INTEGER
               {
               disabled (0),
               enabled (1)
               }
   MAX-ACCESS  read-write
   STATUS      current
   DESCRIPTION
      "Path: swPort.editConf.pppoEClient.ipV6.addresses.ra.autonomousFlag

       Possibilities:
               disabled   (0)
               enabled   (1)"
   ::= {er1645v2EthPrtSwF2PppOEIpV6AddressesEntry 67567616}

er1645v2EthPrtSwF2PppOEIpV6AddressesRaValidLifeTime OBJECT-TYPE
   SYNTAX      TimeTicks
   MAX-ACCESS  read-write
   STATUS      current
   DESCRIPTION
      "Path: swPort.editConf.pppoEClient.ipV6.addresses.ra.validLifeTime

       Time in centi-second."
   ::= {er1645v2EthPrtSwF2PppOEIpV6AddressesEntry 67239936}

er1645v2EthPrtSwF2PppOEIpV6AddressesRaValidLTMode OBJECT-TYPE
   SYNTAX      INTEGER
               {
               fixed (0),
               infinite (2)
               }
   MAX-ACCESS  read-write
   STATUS      current
   DESCRIPTION
      "Path: swPort.editConf.pppoEClient.ipV6.addresses.ra.validLifeTimeMode

       Possibilities:
               fixed   (0)
               infinite   (2)"
   ::= {er1645v2EthPrtSwF2PppOEIpV6AddressesEntry 67305472}

er1645v2EthPrtSwF2PppOEIpV6AddressesRaPrefLifeTime OBJECT-TYPE
   SYNTAX      TimeTicks
   MAX-ACCESS  read-write
   STATUS      current
   DESCRIPTION
      "Path: swPort.editConf.pppoEClient.ipV6.addresses.ra.prefLifeTime

       Time in centi-second."
   ::= {er1645v2EthPrtSwF2PppOEIpV6AddressesEntry 67436544}

er1645v2EthPrtSwF2PppOEIpV6AddressesRaPrefLTMode OBJECT-TYPE
   SYNTAX      INTEGER
               {
               fixed (0),
               infinite (2)
               }
   MAX-ACCESS  read-write
   STATUS      current
   DESCRIPTION
      "Path: swPort.editConf.pppoEClient.ipV6.addresses.ra.prefLifeTimeMode

       Possibilities:
               fixed   (0)
               infinite   (2)"
   ::= {er1645v2EthPrtSwF2PppOEIpV6AddressesEntry 67502080}

er1645v2EthPrtSwF2PppOEIpV6RaDnsOptionsRdnssServers OBJECT-TYPE
   SYNTAX      SEQUENCE OF Er1645v2EthPrtSwF2PppOEIpV6RaDnsOptionsRdnssServersEntry
   MAX-ACCESS  not-accessible
   STATUS      current
   DESCRIPTION
      ""
   ::= {er1645v2EthPrtSwF2PppOE 705039144}

er1645v2EthPrtSwF2PppOEIpV6RaDnsOptionsRdnssServersEntry OBJECT-TYPE
   SYNTAX      Er1645v2EthPrtSwF2PppOEIpV6RaDnsOptionsRdnssServersEntry
   MAX-ACCESS  not-accessible
   STATUS      current
   DESCRIPTION
      ""
   INDEX      { er1645v2EthPrtSwF2PppOEIpV6RaDnsOptionsRdnssServersGlobalIx,
                er1645v2EthPrtSwF2PppOETableIx,
                er1645v2EthPrtSwF2PppOEIpV6RaDnsOptionsRdnssServersTableIx }
   ::= {er1645v2EthPrtSwF2PppOEIpV6RaDnsOptionsRdnssServers 1}

Er1645v2EthPrtSwF2PppOEIpV6RaDnsOptionsRdnssServersEntry ::=
   SEQUENCE
      {
      er1645v2EthPrtSwF2PppOEIpV6RaDnsOptionsRdnssServersActions
         VariableLengthTableActions,
      er1645v2EthPrtSwF2PppOEIpV6RaDnsOptionsRdnssServersGlobalIx
         GlobalIndex,
      er1645v2EthPrtSwF2PppOEIpV6RaDnsOptionsRdnssServersTableIx
         TableIndex,
      er1645v2EthPrtSwF2PppOEIpV6RaDnsOptionsRdnssServersAddress
         Ipv6Address
      }

er1645v2EthPrtSwF2PppOEIpV6RaDnsOptionsRdnssServersActions OBJECT-TYPE
   SYNTAX      VariableLengthTableActions
   MAX-ACCESS  read-write
   STATUS      current
   DESCRIPTION
      "By way of this field, some manipulations
       on this table may be performed."
   ::= {er1645v2EthPrtSwF2PppOEIpV6RaDnsOptionsRdnssServersEntry 2}

er1645v2EthPrtSwF2PppOEIpV6RaDnsOptionsRdnssServersGlobalIx OBJECT-TYPE
   SYNTAX      GlobalIndex
   MAX-ACCESS  not-accessible
   STATUS      current
   DESCRIPTION
      "The value of the tlsCntTreeGlobalIndex of the MANAGED OBJECT."
   ::= {er1645v2EthPrtSwF2PppOEIpV6RaDnsOptionsRdnssServersEntry 10}

er1645v2EthPrtSwF2PppOEIpV6RaDnsOptionsRdnssServersTableIx OBJECT-TYPE
   SYNTAX      TableIndex
   MAX-ACCESS  not-accessible
   STATUS      current
   DESCRIPTION
      ""
   ::= {er1645v2EthPrtSwF2PppOEIpV6RaDnsOptionsRdnssServersEntry 11}

er1645v2EthPrtSwF2PppOEIpV6RaDnsOptionsRdnssServersAddress OBJECT-TYPE
   SYNTAX      Ipv6Address
   MAX-ACCESS  read-write
   STATUS      current
   DESCRIPTION
      "Path: swPort.editConf.pppoEClient.ipV6.ra.dnsOptions.rdnss.servers.address

       ipv6 address"
   ::= {er1645v2EthPrtSwF2PppOEIpV6RaDnsOptionsRdnssServersEntry 16777216}

er1645v2EthPrtSwF2PppOEIpV6RaDnsOptionsDnsslDomains OBJECT-TYPE
   SYNTAX      SEQUENCE OF Er1645v2EthPrtSwF2PppOEIpV6RaDnsOptionsDnsslDomainsEntry
   MAX-ACCESS  not-accessible
   STATUS      current
   DESCRIPTION
      ""
   ::= {er1645v2EthPrtSwF2PppOE 705039176}

er1645v2EthPrtSwF2PppOEIpV6RaDnsOptionsDnsslDomainsEntry OBJECT-TYPE
   SYNTAX      Er1645v2EthPrtSwF2PppOEIpV6RaDnsOptionsDnsslDomainsEntry
   MAX-ACCESS  not-accessible
   STATUS      current
   DESCRIPTION
      ""
   INDEX      { er1645v2EthPrtSwF2PppOEIpV6RaDnsOptionsDnsslDomainsGlobalIx,
                er1645v2EthPrtSwF2PppOETableIx,
                er1645v2EthPrtSwF2PppOEIpV6RaDnsOptionsDnsslDomainsTableIx }
   ::= {er1645v2EthPrtSwF2PppOEIpV6RaDnsOptionsDnsslDomains 1}

Er1645v2EthPrtSwF2PppOEIpV6RaDnsOptionsDnsslDomainsEntry ::=
   SEQUENCE
      {
      er1645v2EthPrtSwF2PppOEIpV6RaDnsOptionsDnsslDomainsActions
         VariableLengthTableActions,
      er1645v2EthPrtSwF2PppOEIpV6RaDnsOptionsDnsslDomainsGlobalIx
         GlobalIndex,
      er1645v2EthPrtSwF2PppOEIpV6RaDnsOptionsDnsslDomainsTableIx
         TableIndex,
      er1645v2EthPrtSwF2PppOEIpV6RaDnsOptionsDnsslDomainsName
         DisplayString
      }

er1645v2EthPrtSwF2PppOEIpV6RaDnsOptionsDnsslDomainsActions OBJECT-TYPE
   SYNTAX      VariableLengthTableActions
   MAX-ACCESS  read-write
   STATUS      current
   DESCRIPTION
      "By way of this field, some manipulations
       on this table may be performed."
   ::= {er1645v2EthPrtSwF2PppOEIpV6RaDnsOptionsDnsslDomainsEntry 2}

er1645v2EthPrtSwF2PppOEIpV6RaDnsOptionsDnsslDomainsGlobalIx OBJECT-TYPE
   SYNTAX      GlobalIndex
   MAX-ACCESS  not-accessible
   STATUS      current
   DESCRIPTION
      "The value of the tlsCntTreeGlobalIndex of the MANAGED OBJECT."
   ::= {er1645v2EthPrtSwF2PppOEIpV6RaDnsOptionsDnsslDomainsEntry 10}

er1645v2EthPrtSwF2PppOEIpV6RaDnsOptionsDnsslDomainsTableIx OBJECT-TYPE
   SYNTAX      TableIndex
   MAX-ACCESS  not-accessible
   STATUS      current
   DESCRIPTION
      ""
   ::= {er1645v2EthPrtSwF2PppOEIpV6RaDnsOptionsDnsslDomainsEntry 11}

er1645v2EthPrtSwF2PppOEIpV6RaDnsOptionsDnsslDomainsName OBJECT-TYPE
   SYNTAX      DisplayString
   MAX-ACCESS  read-write
   STATUS      current
   DESCRIPTION
      "Path: swPort.editConf.pppoEClient.ipV6.ra.dnsOptions.dnssl.domains.name"
   ::= {er1645v2EthPrtSwF2PppOEIpV6RaDnsOptionsDnsslDomainsEntry 16777216}

er1645v2EthPrtSwF2PppOEIpV6DhcpClientUserClassOpt OBJECT-TYPE
   SYNTAX      SEQUENCE OF Er1645v2EthPrtSwF2PppOEIpV6DhcpClientUserClassOptEntry
   MAX-ACCESS  not-accessible
   STATUS      current
   DESCRIPTION
      ""
   ::= {er1645v2EthPrtSwF2PppOE 705312768}

er1645v2EthPrtSwF2PppOEIpV6DhcpClientUserClassOptEntry OBJECT-TYPE
   SYNTAX      Er1645v2EthPrtSwF2PppOEIpV6DhcpClientUserClassOptEntry
   MAX-ACCESS  not-accessible
   STATUS      current
   DESCRIPTION
      ""
   INDEX      { er1645v2EthPrtSwF2PppOEIpV6DhcpClientUserClassOptGlobalIx,
                er1645v2EthPrtSwF2PppOETableIx,
                er1645v2EthPrtSwF2PppOEIpV6DhcpClientUserClassOptTableIx }
   ::= {er1645v2EthPrtSwF2PppOEIpV6DhcpClientUserClassOpt 1}

Er1645v2EthPrtSwF2PppOEIpV6DhcpClientUserClassOptEntry ::=
   SEQUENCE
      {
      er1645v2EthPrtSwF2PppOEIpV6DhcpClientUserClassOptActions
         VariableLengthTableActions,
      er1645v2EthPrtSwF2PppOEIpV6DhcpClientUserClassOptGlobalIx
         GlobalIndex,
      er1645v2EthPrtSwF2PppOEIpV6DhcpClientUserClassOptTableIx
         TableIndex,
      er1645v2EthPrtSwF2PppOEIpV6DhcpClientUserClassOptValueAscii
         DisplayString,
      er1645v2EthPrtSwF2PppOEIpV6DhcpClientUserClassOptValueDecimal
         Integer32,
      er1645v2EthPrtSwF2PppOEIpV6DhcpClientUserClassOptValueHexData
         OCTET STRING
      }

er1645v2EthPrtSwF2PppOEIpV6DhcpClientUserClassOptActions OBJECT-TYPE
   SYNTAX      VariableLengthTableActions
   MAX-ACCESS  read-write
   STATUS      current
   DESCRIPTION
      "By way of this field, some manipulations
       on this table may be performed."
   ::= {er1645v2EthPrtSwF2PppOEIpV6DhcpClientUserClassOptEntry 2}

er1645v2EthPrtSwF2PppOEIpV6DhcpClientUserClassOptGlobalIx OBJECT-TYPE
   SYNTAX      GlobalIndex
   MAX-ACCESS  not-accessible
   STATUS      current
   DESCRIPTION
      "The value of the tlsCntTreeGlobalIndex of the MANAGED OBJECT."
   ::= {er1645v2EthPrtSwF2PppOEIpV6DhcpClientUserClassOptEntry 10}

er1645v2EthPrtSwF2PppOEIpV6DhcpClientUserClassOptTableIx OBJECT-TYPE
   SYNTAX      TableIndex
   MAX-ACCESS  not-accessible
   STATUS      current
   DESCRIPTION
      ""
   ::= {er1645v2EthPrtSwF2PppOEIpV6DhcpClientUserClassOptEntry 11}

er1645v2EthPrtSwF2PppOEIpV6DhcpClientUserClassOptValueAscii OBJECT-TYPE
   SYNTAX      DisplayString
   MAX-ACCESS  read-write
   STATUS      current
   DESCRIPTION
      "Path: swPort.editConf.pppoEClient.ipV6.dhcp.client.userClassOpt.value.ascii"
   ::= {er1645v2EthPrtSwF2PppOEIpV6DhcpClientUserClassOptEntry 16842752}

er1645v2EthPrtSwF2PppOEIpV6DhcpClientUserClassOptValueDecimal OBJECT-TYPE
   SYNTAX      Integer32
   MAX-ACCESS  read-write
   STATUS      current
   DESCRIPTION
      "Path: swPort.editConf.pppoEClient.ipV6.dhcp.client.userClassOpt.value.decimal"
   ::= {er1645v2EthPrtSwF2PppOEIpV6DhcpClientUserClassOptEntry 16908288}

er1645v2EthPrtSwF2PppOEIpV6DhcpClientUserClassOptValueHexData OBJECT-TYPE
   SYNTAX      OCTET STRING
   MAX-ACCESS  read-write
   STATUS      current
   DESCRIPTION
      "Path: swPort.editConf.pppoEClient.ipV6.dhcp.client.userClassOpt.value.hexData"
   ::= {er1645v2EthPrtSwF2PppOEIpV6DhcpClientUserClassOptEntry 16973824}

er1645v2EthPrtSwF2PppOEIpV6DhcpClientVendorCl OBJECT-TYPE
   SYNTAX      SEQUENCE OF Er1645v2EthPrtSwF2PppOEIpV6DhcpClientVendorClEntry
   MAX-ACCESS  not-accessible
   STATUS      current
   DESCRIPTION
      ""
   ::= {er1645v2EthPrtSwF2PppOE 705313792}

er1645v2EthPrtSwF2PppOEIpV6DhcpClientVendorClEntry OBJECT-TYPE
   SYNTAX      Er1645v2EthPrtSwF2PppOEIpV6DhcpClientVendorClEntry
   MAX-ACCESS  not-accessible
   STATUS      current
   DESCRIPTION
      ""
   INDEX      { er1645v2EthPrtSwF2PppOEIpV6DhcpClientVendorClGlobalIx,
                er1645v2EthPrtSwF2PppOETableIx,
                er1645v2EthPrtSwF2PppOEIpV6DhcpClientVendorClTableIx }
   ::= {er1645v2EthPrtSwF2PppOEIpV6DhcpClientVendorCl 1}

Er1645v2EthPrtSwF2PppOEIpV6DhcpClientVendorClEntry ::=
   SEQUENCE
      {
      er1645v2EthPrtSwF2PppOEIpV6DhcpClientVendorClActions
         VariableLengthTableActions,
      er1645v2EthPrtSwF2PppOEIpV6DhcpClientVendorClGlobalIx
         GlobalIndex,
      er1645v2EthPrtSwF2PppOEIpV6DhcpClientVendorClTableIx
         TableIndex,
      er1645v2EthPrtSwF2PppOEIpV6DhcpClientVendorClValueAscii
         DisplayString,
      er1645v2EthPrtSwF2PppOEIpV6DhcpClientVendorClValueDecimal
         Integer32,
      er1645v2EthPrtSwF2PppOEIpV6DhcpClientVendorClValueHexData
         OCTET STRING
      }

er1645v2EthPrtSwF2PppOEIpV6DhcpClientVendorClActions OBJECT-TYPE
   SYNTAX      VariableLengthTableActions
   MAX-ACCESS  read-write
   STATUS      current
   DESCRIPTION
      "By way of this field, some manipulations
       on this table may be performed."
   ::= {er1645v2EthPrtSwF2PppOEIpV6DhcpClientVendorClEntry 2}

er1645v2EthPrtSwF2PppOEIpV6DhcpClientVendorClGlobalIx OBJECT-TYPE
   SYNTAX      GlobalIndex
   MAX-ACCESS  not-accessible
   STATUS      current
   DESCRIPTION
      "The value of the tlsCntTreeGlobalIndex of the MANAGED OBJECT."
   ::= {er1645v2EthPrtSwF2PppOEIpV6DhcpClientVendorClEntry 10}

er1645v2EthPrtSwF2PppOEIpV6DhcpClientVendorClTableIx OBJECT-TYPE
   SYNTAX      TableIndex
   MAX-ACCESS  not-accessible
   STATUS      current
   DESCRIPTION
      ""
   ::= {er1645v2EthPrtSwF2PppOEIpV6DhcpClientVendorClEntry 11}

er1645v2EthPrtSwF2PppOEIpV6DhcpClientVendorClValueAscii OBJECT-TYPE
   SYNTAX      DisplayString
   MAX-ACCESS  read-write
   STATUS      current
   DESCRIPTION
      "Path: swPort.editConf.pppoEClient.ipV6.dhcp.client.vendorClassOpt.value.ascii"
   ::= {er1645v2EthPrtSwF2PppOEIpV6DhcpClientVendorClEntry 16842752}

er1645v2EthPrtSwF2PppOEIpV6DhcpClientVendorClValueDecimal OBJECT-TYPE
   SYNTAX      Integer32
   MAX-ACCESS  read-write
   STATUS      current
   DESCRIPTION
      "Path: swPort.editConf.pppoEClient.ipV6.dhcp.client.vendorClassOpt.value.decimal"
   ::= {er1645v2EthPrtSwF2PppOEIpV6DhcpClientVendorClEntry 16908288}

er1645v2EthPrtSwF2PppOEIpV6DhcpClientVendorClValueHexData OBJECT-TYPE
   SYNTAX      OCTET STRING
   MAX-ACCESS  read-write
   STATUS      current
   DESCRIPTION
      "Path: swPort.editConf.pppoEClient.ipV6.dhcp.client.vendorClassOpt.value.hexData"
   ::= {er1645v2EthPrtSwF2PppOEIpV6DhcpClientVendorClEntry 16973824}

er1645v2EthPrtSwF2PppOEIpV6DhcpRelayDestinations OBJECT-TYPE
   SYNTAX      SEQUENCE OF Er1645v2EthPrtSwF2PppOEIpV6DhcpRelayDestinationsEntry
   MAX-ACCESS  not-accessible
   STATUS      current
   DESCRIPTION
      ""
   ::= {er1645v2EthPrtSwF2PppOE 705323072}

er1645v2EthPrtSwF2PppOEIpV6DhcpRelayDestinationsEntry OBJECT-TYPE
   SYNTAX      Er1645v2EthPrtSwF2PppOEIpV6DhcpRelayDestinationsEntry
   MAX-ACCESS  not-accessible
   STATUS      current
   DESCRIPTION
      ""
   INDEX      { er1645v2EthPrtSwF2PppOEIpV6DhcpRelayDestinationsGlobalIx,
                er1645v2EthPrtSwF2PppOETableIx,
                er1645v2EthPrtSwF2PppOEIpV6DhcpRelayDestinationsTableIx }
   ::= {er1645v2EthPrtSwF2PppOEIpV6DhcpRelayDestinations 1}

Er1645v2EthPrtSwF2PppOEIpV6DhcpRelayDestinationsEntry ::=
   SEQUENCE
      {
      er1645v2EthPrtSwF2PppOEIpV6DhcpRelayDestinationsActions
         VariableLengthTableActions,
      er1645v2EthPrtSwF2PppOEIpV6DhcpRelayDestinationsGlobalIx
         GlobalIndex,
      er1645v2EthPrtSwF2PppOEIpV6DhcpRelayDestinationsTableIx
         TableIndex,
      er1645v2EthPrtSwF2PppOEIpV6DhcpRelayDestinationsAddress
         Ipv6Address,
      er1645v2EthPrtSwF2PppOEIpV6DhcpRelayDestinationsInterface
         DisplayString
      }

er1645v2EthPrtSwF2PppOEIpV6DhcpRelayDestinationsActions OBJECT-TYPE
   SYNTAX      VariableLengthTableActions
   MAX-ACCESS  read-write
   STATUS      current
   DESCRIPTION
      "By way of this field, some manipulations
       on this table may be performed."
   ::= {er1645v2EthPrtSwF2PppOEIpV6DhcpRelayDestinationsEntry 2}

er1645v2EthPrtSwF2PppOEIpV6DhcpRelayDestinationsGlobalIx OBJECT-TYPE
   SYNTAX      GlobalIndex
   MAX-ACCESS  not-accessible
   STATUS      current
   DESCRIPTION
      "The value of the tlsCntTreeGlobalIndex of the MANAGED OBJECT."
   ::= {er1645v2EthPrtSwF2PppOEIpV6DhcpRelayDestinationsEntry 10}

er1645v2EthPrtSwF2PppOEIpV6DhcpRelayDestinationsTableIx OBJECT-TYPE
   SYNTAX      TableIndex
   MAX-ACCESS  not-accessible
   STATUS      current
   DESCRIPTION
      ""
   ::= {er1645v2EthPrtSwF2PppOEIpV6DhcpRelayDestinationsEntry 11}

er1645v2EthPrtSwF2PppOEIpV6DhcpRelayDestinationsAddress OBJECT-TYPE
   SYNTAX      Ipv6Address
   MAX-ACCESS  read-write
   STATUS      current
   DESCRIPTION
      "Path: swPort.editConf.pppoEClient.ipV6.dhcp.relay.destinations.address

       ipv6 address"
   ::= {er1645v2EthPrtSwF2PppOEIpV6DhcpRelayDestinationsEntry 16777216}

er1645v2EthPrtSwF2PppOEIpV6DhcpRelayDestinationsInterface OBJECT-TYPE
   SYNTAX      DisplayString
   MAX-ACCESS  read-write
   STATUS      current
   DESCRIPTION
      "Path: swPort.editConf.pppoEClient.ipV6.dhcp.relay.destinations.interface"
   ::= {er1645v2EthPrtSwF2PppOEIpV6DhcpRelayDestinationsEntry 33554432}


er1645v2EthPrtSwF2PppOES OBJECT IDENTIFIER ::= {er1645v2EthPrtSwF2 37}

er1645v2EthPrtSwF2PppOESTable OBJECT-TYPE
   SYNTAX      SEQUENCE OF Er1645v2EthPrtSwF2PppOESEntry
   MAX-ACCESS  not-accessible
   STATUS      current
   DESCRIPTION
      "ppp server name on interface"
   ::= {er1645v2EthPrtSwF2PppOES 1}

er1645v2EthPrtSwF2PppOESEntry OBJECT-TYPE
   SYNTAX      Er1645v2EthPrtSwF2PppOESEntry
   MAX-ACCESS  not-accessible
   STATUS      current
   DESCRIPTION
      ""
   INDEX      { er1645v2EthPrtSwF2PppOESGlobalIx }
   ::= {er1645v2EthPrtSwF2PppOESTable 1}

Er1645v2EthPrtSwF2PppOESEntry ::=
   SEQUENCE
      {
      er1645v2EthPrtSwF2PppOESGlobalIx
         GlobalIndex,
      er1645v2EthPrtSwF2PppOESValue
         DisplayString
      }

er1645v2EthPrtSwF2PppOESGlobalIx OBJECT-TYPE
   SYNTAX      GlobalIndex
   MAX-ACCESS  not-accessible
   STATUS      current
   DESCRIPTION
      "The value of the tlsCntTreeGlobalIndex of the MANAGED OBJECT."
   ::= {er1645v2EthPrtSwF2PppOESEntry 10}

er1645v2EthPrtSwF2PppOESValue OBJECT-TYPE
   SYNTAX      DisplayString
   MAX-ACCESS  read-write
   STATUS      current
   DESCRIPTION
      "Path: swPort.editConf.pppoEServer"
   ::= {er1645v2EthPrtSwF2PppOESEntry 2147483648}


er1645v2EthPrtSwF2AdminStatus OBJECT IDENTIFIER ::= {er1645v2EthPrtSwF2 106}

er1645v2EthPrtSwF2AdminStatusTable OBJECT-TYPE
   SYNTAX      SEQUENCE OF Er1645v2EthPrtSwF2AdminStatusEntry
   MAX-ACCESS  not-accessible
   STATUS      current
   DESCRIPTION
      "ifAdminStatus"
   ::= {er1645v2EthPrtSwF2AdminStatus 1}

er1645v2EthPrtSwF2AdminStatusEntry OBJECT-TYPE
   SYNTAX      Er1645v2EthPrtSwF2AdminStatusEntry
   MAX-ACCESS  not-accessible
   STATUS      current
   DESCRIPTION
      ""
   INDEX      { er1645v2EthPrtSwF2AdminStatusGlobalIx }
   ::= {er1645v2EthPrtSwF2AdminStatusTable 1}

Er1645v2EthPrtSwF2AdminStatusEntry ::=
   SEQUENCE
      {
      er1645v2EthPrtSwF2AdminStatusGlobalIx
         GlobalIndex,
      er1645v2EthPrtSwF2AdminStatusValue
         INTEGER
      }

er1645v2EthPrtSwF2AdminStatusGlobalIx OBJECT-TYPE
   SYNTAX      GlobalIndex
   MAX-ACCESS  not-accessible
   STATUS      current
   DESCRIPTION
      "The value of the tlsCntTreeGlobalIndex of the MANAGED OBJECT."
   ::= {er1645v2EthPrtSwF2AdminStatusEntry 10}

er1645v2EthPrtSwF2AdminStatusValue OBJECT-TYPE
   SYNTAX      INTEGER
               {
               up (1),
               down (2)
               }
   MAX-ACCESS  read-write
   STATUS      current
   DESCRIPTION
      "Path: swPort.editConf.adminStatus

       Possibilities:
               up   (1)
               down   (2)"
   ::= {er1645v2EthPrtSwF2AdminStatusEntry 2147483648}


er1645v2EthPrtSwF2AlarmMask OBJECT IDENTIFIER ::= {er1645v2EthPrtSwF2 135}

er1645v2EthPrtSwF2AlarmMaskTable OBJECT-TYPE
   SYNTAX      SEQUENCE OF Er1645v2EthPrtSwF2AlarmMaskEntry
   MAX-ACCESS  not-accessible
   STATUS      current
   DESCRIPTION
      "ifAlarmMask"
   ::= {er1645v2EthPrtSwF2AlarmMask 1}

er1645v2EthPrtSwF2AlarmMaskEntry OBJECT-TYPE
   SYNTAX      Er1645v2EthPrtSwF2AlarmMaskEntry
   MAX-ACCESS  not-accessible
   STATUS      current
   DESCRIPTION
      ""
   INDEX      { er1645v2EthPrtSwF2AlarmMaskGlobalIx }
   ::= {er1645v2EthPrtSwF2AlarmMaskTable 1}

Er1645v2EthPrtSwF2AlarmMaskEntry ::=
   SEQUENCE
      {
      er1645v2EthPrtSwF2AlarmMaskGlobalIx
         GlobalIndex,
      er1645v2EthPrtSwF2AlarmMaskValue
         Integer32
      }

er1645v2EthPrtSwF2AlarmMaskGlobalIx OBJECT-TYPE
   SYNTAX      GlobalIndex
   MAX-ACCESS  not-accessible
   STATUS      current
   DESCRIPTION
      "The value of the tlsCntTreeGlobalIndex of the MANAGED OBJECT."
   ::= {er1645v2EthPrtSwF2AlarmMaskEntry 10}

er1645v2EthPrtSwF2AlarmMaskValue OBJECT-TYPE
   SYNTAX      Integer32
   MAX-ACCESS  read-write
   STATUS      current
   DESCRIPTION
      "Path: swPort.editConf.alarmMask

       Bit meanings:
               bit 0 = linkDown,
               bit 9 = pppoEDown"
   ::= {er1645v2EthPrtSwF2AlarmMaskEntry 2147483648}


er1645v2EthPrtSwF2AlarmLev OBJECT IDENTIFIER ::= {er1645v2EthPrtSwF2 170}

er1645v2EthPrtSwF2AlarmLevSSCTable OBJECT-TYPE
   SYNTAX      SEQUENCE OF Er1645v2EthPrtSwF2AlarmLevEntry
   MAX-ACCESS  not-accessible
   STATUS      current
   DESCRIPTION
      "IfAlarmLevels"
   ::= {er1645v2EthPrtSwF2AlarmLev 1}

er1645v2EthPrtSwF2AlarmLevEntry OBJECT-TYPE
   SYNTAX      Er1645v2EthPrtSwF2AlarmLevEntry
   MAX-ACCESS  not-accessible
   STATUS      current
   DESCRIPTION
      ""
   INDEX      { er1645v2EthPrtSwF2AlarmLevGlobalIx }
   ::= {er1645v2EthPrtSwF2AlarmLevSSCTable 1}

Er1645v2EthPrtSwF2AlarmLevEntry ::=
   SEQUENCE
      {
      er1645v2EthPrtSwF2AlarmLevGlobalIx
         GlobalIndex,
      er1645v2EthPrtSwF2AlarmLevLinkDown
         Integer32,
      er1645v2EthPrtSwF2AlarmLevPppoEDown
         Integer32
      }

er1645v2EthPrtSwF2AlarmLevGlobalIx OBJECT-TYPE
   SYNTAX      GlobalIndex
   MAX-ACCESS  not-accessible
   STATUS      current
   DESCRIPTION
      "The value of the tlsCntTreeGlobalIndex of the MANAGED OBJECT."
   ::= {er1645v2EthPrtSwF2AlarmLevEntry 10}

er1645v2EthPrtSwF2AlarmLevLinkDown OBJECT-TYPE
   SYNTAX      Integer32
   MAX-ACCESS  read-write
   STATUS      current
   DESCRIPTION
      "Path: swPort.editConf.alarmLevel.linkDown"
   ::= {er1645v2EthPrtSwF2AlarmLevEntry 16777216}

er1645v2EthPrtSwF2AlarmLevPppoEDown OBJECT-TYPE
   SYNTAX      Integer32
   MAX-ACCESS  read-write
   STATUS      current
   DESCRIPTION
      "Path: swPort.editConf.alarmLevel.pppoEDown"
   ::= {er1645v2EthPrtSwF2AlarmLevEntry 167772160}


er1645v2EthPrtSwF2PriorityPolicy OBJECT IDENTIFIER ::= {er1645v2EthPrtSwF2 39}

er1645v2EthPrtSwF2PriorityPolicyTable OBJECT-TYPE
   SYNTAX      SEQUENCE OF Er1645v2EthPrtSwF2PriorityPolicyEntry
   MAX-ACCESS  not-accessible
   STATUS      current
   DESCRIPTION
      "Preferred Policy"
   ::= {er1645v2EthPrtSwF2PriorityPolicy 1}

er1645v2EthPrtSwF2PriorityPolicyEntry OBJECT-TYPE
   SYNTAX      Er1645v2EthPrtSwF2PriorityPolicyEntry
   MAX-ACCESS  not-accessible
   STATUS      current
   DESCRIPTION
      ""
   INDEX      { er1645v2EthPrtSwF2PriorityPolicyGlobalIx }
   ::= {er1645v2EthPrtSwF2PriorityPolicyTable 1}

Er1645v2EthPrtSwF2PriorityPolicyEntry ::=
   SEQUENCE
      {
      er1645v2EthPrtSwF2PriorityPolicyGlobalIx
         GlobalIndex,
      er1645v2EthPrtSwF2PriorityPolicyValue
         DisplayString
      }

er1645v2EthPrtSwF2PriorityPolicyGlobalIx OBJECT-TYPE
   SYNTAX      GlobalIndex
   MAX-ACCESS  not-accessible
   STATUS      current
   DESCRIPTION
      "The value of the tlsCntTreeGlobalIndex of the MANAGED OBJECT."
   ::= {er1645v2EthPrtSwF2PriorityPolicyEntry 10}

er1645v2EthPrtSwF2PriorityPolicyValue OBJECT-TYPE
   SYNTAX      DisplayString
   MAX-ACCESS  read-write
   STATUS      current
   DESCRIPTION
      "Path: swPort.editConf.priorityPolicy"
   ::= {er1645v2EthPrtSwF2PriorityPolicyEntry 2147483648}


er1645v2EthPrtSwF2Lst OBJECT IDENTIFIER ::= {er1645v2EthPrtSwF2 12}

er1645v2EthPrtSwF2LstSSCTable OBJECT-TYPE
   SYNTAX      SEQUENCE OF Er1645v2EthPrtSwF2LstEntry
   MAX-ACCESS  not-accessible
   STATUS      current
   DESCRIPTION
      ""
   ::= {er1645v2EthPrtSwF2Lst 1}

er1645v2EthPrtSwF2LstEntry OBJECT-TYPE
   SYNTAX      Er1645v2EthPrtSwF2LstEntry
   MAX-ACCESS  not-accessible
   STATUS      current
   DESCRIPTION
      ""
   INDEX      { er1645v2EthPrtSwF2LstGlobalIx }
   ::= {er1645v2EthPrtSwF2LstSSCTable 1}

Er1645v2EthPrtSwF2LstEntry ::=
   SEQUENCE
      {
      er1645v2EthPrtSwF2LstGlobalIx
         GlobalIndex,
      er1645v2EthPrtSwF2LstTrackedInterface
         DisplayString
      }

er1645v2EthPrtSwF2LstGlobalIx OBJECT-TYPE
   SYNTAX      GlobalIndex
   MAX-ACCESS  not-accessible
   STATUS      current
   DESCRIPTION
      "The value of the tlsCntTreeGlobalIndex of the MANAGED OBJECT."
   ::= {er1645v2EthPrtSwF2LstEntry 10}

er1645v2EthPrtSwF2LstTrackedInterface OBJECT-TYPE
   SYNTAX      DisplayString
   MAX-ACCESS  read-write
   STATUS      current
   DESCRIPTION
      "Path: swPort.editConf.linkStateTracking.trackedInterface"
   ::= {er1645v2EthPrtSwF2LstEntry 16777216}



sr1645v2EthPrtSwF2 OBJECT IDENTIFIER ::= {r1645v2EthPrtSwF2 14}


sr1645v2EthPrtSwF2Descr OBJECT IDENTIFIER ::= {sr1645v2EthPrtSwF2 101}

sr1645v2EthPrtSwF2DescrTable OBJECT-TYPE
   SYNTAX      SEQUENCE OF Sr1645v2EthPrtSwF2DescrEntry
   MAX-ACCESS  not-accessible
   STATUS      current
   DESCRIPTION
      "ifDescr"
   ::= {sr1645v2EthPrtSwF2Descr 1}

sr1645v2EthPrtSwF2DescrEntry OBJECT-TYPE
   SYNTAX      Sr1645v2EthPrtSwF2DescrEntry
   MAX-ACCESS  not-accessible
   STATUS      current
   DESCRIPTION
      ""
   INDEX      { sr1645v2EthPrtSwF2DescrGlobalIx }
   ::= {sr1645v2EthPrtSwF2DescrTable 1}

Sr1645v2EthPrtSwF2DescrEntry ::=
   SEQUENCE
      {
      sr1645v2EthPrtSwF2DescrGlobalIx
         GlobalIndex,
      sr1645v2EthPrtSwF2DescrValue
         DisplayString
      }

sr1645v2EthPrtSwF2DescrGlobalIx OBJECT-TYPE
   SYNTAX      GlobalIndex
   MAX-ACCESS  not-accessible
   STATUS      current
   DESCRIPTION
      "The value of the tlsCntTreeGlobalIndex of the MANAGED OBJECT."
   ::= {sr1645v2EthPrtSwF2DescrEntry 10}

sr1645v2EthPrtSwF2DescrValue OBJECT-TYPE
   SYNTAX      DisplayString
   MAX-ACCESS  read-only
   STATUS      current
   DESCRIPTION
      "Path: swPort.status.ifDescr"
   ::= {sr1645v2EthPrtSwF2DescrEntry 2147483648}


sr1645v2EthPrtSwF2Type OBJECT IDENTIFIER ::= {sr1645v2EthPrtSwF2 102}

sr1645v2EthPrtSwF2TypeTable OBJECT-TYPE
   SYNTAX      SEQUENCE OF Sr1645v2EthPrtSwF2TypeEntry
   MAX-ACCESS  not-accessible
   STATUS      current
   DESCRIPTION
      "ifType"
   ::= {sr1645v2EthPrtSwF2Type 1}

sr1645v2EthPrtSwF2TypeEntry OBJECT-TYPE
   SYNTAX      Sr1645v2EthPrtSwF2TypeEntry
   MAX-ACCESS  not-accessible
   STATUS      current
   DESCRIPTION
      ""
   INDEX      { sr1645v2EthPrtSwF2TypeGlobalIx }
   ::= {sr1645v2EthPrtSwF2TypeTable 1}

Sr1645v2EthPrtSwF2TypeEntry ::=
   SEQUENCE
      {
      sr1645v2EthPrtSwF2TypeGlobalIx
         GlobalIndex,
      sr1645v2EthPrtSwF2TypeValue
         INTEGER
      }

sr1645v2EthPrtSwF2TypeGlobalIx OBJECT-TYPE
   SYNTAX      GlobalIndex
   MAX-ACCESS  not-accessible
   STATUS      current
   DESCRIPTION
      "The value of the tlsCntTreeGlobalIndex of the MANAGED OBJECT."
   ::= {sr1645v2EthPrtSwF2TypeEntry 10}

sr1645v2EthPrtSwF2TypeValue OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: swPort.status.ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1645v2EthPrtSwF2TypeEntry 2147483648}


sr1645v2EthPrtSwF2Mtu OBJECT IDENTIFIER ::= {sr1645v2EthPrtSwF2 103}

sr1645v2EthPrtSwF2MtuTable OBJECT-TYPE
   SYNTAX      SEQUENCE OF Sr1645v2EthPrtSwF2MtuEntry
   MAX-ACCESS  not-accessible
   STATUS      current
   DESCRIPTION
      "ifMtu"
   ::= {sr1645v2EthPrtSwF2Mtu 1}

sr1645v2EthPrtSwF2MtuEntry OBJECT-TYPE
   SYNTAX      Sr1645v2EthPrtSwF2MtuEntry
   MAX-ACCESS  not-accessible
   STATUS      current
   DESCRIPTION
      ""
   INDEX      { sr1645v2EthPrtSwF2MtuGlobalIx }
   ::= {sr1645v2EthPrtSwF2MtuTable 1}

Sr1645v2EthPrtSwF2MtuEntry ::=
   SEQUENCE
      {
      sr1645v2EthPrtSwF2MtuGlobalIx
         GlobalIndex,
      sr1645v2EthPrtSwF2MtuValue
         Integer32
      }

sr1645v2EthPrtSwF2MtuGlobalIx OBJECT-TYPE
   SYNTAX      GlobalIndex
   MAX-ACCESS  not-accessible
   STATUS      current
   DESCRIPTION
      "The value of the tlsCntTreeGlobalIndex of the MANAGED OBJECT."
   ::= {sr1645v2EthPrtSwF2MtuEntry 10}

sr1645v2EthPrtSwF2MtuValue OBJECT-TYPE
   SYNTAX      Integer32
   MAX-ACCESS  read-only
   STATUS      current
   DESCRIPTION
      "Path: swPort.status.ifMtu"
   ::= {sr1645v2EthPrtSwF2MtuEntry 2147483648}


sr1645v2EthPrtSwF2OperStatus OBJECT IDENTIFIER ::= {sr1645v2EthPrtSwF2 107}

sr1645v2EthPrtSwF2OperStatusTable OBJECT-TYPE
   SYNTAX      SEQUENCE OF Sr1645v2EthPrtSwF2OperStatusEntry
   MAX-ACCESS  not-accessible
   STATUS      current
   DESCRIPTION
      "ifOperStatus"
   ::= {sr1645v2EthPrtSwF2OperStatus 1}

sr1645v2EthPrtSwF2OperStatusEntry OBJECT-TYPE
   SYNTAX      Sr1645v2EthPrtSwF2OperStatusEntry
   MAX-ACCESS  not-accessible
   STATUS      current
   DESCRIPTION
      ""
   INDEX      { sr1645v2EthPrtSwF2OperStatusGlobalIx }
   ::= {sr1645v2EthPrtSwF2OperStatusTable 1}

Sr1645v2EthPrtSwF2OperStatusEntry ::=
   SEQUENCE
      {
      sr1645v2EthPrtSwF2OperStatusGlobalIx
         GlobalIndex,
      sr1645v2EthPrtSwF2OperStatusValue
         INTEGER
      }

sr1645v2EthPrtSwF2OperStatusGlobalIx OBJECT-TYPE
   SYNTAX      GlobalIndex
   MAX-ACCESS  not-accessible
   STATUS      current
   DESCRIPTION
      "The value of the tlsCntTreeGlobalIndex of the MANAGED OBJECT."
   ::= {sr1645v2EthPrtSwF2OperStatusEntry 10}

sr1645v2EthPrtSwF2OperStatusValue OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: swPort.status.ifOperStatus

       Possibilities:
               up   (1)
               down   (2)
               testing   (3)
               unknown   (4)
               dormant   (5)
               notPresent   (6)
               lowerLayerDown   (7)"
   ::= {sr1645v2EthPrtSwF2OperStatusEntry 2147483648}


sr1645v2EthPrtSwF2LastChange OBJECT IDENTIFIER ::= {sr1645v2EthPrtSwF2 108}

sr1645v2EthPrtSwF2LastChangeTable OBJECT-TYPE
   SYNTAX      SEQUENCE OF Sr1645v2EthPrtSwF2LastChangeEntry
   MAX-ACCESS  not-accessible
   STATUS      current
   DESCRIPTION
      "ifLastChange"
   ::= {sr1645v2EthPrtSwF2LastChange 1}

sr1645v2EthPrtSwF2LastChangeEntry OBJECT-TYPE
   SYNTAX      Sr1645v2EthPrtSwF2LastChangeEntry
   MAX-ACCESS  not-accessible
   STATUS      current
   DESCRIPTION
      ""
   INDEX      { sr1645v2EthPrtSwF2LastChangeGlobalIx }
   ::= {sr1645v2EthPrtSwF2LastChangeTable 1}

Sr1645v2EthPrtSwF2LastChangeEntry ::=
   SEQUENCE
      {
      sr1645v2EthPrtSwF2LastChangeGlobalIx
         GlobalIndex,
      sr1645v2EthPrtSwF2LastChangeValue
         TimeTicks
      }

sr1645v2EthPrtSwF2LastChangeGlobalIx OBJECT-TYPE
   SYNTAX      GlobalIndex
   MAX-ACCESS  not-accessible
   STATUS      current
   DESCRIPTION
      "The value of the tlsCntTreeGlobalIndex of the MANAGED OBJECT."
   ::= {sr1645v2EthPrtSwF2LastChangeEntry 10}

sr1645v2EthPrtSwF2LastChangeValue OBJECT-TYPE
   SYNTAX      TimeTicks
   MAX-ACCESS  read-only
   STATUS      current
   DESCRIPTION
      "Path: swPort.status.ifLastChange

       Time in centi-second."
   ::= {sr1645v2EthPrtSwF2LastChangeEntry 2147483648}


sr1645v2EthPrtSwF2LastChangeD OBJECT IDENTIFIER ::= {sr1645v2EthPrtSwF2 183}

sr1645v2EthPrtSwF2LastChangeDTable OBJECT-TYPE
   SYNTAX      SEQUENCE OF Sr1645v2EthPrtSwF2LastChangeDEntry
   MAX-ACCESS  not-accessible
   STATUS      current
   DESCRIPTION
      "ifLastChangeDate"
   ::= {sr1645v2EthPrtSwF2LastChangeD 1}

sr1645v2EthPrtSwF2LastChangeDEntry OBJECT-TYPE
   SYNTAX      Sr1645v2EthPrtSwF2LastChangeDEntry
   MAX-ACCESS  not-accessible
   STATUS      current
   DESCRIPTION
      ""
   INDEX      { sr1645v2EthPrtSwF2LastChangeDGlobalIx }
   ::= {sr1645v2EthPrtSwF2LastChangeDTable 1}

Sr1645v2EthPrtSwF2LastChangeDEntry ::=
   SEQUENCE
      {
      sr1645v2EthPrtSwF2LastChangeDGlobalIx
         GlobalIndex,
      sr1645v2EthPrtSwF2LastChangeDValue
         DisplayString
      }

sr1645v2EthPrtSwF2LastChangeDGlobalIx OBJECT-TYPE
   SYNTAX      GlobalIndex
   MAX-ACCESS  not-accessible
   STATUS      current
   DESCRIPTION
      "The value of the tlsCntTreeGlobalIndex of the MANAGED OBJECT."
   ::= {sr1645v2EthPrtSwF2LastChangeDEntry 10}

sr1645v2EthPrtSwF2LastChangeDValue OBJECT-TYPE
   SYNTAX      DisplayString
   MAX-ACCESS  read-only
   STATUS      current
   DESCRIPTION
      "Path: swPort.status.ifLastChangeDate"
   ::= {sr1645v2EthPrtSwF2LastChangeDEntry 2147483648}


sr1645v2EthPrtSwF2Speed OBJECT IDENTIFIER ::= {sr1645v2EthPrtSwF2 104}

sr1645v2EthPrtSwF2SpeedTable OBJECT-TYPE
   SYNTAX      SEQUENCE OF Sr1645v2EthPrtSwF2SpeedEntry
   MAX-ACCESS  not-accessible
   STATUS      current
   DESCRIPTION
      "ifSpeed"
   ::= {sr1645v2EthPrtSwF2Speed 1}

sr1645v2EthPrtSwF2SpeedEntry OBJECT-TYPE
   SYNTAX      Sr1645v2EthPrtSwF2SpeedEntry
   MAX-ACCESS  not-accessible
   STATUS      current
   DESCRIPTION
      ""
   INDEX      { sr1645v2EthPrtSwF2SpeedGlobalIx }
   ::= {sr1645v2EthPrtSwF2SpeedTable 1}

Sr1645v2EthPrtSwF2SpeedEntry ::=
   SEQUENCE
      {
      sr1645v2EthPrtSwF2SpeedGlobalIx
         GlobalIndex,
      sr1645v2EthPrtSwF2SpeedValue
         Gauge32
      }

sr1645v2EthPrtSwF2SpeedGlobalIx OBJECT-TYPE
   SYNTAX      GlobalIndex
   MAX-ACCESS  not-accessible
   STATUS      current
   DESCRIPTION
      "The value of the tlsCntTreeGlobalIndex of the MANAGED OBJECT."
   ::= {sr1645v2EthPrtSwF2SpeedEntry 10}

sr1645v2EthPrtSwF2SpeedValue OBJECT-TYPE
   SYNTAX      Gauge32
   MAX-ACCESS  read-only
   STATUS      current
   DESCRIPTION
      "Path: swPort.status.ifSpeed

       32 bit unsigned gauge value."
   ::= {sr1645v2EthPrtSwF2SpeedEntry 2147483648}


sr1645v2EthPrtSwF2Ip OBJECT IDENTIFIER ::= {sr1645v2EthPrtSwF2 16}

sr1645v2EthPrtSwF2IpSSCTable OBJECT-TYPE
   SYNTAX      SEQUENCE OF Sr1645v2EthPrtSwF2IpEntry
   MAX-ACCESS  not-accessible
   STATUS      current
   DESCRIPTION
      "ip interface status parameters"
   ::= {sr1645v2EthPrtSwF2Ip 1}

sr1645v2EthPrtSwF2IpEntry OBJECT-TYPE
   SYNTAX      Sr1645v2EthPrtSwF2IpEntry
   MAX-ACCESS  not-accessible
   STATUS      current
   DESCRIPTION
      ""
   INDEX      { sr1645v2EthPrtSwF2IpGlobalIx }
   ::= {sr1645v2EthPrtSwF2IpSSCTable 1}

Sr1645v2EthPrtSwF2IpEntry ::=
   SEQUENCE
      {
      sr1645v2EthPrtSwF2IpGlobalIx
         GlobalIndex,
      sr1645v2EthPrtSwF2IpStatus
         INTEGER,
      sr1645v2EthPrtSwF2IpAddress
         IpAddress,
      sr1645v2EthPrtSwF2IpNetMask
         IpAddress,
      sr1645v2EthPrtSwF2IpDhcpStatus
         INTEGER,
      sr1645v2EthPrtSwF2IpDhcpLeaseTime
         TimeTicks
      }

sr1645v2EthPrtSwF2IpGlobalIx OBJECT-TYPE
   SYNTAX      GlobalIndex
   MAX-ACCESS  not-accessible
   STATUS      current
   DESCRIPTION
      "The value of the tlsCntTreeGlobalIndex of the MANAGED OBJECT."
   ::= {sr1645v2EthPrtSwF2IpEntry 10}

sr1645v2EthPrtSwF2IpStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: swPort.status.ip.status

       Possibilities:
               up   (1)
               down   (2)
               testing   (3)
               unknown   (4)
               dormant   (5)
               notPresent   (6)
               lowerLayerDown   (7)"
   ::= {sr1645v2EthPrtSwF2IpEntry 1795162112}

sr1645v2EthPrtSwF2IpAddress OBJECT-TYPE
   SYNTAX      IpAddress
   MAX-ACCESS  read-only
   STATUS      current
   DESCRIPTION
      "Path: swPort.status.ip.address"
   ::= {sr1645v2EthPrtSwF2IpEntry 2030043136}

sr1645v2EthPrtSwF2IpNetMask OBJECT-TYPE
   SYNTAX      IpAddress
   MAX-ACCESS  read-only
   STATUS      current
   DESCRIPTION
      "Path: swPort.status.ip.netMask"
   ::= {sr1645v2EthPrtSwF2IpEntry 2063597568}

sr1645v2EthPrtSwF2IpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: swPort.status.ip.dhcp.status

       Possibilities:
               none   (0)
               selecting   (1)
               requesting   (2)
               rebinding   (3)
               bound   (4)
               renewing   (5)
               rebooting   (6)
               initreboot   (7)"
   ::= {sr1645v2EthPrtSwF2IpEntry 402718720}

sr1645v2EthPrtSwF2IpDhcpLeaseTime OBJECT-TYPE
   SYNTAX      TimeTicks
   MAX-ACCESS  read-only
   STATUS      current
   DESCRIPTION
      "Path: swPort.status.ip.dhcp.leaseTime

       Time in centi-second."
   ::= {sr1645v2EthPrtSwF2IpEntry 402784256}

sr1645v2EthPrtSwF2IpSecondaryIp OBJECT-TYPE
   SYNTAX      SEQUENCE OF Sr1645v2EthPrtSwF2IpSecondaryIpEntry
   MAX-ACCESS  not-accessible
   STATUS      current
   DESCRIPTION
      ""
   ::= {sr1645v2EthPrtSwF2Ip 385875968}

sr1645v2EthPrtSwF2IpSecondaryIpEntry OBJECT-TYPE
   SYNTAX      Sr1645v2EthPrtSwF2IpSecondaryIpEntry
   MAX-ACCESS  not-accessible
   STATUS      current
   DESCRIPTION
      ""
   INDEX      { sr1645v2EthPrtSwF2IpSecondaryIpGlobalIx,
                sr1645v2EthPrtSwF2IpSecondaryIpTableIx }
   ::= {sr1645v2EthPrtSwF2IpSecondaryIp 1}

Sr1645v2EthPrtSwF2IpSecondaryIpEntry ::=
   SEQUENCE
      {
      sr1645v2EthPrtSwF2IpSecondaryIpGlobalIx
         GlobalIndex,
      sr1645v2EthPrtSwF2IpSecondaryIpTableIx
         TableIndex,
      sr1645v2EthPrtSwF2IpSecondaryIpAddress
         IpAddress,
      sr1645v2EthPrtSwF2IpSecondaryIpNetMask
         IpAddress
      }

sr1645v2EthPrtSwF2IpSecondaryIpGlobalIx OBJECT-TYPE
   SYNTAX      GlobalIndex
   MAX-ACCESS  not-accessible
   STATUS      current
   DESCRIPTION
      "The value of the tlsCntTreeGlobalIndex of the MANAGED OBJECT."
   ::= {sr1645v2EthPrtSwF2IpSecondaryIpEntry 10}

sr1645v2EthPrtSwF2IpSecondaryIpTableIx OBJECT-TYPE
   SYNTAX      TableIndex
   MAX-ACCESS  not-accessible
   STATUS      current
   DESCRIPTION
      ""
   ::= {sr1645v2EthPrtSwF2IpSecondaryIpEntry 11}

sr1645v2EthPrtSwF2IpSecondaryIpAddress OBJECT-TYPE
   SYNTAX      IpAddress
   MAX-ACCESS  read-only
   STATUS      current
   DESCRIPTION
      "Path: swPort.status.ip.secondaryIp.address"
   ::= {sr1645v2EthPrtSwF2IpSecondaryIpEntry 2030043136}

sr1645v2EthPrtSwF2IpSecondaryIpNetMask OBJECT-TYPE
   SYNTAX      IpAddress
   MAX-ACCESS  read-only
   STATUS      current
   DESCRIPTION
      "Path: swPort.status.ip.secondaryIp.netMask"
   ::= {sr1645v2EthPrtSwF2IpSecondaryIpEntry 2063597568}


sr1645v2EthPrtSwF2ArpCache OBJECT IDENTIFIER ::= {sr1645v2EthPrtSwF2 11}

sr1645v2EthPrtSwF2ArpCacheSSCTable OBJECT-TYPE
   SYNTAX      SEQUENCE OF Sr1645v2EthPrtSwF2ArpCacheEntry
   MAX-ACCESS  not-accessible
   STATUS      current
   DESCRIPTION
      "arp cache of ethernet interface"
   ::= {sr1645v2EthPrtSwF2ArpCache 1}

sr1645v2EthPrtSwF2ArpCacheEntry OBJECT-TYPE
   SYNTAX      Sr1645v2EthPrtSwF2ArpCacheEntry
   MAX-ACCESS  not-accessible
   STATUS      current
   DESCRIPTION
      ""
   INDEX      { sr1645v2EthPrtSwF2ArpCacheGlobalIx,
                sr1645v2EthPrtSwF2ArpCacheTableIx }
   ::= {sr1645v2EthPrtSwF2ArpCacheSSCTable 1}

Sr1645v2EthPrtSwF2ArpCacheEntry ::=
   SEQUENCE
      {
      sr1645v2EthPrtSwF2ArpCacheGlobalIx
         GlobalIndex,
      sr1645v2EthPrtSwF2ArpCacheTableIx
         TableIndex,
      sr1645v2EthPrtSwF2ArpCacheMacAddress
         OCTET STRING,
      sr1645v2EthPrtSwF2ArpCacheIpAddress
         IpAddress,
      sr1645v2EthPrtSwF2ArpCacheType
         INTEGER,
      sr1645v2EthPrtSwF2ArpCacheTimeOut
         TimeTicks
      }

sr1645v2EthPrtSwF2ArpCacheGlobalIx OBJECT-TYPE
   SYNTAX      GlobalIndex
   MAX-ACCESS  not-accessible
   STATUS      current
   DESCRIPTION
      "The value of the tlsCntTreeGlobalIndex of the MANAGED OBJECT."
   ::= {sr1645v2EthPrtSwF2ArpCacheEntry 10}

sr1645v2EthPrtSwF2ArpCacheTableIx OBJECT-TYPE
   SYNTAX      TableIndex
   MAX-ACCESS  not-accessible
   STATUS      current
   DESCRIPTION
      ""
   ::= {sr1645v2EthPrtSwF2ArpCacheEntry 11}

sr1645v2EthPrtSwF2ArpCacheMacAddress OBJECT-TYPE
   SYNTAX      OCTET STRING
   MAX-ACCESS  read-only
   STATUS      current
   DESCRIPTION
      "Path: swPort.status.arpCache.macAddress

       MAC address."
   ::= {sr1645v2EthPrtSwF2ArpCacheEntry 16777216}

sr1645v2EthPrtSwF2ArpCacheIpAddress OBJECT-TYPE
   SYNTAX      IpAddress
   MAX-ACCESS  read-only
   STATUS      current
   DESCRIPTION
      "Path: swPort.status.arpCache.ipAddress"
   ::= {sr1645v2EthPrtSwF2ArpCacheEntry 33554432}

sr1645v2EthPrtSwF2ArpCacheType OBJECT-TYPE
   SYNTAX      INTEGER
               {
               static (0),
               dynamic (1)
               }
   MAX-ACCESS  read-only
   STATUS      current
   DESCRIPTION
      "Path: swPort.status.arpCache.type

       Possibilities:
               static   (0)
               dynamic   (1)"
   ::= {sr1645v2EthPrtSwF2ArpCacheEntry 50331648}

sr1645v2EthPrtSwF2ArpCacheTimeOut OBJECT-TYPE
   SYNTAX      TimeTicks
   MAX-ACCESS  read-only
   STATUS      current
   DESCRIPTION
      "Path: swPort.status.arpCache.timeOut

       Time in centi-second."
   ::= {sr1645v2EthPrtSwF2ArpCacheEntry 67108864}


sr1645v2EthPrtSwF2BrS OBJECT IDENTIFIER ::= {sr1645v2EthPrtSwF2 28}

sr1645v2EthPrtSwF2BrSSSCTable OBJECT-TYPE
   SYNTAX      SEQUENCE OF Sr1645v2EthPrtSwF2BrSEntry
   MAX-ACCESS  not-accessible
   STATUS      current
   DESCRIPTION
      "spanning tree status ethernet interface"
   ::= {sr1645v2EthPrtSwF2BrS 1}

sr1645v2EthPrtSwF2BrSEntry OBJECT-TYPE
   SYNTAX      Sr1645v2EthPrtSwF2BrSEntry
   MAX-ACCESS  not-accessible
   STATUS      current
   DESCRIPTION
      ""
   INDEX      { sr1645v2EthPrtSwF2BrSGlobalIx }
   ::= {sr1645v2EthPrtSwF2BrSSSCTable 1}

Sr1645v2EthPrtSwF2BrSEntry ::=
   SEQUENCE
      {
      sr1645v2EthPrtSwF2BrSGlobalIx
         GlobalIndex,
      sr1645v2EthPrtSwF2BrSStatus
         INTEGER,
      sr1645v2EthPrtSwF2BrSStPortRole
         INTEGER,
      sr1645v2EthPrtSwF2BrSStPortId
         Integer32,
      sr1645v2EthPrtSwF2BrSStPpCostExtPathCost
         Integer32,
      sr1645v2EthPrtSwF2BrSStPpCostIntPathCost
         Integer32,
      sr1645v2EthPrtSwF2BrSStExtRpCost
         Integer32,
      sr1645v2EthPrtSwF2BrSStIntRpCost
         Integer32,
      sr1645v2EthPrtSwF2BrSStDesBrIdPriority
         Integer32,
      sr1645v2EthPrtSwF2BrSStDesBrIdMacAddress
         OCTET STRING,
      sr1645v2EthPrtSwF2BrSStDesPrtId
         Integer32,
      sr1645v2EthPrtSwF2BrSStDesInt
         INTEGER,
      sr1645v2EthPrtSwF2BrSStEdgeDetection
         INTEGER
      }

sr1645v2EthPrtSwF2BrSGlobalIx OBJECT-TYPE
   SYNTAX      GlobalIndex
   MAX-ACCESS  not-accessible
   STATUS      current
   DESCRIPTION
      "The value of the tlsCntTreeGlobalIndex of the MANAGED OBJECT."
   ::= {sr1645v2EthPrtSwF2BrSEntry 10}

sr1645v2EthPrtSwF2BrSStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: swPort.status.bridging.status

       Possibilities:
               disabled   (0)
               discarding   (1)
               learning   (2)
               forwarding   (3)
               backupBlockedIntfDown   (256)
               backupBlockedIntfUp   (259)
               shutdown   (255)"
   ::= {sr1645v2EthPrtSwF2BrSEntry 16777216}

sr1645v2EthPrtSwF2BrSStPortRole OBJECT-TYPE
   SYNTAX      INTEGER
               {
               none (0),
               root (1),
               designated (2),
               alternate (3),
               backup (4),
               disabled (5),
               master (6)
               }
   MAX-ACCESS  read-only
   STATUS      current
   DESCRIPTION
      "Path: swPort.status.bridging.spanningTree.portRole

       Possibilities:
               none   (0)
               root   (1)
               designated   (2)
               alternate   (3)
               backup   (4)
               disabled   (5)
               master   (6)"
   ::= {sr1645v2EthPrtSwF2BrSEntry 33619968}

sr1645v2EthPrtSwF2BrSStPortId OBJECT-TYPE
   SYNTAX      Integer32
   MAX-ACCESS  read-only
   STATUS      current
   DESCRIPTION
      "Path: swPort.status.bridging.spanningTree.portId"
   ::= {sr1645v2EthPrtSwF2BrSEntry 33685504}

sr1645v2EthPrtSwF2BrSStPpCostExtPathCost OBJECT-TYPE
   SYNTAX      Integer32
   MAX-ACCESS  read-only
   STATUS      current
   DESCRIPTION
      "Path: swPort.status.bridging.spanningTree.portPathCosts.extPathCost"
   ::= {sr1645v2EthPrtSwF2BrSEntry 33751296}

sr1645v2EthPrtSwF2BrSStPpCostIntPathCost OBJECT-TYPE
   SYNTAX      Integer32
   MAX-ACCESS  read-only
   STATUS      current
   DESCRIPTION
      "Path: swPort.status.bridging.spanningTree.portPathCosts.intPathCost"
   ::= {sr1645v2EthPrtSwF2BrSEntry 33751552}

sr1645v2EthPrtSwF2BrSStExtRpCost OBJECT-TYPE
   SYNTAX      Integer32
   MAX-ACCESS  read-only
   STATUS      current
   DESCRIPTION
      "Path: swPort.status.bridging.spanningTree.extRootPathCost"
   ::= {sr1645v2EthPrtSwF2BrSEntry 33816576}

sr1645v2EthPrtSwF2BrSStIntRpCost OBJECT-TYPE
   SYNTAX      Integer32
   MAX-ACCESS  read-only
   STATUS      current
   DESCRIPTION
      "Path: swPort.status.bridging.spanningTree.intRootPathCost"
   ::= {sr1645v2EthPrtSwF2BrSEntry 33882112}

sr1645v2EthPrtSwF2BrSStDesBrIdPriority OBJECT-TYPE
   SYNTAX      Integer32
   MAX-ACCESS  read-only
   STATUS      current
   DESCRIPTION
      "Path: swPort.status.bridging.spanningTree.designatedBridgeId.priority"
   ::= {sr1645v2EthPrtSwF2BrSEntry 33947904}

sr1645v2EthPrtSwF2BrSStDesBrIdMacAddress OBJECT-TYPE
   SYNTAX      OCTET STRING
   MAX-ACCESS  read-only
   STATUS      current
   DESCRIPTION
      "Path: swPort.status.bridging.spanningTree.designatedBridgeId.macAddress

       MAC address."
   ::= {sr1645v2EthPrtSwF2BrSEntry 33948160}

sr1645v2EthPrtSwF2BrSStDesPrtId OBJECT-TYPE
   SYNTAX      Integer32
   MAX-ACCESS  read-only
   STATUS      current
   DESCRIPTION
      "Path: swPort.status.bridging.spanningTree.designatedPortId"
   ::= {sr1645v2EthPrtSwF2BrSEntry 34013184}

sr1645v2EthPrtSwF2BrSStDesInt OBJECT-TYPE
   SYNTAX      INTEGER
               {
               no (0),
               yes (1)
               }
   MAX-ACCESS  read-only
   STATUS      current
   DESCRIPTION
      "Path: swPort.status.bridging.spanningTree.designatedOrInternal

       Possibilities:
               no   (0)
               yes   (1)"
   ::= {sr1645v2EthPrtSwF2BrSEntry 34078720}

sr1645v2EthPrtSwF2BrSStEdgeDetection OBJECT-TYPE
   SYNTAX      INTEGER
               {
               none (0),
               edge (1),
               notEdge (2)
               }
   MAX-ACCESS  read-only
   STATUS      current
   DESCRIPTION
      "Path: swPort.status.bridging.spanningTree.edgeDetection

       Possibilities:
               none   (0)
               edge   (1)
               notEdge   (2)"
   ::= {sr1645v2EthPrtSwF2BrSEntry 34144256}


sr1645v2EthPrtSwF2MacAddress OBJECT IDENTIFIER ::= {sr1645v2EthPrtSwF2 105}

sr1645v2EthPrtSwF2MacAddressTable OBJECT-TYPE
   SYNTAX      SEQUENCE OF Sr1645v2EthPrtSwF2MacAddressEntry
   MAX-ACCESS  not-accessible
   STATUS      current
   DESCRIPTION
      "ifPhysAddress"
   ::= {sr1645v2EthPrtSwF2MacAddress 1}

sr1645v2EthPrtSwF2MacAddressEntry OBJECT-TYPE
   SYNTAX      Sr1645v2EthPrtSwF2MacAddressEntry
   MAX-ACCESS  not-accessible
   STATUS      current
   DESCRIPTION
      ""
   INDEX      { sr1645v2EthPrtSwF2MacAddressGlobalIx }
   ::= {sr1645v2EthPrtSwF2MacAddressTable 1}

Sr1645v2EthPrtSwF2MacAddressEntry ::=
   SEQUENCE
      {
      sr1645v2EthPrtSwF2MacAddressGlobalIx
         GlobalIndex,
      sr1645v2EthPrtSwF2MacAddressValue
         OCTET STRING
      }

sr1645v2EthPrtSwF2MacAddressGlobalIx OBJECT-TYPE
   SYNTAX      GlobalIndex
   MAX-ACCESS  not-accessible
   STATUS      current
   DESCRIPTION
      "The value of the tlsCntTreeGlobalIndex of the MANAGED OBJECT."
   ::= {sr1645v2EthPrtSwF2MacAddressEntry 10}

sr1645v2EthPrtSwF2MacAddressValue OBJECT-TYPE
   SYNTAX      OCTET STRING
   MAX-ACCESS  read-only
   STATUS      current
   DESCRIPTION
      "Path: swPort.status.macAddress

       MAC address."
   ::= {sr1645v2EthPrtSwF2MacAddressEntry 2147483648}


sr1645v2EthPrtSwF2IpAdEntBcastAddr OBJECT IDENTIFIER ::= {sr1645v2EthPrtSwF2 124}

sr1645v2EthPrtSwF2IpAdEntBcastAddrTable OBJECT-TYPE
   SYNTAX      SEQUENCE OF Sr1645v2EthPrtSwF2IpAdEntBcastAddrEntry
   MAX-ACCESS  not-accessible
   STATUS      current
   DESCRIPTION
      "ipAdEntBcastAddr"
   ::= {sr1645v2EthPrtSwF2IpAdEntBcastAddr 1}

sr1645v2EthPrtSwF2IpAdEntBcastAddrEntry OBJECT-TYPE
   SYNTAX      Sr1645v2EthPrtSwF2IpAdEntBcastAddrEntry
   MAX-ACCESS  not-accessible
   STATUS      current
   DESCRIPTION
      ""
   INDEX      { sr1645v2EthPrtSwF2IpAdEntBcastAddrGlobalIx }
   ::= {sr1645v2EthPrtSwF2IpAdEntBcastAddrTable 1}

Sr1645v2EthPrtSwF2IpAdEntBcastAddrEntry ::=
   SEQUENCE
      {
      sr1645v2EthPrtSwF2IpAdEntBcastAddrGlobalIx
         GlobalIndex,
      sr1645v2EthPrtSwF2IpAdEntBcastAddrValue
         Integer32
      }

sr1645v2EthPrtSwF2IpAdEntBcastAddrGlobalIx OBJECT-TYPE
   SYNTAX      GlobalIndex
   MAX-ACCESS  not-accessible
   STATUS      current
   DESCRIPTION
      "The value of the tlsCntTreeGlobalIndex of the MANAGED OBJECT."
   ::= {sr1645v2EthPrtSwF2IpAdEntBcastAddrEntry 10}

sr1645v2EthPrtSwF2IpAdEntBcastAddrValue OBJECT-TYPE
   SYNTAX      Integer32
   MAX-ACCESS  read-only
   STATUS      current
   DESCRIPTION
      "Path: swPort.status.ipAdEntBcastAddr"
   ::= {sr1645v2EthPrtSwF2IpAdEntBcastAddrEntry 2147483648}


sr1645v2EthPrtSwF2IpAdEntReasmMaxSize OBJECT IDENTIFIER ::= {sr1645v2EthPrtSwF2 125}

sr1645v2EthPrtSwF2IpAdEntReasmMaxSizeTable OBJECT-TYPE
   SYNTAX      SEQUENCE OF Sr1645v2EthPrtSwF2IpAdEntReasmMaxSizeEntry
   MAX-ACCESS  not-accessible
   STATUS      current
   DESCRIPTION
      "ipAdEntReasmMaxSize"
   ::= {sr1645v2EthPrtSwF2IpAdEntReasmMaxSize 1}

sr1645v2EthPrtSwF2IpAdEntReasmMaxSizeEntry OBJECT-TYPE
   SYNTAX      Sr1645v2EthPrtSwF2IpAdEntReasmMaxSizeEntry
   MAX-ACCESS  not-accessible
   STATUS      current
   DESCRIPTION
      ""
   INDEX      { sr1645v2EthPrtSwF2IpAdEntReasmMaxSizeGlobalIx }
   ::= {sr1645v2EthPrtSwF2IpAdEntReasmMaxSizeTable 1}

Sr1645v2EthPrtSwF2IpAdEntReasmMaxSizeEntry ::=
   SEQUENCE
      {
      sr1645v2EthPrtSwF2IpAdEntReasmMaxSizeGlobalIx
         GlobalIndex,
      sr1645v2EthPrtSwF2IpAdEntReasmMaxSizeValue
         Integer32
      }

sr1645v2EthPrtSwF2IpAdEntReasmMaxSizeGlobalIx OBJECT-TYPE
   SYNTAX      GlobalIndex
   MAX-ACCESS  not-accessible
   STATUS      current
   DESCRIPTION
      "The value of the tlsCntTreeGlobalIndex of the MANAGED OBJECT."
   ::= {sr1645v2EthPrtSwF2IpAdEntReasmMaxSizeEntry 10}

sr1645v2EthPrtSwF2IpAdEntReasmMaxSizeValue OBJECT-TYPE
   SYNTAX      Integer32
   MAX-ACCESS  read-only
   STATUS      current
   DESCRIPTION
      "Path: swPort.status.ipAdEntReasmMaxSize"
   ::= {sr1645v2EthPrtSwF2IpAdEntReasmMaxSizeEntry 2147483648}


sr1645v2EthPrtSwF2Oam OBJECT IDENTIFIER ::= {sr1645v2EthPrtSwF2 901}

sr1645v2EthPrtSwF2OamSSCTable OBJECT-TYPE
   SYNTAX      SEQUENCE OF Sr1645v2EthPrtSwF2OamEntry
   MAX-ACCESS  not-accessible
   STATUS      current
   DESCRIPTION
      "OAM discovery state"
   ::= {sr1645v2EthPrtSwF2Oam 1}

sr1645v2EthPrtSwF2OamEntry OBJECT-TYPE
   SYNTAX      Sr1645v2EthPrtSwF2OamEntry
   MAX-ACCESS  not-accessible
   STATUS      current
   DESCRIPTION
      ""
   INDEX      { sr1645v2EthPrtSwF2OamGlobalIx }
   ::= {sr1645v2EthPrtSwF2OamSSCTable 1}

Sr1645v2EthPrtSwF2OamEntry ::=
   SEQUENCE
      {
      sr1645v2EthPrtSwF2OamGlobalIx
         GlobalIndex,
      sr1645v2EthPrtSwF2OamDiscovery
         INTEGER,
      sr1645v2EthPrtSwF2OamLoopback
         INTEGER,
      sr1645v2EthPrtSwF2OamLocalInfoVersion
         Integer32,
      sr1645v2EthPrtSwF2OamLocalInfoRevision
         Integer32,
      sr1645v2EthPrtSwF2OamLocalInfoStateMuxAction
         INTEGER,
      sr1645v2EthPrtSwF2OamLocalInfoStateParserAction
         INTEGER,
      sr1645v2EthPrtSwF2OamLocalInfoOui
         OCTET STRING,
      sr1645v2EthPrtSwF2OamLocalInfoVendorInfo
         OCTET STRING,
      sr1645v2EthPrtSwF2OamLocalInfoVarRetrieval
         INTEGER,
      sr1645v2EthPrtSwF2OamLocalInfoLinkEvents
         INTEGER,
      sr1645v2EthPrtSwF2OamLocalInfoLoopback
         INTEGER,
      sr1645v2EthPrtSwF2OamLocalInfoUnidirectional
         INTEGER,
      sr1645v2EthPrtSwF2OamLocalInfoMode
         INTEGER,
      sr1645v2EthPrtSwF2OamLocalInfoMaxPduSize
         Integer32,
      sr1645v2EthPrtSwF2OamRemoteInfoVersion
         Integer32,
      sr1645v2EthPrtSwF2OamRemoteInfoRevision
         Integer32,
      sr1645v2EthPrtSwF2OamRemoteInfoStateMuxAction
         INTEGER,
      sr1645v2EthPrtSwF2OamRemoteInfoStateParserAction
         INTEGER,
      sr1645v2EthPrtSwF2OamRemoteInfoOui
         OCTET STRING,
      sr1645v2EthPrtSwF2OamRemoteInfoVendorInfo
         OCTET STRING,
      sr1645v2EthPrtSwF2OamRemoteInfoVarRetrieval
         INTEGER,
      sr1645v2EthPrtSwF2OamRemoteInfoLinkEvents
         INTEGER,
      sr1645v2EthPrtSwF2OamRemoteInfoLoopback
         INTEGER,
      sr1645v2EthPrtSwF2OamRemoteInfoUnidirectional
         INTEGER,
      sr1645v2EthPrtSwF2OamRemoteInfoMode
         INTEGER,
      sr1645v2EthPrtSwF2OamRemoteInfoMaxPduSize
         Integer32,
      sr1645v2EthPrtSwF2OamEventsErroredSymbolWindow
         Integer32,
      sr1645v2EthPrtSwF2OamEventsErroredSymbolThreshold
         OCTET STRING,
      sr1645v2EthPrtSwF2OamEventsErroredFramePeriodWindow
         INTEGER,
      sr1645v2EthPrtSwF2OamEventsErroredFramePeriodThreshold
         Integer32,
      sr1645v2EthPrtSwF2OamEventsErroredFrameWindow
         Integer32,
      sr1645v2EthPrtSwF2OamEventsErroredFrameThreshold
         Integer32,
      sr1645v2EthPrtSwF2OamEventsErroredFrameSecondsWindow
         Integer32,
      sr1645v2EthPrtSwF2OamEventsErroredFrameSecondsThreshold
         Integer32
      }

sr1645v2EthPrtSwF2OamGlobalIx OBJECT-TYPE
   SYNTAX      GlobalIndex
   MAX-ACCESS  not-accessible
   STATUS      current
   DESCRIPTION
      "The value of the tlsCntTreeGlobalIndex of the MANAGED OBJECT."
   ::= {sr1645v2EthPrtSwF2OamEntry 10}

sr1645v2EthPrtSwF2OamDiscovery OBJECT-TYPE
   SYNTAX      INTEGER
               {
               fault (0),
               sendLocal (1),
               passiveWait (2),
               sendLocalRemote (3),
               sendLocalRemoteOk (4),
               sendAny (5)
               }
   MAX-ACCESS  read-only
   STATUS      current
   DESCRIPTION
      "Path: swPort.status.oam.discovery

       Possibilities:
               fault   (0)
               sendLocal   (1)
               passiveWait   (2)
               sendLocalRemote   (3)
               sendLocalRemoteOk   (4)
               sendAny   (5)"
   ::= {sr1645v2EthPrtSwF2OamEntry 16777216}

sr1645v2EthPrtSwF2OamLoopback OBJECT-TYPE
   SYNTAX      INTEGER
               {
               idle (0),
               waiting (1),
               localRunning (2),
               remoteRunning (3)
               }
   MAX-ACCESS  read-only
   STATUS      current
   DESCRIPTION
      "Path: swPort.status.oam.loopback

       Possibilities:
               idle   (0)
               waiting   (1)
               localRunning   (2)
               remoteRunning   (3)"
   ::= {sr1645v2EthPrtSwF2OamEntry 33554432}

sr1645v2EthPrtSwF2OamLocalInfoVersion OBJECT-TYPE
   SYNTAX      Integer32
   MAX-ACCESS  read-only
   STATUS      current
   DESCRIPTION
      "Path: swPort.status.oam.localInfo.version"
   ::= {sr1645v2EthPrtSwF2OamEntry 50397184}

sr1645v2EthPrtSwF2OamLocalInfoRevision OBJECT-TYPE
   SYNTAX      Integer32
   MAX-ACCESS  read-only
   STATUS      current
   DESCRIPTION
      "Path: swPort.status.oam.localInfo.revision"
   ::= {sr1645v2EthPrtSwF2OamEntry 50462720}

sr1645v2EthPrtSwF2OamLocalInfoStateMuxAction OBJECT-TYPE
   SYNTAX      INTEGER
               {
               forwarding (0),
               discarding (1)
               }
   MAX-ACCESS  read-only
   STATUS      current
   DESCRIPTION
      "Path: swPort.status.oam.localInfo.state.muxAction

       Possibilities:
               forwarding   (0)
               discarding   (1)"
   ::= {sr1645v2EthPrtSwF2OamEntry 50528512}

sr1645v2EthPrtSwF2OamLocalInfoStateParserAction OBJECT-TYPE
   SYNTAX      INTEGER
               {
               forwarding (0),
               loopback (1),
               discarding (2),
               reserved (3)
               }
   MAX-ACCESS  read-only
   STATUS      current
   DESCRIPTION
      "Path: swPort.status.oam.localInfo.state.parserAction

       Possibilities:
               forwarding   (0)
               loopback   (1)
               discarding   (2)
               reserved   (3)"
   ::= {sr1645v2EthPrtSwF2OamEntry 50528768}

sr1645v2EthPrtSwF2OamLocalInfoOui OBJECT-TYPE
   SYNTAX      OCTET STRING
   MAX-ACCESS  read-only
   STATUS      current
   DESCRIPTION
      "Path: swPort.status.oam.localInfo.oui"
   ::= {sr1645v2EthPrtSwF2OamEntry 50593792}

sr1645v2EthPrtSwF2OamLocalInfoVendorInfo OBJECT-TYPE
   SYNTAX      OCTET STRING
   MAX-ACCESS  read-only
   STATUS      current
   DESCRIPTION
      "Path: swPort.status.oam.localInfo.vendorInfo"
   ::= {sr1645v2EthPrtSwF2OamEntry 50659328}

sr1645v2EthPrtSwF2OamLocalInfoVarRetrieval OBJECT-TYPE
   SYNTAX      INTEGER
               {
               notSupported (0),
               supported (1)
               }
   MAX-ACCESS  read-only
   STATUS      current
   DESCRIPTION
      "Path: swPort.status.oam.localInfo.varRetrieval

       Possibilities:
               notSupported   (0)
               supported   (1)"
   ::= {sr1645v2EthPrtSwF2OamEntry 50724864}

sr1645v2EthPrtSwF2OamLocalInfoLinkEvents OBJECT-TYPE
   SYNTAX      INTEGER
               {
               ignored (0),
               interpreted (1)
               }
   MAX-ACCESS  read-only
   STATUS      current
   DESCRIPTION
      "Path: swPort.status.oam.localInfo.linkEvents

       Possibilities:
               ignored   (0)
               interpreted   (1)"
   ::= {sr1645v2EthPrtSwF2OamEntry 50790400}

sr1645v2EthPrtSwF2OamLocalInfoLoopback OBJECT-TYPE
   SYNTAX      INTEGER
               {
               notSupported (0),
               supported (1)
               }
   MAX-ACCESS  read-only
   STATUS      current
   DESCRIPTION
      "Path: swPort.status.oam.localInfo.loopback

       Possibilities:
               notSupported   (0)
               supported   (1)"
   ::= {sr1645v2EthPrtSwF2OamEntry 50855936}

sr1645v2EthPrtSwF2OamLocalInfoUnidirectional OBJECT-TYPE
   SYNTAX      INTEGER
               {
               notSupported (0),
               supported (1)
               }
   MAX-ACCESS  read-only
   STATUS      current
   DESCRIPTION
      "Path: swPort.status.oam.localInfo.unidirectional

       Possibilities:
               notSupported   (0)
               supported   (1)"
   ::= {sr1645v2EthPrtSwF2OamEntry 50921472}

sr1645v2EthPrtSwF2OamLocalInfoMode OBJECT-TYPE
   SYNTAX      INTEGER
               {
               passive (0),
               active (1)
               }
   MAX-ACCESS  read-only
   STATUS      current
   DESCRIPTION
      "Path: swPort.status.oam.localInfo.mode

       Possibilities:
               passive   (0)
               active   (1)"
   ::= {sr1645v2EthPrtSwF2OamEntry 50987008}

sr1645v2EthPrtSwF2OamLocalInfoMaxPduSize OBJECT-TYPE
   SYNTAX      Integer32
   MAX-ACCESS  read-only
   STATUS      current
   DESCRIPTION
      "Path: swPort.status.oam.localInfo.maxPduSize"
   ::= {sr1645v2EthPrtSwF2OamEntry 51052544}

sr1645v2EthPrtSwF2OamRemoteInfoVersion OBJECT-TYPE
   SYNTAX      Integer32
   MAX-ACCESS  read-only
   STATUS      current
   DESCRIPTION
      "Path: swPort.status.oam.remoteInfo.version"
   ::= {sr1645v2EthPrtSwF2OamEntry 67174400}

sr1645v2EthPrtSwF2OamRemoteInfoRevision OBJECT-TYPE
   SYNTAX      Integer32
   MAX-ACCESS  read-only
   STATUS      current
   DESCRIPTION
      "Path: swPort.status.oam.remoteInfo.revision"
   ::= {sr1645v2EthPrtSwF2OamEntry 67239936}

sr1645v2EthPrtSwF2OamRemoteInfoStateMuxAction OBJECT-TYPE
   SYNTAX      INTEGER
               {
               forwarding (0),
               discarding (1)
               }
   MAX-ACCESS  read-only
   STATUS      current
   DESCRIPTION
      "Path: swPort.status.oam.remoteInfo.state.muxAction

       Possibilities:
               forwarding   (0)
               discarding   (1)"
   ::= {sr1645v2EthPrtSwF2OamEntry 67305728}

sr1645v2EthPrtSwF2OamRemoteInfoStateParserAction OBJECT-TYPE
   SYNTAX      INTEGER
               {
               forwarding (0),
               loopback (1),
               discarding (2),
               reserved (3)
               }
   MAX-ACCESS  read-only
   STATUS      current
   DESCRIPTION
      "Path: swPort.status.oam.remoteInfo.state.parserAction

       Possibilities:
               forwarding   (0)
               loopback   (1)
               discarding   (2)
               reserved   (3)"
   ::= {sr1645v2EthPrtSwF2OamEntry 67305984}

sr1645v2EthPrtSwF2OamRemoteInfoOui OBJECT-TYPE
   SYNTAX      OCTET STRING
   MAX-ACCESS  read-only
   STATUS      current
   DESCRIPTION
      "Path: swPort.status.oam.remoteInfo.oui"
   ::= {sr1645v2EthPrtSwF2OamEntry 67371008}

sr1645v2EthPrtSwF2OamRemoteInfoVendorInfo OBJECT-TYPE
   SYNTAX      OCTET STRING
   MAX-ACCESS  read-only
   STATUS      current
   DESCRIPTION
      "Path: swPort.status.oam.remoteInfo.vendorInfo"
   ::= {sr1645v2EthPrtSwF2OamEntry 67436544}

sr1645v2EthPrtSwF2OamRemoteInfoVarRetrieval OBJECT-TYPE
   SYNTAX      INTEGER
               {
               notSupported (0),
               supported (1)
               }
   MAX-ACCESS  read-only
   STATUS      current
   DESCRIPTION
      "Path: swPort.status.oam.remoteInfo.varRetrieval

       Possibilities:
               notSupported   (0)
               supported   (1)"
   ::= {sr1645v2EthPrtSwF2OamEntry 67502080}

sr1645v2EthPrtSwF2OamRemoteInfoLinkEvents OBJECT-TYPE
   SYNTAX      INTEGER
               {
               ignored (0),
               interpreted (1)
               }
   MAX-ACCESS  read-only
   STATUS      current
   DESCRIPTION
      "Path: swPort.status.oam.remoteInfo.linkEvents

       Possibilities:
               ignored   (0)
               interpreted   (1)"
   ::= {sr1645v2EthPrtSwF2OamEntry 67567616}

sr1645v2EthPrtSwF2OamRemoteInfoLoopback OBJECT-TYPE
   SYNTAX      INTEGER
               {
               notSupported (0),
               supported (1)
               }
   MAX-ACCESS  read-only
   STATUS      current
   DESCRIPTION
      "Path: swPort.status.oam.remoteInfo.loopback

       Possibilities:
               notSupported   (0)
               supported   (1)"
   ::= {sr1645v2EthPrtSwF2OamEntry 67633152}

sr1645v2EthPrtSwF2OamRemoteInfoUnidirectional OBJECT-TYPE
   SYNTAX      INTEGER
               {
               notSupported (0),
               supported (1)
               }
   MAX-ACCESS  read-only
   STATUS      current
   DESCRIPTION
      "Path: swPort.status.oam.remoteInfo.unidirectional

       Possibilities:
               notSupported   (0)
               supported   (1)"
   ::= {sr1645v2EthPrtSwF2OamEntry 67698688}

sr1645v2EthPrtSwF2OamRemoteInfoMode OBJECT-TYPE
   SYNTAX      INTEGER
               {
               passive (0),
               active (1)
               }
   MAX-ACCESS  read-only
   STATUS      current
   DESCRIPTION
      "Path: swPort.status.oam.remoteInfo.mode

       Possibilities:
               passive   (0)
               active   (1)"
   ::= {sr1645v2EthPrtSwF2OamEntry 67764224}

sr1645v2EthPrtSwF2OamRemoteInfoMaxPduSize OBJECT-TYPE
   SYNTAX      Integer32
   MAX-ACCESS  read-only
   STATUS      current
   DESCRIPTION
      "Path: swPort.status.oam.remoteInfo.maxPduSize"
   ::= {sr1645v2EthPrtSwF2OamEntry 67829760}

sr1645v2EthPrtSwF2OamEventsErroredSymbolWindow OBJECT-TYPE
   SYNTAX      Integer32
   UNITS       "symbols"
   MAX-ACCESS  read-only
   STATUS      current
   DESCRIPTION
      "Path: swPort.status.oam.events.erroredSymbol.window

       unit name = symbols"
   ::= {sr1645v2EthPrtSwF2OamEntry 83951872}

sr1645v2EthPrtSwF2OamEventsErroredSymbolThreshold OBJECT-TYPE
   SYNTAX      OCTET STRING
   UNITS       "symbols"
   MAX-ACCESS  read-only
   STATUS      current
   DESCRIPTION
      "Path: swPort.status.oam.events.erroredSymbol.threshold

       unit name = symbols"
   ::= {sr1645v2EthPrtSwF2OamEntry 83952128}

sr1645v2EthPrtSwF2OamEventsErroredFramePeriodWindow OBJECT-TYPE
   SYNTAX      INTEGER
               {
               default (0)
               }
   UNITS       "frames"
   MAX-ACCESS  read-only
   STATUS      current
   DESCRIPTION
      "Path: swPort.status.oam.events.erroredFramePeriod.window

       unit name = frames

       Possibilities:
               default   (0)"
   ::= {sr1645v2EthPrtSwF2OamEntry 84017408}

sr1645v2EthPrtSwF2OamEventsErroredFramePeriodThreshold OBJECT-TYPE
   SYNTAX      Integer32
   UNITS       "frames"
   MAX-ACCESS  read-only
   STATUS      current
   DESCRIPTION
      "Path: swPort.status.oam.events.erroredFramePeriod.threshold

       unit name = frames"
   ::= {sr1645v2EthPrtSwF2OamEntry 84017664}

sr1645v2EthPrtSwF2OamEventsErroredFrameWindow OBJECT-TYPE
   SYNTAX      Integer32
   UNITS       "100msec"
   MAX-ACCESS  read-only
   STATUS      current
   DESCRIPTION
      "Path: swPort.status.oam.events.erroredFrame.window

       unit name = 100msec"
   ::= {sr1645v2EthPrtSwF2OamEntry 84082944}

sr1645v2EthPrtSwF2OamEventsErroredFrameThreshold OBJECT-TYPE
   SYNTAX      Integer32
   UNITS       "frames"
   MAX-ACCESS  read-only
   STATUS      current
   DESCRIPTION
      "Path: swPort.status.oam.events.erroredFrame.threshold

       unit name = frames"
   ::= {sr1645v2EthPrtSwF2OamEntry 84083200}

sr1645v2EthPrtSwF2OamEventsErroredFrameSecondsWindow OBJECT-TYPE
   SYNTAX      Integer32
   UNITS       "100msec"
   MAX-ACCESS  read-only
   STATUS      current
   DESCRIPTION
      "Path: swPort.status.oam.events.erroredFrameSeconds.window

       unit name = 100msec"
   ::= {sr1645v2EthPrtSwF2OamEntry 84148480}

sr1645v2EthPrtSwF2OamEventsErroredFrameSecondsThreshold OBJECT-TYPE
   SYNTAX      Integer32
   UNITS       "frames"
   MAX-ACCESS  read-only
   STATUS      current
   DESCRIPTION
      "Path: swPort.status.oam.events.erroredFrameSeconds.threshold

       unit name = frames"
   ::= {sr1645v2EthPrtSwF2OamEntry 84148736}


sr1645v2EthPrtSwF2OamEventLog OBJECT IDENTIFIER ::= {sr1645v2EthPrtSwF2 911}

sr1645v2EthPrtSwF2OamEventLogSSCTable OBJECT-TYPE
   SYNTAX      SEQUENCE OF Sr1645v2EthPrtSwF2OamEventLogEntry
   MAX-ACCESS  not-accessible
   STATUS      current
   DESCRIPTION
      "OAM event log"
   ::= {sr1645v2EthPrtSwF2OamEventLog 1}

sr1645v2EthPrtSwF2OamEventLogEntry OBJECT-TYPE
   SYNTAX      Sr1645v2EthPrtSwF2OamEventLogEntry
   MAX-ACCESS  not-accessible
   STATUS      current
   DESCRIPTION
      ""
   INDEX      { sr1645v2EthPrtSwF2OamEventLogGlobalIx,
                sr1645v2EthPrtSwF2OamEventLogTableIx }
   ::= {sr1645v2EthPrtSwF2OamEventLogSSCTable 1}

Sr1645v2EthPrtSwF2OamEventLogEntry ::=
   SEQUENCE
      {
      sr1645v2EthPrtSwF2OamEventLogGlobalIx
         GlobalIndex,
      sr1645v2EthPrtSwF2OamEventLogTableIx
         TableIndex,
      sr1645v2EthPrtSwF2OamEventLogSysUpTime
         TimeTicks,
      sr1645v2EthPrtSwF2OamEventLogLocation
         INTEGER,
      sr1645v2EthPrtSwF2OamEventLogType
         INTEGER,
      sr1645v2EthPrtSwF2OamEventLogOui
         OCTET STRING,
      sr1645v2EthPrtSwF2OamEventLogWindow
         Counter64,
      sr1645v2EthPrtSwF2OamEventLogThreshold
         Counter64,
      sr1645v2EthPrtSwF2OamEventLogTotal
         Counter32,
      sr1645v2EthPrtSwF2OamEventLogValue
         Counter64,
      sr1645v2EthPrtSwF2OamEventLogRunningTotal
         Counter64
      }

sr1645v2EthPrtSwF2OamEventLogGlobalIx OBJECT-TYPE
   SYNTAX      GlobalIndex
   MAX-ACCESS  not-accessible
   STATUS      current
   DESCRIPTION
      "The value of the tlsCntTreeGlobalIndex of the MANAGED OBJECT."
   ::= {sr1645v2EthPrtSwF2OamEventLogEntry 10}

sr1645v2EthPrtSwF2OamEventLogTableIx OBJECT-TYPE
   SYNTAX      TableIndex
   MAX-ACCESS  not-accessible
   STATUS      current
   DESCRIPTION
      ""
   ::= {sr1645v2EthPrtSwF2OamEventLogEntry 11}

sr1645v2EthPrtSwF2OamEventLogSysUpTime OBJECT-TYPE
   SYNTAX      TimeTicks
   MAX-ACCESS  read-only
   STATUS      current
   DESCRIPTION
      "Path: swPort.status.oamEventLog.sysUpTime

       Time in centi-second."
   ::= {sr1645v2EthPrtSwF2OamEventLogEntry 16777216}

sr1645v2EthPrtSwF2OamEventLogLocation OBJECT-TYPE
   SYNTAX      INTEGER
               {
               local (1),
               remote (2)
               }
   MAX-ACCESS  read-only
   STATUS      current
   DESCRIPTION
      "Path: swPort.status.oamEventLog.location

       Possibilities:
               local   (1)
               remote   (2)"
   ::= {sr1645v2EthPrtSwF2OamEventLogEntry 33554432}

sr1645v2EthPrtSwF2OamEventLogType OBJECT-TYPE
   SYNTAX      INTEGER
               {
               erroredSymbols (1),
               erroredFramePeriod (2),
               erroredFrame (3),
               erroredFrameSeconds (4),
               linkFault (256),
               dyingGasp (257),
               criticalLink (258)
               }
   MAX-ACCESS  read-only
   STATUS      current
   DESCRIPTION
      "Path: swPort.status.oamEventLog.type

       Possibilities:
               erroredSymbols   (1)
               erroredFramePeriod   (2)
               erroredFrame   (3)
               erroredFrameSeconds   (4)
               linkFault   (256)
               dyingGasp   (257)
               criticalLink   (258)"
   ::= {sr1645v2EthPrtSwF2OamEventLogEntry 50331648}

sr1645v2EthPrtSwF2OamEventLogOui OBJECT-TYPE
   SYNTAX      OCTET STRING
   MAX-ACCESS  read-only
   STATUS      current
   DESCRIPTION
      "Path: swPort.status.oamEventLog.oui"
   ::= {sr1645v2EthPrtSwF2OamEventLogEntry 67108864}

sr1645v2EthPrtSwF2OamEventLogWindow OBJECT-TYPE
   SYNTAX      Counter64
   MAX-ACCESS  read-only
   STATUS      current
   DESCRIPTION
      "Path: swPort.status.oamEventLog.window

       64 bit unsigned wrappable counter."
   ::= {sr1645v2EthPrtSwF2OamEventLogEntry 83886080}

sr1645v2EthPrtSwF2OamEventLogThreshold OBJECT-TYPE
   SYNTAX      Counter64
   MAX-ACCESS  read-only
   STATUS      current
   DESCRIPTION
      "Path: swPort.status.oamEventLog.threshold

       64 bit unsigned wrappable counter."
   ::= {sr1645v2EthPrtSwF2OamEventLogEntry 100663296}

sr1645v2EthPrtSwF2OamEventLogTotal OBJECT-TYPE
   SYNTAX      Counter32
   MAX-ACCESS  read-only
   STATUS      current
   DESCRIPTION
      "Path: swPort.status.oamEventLog.total

       32 bit unsigned wrappable counter."
   ::= {sr1645v2EthPrtSwF2OamEventLogEntry 117440512}

sr1645v2EthPrtSwF2OamEventLogValue OBJECT-TYPE
   SYNTAX      Counter64
   MAX-ACCESS  read-only
   STATUS      current
   DESCRIPTION
      "Path: swPort.status.oamEventLog.value

       64 bit unsigned wrappable counter."
   ::= {sr1645v2EthPrtSwF2OamEventLogEntry 134217728}

sr1645v2EthPrtSwF2OamEventLogRunningTotal OBJECT-TYPE
   SYNTAX      Counter64
   MAX-ACCESS  read-only
   STATUS      current
   DESCRIPTION
      "Path: swPort.status.oamEventLog.runningTotal

       64 bit unsigned wrappable counter."
   ::= {sr1645v2EthPrtSwF2OamEventLogEntry 150994944}


sr1645v2EthPrtSwF2Vlan OBJECT IDENTIFIER ::= {sr1645v2EthPrtSwF2 34}

sr1645v2EthPrtSwF2VlanSSCTable OBJECT-TYPE
   SYNTAX      SEQUENCE OF Sr1645v2EthPrtSwF2VlanEntry
   MAX-ACCESS  not-accessible
   STATUS      current
   DESCRIPTION
      ""
   ::= {sr1645v2EthPrtSwF2Vlan 1}

sr1645v2EthPrtSwF2VlanEntry OBJECT-TYPE
   SYNTAX      Sr1645v2EthPrtSwF2VlanEntry
   MAX-ACCESS  not-accessible
   STATUS      current
   DESCRIPTION
      ""
   INDEX      { sr1645v2EthPrtSwF2VlanGlobalIx,
                sr1645v2EthPrtSwF2VlanTableIx }
   ::= {sr1645v2EthPrtSwF2VlanSSCTable 1}

Sr1645v2EthPrtSwF2VlanEntry ::=
   SEQUENCE
      {
      sr1645v2EthPrtSwF2VlanGlobalIx
         GlobalIndex,
      sr1645v2EthPrtSwF2VlanTableIx
         TableIndex,
      sr1645v2EthPrtSwF2VlanName
         DisplayString,
      sr1645v2EthPrtSwF2VlanMode
         INTEGER,
      sr1645v2EthPrtSwF2VlanIfOperStatus
         INTEGER,
      sr1645v2EthPrtSwF2VlanIfLastChange
         TimeTicks,
      sr1645v2EthPrtSwF2VlanIfLastChangeDate
         DisplayString,
      sr1645v2EthPrtSwF2VlanIpAddress
         IpAddress,
      sr1645v2EthPrtSwF2VlanIpNetMask
         IpAddress,
      sr1645v2EthPrtSwF2VlanIpRemote
         IpAddress,
      sr1645v2EthPrtSwF2VlanIpDhcpStatus
         INTEGER,
      sr1645v2EthPrtSwF2VlanIpDhcpLeaseTime
         TimeTicks,
      sr1645v2EthPrtSwF2VlanIpV6State
         INTEGER,
      sr1645v2EthPrtSwF2VlanIpV6InterfaceId
         OCTET STRING,
      sr1645v2EthPrtSwF2VlanIpV6LinkMtu
         Integer32,
      sr1645v2EthPrtSwF2VlanIpV6HopLimit
         Integer32,
      sr1645v2EthPrtSwF2VlanIpV6DhcpIaid
         Counter32,
      sr1645v2EthPrtSwF2VlanIpV6RaRcvOption
         Integer32,
      sr1645v2EthPrtSwF2VlanBridgingStatus
         INTEGER,
      sr1645v2EthPrtSwF2VlanBridgingSpanningTreePortRole
         INTEGER,
      sr1645v2EthPrtSwF2VlanBridgingSpanningTreePortId
         Integer32,
      sr1645v2EthPrtSwF2VlanBridgingSpanningTreePpCostExtPathCost
         Integer32,
      sr1645v2EthPrtSwF2VlanBridgingSpanningTreePpCostIntPathCost
         Integer32,
      sr1645v2EthPrtSwF2VlanBridgingSpanningTreeExtRpCost
         Integer32,
      sr1645v2EthPrtSwF2VlanBridgingSpanningTreeIntRpCost
         Integer32,
      sr1645v2EthPrtSwF2VlanBridgingSpanningTreeDesBrIdPriority
         Integer32,
      sr1645v2EthPrtSwF2VlanBridgingSpanningTreeDesBrIdMacAddress
         OCTET STRING,
      sr1645v2EthPrtSwF2VlanBridgingSpanningTreeDesPrtId
         Integer32,
      sr1645v2EthPrtSwF2VlanBridgingSpanningTreeDesInt
         INTEGER,
      sr1645v2EthPrtSwF2VlanBridgingSpanningTreeEdgeDetection
         INTEGER,
      sr1645v2EthPrtSwF2VlanVlanVid
         Integer32,
      sr1645v2EthPrtSwF2VlanPppOEthDiscState
         INTEGER,
      sr1645v2EthPrtSwF2VlanPppOEthPeerMac
         OCTET STRING,
      sr1645v2EthPrtSwF2VlanPppOEthServiceName
         DisplayString,
      sr1645v2EthPrtSwF2VlanPppLcpState
         INTEGER,
      sr1645v2EthPrtSwF2VlanPppIpcpState
         INTEGER,
      sr1645v2EthPrtSwF2VlanPppIp6cpState
         INTEGER,
      sr1645v2EthPrtSwF2VlanPppMyAutSt
         INTEGER,
      sr1645v2EthPrtSwF2VlanPppHisAutSt
         INTEGER,
      sr1645v2EthPrtSwF2VlanPppMru
         Integer32
      }

sr1645v2EthPrtSwF2VlanGlobalIx OBJECT-TYPE
   SYNTAX      GlobalIndex
   MAX-ACCESS  not-accessible
   STATUS      current
   DESCRIPTION
      "The value of the tlsCntTreeGlobalIndex of the MANAGED OBJECT."
   ::= {sr1645v2EthPrtSwF2VlanEntry 10}

sr1645v2EthPrtSwF2VlanTableIx OBJECT-TYPE
   SYNTAX      TableIndex
   MAX-ACCESS  not-accessible
   STATUS      current
   DESCRIPTION
      ""
   ::= {sr1645v2EthPrtSwF2VlanEntry 11}

sr1645v2EthPrtSwF2VlanName OBJECT-TYPE
   SYNTAX      DisplayString
   MAX-ACCESS  read-only
   STATUS      current
   DESCRIPTION
      "Path: swPort.status.vlan.name"
   ::= {sr1645v2EthPrtSwF2VlanEntry 16777216}

sr1645v2EthPrtSwF2VlanMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: swPort.status.vlan.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1645v2EthPrtSwF2VlanEntry 335544320}

sr1645v2EthPrtSwF2VlanIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: swPort.status.vlan.ifOperStatus

       Possibilities:
               up   (1)
               down   (2)
               testing   (3)
               unknown   (4)
               dormant   (5)
               notPresent   (6)
               lowerLayerDown   (7)"
   ::= {sr1645v2EthPrtSwF2VlanEntry 1795162112}

sr1645v2EthPrtSwF2VlanIfLastChange OBJECT-TYPE
   SYNTAX      TimeTicks
   MAX-ACCESS  read-only
   STATUS      current
   DESCRIPTION
      "Path: swPort.status.vlan.ifLastChange

       Time in centi-second."
   ::= {sr1645v2EthPrtSwF2VlanEntry 1811939328}

sr1645v2EthPrtSwF2VlanIfLastChangeDate OBJECT-TYPE
   SYNTAX      DisplayString
   MAX-ACCESS  read-only
   STATUS      current
   DESCRIPTION
      "Path: swPort.status.vlan.ifLastChangeDate"
   ::= {sr1645v2EthPrtSwF2VlanEntry 3070230528}

sr1645v2EthPrtSwF2VlanIpAddress OBJECT-TYPE
   SYNTAX      IpAddress
   MAX-ACCESS  read-only
   STATUS      current
   DESCRIPTION
      "Path: swPort.status.vlan.ip.address"
   ::= {sr1645v2EthPrtSwF2VlanEntry 51380224}

sr1645v2EthPrtSwF2VlanIpNetMask OBJECT-TYPE
   SYNTAX      IpAddress
   MAX-ACCESS  read-only
   STATUS      current
   DESCRIPTION
      "Path: swPort.status.vlan.ip.netMask"
   ::= {sr1645v2EthPrtSwF2VlanEntry 51445760}

sr1645v2EthPrtSwF2VlanIpRemote OBJECT-TYPE
   SYNTAX      IpAddress
   MAX-ACCESS  read-only
   STATUS      current
   DESCRIPTION
      "Path: swPort.status.vlan.ip.remote"
   ::= {sr1645v2EthPrtSwF2VlanEntry 51511296}

sr1645v2EthPrtSwF2VlanIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: swPort.status.vlan.ip.dhcp.status

       Possibilities:
               none   (0)
               selecting   (1)
               requesting   (2)
               rebinding   (3)
               bound   (4)
               renewing   (5)
               rebooting   (6)
               initreboot   (7)"
   ::= {sr1645v2EthPrtSwF2VlanEntry 51904768}

sr1645v2EthPrtSwF2VlanIpDhcpLeaseTime OBJECT-TYPE
   SYNTAX      TimeTicks
   MAX-ACCESS  read-only
   STATUS      current
   DESCRIPTION
      "Path: swPort.status.vlan.ip.dhcp.leaseTime

       Time in centi-second."
   ::= {sr1645v2EthPrtSwF2VlanEntry 51905024}

sr1645v2EthPrtSwF2VlanIpV6State OBJECT-TYPE
   SYNTAX      INTEGER
               {
               disabled (0),
               enabled (1)
               }
   MAX-ACCESS  read-only
   STATUS      current
   DESCRIPTION
      "Path: swPort.status.vlan.ipV6.state

       Possibilities:
               disabled   (0)
               enabled   (1)"
   ::= {sr1645v2EthPrtSwF2VlanEntry 100728832}

sr1645v2EthPrtSwF2VlanIpV6InterfaceId OBJECT-TYPE
   SYNTAX      OCTET STRING
   MAX-ACCESS  read-only
   STATUS      current
   DESCRIPTION
      "Path: swPort.status.vlan.ipV6.interfaceId"
   ::= {sr1645v2EthPrtSwF2VlanEntry 100794368}

sr1645v2EthPrtSwF2VlanIpV6LinkMtu OBJECT-TYPE
   SYNTAX      Integer32
   MAX-ACCESS  read-only
   STATUS      current
   DESCRIPTION
      "Path: swPort.status.vlan.ipV6.linkMtu"
   ::= {sr1645v2EthPrtSwF2VlanEntry 100925440}

sr1645v2EthPrtSwF2VlanIpV6HopLimit OBJECT-TYPE
   SYNTAX      Integer32
   MAX-ACCESS  read-only
   STATUS      current
   DESCRIPTION
      "Path: swPort.status.vlan.ipV6.hopLimit"
   ::= {sr1645v2EthPrtSwF2VlanEntry 100990976}

sr1645v2EthPrtSwF2VlanIpV6DhcpIaid OBJECT-TYPE
   SYNTAX      Counter32
   MAX-ACCESS  read-only
   STATUS      current
   DESCRIPTION
      "Path: swPort.status.vlan.ipV6.dhcp.iaid

       32 bit unsigned wrappable counter."
   ::= {sr1645v2EthPrtSwF2VlanEntry 101056768}

sr1645v2EthPrtSwF2VlanIpV6RaRcvOption OBJECT-TYPE
   SYNTAX      Integer32
   MAX-ACCESS  read-only
   STATUS      current
   DESCRIPTION
      "Path: swPort.status.vlan.ipV6.raRcvOption

       Bit meanings:
               bit 0 = linkMtu,
               bit 1 = srcLinkLayer,
               bit 2 = prefixInfo,
               bit 3 = rdnss,
               bit 4 = dnssl"
   ::= {sr1645v2EthPrtSwF2VlanEntry 101122048}

sr1645v2EthPrtSwF2VlanBridgingStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: swPort.status.vlan.bridging.status

       Possibilities:
               disabled   (0)
               discarding   (1)
               learning   (2)
               forwarding   (3)
               backupBlockedIntfDown   (256)
               backupBlockedIntfUp   (259)
               shutdown   (255)"
   ::= {sr1645v2EthPrtSwF2VlanEntry 453050368}

sr1645v2EthPrtSwF2VlanBridgingSpanningTreePortRole OBJECT-TYPE
   SYNTAX      INTEGER
               {
               none (0),
               root (1),
               designated (2),
               alternate (3),
               backup (4),
               disabled (5),
               master (6)
               }
   MAX-ACCESS  read-only
   STATUS      current
   DESCRIPTION
      "Path: swPort.status.vlan.bridging.spanningTree.portRole

       Possibilities:
               none   (0)
               root   (1)
               designated   (2)
               alternate   (3)
               backup   (4)
               disabled   (5)
               master   (6)"
   ::= {sr1645v2EthPrtSwF2VlanEntry 453116160}

sr1645v2EthPrtSwF2VlanBridgingSpanningTreePortId OBJECT-TYPE
   SYNTAX      Integer32
   MAX-ACCESS  read-only
   STATUS      current
   DESCRIPTION
      "Path: swPort.status.vlan.bridging.spanningTree.portId"
   ::= {sr1645v2EthPrtSwF2VlanEntry 453116416}

sr1645v2EthPrtSwF2VlanBridgingSpanningTreePpCostExtPathCost OBJECT-TYPE
   SYNTAX      Integer32
   MAX-ACCESS  read-only
   STATUS      current
   DESCRIPTION
      "Path: swPort.status.vlan.bridging.spanningTree.portPathCosts.extPathCost"
   ::= {sr1645v2EthPrtSwF2VlanEntry 453116673}

sr1645v2EthPrtSwF2VlanBridgingSpanningTreePpCostIntPathCost OBJECT-TYPE
   SYNTAX      Integer32
   MAX-ACCESS  read-only
   STATUS      current
   DESCRIPTION
      "Path: swPort.status.vlan.bridging.spanningTree.portPathCosts.intPathCost"
   ::= {sr1645v2EthPrtSwF2VlanEntry 453116674}

sr1645v2EthPrtSwF2VlanBridgingSpanningTreeExtRpCost OBJECT-TYPE
   SYNTAX      Integer32
   MAX-ACCESS  read-only
   STATUS      current
   DESCRIPTION
      "Path: swPort.status.vlan.bridging.spanningTree.extRootPathCost"
   ::= {sr1645v2EthPrtSwF2VlanEntry 453116928}

sr1645v2EthPrtSwF2VlanBridgingSpanningTreeIntRpCost OBJECT-TYPE
   SYNTAX      Integer32
   MAX-ACCESS  read-only
   STATUS      current
   DESCRIPTION
      "Path: swPort.status.vlan.bridging.spanningTree.intRootPathCost"
   ::= {sr1645v2EthPrtSwF2VlanEntry 453117184}

sr1645v2EthPrtSwF2VlanBridgingSpanningTreeDesBrIdPriority OBJECT-TYPE
   SYNTAX      Integer32
   MAX-ACCESS  read-only
   STATUS      current
   DESCRIPTION
      "Path: swPort.status.vlan.bridging.spanningTree.designatedBridgeId.priority"
   ::= {sr1645v2EthPrtSwF2VlanEntry 453117441}

sr1645v2EthPrtSwF2VlanBridgingSpanningTreeDesBrIdMacAddress OBJECT-TYPE
   SYNTAX      OCTET STRING
   MAX-ACCESS  read-only
   STATUS      current
   DESCRIPTION
      "Path: swPort.status.vlan.bridging.spanningTree.designatedBridgeId.macAddress

       MAC address."
   ::= {sr1645v2EthPrtSwF2VlanEntry 453117442}

sr1645v2EthPrtSwF2VlanBridgingSpanningTreeDesPrtId OBJECT-TYPE
   SYNTAX      Integer32
   MAX-ACCESS  read-only
   STATUS      current
   DESCRIPTION
      "Path: swPort.status.vlan.bridging.spanningTree.designatedPortId"
   ::= {sr1645v2EthPrtSwF2VlanEntry 453117696}

sr1645v2EthPrtSwF2VlanBridgingSpanningTreeDesInt OBJECT-TYPE
   SYNTAX      INTEGER
               {
               no (0),
               yes (1)
               }
   MAX-ACCESS  read-only
   STATUS      current
   DESCRIPTION
      "Path: swPort.status.vlan.bridging.spanningTree.designatedOrInternal

       Possibilities:
               no   (0)
               yes   (1)"
   ::= {sr1645v2EthPrtSwF2VlanEntry 453117952}

sr1645v2EthPrtSwF2VlanBridgingSpanningTreeEdgeDetection OBJECT-TYPE
   SYNTAX      INTEGER
               {
               none (0),
               edge (1),
               notEdge (2)
               }
   MAX-ACCESS  read-only
   STATUS      current
   DESCRIPTION
      "Path: swPort.status.vlan.bridging.spanningTree.edgeDetection

       Possibilities:
               none   (0)
               edge   (1)
               notEdge   (2)"
   ::= {sr1645v2EthPrtSwF2VlanEntry 453118208}

sr1645v2EthPrtSwF2VlanVlanVid OBJECT-TYPE
   SYNTAX      Integer32
   MAX-ACCESS  read-only
   STATUS      current
   DESCRIPTION
      "Path: swPort.status.vlan.vlan.vid"
   ::= {sr1645v2EthPrtSwF2VlanEntry 234946560}

sr1645v2EthPrtSwF2VlanPppOEthDiscState OBJECT-TYPE
   SYNTAX      INTEGER
               {
               idle (0),
               waitForPADO (1),
               waitForPADS (2),
               established (3)
               }
   MAX-ACCESS  read-only
   STATUS      current
   DESCRIPTION
      "Path: swPort.status.vlan.pppOverEth.discState

       Possibilities:
               idle   (0)
               waitForPADO   (1)
               waitForPADS   (2)
               established   (3)"
   ::= {sr1645v2EthPrtSwF2VlanEntry 67174400}

sr1645v2EthPrtSwF2VlanPppOEthPeerMac OBJECT-TYPE
   SYNTAX      OCTET STRING
   MAX-ACCESS  read-only
   STATUS      current
   DESCRIPTION
      "Path: swPort.status.vlan.pppOverEth.remoteMacAddress

       MAC address."
   ::= {sr1645v2EthPrtSwF2VlanEntry 67239936}

sr1645v2EthPrtSwF2VlanPppOEthServiceName OBJECT-TYPE
   SYNTAX      DisplayString
   MAX-ACCESS  read-only
   STATUS      current
   DESCRIPTION
      "Path: swPort.status.vlan.pppOverEth.serviceName"
   ::= {sr1645v2EthPrtSwF2VlanEntry 67305472}

sr1645v2EthPrtSwF2VlanPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: swPort.status.vlan.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2EthPrtSwF2VlanEntry 83951616}

sr1645v2EthPrtSwF2VlanPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: swPort.status.vlan.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2EthPrtSwF2VlanEntry 84017152}

sr1645v2EthPrtSwF2VlanPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: swPort.status.vlan.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2EthPrtSwF2VlanEntry 84869120}

sr1645v2EthPrtSwF2VlanPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: swPort.status.vlan.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1645v2EthPrtSwF2VlanEntry 84541440}

sr1645v2EthPrtSwF2VlanPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: swPort.status.vlan.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1645v2EthPrtSwF2VlanEntry 84606976}

sr1645v2EthPrtSwF2VlanPppMru OBJECT-TYPE
   SYNTAX      Integer32
   MAX-ACCESS  read-only
   STATUS      current
   DESCRIPTION
      "Path: swPort.status.vlan.ppp.mru"
   ::= {sr1645v2EthPrtSwF2VlanEntry 84934656}

sr1645v2EthPrtSwF2VlanIpSecondaryIp OBJECT-TYPE
   SYNTAX      SEQUENCE OF Sr1645v2EthPrtSwF2VlanIpSecondaryIpEntry
   MAX-ACCESS  not-accessible
   STATUS      current
   DESCRIPTION
      ""
   ::= {sr1645v2EthPrtSwF2Vlan 51838976}

sr1645v2EthPrtSwF2VlanIpSecondaryIpEntry OBJECT-TYPE
   SYNTAX      Sr1645v2EthPrtSwF2VlanIpSecondaryIpEntry
   MAX-ACCESS  not-accessible
   STATUS      current
   DESCRIPTION
      ""
   INDEX      { sr1645v2EthPrtSwF2VlanIpSecondaryIpGlobalIx,
                sr1645v2EthPrtSwF2VlanTableIx,
                sr1645v2EthPrtSwF2VlanIpSecondaryIpTableIx }
   ::= {sr1645v2EthPrtSwF2VlanIpSecondaryIp 1}

Sr1645v2EthPrtSwF2VlanIpSecondaryIpEntry ::=
   SEQUENCE
      {
      sr1645v2EthPrtSwF2VlanIpSecondaryIpGlobalIx
         GlobalIndex,
      sr1645v2EthPrtSwF2VlanIpSecondaryIpTableIx
         TableIndex,
      sr1645v2EthPrtSwF2VlanIpSecondaryIpAddress
         IpAddress,
      sr1645v2EthPrtSwF2VlanIpSecondaryIpNetMask
         IpAddress
      }

sr1645v2EthPrtSwF2VlanIpSecondaryIpGlobalIx OBJECT-TYPE
   SYNTAX      GlobalIndex
   MAX-ACCESS  not-accessible
   STATUS      current
   DESCRIPTION
      "The value of the tlsCntTreeGlobalIndex of the MANAGED OBJECT."
   ::= {sr1645v2EthPrtSwF2VlanIpSecondaryIpEntry 10}

sr1645v2EthPrtSwF2VlanIpSecondaryIpTableIx OBJECT-TYPE
   SYNTAX      TableIndex
   MAX-ACCESS  not-accessible
   STATUS      current
   DESCRIPTION
      ""
   ::= {sr1645v2EthPrtSwF2VlanIpSecondaryIpEntry 11}

sr1645v2EthPrtSwF2VlanIpSecondaryIpAddress OBJECT-TYPE
   SYNTAX      IpAddress
   MAX-ACCESS  read-only
   STATUS      current
   DESCRIPTION
      "Path: swPort.status.vlan.ip.secondaryIp.address"
   ::= {sr1645v2EthPrtSwF2VlanIpSecondaryIpEntry 2030043136}

sr1645v2EthPrtSwF2VlanIpSecondaryIpNetMask OBJECT-TYPE
   SYNTAX      IpAddress
   MAX-ACCESS  read-only
   STATUS      current
   DESCRIPTION
      "Path: swPort.status.vlan.ip.secondaryIp.netMask"
   ::= {sr1645v2EthPrtSwF2VlanIpSecondaryIpEntry 2063597568}

sr1645v2EthPrtSwF2VlanIpV6Addresses OBJECT-TYPE
   SYNTAX      SEQUENCE OF Sr1645v2EthPrtSwF2VlanIpV6AddressesEntry
   MAX-ACCESS  not-accessible
   STATUS      current
   DESCRIPTION
      ""
   ::= {sr1645v2EthPrtSwF2Vlan 100859904}

sr1645v2EthPrtSwF2VlanIpV6AddressesEntry OBJECT-TYPE
   SYNTAX      Sr1645v2EthPrtSwF2VlanIpV6AddressesEntry
   MAX-ACCESS  not-accessible
   STATUS      current
   DESCRIPTION
      ""
   INDEX      { sr1645v2EthPrtSwF2VlanIpV6AddressesGlobalIx,
                sr1645v2EthPrtSwF2VlanTableIx,
                sr1645v2EthPrtSwF2VlanIpV6AddressesTableIx }
   ::= {sr1645v2EthPrtSwF2VlanIpV6Addresses 1}

Sr1645v2EthPrtSwF2VlanIpV6AddressesEntry ::=
   SEQUENCE
      {
      sr1645v2EthPrtSwF2VlanIpV6AddressesGlobalIx
         GlobalIndex,
      sr1645v2EthPrtSwF2VlanIpV6AddressesTableIx
         TableIndex,
      sr1645v2EthPrtSwF2VlanIpV6AddressesAddress
         Ipv6Address,
      sr1645v2EthPrtSwF2VlanIpV6AddressesPrefixLength
         Integer32,
      sr1645v2EthPrtSwF2VlanIpV6AddressesStatus
         INTEGER,
      sr1645v2EthPrtSwF2VlanIpV6AddressesOrigin
         INTEGER,
      sr1645v2EthPrtSwF2VlanIpV6AddressesFlagsInterfaceId
         INTEGER,
      sr1645v2EthPrtSwF2VlanIpV6AddressesFlagsAnycast
         INTEGER,
      sr1645v2EthPrtSwF2VlanIpV6AddressesTimersValidLifeTime
         TimeTicks,
      sr1645v2EthPrtSwF2VlanIpV6AddressesTimersPrefLifeTime
         TimeTicks
      }

sr1645v2EthPrtSwF2VlanIpV6AddressesGlobalIx OBJECT-TYPE
   SYNTAX      GlobalIndex
   MAX-ACCESS  not-accessible
   STATUS      current
   DESCRIPTION
      "The value of the tlsCntTreeGlobalIndex of the MANAGED OBJECT."
   ::= {sr1645v2EthPrtSwF2VlanIpV6AddressesEntry 10}

sr1645v2EthPrtSwF2VlanIpV6AddressesTableIx OBJECT-TYPE
   SYNTAX      TableIndex
   MAX-ACCESS  not-accessible
   STATUS      current
   DESCRIPTION
      ""
   ::= {sr1645v2EthPrtSwF2VlanIpV6AddressesEntry 11}

sr1645v2EthPrtSwF2VlanIpV6AddressesAddress OBJECT-TYPE
   SYNTAX      Ipv6Address
   MAX-ACCESS  read-only
   STATUS      current
   DESCRIPTION
      "Path: swPort.status.vlan.ipV6.addresses.address

       ipv6 address"
   ::= {sr1645v2EthPrtSwF2VlanIpV6AddressesEntry 16777216}

sr1645v2EthPrtSwF2VlanIpV6AddressesPrefixLength OBJECT-TYPE
   SYNTAX      Integer32
   MAX-ACCESS  read-only
   STATUS      current
   DESCRIPTION
      "Path: swPort.status.vlan.ipV6.addresses.prefixLength"
   ::= {sr1645v2EthPrtSwF2VlanIpV6AddressesEntry 33554432}

sr1645v2EthPrtSwF2VlanIpV6AddressesStatus OBJECT-TYPE
   SYNTAX      INTEGER
               {
               invalid (0),
               tentative (1),
               deprecated (2),
               preferred (3)
               }
   MAX-ACCESS  read-only
   STATUS      current
   DESCRIPTION
      "Path: swPort.status.vlan.ipV6.addresses.status

       Possibilities:
               invalid   (0)
               tentative   (1)
               deprecated   (2)
               preferred   (3)"
   ::= {sr1645v2EthPrtSwF2VlanIpV6AddressesEntry 50331648}

sr1645v2EthPrtSwF2VlanIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: swPort.status.vlan.ipV6.addresses.origin

       Possibilities:
               unknown   (0)
               manual   (1)
               generalPrefix   (2)
               statelessAuto   (3)
               statefullAuto   (4)"
   ::= {sr1645v2EthPrtSwF2VlanIpV6AddressesEntry 67108864}

sr1645v2EthPrtSwF2VlanIpV6AddressesFlagsInterfaceId OBJECT-TYPE
   SYNTAX      INTEGER
               {
               no (0),
               yes (1)
               }
   MAX-ACCESS  read-only
   STATUS      current
   DESCRIPTION
      "Path: swPort.status.vlan.ipV6.addresses.flags.interfaceId

       Possibilities:
               no   (0)
               yes   (1)"
   ::= {sr1645v2EthPrtSwF2VlanIpV6AddressesEntry 83951616}

sr1645v2EthPrtSwF2VlanIpV6AddressesFlagsAnycast OBJECT-TYPE
   SYNTAX      INTEGER
               {
               no (0),
               yes (1)
               }
   MAX-ACCESS  read-only
   STATUS      current
   DESCRIPTION
      "Path: swPort.status.vlan.ipV6.addresses.flags.anycast

       Possibilities:
               no   (0)
               yes   (1)"
   ::= {sr1645v2EthPrtSwF2VlanIpV6AddressesEntry 84017152}

sr1645v2EthPrtSwF2VlanIpV6AddressesTimersValidLifeTime OBJECT-TYPE
   SYNTAX      TimeTicks
   MAX-ACCESS  read-only
   STATUS      current
   DESCRIPTION
      "Path: swPort.status.vlan.ipV6.addresses.timers.validLifeTime

       Time in centi-second."
   ::= {sr1645v2EthPrtSwF2VlanIpV6AddressesEntry 100794368}

sr1645v2EthPrtSwF2VlanIpV6AddressesTimersPrefLifeTime OBJECT-TYPE
   SYNTAX      TimeTicks
   MAX-ACCESS  read-only
   STATUS      current
   DESCRIPTION
      "Path: swPort.status.vlan.ipV6.addresses.timers.prefLifeTime

       Time in centi-second."
   ::= {sr1645v2EthPrtSwF2VlanIpV6AddressesEntry 100728832}

sr1645v2EthPrtSwF2VlanVlanArpCache OBJECT-TYPE
   SYNTAX      SEQUENCE OF Sr1645v2EthPrtSwF2VlanVlanArpCacheEntry
   MAX-ACCESS  not-accessible
   STATUS      current
   DESCRIPTION
      ""
   ::= {sr1645v2EthPrtSwF2Vlan 235601920}

sr1645v2EthPrtSwF2VlanVlanArpCacheEntry OBJECT-TYPE
   SYNTAX      Sr1645v2EthPrtSwF2VlanVlanArpCacheEntry
   MAX-ACCESS  not-accessible
   STATUS      current
   DESCRIPTION
      ""
   INDEX      { sr1645v2EthPrtSwF2VlanVlanArpCacheGlobalIx,
                sr1645v2EthPrtSwF2VlanTableIx,
                sr1645v2EthPrtSwF2VlanVlanArpCacheTableIx }
   ::= {sr1645v2EthPrtSwF2VlanVlanArpCache 1}

Sr1645v2EthPrtSwF2VlanVlanArpCacheEntry ::=
   SEQUENCE
      {
      sr1645v2EthPrtSwF2VlanVlanArpCacheGlobalIx
         GlobalIndex,
      sr1645v2EthPrtSwF2VlanVlanArpCacheTableIx
         TableIndex,
      sr1645v2EthPrtSwF2VlanVlanArpCacheMacAddress
         OCTET STRING,
      sr1645v2EthPrtSwF2VlanVlanArpCacheIpAddress
         IpAddress,
      sr1645v2EthPrtSwF2VlanVlanArpCacheType
         INTEGER,
      sr1645v2EthPrtSwF2VlanVlanArpCacheTimeOut
         TimeTicks
      }

sr1645v2EthPrtSwF2VlanVlanArpCacheGlobalIx OBJECT-TYPE
   SYNTAX      GlobalIndex
   MAX-ACCESS  not-accessible
   STATUS      current
   DESCRIPTION
      "The value of the tlsCntTreeGlobalIndex of the MANAGED OBJECT."
   ::= {sr1645v2EthPrtSwF2VlanVlanArpCacheEntry 10}

sr1645v2EthPrtSwF2VlanVlanArpCacheTableIx OBJECT-TYPE
   SYNTAX      TableIndex
   MAX-ACCESS  not-accessible
   STATUS      current
   DESCRIPTION
      ""
   ::= {sr1645v2EthPrtSwF2VlanVlanArpCacheEntry 11}

sr1645v2EthPrtSwF2VlanVlanArpCacheMacAddress OBJECT-TYPE
   SYNTAX      OCTET STRING
   MAX-ACCESS  read-only
   STATUS      current
   DESCRIPTION
      "Path: swPort.status.vlan.vlan.arpCache.macAddress

       MAC address."
   ::= {sr1645v2EthPrtSwF2VlanVlanArpCacheEntry 16777216}

sr1645v2EthPrtSwF2VlanVlanArpCacheIpAddress OBJECT-TYPE
   SYNTAX      IpAddress
   MAX-ACCESS  read-only
   STATUS      current
   DESCRIPTION
      "Path: swPort.status.vlan.vlan.arpCache.ipAddress"
   ::= {sr1645v2EthPrtSwF2VlanVlanArpCacheEntry 33554432}

sr1645v2EthPrtSwF2VlanVlanArpCacheType OBJECT-TYPE
   SYNTAX      INTEGER
               {
               static (0),
               dynamic (1)
               }
   MAX-ACCESS  read-only
   STATUS      current
   DESCRIPTION
      "Path: swPort.status.vlan.vlan.arpCache.type

       Possibilities:
               static   (0)
               dynamic   (1)"
   ::= {sr1645v2EthPrtSwF2VlanVlanArpCacheEntry 50331648}

sr1645v2EthPrtSwF2VlanVlanArpCacheTimeOut OBJECT-TYPE
   SYNTAX      TimeTicks
   MAX-ACCESS  read-only
   STATUS      current
   DESCRIPTION
      "Path: swPort.status.vlan.vlan.arpCache.timeOut

       Time in centi-second."
   ::= {sr1645v2EthPrtSwF2VlanVlanArpCacheEntry 67108864}


sr1645v2EthPrtSwF2PppOE OBJECT IDENTIFIER ::= {sr1645v2EthPrtSwF2 36}

sr1645v2EthPrtSwF2PppOESSCTable OBJECT-TYPE
   SYNTAX      SEQUENCE OF Sr1645v2EthPrtSwF2PppOEEntry
   MAX-ACCESS  not-accessible
   STATUS      current
   DESCRIPTION
      ""
   ::= {sr1645v2EthPrtSwF2PppOE 1}

sr1645v2EthPrtSwF2PppOEEntry OBJECT-TYPE
   SYNTAX      Sr1645v2EthPrtSwF2PppOEEntry
   MAX-ACCESS  not-accessible
   STATUS      current
   DESCRIPTION
      ""
   INDEX      { sr1645v2EthPrtSwF2PppOEGlobalIx,
                sr1645v2EthPrtSwF2PppOETableIx }
   ::= {sr1645v2EthPrtSwF2PppOESSCTable 1}

Sr1645v2EthPrtSwF2PppOEEntry ::=
   SEQUENCE
      {
      sr1645v2EthPrtSwF2PppOEGlobalIx
         GlobalIndex,
      sr1645v2EthPrtSwF2PppOETableIx
         TableIndex,
      sr1645v2EthPrtSwF2PppOEName
         DisplayString,
      sr1645v2EthPrtSwF2PppOEMode
         INTEGER,
      sr1645v2EthPrtSwF2PppOEIfOperStatus
         INTEGER,
      sr1645v2EthPrtSwF2PppOEIfLastChange
         TimeTicks,
      sr1645v2EthPrtSwF2PppOEIfLastChangeDate
         DisplayString,
      sr1645v2EthPrtSwF2PppOEIpAddress
         IpAddress,
      sr1645v2EthPrtSwF2PppOEIpNetMask
         IpAddress,
      sr1645v2EthPrtSwF2PppOEIpRemote
         IpAddress,
      sr1645v2EthPrtSwF2PppOEPppOEthDiscState
         INTEGER,
      sr1645v2EthPrtSwF2PppOEPppOEthPeerMac
         OCTET STRING,
      sr1645v2EthPrtSwF2PppOEPppOEthServiceName
         DisplayString,
      sr1645v2EthPrtSwF2PppOEPppLcpState
         INTEGER,
      sr1645v2EthPrtSwF2PppOEPppIpcpState
         INTEGER,
      sr1645v2EthPrtSwF2PppOEPppIp6cpState
         INTEGER,
      sr1645v2EthPrtSwF2PppOEPppMyAutSt
         INTEGER,
      sr1645v2EthPrtSwF2PppOEPppHisAutSt
         INTEGER,
      sr1645v2EthPrtSwF2PppOEPppMru
         Integer32,
      sr1645v2EthPrtSwF2PppOEIpV6State
         INTEGER,
      sr1645v2EthPrtSwF2PppOEIpV6InterfaceId
         OCTET STRING,
      sr1645v2EthPrtSwF2PppOEIpV6LinkMtu
         Integer32,
      sr1645v2EthPrtSwF2PppOEIpV6HopLimit
         Integer32,
      sr1645v2EthPrtSwF2PppOEIpV6DhcpIaid
         Counter32,
      sr1645v2EthPrtSwF2PppOEIpV6RaRcvOption
         Integer32
      }

sr1645v2EthPrtSwF2PppOEGlobalIx OBJECT-TYPE
   SYNTAX      GlobalIndex
   MAX-ACCESS  not-accessible
   STATUS      current
   DESCRIPTION
      "The value of the tlsCntTreeGlobalIndex of the MANAGED OBJECT."
   ::= {sr1645v2EthPrtSwF2PppOEEntry 10}

sr1645v2EthPrtSwF2PppOETableIx OBJECT-TYPE
   SYNTAX      TableIndex
   MAX-ACCESS  not-accessible
   STATUS      current
   DESCRIPTION
      ""
   ::= {sr1645v2EthPrtSwF2PppOEEntry 11}

sr1645v2EthPrtSwF2PppOEName OBJECT-TYPE
   SYNTAX      DisplayString
   MAX-ACCESS  read-only
   STATUS      current
   DESCRIPTION
      "Path: swPort.status.pppoEClient.name"
   ::= {sr1645v2EthPrtSwF2PppOEEntry 16777216}

sr1645v2EthPrtSwF2PppOEMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: swPort.status.pppoEClient.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1645v2EthPrtSwF2PppOEEntry 335544320}

sr1645v2EthPrtSwF2PppOEIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: swPort.status.pppoEClient.ifOperStatus

       Possibilities:
               up   (1)
               down   (2)
               testing   (3)
               unknown   (4)
               dormant   (5)
               notPresent   (6)
               lowerLayerDown   (7)"
   ::= {sr1645v2EthPrtSwF2PppOEEntry 1795162112}

sr1645v2EthPrtSwF2PppOEIfLastChange OBJECT-TYPE
   SYNTAX      TimeTicks
   MAX-ACCESS  read-only
   STATUS      current
   DESCRIPTION
      "Path: swPort.status.pppoEClient.ifLastChange

       Time in centi-second."
   ::= {sr1645v2EthPrtSwF2PppOEEntry 1811939328}

sr1645v2EthPrtSwF2PppOEIfLastChangeDate OBJECT-TYPE
   SYNTAX      DisplayString
   MAX-ACCESS  read-only
   STATUS      current
   DESCRIPTION
      "Path: swPort.status.pppoEClient.ifLastChangeDate"
   ::= {sr1645v2EthPrtSwF2PppOEEntry 3070230528}

sr1645v2EthPrtSwF2PppOEIpAddress OBJECT-TYPE
   SYNTAX      IpAddress
   MAX-ACCESS  read-only
   STATUS      current
   DESCRIPTION
      "Path: swPort.status.pppoEClient.ip.address"
   ::= {sr1645v2EthPrtSwF2PppOEEntry 51380224}

sr1645v2EthPrtSwF2PppOEIpNetMask OBJECT-TYPE
   SYNTAX      IpAddress
   MAX-ACCESS  read-only
   STATUS      current
   DESCRIPTION
      "Path: swPort.status.pppoEClient.ip.netMask"
   ::= {sr1645v2EthPrtSwF2PppOEEntry 51445760}

sr1645v2EthPrtSwF2PppOEIpRemote OBJECT-TYPE
   SYNTAX      IpAddress
   MAX-ACCESS  read-only
   STATUS      current
   DESCRIPTION
      "Path: swPort.status.pppoEClient.ip.remote"
   ::= {sr1645v2EthPrtSwF2PppOEEntry 51511296}

sr1645v2EthPrtSwF2PppOEPppOEthDiscState OBJECT-TYPE
   SYNTAX      INTEGER
               {
               idle (0),
               waitForPADO (1),
               waitForPADS (2),
               established (3)
               }
   MAX-ACCESS  read-only
   STATUS      current
   DESCRIPTION
      "Path: swPort.status.pppoEClient.pppOverEth.discState

       Possibilities:
               idle   (0)
               waitForPADO   (1)
               waitForPADS   (2)
               established   (3)"
   ::= {sr1645v2EthPrtSwF2PppOEEntry 67174400}

sr1645v2EthPrtSwF2PppOEPppOEthPeerMac OBJECT-TYPE
   SYNTAX      OCTET STRING
   MAX-ACCESS  read-only
   STATUS      current
   DESCRIPTION
      "Path: swPort.status.pppoEClient.pppOverEth.remoteMacAddress

       MAC address."
   ::= {sr1645v2EthPrtSwF2PppOEEntry 67239936}

sr1645v2EthPrtSwF2PppOEPppOEthServiceName OBJECT-TYPE
   SYNTAX      DisplayString
   MAX-ACCESS  read-only
   STATUS      current
   DESCRIPTION
      "Path: swPort.status.pppoEClient.pppOverEth.serviceName"
   ::= {sr1645v2EthPrtSwF2PppOEEntry 67305472}

sr1645v2EthPrtSwF2PppOEPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: swPort.status.pppoEClient.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2EthPrtSwF2PppOEEntry 83951616}

sr1645v2EthPrtSwF2PppOEPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: swPort.status.pppoEClient.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2EthPrtSwF2PppOEEntry 84017152}

sr1645v2EthPrtSwF2PppOEPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: swPort.status.pppoEClient.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2EthPrtSwF2PppOEEntry 84869120}

sr1645v2EthPrtSwF2PppOEPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: swPort.status.pppoEClient.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1645v2EthPrtSwF2PppOEEntry 84541440}

sr1645v2EthPrtSwF2PppOEPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: swPort.status.pppoEClient.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1645v2EthPrtSwF2PppOEEntry 84606976}

sr1645v2EthPrtSwF2PppOEPppMru OBJECT-TYPE
   SYNTAX      Integer32
   MAX-ACCESS  read-only
   STATUS      current
   DESCRIPTION
      "Path: swPort.status.pppoEClient.ppp.mru"
   ::= {sr1645v2EthPrtSwF2PppOEEntry 84934656}

sr1645v2EthPrtSwF2PppOEIpV6State OBJECT-TYPE
   SYNTAX      INTEGER
               {
               disabled (0),
               enabled (1)
               }
   MAX-ACCESS  read-only
   STATUS      current
   DESCRIPTION
      "Path: swPort.status.pppoEClient.ipV6.state

       Possibilities:
               disabled   (0)
               enabled   (1)"
   ::= {sr1645v2EthPrtSwF2PppOEEntry 100728832}

sr1645v2EthPrtSwF2PppOEIpV6InterfaceId OBJECT-TYPE
   SYNTAX      OCTET STRING
   MAX-ACCESS  read-only
   STATUS      current
   DESCRIPTION
      "Path: swPort.status.pppoEClient.ipV6.interfaceId"
   ::= {sr1645v2EthPrtSwF2PppOEEntry 100794368}

sr1645v2EthPrtSwF2PppOEIpV6LinkMtu OBJECT-TYPE
   SYNTAX      Integer32
   MAX-ACCESS  read-only
   STATUS      current
   DESCRIPTION
      "Path: swPort.status.pppoEClient.ipV6.linkMtu"
   ::= {sr1645v2EthPrtSwF2PppOEEntry 100925440}

sr1645v2EthPrtSwF2PppOEIpV6HopLimit OBJECT-TYPE
   SYNTAX      Integer32
   MAX-ACCESS  read-only
   STATUS      current
   DESCRIPTION
      "Path: swPort.status.pppoEClient.ipV6.hopLimit"
   ::= {sr1645v2EthPrtSwF2PppOEEntry 100990976}

sr1645v2EthPrtSwF2PppOEIpV6DhcpIaid OBJECT-TYPE
   SYNTAX      Counter32
   MAX-ACCESS  read-only
   STATUS      current
   DESCRIPTION
      "Path: swPort.status.pppoEClient.ipV6.dhcp.iaid

       32 bit unsigned wrappable counter."
   ::= {sr1645v2EthPrtSwF2PppOEEntry 101056768}

sr1645v2EthPrtSwF2PppOEIpV6RaRcvOption OBJECT-TYPE
   SYNTAX      Integer32
   MAX-ACCESS  read-only
   STATUS      current
   DESCRIPTION
      "Path: swPort.status.pppoEClient.ipV6.raRcvOption

       Bit meanings:
               bit 0 = linkMtu,
               bit 1 = srcLinkLayer,
               bit 2 = prefixInfo,
               bit 3 = rdnss,
               bit 4 = dnssl"
   ::= {sr1645v2EthPrtSwF2PppOEEntry 101122048}

sr1645v2EthPrtSwF2PppOEIpV6Addresses OBJECT-TYPE
   SYNTAX      SEQUENCE OF Sr1645v2EthPrtSwF2PppOEIpV6AddressesEntry
   MAX-ACCESS  not-accessible
   STATUS      current
   DESCRIPTION
      ""
   ::= {sr1645v2EthPrtSwF2PppOE 100859904}

sr1645v2EthPrtSwF2PppOEIpV6AddressesEntry OBJECT-TYPE
   SYNTAX      Sr1645v2EthPrtSwF2PppOEIpV6AddressesEntry
   MAX-ACCESS  not-accessible
   STATUS      current
   DESCRIPTION
      ""
   INDEX      { sr1645v2EthPrtSwF2PppOEIpV6AddressesGlobalIx,
                sr1645v2EthPrtSwF2PppOETableIx,
                sr1645v2EthPrtSwF2PppOEIpV6AddressesTableIx }
   ::= {sr1645v2EthPrtSwF2PppOEIpV6Addresses 1}

Sr1645v2EthPrtSwF2PppOEIpV6AddressesEntry ::=
   SEQUENCE
      {
      sr1645v2EthPrtSwF2PppOEIpV6AddressesGlobalIx
         GlobalIndex,
      sr1645v2EthPrtSwF2PppOEIpV6AddressesTableIx
         TableIndex,
      sr1645v2EthPrtSwF2PppOEIpV6AddressesAddress
         Ipv6Address,
      sr1645v2EthPrtSwF2PppOEIpV6AddressesPrefixLength
         Integer32,
      sr1645v2EthPrtSwF2PppOEIpV6AddressesStatus
         INTEGER,
      sr1645v2EthPrtSwF2PppOEIpV6AddressesOrigin
         INTEGER,
      sr1645v2EthPrtSwF2PppOEIpV6AddressesFlagsInterfaceId
         INTEGER,
      sr1645v2EthPrtSwF2PppOEIpV6AddressesFlagsAnycast
         INTEGER,
      sr1645v2EthPrtSwF2PppOEIpV6AddressesTimersValidLifeTime
         TimeTicks,
      sr1645v2EthPrtSwF2PppOEIpV6AddressesTimersPrefLifeTime
         TimeTicks
      }

sr1645v2EthPrtSwF2PppOEIpV6AddressesGlobalIx OBJECT-TYPE
   SYNTAX      GlobalIndex
   MAX-ACCESS  not-accessible
   STATUS      current
   DESCRIPTION
      "The value of the tlsCntTreeGlobalIndex of the MANAGED OBJECT."
   ::= {sr1645v2EthPrtSwF2PppOEIpV6AddressesEntry 10}

sr1645v2EthPrtSwF2PppOEIpV6AddressesTableIx OBJECT-TYPE
   SYNTAX      TableIndex
   MAX-ACCESS  not-accessible
   STATUS      current
   DESCRIPTION
      ""
   ::= {sr1645v2EthPrtSwF2PppOEIpV6AddressesEntry 11}

sr1645v2EthPrtSwF2PppOEIpV6AddressesAddress OBJECT-TYPE
   SYNTAX      Ipv6Address
   MAX-ACCESS  read-only
   STATUS      current
   DESCRIPTION
      "Path: swPort.status.pppoEClient.ipV6.addresses.address

       ipv6 address"
   ::= {sr1645v2EthPrtSwF2PppOEIpV6AddressesEntry 16777216}

sr1645v2EthPrtSwF2PppOEIpV6AddressesPrefixLength OBJECT-TYPE
   SYNTAX      Integer32
   MAX-ACCESS  read-only
   STATUS      current
   DESCRIPTION
      "Path: swPort.status.pppoEClient.ipV6.addresses.prefixLength"
   ::= {sr1645v2EthPrtSwF2PppOEIpV6AddressesEntry 33554432}

sr1645v2EthPrtSwF2PppOEIpV6AddressesStatus OBJECT-TYPE
   SYNTAX      INTEGER
               {
               invalid (0),
               tentative (1),
               deprecated (2),
               preferred (3)
               }
   MAX-ACCESS  read-only
   STATUS      current
   DESCRIPTION
      "Path: swPort.status.pppoEClient.ipV6.addresses.status

       Possibilities:
               invalid   (0)
               tentative   (1)
               deprecated   (2)
               preferred   (3)"
   ::= {sr1645v2EthPrtSwF2PppOEIpV6AddressesEntry 50331648}

sr1645v2EthPrtSwF2PppOEIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: swPort.status.pppoEClient.ipV6.addresses.origin

       Possibilities:
               unknown   (0)
               manual   (1)
               generalPrefix   (2)
               statelessAuto   (3)
               statefullAuto   (4)"
   ::= {sr1645v2EthPrtSwF2PppOEIpV6AddressesEntry 67108864}

sr1645v2EthPrtSwF2PppOEIpV6AddressesFlagsInterfaceId OBJECT-TYPE
   SYNTAX      INTEGER
               {
               no (0),
               yes (1)
               }
   MAX-ACCESS  read-only
   STATUS      current
   DESCRIPTION
      "Path: swPort.status.pppoEClient.ipV6.addresses.flags.interfaceId

       Possibilities:
               no   (0)
               yes   (1)"
   ::= {sr1645v2EthPrtSwF2PppOEIpV6AddressesEntry 83951616}

sr1645v2EthPrtSwF2PppOEIpV6AddressesFlagsAnycast OBJECT-TYPE
   SYNTAX      INTEGER
               {
               no (0),
               yes (1)
               }
   MAX-ACCESS  read-only
   STATUS      current
   DESCRIPTION
      "Path: swPort.status.pppoEClient.ipV6.addresses.flags.anycast

       Possibilities:
               no   (0)
               yes   (1)"
   ::= {sr1645v2EthPrtSwF2PppOEIpV6AddressesEntry 84017152}

sr1645v2EthPrtSwF2PppOEIpV6AddressesTimersValidLifeTime OBJECT-TYPE
   SYNTAX      TimeTicks
   MAX-ACCESS  read-only
   STATUS      current
   DESCRIPTION
      "Path: swPort.status.pppoEClient.ipV6.addresses.timers.validLifeTime

       Time in centi-second."
   ::= {sr1645v2EthPrtSwF2PppOEIpV6AddressesEntry 100794368}

sr1645v2EthPrtSwF2PppOEIpV6AddressesTimersPrefLifeTime OBJECT-TYPE
   SYNTAX      TimeTicks
   MAX-ACCESS  read-only
   STATUS      current
   DESCRIPTION
      "Path: swPort.status.pppoEClient.ipV6.addresses.timers.prefLifeTime

       Time in centi-second."
   ::= {sr1645v2EthPrtSwF2PppOEIpV6AddressesEntry 100728832}


sr1645v2EthPrtSwF2Dot1x OBJECT IDENTIFIER ::= {sr1645v2EthPrtSwF2 190}

sr1645v2EthPrtSwF2Dot1xSSCTable OBJECT-TYPE
   SYNTAX      SEQUENCE OF Sr1645v2EthPrtSwF2Dot1xEntry
   MAX-ACCESS  not-accessible
   STATUS      current
   DESCRIPTION
      "Ethernet Switch VLAN Table"
   ::= {sr1645v2EthPrtSwF2Dot1x 1}

sr1645v2EthPrtSwF2Dot1xEntry OBJECT-TYPE
   SYNTAX      Sr1645v2EthPrtSwF2Dot1xEntry
   MAX-ACCESS  not-accessible
   STATUS      current
   DESCRIPTION
      ""
   INDEX      { sr1645v2EthPrtSwF2Dot1xGlobalIx,
                sr1645v2EthPrtSwF2Dot1xTableIx }
   ::= {sr1645v2EthPrtSwF2Dot1xSSCTable 1}

Sr1645v2EthPrtSwF2Dot1xEntry ::=
   SEQUENCE
      {
      sr1645v2EthPrtSwF2Dot1xGlobalIx
         GlobalIndex,
      sr1645v2EthPrtSwF2Dot1xTableIx
         TableIndex,
      sr1645v2EthPrtSwF2Dot1xRemote
         OCTET STRING,
      sr1645v2EthPrtSwF2Dot1xAuthorized
         INTEGER,
      sr1645v2EthPrtSwF2Dot1xAuthenticator
         INTEGER,
      sr1645v2EthPrtSwF2Dot1xBackEnd
         INTEGER,
      sr1645v2EthPrtSwF2Dot1xRetries
         Integer32,
      sr1645v2EthPrtSwF2Dot1xReAuthTime
         TimeTicks,
      sr1645v2EthPrtSwF2Dot1xHoldTime
         TimeTicks
      }

sr1645v2EthPrtSwF2Dot1xGlobalIx OBJECT-TYPE
   SYNTAX      GlobalIndex
   MAX-ACCESS  not-accessible
   STATUS      current
   DESCRIPTION
      "The value of the tlsCntTreeGlobalIndex of the MANAGED OBJECT."
   ::= {sr1645v2EthPrtSwF2Dot1xEntry 10}

sr1645v2EthPrtSwF2Dot1xTableIx OBJECT-TYPE
   SYNTAX      TableIndex
   MAX-ACCESS  not-accessible
   STATUS      current
   DESCRIPTION
      ""
   ::= {sr1645v2EthPrtSwF2Dot1xEntry 11}

sr1645v2EthPrtSwF2Dot1xRemote OBJECT-TYPE
   SYNTAX      OCTET STRING
   MAX-ACCESS  read-only
   STATUS      current
   DESCRIPTION
      "Path: swPort.status.dot1x.remote

       MAC address."
   ::= {sr1645v2EthPrtSwF2Dot1xEntry 16777216}

sr1645v2EthPrtSwF2Dot1xAuthorized OBJECT-TYPE
   SYNTAX      INTEGER
               {
               no (0),
               yes (1)
               }
   MAX-ACCESS  read-only
   STATUS      current
   DESCRIPTION
      "Path: swPort.status.dot1x.authorized

       Possibilities:
               no   (0)
               yes   (1)"
   ::= {sr1645v2EthPrtSwF2Dot1xEntry 33554432}

sr1645v2EthPrtSwF2Dot1xAuthenticator OBJECT-TYPE
   SYNTAX      INTEGER
               {
               preInit (0),
               initialize (1),
               disconnected (2),
               restart (3),
               connecting (4),
               authenticating (5),
               authenticated (6),
               aborting (7),
               held (8),
               forceAuth (9),
               forceUnauth (10)
               }
   MAX-ACCESS  read-only
   STATUS      current
   DESCRIPTION
      "Path: swPort.status.dot1x.authenticator

       Possibilities:
               preInit   (0)
               initialize   (1)
               disconnected   (2)
               restart   (3)
               connecting   (4)
               authenticating   (5)
               authenticated   (6)
               aborting   (7)
               held   (8)
               forceAuth   (9)
               forceUnauth   (10)"
   ::= {sr1645v2EthPrtSwF2Dot1xEntry 50331648}

sr1645v2EthPrtSwF2Dot1xBackEnd OBJECT-TYPE
   SYNTAX      INTEGER
               {
               preInit (0),
               initialize (1),
               idle (2),
               request (3),
               response (4),
               success (5),
               failure (6),
               radiusTimeout (7),
               timeout (8)
               }
   MAX-ACCESS  read-only
   STATUS      current
   DESCRIPTION
      "Path: swPort.status.dot1x.backEnd

       Possibilities:
               preInit   (0)
               initialize   (1)
               idle   (2)
               request   (3)
               response   (4)
               success   (5)
               failure   (6)
               radiusTimeout   (7)
               timeout   (8)"
   ::= {sr1645v2EthPrtSwF2Dot1xEntry 67108864}

sr1645v2EthPrtSwF2Dot1xRetries OBJECT-TYPE
   SYNTAX      Integer32
   MAX-ACCESS  read-only
   STATUS      current
   DESCRIPTION
      "Path: swPort.status.dot1x.retries"
   ::= {sr1645v2EthPrtSwF2Dot1xEntry 83886080}

sr1645v2EthPrtSwF2Dot1xReAuthTime OBJECT-TYPE
   SYNTAX      TimeTicks
   MAX-ACCESS  read-only
   STATUS      current
   DESCRIPTION
      "Path: swPort.status.dot1x.reAuthTime

       Time in centi-second."
   ::= {sr1645v2EthPrtSwF2Dot1xEntry 100663296}

sr1645v2EthPrtSwF2Dot1xHoldTime OBJECT-TYPE
   SYNTAX      TimeTicks
   MAX-ACCESS  read-only
   STATUS      current
   DESCRIPTION
      "Path: swPort.status.dot1x.holdTime

       Time in centi-second."
   ::= {sr1645v2EthPrtSwF2Dot1xEntry 117440512}


sr1645v2EthPrtSwF2IpV6 OBJECT IDENTIFIER ::= {sr1645v2EthPrtSwF2 17}

sr1645v2EthPrtSwF2IpV6SSCTable OBJECT-TYPE
   SYNTAX      SEQUENCE OF Sr1645v2EthPrtSwF2IpV6Entry
   MAX-ACCESS  not-accessible
   STATUS      current
   DESCRIPTION
      "IPv6 interface config parameters"
   ::= {sr1645v2EthPrtSwF2IpV6 1}

sr1645v2EthPrtSwF2IpV6Entry OBJECT-TYPE
   SYNTAX      Sr1645v2EthPrtSwF2IpV6Entry
   MAX-ACCESS  not-accessible
   STATUS      current
   DESCRIPTION
      ""
   INDEX      { sr1645v2EthPrtSwF2IpV6GlobalIx }
   ::= {sr1645v2EthPrtSwF2IpV6SSCTable 1}

Sr1645v2EthPrtSwF2IpV6Entry ::=
   SEQUENCE
      {
      sr1645v2EthPrtSwF2IpV6GlobalIx
         GlobalIndex,
      sr1645v2EthPrtSwF2IpV6State
         INTEGER,
      sr1645v2EthPrtSwF2IpV6InterfaceId
         OCTET STRING,
      sr1645v2EthPrtSwF2IpV6LinkMtu
         Integer32,
      sr1645v2EthPrtSwF2IpV6HopLimit
         Integer32,
      sr1645v2EthPrtSwF2IpV6DhcpIaid
         Counter32,
      sr1645v2EthPrtSwF2IpV6RaRcvOption
         Integer32
      }

sr1645v2EthPrtSwF2IpV6GlobalIx OBJECT-TYPE
   SYNTAX      GlobalIndex
   MAX-ACCESS  not-accessible
   STATUS      current
   DESCRIPTION
      "The value of the tlsCntTreeGlobalIndex of the MANAGED OBJECT."
   ::= {sr1645v2EthPrtSwF2IpV6Entry 10}

sr1645v2EthPrtSwF2IpV6State OBJECT-TYPE
   SYNTAX      INTEGER
               {
               disabled (0),
               enabled (1)
               }
   MAX-ACCESS  read-only
   STATUS      current
   DESCRIPTION
      "Path: swPort.status.ipV6.state

       Possibilities:
               disabled   (0)
               enabled   (1)"
   ::= {sr1645v2EthPrtSwF2IpV6Entry 16777216}

sr1645v2EthPrtSwF2IpV6InterfaceId OBJECT-TYPE
   SYNTAX      OCTET STRING
   MAX-ACCESS  read-only
   STATUS      current
   DESCRIPTION
      "Path: swPort.status.ipV6.interfaceId"
   ::= {sr1645v2EthPrtSwF2IpV6Entry 33554432}

sr1645v2EthPrtSwF2IpV6LinkMtu OBJECT-TYPE
   SYNTAX      Integer32
   MAX-ACCESS  read-only
   STATUS      current
   DESCRIPTION
      "Path: swPort.status.ipV6.linkMtu"
   ::= {sr1645v2EthPrtSwF2IpV6Entry 67108864}

sr1645v2EthPrtSwF2IpV6HopLimit OBJECT-TYPE
   SYNTAX      Integer32
   MAX-ACCESS  read-only
   STATUS      current
   DESCRIPTION
      "Path: swPort.status.ipV6.hopLimit"
   ::= {sr1645v2EthPrtSwF2IpV6Entry 83886080}

sr1645v2EthPrtSwF2IpV6DhcpIaid OBJECT-TYPE
   SYNTAX      Counter32
   MAX-ACCESS  read-only
   STATUS      current
   DESCRIPTION
      "Path: swPort.status.ipV6.dhcp.iaid

       32 bit unsigned wrappable counter."
   ::= {sr1645v2EthPrtSwF2IpV6Entry 100728832}

sr1645v2EthPrtSwF2IpV6RaRcvOption OBJECT-TYPE
   SYNTAX      Integer32
   MAX-ACCESS  read-only
   STATUS      current
   DESCRIPTION
      "Path: swPort.status.ipV6.raRcvOption

       Bit meanings:
               bit 0 = linkMtu,
               bit 1 = srcLinkLayer,
               bit 2 = prefixInfo,
               bit 3 = rdnss,
               bit 4 = dnssl"
   ::= {sr1645v2EthPrtSwF2IpV6Entry 117440512}

sr1645v2EthPrtSwF2IpV6Addresses OBJECT-TYPE
   SYNTAX      SEQUENCE OF Sr1645v2EthPrtSwF2IpV6AddressesEntry
   MAX-ACCESS  not-accessible
   STATUS      current
   DESCRIPTION
      ""
   ::= {sr1645v2EthPrtSwF2IpV6 50331648}

sr1645v2EthPrtSwF2IpV6AddressesEntry OBJECT-TYPE
   SYNTAX      Sr1645v2EthPrtSwF2IpV6AddressesEntry
   MAX-ACCESS  not-accessible
   STATUS      current
   DESCRIPTION
      ""
   INDEX      { sr1645v2EthPrtSwF2IpV6AddressesGlobalIx,
                sr1645v2EthPrtSwF2IpV6AddressesTableIx }
   ::= {sr1645v2EthPrtSwF2IpV6Addresses 1}

Sr1645v2EthPrtSwF2IpV6AddressesEntry ::=
   SEQUENCE
      {
      sr1645v2EthPrtSwF2IpV6AddressesGlobalIx
         GlobalIndex,
      sr1645v2EthPrtSwF2IpV6AddressesTableIx
         TableIndex,
      sr1645v2EthPrtSwF2IpV6AddressesAddress
         Ipv6Address,
      sr1645v2EthPrtSwF2IpV6AddressesPrefixLength
         Integer32,
      sr1645v2EthPrtSwF2IpV6AddressesStatus
         INTEGER,
      sr1645v2EthPrtSwF2IpV6AddressesOrigin
         INTEGER,
      sr1645v2EthPrtSwF2IpV6AddressesFlagsInterfaceId
         INTEGER,
      sr1645v2EthPrtSwF2IpV6AddressesFlagsAnycast
         INTEGER,
      sr1645v2EthPrtSwF2IpV6AddressesTimersValidLifeTime
         TimeTicks,
      sr1645v2EthPrtSwF2IpV6AddressesTimersPrefLifeTime
         TimeTicks
      }

sr1645v2EthPrtSwF2IpV6AddressesGlobalIx OBJECT-TYPE
   SYNTAX      GlobalIndex
   MAX-ACCESS  not-accessible
   STATUS      current
   DESCRIPTION
      "The value of the tlsCntTreeGlobalIndex of the MANAGED OBJECT."
   ::= {sr1645v2EthPrtSwF2IpV6AddressesEntry 10}

sr1645v2EthPrtSwF2IpV6AddressesTableIx OBJECT-TYPE
   SYNTAX      TableIndex
   MAX-ACCESS  not-accessible
   STATUS      current
   DESCRIPTION
      ""
   ::= {sr1645v2EthPrtSwF2IpV6AddressesEntry 11}

sr1645v2EthPrtSwF2IpV6AddressesAddress OBJECT-TYPE
   SYNTAX      Ipv6Address
   MAX-ACCESS  read-only
   STATUS      current
   DESCRIPTION
      "Path: swPort.status.ipV6.addresses.address

       ipv6 address"
   ::= {sr1645v2EthPrtSwF2IpV6AddressesEntry 16777216}

sr1645v2EthPrtSwF2IpV6AddressesPrefixLength OBJECT-TYPE
   SYNTAX      Integer32
   MAX-ACCESS  read-only
   STATUS      current
   DESCRIPTION
      "Path: swPort.status.ipV6.addresses.prefixLength"
   ::= {sr1645v2EthPrtSwF2IpV6AddressesEntry 33554432}

sr1645v2EthPrtSwF2IpV6AddressesStatus OBJECT-TYPE
   SYNTAX      INTEGER
               {
               invalid (0),
               tentative (1),
               deprecated (2),
               preferred (3)
               }
   MAX-ACCESS  read-only
   STATUS      current
   DESCRIPTION
      "Path: swPort.status.ipV6.addresses.status

       Possibilities:
               invalid   (0)
               tentative   (1)
               deprecated   (2)
               preferred   (3)"
   ::= {sr1645v2EthPrtSwF2IpV6AddressesEntry 50331648}

sr1645v2EthPrtSwF2IpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: swPort.status.ipV6.addresses.origin

       Possibilities:
               unknown   (0)
               manual   (1)
               generalPrefix   (2)
               statelessAuto   (3)
               statefullAuto   (4)"
   ::= {sr1645v2EthPrtSwF2IpV6AddressesEntry 67108864}

sr1645v2EthPrtSwF2IpV6AddressesFlagsInterfaceId OBJECT-TYPE
   SYNTAX      INTEGER
               {
               no (0),
               yes (1)
               }
   MAX-ACCESS  read-only
   STATUS      current
   DESCRIPTION
      "Path: swPort.status.ipV6.addresses.flags.interfaceId

       Possibilities:
               no   (0)
               yes   (1)"
   ::= {sr1645v2EthPrtSwF2IpV6AddressesEntry 83951616}

sr1645v2EthPrtSwF2IpV6AddressesFlagsAnycast OBJECT-TYPE
   SYNTAX      INTEGER
               {
               no (0),
               yes (1)
               }
   MAX-ACCESS  read-only
   STATUS      current
   DESCRIPTION
      "Path: swPort.status.ipV6.addresses.flags.anycast

       Possibilities:
               no   (0)
               yes   (1)"
   ::= {sr1645v2EthPrtSwF2IpV6AddressesEntry 84017152}

sr1645v2EthPrtSwF2IpV6AddressesTimersValidLifeTime OBJECT-TYPE
   SYNTAX      TimeTicks
   MAX-ACCESS  read-only
   STATUS      current
   DESCRIPTION
      "Path: swPort.status.ipV6.addresses.timers.validLifeTime

       Time in centi-second."
   ::= {sr1645v2EthPrtSwF2IpV6AddressesEntry 100794368}

sr1645v2EthPrtSwF2IpV6AddressesTimersPrefLifeTime OBJECT-TYPE
   SYNTAX      TimeTicks
   MAX-ACCESS  read-only
   STATUS      current
   DESCRIPTION
      "Path: swPort.status.ipV6.addresses.timers.prefLifeTime

       Time in centi-second."
   ::= {sr1645v2EthPrtSwF2IpV6AddressesEntry 100728832}


sr1645v2EthPrtSwF2SnmpIndex OBJECT IDENTIFIER ::= {sr1645v2EthPrtSwF2 269}

sr1645v2EthPrtSwF2SnmpIndexTable OBJECT-TYPE
   SYNTAX      SEQUENCE OF Sr1645v2EthPrtSwF2SnmpIndexEntry
   MAX-ACCESS  not-accessible
   STATUS      current
   DESCRIPTION
      "SNMP index assigned to this object"
   ::= {sr1645v2EthPrtSwF2SnmpIndex 1}

sr1645v2EthPrtSwF2SnmpIndexEntry OBJECT-TYPE
   SYNTAX      Sr1645v2EthPrtSwF2SnmpIndexEntry
   MAX-ACCESS  not-accessible
   STATUS      current
   DESCRIPTION
      ""
   INDEX      { sr1645v2EthPrtSwF2SnmpIndexGlobalIx }
   ::= {sr1645v2EthPrtSwF2SnmpIndexTable 1}

Sr1645v2EthPrtSwF2SnmpIndexEntry ::=
   SEQUENCE
      {
      sr1645v2EthPrtSwF2SnmpIndexGlobalIx
         GlobalIndex,
      sr1645v2EthPrtSwF2SnmpIndexValue
         Integer32
      }

sr1645v2EthPrtSwF2SnmpIndexGlobalIx OBJECT-TYPE
   SYNTAX      GlobalIndex
   MAX-ACCESS  not-accessible
   STATUS      current
   DESCRIPTION
      "The value of the tlsCntTreeGlobalIndex of the MANAGED OBJECT."
   ::= {sr1645v2EthPrtSwF2SnmpIndexEntry 10}

sr1645v2EthPrtSwF2SnmpIndexValue OBJECT-TYPE
   SYNTAX      Integer32
   MAX-ACCESS  read-only
   STATUS      current
   DESCRIPTION
      "Path: swPort.status.snmpIndex"
   ::= {sr1645v2EthPrtSwF2SnmpIndexEntry 2147483648}


sr1645v2EthPrtSwF2Lst OBJECT IDENTIFIER ::= {sr1645v2EthPrtSwF2 18}

sr1645v2EthPrtSwF2LstSSCTable OBJECT-TYPE
   SYNTAX      SEQUENCE OF Sr1645v2EthPrtSwF2LstEntry
   MAX-ACCESS  not-accessible
   STATUS      current
   DESCRIPTION
      ""
   ::= {sr1645v2EthPrtSwF2Lst 1}

sr1645v2EthPrtSwF2LstEntry OBJECT-TYPE
   SYNTAX      Sr1645v2EthPrtSwF2LstEntry
   MAX-ACCESS  not-accessible
   STATUS      current
   DESCRIPTION
      ""
   INDEX      { sr1645v2EthPrtSwF2LstGlobalIx }
   ::= {sr1645v2EthPrtSwF2LstSSCTable 1}

Sr1645v2EthPrtSwF2LstEntry ::=
   SEQUENCE
      {
      sr1645v2EthPrtSwF2LstGlobalIx
         GlobalIndex,
      sr1645v2EthPrtSwF2LstTrackedInterface
         DisplayString,
      sr1645v2EthPrtSwF2LstIfOperStatus
         INTEGER
      }

sr1645v2EthPrtSwF2LstGlobalIx OBJECT-TYPE
   SYNTAX      GlobalIndex
   MAX-ACCESS  not-accessible
   STATUS      current
   DESCRIPTION
      "The value of the tlsCntTreeGlobalIndex of the MANAGED OBJECT."
   ::= {sr1645v2EthPrtSwF2LstEntry 10}

sr1645v2EthPrtSwF2LstTrackedInterface OBJECT-TYPE
   SYNTAX      DisplayString
   MAX-ACCESS  read-only
   STATUS      current
   DESCRIPTION
      "Path: swPort.status.linkStateTracking.trackedInterface"
   ::= {sr1645v2EthPrtSwF2LstEntry 16777216}

sr1645v2EthPrtSwF2LstIfOperStatus OBJECT-TYPE
   SYNTAX      INTEGER
               {
               up (1),
               down (2),
               testing (3),
               unknown (4),
               dormant (5),
               notPresent (6),
               lowerLayerDown (7),
               s (255)
               }
   MAX-ACCESS  read-only
   STATUS      current
   DESCRIPTION
      "Path: swPort.status.linkStateTracking.ifOperStatus

       Possibilities:
               up   (1)
               down   (2)
               testing   (3)
               unknown   (4)
               dormant   (5)
               notPresent   (6)
               lowerLayerDown   (7)
                  (255)"
   ::= {sr1645v2EthPrtSwF2LstEntry 50331648}


sr1645v2EthPrtSwF2HwPorts OBJECT IDENTIFIER ::= {sr1645v2EthPrtSwF2 270}

sr1645v2EthPrtSwF2HwPortsSSCTable OBJECT-TYPE
   SYNTAX      SEQUENCE OF Sr1645v2EthPrtSwF2HwPortsEntry
   MAX-ACCESS  not-accessible
   STATUS      current
   DESCRIPTION
      ""
   ::= {sr1645v2EthPrtSwF2HwPorts 1}

sr1645v2EthPrtSwF2HwPortsEntry OBJECT-TYPE
   SYNTAX      Sr1645v2EthPrtSwF2HwPortsEntry
   MAX-ACCESS  not-accessible
   STATUS      current
   DESCRIPTION
      ""
   INDEX      { sr1645v2EthPrtSwF2HwPortsGlobalIx,
                sr1645v2EthPrtSwF2HwPortsTableIx }
   ::= {sr1645v2EthPrtSwF2HwPortsSSCTable 1}

Sr1645v2EthPrtSwF2HwPortsEntry ::=
   SEQUENCE
      {
      sr1645v2EthPrtSwF2HwPortsGlobalIx
         GlobalIndex,
      sr1645v2EthPrtSwF2HwPortsTableIx
         TableIndex,
      sr1645v2EthPrtSwF2HwPortsHwPort
         INTEGER,
      sr1645v2EthPrtSwF2HwPortsStatus
         INTEGER
      }

sr1645v2EthPrtSwF2HwPortsGlobalIx OBJECT-TYPE
   SYNTAX      GlobalIndex
   MAX-ACCESS  not-accessible
   STATUS      current
   DESCRIPTION
      "The value of the tlsCntTreeGlobalIndex of the MANAGED OBJECT."
   ::= {sr1645v2EthPrtSwF2HwPortsEntry 10}

sr1645v2EthPrtSwF2HwPortsTableIx OBJECT-TYPE
   SYNTAX      TableIndex
   MAX-ACCESS  not-accessible
   STATUS      current
   DESCRIPTION
      ""
   ::= {sr1645v2EthPrtSwF2HwPortsEntry 11}

sr1645v2EthPrtSwF2HwPortsHwPort OBJECT-TYPE
   SYNTAX      INTEGER
               {
               hwPortu1 (1),
               hwPortu2 (2),
               hwPortu3 (3),
               hwPortu4 (4),
               hwPortu5 (5),
               hwPortu6 (6),
               hwPortu7 (7),
               hwPortu8 (8),
               hwPortuLocalPort (65535)
               }
   MAX-ACCESS  read-only
   STATUS      current
   DESCRIPTION
      "Path: swPort.status.hwPorts.hwPort

       Possibilities:
               hwPort_1   (1)
               hwPort_2   (2)
               hwPort_3   (3)
               hwPort_4   (4)
               hwPort_5   (5)
               hwPort_6   (6)
               hwPort_7   (7)
               hwPort_8   (8)
               hwPort_LocalPort   (65535)"
   ::= {sr1645v2EthPrtSwF2HwPortsEntry 16777216}

sr1645v2EthPrtSwF2HwPortsStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: swPort.status.hwPorts.status

       Possibilities:
               up   (1)
               down   (2)
               testing   (3)
               unknown   (4)
               dormant   (5)
               notPresent   (6)
               lowerLayerDown   (7)"
   ::= {sr1645v2EthPrtSwF2HwPortsEntry 33554432}



pr1645v2EthPrtSwF2 OBJECT IDENTIFIER ::= {r1645v2EthPrtSwF2 12}


pr1645v2EthPrtSwF2InOctets OBJECT IDENTIFIER ::= {pr1645v2EthPrtSwF2 109}

pr1645v2EthPrtSwF2InOctetsTable OBJECT-TYPE
   SYNTAX      SEQUENCE OF Pr1645v2EthPrtSwF2InOctetsEntry
   MAX-ACCESS  not-accessible
   STATUS      current
   DESCRIPTION
      "ifInOctets"
   ::= {pr1645v2EthPrtSwF2InOctets 1}

pr1645v2EthPrtSwF2InOctetsEntry OBJECT-TYPE
   SYNTAX      Pr1645v2EthPrtSwF2InOctetsEntry
   MAX-ACCESS  not-accessible
   STATUS      current
   DESCRIPTION
      ""
   INDEX      { pr1645v2EthPrtSwF2InOctetsGlobalIx }
   ::= {pr1645v2EthPrtSwF2InOctetsTable 1}

Pr1645v2EthPrtSwF2InOctetsEntry ::=
   SEQUENCE
      {
      pr1645v2EthPrtSwF2InOctetsGlobalIx
         GlobalIndex,
      pr1645v2EthPrtSwF2InOctetsValue
         Counter64
      }

pr1645v2EthPrtSwF2InOctetsGlobalIx OBJECT-TYPE
   SYNTAX      GlobalIndex
   MAX-ACCESS  not-accessible
   STATUS      current
   DESCRIPTION
      "The value of the tlsCntTreeGlobalIndex of the MANAGED OBJECT."
   ::= {pr1645v2EthPrtSwF2InOctetsEntry 10}

pr1645v2EthPrtSwF2InOctetsValue OBJECT-TYPE
   SYNTAX      Counter64
   MAX-ACCESS  read-only
   STATUS      current
   DESCRIPTION
      "Path: swPort.performance.ifInOctets

       64 bit unsigned wrappable counter."
   ::= {pr1645v2EthPrtSwF2InOctetsEntry 2147483648}


pr1645v2EthPrtSwF2InUcast OBJECT IDENTIFIER ::= {pr1645v2EthPrtSwF2 110}

pr1645v2EthPrtSwF2InUcastTable OBJECT-TYPE
   SYNTAX      SEQUENCE OF Pr1645v2EthPrtSwF2InUcastEntry
   MAX-ACCESS  not-accessible
   STATUS      current
   DESCRIPTION
      "ifInUcastPkts"
   ::= {pr1645v2EthPrtSwF2InUcast 1}

pr1645v2EthPrtSwF2InUcastEntry OBJECT-TYPE
   SYNTAX      Pr1645v2EthPrtSwF2InUcastEntry
   MAX-ACCESS  not-accessible
   STATUS      current
   DESCRIPTION
      ""
   INDEX      { pr1645v2EthPrtSwF2InUcastGlobalIx }
   ::= {pr1645v2EthPrtSwF2InUcastTable 1}

Pr1645v2EthPrtSwF2InUcastEntry ::=
   SEQUENCE
      {
      pr1645v2EthPrtSwF2InUcastGlobalIx
         GlobalIndex,
      pr1645v2EthPrtSwF2InUcastValue
         Counter64
      }

pr1645v2EthPrtSwF2InUcastGlobalIx OBJECT-TYPE
   SYNTAX      GlobalIndex
   MAX-ACCESS  not-accessible
   STATUS      current
   DESCRIPTION
      "The value of the tlsCntTreeGlobalIndex of the MANAGED OBJECT."
   ::= {pr1645v2EthPrtSwF2InUcastEntry 10}

pr1645v2EthPrtSwF2InUcastValue OBJECT-TYPE
   SYNTAX      Counter64
   MAX-ACCESS  read-only
   STATUS      current
   DESCRIPTION
      "Path: swPort.performance.ifInUcastPkts

       64 bit unsigned wrappable counter."
   ::= {pr1645v2EthPrtSwF2InUcastEntry 2147483648}


pr1645v2EthPrtSwF2InNUcastPkts OBJECT IDENTIFIER ::= {pr1645v2EthPrtSwF2 111}

pr1645v2EthPrtSwF2InNUcastPktsTable OBJECT-TYPE
   SYNTAX      SEQUENCE OF Pr1645v2EthPrtSwF2InNUcastPktsEntry
   MAX-ACCESS  not-accessible
   STATUS      current
   DESCRIPTION
      "ifInNUcastPkts"
   ::= {pr1645v2EthPrtSwF2InNUcastPkts 1}

pr1645v2EthPrtSwF2InNUcastPktsEntry OBJECT-TYPE
   SYNTAX      Pr1645v2EthPrtSwF2InNUcastPktsEntry
   MAX-ACCESS  not-accessible
   STATUS      current
   DESCRIPTION
      ""
   INDEX      { pr1645v2EthPrtSwF2InNUcastPktsGlobalIx }
   ::= {pr1645v2EthPrtSwF2InNUcastPktsTable 1}

Pr1645v2EthPrtSwF2InNUcastPktsEntry ::=
   SEQUENCE
      {
      pr1645v2EthPrtSwF2InNUcastPktsGlobalIx
         GlobalIndex,
      pr1645v2EthPrtSwF2InNUcastPktsValue
         Counter64
      }

pr1645v2EthPrtSwF2InNUcastPktsGlobalIx OBJECT-TYPE
   SYNTAX      GlobalIndex
   MAX-ACCESS  not-accessible
   STATUS      current
   DESCRIPTION
      "The value of the tlsCntTreeGlobalIndex of the MANAGED OBJECT."
   ::= {pr1645v2EthPrtSwF2InNUcastPktsEntry 10}

pr1645v2EthPrtSwF2InNUcastPktsValue OBJECT-TYPE
   SYNTAX      Counter64
   MAX-ACCESS  read-only
   STATUS      current
   DESCRIPTION
      "Path: swPort.performance.ifInNUcastPkts

       64 bit unsigned wrappable counter."
   ::= {pr1645v2EthPrtSwF2InNUcastPktsEntry 2147483648}


pr1645v2EthPrtSwF2InBcastPkts OBJECT IDENTIFIER ::= {pr1645v2EthPrtSwF2 211}

pr1645v2EthPrtSwF2InBcastPktsTable OBJECT-TYPE
   SYNTAX      SEQUENCE OF Pr1645v2EthPrtSwF2InBcastPktsEntry
   MAX-ACCESS  not-accessible
   STATUS      current
   DESCRIPTION
      "ifInBcastPkts"
   ::= {pr1645v2EthPrtSwF2InBcastPkts 1}

pr1645v2EthPrtSwF2InBcastPktsEntry OBJECT-TYPE
   SYNTAX      Pr1645v2EthPrtSwF2InBcastPktsEntry
   MAX-ACCESS  not-accessible
   STATUS      current
   DESCRIPTION
      ""
   INDEX      { pr1645v2EthPrtSwF2InBcastPktsGlobalIx }
   ::= {pr1645v2EthPrtSwF2InBcastPktsTable 1}

Pr1645v2EthPrtSwF2InBcastPktsEntry ::=
   SEQUENCE
      {
      pr1645v2EthPrtSwF2InBcastPktsGlobalIx
         GlobalIndex,
      pr1645v2EthPrtSwF2InBcastPktsValue
         Counter64
      }

pr1645v2EthPrtSwF2InBcastPktsGlobalIx OBJECT-TYPE
   SYNTAX      GlobalIndex
   MAX-ACCESS  not-accessible
   STATUS      current
   DESCRIPTION
      "The value of the tlsCntTreeGlobalIndex of the MANAGED OBJECT."
   ::= {pr1645v2EthPrtSwF2InBcastPktsEntry 10}

pr1645v2EthPrtSwF2InBcastPktsValue OBJECT-TYPE
   SYNTAX      Counter64
   MAX-ACCESS  read-only
   STATUS      current
   DESCRIPTION
      "Path: swPort.performance.ifInBcastPkts

       64 bit unsigned wrappable counter."
   ::= {pr1645v2EthPrtSwF2InBcastPktsEntry 2147483648}


pr1645v2EthPrtSwF2InMcastPkts OBJECT IDENTIFIER ::= {pr1645v2EthPrtSwF2 221}

pr1645v2EthPrtSwF2InMcastPktsTable OBJECT-TYPE
   SYNTAX      SEQUENCE OF Pr1645v2EthPrtSwF2InMcastPktsEntry
   MAX-ACCESS  not-accessible
   STATUS      current
   DESCRIPTION
      "ifInNUcastPkts"
   ::= {pr1645v2EthPrtSwF2InMcastPkts 1}

pr1645v2EthPrtSwF2InMcastPktsEntry OBJECT-TYPE
   SYNTAX      Pr1645v2EthPrtSwF2InMcastPktsEntry
   MAX-ACCESS  not-accessible
   STATUS      current
   DESCRIPTION
      ""
   INDEX      { pr1645v2EthPrtSwF2InMcastPktsGlobalIx }
   ::= {pr1645v2EthPrtSwF2InMcastPktsTable 1}

Pr1645v2EthPrtSwF2InMcastPktsEntry ::=
   SEQUENCE
      {
      pr1645v2EthPrtSwF2InMcastPktsGlobalIx
         GlobalIndex,
      pr1645v2EthPrtSwF2InMcastPktsValue
         Counter64
      }

pr1645v2EthPrtSwF2InMcastPktsGlobalIx OBJECT-TYPE
   SYNTAX      GlobalIndex
   MAX-ACCESS  not-accessible
   STATUS      current
   DESCRIPTION
      "The value of the tlsCntTreeGlobalIndex of the MANAGED OBJECT."
   ::= {pr1645v2EthPrtSwF2InMcastPktsEntry 10}

pr1645v2EthPrtSwF2InMcastPktsValue OBJECT-TYPE
   SYNTAX      Counter64
   MAX-ACCESS  read-only
   STATUS      current
   DESCRIPTION
      "Path: swPort.performance.ifInMcastPkts

       64 bit unsigned wrappable counter."
   ::= {pr1645v2EthPrtSwF2InMcastPktsEntry 2147483648}


pr1645v2EthPrtSwF2InDiscards OBJECT IDENTIFIER ::= {pr1645v2EthPrtSwF2 112}

pr1645v2EthPrtSwF2InDiscardsTable OBJECT-TYPE
   SYNTAX      SEQUENCE OF Pr1645v2EthPrtSwF2InDiscardsEntry
   MAX-ACCESS  not-accessible
   STATUS      current
   DESCRIPTION
      "ifInDiscards"
   ::= {pr1645v2EthPrtSwF2InDiscards 1}

pr1645v2EthPrtSwF2InDiscardsEntry OBJECT-TYPE
   SYNTAX      Pr1645v2EthPrtSwF2InDiscardsEntry
   MAX-ACCESS  not-accessible
   STATUS      current
   DESCRIPTION
      ""
   INDEX      { pr1645v2EthPrtSwF2InDiscardsGlobalIx }
   ::= {pr1645v2EthPrtSwF2InDiscardsTable 1}

Pr1645v2EthPrtSwF2InDiscardsEntry ::=
   SEQUENCE
      {
      pr1645v2EthPrtSwF2InDiscardsGlobalIx
         GlobalIndex,
      pr1645v2EthPrtSwF2InDiscardsValue
         Counter64
      }

pr1645v2EthPrtSwF2InDiscardsGlobalIx OBJECT-TYPE
   SYNTAX      GlobalIndex
   MAX-ACCESS  not-accessible
   STATUS      current
   DESCRIPTION
      "The value of the tlsCntTreeGlobalIndex of the MANAGED OBJECT."
   ::= {pr1645v2EthPrtSwF2InDiscardsEntry 10}

pr1645v2EthPrtSwF2InDiscardsValue OBJECT-TYPE
   SYNTAX      Counter64
   MAX-ACCESS  read-only
   STATUS      current
   DESCRIPTION
      "Path: swPort.performance.ifInDiscards

       64 bit unsigned wrappable counter."
   ::= {pr1645v2EthPrtSwF2InDiscardsEntry 2147483648}


pr1645v2EthPrtSwF2InErrors OBJECT IDENTIFIER ::= {pr1645v2EthPrtSwF2 113}

pr1645v2EthPrtSwF2InErrorsTable OBJECT-TYPE
   SYNTAX      SEQUENCE OF Pr1645v2EthPrtSwF2InErrorsEntry
   MAX-ACCESS  not-accessible
   STATUS      current
   DESCRIPTION
      "ifInErrors"
   ::= {pr1645v2EthPrtSwF2InErrors 1}

pr1645v2EthPrtSwF2InErrorsEntry OBJECT-TYPE
   SYNTAX      Pr1645v2EthPrtSwF2InErrorsEntry
   MAX-ACCESS  not-accessible
   STATUS      current
   DESCRIPTION
      ""
   INDEX      { pr1645v2EthPrtSwF2InErrorsGlobalIx }
   ::= {pr1645v2EthPrtSwF2InErrorsTable 1}

Pr1645v2EthPrtSwF2InErrorsEntry ::=
   SEQUENCE
      {
      pr1645v2EthPrtSwF2InErrorsGlobalIx
         GlobalIndex,
      pr1645v2EthPrtSwF2InErrorsValue
         Counter64
      }

pr1645v2EthPrtSwF2InErrorsGlobalIx OBJECT-TYPE
   SYNTAX      GlobalIndex
   MAX-ACCESS  not-accessible
   STATUS      current
   DESCRIPTION
      "The value of the tlsCntTreeGlobalIndex of the MANAGED OBJECT."
   ::= {pr1645v2EthPrtSwF2InErrorsEntry 10}

pr1645v2EthPrtSwF2InErrorsValue OBJECT-TYPE
   SYNTAX      Counter64
   MAX-ACCESS  read-only
   STATUS      current
   DESCRIPTION
      "Path: swPort.performance.ifInErrors

       64 bit unsigned wrappable counter."
   ::= {pr1645v2EthPrtSwF2InErrorsEntry 2147483648}


pr1645v2EthPrtSwF2InUnknownProtos OBJECT IDENTIFIER ::= {pr1645v2EthPrtSwF2 114}

pr1645v2EthPrtSwF2InUnknownProtosTable OBJECT-TYPE
   SYNTAX      SEQUENCE OF Pr1645v2EthPrtSwF2InUnknownProtosEntry
   MAX-ACCESS  not-accessible
   STATUS      current
   DESCRIPTION
      "ifInUnknownprotos"
   ::= {pr1645v2EthPrtSwF2InUnknownProtos 1}

pr1645v2EthPrtSwF2InUnknownProtosEntry OBJECT-TYPE
   SYNTAX      Pr1645v2EthPrtSwF2InUnknownProtosEntry
   MAX-ACCESS  not-accessible
   STATUS      current
   DESCRIPTION
      ""
   INDEX      { pr1645v2EthPrtSwF2InUnknownProtosGlobalIx }
   ::= {pr1645v2EthPrtSwF2InUnknownProtosTable 1}

Pr1645v2EthPrtSwF2InUnknownProtosEntry ::=
   SEQUENCE
      {
      pr1645v2EthPrtSwF2InUnknownProtosGlobalIx
         GlobalIndex,
      pr1645v2EthPrtSwF2InUnknownProtosValue
         Counter64
      }

pr1645v2EthPrtSwF2InUnknownProtosGlobalIx OBJECT-TYPE
   SYNTAX      GlobalIndex
   MAX-ACCESS  not-accessible
   STATUS      current
   DESCRIPTION
      "The value of the tlsCntTreeGlobalIndex of the MANAGED OBJECT."
   ::= {pr1645v2EthPrtSwF2InUnknownProtosEntry 10}

pr1645v2EthPrtSwF2InUnknownProtosValue OBJECT-TYPE
   SYNTAX      Counter64
   MAX-ACCESS  read-only
   STATUS      current
   DESCRIPTION
      "Path: swPort.performance.ifInUnknownProtos

       64 bit unsigned wrappable counter."
   ::= {pr1645v2EthPrtSwF2InUnknownProtosEntry 2147483648}


pr1645v2EthPrtSwF2InDropEx OBJECT IDENTIFIER ::= {pr1645v2EthPrtSwF2 130}

pr1645v2EthPrtSwF2InDropExTable OBJECT-TYPE
   SYNTAX      SEQUENCE OF Pr1645v2EthPrtSwF2InDropExEntry
   MAX-ACCESS  not-accessible
   STATUS      current
   DESCRIPTION
      "ifInDiscards"
   ::= {pr1645v2EthPrtSwF2InDropEx 1}

pr1645v2EthPrtSwF2InDropExEntry OBJECT-TYPE
   SYNTAX      Pr1645v2EthPrtSwF2InDropExEntry
   MAX-ACCESS  not-accessible
   STATUS      current
   DESCRIPTION
      ""
   INDEX      { pr1645v2EthPrtSwF2InDropExGlobalIx }
   ::= {pr1645v2EthPrtSwF2InDropExTable 1}

Pr1645v2EthPrtSwF2InDropExEntry ::=
   SEQUENCE
      {
      pr1645v2EthPrtSwF2InDropExGlobalIx
         GlobalIndex,
      pr1645v2EthPrtSwF2InDropExValue
         Counter64
      }

pr1645v2EthPrtSwF2InDropExGlobalIx OBJECT-TYPE
   SYNTAX      GlobalIndex
   MAX-ACCESS  not-accessible
   STATUS      current
   DESCRIPTION
      "The value of the tlsCntTreeGlobalIndex of the MANAGED OBJECT."
   ::= {pr1645v2EthPrtSwF2InDropExEntry 10}

pr1645v2EthPrtSwF2InDropExValue OBJECT-TYPE
   SYNTAX      Counter64
   MAX-ACCESS  read-only
   STATUS      current
   DESCRIPTION
      "Path: swPort.performance.ifInDropLevelExceeded

       64 bit unsigned wrappable counter."
   ::= {pr1645v2EthPrtSwF2InDropExEntry 2147483648}


pr1645v2EthPrtSwF2InDropNoMac OBJECT IDENTIFIER ::= {pr1645v2EthPrtSwF2 133}

pr1645v2EthPrtSwF2InDropNoMacTable OBJECT-TYPE
   SYNTAX      SEQUENCE OF Pr1645v2EthPrtSwF2InDropNoMacEntry
   MAX-ACCESS  not-accessible
   STATUS      current
   DESCRIPTION
      "ifInDiscards"
   ::= {pr1645v2EthPrtSwF2InDropNoMac 1}

pr1645v2EthPrtSwF2InDropNoMacEntry OBJECT-TYPE
   SYNTAX      Pr1645v2EthPrtSwF2InDropNoMacEntry
   MAX-ACCESS  not-accessible
   STATUS      current
   DESCRIPTION
      ""
   INDEX      { pr1645v2EthPrtSwF2InDropNoMacGlobalIx }
   ::= {pr1645v2EthPrtSwF2InDropNoMacTable 1}

Pr1645v2EthPrtSwF2InDropNoMacEntry ::=
   SEQUENCE
      {
      pr1645v2EthPrtSwF2InDropNoMacGlobalIx
         GlobalIndex,
      pr1645v2EthPrtSwF2InDropNoMacValue
         Counter64
      }

pr1645v2EthPrtSwF2InDropNoMacGlobalIx OBJECT-TYPE
   SYNTAX      GlobalIndex
   MAX-ACCESS  not-accessible
   STATUS      current
   DESCRIPTION
      "The value of the tlsCntTreeGlobalIndex of the MANAGED OBJECT."
   ::= {pr1645v2EthPrtSwF2InDropNoMacEntry 10}

pr1645v2EthPrtSwF2InDropNoMacValue OBJECT-TYPE
   SYNTAX      Counter64
   MAX-ACCESS  read-only
   STATUS      current
   DESCRIPTION
      "Path: swPort.performance.ifInDiscardsNoMacFit

       64 bit unsigned wrappable counter."
   ::= {pr1645v2EthPrtSwF2InDropNoMacEntry 2147483648}


pr1645v2EthPrtSwF2InDropNUCast OBJECT IDENTIFIER ::= {pr1645v2EthPrtSwF2 136}

pr1645v2EthPrtSwF2InDropNUCastTable OBJECT-TYPE
   SYNTAX      SEQUENCE OF Pr1645v2EthPrtSwF2InDropNUCastEntry
   MAX-ACCESS  not-accessible
   STATUS      current
   DESCRIPTION
      "ifInDiscards"
   ::= {pr1645v2EthPrtSwF2InDropNUCast 1}

pr1645v2EthPrtSwF2InDropNUCastEntry OBJECT-TYPE
   SYNTAX      Pr1645v2EthPrtSwF2InDropNUCastEntry
   MAX-ACCESS  not-accessible
   STATUS      current
   DESCRIPTION
      ""
   INDEX      { pr1645v2EthPrtSwF2InDropNUCastGlobalIx }
   ::= {pr1645v2EthPrtSwF2InDropNUCastTable 1}

Pr1645v2EthPrtSwF2InDropNUCastEntry ::=
   SEQUENCE
      {
      pr1645v2EthPrtSwF2InDropNUCastGlobalIx
         GlobalIndex,
      pr1645v2EthPrtSwF2InDropNUCastValue
         Counter64
      }

pr1645v2EthPrtSwF2InDropNUCastGlobalIx OBJECT-TYPE
   SYNTAX      GlobalIndex
   MAX-ACCESS  not-accessible
   STATUS      current
   DESCRIPTION
      "The value of the tlsCntTreeGlobalIndex of the MANAGED OBJECT."
   ::= {pr1645v2EthPrtSwF2InDropNUCastEntry 10}

pr1645v2EthPrtSwF2InDropNUCastValue OBJECT-TYPE
   SYNTAX      Counter64
   MAX-ACCESS  read-only
   STATUS      current
   DESCRIPTION
      "Path: swPort.performance.ifInDiscardsNUCast

       64 bit unsigned wrappable counter."
   ::= {pr1645v2EthPrtSwF2InDropNUCastEntry 2147483648}


pr1645v2EthPrtSwF2InDropFilter OBJECT IDENTIFIER ::= {pr1645v2EthPrtSwF2 137}

pr1645v2EthPrtSwF2InDropFilterTable OBJECT-TYPE
   SYNTAX      SEQUENCE OF Pr1645v2EthPrtSwF2InDropFilterEntry
   MAX-ACCESS  not-accessible
   STATUS      current
   DESCRIPTION
      "ifInDiscards"
   ::= {pr1645v2EthPrtSwF2InDropFilter 1}

pr1645v2EthPrtSwF2InDropFilterEntry OBJECT-TYPE
   SYNTAX      Pr1645v2EthPrtSwF2InDropFilterEntry
   MAX-ACCESS  not-accessible
   STATUS      current
   DESCRIPTION
      ""
   INDEX      { pr1645v2EthPrtSwF2InDropFilterGlobalIx }
   ::= {pr1645v2EthPrtSwF2InDropFilterTable 1}

Pr1645v2EthPrtSwF2InDropFilterEntry ::=
   SEQUENCE
      {
      pr1645v2EthPrtSwF2InDropFilterGlobalIx
         GlobalIndex,
      pr1645v2EthPrtSwF2InDropFilterValue
         Counter64
      }

pr1645v2EthPrtSwF2InDropFilterGlobalIx OBJECT-TYPE
   SYNTAX      GlobalIndex
   MAX-ACCESS  not-accessible
   STATUS      current
   DESCRIPTION
      "The value of the tlsCntTreeGlobalIndex of the MANAGED OBJECT."
   ::= {pr1645v2EthPrtSwF2InDropFilterEntry 10}

pr1645v2EthPrtSwF2InDropFilterValue OBJECT-TYPE
   SYNTAX      Counter64
   MAX-ACCESS  read-only
   STATUS      current
   DESCRIPTION
      "Path: swPort.performance.ifInDiscardsFilter

       64 bit unsigned wrappable counter."
   ::= {pr1645v2EthPrtSwF2InDropFilterEntry 2147483648}


pr1645v2EthPrtSwF2InQueues OBJECT IDENTIFIER ::= {pr1645v2EthPrtSwF2 131}

pr1645v2EthPrtSwF2InQueuesSSCTable OBJECT-TYPE
   SYNTAX      SEQUENCE OF Pr1645v2EthPrtSwF2InQueuesEntry
   MAX-ACCESS  not-accessible
   STATUS      current
   DESCRIPTION
      "Queue Lengths"
   ::= {pr1645v2EthPrtSwF2InQueues 1}

pr1645v2EthPrtSwF2InQueuesEntry OBJECT-TYPE
   SYNTAX      Pr1645v2EthPrtSwF2InQueuesEntry
   MAX-ACCESS  not-accessible
   STATUS      current
   DESCRIPTION
      ""
   INDEX      { pr1645v2EthPrtSwF2InQueuesGlobalIx,
                pr1645v2EthPrtSwF2InQueuesTableIx }
   ::= {pr1645v2EthPrtSwF2InQueuesSSCTable 1}

Pr1645v2EthPrtSwF2InQueuesEntry ::=
   SEQUENCE
      {
      pr1645v2EthPrtSwF2InQueuesGlobalIx
         GlobalIndex,
      pr1645v2EthPrtSwF2InQueuesTableIx
         TableIndex,
      pr1645v2EthPrtSwF2InQueuesName
         INTEGER,
      pr1645v2EthPrtSwF2InQueuesLength
         Integer32,
      pr1645v2EthPrtSwF2InQueuesOctetLength
         Integer32,
      pr1645v2EthPrtSwF2InQueuesRedLength
         Integer32,
      pr1645v2EthPrtSwF2InQueuesPacketsTotal
         Counter64,
      pr1645v2EthPrtSwF2InQueuesPacketsDirectTx
         Counter64,
      pr1645v2EthPrtSwF2InQueuesPacketsQueued
         Counter64,
      pr1645v2EthPrtSwF2InQueuesPacketsDropped
         Counter64,
      pr1645v2EthPrtSwF2InQueuesPacketsRedDropped
         Counter64,
      pr1645v2EthPrtSwF2InQueuesPacketsCirTx
         Counter64,
      pr1645v2EthPrtSwF2InQueuesPacketsEirTx
         Counter64,
      pr1645v2EthPrtSwF2InQueuesPacketsViolateTx
         Counter64,
      pr1645v2EthPrtSwF2InQueuesOctetsTotal
         Counter64,
      pr1645v2EthPrtSwF2InQueuesOctetsDirectTx
         Counter64,
      pr1645v2EthPrtSwF2InQueuesOctetsQueued
         Counter64,
      pr1645v2EthPrtSwF2InQueuesOctetsDropped
         Counter64,
      pr1645v2EthPrtSwF2InQueuesOctetsRedDropped
         Counter64,
      pr1645v2EthPrtSwF2InQueuesOctetsCirTx
         Counter64,
      pr1645v2EthPrtSwF2InQueuesOctetsEirTx
         Counter64,
      pr1645v2EthPrtSwF2InQueuesOctetsViolateTx
         Counter64,
      pr1645v2EthPrtSwF2InQueuesOctetsBandwidth15sec
         Integer32,
      pr1645v2EthPrtSwF2InQueuesOctetsBandwidth30sec
         Integer32,
      pr1645v2EthPrtSwF2InQueuesOctetsBandwidth1min
         Integer32,
      pr1645v2EthPrtSwF2InQueuesOctetsBandwidth2min
         Integer32,
      pr1645v2EthPrtSwF2InQueuesOctetsBandwidth5min
         Integer32
      }

pr1645v2EthPrtSwF2InQueuesGlobalIx OBJECT-TYPE
   SYNTAX      GlobalIndex
   MAX-ACCESS  not-accessible
   STATUS      current
   DESCRIPTION
      "The value of the tlsCntTreeGlobalIndex of the MANAGED OBJECT."
   ::= {pr1645v2EthPrtSwF2InQueuesEntry 10}

pr1645v2EthPrtSwF2InQueuesTableIx OBJECT-TYPE
   SYNTAX      TableIndex
   MAX-ACCESS  not-accessible
   STATUS      current
   DESCRIPTION
      ""
   ::= {pr1645v2EthPrtSwF2InQueuesEntry 11}

pr1645v2EthPrtSwF2InQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: swPort.performance.ifInPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2EthPrtSwF2InQueuesEntry 16777216}

pr1645v2EthPrtSwF2InQueuesLength OBJECT-TYPE
   SYNTAX      Integer32
   MAX-ACCESS  read-only
   STATUS      current
   DESCRIPTION
      "Path: swPort.performance.ifInPriorityQueues.length"
   ::= {pr1645v2EthPrtSwF2InQueuesEntry 33554432}

pr1645v2EthPrtSwF2InQueuesOctetLength OBJECT-TYPE
   SYNTAX      Integer32
   MAX-ACCESS  read-only
   STATUS      current
   DESCRIPTION
      "Path: swPort.performance.ifInPriorityQueues.octetLength"
   ::= {pr1645v2EthPrtSwF2InQueuesEntry 150994944}

pr1645v2EthPrtSwF2InQueuesRedLength OBJECT-TYPE
   SYNTAX      Integer32
   MAX-ACCESS  read-only
   STATUS      current
   DESCRIPTION
      "Path: swPort.performance.ifInPriorityQueues.redLength"
   ::= {pr1645v2EthPrtSwF2InQueuesEntry 134217728}

pr1645v2EthPrtSwF2InQueuesPacketsTotal OBJECT-TYPE
   SYNTAX      Counter64
   MAX-ACCESS  read-only
   STATUS      current
   DESCRIPTION
      "Path: swPort.performance.ifInPriorityQueues.packets.total

       64 bit unsigned wrappable counter."
   ::= {pr1645v2EthPrtSwF2InQueuesEntry 50790400}

pr1645v2EthPrtSwF2InQueuesPacketsDirectTx OBJECT-TYPE
   SYNTAX      Counter64
   MAX-ACCESS  read-only
   STATUS      current
   DESCRIPTION
      "Path: swPort.performance.ifInPriorityQueues.packets.directTx

       64 bit unsigned wrappable counter."
   ::= {pr1645v2EthPrtSwF2InQueuesEntry 50397184}

pr1645v2EthPrtSwF2InQueuesPacketsQueued OBJECT-TYPE
   SYNTAX      Counter64
   MAX-ACCESS  read-only
   STATUS      current
   DESCRIPTION
      "Path: swPort.performance.ifInPriorityQueues.packets.queued

       64 bit unsigned wrappable counter."
   ::= {pr1645v2EthPrtSwF2InQueuesEntry 50462720}

pr1645v2EthPrtSwF2InQueuesPacketsDropped OBJECT-TYPE
   SYNTAX      Counter64
   MAX-ACCESS  read-only
   STATUS      current
   DESCRIPTION
      "Path: swPort.performance.ifInPriorityQueues.packets.dropped

       64 bit unsigned wrappable counter."
   ::= {pr1645v2EthPrtSwF2InQueuesEntry 50528256}

pr1645v2EthPrtSwF2InQueuesPacketsRedDropped OBJECT-TYPE
   SYNTAX      Counter64
   MAX-ACCESS  read-only
   STATUS      current
   DESCRIPTION
      "Path: swPort.performance.ifInPriorityQueues.packets.redDropped

       64 bit unsigned wrappable counter."
   ::= {pr1645v2EthPrtSwF2InQueuesEntry 50724864}

pr1645v2EthPrtSwF2InQueuesPacketsCirTx OBJECT-TYPE
   SYNTAX      Counter64
   MAX-ACCESS  read-only
   STATUS      current
   DESCRIPTION
      "Path: swPort.performance.ifInPriorityQueues.packets.cirTx

       64 bit unsigned wrappable counter."
   ::= {pr1645v2EthPrtSwF2InQueuesEntry 50593792}

pr1645v2EthPrtSwF2InQueuesPacketsEirTx OBJECT-TYPE
   SYNTAX      Counter64
   MAX-ACCESS  read-only
   STATUS      current
   DESCRIPTION
      "Path: swPort.performance.ifInPriorityQueues.packets.eirTx

       64 bit unsigned wrappable counter."
   ::= {pr1645v2EthPrtSwF2InQueuesEntry 50659328}

pr1645v2EthPrtSwF2InQueuesPacketsViolateTx OBJECT-TYPE
   SYNTAX      Counter64
   MAX-ACCESS  read-only
   STATUS      current
   DESCRIPTION
      "Path: swPort.performance.ifInPriorityQueues.packets.violateTx

       64 bit unsigned wrappable counter."
   ::= {pr1645v2EthPrtSwF2InQueuesEntry 50855936}

pr1645v2EthPrtSwF2InQueuesOctetsTotal OBJECT-TYPE
   SYNTAX      Counter64
   MAX-ACCESS  read-only
   STATUS      current
   DESCRIPTION
      "Path: swPort.performance.ifInPriorityQueues.octets.total

       64 bit unsigned wrappable counter."
   ::= {pr1645v2EthPrtSwF2InQueuesEntry 67567616}

pr1645v2EthPrtSwF2InQueuesOctetsDirectTx OBJECT-TYPE
   SYNTAX      Counter64
   MAX-ACCESS  read-only
   STATUS      current
   DESCRIPTION
      "Path: swPort.performance.ifInPriorityQueues.octets.directTx

       64 bit unsigned wrappable counter."
   ::= {pr1645v2EthPrtSwF2InQueuesEntry 67174400}

pr1645v2EthPrtSwF2InQueuesOctetsQueued OBJECT-TYPE
   SYNTAX      Counter64
   MAX-ACCESS  read-only
   STATUS      current
   DESCRIPTION
      "Path: swPort.performance.ifInPriorityQueues.octets.queued

       64 bit unsigned wrappable counter."
   ::= {pr1645v2EthPrtSwF2InQueuesEntry 67239936}

pr1645v2EthPrtSwF2InQueuesOctetsDropped OBJECT-TYPE
   SYNTAX      Counter64
   MAX-ACCESS  read-only
   STATUS      current
   DESCRIPTION
      "Path: swPort.performance.ifInPriorityQueues.octets.dropped

       64 bit unsigned wrappable counter."
   ::= {pr1645v2EthPrtSwF2InQueuesEntry 67305472}

pr1645v2EthPrtSwF2InQueuesOctetsRedDropped OBJECT-TYPE
   SYNTAX      Counter64
   MAX-ACCESS  read-only
   STATUS      current
   DESCRIPTION
      "Path: swPort.performance.ifInPriorityQueues.octets.redDropped

       64 bit unsigned wrappable counter."
   ::= {pr1645v2EthPrtSwF2InQueuesEntry 67502080}

pr1645v2EthPrtSwF2InQueuesOctetsCirTx OBJECT-TYPE
   SYNTAX      Counter64
   MAX-ACCESS  read-only
   STATUS      current
   DESCRIPTION
      "Path: swPort.performance.ifInPriorityQueues.octets.cirTx

       64 bit unsigned wrappable counter."
   ::= {pr1645v2EthPrtSwF2InQueuesEntry 67371008}

pr1645v2EthPrtSwF2InQueuesOctetsEirTx OBJECT-TYPE
   SYNTAX      Counter64
   MAX-ACCESS  read-only
   STATUS      current
   DESCRIPTION
      "Path: swPort.performance.ifInPriorityQueues.octets.eirTx

       64 bit unsigned wrappable counter."
   ::= {pr1645v2EthPrtSwF2InQueuesEntry 67436544}

pr1645v2EthPrtSwF2InQueuesOctetsViolateTx OBJECT-TYPE
   SYNTAX      Counter64
   MAX-ACCESS  read-only
   STATUS      current
   DESCRIPTION
      "Path: swPort.performance.ifInPriorityQueues.octets.violateTx

       64 bit unsigned wrappable counter."
   ::= {pr1645v2EthPrtSwF2InQueuesEntry 67633152}

pr1645v2EthPrtSwF2InQueuesOctetsBandwidth15sec OBJECT-TYPE
   SYNTAX      Integer32
   MAX-ACCESS  read-only
   STATUS      current
   DESCRIPTION
      "Path: swPort.performance.ifInPriorityQueues.octets.bandwidth.15sec

       unit name = bps
       formula = 8 * ; 8 /"
   ::= {pr1645v2EthPrtSwF2InQueuesEntry 70386944}

pr1645v2EthPrtSwF2InQueuesOctetsBandwidth30sec OBJECT-TYPE
   SYNTAX      Integer32
   MAX-ACCESS  read-only
   STATUS      current
   DESCRIPTION
      "Path: swPort.performance.ifInPriorityQueues.octets.bandwidth.30sec

       unit name = bps
       formula = 8 * ; 8 /"
   ::= {pr1645v2EthPrtSwF2InQueuesEntry 70388224}

pr1645v2EthPrtSwF2InQueuesOctetsBandwidth1min OBJECT-TYPE
   SYNTAX      Integer32
   MAX-ACCESS  read-only
   STATUS      current
   DESCRIPTION
      "Path: swPort.performance.ifInPriorityQueues.octets.bandwidth.1min

       unit name = bps
       formula = 8 * ; 8 /"
   ::= {pr1645v2EthPrtSwF2InQueuesEntry 70390784}

pr1645v2EthPrtSwF2InQueuesOctetsBandwidth2min OBJECT-TYPE
   SYNTAX      Integer32
   MAX-ACCESS  read-only
   STATUS      current
   DESCRIPTION
      "Path: swPort.performance.ifInPriorityQueues.octets.bandwidth.2min

       unit name = bps
       formula = 8 * ; 8 /"
   ::= {pr1645v2EthPrtSwF2InQueuesEntry 70395904}

pr1645v2EthPrtSwF2InQueuesOctetsBandwidth5min OBJECT-TYPE
   SYNTAX      Integer32
   MAX-ACCESS  read-only
   STATUS      current
   DESCRIPTION
      "Path: swPort.performance.ifInPriorityQueues.octets.bandwidth.5min

       unit name = bps
       formula = 8 * ; 8 /"
   ::= {pr1645v2EthPrtSwF2InQueuesEntry 70411264}

pr1645v2EthPrtSwF2InQueuesH2Performance OBJECT-TYPE
   SYNTAX      SEQUENCE OF Pr1645v2EthPrtSwF2InQueuesH2PerformanceEntry
   MAX-ACCESS  not-accessible
   STATUS      current
   DESCRIPTION
      ""
   ::= {pr1645v2EthPrtSwF2InQueues 83886080}

pr1645v2EthPrtSwF2InQueuesH2PerformanceEntry OBJECT-TYPE
   SYNTAX      Pr1645v2EthPrtSwF2InQueuesH2PerformanceEntry
   MAX-ACCESS  not-accessible
   STATUS      current
   DESCRIPTION
      ""
   INDEX      { pr1645v2EthPrtSwF2InQueuesH2PerformanceGlobalIx,
                pr1645v2EthPrtSwF2InQueuesTableIx,
                pr1645v2EthPrtSwF2InQueuesH2PerformanceTableIx }
   ::= {pr1645v2EthPrtSwF2InQueuesH2Performance 1}

Pr1645v2EthPrtSwF2InQueuesH2PerformanceEntry ::=
   SEQUENCE
      {
      pr1645v2EthPrtSwF2InQueuesH2PerformanceGlobalIx
         GlobalIndex,
      pr1645v2EthPrtSwF2InQueuesH2PerformanceTableIx
         TableIndex,
      pr1645v2EthPrtSwF2InQueuesH2PerformanceSysUpTime
         TimeTicks,
      pr1645v2EthPrtSwF2InQueuesH2PerformanceTotPkts
         Counter64,
      pr1645v2EthPrtSwF2InQueuesH2PerformanceDirTxPkts
         Counter64,
      pr1645v2EthPrtSwF2InQueuesH2PerformanceQdPkts
         Counter64,
      pr1645v2EthPrtSwF2InQueuesH2PerformanceDropPkts
         Counter64,
      pr1645v2EthPrtSwF2InQueuesH2PerformanceRDropPkts
         Counter64,
      pr1645v2EthPrtSwF2InQueuesH2PerformanceCirTxPkts
         Counter64,
      pr1645v2EthPrtSwF2InQueuesH2PerformanceEirTxPkts
         Counter64,
      pr1645v2EthPrtSwF2InQueuesH2PerformanceViolTxPkts
         Counter64,
      pr1645v2EthPrtSwF2InQueuesH2PerformanceTotOcts
         Counter64,
      pr1645v2EthPrtSwF2InQueuesH2PerformanceDirTxOcts
         Counter64,
      pr1645v2EthPrtSwF2InQueuesH2PerformanceQdOcts
         Counter64,
      pr1645v2EthPrtSwF2InQueuesH2PerformanceDropOcts
         Counter64,
      pr1645v2EthPrtSwF2InQueuesH2PerformanceRDropOcts
         Counter64,
      pr1645v2EthPrtSwF2InQueuesH2PerformanceCirTxOcts
         Counter64,
      pr1645v2EthPrtSwF2InQueuesH2PerformanceEirTxOcts
         Counter64,
      pr1645v2EthPrtSwF2InQueuesH2PerformanceViolTxOcts
         Counter64,
      pr1645v2EthPrtSwF2InQueuesH2PerformanceBandwidth
         Integer32
      }

pr1645v2EthPrtSwF2InQueuesH2PerformanceGlobalIx OBJECT-TYPE
   SYNTAX      GlobalIndex
   MAX-ACCESS  not-accessible
   STATUS      current
   DESCRIPTION
      "The value of the tlsCntTreeGlobalIndex of the MANAGED OBJECT."
   ::= {pr1645v2EthPrtSwF2InQueuesH2PerformanceEntry 10}

pr1645v2EthPrtSwF2InQueuesH2PerformanceTableIx OBJECT-TYPE
   SYNTAX      TableIndex
   MAX-ACCESS  not-accessible
   STATUS      current
   DESCRIPTION
      ""
   ::= {pr1645v2EthPrtSwF2InQueuesH2PerformanceEntry 11}

pr1645v2EthPrtSwF2InQueuesH2PerformanceSysUpTime OBJECT-TYPE
   SYNTAX      TimeTicks
   MAX-ACCESS  read-only
   STATUS      current
   DESCRIPTION
      "Path: swPort.performance.ifInPriorityQueues.h2Performance.sysUpTime

       Time in centi-second."
   ::= {pr1645v2EthPrtSwF2InQueuesH2PerformanceEntry 16777216}

pr1645v2EthPrtSwF2InQueuesH2PerformanceTotPkts OBJECT-TYPE
   SYNTAX      Counter64
   MAX-ACCESS  read-only
   STATUS      current
   DESCRIPTION
      "Path: swPort.performance.ifInPriorityQueues.h2Performance.totalPkts

       64 bit unsigned wrappable counter."
   ::= {pr1645v2EthPrtSwF2InQueuesH2PerformanceEntry 234881024}

pr1645v2EthPrtSwF2InQueuesH2PerformanceDirTxPkts OBJECT-TYPE
   SYNTAX      Counter64
   MAX-ACCESS  read-only
   STATUS      current
   DESCRIPTION
      "Path: swPort.performance.ifInPriorityQueues.h2Performance.directTxPkts

       64 bit unsigned wrappable counter."
   ::= {pr1645v2EthPrtSwF2InQueuesH2PerformanceEntry 33554432}

pr1645v2EthPrtSwF2InQueuesH2PerformanceQdPkts OBJECT-TYPE
   SYNTAX      Counter64
   MAX-ACCESS  read-only
   STATUS      current
   DESCRIPTION
      "Path: swPort.performance.ifInPriorityQueues.h2Performance.queuedPkts

       64 bit unsigned wrappable counter."
   ::= {pr1645v2EthPrtSwF2InQueuesH2PerformanceEntry 50331648}

pr1645v2EthPrtSwF2InQueuesH2PerformanceDropPkts OBJECT-TYPE
   SYNTAX      Counter64
   MAX-ACCESS  read-only
   STATUS      current
   DESCRIPTION
      "Path: swPort.performance.ifInPriorityQueues.h2Performance.droppedPkts

       64 bit unsigned wrappable counter."
   ::= {pr1645v2EthPrtSwF2InQueuesH2PerformanceEntry 67108864}

pr1645v2EthPrtSwF2InQueuesH2PerformanceRDropPkts OBJECT-TYPE
   SYNTAX      Counter64
   MAX-ACCESS  read-only
   STATUS      current
   DESCRIPTION
      "Path: swPort.performance.ifInPriorityQueues.h2Performance.redDroppedPkts

       64 bit unsigned wrappable counter."
   ::= {pr1645v2EthPrtSwF2InQueuesH2PerformanceEntry 201326592}

pr1645v2EthPrtSwF2InQueuesH2PerformanceCirTxPkts OBJECT-TYPE
   SYNTAX      Counter64
   MAX-ACCESS  read-only
   STATUS      current
   DESCRIPTION
      "Path: swPort.performance.ifInPriorityQueues.h2Performance.cirTxPkts

       64 bit unsigned wrappable counter."
   ::= {pr1645v2EthPrtSwF2InQueuesH2PerformanceEntry 83886080}

pr1645v2EthPrtSwF2InQueuesH2PerformanceEirTxPkts OBJECT-TYPE
   SYNTAX      Counter64
   MAX-ACCESS  read-only
   STATUS      current
   DESCRIPTION
      "Path: swPort.performance.ifInPriorityQueues.h2Performance.eirTxPkts

       64 bit unsigned wrappable counter."
   ::= {pr1645v2EthPrtSwF2InQueuesH2PerformanceEntry 100663296}

pr1645v2EthPrtSwF2InQueuesH2PerformanceViolTxPkts OBJECT-TYPE
   SYNTAX      Counter64
   MAX-ACCESS  read-only
   STATUS      current
   DESCRIPTION
      "Path: swPort.performance.ifInPriorityQueues.h2Performance.violateTxPkts

       64 bit unsigned wrappable counter."
   ::= {pr1645v2EthPrtSwF2InQueuesH2PerformanceEntry 301989888}

pr1645v2EthPrtSwF2InQueuesH2PerformanceTotOcts OBJECT-TYPE
   SYNTAX      Counter64
   MAX-ACCESS  read-only
   STATUS      current
   DESCRIPTION
      "Path: swPort.performance.ifInPriorityQueues.h2Performance.totalOctets

       64 bit unsigned wrappable counter."
   ::= {pr1645v2EthPrtSwF2InQueuesH2PerformanceEntry 251658240}

pr1645v2EthPrtSwF2InQueuesH2PerformanceDirTxOcts OBJECT-TYPE
   SYNTAX      Counter64
   MAX-ACCESS  read-only
   STATUS      current
   DESCRIPTION
      "Path: swPort.performance.ifInPriorityQueues.h2Performance.directTxOctets

       64 bit unsigned wrappable counter."
   ::= {pr1645v2EthPrtSwF2InQueuesH2PerformanceEntry 117440512}

pr1645v2EthPrtSwF2InQueuesH2PerformanceQdOcts OBJECT-TYPE
   SYNTAX      Counter64
   MAX-ACCESS  read-only
   STATUS      current
   DESCRIPTION
      "Path: swPort.performance.ifInPriorityQueues.h2Performance.queuedOctets

       64 bit unsigned wrappable counter."
   ::= {pr1645v2EthPrtSwF2InQueuesH2PerformanceEntry 134217728}

pr1645v2EthPrtSwF2InQueuesH2PerformanceDropOcts OBJECT-TYPE
   SYNTAX      Counter64
   MAX-ACCESS  read-only
   STATUS      current
   DESCRIPTION
      "Path: swPort.performance.ifInPriorityQueues.h2Performance.droppedOctets

       64 bit unsigned wrappable counter."
   ::= {pr1645v2EthPrtSwF2InQueuesH2PerformanceEntry 150994944}

pr1645v2EthPrtSwF2InQueuesH2PerformanceRDropOcts OBJECT-TYPE
   SYNTAX      Counter64
   MAX-ACCESS  read-only
   STATUS      current
   DESCRIPTION
      "Path: swPort.performance.ifInPriorityQueues.h2Performance.redDroppedOctets

       64 bit unsigned wrappable counter."
   ::= {pr1645v2EthPrtSwF2InQueuesH2PerformanceEntry 218103808}

pr1645v2EthPrtSwF2InQueuesH2PerformanceCirTxOcts OBJECT-TYPE
   SYNTAX      Counter64
   MAX-ACCESS  read-only
   STATUS      current
   DESCRIPTION
      "Path: swPort.performance.ifInPriorityQueues.h2Performance.cirTxOctets

       64 bit unsigned wrappable counter."
   ::= {pr1645v2EthPrtSwF2InQueuesH2PerformanceEntry 167772160}

pr1645v2EthPrtSwF2InQueuesH2PerformanceEirTxOcts OBJECT-TYPE
   SYNTAX      Counter64
   MAX-ACCESS  read-only
   STATUS      current
   DESCRIPTION
      "Path: swPort.performance.ifInPriorityQueues.h2Performance.eirTxOctets

       64 bit unsigned wrappable counter."
   ::= {pr1645v2EthPrtSwF2InQueuesH2PerformanceEntry 184549376}

pr1645v2EthPrtSwF2InQueuesH2PerformanceViolTxOcts OBJECT-TYPE
   SYNTAX      Counter64
   MAX-ACCESS  read-only
   STATUS      current
   DESCRIPTION
      "Path: swPort.performance.ifInPriorityQueues.h2Performance.violateTxOctets

       64 bit unsigned wrappable counter."
   ::= {pr1645v2EthPrtSwF2InQueuesH2PerformanceEntry 318767104}

pr1645v2EthPrtSwF2InQueuesH2PerformanceBandwidth OBJECT-TYPE
   SYNTAX      Integer32
   MAX-ACCESS  read-only
   STATUS      current
   DESCRIPTION
      "Path: swPort.performance.ifInPriorityQueues.h2Performance.bandwidth

       unit name = bps
       formula = 8 * ; 8 /"
   ::= {pr1645v2EthPrtSwF2InQueuesH2PerformanceEntry 268435456}

pr1645v2EthPrtSwF2InQueuesH24Performance OBJECT-TYPE
   SYNTAX      SEQUENCE OF Pr1645v2EthPrtSwF2InQueuesH24PerformanceEntry
   MAX-ACCESS  not-accessible
   STATUS      current
   DESCRIPTION
      ""
   ::= {pr1645v2EthPrtSwF2InQueues 100663296}

pr1645v2EthPrtSwF2InQueuesH24PerformanceEntry OBJECT-TYPE
   SYNTAX      Pr1645v2EthPrtSwF2InQueuesH24PerformanceEntry
   MAX-ACCESS  not-accessible
   STATUS      current
   DESCRIPTION
      ""
   INDEX      { pr1645v2EthPrtSwF2InQueuesH24PerformanceGlobalIx,
                pr1645v2EthPrtSwF2InQueuesTableIx,
                pr1645v2EthPrtSwF2InQueuesH24PerformanceTableIx }
   ::= {pr1645v2EthPrtSwF2InQueuesH24Performance 1}

Pr1645v2EthPrtSwF2InQueuesH24PerformanceEntry ::=
   SEQUENCE
      {
      pr1645v2EthPrtSwF2InQueuesH24PerformanceGlobalIx
         GlobalIndex,
      pr1645v2EthPrtSwF2InQueuesH24PerformanceTableIx
         TableIndex,
      pr1645v2EthPrtSwF2InQueuesH24PerformanceSysUpTime
         TimeTicks,
      pr1645v2EthPrtSwF2InQueuesH24PerformanceTotPkts
         Counter64,
      pr1645v2EthPrtSwF2InQueuesH24PerformanceDirTxPkts
         Counter64,
      pr1645v2EthPrtSwF2InQueuesH24PerformanceQdPkts
         Counter64,
      pr1645v2EthPrtSwF2InQueuesH24PerformanceDropPkts
         Counter64,
      pr1645v2EthPrtSwF2InQueuesH24PerformanceRDropPkts
         Counter64,
      pr1645v2EthPrtSwF2InQueuesH24PerformanceCirTxPkts
         Counter64,
      pr1645v2EthPrtSwF2InQueuesH24PerformanceEirTxPkts
         Counter64,
      pr1645v2EthPrtSwF2InQueuesH24PerformanceViolTxPkts
         Counter64,
      pr1645v2EthPrtSwF2InQueuesH24PerformanceTotOcts
         Counter64,
      pr1645v2EthPrtSwF2InQueuesH24PerformanceDirTxOcts
         Counter64,
      pr1645v2EthPrtSwF2InQueuesH24PerformanceQdOcts
         Counter64,
      pr1645v2EthPrtSwF2InQueuesH24PerformanceDropOcts
         Counter64,
      pr1645v2EthPrtSwF2InQueuesH24PerformanceRDropOcts
         Counter64,
      pr1645v2EthPrtSwF2InQueuesH24PerformanceCirTxOcts
         Counter64,
      pr1645v2EthPrtSwF2InQueuesH24PerformanceEirTxOcts
         Counter64,
      pr1645v2EthPrtSwF2InQueuesH24PerformanceViolTxOcts
         Counter64,
      pr1645v2EthPrtSwF2InQueuesH24PerformanceBandwidth
         Integer32
      }

pr1645v2EthPrtSwF2InQueuesH24PerformanceGlobalIx OBJECT-TYPE
   SYNTAX      GlobalIndex
   MAX-ACCESS  not-accessible
   STATUS      current
   DESCRIPTION
      "The value of the tlsCntTreeGlobalIndex of the MANAGED OBJECT."
   ::= {pr1645v2EthPrtSwF2InQueuesH24PerformanceEntry 10}

pr1645v2EthPrtSwF2InQueuesH24PerformanceTableIx OBJECT-TYPE
   SYNTAX      TableIndex
   MAX-ACCESS  not-accessible
   STATUS      current
   DESCRIPTION
      ""
   ::= {pr1645v2EthPrtSwF2InQueuesH24PerformanceEntry 11}

pr1645v2EthPrtSwF2InQueuesH24PerformanceSysUpTime OBJECT-TYPE
   SYNTAX      TimeTicks
   MAX-ACCESS  read-only
   STATUS      current
   DESCRIPTION
      "Path: swPort.performance.ifInPriorityQueues.h24Performance.sysUpTime

       Time in centi-second."
   ::= {pr1645v2EthPrtSwF2InQueuesH24PerformanceEntry 16777216}

pr1645v2EthPrtSwF2InQueuesH24PerformanceTotPkts OBJECT-TYPE
   SYNTAX      Counter64
   MAX-ACCESS  read-only
   STATUS      current
   DESCRIPTION
      "Path: swPort.performance.ifInPriorityQueues.h24Performance.totalPkts

       64 bit unsigned wrappable counter."
   ::= {pr1645v2EthPrtSwF2InQueuesH24PerformanceEntry 234881024}

pr1645v2EthPrtSwF2InQueuesH24PerformanceDirTxPkts OBJECT-TYPE
   SYNTAX      Counter64
   MAX-ACCESS  read-only
   STATUS      current
   DESCRIPTION
      "Path: swPort.performance.ifInPriorityQueues.h24Performance.directTxPkts

       64 bit unsigned wrappable counter."
   ::= {pr1645v2EthPrtSwF2InQueuesH24PerformanceEntry 33554432}

pr1645v2EthPrtSwF2InQueuesH24PerformanceQdPkts OBJECT-TYPE
   SYNTAX      Counter64
   MAX-ACCESS  read-only
   STATUS      current
   DESCRIPTION
      "Path: swPort.performance.ifInPriorityQueues.h24Performance.queuedPkts

       64 bit unsigned wrappable counter."
   ::= {pr1645v2EthPrtSwF2InQueuesH24PerformanceEntry 50331648}

pr1645v2EthPrtSwF2InQueuesH24PerformanceDropPkts OBJECT-TYPE
   SYNTAX      Counter64
   MAX-ACCESS  read-only
   STATUS      current
   DESCRIPTION
      "Path: swPort.performance.ifInPriorityQueues.h24Performance.droppedPkts

       64 bit unsigned wrappable counter."
   ::= {pr1645v2EthPrtSwF2InQueuesH24PerformanceEntry 67108864}

pr1645v2EthPrtSwF2InQueuesH24PerformanceRDropPkts OBJECT-TYPE
   SYNTAX      Counter64
   MAX-ACCESS  read-only
   STATUS      current
   DESCRIPTION
      "Path: swPort.performance.ifInPriorityQueues.h24Performance.redDroppedPkts

       64 bit unsigned wrappable counter."
   ::= {pr1645v2EthPrtSwF2InQueuesH24PerformanceEntry 201326592}

pr1645v2EthPrtSwF2InQueuesH24PerformanceCirTxPkts OBJECT-TYPE
   SYNTAX      Counter64
   MAX-ACCESS  read-only
   STATUS      current
   DESCRIPTION
      "Path: swPort.performance.ifInPriorityQueues.h24Performance.cirTxPkts

       64 bit unsigned wrappable counter."
   ::= {pr1645v2EthPrtSwF2InQueuesH24PerformanceEntry 83886080}

pr1645v2EthPrtSwF2InQueuesH24PerformanceEirTxPkts OBJECT-TYPE
   SYNTAX      Counter64
   MAX-ACCESS  read-only
   STATUS      current
   DESCRIPTION
      "Path: swPort.performance.ifInPriorityQueues.h24Performance.eirTxPkts

       64 bit unsigned wrappable counter."
   ::= {pr1645v2EthPrtSwF2InQueuesH24PerformanceEntry 100663296}

pr1645v2EthPrtSwF2InQueuesH24PerformanceViolTxPkts OBJECT-TYPE
   SYNTAX      Counter64
   MAX-ACCESS  read-only
   STATUS      current
   DESCRIPTION
      "Path: swPort.performance.ifInPriorityQueues.h24Performance.violateTxPkts

       64 bit unsigned wrappable counter."
   ::= {pr1645v2EthPrtSwF2InQueuesH24PerformanceEntry 301989888}

pr1645v2EthPrtSwF2InQueuesH24PerformanceTotOcts OBJECT-TYPE
   SYNTAX      Counter64
   MAX-ACCESS  read-only
   STATUS      current
   DESCRIPTION
      "Path: swPort.performance.ifInPriorityQueues.h24Performance.totalOctets

       64 bit unsigned wrappable counter."
   ::= {pr1645v2EthPrtSwF2InQueuesH24PerformanceEntry 251658240}

pr1645v2EthPrtSwF2InQueuesH24PerformanceDirTxOcts OBJECT-TYPE
   SYNTAX      Counter64
   MAX-ACCESS  read-only
   STATUS      current
   DESCRIPTION
      "Path: swPort.performance.ifInPriorityQueues.h24Performance.directTxOctets

       64 bit unsigned wrappable counter."
   ::= {pr1645v2EthPrtSwF2InQueuesH24PerformanceEntry 117440512}

pr1645v2EthPrtSwF2InQueuesH24PerformanceQdOcts OBJECT-TYPE
   SYNTAX      Counter64
   MAX-ACCESS  read-only
   STATUS      current
   DESCRIPTION
      "Path: swPort.performance.ifInPriorityQueues.h24Performance.queuedOctets

       64 bit unsigned wrappable counter."
   ::= {pr1645v2EthPrtSwF2InQueuesH24PerformanceEntry 134217728}

pr1645v2EthPrtSwF2InQueuesH24PerformanceDropOcts OBJECT-TYPE
   SYNTAX      Counter64
   MAX-ACCESS  read-only
   STATUS      current
   DESCRIPTION
      "Path: swPort.performance.ifInPriorityQueues.h24Performance.droppedOctets

       64 bit unsigned wrappable counter."
   ::= {pr1645v2EthPrtSwF2InQueuesH24PerformanceEntry 150994944}

pr1645v2EthPrtSwF2InQueuesH24PerformanceRDropOcts OBJECT-TYPE
   SYNTAX      Counter64
   MAX-ACCESS  read-only
   STATUS      current
   DESCRIPTION
      "Path: swPort.performance.ifInPriorityQueues.h24Performance.redDroppedOctets

       64 bit unsigned wrappable counter."
   ::= {pr1645v2EthPrtSwF2InQueuesH24PerformanceEntry 218103808}

pr1645v2EthPrtSwF2InQueuesH24PerformanceCirTxOcts OBJECT-TYPE
   SYNTAX      Counter64
   MAX-ACCESS  read-only
   STATUS      current
   DESCRIPTION
      "Path: swPort.performance.ifInPriorityQueues.h24Performance.cirTxOctets

       64 bit unsigned wrappable counter."
   ::= {pr1645v2EthPrtSwF2InQueuesH24PerformanceEntry 167772160}

pr1645v2EthPrtSwF2InQueuesH24PerformanceEirTxOcts OBJECT-TYPE
   SYNTAX      Counter64
   MAX-ACCESS  read-only
   STATUS      current
   DESCRIPTION
      "Path: swPort.performance.ifInPriorityQueues.h24Performance.eirTxOctets

       64 bit unsigned wrappable counter."
   ::= {pr1645v2EthPrtSwF2InQueuesH24PerformanceEntry 184549376}

pr1645v2EthPrtSwF2InQueuesH24PerformanceViolTxOcts OBJECT-TYPE
   SYNTAX      Counter64
   MAX-ACCESS  read-only
   STATUS      current
   DESCRIPTION
      "Path: swPort.performance.ifInPriorityQueues.h24Performance.violateTxOctets

       64 bit unsigned wrappable counter."
   ::= {pr1645v2EthPrtSwF2InQueuesH24PerformanceEntry 318767104}

pr1645v2EthPrtSwF2InQueuesH24PerformanceBandwidth OBJECT-TYPE
   SYNTAX      Integer32
   MAX-ACCESS  read-only
   STATUS      current
   DESCRIPTION
      "Path: swPort.performance.ifInPriorityQueues.h24Performance.bandwidth

       unit name = bps
       formula = 8 * ; 8 /"
   ::= {pr1645v2EthPrtSwF2InQueuesH24PerformanceEntry 268435456}

pr1645v2EthPrtSwF2InQueuesD7Performance OBJECT-TYPE
   SYNTAX      SEQUENCE OF Pr1645v2EthPrtSwF2InQueuesD7PerformanceEntry
   MAX-ACCESS  not-accessible
   STATUS      current
   DESCRIPTION
      ""
   ::= {pr1645v2EthPrtSwF2InQueues 117440512}

pr1645v2EthPrtSwF2InQueuesD7PerformanceEntry OBJECT-TYPE
   SYNTAX      Pr1645v2EthPrtSwF2InQueuesD7PerformanceEntry
   MAX-ACCESS  not-accessible
   STATUS      current
   DESCRIPTION
      ""
   INDEX      { pr1645v2EthPrtSwF2InQueuesD7PerformanceGlobalIx,
                pr1645v2EthPrtSwF2InQueuesTableIx,
                pr1645v2EthPrtSwF2InQueuesD7PerformanceTableIx }
   ::= {pr1645v2EthPrtSwF2InQueuesD7Performance 1}

Pr1645v2EthPrtSwF2InQueuesD7PerformanceEntry ::=
   SEQUENCE
      {
      pr1645v2EthPrtSwF2InQueuesD7PerformanceGlobalIx
         GlobalIndex,
      pr1645v2EthPrtSwF2InQueuesD7PerformanceTableIx
         TableIndex,
      pr1645v2EthPrtSwF2InQueuesD7PerformanceSysUpTime
         TimeTicks,
      pr1645v2EthPrtSwF2InQueuesD7PerformanceTotPkts
         Counter64,
      pr1645v2EthPrtSwF2InQueuesD7PerformanceDirTxPkts
         Counter64,
      pr1645v2EthPrtSwF2InQueuesD7PerformanceQdPkts
         Counter64,
      pr1645v2EthPrtSwF2InQueuesD7PerformanceDropPkts
         Counter64,
      pr1645v2EthPrtSwF2InQueuesD7PerformanceRDropPkts
         Counter64,
      pr1645v2EthPrtSwF2InQueuesD7PerformanceCirTxPkts
         Counter64,
      pr1645v2EthPrtSwF2InQueuesD7PerformanceEirTxPkts
         Counter64,
      pr1645v2EthPrtSwF2InQueuesD7PerformanceViolTxPkts
         Counter64,
      pr1645v2EthPrtSwF2InQueuesD7PerformanceTotOcts
         Counter64,
      pr1645v2EthPrtSwF2InQueuesD7PerformanceDirTxOcts
         Counter64,
      pr1645v2EthPrtSwF2InQueuesD7PerformanceQdOcts
         Counter64,
      pr1645v2EthPrtSwF2InQueuesD7PerformanceDropOcts
         Counter64,
      pr1645v2EthPrtSwF2InQueuesD7PerformanceRDropOcts
         Counter64,
      pr1645v2EthPrtSwF2InQueuesD7PerformanceCirTxOcts
         Counter64,
      pr1645v2EthPrtSwF2InQueuesD7PerformanceEirTxOcts
         Counter64,
      pr1645v2EthPrtSwF2InQueuesD7PerformanceViolTxOcts
         Counter64,
      pr1645v2EthPrtSwF2InQueuesD7PerformanceBandwidth
         Integer32
      }

pr1645v2EthPrtSwF2InQueuesD7PerformanceGlobalIx OBJECT-TYPE
   SYNTAX      GlobalIndex
   MAX-ACCESS  not-accessible
   STATUS      current
   DESCRIPTION
      "The value of the tlsCntTreeGlobalIndex of the MANAGED OBJECT."
   ::= {pr1645v2EthPrtSwF2InQueuesD7PerformanceEntry 10}

pr1645v2EthPrtSwF2InQueuesD7PerformanceTableIx OBJECT-TYPE
   SYNTAX      TableIndex
   MAX-ACCESS  not-accessible
   STATUS      current
   DESCRIPTION
      ""
   ::= {pr1645v2EthPrtSwF2InQueuesD7PerformanceEntry 11}

pr1645v2EthPrtSwF2InQueuesD7PerformanceSysUpTime OBJECT-TYPE
   SYNTAX      TimeTicks
   MAX-ACCESS  read-only
   STATUS      current
   DESCRIPTION
      "Path: swPort.performance.ifInPriorityQueues.d7Performance.sysUpTime

       Time in centi-second."
   ::= {pr1645v2EthPrtSwF2InQueuesD7PerformanceEntry 16777216}

pr1645v2EthPrtSwF2InQueuesD7PerformanceTotPkts OBJECT-TYPE
   SYNTAX      Counter64
   MAX-ACCESS  read-only
   STATUS      current
   DESCRIPTION
      "Path: swPort.performance.ifInPriorityQueues.d7Performance.totalPkts

       64 bit unsigned wrappable counter."
   ::= {pr1645v2EthPrtSwF2InQueuesD7PerformanceEntry 234881024}

pr1645v2EthPrtSwF2InQueuesD7PerformanceDirTxPkts OBJECT-TYPE
   SYNTAX      Counter64
   MAX-ACCESS  read-only
   STATUS      current
   DESCRIPTION
      "Path: swPort.performance.ifInPriorityQueues.d7Performance.directTxPkts

       64 bit unsigned wrappable counter."
   ::= {pr1645v2EthPrtSwF2InQueuesD7PerformanceEntry 33554432}

pr1645v2EthPrtSwF2InQueuesD7PerformanceQdPkts OBJECT-TYPE
   SYNTAX      Counter64
   MAX-ACCESS  read-only
   STATUS      current
   DESCRIPTION
      "Path: swPort.performance.ifInPriorityQueues.d7Performance.queuedPkts

       64 bit unsigned wrappable counter."
   ::= {pr1645v2EthPrtSwF2InQueuesD7PerformanceEntry 50331648}

pr1645v2EthPrtSwF2InQueuesD7PerformanceDropPkts OBJECT-TYPE
   SYNTAX      Counter64
   MAX-ACCESS  read-only
   STATUS      current
   DESCRIPTION
      "Path: swPort.performance.ifInPriorityQueues.d7Performance.droppedPkts

       64 bit unsigned wrappable counter."
   ::= {pr1645v2EthPrtSwF2InQueuesD7PerformanceEntry 67108864}

pr1645v2EthPrtSwF2InQueuesD7PerformanceRDropPkts OBJECT-TYPE
   SYNTAX      Counter64
   MAX-ACCESS  read-only
   STATUS      current
   DESCRIPTION
      "Path: swPort.performance.ifInPriorityQueues.d7Performance.redDroppedPkts

       64 bit unsigned wrappable counter."
   ::= {pr1645v2EthPrtSwF2InQueuesD7PerformanceEntry 201326592}

pr1645v2EthPrtSwF2InQueuesD7PerformanceCirTxPkts OBJECT-TYPE
   SYNTAX      Counter64
   MAX-ACCESS  read-only
   STATUS      current
   DESCRIPTION
      "Path: swPort.performance.ifInPriorityQueues.d7Performance.cirTxPkts

       64 bit unsigned wrappable counter."
   ::= {pr1645v2EthPrtSwF2InQueuesD7PerformanceEntry 83886080}

pr1645v2EthPrtSwF2InQueuesD7PerformanceEirTxPkts OBJECT-TYPE
   SYNTAX      Counter64
   MAX-ACCESS  read-only
   STATUS      current
   DESCRIPTION
      "Path: swPort.performance.ifInPriorityQueues.d7Performance.eirTxPkts

       64 bit unsigned wrappable counter."
   ::= {pr1645v2EthPrtSwF2InQueuesD7PerformanceEntry 100663296}

pr1645v2EthPrtSwF2InQueuesD7PerformanceViolTxPkts OBJECT-TYPE
   SYNTAX      Counter64
   MAX-ACCESS  read-only
   STATUS      current
   DESCRIPTION
      "Path: swPort.performance.ifInPriorityQueues.d7Performance.violateTxPkts

       64 bit unsigned wrappable counter."
   ::= {pr1645v2EthPrtSwF2InQueuesD7PerformanceEntry 301989888}

pr1645v2EthPrtSwF2InQueuesD7PerformanceTotOcts OBJECT-TYPE
   SYNTAX      Counter64
   MAX-ACCESS  read-only
   STATUS      current
   DESCRIPTION
      "Path: swPort.performance.ifInPriorityQueues.d7Performance.totalOctets

       64 bit unsigned wrappable counter."
   ::= {pr1645v2EthPrtSwF2InQueuesD7PerformanceEntry 251658240}

pr1645v2EthPrtSwF2InQueuesD7PerformanceDirTxOcts OBJECT-TYPE
   SYNTAX      Counter64
   MAX-ACCESS  read-only
   STATUS      current
   DESCRIPTION
      "Path: swPort.performance.ifInPriorityQueues.d7Performance.directTxOctets

       64 bit unsigned wrappable counter."
   ::= {pr1645v2EthPrtSwF2InQueuesD7PerformanceEntry 117440512}

pr1645v2EthPrtSwF2InQueuesD7PerformanceQdOcts OBJECT-TYPE
   SYNTAX      Counter64
   MAX-ACCESS  read-only
   STATUS      current
   DESCRIPTION
      "Path: swPort.performance.ifInPriorityQueues.d7Performance.queuedOctets

       64 bit unsigned wrappable counter."
   ::= {pr1645v2EthPrtSwF2InQueuesD7PerformanceEntry 134217728}

pr1645v2EthPrtSwF2InQueuesD7PerformanceDropOcts OBJECT-TYPE
   SYNTAX      Counter64
   MAX-ACCESS  read-only
   STATUS      current
   DESCRIPTION
      "Path: swPort.performance.ifInPriorityQueues.d7Performance.droppedOctets

       64 bit unsigned wrappable counter."
   ::= {pr1645v2EthPrtSwF2InQueuesD7PerformanceEntry 150994944}

pr1645v2EthPrtSwF2InQueuesD7PerformanceRDropOcts OBJECT-TYPE
   SYNTAX      Counter64
   MAX-ACCESS  read-only
   STATUS      current
   DESCRIPTION
      "Path: swPort.performance.ifInPriorityQueues.d7Performance.redDroppedOctets

       64 bit unsigned wrappable counter."
   ::= {pr1645v2EthPrtSwF2InQueuesD7PerformanceEntry 218103808}

pr1645v2EthPrtSwF2InQueuesD7PerformanceCirTxOcts OBJECT-TYPE
   SYNTAX      Counter64
   MAX-ACCESS  read-only
   STATUS      current
   DESCRIPTION
      "Path: swPort.performance.ifInPriorityQueues.d7Performance.cirTxOctets

       64 bit unsigned wrappable counter."
   ::= {pr1645v2EthPrtSwF2InQueuesD7PerformanceEntry 167772160}

pr1645v2EthPrtSwF2InQueuesD7PerformanceEirTxOcts OBJECT-TYPE
   SYNTAX      Counter64
   MAX-ACCESS  read-only
   STATUS      current
   DESCRIPTION
      "Path: swPort.performance.ifInPriorityQueues.d7Performance.eirTxOctets

       64 bit unsigned wrappable counter."
   ::= {pr1645v2EthPrtSwF2InQueuesD7PerformanceEntry 184549376}

pr1645v2EthPrtSwF2InQueuesD7PerformanceViolTxOcts OBJECT-TYPE
   SYNTAX      Counter64
   MAX-ACCESS  read-only
   STATUS      current
   DESCRIPTION
      "Path: swPort.performance.ifInPriorityQueues.d7Performance.violateTxOctets

       64 bit unsigned wrappable counter."
   ::= {pr1645v2EthPrtSwF2InQueuesD7PerformanceEntry 318767104}

pr1645v2EthPrtSwF2InQueuesD7PerformanceBandwidth OBJECT-TYPE
   SYNTAX      Integer32
   MAX-ACCESS  read-only
   STATUS      current
   DESCRIPTION
      "Path: swPort.performance.ifInPriorityQueues.d7Performance.bandwidth

       unit name = bps
       formula = 8 * ; 8 /"
   ::= {pr1645v2EthPrtSwF2InQueuesD7PerformanceEntry 268435456}


pr1645v2EthPrtSwF2InBandwidth OBJECT IDENTIFIER ::= {pr1645v2EthPrtSwF2 181}

pr1645v2EthPrtSwF2InBandwidthSSCTable OBJECT-TYPE
   SYNTAX      SEQUENCE OF Pr1645v2EthPrtSwF2InBandwidthEntry
   MAX-ACCESS  not-accessible
   STATUS      current
   DESCRIPTION
      "bandwidth"
   ::= {pr1645v2EthPrtSwF2InBandwidth 1}

pr1645v2EthPrtSwF2InBandwidthEntry OBJECT-TYPE
   SYNTAX      Pr1645v2EthPrtSwF2InBandwidthEntry
   MAX-ACCESS  not-accessible
   STATUS      current
   DESCRIPTION
      ""
   INDEX      { pr1645v2EthPrtSwF2InBandwidthGlobalIx }
   ::= {pr1645v2EthPrtSwF2InBandwidthSSCTable 1}

Pr1645v2EthPrtSwF2InBandwidthEntry ::=
   SEQUENCE
      {
      pr1645v2EthPrtSwF2InBandwidthGlobalIx
         GlobalIndex,
      pr1645v2EthPrtSwF2InBandwidth15sec
         Integer32,
      pr1645v2EthPrtSwF2InBandwidth30sec
         Integer32,
      pr1645v2EthPrtSwF2InBandwidth1min
         Integer32,
      pr1645v2EthPrtSwF2InBandwidth2min
         Integer32,
      pr1645v2EthPrtSwF2InBandwidth5min
         Integer32
      }

pr1645v2EthPrtSwF2InBandwidthGlobalIx OBJECT-TYPE
   SYNTAX      GlobalIndex
   MAX-ACCESS  not-accessible
   STATUS      current
   DESCRIPTION
      "The value of the tlsCntTreeGlobalIndex of the MANAGED OBJECT."
   ::= {pr1645v2EthPrtSwF2InBandwidthEntry 10}

pr1645v2EthPrtSwF2InBandwidth15sec OBJECT-TYPE
   SYNTAX      Integer32
   MAX-ACCESS  read-only
   STATUS      current
   DESCRIPTION
      "Path: swPort.performance.ifInBandwidth.15sec

       unit name = bps
       formula = 8 * ; 8 /"
   ::= {pr1645v2EthPrtSwF2InBandwidthEntry 83886080}

pr1645v2EthPrtSwF2InBandwidth30sec OBJECT-TYPE
   SYNTAX      Integer32
   MAX-ACCESS  read-only
   STATUS      current
   DESCRIPTION
      "Path: swPort.performance.ifInBandwidth.30sec

       unit name = bps
       formula = 8 * ; 8 /"
   ::= {pr1645v2EthPrtSwF2InBandwidthEntry 167772160}

pr1645v2EthPrtSwF2InBandwidth1min OBJECT-TYPE
   SYNTAX      Integer32
   MAX-ACCESS  read-only
   STATUS      current
   DESCRIPTION
      "Path: swPort.performance.ifInBandwidth.1min

       unit name = bps
       formula = 8 * ; 8 /"
   ::= {pr1645v2EthPrtSwF2InBandwidthEntry 335544320}

pr1645v2EthPrtSwF2InBandwidth2min OBJECT-TYPE
   SYNTAX      Integer32
   MAX-ACCESS  read-only
   STATUS      current
   DESCRIPTION
      "Path: swPort.performance.ifInBandwidth.2min

       unit name = bps
       formula = 8 * ; 8 /"
   ::= {pr1645v2EthPrtSwF2InBandwidthEntry 671088640}

pr1645v2EthPrtSwF2InBandwidth5min OBJECT-TYPE
   SYNTAX      Integer32
   MAX-ACCESS  read-only
   STATUS      current
   DESCRIPTION
      "Path: swPort.performance.ifInBandwidth.5min

       unit name = bps
       formula = 8 * ; 8 /"
   ::= {pr1645v2EthPrtSwF2InBandwidthEntry 1677721600}


pr1645v2EthPrtSwF2OutOctets OBJECT IDENTIFIER ::= {pr1645v2EthPrtSwF2 115}

pr1645v2EthPrtSwF2OutOctetsTable OBJECT-TYPE
   SYNTAX      SEQUENCE OF Pr1645v2EthPrtSwF2OutOctetsEntry
   MAX-ACCESS  not-accessible
   STATUS      current
   DESCRIPTION
      "ifOutOctets"
   ::= {pr1645v2EthPrtSwF2OutOctets 1}

pr1645v2EthPrtSwF2OutOctetsEntry OBJECT-TYPE
   SYNTAX      Pr1645v2EthPrtSwF2OutOctetsEntry
   MAX-ACCESS  not-accessible
   STATUS      current
   DESCRIPTION
      ""
   INDEX      { pr1645v2EthPrtSwF2OutOctetsGlobalIx }
   ::= {pr1645v2EthPrtSwF2OutOctetsTable 1}

Pr1645v2EthPrtSwF2OutOctetsEntry ::=
   SEQUENCE
      {
      pr1645v2EthPrtSwF2OutOctetsGlobalIx
         GlobalIndex,
      pr1645v2EthPrtSwF2OutOctetsValue
         Counter64
      }

pr1645v2EthPrtSwF2OutOctetsGlobalIx OBJECT-TYPE
   SYNTAX      GlobalIndex
   MAX-ACCESS  not-accessible
   STATUS      current
   DESCRIPTION
      "The value of the tlsCntTreeGlobalIndex of the MANAGED OBJECT."
   ::= {pr1645v2EthPrtSwF2OutOctetsEntry 10}

pr1645v2EthPrtSwF2OutOctetsValue OBJECT-TYPE
   SYNTAX      Counter64
   MAX-ACCESS  read-only
   STATUS      current
   DESCRIPTION
      "Path: swPort.performance.ifOutOctets

       64 bit unsigned wrappable counter."
   ::= {pr1645v2EthPrtSwF2OutOctetsEntry 2147483648}


pr1645v2EthPrtSwF2OutUcastPkts OBJECT IDENTIFIER ::= {pr1645v2EthPrtSwF2 116}

pr1645v2EthPrtSwF2OutUcastPktsTable OBJECT-TYPE
   SYNTAX      SEQUENCE OF Pr1645v2EthPrtSwF2OutUcastPktsEntry
   MAX-ACCESS  not-accessible
   STATUS      current
   DESCRIPTION
      "ifOutUcastPkts"
   ::= {pr1645v2EthPrtSwF2OutUcastPkts 1}

pr1645v2EthPrtSwF2OutUcastPktsEntry OBJECT-TYPE
   SYNTAX      Pr1645v2EthPrtSwF2OutUcastPktsEntry
   MAX-ACCESS  not-accessible
   STATUS      current
   DESCRIPTION
      ""
   INDEX      { pr1645v2EthPrtSwF2OutUcastPktsGlobalIx }
   ::= {pr1645v2EthPrtSwF2OutUcastPktsTable 1}

Pr1645v2EthPrtSwF2OutUcastPktsEntry ::=
   SEQUENCE
      {
      pr1645v2EthPrtSwF2OutUcastPktsGlobalIx
         GlobalIndex,
      pr1645v2EthPrtSwF2OutUcastPktsValue
         Counter64
      }

pr1645v2EthPrtSwF2OutUcastPktsGlobalIx OBJECT-TYPE
   SYNTAX      GlobalIndex
   MAX-ACCESS  not-accessible
   STATUS      current
   DESCRIPTION
      "The value of the tlsCntTreeGlobalIndex of the MANAGED OBJECT."
   ::= {pr1645v2EthPrtSwF2OutUcastPktsEntry 10}

pr1645v2EthPrtSwF2OutUcastPktsValue OBJECT-TYPE
   SYNTAX      Counter64
   MAX-ACCESS  read-only
   STATUS      current
   DESCRIPTION
      "Path: swPort.performance.ifOutUcastPkts

       64 bit unsigned wrappable counter."
   ::= {pr1645v2EthPrtSwF2OutUcastPktsEntry 2147483648}


pr1645v2EthPrtSwF2OutNUcastPkts OBJECT IDENTIFIER ::= {pr1645v2EthPrtSwF2 117}

pr1645v2EthPrtSwF2OutNUcastPktsTable OBJECT-TYPE
   SYNTAX      SEQUENCE OF Pr1645v2EthPrtSwF2OutNUcastPktsEntry
   MAX-ACCESS  not-accessible
   STATUS      current
   DESCRIPTION
      "ifOutNUcastPkts"
   ::= {pr1645v2EthPrtSwF2OutNUcastPkts 1}

pr1645v2EthPrtSwF2OutNUcastPktsEntry OBJECT-TYPE
   SYNTAX      Pr1645v2EthPrtSwF2OutNUcastPktsEntry
   MAX-ACCESS  not-accessible
   STATUS      current
   DESCRIPTION
      ""
   INDEX      { pr1645v2EthPrtSwF2OutNUcastPktsGlobalIx }
   ::= {pr1645v2EthPrtSwF2OutNUcastPktsTable 1}

Pr1645v2EthPrtSwF2OutNUcastPktsEntry ::=
   SEQUENCE
      {
      pr1645v2EthPrtSwF2OutNUcastPktsGlobalIx
         GlobalIndex,
      pr1645v2EthPrtSwF2OutNUcastPktsValue
         Counter64
      }

pr1645v2EthPrtSwF2OutNUcastPktsGlobalIx OBJECT-TYPE
   SYNTAX      GlobalIndex
   MAX-ACCESS  not-accessible
   STATUS      current
   DESCRIPTION
      "The value of the tlsCntTreeGlobalIndex of the MANAGED OBJECT."
   ::= {pr1645v2EthPrtSwF2OutNUcastPktsEntry 10}

pr1645v2EthPrtSwF2OutNUcastPktsValue OBJECT-TYPE
   SYNTAX      Counter64
   MAX-ACCESS  read-only
   STATUS      current
   DESCRIPTION
      "Path: swPort.performance.ifOutNUcastPkts

       64 bit unsigned wrappable counter."
   ::= {pr1645v2EthPrtSwF2OutNUcastPktsEntry 2147483648}


pr1645v2EthPrtSwF2OutBcastPkts OBJECT IDENTIFIER ::= {pr1645v2EthPrtSwF2 217}

pr1645v2EthPrtSwF2OutBcastPktsTable OBJECT-TYPE
   SYNTAX      SEQUENCE OF Pr1645v2EthPrtSwF2OutBcastPktsEntry
   MAX-ACCESS  not-accessible
   STATUS      current
   DESCRIPTION
      "ifOutBcastPkts"
   ::= {pr1645v2EthPrtSwF2OutBcastPkts 1}

pr1645v2EthPrtSwF2OutBcastPktsEntry OBJECT-TYPE
   SYNTAX      Pr1645v2EthPrtSwF2OutBcastPktsEntry
   MAX-ACCESS  not-accessible
   STATUS      current
   DESCRIPTION
      ""
   INDEX      { pr1645v2EthPrtSwF2OutBcastPktsGlobalIx }
   ::= {pr1645v2EthPrtSwF2OutBcastPktsTable 1}

Pr1645v2EthPrtSwF2OutBcastPktsEntry ::=
   SEQUENCE
      {
      pr1645v2EthPrtSwF2OutBcastPktsGlobalIx
         GlobalIndex,
      pr1645v2EthPrtSwF2OutBcastPktsValue
         Counter64
      }

pr1645v2EthPrtSwF2OutBcastPktsGlobalIx OBJECT-TYPE
   SYNTAX      GlobalIndex
   MAX-ACCESS  not-accessible
   STATUS      current
   DESCRIPTION
      "The value of the tlsCntTreeGlobalIndex of the MANAGED OBJECT."
   ::= {pr1645v2EthPrtSwF2OutBcastPktsEntry 10}

pr1645v2EthPrtSwF2OutBcastPktsValue OBJECT-TYPE
   SYNTAX      Counter64
   MAX-ACCESS  read-only
   STATUS      current
   DESCRIPTION
      "Path: swPort.performance.ifOutBcastPkts

       64 bit unsigned wrappable counter."
   ::= {pr1645v2EthPrtSwF2OutBcastPktsEntry 2147483648}


pr1645v2EthPrtSwF2OutMcastPkts OBJECT IDENTIFIER ::= {pr1645v2EthPrtSwF2 227}

pr1645v2EthPrtSwF2OutMcastPktsTable OBJECT-TYPE
   SYNTAX      SEQUENCE OF Pr1645v2EthPrtSwF2OutMcastPktsEntry
   MAX-ACCESS  not-accessible
   STATUS      current
   DESCRIPTION
      "ifOutMcastPkts"
   ::= {pr1645v2EthPrtSwF2OutMcastPkts 1}

pr1645v2EthPrtSwF2OutMcastPktsEntry OBJECT-TYPE
   SYNTAX      Pr1645v2EthPrtSwF2OutMcastPktsEntry
   MAX-ACCESS  not-accessible
   STATUS      current
   DESCRIPTION
      ""
   INDEX      { pr1645v2EthPrtSwF2OutMcastPktsGlobalIx }
   ::= {pr1645v2EthPrtSwF2OutMcastPktsTable 1}

Pr1645v2EthPrtSwF2OutMcastPktsEntry ::=
   SEQUENCE
      {
      pr1645v2EthPrtSwF2OutMcastPktsGlobalIx
         GlobalIndex,
      pr1645v2EthPrtSwF2OutMcastPktsValue
         Counter64
      }

pr1645v2EthPrtSwF2OutMcastPktsGlobalIx OBJECT-TYPE
   SYNTAX      GlobalIndex
   MAX-ACCESS  not-accessible
   STATUS      current
   DESCRIPTION
      "The value of the tlsCntTreeGlobalIndex of the MANAGED OBJECT."
   ::= {pr1645v2EthPrtSwF2OutMcastPktsEntry 10}

pr1645v2EthPrtSwF2OutMcastPktsValue OBJECT-TYPE
   SYNTAX      Counter64
   MAX-ACCESS  read-only
   STATUS      current
   DESCRIPTION
      "Path: swPort.performance.ifOutMcastPkts

       64 bit unsigned wrappable counter."
   ::= {pr1645v2EthPrtSwF2OutMcastPktsEntry 2147483648}


pr1645v2EthPrtSwF2OutDiscards OBJECT IDENTIFIER ::= {pr1645v2EthPrtSwF2 118}

pr1645v2EthPrtSwF2OutDiscardsTable OBJECT-TYPE
   SYNTAX      SEQUENCE OF Pr1645v2EthPrtSwF2OutDiscardsEntry
   MAX-ACCESS  not-accessible
   STATUS      current
   DESCRIPTION
      "ifOutDiscards"
   ::= {pr1645v2EthPrtSwF2OutDiscards 1}

pr1645v2EthPrtSwF2OutDiscardsEntry OBJECT-TYPE
   SYNTAX      Pr1645v2EthPrtSwF2OutDiscardsEntry
   MAX-ACCESS  not-accessible
   STATUS      current
   DESCRIPTION
      ""
   INDEX      { pr1645v2EthPrtSwF2OutDiscardsGlobalIx }
   ::= {pr1645v2EthPrtSwF2OutDiscardsTable 1}

Pr1645v2EthPrtSwF2OutDiscardsEntry ::=
   SEQUENCE
      {
      pr1645v2EthPrtSwF2OutDiscardsGlobalIx
         GlobalIndex,
      pr1645v2EthPrtSwF2OutDiscardsValue
         Counter64
      }

pr1645v2EthPrtSwF2OutDiscardsGlobalIx OBJECT-TYPE
   SYNTAX      GlobalIndex
   MAX-ACCESS  not-accessible
   STATUS      current
   DESCRIPTION
      "The value of the tlsCntTreeGlobalIndex of the MANAGED OBJECT."
   ::= {pr1645v2EthPrtSwF2OutDiscardsEntry 10}

pr1645v2EthPrtSwF2OutDiscardsValue OBJECT-TYPE
   SYNTAX      Counter64
   MAX-ACCESS  read-only
   STATUS      current
   DESCRIPTION
      "Path: swPort.performance.ifOutDiscards

       64 bit unsigned wrappable counter."
   ::= {pr1645v2EthPrtSwF2OutDiscardsEntry 2147483648}


pr1645v2EthPrtSwF2OutErrors OBJECT IDENTIFIER ::= {pr1645v2EthPrtSwF2 119}

pr1645v2EthPrtSwF2OutErrorsTable OBJECT-TYPE
   SYNTAX      SEQUENCE OF Pr1645v2EthPrtSwF2OutErrorsEntry
   MAX-ACCESS  not-accessible
   STATUS      current
   DESCRIPTION
      "ifOutErrors"
   ::= {pr1645v2EthPrtSwF2OutErrors 1}

pr1645v2EthPrtSwF2OutErrorsEntry OBJECT-TYPE
   SYNTAX      Pr1645v2EthPrtSwF2OutErrorsEntry
   MAX-ACCESS  not-accessible
   STATUS      current
   DESCRIPTION
      ""
   INDEX      { pr1645v2EthPrtSwF2OutErrorsGlobalIx }
   ::= {pr1645v2EthPrtSwF2OutErrorsTable 1}

Pr1645v2EthPrtSwF2OutErrorsEntry ::=
   SEQUENCE
      {
      pr1645v2EthPrtSwF2OutErrorsGlobalIx
         GlobalIndex,
      pr1645v2EthPrtSwF2OutErrorsValue
         Counter64
      }

pr1645v2EthPrtSwF2OutErrorsGlobalIx OBJECT-TYPE
   SYNTAX      GlobalIndex
   MAX-ACCESS  not-accessible
   STATUS      current
   DESCRIPTION
      "The value of the tlsCntTreeGlobalIndex of the MANAGED OBJECT."
   ::= {pr1645v2EthPrtSwF2OutErrorsEntry 10}

pr1645v2EthPrtSwF2OutErrorsValue OBJECT-TYPE
   SYNTAX      Counter64
   MAX-ACCESS  read-only
   STATUS      current
   DESCRIPTION
      "Path: swPort.performance.ifOutErrors

       64 bit unsigned wrappable counter."
   ::= {pr1645v2EthPrtSwF2OutErrorsEntry 2147483648}


pr1645v2EthPrtSwF2OutQLen OBJECT IDENTIFIER ::= {pr1645v2EthPrtSwF2 120}

pr1645v2EthPrtSwF2OutQLenTable OBJECT-TYPE
   SYNTAX      SEQUENCE OF Pr1645v2EthPrtSwF2OutQLenEntry
   MAX-ACCESS  not-accessible
   STATUS      current
   DESCRIPTION
      "ifOutQLen"
   ::= {pr1645v2EthPrtSwF2OutQLen 1}

pr1645v2EthPrtSwF2OutQLenEntry OBJECT-TYPE
   SYNTAX      Pr1645v2EthPrtSwF2OutQLenEntry
   MAX-ACCESS  not-accessible
   STATUS      current
   DESCRIPTION
      ""
   INDEX      { pr1645v2EthPrtSwF2OutQLenGlobalIx }
   ::= {pr1645v2EthPrtSwF2OutQLenTable 1}

Pr1645v2EthPrtSwF2OutQLenEntry ::=
   SEQUENCE
      {
      pr1645v2EthPrtSwF2OutQLenGlobalIx
         GlobalIndex,
      pr1645v2EthPrtSwF2OutQLenValue
         Gauge32
      }

pr1645v2EthPrtSwF2OutQLenGlobalIx OBJECT-TYPE
   SYNTAX      GlobalIndex
   MAX-ACCESS  not-accessible
   STATUS      current
   DESCRIPTION
      "The value of the tlsCntTreeGlobalIndex of the MANAGED OBJECT."
   ::= {pr1645v2EthPrtSwF2OutQLenEntry 10}

pr1645v2EthPrtSwF2OutQLenValue OBJECT-TYPE
   SYNTAX      Gauge32
   MAX-ACCESS  read-only
   STATUS      current
   DESCRIPTION
      "Path: swPort.performance.ifOutQLen

       32 bit unsigned gauge value."
   ::= {pr1645v2EthPrtSwF2OutQLenEntry 2147483648}


pr1645v2EthPrtSwF2OutDropEx OBJECT IDENTIFIER ::= {pr1645v2EthPrtSwF2 127}

pr1645v2EthPrtSwF2OutDropExTable OBJECT-TYPE
   SYNTAX      SEQUENCE OF Pr1645v2EthPrtSwF2OutDropExEntry
   MAX-ACCESS  not-accessible
   STATUS      current
   DESCRIPTION
      "ifOutDiscards"
   ::= {pr1645v2EthPrtSwF2OutDropEx 1}

pr1645v2EthPrtSwF2OutDropExEntry OBJECT-TYPE
   SYNTAX      Pr1645v2EthPrtSwF2OutDropExEntry
   MAX-ACCESS  not-accessible
   STATUS      current
   DESCRIPTION
      ""
   INDEX      { pr1645v2EthPrtSwF2OutDropExGlobalIx }
   ::= {pr1645v2EthPrtSwF2OutDropExTable 1}

Pr1645v2EthPrtSwF2OutDropExEntry ::=
   SEQUENCE
      {
      pr1645v2EthPrtSwF2OutDropExGlobalIx
         GlobalIndex,
      pr1645v2EthPrtSwF2OutDropExValue
         Counter64
      }

pr1645v2EthPrtSwF2OutDropExGlobalIx OBJECT-TYPE
   SYNTAX      GlobalIndex
   MAX-ACCESS  not-accessible
   STATUS      current
   DESCRIPTION
      "The value of the tlsCntTreeGlobalIndex of the MANAGED OBJECT."
   ::= {pr1645v2EthPrtSwF2OutDropExEntry 10}

pr1645v2EthPrtSwF2OutDropExValue OBJECT-TYPE
   SYNTAX      Counter64
   MAX-ACCESS  read-only
   STATUS      current
   DESCRIPTION
      "Path: swPort.performance.ifOutDropLevelExceeded

       64 bit unsigned wrappable counter."
   ::= {pr1645v2EthPrtSwF2OutDropExEntry 2147483648}


pr1645v2EthPrtSwF2OutDropNoArp OBJECT IDENTIFIER ::= {pr1645v2EthPrtSwF2 134}

pr1645v2EthPrtSwF2OutDropNoArpTable OBJECT-TYPE
   SYNTAX      SEQUENCE OF Pr1645v2EthPrtSwF2OutDropNoArpEntry
   MAX-ACCESS  not-accessible
   STATUS      current
   DESCRIPTION
      "ifOutDiscards"
   ::= {pr1645v2EthPrtSwF2OutDropNoArp 1}

pr1645v2EthPrtSwF2OutDropNoArpEntry OBJECT-TYPE
   SYNTAX      Pr1645v2EthPrtSwF2OutDropNoArpEntry
   MAX-ACCESS  not-accessible
   STATUS      current
   DESCRIPTION
      ""
   INDEX      { pr1645v2EthPrtSwF2OutDropNoArpGlobalIx }
   ::= {pr1645v2EthPrtSwF2OutDropNoArpTable 1}

Pr1645v2EthPrtSwF2OutDropNoArpEntry ::=
   SEQUENCE
      {
      pr1645v2EthPrtSwF2OutDropNoArpGlobalIx
         GlobalIndex,
      pr1645v2EthPrtSwF2OutDropNoArpValue
         Counter64
      }

pr1645v2EthPrtSwF2OutDropNoArpGlobalIx OBJECT-TYPE
   SYNTAX      GlobalIndex
   MAX-ACCESS  not-accessible
   STATUS      current
   DESCRIPTION
      "The value of the tlsCntTreeGlobalIndex of the MANAGED OBJECT."
   ::= {pr1645v2EthPrtSwF2OutDropNoArpEntry 10}

pr1645v2EthPrtSwF2OutDropNoArpValue OBJECT-TYPE
   SYNTAX      Counter64
   MAX-ACCESS  read-only
   STATUS      current
   DESCRIPTION
      "Path: swPort.performance.ifOutDiscardsNoArp

       64 bit unsigned wrappable counter."
   ::= {pr1645v2EthPrtSwF2OutDropNoArpEntry 2147483648}


pr1645v2EthPrtSwF2OutDropFilter OBJECT IDENTIFIER ::= {pr1645v2EthPrtSwF2 138}

pr1645v2EthPrtSwF2OutDropFilterTable OBJECT-TYPE
   SYNTAX      SEQUENCE OF Pr1645v2EthPrtSwF2OutDropFilterEntry
   MAX-ACCESS  not-accessible
   STATUS      current
   DESCRIPTION
      "ifOutDiscards"
   ::= {pr1645v2EthPrtSwF2OutDropFilter 1}

pr1645v2EthPrtSwF2OutDropFilterEntry OBJECT-TYPE
   SYNTAX      Pr1645v2EthPrtSwF2OutDropFilterEntry
   MAX-ACCESS  not-accessible
   STATUS      current
   DESCRIPTION
      ""
   INDEX      { pr1645v2EthPrtSwF2OutDropFilterGlobalIx }
   ::= {pr1645v2EthPrtSwF2OutDropFilterTable 1}

Pr1645v2EthPrtSwF2OutDropFilterEntry ::=
   SEQUENCE
      {
      pr1645v2EthPrtSwF2OutDropFilterGlobalIx
         GlobalIndex,
      pr1645v2EthPrtSwF2OutDropFilterValue
         Counter64
      }

pr1645v2EthPrtSwF2OutDropFilterGlobalIx OBJECT-TYPE
   SYNTAX      GlobalIndex
   MAX-ACCESS  not-accessible
   STATUS      current
   DESCRIPTION
      "The value of the tlsCntTreeGlobalIndex of the MANAGED OBJECT."
   ::= {pr1645v2EthPrtSwF2OutDropFilterEntry 10}

pr1645v2EthPrtSwF2OutDropFilterValue OBJECT-TYPE
   SYNTAX      Counter64
   MAX-ACCESS  read-only
   STATUS      current
   DESCRIPTION
      "Path: swPort.performance.ifOutDiscardsFilter

       64 bit unsigned wrappable counter."
   ::= {pr1645v2EthPrtSwF2OutDropFilterEntry 2147483648}


pr1645v2EthPrtSwF2OutQueues OBJECT IDENTIFIER ::= {pr1645v2EthPrtSwF2 129}

pr1645v2EthPrtSwF2OutQueuesSSCTable OBJECT-TYPE
   SYNTAX      SEQUENCE OF Pr1645v2EthPrtSwF2OutQueuesEntry
   MAX-ACCESS  not-accessible
   STATUS      current
   DESCRIPTION
      "Queue Lengths"
   ::= {pr1645v2EthPrtSwF2OutQueues 1}

pr1645v2EthPrtSwF2OutQueuesEntry OBJECT-TYPE
   SYNTAX      Pr1645v2EthPrtSwF2OutQueuesEntry
   MAX-ACCESS  not-accessible
   STATUS      current
   DESCRIPTION
      ""
   INDEX      { pr1645v2EthPrtSwF2OutQueuesGlobalIx,
                pr1645v2EthPrtSwF2OutQueuesTableIx }
   ::= {pr1645v2EthPrtSwF2OutQueuesSSCTable 1}

Pr1645v2EthPrtSwF2OutQueuesEntry ::=
   SEQUENCE
      {
      pr1645v2EthPrtSwF2OutQueuesGlobalIx
         GlobalIndex,
      pr1645v2EthPrtSwF2OutQueuesTableIx
         TableIndex,
      pr1645v2EthPrtSwF2OutQueuesName
         INTEGER,
      pr1645v2EthPrtSwF2OutQueuesLength
         Integer32,
      pr1645v2EthPrtSwF2OutQueuesOctetLength
         Integer32,
      pr1645v2EthPrtSwF2OutQueuesRedLength
         Integer32,
      pr1645v2EthPrtSwF2OutQueuesPacketsTotal
         Counter64,
      pr1645v2EthPrtSwF2OutQueuesPacketsDirectTx
         Counter64,
      pr1645v2EthPrtSwF2OutQueuesPacketsQueued
         Counter64,
      pr1645v2EthPrtSwF2OutQueuesPacketsDropped
         Counter64,
      pr1645v2EthPrtSwF2OutQueuesPacketsRedDropped
         Counter64,
      pr1645v2EthPrtSwF2OutQueuesPacketsCirTx
         Counter64,
      pr1645v2EthPrtSwF2OutQueuesPacketsEirTx
         Counter64,
      pr1645v2EthPrtSwF2OutQueuesPacketsViolateTx
         Counter64,
      pr1645v2EthPrtSwF2OutQueuesOctetsTotal
         Counter64,
      pr1645v2EthPrtSwF2OutQueuesOctetsDirectTx
         Counter64,
      pr1645v2EthPrtSwF2OutQueuesOctetsQueued
         Counter64,
      pr1645v2EthPrtSwF2OutQueuesOctetsDropped
         Counter64,
      pr1645v2EthPrtSwF2OutQueuesOctetsRedDropped
         Counter64,
      pr1645v2EthPrtSwF2OutQueuesOctetsCirTx
         Counter64,
      pr1645v2EthPrtSwF2OutQueuesOctetsEirTx
         Counter64,
      pr1645v2EthPrtSwF2OutQueuesOctetsViolateTx
         Counter64,
      pr1645v2EthPrtSwF2OutQueuesOctetsBandwidth15sec
         Integer32,
      pr1645v2EthPrtSwF2OutQueuesOctetsBandwidth30sec
         Integer32,
      pr1645v2EthPrtSwF2OutQueuesOctetsBandwidth1min
         Integer32,
      pr1645v2EthPrtSwF2OutQueuesOctetsBandwidth2min
         Integer32,
      pr1645v2EthPrtSwF2OutQueuesOctetsBandwidth5min
         Integer32
      }

pr1645v2EthPrtSwF2OutQueuesGlobalIx OBJECT-TYPE
   SYNTAX      GlobalIndex
   MAX-ACCESS  not-accessible
   STATUS      current
   DESCRIPTION
      "The value of the tlsCntTreeGlobalIndex of the MANAGED OBJECT."
   ::= {pr1645v2EthPrtSwF2OutQueuesEntry 10}

pr1645v2EthPrtSwF2OutQueuesTableIx OBJECT-TYPE
   SYNTAX      TableIndex
   MAX-ACCESS  not-accessible
   STATUS      current
   DESCRIPTION
      ""
   ::= {pr1645v2EthPrtSwF2OutQueuesEntry 11}

pr1645v2EthPrtSwF2OutQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: swPort.performance.ifOutPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2EthPrtSwF2OutQueuesEntry 16777216}

pr1645v2EthPrtSwF2OutQueuesLength OBJECT-TYPE
   SYNTAX      Integer32
   MAX-ACCESS  read-only
   STATUS      current
   DESCRIPTION
      "Path: swPort.performance.ifOutPriorityQueues.length"
   ::= {pr1645v2EthPrtSwF2OutQueuesEntry 33554432}

pr1645v2EthPrtSwF2OutQueuesOctetLength OBJECT-TYPE
   SYNTAX      Integer32
   MAX-ACCESS  read-only
   STATUS      current
   DESCRIPTION
      "Path: swPort.performance.ifOutPriorityQueues.octetLength"
   ::= {pr1645v2EthPrtSwF2OutQueuesEntry 150994944}

pr1645v2EthPrtSwF2OutQueuesRedLength OBJECT-TYPE
   SYNTAX      Integer32
   MAX-ACCESS  read-only
   STATUS      current
   DESCRIPTION
      "Path: swPort.performance.ifOutPriorityQueues.redLength"
   ::= {pr1645v2EthPrtSwF2OutQueuesEntry 134217728}

pr1645v2EthPrtSwF2OutQueuesPacketsTotal OBJECT-TYPE
   SYNTAX      Counter64
   MAX-ACCESS  read-only
   STATUS      current
   DESCRIPTION
      "Path: swPort.performance.ifOutPriorityQueues.packets.total

       64 bit unsigned wrappable counter."
   ::= {pr1645v2EthPrtSwF2OutQueuesEntry 50790400}

pr1645v2EthPrtSwF2OutQueuesPacketsDirectTx OBJECT-TYPE
   SYNTAX      Counter64
   MAX-ACCESS  read-only
   STATUS      current
   DESCRIPTION
      "Path: swPort.performance.ifOutPriorityQueues.packets.directTx

       64 bit unsigned wrappable counter."
   ::= {pr1645v2EthPrtSwF2OutQueuesEntry 50397184}

pr1645v2EthPrtSwF2OutQueuesPacketsQueued OBJECT-TYPE
   SYNTAX      Counter64
   MAX-ACCESS  read-only
   STATUS      current
   DESCRIPTION
      "Path: swPort.performance.ifOutPriorityQueues.packets.queued

       64 bit unsigned wrappable counter."
   ::= {pr1645v2EthPrtSwF2OutQueuesEntry 50462720}

pr1645v2EthPrtSwF2OutQueuesPacketsDropped OBJECT-TYPE
   SYNTAX      Counter64
   MAX-ACCESS  read-only
   STATUS      current
   DESCRIPTION
      "Path: swPort.performance.ifOutPriorityQueues.packets.dropped

       64 bit unsigned wrappable counter."
   ::= {pr1645v2EthPrtSwF2OutQueuesEntry 50528256}

pr1645v2EthPrtSwF2OutQueuesPacketsRedDropped OBJECT-TYPE
   SYNTAX      Counter64
   MAX-ACCESS  read-only
   STATUS      current
   DESCRIPTION
      "Path: swPort.performance.ifOutPriorityQueues.packets.redDropped

       64 bit unsigned wrappable counter."
   ::= {pr1645v2EthPrtSwF2OutQueuesEntry 50724864}

pr1645v2EthPrtSwF2OutQueuesPacketsCirTx OBJECT-TYPE
   SYNTAX      Counter64
   MAX-ACCESS  read-only
   STATUS      current
   DESCRIPTION
      "Path: swPort.performance.ifOutPriorityQueues.packets.cirTx

       64 bit unsigned wrappable counter."
   ::= {pr1645v2EthPrtSwF2OutQueuesEntry 50593792}

pr1645v2EthPrtSwF2OutQueuesPacketsEirTx OBJECT-TYPE
   SYNTAX      Counter64
   MAX-ACCESS  read-only
   STATUS      current
   DESCRIPTION
      "Path: swPort.performance.ifOutPriorityQueues.packets.eirTx

       64 bit unsigned wrappable counter."
   ::= {pr1645v2EthPrtSwF2OutQueuesEntry 50659328}

pr1645v2EthPrtSwF2OutQueuesPacketsViolateTx OBJECT-TYPE
   SYNTAX      Counter64
   MAX-ACCESS  read-only
   STATUS      current
   DESCRIPTION
      "Path: swPort.performance.ifOutPriorityQueues.packets.violateTx

       64 bit unsigned wrappable counter."
   ::= {pr1645v2EthPrtSwF2OutQueuesEntry 50855936}

pr1645v2EthPrtSwF2OutQueuesOctetsTotal OBJECT-TYPE
   SYNTAX      Counter64
   MAX-ACCESS  read-only
   STATUS      current
   DESCRIPTION
      "Path: swPort.performance.ifOutPriorityQueues.octets.total

       64 bit unsigned wrappable counter."
   ::= {pr1645v2EthPrtSwF2OutQueuesEntry 67567616}

pr1645v2EthPrtSwF2OutQueuesOctetsDirectTx OBJECT-TYPE
   SYNTAX      Counter64
   MAX-ACCESS  read-only
   STATUS      current
   DESCRIPTION
      "Path: swPort.performance.ifOutPriorityQueues.octets.directTx

       64 bit unsigned wrappable counter."
   ::= {pr1645v2EthPrtSwF2OutQueuesEntry 67174400}

pr1645v2EthPrtSwF2OutQueuesOctetsQueued OBJECT-TYPE
   SYNTAX      Counter64
   MAX-ACCESS  read-only
   STATUS      current
   DESCRIPTION
      "Path: swPort.performance.ifOutPriorityQueues.octets.queued

       64 bit unsigned wrappable counter."
   ::= {pr1645v2EthPrtSwF2OutQueuesEntry 67239936}

pr1645v2EthPrtSwF2OutQueuesOctetsDropped OBJECT-TYPE
   SYNTAX      Counter64
   MAX-ACCESS  read-only
   STATUS      current
   DESCRIPTION
      "Path: swPort.performance.ifOutPriorityQueues.octets.dropped

       64 bit unsigned wrappable counter."
   ::= {pr1645v2EthPrtSwF2OutQueuesEntry 67305472}

pr1645v2EthPrtSwF2OutQueuesOctetsRedDropped OBJECT-TYPE
   SYNTAX      Counter64
   MAX-ACCESS  read-only
   STATUS      current
   DESCRIPTION
      "Path: swPort.performance.ifOutPriorityQueues.octets.redDropped

       64 bit unsigned wrappable counter."
   ::= {pr1645v2EthPrtSwF2OutQueuesEntry 67502080}

pr1645v2EthPrtSwF2OutQueuesOctetsCirTx OBJECT-TYPE
   SYNTAX      Counter64
   MAX-ACCESS  read-only
   STATUS      current
   DESCRIPTION
      "Path: swPort.performance.ifOutPriorityQueues.octets.cirTx

       64 bit unsigned wrappable counter."
   ::= {pr1645v2EthPrtSwF2OutQueuesEntry 67371008}

pr1645v2EthPrtSwF2OutQueuesOctetsEirTx OBJECT-TYPE
   SYNTAX      Counter64
   MAX-ACCESS  read-only
   STATUS      current
   DESCRIPTION
      "Path: swPort.performance.ifOutPriorityQueues.octets.eirTx

       64 bit unsigned wrappable counter."
   ::= {pr1645v2EthPrtSwF2OutQueuesEntry 67436544}

pr1645v2EthPrtSwF2OutQueuesOctetsViolateTx OBJECT-TYPE
   SYNTAX      Counter64
   MAX-ACCESS  read-only
   STATUS      current
   DESCRIPTION
      "Path: swPort.performance.ifOutPriorityQueues.octets.violateTx

       64 bit unsigned wrappable counter."
   ::= {pr1645v2EthPrtSwF2OutQueuesEntry 67633152}

pr1645v2EthPrtSwF2OutQueuesOctetsBandwidth15sec OBJECT-TYPE
   SYNTAX      Integer32
   MAX-ACCESS  read-only
   STATUS      current
   DESCRIPTION
      "Path: swPort.performance.ifOutPriorityQueues.octets.bandwidth.15sec

       unit name = bps
       formula = 8 * ; 8 /"
   ::= {pr1645v2EthPrtSwF2OutQueuesEntry 70386944}

pr1645v2EthPrtSwF2OutQueuesOctetsBandwidth30sec OBJECT-TYPE
   SYNTAX      Integer32
   MAX-ACCESS  read-only
   STATUS      current
   DESCRIPTION
      "Path: swPort.performance.ifOutPriorityQueues.octets.bandwidth.30sec

       unit name = bps
       formula = 8 * ; 8 /"
   ::= {pr1645v2EthPrtSwF2OutQueuesEntry 70388224}

pr1645v2EthPrtSwF2OutQueuesOctetsBandwidth1min OBJECT-TYPE
   SYNTAX      Integer32
   MAX-ACCESS  read-only
   STATUS      current
   DESCRIPTION
      "Path: swPort.performance.ifOutPriorityQueues.octets.bandwidth.1min

       unit name = bps
       formula = 8 * ; 8 /"
   ::= {pr1645v2EthPrtSwF2OutQueuesEntry 70390784}

pr1645v2EthPrtSwF2OutQueuesOctetsBandwidth2min OBJECT-TYPE
   SYNTAX      Integer32
   MAX-ACCESS  read-only
   STATUS      current
   DESCRIPTION
      "Path: swPort.performance.ifOutPriorityQueues.octets.bandwidth.2min

       unit name = bps
       formula = 8 * ; 8 /"
   ::= {pr1645v2EthPrtSwF2OutQueuesEntry 70395904}

pr1645v2EthPrtSwF2OutQueuesOctetsBandwidth5min OBJECT-TYPE
   SYNTAX      Integer32
   MAX-ACCESS  read-only
   STATUS      current
   DESCRIPTION
      "Path: swPort.performance.ifOutPriorityQueues.octets.bandwidth.5min

       unit name = bps
       formula = 8 * ; 8 /"
   ::= {pr1645v2EthPrtSwF2OutQueuesEntry 70411264}

pr1645v2EthPrtSwF2OutQueuesH2Performance OBJECT-TYPE
   SYNTAX      SEQUENCE OF Pr1645v2EthPrtSwF2OutQueuesH2PerformanceEntry
   MAX-ACCESS  not-accessible
   STATUS      current
   DESCRIPTION
      ""
   ::= {pr1645v2EthPrtSwF2OutQueues 83886080}

pr1645v2EthPrtSwF2OutQueuesH2PerformanceEntry OBJECT-TYPE
   SYNTAX      Pr1645v2EthPrtSwF2OutQueuesH2PerformanceEntry
   MAX-ACCESS  not-accessible
   STATUS      current
   DESCRIPTION
      ""
   INDEX      { pr1645v2EthPrtSwF2OutQueuesH2PerformanceGlobalIx,
                pr1645v2EthPrtSwF2OutQueuesTableIx,
                pr1645v2EthPrtSwF2OutQueuesH2PerformanceTableIx }
   ::= {pr1645v2EthPrtSwF2OutQueuesH2Performance 1}

Pr1645v2EthPrtSwF2OutQueuesH2PerformanceEntry ::=
   SEQUENCE
      {
      pr1645v2EthPrtSwF2OutQueuesH2PerformanceGlobalIx
         GlobalIndex,
      pr1645v2EthPrtSwF2OutQueuesH2PerformanceTableIx
         TableIndex,
      pr1645v2EthPrtSwF2OutQueuesH2PerformanceSysUpTime
         TimeTicks,
      pr1645v2EthPrtSwF2OutQueuesH2PerformanceTotPkts
         Counter64,
      pr1645v2EthPrtSwF2OutQueuesH2PerformanceDirTxPkts
         Counter64,
      pr1645v2EthPrtSwF2OutQueuesH2PerformanceQdPkts
         Counter64,
      pr1645v2EthPrtSwF2OutQueuesH2PerformanceDropPkts
         Counter64,
      pr1645v2EthPrtSwF2OutQueuesH2PerformanceRDropPkts
         Counter64,
      pr1645v2EthPrtSwF2OutQueuesH2PerformanceCirTxPkts
         Counter64,
      pr1645v2EthPrtSwF2OutQueuesH2PerformanceEirTxPkts
         Counter64,
      pr1645v2EthPrtSwF2OutQueuesH2PerformanceViolTxPkts
         Counter64,
      pr1645v2EthPrtSwF2OutQueuesH2PerformanceTotOcts
         Counter64,
      pr1645v2EthPrtSwF2OutQueuesH2PerformanceDirTxOcts
         Counter64,
      pr1645v2EthPrtSwF2OutQueuesH2PerformanceQdOcts
         Counter64,
      pr1645v2EthPrtSwF2OutQueuesH2PerformanceDropOcts
         Counter64,
      pr1645v2EthPrtSwF2OutQueuesH2PerformanceRDropOcts
         Counter64,
      pr1645v2EthPrtSwF2OutQueuesH2PerformanceCirTxOcts
         Counter64,
      pr1645v2EthPrtSwF2OutQueuesH2PerformanceEirTxOcts
         Counter64,
      pr1645v2EthPrtSwF2OutQueuesH2PerformanceViolTxOcts
         Counter64,
      pr1645v2EthPrtSwF2OutQueuesH2PerformanceBandwidth
         Integer32
      }

pr1645v2EthPrtSwF2OutQueuesH2PerformanceGlobalIx OBJECT-TYPE
   SYNTAX      GlobalIndex
   MAX-ACCESS  not-accessible
   STATUS      current
   DESCRIPTION
      "The value of the tlsCntTreeGlobalIndex of the MANAGED OBJECT."
   ::= {pr1645v2EthPrtSwF2OutQueuesH2PerformanceEntry 10}

pr1645v2EthPrtSwF2OutQueuesH2PerformanceTableIx OBJECT-TYPE
   SYNTAX      TableIndex
   MAX-ACCESS  not-accessible
   STATUS      current
   DESCRIPTION
      ""
   ::= {pr1645v2EthPrtSwF2OutQueuesH2PerformanceEntry 11}

pr1645v2EthPrtSwF2OutQueuesH2PerformanceSysUpTime OBJECT-TYPE
   SYNTAX      TimeTicks
   MAX-ACCESS  read-only
   STATUS      current
   DESCRIPTION
      "Path: swPort.performance.ifOutPriorityQueues.h2Performance.sysUpTime

       Time in centi-second."
   ::= {pr1645v2EthPrtSwF2OutQueuesH2PerformanceEntry 16777216}

pr1645v2EthPrtSwF2OutQueuesH2PerformanceTotPkts OBJECT-TYPE
   SYNTAX      Counter64
   MAX-ACCESS  read-only
   STATUS      current
   DESCRIPTION
      "Path: swPort.performance.ifOutPriorityQueues.h2Performance.totalPkts

       64 bit unsigned wrappable counter."
   ::= {pr1645v2EthPrtSwF2OutQueuesH2PerformanceEntry 234881024}

pr1645v2EthPrtSwF2OutQueuesH2PerformanceDirTxPkts OBJECT-TYPE
   SYNTAX      Counter64
   MAX-ACCESS  read-only
   STATUS      current
   DESCRIPTION
      "Path: swPort.performance.ifOutPriorityQueues.h2Performance.directTxPkts

       64 bit unsigned wrappable counter."
   ::= {pr1645v2EthPrtSwF2OutQueuesH2PerformanceEntry 33554432}

pr1645v2EthPrtSwF2OutQueuesH2PerformanceQdPkts OBJECT-TYPE
   SYNTAX      Counter64
   MAX-ACCESS  read-only
   STATUS      current
   DESCRIPTION
      "Path: swPort.performance.ifOutPriorityQueues.h2Performance.queuedPkts

       64 bit unsigned wrappable counter."
   ::= {pr1645v2EthPrtSwF2OutQueuesH2PerformanceEntry 50331648}

pr1645v2EthPrtSwF2OutQueuesH2PerformanceDropPkts OBJECT-TYPE
   SYNTAX      Counter64
   MAX-ACCESS  read-only
   STATUS      current
   DESCRIPTION
      "Path: swPort.performance.ifOutPriorityQueues.h2Performance.droppedPkts

       64 bit unsigned wrappable counter."
   ::= {pr1645v2EthPrtSwF2OutQueuesH2PerformanceEntry 67108864}

pr1645v2EthPrtSwF2OutQueuesH2PerformanceRDropPkts OBJECT-TYPE
   SYNTAX      Counter64
   MAX-ACCESS  read-only
   STATUS      current
   DESCRIPTION
      "Path: swPort.performance.ifOutPriorityQueues.h2Performance.redDroppedPkts

       64 bit unsigned wrappable counter."
   ::= {pr1645v2EthPrtSwF2OutQueuesH2PerformanceEntry 201326592}

pr1645v2EthPrtSwF2OutQueuesH2PerformanceCirTxPkts OBJECT-TYPE
   SYNTAX      Counter64
   MAX-ACCESS  read-only
   STATUS      current
   DESCRIPTION
      "Path: swPort.performance.ifOutPriorityQueues.h2Performance.cirTxPkts

       64 bit unsigned wrappable counter."
   ::= {pr1645v2EthPrtSwF2OutQueuesH2PerformanceEntry 83886080}

pr1645v2EthPrtSwF2OutQueuesH2PerformanceEirTxPkts OBJECT-TYPE
   SYNTAX      Counter64
   MAX-ACCESS  read-only
   STATUS      current
   DESCRIPTION
      "Path: swPort.performance.ifOutPriorityQueues.h2Performance.eirTxPkts

       64 bit unsigned wrappable counter."
   ::= {pr1645v2EthPrtSwF2OutQueuesH2PerformanceEntry 100663296}

pr1645v2EthPrtSwF2OutQueuesH2PerformanceViolTxPkts OBJECT-TYPE
   SYNTAX      Counter64
   MAX-ACCESS  read-only
   STATUS      current
   DESCRIPTION
      "Path: swPort.performance.ifOutPriorityQueues.h2Performance.violateTxPkts

       64 bit unsigned wrappable counter."
   ::= {pr1645v2EthPrtSwF2OutQueuesH2PerformanceEntry 301989888}

pr1645v2EthPrtSwF2OutQueuesH2PerformanceTotOcts OBJECT-TYPE
   SYNTAX      Counter64
   MAX-ACCESS  read-only
   STATUS      current
   DESCRIPTION
      "Path: swPort.performance.ifOutPriorityQueues.h2Performance.totalOctets

       64 bit unsigned wrappable counter."
   ::= {pr1645v2EthPrtSwF2OutQueuesH2PerformanceEntry 251658240}

pr1645v2EthPrtSwF2OutQueuesH2PerformanceDirTxOcts OBJECT-TYPE
   SYNTAX      Counter64
   MAX-ACCESS  read-only
   STATUS      current
   DESCRIPTION
      "Path: swPort.performance.ifOutPriorityQueues.h2Performance.directTxOctets

       64 bit unsigned wrappable counter."
   ::= {pr1645v2EthPrtSwF2OutQueuesH2PerformanceEntry 117440512}

pr1645v2EthPrtSwF2OutQueuesH2PerformanceQdOcts OBJECT-TYPE
   SYNTAX      Counter64
   MAX-ACCESS  read-only
   STATUS      current
   DESCRIPTION
      "Path: swPort.performance.ifOutPriorityQueues.h2Performance.queuedOctets

       64 bit unsigned wrappable counter."
   ::= {pr1645v2EthPrtSwF2OutQueuesH2PerformanceEntry 134217728}

pr1645v2EthPrtSwF2OutQueuesH2PerformanceDropOcts OBJECT-TYPE
   SYNTAX      Counter64
   MAX-ACCESS  read-only
   STATUS      current
   DESCRIPTION
      "Path: swPort.performance.ifOutPriorityQueues.h2Performance.droppedOctets

       64 bit unsigned wrappable counter."
   ::= {pr1645v2EthPrtSwF2OutQueuesH2PerformanceEntry 150994944}

pr1645v2EthPrtSwF2OutQueuesH2PerformanceRDropOcts OBJECT-TYPE
   SYNTAX      Counter64
   MAX-ACCESS  read-only
   STATUS      current
   DESCRIPTION
      "Path: swPort.performance.ifOutPriorityQueues.h2Performance.redDroppedOctets

       64 bit unsigned wrappable counter."
   ::= {pr1645v2EthPrtSwF2OutQueuesH2PerformanceEntry 218103808}

pr1645v2EthPrtSwF2OutQueuesH2PerformanceCirTxOcts OBJECT-TYPE
   SYNTAX      Counter64
   MAX-ACCESS  read-only
   STATUS      current
   DESCRIPTION
      "Path: swPort.performance.ifOutPriorityQueues.h2Performance.cirTxOctets

       64 bit unsigned wrappable counter."
   ::= {pr1645v2EthPrtSwF2OutQueuesH2PerformanceEntry 167772160}

pr1645v2EthPrtSwF2OutQueuesH2PerformanceEirTxOcts OBJECT-TYPE
   SYNTAX      Counter64
   MAX-ACCESS  read-only
   STATUS      current
   DESCRIPTION
      "Path: swPort.performance.ifOutPriorityQueues.h2Performance.eirTxOctets

       64 bit unsigned wrappable counter."
   ::= {pr1645v2EthPrtSwF2OutQueuesH2PerformanceEntry 184549376}

pr1645v2EthPrtSwF2OutQueuesH2PerformanceViolTxOcts OBJECT-TYPE
   SYNTAX      Counter64
   MAX-ACCESS  read-only
   STATUS      current
   DESCRIPTION
      "Path: swPort.performance.ifOutPriorityQueues.h2Performance.violateTxOctets

       64 bit unsigned wrappable counter."
   ::= {pr1645v2EthPrtSwF2OutQueuesH2PerformanceEntry 318767104}

pr1645v2EthPrtSwF2OutQueuesH2PerformanceBandwidth OBJECT-TYPE
   SYNTAX      Integer32
   MAX-ACCESS  read-only
   STATUS      current
   DESCRIPTION
      "Path: swPort.performance.ifOutPriorityQueues.h2Performance.bandwidth

       unit name = bps
       formula = 8 * ; 8 /"
   ::= {pr1645v2EthPrtSwF2OutQueuesH2PerformanceEntry 268435456}

pr1645v2EthPrtSwF2OutQueuesH24Performance OBJECT-TYPE
   SYNTAX      SEQUENCE OF Pr1645v2EthPrtSwF2OutQueuesH24PerformanceEntry
   MAX-ACCESS  not-accessible
   STATUS      current
   DESCRIPTION
      ""
   ::= {pr1645v2EthPrtSwF2OutQueues 100663296}

pr1645v2EthPrtSwF2OutQueuesH24PerformanceEntry OBJECT-TYPE
   SYNTAX      Pr1645v2EthPrtSwF2OutQueuesH24PerformanceEntry
   MAX-ACCESS  not-accessible
   STATUS      current
   DESCRIPTION
      ""
   INDEX      { pr1645v2EthPrtSwF2OutQueuesH24PerformanceGlobalIx,
                pr1645v2EthPrtSwF2OutQueuesTableIx,
                pr1645v2EthPrtSwF2OutQueuesH24PerformanceTableIx }
   ::= {pr1645v2EthPrtSwF2OutQueuesH24Performance 1}

Pr1645v2EthPrtSwF2OutQueuesH24PerformanceEntry ::=
   SEQUENCE
      {
      pr1645v2EthPrtSwF2OutQueuesH24PerformanceGlobalIx
         GlobalIndex,
      pr1645v2EthPrtSwF2OutQueuesH24PerformanceTableIx
         TableIndex,
      pr1645v2EthPrtSwF2OutQueuesH24PerformanceSysUpTime
         TimeTicks,
      pr1645v2EthPrtSwF2OutQueuesH24PerformanceTotPkts
         Counter64,
      pr1645v2EthPrtSwF2OutQueuesH24PerformanceDirTxPkts
         Counter64,
      pr1645v2EthPrtSwF2OutQueuesH24PerformanceQdPkts
         Counter64,
      pr1645v2EthPrtSwF2OutQueuesH24PerformanceDropPkts
         Counter64,
      pr1645v2EthPrtSwF2OutQueuesH24PerformanceRDropPkts
         Counter64,
      pr1645v2EthPrtSwF2OutQueuesH24PerformanceCirTxPkts
         Counter64,
      pr1645v2EthPrtSwF2OutQueuesH24PerformanceEirTxPkts
         Counter64,
      pr1645v2EthPrtSwF2OutQueuesH24PerformanceViolTxPkts
         Counter64,
      pr1645v2EthPrtSwF2OutQueuesH24PerformanceTotOcts
         Counter64,
      pr1645v2EthPrtSwF2OutQueuesH24PerformanceDirTxOcts
         Counter64,
      pr1645v2EthPrtSwF2OutQueuesH24PerformanceQdOcts
         Counter64,
      pr1645v2EthPrtSwF2OutQueuesH24PerformanceDropOcts
         Counter64,
      pr1645v2EthPrtSwF2OutQueuesH24PerformanceRDropOcts
         Counter64,
      pr1645v2EthPrtSwF2OutQueuesH24PerformanceCirTxOcts
         Counter64,
      pr1645v2EthPrtSwF2OutQueuesH24PerformanceEirTxOcts
         Counter64,
      pr1645v2EthPrtSwF2OutQueuesH24PerformanceViolTxOcts
         Counter64,
      pr1645v2EthPrtSwF2OutQueuesH24PerformanceBandwidth
         Integer32
      }

pr1645v2EthPrtSwF2OutQueuesH24PerformanceGlobalIx OBJECT-TYPE
   SYNTAX      GlobalIndex
   MAX-ACCESS  not-accessible
   STATUS      current
   DESCRIPTION
      "The value of the tlsCntTreeGlobalIndex of the MANAGED OBJECT."
   ::= {pr1645v2EthPrtSwF2OutQueuesH24PerformanceEntry 10}

pr1645v2EthPrtSwF2OutQueuesH24PerformanceTableIx OBJECT-TYPE
   SYNTAX      TableIndex
   MAX-ACCESS  not-accessible
   STATUS      current
   DESCRIPTION
      ""
   ::= {pr1645v2EthPrtSwF2OutQueuesH24PerformanceEntry 11}

pr1645v2EthPrtSwF2OutQueuesH24PerformanceSysUpTime OBJECT-TYPE
   SYNTAX      TimeTicks
   MAX-ACCESS  read-only
   STATUS      current
   DESCRIPTION
      "Path: swPort.performance.ifOutPriorityQueues.h24Performance.sysUpTime

       Time in centi-second."
   ::= {pr1645v2EthPrtSwF2OutQueuesH24PerformanceEntry 16777216}

pr1645v2EthPrtSwF2OutQueuesH24PerformanceTotPkts OBJECT-TYPE
   SYNTAX      Counter64
   MAX-ACCESS  read-only
   STATUS      current
   DESCRIPTION
      "Path: swPort.performance.ifOutPriorityQueues.h24Performance.totalPkts

       64 bit unsigned wrappable counter."
   ::= {pr1645v2EthPrtSwF2OutQueuesH24PerformanceEntry 234881024}

pr1645v2EthPrtSwF2OutQueuesH24PerformanceDirTxPkts OBJECT-TYPE
   SYNTAX      Counter64
   MAX-ACCESS  read-only
   STATUS      current
   DESCRIPTION
      "Path: swPort.performance.ifOutPriorityQueues.h24Performance.directTxPkts

       64 bit unsigned wrappable counter."
   ::= {pr1645v2EthPrtSwF2OutQueuesH24PerformanceEntry 33554432}

pr1645v2EthPrtSwF2OutQueuesH24PerformanceQdPkts OBJECT-TYPE
   SYNTAX      Counter64
   MAX-ACCESS  read-only
   STATUS      current
   DESCRIPTION
      "Path: swPort.performance.ifOutPriorityQueues.h24Performance.queuedPkts

       64 bit unsigned wrappable counter."
   ::= {pr1645v2EthPrtSwF2OutQueuesH24PerformanceEntry 50331648}

pr1645v2EthPrtSwF2OutQueuesH24PerformanceDropPkts OBJECT-TYPE
   SYNTAX      Counter64
   MAX-ACCESS  read-only
   STATUS      current
   DESCRIPTION
      "Path: swPort.performance.ifOutPriorityQueues.h24Performance.droppedPkts

       64 bit unsigned wrappable counter."
   ::= {pr1645v2EthPrtSwF2OutQueuesH24PerformanceEntry 67108864}

pr1645v2EthPrtSwF2OutQueuesH24PerformanceRDropPkts OBJECT-TYPE
   SYNTAX      Counter64
   MAX-ACCESS  read-only
   STATUS      current
   DESCRIPTION
      "Path: swPort.performance.ifOutPriorityQueues.h24Performance.redDroppedPkts

       64 bit unsigned wrappable counter."
   ::= {pr1645v2EthPrtSwF2OutQueuesH24PerformanceEntry 201326592}

pr1645v2EthPrtSwF2OutQueuesH24PerformanceCirTxPkts OBJECT-TYPE
   SYNTAX      Counter64
   MAX-ACCESS  read-only
   STATUS      current
   DESCRIPTION
      "Path: swPort.performance.ifOutPriorityQueues.h24Performance.cirTxPkts

       64 bit unsigned wrappable counter."
   ::= {pr1645v2EthPrtSwF2OutQueuesH24PerformanceEntry 83886080}

pr1645v2EthPrtSwF2OutQueuesH24PerformanceEirTxPkts OBJECT-TYPE
   SYNTAX      Counter64
   MAX-ACCESS  read-only
   STATUS      current
   DESCRIPTION
      "Path: swPort.performance.ifOutPriorityQueues.h24Performance.eirTxPkts

       64 bit unsigned wrappable counter."
   ::= {pr1645v2EthPrtSwF2OutQueuesH24PerformanceEntry 100663296}

pr1645v2EthPrtSwF2OutQueuesH24PerformanceViolTxPkts OBJECT-TYPE
   SYNTAX      Counter64
   MAX-ACCESS  read-only
   STATUS      current
   DESCRIPTION
      "Path: swPort.performance.ifOutPriorityQueues.h24Performance.violateTxPkts

       64 bit unsigned wrappable counter."
   ::= {pr1645v2EthPrtSwF2OutQueuesH24PerformanceEntry 301989888}

pr1645v2EthPrtSwF2OutQueuesH24PerformanceTotOcts OBJECT-TYPE
   SYNTAX      Counter64
   MAX-ACCESS  read-only
   STATUS      current
   DESCRIPTION
      "Path: swPort.performance.ifOutPriorityQueues.h24Performance.totalOctets

       64 bit unsigned wrappable counter."
   ::= {pr1645v2EthPrtSwF2OutQueuesH24PerformanceEntry 251658240}

pr1645v2EthPrtSwF2OutQueuesH24PerformanceDirTxOcts OBJECT-TYPE
   SYNTAX      Counter64
   MAX-ACCESS  read-only
   STATUS      current
   DESCRIPTION
      "Path: swPort.performance.ifOutPriorityQueues.h24Performance.directTxOctets

       64 bit unsigned wrappable counter."
   ::= {pr1645v2EthPrtSwF2OutQueuesH24PerformanceEntry 117440512}

pr1645v2EthPrtSwF2OutQueuesH24PerformanceQdOcts OBJECT-TYPE
   SYNTAX      Counter64
   MAX-ACCESS  read-only
   STATUS      current
   DESCRIPTION
      "Path: swPort.performance.ifOutPriorityQueues.h24Performance.queuedOctets

       64 bit unsigned wrappable counter."
   ::= {pr1645v2EthPrtSwF2OutQueuesH24PerformanceEntry 134217728}

pr1645v2EthPrtSwF2OutQueuesH24PerformanceDropOcts OBJECT-TYPE
   SYNTAX      Counter64
   MAX-ACCESS  read-only
   STATUS      current
   DESCRIPTION
      "Path: swPort.performance.ifOutPriorityQueues.h24Performance.droppedOctets

       64 bit unsigned wrappable counter."
   ::= {pr1645v2EthPrtSwF2OutQueuesH24PerformanceEntry 150994944}

pr1645v2EthPrtSwF2OutQueuesH24PerformanceRDropOcts OBJECT-TYPE
   SYNTAX      Counter64
   MAX-ACCESS  read-only
   STATUS      current
   DESCRIPTION
      "Path: swPort.performance.ifOutPriorityQueues.h24Performance.redDroppedOctets

       64 bit unsigned wrappable counter."
   ::= {pr1645v2EthPrtSwF2OutQueuesH24PerformanceEntry 218103808}

pr1645v2EthPrtSwF2OutQueuesH24PerformanceCirTxOcts OBJECT-TYPE
   SYNTAX      Counter64
   MAX-ACCESS  read-only
   STATUS      current
   DESCRIPTION
      "Path: swPort.performance.ifOutPriorityQueues.h24Performance.cirTxOctets

       64 bit unsigned wrappable counter."
   ::= {pr1645v2EthPrtSwF2OutQueuesH24PerformanceEntry 167772160}

pr1645v2EthPrtSwF2OutQueuesH24PerformanceEirTxOcts OBJECT-TYPE
   SYNTAX      Counter64
   MAX-ACCESS  read-only
   STATUS      current
   DESCRIPTION
      "Path: swPort.performance.ifOutPriorityQueues.h24Performance.eirTxOctets

       64 bit unsigned wrappable counter."
   ::= {pr1645v2EthPrtSwF2OutQueuesH24PerformanceEntry 184549376}

pr1645v2EthPrtSwF2OutQueuesH24PerformanceViolTxOcts OBJECT-TYPE
   SYNTAX      Counter64
   MAX-ACCESS  read-only
   STATUS      current
   DESCRIPTION
      "Path: swPort.performance.ifOutPriorityQueues.h24Performance.violateTxOctets

       64 bit unsigned wrappable counter."
   ::= {pr1645v2EthPrtSwF2OutQueuesH24PerformanceEntry 318767104}

pr1645v2EthPrtSwF2OutQueuesH24PerformanceBandwidth OBJECT-TYPE
   SYNTAX      Integer32
   MAX-ACCESS  read-only
   STATUS      current
   DESCRIPTION
      "Path: swPort.performance.ifOutPriorityQueues.h24Performance.bandwidth

       unit name = bps
       formula = 8 * ; 8 /"
   ::= {pr1645v2EthPrtSwF2OutQueuesH24PerformanceEntry 268435456}

pr1645v2EthPrtSwF2OutQueuesD7Performance OBJECT-TYPE
   SYNTAX      SEQUENCE OF Pr1645v2EthPrtSwF2OutQueuesD7PerformanceEntry
   MAX-ACCESS  not-accessible
   STATUS      current
   DESCRIPTION
      ""
   ::= {pr1645v2EthPrtSwF2OutQueues 117440512}

pr1645v2EthPrtSwF2OutQueuesD7PerformanceEntry OBJECT-TYPE
   SYNTAX      Pr1645v2EthPrtSwF2OutQueuesD7PerformanceEntry
   MAX-ACCESS  not-accessible
   STATUS      current
   DESCRIPTION
      ""
   INDEX      { pr1645v2EthPrtSwF2OutQueuesD7PerformanceGlobalIx,
                pr1645v2EthPrtSwF2OutQueuesTableIx,
                pr1645v2EthPrtSwF2OutQueuesD7PerformanceTableIx }
   ::= {pr1645v2EthPrtSwF2OutQueuesD7Performance 1}

Pr1645v2EthPrtSwF2OutQueuesD7PerformanceEntry ::=
   SEQUENCE
      {
      pr1645v2EthPrtSwF2OutQueuesD7PerformanceGlobalIx
         GlobalIndex,
      pr1645v2EthPrtSwF2OutQueuesD7PerformanceTableIx
         TableIndex,
      pr1645v2EthPrtSwF2OutQueuesD7PerformanceSysUpTime
         TimeTicks,
      pr1645v2EthPrtSwF2OutQueuesD7PerformanceTotPkts
         Counter64,
      pr1645v2EthPrtSwF2OutQueuesD7PerformanceDirTxPkts
         Counter64,
      pr1645v2EthPrtSwF2OutQueuesD7PerformanceQdPkts
         Counter64,
      pr1645v2EthPrtSwF2OutQueuesD7PerformanceDropPkts
         Counter64,
      pr1645v2EthPrtSwF2OutQueuesD7PerformanceRDropPkts
         Counter64,
      pr1645v2EthPrtSwF2OutQueuesD7PerformanceCirTxPkts
         Counter64,
      pr1645v2EthPrtSwF2OutQueuesD7PerformanceEirTxPkts
         Counter64,
      pr1645v2EthPrtSwF2OutQueuesD7PerformanceViolTxPkts
         Counter64,
      pr1645v2EthPrtSwF2OutQueuesD7PerformanceTotOcts
         Counter64,
      pr1645v2EthPrtSwF2OutQueuesD7PerformanceDirTxOcts
         Counter64,
      pr1645v2EthPrtSwF2OutQueuesD7PerformanceQdOcts
         Counter64,
      pr1645v2EthPrtSwF2OutQueuesD7PerformanceDropOcts
         Counter64,
      pr1645v2EthPrtSwF2OutQueuesD7PerformanceRDropOcts
         Counter64,
      pr1645v2EthPrtSwF2OutQueuesD7PerformanceCirTxOcts
         Counter64,
      pr1645v2EthPrtSwF2OutQueuesD7PerformanceEirTxOcts
         Counter64,
      pr1645v2EthPrtSwF2OutQueuesD7PerformanceViolTxOcts
         Counter64,
      pr1645v2EthPrtSwF2OutQueuesD7PerformanceBandwidth
         Integer32
      }

pr1645v2EthPrtSwF2OutQueuesD7PerformanceGlobalIx OBJECT-TYPE
   SYNTAX      GlobalIndex
   MAX-ACCESS  not-accessible
   STATUS      current
   DESCRIPTION
      "The value of the tlsCntTreeGlobalIndex of the MANAGED OBJECT."
   ::= {pr1645v2EthPrtSwF2OutQueuesD7PerformanceEntry 10}

pr1645v2EthPrtSwF2OutQueuesD7PerformanceTableIx OBJECT-TYPE
   SYNTAX      TableIndex
   MAX-ACCESS  not-accessible
   STATUS      current
   DESCRIPTION
      ""
   ::= {pr1645v2EthPrtSwF2OutQueuesD7PerformanceEntry 11}

pr1645v2EthPrtSwF2OutQueuesD7PerformanceSysUpTime OBJECT-TYPE
   SYNTAX      TimeTicks
   MAX-ACCESS  read-only
   STATUS      current
   DESCRIPTION
      "Path: swPort.performance.ifOutPriorityQueues.d7Performance.sysUpTime

       Time in centi-second."
   ::= {pr1645v2EthPrtSwF2OutQueuesD7PerformanceEntry 16777216}

pr1645v2EthPrtSwF2OutQueuesD7PerformanceTotPkts OBJECT-TYPE
   SYNTAX      Counter64
   MAX-ACCESS  read-only
   STATUS      current
   DESCRIPTION
      "Path: swPort.performance.ifOutPriorityQueues.d7Performance.totalPkts

       64 bit unsigned wrappable counter."
   ::= {pr1645v2EthPrtSwF2OutQueuesD7PerformanceEntry 234881024}

pr1645v2EthPrtSwF2OutQueuesD7PerformanceDirTxPkts OBJECT-TYPE
   SYNTAX      Counter64
   MAX-ACCESS  read-only
   STATUS      current
   DESCRIPTION
      "Path: swPort.performance.ifOutPriorityQueues.d7Performance.directTxPkts

       64 bit unsigned wrappable counter."
   ::= {pr1645v2EthPrtSwF2OutQueuesD7PerformanceEntry 33554432}

pr1645v2EthPrtSwF2OutQueuesD7PerformanceQdPkts OBJECT-TYPE
   SYNTAX      Counter64
   MAX-ACCESS  read-only
   STATUS      current
   DESCRIPTION
      "Path: swPort.performance.ifOutPriorityQueues.d7Performance.queuedPkts

       64 bit unsigned wrappable counter."
   ::= {pr1645v2EthPrtSwF2OutQueuesD7PerformanceEntry 50331648}

pr1645v2EthPrtSwF2OutQueuesD7PerformanceDropPkts OBJECT-TYPE
   SYNTAX      Counter64
   MAX-ACCESS  read-only
   STATUS      current
   DESCRIPTION
      "Path: swPort.performance.ifOutPriorityQueues.d7Performance.droppedPkts

       64 bit unsigned wrappable counter."
   ::= {pr1645v2EthPrtSwF2OutQueuesD7PerformanceEntry 67108864}

pr1645v2EthPrtSwF2OutQueuesD7PerformanceRDropPkts OBJECT-TYPE
   SYNTAX      Counter64
   MAX-ACCESS  read-only
   STATUS      current
   DESCRIPTION
      "Path: swPort.performance.ifOutPriorityQueues.d7Performance.redDroppedPkts

       64 bit unsigned wrappable counter."
   ::= {pr1645v2EthPrtSwF2OutQueuesD7PerformanceEntry 201326592}

pr1645v2EthPrtSwF2OutQueuesD7PerformanceCirTxPkts OBJECT-TYPE
   SYNTAX      Counter64
   MAX-ACCESS  read-only
   STATUS      current
   DESCRIPTION
      "Path: swPort.performance.ifOutPriorityQueues.d7Performance.cirTxPkts

       64 bit unsigned wrappable counter."
   ::= {pr1645v2EthPrtSwF2OutQueuesD7PerformanceEntry 83886080}

pr1645v2EthPrtSwF2OutQueuesD7PerformanceEirTxPkts OBJECT-TYPE
   SYNTAX      Counter64
   MAX-ACCESS  read-only
   STATUS      current
   DESCRIPTION
      "Path: swPort.performance.ifOutPriorityQueues.d7Performance.eirTxPkts

       64 bit unsigned wrappable counter."
   ::= {pr1645v2EthPrtSwF2OutQueuesD7PerformanceEntry 100663296}

pr1645v2EthPrtSwF2OutQueuesD7PerformanceViolTxPkts OBJECT-TYPE
   SYNTAX      Counter64
   MAX-ACCESS  read-only
   STATUS      current
   DESCRIPTION
      "Path: swPort.performance.ifOutPriorityQueues.d7Performance.violateTxPkts

       64 bit unsigned wrappable counter."
   ::= {pr1645v2EthPrtSwF2OutQueuesD7PerformanceEntry 301989888}

pr1645v2EthPrtSwF2OutQueuesD7PerformanceTotOcts OBJECT-TYPE
   SYNTAX      Counter64
   MAX-ACCESS  read-only
   STATUS      current
   DESCRIPTION
      "Path: swPort.performance.ifOutPriorityQueues.d7Performance.totalOctets

       64 bit unsigned wrappable counter."
   ::= {pr1645v2EthPrtSwF2OutQueuesD7PerformanceEntry 251658240}

pr1645v2EthPrtSwF2OutQueuesD7PerformanceDirTxOcts OBJECT-TYPE
   SYNTAX      Counter64
   MAX-ACCESS  read-only
   STATUS      current
   DESCRIPTION
      "Path: swPort.performance.ifOutPriorityQueues.d7Performance.directTxOctets

       64 bit unsigned wrappable counter."
   ::= {pr1645v2EthPrtSwF2OutQueuesD7PerformanceEntry 117440512}

pr1645v2EthPrtSwF2OutQueuesD7PerformanceQdOcts OBJECT-TYPE
   SYNTAX      Counter64
   MAX-ACCESS  read-only
   STATUS      current
   DESCRIPTION
      "Path: swPort.performance.ifOutPriorityQueues.d7Performance.queuedOctets

       64 bit unsigned wrappable counter."
   ::= {pr1645v2EthPrtSwF2OutQueuesD7PerformanceEntry 134217728}

pr1645v2EthPrtSwF2OutQueuesD7PerformanceDropOcts OBJECT-TYPE
   SYNTAX      Counter64
   MAX-ACCESS  read-only
   STATUS      current
   DESCRIPTION
      "Path: swPort.performance.ifOutPriorityQueues.d7Performance.droppedOctets

       64 bit unsigned wrappable counter."
   ::= {pr1645v2EthPrtSwF2OutQueuesD7PerformanceEntry 150994944}

pr1645v2EthPrtSwF2OutQueuesD7PerformanceRDropOcts OBJECT-TYPE
   SYNTAX      Counter64
   MAX-ACCESS  read-only
   STATUS      current
   DESCRIPTION
      "Path: swPort.performance.ifOutPriorityQueues.d7Performance.redDroppedOctets

       64 bit unsigned wrappable counter."
   ::= {pr1645v2EthPrtSwF2OutQueuesD7PerformanceEntry 218103808}

pr1645v2EthPrtSwF2OutQueuesD7PerformanceCirTxOcts OBJECT-TYPE
   SYNTAX      Counter64
   MAX-ACCESS  read-only
   STATUS      current
   DESCRIPTION
      "Path: swPort.performance.ifOutPriorityQueues.d7Performance.cirTxOctets

       64 bit unsigned wrappable counter."
   ::= {pr1645v2EthPrtSwF2OutQueuesD7PerformanceEntry 167772160}

pr1645v2EthPrtSwF2OutQueuesD7PerformanceEirTxOcts OBJECT-TYPE
   SYNTAX      Counter64
   MAX-ACCESS  read-only
   STATUS      current
   DESCRIPTION
      "Path: swPort.performance.ifOutPriorityQueues.d7Performance.eirTxOctets

       64 bit unsigned wrappable counter."
   ::= {pr1645v2EthPrtSwF2OutQueuesD7PerformanceEntry 184549376}

pr1645v2EthPrtSwF2OutQueuesD7PerformanceViolTxOcts OBJECT-TYPE
   SYNTAX      Counter64
   MAX-ACCESS  read-only
   STATUS      current
   DESCRIPTION
      "Path: swPort.performance.ifOutPriorityQueues.d7Performance.violateTxOctets

       64 bit unsigned wrappable counter."
   ::= {pr1645v2EthPrtSwF2OutQueuesD7PerformanceEntry 318767104}

pr1645v2EthPrtSwF2OutQueuesD7PerformanceBandwidth OBJECT-TYPE
   SYNTAX      Integer32
   MAX-ACCESS  read-only
   STATUS      current
   DESCRIPTION
      "Path: swPort.performance.ifOutPriorityQueues.d7Performance.bandwidth

       unit name = bps
       formula = 8 * ; 8 /"
   ::= {pr1645v2EthPrtSwF2OutQueuesD7PerformanceEntry 268435456}


pr1645v2EthPrtSwF2OutBandwidth OBJECT IDENTIFIER ::= {pr1645v2EthPrtSwF2 182}

pr1645v2EthPrtSwF2OutBandwidthSSCTable OBJECT-TYPE
   SYNTAX      SEQUENCE OF Pr1645v2EthPrtSwF2OutBandwidthEntry
   MAX-ACCESS  not-accessible
   STATUS      current
   DESCRIPTION
      "bandwidth"
   ::= {pr1645v2EthPrtSwF2OutBandwidth 1}

pr1645v2EthPrtSwF2OutBandwidthEntry OBJECT-TYPE
   SYNTAX      Pr1645v2EthPrtSwF2OutBandwidthEntry
   MAX-ACCESS  not-accessible
   STATUS      current
   DESCRIPTION
      ""
   INDEX      { pr1645v2EthPrtSwF2OutBandwidthGlobalIx }
   ::= {pr1645v2EthPrtSwF2OutBandwidthSSCTable 1}

Pr1645v2EthPrtSwF2OutBandwidthEntry ::=
   SEQUENCE
      {
      pr1645v2EthPrtSwF2OutBandwidthGlobalIx
         GlobalIndex,
      pr1645v2EthPrtSwF2OutBandwidth15sec
         Integer32,
      pr1645v2EthPrtSwF2OutBandwidth30sec
         Integer32,
      pr1645v2EthPrtSwF2OutBandwidth1min
         Integer32,
      pr1645v2EthPrtSwF2OutBandwidth2min
         Integer32,
      pr1645v2EthPrtSwF2OutBandwidth5min
         Integer32
      }

pr1645v2EthPrtSwF2OutBandwidthGlobalIx OBJECT-TYPE
   SYNTAX      GlobalIndex
   MAX-ACCESS  not-accessible
   STATUS      current
   DESCRIPTION
      "The value of the tlsCntTreeGlobalIndex of the MANAGED OBJECT."
   ::= {pr1645v2EthPrtSwF2OutBandwidthEntry 10}

pr1645v2EthPrtSwF2OutBandwidth15sec OBJECT-TYPE
   SYNTAX      Integer32
   MAX-ACCESS  read-only
   STATUS      current
   DESCRIPTION
      "Path: swPort.performance.ifOutBandwidth.15sec

       unit name = bps
       formula = 8 * ; 8 /"
   ::= {pr1645v2EthPrtSwF2OutBandwidthEntry 83886080}

pr1645v2EthPrtSwF2OutBandwidth30sec OBJECT-TYPE
   SYNTAX      Integer32
   MAX-ACCESS  read-only
   STATUS      current
   DESCRIPTION
      "Path: swPort.performance.ifOutBandwidth.30sec

       unit name = bps
       formula = 8 * ; 8 /"
   ::= {pr1645v2EthPrtSwF2OutBandwidthEntry 167772160}

pr1645v2EthPrtSwF2OutBandwidth1min OBJECT-TYPE
   SYNTAX      Integer32
   MAX-ACCESS  read-only
   STATUS      current
   DESCRIPTION
      "Path: swPort.performance.ifOutBandwidth.1min

       unit name = bps
       formula = 8 * ; 8 /"
   ::= {pr1645v2EthPrtSwF2OutBandwidthEntry 335544320}

pr1645v2EthPrtSwF2OutBandwidth2min OBJECT-TYPE
   SYNTAX      Integer32
   MAX-ACCESS  read-only
   STATUS      current
   DESCRIPTION
      "Path: swPort.performance.ifOutBandwidth.2min

       unit name = bps
       formula = 8 * ; 8 /"
   ::= {pr1645v2EthPrtSwF2OutBandwidthEntry 671088640}

pr1645v2EthPrtSwF2OutBandwidth5min OBJECT-TYPE
   SYNTAX      Integer32
   MAX-ACCESS  read-only
   STATUS      current
   DESCRIPTION
      "Path: swPort.performance.ifOutBandwidth.5min

       unit name = bps
       formula = 8 * ; 8 /"
   ::= {pr1645v2EthPrtSwF2OutBandwidthEntry 1677721600}


pr1645v2EthPrtSwF2InP OBJECT IDENTIFIER ::= {pr1645v2EthPrtSwF2 307}

pr1645v2EthPrtSwF2InPSSCTable OBJECT-TYPE
   SYNTAX      SEQUENCE OF Pr1645v2EthPrtSwF2InPEntry
   MAX-ACCESS  not-accessible
   STATUS      current
   DESCRIPTION
      "h2IfInPerformance"
   ::= {pr1645v2EthPrtSwF2InP 1}

pr1645v2EthPrtSwF2InPEntry OBJECT-TYPE
   SYNTAX      Pr1645v2EthPrtSwF2InPEntry
   MAX-ACCESS  not-accessible
   STATUS      current
   DESCRIPTION
      ""
   INDEX      { pr1645v2EthPrtSwF2InPGlobalIx,
                pr1645v2EthPrtSwF2InPTableIx }
   ::= {pr1645v2EthPrtSwF2InPSSCTable 1}

Pr1645v2EthPrtSwF2InPEntry ::=
   SEQUENCE
      {
      pr1645v2EthPrtSwF2InPGlobalIx
         GlobalIndex,
      pr1645v2EthPrtSwF2InPTableIx
         TableIndex,
      pr1645v2EthPrtSwF2InPSysUpTime
         TimeTicks,
      pr1645v2EthPrtSwF2InPIfUpTime
         TimeTicks,
      pr1645v2EthPrtSwF2InPIfStatChanges
         Counter32,
      pr1645v2EthPrtSwF2InPIfInOctets
         Counter64,
      pr1645v2EthPrtSwF2InPIfInUCPkts
         Counter64,
      pr1645v2EthPrtSwF2InPIfInNUCPkts
         Counter64,
      pr1645v2EthPrtSwF2InPIfInBCPkts
         Counter64,
      pr1645v2EthPrtSwF2InPIfInMCPkts
         Counter64,
      pr1645v2EthPrtSwF2InPIfInDiscards
         Counter64,
      pr1645v2EthPrtSwF2InPIfInErrors
         Counter64,
      pr1645v2EthPrtSwF2InPIfInUnkwn
         Counter64,
      pr1645v2EthPrtSwF2InPInDropEx
         Counter64,
      pr1645v2EthPrtSwF2InPInDropNoMac
         Counter64,
      pr1645v2EthPrtSwF2InPInDropNUCast
         Counter64,
      pr1645v2EthPrtSwF2InPInDropFilter
         Counter64,
      pr1645v2EthPrtSwF2InPIfInBandwidth
         Integer32,
      pr1645v2EthPrtSwF2InPIfOutOctets
         Counter64,
      pr1645v2EthPrtSwF2InPIfOutUCPkts
         Counter64,
      pr1645v2EthPrtSwF2InPIfOutNUCPkts
         Counter64,
      pr1645v2EthPrtSwF2InPIfOutBCPkts
         Counter64,
      pr1645v2EthPrtSwF2InPIfOutMCPkts
         Counter64,
      pr1645v2EthPrtSwF2InPIfOutDiscards
         Counter64,
      pr1645v2EthPrtSwF2InPIfOutErrors
         Counter64,
      pr1645v2EthPrtSwF2InPOutDropEx
         Counter64,
      pr1645v2EthPrtSwF2InPOutDropNoArp
         Counter64,
      pr1645v2EthPrtSwF2InPOutDropFilter
         Counter64,
      pr1645v2EthPrtSwF2InPIfOutBandwidth
         Integer32,
      pr1645v2EthPrtSwF2InPIfErrSec
         Counter32
      }

pr1645v2EthPrtSwF2InPGlobalIx OBJECT-TYPE
   SYNTAX      GlobalIndex
   MAX-ACCESS  not-accessible
   STATUS      current
   DESCRIPTION
      "The value of the tlsCntTreeGlobalIndex of the MANAGED OBJECT."
   ::= {pr1645v2EthPrtSwF2InPEntry 10}

pr1645v2EthPrtSwF2InPTableIx OBJECT-TYPE
   SYNTAX      TableIndex
   MAX-ACCESS  not-accessible
   STATUS      current
   DESCRIPTION
      ""
   ::= {pr1645v2EthPrtSwF2InPEntry 11}

pr1645v2EthPrtSwF2InPSysUpTime OBJECT-TYPE
   SYNTAX      TimeTicks
   MAX-ACCESS  read-only
   STATUS      current
   DESCRIPTION
      "Path: swPort.performance.h2Performance.sysUpTime

       Time in centi-second."
   ::= {pr1645v2EthPrtSwF2InPEntry 16777216}

pr1645v2EthPrtSwF2InPIfUpTime OBJECT-TYPE
   SYNTAX      TimeTicks
   MAX-ACCESS  read-only
   STATUS      current
   DESCRIPTION
      "Path: swPort.performance.h2Performance.ifUpTime

       Time in centi-second."
   ::= {pr1645v2EthPrtSwF2InPEntry 33554432}

pr1645v2EthPrtSwF2InPIfStatChanges OBJECT-TYPE
   SYNTAX      Counter32
   MAX-ACCESS  read-only
   STATUS      current
   DESCRIPTION
      "Path: swPort.performance.h2Performance.ifStatusChanges

       32 bit unsigned wrappable counter."
   ::= {pr1645v2EthPrtSwF2InPEntry 50331648}

pr1645v2EthPrtSwF2InPIfInOctets OBJECT-TYPE
   SYNTAX      Counter64
   MAX-ACCESS  read-only
   STATUS      current
   DESCRIPTION
      "Path: swPort.performance.h2Performance.ifInOctets

       64 bit unsigned wrappable counter."
   ::= {pr1645v2EthPrtSwF2InPEntry 67108864}

pr1645v2EthPrtSwF2InPIfInUCPkts OBJECT-TYPE
   SYNTAX      Counter64
   MAX-ACCESS  read-only
   STATUS      current
   DESCRIPTION
      "Path: swPort.performance.h2Performance.ifInUcastPkts

       64 bit unsigned wrappable counter."
   ::= {pr1645v2EthPrtSwF2InPEntry 83886080}

pr1645v2EthPrtSwF2InPIfInNUCPkts OBJECT-TYPE
   SYNTAX      Counter64
   MAX-ACCESS  read-only
   STATUS      current
   DESCRIPTION
      "Path: swPort.performance.h2Performance.ifInNUcastPkts

       64 bit unsigned wrappable counter."
   ::= {pr1645v2EthPrtSwF2InPEntry 100663296}

pr1645v2EthPrtSwF2InPIfInBCPkts OBJECT-TYPE
   SYNTAX      Counter64
   MAX-ACCESS  read-only
   STATUS      current
   DESCRIPTION
      "Path: swPort.performance.h2Performance.ifInBcastPkts

       64 bit unsigned wrappable counter."
   ::= {pr1645v2EthPrtSwF2InPEntry 419430400}

pr1645v2EthPrtSwF2InPIfInMCPkts OBJECT-TYPE
   SYNTAX      Counter64
   MAX-ACCESS  read-only
   STATUS      current
   DESCRIPTION
      "Path: swPort.performance.h2Performance.ifInMcastPkts

       64 bit unsigned wrappable counter."
   ::= {pr1645v2EthPrtSwF2InPEntry 436207616}

pr1645v2EthPrtSwF2InPIfInDiscards OBJECT-TYPE
   SYNTAX      Counter64
   MAX-ACCESS  read-only
   STATUS      current
   DESCRIPTION
      "Path: swPort.performance.h2Performance.ifInDiscards

       64 bit unsigned wrappable counter."
   ::= {pr1645v2EthPrtSwF2InPEntry 117440512}

pr1645v2EthPrtSwF2InPIfInErrors OBJECT-TYPE
   SYNTAX      Counter64
   MAX-ACCESS  read-only
   STATUS      current
   DESCRIPTION
      "Path: swPort.performance.h2Performance.ifInErrors

       64 bit unsigned wrappable counter."
   ::= {pr1645v2EthPrtSwF2InPEntry 134217728}

pr1645v2EthPrtSwF2InPIfInUnkwn OBJECT-TYPE
   SYNTAX      Counter64
   MAX-ACCESS  read-only
   STATUS      current
   DESCRIPTION
      "Path: swPort.performance.h2Performance.ifInUnknownProtos

       64 bit unsigned wrappable counter."
   ::= {pr1645v2EthPrtSwF2InPEntry 150994944}

pr1645v2EthPrtSwF2InPInDropEx OBJECT-TYPE
   SYNTAX      Counter64
   MAX-ACCESS  read-only
   STATUS      current
   DESCRIPTION
      "Path: swPort.performance.h2Performance.ifInDropLevelExceeded

       64 bit unsigned wrappable counter."
   ::= {pr1645v2EthPrtSwF2InPEntry 335544320}

pr1645v2EthPrtSwF2InPInDropNoMac OBJECT-TYPE
   SYNTAX      Counter64
   MAX-ACCESS  read-only
   STATUS      current
   DESCRIPTION
      "Path: swPort.performance.h2Performance.fInDiscardsNoMacFit

       64 bit unsigned wrappable counter."
   ::= {pr1645v2EthPrtSwF2InPEntry 301989888}

pr1645v2EthPrtSwF2InPInDropNUCast OBJECT-TYPE
   SYNTAX      Counter64
   MAX-ACCESS  read-only
   STATUS      current
   DESCRIPTION
      "Path: swPort.performance.h2Performance.fInDiscardsNUCast

       64 bit unsigned wrappable counter."
   ::= {pr1645v2EthPrtSwF2InPEntry 318767104}

pr1645v2EthPrtSwF2InPInDropFilter OBJECT-TYPE
   SYNTAX      Counter64
   MAX-ACCESS  read-only
   STATUS      current
   DESCRIPTION
      "Path: swPort.performance.h2Performance.fInDiscardsFilter

       64 bit unsigned wrappable counter."
   ::= {pr1645v2EthPrtSwF2InPEntry 385875968}

pr1645v2EthPrtSwF2InPIfInBandwidth OBJECT-TYPE
   SYNTAX      Integer32
   MAX-ACCESS  read-only
   STATUS      current
   DESCRIPTION
      "Path: swPort.performance.h2Performance.ifInBandwidth

       unit name = bps
       formula = 8 * ; 8 /"
   ::= {pr1645v2EthPrtSwF2InPEntry 268435456}

pr1645v2EthPrtSwF2InPIfOutOctets OBJECT-TYPE
   SYNTAX      Counter64
   MAX-ACCESS  read-only
   STATUS      current
   DESCRIPTION
      "Path: swPort.performance.h2Performance.ifOutOctets

       64 bit unsigned wrappable counter."
   ::= {pr1645v2EthPrtSwF2InPEntry 167772160}

pr1645v2EthPrtSwF2InPIfOutUCPkts OBJECT-TYPE
   SYNTAX      Counter64
   MAX-ACCESS  read-only
   STATUS      current
   DESCRIPTION
      "Path: swPort.performance.h2Performance.ifOutUcastPkts

       64 bit unsigned wrappable counter."
   ::= {pr1645v2EthPrtSwF2InPEntry 184549376}

pr1645v2EthPrtSwF2InPIfOutNUCPkts OBJECT-TYPE
   SYNTAX      Counter64
   MAX-ACCESS  read-only
   STATUS      current
   DESCRIPTION
      "Path: swPort.performance.h2Performance.ifOutNUcastPkts

       64 bit unsigned wrappable counter."
   ::= {pr1645v2EthPrtSwF2InPEntry 201326592}

pr1645v2EthPrtSwF2InPIfOutBCPkts OBJECT-TYPE
   SYNTAX      Counter64
   MAX-ACCESS  read-only
   STATUS      current
   DESCRIPTION
      "Path: swPort.performance.h2Performance.ifOutBcastPkts

       64 bit unsigned wrappable counter."
   ::= {pr1645v2EthPrtSwF2InPEntry 452984832}

pr1645v2EthPrtSwF2InPIfOutMCPkts OBJECT-TYPE
   SYNTAX      Counter64
   MAX-ACCESS  read-only
   STATUS      current
   DESCRIPTION
      "Path: swPort.performance.h2Performance.ifOutMcastPkts

       64 bit unsigned wrappable counter."
   ::= {pr1645v2EthPrtSwF2InPEntry 469762048}

pr1645v2EthPrtSwF2InPIfOutDiscards OBJECT-TYPE
   SYNTAX      Counter64
   MAX-ACCESS  read-only
   STATUS      current
   DESCRIPTION
      "Path: swPort.performance.h2Performance.ifOutDiscards

       64 bit unsigned wrappable counter."
   ::= {pr1645v2EthPrtSwF2InPEntry 218103808}

pr1645v2EthPrtSwF2InPIfOutErrors OBJECT-TYPE
   SYNTAX      Counter64
   MAX-ACCESS  read-only
   STATUS      current
   DESCRIPTION
      "Path: swPort.performance.h2Performance.ifOutErrors

       64 bit unsigned wrappable counter."
   ::= {pr1645v2EthPrtSwF2InPEntry 234881024}

pr1645v2EthPrtSwF2InPOutDropEx OBJECT-TYPE
   SYNTAX      Counter64
   MAX-ACCESS  read-only
   STATUS      current
   DESCRIPTION
      "Path: swPort.performance.h2Performance.ifOutDropLevelExceeded

       64 bit unsigned wrappable counter."
   ::= {pr1645v2EthPrtSwF2InPEntry 352321536}

pr1645v2EthPrtSwF2InPOutDropNoArp OBJECT-TYPE
   SYNTAX      Counter64
   MAX-ACCESS  read-only
   STATUS      current
   DESCRIPTION
      "Path: swPort.performance.h2Performance.ifOutDiscardsNoArp

       64 bit unsigned wrappable counter."
   ::= {pr1645v2EthPrtSwF2InPEntry 369098752}

pr1645v2EthPrtSwF2InPOutDropFilter OBJECT-TYPE
   SYNTAX      Counter64
   MAX-ACCESS  read-only
   STATUS      current
   DESCRIPTION
      "Path: swPort.performance.h2Performance.ifOutDiscardsFilter

       64 bit unsigned wrappable counter."
   ::= {pr1645v2EthPrtSwF2InPEntry 402653184}

pr1645v2EthPrtSwF2InPIfOutBandwidth OBJECT-TYPE
   SYNTAX      Integer32
   MAX-ACCESS  read-only
   STATUS      current
   DESCRIPTION
      "Path: swPort.performance.h2Performance.ifOutBandwidth

       unit name = bps
       formula = 8 * ; 8 /"
   ::= {pr1645v2EthPrtSwF2InPEntry 285212672}

pr1645v2EthPrtSwF2InPIfErrSec OBJECT-TYPE
   SYNTAX      Counter32
   MAX-ACCESS  read-only
   STATUS      current
   DESCRIPTION
      "Path: swPort.performance.h2Performance.ifErrSec

       32 bit unsigned wrappable counter."
   ::= {pr1645v2EthPrtSwF2InPEntry 251658240}


pr1645v2EthPrtSwF2H24InP OBJECT IDENTIFIER ::= {pr1645v2EthPrtSwF2 308}

pr1645v2EthPrtSwF2H24InPSSCTable OBJECT-TYPE
   SYNTAX      SEQUENCE OF Pr1645v2EthPrtSwF2H24InPEntry
   MAX-ACCESS  not-accessible
   STATUS      current
   DESCRIPTION
      "h24IfInPerformance"
   ::= {pr1645v2EthPrtSwF2H24InP 1}

pr1645v2EthPrtSwF2H24InPEntry OBJECT-TYPE
   SYNTAX      Pr1645v2EthPrtSwF2H24InPEntry
   MAX-ACCESS  not-accessible
   STATUS      current
   DESCRIPTION
      ""
   INDEX      { pr1645v2EthPrtSwF2H24InPGlobalIx,
                pr1645v2EthPrtSwF2H24InPTableIx }
   ::= {pr1645v2EthPrtSwF2H24InPSSCTable 1}

Pr1645v2EthPrtSwF2H24InPEntry ::=
   SEQUENCE
      {
      pr1645v2EthPrtSwF2H24InPGlobalIx
         GlobalIndex,
      pr1645v2EthPrtSwF2H24InPTableIx
         TableIndex,
      pr1645v2EthPrtSwF2H24InPSysUpTime
         TimeTicks,
      pr1645v2EthPrtSwF2H24InPIfUpTime
         TimeTicks,
      pr1645v2EthPrtSwF2H24InPIfStatChanges
         Counter32,
      pr1645v2EthPrtSwF2H24InPIfInOctets
         Counter64,
      pr1645v2EthPrtSwF2H24InPIfInUCPkts
         Counter64,
      pr1645v2EthPrtSwF2H24InPIfInNUCPkts
         Counter64,
      pr1645v2EthPrtSwF2H24InPIfInBCPkts
         Counter64,
      pr1645v2EthPrtSwF2H24InPIfInMCPkts
         Counter64,
      pr1645v2EthPrtSwF2H24InPIfInDiscards
         Counter64,
      pr1645v2EthPrtSwF2H24InPIfInErrors
         Counter64,
      pr1645v2EthPrtSwF2H24InPIfInUnkwn
         Counter64,
      pr1645v2EthPrtSwF2H24InPInDropEx
         Counter64,
      pr1645v2EthPrtSwF2H24InPInDropNoMac
         Counter64,
      pr1645v2EthPrtSwF2H24InPInDropNUCast
         Counter64,
      pr1645v2EthPrtSwF2H24InPInDropFilter
         Counter64,
      pr1645v2EthPrtSwF2H24InPIfInBandwidth
         Integer32,
      pr1645v2EthPrtSwF2H24InPIfOutOctets
         Counter64,
      pr1645v2EthPrtSwF2H24InPIfOutUCPkts
         Counter64,
      pr1645v2EthPrtSwF2H24InPIfOutNUCPkts
         Counter64,
      pr1645v2EthPrtSwF2H24InPIfOutBCPkts
         Counter64,
      pr1645v2EthPrtSwF2H24InPIfOutMCPkts
         Counter64,
      pr1645v2EthPrtSwF2H24InPIfOutDiscards
         Counter64,
      pr1645v2EthPrtSwF2H24InPIfOutErrors
         Counter64,
      pr1645v2EthPrtSwF2H24InPOutDropEx
         Counter64,
      pr1645v2EthPrtSwF2H24InPOutDropNoArp
         Counter64,
      pr1645v2EthPrtSwF2H24InPOutDropFilter
         Counter64,
      pr1645v2EthPrtSwF2H24InPIfOutBandwidth
         Integer32,
      pr1645v2EthPrtSwF2H24InPIfErrSec
         Counter32
      }

pr1645v2EthPrtSwF2H24InPGlobalIx OBJECT-TYPE
   SYNTAX      GlobalIndex
   MAX-ACCESS  not-accessible
   STATUS      current
   DESCRIPTION
      "The value of the tlsCntTreeGlobalIndex of the MANAGED OBJECT."
   ::= {pr1645v2EthPrtSwF2H24InPEntry 10}

pr1645v2EthPrtSwF2H24InPTableIx OBJECT-TYPE
   SYNTAX      TableIndex
   MAX-ACCESS  not-accessible
   STATUS      current
   DESCRIPTION
      ""
   ::= {pr1645v2EthPrtSwF2H24InPEntry 11}

pr1645v2EthPrtSwF2H24InPSysUpTime OBJECT-TYPE
   SYNTAX      TimeTicks
   MAX-ACCESS  read-only
   STATUS      current
   DESCRIPTION
      "Path: swPort.performance.h24Performance.sysUpTime

       Time in centi-second."
   ::= {pr1645v2EthPrtSwF2H24InPEntry 16777216}

pr1645v2EthPrtSwF2H24InPIfUpTime OBJECT-TYPE
   SYNTAX      TimeTicks
   MAX-ACCESS  read-only
   STATUS      current
   DESCRIPTION
      "Path: swPort.performance.h24Performance.ifUpTime

       Time in centi-second."
   ::= {pr1645v2EthPrtSwF2H24InPEntry 33554432}

pr1645v2EthPrtSwF2H24InPIfStatChanges OBJECT-TYPE
   SYNTAX      Counter32
   MAX-ACCESS  read-only
   STATUS      current
   DESCRIPTION
      "Path: swPort.performance.h24Performance.ifStatusChanges

       32 bit unsigned wrappable counter."
   ::= {pr1645v2EthPrtSwF2H24InPEntry 50331648}

pr1645v2EthPrtSwF2H24InPIfInOctets OBJECT-TYPE
   SYNTAX      Counter64
   MAX-ACCESS  read-only
   STATUS      current
   DESCRIPTION
      "Path: swPort.performance.h24Performance.ifInOctets

       64 bit unsigned wrappable counter."
   ::= {pr1645v2EthPrtSwF2H24InPEntry 67108864}

pr1645v2EthPrtSwF2H24InPIfInUCPkts OBJECT-TYPE
   SYNTAX      Counter64
   MAX-ACCESS  read-only
   STATUS      current
   DESCRIPTION
      "Path: swPort.performance.h24Performance.ifInUcastPkts

       64 bit unsigned wrappable counter."
   ::= {pr1645v2EthPrtSwF2H24InPEntry 83886080}

pr1645v2EthPrtSwF2H24InPIfInNUCPkts OBJECT-TYPE
   SYNTAX      Counter64
   MAX-ACCESS  read-only
   STATUS      current
   DESCRIPTION
      "Path: swPort.performance.h24Performance.ifInNUcastPkts

       64 bit unsigned wrappable counter."
   ::= {pr1645v2EthPrtSwF2H24InPEntry 100663296}

pr1645v2EthPrtSwF2H24InPIfInBCPkts OBJECT-TYPE
   SYNTAX      Counter64
   MAX-ACCESS  read-only
   STATUS      current
   DESCRIPTION
      "Path: swPort.performance.h24Performance.ifInBcastPkts

       64 bit unsigned wrappable counter."
   ::= {pr1645v2EthPrtSwF2H24InPEntry 419430400}

pr1645v2EthPrtSwF2H24InPIfInMCPkts OBJECT-TYPE
   SYNTAX      Counter64
   MAX-ACCESS  read-only
   STATUS      current
   DESCRIPTION
      "Path: swPort.performance.h24Performance.ifInMcastPkts

       64 bit unsigned wrappable counter."
   ::= {pr1645v2EthPrtSwF2H24InPEntry 436207616}

pr1645v2EthPrtSwF2H24InPIfInDiscards OBJECT-TYPE
   SYNTAX      Counter64
   MAX-ACCESS  read-only
   STATUS      current
   DESCRIPTION
      "Path: swPort.performance.h24Performance.ifInDiscards

       64 bit unsigned wrappable counter."
   ::= {pr1645v2EthPrtSwF2H24InPEntry 117440512}

pr1645v2EthPrtSwF2H24InPIfInErrors OBJECT-TYPE
   SYNTAX      Counter64
   MAX-ACCESS  read-only
   STATUS      current
   DESCRIPTION
      "Path: swPort.performance.h24Performance.ifInErrors

       64 bit unsigned wrappable counter."
   ::= {pr1645v2EthPrtSwF2H24InPEntry 134217728}

pr1645v2EthPrtSwF2H24InPIfInUnkwn OBJECT-TYPE
   SYNTAX      Counter64
   MAX-ACCESS  read-only
   STATUS      current
   DESCRIPTION
      "Path: swPort.performance.h24Performance.ifInUnknownProtos

       64 bit unsigned wrappable counter."
   ::= {pr1645v2EthPrtSwF2H24InPEntry 150994944}

pr1645v2EthPrtSwF2H24InPInDropEx OBJECT-TYPE
   SYNTAX      Counter64
   MAX-ACCESS  read-only
   STATUS      current
   DESCRIPTION
      "Path: swPort.performance.h24Performance.ifInDropLevelExceeded

       64 bit unsigned wrappable counter."
   ::= {pr1645v2EthPrtSwF2H24InPEntry 335544320}

pr1645v2EthPrtSwF2H24InPInDropNoMac OBJECT-TYPE
   SYNTAX      Counter64
   MAX-ACCESS  read-only
   STATUS      current
   DESCRIPTION
      "Path: swPort.performance.h24Performance.fInDiscardsNoMacFit

       64 bit unsigned wrappable counter."
   ::= {pr1645v2EthPrtSwF2H24InPEntry 301989888}

pr1645v2EthPrtSwF2H24InPInDropNUCast OBJECT-TYPE
   SYNTAX      Counter64
   MAX-ACCESS  read-only
   STATUS      current
   DESCRIPTION
      "Path: swPort.performance.h24Performance.fInDiscardsNUCast

       64 bit unsigned wrappable counter."
   ::= {pr1645v2EthPrtSwF2H24InPEntry 318767104}

pr1645v2EthPrtSwF2H24InPInDropFilter OBJECT-TYPE
   SYNTAX      Counter64
   MAX-ACCESS  read-only
   STATUS      current
   DESCRIPTION
      "Path: swPort.performance.h24Performance.fInDiscardsFilter

       64 bit unsigned wrappable counter."
   ::= {pr1645v2EthPrtSwF2H24InPEntry 385875968}

pr1645v2EthPrtSwF2H24InPIfInBandwidth OBJECT-TYPE
   SYNTAX      Integer32
   MAX-ACCESS  read-only
   STATUS      current
   DESCRIPTION
      "Path: swPort.performance.h24Performance.ifInBandwidth

       unit name = bps
       formula = 8 * ; 8 /"
   ::= {pr1645v2EthPrtSwF2H24InPEntry 268435456}

pr1645v2EthPrtSwF2H24InPIfOutOctets OBJECT-TYPE
   SYNTAX      Counter64
   MAX-ACCESS  read-only
   STATUS      current
   DESCRIPTION
      "Path: swPort.performance.h24Performance.ifOutOctets

       64 bit unsigned wrappable counter."
   ::= {pr1645v2EthPrtSwF2H24InPEntry 167772160}

pr1645v2EthPrtSwF2H24InPIfOutUCPkts OBJECT-TYPE
   SYNTAX      Counter64
   MAX-ACCESS  read-only
   STATUS      current
   DESCRIPTION
      "Path: swPort.performance.h24Performance.ifOutUcastPkts

       64 bit unsigned wrappable counter."
   ::= {pr1645v2EthPrtSwF2H24InPEntry 184549376}

pr1645v2EthPrtSwF2H24InPIfOutNUCPkts OBJECT-TYPE
   SYNTAX      Counter64
   MAX-ACCESS  read-only
   STATUS      current
   DESCRIPTION
      "Path: swPort.performance.h24Performance.ifOutNUcastPkts

       64 bit unsigned wrappable counter."
   ::= {pr1645v2EthPrtSwF2H24InPEntry 201326592}

pr1645v2EthPrtSwF2H24InPIfOutBCPkts OBJECT-TYPE
   SYNTAX      Counter64
   MAX-ACCESS  read-only
   STATUS      current
   DESCRIPTION
      "Path: swPort.performance.h24Performance.ifOutBcastPkts

       64 bit unsigned wrappable counter."
   ::= {pr1645v2EthPrtSwF2H24InPEntry 452984832}

pr1645v2EthPrtSwF2H24InPIfOutMCPkts OBJECT-TYPE
   SYNTAX      Counter64
   MAX-ACCESS  read-only
   STATUS      current
   DESCRIPTION
      "Path: swPort.performance.h24Performance.ifOutMcastPkts

       64 bit unsigned wrappable counter."
   ::= {pr1645v2EthPrtSwF2H24InPEntry 469762048}

pr1645v2EthPrtSwF2H24InPIfOutDiscards OBJECT-TYPE
   SYNTAX      Counter64
   MAX-ACCESS  read-only
   STATUS      current
   DESCRIPTION
      "Path: swPort.performance.h24Performance.ifOutDiscards

       64 bit unsigned wrappable counter."
   ::= {pr1645v2EthPrtSwF2H24InPEntry 218103808}

pr1645v2EthPrtSwF2H24InPIfOutErrors OBJECT-TYPE
   SYNTAX      Counter64
   MAX-ACCESS  read-only
   STATUS      current
   DESCRIPTION
      "Path: swPort.performance.h24Performance.ifOutErrors

       64 bit unsigned wrappable counter."
   ::= {pr1645v2EthPrtSwF2H24InPEntry 234881024}

pr1645v2EthPrtSwF2H24InPOutDropEx OBJECT-TYPE
   SYNTAX      Counter64
   MAX-ACCESS  read-only
   STATUS      current
   DESCRIPTION
      "Path: swPort.performance.h24Performance.ifOutDropLevelExceeded

       64 bit unsigned wrappable counter."
   ::= {pr1645v2EthPrtSwF2H24InPEntry 352321536}

pr1645v2EthPrtSwF2H24InPOutDropNoArp OBJECT-TYPE
   SYNTAX      Counter64
   MAX-ACCESS  read-only
   STATUS      current
   DESCRIPTION
      "Path: swPort.performance.h24Performance.ifOutDiscardsNoArp

       64 bit unsigned wrappable counter."
   ::= {pr1645v2EthPrtSwF2H24InPEntry 369098752}

pr1645v2EthPrtSwF2H24InPOutDropFilter OBJECT-TYPE
   SYNTAX      Counter64
   MAX-ACCESS  read-only
   STATUS      current
   DESCRIPTION
      "Path: swPort.performance.h24Performance.ifOutDiscardsFilter

       64 bit unsigned wrappable counter."
   ::= {pr1645v2EthPrtSwF2H24InPEntry 402653184}

pr1645v2EthPrtSwF2H24InPIfOutBandwidth OBJECT-TYPE
   SYNTAX      Integer32
   MAX-ACCESS  read-only
   STATUS      current
   DESCRIPTION
      "Path: swPort.performance.h24Performance.ifOutBandwidth

       unit name = bps
       formula = 8 * ; 8 /"
   ::= {pr1645v2EthPrtSwF2H24InPEntry 285212672}

pr1645v2EthPrtSwF2H24InPIfErrSec OBJECT-TYPE
   SYNTAX      Counter32
   MAX-ACCESS  read-only
   STATUS      current
   DESCRIPTION
      "Path: swPort.performance.h24Performance.ifErrSec

       32 bit unsigned wrappable counter."
   ::= {pr1645v2EthPrtSwF2H24InPEntry 251658240}


pr1645v2EthPrtSwF2D7InP OBJECT IDENTIFIER ::= {pr1645v2EthPrtSwF2 309}

pr1645v2EthPrtSwF2D7InPSSCTable OBJECT-TYPE
   SYNTAX      SEQUENCE OF Pr1645v2EthPrtSwF2D7InPEntry
   MAX-ACCESS  not-accessible
   STATUS      current
   DESCRIPTION
      "d7IfInPerformance"
   ::= {pr1645v2EthPrtSwF2D7InP 1}

pr1645v2EthPrtSwF2D7InPEntry OBJECT-TYPE
   SYNTAX      Pr1645v2EthPrtSwF2D7InPEntry
   MAX-ACCESS  not-accessible
   STATUS      current
   DESCRIPTION
      ""
   INDEX      { pr1645v2EthPrtSwF2D7InPGlobalIx,
                pr1645v2EthPrtSwF2D7InPTableIx }
   ::= {pr1645v2EthPrtSwF2D7InPSSCTable 1}

Pr1645v2EthPrtSwF2D7InPEntry ::=
   SEQUENCE
      {
      pr1645v2EthPrtSwF2D7InPGlobalIx
         GlobalIndex,
      pr1645v2EthPrtSwF2D7InPTableIx
         TableIndex,
      pr1645v2EthPrtSwF2D7InPSysUpTime
         TimeTicks,
      pr1645v2EthPrtSwF2D7InPIfUpTime
         TimeTicks,
      pr1645v2EthPrtSwF2D7InPIfStatChanges
         Counter32,
      pr1645v2EthPrtSwF2D7InPIfInOctets
         Counter64,
      pr1645v2EthPrtSwF2D7InPIfInUCPkts
         Counter64,
      pr1645v2EthPrtSwF2D7InPIfInNUCPkts
         Counter64,
      pr1645v2EthPrtSwF2D7InPIfInBCPkts
         Counter64,
      pr1645v2EthPrtSwF2D7InPIfInMCPkts
         Counter64,
      pr1645v2EthPrtSwF2D7InPIfInDiscards
         Counter64,
      pr1645v2EthPrtSwF2D7InPIfInErrors
         Counter64,
      pr1645v2EthPrtSwF2D7InPIfInUnkwn
         Counter64,
      pr1645v2EthPrtSwF2D7InPInDropEx
         Counter64,
      pr1645v2EthPrtSwF2D7InPInDropNoMac
         Counter64,
      pr1645v2EthPrtSwF2D7InPInDropNUCast
         Counter64,
      pr1645v2EthPrtSwF2D7InPInDropFilter
         Counter64,
      pr1645v2EthPrtSwF2D7InPIfInBandwidth
         Integer32,
      pr1645v2EthPrtSwF2D7InPIfOutOctets
         Counter64,
      pr1645v2EthPrtSwF2D7InPIfOutUCPkts
         Counter64,
      pr1645v2EthPrtSwF2D7InPIfOutNUCPkts
         Counter64,
      pr1645v2EthPrtSwF2D7InPIfOutBCPkts
         Counter64,
      pr1645v2EthPrtSwF2D7InPIfOutMCPkts
         Counter64,
      pr1645v2EthPrtSwF2D7InPIfOutDiscards
         Counter64,
      pr1645v2EthPrtSwF2D7InPIfOutErrors
         Counter64,
      pr1645v2EthPrtSwF2D7InPOutDropEx
         Counter64,
      pr1645v2EthPrtSwF2D7InPOutDropNoArp
         Counter64,
      pr1645v2EthPrtSwF2D7InPOutDropFilter
         Counter64,
      pr1645v2EthPrtSwF2D7InPIfOutBandwidth
         Integer32,
      pr1645v2EthPrtSwF2D7InPIfErrSec
         Counter32
      }

pr1645v2EthPrtSwF2D7InPGlobalIx OBJECT-TYPE
   SYNTAX      GlobalIndex
   MAX-ACCESS  not-accessible
   STATUS      current
   DESCRIPTION
      "The value of the tlsCntTreeGlobalIndex of the MANAGED OBJECT."
   ::= {pr1645v2EthPrtSwF2D7InPEntry 10}

pr1645v2EthPrtSwF2D7InPTableIx OBJECT-TYPE
   SYNTAX      TableIndex
   MAX-ACCESS  not-accessible
   STATUS      current
   DESCRIPTION
      ""
   ::= {pr1645v2EthPrtSwF2D7InPEntry 11}

pr1645v2EthPrtSwF2D7InPSysUpTime OBJECT-TYPE
   SYNTAX      TimeTicks
   MAX-ACCESS  read-only
   STATUS      current
   DESCRIPTION
      "Path: swPort.performance.d7Performance.sysUpTime

       Time in centi-second."
   ::= {pr1645v2EthPrtSwF2D7InPEntry 16777216}

pr1645v2EthPrtSwF2D7InPIfUpTime OBJECT-TYPE
   SYNTAX      TimeTicks
   MAX-ACCESS  read-only
   STATUS      current
   DESCRIPTION
      "Path: swPort.performance.d7Performance.ifUpTime

       Time in centi-second."
   ::= {pr1645v2EthPrtSwF2D7InPEntry 33554432}

pr1645v2EthPrtSwF2D7InPIfStatChanges OBJECT-TYPE
   SYNTAX      Counter32
   MAX-ACCESS  read-only
   STATUS      current
   DESCRIPTION
      "Path: swPort.performance.d7Performance.ifStatusChanges

       32 bit unsigned wrappable counter."
   ::= {pr1645v2EthPrtSwF2D7InPEntry 50331648}

pr1645v2EthPrtSwF2D7InPIfInOctets OBJECT-TYPE
   SYNTAX      Counter64
   MAX-ACCESS  read-only
   STATUS      current
   DESCRIPTION
      "Path: swPort.performance.d7Performance.ifInOctets

       64 bit unsigned wrappable counter."
   ::= {pr1645v2EthPrtSwF2D7InPEntry 67108864}

pr1645v2EthPrtSwF2D7InPIfInUCPkts OBJECT-TYPE
   SYNTAX      Counter64
   MAX-ACCESS  read-only
   STATUS      current
   DESCRIPTION
      "Path: swPort.performance.d7Performance.ifInUcastPkts

       64 bit unsigned wrappable counter."
   ::= {pr1645v2EthPrtSwF2D7InPEntry 83886080}

pr1645v2EthPrtSwF2D7InPIfInNUCPkts OBJECT-TYPE
   SYNTAX      Counter64
   MAX-ACCESS  read-only
   STATUS      current
   DESCRIPTION
      "Path: swPort.performance.d7Performance.ifInNUcastPkts

       64 bit unsigned wrappable counter."
   ::= {pr1645v2EthPrtSwF2D7InPEntry 100663296}

pr1645v2EthPrtSwF2D7InPIfInBCPkts OBJECT-TYPE
   SYNTAX      Counter64
   MAX-ACCESS  read-only
   STATUS      current
   DESCRIPTION
      "Path: swPort.performance.d7Performance.ifInBcastPkts

       64 bit unsigned wrappable counter."
   ::= {pr1645v2EthPrtSwF2D7InPEntry 419430400}

pr1645v2EthPrtSwF2D7InPIfInMCPkts OBJECT-TYPE
   SYNTAX      Counter64
   MAX-ACCESS  read-only
   STATUS      current
   DESCRIPTION
      "Path: swPort.performance.d7Performance.ifInMcastPkts

       64 bit unsigned wrappable counter."
   ::= {pr1645v2EthPrtSwF2D7InPEntry 436207616}

pr1645v2EthPrtSwF2D7InPIfInDiscards OBJECT-TYPE
   SYNTAX      Counter64
   MAX-ACCESS  read-only
   STATUS      current
   DESCRIPTION
      "Path: swPort.performance.d7Performance.ifInDiscards

       64 bit unsigned wrappable counter."
   ::= {pr1645v2EthPrtSwF2D7InPEntry 117440512}

pr1645v2EthPrtSwF2D7InPIfInErrors OBJECT-TYPE
   SYNTAX      Counter64
   MAX-ACCESS  read-only
   STATUS      current
   DESCRIPTION
      "Path: swPort.performance.d7Performance.ifInErrors

       64 bit unsigned wrappable counter."
   ::= {pr1645v2EthPrtSwF2D7InPEntry 134217728}

pr1645v2EthPrtSwF2D7InPIfInUnkwn OBJECT-TYPE
   SYNTAX      Counter64
   MAX-ACCESS  read-only
   STATUS      current
   DESCRIPTION
      "Path: swPort.performance.d7Performance.ifInUnknownProtos

       64 bit unsigned wrappable counter."
   ::= {pr1645v2EthPrtSwF2D7InPEntry 150994944}

pr1645v2EthPrtSwF2D7InPInDropEx OBJECT-TYPE
   SYNTAX      Counter64
   MAX-ACCESS  read-only
   STATUS      current
   DESCRIPTION
      "Path: swPort.performance.d7Performance.ifInDropLevelExceeded

       64 bit unsigned wrappable counter."
   ::= {pr1645v2EthPrtSwF2D7InPEntry 335544320}

pr1645v2EthPrtSwF2D7InPInDropNoMac OBJECT-TYPE
   SYNTAX      Counter64
   MAX-ACCESS  read-only
   STATUS      current
   DESCRIPTION
      "Path: swPort.performance.d7Performance.fInDiscardsNoMacFit

       64 bit unsigned wrappable counter."
   ::= {pr1645v2EthPrtSwF2D7InPEntry 301989888}

pr1645v2EthPrtSwF2D7InPInDropNUCast OBJECT-TYPE
   SYNTAX      Counter64
   MAX-ACCESS  read-only
   STATUS      current
   DESCRIPTION
      "Path: swPort.performance.d7Performance.fInDiscardsNUCast

       64 bit unsigned wrappable counter."
   ::= {pr1645v2EthPrtSwF2D7InPEntry 318767104}

pr1645v2EthPrtSwF2D7InPInDropFilter OBJECT-TYPE
   SYNTAX      Counter64
   MAX-ACCESS  read-only
   STATUS      current
   DESCRIPTION
      "Path: swPort.performance.d7Performance.fInDiscardsFilter

       64 bit unsigned wrappable counter."
   ::= {pr1645v2EthPrtSwF2D7InPEntry 385875968}

pr1645v2EthPrtSwF2D7InPIfInBandwidth OBJECT-TYPE
   SYNTAX      Integer32
   MAX-ACCESS  read-only
   STATUS      current
   DESCRIPTION
      "Path: swPort.performance.d7Performance.ifInBandwidth

       unit name = bps
       formula = 8 * ; 8 /"
   ::= {pr1645v2EthPrtSwF2D7InPEntry 268435456}

pr1645v2EthPrtSwF2D7InPIfOutOctets OBJECT-TYPE
   SYNTAX      Counter64
   MAX-ACCESS  read-only
   STATUS      current
   DESCRIPTION
      "Path: swPort.performance.d7Performance.ifOutOctets

       64 bit unsigned wrappable counter."
   ::= {pr1645v2EthPrtSwF2D7InPEntry 167772160}

pr1645v2EthPrtSwF2D7InPIfOutUCPkts OBJECT-TYPE
   SYNTAX      Counter64
   MAX-ACCESS  read-only
   STATUS      current
   DESCRIPTION
      "Path: swPort.performance.d7Performance.ifOutUcastPkts

       64 bit unsigned wrappable counter."
   ::= {pr1645v2EthPrtSwF2D7InPEntry 184549376}

pr1645v2EthPrtSwF2D7InPIfOutNUCPkts OBJECT-TYPE
   SYNTAX      Counter64
   MAX-ACCESS  read-only
   STATUS      current
   DESCRIPTION
      "Path: swPort.performance.d7Performance.ifOutNUcastPkts

       64 bit unsigned wrappable counter."
   ::= {pr1645v2EthPrtSwF2D7InPEntry 201326592}

pr1645v2EthPrtSwF2D7InPIfOutBCPkts OBJECT-TYPE
   SYNTAX      Counter64
   MAX-ACCESS  read-only
   STATUS      current
   DESCRIPTION
      "Path: swPort.performance.d7Performance.ifOutBcastPkts

       64 bit unsigned wrappable counter."
   ::= {pr1645v2EthPrtSwF2D7InPEntry 452984832}

pr1645v2EthPrtSwF2D7InPIfOutMCPkts OBJECT-TYPE
   SYNTAX      Counter64
   MAX-ACCESS  read-only
   STATUS      current
   DESCRIPTION
      "Path: swPort.performance.d7Performance.ifOutMcastPkts

       64 bit unsigned wrappable counter."
   ::= {pr1645v2EthPrtSwF2D7InPEntry 469762048}

pr1645v2EthPrtSwF2D7InPIfOutDiscards OBJECT-TYPE
   SYNTAX      Counter64
   MAX-ACCESS  read-only
   STATUS      current
   DESCRIPTION
      "Path: swPort.performance.d7Performance.ifOutDiscards

       64 bit unsigned wrappable counter."
   ::= {pr1645v2EthPrtSwF2D7InPEntry 218103808}

pr1645v2EthPrtSwF2D7InPIfOutErrors OBJECT-TYPE
   SYNTAX      Counter64
   MAX-ACCESS  read-only
   STATUS      current
   DESCRIPTION
      "Path: swPort.performance.d7Performance.ifOutErrors

       64 bit unsigned wrappable counter."
   ::= {pr1645v2EthPrtSwF2D7InPEntry 234881024}

pr1645v2EthPrtSwF2D7InPOutDropEx OBJECT-TYPE
   SYNTAX      Counter64
   MAX-ACCESS  read-only
   STATUS      current
   DESCRIPTION
      "Path: swPort.performance.d7Performance.ifOutDropLevelExceeded

       64 bit unsigned wrappable counter."
   ::= {pr1645v2EthPrtSwF2D7InPEntry 352321536}

pr1645v2EthPrtSwF2D7InPOutDropNoArp OBJECT-TYPE
   SYNTAX      Counter64
   MAX-ACCESS  read-only
   STATUS      current
   DESCRIPTION
      "Path: swPort.performance.d7Performance.ifOutDiscardsNoArp

       64 bit unsigned wrappable counter."
   ::= {pr1645v2EthPrtSwF2D7InPEntry 369098752}

pr1645v2EthPrtSwF2D7InPOutDropFilter OBJECT-TYPE
   SYNTAX      Counter64
   MAX-ACCESS  read-only
   STATUS      current
   DESCRIPTION
      "Path: swPort.performance.d7Performance.ifOutDiscardsFilter

       64 bit unsigned wrappable counter."
   ::= {pr1645v2EthPrtSwF2D7InPEntry 402653184}

pr1645v2EthPrtSwF2D7InPIfOutBandwidth OBJECT-TYPE
   SYNTAX      Integer32
   MAX-ACCESS  read-only
   STATUS      current
   DESCRIPTION
      "Path: swPort.performance.d7Performance.ifOutBandwidth

       unit name = bps
       formula = 8 * ; 8 /"
   ::= {pr1645v2EthPrtSwF2D7InPEntry 285212672}

pr1645v2EthPrtSwF2D7InPIfErrSec OBJECT-TYPE
   SYNTAX      Counter32
   MAX-ACCESS  read-only
   STATUS      current
   DESCRIPTION
      "Path: swPort.performance.d7Performance.ifErrSec

       32 bit unsigned wrappable counter."
   ::= {pr1645v2EthPrtSwF2D7InPEntry 251658240}


pr1645v2EthPrtSwF2Oam OBJECT IDENTIFIER ::= {pr1645v2EthPrtSwF2 910}

pr1645v2EthPrtSwF2OamSSCTable OBJECT-TYPE
   SYNTAX      SEQUENCE OF Pr1645v2EthPrtSwF2OamEntry
   MAX-ACCESS  not-accessible
   STATUS      current
   DESCRIPTION
      "OAM statistics"
   ::= {pr1645v2EthPrtSwF2Oam 1}

pr1645v2EthPrtSwF2OamEntry OBJECT-TYPE
   SYNTAX      Pr1645v2EthPrtSwF2OamEntry
   MAX-ACCESS  not-accessible
   STATUS      current
   DESCRIPTION
      ""
   INDEX      { pr1645v2EthPrtSwF2OamGlobalIx }
   ::= {pr1645v2EthPrtSwF2OamSSCTable 1}

Pr1645v2EthPrtSwF2OamEntry ::=
   SEQUENCE
      {
      pr1645v2EthPrtSwF2OamGlobalIx
         GlobalIndex,
      pr1645v2EthPrtSwF2OamInformationTx
         Counter32,
      pr1645v2EthPrtSwF2OamInformationRx
         Counter32,
      pr1645v2EthPrtSwF2OamUniqueEventNotifTx
         Counter32,
      pr1645v2EthPrtSwF2OamUniqueEventNotifRx
         Counter32,
      pr1645v2EthPrtSwF2OamLoopbackCtrlTx
         Counter32,
      pr1645v2EthPrtSwF2OamLoopbackCtrlRx
         Counter32,
      pr1645v2EthPrtSwF2OamVarReqTx
         Counter32,
      pr1645v2EthPrtSwF2OamVarReqRx
         Counter32,
      pr1645v2EthPrtSwF2OamVarRespTx
         Counter32,
      pr1645v2EthPrtSwF2OamVarRespRx
         Counter32,
      pr1645v2EthPrtSwF2OamOrgSpecificTx
         Counter32,
      pr1645v2EthPrtSwF2OamOrgSpecificRx
         Counter32,
      pr1645v2EthPrtSwF2OamUnsupportedCodesTx
         Counter32,
      pr1645v2EthPrtSwF2OamUnsupportedCodesRx
         Counter32,
      pr1645v2EthPrtSwF2OamPduDiscardRx
         Counter32,
      pr1645v2EthPrtSwF2OamDataDiscardTx
         Counter32,
      pr1645v2EthPrtSwF2OamDataDiscardRx
         Counter32
      }

pr1645v2EthPrtSwF2OamGlobalIx OBJECT-TYPE
   SYNTAX      GlobalIndex
   MAX-ACCESS  not-accessible
   STATUS      current
   DESCRIPTION
      "The value of the tlsCntTreeGlobalIndex of the MANAGED OBJECT."
   ::= {pr1645v2EthPrtSwF2OamEntry 10}

pr1645v2EthPrtSwF2OamInformationTx OBJECT-TYPE
   SYNTAX      Counter32
   MAX-ACCESS  read-only
   STATUS      current
   DESCRIPTION
      "Path: swPort.performance.oam.informationTx

       32 bit unsigned wrappable counter."
   ::= {pr1645v2EthPrtSwF2OamEntry 16777216}

pr1645v2EthPrtSwF2OamInformationRx OBJECT-TYPE
   SYNTAX      Counter32
   MAX-ACCESS  read-only
   STATUS      current
   DESCRIPTION
      "Path: swPort.performance.oam.informationRx

       32 bit unsigned wrappable counter."
   ::= {pr1645v2EthPrtSwF2OamEntry 33554432}

pr1645v2EthPrtSwF2OamUniqueEventNotifTx OBJECT-TYPE
   SYNTAX      Counter32
   MAX-ACCESS  read-only
   STATUS      current
   DESCRIPTION
      "Path: swPort.performance.oam.uniqueEventNotifTx

       32 bit unsigned wrappable counter."
   ::= {pr1645v2EthPrtSwF2OamEntry 50331648}

pr1645v2EthPrtSwF2OamUniqueEventNotifRx OBJECT-TYPE
   SYNTAX      Counter32
   MAX-ACCESS  read-only
   STATUS      current
   DESCRIPTION
      "Path: swPort.performance.oam.uniqueEventNotifRx

       32 bit unsigned wrappable counter."
   ::= {pr1645v2EthPrtSwF2OamEntry 67108864}

pr1645v2EthPrtSwF2OamLoopbackCtrlTx OBJECT-TYPE
   SYNTAX      Counter32
   MAX-ACCESS  read-only
   STATUS      current
   DESCRIPTION
      "Path: swPort.performance.oam.loopbackCtrlTx

       32 bit unsigned wrappable counter."
   ::= {pr1645v2EthPrtSwF2OamEntry 117440512}

pr1645v2EthPrtSwF2OamLoopbackCtrlRx OBJECT-TYPE
   SYNTAX      Counter32
   MAX-ACCESS  read-only
   STATUS      current
   DESCRIPTION
      "Path: swPort.performance.oam.loopbackCtrlRx

       32 bit unsigned wrappable counter."
   ::= {pr1645v2EthPrtSwF2OamEntry 134217728}

pr1645v2EthPrtSwF2OamVarReqTx OBJECT-TYPE
   SYNTAX      Counter32
   MAX-ACCESS  read-only
   STATUS      current
   DESCRIPTION
      "Path: swPort.performance.oam.varReqTx

       32 bit unsigned wrappable counter."
   ::= {pr1645v2EthPrtSwF2OamEntry 150994944}

pr1645v2EthPrtSwF2OamVarReqRx OBJECT-TYPE
   SYNTAX      Counter32
   MAX-ACCESS  read-only
   STATUS      current
   DESCRIPTION
      "Path: swPort.performance.oam.varReqRx

       32 bit unsigned wrappable counter."
   ::= {pr1645v2EthPrtSwF2OamEntry 167772160}

pr1645v2EthPrtSwF2OamVarRespTx OBJECT-TYPE
   SYNTAX      Counter32
   MAX-ACCESS  read-only
   STATUS      current
   DESCRIPTION
      "Path: swPort.performance.oam.varRespTx

       32 bit unsigned wrappable counter."
   ::= {pr1645v2EthPrtSwF2OamEntry 184549376}

pr1645v2EthPrtSwF2OamVarRespRx OBJECT-TYPE
   SYNTAX      Counter32
   MAX-ACCESS  read-only
   STATUS      current
   DESCRIPTION
      "Path: swPort.performance.oam.varRespRx

       32 bit unsigned wrappable counter."
   ::= {pr1645v2EthPrtSwF2OamEntry 201326592}

pr1645v2EthPrtSwF2OamOrgSpecificTx OBJECT-TYPE
   SYNTAX      Counter32
   MAX-ACCESS  read-only
   STATUS      current
   DESCRIPTION
      "Path: swPort.performance.oam.orgSpecificTx

       32 bit unsigned wrappable counter."
   ::= {pr1645v2EthPrtSwF2OamEntry 218103808}

pr1645v2EthPrtSwF2OamOrgSpecificRx OBJECT-TYPE
   SYNTAX      Counter32
   MAX-ACCESS  read-only
   STATUS      current
   DESCRIPTION
      "Path: swPort.performance.oam.orgSpecificRx

       32 bit unsigned wrappable counter."
   ::= {pr1645v2EthPrtSwF2OamEntry 234881024}

pr1645v2EthPrtSwF2OamUnsupportedCodesTx OBJECT-TYPE
   SYNTAX      Counter32
   MAX-ACCESS  read-only
   STATUS      current
   DESCRIPTION
      "Path: swPort.performance.oam.unsupportedCodesTx

       32 bit unsigned wrappable counter."
   ::= {pr1645v2EthPrtSwF2OamEntry 251658240}

pr1645v2EthPrtSwF2OamUnsupportedCodesRx OBJECT-TYPE
   SYNTAX      Counter32
   MAX-ACCESS  read-only
   STATUS      current
   DESCRIPTION
      "Path: swPort.performance.oam.unsupportedCodesRx

       32 bit unsigned wrappable counter."
   ::= {pr1645v2EthPrtSwF2OamEntry 268435456}

pr1645v2EthPrtSwF2OamPduDiscardRx OBJECT-TYPE
   SYNTAX      Counter32
   MAX-ACCESS  read-only
   STATUS      current
   DESCRIPTION
      "Path: swPort.performance.oam.pduDiscardRx

       32 bit unsigned wrappable counter."
   ::= {pr1645v2EthPrtSwF2OamEntry 1694498816}

pr1645v2EthPrtSwF2OamDataDiscardTx OBJECT-TYPE
   SYNTAX      Counter32
   MAX-ACCESS  read-only
   STATUS      current
   DESCRIPTION
      "Path: swPort.performance.oam.dataDiscardTx

       32 bit unsigned wrappable counter."
   ::= {pr1645v2EthPrtSwF2OamEntry 1711276032}

pr1645v2EthPrtSwF2OamDataDiscardRx OBJECT-TYPE
   SYNTAX      Counter32
   MAX-ACCESS  read-only
   STATUS      current
   DESCRIPTION
      "Path: swPort.performance.oam.dataDiscardRx

       32 bit unsigned wrappable counter."
   ::= {pr1645v2EthPrtSwF2OamEntry 1728053248}


pr1645v2EthPrtSwF2Vlan OBJECT IDENTIFIER ::= {pr1645v2EthPrtSwF2 310}

pr1645v2EthPrtSwF2VlanSSCTable OBJECT-TYPE
   SYNTAX      SEQUENCE OF Pr1645v2EthPrtSwF2VlanEntry
   MAX-ACCESS  not-accessible
   STATUS      current
   DESCRIPTION
      ""
   ::= {pr1645v2EthPrtSwF2Vlan 1}

pr1645v2EthPrtSwF2VlanEntry OBJECT-TYPE
   SYNTAX      Pr1645v2EthPrtSwF2VlanEntry
   MAX-ACCESS  not-accessible
   STATUS      current
   DESCRIPTION
      ""
   INDEX      { pr1645v2EthPrtSwF2VlanGlobalIx,
                pr1645v2EthPrtSwF2VlanTableIx }
   ::= {pr1645v2EthPrtSwF2VlanSSCTable 1}

Pr1645v2EthPrtSwF2VlanEntry ::=
   SEQUENCE
      {
      pr1645v2EthPrtSwF2VlanGlobalIx
         GlobalIndex,
      pr1645v2EthPrtSwF2VlanTableIx
         TableIndex,
      pr1645v2EthPrtSwF2VlanName
         DisplayString,
      pr1645v2EthPrtSwF2VlanMCInOctets
         Counter64,
      pr1645v2EthPrtSwF2VlanMCInUcast
         Counter64,
      pr1645v2EthPrtSwF2VlanMCInNUcastPkts
         Counter64,
      pr1645v2EthPrtSwF2VlanMCInBcastPkts
         Counter64,
      pr1645v2EthPrtSwF2VlanMCInMcastPkts
         Counter64,
      pr1645v2EthPrtSwF2VlanMCInDiscards
         Counter64,
      pr1645v2EthPrtSwF2VlanMCInErrors
         Counter64,
      pr1645v2EthPrtSwF2VlanMCInUnknownProtos
         Counter64,
      pr1645v2EthPrtSwF2VlanMCInDropEx
         Counter64,
      pr1645v2EthPrtSwF2VlanMCInDropNoMac
         Counter64,
      pr1645v2EthPrtSwF2VlanMCInDropNUCast
         Counter64,
      pr1645v2EthPrtSwF2VlanMCInDropFilter
         Counter64,
      pr1645v2EthPrtSwF2VlanMCInBandwidth15sec
         Integer32,
      pr1645v2EthPrtSwF2VlanMCInBandwidth30sec
         Integer32,
      pr1645v2EthPrtSwF2VlanMCInBandwidth1min
         Integer32,
      pr1645v2EthPrtSwF2VlanMCInBandwidth2min
         Integer32,
      pr1645v2EthPrtSwF2VlanMCInBandwidth5min
         Integer32,
      pr1645v2EthPrtSwF2VlanMCOutOctets
         Counter64,
      pr1645v2EthPrtSwF2VlanMCOutUcastPkts
         Counter64,
      pr1645v2EthPrtSwF2VlanMCOutNUcastPkts
         Counter64,
      pr1645v2EthPrtSwF2VlanMCOutBcastPkts
         Counter64,
      pr1645v2EthPrtSwF2VlanMCOutMcastPkts
         Counter64,
      pr1645v2EthPrtSwF2VlanMCOutDiscards
         Counter64,
      pr1645v2EthPrtSwF2VlanMCOutErrors
         Counter64,
      pr1645v2EthPrtSwF2VlanMCOutQLen
         Counter32,
      pr1645v2EthPrtSwF2VlanMCOutDropEx
         Counter64,
      pr1645v2EthPrtSwF2VlanMCOutDropNoArp
         Counter64,
      pr1645v2EthPrtSwF2VlanMCOutDropFilter
         Counter64,
      pr1645v2EthPrtSwF2VlanMCOutBandwidth15sec
         Integer32,
      pr1645v2EthPrtSwF2VlanMCOutBandwidth30sec
         Integer32,
      pr1645v2EthPrtSwF2VlanMCOutBandwidth1min
         Integer32,
      pr1645v2EthPrtSwF2VlanMCOutBandwidth2min
         Integer32,
      pr1645v2EthPrtSwF2VlanMCOutBandwidth5min
         Integer32,
      pr1645v2EthPrtSwF2VlanVlanVid
         Integer32,
      pr1645v2EthPrtSwF2VlanPppLinkMonitoringRequestsSent
         Gauge32,
      pr1645v2EthPrtSwF2VlanPppLinkMonitoringRepliesRcvd
         Gauge32,
      pr1645v2EthPrtSwF2VlanPppLinkMonitoringRequestsRcvd
         Gauge32,
      pr1645v2EthPrtSwF2VlanPppLinkMonitoringRepliesSent
         Gauge32
      }

pr1645v2EthPrtSwF2VlanGlobalIx OBJECT-TYPE
   SYNTAX      GlobalIndex
   MAX-ACCESS  not-accessible
   STATUS      current
   DESCRIPTION
      "The value of the tlsCntTreeGlobalIndex of the MANAGED OBJECT."
   ::= {pr1645v2EthPrtSwF2VlanEntry 10}

pr1645v2EthPrtSwF2VlanTableIx OBJECT-TYPE
   SYNTAX      TableIndex
   MAX-ACCESS  not-accessible
   STATUS      current
   DESCRIPTION
      ""
   ::= {pr1645v2EthPrtSwF2VlanEntry 11}

pr1645v2EthPrtSwF2VlanName OBJECT-TYPE
   SYNTAX      DisplayString
   MAX-ACCESS  read-only
   STATUS      current
   DESCRIPTION
      "Path: swPort.performance.vlan.name"
   ::= {pr1645v2EthPrtSwF2VlanEntry 16777216}

pr1645v2EthPrtSwF2VlanMCInOctets OBJECT-TYPE
   SYNTAX      Counter64
   MAX-ACCESS  read-only
   STATUS      current
   DESCRIPTION
      "Path: swPort.performance.vlan.mibCounters.ifInOctets

       64 bit unsigned wrappable counter."
   ::= {pr1645v2EthPrtSwF2VlanEntry 40697856}

pr1645v2EthPrtSwF2VlanMCInUcast OBJECT-TYPE
   SYNTAX      Counter64
   MAX-ACCESS  read-only
   STATUS      current
   DESCRIPTION
      "Path: swPort.performance.vlan.mibCounters.ifInUcastPkts

       64 bit unsigned wrappable counter."
   ::= {pr1645v2EthPrtSwF2VlanEntry 40763392}

pr1645v2EthPrtSwF2VlanMCInNUcastPkts OBJECT-TYPE
   SYNTAX      Counter64
   MAX-ACCESS  read-only
   STATUS      current
   DESCRIPTION
      "Path: swPort.performance.vlan.mibCounters.ifInNUcastPkts

       64 bit unsigned wrappable counter."
   ::= {pr1645v2EthPrtSwF2VlanEntry 40828928}

pr1645v2EthPrtSwF2VlanMCInBcastPkts OBJECT-TYPE
   SYNTAX      Counter64
   MAX-ACCESS  read-only
   STATUS      current
   DESCRIPTION
      "Path: swPort.performance.vlan.mibCounters.ifInBcastPkts

       64 bit unsigned wrappable counter."
   ::= {pr1645v2EthPrtSwF2VlanEntry 47382528}

pr1645v2EthPrtSwF2VlanMCInMcastPkts OBJECT-TYPE
   SYNTAX      Counter64
   MAX-ACCESS  read-only
   STATUS      current
   DESCRIPTION
      "Path: swPort.performance.vlan.mibCounters.ifInMcastPkts

       64 bit unsigned wrappable counter."
   ::= {pr1645v2EthPrtSwF2VlanEntry 48037888}

pr1645v2EthPrtSwF2VlanMCInDiscards OBJECT-TYPE
   SYNTAX      Counter64
   MAX-ACCESS  read-only
   STATUS      current
   DESCRIPTION
      "Path: swPort.performance.vlan.mibCounters.ifInDiscards

       64 bit unsigned wrappable counter."
   ::= {pr1645v2EthPrtSwF2VlanEntry 40894464}

pr1645v2EthPrtSwF2VlanMCInErrors OBJECT-TYPE
   SYNTAX      Counter64
   MAX-ACCESS  read-only
   STATUS      current
   DESCRIPTION
      "Path: swPort.performance.vlan.mibCounters.ifInErrors

       64 bit unsigned wrappable counter."
   ::= {pr1645v2EthPrtSwF2VlanEntry 40960000}

pr1645v2EthPrtSwF2VlanMCInUnknownProtos OBJECT-TYPE
   SYNTAX      Counter64
   MAX-ACCESS  read-only
   STATUS      current
   DESCRIPTION
      "Path: swPort.performance.vlan.mibCounters.ifInUnknownProtos

       64 bit unsigned wrappable counter."
   ::= {pr1645v2EthPrtSwF2VlanEntry 41025536}

pr1645v2EthPrtSwF2VlanMCInDropEx OBJECT-TYPE
   SYNTAX      Counter64
   MAX-ACCESS  read-only
   STATUS      current
   DESCRIPTION
      "Path: swPort.performance.vlan.mibCounters.ifInDropLevelExceeded

       64 bit unsigned wrappable counter."
   ::= {pr1645v2EthPrtSwF2VlanEntry 42074112}

pr1645v2EthPrtSwF2VlanMCInDropNoMac OBJECT-TYPE
   SYNTAX      Counter64
   MAX-ACCESS  read-only
   STATUS      current
   DESCRIPTION
      "Path: swPort.performance.vlan.mibCounters.ifInDiscardsNoMacFit

       64 bit unsigned wrappable counter."
   ::= {pr1645v2EthPrtSwF2VlanEntry 42270720}

pr1645v2EthPrtSwF2VlanMCInDropNUCast OBJECT-TYPE
   SYNTAX      Counter64
   MAX-ACCESS  read-only
   STATUS      current
   DESCRIPTION
      "Path: swPort.performance.vlan.mibCounters.ifInDiscardsNUCast

       64 bit unsigned wrappable counter."
   ::= {pr1645v2EthPrtSwF2VlanEntry 42467328}

pr1645v2EthPrtSwF2VlanMCInDropFilter OBJECT-TYPE
   SYNTAX      Counter64
   MAX-ACCESS  read-only
   STATUS      current
   DESCRIPTION
      "Path: swPort.performance.vlan.mibCounters.ifInDiscardsFilter

       64 bit unsigned wrappable counter."
   ::= {pr1645v2EthPrtSwF2VlanEntry 42532864}

pr1645v2EthPrtSwF2VlanMCInBandwidth15sec OBJECT-TYPE
   SYNTAX      Integer32
   MAX-ACCESS  read-only
   STATUS      current
   DESCRIPTION
      "Path: swPort.performance.vlan.mibCounters.ifInBandwidth.15sec

       unit name = bps
       formula = 8 * ; 8 /"
   ::= {pr1645v2EthPrtSwF2VlanEntry 45417728}

pr1645v2EthPrtSwF2VlanMCInBandwidth30sec OBJECT-TYPE
   SYNTAX      Integer32
   MAX-ACCESS  read-only
   STATUS      current
   DESCRIPTION
      "Path: swPort.performance.vlan.mibCounters.ifInBandwidth.30sec

       unit name = bps
       formula = 8 * ; 8 /"
   ::= {pr1645v2EthPrtSwF2VlanEntry 45419008}

pr1645v2EthPrtSwF2VlanMCInBandwidth1min OBJECT-TYPE
   SYNTAX      Integer32
   MAX-ACCESS  read-only
   STATUS      current
   DESCRIPTION
      "Path: swPort.performance.vlan.mibCounters.ifInBandwidth.1min

       unit name = bps
       formula = 8 * ; 8 /"
   ::= {pr1645v2EthPrtSwF2VlanEntry 45421568}

pr1645v2EthPrtSwF2VlanMCInBandwidth2min OBJECT-TYPE
   SYNTAX      Integer32
   MAX-ACCESS  read-only
   STATUS      current
   DESCRIPTION
      "Path: swPort.performance.vlan.mibCounters.ifInBandwidth.2min

       unit name = bps
       formula = 8 * ; 8 /"
   ::= {pr1645v2EthPrtSwF2VlanEntry 45426688}

pr1645v2EthPrtSwF2VlanMCInBandwidth5min OBJECT-TYPE
   SYNTAX      Integer32
   MAX-ACCESS  read-only
   STATUS      current
   DESCRIPTION
      "Path: swPort.performance.vlan.mibCounters.ifInBandwidth.5min

       unit name = bps
       formula = 8 * ; 8 /"
   ::= {pr1645v2EthPrtSwF2VlanEntry 45442048}

pr1645v2EthPrtSwF2VlanMCOutOctets OBJECT-TYPE
   SYNTAX      Counter64
   MAX-ACCESS  read-only
   STATUS      current
   DESCRIPTION
      "Path: swPort.performance.vlan.mibCounters.ifOutOctets

       64 bit unsigned wrappable counter."
   ::= {pr1645v2EthPrtSwF2VlanEntry 41091072}

pr1645v2EthPrtSwF2VlanMCOutUcastPkts OBJECT-TYPE
   SYNTAX      Counter64
   MAX-ACCESS  read-only
   STATUS      current
   DESCRIPTION
      "Path: swPort.performance.vlan.mibCounters.ifOutUcastPkts

       64 bit unsigned wrappable counter."
   ::= {pr1645v2EthPrtSwF2VlanEntry 41156608}

pr1645v2EthPrtSwF2VlanMCOutNUcastPkts OBJECT-TYPE
   SYNTAX      Counter64
   MAX-ACCESS  read-only
   STATUS      current
   DESCRIPTION
      "Path: swPort.performance.vlan.mibCounters.ifOutNUcastPkts

       64 bit unsigned wrappable counter."
   ::= {pr1645v2EthPrtSwF2VlanEntry 41222144}

pr1645v2EthPrtSwF2VlanMCOutBcastPkts OBJECT-TYPE
   SYNTAX      Counter64
   MAX-ACCESS  read-only
   STATUS      current
   DESCRIPTION
      "Path: swPort.performance.vlan.mibCounters.ifOutBcastPkts

       64 bit unsigned wrappable counter."
   ::= {pr1645v2EthPrtSwF2VlanEntry 47775744}

pr1645v2EthPrtSwF2VlanMCOutMcastPkts OBJECT-TYPE
   SYNTAX      Counter64
   MAX-ACCESS  read-only
   STATUS      current
   DESCRIPTION
      "Path: swPort.performance.vlan.mibCounters.ifOutMcastPkts

       64 bit unsigned wrappable counter."
   ::= {pr1645v2EthPrtSwF2VlanEntry 48431104}

pr1645v2EthPrtSwF2VlanMCOutDiscards OBJECT-TYPE
   SYNTAX      Counter64
   MAX-ACCESS  read-only
   STATUS      current
   DESCRIPTION
      "Path: swPort.performance.vlan.mibCounters.ifOutDiscards

       64 bit unsigned wrappable counter."
   ::= {pr1645v2EthPrtSwF2VlanEntry 41287680}

pr1645v2EthPrtSwF2VlanMCOutErrors OBJECT-TYPE
   SYNTAX      Counter64
   MAX-ACCESS  read-only
   STATUS      current
   DESCRIPTION
      "Path: swPort.performance.vlan.mibCounters.ifOutErrors

       64 bit unsigned wrappable counter."
   ::= {pr1645v2EthPrtSwF2VlanEntry 41353216}

pr1645v2EthPrtSwF2VlanMCOutQLen OBJECT-TYPE
   SYNTAX      Counter32
   MAX-ACCESS  read-only
   STATUS      current
   DESCRIPTION
      "Path: swPort.performance.vlan.mibCounters.ifOutQLen

       32 bit unsigned wrappable counter."
   ::= {pr1645v2EthPrtSwF2VlanEntry 41418752}

pr1645v2EthPrtSwF2VlanMCOutDropEx OBJECT-TYPE
   SYNTAX      Counter64
   MAX-ACCESS  read-only
   STATUS      current
   DESCRIPTION
      "Path: swPort.performance.vlan.mibCounters.ifOutDropLevelExceeded

       64 bit unsigned wrappable counter."
   ::= {pr1645v2EthPrtSwF2VlanEntry 41484288}

pr1645v2EthPrtSwF2VlanMCOutDropNoArp OBJECT-TYPE
   SYNTAX      Counter64
   MAX-ACCESS  read-only
   STATUS      current
   DESCRIPTION
      "Path: swPort.performance.vlan.mibCounters.ifOutDiscardsNoArp

       64 bit unsigned wrappable counter."
   ::= {pr1645v2EthPrtSwF2VlanEntry 42336256}

pr1645v2EthPrtSwF2VlanMCOutDropFilter OBJECT-TYPE
   SYNTAX      Counter64
   MAX-ACCESS  read-only
   STATUS      current
   DESCRIPTION
      "Path: swPort.performance.vlan.mibCounters.ifOutDiscardsFilter

       64 bit unsigned wrappable counter."
   ::= {pr1645v2EthPrtSwF2VlanEntry 42598400}

pr1645v2EthPrtSwF2VlanMCOutBandwidth15sec OBJECT-TYPE
   SYNTAX      Integer32
   MAX-ACCESS  read-only
   STATUS      current
   DESCRIPTION
      "Path: swPort.performance.vlan.mibCounters.ifOutBandwidth.15sec

       unit name = bps
       formula = 8 * ; 8 /"
   ::= {pr1645v2EthPrtSwF2VlanEntry 45483264}

pr1645v2EthPrtSwF2VlanMCOutBandwidth30sec OBJECT-TYPE
   SYNTAX      Integer32
   MAX-ACCESS  read-only
   STATUS      current
   DESCRIPTION
      "Path: swPort.performance.vlan.mibCounters.ifOutBandwidth.30sec

       unit name = bps
       formula = 8 * ; 8 /"
   ::= {pr1645v2EthPrtSwF2VlanEntry 45484544}

pr1645v2EthPrtSwF2VlanMCOutBandwidth1min OBJECT-TYPE
   SYNTAX      Integer32
   MAX-ACCESS  read-only
   STATUS      current
   DESCRIPTION
      "Path: swPort.performance.vlan.mibCounters.ifOutBandwidth.1min

       unit name = bps
       formula = 8 * ; 8 /"
   ::= {pr1645v2EthPrtSwF2VlanEntry 45487104}

pr1645v2EthPrtSwF2VlanMCOutBandwidth2min OBJECT-TYPE
   SYNTAX      Integer32
   MAX-ACCESS  read-only
   STATUS      current
   DESCRIPTION
      "Path: swPort.performance.vlan.mibCounters.ifOutBandwidth.2min

       unit name = bps
       formula = 8 * ; 8 /"
   ::= {pr1645v2EthPrtSwF2VlanEntry 45492224}

pr1645v2EthPrtSwF2VlanMCOutBandwidth5min OBJECT-TYPE
   SYNTAX      Integer32
   MAX-ACCESS  read-only
   STATUS      current
   DESCRIPTION
      "Path: swPort.performance.vlan.mibCounters.ifOutBandwidth.5min

       unit name = bps
       formula = 8 * ; 8 /"
   ::= {pr1645v2EthPrtSwF2VlanEntry 45507584}

pr1645v2EthPrtSwF2VlanVlanVid OBJECT-TYPE
   SYNTAX      Integer32
   MAX-ACCESS  read-only
   STATUS      current
   DESCRIPTION
      "Path: swPort.performance.vlan.vlan.vid"
   ::= {pr1645v2EthPrtSwF2VlanEntry 234946560}

pr1645v2EthPrtSwF2VlanPppLinkMonitoringRequestsSent OBJECT-TYPE
   SYNTAX      Gauge32
   MAX-ACCESS  read-only
   STATUS      current
   DESCRIPTION
      "Path: swPort.performance.vlan.ppp.linkMonitoring.requestsSent

       32 bit unsigned gauge value."
   ::= {pr1645v2EthPrtSwF2VlanEntry 50397440}

pr1645v2EthPrtSwF2VlanPppLinkMonitoringRepliesRcvd OBJECT-TYPE
   SYNTAX      Gauge32
   MAX-ACCESS  read-only
   STATUS      current
   DESCRIPTION
      "Path: swPort.performance.vlan.ppp.linkMonitoring.repliesRcvd

       32 bit unsigned gauge value."
   ::= {pr1645v2EthPrtSwF2VlanEntry 50397696}

pr1645v2EthPrtSwF2VlanPppLinkMonitoringRequestsRcvd OBJECT-TYPE
   SYNTAX      Gauge32
   MAX-ACCESS  read-only
   STATUS      current
   DESCRIPTION
      "Path: swPort.performance.vlan.ppp.linkMonitoring.requestsRcvd

       32 bit unsigned gauge value."
   ::= {pr1645v2EthPrtSwF2VlanEntry 50397952}

pr1645v2EthPrtSwF2VlanPppLinkMonitoringRepliesSent OBJECT-TYPE
   SYNTAX      Gauge32
   MAX-ACCESS  read-only
   STATUS      current
   DESCRIPTION
      "Path: swPort.performance.vlan.ppp.linkMonitoring.repliesSent

       32 bit unsigned gauge value."
   ::= {pr1645v2EthPrtSwF2VlanEntry 50398208}

pr1645v2EthPrtSwF2VlanMCH2P OBJECT-TYPE
   SYNTAX      SEQUENCE OF Pr1645v2EthPrtSwF2VlanMCH2PEntry
   MAX-ACCESS  not-accessible
   STATUS      current
   DESCRIPTION
      ""
   ::= {pr1645v2EthPrtSwF2Vlan 41549824}

pr1645v2EthPrtSwF2VlanMCH2PEntry OBJECT-TYPE
   SYNTAX      Pr1645v2EthPrtSwF2VlanMCH2PEntry
   MAX-ACCESS  not-accessible
   STATUS      current
   DESCRIPTION
      ""
   INDEX      { pr1645v2EthPrtSwF2VlanMCH2PGlobalIx,
                pr1645v2EthPrtSwF2VlanTableIx,
                pr1645v2EthPrtSwF2VlanMCH2PTableIx }
   ::= {pr1645v2EthPrtSwF2VlanMCH2P 1}

Pr1645v2EthPrtSwF2VlanMCH2PEntry ::=
   SEQUENCE
      {
      pr1645v2EthPrtSwF2VlanMCH2PGlobalIx
         GlobalIndex,
      pr1645v2EthPrtSwF2VlanMCH2PTableIx
         TableIndex,
      pr1645v2EthPrtSwF2VlanMCH2PSysUpTime
         TimeTicks,
      pr1645v2EthPrtSwF2VlanMCH2PIfUpTime
         TimeTicks,
      pr1645v2EthPrtSwF2VlanMCH2PIfStatChanges
         Counter32,
      pr1645v2EthPrtSwF2VlanMCH2PIfInOctets
         Counter64,
      pr1645v2EthPrtSwF2VlanMCH2PIfInUCPkts
         Counter64,
      pr1645v2EthPrtSwF2VlanMCH2PIfInNUCPkts
         Counter64,
      pr1645v2EthPrtSwF2VlanMCH2PIfInBCPkts
         Counter64,
      pr1645v2EthPrtSwF2VlanMCH2PIfInMCPkts
         Counter64,
      pr1645v2EthPrtSwF2VlanMCH2PIfInDiscards
         Counter64,
      pr1645v2EthPrtSwF2VlanMCH2PIfInErrors
         Counter64,
      pr1645v2EthPrtSwF2VlanMCH2PIfInUnkwn
         Counter64,
      pr1645v2EthPrtSwF2VlanMCH2PInDropEx
         Counter64,
      pr1645v2EthPrtSwF2VlanMCH2PInDropNoMac
         Counter64,
      pr1645v2EthPrtSwF2VlanMCH2PInDropNUCast
         Counter64,
      pr1645v2EthPrtSwF2VlanMCH2PInDropFilter
         Counter64,
      pr1645v2EthPrtSwF2VlanMCH2PIfInBandwidth
         Integer32,
      pr1645v2EthPrtSwF2VlanMCH2PIfOutOctets
         Counter64,
      pr1645v2EthPrtSwF2VlanMCH2PIfOutUCPkts
         Counter64,
      pr1645v2EthPrtSwF2VlanMCH2PIfOutNUCPkts
         Counter64,
      pr1645v2EthPrtSwF2VlanMCH2PIfOutBCPkts
         Counter64,
      pr1645v2EthPrtSwF2VlanMCH2PIfOutMCPkts
         Counter64,
      pr1645v2EthPrtSwF2VlanMCH2PIfOutDiscards
         Counter64,
      pr1645v2EthPrtSwF2VlanMCH2PIfOutErrors
         Counter64,
      pr1645v2EthPrtSwF2VlanMCH2POutDropEx
         Counter64,
      pr1645v2EthPrtSwF2VlanMCH2POutDropNoArp
         Counter64,
      pr1645v2EthPrtSwF2VlanMCH2POutDropFilter
         Counter64,
      pr1645v2EthPrtSwF2VlanMCH2PIfOutBandwidth
         Integer32,
      pr1645v2EthPrtSwF2VlanMCH2PIfErrSec
         Counter32
      }

pr1645v2EthPrtSwF2VlanMCH2PGlobalIx OBJECT-TYPE
   SYNTAX      GlobalIndex
   MAX-ACCESS  not-accessible
   STATUS      current
   DESCRIPTION
      "The value of the tlsCntTreeGlobalIndex of the MANAGED OBJECT."
   ::= {pr1645v2EthPrtSwF2VlanMCH2PEntry 10}

pr1645v2EthPrtSwF2VlanMCH2PTableIx OBJECT-TYPE
   SYNTAX      TableIndex
   MAX-ACCESS  not-accessible
   STATUS      current
   DESCRIPTION
      ""
   ::= {pr1645v2EthPrtSwF2VlanMCH2PEntry 11}

pr1645v2EthPrtSwF2VlanMCH2PSysUpTime OBJECT-TYPE
   SYNTAX      TimeTicks
   MAX-ACCESS  read-only
   STATUS      current
   DESCRIPTION
      "Path: swPort.performance.vlan.mibCounters.h2Performance.sysUpTime

       Time in centi-second."
   ::= {pr1645v2EthPrtSwF2VlanMCH2PEntry 16777216}

pr1645v2EthPrtSwF2VlanMCH2PIfUpTime OBJECT-TYPE
   SYNTAX      TimeTicks
   MAX-ACCESS  read-only
   STATUS      current
   DESCRIPTION
      "Path: swPort.performance.vlan.mibCounters.h2Performance.ifUpTime

       Time in centi-second."
   ::= {pr1645v2EthPrtSwF2VlanMCH2PEntry 33554432}

pr1645v2EthPrtSwF2VlanMCH2PIfStatChanges OBJECT-TYPE
   SYNTAX      Counter32
   MAX-ACCESS  read-only
   STATUS      current
   DESCRIPTION
      "Path: swPort.performance.vlan.mibCounters.h2Performance.ifStatusChanges

       32 bit unsigned wrappable counter."
   ::= {pr1645v2EthPrtSwF2VlanMCH2PEntry 50331648}

pr1645v2EthPrtSwF2VlanMCH2PIfInOctets OBJECT-TYPE
   SYNTAX      Counter64
   MAX-ACCESS  read-only
   STATUS      current
   DESCRIPTION
      "Path: swPort.performance.vlan.mibCounters.h2Performance.ifInOctets

       64 bit unsigned wrappable counter."
   ::= {pr1645v2EthPrtSwF2VlanMCH2PEntry 67108864}

pr1645v2EthPrtSwF2VlanMCH2PIfInUCPkts OBJECT-TYPE
   SYNTAX      Counter64
   MAX-ACCESS  read-only
   STATUS      current
   DESCRIPTION
      "Path: swPort.performance.vlan.mibCounters.h2Performance.ifInUcastPkts

       64 bit unsigned wrappable counter."
   ::= {pr1645v2EthPrtSwF2VlanMCH2PEntry 83886080}

pr1645v2EthPrtSwF2VlanMCH2PIfInNUCPkts OBJECT-TYPE
   SYNTAX      Counter64
   MAX-ACCESS  read-only
   STATUS      current
   DESCRIPTION
      "Path: swPort.performance.vlan.mibCounters.h2Performance.ifInNUcastPkts

       64 bit unsigned wrappable counter."
   ::= {pr1645v2EthPrtSwF2VlanMCH2PEntry 100663296}

pr1645v2EthPrtSwF2VlanMCH2PIfInBCPkts OBJECT-TYPE
   SYNTAX      Counter64
   MAX-ACCESS  read-only
   STATUS      current
   DESCRIPTION
      "Path: swPort.performance.vlan.mibCounters.h2Performance.ifInBcastPkts

       64 bit unsigned wrappable counter."
   ::= {pr1645v2EthPrtSwF2VlanMCH2PEntry 419430400}

pr1645v2EthPrtSwF2VlanMCH2PIfInMCPkts OBJECT-TYPE
   SYNTAX      Counter64
   MAX-ACCESS  read-only
   STATUS      current
   DESCRIPTION
      "Path: swPort.performance.vlan.mibCounters.h2Performance.ifInMcastPkts

       64 bit unsigned wrappable counter."
   ::= {pr1645v2EthPrtSwF2VlanMCH2PEntry 436207616}

pr1645v2EthPrtSwF2VlanMCH2PIfInDiscards OBJECT-TYPE
   SYNTAX      Counter64
   MAX-ACCESS  read-only
   STATUS      current
   DESCRIPTION
      "Path: swPort.performance.vlan.mibCounters.h2Performance.ifInDiscards

       64 bit unsigned wrappable counter."
   ::= {pr1645v2EthPrtSwF2VlanMCH2PEntry 117440512}

pr1645v2EthPrtSwF2VlanMCH2PIfInErrors OBJECT-TYPE
   SYNTAX      Counter64
   MAX-ACCESS  read-only
   STATUS      current
   DESCRIPTION
      "Path: swPort.performance.vlan.mibCounters.h2Performance.ifInErrors

       64 bit unsigned wrappable counter."
   ::= {pr1645v2EthPrtSwF2VlanMCH2PEntry 134217728}

pr1645v2EthPrtSwF2VlanMCH2PIfInUnkwn OBJECT-TYPE
   SYNTAX      Counter64
   MAX-ACCESS  read-only
   STATUS      current
   DESCRIPTION
      "Path: swPort.performance.vlan.mibCounters.h2Performance.ifInUnknownProtos

       64 bit unsigned wrappable counter."
   ::= {pr1645v2EthPrtSwF2VlanMCH2PEntry 150994944}

pr1645v2EthPrtSwF2VlanMCH2PInDropEx OBJECT-TYPE
   SYNTAX      Counter64
   MAX-ACCESS  read-only
   STATUS      current
   DESCRIPTION
      "Path: swPort.performance.vlan.mibCounters.h2Performance.ifInDropLevelExceeded

       64 bit unsigned wrappable counter."
   ::= {pr1645v2EthPrtSwF2VlanMCH2PEntry 335544320}

pr1645v2EthPrtSwF2VlanMCH2PInDropNoMac OBJECT-TYPE
   SYNTAX      Counter64
   MAX-ACCESS  read-only
   STATUS      current
   DESCRIPTION
      "Path: swPort.performance.vlan.mibCounters.h2Performance.fInDiscardsNoMacFit

       64 bit unsigned wrappable counter."
   ::= {pr1645v2EthPrtSwF2VlanMCH2PEntry 301989888}

pr1645v2EthPrtSwF2VlanMCH2PInDropNUCast OBJECT-TYPE
   SYNTAX      Counter64
   MAX-ACCESS  read-only
   STATUS      current
   DESCRIPTION
      "Path: swPort.performance.vlan.mibCounters.h2Performance.fInDiscardsNUCast

       64 bit unsigned wrappable counter."
   ::= {pr1645v2EthPrtSwF2VlanMCH2PEntry 318767104}

pr1645v2EthPrtSwF2VlanMCH2PInDropFilter OBJECT-TYPE
   SYNTAX      Counter64
   MAX-ACCESS  read-only
   STATUS      current
   DESCRIPTION
      "Path: swPort.performance.vlan.mibCounters.h2Performance.fInDiscardsFilter

       64 bit unsigned wrappable counter."
   ::= {pr1645v2EthPrtSwF2VlanMCH2PEntry 385875968}

pr1645v2EthPrtSwF2VlanMCH2PIfInBandwidth OBJECT-TYPE
   SYNTAX      Integer32
   MAX-ACCESS  read-only
   STATUS      current
   DESCRIPTION
      "Path: swPort.performance.vlan.mibCounters.h2Performance.ifInBandwidth

       unit name = bps
       formula = 8 * ; 8 /"
   ::= {pr1645v2EthPrtSwF2VlanMCH2PEntry 268435456}

pr1645v2EthPrtSwF2VlanMCH2PIfOutOctets OBJECT-TYPE
   SYNTAX      Counter64
   MAX-ACCESS  read-only
   STATUS      current
   DESCRIPTION
      "Path: swPort.performance.vlan.mibCounters.h2Performance.ifOutOctets

       64 bit unsigned wrappable counter."
   ::= {pr1645v2EthPrtSwF2VlanMCH2PEntry 167772160}

pr1645v2EthPrtSwF2VlanMCH2PIfOutUCPkts OBJECT-TYPE
   SYNTAX      Counter64
   MAX-ACCESS  read-only
   STATUS      current
   DESCRIPTION
      "Path: swPort.performance.vlan.mibCounters.h2Performance.ifOutUcastPkts

       64 bit unsigned wrappable counter."
   ::= {pr1645v2EthPrtSwF2VlanMCH2PEntry 184549376}

pr1645v2EthPrtSwF2VlanMCH2PIfOutNUCPkts OBJECT-TYPE
   SYNTAX      Counter64
   MAX-ACCESS  read-only
   STATUS      current
   DESCRIPTION
      "Path: swPort.performance.vlan.mibCounters.h2Performance.ifOutNUcastPkts

       64 bit unsigned wrappable counter."
   ::= {pr1645v2EthPrtSwF2VlanMCH2PEntry 201326592}

pr1645v2EthPrtSwF2VlanMCH2PIfOutBCPkts OBJECT-TYPE
   SYNTAX      Counter64
   MAX-ACCESS  read-only
   STATUS      current
   DESCRIPTION
      "Path: swPort.performance.vlan.mibCounters.h2Performance.ifOutBcastPkts

       64 bit unsigned wrappable counter."
   ::= {pr1645v2EthPrtSwF2VlanMCH2PEntry 452984832}

pr1645v2EthPrtSwF2VlanMCH2PIfOutMCPkts OBJECT-TYPE
   SYNTAX      Counter64
   MAX-ACCESS  read-only
   STATUS      current
   DESCRIPTION
      "Path: swPort.performance.vlan.mibCounters.h2Performance.ifOutMcastPkts

       64 bit unsigned wrappable counter."
   ::= {pr1645v2EthPrtSwF2VlanMCH2PEntry 469762048}

pr1645v2EthPrtSwF2VlanMCH2PIfOutDiscards OBJECT-TYPE
   SYNTAX      Counter64
   MAX-ACCESS  read-only
   STATUS      current
   DESCRIPTION
      "Path: swPort.performance.vlan.mibCounters.h2Performance.ifOutDiscards

       64 bit unsigned wrappable counter."
   ::= {pr1645v2EthPrtSwF2VlanMCH2PEntry 218103808}

pr1645v2EthPrtSwF2VlanMCH2PIfOutErrors OBJECT-TYPE
   SYNTAX      Counter64
   MAX-ACCESS  read-only
   STATUS      current
   DESCRIPTION
      "Path: swPort.performance.vlan.mibCounters.h2Performance.ifOutErrors

       64 bit unsigned wrappable counter."
   ::= {pr1645v2EthPrtSwF2VlanMCH2PEntry 234881024}

pr1645v2EthPrtSwF2VlanMCH2POutDropEx OBJECT-TYPE
   SYNTAX      Counter64
   MAX-ACCESS  read-only
   STATUS      current
   DESCRIPTION
      "Path: swPort.performance.vlan.mibCounters.h2Performance.ifOutDropLevelExceeded

       64 bit unsigned wrappable counter."
   ::= {pr1645v2EthPrtSwF2VlanMCH2PEntry 352321536}

pr1645v2EthPrtSwF2VlanMCH2POutDropNoArp OBJECT-TYPE
   SYNTAX      Counter64
   MAX-ACCESS  read-only
   STATUS      current
   DESCRIPTION
      "Path: swPort.performance.vlan.mibCounters.h2Performance.ifOutDiscardsNoArp

       64 bit unsigned wrappable counter."
   ::= {pr1645v2EthPrtSwF2VlanMCH2PEntry 369098752}

pr1645v2EthPrtSwF2VlanMCH2POutDropFilter OBJECT-TYPE
   SYNTAX      Counter64
   MAX-ACCESS  read-only
   STATUS      current
   DESCRIPTION
      "Path: swPort.performance.vlan.mibCounters.h2Performance.ifOutDiscardsFilter

       64 bit unsigned wrappable counter."
   ::= {pr1645v2EthPrtSwF2VlanMCH2PEntry 402653184}

pr1645v2EthPrtSwF2VlanMCH2PIfOutBandwidth OBJECT-TYPE
   SYNTAX      Integer32
   MAX-ACCESS  read-only
   STATUS      current
   DESCRIPTION
      "Path: swPort.performance.vlan.mibCounters.h2Performance.ifOutBandwidth

       unit name = bps
       formula = 8 * ; 8 /"
   ::= {pr1645v2EthPrtSwF2VlanMCH2PEntry 285212672}

pr1645v2EthPrtSwF2VlanMCH2PIfErrSec OBJECT-TYPE
   SYNTAX      Counter32
   MAX-ACCESS  read-only
   STATUS      current
   DESCRIPTION
      "Path: swPort.performance.vlan.mibCounters.h2Performance.ifErrSec

       32 bit unsigned wrappable counter."
   ::= {pr1645v2EthPrtSwF2VlanMCH2PEntry 251658240}

pr1645v2EthPrtSwF2VlanMCH24P OBJECT-TYPE
   SYNTAX      SEQUENCE OF Pr1645v2EthPrtSwF2VlanMCH24PEntry
   MAX-ACCESS  not-accessible
   STATUS      current
   DESCRIPTION
      ""
   ::= {pr1645v2EthPrtSwF2Vlan 41615360}

pr1645v2EthPrtSwF2VlanMCH24PEntry OBJECT-TYPE
   SYNTAX      Pr1645v2EthPrtSwF2VlanMCH24PEntry
   MAX-ACCESS  not-accessible
   STATUS      current
   DESCRIPTION
      ""
   INDEX      { pr1645v2EthPrtSwF2VlanMCH24PGlobalIx,
                pr1645v2EthPrtSwF2VlanTableIx,
                pr1645v2EthPrtSwF2VlanMCH24PTableIx }
   ::= {pr1645v2EthPrtSwF2VlanMCH24P 1}

Pr1645v2EthPrtSwF2VlanMCH24PEntry ::=
   SEQUENCE
      {
      pr1645v2EthPrtSwF2VlanMCH24PGlobalIx
         GlobalIndex,
      pr1645v2EthPrtSwF2VlanMCH24PTableIx
         TableIndex,
      pr1645v2EthPrtSwF2VlanMCH24PSysUpTime
         TimeTicks,
      pr1645v2EthPrtSwF2VlanMCH24PIfUpTime
         TimeTicks,
      pr1645v2EthPrtSwF2VlanMCH24PIfStatChanges
         Counter32,
      pr1645v2EthPrtSwF2VlanMCH24PIfInOctets
         Counter64,
      pr1645v2EthPrtSwF2VlanMCH24PIfInUCPkts
         Counter64,
      pr1645v2EthPrtSwF2VlanMCH24PIfInNUCPkts
         Counter64,
      pr1645v2EthPrtSwF2VlanMCH24PIfInBCPkts
         Counter64,
      pr1645v2EthPrtSwF2VlanMCH24PIfInMCPkts
         Counter64,
      pr1645v2EthPrtSwF2VlanMCH24PIfInDiscards
         Counter64,
      pr1645v2EthPrtSwF2VlanMCH24PIfInErrors
         Counter64,
      pr1645v2EthPrtSwF2VlanMCH24PIfInUnkwn
         Counter64,
      pr1645v2EthPrtSwF2VlanMCH24PInDropEx
         Counter64,
      pr1645v2EthPrtSwF2VlanMCH24PInDropNoMac
         Counter64,
      pr1645v2EthPrtSwF2VlanMCH24PInDropNUCast
         Counter64,
      pr1645v2EthPrtSwF2VlanMCH24PInDropFilter
         Counter64,
      pr1645v2EthPrtSwF2VlanMCH24PIfInBandwidth
         Integer32,
      pr1645v2EthPrtSwF2VlanMCH24PIfOutOctets
         Counter64,
      pr1645v2EthPrtSwF2VlanMCH24PIfOutUCPkts
         Counter64,
      pr1645v2EthPrtSwF2VlanMCH24PIfOutNUCPkts
         Counter64,
      pr1645v2EthPrtSwF2VlanMCH24PIfOutBCPkts
         Counter64,
      pr1645v2EthPrtSwF2VlanMCH24PIfOutMCPkts
         Counter64,
      pr1645v2EthPrtSwF2VlanMCH24PIfOutDiscards
         Counter64,
      pr1645v2EthPrtSwF2VlanMCH24PIfOutErrors
         Counter64,
      pr1645v2EthPrtSwF2VlanMCH24POutDropEx
         Counter64,
      pr1645v2EthPrtSwF2VlanMCH24POutDropNoArp
         Counter64,
      pr1645v2EthPrtSwF2VlanMCH24POutDropFilter
         Counter64,
      pr1645v2EthPrtSwF2VlanMCH24PIfOutBandwidth
         Integer32,
      pr1645v2EthPrtSwF2VlanMCH24PIfErrSec
         Counter32
      }

pr1645v2EthPrtSwF2VlanMCH24PGlobalIx OBJECT-TYPE
   SYNTAX      GlobalIndex
   MAX-ACCESS  not-accessible
   STATUS      current
   DESCRIPTION
      "The value of the tlsCntTreeGlobalIndex of the MANAGED OBJECT."
   ::= {pr1645v2EthPrtSwF2VlanMCH24PEntry 10}

pr1645v2EthPrtSwF2VlanMCH24PTableIx OBJECT-TYPE
   SYNTAX      TableIndex
   MAX-ACCESS  not-accessible
   STATUS      current
   DESCRIPTION
      ""
   ::= {pr1645v2EthPrtSwF2VlanMCH24PEntry 11}

pr1645v2EthPrtSwF2VlanMCH24PSysUpTime OBJECT-TYPE
   SYNTAX      TimeTicks
   MAX-ACCESS  read-only
   STATUS      current
   DESCRIPTION
      "Path: swPort.performance.vlan.mibCounters.h24Performance.sysUpTime

       Time in centi-second."
   ::= {pr1645v2EthPrtSwF2VlanMCH24PEntry 16777216}

pr1645v2EthPrtSwF2VlanMCH24PIfUpTime OBJECT-TYPE
   SYNTAX      TimeTicks
   MAX-ACCESS  read-only
   STATUS      current
   DESCRIPTION
      "Path: swPort.performance.vlan.mibCounters.h24Performance.ifUpTime

       Time in centi-second."
   ::= {pr1645v2EthPrtSwF2VlanMCH24PEntry 33554432}

pr1645v2EthPrtSwF2VlanMCH24PIfStatChanges OBJECT-TYPE
   SYNTAX      Counter32
   MAX-ACCESS  read-only
   STATUS      current
   DESCRIPTION
      "Path: swPort.performance.vlan.mibCounters.h24Performance.ifStatusChanges

       32 bit unsigned wrappable counter."
   ::= {pr1645v2EthPrtSwF2VlanMCH24PEntry 50331648}

pr1645v2EthPrtSwF2VlanMCH24PIfInOctets OBJECT-TYPE
   SYNTAX      Counter64
   MAX-ACCESS  read-only
   STATUS      current
   DESCRIPTION
      "Path: swPort.performance.vlan.mibCounters.h24Performance.ifInOctets

       64 bit unsigned wrappable counter."
   ::= {pr1645v2EthPrtSwF2VlanMCH24PEntry 67108864}

pr1645v2EthPrtSwF2VlanMCH24PIfInUCPkts OBJECT-TYPE
   SYNTAX      Counter64
   MAX-ACCESS  read-only
   STATUS      current
   DESCRIPTION
      "Path: swPort.performance.vlan.mibCounters.h24Performance.ifInUcastPkts

       64 bit unsigned wrappable counter."
   ::= {pr1645v2EthPrtSwF2VlanMCH24PEntry 83886080}

pr1645v2EthPrtSwF2VlanMCH24PIfInNUCPkts OBJECT-TYPE
   SYNTAX      Counter64
   MAX-ACCESS  read-only
   STATUS      current
   DESCRIPTION
      "Path: swPort.performance.vlan.mibCounters.h24Performance.ifInNUcastPkts

       64 bit unsigned wrappable counter."
   ::= {pr1645v2EthPrtSwF2VlanMCH24PEntry 100663296}

pr1645v2EthPrtSwF2VlanMCH24PIfInBCPkts OBJECT-TYPE
   SYNTAX      Counter64
   MAX-ACCESS  read-only
   STATUS      current
   DESCRIPTION
      "Path: swPort.performance.vlan.mibCounters.h24Performance.ifInBcastPkts

       64 bit unsigned wrappable counter."
   ::= {pr1645v2EthPrtSwF2VlanMCH24PEntry 419430400}

pr1645v2EthPrtSwF2VlanMCH24PIfInMCPkts OBJECT-TYPE
   SYNTAX      Counter64
   MAX-ACCESS  read-only
   STATUS      current
   DESCRIPTION
      "Path: swPort.performance.vlan.mibCounters.h24Performance.ifInMcastPkts

       64 bit unsigned wrappable counter."
   ::= {pr1645v2EthPrtSwF2VlanMCH24PEntry 436207616}

pr1645v2EthPrtSwF2VlanMCH24PIfInDiscards OBJECT-TYPE
   SYNTAX      Counter64
   MAX-ACCESS  read-only
   STATUS      current
   DESCRIPTION
      "Path: swPort.performance.vlan.mibCounters.h24Performance.ifInDiscards

       64 bit unsigned wrappable counter."
   ::= {pr1645v2EthPrtSwF2VlanMCH24PEntry 117440512}

pr1645v2EthPrtSwF2VlanMCH24PIfInErrors OBJECT-TYPE
   SYNTAX      Counter64
   MAX-ACCESS  read-only
   STATUS      current
   DESCRIPTION
      "Path: swPort.performance.vlan.mibCounters.h24Performance.ifInErrors

       64 bit unsigned wrappable counter."
   ::= {pr1645v2EthPrtSwF2VlanMCH24PEntry 134217728}

pr1645v2EthPrtSwF2VlanMCH24PIfInUnkwn OBJECT-TYPE
   SYNTAX      Counter64
   MAX-ACCESS  read-only
   STATUS      current
   DESCRIPTION
      "Path: swPort.performance.vlan.mibCounters.h24Performance.ifInUnknownProtos

       64 bit unsigned wrappable counter."
   ::= {pr1645v2EthPrtSwF2VlanMCH24PEntry 150994944}

pr1645v2EthPrtSwF2VlanMCH24PInDropEx OBJECT-TYPE
   SYNTAX      Counter64
   MAX-ACCESS  read-only
   STATUS      current
   DESCRIPTION
      "Path: swPort.performance.vlan.mibCounters.h24Performance.ifInDropLevelExceeded

       64 bit unsigned wrappable counter."
   ::= {pr1645v2EthPrtSwF2VlanMCH24PEntry 335544320}

pr1645v2EthPrtSwF2VlanMCH24PInDropNoMac OBJECT-TYPE
   SYNTAX      Counter64
   MAX-ACCESS  read-only
   STATUS      current
   DESCRIPTION
      "Path: swPort.performance.vlan.mibCounters.h24Performance.fInDiscardsNoMacFit

       64 bit unsigned wrappable counter."
   ::= {pr1645v2EthPrtSwF2VlanMCH24PEntry 301989888}

pr1645v2EthPrtSwF2VlanMCH24PInDropNUCast OBJECT-TYPE
   SYNTAX      Counter64
   MAX-ACCESS  read-only
   STATUS      current
   DESCRIPTION
      "Path: swPort.performance.vlan.mibCounters.h24Performance.fInDiscardsNUCast

       64 bit unsigned wrappable counter."
   ::= {pr1645v2EthPrtSwF2VlanMCH24PEntry 318767104}

pr1645v2EthPrtSwF2VlanMCH24PInDropFilter OBJECT-TYPE
   SYNTAX      Counter64
   MAX-ACCESS  read-only
   STATUS      current
   DESCRIPTION
      "Path: swPort.performance.vlan.mibCounters.h24Performance.fInDiscardsFilter

       64 bit unsigned wrappable counter."
   ::= {pr1645v2EthPrtSwF2VlanMCH24PEntry 385875968}

pr1645v2EthPrtSwF2VlanMCH24PIfInBandwidth OBJECT-TYPE
   SYNTAX      Integer32
   MAX-ACCESS  read-only
   STATUS      current
   DESCRIPTION
      "Path: swPort.performance.vlan.mibCounters.h24Performance.ifInBandwidth

       unit name = bps
       formula = 8 * ; 8 /"
   ::= {pr1645v2EthPrtSwF2VlanMCH24PEntry 268435456}

pr1645v2EthPrtSwF2VlanMCH24PIfOutOctets OBJECT-TYPE
   SYNTAX      Counter64
   MAX-ACCESS  read-only
   STATUS      current
   DESCRIPTION
      "Path: swPort.performance.vlan.mibCounters.h24Performance.ifOutOctets

       64 bit unsigned wrappable counter."
   ::= {pr1645v2EthPrtSwF2VlanMCH24PEntry 167772160}

pr1645v2EthPrtSwF2VlanMCH24PIfOutUCPkts OBJECT-TYPE
   SYNTAX      Counter64
   MAX-ACCESS  read-only
   STATUS      current
   DESCRIPTION
      "Path: swPort.performance.vlan.mibCounters.h24Performance.ifOutUcastPkts

       64 bit unsigned wrappable counter."
   ::= {pr1645v2EthPrtSwF2VlanMCH24PEntry 184549376}

pr1645v2EthPrtSwF2VlanMCH24PIfOutNUCPkts OBJECT-TYPE
   SYNTAX      Counter64
   MAX-ACCESS  read-only
   STATUS      current
   DESCRIPTION
      "Path: swPort.performance.vlan.mibCounters.h24Performance.ifOutNUcastPkts

       64 bit unsigned wrappable counter."
   ::= {pr1645v2EthPrtSwF2VlanMCH24PEntry 201326592}

pr1645v2EthPrtSwF2VlanMCH24PIfOutBCPkts OBJECT-TYPE
   SYNTAX      Counter64
   MAX-ACCESS  read-only
   STATUS      current
   DESCRIPTION
      "Path: swPort.performance.vlan.mibCounters.h24Performance.ifOutBcastPkts

       64 bit unsigned wrappable counter."
   ::= {pr1645v2EthPrtSwF2VlanMCH24PEntry 452984832}

pr1645v2EthPrtSwF2VlanMCH24PIfOutMCPkts OBJECT-TYPE
   SYNTAX      Counter64
   MAX-ACCESS  read-only
   STATUS      current
   DESCRIPTION
      "Path: swPort.performance.vlan.mibCounters.h24Performance.ifOutMcastPkts

       64 bit unsigned wrappable counter."
   ::= {pr1645v2EthPrtSwF2VlanMCH24PEntry 469762048}

pr1645v2EthPrtSwF2VlanMCH24PIfOutDiscards OBJECT-TYPE
   SYNTAX      Counter64
   MAX-ACCESS  read-only
   STATUS      current
   DESCRIPTION
      "Path: swPort.performance.vlan.mibCounters.h24Performance.ifOutDiscards

       64 bit unsigned wrappable counter."
   ::= {pr1645v2EthPrtSwF2VlanMCH24PEntry 218103808}

pr1645v2EthPrtSwF2VlanMCH24PIfOutErrors OBJECT-TYPE
   SYNTAX      Counter64
   MAX-ACCESS  read-only
   STATUS      current
   DESCRIPTION
      "Path: swPort.performance.vlan.mibCounters.h24Performance.ifOutErrors

       64 bit unsigned wrappable counter."
   ::= {pr1645v2EthPrtSwF2VlanMCH24PEntry 234881024}

pr1645v2EthPrtSwF2VlanMCH24POutDropEx OBJECT-TYPE
   SYNTAX      Counter64
   MAX-ACCESS  read-only
   STATUS      current
   DESCRIPTION
      "Path: swPort.performance.vlan.mibCounters.h24Performance.ifOutDropLevelExceeded

       64 bit unsigned wrappable counter."
   ::= {pr1645v2EthPrtSwF2VlanMCH24PEntry 352321536}

pr1645v2EthPrtSwF2VlanMCH24POutDropNoArp OBJECT-TYPE
   SYNTAX      Counter64
   MAX-ACCESS  read-only
   STATUS      current
   DESCRIPTION
      "Path: swPort.performance.vlan.mibCounters.h24Performance.ifOutDiscardsNoArp

       64 bit unsigned wrappable counter."
   ::= {pr1645v2EthPrtSwF2VlanMCH24PEntry 369098752}

pr1645v2EthPrtSwF2VlanMCH24POutDropFilter OBJECT-TYPE
   SYNTAX      Counter64
   MAX-ACCESS  read-only
   STATUS      current
   DESCRIPTION
      "Path: swPort.performance.vlan.mibCounters.h24Performance.ifOutDiscardsFilter

       64 bit unsigned wrappable counter."
   ::= {pr1645v2EthPrtSwF2VlanMCH24PEntry 402653184}

pr1645v2EthPrtSwF2VlanMCH24PIfOutBandwidth OBJECT-TYPE
   SYNTAX      Integer32
   MAX-ACCESS  read-only
   STATUS      current
   DESCRIPTION
      "Path: swPort.performance.vlan.mibCounters.h24Performance.ifOutBandwidth

       unit name = bps
       formula = 8 * ; 8 /"
   ::= {pr1645v2EthPrtSwF2VlanMCH24PEntry 285212672}

pr1645v2EthPrtSwF2VlanMCH24PIfErrSec OBJECT-TYPE
   SYNTAX      Counter32
   MAX-ACCESS  read-only
   STATUS      current
   DESCRIPTION
      "Path: swPort.performance.vlan.mibCounters.h24Performance.ifErrSec

       32 bit unsigned wrappable counter."
   ::= {pr1645v2EthPrtSwF2VlanMCH24PEntry 251658240}

pr1645v2EthPrtSwF2VlanMCD7P OBJECT-TYPE
   SYNTAX      SEQUENCE OF Pr1645v2EthPrtSwF2VlanMCD7PEntry
   MAX-ACCESS  not-accessible
   STATUS      current
   DESCRIPTION
      ""
   ::= {pr1645v2EthPrtSwF2Vlan 41680896}

pr1645v2EthPrtSwF2VlanMCD7PEntry OBJECT-TYPE
   SYNTAX      Pr1645v2EthPrtSwF2VlanMCD7PEntry
   MAX-ACCESS  not-accessible
   STATUS      current
   DESCRIPTION
      ""
   INDEX      { pr1645v2EthPrtSwF2VlanMCD7PGlobalIx,
                pr1645v2EthPrtSwF2VlanTableIx,
                pr1645v2EthPrtSwF2VlanMCD7PTableIx }
   ::= {pr1645v2EthPrtSwF2VlanMCD7P 1}

Pr1645v2EthPrtSwF2VlanMCD7PEntry ::=
   SEQUENCE
      {
      pr1645v2EthPrtSwF2VlanMCD7PGlobalIx
         GlobalIndex,
      pr1645v2EthPrtSwF2VlanMCD7PTableIx
         TableIndex,
      pr1645v2EthPrtSwF2VlanMCD7PSysUpTime
         TimeTicks,
      pr1645v2EthPrtSwF2VlanMCD7PIfUpTime
         TimeTicks,
      pr1645v2EthPrtSwF2VlanMCD7PIfStatChanges
         Counter32,
      pr1645v2EthPrtSwF2VlanMCD7PIfInOctets
         Counter64,
      pr1645v2EthPrtSwF2VlanMCD7PIfInUCPkts
         Counter64,
      pr1645v2EthPrtSwF2VlanMCD7PIfInNUCPkts
         Counter64,
      pr1645v2EthPrtSwF2VlanMCD7PIfInBCPkts
         Counter64,
      pr1645v2EthPrtSwF2VlanMCD7PIfInMCPkts
         Counter64,
      pr1645v2EthPrtSwF2VlanMCD7PIfInDiscards
         Counter64,
      pr1645v2EthPrtSwF2VlanMCD7PIfInErrors
         Counter64,
      pr1645v2EthPrtSwF2VlanMCD7PIfInUnkwn
         Counter64,
      pr1645v2EthPrtSwF2VlanMCD7PInDropEx
         Counter64,
      pr1645v2EthPrtSwF2VlanMCD7PInDropNoMac
         Counter64,
      pr1645v2EthPrtSwF2VlanMCD7PInDropNUCast
         Counter64,
      pr1645v2EthPrtSwF2VlanMCD7PInDropFilter
         Counter64,
      pr1645v2EthPrtSwF2VlanMCD7PIfInBandwidth
         Integer32,
      pr1645v2EthPrtSwF2VlanMCD7PIfOutOctets
         Counter64,
      pr1645v2EthPrtSwF2VlanMCD7PIfOutUCPkts
         Counter64,
      pr1645v2EthPrtSwF2VlanMCD7PIfOutNUCPkts
         Counter64,
      pr1645v2EthPrtSwF2VlanMCD7PIfOutBCPkts
         Counter64,
      pr1645v2EthPrtSwF2VlanMCD7PIfOutMCPkts
         Counter64,
      pr1645v2EthPrtSwF2VlanMCD7PIfOutDiscards
         Counter64,
      pr1645v2EthPrtSwF2VlanMCD7PIfOutErrors
         Counter64,
      pr1645v2EthPrtSwF2VlanMCD7POutDropEx
         Counter64,
      pr1645v2EthPrtSwF2VlanMCD7POutDropNoArp
         Counter64,
      pr1645v2EthPrtSwF2VlanMCD7POutDropFilter
         Counter64,
      pr1645v2EthPrtSwF2VlanMCD7PIfOutBandwidth
         Integer32,
      pr1645v2EthPrtSwF2VlanMCD7PIfErrSec
         Counter32
      }

pr1645v2EthPrtSwF2VlanMCD7PGlobalIx OBJECT-TYPE
   SYNTAX      GlobalIndex
   MAX-ACCESS  not-accessible
   STATUS      current
   DESCRIPTION
      "The value of the tlsCntTreeGlobalIndex of the MANAGED OBJECT."
   ::= {pr1645v2EthPrtSwF2VlanMCD7PEntry 10}

pr1645v2EthPrtSwF2VlanMCD7PTableIx OBJECT-TYPE
   SYNTAX      TableIndex
   MAX-ACCESS  not-accessible
   STATUS      current
   DESCRIPTION
      ""
   ::= {pr1645v2EthPrtSwF2VlanMCD7PEntry 11}

pr1645v2EthPrtSwF2VlanMCD7PSysUpTime OBJECT-TYPE
   SYNTAX      TimeTicks
   MAX-ACCESS  read-only
   STATUS      current
   DESCRIPTION
      "Path: swPort.performance.vlan.mibCounters.d7Performance.sysUpTime

       Time in centi-second."
   ::= {pr1645v2EthPrtSwF2VlanMCD7PEntry 16777216}

pr1645v2EthPrtSwF2VlanMCD7PIfUpTime OBJECT-TYPE
   SYNTAX      TimeTicks
   MAX-ACCESS  read-only
   STATUS      current
   DESCRIPTION
      "Path: swPort.performance.vlan.mibCounters.d7Performance.ifUpTime

       Time in centi-second."
   ::= {pr1645v2EthPrtSwF2VlanMCD7PEntry 33554432}

pr1645v2EthPrtSwF2VlanMCD7PIfStatChanges OBJECT-TYPE
   SYNTAX      Counter32
   MAX-ACCESS  read-only
   STATUS      current
   DESCRIPTION
      "Path: swPort.performance.vlan.mibCounters.d7Performance.ifStatusChanges

       32 bit unsigned wrappable counter."
   ::= {pr1645v2EthPrtSwF2VlanMCD7PEntry 50331648}

pr1645v2EthPrtSwF2VlanMCD7PIfInOctets OBJECT-TYPE
   SYNTAX      Counter64
   MAX-ACCESS  read-only
   STATUS      current
   DESCRIPTION
      "Path: swPort.performance.vlan.mibCounters.d7Performance.ifInOctets

       64 bit unsigned wrappable counter."
   ::= {pr1645v2EthPrtSwF2VlanMCD7PEntry 67108864}

pr1645v2EthPrtSwF2VlanMCD7PIfInUCPkts OBJECT-TYPE
   SYNTAX      Counter64
   MAX-ACCESS  read-only
   STATUS      current
   DESCRIPTION
      "Path: swPort.performance.vlan.mibCounters.d7Performance.ifInUcastPkts

       64 bit unsigned wrappable counter."
   ::= {pr1645v2EthPrtSwF2VlanMCD7PEntry 83886080}

pr1645v2EthPrtSwF2VlanMCD7PIfInNUCPkts OBJECT-TYPE
   SYNTAX      Counter64
   MAX-ACCESS  read-only
   STATUS      current
   DESCRIPTION
      "Path: swPort.performance.vlan.mibCounters.d7Performance.ifInNUcastPkts

       64 bit unsigned wrappable counter."
   ::= {pr1645v2EthPrtSwF2VlanMCD7PEntry 100663296}

pr1645v2EthPrtSwF2VlanMCD7PIfInBCPkts OBJECT-TYPE
   SYNTAX      Counter64
   MAX-ACCESS  read-only
   STATUS      current
   DESCRIPTION
      "Path: swPort.performance.vlan.mibCounters.d7Performance.ifInBcastPkts

       64 bit unsigned wrappable counter."
   ::= {pr1645v2EthPrtSwF2VlanMCD7PEntry 419430400}

pr1645v2EthPrtSwF2VlanMCD7PIfInMCPkts OBJECT-TYPE
   SYNTAX      Counter64
   MAX-ACCESS  read-only
   STATUS      current
   DESCRIPTION
      "Path: swPort.performance.vlan.mibCounters.d7Performance.ifInMcastPkts

       64 bit unsigned wrappable counter."
   ::= {pr1645v2EthPrtSwF2VlanMCD7PEntry 436207616}

pr1645v2EthPrtSwF2VlanMCD7PIfInDiscards OBJECT-TYPE
   SYNTAX      Counter64
   MAX-ACCESS  read-only
   STATUS      current
   DESCRIPTION
      "Path: swPort.performance.vlan.mibCounters.d7Performance.ifInDiscards

       64 bit unsigned wrappable counter."
   ::= {pr1645v2EthPrtSwF2VlanMCD7PEntry 117440512}

pr1645v2EthPrtSwF2VlanMCD7PIfInErrors OBJECT-TYPE
   SYNTAX      Counter64
   MAX-ACCESS  read-only
   STATUS      current
   DESCRIPTION
      "Path: swPort.performance.vlan.mibCounters.d7Performance.ifInErrors

       64 bit unsigned wrappable counter."
   ::= {pr1645v2EthPrtSwF2VlanMCD7PEntry 134217728}

pr1645v2EthPrtSwF2VlanMCD7PIfInUnkwn OBJECT-TYPE
   SYNTAX      Counter64
   MAX-ACCESS  read-only
   STATUS      current
   DESCRIPTION
      "Path: swPort.performance.vlan.mibCounters.d7Performance.ifInUnknownProtos

       64 bit unsigned wrappable counter."
   ::= {pr1645v2EthPrtSwF2VlanMCD7PEntry 150994944}

pr1645v2EthPrtSwF2VlanMCD7PInDropEx OBJECT-TYPE
   SYNTAX      Counter64
   MAX-ACCESS  read-only
   STATUS      current
   DESCRIPTION
      "Path: swPort.performance.vlan.mibCounters.d7Performance.ifInDropLevelExceeded

       64 bit unsigned wrappable counter."
   ::= {pr1645v2EthPrtSwF2VlanMCD7PEntry 335544320}

pr1645v2EthPrtSwF2VlanMCD7PInDropNoMac OBJECT-TYPE
   SYNTAX      Counter64
   MAX-ACCESS  read-only
   STATUS      current
   DESCRIPTION
      "Path: swPort.performance.vlan.mibCounters.d7Performance.fInDiscardsNoMacFit

       64 bit unsigned wrappable counter."
   ::= {pr1645v2EthPrtSwF2VlanMCD7PEntry 301989888}

pr1645v2EthPrtSwF2VlanMCD7PInDropNUCast OBJECT-TYPE
   SYNTAX      Counter64
   MAX-ACCESS  read-only
   STATUS      current
   DESCRIPTION
      "Path: swPort.performance.vlan.mibCounters.d7Performance.fInDiscardsNUCast

       64 bit unsigned wrappable counter."
   ::= {pr1645v2EthPrtSwF2VlanMCD7PEntry 318767104}

pr1645v2EthPrtSwF2VlanMCD7PInDropFilter OBJECT-TYPE
   SYNTAX      Counter64
   MAX-ACCESS  read-only
   STATUS      current
   DESCRIPTION
      "Path: swPort.performance.vlan.mibCounters.d7Performance.fInDiscardsFilter

       64 bit unsigned wrappable counter."
   ::= {pr1645v2EthPrtSwF2VlanMCD7PEntry 385875968}

pr1645v2EthPrtSwF2VlanMCD7PIfInBandwidth OBJECT-TYPE
   SYNTAX      Integer32
   MAX-ACCESS  read-only
   STATUS      current
   DESCRIPTION
      "Path: swPort.performance.vlan.mibCounters.d7Performance.ifInBandwidth

       unit name = bps
       formula = 8 * ; 8 /"
   ::= {pr1645v2EthPrtSwF2VlanMCD7PEntry 268435456}

pr1645v2EthPrtSwF2VlanMCD7PIfOutOctets OBJECT-TYPE
   SYNTAX      Counter64
   MAX-ACCESS  read-only
   STATUS      current
   DESCRIPTION
      "Path: swPort.performance.vlan.mibCounters.d7Performance.ifOutOctets

       64 bit unsigned wrappable counter."
   ::= {pr1645v2EthPrtSwF2VlanMCD7PEntry 167772160}

pr1645v2EthPrtSwF2VlanMCD7PIfOutUCPkts OBJECT-TYPE
   SYNTAX      Counter64
   MAX-ACCESS  read-only
   STATUS      current
   DESCRIPTION
      "Path: swPort.performance.vlan.mibCounters.d7Performance.ifOutUcastPkts

       64 bit unsigned wrappable counter."
   ::= {pr1645v2EthPrtSwF2VlanMCD7PEntry 184549376}

pr1645v2EthPrtSwF2VlanMCD7PIfOutNUCPkts OBJECT-TYPE
   SYNTAX      Counter64
   MAX-ACCESS  read-only
   STATUS      current
   DESCRIPTION
      "Path: swPort.performance.vlan.mibCounters.d7Performance.ifOutNUcastPkts

       64 bit unsigned wrappable counter."
   ::= {pr1645v2EthPrtSwF2VlanMCD7PEntry 201326592}

pr1645v2EthPrtSwF2VlanMCD7PIfOutBCPkts OBJECT-TYPE
   SYNTAX      Counter64
   MAX-ACCESS  read-only
   STATUS      current
   DESCRIPTION
      "Path: swPort.performance.vlan.mibCounters.d7Performance.ifOutBcastPkts

       64 bit unsigned wrappable counter."
   ::= {pr1645v2EthPrtSwF2VlanMCD7PEntry 452984832}

pr1645v2EthPrtSwF2VlanMCD7PIfOutMCPkts OBJECT-TYPE
   SYNTAX      Counter64
   MAX-ACCESS  read-only
   STATUS      current
   DESCRIPTION
      "Path: swPort.performance.vlan.mibCounters.d7Performance.ifOutMcastPkts

       64 bit unsigned wrappable counter."
   ::= {pr1645v2EthPrtSwF2VlanMCD7PEntry 469762048}

pr1645v2EthPrtSwF2VlanMCD7PIfOutDiscards OBJECT-TYPE
   SYNTAX      Counter64
   MAX-ACCESS  read-only
   STATUS      current
   DESCRIPTION
      "Path: swPort.performance.vlan.mibCounters.d7Performance.ifOutDiscards

       64 bit unsigned wrappable counter."
   ::= {pr1645v2EthPrtSwF2VlanMCD7PEntry 218103808}

pr1645v2EthPrtSwF2VlanMCD7PIfOutErrors OBJECT-TYPE
   SYNTAX      Counter64
   MAX-ACCESS  read-only
   STATUS      current
   DESCRIPTION
      "Path: swPort.performance.vlan.mibCounters.d7Performance.ifOutErrors

       64 bit unsigned wrappable counter."
   ::= {pr1645v2EthPrtSwF2VlanMCD7PEntry 234881024}

pr1645v2EthPrtSwF2VlanMCD7POutDropEx OBJECT-TYPE
   SYNTAX      Counter64
   MAX-ACCESS  read-only
   STATUS      current
   DESCRIPTION
      "Path: swPort.performance.vlan.mibCounters.d7Performance.ifOutDropLevelExceeded

       64 bit unsigned wrappable counter."
   ::= {pr1645v2EthPrtSwF2VlanMCD7PEntry 352321536}

pr1645v2EthPrtSwF2VlanMCD7POutDropNoArp OBJECT-TYPE
   SYNTAX      Counter64
   MAX-ACCESS  read-only
   STATUS      current
   DESCRIPTION
      "Path: swPort.performance.vlan.mibCounters.d7Performance.ifOutDiscardsNoArp

       64 bit unsigned wrappable counter."
   ::= {pr1645v2EthPrtSwF2VlanMCD7PEntry 369098752}

pr1645v2EthPrtSwF2VlanMCD7POutDropFilter OBJECT-TYPE
   SYNTAX      Counter64
   MAX-ACCESS  read-only
   STATUS      current
   DESCRIPTION
      "Path: swPort.performance.vlan.mibCounters.d7Performance.ifOutDiscardsFilter

       64 bit unsigned wrappable counter."
   ::= {pr1645v2EthPrtSwF2VlanMCD7PEntry 402653184}

pr1645v2EthPrtSwF2VlanMCD7PIfOutBandwidth OBJECT-TYPE
   SYNTAX      Integer32
   MAX-ACCESS  read-only
   STATUS      current
   DESCRIPTION
      "Path: swPort.performance.vlan.mibCounters.d7Performance.ifOutBandwidth

       unit name = bps
       formula = 8 * ; 8 /"
   ::= {pr1645v2EthPrtSwF2VlanMCD7PEntry 285212672}

pr1645v2EthPrtSwF2VlanMCD7PIfErrSec OBJECT-TYPE
   SYNTAX      Counter32
   MAX-ACCESS  read-only
   STATUS      current
   DESCRIPTION
      "Path: swPort.performance.vlan.mibCounters.d7Performance.ifErrSec

       32 bit unsigned wrappable counter."
   ::= {pr1645v2EthPrtSwF2VlanMCD7PEntry 251658240}

pr1645v2EthPrtSwF2VlanInPQs OBJECT-TYPE
   SYNTAX      SEQUENCE OF Pr1645v2EthPrtSwF2VlanInPQsEntry
   MAX-ACCESS  not-accessible
   STATUS      current
   DESCRIPTION
      ""
   ::= {pr1645v2EthPrtSwF2Vlan 100663296}

pr1645v2EthPrtSwF2VlanInPQsEntry OBJECT-TYPE
   SYNTAX      Pr1645v2EthPrtSwF2VlanInPQsEntry
   MAX-ACCESS  not-accessible
   STATUS      current
   DESCRIPTION
      ""
   INDEX      { pr1645v2EthPrtSwF2VlanInPQsGlobalIx,
                pr1645v2EthPrtSwF2VlanTableIx,
                pr1645v2EthPrtSwF2VlanInPQsTableIx }
   ::= {pr1645v2EthPrtSwF2VlanInPQs 1}

Pr1645v2EthPrtSwF2VlanInPQsEntry ::=
   SEQUENCE
      {
      pr1645v2EthPrtSwF2VlanInPQsGlobalIx
         GlobalIndex,
      pr1645v2EthPrtSwF2VlanInPQsTableIx
         TableIndex,
      pr1645v2EthPrtSwF2VlanInPQsName
         INTEGER,
      pr1645v2EthPrtSwF2VlanInPQsLength
         Integer32,
      pr1645v2EthPrtSwF2VlanInPQsOctetLength
         Integer32,
      pr1645v2EthPrtSwF2VlanInPQsRedLength
         Integer32,
      pr1645v2EthPrtSwF2VlanInPQsPacketsTotal
         Counter64,
      pr1645v2EthPrtSwF2VlanInPQsPacketsDirectTx
         Counter64,
      pr1645v2EthPrtSwF2VlanInPQsPacketsQueued
         Counter64,
      pr1645v2EthPrtSwF2VlanInPQsPacketsDropped
         Counter64,
      pr1645v2EthPrtSwF2VlanInPQsPacketsRedDropped
         Counter64,
      pr1645v2EthPrtSwF2VlanInPQsPacketsCirTx
         Counter64,
      pr1645v2EthPrtSwF2VlanInPQsPacketsEirTx
         Counter64,
      pr1645v2EthPrtSwF2VlanInPQsPacketsViolateTx
         Counter64,
      pr1645v2EthPrtSwF2VlanInPQsOctetsTotal
         Counter64,
      pr1645v2EthPrtSwF2VlanInPQsOctetsDirectTx
         Counter64,
      pr1645v2EthPrtSwF2VlanInPQsOctetsQueued
         Counter64,
      pr1645v2EthPrtSwF2VlanInPQsOctetsDropped
         Counter64,
      pr1645v2EthPrtSwF2VlanInPQsOctetsRedDropped
         Counter64,
      pr1645v2EthPrtSwF2VlanInPQsOctetsCirTx
         Counter64,
      pr1645v2EthPrtSwF2VlanInPQsOctetsEirTx
         Counter64,
      pr1645v2EthPrtSwF2VlanInPQsOctetsViolateTx
         Counter64,
      pr1645v2EthPrtSwF2VlanInPQsOctetsBandwidth15sec
         Integer32,
      pr1645v2EthPrtSwF2VlanInPQsOctetsBandwidth30sec
         Integer32,
      pr1645v2EthPrtSwF2VlanInPQsOctetsBandwidth1min
         Integer32,
      pr1645v2EthPrtSwF2VlanInPQsOctetsBandwidth2min
         Integer32,
      pr1645v2EthPrtSwF2VlanInPQsOctetsBandwidth5min
         Integer32
      }

pr1645v2EthPrtSwF2VlanInPQsGlobalIx OBJECT-TYPE
   SYNTAX      GlobalIndex
   MAX-ACCESS  not-accessible
   STATUS      current
   DESCRIPTION
      "The value of the tlsCntTreeGlobalIndex of the MANAGED OBJECT."
   ::= {pr1645v2EthPrtSwF2VlanInPQsEntry 10}

pr1645v2EthPrtSwF2VlanInPQsTableIx OBJECT-TYPE
   SYNTAX      TableIndex
   MAX-ACCESS  not-accessible
   STATUS      current
   DESCRIPTION
      ""
   ::= {pr1645v2EthPrtSwF2VlanInPQsEntry 11}

pr1645v2EthPrtSwF2VlanInPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: swPort.performance.vlan.inPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2EthPrtSwF2VlanInPQsEntry 16777216}

pr1645v2EthPrtSwF2VlanInPQsLength OBJECT-TYPE
   SYNTAX      Integer32
   MAX-ACCESS  read-only
   STATUS      current
   DESCRIPTION
      "Path: swPort.performance.vlan.inPriorityQueues.length"
   ::= {pr1645v2EthPrtSwF2VlanInPQsEntry 33554432}

pr1645v2EthPrtSwF2VlanInPQsOctetLength OBJECT-TYPE
   SYNTAX      Integer32
   MAX-ACCESS  read-only
   STATUS      current
   DESCRIPTION
      "Path: swPort.performance.vlan.inPriorityQueues.octetLength"
   ::= {pr1645v2EthPrtSwF2VlanInPQsEntry 150994944}

pr1645v2EthPrtSwF2VlanInPQsRedLength OBJECT-TYPE
   SYNTAX      Integer32
   MAX-ACCESS  read-only
   STATUS      current
   DESCRIPTION
      "Path: swPort.performance.vlan.inPriorityQueues.redLength"
   ::= {pr1645v2EthPrtSwF2VlanInPQsEntry 134217728}

pr1645v2EthPrtSwF2VlanInPQsPacketsTotal OBJECT-TYPE
   SYNTAX      Counter64
   MAX-ACCESS  read-only
   STATUS      current
   DESCRIPTION
      "Path: swPort.performance.vlan.inPriorityQueues.packets.total

       64 bit unsigned wrappable counter."
   ::= {pr1645v2EthPrtSwF2VlanInPQsEntry 50790400}

pr1645v2EthPrtSwF2VlanInPQsPacketsDirectTx OBJECT-TYPE
   SYNTAX      Counter64
   MAX-ACCESS  read-only
   STATUS      current
   DESCRIPTION
      "Path: swPort.performance.vlan.inPriorityQueues.packets.directTx

       64 bit unsigned wrappable counter."
   ::= {pr1645v2EthPrtSwF2VlanInPQsEntry 50397184}

pr1645v2EthPrtSwF2VlanInPQsPacketsQueued OBJECT-TYPE
   SYNTAX      Counter64
   MAX-ACCESS  read-only
   STATUS      current
   DESCRIPTION
      "Path: swPort.performance.vlan.inPriorityQueues.packets.queued

       64 bit unsigned wrappable counter."
   ::= {pr1645v2EthPrtSwF2VlanInPQsEntry 50462720}

pr1645v2EthPrtSwF2VlanInPQsPacketsDropped OBJECT-TYPE
   SYNTAX      Counter64
   MAX-ACCESS  read-only
   STATUS      current
   DESCRIPTION
      "Path: swPort.performance.vlan.inPriorityQueues.packets.dropped

       64 bit unsigned wrappable counter."
   ::= {pr1645v2EthPrtSwF2VlanInPQsEntry 50528256}

pr1645v2EthPrtSwF2VlanInPQsPacketsRedDropped OBJECT-TYPE
   SYNTAX      Counter64
   MAX-ACCESS  read-only
   STATUS      current
   DESCRIPTION
      "Path: swPort.performance.vlan.inPriorityQueues.packets.redDropped

       64 bit unsigned wrappable counter."
   ::= {pr1645v2EthPrtSwF2VlanInPQsEntry 50724864}

pr1645v2EthPrtSwF2VlanInPQsPacketsCirTx OBJECT-TYPE
   SYNTAX      Counter64
   MAX-ACCESS  read-only
   STATUS      current
   DESCRIPTION
      "Path: swPort.performance.vlan.inPriorityQueues.packets.cirTx

       64 bit unsigned wrappable counter."
   ::= {pr1645v2EthPrtSwF2VlanInPQsEntry 50593792}

pr1645v2EthPrtSwF2VlanInPQsPacketsEirTx OBJECT-TYPE
   SYNTAX      Counter64
   MAX-ACCESS  read-only
   STATUS      current
   DESCRIPTION
      "Path: swPort.performance.vlan.inPriorityQueues.packets.eirTx

       64 bit unsigned wrappable counter."
   ::= {pr1645v2EthPrtSwF2VlanInPQsEntry 50659328}

pr1645v2EthPrtSwF2VlanInPQsPacketsViolateTx OBJECT-TYPE
   SYNTAX      Counter64
   MAX-ACCESS  read-only
   STATUS      current
   DESCRIPTION
      "Path: swPort.performance.vlan.inPriorityQueues.packets.violateTx

       64 bit unsigned wrappable counter."
   ::= {pr1645v2EthPrtSwF2VlanInPQsEntry 50855936}

pr1645v2EthPrtSwF2VlanInPQsOctetsTotal OBJECT-TYPE
   SYNTAX      Counter64
   MAX-ACCESS  read-only
   STATUS      current
   DESCRIPTION
      "Path: swPort.performance.vlan.inPriorityQueues.octets.total

       64 bit unsigned wrappable counter."
   ::= {pr1645v2EthPrtSwF2VlanInPQsEntry 67567616}

pr1645v2EthPrtSwF2VlanInPQsOctetsDirectTx OBJECT-TYPE
   SYNTAX      Counter64
   MAX-ACCESS  read-only
   STATUS      current
   DESCRIPTION
      "Path: swPort.performance.vlan.inPriorityQueues.octets.directTx

       64 bit unsigned wrappable counter."
   ::= {pr1645v2EthPrtSwF2VlanInPQsEntry 67174400}

pr1645v2EthPrtSwF2VlanInPQsOctetsQueued OBJECT-TYPE
   SYNTAX      Counter64
   MAX-ACCESS  read-only
   STATUS      current
   DESCRIPTION
      "Path: swPort.performance.vlan.inPriorityQueues.octets.queued

       64 bit unsigned wrappable counter."
   ::= {pr1645v2EthPrtSwF2VlanInPQsEntry 67239936}

pr1645v2EthPrtSwF2VlanInPQsOctetsDropped OBJECT-TYPE
   SYNTAX      Counter64
   MAX-ACCESS  read-only
   STATUS      current
   DESCRIPTION
      "Path: swPort.performance.vlan.inPriorityQueues.octets.dropped

       64 bit unsigned wrappable counter."
   ::= {pr1645v2EthPrtSwF2VlanInPQsEntry 67305472}

pr1645v2EthPrtSwF2VlanInPQsOctetsRedDropped OBJECT-TYPE
   SYNTAX      Counter64
   MAX-ACCESS  read-only
   STATUS      current
   DESCRIPTION
      "Path: swPort.performance.vlan.inPriorityQueues.octets.redDropped

       64 bit unsigned wrappable counter."
   ::= {pr1645v2EthPrtSwF2VlanInPQsEntry 67502080}

pr1645v2EthPrtSwF2VlanInPQsOctetsCirTx OBJECT-TYPE
   SYNTAX      Counter64
   MAX-ACCESS  read-only
   STATUS      current
   DESCRIPTION
      "Path: swPort.performance.vlan.inPriorityQueues.octets.cirTx

       64 bit unsigned wrappable counter."
   ::= {pr1645v2EthPrtSwF2VlanInPQsEntry 67371008}

pr1645v2EthPrtSwF2VlanInPQsOctetsEirTx OBJECT-TYPE
   SYNTAX      Counter64
   MAX-ACCESS  read-only
   STATUS      current
   DESCRIPTION
      "Path: swPort.performance.vlan.inPriorityQueues.octets.eirTx

       64 bit unsigned wrappable counter."
   ::= {pr1645v2EthPrtSwF2VlanInPQsEntry 67436544}

pr1645v2EthPrtSwF2VlanInPQsOctetsViolateTx OBJECT-TYPE
   SYNTAX      Counter64
   MAX-ACCESS  read-only
   STATUS      current
   DESCRIPTION
      "Path: swPort.performance.vlan.inPriorityQueues.octets.violateTx

       64 bit unsigned wrappable counter."
   ::= {pr1645v2EthPrtSwF2VlanInPQsEntry 67633152}

pr1645v2EthPrtSwF2VlanInPQsOctetsBandwidth15sec OBJECT-TYPE
   SYNTAX      Integer32
   MAX-ACCESS  read-only
   STATUS      current
   DESCRIPTION
      "Path: swPort.performance.vlan.inPriorityQueues.octets.bandwidth.15sec

       unit name = bps
       formula = 8 * ; 8 /"
   ::= {pr1645v2EthPrtSwF2VlanInPQsEntry 70386944}

pr1645v2EthPrtSwF2VlanInPQsOctetsBandwidth30sec OBJECT-TYPE
   SYNTAX      Integer32
   MAX-ACCESS  read-only
   STATUS      current
   DESCRIPTION
      "Path: swPort.performance.vlan.inPriorityQueues.octets.bandwidth.30sec

       unit name = bps
       formula = 8 * ; 8 /"
   ::= {pr1645v2EthPrtSwF2VlanInPQsEntry 70388224}

pr1645v2EthPrtSwF2VlanInPQsOctetsBandwidth1min OBJECT-TYPE
   SYNTAX      Integer32
   MAX-ACCESS  read-only
   STATUS      current
   DESCRIPTION
      "Path: swPort.performance.vlan.inPriorityQueues.octets.bandwidth.1min

       unit name = bps
       formula = 8 * ; 8 /"
   ::= {pr1645v2EthPrtSwF2VlanInPQsEntry 70390784}

pr1645v2EthPrtSwF2VlanInPQsOctetsBandwidth2min OBJECT-TYPE
   SYNTAX      Integer32
   MAX-ACCESS  read-only
   STATUS      current
   DESCRIPTION
      "Path: swPort.performance.vlan.inPriorityQueues.octets.bandwidth.2min

       unit name = bps
       formula = 8 * ; 8 /"
   ::= {pr1645v2EthPrtSwF2VlanInPQsEntry 70395904}

pr1645v2EthPrtSwF2VlanInPQsOctetsBandwidth5min OBJECT-TYPE
   SYNTAX      Integer32
   MAX-ACCESS  read-only
   STATUS      current
   DESCRIPTION
      "Path: swPort.performance.vlan.inPriorityQueues.octets.bandwidth.5min

       unit name = bps
       formula = 8 * ; 8 /"
   ::= {pr1645v2EthPrtSwF2VlanInPQsEntry 70411264}

pr1645v2EthPrtSwF2VlanInPQsH2Performance OBJECT-TYPE
   SYNTAX      SEQUENCE OF Pr1645v2EthPrtSwF2VlanInPQsH2PerformanceEntry
   MAX-ACCESS  not-accessible
   STATUS      current
   DESCRIPTION
      ""
   ::= {pr1645v2EthPrtSwF2Vlan 100990976}

pr1645v2EthPrtSwF2VlanInPQsH2PerformanceEntry OBJECT-TYPE
   SYNTAX      Pr1645v2EthPrtSwF2VlanInPQsH2PerformanceEntry
   MAX-ACCESS  not-accessible
   STATUS      current
   DESCRIPTION
      ""
   INDEX      { pr1645v2EthPrtSwF2VlanInPQsH2PerformanceGlobalIx,
                pr1645v2EthPrtSwF2VlanTableIx,
                pr1645v2EthPrtSwF2VlanInPQsTableIx,
                pr1645v2EthPrtSwF2VlanInPQsH2PerformanceTableIx }
   ::= {pr1645v2EthPrtSwF2VlanInPQsH2Performance 1}

Pr1645v2EthPrtSwF2VlanInPQsH2PerformanceEntry ::=
   SEQUENCE
      {
      pr1645v2EthPrtSwF2VlanInPQsH2PerformanceGlobalIx
         GlobalIndex,
      pr1645v2EthPrtSwF2VlanInPQsH2PerformanceTableIx
         TableIndex,
      pr1645v2EthPrtSwF2VlanInPQsH2PerformanceSysUpTime
         TimeTicks,
      pr1645v2EthPrtSwF2VlanInPQsH2PerformanceTotPkts
         Counter64,
      pr1645v2EthPrtSwF2VlanInPQsH2PerformanceDirTxPkts
         Counter64,
      pr1645v2EthPrtSwF2VlanInPQsH2PerformanceQdPkts
         Counter64,
      pr1645v2EthPrtSwF2VlanInPQsH2PerformanceDropPkts
         Counter64,
      pr1645v2EthPrtSwF2VlanInPQsH2PerformanceRDropPkts
         Counter64,
      pr1645v2EthPrtSwF2VlanInPQsH2PerformanceCirTxPkts
         Counter64,
      pr1645v2EthPrtSwF2VlanInPQsH2PerformanceEirTxPkts
         Counter64,
      pr1645v2EthPrtSwF2VlanInPQsH2PerformanceViolTxPkts
         Counter64,
      pr1645v2EthPrtSwF2VlanInPQsH2PerformanceTotOcts
         Counter64,
      pr1645v2EthPrtSwF2VlanInPQsH2PerformanceDirTxOcts
         Counter64,
      pr1645v2EthPrtSwF2VlanInPQsH2PerformanceQdOcts
         Counter64,
      pr1645v2EthPrtSwF2VlanInPQsH2PerformanceDropOcts
         Counter64,
      pr1645v2EthPrtSwF2VlanInPQsH2PerformanceRDropOcts
         Counter64,
      pr1645v2EthPrtSwF2VlanInPQsH2PerformanceCirTxOcts
         Counter64,
      pr1645v2EthPrtSwF2VlanInPQsH2PerformanceEirTxOcts
         Counter64,
      pr1645v2EthPrtSwF2VlanInPQsH2PerformanceViolTxOcts
         Counter64,
      pr1645v2EthPrtSwF2VlanInPQsH2PerformanceBandwidth
         Integer32
      }

pr1645v2EthPrtSwF2VlanInPQsH2PerformanceGlobalIx OBJECT-TYPE
   SYNTAX      GlobalIndex
   MAX-ACCESS  not-accessible
   STATUS      current
   DESCRIPTION
      "The value of the tlsCntTreeGlobalIndex of the MANAGED OBJECT."
   ::= {pr1645v2EthPrtSwF2VlanInPQsH2PerformanceEntry 10}

pr1645v2EthPrtSwF2VlanInPQsH2PerformanceTableIx OBJECT-TYPE
   SYNTAX      TableIndex
   MAX-ACCESS  not-accessible
   STATUS      current
   DESCRIPTION
      ""
   ::= {pr1645v2EthPrtSwF2VlanInPQsH2PerformanceEntry 11}

pr1645v2EthPrtSwF2VlanInPQsH2PerformanceSysUpTime OBJECT-TYPE
   SYNTAX      TimeTicks
   MAX-ACCESS  read-only
   STATUS      current
   DESCRIPTION
      "Path: swPort.performance.vlan.inPriorityQueues.h2Performance.sysUpTime

       Time in centi-second."
   ::= {pr1645v2EthPrtSwF2VlanInPQsH2PerformanceEntry 16777216}

pr1645v2EthPrtSwF2VlanInPQsH2PerformanceTotPkts OBJECT-TYPE
   SYNTAX      Counter64
   MAX-ACCESS  read-only
   STATUS      current
   DESCRIPTION
      "Path: swPort.performance.vlan.inPriorityQueues.h2Performance.totalPkts

       64 bit unsigned wrappable counter."
   ::= {pr1645v2EthPrtSwF2VlanInPQsH2PerformanceEntry 234881024}

pr1645v2EthPrtSwF2VlanInPQsH2PerformanceDirTxPkts OBJECT-TYPE
   SYNTAX      Counter64
   MAX-ACCESS  read-only
   STATUS      current
   DESCRIPTION
      "Path: swPort.performance.vlan.inPriorityQueues.h2Performance.directTxPkts

       64 bit unsigned wrappable counter."
   ::= {pr1645v2EthPrtSwF2VlanInPQsH2PerformanceEntry 33554432}

pr1645v2EthPrtSwF2VlanInPQsH2PerformanceQdPkts OBJECT-TYPE
   SYNTAX      Counter64
   MAX-ACCESS  read-only
   STATUS      current
   DESCRIPTION
      "Path: swPort.performance.vlan.inPriorityQueues.h2Performance.queuedPkts

       64 bit unsigned wrappable counter."
   ::= {pr1645v2EthPrtSwF2VlanInPQsH2PerformanceEntry 50331648}

pr1645v2EthPrtSwF2VlanInPQsH2PerformanceDropPkts OBJECT-TYPE
   SYNTAX      Counter64
   MAX-ACCESS  read-only
   STATUS      current
   DESCRIPTION
      "Path: swPort.performance.vlan.inPriorityQueues.h2Performance.droppedPkts

       64 bit unsigned wrappable counter."
   ::= {pr1645v2EthPrtSwF2VlanInPQsH2PerformanceEntry 67108864}

pr1645v2EthPrtSwF2VlanInPQsH2PerformanceRDropPkts OBJECT-TYPE
   SYNTAX      Counter64
   MAX-ACCESS  read-only
   STATUS      current
   DESCRIPTION
      "Path: swPort.performance.vlan.inPriorityQueues.h2Performance.redDroppedPkts

       64 bit unsigned wrappable counter."
   ::= {pr1645v2EthPrtSwF2VlanInPQsH2PerformanceEntry 201326592}

pr1645v2EthPrtSwF2VlanInPQsH2PerformanceCirTxPkts OBJECT-TYPE
   SYNTAX      Counter64
   MAX-ACCESS  read-only
   STATUS      current
   DESCRIPTION
      "Path: swPort.performance.vlan.inPriorityQueues.h2Performance.cirTxPkts

       64 bit unsigned wrappable counter."
   ::= {pr1645v2EthPrtSwF2VlanInPQsH2PerformanceEntry 83886080}

pr1645v2EthPrtSwF2VlanInPQsH2PerformanceEirTxPkts OBJECT-TYPE
   SYNTAX      Counter64
   MAX-ACCESS  read-only
   STATUS      current
   DESCRIPTION
      "Path: swPort.performance.vlan.inPriorityQueues.h2Performance.eirTxPkts

       64 bit unsigned wrappable counter."
   ::= {pr1645v2EthPrtSwF2VlanInPQsH2PerformanceEntry 100663296}

pr1645v2EthPrtSwF2VlanInPQsH2PerformanceViolTxPkts OBJECT-TYPE
   SYNTAX      Counter64
   MAX-ACCESS  read-only
   STATUS      current
   DESCRIPTION
      "Path: swPort.performance.vlan.inPriorityQueues.h2Performance.violateTxPkts

       64 bit unsigned wrappable counter."
   ::= {pr1645v2EthPrtSwF2VlanInPQsH2PerformanceEntry 301989888}

pr1645v2EthPrtSwF2VlanInPQsH2PerformanceTotOcts OBJECT-TYPE
   SYNTAX      Counter64
   MAX-ACCESS  read-only
   STATUS      current
   DESCRIPTION
      "Path: swPort.performance.vlan.inPriorityQueues.h2Performance.totalOctets

       64 bit unsigned wrappable counter."
   ::= {pr1645v2EthPrtSwF2VlanInPQsH2PerformanceEntry 251658240}

pr1645v2EthPrtSwF2VlanInPQsH2PerformanceDirTxOcts OBJECT-TYPE
   SYNTAX      Counter64
   MAX-ACCESS  read-only
   STATUS      current
   DESCRIPTION
      "Path: swPort.performance.vlan.inPriorityQueues.h2Performance.directTxOctets

       64 bit unsigned wrappable counter."
   ::= {pr1645v2EthPrtSwF2VlanInPQsH2PerformanceEntry 117440512}

pr1645v2EthPrtSwF2VlanInPQsH2PerformanceQdOcts OBJECT-TYPE
   SYNTAX      Counter64
   MAX-ACCESS  read-only
   STATUS      current
   DESCRIPTION
      "Path: swPort.performance.vlan.inPriorityQueues.h2Performance.queuedOctets

       64 bit unsigned wrappable counter."
   ::= {pr1645v2EthPrtSwF2VlanInPQsH2PerformanceEntry 134217728}

pr1645v2EthPrtSwF2VlanInPQsH2PerformanceDropOcts OBJECT-TYPE
   SYNTAX      Counter64
   MAX-ACCESS  read-only
   STATUS      current
   DESCRIPTION
      "Path: swPort.performance.vlan.inPriorityQueues.h2Performance.droppedOctets

       64 bit unsigned wrappable counter."
   ::= {pr1645v2EthPrtSwF2VlanInPQsH2PerformanceEntry 150994944}

pr1645v2EthPrtSwF2VlanInPQsH2PerformanceRDropOcts OBJECT-TYPE
   SYNTAX      Counter64
   MAX-ACCESS  read-only
   STATUS      current
   DESCRIPTION
      "Path: swPort.performance.vlan.inPriorityQueues.h2Performance.redDroppedOctets

       64 bit unsigned wrappable counter."
   ::= {pr1645v2EthPrtSwF2VlanInPQsH2PerformanceEntry 218103808}

pr1645v2EthPrtSwF2VlanInPQsH2PerformanceCirTxOcts OBJECT-TYPE
   SYNTAX      Counter64
   MAX-ACCESS  read-only
   STATUS      current
   DESCRIPTION
      "Path: swPort.performance.vlan.inPriorityQueues.h2Performance.cirTxOctets

       64 bit unsigned wrappable counter."
   ::= {pr1645v2EthPrtSwF2VlanInPQsH2PerformanceEntry 167772160}

pr1645v2EthPrtSwF2VlanInPQsH2PerformanceEirTxOcts OBJECT-TYPE
   SYNTAX      Counter64
   MAX-ACCESS  read-only
   STATUS      current
   DESCRIPTION
      "Path: swPort.performance.vlan.inPriorityQueues.h2Performance.eirTxOctets

       64 bit unsigned wrappable counter."
   ::= {pr1645v2EthPrtSwF2VlanInPQsH2PerformanceEntry 184549376}

pr1645v2EthPrtSwF2VlanInPQsH2PerformanceViolTxOcts OBJECT-TYPE
   SYNTAX      Counter64
   MAX-ACCESS  read-only
   STATUS      current
   DESCRIPTION
      "Path: swPort.performance.vlan.inPriorityQueues.h2Performance.violateTxOctets

       64 bit unsigned wrappable counter."
   ::= {pr1645v2EthPrtSwF2VlanInPQsH2PerformanceEntry 318767104}

pr1645v2EthPrtSwF2VlanInPQsH2PerformanceBandwidth OBJECT-TYPE
   SYNTAX      Integer32
   MAX-ACCESS  read-only
   STATUS      current
   DESCRIPTION
      "Path: swPort.performance.vlan.inPriorityQueues.h2Performance.bandwidth

       unit name = bps
       formula = 8 * ; 8 /"
   ::= {pr1645v2EthPrtSwF2VlanInPQsH2PerformanceEntry 268435456}

pr1645v2EthPrtSwF2VlanInPQsH24Performance OBJECT-TYPE
   SYNTAX      SEQUENCE OF Pr1645v2EthPrtSwF2VlanInPQsH24PerformanceEntry
   MAX-ACCESS  not-accessible
   STATUS      current
   DESCRIPTION
      ""
   ::= {pr1645v2EthPrtSwF2Vlan 101056512}

pr1645v2EthPrtSwF2VlanInPQsH24PerformanceEntry OBJECT-TYPE
   SYNTAX      Pr1645v2EthPrtSwF2VlanInPQsH24PerformanceEntry
   MAX-ACCESS  not-accessible
   STATUS      current
   DESCRIPTION
      ""
   INDEX      { pr1645v2EthPrtSwF2VlanInPQsH24PerformanceGlobalIx,
                pr1645v2EthPrtSwF2VlanTableIx,
                pr1645v2EthPrtSwF2VlanInPQsTableIx,
                pr1645v2EthPrtSwF2VlanInPQsH24PerformanceTableIx }
   ::= {pr1645v2EthPrtSwF2VlanInPQsH24Performance 1}

Pr1645v2EthPrtSwF2VlanInPQsH24PerformanceEntry ::=
   SEQUENCE
      {
      pr1645v2EthPrtSwF2VlanInPQsH24PerformanceGlobalIx
         GlobalIndex,
      pr1645v2EthPrtSwF2VlanInPQsH24PerformanceTableIx
         TableIndex,
      pr1645v2EthPrtSwF2VlanInPQsH24PerformanceSysUpTime
         TimeTicks,
      pr1645v2EthPrtSwF2VlanInPQsH24PerformanceTotPkts
         Counter64,
      pr1645v2EthPrtSwF2VlanInPQsH24PerformanceDirTxPkts
         Counter64,
      pr1645v2EthPrtSwF2VlanInPQsH24PerformanceQdPkts
         Counter64,
      pr1645v2EthPrtSwF2VlanInPQsH24PerformanceDropPkts
         Counter64,
      pr1645v2EthPrtSwF2VlanInPQsH24PerformanceRDropPkts
         Counter64,
      pr1645v2EthPrtSwF2VlanInPQsH24PerformanceCirTxPkts
         Counter64,
      pr1645v2EthPrtSwF2VlanInPQsH24PerformanceEirTxPkts
         Counter64,
      pr1645v2EthPrtSwF2VlanInPQsH24PerformanceViolTxPkts
         Counter64,
      pr1645v2EthPrtSwF2VlanInPQsH24PerformanceTotOcts
         Counter64,
      pr1645v2EthPrtSwF2VlanInPQsH24PerformanceDirTxOcts
         Counter64,
      pr1645v2EthPrtSwF2VlanInPQsH24PerformanceQdOcts
         Counter64,
      pr1645v2EthPrtSwF2VlanInPQsH24PerformanceDropOcts
         Counter64,
      pr1645v2EthPrtSwF2VlanInPQsH24PerformanceRDropOcts
         Counter64,
      pr1645v2EthPrtSwF2VlanInPQsH24PerformanceCirTxOcts
         Counter64,
      pr1645v2EthPrtSwF2VlanInPQsH24PerformanceEirTxOcts
         Counter64,
      pr1645v2EthPrtSwF2VlanInPQsH24PerformanceViolTxOcts
         Counter64,
      pr1645v2EthPrtSwF2VlanInPQsH24PerformanceBandwidth
         Integer32
      }

pr1645v2EthPrtSwF2VlanInPQsH24PerformanceGlobalIx OBJECT-TYPE
   SYNTAX      GlobalIndex
   MAX-ACCESS  not-accessible
   STATUS      current
   DESCRIPTION
      "The value of the tlsCntTreeGlobalIndex of the MANAGED OBJECT."
   ::= {pr1645v2EthPrtSwF2VlanInPQsH24PerformanceEntry 10}

pr1645v2EthPrtSwF2VlanInPQsH24PerformanceTableIx OBJECT-TYPE
   SYNTAX      TableIndex
   MAX-ACCESS  not-accessible
   STATUS      current
   DESCRIPTION
      ""
   ::= {pr1645v2EthPrtSwF2VlanInPQsH24PerformanceEntry 11}

pr1645v2EthPrtSwF2VlanInPQsH24PerformanceSysUpTime OBJECT-TYPE
   SYNTAX      TimeTicks
   MAX-ACCESS  read-only
   STATUS      current
   DESCRIPTION
      "Path: swPort.performance.vlan.inPriorityQueues.h24Performance.sysUpTime

       Time in centi-second."
   ::= {pr1645v2EthPrtSwF2VlanInPQsH24PerformanceEntry 16777216}

pr1645v2EthPrtSwF2VlanInPQsH24PerformanceTotPkts OBJECT-TYPE
   SYNTAX      Counter64
   MAX-ACCESS  read-only
   STATUS      current
   DESCRIPTION
      "Path: swPort.performance.vlan.inPriorityQueues.h24Performance.totalPkts

       64 bit unsigned wrappable counter."
   ::= {pr1645v2EthPrtSwF2VlanInPQsH24PerformanceEntry 234881024}

pr1645v2EthPrtSwF2VlanInPQsH24PerformanceDirTxPkts OBJECT-TYPE
   SYNTAX      Counter64
   MAX-ACCESS  read-only
   STATUS      current
   DESCRIPTION
      "Path: swPort.performance.vlan.inPriorityQueues.h24Performance.directTxPkts

       64 bit unsigned wrappable counter."
   ::= {pr1645v2EthPrtSwF2VlanInPQsH24PerformanceEntry 33554432}

pr1645v2EthPrtSwF2VlanInPQsH24PerformanceQdPkts OBJECT-TYPE
   SYNTAX      Counter64
   MAX-ACCESS  read-only
   STATUS      current
   DESCRIPTION
      "Path: swPort.performance.vlan.inPriorityQueues.h24Performance.queuedPkts

       64 bit unsigned wrappable counter."
   ::= {pr1645v2EthPrtSwF2VlanInPQsH24PerformanceEntry 50331648}

pr1645v2EthPrtSwF2VlanInPQsH24PerformanceDropPkts OBJECT-TYPE
   SYNTAX      Counter64
   MAX-ACCESS  read-only
   STATUS      current
   DESCRIPTION
      "Path: swPort.performance.vlan.inPriorityQueues.h24Performance.droppedPkts

       64 bit unsigned wrappable counter."
   ::= {pr1645v2EthPrtSwF2VlanInPQsH24PerformanceEntry 67108864}

pr1645v2EthPrtSwF2VlanInPQsH24PerformanceRDropPkts OBJECT-TYPE
   SYNTAX      Counter64
   MAX-ACCESS  read-only
   STATUS      current
   DESCRIPTION
      "Path: swPort.performance.vlan.inPriorityQueues.h24Performance.redDroppedPkts

       64 bit unsigned wrappable counter."
   ::= {pr1645v2EthPrtSwF2VlanInPQsH24PerformanceEntry 201326592}

pr1645v2EthPrtSwF2VlanInPQsH24PerformanceCirTxPkts OBJECT-TYPE
   SYNTAX      Counter64
   MAX-ACCESS  read-only
   STATUS      current
   DESCRIPTION
      "Path: swPort.performance.vlan.inPriorityQueues.h24Performance.cirTxPkts

       64 bit unsigned wrappable counter."
   ::= {pr1645v2EthPrtSwF2VlanInPQsH24PerformanceEntry 83886080}

pr1645v2EthPrtSwF2VlanInPQsH24PerformanceEirTxPkts OBJECT-TYPE
   SYNTAX      Counter64
   MAX-ACCESS  read-only
   STATUS      current
   DESCRIPTION
      "Path: swPort.performance.vlan.inPriorityQueues.h24Performance.eirTxPkts

       64 bit unsigned wrappable counter."
   ::= {pr1645v2EthPrtSwF2VlanInPQsH24PerformanceEntry 100663296}

pr1645v2EthPrtSwF2VlanInPQsH24PerformanceViolTxPkts OBJECT-TYPE
   SYNTAX      Counter64
   MAX-ACCESS  read-only
   STATUS      current
   DESCRIPTION
      "Path: swPort.performance.vlan.inPriorityQueues.h24Performance.violateTxPkts

       64 bit unsigned wrappable counter."
   ::= {pr1645v2EthPrtSwF2VlanInPQsH24PerformanceEntry 301989888}

pr1645v2EthPrtSwF2VlanInPQsH24PerformanceTotOcts OBJECT-TYPE
   SYNTAX      Counter64
   MAX-ACCESS  read-only
   STATUS      current
   DESCRIPTION
      "Path: swPort.performance.vlan.inPriorityQueues.h24Performance.totalOctets

       64 bit unsigned wrappable counter."
   ::= {pr1645v2EthPrtSwF2VlanInPQsH24PerformanceEntry 251658240}

pr1645v2EthPrtSwF2VlanInPQsH24PerformanceDirTxOcts OBJECT-TYPE
   SYNTAX      Counter64
   MAX-ACCESS  read-only
   STATUS      current
   DESCRIPTION
      "Path: swPort.performance.vlan.inPriorityQueues.h24Performance.directTxOctets

       64 bit unsigned wrappable counter."
   ::= {pr1645v2EthPrtSwF2VlanInPQsH24PerformanceEntry 117440512}

pr1645v2EthPrtSwF2VlanInPQsH24PerformanceQdOcts OBJECT-TYPE
   SYNTAX      Counter64
   MAX-ACCESS  read-only
   STATUS      current
   DESCRIPTION
      "Path: swPort.performance.vlan.inPriorityQueues.h24Performance.queuedOctets

       64 bit unsigned wrappable counter."
   ::= {pr1645v2EthPrtSwF2VlanInPQsH24PerformanceEntry 134217728}

pr1645v2EthPrtSwF2VlanInPQsH24PerformanceDropOcts OBJECT-TYPE
   SYNTAX      Counter64
   MAX-ACCESS  read-only
   STATUS      current
   DESCRIPTION
      "Path: swPort.performance.vlan.inPriorityQueues.h24Performance.droppedOctets

       64 bit unsigned wrappable counter."
   ::= {pr1645v2EthPrtSwF2VlanInPQsH24PerformanceEntry 150994944}

pr1645v2EthPrtSwF2VlanInPQsH24PerformanceRDropOcts OBJECT-TYPE
   SYNTAX      Counter64
   MAX-ACCESS  read-only
   STATUS      current
   DESCRIPTION
      "Path: swPort.performance.vlan.inPriorityQueues.h24Performance.redDroppedOctets

       64 bit unsigned wrappable counter."
   ::= {pr1645v2EthPrtSwF2VlanInPQsH24PerformanceEntry 218103808}

pr1645v2EthPrtSwF2VlanInPQsH24PerformanceCirTxOcts OBJECT-TYPE
   SYNTAX      Counter64
   MAX-ACCESS  read-only
   STATUS      current
   DESCRIPTION
      "Path: swPort.performance.vlan.inPriorityQueues.h24Performance.cirTxOctets

       64 bit unsigned wrappable counter."
   ::= {pr1645v2EthPrtSwF2VlanInPQsH24PerformanceEntry 167772160}

pr1645v2EthPrtSwF2VlanInPQsH24PerformanceEirTxOcts OBJECT-TYPE
   SYNTAX      Counter64
   MAX-ACCESS  read-only
   STATUS      current
   DESCRIPTION
      "Path: swPort.performance.vlan.inPriorityQueues.h24Performance.eirTxOctets

       64 bit unsigned wrappable counter."
   ::= {pr1645v2EthPrtSwF2VlanInPQsH24PerformanceEntry 184549376}

pr1645v2EthPrtSwF2VlanInPQsH24PerformanceViolTxOcts OBJECT-TYPE
   SYNTAX      Counter64
   MAX-ACCESS  read-only
   STATUS      current
   DESCRIPTION
      "Path: swPort.performance.vlan.inPriorityQueues.h24Performance.violateTxOctets

       64 bit unsigned wrappable counter."
   ::= {pr1645v2EthPrtSwF2VlanInPQsH24PerformanceEntry 318767104}

pr1645v2EthPrtSwF2VlanInPQsH24PerformanceBandwidth OBJECT-TYPE
   SYNTAX      Integer32
   MAX-ACCESS  read-only
   STATUS      current
   DESCRIPTION
      "Path: swPort.performance.vlan.inPriorityQueues.h24Performance.bandwidth

       unit name = bps
       formula = 8 * ; 8 /"
   ::= {pr1645v2EthPrtSwF2VlanInPQsH24PerformanceEntry 268435456}

pr1645v2EthPrtSwF2VlanInPQsD7Performance OBJECT-TYPE
   SYNTAX      SEQUENCE OF Pr1645v2EthPrtSwF2VlanInPQsD7PerformanceEntry
   MAX-ACCESS  not-accessible
   STATUS      current
   DESCRIPTION
      ""
   ::= {pr1645v2EthPrtSwF2Vlan 101122048}

pr1645v2EthPrtSwF2VlanInPQsD7PerformanceEntry OBJECT-TYPE
   SYNTAX      Pr1645v2EthPrtSwF2VlanInPQsD7PerformanceEntry
   MAX-ACCESS  not-accessible
   STATUS      current
   DESCRIPTION
      ""
   INDEX      { pr1645v2EthPrtSwF2VlanInPQsD7PerformanceGlobalIx,
                pr1645v2EthPrtSwF2VlanTableIx,
                pr1645v2EthPrtSwF2VlanInPQsTableIx,
                pr1645v2EthPrtSwF2VlanInPQsD7PerformanceTableIx }
   ::= {pr1645v2EthPrtSwF2VlanInPQsD7Performance 1}

Pr1645v2EthPrtSwF2VlanInPQsD7PerformanceEntry ::=
   SEQUENCE
      {
      pr1645v2EthPrtSwF2VlanInPQsD7PerformanceGlobalIx
         GlobalIndex,
      pr1645v2EthPrtSwF2VlanInPQsD7PerformanceTableIx
         TableIndex,
      pr1645v2EthPrtSwF2VlanInPQsD7PerformanceSysUpTime
         TimeTicks,
      pr1645v2EthPrtSwF2VlanInPQsD7PerformanceTotPkts
         Counter64,
      pr1645v2EthPrtSwF2VlanInPQsD7PerformanceDirTxPkts
         Counter64,
      pr1645v2EthPrtSwF2VlanInPQsD7PerformanceQdPkts
         Counter64,
      pr1645v2EthPrtSwF2VlanInPQsD7PerformanceDropPkts
         Counter64,
      pr1645v2EthPrtSwF2VlanInPQsD7PerformanceRDropPkts
         Counter64,
      pr1645v2EthPrtSwF2VlanInPQsD7PerformanceCirTxPkts
         Counter64,
      pr1645v2EthPrtSwF2VlanInPQsD7PerformanceEirTxPkts
         Counter64,
      pr1645v2EthPrtSwF2VlanInPQsD7PerformanceViolTxPkts
         Counter64,
      pr1645v2EthPrtSwF2VlanInPQsD7PerformanceTotOcts
         Counter64,
      pr1645v2EthPrtSwF2VlanInPQsD7PerformanceDirTxOcts
         Counter64,
      pr1645v2EthPrtSwF2VlanInPQsD7PerformanceQdOcts
         Counter64,
      pr1645v2EthPrtSwF2VlanInPQsD7PerformanceDropOcts
         Counter64,
      pr1645v2EthPrtSwF2VlanInPQsD7PerformanceRDropOcts
         Counter64,
      pr1645v2EthPrtSwF2VlanInPQsD7PerformanceCirTxOcts
         Counter64,
      pr1645v2EthPrtSwF2VlanInPQsD7PerformanceEirTxOcts
         Counter64,
      pr1645v2EthPrtSwF2VlanInPQsD7PerformanceViolTxOcts
         Counter64,
      pr1645v2EthPrtSwF2VlanInPQsD7PerformanceBandwidth
         Integer32
      }

pr1645v2EthPrtSwF2VlanInPQsD7PerformanceGlobalIx OBJECT-TYPE
   SYNTAX      GlobalIndex
   MAX-ACCESS  not-accessible
   STATUS      current
   DESCRIPTION
      "The value of the tlsCntTreeGlobalIndex of the MANAGED OBJECT."
   ::= {pr1645v2EthPrtSwF2VlanInPQsD7PerformanceEntry 10}

pr1645v2EthPrtSwF2VlanInPQsD7PerformanceTableIx OBJECT-TYPE
   SYNTAX      TableIndex
   MAX-ACCESS  not-accessible
   STATUS      current
   DESCRIPTION
      ""
   ::= {pr1645v2EthPrtSwF2VlanInPQsD7PerformanceEntry 11}

pr1645v2EthPrtSwF2VlanInPQsD7PerformanceSysUpTime OBJECT-TYPE
   SYNTAX      TimeTicks
   MAX-ACCESS  read-only
   STATUS      current
   DESCRIPTION
      "Path: swPort.performance.vlan.inPriorityQueues.d7Performance.sysUpTime

       Time in centi-second."
   ::= {pr1645v2EthPrtSwF2VlanInPQsD7PerformanceEntry 16777216}

pr1645v2EthPrtSwF2VlanInPQsD7PerformanceTotPkts OBJECT-TYPE
   SYNTAX      Counter64
   MAX-ACCESS  read-only
   STATUS      current
   DESCRIPTION
      "Path: swPort.performance.vlan.inPriorityQueues.d7Performance.totalPkts

       64 bit unsigned wrappable counter."
   ::= {pr1645v2EthPrtSwF2VlanInPQsD7PerformanceEntry 234881024}

pr1645v2EthPrtSwF2VlanInPQsD7PerformanceDirTxPkts OBJECT-TYPE
   SYNTAX      Counter64
   MAX-ACCESS  read-only
   STATUS      current
   DESCRIPTION
      "Path: swPort.performance.vlan.inPriorityQueues.d7Performance.directTxPkts

       64 bit unsigned wrappable counter."
   ::= {pr1645v2EthPrtSwF2VlanInPQsD7PerformanceEntry 33554432}

pr1645v2EthPrtSwF2VlanInPQsD7PerformanceQdPkts OBJECT-TYPE
   SYNTAX      Counter64
   MAX-ACCESS  read-only
   STATUS      current
   DESCRIPTION
      "Path: swPort.performance.vlan.inPriorityQueues.d7Performance.queuedPkts

       64 bit unsigned wrappable counter."
   ::= {pr1645v2EthPrtSwF2VlanInPQsD7PerformanceEntry 50331648}

pr1645v2EthPrtSwF2VlanInPQsD7PerformanceDropPkts OBJECT-TYPE
   SYNTAX      Counter64
   MAX-ACCESS  read-only
   STATUS      current
   DESCRIPTION
      "Path: swPort.performance.vlan.inPriorityQueues.d7Performance.droppedPkts

       64 bit unsigned wrappable counter."
   ::= {pr1645v2EthPrtSwF2VlanInPQsD7PerformanceEntry 67108864}

pr1645v2EthPrtSwF2VlanInPQsD7PerformanceRDropPkts OBJECT-TYPE
   SYNTAX      Counter64
   MAX-ACCESS  read-only
   STATUS      current
   DESCRIPTION
      "Path: swPort.performance.vlan.inPriorityQueues.d7Performance.redDroppedPkts

       64 bit unsigned wrappable counter."
   ::= {pr1645v2EthPrtSwF2VlanInPQsD7PerformanceEntry 201326592}

pr1645v2EthPrtSwF2VlanInPQsD7PerformanceCirTxPkts OBJECT-TYPE
   SYNTAX      Counter64
   MAX-ACCESS  read-only
   STATUS      current
   DESCRIPTION
      "Path: swPort.performance.vlan.inPriorityQueues.d7Performance.cirTxPkts

       64 bit unsigned wrappable counter."
   ::= {pr1645v2EthPrtSwF2VlanInPQsD7PerformanceEntry 83886080}

pr1645v2EthPrtSwF2VlanInPQsD7PerformanceEirTxPkts OBJECT-TYPE
   SYNTAX      Counter64
   MAX-ACCESS  read-only
   STATUS      current
   DESCRIPTION
      "Path: swPort.performance.vlan.inPriorityQueues.d7Performance.eirTxPkts

       64 bit unsigned wrappable counter."
   ::= {pr1645v2EthPrtSwF2VlanInPQsD7PerformanceEntry 100663296}

pr1645v2EthPrtSwF2VlanInPQsD7PerformanceViolTxPkts OBJECT-TYPE
   SYNTAX      Counter64
   MAX-ACCESS  read-only
   STATUS      current
   DESCRIPTION
      "Path: swPort.performance.vlan.inPriorityQueues.d7Performance.violateTxPkts

       64 bit unsigned wrappable counter."
   ::= {pr1645v2EthPrtSwF2VlanInPQsD7PerformanceEntry 301989888}

pr1645v2EthPrtSwF2VlanInPQsD7PerformanceTotOcts OBJECT-TYPE
   SYNTAX      Counter64
   MAX-ACCESS  read-only
   STATUS      current
   DESCRIPTION
      "Path: swPort.performance.vlan.inPriorityQueues.d7Performance.totalOctets

       64 bit unsigned wrappable counter."
   ::= {pr1645v2EthPrtSwF2VlanInPQsD7PerformanceEntry 251658240}

pr1645v2EthPrtSwF2VlanInPQsD7PerformanceDirTxOcts OBJECT-TYPE
   SYNTAX      Counter64
   MAX-ACCESS  read-only
   STATUS      current
   DESCRIPTION
      "Path: swPort.performance.vlan.inPriorityQueues.d7Performance.directTxOctets

       64 bit unsigned wrappable counter."
   ::= {pr1645v2EthPrtSwF2VlanInPQsD7PerformanceEntry 117440512}

pr1645v2EthPrtSwF2VlanInPQsD7PerformanceQdOcts OBJECT-TYPE
   SYNTAX      Counter64
   MAX-ACCESS  read-only
   STATUS      current
   DESCRIPTION
      "Path: swPort.performance.vlan.inPriorityQueues.d7Performance.queuedOctets

       64 bit unsigned wrappable counter."
   ::= {pr1645v2EthPrtSwF2VlanInPQsD7PerformanceEntry 134217728}

pr1645v2EthPrtSwF2VlanInPQsD7PerformanceDropOcts OBJECT-TYPE
   SYNTAX      Counter64
   MAX-ACCESS  read-only
   STATUS      current
   DESCRIPTION
      "Path: swPort.performance.vlan.inPriorityQueues.d7Performance.droppedOctets

       64 bit unsigned wrappable counter."
   ::= {pr1645v2EthPrtSwF2VlanInPQsD7PerformanceEntry 150994944}

pr1645v2EthPrtSwF2VlanInPQsD7PerformanceRDropOcts OBJECT-TYPE
   SYNTAX      Counter64
   MAX-ACCESS  read-only
   STATUS      current
   DESCRIPTION
      "Path: swPort.performance.vlan.inPriorityQueues.d7Performance.redDroppedOctets

       64 bit unsigned wrappable counter."
   ::= {pr1645v2EthPrtSwF2VlanInPQsD7PerformanceEntry 218103808}

pr1645v2EthPrtSwF2VlanInPQsD7PerformanceCirTxOcts OBJECT-TYPE
   SYNTAX      Counter64
   MAX-ACCESS  read-only
   STATUS      current
   DESCRIPTION
      "Path: swPort.performance.vlan.inPriorityQueues.d7Performance.cirTxOctets

       64 bit unsigned wrappable counter."
   ::= {pr1645v2EthPrtSwF2VlanInPQsD7PerformanceEntry 167772160}

pr1645v2EthPrtSwF2VlanInPQsD7PerformanceEirTxOcts OBJECT-TYPE
   SYNTAX      Counter64
   MAX-ACCESS  read-only
   STATUS      current
   DESCRIPTION
      "Path: swPort.performance.vlan.inPriorityQueues.d7Performance.eirTxOctets

       64 bit unsigned wrappable counter."
   ::= {pr1645v2EthPrtSwF2VlanInPQsD7PerformanceEntry 184549376}

pr1645v2EthPrtSwF2VlanInPQsD7PerformanceViolTxOcts OBJECT-TYPE
   SYNTAX      Counter64
   MAX-ACCESS  read-only
   STATUS      current
   DESCRIPTION
      "Path: swPort.performance.vlan.inPriorityQueues.d7Performance.violateTxOctets

       64 bit unsigned wrappable counter."
   ::= {pr1645v2EthPrtSwF2VlanInPQsD7PerformanceEntry 318767104}

pr1645v2EthPrtSwF2VlanInPQsD7PerformanceBandwidth OBJECT-TYPE
   SYNTAX      Integer32
   MAX-ACCESS  read-only
   STATUS      current
   DESCRIPTION
      "Path: swPort.performance.vlan.inPriorityQueues.d7Performance.bandwidth

       unit name = bps
       formula = 8 * ; 8 /"
   ::= {pr1645v2EthPrtSwF2VlanInPQsD7PerformanceEntry 268435456}

pr1645v2EthPrtSwF2VlanOutPQs OBJECT-TYPE
   SYNTAX      SEQUENCE OF Pr1645v2EthPrtSwF2VlanOutPQsEntry
   MAX-ACCESS  not-accessible
   STATUS      current
   DESCRIPTION
      ""
   ::= {pr1645v2EthPrtSwF2Vlan 83886080}

pr1645v2EthPrtSwF2VlanOutPQsEntry OBJECT-TYPE
   SYNTAX      Pr1645v2EthPrtSwF2VlanOutPQsEntry
   MAX-ACCESS  not-accessible
   STATUS      current
   DESCRIPTION
      ""
   INDEX      { pr1645v2EthPrtSwF2VlanOutPQsGlobalIx,
                pr1645v2EthPrtSwF2VlanTableIx,
                pr1645v2EthPrtSwF2VlanOutPQsTableIx }
   ::= {pr1645v2EthPrtSwF2VlanOutPQs 1}

Pr1645v2EthPrtSwF2VlanOutPQsEntry ::=
   SEQUENCE
      {
      pr1645v2EthPrtSwF2VlanOutPQsGlobalIx
         GlobalIndex,
      pr1645v2EthPrtSwF2VlanOutPQsTableIx
         TableIndex,
      pr1645v2EthPrtSwF2VlanOutPQsName
         INTEGER,
      pr1645v2EthPrtSwF2VlanOutPQsLength
         Integer32,
      pr1645v2EthPrtSwF2VlanOutPQsOctetLength
         Integer32,
      pr1645v2EthPrtSwF2VlanOutPQsRedLength
         Integer32,
      pr1645v2EthPrtSwF2VlanOutPQsPacketsTotal
         Counter64,
      pr1645v2EthPrtSwF2VlanOutPQsPacketsDirectTx
         Counter64,
      pr1645v2EthPrtSwF2VlanOutPQsPacketsQueued
         Counter64,
      pr1645v2EthPrtSwF2VlanOutPQsPacketsDropped
         Counter64,
      pr1645v2EthPrtSwF2VlanOutPQsPacketsRedDropped
         Counter64,
      pr1645v2EthPrtSwF2VlanOutPQsPacketsCirTx
         Counter64,
      pr1645v2EthPrtSwF2VlanOutPQsPacketsEirTx
         Counter64,
      pr1645v2EthPrtSwF2VlanOutPQsPacketsViolateTx
         Counter64,
      pr1645v2EthPrtSwF2VlanOutPQsOctetsTotal
         Counter64,
      pr1645v2EthPrtSwF2VlanOutPQsOctetsDirectTx
         Counter64,
      pr1645v2EthPrtSwF2VlanOutPQsOctetsQueued
         Counter64,
      pr1645v2EthPrtSwF2VlanOutPQsOctetsDropped
         Counter64,
      pr1645v2EthPrtSwF2VlanOutPQsOctetsRedDropped
         Counter64,
      pr1645v2EthPrtSwF2VlanOutPQsOctetsCirTx
         Counter64,
      pr1645v2EthPrtSwF2VlanOutPQsOctetsEirTx
         Counter64,
      pr1645v2EthPrtSwF2VlanOutPQsOctetsViolateTx
         Counter64,
      pr1645v2EthPrtSwF2VlanOutPQsOctetsBandwidth15sec
         Integer32,
      pr1645v2EthPrtSwF2VlanOutPQsOctetsBandwidth30sec
         Integer32,
      pr1645v2EthPrtSwF2VlanOutPQsOctetsBandwidth1min
         Integer32,
      pr1645v2EthPrtSwF2VlanOutPQsOctetsBandwidth2min
         Integer32,
      pr1645v2EthPrtSwF2VlanOutPQsOctetsBandwidth5min
         Integer32
      }

pr1645v2EthPrtSwF2VlanOutPQsGlobalIx OBJECT-TYPE
   SYNTAX      GlobalIndex
   MAX-ACCESS  not-accessible
   STATUS      current
   DESCRIPTION
      "The value of the tlsCntTreeGlobalIndex of the MANAGED OBJECT."
   ::= {pr1645v2EthPrtSwF2VlanOutPQsEntry 10}

pr1645v2EthPrtSwF2VlanOutPQsTableIx OBJECT-TYPE
   SYNTAX      TableIndex
   MAX-ACCESS  not-accessible
   STATUS      current
   DESCRIPTION
      ""
   ::= {pr1645v2EthPrtSwF2VlanOutPQsEntry 11}

pr1645v2EthPrtSwF2VlanOutPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: swPort.performance.vlan.outPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2EthPrtSwF2VlanOutPQsEntry 16777216}

pr1645v2EthPrtSwF2VlanOutPQsLength OBJECT-TYPE
   SYNTAX      Integer32
   MAX-ACCESS  read-only
   STATUS      current
   DESCRIPTION
      "Path: swPort.performance.vlan.outPriorityQueues.length"
   ::= {pr1645v2EthPrtSwF2VlanOutPQsEntry 33554432}

pr1645v2EthPrtSwF2VlanOutPQsOctetLength OBJECT-TYPE
   SYNTAX      Integer32
   MAX-ACCESS  read-only
   STATUS      current
   DESCRIPTION
      "Path: swPort.performance.vlan.outPriorityQueues.octetLength"
   ::= {pr1645v2EthPrtSwF2VlanOutPQsEntry 150994944}

pr1645v2EthPrtSwF2VlanOutPQsRedLength OBJECT-TYPE
   SYNTAX      Integer32
   MAX-ACCESS  read-only
   STATUS      current
   DESCRIPTION
      "Path: swPort.performance.vlan.outPriorityQueues.redLength"
   ::= {pr1645v2EthPrtSwF2VlanOutPQsEntry 134217728}

pr1645v2EthPrtSwF2VlanOutPQsPacketsTotal OBJECT-TYPE
   SYNTAX      Counter64
   MAX-ACCESS  read-only
   STATUS      current
   DESCRIPTION
      "Path: swPort.performance.vlan.outPriorityQueues.packets.total

       64 bit unsigned wrappable counter."
   ::= {pr1645v2EthPrtSwF2VlanOutPQsEntry 50790400}

pr1645v2EthPrtSwF2VlanOutPQsPacketsDirectTx OBJECT-TYPE
   SYNTAX      Counter64
   MAX-ACCESS  read-only
   STATUS      current
   DESCRIPTION
      "Path: swPort.performance.vlan.outPriorityQueues.packets.directTx

       64 bit unsigned wrappable counter."
   ::= {pr1645v2EthPrtSwF2VlanOutPQsEntry 50397184}

pr1645v2EthPrtSwF2VlanOutPQsPacketsQueued OBJECT-TYPE
   SYNTAX      Counter64
   MAX-ACCESS  read-only
   STATUS      current
   DESCRIPTION
      "Path: swPort.performance.vlan.outPriorityQueues.packets.queued

       64 bit unsigned wrappable counter."
   ::= {pr1645v2EthPrtSwF2VlanOutPQsEntry 50462720}

pr1645v2EthPrtSwF2VlanOutPQsPacketsDropped OBJECT-TYPE
   SYNTAX      Counter64
   MAX-ACCESS  read-only
   STATUS      current
   DESCRIPTION
      "Path: swPort.performance.vlan.outPriorityQueues.packets.dropped

       64 bit unsigned wrappable counter."
   ::= {pr1645v2EthPrtSwF2VlanOutPQsEntry 50528256}

pr1645v2EthPrtSwF2VlanOutPQsPacketsRedDropped OBJECT-TYPE
   SYNTAX      Counter64
   MAX-ACCESS  read-only
   STATUS      current
   DESCRIPTION
      "Path: swPort.performance.vlan.outPriorityQueues.packets.redDropped

       64 bit unsigned wrappable counter."
   ::= {pr1645v2EthPrtSwF2VlanOutPQsEntry 50724864}

pr1645v2EthPrtSwF2VlanOutPQsPacketsCirTx OBJECT-TYPE
   SYNTAX      Counter64
   MAX-ACCESS  read-only
   STATUS      current
   DESCRIPTION
      "Path: swPort.performance.vlan.outPriorityQueues.packets.cirTx

       64 bit unsigned wrappable counter."
   ::= {pr1645v2EthPrtSwF2VlanOutPQsEntry 50593792}

pr1645v2EthPrtSwF2VlanOutPQsPacketsEirTx OBJECT-TYPE
   SYNTAX      Counter64
   MAX-ACCESS  read-only
   STATUS      current
   DESCRIPTION
      "Path: swPort.performance.vlan.outPriorityQueues.packets.eirTx

       64 bit unsigned wrappable counter."
   ::= {pr1645v2EthPrtSwF2VlanOutPQsEntry 50659328}

pr1645v2EthPrtSwF2VlanOutPQsPacketsViolateTx OBJECT-TYPE
   SYNTAX      Counter64
   MAX-ACCESS  read-only
   STATUS      current
   DESCRIPTION
      "Path: swPort.performance.vlan.outPriorityQueues.packets.violateTx

       64 bit unsigned wrappable counter."
   ::= {pr1645v2EthPrtSwF2VlanOutPQsEntry 50855936}

pr1645v2EthPrtSwF2VlanOutPQsOctetsTotal OBJECT-TYPE
   SYNTAX      Counter64
   MAX-ACCESS  read-only
   STATUS      current
   DESCRIPTION
      "Path: swPort.performance.vlan.outPriorityQueues.octets.total

       64 bit unsigned wrappable counter."
   ::= {pr1645v2EthPrtSwF2VlanOutPQsEntry 67567616}

pr1645v2EthPrtSwF2VlanOutPQsOctetsDirectTx OBJECT-TYPE
   SYNTAX      Counter64
   MAX-ACCESS  read-only
   STATUS      current
   DESCRIPTION
      "Path: swPort.performance.vlan.outPriorityQueues.octets.directTx

       64 bit unsigned wrappable counter."
   ::= {pr1645v2EthPrtSwF2VlanOutPQsEntry 67174400}

pr1645v2EthPrtSwF2VlanOutPQsOctetsQueued OBJECT-TYPE
   SYNTAX      Counter64
   MAX-ACCESS  read-only
   STATUS      current
   DESCRIPTION
      "Path: swPort.performance.vlan.outPriorityQueues.octets.queued

       64 bit unsigned wrappable counter."
   ::= {pr1645v2EthPrtSwF2VlanOutPQsEntry 67239936}

pr1645v2EthPrtSwF2VlanOutPQsOctetsDropped OBJECT-TYPE
   SYNTAX      Counter64
   MAX-ACCESS  read-only
   STATUS      current
   DESCRIPTION
      "Path: swPort.performance.vlan.outPriorityQueues.octets.dropped

       64 bit unsigned wrappable counter."
   ::= {pr1645v2EthPrtSwF2VlanOutPQsEntry 67305472}

pr1645v2EthPrtSwF2VlanOutPQsOctetsRedDropped OBJECT-TYPE
   SYNTAX      Counter64
   MAX-ACCESS  read-only
   STATUS      current
   DESCRIPTION
      "Path: swPort.performance.vlan.outPriorityQueues.octets.redDropped

       64 bit unsigned wrappable counter."
   ::= {pr1645v2EthPrtSwF2VlanOutPQsEntry 67502080}

pr1645v2EthPrtSwF2VlanOutPQsOctetsCirTx OBJECT-TYPE
   SYNTAX      Counter64
   MAX-ACCESS  read-only
   STATUS      current
   DESCRIPTION
      "Path: swPort.performance.vlan.outPriorityQueues.octets.cirTx

       64 bit unsigned wrappable counter."
   ::= {pr1645v2EthPrtSwF2VlanOutPQsEntry 67371008}

pr1645v2EthPrtSwF2VlanOutPQsOctetsEirTx OBJECT-TYPE
   SYNTAX      Counter64
   MAX-ACCESS  read-only
   STATUS      current
   DESCRIPTION
      "Path: swPort.performance.vlan.outPriorityQueues.octets.eirTx

       64 bit unsigned wrappable counter."
   ::= {pr1645v2EthPrtSwF2VlanOutPQsEntry 67436544}

pr1645v2EthPrtSwF2VlanOutPQsOctetsViolateTx OBJECT-TYPE
   SYNTAX      Counter64
   MAX-ACCESS  read-only
   STATUS      current
   DESCRIPTION
      "Path: swPort.performance.vlan.outPriorityQueues.octets.violateTx

       64 bit unsigned wrappable counter."
   ::= {pr1645v2EthPrtSwF2VlanOutPQsEntry 67633152}

pr1645v2EthPrtSwF2VlanOutPQsOctetsBandwidth15sec OBJECT-TYPE
   SYNTAX      Integer32
   MAX-ACCESS  read-only
   STATUS      current
   DESCRIPTION
      "Path: swPort.performance.vlan.outPriorityQueues.octets.bandwidth.15sec

       unit name = bps
       formula = 8 * ; 8 /"
   ::= {pr1645v2EthPrtSwF2VlanOutPQsEntry 70386944}

pr1645v2EthPrtSwF2VlanOutPQsOctetsBandwidth30sec OBJECT-TYPE
   SYNTAX      Integer32
   MAX-ACCESS  read-only
   STATUS      current
   DESCRIPTION
      "Path: swPort.performance.vlan.outPriorityQueues.octets.bandwidth.30sec

       unit name = bps
       formula = 8 * ; 8 /"
   ::= {pr1645v2EthPrtSwF2VlanOutPQsEntry 70388224}

pr1645v2EthPrtSwF2VlanOutPQsOctetsBandwidth1min OBJECT-TYPE
   SYNTAX      Integer32
   MAX-ACCESS  read-only
   STATUS      current
   DESCRIPTION
      "Path: swPort.performance.vlan.outPriorityQueues.octets.bandwidth.1min

       unit name = bps
       formula = 8 * ; 8 /"
   ::= {pr1645v2EthPrtSwF2VlanOutPQsEntry 70390784}

pr1645v2EthPrtSwF2VlanOutPQsOctetsBandwidth2min OBJECT-TYPE
   SYNTAX      Integer32
   MAX-ACCESS  read-only
   STATUS      current
   DESCRIPTION
      "Path: swPort.performance.vlan.outPriorityQueues.octets.bandwidth.2min

       unit name = bps
       formula = 8 * ; 8 /"
   ::= {pr1645v2EthPrtSwF2VlanOutPQsEntry 70395904}

pr1645v2EthPrtSwF2VlanOutPQsOctetsBandwidth5min OBJECT-TYPE
   SYNTAX      Integer32
   MAX-ACCESS  read-only
   STATUS      current
   DESCRIPTION
      "Path: swPort.performance.vlan.outPriorityQueues.octets.bandwidth.5min

       unit name = bps
       formula = 8 * ; 8 /"
   ::= {pr1645v2EthPrtSwF2VlanOutPQsEntry 70411264}

pr1645v2EthPrtSwF2VlanOutPQsH2Performance OBJECT-TYPE
   SYNTAX      SEQUENCE OF Pr1645v2EthPrtSwF2VlanOutPQsH2PerformanceEntry
   MAX-ACCESS  not-accessible
   STATUS      current
   DESCRIPTION
      ""
   ::= {pr1645v2EthPrtSwF2Vlan 84213760}

pr1645v2EthPrtSwF2VlanOutPQsH2PerformanceEntry OBJECT-TYPE
   SYNTAX      Pr1645v2EthPrtSwF2VlanOutPQsH2PerformanceEntry
   MAX-ACCESS  not-accessible
   STATUS      current
   DESCRIPTION
      ""
   INDEX      { pr1645v2EthPrtSwF2VlanOutPQsH2PerformanceGlobalIx,
                pr1645v2EthPrtSwF2VlanTableIx,
                pr1645v2EthPrtSwF2VlanOutPQsTableIx,
                pr1645v2EthPrtSwF2VlanOutPQsH2PerformanceTableIx }
   ::= {pr1645v2EthPrtSwF2VlanOutPQsH2Performance 1}

Pr1645v2EthPrtSwF2VlanOutPQsH2PerformanceEntry ::=
   SEQUENCE
      {
      pr1645v2EthPrtSwF2VlanOutPQsH2PerformanceGlobalIx
         GlobalIndex,
      pr1645v2EthPrtSwF2VlanOutPQsH2PerformanceTableIx
         TableIndex,
      pr1645v2EthPrtSwF2VlanOutPQsH2PerformanceSysUpTime
         TimeTicks,
      pr1645v2EthPrtSwF2VlanOutPQsH2PerformanceTotPkts
         Counter64,
      pr1645v2EthPrtSwF2VlanOutPQsH2PerformanceDirTxPkts
         Counter64,
      pr1645v2EthPrtSwF2VlanOutPQsH2PerformanceQdPkts
         Counter64,
      pr1645v2EthPrtSwF2VlanOutPQsH2PerformanceDropPkts
         Counter64,
      pr1645v2EthPrtSwF2VlanOutPQsH2PerformanceRDropPkts
         Counter64,
      pr1645v2EthPrtSwF2VlanOutPQsH2PerformanceCirTxPkts
         Counter64,
      pr1645v2EthPrtSwF2VlanOutPQsH2PerformanceEirTxPkts
         Counter64,
      pr1645v2EthPrtSwF2VlanOutPQsH2PerformanceViolTxPkts
         Counter64,
      pr1645v2EthPrtSwF2VlanOutPQsH2PerformanceTotOcts
         Counter64,
      pr1645v2EthPrtSwF2VlanOutPQsH2PerformanceDirTxOcts
         Counter64,
      pr1645v2EthPrtSwF2VlanOutPQsH2PerformanceQdOcts
         Counter64,
      pr1645v2EthPrtSwF2VlanOutPQsH2PerformanceDropOcts
         Counter64,
      pr1645v2EthPrtSwF2VlanOutPQsH2PerformanceRDropOcts
         Counter64,
      pr1645v2EthPrtSwF2VlanOutPQsH2PerformanceCirTxOcts
         Counter64,
      pr1645v2EthPrtSwF2VlanOutPQsH2PerformanceEirTxOcts
         Counter64,
      pr1645v2EthPrtSwF2VlanOutPQsH2PerformanceViolTxOcts
         Counter64,
      pr1645v2EthPrtSwF2VlanOutPQsH2PerformanceBandwidth
         Integer32
      }

pr1645v2EthPrtSwF2VlanOutPQsH2PerformanceGlobalIx OBJECT-TYPE
   SYNTAX      GlobalIndex
   MAX-ACCESS  not-accessible
   STATUS      current
   DESCRIPTION
      "The value of the tlsCntTreeGlobalIndex of the MANAGED OBJECT."
   ::= {pr1645v2EthPrtSwF2VlanOutPQsH2PerformanceEntry 10}

pr1645v2EthPrtSwF2VlanOutPQsH2PerformanceTableIx OBJECT-TYPE
   SYNTAX      TableIndex
   MAX-ACCESS  not-accessible
   STATUS      current
   DESCRIPTION
      ""
   ::= {pr1645v2EthPrtSwF2VlanOutPQsH2PerformanceEntry 11}

pr1645v2EthPrtSwF2VlanOutPQsH2PerformanceSysUpTime OBJECT-TYPE
   SYNTAX      TimeTicks
   MAX-ACCESS  read-only
   STATUS      current
   DESCRIPTION
      "Path: swPort.performance.vlan.outPriorityQueues.h2Performance.sysUpTime

       Time in centi-second."
   ::= {pr1645v2EthPrtSwF2VlanOutPQsH2PerformanceEntry 16777216}

pr1645v2EthPrtSwF2VlanOutPQsH2PerformanceTotPkts OBJECT-TYPE
   SYNTAX      Counter64
   MAX-ACCESS  read-only
   STATUS      current
   DESCRIPTION
      "Path: swPort.performance.vlan.outPriorityQueues.h2Performance.totalPkts

       64 bit unsigned wrappable counter."
   ::= {pr1645v2EthPrtSwF2VlanOutPQsH2PerformanceEntry 234881024}

pr1645v2EthPrtSwF2VlanOutPQsH2PerformanceDirTxPkts OBJECT-TYPE
   SYNTAX      Counter64
   MAX-ACCESS  read-only
   STATUS      current
   DESCRIPTION
      "Path: swPort.performance.vlan.outPriorityQueues.h2Performance.directTxPkts

       64 bit unsigned wrappable counter."
   ::= {pr1645v2EthPrtSwF2VlanOutPQsH2PerformanceEntry 33554432}

pr1645v2EthPrtSwF2VlanOutPQsH2PerformanceQdPkts OBJECT-TYPE
   SYNTAX      Counter64
   MAX-ACCESS  read-only
   STATUS      current
   DESCRIPTION
      "Path: swPort.performance.vlan.outPriorityQueues.h2Performance.queuedPkts

       64 bit unsigned wrappable counter."
   ::= {pr1645v2EthPrtSwF2VlanOutPQsH2PerformanceEntry 50331648}

pr1645v2EthPrtSwF2VlanOutPQsH2PerformanceDropPkts OBJECT-TYPE
   SYNTAX      Counter64
   MAX-ACCESS  read-only
   STATUS      current
   DESCRIPTION
      "Path: swPort.performance.vlan.outPriorityQueues.h2Performance.droppedPkts

       64 bit unsigned wrappable counter."
   ::= {pr1645v2EthPrtSwF2VlanOutPQsH2PerformanceEntry 67108864}

pr1645v2EthPrtSwF2VlanOutPQsH2PerformanceRDropPkts OBJECT-TYPE
   SYNTAX      Counter64
   MAX-ACCESS  read-only
   STATUS      current
   DESCRIPTION
      "Path: swPort.performance.vlan.outPriorityQueues.h2Performance.redDroppedPkts

       64 bit unsigned wrappable counter."
   ::= {pr1645v2EthPrtSwF2VlanOutPQsH2PerformanceEntry 201326592}

pr1645v2EthPrtSwF2VlanOutPQsH2PerformanceCirTxPkts OBJECT-TYPE
   SYNTAX      Counter64
   MAX-ACCESS  read-only
   STATUS      current
   DESCRIPTION
      "Path: swPort.performance.vlan.outPriorityQueues.h2Performance.cirTxPkts

       64 bit unsigned wrappable counter."
   ::= {pr1645v2EthPrtSwF2VlanOutPQsH2PerformanceEntry 83886080}

pr1645v2EthPrtSwF2VlanOutPQsH2PerformanceEirTxPkts OBJECT-TYPE
   SYNTAX      Counter64
   MAX-ACCESS  read-only
   STATUS      current
   DESCRIPTION
      "Path: swPort.performance.vlan.outPriorityQueues.h2Performance.eirTxPkts

       64 bit unsigned wrappable counter."
   ::= {pr1645v2EthPrtSwF2VlanOutPQsH2PerformanceEntry 100663296}

pr1645v2EthPrtSwF2VlanOutPQsH2PerformanceViolTxPkts OBJECT-TYPE
   SYNTAX      Counter64
   MAX-ACCESS  read-only
   STATUS      current
   DESCRIPTION
      "Path: swPort.performance.vlan.outPriorityQueues.h2Performance.violateTxPkts

       64 bit unsigned wrappable counter."
   ::= {pr1645v2EthPrtSwF2VlanOutPQsH2PerformanceEntry 301989888}

pr1645v2EthPrtSwF2VlanOutPQsH2PerformanceTotOcts OBJECT-TYPE
   SYNTAX      Counter64
   MAX-ACCESS  read-only
   STATUS      current
   DESCRIPTION
      "Path: swPort.performance.vlan.outPriorityQueues.h2Performance.totalOctets

       64 bit unsigned wrappable counter."
   ::= {pr1645v2EthPrtSwF2VlanOutPQsH2PerformanceEntry 251658240}

pr1645v2EthPrtSwF2VlanOutPQsH2PerformanceDirTxOcts OBJECT-TYPE
   SYNTAX      Counter64
   MAX-ACCESS  read-only
   STATUS      current
   DESCRIPTION
      "Path: swPort.performance.vlan.outPriorityQueues.h2Performance.directTxOctets

       64 bit unsigned wrappable counter."
   ::= {pr1645v2EthPrtSwF2VlanOutPQsH2PerformanceEntry 117440512}

pr1645v2EthPrtSwF2VlanOutPQsH2PerformanceQdOcts OBJECT-TYPE
   SYNTAX      Counter64
   MAX-ACCESS  read-only
   STATUS      current
   DESCRIPTION
      "Path: swPort.performance.vlan.outPriorityQueues.h2Performance.queuedOctets

       64 bit unsigned wrappable counter."
   ::= {pr1645v2EthPrtSwF2VlanOutPQsH2PerformanceEntry 134217728}

pr1645v2EthPrtSwF2VlanOutPQsH2PerformanceDropOcts OBJECT-TYPE
   SYNTAX      Counter64
   MAX-ACCESS  read-only
   STATUS      current
   DESCRIPTION
      "Path: swPort.performance.vlan.outPriorityQueues.h2Performance.droppedOctets

       64 bit unsigned wrappable counter."
   ::= {pr1645v2EthPrtSwF2VlanOutPQsH2PerformanceEntry 150994944}

pr1645v2EthPrtSwF2VlanOutPQsH2PerformanceRDropOcts OBJECT-TYPE
   SYNTAX      Counter64
   MAX-ACCESS  read-only
   STATUS      current
   DESCRIPTION
      "Path: swPort.performance.vlan.outPriorityQueues.h2Performance.redDroppedOctets

       64 bit unsigned wrappable counter."
   ::= {pr1645v2EthPrtSwF2VlanOutPQsH2PerformanceEntry 218103808}

pr1645v2EthPrtSwF2VlanOutPQsH2PerformanceCirTxOcts OBJECT-TYPE
   SYNTAX      Counter64
   MAX-ACCESS  read-only
   STATUS      current
   DESCRIPTION
      "Path: swPort.performance.vlan.outPriorityQueues.h2Performance.cirTxOctets

       64 bit unsigned wrappable counter."
   ::= {pr1645v2EthPrtSwF2VlanOutPQsH2PerformanceEntry 167772160}

pr1645v2EthPrtSwF2VlanOutPQsH2PerformanceEirTxOcts OBJECT-TYPE
   SYNTAX      Counter64
   MAX-ACCESS  read-only
   STATUS      current
   DESCRIPTION
      "Path: swPort.performance.vlan.outPriorityQueues.h2Performance.eirTxOctets

       64 bit unsigned wrappable counter."
   ::= {pr1645v2EthPrtSwF2VlanOutPQsH2PerformanceEntry 184549376}

pr1645v2EthPrtSwF2VlanOutPQsH2PerformanceViolTxOcts OBJECT-TYPE
   SYNTAX      Counter64
   MAX-ACCESS  read-only
   STATUS      current
   DESCRIPTION
      "Path: swPort.performance.vlan.outPriorityQueues.h2Performance.violateTxOctets

       64 bit unsigned wrappable counter."
   ::= {pr1645v2EthPrtSwF2VlanOutPQsH2PerformanceEntry 318767104}

pr1645v2EthPrtSwF2VlanOutPQsH2PerformanceBandwidth OBJECT-TYPE
   SYNTAX      Integer32
   MAX-ACCESS  read-only
   STATUS      current
   DESCRIPTION
      "Path: swPort.performance.vlan.outPriorityQueues.h2Performance.bandwidth

       unit name = bps
       formula = 8 * ; 8 /"
   ::= {pr1645v2EthPrtSwF2VlanOutPQsH2PerformanceEntry 268435456}

pr1645v2EthPrtSwF2VlanOutPQsH24Performance OBJECT-TYPE
   SYNTAX      SEQUENCE OF Pr1645v2EthPrtSwF2VlanOutPQsH24PerformanceEntry
   MAX-ACCESS  not-accessible
   STATUS      current
   DESCRIPTION
      ""
   ::= {pr1645v2EthPrtSwF2Vlan 84279296}

pr1645v2EthPrtSwF2VlanOutPQsH24PerformanceEntry OBJECT-TYPE
   SYNTAX      Pr1645v2EthPrtSwF2VlanOutPQsH24PerformanceEntry
   MAX-ACCESS  not-accessible
   STATUS      current
   DESCRIPTION
      ""
   INDEX      { pr1645v2EthPrtSwF2VlanOutPQsH24PerformanceGlobalIx,
                pr1645v2EthPrtSwF2VlanTableIx,
                pr1645v2EthPrtSwF2VlanOutPQsTableIx,
                pr1645v2EthPrtSwF2VlanOutPQsH24PerformanceTableIx }
   ::= {pr1645v2EthPrtSwF2VlanOutPQsH24Performance 1}

Pr1645v2EthPrtSwF2VlanOutPQsH24PerformanceEntry ::=
   SEQUENCE
      {
      pr1645v2EthPrtSwF2VlanOutPQsH24PerformanceGlobalIx
         GlobalIndex,
      pr1645v2EthPrtSwF2VlanOutPQsH24PerformanceTableIx
         TableIndex,
      pr1645v2EthPrtSwF2VlanOutPQsH24PerformanceSysUpTime
         TimeTicks,
      pr1645v2EthPrtSwF2VlanOutPQsH24PerformanceTotPkts
         Counter64,
      pr1645v2EthPrtSwF2VlanOutPQsH24PerformanceDirTxPkts
         Counter64,
      pr1645v2EthPrtSwF2VlanOutPQsH24PerformanceQdPkts
         Counter64,
      pr1645v2EthPrtSwF2VlanOutPQsH24PerformanceDropPkts
         Counter64,
      pr1645v2EthPrtSwF2VlanOutPQsH24PerformanceRDropPkts
         Counter64,
      pr1645v2EthPrtSwF2VlanOutPQsH24PerformanceCirTxPkts
         Counter64,
      pr1645v2EthPrtSwF2VlanOutPQsH24PerformanceEirTxPkts
         Counter64,
      pr1645v2EthPrtSwF2VlanOutPQsH24PerformanceViolTxPkts
         Counter64,
      pr1645v2EthPrtSwF2VlanOutPQsH24PerformanceTotOcts
         Counter64,
      pr1645v2EthPrtSwF2VlanOutPQsH24PerformanceDirTxOcts
         Counter64,
      pr1645v2EthPrtSwF2VlanOutPQsH24PerformanceQdOcts
         Counter64,
      pr1645v2EthPrtSwF2VlanOutPQsH24PerformanceDropOcts
         Counter64,
      pr1645v2EthPrtSwF2VlanOutPQsH24PerformanceRDropOcts
         Counter64,
      pr1645v2EthPrtSwF2VlanOutPQsH24PerformanceCirTxOcts
         Counter64,
      pr1645v2EthPrtSwF2VlanOutPQsH24PerformanceEirTxOcts
         Counter64,
      pr1645v2EthPrtSwF2VlanOutPQsH24PerformanceViolTxOcts
         Counter64,
      pr1645v2EthPrtSwF2VlanOutPQsH24PerformanceBandwidth
         Integer32
      }

pr1645v2EthPrtSwF2VlanOutPQsH24PerformanceGlobalIx OBJECT-TYPE
   SYNTAX      GlobalIndex
   MAX-ACCESS  not-accessible
   STATUS      current
   DESCRIPTION
      "The value of the tlsCntTreeGlobalIndex of the MANAGED OBJECT."
   ::= {pr1645v2EthPrtSwF2VlanOutPQsH24PerformanceEntry 10}

pr1645v2EthPrtSwF2VlanOutPQsH24PerformanceTableIx OBJECT-TYPE
   SYNTAX      TableIndex
   MAX-ACCESS  not-accessible
   STATUS      current
   DESCRIPTION
      ""
   ::= {pr1645v2EthPrtSwF2VlanOutPQsH24PerformanceEntry 11}

pr1645v2EthPrtSwF2VlanOutPQsH24PerformanceSysUpTime OBJECT-TYPE
   SYNTAX      TimeTicks
   MAX-ACCESS  read-only
   STATUS      current
   DESCRIPTION
      "Path: swPort.performance.vlan.outPriorityQueues.h24Performance.sysUpTime

       Time in centi-second."
   ::= {pr1645v2EthPrtSwF2VlanOutPQsH24PerformanceEntry 16777216}

pr1645v2EthPrtSwF2VlanOutPQsH24PerformanceTotPkts OBJECT-TYPE
   SYNTAX      Counter64
   MAX-ACCESS  read-only
   STATUS      current
   DESCRIPTION
      "Path: swPort.performance.vlan.outPriorityQueues.h24Performance.totalPkts

       64 bit unsigned wrappable counter."
   ::= {pr1645v2EthPrtSwF2VlanOutPQsH24PerformanceEntry 234881024}

pr1645v2EthPrtSwF2VlanOutPQsH24PerformanceDirTxPkts OBJECT-TYPE
   SYNTAX      Counter64
   MAX-ACCESS  read-only
   STATUS      current
   DESCRIPTION
      "Path: swPort.performance.vlan.outPriorityQueues.h24Performance.directTxPkts

       64 bit unsigned wrappable counter."
   ::= {pr1645v2EthPrtSwF2VlanOutPQsH24PerformanceEntry 33554432}

pr1645v2EthPrtSwF2VlanOutPQsH24PerformanceQdPkts OBJECT-TYPE
   SYNTAX      Counter64
   MAX-ACCESS  read-only
   STATUS      current
   DESCRIPTION
      "Path: swPort.performance.vlan.outPriorityQueues.h24Performance.queuedPkts

       64 bit unsigned wrappable counter."
   ::= {pr1645v2EthPrtSwF2VlanOutPQsH24PerformanceEntry 50331648}

pr1645v2EthPrtSwF2VlanOutPQsH24PerformanceDropPkts OBJECT-TYPE
   SYNTAX      Counter64
   MAX-ACCESS  read-only
   STATUS      current
   DESCRIPTION
      "Path: swPort.performance.vlan.outPriorityQueues.h24Performance.droppedPkts

       64 bit unsigned wrappable counter."
   ::= {pr1645v2EthPrtSwF2VlanOutPQsH24PerformanceEntry 67108864}

pr1645v2EthPrtSwF2VlanOutPQsH24PerformanceRDropPkts OBJECT-TYPE
   SYNTAX      Counter64
   MAX-ACCESS  read-only
   STATUS      current
   DESCRIPTION
      "Path: swPort.performance.vlan.outPriorityQueues.h24Performance.redDroppedPkts

       64 bit unsigned wrappable counter."
   ::= {pr1645v2EthPrtSwF2VlanOutPQsH24PerformanceEntry 201326592}

pr1645v2EthPrtSwF2VlanOutPQsH24PerformanceCirTxPkts OBJECT-TYPE
   SYNTAX      Counter64
   MAX-ACCESS  read-only
   STATUS      current
   DESCRIPTION
      "Path: swPort.performance.vlan.outPriorityQueues.h24Performance.cirTxPkts

       64 bit unsigned wrappable counter."
   ::= {pr1645v2EthPrtSwF2VlanOutPQsH24PerformanceEntry 83886080}

pr1645v2EthPrtSwF2VlanOutPQsH24PerformanceEirTxPkts OBJECT-TYPE
   SYNTAX      Counter64
   MAX-ACCESS  read-only
   STATUS      current
   DESCRIPTION
      "Path: swPort.performance.vlan.outPriorityQueues.h24Performance.eirTxPkts

       64 bit unsigned wrappable counter."
   ::= {pr1645v2EthPrtSwF2VlanOutPQsH24PerformanceEntry 100663296}

pr1645v2EthPrtSwF2VlanOutPQsH24PerformanceViolTxPkts OBJECT-TYPE
   SYNTAX      Counter64
   MAX-ACCESS  read-only
   STATUS      current
   DESCRIPTION
      "Path: swPort.performance.vlan.outPriorityQueues.h24Performance.violateTxPkts

       64 bit unsigned wrappable counter."
   ::= {pr1645v2EthPrtSwF2VlanOutPQsH24PerformanceEntry 301989888}

pr1645v2EthPrtSwF2VlanOutPQsH24PerformanceTotOcts OBJECT-TYPE
   SYNTAX      Counter64
   MAX-ACCESS  read-only
   STATUS      current
   DESCRIPTION
      "Path: swPort.performance.vlan.outPriorityQueues.h24Performance.totalOctets

       64 bit unsigned wrappable counter."
   ::= {pr1645v2EthPrtSwF2VlanOutPQsH24PerformanceEntry 251658240}

pr1645v2EthPrtSwF2VlanOutPQsH24PerformanceDirTxOcts OBJECT-TYPE
   SYNTAX      Counter64
   MAX-ACCESS  read-only
   STATUS      current
   DESCRIPTION
      "Path: swPort.performance.vlan.outPriorityQueues.h24Performance.directTxOctets

       64 bit unsigned wrappable counter."
   ::= {pr1645v2EthPrtSwF2VlanOutPQsH24PerformanceEntry 117440512}

pr1645v2EthPrtSwF2VlanOutPQsH24PerformanceQdOcts OBJECT-TYPE
   SYNTAX      Counter64
   MAX-ACCESS  read-only
   STATUS      current
   DESCRIPTION
      "Path: swPort.performance.vlan.outPriorityQueues.h24Performance.queuedOctets

       64 bit unsigned wrappable counter."
   ::= {pr1645v2EthPrtSwF2VlanOutPQsH24PerformanceEntry 134217728}

pr1645v2EthPrtSwF2VlanOutPQsH24PerformanceDropOcts OBJECT-TYPE
   SYNTAX      Counter64
   MAX-ACCESS  read-only
   STATUS      current
   DESCRIPTION
      "Path: swPort.performance.vlan.outPriorityQueues.h24Performance.droppedOctets

       64 bit unsigned wrappable counter."
   ::= {pr1645v2EthPrtSwF2VlanOutPQsH24PerformanceEntry 150994944}

pr1645v2EthPrtSwF2VlanOutPQsH24PerformanceRDropOcts OBJECT-TYPE
   SYNTAX      Counter64
   MAX-ACCESS  read-only
   STATUS      current
   DESCRIPTION
      "Path: swPort.performance.vlan.outPriorityQueues.h24Performance.redDroppedOctets

       64 bit unsigned wrappable counter."
   ::= {pr1645v2EthPrtSwF2VlanOutPQsH24PerformanceEntry 218103808}

pr1645v2EthPrtSwF2VlanOutPQsH24PerformanceCirTxOcts OBJECT-TYPE
   SYNTAX      Counter64
   MAX-ACCESS  read-only
   STATUS      current
   DESCRIPTION
      "Path: swPort.performance.vlan.outPriorityQueues.h24Performance.cirTxOctets

       64 bit unsigned wrappable counter."
   ::= {pr1645v2EthPrtSwF2VlanOutPQsH24PerformanceEntry 167772160}

pr1645v2EthPrtSwF2VlanOutPQsH24PerformanceEirTxOcts OBJECT-TYPE
   SYNTAX      Counter64
   MAX-ACCESS  read-only
   STATUS      current
   DESCRIPTION
      "Path: swPort.performance.vlan.outPriorityQueues.h24Performance.eirTxOctets

       64 bit unsigned wrappable counter."
   ::= {pr1645v2EthPrtSwF2VlanOutPQsH24PerformanceEntry 184549376}

pr1645v2EthPrtSwF2VlanOutPQsH24PerformanceViolTxOcts OBJECT-TYPE
   SYNTAX      Counter64
   MAX-ACCESS  read-only
   STATUS      current
   DESCRIPTION
      "Path: swPort.performance.vlan.outPriorityQueues.h24Performance.violateTxOctets

       64 bit unsigned wrappable counter."
   ::= {pr1645v2EthPrtSwF2VlanOutPQsH24PerformanceEntry 318767104}

pr1645v2EthPrtSwF2VlanOutPQsH24PerformanceBandwidth OBJECT-TYPE
   SYNTAX      Integer32
   MAX-ACCESS  read-only
   STATUS      current
   DESCRIPTION
      "Path: swPort.performance.vlan.outPriorityQueues.h24Performance.bandwidth

       unit name = bps
       formula = 8 * ; 8 /"
   ::= {pr1645v2EthPrtSwF2VlanOutPQsH24PerformanceEntry 268435456}

pr1645v2EthPrtSwF2VlanOutPQsD7Performance OBJECT-TYPE
   SYNTAX      SEQUENCE OF Pr1645v2EthPrtSwF2VlanOutPQsD7PerformanceEntry
   MAX-ACCESS  not-accessible
   STATUS      current
   DESCRIPTION
      ""
   ::= {pr1645v2EthPrtSwF2Vlan 84344832}

pr1645v2EthPrtSwF2VlanOutPQsD7PerformanceEntry OBJECT-TYPE
   SYNTAX      Pr1645v2EthPrtSwF2VlanOutPQsD7PerformanceEntry
   MAX-ACCESS  not-accessible
   STATUS      current
   DESCRIPTION
      ""
   INDEX      { pr1645v2EthPrtSwF2VlanOutPQsD7PerformanceGlobalIx,
                pr1645v2EthPrtSwF2VlanTableIx,
                pr1645v2EthPrtSwF2VlanOutPQsTableIx,
                pr1645v2EthPrtSwF2VlanOutPQsD7PerformanceTableIx }
   ::= {pr1645v2EthPrtSwF2VlanOutPQsD7Performance 1}

Pr1645v2EthPrtSwF2VlanOutPQsD7PerformanceEntry ::=
   SEQUENCE
      {
      pr1645v2EthPrtSwF2VlanOutPQsD7PerformanceGlobalIx
         GlobalIndex,
      pr1645v2EthPrtSwF2VlanOutPQsD7PerformanceTableIx
         TableIndex,
      pr1645v2EthPrtSwF2VlanOutPQsD7PerformanceSysUpTime
         TimeTicks,
      pr1645v2EthPrtSwF2VlanOutPQsD7PerformanceTotPkts
         Counter64,
      pr1645v2EthPrtSwF2VlanOutPQsD7PerformanceDirTxPkts
         Counter64,
      pr1645v2EthPrtSwF2VlanOutPQsD7PerformanceQdPkts
         Counter64,
      pr1645v2EthPrtSwF2VlanOutPQsD7PerformanceDropPkts
         Counter64,
      pr1645v2EthPrtSwF2VlanOutPQsD7PerformanceRDropPkts
         Counter64,
      pr1645v2EthPrtSwF2VlanOutPQsD7PerformanceCirTxPkts
         Counter64,
      pr1645v2EthPrtSwF2VlanOutPQsD7PerformanceEirTxPkts
         Counter64,
      pr1645v2EthPrtSwF2VlanOutPQsD7PerformanceViolTxPkts
         Counter64,
      pr1645v2EthPrtSwF2VlanOutPQsD7PerformanceTotOcts
         Counter64,
      pr1645v2EthPrtSwF2VlanOutPQsD7PerformanceDirTxOcts
         Counter64,
      pr1645v2EthPrtSwF2VlanOutPQsD7PerformanceQdOcts
         Counter64,
      pr1645v2EthPrtSwF2VlanOutPQsD7PerformanceDropOcts
         Counter64,
      pr1645v2EthPrtSwF2VlanOutPQsD7PerformanceRDropOcts
         Counter64,
      pr1645v2EthPrtSwF2VlanOutPQsD7PerformanceCirTxOcts
         Counter64,
      pr1645v2EthPrtSwF2VlanOutPQsD7PerformanceEirTxOcts
         Counter64,
      pr1645v2EthPrtSwF2VlanOutPQsD7PerformanceViolTxOcts
         Counter64,
      pr1645v2EthPrtSwF2VlanOutPQsD7PerformanceBandwidth
         Integer32
      }

pr1645v2EthPrtSwF2VlanOutPQsD7PerformanceGlobalIx OBJECT-TYPE
   SYNTAX      GlobalIndex
   MAX-ACCESS  not-accessible
   STATUS      current
   DESCRIPTION
      "The value of the tlsCntTreeGlobalIndex of the MANAGED OBJECT."
   ::= {pr1645v2EthPrtSwF2VlanOutPQsD7PerformanceEntry 10}

pr1645v2EthPrtSwF2VlanOutPQsD7PerformanceTableIx OBJECT-TYPE
   SYNTAX      TableIndex
   MAX-ACCESS  not-accessible
   STATUS      current
   DESCRIPTION
      ""
   ::= {pr1645v2EthPrtSwF2VlanOutPQsD7PerformanceEntry 11}

pr1645v2EthPrtSwF2VlanOutPQsD7PerformanceSysUpTime OBJECT-TYPE
   SYNTAX      TimeTicks
   MAX-ACCESS  read-only
   STATUS      current
   DESCRIPTION
      "Path: swPort.performance.vlan.outPriorityQueues.d7Performance.sysUpTime

       Time in centi-second."
   ::= {pr1645v2EthPrtSwF2VlanOutPQsD7PerformanceEntry 16777216}

pr1645v2EthPrtSwF2VlanOutPQsD7PerformanceTotPkts OBJECT-TYPE
   SYNTAX      Counter64
   MAX-ACCESS  read-only
   STATUS      current
   DESCRIPTION
      "Path: swPort.performance.vlan.outPriorityQueues.d7Performance.totalPkts

       64 bit unsigned wrappable counter."
   ::= {pr1645v2EthPrtSwF2VlanOutPQsD7PerformanceEntry 234881024}

pr1645v2EthPrtSwF2VlanOutPQsD7PerformanceDirTxPkts OBJECT-TYPE
   SYNTAX      Counter64
   MAX-ACCESS  read-only
   STATUS      current
   DESCRIPTION
      "Path: swPort.performance.vlan.outPriorityQueues.d7Performance.directTxPkts

       64 bit unsigned wrappable counter."
   ::= {pr1645v2EthPrtSwF2VlanOutPQsD7PerformanceEntry 33554432}

pr1645v2EthPrtSwF2VlanOutPQsD7PerformanceQdPkts OBJECT-TYPE
   SYNTAX      Counter64
   MAX-ACCESS  read-only
   STATUS      current
   DESCRIPTION
      "Path: swPort.performance.vlan.outPriorityQueues.d7Performance.queuedPkts

       64 bit unsigned wrappable counter."
   ::= {pr1645v2EthPrtSwF2VlanOutPQsD7PerformanceEntry 50331648}

pr1645v2EthPrtSwF2VlanOutPQsD7PerformanceDropPkts OBJECT-TYPE
   SYNTAX      Counter64
   MAX-ACCESS  read-only
   STATUS      current
   DESCRIPTION
      "Path: swPort.performance.vlan.outPriorityQueues.d7Performance.droppedPkts

       64 bit unsigned wrappable counter."
   ::= {pr1645v2EthPrtSwF2VlanOutPQsD7PerformanceEntry 67108864}

pr1645v2EthPrtSwF2VlanOutPQsD7PerformanceRDropPkts OBJECT-TYPE
   SYNTAX      Counter64
   MAX-ACCESS  read-only
   STATUS      current
   DESCRIPTION
      "Path: swPort.performance.vlan.outPriorityQueues.d7Performance.redDroppedPkts

       64 bit unsigned wrappable counter."
   ::= {pr1645v2EthPrtSwF2VlanOutPQsD7PerformanceEntry 201326592}

pr1645v2EthPrtSwF2VlanOutPQsD7PerformanceCirTxPkts OBJECT-TYPE
   SYNTAX      Counter64
   MAX-ACCESS  read-only
   STATUS      current
   DESCRIPTION
      "Path: swPort.performance.vlan.outPriorityQueues.d7Performance.cirTxPkts

       64 bit unsigned wrappable counter."
   ::= {pr1645v2EthPrtSwF2VlanOutPQsD7PerformanceEntry 83886080}

pr1645v2EthPrtSwF2VlanOutPQsD7PerformanceEirTxPkts OBJECT-TYPE
   SYNTAX      Counter64
   MAX-ACCESS  read-only
   STATUS      current
   DESCRIPTION
      "Path: swPort.performance.vlan.outPriorityQueues.d7Performance.eirTxPkts

       64 bit unsigned wrappable counter."
   ::= {pr1645v2EthPrtSwF2VlanOutPQsD7PerformanceEntry 100663296}

pr1645v2EthPrtSwF2VlanOutPQsD7PerformanceViolTxPkts OBJECT-TYPE
   SYNTAX      Counter64
   MAX-ACCESS  read-only
   STATUS      current
   DESCRIPTION
      "Path: swPort.performance.vlan.outPriorityQueues.d7Performance.violateTxPkts

       64 bit unsigned wrappable counter."
   ::= {pr1645v2EthPrtSwF2VlanOutPQsD7PerformanceEntry 301989888}

pr1645v2EthPrtSwF2VlanOutPQsD7PerformanceTotOcts OBJECT-TYPE
   SYNTAX      Counter64
   MAX-ACCESS  read-only
   STATUS      current
   DESCRIPTION
      "Path: swPort.performance.vlan.outPriorityQueues.d7Performance.totalOctets

       64 bit unsigned wrappable counter."
   ::= {pr1645v2EthPrtSwF2VlanOutPQsD7PerformanceEntry 251658240}

pr1645v2EthPrtSwF2VlanOutPQsD7PerformanceDirTxOcts OBJECT-TYPE
   SYNTAX      Counter64
   MAX-ACCESS  read-only
   STATUS      current
   DESCRIPTION
      "Path: swPort.performance.vlan.outPriorityQueues.d7Performance.directTxOctets

       64 bit unsigned wrappable counter."
   ::= {pr1645v2EthPrtSwF2VlanOutPQsD7PerformanceEntry 117440512}

pr1645v2EthPrtSwF2VlanOutPQsD7PerformanceQdOcts OBJECT-TYPE
   SYNTAX      Counter64
   MAX-ACCESS  read-only
   STATUS      current
   DESCRIPTION
      "Path: swPort.performance.vlan.outPriorityQueues.d7Performance.queuedOctets

       64 bit unsigned wrappable counter."
   ::= {pr1645v2EthPrtSwF2VlanOutPQsD7PerformanceEntry 134217728}

pr1645v2EthPrtSwF2VlanOutPQsD7PerformanceDropOcts OBJECT-TYPE
   SYNTAX      Counter64
   MAX-ACCESS  read-only
   STATUS      current
   DESCRIPTION
      "Path: swPort.performance.vlan.outPriorityQueues.d7Performance.droppedOctets

       64 bit unsigned wrappable counter."
   ::= {pr1645v2EthPrtSwF2VlanOutPQsD7PerformanceEntry 150994944}

pr1645v2EthPrtSwF2VlanOutPQsD7PerformanceRDropOcts OBJECT-TYPE
   SYNTAX      Counter64
   MAX-ACCESS  read-only
   STATUS      current
   DESCRIPTION
      "Path: swPort.performance.vlan.outPriorityQueues.d7Performance.redDroppedOctets

       64 bit unsigned wrappable counter."
   ::= {pr1645v2EthPrtSwF2VlanOutPQsD7PerformanceEntry 218103808}

pr1645v2EthPrtSwF2VlanOutPQsD7PerformanceCirTxOcts OBJECT-TYPE
   SYNTAX      Counter64
   MAX-ACCESS  read-only
   STATUS      current
   DESCRIPTION
      "Path: swPort.performance.vlan.outPriorityQueues.d7Performance.cirTxOctets

       64 bit unsigned wrappable counter."
   ::= {pr1645v2EthPrtSwF2VlanOutPQsD7PerformanceEntry 167772160}

pr1645v2EthPrtSwF2VlanOutPQsD7PerformanceEirTxOcts OBJECT-TYPE
   SYNTAX      Counter64
   MAX-ACCESS  read-only
   STATUS      current
   DESCRIPTION
      "Path: swPort.performance.vlan.outPriorityQueues.d7Performance.eirTxOctets

       64 bit unsigned wrappable counter."
   ::= {pr1645v2EthPrtSwF2VlanOutPQsD7PerformanceEntry 184549376}

pr1645v2EthPrtSwF2VlanOutPQsD7PerformanceViolTxOcts OBJECT-TYPE
   SYNTAX      Counter64
   MAX-ACCESS  read-only
   STATUS      current
   DESCRIPTION
      "Path: swPort.performance.vlan.outPriorityQueues.d7Performance.violateTxOctets

       64 bit unsigned wrappable counter."
   ::= {pr1645v2EthPrtSwF2VlanOutPQsD7PerformanceEntry 318767104}

pr1645v2EthPrtSwF2VlanOutPQsD7PerformanceBandwidth OBJECT-TYPE
   SYNTAX      Integer32
   MAX-ACCESS  read-only
   STATUS      current
   DESCRIPTION
      "Path: swPort.performance.vlan.outPriorityQueues.d7Performance.bandwidth

       unit name = bps
       formula = 8 * ; 8 /"
   ::= {pr1645v2EthPrtSwF2VlanOutPQsD7PerformanceEntry 268435456}


pr1645v2EthPrtSwF2PPPoE OBJECT IDENTIFIER ::= {pr1645v2EthPrtSwF2 53}

pr1645v2EthPrtSwF2PPPoESSCTable OBJECT-TYPE
   SYNTAX      SEQUENCE OF Pr1645v2EthPrtSwF2PPPoEEntry
   MAX-ACCESS  not-accessible
   STATUS      current
   DESCRIPTION
      ""
   ::= {pr1645v2EthPrtSwF2PPPoE 1}

pr1645v2EthPrtSwF2PPPoEEntry OBJECT-TYPE
   SYNTAX      Pr1645v2EthPrtSwF2PPPoEEntry
   MAX-ACCESS  not-accessible
   STATUS      current
   DESCRIPTION
      ""
   INDEX      { pr1645v2EthPrtSwF2PPPoEGlobalIx,
                pr1645v2EthPrtSwF2PPPoETableIx }
   ::= {pr1645v2EthPrtSwF2PPPoESSCTable 1}

Pr1645v2EthPrtSwF2PPPoEEntry ::=
   SEQUENCE
      {
      pr1645v2EthPrtSwF2PPPoEGlobalIx
         GlobalIndex,
      pr1645v2EthPrtSwF2PPPoETableIx
         TableIndex,
      pr1645v2EthPrtSwF2PPPoEName
         DisplayString,
      pr1645v2EthPrtSwF2PPPoEMCInOctets
         Counter64,
      pr1645v2EthPrtSwF2PPPoEMCInUcast
         Counter64,
      pr1645v2EthPrtSwF2PPPoEMCInNUcastPkts
         Counter64,
      pr1645v2EthPrtSwF2PPPoEMCInBcastPkts
         Counter64,
      pr1645v2EthPrtSwF2PPPoEMCInMcastPkts
         Counter64,
      pr1645v2EthPrtSwF2PPPoEMCInDiscards
         Counter64,
      pr1645v2EthPrtSwF2PPPoEMCInErrors
         Counter64,
      pr1645v2EthPrtSwF2PPPoEMCInUnknownProtos
         Counter64,
      pr1645v2EthPrtSwF2PPPoEMCInDropEx
         Counter64,
      pr1645v2EthPrtSwF2PPPoEMCInDropNoMac
         Counter64,
      pr1645v2EthPrtSwF2PPPoEMCInDropNUCast
         Counter64,
      pr1645v2EthPrtSwF2PPPoEMCInDropFilter
         Counter64,
      pr1645v2EthPrtSwF2PPPoEMCInBandwidth15sec
         Integer32,
      pr1645v2EthPrtSwF2PPPoEMCInBandwidth30sec
         Integer32,
      pr1645v2EthPrtSwF2PPPoEMCInBandwidth1min
         Integer32,
      pr1645v2EthPrtSwF2PPPoEMCInBandwidth2min
         Integer32,
      pr1645v2EthPrtSwF2PPPoEMCInBandwidth5min
         Integer32,
      pr1645v2EthPrtSwF2PPPoEMCOutOctets
         Counter64,
      pr1645v2EthPrtSwF2PPPoEMCOutUcastPkts
         Counter64,
      pr1645v2EthPrtSwF2PPPoEMCOutNUcastPkts
         Counter64,
      pr1645v2EthPrtSwF2PPPoEMCOutBcastPkts
         Counter64,
      pr1645v2EthPrtSwF2PPPoEMCOutMcastPkts
         Counter64,
      pr1645v2EthPrtSwF2PPPoEMCOutDiscards
         Counter64,
      pr1645v2EthPrtSwF2PPPoEMCOutErrors
         Counter64,
      pr1645v2EthPrtSwF2PPPoEMCOutQLen
         Counter32,
      pr1645v2EthPrtSwF2PPPoEMCOutDropEx
         Counter64,
      pr1645v2EthPrtSwF2PPPoEMCOutDropNoArp
         Counter64,
      pr1645v2EthPrtSwF2PPPoEMCOutDropFilter
         Counter64,
      pr1645v2EthPrtSwF2PPPoEMCOutBandwidth15sec
         Integer32,
      pr1645v2EthPrtSwF2PPPoEMCOutBandwidth30sec
         Integer32,
      pr1645v2EthPrtSwF2PPPoEMCOutBandwidth1min
         Integer32,
      pr1645v2EthPrtSwF2PPPoEMCOutBandwidth2min
         Integer32,
      pr1645v2EthPrtSwF2PPPoEMCOutBandwidth5min
         Integer32,
      pr1645v2EthPrtSwF2PPPoEPppLinkMonitoringRequestsSent
         Gauge32,
      pr1645v2EthPrtSwF2PPPoEPppLinkMonitoringRepliesRcvd
         Gauge32,
      pr1645v2EthPrtSwF2PPPoEPppLinkMonitoringRequestsRcvd
         Gauge32,
      pr1645v2EthPrtSwF2PPPoEPppLinkMonitoringRepliesSent
         Gauge32
      }

pr1645v2EthPrtSwF2PPPoEGlobalIx OBJECT-TYPE
   SYNTAX      GlobalIndex
   MAX-ACCESS  not-accessible
   STATUS      current
   DESCRIPTION
      "The value of the tlsCntTreeGlobalIndex of the MANAGED OBJECT."
   ::= {pr1645v2EthPrtSwF2PPPoEEntry 10}

pr1645v2EthPrtSwF2PPPoETableIx OBJECT-TYPE
   SYNTAX      TableIndex
   MAX-ACCESS  not-accessible
   STATUS      current
   DESCRIPTION
      ""
   ::= {pr1645v2EthPrtSwF2PPPoEEntry 11}

pr1645v2EthPrtSwF2PPPoEName OBJECT-TYPE
   SYNTAX      DisplayString
   MAX-ACCESS  read-only
   STATUS      current
   DESCRIPTION
      "Path: swPort.performance.pppoEClient.name"
   ::= {pr1645v2EthPrtSwF2PPPoEEntry 16777216}

pr1645v2EthPrtSwF2PPPoEMCInOctets OBJECT-TYPE
   SYNTAX      Counter64
   MAX-ACCESS  read-only
   STATUS      current
   DESCRIPTION
      "Path: swPort.performance.pppoEClient.mibCounters.ifInOctets

       64 bit unsigned wrappable counter."
   ::= {pr1645v2EthPrtSwF2PPPoEEntry 40697856}

pr1645v2EthPrtSwF2PPPoEMCInUcast OBJECT-TYPE
   SYNTAX      Counter64
   MAX-ACCESS  read-only
   STATUS      current
   DESCRIPTION
      "Path: swPort.performance.pppoEClient.mibCounters.ifInUcastPkts

       64 bit unsigned wrappable counter."
   ::= {pr1645v2EthPrtSwF2PPPoEEntry 40763392}

pr1645v2EthPrtSwF2PPPoEMCInNUcastPkts OBJECT-TYPE
   SYNTAX      Counter64
   MAX-ACCESS  read-only
   STATUS      current
   DESCRIPTION
      "Path: swPort.performance.pppoEClient.mibCounters.ifInNUcastPkts

       64 bit unsigned wrappable counter."
   ::= {pr1645v2EthPrtSwF2PPPoEEntry 40828928}

pr1645v2EthPrtSwF2PPPoEMCInBcastPkts OBJECT-TYPE
   SYNTAX      Counter64
   MAX-ACCESS  read-only
   STATUS      current
   DESCRIPTION
      "Path: swPort.performance.pppoEClient.mibCounters.ifInBcastPkts

       64 bit unsigned wrappable counter."
   ::= {pr1645v2EthPrtSwF2PPPoEEntry 47382528}

pr1645v2EthPrtSwF2PPPoEMCInMcastPkts OBJECT-TYPE
   SYNTAX      Counter64
   MAX-ACCESS  read-only
   STATUS      current
   DESCRIPTION
      "Path: swPort.performance.pppoEClient.mibCounters.ifInMcastPkts

       64 bit unsigned wrappable counter."
   ::= {pr1645v2EthPrtSwF2PPPoEEntry 48037888}

pr1645v2EthPrtSwF2PPPoEMCInDiscards OBJECT-TYPE
   SYNTAX      Counter64
   MAX-ACCESS  read-only
   STATUS      current
   DESCRIPTION
      "Path: swPort.performance.pppoEClient.mibCounters.ifInDiscards

       64 bit unsigned wrappable counter."
   ::= {pr1645v2EthPrtSwF2PPPoEEntry 40894464}

pr1645v2EthPrtSwF2PPPoEMCInErrors OBJECT-TYPE
   SYNTAX      Counter64
   MAX-ACCESS  read-only
   STATUS      current
   DESCRIPTION
      "Path: swPort.performance.pppoEClient.mibCounters.ifInErrors

       64 bit unsigned wrappable counter."
   ::= {pr1645v2EthPrtSwF2PPPoEEntry 40960000}

pr1645v2EthPrtSwF2PPPoEMCInUnknownProtos OBJECT-TYPE
   SYNTAX      Counter64
   MAX-ACCESS  read-only
   STATUS      current
   DESCRIPTION
      "Path: swPort.performance.pppoEClient.mibCounters.ifInUnknownProtos

       64 bit unsigned wrappable counter."
   ::= {pr1645v2EthPrtSwF2PPPoEEntry 41025536}

pr1645v2EthPrtSwF2PPPoEMCInDropEx OBJECT-TYPE
   SYNTAX      Counter64
   MAX-ACCESS  read-only
   STATUS      current
   DESCRIPTION
      "Path: swPort.performance.pppoEClient.mibCounters.ifInDropLevelExceeded

       64 bit unsigned wrappable counter."
   ::= {pr1645v2EthPrtSwF2PPPoEEntry 42074112}

pr1645v2EthPrtSwF2PPPoEMCInDropNoMac OBJECT-TYPE
   SYNTAX      Counter64
   MAX-ACCESS  read-only
   STATUS      current
   DESCRIPTION
      "Path: swPort.performance.pppoEClient.mibCounters.ifInDiscardsNoMacFit

       64 bit unsigned wrappable counter."
   ::= {pr1645v2EthPrtSwF2PPPoEEntry 42270720}

pr1645v2EthPrtSwF2PPPoEMCInDropNUCast OBJECT-TYPE
   SYNTAX      Counter64
   MAX-ACCESS  read-only
   STATUS      current
   DESCRIPTION
      "Path: swPort.performance.pppoEClient.mibCounters.ifInDiscardsNUCast

       64 bit unsigned wrappable counter."
   ::= {pr1645v2EthPrtSwF2PPPoEEntry 42467328}

pr1645v2EthPrtSwF2PPPoEMCInDropFilter OBJECT-TYPE
   SYNTAX      Counter64
   MAX-ACCESS  read-only
   STATUS      current
   DESCRIPTION
      "Path: swPort.performance.pppoEClient.mibCounters.ifInDiscardsFilter

       64 bit unsigned wrappable counter."
   ::= {pr1645v2EthPrtSwF2PPPoEEntry 42532864}

pr1645v2EthPrtSwF2PPPoEMCInBandwidth15sec OBJECT-TYPE
   SYNTAX      Integer32
   MAX-ACCESS  read-only
   STATUS      current
   DESCRIPTION
      "Path: swPort.performance.pppoEClient.mibCounters.ifInBandwidth.15sec

       unit name = bps
       formula = 8 * ; 8 /"
   ::= {pr1645v2EthPrtSwF2PPPoEEntry 45417728}

pr1645v2EthPrtSwF2PPPoEMCInBandwidth30sec OBJECT-TYPE
   SYNTAX      Integer32
   MAX-ACCESS  read-only
   STATUS      current
   DESCRIPTION
      "Path: swPort.performance.pppoEClient.mibCounters.ifInBandwidth.30sec

       unit name = bps
       formula = 8 * ; 8 /"
   ::= {pr1645v2EthPrtSwF2PPPoEEntry 45419008}

pr1645v2EthPrtSwF2PPPoEMCInBandwidth1min OBJECT-TYPE
   SYNTAX      Integer32
   MAX-ACCESS  read-only
   STATUS      current
   DESCRIPTION
      "Path: swPort.performance.pppoEClient.mibCounters.ifInBandwidth.1min

       unit name = bps
       formula = 8 * ; 8 /"
   ::= {pr1645v2EthPrtSwF2PPPoEEntry 45421568}

pr1645v2EthPrtSwF2PPPoEMCInBandwidth2min OBJECT-TYPE
   SYNTAX      Integer32
   MAX-ACCESS  read-only
   STATUS      current
   DESCRIPTION
      "Path: swPort.performance.pppoEClient.mibCounters.ifInBandwidth.2min

       unit name = bps
       formula = 8 * ; 8 /"
   ::= {pr1645v2EthPrtSwF2PPPoEEntry 45426688}

pr1645v2EthPrtSwF2PPPoEMCInBandwidth5min OBJECT-TYPE
   SYNTAX      Integer32
   MAX-ACCESS  read-only
   STATUS      current
   DESCRIPTION
      "Path: swPort.performance.pppoEClient.mibCounters.ifInBandwidth.5min

       unit name = bps
       formula = 8 * ; 8 /"
   ::= {pr1645v2EthPrtSwF2PPPoEEntry 45442048}

pr1645v2EthPrtSwF2PPPoEMCOutOctets OBJECT-TYPE
   SYNTAX      Counter64
   MAX-ACCESS  read-only
   STATUS      current
   DESCRIPTION
      "Path: swPort.performance.pppoEClient.mibCounters.ifOutOctets

       64 bit unsigned wrappable counter."
   ::= {pr1645v2EthPrtSwF2PPPoEEntry 41091072}

pr1645v2EthPrtSwF2PPPoEMCOutUcastPkts OBJECT-TYPE
   SYNTAX      Counter64
   MAX-ACCESS  read-only
   STATUS      current
   DESCRIPTION
      "Path: swPort.performance.pppoEClient.mibCounters.ifOutUcastPkts

       64 bit unsigned wrappable counter."
   ::= {pr1645v2EthPrtSwF2PPPoEEntry 41156608}

pr1645v2EthPrtSwF2PPPoEMCOutNUcastPkts OBJECT-TYPE
   SYNTAX      Counter64
   MAX-ACCESS  read-only
   STATUS      current
   DESCRIPTION
      "Path: swPort.performance.pppoEClient.mibCounters.ifOutNUcastPkts

       64 bit unsigned wrappable counter."
   ::= {pr1645v2EthPrtSwF2PPPoEEntry 41222144}

pr1645v2EthPrtSwF2PPPoEMCOutBcastPkts OBJECT-TYPE
   SYNTAX      Counter64
   MAX-ACCESS  read-only
   STATUS      current
   DESCRIPTION
      "Path: swPort.performance.pppoEClient.mibCounters.ifOutBcastPkts

       64 bit unsigned wrappable counter."
   ::= {pr1645v2EthPrtSwF2PPPoEEntry 47775744}

pr1645v2EthPrtSwF2PPPoEMCOutMcastPkts OBJECT-TYPE
   SYNTAX      Counter64
   MAX-ACCESS  read-only
   STATUS      current
   DESCRIPTION
      "Path: swPort.performance.pppoEClient.mibCounters.ifOutMcastPkts

       64 bit unsigned wrappable counter."
   ::= {pr1645v2EthPrtSwF2PPPoEEntry 48431104}

pr1645v2EthPrtSwF2PPPoEMCOutDiscards OBJECT-TYPE
   SYNTAX      Counter64
   MAX-ACCESS  read-only
   STATUS      current
   DESCRIPTION
      "Path: swPort.performance.pppoEClient.mibCounters.ifOutDiscards

       64 bit unsigned wrappable counter."
   ::= {pr1645v2EthPrtSwF2PPPoEEntry 41287680}

pr1645v2EthPrtSwF2PPPoEMCOutErrors OBJECT-TYPE
   SYNTAX      Counter64
   MAX-ACCESS  read-only
   STATUS      current
   DESCRIPTION
      "Path: swPort.performance.pppoEClient.mibCounters.ifOutErrors

       64 bit unsigned wrappable counter."
   ::= {pr1645v2EthPrtSwF2PPPoEEntry 41353216}

pr1645v2EthPrtSwF2PPPoEMCOutQLen OBJECT-TYPE
   SYNTAX      Counter32
   MAX-ACCESS  read-only
   STATUS      current
   DESCRIPTION
      "Path: swPort.performance.pppoEClient.mibCounters.ifOutQLen

       32 bit unsigned wrappable counter."
   ::= {pr1645v2EthPrtSwF2PPPoEEntry 41418752}

pr1645v2EthPrtSwF2PPPoEMCOutDropEx OBJECT-TYPE
   SYNTAX      Counter64
   MAX-ACCESS  read-only
   STATUS      current
   DESCRIPTION
      "Path: swPort.performance.pppoEClient.mibCounters.ifOutDropLevelExceeded

       64 bit unsigned wrappable counter."
   ::= {pr1645v2EthPrtSwF2PPPoEEntry 41484288}

pr1645v2EthPrtSwF2PPPoEMCOutDropNoArp OBJECT-TYPE
   SYNTAX      Counter64
   MAX-ACCESS  read-only
   STATUS      current
   DESCRIPTION
      "Path: swPort.performance.pppoEClient.mibCounters.ifOutDiscardsNoArp

       64 bit unsigned wrappable counter."
   ::= {pr1645v2EthPrtSwF2PPPoEEntry 42336256}

pr1645v2EthPrtSwF2PPPoEMCOutDropFilter OBJECT-TYPE
   SYNTAX      Counter64
   MAX-ACCESS  read-only
   STATUS      current
   DESCRIPTION
      "Path: swPort.performance.pppoEClient.mibCounters.ifOutDiscardsFilter

       64 bit unsigned wrappable counter."
   ::= {pr1645v2EthPrtSwF2PPPoEEntry 42598400}

pr1645v2EthPrtSwF2PPPoEMCOutBandwidth15sec OBJECT-TYPE
   SYNTAX      Integer32
   MAX-ACCESS  read-only
   STATUS      current
   DESCRIPTION
      "Path: swPort.performance.pppoEClient.mibCounters.ifOutBandwidth.15sec

       unit name = bps
       formula = 8 * ; 8 /"
   ::= {pr1645v2EthPrtSwF2PPPoEEntry 45483264}

pr1645v2EthPrtSwF2PPPoEMCOutBandwidth30sec OBJECT-TYPE
   SYNTAX      Integer32
   MAX-ACCESS  read-only
   STATUS      current
   DESCRIPTION
      "Path: swPort.performance.pppoEClient.mibCounters.ifOutBandwidth.30sec

       unit name = bps
       formula = 8 * ; 8 /"
   ::= {pr1645v2EthPrtSwF2PPPoEEntry 45484544}

pr1645v2EthPrtSwF2PPPoEMCOutBandwidth1min OBJECT-TYPE
   SYNTAX      Integer32
   MAX-ACCESS  read-only
   STATUS      current
   DESCRIPTION
      "Path: swPort.performance.pppoEClient.mibCounters.ifOutBandwidth.1min

       unit name = bps
       formula = 8 * ; 8 /"
   ::= {pr1645v2EthPrtSwF2PPPoEEntry 45487104}

pr1645v2EthPrtSwF2PPPoEMCOutBandwidth2min OBJECT-TYPE
   SYNTAX      Integer32
   MAX-ACCESS  read-only
   STATUS      current
   DESCRIPTION
      "Path: swPort.performance.pppoEClient.mibCounters.ifOutBandwidth.2min

       unit name = bps
       formula = 8 * ; 8 /"
   ::= {pr1645v2EthPrtSwF2PPPoEEntry 45492224}

pr1645v2EthPrtSwF2PPPoEMCOutBandwidth5min OBJECT-TYPE
   SYNTAX      Integer32
   MAX-ACCESS  read-only
   STATUS      current
   DESCRIPTION
      "Path: swPort.performance.pppoEClient.mibCounters.ifOutBandwidth.5min

       unit name = bps
       formula = 8 * ; 8 /"
   ::= {pr1645v2EthPrtSwF2PPPoEEntry 45507584}

pr1645v2EthPrtSwF2PPPoEPppLinkMonitoringRequestsSent OBJECT-TYPE
   SYNTAX      Gauge32
   MAX-ACCESS  read-only
   STATUS      current
   DESCRIPTION
      "Path: swPort.performance.pppoEClient.ppp.linkMonitoring.requestsSent

       32 bit unsigned gauge value."
   ::= {pr1645v2EthPrtSwF2PPPoEEntry 50397440}

pr1645v2EthPrtSwF2PPPoEPppLinkMonitoringRepliesRcvd OBJECT-TYPE
   SYNTAX      Gauge32
   MAX-ACCESS  read-only
   STATUS      current
   DESCRIPTION
      "Path: swPort.performance.pppoEClient.ppp.linkMonitoring.repliesRcvd

       32 bit unsigned gauge value."
   ::= {pr1645v2EthPrtSwF2PPPoEEntry 50397696}

pr1645v2EthPrtSwF2PPPoEPppLinkMonitoringRequestsRcvd OBJECT-TYPE
   SYNTAX      Gauge32
   MAX-ACCESS  read-only
   STATUS      current
   DESCRIPTION
      "Path: swPort.performance.pppoEClient.ppp.linkMonitoring.requestsRcvd

       32 bit unsigned gauge value."
   ::= {pr1645v2EthPrtSwF2PPPoEEntry 50397952}

pr1645v2EthPrtSwF2PPPoEPppLinkMonitoringRepliesSent OBJECT-TYPE
   SYNTAX      Gauge32
   MAX-ACCESS  read-only
   STATUS      current
   DESCRIPTION
      "Path: swPort.performance.pppoEClient.ppp.linkMonitoring.repliesSent

       32 bit unsigned gauge value."
   ::= {pr1645v2EthPrtSwF2PPPoEEntry 50398208}

pr1645v2EthPrtSwF2PPPoEMCH2P OBJECT-TYPE
   SYNTAX      SEQUENCE OF Pr1645v2EthPrtSwF2PPPoEMCH2PEntry
   MAX-ACCESS  not-accessible
   STATUS      current
   DESCRIPTION
      ""
   ::= {pr1645v2EthPrtSwF2PPPoE 41549824}

pr1645v2EthPrtSwF2PPPoEMCH2PEntry OBJECT-TYPE
   SYNTAX      Pr1645v2EthPrtSwF2PPPoEMCH2PEntry
   MAX-ACCESS  not-accessible
   STATUS      current
   DESCRIPTION
      ""
   INDEX      { pr1645v2EthPrtSwF2PPPoEMCH2PGlobalIx,
                pr1645v2EthPrtSwF2PPPoETableIx,
                pr1645v2EthPrtSwF2PPPoEMCH2PTableIx }
   ::= {pr1645v2EthPrtSwF2PPPoEMCH2P 1}

Pr1645v2EthPrtSwF2PPPoEMCH2PEntry ::=
   SEQUENCE
      {
      pr1645v2EthPrtSwF2PPPoEMCH2PGlobalIx
         GlobalIndex,
      pr1645v2EthPrtSwF2PPPoEMCH2PTableIx
         TableIndex,
      pr1645v2EthPrtSwF2PPPoEMCH2PSysUpTime
         TimeTicks,
      pr1645v2EthPrtSwF2PPPoEMCH2PIfUpTime
         TimeTicks,
      pr1645v2EthPrtSwF2PPPoEMCH2PIfStatChanges
         Counter32,
      pr1645v2EthPrtSwF2PPPoEMCH2PIfInOctets
         Counter64,
      pr1645v2EthPrtSwF2PPPoEMCH2PIfInUCPkts
         Counter64,
      pr1645v2EthPrtSwF2PPPoEMCH2PIfInNUCPkts
         Counter64,
      pr1645v2EthPrtSwF2PPPoEMCH2PIfInBCPkts
         Counter64,
      pr1645v2EthPrtSwF2PPPoEMCH2PIfInMCPkts
         Counter64,
      pr1645v2EthPrtSwF2PPPoEMCH2PIfInDiscards
         Counter64,
      pr1645v2EthPrtSwF2PPPoEMCH2PIfInErrors
         Counter64,
      pr1645v2EthPrtSwF2PPPoEMCH2PIfInUnkwn
         Counter64,
      pr1645v2EthPrtSwF2PPPoEMCH2PInDropEx
         Counter64,
      pr1645v2EthPrtSwF2PPPoEMCH2PInDropNoMac
         Counter64,
      pr1645v2EthPrtSwF2PPPoEMCH2PInDropNUCast
         Counter64,
      pr1645v2EthPrtSwF2PPPoEMCH2PInDropFilter
         Counter64,
      pr1645v2EthPrtSwF2PPPoEMCH2PIfInBandwidth
         Integer32,
      pr1645v2EthPrtSwF2PPPoEMCH2PIfOutOctets
         Counter64,
      pr1645v2EthPrtSwF2PPPoEMCH2PIfOutUCPkts
         Counter64,
      pr1645v2EthPrtSwF2PPPoEMCH2PIfOutNUCPkts
         Counter64,
      pr1645v2EthPrtSwF2PPPoEMCH2PIfOutBCPkts
         Counter64,
      pr1645v2EthPrtSwF2PPPoEMCH2PIfOutMCPkts
         Counter64,
      pr1645v2EthPrtSwF2PPPoEMCH2PIfOutDiscards
         Counter64,
      pr1645v2EthPrtSwF2PPPoEMCH2PIfOutErrors
         Counter64,
      pr1645v2EthPrtSwF2PPPoEMCH2POutDropEx
         Counter64,
      pr1645v2EthPrtSwF2PPPoEMCH2POutDropNoArp
         Counter64,
      pr1645v2EthPrtSwF2PPPoEMCH2POutDropFilter
         Counter64,
      pr1645v2EthPrtSwF2PPPoEMCH2PIfOutBandwidth
         Integer32,
      pr1645v2EthPrtSwF2PPPoEMCH2PIfErrSec
         Counter32
      }

pr1645v2EthPrtSwF2PPPoEMCH2PGlobalIx OBJECT-TYPE
   SYNTAX      GlobalIndex
   MAX-ACCESS  not-accessible
   STATUS      current
   DESCRIPTION
      "The value of the tlsCntTreeGlobalIndex of the MANAGED OBJECT."
   ::= {pr1645v2EthPrtSwF2PPPoEMCH2PEntry 10}

pr1645v2EthPrtSwF2PPPoEMCH2PTableIx OBJECT-TYPE
   SYNTAX      TableIndex
   MAX-ACCESS  not-accessible
   STATUS      current
   DESCRIPTION
      ""
   ::= {pr1645v2EthPrtSwF2PPPoEMCH2PEntry 11}

pr1645v2EthPrtSwF2PPPoEMCH2PSysUpTime OBJECT-TYPE
   SYNTAX      TimeTicks
   MAX-ACCESS  read-only
   STATUS      current
   DESCRIPTION
      "Path: swPort.performance.pppoEClient.mibCounters.h2Performance.sysUpTime

       Time in centi-second."
   ::= {pr1645v2EthPrtSwF2PPPoEMCH2PEntry 16777216}

pr1645v2EthPrtSwF2PPPoEMCH2PIfUpTime OBJECT-TYPE
   SYNTAX      TimeTicks
   MAX-ACCESS  read-only
   STATUS      current
   DESCRIPTION
      "Path: swPort.performance.pppoEClient.mibCounters.h2Performance.ifUpTime

       Time in centi-second."
   ::= {pr1645v2EthPrtSwF2PPPoEMCH2PEntry 33554432}

pr1645v2EthPrtSwF2PPPoEMCH2PIfStatChanges OBJECT-TYPE
   SYNTAX      Counter32
   MAX-ACCESS  read-only
   STATUS      current
   DESCRIPTION
      "Path: swPort.performance.pppoEClient.mibCounters.h2Performance.ifStatusChanges

       32 bit unsigned wrappable counter."
   ::= {pr1645v2EthPrtSwF2PPPoEMCH2PEntry 50331648}

pr1645v2EthPrtSwF2PPPoEMCH2PIfInOctets OBJECT-TYPE
   SYNTAX      Counter64
   MAX-ACCESS  read-only
   STATUS      current
   DESCRIPTION
      "Path: swPort.performance.pppoEClient.mibCounters.h2Performance.ifInOctets

       64 bit unsigned wrappable counter."
   ::= {pr1645v2EthPrtSwF2PPPoEMCH2PEntry 67108864}

pr1645v2EthPrtSwF2PPPoEMCH2PIfInUCPkts OBJECT-TYPE
   SYNTAX      Counter64
   MAX-ACCESS  read-only
   STATUS      current
   DESCRIPTION
      "Path: swPort.performance.pppoEClient.mibCounters.h2Performance.ifInUcastPkts

       64 bit unsigned wrappable counter."
   ::= {pr1645v2EthPrtSwF2PPPoEMCH2PEntry 83886080}

pr1645v2EthPrtSwF2PPPoEMCH2PIfInNUCPkts OBJECT-TYPE
   SYNTAX      Counter64
   MAX-ACCESS  read-only
   STATUS      current
   DESCRIPTION
      "Path: swPort.performance.pppoEClient.mibCounters.h2Performance.ifInNUcastPkts

       64 bit unsigned wrappable counter."
   ::= {pr1645v2EthPrtSwF2PPPoEMCH2PEntry 100663296}

pr1645v2EthPrtSwF2PPPoEMCH2PIfInBCPkts OBJECT-TYPE
   SYNTAX      Counter64
   MAX-ACCESS  read-only
   STATUS      current
   DESCRIPTION
      "Path: swPort.performance.pppoEClient.mibCounters.h2Performance.ifInBcastPkts

       64 bit unsigned wrappable counter."
   ::= {pr1645v2EthPrtSwF2PPPoEMCH2PEntry 419430400}

pr1645v2EthPrtSwF2PPPoEMCH2PIfInMCPkts OBJECT-TYPE
   SYNTAX      Counter64
   MAX-ACCESS  read-only
   STATUS      current
   DESCRIPTION
      "Path: swPort.performance.pppoEClient.mibCounters.h2Performance.ifInMcastPkts

       64 bit unsigned wrappable counter."
   ::= {pr1645v2EthPrtSwF2PPPoEMCH2PEntry 436207616}

pr1645v2EthPrtSwF2PPPoEMCH2PIfInDiscards OBJECT-TYPE
   SYNTAX      Counter64
   MAX-ACCESS  read-only
   STATUS      current
   DESCRIPTION
      "Path: swPort.performance.pppoEClient.mibCounters.h2Performance.ifInDiscards

       64 bit unsigned wrappable counter."
   ::= {pr1645v2EthPrtSwF2PPPoEMCH2PEntry 117440512}

pr1645v2EthPrtSwF2PPPoEMCH2PIfInErrors OBJECT-TYPE
   SYNTAX      Counter64
   MAX-ACCESS  read-only
   STATUS      current
   DESCRIPTION
      "Path: swPort.performance.pppoEClient.mibCounters.h2Performance.ifInErrors

       64 bit unsigned wrappable counter."
   ::= {pr1645v2EthPrtSwF2PPPoEMCH2PEntry 134217728}

pr1645v2EthPrtSwF2PPPoEMCH2PIfInUnkwn OBJECT-TYPE
   SYNTAX      Counter64
   MAX-ACCESS  read-only
   STATUS      current
   DESCRIPTION
      "Path: swPort.performance.pppoEClient.mibCounters.h2Performance.ifInUnknownProtos

       64 bit unsigned wrappable counter."
   ::= {pr1645v2EthPrtSwF2PPPoEMCH2PEntry 150994944}

pr1645v2EthPrtSwF2PPPoEMCH2PInDropEx OBJECT-TYPE
   SYNTAX      Counter64
   MAX-ACCESS  read-only
   STATUS      current
   DESCRIPTION
      "Path: swPort.performance.pppoEClient.mibCounters.h2Performance.ifInDropLevelExceeded

       64 bit unsigned wrappable counter."
   ::= {pr1645v2EthPrtSwF2PPPoEMCH2PEntry 335544320}

pr1645v2EthPrtSwF2PPPoEMCH2PInDropNoMac OBJECT-TYPE
   SYNTAX      Counter64
   MAX-ACCESS  read-only
   STATUS      current
   DESCRIPTION
      "Path: swPort.performance.pppoEClient.mibCounters.h2Performance.fInDiscardsNoMacFit

       64 bit unsigned wrappable counter."
   ::= {pr1645v2EthPrtSwF2PPPoEMCH2PEntry 301989888}

pr1645v2EthPrtSwF2PPPoEMCH2PInDropNUCast OBJECT-TYPE
   SYNTAX      Counter64
   MAX-ACCESS  read-only
   STATUS      current
   DESCRIPTION
      "Path: swPort.performance.pppoEClient.mibCounters.h2Performance.fInDiscardsNUCast

       64 bit unsigned wrappable counter."
   ::= {pr1645v2EthPrtSwF2PPPoEMCH2PEntry 318767104}

pr1645v2EthPrtSwF2PPPoEMCH2PInDropFilter OBJECT-TYPE
   SYNTAX      Counter64
   MAX-ACCESS  read-only
   STATUS      current
   DESCRIPTION
      "Path: swPort.performance.pppoEClient.mibCounters.h2Performance.fInDiscardsFilter

       64 bit unsigned wrappable counter."
   ::= {pr1645v2EthPrtSwF2PPPoEMCH2PEntry 385875968}

pr1645v2EthPrtSwF2PPPoEMCH2PIfInBandwidth OBJECT-TYPE
   SYNTAX      Integer32
   MAX-ACCESS  read-only
   STATUS      current
   DESCRIPTION
      "Path: swPort.performance.pppoEClient.mibCounters.h2Performance.ifInBandwidth

       unit name = bps
       formula = 8 * ; 8 /"
   ::= {pr1645v2EthPrtSwF2PPPoEMCH2PEntry 268435456}

pr1645v2EthPrtSwF2PPPoEMCH2PIfOutOctets OBJECT-TYPE
   SYNTAX      Counter64
   MAX-ACCESS  read-only
   STATUS      current
   DESCRIPTION
      "Path: swPort.performance.pppoEClient.mibCounters.h2Performance.ifOutOctets

       64 bit unsigned wrappable counter."
   ::= {pr1645v2EthPrtSwF2PPPoEMCH2PEntry 167772160}

pr1645v2EthPrtSwF2PPPoEMCH2PIfOutUCPkts OBJECT-TYPE
   SYNTAX      Counter64
   MAX-ACCESS  read-only
   STATUS      current
   DESCRIPTION
      "Path: swPort.performance.pppoEClient.mibCounters.h2Performance.ifOutUcastPkts

       64 bit unsigned wrappable counter."
   ::= {pr1645v2EthPrtSwF2PPPoEMCH2PEntry 184549376}

pr1645v2EthPrtSwF2PPPoEMCH2PIfOutNUCPkts OBJECT-TYPE
   SYNTAX      Counter64
   MAX-ACCESS  read-only
   STATUS      current
   DESCRIPTION
      "Path: swPort.performance.pppoEClient.mibCounters.h2Performance.ifOutNUcastPkts

       64 bit unsigned wrappable counter."
   ::= {pr1645v2EthPrtSwF2PPPoEMCH2PEntry 201326592}

pr1645v2EthPrtSwF2PPPoEMCH2PIfOutBCPkts OBJECT-TYPE
   SYNTAX      Counter64
   MAX-ACCESS  read-only
   STATUS      current
   DESCRIPTION
      "Path: swPort.performance.pppoEClient.mibCounters.h2Performance.ifOutBcastPkts

       64 bit unsigned wrappable counter."
   ::= {pr1645v2EthPrtSwF2PPPoEMCH2PEntry 452984832}

pr1645v2EthPrtSwF2PPPoEMCH2PIfOutMCPkts OBJECT-TYPE
   SYNTAX      Counter64
   MAX-ACCESS  read-only
   STATUS      current
   DESCRIPTION
      "Path: swPort.performance.pppoEClient.mibCounters.h2Performance.ifOutMcastPkts

       64 bit unsigned wrappable counter."
   ::= {pr1645v2EthPrtSwF2PPPoEMCH2PEntry 469762048}

pr1645v2EthPrtSwF2PPPoEMCH2PIfOutDiscards OBJECT-TYPE
   SYNTAX      Counter64
   MAX-ACCESS  read-only
   STATUS      current
   DESCRIPTION
      "Path: swPort.performance.pppoEClient.mibCounters.h2Performance.ifOutDiscards

       64 bit unsigned wrappable counter."
   ::= {pr1645v2EthPrtSwF2PPPoEMCH2PEntry 218103808}

pr1645v2EthPrtSwF2PPPoEMCH2PIfOutErrors OBJECT-TYPE
   SYNTAX      Counter64
   MAX-ACCESS  read-only
   STATUS      current
   DESCRIPTION
      "Path: swPort.performance.pppoEClient.mibCounters.h2Performance.ifOutErrors

       64 bit unsigned wrappable counter."
   ::= {pr1645v2EthPrtSwF2PPPoEMCH2PEntry 234881024}

pr1645v2EthPrtSwF2PPPoEMCH2POutDropEx OBJECT-TYPE
   SYNTAX      Counter64
   MAX-ACCESS  read-only
   STATUS      current
   DESCRIPTION
      "Path: swPort.performance.pppoEClient.mibCounters.h2Performance.ifOutDropLevelExceeded

       64 bit unsigned wrappable counter."
   ::= {pr1645v2EthPrtSwF2PPPoEMCH2PEntry 352321536}

pr1645v2EthPrtSwF2PPPoEMCH2POutDropNoArp OBJECT-TYPE
   SYNTAX      Counter64
   MAX-ACCESS  read-only
   STATUS      current
   DESCRIPTION
      "Path: swPort.performance.pppoEClient.mibCounters.h2Performance.ifOutDiscardsNoArp

       64 bit unsigned wrappable counter."
   ::= {pr1645v2EthPrtSwF2PPPoEMCH2PEntry 369098752}

pr1645v2EthPrtSwF2PPPoEMCH2POutDropFilter OBJECT-TYPE
   SYNTAX      Counter64
   MAX-ACCESS  read-only
   STATUS      current
   DESCRIPTION
      "Path: swPort.performance.pppoEClient.mibCounters.h2Performance.ifOutDiscardsFilter

       64 bit unsigned wrappable counter."
   ::= {pr1645v2EthPrtSwF2PPPoEMCH2PEntry 402653184}

pr1645v2EthPrtSwF2PPPoEMCH2PIfOutBandwidth OBJECT-TYPE
   SYNTAX      Integer32
   MAX-ACCESS  read-only
   STATUS      current
   DESCRIPTION
      "Path: swPort.performance.pppoEClient.mibCounters.h2Performance.ifOutBandwidth

       unit name = bps
       formula = 8 * ; 8 /"
   ::= {pr1645v2EthPrtSwF2PPPoEMCH2PEntry 285212672}

pr1645v2EthPrtSwF2PPPoEMCH2PIfErrSec OBJECT-TYPE
   SYNTAX      Counter32
   MAX-ACCESS  read-only
   STATUS      current
   DESCRIPTION
      "Path: swPort.performance.pppoEClient.mibCounters.h2Performance.ifErrSec

       32 bit unsigned wrappable counter."
   ::= {pr1645v2EthPrtSwF2PPPoEMCH2PEntry 251658240}

pr1645v2EthPrtSwF2PPPoEMCH24P OBJECT-TYPE
   SYNTAX      SEQUENCE OF Pr1645v2EthPrtSwF2PPPoEMCH24PEntry
   MAX-ACCESS  not-accessible
   STATUS      current
   DESCRIPTION
      ""
   ::= {pr1645v2EthPrtSwF2PPPoE 41615360}

pr1645v2EthPrtSwF2PPPoEMCH24PEntry OBJECT-TYPE
   SYNTAX      Pr1645v2EthPrtSwF2PPPoEMCH24PEntry
   MAX-ACCESS  not-accessible
   STATUS      current
   DESCRIPTION
      ""
   INDEX      { pr1645v2EthPrtSwF2PPPoEMCH24PGlobalIx,
                pr1645v2EthPrtSwF2PPPoETableIx,
                pr1645v2EthPrtSwF2PPPoEMCH24PTableIx }
   ::= {pr1645v2EthPrtSwF2PPPoEMCH24P 1}

Pr1645v2EthPrtSwF2PPPoEMCH24PEntry ::=
   SEQUENCE
      {
      pr1645v2EthPrtSwF2PPPoEMCH24PGlobalIx
         GlobalIndex,
      pr1645v2EthPrtSwF2PPPoEMCH24PTableIx
         TableIndex,
      pr1645v2EthPrtSwF2PPPoEMCH24PSysUpTime
         TimeTicks,
      pr1645v2EthPrtSwF2PPPoEMCH24PIfUpTime
         TimeTicks,
      pr1645v2EthPrtSwF2PPPoEMCH24PIfStatChanges
         Counter32,
      pr1645v2EthPrtSwF2PPPoEMCH24PIfInOctets
         Counter64,
      pr1645v2EthPrtSwF2PPPoEMCH24PIfInUCPkts
         Counter64,
      pr1645v2EthPrtSwF2PPPoEMCH24PIfInNUCPkts
         Counter64,
      pr1645v2EthPrtSwF2PPPoEMCH24PIfInBCPkts
         Counter64,
      pr1645v2EthPrtSwF2PPPoEMCH24PIfInMCPkts
         Counter64,
      pr1645v2EthPrtSwF2PPPoEMCH24PIfInDiscards
         Counter64,
      pr1645v2EthPrtSwF2PPPoEMCH24PIfInErrors
         Counter64,
      pr1645v2EthPrtSwF2PPPoEMCH24PIfInUnkwn
         Counter64,
      pr1645v2EthPrtSwF2PPPoEMCH24PInDropEx
         Counter64,
      pr1645v2EthPrtSwF2PPPoEMCH24PInDropNoMac
         Counter64,
      pr1645v2EthPrtSwF2PPPoEMCH24PInDropNUCast
         Counter64,
      pr1645v2EthPrtSwF2PPPoEMCH24PInDropFilter
         Counter64,
      pr1645v2EthPrtSwF2PPPoEMCH24PIfInBandwidth
         Integer32,
      pr1645v2EthPrtSwF2PPPoEMCH24PIfOutOctets
         Counter64,
      pr1645v2EthPrtSwF2PPPoEMCH24PIfOutUCPkts
         Counter64,
      pr1645v2EthPrtSwF2PPPoEMCH24PIfOutNUCPkts
         Counter64,
      pr1645v2EthPrtSwF2PPPoEMCH24PIfOutBCPkts
         Counter64,
      pr1645v2EthPrtSwF2PPPoEMCH24PIfOutMCPkts
         Counter64,
      pr1645v2EthPrtSwF2PPPoEMCH24PIfOutDiscards
         Counter64,
      pr1645v2EthPrtSwF2PPPoEMCH24PIfOutErrors
         Counter64,
      pr1645v2EthPrtSwF2PPPoEMCH24POutDropEx
         Counter64,
      pr1645v2EthPrtSwF2PPPoEMCH24POutDropNoArp
         Counter64,
      pr1645v2EthPrtSwF2PPPoEMCH24POutDropFilter
         Counter64,
      pr1645v2EthPrtSwF2PPPoEMCH24PIfOutBandwidth
         Integer32,
      pr1645v2EthPrtSwF2PPPoEMCH24PIfErrSec
         Counter32
      }

pr1645v2EthPrtSwF2PPPoEMCH24PGlobalIx OBJECT-TYPE
   SYNTAX      GlobalIndex
   MAX-ACCESS  not-accessible
   STATUS      current
   DESCRIPTION
      "The value of the tlsCntTreeGlobalIndex of the MANAGED OBJECT."
   ::= {pr1645v2EthPrtSwF2PPPoEMCH24PEntry 10}

pr1645v2EthPrtSwF2PPPoEMCH24PTableIx OBJECT-TYPE
   SYNTAX      TableIndex
   MAX-ACCESS  not-accessible
   STATUS      current
   DESCRIPTION
      ""
   ::= {pr1645v2EthPrtSwF2PPPoEMCH24PEntry 11}

pr1645v2EthPrtSwF2PPPoEMCH24PSysUpTime OBJECT-TYPE
   SYNTAX      TimeTicks
   MAX-ACCESS  read-only
   STATUS      current
   DESCRIPTION
      "Path: swPort.performance.pppoEClient.mibCounters.h24Performance.sysUpTime

       Time in centi-second."
   ::= {pr1645v2EthPrtSwF2PPPoEMCH24PEntry 16777216}

pr1645v2EthPrtSwF2PPPoEMCH24PIfUpTime OBJECT-TYPE
   SYNTAX      TimeTicks
   MAX-ACCESS  read-only
   STATUS      current
   DESCRIPTION
      "Path: swPort.performance.pppoEClient.mibCounters.h24Performance.ifUpTime

       Time in centi-second."
   ::= {pr1645v2EthPrtSwF2PPPoEMCH24PEntry 33554432}

pr1645v2EthPrtSwF2PPPoEMCH24PIfStatChanges OBJECT-TYPE
   SYNTAX      Counter32
   MAX-ACCESS  read-only
   STATUS      current
   DESCRIPTION
      "Path: swPort.performance.pppoEClient.mibCounters.h24Performance.ifStatusChanges

       32 bit unsigned wrappable counter."
   ::= {pr1645v2EthPrtSwF2PPPoEMCH24PEntry 50331648}

pr1645v2EthPrtSwF2PPPoEMCH24PIfInOctets OBJECT-TYPE
   SYNTAX      Counter64
   MAX-ACCESS  read-only
   STATUS      current
   DESCRIPTION
      "Path: swPort.performance.pppoEClient.mibCounters.h24Performance.ifInOctets

       64 bit unsigned wrappable counter."
   ::= {pr1645v2EthPrtSwF2PPPoEMCH24PEntry 67108864}

pr1645v2EthPrtSwF2PPPoEMCH24PIfInUCPkts OBJECT-TYPE
   SYNTAX      Counter64
   MAX-ACCESS  read-only
   STATUS      current
   DESCRIPTION
      "Path: swPort.performance.pppoEClient.mibCounters.h24Performance.ifInUcastPkts

       64 bit unsigned wrappable counter."
   ::= {pr1645v2EthPrtSwF2PPPoEMCH24PEntry 83886080}

pr1645v2EthPrtSwF2PPPoEMCH24PIfInNUCPkts OBJECT-TYPE
   SYNTAX      Counter64
   MAX-ACCESS  read-only
   STATUS      current
   DESCRIPTION
      "Path: swPort.performance.pppoEClient.mibCounters.h24Performance.ifInNUcastPkts

       64 bit unsigned wrappable counter."
   ::= {pr1645v2EthPrtSwF2PPPoEMCH24PEntry 100663296}

pr1645v2EthPrtSwF2PPPoEMCH24PIfInBCPkts OBJECT-TYPE
   SYNTAX      Counter64
   MAX-ACCESS  read-only
   STATUS      current
   DESCRIPTION
      "Path: swPort.performance.pppoEClient.mibCounters.h24Performance.ifInBcastPkts

       64 bit unsigned wrappable counter."
   ::= {pr1645v2EthPrtSwF2PPPoEMCH24PEntry 419430400}

pr1645v2EthPrtSwF2PPPoEMCH24PIfInMCPkts OBJECT-TYPE
   SYNTAX      Counter64
   MAX-ACCESS  read-only
   STATUS      current
   DESCRIPTION
      "Path: swPort.performance.pppoEClient.mibCounters.h24Performance.ifInMcastPkts

       64 bit unsigned wrappable counter."
   ::= {pr1645v2EthPrtSwF2PPPoEMCH24PEntry 436207616}

pr1645v2EthPrtSwF2PPPoEMCH24PIfInDiscards OBJECT-TYPE
   SYNTAX      Counter64
   MAX-ACCESS  read-only
   STATUS      current
   DESCRIPTION
      "Path: swPort.performance.pppoEClient.mibCounters.h24Performance.ifInDiscards

       64 bit unsigned wrappable counter."
   ::= {pr1645v2EthPrtSwF2PPPoEMCH24PEntry 117440512}

pr1645v2EthPrtSwF2PPPoEMCH24PIfInErrors OBJECT-TYPE
   SYNTAX      Counter64
   MAX-ACCESS  read-only
   STATUS      current
   DESCRIPTION
      "Path: swPort.performance.pppoEClient.mibCounters.h24Performance.ifInErrors

       64 bit unsigned wrappable counter."
   ::= {pr1645v2EthPrtSwF2PPPoEMCH24PEntry 134217728}

pr1645v2EthPrtSwF2PPPoEMCH24PIfInUnkwn OBJECT-TYPE
   SYNTAX      Counter64
   MAX-ACCESS  read-only
   STATUS      current
   DESCRIPTION
      "Path: swPort.performance.pppoEClient.mibCounters.h24Performance.ifInUnknownProtos

       64 bit unsigned wrappable counter."
   ::= {pr1645v2EthPrtSwF2PPPoEMCH24PEntry 150994944}

pr1645v2EthPrtSwF2PPPoEMCH24PInDropEx OBJECT-TYPE
   SYNTAX      Counter64
   MAX-ACCESS  read-only
   STATUS      current
   DESCRIPTION
      "Path: swPort.performance.pppoEClient.mibCounters.h24Performance.ifInDropLevelExceeded

       64 bit unsigned wrappable counter."
   ::= {pr1645v2EthPrtSwF2PPPoEMCH24PEntry 335544320}

pr1645v2EthPrtSwF2PPPoEMCH24PInDropNoMac OBJECT-TYPE
   SYNTAX      Counter64
   MAX-ACCESS  read-only
   STATUS      current
   DESCRIPTION
      "Path: swPort.performance.pppoEClient.mibCounters.h24Performance.fInDiscardsNoMacFit

       64 bit unsigned wrappable counter."
   ::= {pr1645v2EthPrtSwF2PPPoEMCH24PEntry 301989888}

pr1645v2EthPrtSwF2PPPoEMCH24PInDropNUCast OBJECT-TYPE
   SYNTAX      Counter64
   MAX-ACCESS  read-only
   STATUS      current
   DESCRIPTION
      "Path: swPort.performance.pppoEClient.mibCounters.h24Performance.fInDiscardsNUCast

       64 bit unsigned wrappable counter."
   ::= {pr1645v2EthPrtSwF2PPPoEMCH24PEntry 318767104}

pr1645v2EthPrtSwF2PPPoEMCH24PInDropFilter OBJECT-TYPE
   SYNTAX      Counter64
   MAX-ACCESS  read-only
   STATUS      current
   DESCRIPTION
      "Path: swPort.performance.pppoEClient.mibCounters.h24Performance.fInDiscardsFilter

       64 bit unsigned wrappable counter."
   ::= {pr1645v2EthPrtSwF2PPPoEMCH24PEntry 385875968}

pr1645v2EthPrtSwF2PPPoEMCH24PIfInBandwidth OBJECT-TYPE
   SYNTAX      Integer32
   MAX-ACCESS  read-only
   STATUS      current
   DESCRIPTION
      "Path: swPort.performance.pppoEClient.mibCounters.h24Performance.ifInBandwidth

       unit name = bps
       formula = 8 * ; 8 /"
   ::= {pr1645v2EthPrtSwF2PPPoEMCH24PEntry 268435456}

pr1645v2EthPrtSwF2PPPoEMCH24PIfOutOctets OBJECT-TYPE
   SYNTAX      Counter64
   MAX-ACCESS  read-only
   STATUS      current
   DESCRIPTION
      "Path: swPort.performance.pppoEClient.mibCounters.h24Performance.ifOutOctets

       64 bit unsigned wrappable counter."
   ::= {pr1645v2EthPrtSwF2PPPoEMCH24PEntry 167772160}

pr1645v2EthPrtSwF2PPPoEMCH24PIfOutUCPkts OBJECT-TYPE
   SYNTAX      Counter64
   MAX-ACCESS  read-only
   STATUS      current
   DESCRIPTION
      "Path: swPort.performance.pppoEClient.mibCounters.h24Performance.ifOutUcastPkts

       64 bit unsigned wrappable counter."
   ::= {pr1645v2EthPrtSwF2PPPoEMCH24PEntry 184549376}

pr1645v2EthPrtSwF2PPPoEMCH24PIfOutNUCPkts OBJECT-TYPE
   SYNTAX      Counter64
   MAX-ACCESS  read-only
   STATUS      current
   DESCRIPTION
      "Path: swPort.performance.pppoEClient.mibCounters.h24Performance.ifOutNUcastPkts

       64 bit unsigned wrappable counter."
   ::= {pr1645v2EthPrtSwF2PPPoEMCH24PEntry 201326592}

pr1645v2EthPrtSwF2PPPoEMCH24PIfOutBCPkts OBJECT-TYPE
   SYNTAX      Counter64
   MAX-ACCESS  read-only
   STATUS      current
   DESCRIPTION
      "Path: swPort.performance.pppoEClient.mibCounters.h24Performance.ifOutBcastPkts

       64 bit unsigned wrappable counter."
   ::= {pr1645v2EthPrtSwF2PPPoEMCH24PEntry 452984832}

pr1645v2EthPrtSwF2PPPoEMCH24PIfOutMCPkts OBJECT-TYPE
   SYNTAX      Counter64
   MAX-ACCESS  read-only
   STATUS      current
   DESCRIPTION
      "Path: swPort.performance.pppoEClient.mibCounters.h24Performance.ifOutMcastPkts

       64 bit unsigned wrappable counter."
   ::= {pr1645v2EthPrtSwF2PPPoEMCH24PEntry 469762048}

pr1645v2EthPrtSwF2PPPoEMCH24PIfOutDiscards OBJECT-TYPE
   SYNTAX      Counter64
   MAX-ACCESS  read-only
   STATUS      current
   DESCRIPTION
      "Path: swPort.performance.pppoEClient.mibCounters.h24Performance.ifOutDiscards

       64 bit unsigned wrappable counter."
   ::= {pr1645v2EthPrtSwF2PPPoEMCH24PEntry 218103808}

pr1645v2EthPrtSwF2PPPoEMCH24PIfOutErrors OBJECT-TYPE
   SYNTAX      Counter64
   MAX-ACCESS  read-only
   STATUS      current
   DESCRIPTION
      "Path: swPort.performance.pppoEClient.mibCounters.h24Performance.ifOutErrors

       64 bit unsigned wrappable counter."
   ::= {pr1645v2EthPrtSwF2PPPoEMCH24PEntry 234881024}

pr1645v2EthPrtSwF2PPPoEMCH24POutDropEx OBJECT-TYPE
   SYNTAX      Counter64
   MAX-ACCESS  read-only
   STATUS      current
   DESCRIPTION
      "Path: swPort.performance.pppoEClient.mibCounters.h24Performance.ifOutDropLevelExceeded

       64 bit unsigned wrappable counter."
   ::= {pr1645v2EthPrtSwF2PPPoEMCH24PEntry 352321536}

pr1645v2EthPrtSwF2PPPoEMCH24POutDropNoArp OBJECT-TYPE
   SYNTAX      Counter64
   MAX-ACCESS  read-only
   STATUS      current
   DESCRIPTION
      "Path: swPort.performance.pppoEClient.mibCounters.h24Performance.ifOutDiscardsNoArp

       64 bit unsigned wrappable counter."
   ::= {pr1645v2EthPrtSwF2PPPoEMCH24PEntry 369098752}

pr1645v2EthPrtSwF2PPPoEMCH24POutDropFilter OBJECT-TYPE
   SYNTAX      Counter64
   MAX-ACCESS  read-only
   STATUS      current
   DESCRIPTION
      "Path: swPort.performance.pppoEClient.mibCounters.h24Performance.ifOutDiscardsFilter

       64 bit unsigned wrappable counter."
   ::= {pr1645v2EthPrtSwF2PPPoEMCH24PEntry 402653184}

pr1645v2EthPrtSwF2PPPoEMCH24PIfOutBandwidth OBJECT-TYPE
   SYNTAX      Integer32
   MAX-ACCESS  read-only
   STATUS      current
   DESCRIPTION
      "Path: swPort.performance.pppoEClient.mibCounters.h24Performance.ifOutBandwidth

       unit name = bps
       formula = 8 * ; 8 /"
   ::= {pr1645v2EthPrtSwF2PPPoEMCH24PEntry 285212672}

pr1645v2EthPrtSwF2PPPoEMCH24PIfErrSec OBJECT-TYPE
   SYNTAX      Counter32
   MAX-ACCESS  read-only
   STATUS      current
   DESCRIPTION
      "Path: swPort.performance.pppoEClient.mibCounters.h24Performance.ifErrSec

       32 bit unsigned wrappable counter."
   ::= {pr1645v2EthPrtSwF2PPPoEMCH24PEntry 251658240}

pr1645v2EthPrtSwF2PPPoEMCD7P OBJECT-TYPE
   SYNTAX      SEQUENCE OF Pr1645v2EthPrtSwF2PPPoEMCD7PEntry
   MAX-ACCESS  not-accessible
   STATUS      current
   DESCRIPTION
      ""
   ::= {pr1645v2EthPrtSwF2PPPoE 41680896}

pr1645v2EthPrtSwF2PPPoEMCD7PEntry OBJECT-TYPE
   SYNTAX      Pr1645v2EthPrtSwF2PPPoEMCD7PEntry
   MAX-ACCESS  not-accessible
   STATUS      current
   DESCRIPTION
      ""
   INDEX      { pr1645v2EthPrtSwF2PPPoEMCD7PGlobalIx,
                pr1645v2EthPrtSwF2PPPoETableIx,
                pr1645v2EthPrtSwF2PPPoEMCD7PTableIx }
   ::= {pr1645v2EthPrtSwF2PPPoEMCD7P 1}

Pr1645v2EthPrtSwF2PPPoEMCD7PEntry ::=
   SEQUENCE
      {
      pr1645v2EthPrtSwF2PPPoEMCD7PGlobalIx
         GlobalIndex,
      pr1645v2EthPrtSwF2PPPoEMCD7PTableIx
         TableIndex,
      pr1645v2EthPrtSwF2PPPoEMCD7PSysUpTime
         TimeTicks,
      pr1645v2EthPrtSwF2PPPoEMCD7PIfUpTime
         TimeTicks,
      pr1645v2EthPrtSwF2PPPoEMCD7PIfStatChanges
         Counter32,
      pr1645v2EthPrtSwF2PPPoEMCD7PIfInOctets
         Counter64,
      pr1645v2EthPrtSwF2PPPoEMCD7PIfInUCPkts
         Counter64,
      pr1645v2EthPrtSwF2PPPoEMCD7PIfInNUCPkts
         Counter64,
      pr1645v2EthPrtSwF2PPPoEMCD7PIfInBCPkts
         Counter64,
      pr1645v2EthPrtSwF2PPPoEMCD7PIfInMCPkts
         Counter64,
      pr1645v2EthPrtSwF2PPPoEMCD7PIfInDiscards
         Counter64,
      pr1645v2EthPrtSwF2PPPoEMCD7PIfInErrors
         Counter64,
      pr1645v2EthPrtSwF2PPPoEMCD7PIfInUnkwn
         Counter64,
      pr1645v2EthPrtSwF2PPPoEMCD7PInDropEx
         Counter64,
      pr1645v2EthPrtSwF2PPPoEMCD7PInDropNoMac
         Counter64,
      pr1645v2EthPrtSwF2PPPoEMCD7PInDropNUCast
         Counter64,
      pr1645v2EthPrtSwF2PPPoEMCD7PInDropFilter
         Counter64,
      pr1645v2EthPrtSwF2PPPoEMCD7PIfInBandwidth
         Integer32,
      pr1645v2EthPrtSwF2PPPoEMCD7PIfOutOctets
         Counter64,
      pr1645v2EthPrtSwF2PPPoEMCD7PIfOutUCPkts
         Counter64,
      pr1645v2EthPrtSwF2PPPoEMCD7PIfOutNUCPkts
         Counter64,
      pr1645v2EthPrtSwF2PPPoEMCD7PIfOutBCPkts
         Counter64,
      pr1645v2EthPrtSwF2PPPoEMCD7PIfOutMCPkts
         Counter64,
      pr1645v2EthPrtSwF2PPPoEMCD7PIfOutDiscards
         Counter64,
      pr1645v2EthPrtSwF2PPPoEMCD7PIfOutErrors
         Counter64,
      pr1645v2EthPrtSwF2PPPoEMCD7POutDropEx
         Counter64,
      pr1645v2EthPrtSwF2PPPoEMCD7POutDropNoArp
         Counter64,
      pr1645v2EthPrtSwF2PPPoEMCD7POutDropFilter
         Counter64,
      pr1645v2EthPrtSwF2PPPoEMCD7PIfOutBandwidth
         Integer32,
      pr1645v2EthPrtSwF2PPPoEMCD7PIfErrSec
         Counter32
      }

pr1645v2EthPrtSwF2PPPoEMCD7PGlobalIx OBJECT-TYPE
   SYNTAX      GlobalIndex
   MAX-ACCESS  not-accessible
   STATUS      current
   DESCRIPTION
      "The value of the tlsCntTreeGlobalIndex of the MANAGED OBJECT."
   ::= {pr1645v2EthPrtSwF2PPPoEMCD7PEntry 10}

pr1645v2EthPrtSwF2PPPoEMCD7PTableIx OBJECT-TYPE
   SYNTAX      TableIndex
   MAX-ACCESS  not-accessible
   STATUS      current
   DESCRIPTION
      ""
   ::= {pr1645v2EthPrtSwF2PPPoEMCD7PEntry 11}

pr1645v2EthPrtSwF2PPPoEMCD7PSysUpTime OBJECT-TYPE
   SYNTAX      TimeTicks
   MAX-ACCESS  read-only
   STATUS      current
   DESCRIPTION
      "Path: swPort.performance.pppoEClient.mibCounters.d7Performance.sysUpTime

       Time in centi-second."
   ::= {pr1645v2EthPrtSwF2PPPoEMCD7PEntry 16777216}

pr1645v2EthPrtSwF2PPPoEMCD7PIfUpTime OBJECT-TYPE
   SYNTAX      TimeTicks
   MAX-ACCESS  read-only
   STATUS      current
   DESCRIPTION
      "Path: swPort.performance.pppoEClient.mibCounters.d7Performance.ifUpTime

       Time in centi-second."
   ::= {pr1645v2EthPrtSwF2PPPoEMCD7PEntry 33554432}

pr1645v2EthPrtSwF2PPPoEMCD7PIfStatChanges OBJECT-TYPE
   SYNTAX      Counter32
   MAX-ACCESS  read-only
   STATUS      current
   DESCRIPTION
      "Path: swPort.performance.pppoEClient.mibCounters.d7Performance.ifStatusChanges

       32 bit unsigned wrappable counter."
   ::= {pr1645v2EthPrtSwF2PPPoEMCD7PEntry 50331648}

pr1645v2EthPrtSwF2PPPoEMCD7PIfInOctets OBJECT-TYPE
   SYNTAX      Counter64
   MAX-ACCESS  read-only
   STATUS      current
   DESCRIPTION
      "Path: swPort.performance.pppoEClient.mibCounters.d7Performance.ifInOctets

       64 bit unsigned wrappable counter."
   ::= {pr1645v2EthPrtSwF2PPPoEMCD7PEntry 67108864}

pr1645v2EthPrtSwF2PPPoEMCD7PIfInUCPkts OBJECT-TYPE
   SYNTAX      Counter64
   MAX-ACCESS  read-only
   STATUS      current
   DESCRIPTION
      "Path: swPort.performance.pppoEClient.mibCounters.d7Performance.ifInUcastPkts

       64 bit unsigned wrappable counter."
   ::= {pr1645v2EthPrtSwF2PPPoEMCD7PEntry 83886080}

pr1645v2EthPrtSwF2PPPoEMCD7PIfInNUCPkts OBJECT-TYPE
   SYNTAX      Counter64
   MAX-ACCESS  read-only
   STATUS      current
   DESCRIPTION
      "Path: swPort.performance.pppoEClient.mibCounters.d7Performance.ifInNUcastPkts

       64 bit unsigned wrappable counter."
   ::= {pr1645v2EthPrtSwF2PPPoEMCD7PEntry 100663296}

pr1645v2EthPrtSwF2PPPoEMCD7PIfInBCPkts OBJECT-TYPE
   SYNTAX      Counter64
   MAX-ACCESS  read-only
   STATUS      current
   DESCRIPTION
      "Path: swPort.performance.pppoEClient.mibCounters.d7Performance.ifInBcastPkts

       64 bit unsigned wrappable counter."
   ::= {pr1645v2EthPrtSwF2PPPoEMCD7PEntry 419430400}

pr1645v2EthPrtSwF2PPPoEMCD7PIfInMCPkts OBJECT-TYPE
   SYNTAX      Counter64
   MAX-ACCESS  read-only
   STATUS      current
   DESCRIPTION
      "Path: swPort.performance.pppoEClient.mibCounters.d7Performance.ifInMcastPkts

       64 bit unsigned wrappable counter."
   ::= {pr1645v2EthPrtSwF2PPPoEMCD7PEntry 436207616}

pr1645v2EthPrtSwF2PPPoEMCD7PIfInDiscards OBJECT-TYPE
   SYNTAX      Counter64
   MAX-ACCESS  read-only
   STATUS      current
   DESCRIPTION
      "Path: swPort.performance.pppoEClient.mibCounters.d7Performance.ifInDiscards

       64 bit unsigned wrappable counter."
   ::= {pr1645v2EthPrtSwF2PPPoEMCD7PEntry 117440512}

pr1645v2EthPrtSwF2PPPoEMCD7PIfInErrors OBJECT-TYPE
   SYNTAX      Counter64
   MAX-ACCESS  read-only
   STATUS      current
   DESCRIPTION
      "Path: swPort.performance.pppoEClient.mibCounters.d7Performance.ifInErrors

       64 bit unsigned wrappable counter."
   ::= {pr1645v2EthPrtSwF2PPPoEMCD7PEntry 134217728}

pr1645v2EthPrtSwF2PPPoEMCD7PIfInUnkwn OBJECT-TYPE
   SYNTAX      Counter64
   MAX-ACCESS  read-only
   STATUS      current
   DESCRIPTION
      "Path: swPort.performance.pppoEClient.mibCounters.d7Performance.ifInUnknownProtos

       64 bit unsigned wrappable counter."
   ::= {pr1645v2EthPrtSwF2PPPoEMCD7PEntry 150994944}

pr1645v2EthPrtSwF2PPPoEMCD7PInDropEx OBJECT-TYPE
   SYNTAX      Counter64
   MAX-ACCESS  read-only
   STATUS      current
   DESCRIPTION
      "Path: swPort.performance.pppoEClient.mibCounters.d7Performance.ifInDropLevelExceeded

       64 bit unsigned wrappable counter."
   ::= {pr1645v2EthPrtSwF2PPPoEMCD7PEntry 335544320}

pr1645v2EthPrtSwF2PPPoEMCD7PInDropNoMac OBJECT-TYPE
   SYNTAX      Counter64
   MAX-ACCESS  read-only
   STATUS      current
   DESCRIPTION
      "Path: swPort.performance.pppoEClient.mibCounters.d7Performance.fInDiscardsNoMacFit

       64 bit unsigned wrappable counter."
   ::= {pr1645v2EthPrtSwF2PPPoEMCD7PEntry 301989888}

pr1645v2EthPrtSwF2PPPoEMCD7PInDropNUCast OBJECT-TYPE
   SYNTAX      Counter64
   MAX-ACCESS  read-only
   STATUS      current
   DESCRIPTION
      "Path: swPort.performance.pppoEClient.mibCounters.d7Performance.fInDiscardsNUCast

       64 bit unsigned wrappable counter."
   ::= {pr1645v2EthPrtSwF2PPPoEMCD7PEntry 318767104}

pr1645v2EthPrtSwF2PPPoEMCD7PInDropFilter OBJECT-TYPE
   SYNTAX      Counter64
   MAX-ACCESS  read-only
   STATUS      current
   DESCRIPTION
      "Path: swPort.performance.pppoEClient.mibCounters.d7Performance.fInDiscardsFilter

       64 bit unsigned wrappable counter."
   ::= {pr1645v2EthPrtSwF2PPPoEMCD7PEntry 385875968}

pr1645v2EthPrtSwF2PPPoEMCD7PIfInBandwidth OBJECT-TYPE
   SYNTAX      Integer32
   MAX-ACCESS  read-only
   STATUS      current
   DESCRIPTION
      "Path: swPort.performance.pppoEClient.mibCounters.d7Performance.ifInBandwidth

       unit name = bps
       formula = 8 * ; 8 /"
   ::= {pr1645v2EthPrtSwF2PPPoEMCD7PEntry 268435456}

pr1645v2EthPrtSwF2PPPoEMCD7PIfOutOctets OBJECT-TYPE
   SYNTAX      Counter64
   MAX-ACCESS  read-only
   STATUS      current
   DESCRIPTION
      "Path: swPort.performance.pppoEClient.mibCounters.d7Performance.ifOutOctets

       64 bit unsigned wrappable counter."
   ::= {pr1645v2EthPrtSwF2PPPoEMCD7PEntry 167772160}

pr1645v2EthPrtSwF2PPPoEMCD7PIfOutUCPkts OBJECT-TYPE
   SYNTAX      Counter64
   MAX-ACCESS  read-only
   STATUS      current
   DESCRIPTION
      "Path: swPort.performance.pppoEClient.mibCounters.d7Performance.ifOutUcastPkts

       64 bit unsigned wrappable counter."
   ::= {pr1645v2EthPrtSwF2PPPoEMCD7PEntry 184549376}

pr1645v2EthPrtSwF2PPPoEMCD7PIfOutNUCPkts OBJECT-TYPE
   SYNTAX      Counter64
   MAX-ACCESS  read-only
   STATUS      current
   DESCRIPTION
      "Path: swPort.performance.pppoEClient.mibCounters.d7Performance.ifOutNUcastPkts

       64 bit unsigned wrappable counter."
   ::= {pr1645v2EthPrtSwF2PPPoEMCD7PEntry 201326592}

pr1645v2EthPrtSwF2PPPoEMCD7PIfOutBCPkts OBJECT-TYPE
   SYNTAX      Counter64
   MAX-ACCESS  read-only
   STATUS      current
   DESCRIPTION
      "Path: swPort.performance.pppoEClient.mibCounters.d7Performance.ifOutBcastPkts

       64 bit unsigned wrappable counter."
   ::= {pr1645v2EthPrtSwF2PPPoEMCD7PEntry 452984832}

pr1645v2EthPrtSwF2PPPoEMCD7PIfOutMCPkts OBJECT-TYPE
   SYNTAX      Counter64
   MAX-ACCESS  read-only
   STATUS      current
   DESCRIPTION
      "Path: swPort.performance.pppoEClient.mibCounters.d7Performance.ifOutMcastPkts

       64 bit unsigned wrappable counter."
   ::= {pr1645v2EthPrtSwF2PPPoEMCD7PEntry 469762048}

pr1645v2EthPrtSwF2PPPoEMCD7PIfOutDiscards OBJECT-TYPE
   SYNTAX      Counter64
   MAX-ACCESS  read-only
   STATUS      current
   DESCRIPTION
      "Path: swPort.performance.pppoEClient.mibCounters.d7Performance.ifOutDiscards

       64 bit unsigned wrappable counter."
   ::= {pr1645v2EthPrtSwF2PPPoEMCD7PEntry 218103808}

pr1645v2EthPrtSwF2PPPoEMCD7PIfOutErrors OBJECT-TYPE
   SYNTAX      Counter64
   MAX-ACCESS  read-only
   STATUS      current
   DESCRIPTION
      "Path: swPort.performance.pppoEClient.mibCounters.d7Performance.ifOutErrors

       64 bit unsigned wrappable counter."
   ::= {pr1645v2EthPrtSwF2PPPoEMCD7PEntry 234881024}

pr1645v2EthPrtSwF2PPPoEMCD7POutDropEx OBJECT-TYPE
   SYNTAX      Counter64
   MAX-ACCESS  read-only
   STATUS      current
   DESCRIPTION
      "Path: swPort.performance.pppoEClient.mibCounters.d7Performance.ifOutDropLevelExceeded

       64 bit unsigned wrappable counter."
   ::= {pr1645v2EthPrtSwF2PPPoEMCD7PEntry 352321536}

pr1645v2EthPrtSwF2PPPoEMCD7POutDropNoArp OBJECT-TYPE
   SYNTAX      Counter64
   MAX-ACCESS  read-only
   STATUS      current
   DESCRIPTION
      "Path: swPort.performance.pppoEClient.mibCounters.d7Performance.ifOutDiscardsNoArp

       64 bit unsigned wrappable counter."
   ::= {pr1645v2EthPrtSwF2PPPoEMCD7PEntry 369098752}

pr1645v2EthPrtSwF2PPPoEMCD7POutDropFilter OBJECT-TYPE
   SYNTAX      Counter64
   MAX-ACCESS  read-only
   STATUS      current
   DESCRIPTION
      "Path: swPort.performance.pppoEClient.mibCounters.d7Performance.ifOutDiscardsFilter

       64 bit unsigned wrappable counter."
   ::= {pr1645v2EthPrtSwF2PPPoEMCD7PEntry 402653184}

pr1645v2EthPrtSwF2PPPoEMCD7PIfOutBandwidth OBJECT-TYPE
   SYNTAX      Integer32
   MAX-ACCESS  read-only
   STATUS      current
   DESCRIPTION
      "Path: swPort.performance.pppoEClient.mibCounters.d7Performance.ifOutBandwidth

       unit name = bps
       formula = 8 * ; 8 /"
   ::= {pr1645v2EthPrtSwF2PPPoEMCD7PEntry 285212672}

pr1645v2EthPrtSwF2PPPoEMCD7PIfErrSec OBJECT-TYPE
   SYNTAX      Counter32
   MAX-ACCESS  read-only
   STATUS      current
   DESCRIPTION
      "Path: swPort.performance.pppoEClient.mibCounters.d7Performance.ifErrSec

       32 bit unsigned wrappable counter."
   ::= {pr1645v2EthPrtSwF2PPPoEMCD7PEntry 251658240}



ar1645v2EthPrtSwF2 OBJECT IDENTIFIER ::= {r1645v2EthPrtSwF2 16}


ar1645v2EthPrtSwF2ClearCounters OBJECT IDENTIFIER ::= {ar1645v2EthPrtSwF2 263}

ar1645v2EthPrtSwF2ClearCountersTable OBJECT-TYPE
   SYNTAX      SEQUENCE OF Ar1645v2EthPrtSwF2ClearCountersEntry
   MAX-ACCESS  not-accessible
   STATUS      current
   DESCRIPTION
      "reset counters"
   ::= {ar1645v2EthPrtSwF2ClearCounters 1}

ar1645v2EthPrtSwF2ClearCountersEntry OBJECT-TYPE
   SYNTAX      Ar1645v2EthPrtSwF2ClearCountersEntry
   MAX-ACCESS  not-accessible
   STATUS      current
   DESCRIPTION
      ""
   INDEX      { ar1645v2EthPrtSwF2ClearCountersGlobalIx }
   ::= {ar1645v2EthPrtSwF2ClearCountersTable 1}

Ar1645v2EthPrtSwF2ClearCountersEntry ::=
   SEQUENCE
      {
      ar1645v2EthPrtSwF2ClearCountersGlobalIx
         GlobalIndex,
      ar1645v2EthPrtSwF2ClearCountersValue
         Integer32
      }

ar1645v2EthPrtSwF2ClearCountersGlobalIx OBJECT-TYPE
   SYNTAX      GlobalIndex
   MAX-ACCESS  not-accessible
   STATUS      current
   DESCRIPTION
      "The value of the tlsCntTreeGlobalIndex of the MANAGED OBJECT."
   ::= {ar1645v2EthPrtSwF2ClearCountersEntry 10}

ar1645v2EthPrtSwF2ClearCountersValue OBJECT-TYPE
   SYNTAX      Integer32
   MAX-ACCESS  read-write
   STATUS      current
   DESCRIPTION
      "Path: swPort.actions.clearCounters"
   ::= {ar1645v2EthPrtSwF2ClearCountersEntry 2147483648}


ar1645v2EthPrtSwF2RestartIntf OBJECT IDENTIFIER ::= {ar1645v2EthPrtSwF2 67}

ar1645v2EthPrtSwF2RestartIntfTable OBJECT-TYPE
   SYNTAX      SEQUENCE OF Ar1645v2EthPrtSwF2RestartIntfEntry
   MAX-ACCESS  not-accessible
   STATUS      current
   DESCRIPTION
      "action in the debug group"
   ::= {ar1645v2EthPrtSwF2RestartIntf 1}

ar1645v2EthPrtSwF2RestartIntfEntry OBJECT-TYPE
   SYNTAX      Ar1645v2EthPrtSwF2RestartIntfEntry
   MAX-ACCESS  not-accessible
   STATUS      current
   DESCRIPTION
      ""
   INDEX      { ar1645v2EthPrtSwF2RestartIntfGlobalIx }
   ::= {ar1645v2EthPrtSwF2RestartIntfTable 1}

Ar1645v2EthPrtSwF2RestartIntfEntry ::=
   SEQUENCE
      {
      ar1645v2EthPrtSwF2RestartIntfGlobalIx
         GlobalIndex,
      ar1645v2EthPrtSwF2RestartIntfValue
         Integer32
      }

ar1645v2EthPrtSwF2RestartIntfGlobalIx OBJECT-TYPE
   SYNTAX      GlobalIndex
   MAX-ACCESS  not-accessible
   STATUS      current
   DESCRIPTION
      "The value of the tlsCntTreeGlobalIndex of the MANAGED OBJECT."
   ::= {ar1645v2EthPrtSwF2RestartIntfEntry 10}

ar1645v2EthPrtSwF2RestartIntfValue OBJECT-TYPE
   SYNTAX      Integer32
   MAX-ACCESS  read-write
   STATUS      current
   DESCRIPTION
      "Path: swPort.actions.restartIntf"
   ::= {ar1645v2EthPrtSwF2RestartIntfEntry 2147483648}


ar1645v2EthPrtSwF2ClearOamEventLog OBJECT IDENTIFIER ::= {ar1645v2EthPrtSwF2 916}

ar1645v2EthPrtSwF2ClearOamEventLogTable OBJECT-TYPE
   SYNTAX      SEQUENCE OF Ar1645v2EthPrtSwF2ClearOamEventLogEntry
   MAX-ACCESS  not-accessible
   STATUS      current
   DESCRIPTION
      "clear the OAM event log"
   ::= {ar1645v2EthPrtSwF2ClearOamEventLog 1}

ar1645v2EthPrtSwF2ClearOamEventLogEntry OBJECT-TYPE
   SYNTAX      Ar1645v2EthPrtSwF2ClearOamEventLogEntry
   MAX-ACCESS  not-accessible
   STATUS      current
   DESCRIPTION
      ""
   INDEX      { ar1645v2EthPrtSwF2ClearOamEventLogGlobalIx }
   ::= {ar1645v2EthPrtSwF2ClearOamEventLogTable 1}

Ar1645v2EthPrtSwF2ClearOamEventLogEntry ::=
   SEQUENCE
      {
      ar1645v2EthPrtSwF2ClearOamEventLogGlobalIx
         GlobalIndex,
      ar1645v2EthPrtSwF2ClearOamEventLogValue
         Integer32
      }

ar1645v2EthPrtSwF2ClearOamEventLogGlobalIx OBJECT-TYPE
   SYNTAX      GlobalIndex
   MAX-ACCESS  not-accessible
   STATUS      current
   DESCRIPTION
      "The value of the tlsCntTreeGlobalIndex of the MANAGED OBJECT."
   ::= {ar1645v2EthPrtSwF2ClearOamEventLogEntry 10}

ar1645v2EthPrtSwF2ClearOamEventLogValue OBJECT-TYPE
   SYNTAX      Integer32
   MAX-ACCESS  read-write
   STATUS      current
   DESCRIPTION
      "Path: swPort.actions.clearOamEventLog"
   ::= {ar1645v2EthPrtSwF2ClearOamEventLogEntry 2147483648}


ar1645v2EthPrtSwF2Loopback OBJECT IDENTIFIER ::= {ar1645v2EthPrtSwF2 914}

ar1645v2EthPrtSwF2LoopbackTable OBJECT-TYPE
   SYNTAX      SEQUENCE OF Ar1645v2EthPrtSwF2LoopbackEntry
   MAX-ACCESS  not-accessible
   STATUS      current
   DESCRIPTION
      "ethernet loopback"
   ::= {ar1645v2EthPrtSwF2Loopback 1}

ar1645v2EthPrtSwF2LoopbackEntry OBJECT-TYPE
   SYNTAX      Ar1645v2EthPrtSwF2LoopbackEntry
   MAX-ACCESS  not-accessible
   STATUS      current
   DESCRIPTION
      ""
   INDEX      { ar1645v2EthPrtSwF2LoopbackGlobalIx }
   ::= {ar1645v2EthPrtSwF2LoopbackTable 1}

Ar1645v2EthPrtSwF2LoopbackEntry ::=
   SEQUENCE
      {
      ar1645v2EthPrtSwF2LoopbackGlobalIx
         GlobalIndex,
      ar1645v2EthPrtSwF2LoopbackValue
         Integer32
      }

ar1645v2EthPrtSwF2LoopbackGlobalIx OBJECT-TYPE
   SYNTAX      GlobalIndex
   MAX-ACCESS  not-accessible
   STATUS      current
   DESCRIPTION
      "The value of the tlsCntTreeGlobalIndex of the MANAGED OBJECT."
   ::= {ar1645v2EthPrtSwF2LoopbackEntry 10}

ar1645v2EthPrtSwF2LoopbackValue OBJECT-TYPE
   SYNTAX      Integer32
   MAX-ACCESS  read-write
   STATUS      current
   DESCRIPTION
      "Path: swPort.actions.loopback"
   ::= {ar1645v2EthPrtSwF2LoopbackEntry 2147483648}


ar1645v2EthPrtSwF2Loop OBJECT IDENTIFIER ::= {ar1645v2EthPrtSwF2 915}

ar1645v2EthPrtSwF2LoopSSCTable OBJECT-TYPE
   SYNTAX      SEQUENCE OF Ar1645v2EthPrtSwF2LoopEntry
   MAX-ACCESS  not-accessible
   STATUS      current
   DESCRIPTION
      "ethernet loopback type"
   ::= {ar1645v2EthPrtSwF2Loop 1}

ar1645v2EthPrtSwF2LoopEntry OBJECT-TYPE
   SYNTAX      Ar1645v2EthPrtSwF2LoopEntry
   MAX-ACCESS  not-accessible
   STATUS      current
   DESCRIPTION
      ""
   INDEX      { ar1645v2EthPrtSwF2LoopGlobalIx }
   ::= {ar1645v2EthPrtSwF2LoopSSCTable 1}

Ar1645v2EthPrtSwF2LoopEntry ::=
   SEQUENCE
      {
      ar1645v2EthPrtSwF2LoopGlobalIx
         GlobalIndex,
      ar1645v2EthPrtSwF2LoopAction
         INTEGER,
      ar1645v2EthPrtSwF2LoopTime
         TimeTicks,
      ar1645v2EthPrtSwF2LoopIntfName
         DisplayString
      }

ar1645v2EthPrtSwF2LoopGlobalIx OBJECT-TYPE
   SYNTAX      GlobalIndex
   MAX-ACCESS  not-accessible
   STATUS      current
   DESCRIPTION
      "The value of the tlsCntTreeGlobalIndex of the MANAGED OBJECT."
   ::= {ar1645v2EthPrtSwF2LoopEntry 10}

ar1645v2EthPrtSwF2LoopAction OBJECT-TYPE
   SYNTAX      INTEGER
               {
               start (1),
               stop (2)
               }
   MAX-ACCESS  read-write
   STATUS      current
   DESCRIPTION
      "Path: swPort.actions.loop.action

       Possibilities:
               start   (1)
               stop   (2)"
   ::= {ar1645v2EthPrtSwF2LoopEntry 16777216}

ar1645v2EthPrtSwF2LoopTime OBJECT-TYPE
   SYNTAX      TimeTicks
   MAX-ACCESS  read-write
   STATUS      current
   DESCRIPTION
      "Path: swPort.actions.loop.time

       Time in centi-second."
   ::= {ar1645v2EthPrtSwF2LoopEntry 50331648}

ar1645v2EthPrtSwF2LoopIntfName OBJECT-TYPE
   SYNTAX      DisplayString
   MAX-ACCESS  read-write
   STATUS      current
   DESCRIPTION
      "Path: swPort.actions.loop.intfName"
   ::= {ar1645v2EthPrtSwF2LoopEntry 67108864}


ar1645v2EthPrtSwF2OamRemLoopback OBJECT IDENTIFIER ::= {ar1645v2EthPrtSwF2 912}

ar1645v2EthPrtSwF2OamRemLoopbackTable OBJECT-TYPE
   SYNTAX      SEQUENCE OF Ar1645v2EthPrtSwF2OamRemLoopbackEntry
   MAX-ACCESS  not-accessible
   STATUS      current
   DESCRIPTION
      "OAM Remote Loopback"
   ::= {ar1645v2EthPrtSwF2OamRemLoopback 1}

ar1645v2EthPrtSwF2OamRemLoopbackEntry OBJECT-TYPE
   SYNTAX      Ar1645v2EthPrtSwF2OamRemLoopbackEntry
   MAX-ACCESS  not-accessible
   STATUS      current
   DESCRIPTION
      ""
   INDEX      { ar1645v2EthPrtSwF2OamRemLoopbackGlobalIx }
   ::= {ar1645v2EthPrtSwF2OamRemLoopbackTable 1}

Ar1645v2EthPrtSwF2OamRemLoopbackEntry ::=
   SEQUENCE
      {
      ar1645v2EthPrtSwF2OamRemLoopbackGlobalIx
         GlobalIndex,
      ar1645v2EthPrtSwF2OamRemLoopbackValue
         Integer32
      }

ar1645v2EthPrtSwF2OamRemLoopbackGlobalIx OBJECT-TYPE
   SYNTAX      GlobalIndex
   MAX-ACCESS  not-accessible
   STATUS      current
   DESCRIPTION
      "The value of the tlsCntTreeGlobalIndex of the MANAGED OBJECT."
   ::= {ar1645v2EthPrtSwF2OamRemLoopbackEntry 10}

ar1645v2EthPrtSwF2OamRemLoopbackValue OBJECT-TYPE
   SYNTAX      Integer32
   MAX-ACCESS  read-write
   STATUS      current
   DESCRIPTION
      "Path: swPort.actions.oamRemLoopback"
   ::= {ar1645v2EthPrtSwF2OamRemLoopbackEntry 2147483648}


ar1645v2EthPrtSwF2Type OBJECT IDENTIFIER ::= {ar1645v2EthPrtSwF2 913}

ar1645v2EthPrtSwF2TypeTable OBJECT-TYPE
   SYNTAX      SEQUENCE OF Ar1645v2EthPrtSwF2TypeEntry
   MAX-ACCESS  not-accessible
   STATUS      current
   DESCRIPTION
      "OAM Remote Loopback type"
   ::= {ar1645v2EthPrtSwF2Type 1}

ar1645v2EthPrtSwF2TypeEntry OBJECT-TYPE
   SYNTAX      Ar1645v2EthPrtSwF2TypeEntry
   MAX-ACCESS  not-accessible
   STATUS      current
   DESCRIPTION
      ""
   INDEX      { ar1645v2EthPrtSwF2TypeGlobalIx }
   ::= {ar1645v2EthPrtSwF2TypeTable 1}

Ar1645v2EthPrtSwF2TypeEntry ::=
   SEQUENCE
      {
      ar1645v2EthPrtSwF2TypeGlobalIx
         GlobalIndex,
      ar1645v2EthPrtSwF2TypeValue
         INTEGER
      }

ar1645v2EthPrtSwF2TypeGlobalIx OBJECT-TYPE
   SYNTAX      GlobalIndex
   MAX-ACCESS  not-accessible
   STATUS      current
   DESCRIPTION
      "The value of the tlsCntTreeGlobalIndex of the MANAGED OBJECT."
   ::= {ar1645v2EthPrtSwF2TypeEntry 10}

ar1645v2EthPrtSwF2TypeValue OBJECT-TYPE
   SYNTAX      INTEGER
               {
               start (0),
               stop (1)
               }
   MAX-ACCESS  read-write
   STATUS      current
   DESCRIPTION
      "Path: swPort.actions.type

       Possibilities:
               start   (0)
               stop   (1)"
   ::= {ar1645v2EthPrtSwF2TypeEntry 2147483648}


ar1645v2EthPrtSwF2SendWOL OBJECT IDENTIFIER ::= {ar1645v2EthPrtSwF2 333}

ar1645v2EthPrtSwF2SendWOLTable OBJECT-TYPE
   SYNTAX      SEQUENCE OF Ar1645v2EthPrtSwF2SendWOLEntry
   MAX-ACCESS  not-accessible
   STATUS      current
   DESCRIPTION
      "send a WakeOnLan message on this interface"
   ::= {ar1645v2EthPrtSwF2SendWOL 1}

ar1645v2EthPrtSwF2SendWOLEntry OBJECT-TYPE
   SYNTAX      Ar1645v2EthPrtSwF2SendWOLEntry
   MAX-ACCESS  not-accessible
   STATUS      current
   DESCRIPTION
      ""
   INDEX      { ar1645v2EthPrtSwF2SendWOLGlobalIx }
   ::= {ar1645v2EthPrtSwF2SendWOLTable 1}

Ar1645v2EthPrtSwF2SendWOLEntry ::=
   SEQUENCE
      {
      ar1645v2EthPrtSwF2SendWOLGlobalIx
         GlobalIndex,
      ar1645v2EthPrtSwF2SendWOLValue
         Integer32
      }

ar1645v2EthPrtSwF2SendWOLGlobalIx OBJECT-TYPE
   SYNTAX      GlobalIndex
   MAX-ACCESS  not-accessible
   STATUS      current
   DESCRIPTION
      "The value of the tlsCntTreeGlobalIndex of the MANAGED OBJECT."
   ::= {ar1645v2EthPrtSwF2SendWOLEntry 10}

ar1645v2EthPrtSwF2SendWOLValue OBJECT-TYPE
   SYNTAX      Integer32
   MAX-ACCESS  read-write
   STATUS      current
   DESCRIPTION
      "Path: swPort.actions.sendWOL"
   ::= {ar1645v2EthPrtSwF2SendWOLEntry 2147483648}


ar1645v2EthPrtSwF2WolInfo OBJECT IDENTIFIER ::= {ar1645v2EthPrtSwF2 332}

ar1645v2EthPrtSwF2WolInfoSSCTable OBJECT-TYPE
   SYNTAX      SEQUENCE OF Ar1645v2EthPrtSwF2WolInfoEntry
   MAX-ACCESS  not-accessible
   STATUS      current
   DESCRIPTION
      "content of a WakeOnLan message"
   ::= {ar1645v2EthPrtSwF2WolInfo 1}

ar1645v2EthPrtSwF2WolInfoEntry OBJECT-TYPE
   SYNTAX      Ar1645v2EthPrtSwF2WolInfoEntry
   MAX-ACCESS  not-accessible
   STATUS      current
   DESCRIPTION
      ""
   INDEX      { ar1645v2EthPrtSwF2WolInfoGlobalIx }
   ::= {ar1645v2EthPrtSwF2WolInfoSSCTable 1}

Ar1645v2EthPrtSwF2WolInfoEntry ::=
   SEQUENCE
      {
      ar1645v2EthPrtSwF2WolInfoGlobalIx
         GlobalIndex,
      ar1645v2EthPrtSwF2WolInfoTargetMAC
         OCTET STRING,
      ar1645v2EthPrtSwF2WolInfoPassword
         OCTET STRING
      }

ar1645v2EthPrtSwF2WolInfoGlobalIx OBJECT-TYPE
   SYNTAX      GlobalIndex
   MAX-ACCESS  not-accessible
   STATUS      current
   DESCRIPTION
      "The value of the tlsCntTreeGlobalIndex of the MANAGED OBJECT."
   ::= {ar1645v2EthPrtSwF2WolInfoEntry 10}

ar1645v2EthPrtSwF2WolInfoTargetMAC OBJECT-TYPE
   SYNTAX      OCTET STRING
   MAX-ACCESS  read-write
   STATUS      current
   DESCRIPTION
      "Path: swPort.actions.wolInfo.targetMAC

       MAC address."
   ::= {ar1645v2EthPrtSwF2WolInfoEntry 16777216}

ar1645v2EthPrtSwF2WolInfoPassword OBJECT-TYPE
   SYNTAX      OCTET STRING
   MAX-ACCESS  read-write
   STATUS      current
   DESCRIPTION
      "Path: swPort.actions.wolInfo.password"
   ::= {ar1645v2EthPrtSwF2WolInfoEntry 33554432}


ar1645v2EthPrtSwF2ClearArpCache OBJECT IDENTIFIER ::= {ar1645v2EthPrtSwF2 25}

ar1645v2EthPrtSwF2ClearArpCacheTable OBJECT-TYPE
   SYNTAX      SEQUENCE OF Ar1645v2EthPrtSwF2ClearArpCacheEntry
   MAX-ACCESS  not-accessible
   STATUS      current
   DESCRIPTION
      "clear all dynamic enties in ARP cache table"
   ::= {ar1645v2EthPrtSwF2ClearArpCache 1}

ar1645v2EthPrtSwF2ClearArpCacheEntry OBJECT-TYPE
   SYNTAX      Ar1645v2EthPrtSwF2ClearArpCacheEntry
   MAX-ACCESS  not-accessible
   STATUS      current
   DESCRIPTION
      ""
   INDEX      { ar1645v2EthPrtSwF2ClearArpCacheGlobalIx }
   ::= {ar1645v2EthPrtSwF2ClearArpCacheTable 1}

Ar1645v2EthPrtSwF2ClearArpCacheEntry ::=
   SEQUENCE
      {
      ar1645v2EthPrtSwF2ClearArpCacheGlobalIx
         GlobalIndex,
      ar1645v2EthPrtSwF2ClearArpCacheValue
         Integer32
      }

ar1645v2EthPrtSwF2ClearArpCacheGlobalIx OBJECT-TYPE
   SYNTAX      GlobalIndex
   MAX-ACCESS  not-accessible
   STATUS      current
   DESCRIPTION
      "The value of the tlsCntTreeGlobalIndex of the MANAGED OBJECT."
   ::= {ar1645v2EthPrtSwF2ClearArpCacheEntry 10}

ar1645v2EthPrtSwF2ClearArpCacheValue OBJECT-TYPE
   SYNTAX      Integer32
   MAX-ACCESS  read-write
   STATUS      current
   DESCRIPTION
      "Path: swPort.actions.clearArpCache"
   ::= {ar1645v2EthPrtSwF2ClearArpCacheEntry 2147483648}



fr1645v2EthPrtSwF2 OBJECT IDENTIFIER ::= {r1645v2EthPrtSwF2 13}


fr1645v2EthPrtSwF2Alarm OBJECT IDENTIFIER ::= {fr1645v2EthPrtSwF2 207}

fr1645v2EthPrtSwF2AlarmSSCTable OBJECT-TYPE
   SYNTAX      SEQUENCE OF Fr1645v2EthPrtSwF2AlarmEntry
   MAX-ACCESS  not-accessible
   STATUS      current
   DESCRIPTION
      "IfAlarmInfo"
   ::= {fr1645v2EthPrtSwF2Alarm 1}

fr1645v2EthPrtSwF2AlarmEntry OBJECT-TYPE
   SYNTAX      Fr1645v2EthPrtSwF2AlarmEntry
   MAX-ACCESS  not-accessible
   STATUS      current
   DESCRIPTION
      ""
   INDEX      { fr1645v2EthPrtSwF2AlarmGlobalIx }
   ::= {fr1645v2EthPrtSwF2AlarmSSCTable 1}

Fr1645v2EthPrtSwF2AlarmEntry ::=
   SEQUENCE
      {
      fr1645v2EthPrtSwF2AlarmGlobalIx
         GlobalIndex,
      fr1645v2EthPrtSwF2AlarmDiscriminator
         Integer32,
      fr1645v2EthPrtSwF2AlarmCurrent
         Integer32,
      fr1645v2EthPrtSwF2AlarmPrevious
         Integer32,
      fr1645v2EthPrtSwF2AlarmMask
         Integer32,
      fr1645v2EthPrtSwF2AlarmLevLinkDown
         Integer32,
      fr1645v2EthPrtSwF2AlarmLevPppoEDown
         Integer32
      }

fr1645v2EthPrtSwF2AlarmGlobalIx OBJECT-TYPE
   SYNTAX      GlobalIndex
   MAX-ACCESS  not-accessible
   STATUS      current
   DESCRIPTION
      "The value of the tlsCntTreeGlobalIndex of the MANAGED OBJECT."
   ::= {fr1645v2EthPrtSwF2AlarmEntry 10}

fr1645v2EthPrtSwF2AlarmDiscriminator OBJECT-TYPE
   SYNTAX      Integer32
   MAX-ACCESS  read-only
   STATUS      current
   DESCRIPTION
      "Path: swPort.alarms.alarmInfo.discriminator"
   ::= {fr1645v2EthPrtSwF2AlarmEntry 16777216}

fr1645v2EthPrtSwF2AlarmCurrent OBJECT-TYPE
   SYNTAX      Integer32
   MAX-ACCESS  read-only
   STATUS      current
   DESCRIPTION
      "Path: swPort.alarms.alarmInfo.currentAlarms

       Bit meanings:
               bit 0 = linkDown,
               bit 9 = pppoEDown"
   ::= {fr1645v2EthPrtSwF2AlarmEntry 33554432}

fr1645v2EthPrtSwF2AlarmPrevious OBJECT-TYPE
   SYNTAX      Integer32
   MAX-ACCESS  read-only
   STATUS      current
   DESCRIPTION
      "Path: swPort.alarms.alarmInfo.previousAlarms

       Bit meanings:
               bit 0 = linkDown,
               bit 9 = pppoEDown"
   ::= {fr1645v2EthPrtSwF2AlarmEntry 50331648}

fr1645v2EthPrtSwF2AlarmMask OBJECT-TYPE
   SYNTAX      Integer32
   MAX-ACCESS  read-only
   STATUS      current
   DESCRIPTION
      "Path: swPort.alarms.alarmInfo.alarmMask

       Bit meanings:
               bit 0 = linkDown,
               bit 9 = pppoEDown"
   ::= {fr1645v2EthPrtSwF2AlarmEntry 67108864}

fr1645v2EthPrtSwF2AlarmLevLinkDown OBJECT-TYPE
   SYNTAX      Integer32
   MAX-ACCESS  read-only
   STATUS      current
   DESCRIPTION
      "Path: swPort.alarms.alarmInfo.alarmLevel.linkDown"
   ::= {fr1645v2EthPrtSwF2AlarmEntry 83951616}

fr1645v2EthPrtSwF2AlarmLevPppoEDown OBJECT-TYPE
   SYNTAX      Integer32
   MAX-ACCESS  read-only
   STATUS      current
   DESCRIPTION
      "Path: swPort.alarms.alarmInfo.alarmLevel.pppoEDown"
   ::= {fr1645v2EthPrtSwF2AlarmEntry 84541440}


fr1645v2EthPrtSwF2AlarmE2 OBJECT IDENTIFIER ::= {fr1645v2EthPrtSwF2Alarm 2}

fr1645v2EthPrtSwF2AlarmE2Entry OBJECT IDENTIFIER ::= {fr1645v2EthPrtSwF2AlarmE2 1}

fr1645v2EthPrtSwF2AlarmE2LinkDown OBJECT IDENTIFIER ::= {fr1645v2EthPrtSwF2AlarmE2Entry 10}

fr1645v2EthPrtSwF2AlarmE2LinkDownPfx OBJECT IDENTIFIER ::= {fr1645v2EthPrtSwF2AlarmE2LinkDown 0}

fr1645v2EthPrtSwF2AlarmE2LinkDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'ethPortSwFix2'
                (root='router1645') has changed from the ON to the OFF state."
   ::= {fr1645v2EthPrtSwF2AlarmE2LinkDownPfx 1}

fr1645v2EthPrtSwF2AlarmE2LinkDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'ethPortSwFix2'
                (root='router1645') has changed from the OFF to the ON state."
   ::= {fr1645v2EthPrtSwF2AlarmE2LinkDownPfx 2}

fr1645v2EthPrtSwF2AlarmE2PppoEDown OBJECT IDENTIFIER ::= {fr1645v2EthPrtSwF2AlarmE2Entry 19}

fr1645v2EthPrtSwF2AlarmE2PppoEDownPfx OBJECT IDENTIFIER ::= {fr1645v2EthPrtSwF2AlarmE2PppoEDown 0}

fr1645v2EthPrtSwF2AlarmE2PppoEDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pppoEDown'
                representing an alarm condition in the alarm word
                of attribute 'alarmInfo' of managed object 'ethPortSwFix2'
                (root='router1645') has changed from the ON to the OFF state."
   ::= {fr1645v2EthPrtSwF2AlarmE2PppoEDownPfx 1}

fr1645v2EthPrtSwF2AlarmE2PppoEDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pppoEDown'
                representing an alarm condition in the alarm word
                of attribute 'alarmInfo' of managed object 'ethPortSwFix2'
                (root='router1645') has changed from the OFF to the ON state."
   ::= {fr1645v2EthPrtSwF2AlarmE2PppoEDownPfx 2}



END
