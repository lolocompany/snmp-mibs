OneAccess-R1645v2-2093-PRout DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2PRout OBJECT IDENTIFIER ::= {r1645Rootv2 2093}

r1645v2PRoutMOProp OBJECT IDENTIFIER ::= {r1645v2PRout 1}

r1645v2PRoutMOPropEntry OBJECT IDENTIFIER ::= {r1645v2PRoutMOProp 1}

r1645v2PRoutMOPropPath OBJECT-TYPE
   SYNTAX      ContainmentPath
   MAX-ACCESS  read-only
   STATUS      current
   DESCRIPTION
      "Textual description of the containment tree from the instance of
       the root object down to the instance of the current object."
   ::= {r1645v2PRoutMOPropEntry 3}

r1645v2PRoutMOPropRev OBJECT-TYPE
   SYNTAX      ObjectRevision
   MAX-ACCESS  read-only
   STATUS      current
   DESCRIPTION
      "This value corresponds with the revision of the MANAGED OBJECT."
   ::= {r1645v2PRoutMOPropEntry 4}



er1645v2PRout OBJECT IDENTIFIER ::= {r1645v2PRout 11}


er1645v2PRoutSendPortUnreachable OBJECT-TYPE
   SYNTAX      INTEGER
               {
               disabled (0),
               enabled (1)
               }
   MAX-ACCESS  read-write
   STATUS      current
   DESCRIPTION
      "Path: router.editConf.sendPortUnreachable
       Info: indicates if a ICMP Port Unreachable must be returned to a packet's source if
                        the destination port is unknown

       Possibilities:
               disabled   (0)
               enabled   (1)"
   ::= {er1645v2PRout 31}


er1645v2PRoutSendAdminUnreachable OBJECT-TYPE
   SYNTAX      INTEGER
               {
               disabled (0),
               enabled (1)
               }
   MAX-ACCESS  read-write
   STATUS      current
   DESCRIPTION
      "Path: router.editConf.sendAdminUnreachable
       Info: indicates if an ICMP can be returned to a packet's source if
                        the packet is discarded

       Possibilities:
               disabled   (0)
               enabled   (1)"
   ::= {er1645v2PRout 56}


er1645v2PRoutSendHostUnreachable OBJECT-TYPE
   SYNTAX      INTEGER
               {
               disabled (0),
               enabled (1)
               }
   MAX-ACCESS  read-write
   STATUS      current
   DESCRIPTION
      "Path: router.editConf.sendHostUnreachable
       Info: indicates if a ICMP Host Unreachable must be returned to a packet's source if
                        the destination host is unknown

       Possibilities:
               disabled   (0)
               enabled   (1)"
   ::= {er1645v2PRout 36}


er1645v2PRoutRipUpInt OBJECT-TYPE
   SYNTAX      TimeTicks
   MAX-ACCESS  read-write
   STATUS      current
   DESCRIPTION
      "Path: router.editConf.ripUpdateInterval
       Info: delay between RIP updates sent

       Time in centi-second."
   ::= {er1645v2PRout 35}


er1645v2PRoutRipPreference OBJECT-TYPE
   SYNTAX      Gauge32
   MAX-ACCESS  read-write
   STATUS      current
   DESCRIPTION
      "Path: router.editConf.ripPreference
       Info: preference

       32 bit unsigned gauge value."
   ::= {er1645v2PRout 83}


er1645v2PRoutRipNeighbors OBJECT IDENTIFIER ::= {er1645v2PRout 50}

er1645v2PRoutRipNeighborsSSCTable OBJECT-TYPE
   SYNTAX      SEQUENCE OF Er1645v2PRoutRipNeighborsEntry
   MAX-ACCESS  not-accessible
   STATUS      current
   DESCRIPTION
      "rip neighbor table"
   ::= {er1645v2PRoutRipNeighbors 1}

er1645v2PRoutRipNeighborsEntry OBJECT-TYPE
   SYNTAX      Er1645v2PRoutRipNeighborsEntry
   MAX-ACCESS  not-accessible
   STATUS      current
   DESCRIPTION
      ""
   INDEX      { er1645v2PRoutRipNeighborsTableIx }
   ::= {er1645v2PRoutRipNeighborsSSCTable 1}

Er1645v2PRoutRipNeighborsEntry ::=
   SEQUENCE
      {
      er1645v2PRoutRipNeighborsActions
         VariableLengthTableActions,
      er1645v2PRoutRipNeighborsTableIx
         TableIndex,
      er1645v2PRoutRipNeighborsIpAddress
         IpAddress
      }

er1645v2PRoutRipNeighborsActions OBJECT-TYPE
   SYNTAX      VariableLengthTableActions
   MAX-ACCESS  read-write
   STATUS      current
   DESCRIPTION
      "By way of this field, some manipulations
       on this table may be performed."
   ::= {er1645v2PRoutRipNeighborsEntry 2}

er1645v2PRoutRipNeighborsTableIx OBJECT-TYPE
   SYNTAX      TableIndex
   MAX-ACCESS  not-accessible
   STATUS      current
   DESCRIPTION
      ""
   ::= {er1645v2PRoutRipNeighborsEntry 11}

er1645v2PRoutRipNeighborsIpAddress OBJECT-TYPE
   SYNTAX      IpAddress
   MAX-ACCESS  read-write
   STATUS      current
   DESCRIPTION
      "Path: router.editConf.ripNeighbors.ipAddress"
   ::= {er1645v2PRoutRipNeighborsEntry 67108864}


er1645v2PRoutMulticastRouting OBJECT-TYPE
   SYNTAX      INTEGER
               {
               disabled (0),
               enabled (1)
               }
   MAX-ACCESS  read-write
   STATUS      current
   DESCRIPTION
      "Path: router.editConf.multicastRouting
       Info: indicates if multicast routing (PIM/IGMP) is supported

       Possibilities:
               disabled   (0)
               enabled   (1)"
   ::= {er1645v2PRout 17}


er1645v2PRoutSysSecret OBJECT-TYPE
   SYNTAX      DisplayString
   MAX-ACCESS  read-write
   STATUS      current
   DESCRIPTION
      "Path: router.editConf.sysSecret
       Info: gives our secret for PPP authentication"
   ::= {er1645v2PRout 40}


er1645v2PRoutPppSecretTable OBJECT IDENTIFIER ::= {er1645v2PRout 41}

er1645v2PRoutPppSecretTableSSCTable OBJECT-TYPE
   SYNTAX      SEQUENCE OF Er1645v2PRoutPppSecretTableEntry
   MAX-ACCESS  not-accessible
   STATUS      current
   DESCRIPTION
      "table to store secret values for PPP authentication"
   ::= {er1645v2PRoutPppSecretTable 1}

er1645v2PRoutPppSecretTableEntry OBJECT-TYPE
   SYNTAX      Er1645v2PRoutPppSecretTableEntry
   MAX-ACCESS  not-accessible
   STATUS      current
   DESCRIPTION
      ""
   INDEX      { er1645v2PRoutPppSecretTableTableIx }
   ::= {er1645v2PRoutPppSecretTableSSCTable 1}

Er1645v2PRoutPppSecretTableEntry ::=
   SEQUENCE
      {
      er1645v2PRoutPppSecretTableActions
         VariableLengthTableActions,
      er1645v2PRoutPppSecretTableTableIx
         TableIndex,
      er1645v2PRoutPppSecretTableName
         DisplayString,
      er1645v2PRoutPppSecretTableSecret
         DisplayString,
      er1645v2PRoutPppSecretTableEncModeSecret
         INTEGER,
      er1645v2PRoutPppSecretTableEncSecret
         DisplayString
      }

er1645v2PRoutPppSecretTableActions OBJECT-TYPE
   SYNTAX      VariableLengthTableActions
   MAX-ACCESS  read-write
   STATUS      current
   DESCRIPTION
      "By way of this field, some manipulations
       on this table may be performed."
   ::= {er1645v2PRoutPppSecretTableEntry 2}

er1645v2PRoutPppSecretTableTableIx OBJECT-TYPE
   SYNTAX      TableIndex
   MAX-ACCESS  not-accessible
   STATUS      current
   DESCRIPTION
      ""
   ::= {er1645v2PRoutPppSecretTableEntry 11}

er1645v2PRoutPppSecretTableName OBJECT-TYPE
   SYNTAX      DisplayString
   MAX-ACCESS  read-write
   STATUS      current
   DESCRIPTION
      "Path: router.editConf.pppSecretTable.name"
   ::= {er1645v2PRoutPppSecretTableEntry 16777216}

er1645v2PRoutPppSecretTableSecret OBJECT-TYPE
   SYNTAX      DisplayString
   MAX-ACCESS  read-write
   STATUS      current
   DESCRIPTION
      "Path: router.editConf.pppSecretTable.secret"
   ::= {er1645v2PRoutPppSecretTableEntry 33554432}

er1645v2PRoutPppSecretTableEncModeSecret OBJECT-TYPE
   SYNTAX      INTEGER
               {
               none (1),
               encrypt (2),
               encType1 (3),
               invalid (128)
               }
   MAX-ACCESS  read-write
   STATUS      current
   DESCRIPTION
      "Path: router.editConf.pppSecretTable.encModeSecret

       Possibilities:
               none   (1)
               encrypt   (2)
               encType1   (3)
               invalid   (128)"
   ::= {er1645v2PRoutPppSecretTableEntry 100663296}

er1645v2PRoutPppSecretTableEncSecret OBJECT-TYPE
   SYNTAX      DisplayString
   MAX-ACCESS  read-write
   STATUS      current
   DESCRIPTION
      "Path: router.editConf.pppSecretTable.encSecret"
   ::= {er1645v2PRoutPppSecretTableEntry 117440512}


er1645v2PRoutDhcpStat OBJECT IDENTIFIER ::= {er1645v2PRout 51}

er1645v2PRoutDhcpStatSSCTable OBJECT-TYPE
   SYNTAX      SEQUENCE OF Er1645v2PRoutDhcpStatEntry
   MAX-ACCESS  not-accessible
   STATUS      current
   DESCRIPTION
      "Initialisation DHCP server"
   ::= {er1645v2PRoutDhcpStat 1}

er1645v2PRoutDhcpStatEntry OBJECT-TYPE
   SYNTAX      Er1645v2PRoutDhcpStatEntry
   MAX-ACCESS  not-accessible
   STATUS      current
   DESCRIPTION
      ""
   INDEX      { er1645v2PRoutDhcpStatTableIx }
   ::= {er1645v2PRoutDhcpStatSSCTable 1}

Er1645v2PRoutDhcpStatEntry ::=
   SEQUENCE
      {
      er1645v2PRoutDhcpStatActions
         VariableLengthTableActions,
      er1645v2PRoutDhcpStatTableIx
         TableIndex,
      er1645v2PRoutDhcpStatIpAddress
         IpAddress,
      er1645v2PRoutDhcpStatMask
         IpAddress,
      er1645v2PRoutDhcpStatGateway
         IpAddress,
      er1645v2PRoutDhcpStatInterface
         DisplayString,
      er1645v2PRoutDhcpStatDnsSetting
         INTEGER,
      er1645v2PRoutDhcpStatNameServer
         IpAddress,
      er1645v2PRoutDhcpStatNameServer2
         IpAddress,
      er1645v2PRoutDhcpStatTftpServer
         IpAddress,
      er1645v2PRoutDhcpStatTftpServerOption
         DisplayString,
      er1645v2PRoutDhcpStatMacAddress
         OCTET STRING,
      er1645v2PRoutDhcpStatBootFile
         DisplayString,
      er1645v2PRoutDhcpStatBootFileOption
         DisplayString,
      er1645v2PRoutDhcpStatHostName
         DisplayString,
      er1645v2PRoutDhcpStatDomainName
         DisplayString,
      er1645v2PRoutDhcpStatNetbiosNS
         IpAddress,
      er1645v2PRoutDhcpStatNetbiosNS2
         IpAddress,
      er1645v2PRoutDhcpStatNetbiosNT
         INTEGER
      }

er1645v2PRoutDhcpStatActions OBJECT-TYPE
   SYNTAX      VariableLengthTableActions
   MAX-ACCESS  read-write
   STATUS      current
   DESCRIPTION
      "By way of this field, some manipulations
       on this table may be performed."
   ::= {er1645v2PRoutDhcpStatEntry 2}

er1645v2PRoutDhcpStatTableIx OBJECT-TYPE
   SYNTAX      TableIndex
   MAX-ACCESS  not-accessible
   STATUS      current
   DESCRIPTION
      ""
   ::= {er1645v2PRoutDhcpStatEntry 11}

er1645v2PRoutDhcpStatIpAddress OBJECT-TYPE
   SYNTAX      IpAddress
   MAX-ACCESS  read-write
   STATUS      current
   DESCRIPTION
      "Path: router.editConf.dhcpStatic.ipAddress"
   ::= {er1645v2PRoutDhcpStatEntry 16777216}

er1645v2PRoutDhcpStatMask OBJECT-TYPE
   SYNTAX      IpAddress
   MAX-ACCESS  read-write
   STATUS      current
   DESCRIPTION
      "Path: router.editConf.dhcpStatic.mask"
   ::= {er1645v2PRoutDhcpStatEntry 33554432}

er1645v2PRoutDhcpStatGateway OBJECT-TYPE
   SYNTAX      IpAddress
   MAX-ACCESS  read-write
   STATUS      current
   DESCRIPTION
      "Path: router.editConf.dhcpStatic.gateway"
   ::= {er1645v2PRoutDhcpStatEntry 50331648}

er1645v2PRoutDhcpStatInterface OBJECT-TYPE
   SYNTAX      DisplayString
   MAX-ACCESS  read-write
   STATUS      current
   DESCRIPTION
      "Path: router.editConf.dhcpStatic.interface"
   ::= {er1645v2PRoutDhcpStatEntry 268435456}

er1645v2PRoutDhcpStatDnsSetting OBJECT-TYPE
   SYNTAX      INTEGER
               {
               configured (0),
               learned (1),
               relay (2)
               }
   MAX-ACCESS  read-write
   STATUS      current
   DESCRIPTION
      "Path: router.editConf.dhcpStatic.dnsSetting

       Possibilities:
               configured   (0)
               learned   (1)
               relay   (2)"
   ::= {er1645v2PRoutDhcpStatEntry 285212672}

er1645v2PRoutDhcpStatNameServer OBJECT-TYPE
   SYNTAX      IpAddress
   MAX-ACCESS  read-write
   STATUS      current
   DESCRIPTION
      "Path: router.editConf.dhcpStatic.nameServer"
   ::= {er1645v2PRoutDhcpStatEntry 67108864}

er1645v2PRoutDhcpStatNameServer2 OBJECT-TYPE
   SYNTAX      IpAddress
   MAX-ACCESS  read-write
   STATUS      current
   DESCRIPTION
      "Path: router.editConf.dhcpStatic.nameServer2"
   ::= {er1645v2PRoutDhcpStatEntry 234881024}

er1645v2PRoutDhcpStatTftpServer OBJECT-TYPE
   SYNTAX      IpAddress
   MAX-ACCESS  read-write
   STATUS      current
   DESCRIPTION
      "Path: router.editConf.dhcpStatic.tftpServer"
   ::= {er1645v2PRoutDhcpStatEntry 83886080}

er1645v2PRoutDhcpStatTftpServerOption OBJECT-TYPE
   SYNTAX      DisplayString
   MAX-ACCESS  read-write
   STATUS      current
   DESCRIPTION
      "Path: router.editConf.dhcpStatic.tftpServerOption"
   ::= {er1645v2PRoutDhcpStatEntry 335544320}

er1645v2PRoutDhcpStatMacAddress OBJECT-TYPE
   SYNTAX      OCTET STRING
   MAX-ACCESS  read-write
   STATUS      current
   DESCRIPTION
      "Path: router.editConf.dhcpStatic.macAddress

       MAC address."
   ::= {er1645v2PRoutDhcpStatEntry 100663296}

er1645v2PRoutDhcpStatBootFile OBJECT-TYPE
   SYNTAX      DisplayString
   MAX-ACCESS  read-write
   STATUS      current
   DESCRIPTION
      "Path: router.editConf.dhcpStatic.bootFile"
   ::= {er1645v2PRoutDhcpStatEntry 117440512}

er1645v2PRoutDhcpStatBootFileOption OBJECT-TYPE
   SYNTAX      DisplayString
   MAX-ACCESS  read-write
   STATUS      current
   DESCRIPTION
      "Path: router.editConf.dhcpStatic.bootFileOption"
   ::= {er1645v2PRoutDhcpStatEntry 352321536}

er1645v2PRoutDhcpStatHostName OBJECT-TYPE
   SYNTAX      DisplayString
   MAX-ACCESS  read-write
   STATUS      current
   DESCRIPTION
      "Path: router.editConf.dhcpStatic.hostName"
   ::= {er1645v2PRoutDhcpStatEntry 134217728}

er1645v2PRoutDhcpStatDomainName OBJECT-TYPE
   SYNTAX      DisplayString
   MAX-ACCESS  read-write
   STATUS      current
   DESCRIPTION
      "Path: router.editConf.dhcpStatic.domainName"
   ::= {er1645v2PRoutDhcpStatEntry 150994944}

er1645v2PRoutDhcpStatNetbiosNS OBJECT-TYPE
   SYNTAX      IpAddress
   MAX-ACCESS  read-write
   STATUS      current
   DESCRIPTION
      "Path: router.editConf.dhcpStatic.netbiosNameServer"
   ::= {er1645v2PRoutDhcpStatEntry 167772160}

er1645v2PRoutDhcpStatNetbiosNS2 OBJECT-TYPE
   SYNTAX      IpAddress
   MAX-ACCESS  read-write
   STATUS      current
   DESCRIPTION
      "Path: router.editConf.dhcpStatic.netbiosNameServer2"
   ::= {er1645v2PRoutDhcpStatEntry 251658240}

er1645v2PRoutDhcpStatNetbiosNT OBJECT-TYPE
   SYNTAX      INTEGER
               {
               nomnode (0),
               bmnode (1),
               pmnode (2),
               mmnode (4),
               hmnode (8)
               }
   MAX-ACCESS  read-write
   STATUS      current
   DESCRIPTION
      "Path: router.editConf.dhcpStatic.netbiosNodeType

       Possibilities:
               no-node   (0)
               B-node   (1)
               P-node   (2)
               M-node   (4)
               H-node   (8)"
   ::= {er1645v2PRoutDhcpStatEntry 184549376}

er1645v2PRoutDhcpStatOptions OBJECT-TYPE
   SYNTAX      SEQUENCE OF Er1645v2PRoutDhcpStatOptionsEntry
   MAX-ACCESS  not-accessible
   STATUS      current
   DESCRIPTION
      ""
   ::= {er1645v2PRoutDhcpStat 402653184}

er1645v2PRoutDhcpStatOptionsEntry OBJECT-TYPE
   SYNTAX      Er1645v2PRoutDhcpStatOptionsEntry
   MAX-ACCESS  not-accessible
   STATUS      current
   DESCRIPTION
      ""
   INDEX      { er1645v2PRoutDhcpStatTableIx,
                er1645v2PRoutDhcpStatOptionsTableIx }
   ::= {er1645v2PRoutDhcpStatOptions 1}

Er1645v2PRoutDhcpStatOptionsEntry ::=
   SEQUENCE
      {
      er1645v2PRoutDhcpStatOptionsActions
         VariableLengthTableActions,
      er1645v2PRoutDhcpStatOptionsTableIx
         TableIndex,
      er1645v2PRoutDhcpStatOptionsCode
         Integer32,
      er1645v2PRoutDhcpStatOptionsValueAscii
         DisplayString,
      er1645v2PRoutDhcpStatOptionsValueDecimal
         Integer32,
      er1645v2PRoutDhcpStatOptionsValueHexData
         OCTET STRING,
      er1645v2PRoutDhcpStatOptionsValueIpAddress
         IpAddress
      }

er1645v2PRoutDhcpStatOptionsActions OBJECT-TYPE
   SYNTAX      VariableLengthTableActions
   MAX-ACCESS  read-write
   STATUS      current
   DESCRIPTION
      "By way of this field, some manipulations
       on this table may be performed."
   ::= {er1645v2PRoutDhcpStatOptionsEntry 2}

er1645v2PRoutDhcpStatOptionsTableIx OBJECT-TYPE
   SYNTAX      TableIndex
   MAX-ACCESS  not-accessible
   STATUS      current
   DESCRIPTION
      ""
   ::= {er1645v2PRoutDhcpStatOptionsEntry 11}

er1645v2PRoutDhcpStatOptionsCode OBJECT-TYPE
   SYNTAX      Integer32
   MAX-ACCESS  read-write
   STATUS      current
   DESCRIPTION
      "Path: router.editConf.dhcpStatic.options.code"
   ::= {er1645v2PRoutDhcpStatOptionsEntry 16777216}

er1645v2PRoutDhcpStatOptionsValueAscii OBJECT-TYPE
   SYNTAX      DisplayString
   MAX-ACCESS  read-write
   STATUS      current
   DESCRIPTION
      "Path: router.editConf.dhcpStatic.options.value.ascii"
   ::= {er1645v2PRoutDhcpStatOptionsEntry 33619968}

er1645v2PRoutDhcpStatOptionsValueDecimal OBJECT-TYPE
   SYNTAX      Integer32
   MAX-ACCESS  read-write
   STATUS      current
   DESCRIPTION
      "Path: router.editConf.dhcpStatic.options.value.decimal"
   ::= {er1645v2PRoutDhcpStatOptionsEntry 33685504}

er1645v2PRoutDhcpStatOptionsValueHexData OBJECT-TYPE
   SYNTAX      OCTET STRING
   MAX-ACCESS  read-write
   STATUS      current
   DESCRIPTION
      "Path: router.editConf.dhcpStatic.options.value.hexData"
   ::= {er1645v2PRoutDhcpStatOptionsEntry 33751040}

er1645v2PRoutDhcpStatOptionsValueIpAddress OBJECT-TYPE
   SYNTAX      IpAddress
   MAX-ACCESS  read-write
   STATUS      current
   DESCRIPTION
      "Path: router.editConf.dhcpStatic.options.value.ipAddress"
   ::= {er1645v2PRoutDhcpStatOptionsEntry 33816576}


er1645v2PRoutDhcpDyn OBJECT IDENTIFIER ::= {er1645v2PRout 52}

er1645v2PRoutDhcpDynSSCTable OBJECT-TYPE
   SYNTAX      SEQUENCE OF Er1645v2PRoutDhcpDynEntry
   MAX-ACCESS  not-accessible
   STATUS      current
   DESCRIPTION
      "Initialisation DHCP server"
   ::= {er1645v2PRoutDhcpDyn 1}

er1645v2PRoutDhcpDynEntry OBJECT-TYPE
   SYNTAX      Er1645v2PRoutDhcpDynEntry
   MAX-ACCESS  not-accessible
   STATUS      current
   DESCRIPTION
      ""
   INDEX      { er1645v2PRoutDhcpDynTableIx }
   ::= {er1645v2PRoutDhcpDynSSCTable 1}

Er1645v2PRoutDhcpDynEntry ::=
   SEQUENCE
      {
      er1645v2PRoutDhcpDynActions
         VariableLengthTableActions,
      er1645v2PRoutDhcpDynTableIx
         TableIndex,
      er1645v2PRoutDhcpDynIpcpSubnet
         DisplayString,
      er1645v2PRoutDhcpDynIpStartAddress
         IpAddress,
      er1645v2PRoutDhcpDynIpEndAddress
         IpAddress,
      er1645v2PRoutDhcpDynMask
         IpAddress,
      er1645v2PRoutDhcpDynGateway
         IpAddress,
      er1645v2PRoutDhcpDynInterface
         DisplayString,
      er1645v2PRoutDhcpDynDnsSetting
         INTEGER,
      er1645v2PRoutDhcpDynNameServer
         IpAddress,
      er1645v2PRoutDhcpDynNameServer2
         IpAddress,
      er1645v2PRoutDhcpDynTftpServer
         IpAddress,
      er1645v2PRoutDhcpDynTftpServerOption
         DisplayString,
      er1645v2PRoutDhcpDynLeaseTime
         TimeTicks,
      er1645v2PRoutDhcpDynHoldTime
         TimeTicks,
      er1645v2PRoutDhcpDynBootFile
         DisplayString,
      er1645v2PRoutDhcpDynBootFileOption
         DisplayString,
      er1645v2PRoutDhcpDynHostName
         DisplayString,
      er1645v2PRoutDhcpDynDomainName
         DisplayString,
      er1645v2PRoutDhcpDynNetbiosNS
         IpAddress,
      er1645v2PRoutDhcpDynNetbiosNS2
         IpAddress,
      er1645v2PRoutDhcpDynNetbiosNT
         INTEGER
      }

er1645v2PRoutDhcpDynActions OBJECT-TYPE
   SYNTAX      VariableLengthTableActions
   MAX-ACCESS  read-write
   STATUS      current
   DESCRIPTION
      "By way of this field, some manipulations
       on this table may be performed."
   ::= {er1645v2PRoutDhcpDynEntry 2}

er1645v2PRoutDhcpDynTableIx OBJECT-TYPE
   SYNTAX      TableIndex
   MAX-ACCESS  not-accessible
   STATUS      current
   DESCRIPTION
      ""
   ::= {er1645v2PRoutDhcpDynEntry 11}

er1645v2PRoutDhcpDynIpcpSubnet OBJECT-TYPE
   SYNTAX      DisplayString
   MAX-ACCESS  read-write
   STATUS      current
   DESCRIPTION
      "Path: router.editConf.dhcpDynamic.ipcpSubnet"
   ::= {er1645v2PRoutDhcpDynEntry 301989888}

er1645v2PRoutDhcpDynIpStartAddress OBJECT-TYPE
   SYNTAX      IpAddress
   MAX-ACCESS  read-write
   STATUS      current
   DESCRIPTION
      "Path: router.editConf.dhcpDynamic.ipStartAddress"
   ::= {er1645v2PRoutDhcpDynEntry 16777216}

er1645v2PRoutDhcpDynIpEndAddress OBJECT-TYPE
   SYNTAX      IpAddress
   MAX-ACCESS  read-write
   STATUS      current
   DESCRIPTION
      "Path: router.editConf.dhcpDynamic.ipEndAddress"
   ::= {er1645v2PRoutDhcpDynEntry 33554432}

er1645v2PRoutDhcpDynMask OBJECT-TYPE
   SYNTAX      IpAddress
   MAX-ACCESS  read-write
   STATUS      current
   DESCRIPTION
      "Path: router.editConf.dhcpDynamic.mask"
   ::= {er1645v2PRoutDhcpDynEntry 50331648}

er1645v2PRoutDhcpDynGateway OBJECT-TYPE
   SYNTAX      IpAddress
   MAX-ACCESS  read-write
   STATUS      current
   DESCRIPTION
      "Path: router.editConf.dhcpDynamic.gateway"
   ::= {er1645v2PRoutDhcpDynEntry 67108864}

er1645v2PRoutDhcpDynInterface OBJECT-TYPE
   SYNTAX      DisplayString
   MAX-ACCESS  read-write
   STATUS      current
   DESCRIPTION
      "Path: router.editConf.dhcpDynamic.interface"
   ::= {er1645v2PRoutDhcpDynEntry 268435456}

er1645v2PRoutDhcpDynDnsSetting OBJECT-TYPE
   SYNTAX      INTEGER
               {
               configured (0),
               learned (1),
               relay (2)
               }
   MAX-ACCESS  read-write
   STATUS      current
   DESCRIPTION
      "Path: router.editConf.dhcpDynamic.dnsSetting

       Possibilities:
               configured   (0)
               learned   (1)
               relay   (2)"
   ::= {er1645v2PRoutDhcpDynEntry 285212672}

er1645v2PRoutDhcpDynNameServer OBJECT-TYPE
   SYNTAX      IpAddress
   MAX-ACCESS  read-write
   STATUS      current
   DESCRIPTION
      "Path: router.editConf.dhcpDynamic.nameServer"
   ::= {er1645v2PRoutDhcpDynEntry 83886080}

er1645v2PRoutDhcpDynNameServer2 OBJECT-TYPE
   SYNTAX      IpAddress
   MAX-ACCESS  read-write
   STATUS      current
   DESCRIPTION
      "Path: router.editConf.dhcpDynamic.nameServer2"
   ::= {er1645v2PRoutDhcpDynEntry 234881024}

er1645v2PRoutDhcpDynTftpServer OBJECT-TYPE
   SYNTAX      IpAddress
   MAX-ACCESS  read-write
   STATUS      current
   DESCRIPTION
      "Path: router.editConf.dhcpDynamic.tftpServer"
   ::= {er1645v2PRoutDhcpDynEntry 100663296}

er1645v2PRoutDhcpDynTftpServerOption OBJECT-TYPE
   SYNTAX      DisplayString
   MAX-ACCESS  read-write
   STATUS      current
   DESCRIPTION
      "Path: router.editConf.dhcpDynamic.tftpServerOption"
   ::= {er1645v2PRoutDhcpDynEntry 335544320}

er1645v2PRoutDhcpDynLeaseTime OBJECT-TYPE
   SYNTAX      TimeTicks
   MAX-ACCESS  read-write
   STATUS      current
   DESCRIPTION
      "Path: router.editConf.dhcpDynamic.leaseTime

       Time in centi-second."
   ::= {er1645v2PRoutDhcpDynEntry 117440512}

er1645v2PRoutDhcpDynHoldTime OBJECT-TYPE
   SYNTAX      TimeTicks
   MAX-ACCESS  read-write
   STATUS      current
   DESCRIPTION
      "Path: router.editConf.dhcpDynamic.holdTime

       Time in centi-second."
   ::= {er1645v2PRoutDhcpDynEntry 134217728}

er1645v2PRoutDhcpDynBootFile OBJECT-TYPE
   SYNTAX      DisplayString
   MAX-ACCESS  read-write
   STATUS      current
   DESCRIPTION
      "Path: router.editConf.dhcpDynamic.bootFile"
   ::= {er1645v2PRoutDhcpDynEntry 150994944}

er1645v2PRoutDhcpDynBootFileOption OBJECT-TYPE
   SYNTAX      DisplayString
   MAX-ACCESS  read-write
   STATUS      current
   DESCRIPTION
      "Path: router.editConf.dhcpDynamic.bootFileOption"
   ::= {er1645v2PRoutDhcpDynEntry 352321536}

er1645v2PRoutDhcpDynHostName OBJECT-TYPE
   SYNTAX      DisplayString
   MAX-ACCESS  read-write
   STATUS      current
   DESCRIPTION
      "Path: router.editConf.dhcpDynamic.hostName"
   ::= {er1645v2PRoutDhcpDynEntry 167772160}

er1645v2PRoutDhcpDynDomainName OBJECT-TYPE
   SYNTAX      DisplayString
   MAX-ACCESS  read-write
   STATUS      current
   DESCRIPTION
      "Path: router.editConf.dhcpDynamic.domainName"
   ::= {er1645v2PRoutDhcpDynEntry 184549376}

er1645v2PRoutDhcpDynNetbiosNS OBJECT-TYPE
   SYNTAX      IpAddress
   MAX-ACCESS  read-write
   STATUS      current
   DESCRIPTION
      "Path: router.editConf.dhcpDynamic.netbiosNameServer"
   ::= {er1645v2PRoutDhcpDynEntry 201326592}

er1645v2PRoutDhcpDynNetbiosNS2 OBJECT-TYPE
   SYNTAX      IpAddress
   MAX-ACCESS  read-write
   STATUS      current
   DESCRIPTION
      "Path: router.editConf.dhcpDynamic.netbiosNameServer2"
   ::= {er1645v2PRoutDhcpDynEntry 251658240}

er1645v2PRoutDhcpDynNetbiosNT OBJECT-TYPE
   SYNTAX      INTEGER
               {
               nomnode (0),
               bmnode (1),
               pmnode (2),
               mmnode (4),
               hmnode (8)
               }
   MAX-ACCESS  read-write
   STATUS      current
   DESCRIPTION
      "Path: router.editConf.dhcpDynamic.netbiosNodeType

       Possibilities:
               no-node   (0)
               B-node   (1)
               P-node   (2)
               M-node   (4)
               H-node   (8)"
   ::= {er1645v2PRoutDhcpDynEntry 218103808}

er1645v2PRoutDhcpDynOptions OBJECT-TYPE
   SYNTAX      SEQUENCE OF Er1645v2PRoutDhcpDynOptionsEntry
   MAX-ACCESS  not-accessible
   STATUS      current
   DESCRIPTION
      ""
   ::= {er1645v2PRoutDhcpDyn 402653184}

er1645v2PRoutDhcpDynOptionsEntry OBJECT-TYPE
   SYNTAX      Er1645v2PRoutDhcpDynOptionsEntry
   MAX-ACCESS  not-accessible
   STATUS      current
   DESCRIPTION
      ""
   INDEX      { er1645v2PRoutDhcpDynTableIx,
                er1645v2PRoutDhcpDynOptionsTableIx }
   ::= {er1645v2PRoutDhcpDynOptions 1}

Er1645v2PRoutDhcpDynOptionsEntry ::=
   SEQUENCE
      {
      er1645v2PRoutDhcpDynOptionsActions
         VariableLengthTableActions,
      er1645v2PRoutDhcpDynOptionsTableIx
         TableIndex,
      er1645v2PRoutDhcpDynOptionsCode
         Integer32,
      er1645v2PRoutDhcpDynOptionsValueAscii
         DisplayString,
      er1645v2PRoutDhcpDynOptionsValueDecimal
         Integer32,
      er1645v2PRoutDhcpDynOptionsValueHexData
         OCTET STRING,
      er1645v2PRoutDhcpDynOptionsValueIpAddress
         IpAddress
      }

er1645v2PRoutDhcpDynOptionsActions OBJECT-TYPE
   SYNTAX      VariableLengthTableActions
   MAX-ACCESS  read-write
   STATUS      current
   DESCRIPTION
      "By way of this field, some manipulations
       on this table may be performed."
   ::= {er1645v2PRoutDhcpDynOptionsEntry 2}

er1645v2PRoutDhcpDynOptionsTableIx OBJECT-TYPE
   SYNTAX      TableIndex
   MAX-ACCESS  not-accessible
   STATUS      current
   DESCRIPTION
      ""
   ::= {er1645v2PRoutDhcpDynOptionsEntry 11}

er1645v2PRoutDhcpDynOptionsCode OBJECT-TYPE
   SYNTAX      Integer32
   MAX-ACCESS  read-write
   STATUS      current
   DESCRIPTION
      "Path: router.editConf.dhcpDynamic.options.code"
   ::= {er1645v2PRoutDhcpDynOptionsEntry 16777216}

er1645v2PRoutDhcpDynOptionsValueAscii OBJECT-TYPE
   SYNTAX      DisplayString
   MAX-ACCESS  read-write
   STATUS      current
   DESCRIPTION
      "Path: router.editConf.dhcpDynamic.options.value.ascii"
   ::= {er1645v2PRoutDhcpDynOptionsEntry 33619968}

er1645v2PRoutDhcpDynOptionsValueDecimal OBJECT-TYPE
   SYNTAX      Integer32
   MAX-ACCESS  read-write
   STATUS      current
   DESCRIPTION
      "Path: router.editConf.dhcpDynamic.options.value.decimal"
   ::= {er1645v2PRoutDhcpDynOptionsEntry 33685504}

er1645v2PRoutDhcpDynOptionsValueHexData OBJECT-TYPE
   SYNTAX      OCTET STRING
   MAX-ACCESS  read-write
   STATUS      current
   DESCRIPTION
      "Path: router.editConf.dhcpDynamic.options.value.hexData"
   ::= {er1645v2PRoutDhcpDynOptionsEntry 33751040}

er1645v2PRoutDhcpDynOptionsValueIpAddress OBJECT-TYPE
   SYNTAX      IpAddress
   MAX-ACCESS  read-write
   STATUS      current
   DESCRIPTION
      "Path: router.editConf.dhcpDynamic.options.value.ipAddress"
   ::= {er1645v2PRoutDhcpDynOptionsEntry 33816576}


er1645v2PRoutDhcpCheckAddress OBJECT-TYPE
   SYNTAX      INTEGER
               {
               disabled (0),
               enabled (1),
               arpOnly (2)
               }
   MAX-ACCESS  read-write
   STATUS      current
   DESCRIPTION
      "Path: router.editConf.dhcpCheckAddress
       Info: Should the DCHP server check if the given address is free

       Possibilities:
               disabled   (0)
               enabled   (1)
               arpOnly   (2)"
   ::= {er1645v2PRout 53}


er1645v2PRoutDhcpCustomVendorId OBJECT-TYPE
   SYNTAX      DisplayString
   MAX-ACCESS  read-write
   STATUS      current
   DESCRIPTION
      "Path: router.editConf.dhcpCustomVendorId
       Info: custom-defined DCHP Vendor Id"
   ::= {er1645v2PRout 81}


er1645v2PRoutDhcpClientIdentifier OBJECT-TYPE
   SYNTAX      INTEGER
               {
               default (0),
               lowest (1),
               interfaceMac (2)
               }
   MAX-ACCESS  read-write
   STATUS      current
   DESCRIPTION
      "Path: router.editConf.dhcpClientIdentifier
       Info: custom-defined DCHP Vendor Id

       Possibilities:
               default   (0)
               lowest   (1)
               interfaceMac   (2)"
   ::= {er1645v2PRout 91}


er1645v2PRoutQm OBJECT IDENTIFIER ::= {er1645v2PRout 77}

er1645v2PRoutQmSSC OBJECT IDENTIFIER ::= {er1645v2PRoutQm 1}

er1645v2PRoutQmEntry OBJECT IDENTIFIER ::= {er1645v2PRoutQmSSC 1}

er1645v2PRoutQmMonitor OBJECT-TYPE
   SYNTAX      INTEGER
               {
               disabled (0),
               enabled (1)
               }
   MAX-ACCESS  read-write
   STATUS      current
   DESCRIPTION
      "Path: router.editConf.qualityMonitor.monitor

       Possibilities:
               disabled   (0)
               enabled   (1)"
   ::= {er1645v2PRoutQmEntry 33554432}

er1645v2PRoutQmType OBJECT-TYPE
   SYNTAX      INTEGER
               {
               sequential (0),
               concurrent (1)
               }
   MAX-ACCESS  read-write
   STATUS      current
   DESCRIPTION
      "Path: router.editConf.qualityMonitor.type

       Possibilities:
               sequential   (0)
               concurrent   (1)"
   ::= {er1645v2PRoutQmEntry 16777216}

er1645v2PRoutQmStartDelay OBJECT-TYPE
   SYNTAX      TimeTicks
   MAX-ACCESS  read-write
   STATUS      current
   DESCRIPTION
      "Path: router.editConf.qualityMonitor.startDelay

       Time in centi-second."
   ::= {er1645v2PRoutQmEntry 83886080}

er1645v2PRoutQmDest OBJECT-TYPE
   SYNTAX      SEQUENCE OF Er1645v2PRoutQmDestEntry
   MAX-ACCESS  not-accessible
   STATUS      current
   DESCRIPTION
      ""
   ::= {er1645v2PRoutQm 50331648}

er1645v2PRoutQmDestEntry OBJECT-TYPE
   SYNTAX      Er1645v2PRoutQmDestEntry
   MAX-ACCESS  not-accessible
   STATUS      current
   DESCRIPTION
      ""
   INDEX      { er1645v2PRoutQmDestTableIx }
   ::= {er1645v2PRoutQmDest 1}

Er1645v2PRoutQmDestEntry ::=
   SEQUENCE
      {
      er1645v2PRoutQmDestActions
         VariableLengthTableActions,
      er1645v2PRoutQmDestTableIx
         TableIndex,
      er1645v2PRoutQmDestName
         DisplayString,
      er1645v2PRoutQmDestAdminStatus
         INTEGER,
      er1645v2PRoutQmDestIpAddress
         IpAddress,
      er1645v2PRoutQmDestHostName
         DisplayString,
      er1645v2PRoutQmDestSource
         IpAddress,
      er1645v2PRoutQmDestTos
         INTEGER,
      er1645v2PRoutQmDestPriority
         INTEGER,
      er1645v2PRoutQmDestProtocolIcmp
         OCTET STRING,
      er1645v2PRoutQmDestProtocolUdpEcho
         OCTET STRING,
      er1645v2PRoutQmDestProtocolUdpServerPort
         Integer32,
      er1645v2PRoutQmDestProtocolTwampLightPort
         Integer32,
      er1645v2PRoutQmDestProtocolBfdInterval
         Integer32,
      er1645v2PRoutQmDestProtocolBfdMinRx
         Integer32,
      er1645v2PRoutQmDestProtocolBfdMultiplier
         Integer32,
      er1645v2PRoutQmDestProtocolBfdEcho
         INTEGER,
      er1645v2PRoutQmDestTxInterface
         DisplayString,
      er1645v2PRoutQmDestTxGateway
         IpAddress,
      er1645v2PRoutQmDestInterval
         Integer32,
      er1645v2PRoutQmDestTimeOut
         Integer32,
      er1645v2PRoutQmDestLength
         Integer32,
      er1645v2PRoutQmDestIdleSamples
         Integer32,
      er1645v2PRoutQmDestLossAlarmSamples
         Integer32,
      er1645v2PRoutQmDestLossAlarmAlarmOn
         Integer32,
      er1645v2PRoutQmDestLossAlarmAlarmOff
         Integer32,
      er1645v2PRoutQmDestLossAlarmAlarmUpOn
         Integer32,
      er1645v2PRoutQmDestLossAlarmAlarmUpOff
         Integer32,
      er1645v2PRoutQmDestLossAlarmAlarmDownOn
         Integer32,
      er1645v2PRoutQmDestLossAlarmAlarmDownOff
         Integer32,
      er1645v2PRoutQmDestDelayAlarmSamples
         Integer32,
      er1645v2PRoutQmDestDelayAlarmDelayAvrgOn
         Integer32,
      er1645v2PRoutQmDestDelayAlarmDelayAvrgOff
         Integer32,
      er1645v2PRoutQmDestDelayAlarmDelayMaxOn
         Integer32,
      er1645v2PRoutQmDestDelayAlarmDelayMaxOff
         Integer32,
      er1645v2PRoutQmDestDelayAlarmDelayMinMaxOn
         Integer32,
      er1645v2PRoutQmDestDelayAlarmDelayMinMaxOff
         Integer32,
      er1645v2PRoutQmDestDelayAlarmDsType
         INTEGER,
      er1645v2PRoutQmDestDelayAlarmDsBinsN
         INTEGER,
      er1645v2PRoutQmDestDelayAlarmDsBinsNMn
         Integer32,
      er1645v2PRoutQmDestDelayAlarmDsBinsNMx
         Integer32,
      er1645v2PRoutQmDestDelayAlarmDsBinsTB1
         Integer32,
      er1645v2PRoutQmDestDelayAlarmDsBinsTB2
         Integer32,
      er1645v2PRoutQmDestDelayAlarmDsBinsTB3
         Integer32,
      er1645v2PRoutQmDestDelayAlarmDsBinsTB4
         Integer32,
      er1645v2PRoutQmDestDelayAlarmDsBinsTB5
         Integer32,
      er1645v2PRoutQmDestDelayAlarmDsBinsTB6
         Integer32,
      er1645v2PRoutQmDestDelayAlarmDsBinsTB7
         Integer32,
      er1645v2PRoutQmDestDelayAlarmDsBinsTB8
         Integer32,
      er1645v2PRoutQmDestDelayAlarmDsBinsTMx
         Integer32,
      er1645v2PRoutQmDestDelayAlarmJitterAvrgOn
         Integer32,
      er1645v2PRoutQmDestDelayAlarmJitterAvrgOff
         Integer32,
      er1645v2PRoutQmDestDelayAlarmJitterMaxOn
         Integer32,
      er1645v2PRoutQmDestDelayAlarmJitterMaxOff
         Integer32,
      er1645v2PRoutQmDestDelayAlarmJsN
         INTEGER,
      er1645v2PRoutQmDestDelayAlarmJsNMn
         Integer32,
      er1645v2PRoutQmDestDelayAlarmJsNMx
         Integer32,
      er1645v2PRoutQmDestDelayAlarmJsTB1
         Integer32,
      er1645v2PRoutQmDestDelayAlarmJsTB2
         Integer32,
      er1645v2PRoutQmDestDelayAlarmJsTB3
         Integer32,
      er1645v2PRoutQmDestDelayAlarmJsTB4
         Integer32,
      er1645v2PRoutQmDestDelayAlarmJsTB5
         Integer32,
      er1645v2PRoutQmDestDelayAlarmJsTB6
         Integer32,
      er1645v2PRoutQmDestDelayAlarmJsTB7
         Integer32,
      er1645v2PRoutQmDestDelayAlarmJsTB8
         Integer32,
      er1645v2PRoutQmDestDelayAlarmJsTMx
         Integer32,
      er1645v2PRoutQmDestDelayAlarmJitterUpAvrgOn
         Integer32,
      er1645v2PRoutQmDestDelayAlarmJitterUpAvrgOff
         Integer32,
      er1645v2PRoutQmDestDelayAlarmJitterUpMaxOn
         Integer32,
      er1645v2PRoutQmDestDelayAlarmJitterUpMaxOff
         Integer32,
      er1645v2PRoutQmDestDelayAlarmJupsN
         INTEGER,
      er1645v2PRoutQmDestDelayAlarmJupsNMn
         Integer32,
      er1645v2PRoutQmDestDelayAlarmJupsNMx
         Integer32,
      er1645v2PRoutQmDestDelayAlarmJupsTB1
         Integer32,
      er1645v2PRoutQmDestDelayAlarmJupsTB2
         Integer32,
      er1645v2PRoutQmDestDelayAlarmJupsTB3
         Integer32,
      er1645v2PRoutQmDestDelayAlarmJupsTB4
         Integer32,
      er1645v2PRoutQmDestDelayAlarmJupsTB5
         Integer32,
      er1645v2PRoutQmDestDelayAlarmJupsTB6
         Integer32,
      er1645v2PRoutQmDestDelayAlarmJupsTB7
         Integer32,
      er1645v2PRoutQmDestDelayAlarmJupsTB8
         Integer32,
      er1645v2PRoutQmDestDelayAlarmJupsTMx
         Integer32,
      er1645v2PRoutQmDestDelayAlarmJitterDownAvrgOn
         Integer32,
      er1645v2PRoutQmDestDelayAlarmJitterDownAvrgOff
         Integer32,
      er1645v2PRoutQmDestDelayAlarmJitterDownMaxOn
         Integer32,
      er1645v2PRoutQmDestDelayAlarmJitterDownMaxOff
         Integer32,
      er1645v2PRoutQmDestDelayAlarmJdownsN
         INTEGER,
      er1645v2PRoutQmDestDelayAlarmJdownsNMn
         Integer32,
      er1645v2PRoutQmDestDelayAlarmJdownsNMx
         Integer32,
      er1645v2PRoutQmDestDelayAlarmJdownsTB1
         Integer32,
      er1645v2PRoutQmDestDelayAlarmJdownsTB2
         Integer32,
      er1645v2PRoutQmDestDelayAlarmJdownsTB3
         Integer32,
      er1645v2PRoutQmDestDelayAlarmJdownsTB4
         Integer32,
      er1645v2PRoutQmDestDelayAlarmJdownsTB5
         Integer32,
      er1645v2PRoutQmDestDelayAlarmJdownsTB6
         Integer32,
      er1645v2PRoutQmDestDelayAlarmJdownsTB7
         Integer32,
      er1645v2PRoutQmDestDelayAlarmJdownsTB8
         Integer32,
      er1645v2PRoutQmDestDelayAlarmJdownsTMx
         Integer32,
      er1645v2PRoutQmDestDelayAlarmDelayUpAvrgOn
         Integer32,
      er1645v2PRoutQmDestDelayAlarmDelayUpAvrgOff
         Integer32,
      er1645v2PRoutQmDestDelayAlarmDelayUpMaxOn
         Integer32,
      er1645v2PRoutQmDestDelayAlarmDelayUpMaxOff
         Integer32,
      er1645v2PRoutQmDestDelayAlarmDupsType
         INTEGER,
      er1645v2PRoutQmDestDelayAlarmDupsBinsN
         INTEGER,
      er1645v2PRoutQmDestDelayAlarmDupsBinsNMn
         Integer32,
      er1645v2PRoutQmDestDelayAlarmDupsBinsNMx
         Integer32,
      er1645v2PRoutQmDestDelayAlarmDupsBinsTB1
         Integer32,
      er1645v2PRoutQmDestDelayAlarmDupsBinsTB2
         Integer32,
      er1645v2PRoutQmDestDelayAlarmDupsBinsTB3
         Integer32,
      er1645v2PRoutQmDestDelayAlarmDupsBinsTB4
         Integer32,
      er1645v2PRoutQmDestDelayAlarmDupsBinsTB5
         Integer32,
      er1645v2PRoutQmDestDelayAlarmDupsBinsTB6
         Integer32,
      er1645v2PRoutQmDestDelayAlarmDupsBinsTB7
         Integer32,
      er1645v2PRoutQmDestDelayAlarmDupsBinsTB8
         Integer32,
      er1645v2PRoutQmDestDelayAlarmDupsBinsTMx
         Integer32,
      er1645v2PRoutQmDestDelayAlarmDelayDownAvrgOn
         Integer32,
      er1645v2PRoutQmDestDelayAlarmDelayDownAvrgOff
         Integer32,
      er1645v2PRoutQmDestDelayAlarmDelayDownMaxOn
         Integer32,
      er1645v2PRoutQmDestDelayAlarmDelayDownMaxOff
         Integer32,
      er1645v2PRoutQmDestDelayAlarmDdownsType
         INTEGER,
      er1645v2PRoutQmDestDelayAlarmDdownsBinsN
         INTEGER,
      er1645v2PRoutQmDestDelayAlarmDdownsBinsNMn
         Integer32,
      er1645v2PRoutQmDestDelayAlarmDdownsBinsNMx
         Integer32,
      er1645v2PRoutQmDestDelayAlarmDdownsBinsTB1
         Integer32,
      er1645v2PRoutQmDestDelayAlarmDdownsBinsTB2
         Integer32,
      er1645v2PRoutQmDestDelayAlarmDdownsBinsTB3
         Integer32,
      er1645v2PRoutQmDestDelayAlarmDdownsBinsTB4
         Integer32,
      er1645v2PRoutQmDestDelayAlarmDdownsBinsTB5
         Integer32,
      er1645v2PRoutQmDestDelayAlarmDdownsBinsTB6
         Integer32,
      er1645v2PRoutQmDestDelayAlarmDdownsBinsTB7
         Integer32,
      er1645v2PRoutQmDestDelayAlarmDdownsBinsTB8
         Integer32,
      er1645v2PRoutQmDestDelayAlarmDdownsBinsTMx
         Integer32,
      er1645v2PRoutQmDestAlarmMask
         Integer32,
      er1645v2PRoutQmDestLogging
         INTEGER,
      er1645v2PRoutQmDestLoggingDepth
         INTEGER
      }

er1645v2PRoutQmDestActions OBJECT-TYPE
   SYNTAX      VariableLengthTableActions
   MAX-ACCESS  read-write
   STATUS      current
   DESCRIPTION
      "By way of this field, some manipulations
       on this table may be performed."
   ::= {er1645v2PRoutQmDestEntry 2}

er1645v2PRoutQmDestTableIx OBJECT-TYPE
   SYNTAX      TableIndex
   MAX-ACCESS  not-accessible
   STATUS      current
   DESCRIPTION
      ""
   ::= {er1645v2PRoutQmDestEntry 11}

er1645v2PRoutQmDestName OBJECT-TYPE
   SYNTAX      DisplayString
   MAX-ACCESS  read-write
   STATUS      current
   DESCRIPTION
      "Path: router.editConf.qualityMonitor.destinations.name"
   ::= {er1645v2PRoutQmDestEntry 234881024}

er1645v2PRoutQmDestAdminStatus OBJECT-TYPE
   SYNTAX      INTEGER
               {
               enabled (1),
               onDemand (2),
               disabled (3)
               }
   MAX-ACCESS  read-write
   STATUS      current
   DESCRIPTION
      "Path: router.editConf.qualityMonitor.destinations.adminStatus

       Possibilities:
               enabled   (1)
               onDemand   (2)
               disabled   (3)"
   ::= {er1645v2PRoutQmDestEntry 369098752}

er1645v2PRoutQmDestIpAddress OBJECT-TYPE
   SYNTAX      IpAddress
   MAX-ACCESS  read-write
   STATUS      current
   DESCRIPTION
      "Path: router.editConf.qualityMonitor.destinations.ipAddress"
   ::= {er1645v2PRoutQmDestEntry 16777216}

er1645v2PRoutQmDestHostName OBJECT-TYPE
   SYNTAX      DisplayString
   MAX-ACCESS  read-write
   STATUS      current
   DESCRIPTION
      "Path: router.editConf.qualityMonitor.destinations.hostName"
   ::= {er1645v2PRoutQmDestEntry 33554432}

er1645v2PRoutQmDestSource OBJECT-TYPE
   SYNTAX      IpAddress
   MAX-ACCESS  read-write
   STATUS      current
   DESCRIPTION
      "Path: router.editConf.qualityMonitor.destinations.source"
   ::= {er1645v2PRoutQmDestEntry 184549376}

er1645v2PRoutQmDestTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: router.editConf.qualityMonitor.destinations.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2PRoutQmDestEntry 167772160}

er1645v2PRoutQmDestPriority OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: router.editConf.qualityMonitor.destinations.priority

       Possibilities:
               queue1   (0)
               queue2   (1)
               queue3   (2)
               queue4   (3)
               queue5   (4)
               lowDelayQueue   (5)
               lowDelay2Queue   (6)
               systemQueue   (7)"
   ::= {er1645v2PRoutQmDestEntry 218103808}

er1645v2PRoutQmDestProtocolIcmp OBJECT-TYPE
   SYNTAX      OCTET STRING
   MAX-ACCESS  read-write
   STATUS      current
   DESCRIPTION
      "Path: router.editConf.qualityMonitor.destinations.protocol.icmp"
   ::= {er1645v2PRoutQmDestEntry 50397184}

er1645v2PRoutQmDestProtocolUdpEcho OBJECT-TYPE
   SYNTAX      OCTET STRING
   MAX-ACCESS  read-write
   STATUS      current
   DESCRIPTION
      "Path: router.editConf.qualityMonitor.destinations.protocol.udpEcho"
   ::= {er1645v2PRoutQmDestEntry 50462720}

er1645v2PRoutQmDestProtocolUdpServerPort OBJECT-TYPE
   SYNTAX      Integer32
   MAX-ACCESS  read-write
   STATUS      current
   DESCRIPTION
      "Path: router.editConf.qualityMonitor.destinations.protocol.udpServerPort"
   ::= {er1645v2PRoutQmDestEntry 50528256}

er1645v2PRoutQmDestProtocolTwampLightPort OBJECT-TYPE
   SYNTAX      Integer32
   MAX-ACCESS  read-write
   STATUS      current
   DESCRIPTION
      "Path: router.editConf.qualityMonitor.destinations.protocol.twampLightPort"
   ::= {er1645v2PRoutQmDestEntry 50593792}

er1645v2PRoutQmDestProtocolBfdInterval OBJECT-TYPE
   SYNTAX      Integer32
   UNITS       "ms"
   MAX-ACCESS  read-write
   STATUS      current
   DESCRIPTION
      "Path: router.editConf.qualityMonitor.destinations.protocol.bfd.interval

       unit name = ms"
   ::= {er1645v2PRoutQmDestEntry 50659584}

er1645v2PRoutQmDestProtocolBfdMinRx OBJECT-TYPE
   SYNTAX      Integer32
   UNITS       "ms"
   MAX-ACCESS  read-write
   STATUS      current
   DESCRIPTION
      "Path: router.editConf.qualityMonitor.destinations.protocol.bfd.minRx

       unit name = ms"
   ::= {er1645v2PRoutQmDestEntry 50659840}

er1645v2PRoutQmDestProtocolBfdMultiplier OBJECT-TYPE
   SYNTAX      Integer32
   MAX-ACCESS  read-write
   STATUS      current
   DESCRIPTION
      "Path: router.editConf.qualityMonitor.destinations.protocol.bfd.multiplier"
   ::= {er1645v2PRoutQmDestEntry 50660096}

er1645v2PRoutQmDestProtocolBfdEcho OBJECT-TYPE
   SYNTAX      INTEGER
               {
               txRx (1),
               tx (2),
               rx (3),
               no (4)
               }
   MAX-ACCESS  read-write
   STATUS      current
   DESCRIPTION
      "Path: router.editConf.qualityMonitor.destinations.protocol.bfd.echo

       Possibilities:
               txRx   (1)
               tx   (2)
               rx   (3)
               no   (4)"
   ::= {er1645v2PRoutQmDestEntry 50660352}

er1645v2PRoutQmDestTxInterface OBJECT-TYPE
   SYNTAX      DisplayString
   MAX-ACCESS  read-write
   STATUS      current
   DESCRIPTION
      "Path: router.editConf.qualityMonitor.destinations.txInterface"
   ::= {er1645v2PRoutQmDestEntry 402653184}

er1645v2PRoutQmDestTxGateway OBJECT-TYPE
   SYNTAX      IpAddress
   MAX-ACCESS  read-write
   STATUS      current
   DESCRIPTION
      "Path: router.editConf.qualityMonitor.destinations.txGateway"
   ::= {er1645v2PRoutQmDestEntry 419430400}

er1645v2PRoutQmDestInterval OBJECT-TYPE
   SYNTAX      Integer32
   UNITS       "100msec"
   MAX-ACCESS  read-write
   STATUS      current
   DESCRIPTION
      "Path: router.editConf.qualityMonitor.destinations.interval

       unit name = 100msec"
   ::= {er1645v2PRoutQmDestEntry 67108864}

er1645v2PRoutQmDestTimeOut OBJECT-TYPE
   SYNTAX      Integer32
   UNITS       "100msec"
   MAX-ACCESS  read-write
   STATUS      current
   DESCRIPTION
      "Path: router.editConf.qualityMonitor.destinations.timeOut

       unit name = 100msec"
   ::= {er1645v2PRoutQmDestEntry 150994944}

er1645v2PRoutQmDestLength OBJECT-TYPE
   SYNTAX      Integer32
   MAX-ACCESS  read-write
   STATUS      current
   DESCRIPTION
      "Path: router.editConf.qualityMonitor.destinations.length"
   ::= {er1645v2PRoutQmDestEntry 83886080}

er1645v2PRoutQmDestIdleSamples OBJECT-TYPE
   SYNTAX      Integer32
   MAX-ACCESS  read-write
   STATUS      current
   DESCRIPTION
      "Path: router.editConf.qualityMonitor.destinations.idleSamples"
   ::= {er1645v2PRoutQmDestEntry 268435456}

er1645v2PRoutQmDestLossAlarmSamples OBJECT-TYPE
   SYNTAX      Integer32
   MAX-ACCESS  read-write
   STATUS      current
   DESCRIPTION
      "Path: router.editConf.qualityMonitor.destinations.lossAlarm.samples"
   ::= {er1645v2PRoutQmDestEntry 100728832}

er1645v2PRoutQmDestLossAlarmAlarmOn OBJECT-TYPE
   SYNTAX      Integer32
   MAX-ACCESS  read-write
   STATUS      current
   DESCRIPTION
      "Path: router.editConf.qualityMonitor.destinations.lossAlarm.alarmOn"
   ::= {er1645v2PRoutQmDestEntry 100794368}

er1645v2PRoutQmDestLossAlarmAlarmOff OBJECT-TYPE
   SYNTAX      Integer32
   MAX-ACCESS  read-write
   STATUS      current
   DESCRIPTION
      "Path: router.editConf.qualityMonitor.destinations.lossAlarm.alarmOff"
   ::= {er1645v2PRoutQmDestEntry 100859904}

er1645v2PRoutQmDestLossAlarmAlarmUpOn OBJECT-TYPE
   SYNTAX      Integer32
   MAX-ACCESS  read-write
   STATUS      current
   DESCRIPTION
      "Path: router.editConf.qualityMonitor.destinations.lossAlarm.alarmUpOn"
   ::= {er1645v2PRoutQmDestEntry 100925440}

er1645v2PRoutQmDestLossAlarmAlarmUpOff OBJECT-TYPE
   SYNTAX      Integer32
   MAX-ACCESS  read-write
   STATUS      current
   DESCRIPTION
      "Path: router.editConf.qualityMonitor.destinations.lossAlarm.alarmUpOff"
   ::= {er1645v2PRoutQmDestEntry 100990976}

er1645v2PRoutQmDestLossAlarmAlarmDownOn OBJECT-TYPE
   SYNTAX      Integer32
   MAX-ACCESS  read-write
   STATUS      current
   DESCRIPTION
      "Path: router.editConf.qualityMonitor.destinations.lossAlarm.alarmDownOn"
   ::= {er1645v2PRoutQmDestEntry 101056512}

er1645v2PRoutQmDestLossAlarmAlarmDownOff OBJECT-TYPE
   SYNTAX      Integer32
   MAX-ACCESS  read-write
   STATUS      current
   DESCRIPTION
      "Path: router.editConf.qualityMonitor.destinations.lossAlarm.alarmDownOff"
   ::= {er1645v2PRoutQmDestEntry 101122048}

er1645v2PRoutQmDestDelayAlarmSamples OBJECT-TYPE
   SYNTAX      Integer32
   MAX-ACCESS  read-write
   STATUS      current
   DESCRIPTION
      "Path: router.editConf.qualityMonitor.destinations.delayAlarm.samples"
   ::= {er1645v2PRoutQmDestEntry 117506048}

er1645v2PRoutQmDestDelayAlarmDelayAvrgOn OBJECT-TYPE
   SYNTAX      Integer32
   UNITS       "msec"
   MAX-ACCESS  read-write
   STATUS      current
   DESCRIPTION
      "Path: router.editConf.qualityMonitor.destinations.delayAlarm.delayAvrgOn

       unit name = msec"
   ::= {er1645v2PRoutQmDestEntry 117571584}

er1645v2PRoutQmDestDelayAlarmDelayAvrgOff OBJECT-TYPE
   SYNTAX      Integer32
   UNITS       "msec"
   MAX-ACCESS  read-write
   STATUS      current
   DESCRIPTION
      "Path: router.editConf.qualityMonitor.destinations.delayAlarm.delayAvrgOff

       unit name = msec"
   ::= {er1645v2PRoutQmDestEntry 117637120}

er1645v2PRoutQmDestDelayAlarmDelayMaxOn OBJECT-TYPE
   SYNTAX      Integer32
   UNITS       "msec"
   MAX-ACCESS  read-write
   STATUS      current
   DESCRIPTION
      "Path: router.editConf.qualityMonitor.destinations.delayAlarm.delayMaxOn

       unit name = msec"
   ::= {er1645v2PRoutQmDestEntry 117702656}

er1645v2PRoutQmDestDelayAlarmDelayMaxOff OBJECT-TYPE
   SYNTAX      Integer32
   UNITS       "msec"
   MAX-ACCESS  read-write
   STATUS      current
   DESCRIPTION
      "Path: router.editConf.qualityMonitor.destinations.delayAlarm.delayMaxOff

       unit name = msec"
   ::= {er1645v2PRoutQmDestEntry 117768192}

er1645v2PRoutQmDestDelayAlarmDelayMinMaxOn OBJECT-TYPE
   SYNTAX      Integer32
   UNITS       "msec"
   MAX-ACCESS  read-write
   STATUS      current
   DESCRIPTION
      "Path: router.editConf.qualityMonitor.destinations.delayAlarm.delayMinMaxOn

       unit name = msec"
   ::= {er1645v2PRoutQmDestEntry 118095872}

er1645v2PRoutQmDestDelayAlarmDelayMinMaxOff OBJECT-TYPE
   SYNTAX      Integer32
   UNITS       "msec"
   MAX-ACCESS  read-write
   STATUS      current
   DESCRIPTION
      "Path: router.editConf.qualityMonitor.destinations.delayAlarm.delayMinMaxOff

       unit name = msec"
   ::= {er1645v2PRoutQmDestEntry 118161408}

er1645v2PRoutQmDestDelayAlarmDsType OBJECT-TYPE
   SYNTAX      INTEGER
               {
               fd (1),
               fdr (2)
               }
   MAX-ACCESS  read-write
   STATUS      current
   DESCRIPTION
      "Path: router.editConf.qualityMonitor.destinations.delayAlarm.delayStat.type

       Possibilities:
               fd   (1)
               fdr   (2)"
   ::= {er1645v2PRoutQmDestEntry 119283712}

er1645v2PRoutQmDestDelayAlarmDsBinsN OBJECT-TYPE
   SYNTAX      INTEGER
               {
               none (0)
               }
   MAX-ACCESS  read-write
   STATUS      current
   DESCRIPTION
      "Path: router.editConf.qualityMonitor.destinations.delayAlarm.delayStat.bins.none

       Possibilities:
               none   (0)"
   ::= {er1645v2PRoutQmDestEntry 119292928}

er1645v2PRoutQmDestDelayAlarmDsBinsNMn OBJECT-TYPE
   SYNTAX      Integer32
   UNITS       "msec"
   MAX-ACCESS  read-write
   STATUS      current
   DESCRIPTION
      "Path: router.editConf.qualityMonitor.destinations.delayAlarm.delayStat.bins.range.min

       unit name = msec"
   ::= {er1645v2PRoutQmDestEntry 119294080}

er1645v2PRoutQmDestDelayAlarmDsBinsNMx OBJECT-TYPE
   SYNTAX      Integer32
   UNITS       "msec"
   MAX-ACCESS  read-write
   STATUS      current
   DESCRIPTION
      "Path: router.editConf.qualityMonitor.destinations.delayAlarm.delayStat.bins.range.max

       unit name = msec"
   ::= {er1645v2PRoutQmDestEntry 119294208}

er1645v2PRoutQmDestDelayAlarmDsBinsTB1 OBJECT-TYPE
   SYNTAX      Integer32
   UNITS       "msec"
   MAX-ACCESS  read-write
   STATUS      current
   DESCRIPTION
      "Path: router.editConf.qualityMonitor.destinations.delayAlarm.delayStat.bins.table.bin1

       unit name = msec"
   ::= {er1645v2PRoutQmDestEntry 119295040}

er1645v2PRoutQmDestDelayAlarmDsBinsTB2 OBJECT-TYPE
   SYNTAX      Integer32
   UNITS       "msec"
   MAX-ACCESS  read-write
   STATUS      current
   DESCRIPTION
      "Path: router.editConf.qualityMonitor.destinations.delayAlarm.delayStat.bins.table.bin2

       unit name = msec"
   ::= {er1645v2PRoutQmDestEntry 119295104}

er1645v2PRoutQmDestDelayAlarmDsBinsTB3 OBJECT-TYPE
   SYNTAX      Integer32
   UNITS       "msec"
   MAX-ACCESS  read-write
   STATUS      current
   DESCRIPTION
      "Path: router.editConf.qualityMonitor.destinations.delayAlarm.delayStat.bins.table.bin3

       unit name = msec"
   ::= {er1645v2PRoutQmDestEntry 119295168}

er1645v2PRoutQmDestDelayAlarmDsBinsTB4 OBJECT-TYPE
   SYNTAX      Integer32
   UNITS       "msec"
   MAX-ACCESS  read-write
   STATUS      current
   DESCRIPTION
      "Path: router.editConf.qualityMonitor.destinations.delayAlarm.delayStat.bins.table.bin4

       unit name = msec"
   ::= {er1645v2PRoutQmDestEntry 119295232}

er1645v2PRoutQmDestDelayAlarmDsBinsTB5 OBJECT-TYPE
   SYNTAX      Integer32
   UNITS       "msec"
   MAX-ACCESS  read-write
   STATUS      current
   DESCRIPTION
      "Path: router.editConf.qualityMonitor.destinations.delayAlarm.delayStat.bins.table.bin5

       unit name = msec"
   ::= {er1645v2PRoutQmDestEntry 119295296}

er1645v2PRoutQmDestDelayAlarmDsBinsTB6 OBJECT-TYPE
   SYNTAX      Integer32
   UNITS       "msec"
   MAX-ACCESS  read-write
   STATUS      current
   DESCRIPTION
      "Path: router.editConf.qualityMonitor.destinations.delayAlarm.delayStat.bins.table.bin6

       unit name = msec"
   ::= {er1645v2PRoutQmDestEntry 119295360}

er1645v2PRoutQmDestDelayAlarmDsBinsTB7 OBJECT-TYPE
   SYNTAX      Integer32
   UNITS       "msec"
   MAX-ACCESS  read-write
   STATUS      current
   DESCRIPTION
      "Path: router.editConf.qualityMonitor.destinations.delayAlarm.delayStat.bins.table.bin7

       unit name = msec"
   ::= {er1645v2PRoutQmDestEntry 119295424}

er1645v2PRoutQmDestDelayAlarmDsBinsTB8 OBJECT-TYPE
   SYNTAX      Integer32
   UNITS       "msec"
   MAX-ACCESS  read-write
   STATUS      current
   DESCRIPTION
      "Path: router.editConf.qualityMonitor.destinations.delayAlarm.delayStat.bins.table.bin8

       unit name = msec"
   ::= {er1645v2PRoutQmDestEntry 119295488}

er1645v2PRoutQmDestDelayAlarmDsBinsTMx OBJECT-TYPE
   SYNTAX      Integer32
   UNITS       "msec"
   MAX-ACCESS  read-write
   STATUS      current
   DESCRIPTION
      "Path: router.editConf.qualityMonitor.destinations.delayAlarm.delayStat.bins.table.max

       unit name = msec"
   ::= {er1645v2PRoutQmDestEntry 119295552}

er1645v2PRoutQmDestDelayAlarmJitterAvrgOn OBJECT-TYPE
   SYNTAX      Integer32
   UNITS       "msec"
   MAX-ACCESS  read-write
   STATUS      current
   DESCRIPTION
      "Path: router.editConf.qualityMonitor.destinations.delayAlarm.jitterAvrgOn

       unit name = msec"
   ::= {er1645v2PRoutQmDestEntry 117833728}

er1645v2PRoutQmDestDelayAlarmJitterAvrgOff OBJECT-TYPE
   SYNTAX      Integer32
   UNITS       "msec"
   MAX-ACCESS  read-write
   STATUS      current
   DESCRIPTION
      "Path: router.editConf.qualityMonitor.destinations.delayAlarm.jitterAvrgOff

       unit name = msec"
   ::= {er1645v2PRoutQmDestEntry 117899264}

er1645v2PRoutQmDestDelayAlarmJitterMaxOn OBJECT-TYPE
   SYNTAX      Integer32
   UNITS       "msec"
   MAX-ACCESS  read-write
   STATUS      current
   DESCRIPTION
      "Path: router.editConf.qualityMonitor.destinations.delayAlarm.jitterMaxOn

       unit name = msec"
   ::= {er1645v2PRoutQmDestEntry 117964800}

er1645v2PRoutQmDestDelayAlarmJitterMaxOff OBJECT-TYPE
   SYNTAX      Integer32
   UNITS       "msec"
   MAX-ACCESS  read-write
   STATUS      current
   DESCRIPTION
      "Path: router.editConf.qualityMonitor.destinations.delayAlarm.jitterMaxOff

       unit name = msec"
   ::= {er1645v2PRoutQmDestEntry 118030336}

er1645v2PRoutQmDestDelayAlarmJsN OBJECT-TYPE
   SYNTAX      INTEGER
               {
               none (0)
               }
   MAX-ACCESS  read-write
   STATUS      current
   DESCRIPTION
      "Path: router.editConf.qualityMonitor.destinations.delayAlarm.jitterStat.none

       Possibilities:
               none   (0)"
   ::= {er1645v2PRoutQmDestEntry 119676928}

er1645v2PRoutQmDestDelayAlarmJsNMn OBJECT-TYPE
   SYNTAX      Integer32
   UNITS       "msec"
   MAX-ACCESS  read-write
   STATUS      current
   DESCRIPTION
      "Path: router.editConf.qualityMonitor.destinations.delayAlarm.jitterStat.range.min

       unit name = msec"
   ::= {er1645v2PRoutQmDestEntry 119686144}

er1645v2PRoutQmDestDelayAlarmJsNMx OBJECT-TYPE
   SYNTAX      Integer32
   UNITS       "msec"
   MAX-ACCESS  read-write
   STATUS      current
   DESCRIPTION
      "Path: router.editConf.qualityMonitor.destinations.delayAlarm.jitterStat.range.max

       unit name = msec"
   ::= {er1645v2PRoutQmDestEntry 119687168}

er1645v2PRoutQmDestDelayAlarmJsTB1 OBJECT-TYPE
   SYNTAX      Integer32
   UNITS       "msec"
   MAX-ACCESS  read-write
   STATUS      current
   DESCRIPTION
      "Path: router.editConf.qualityMonitor.destinations.delayAlarm.jitterStat.table.bin1

       unit name = msec"
   ::= {er1645v2PRoutQmDestEntry 119693824}

er1645v2PRoutQmDestDelayAlarmJsTB2 OBJECT-TYPE
   SYNTAX      Integer32
   UNITS       "msec"
   MAX-ACCESS  read-write
   STATUS      current
   DESCRIPTION
      "Path: router.editConf.qualityMonitor.destinations.delayAlarm.jitterStat.table.bin2

       unit name = msec"
   ::= {er1645v2PRoutQmDestEntry 119694336}

er1645v2PRoutQmDestDelayAlarmJsTB3 OBJECT-TYPE
   SYNTAX      Integer32
   UNITS       "msec"
   MAX-ACCESS  read-write
   STATUS      current
   DESCRIPTION
      "Path: router.editConf.qualityMonitor.destinations.delayAlarm.jitterStat.table.bin3

       unit name = msec"
   ::= {er1645v2PRoutQmDestEntry 119694848}

er1645v2PRoutQmDestDelayAlarmJsTB4 OBJECT-TYPE
   SYNTAX      Integer32
   UNITS       "msec"
   MAX-ACCESS  read-write
   STATUS      current
   DESCRIPTION
      "Path: router.editConf.qualityMonitor.destinations.delayAlarm.jitterStat.table.bin4

       unit name = msec"
   ::= {er1645v2PRoutQmDestEntry 119695360}

er1645v2PRoutQmDestDelayAlarmJsTB5 OBJECT-TYPE
   SYNTAX      Integer32
   UNITS       "msec"
   MAX-ACCESS  read-write
   STATUS      current
   DESCRIPTION
      "Path: router.editConf.qualityMonitor.destinations.delayAlarm.jitterStat.table.bin5

       unit name = msec"
   ::= {er1645v2PRoutQmDestEntry 119695872}

er1645v2PRoutQmDestDelayAlarmJsTB6 OBJECT-TYPE
   SYNTAX      Integer32
   UNITS       "msec"
   MAX-ACCESS  read-write
   STATUS      current
   DESCRIPTION
      "Path: router.editConf.qualityMonitor.destinations.delayAlarm.jitterStat.table.bin6

       unit name = msec"
   ::= {er1645v2PRoutQmDestEntry 119696384}

er1645v2PRoutQmDestDelayAlarmJsTB7 OBJECT-TYPE
   SYNTAX      Integer32
   UNITS       "msec"
   MAX-ACCESS  read-write
   STATUS      current
   DESCRIPTION
      "Path: router.editConf.qualityMonitor.destinations.delayAlarm.jitterStat.table.bin7

       unit name = msec"
   ::= {er1645v2PRoutQmDestEntry 119696896}

er1645v2PRoutQmDestDelayAlarmJsTB8 OBJECT-TYPE
   SYNTAX      Integer32
   UNITS       "msec"
   MAX-ACCESS  read-write
   STATUS      current
   DESCRIPTION
      "Path: router.editConf.qualityMonitor.destinations.delayAlarm.jitterStat.table.bin8

       unit name = msec"
   ::= {er1645v2PRoutQmDestEntry 119697408}

er1645v2PRoutQmDestDelayAlarmJsTMx OBJECT-TYPE
   SYNTAX      Integer32
   UNITS       "msec"
   MAX-ACCESS  read-write
   STATUS      current
   DESCRIPTION
      "Path: router.editConf.qualityMonitor.destinations.delayAlarm.jitterStat.table.max

       unit name = msec"
   ::= {er1645v2PRoutQmDestEntry 119697920}

er1645v2PRoutQmDestDelayAlarmJitterUpAvrgOn OBJECT-TYPE
   SYNTAX      Integer32
   UNITS       "msec"
   MAX-ACCESS  read-write
   STATUS      current
   DESCRIPTION
      "Path: router.editConf.qualityMonitor.destinations.delayAlarm.jitterUpAvrgOn

       unit name = msec"
   ::= {er1645v2PRoutQmDestEntry 118226944}

er1645v2PRoutQmDestDelayAlarmJitterUpAvrgOff OBJECT-TYPE
   SYNTAX      Integer32
   UNITS       "msec"
   MAX-ACCESS  read-write
   STATUS      current
   DESCRIPTION
      "Path: router.editConf.qualityMonitor.destinations.delayAlarm.jitterUpAvrgOff

       unit name = msec"
   ::= {er1645v2PRoutQmDestEntry 118292480}

er1645v2PRoutQmDestDelayAlarmJitterUpMaxOn OBJECT-TYPE
   SYNTAX      Integer32
   UNITS       "msec"
   MAX-ACCESS  read-write
   STATUS      current
   DESCRIPTION
      "Path: router.editConf.qualityMonitor.destinations.delayAlarm.jitterUpMaxOn

       unit name = msec"
   ::= {er1645v2PRoutQmDestEntry 118358016}

er1645v2PRoutQmDestDelayAlarmJitterUpMaxOff OBJECT-TYPE
   SYNTAX      Integer32
   UNITS       "msec"
   MAX-ACCESS  read-write
   STATUS      current
   DESCRIPTION
      "Path: router.editConf.qualityMonitor.destinations.delayAlarm.jitterUpMaxOff

       unit name = msec"
   ::= {er1645v2PRoutQmDestEntry 118423552}

er1645v2PRoutQmDestDelayAlarmJupsN OBJECT-TYPE
   SYNTAX      INTEGER
               {
               none (0)
               }
   MAX-ACCESS  read-write
   STATUS      current
   DESCRIPTION
      "Path: router.editConf.qualityMonitor.destinations.delayAlarm.jitterUpStat.none

       Possibilities:
               none   (0)"
   ::= {er1645v2PRoutQmDestEntry 119808000}

er1645v2PRoutQmDestDelayAlarmJupsNMn OBJECT-TYPE
   SYNTAX      Integer32
   UNITS       "msec"
   MAX-ACCESS  read-write
   STATUS      current
   DESCRIPTION
      "Path: router.editConf.qualityMonitor.destinations.delayAlarm.jitterUpStat.range.min

       unit name = msec"
   ::= {er1645v2PRoutQmDestEntry 119817216}

er1645v2PRoutQmDestDelayAlarmJupsNMx OBJECT-TYPE
   SYNTAX      Integer32
   UNITS       "msec"
   MAX-ACCESS  read-write
   STATUS      current
   DESCRIPTION
      "Path: router.editConf.qualityMonitor.destinations.delayAlarm.jitterUpStat.range.max

       unit name = msec"
   ::= {er1645v2PRoutQmDestEntry 119818240}

er1645v2PRoutQmDestDelayAlarmJupsTB1 OBJECT-TYPE
   SYNTAX      Integer32
   UNITS       "msec"
   MAX-ACCESS  read-write
   STATUS      current
   DESCRIPTION
      "Path: router.editConf.qualityMonitor.destinations.delayAlarm.jitterUpStat.table.bin1

       unit name = msec"
   ::= {er1645v2PRoutQmDestEntry 119824896}

er1645v2PRoutQmDestDelayAlarmJupsTB2 OBJECT-TYPE
   SYNTAX      Integer32
   UNITS       "msec"
   MAX-ACCESS  read-write
   STATUS      current
   DESCRIPTION
      "Path: router.editConf.qualityMonitor.destinations.delayAlarm.jitterUpStat.table.bin2

       unit name = msec"
   ::= {er1645v2PRoutQmDestEntry 119825408}

er1645v2PRoutQmDestDelayAlarmJupsTB3 OBJECT-TYPE
   SYNTAX      Integer32
   UNITS       "msec"
   MAX-ACCESS  read-write
   STATUS      current
   DESCRIPTION
      "Path: router.editConf.qualityMonitor.destinations.delayAlarm.jitterUpStat.table.bin3

       unit name = msec"
   ::= {er1645v2PRoutQmDestEntry 119825920}

er1645v2PRoutQmDestDelayAlarmJupsTB4 OBJECT-TYPE
   SYNTAX      Integer32
   UNITS       "msec"
   MAX-ACCESS  read-write
   STATUS      current
   DESCRIPTION
      "Path: router.editConf.qualityMonitor.destinations.delayAlarm.jitterUpStat.table.bin4

       unit name = msec"
   ::= {er1645v2PRoutQmDestEntry 119826432}

er1645v2PRoutQmDestDelayAlarmJupsTB5 OBJECT-TYPE
   SYNTAX      Integer32
   UNITS       "msec"
   MAX-ACCESS  read-write
   STATUS      current
   DESCRIPTION
      "Path: router.editConf.qualityMonitor.destinations.delayAlarm.jitterUpStat.table.bin5

       unit name = msec"
   ::= {er1645v2PRoutQmDestEntry 119826944}

er1645v2PRoutQmDestDelayAlarmJupsTB6 OBJECT-TYPE
   SYNTAX      Integer32
   UNITS       "msec"
   MAX-ACCESS  read-write
   STATUS      current
   DESCRIPTION
      "Path: router.editConf.qualityMonitor.destinations.delayAlarm.jitterUpStat.table.bin6

       unit name = msec"
   ::= {er1645v2PRoutQmDestEntry 119827456}

er1645v2PRoutQmDestDelayAlarmJupsTB7 OBJECT-TYPE
   SYNTAX      Integer32
   UNITS       "msec"
   MAX-ACCESS  read-write
   STATUS      current
   DESCRIPTION
      "Path: router.editConf.qualityMonitor.destinations.delayAlarm.jitterUpStat.table.bin7

       unit name = msec"
   ::= {er1645v2PRoutQmDestEntry 119827968}

er1645v2PRoutQmDestDelayAlarmJupsTB8 OBJECT-TYPE
   SYNTAX      Integer32
   UNITS       "msec"
   MAX-ACCESS  read-write
   STATUS      current
   DESCRIPTION
      "Path: router.editConf.qualityMonitor.destinations.delayAlarm.jitterUpStat.table.bin8

       unit name = msec"
   ::= {er1645v2PRoutQmDestEntry 119828480}

er1645v2PRoutQmDestDelayAlarmJupsTMx OBJECT-TYPE
   SYNTAX      Integer32
   UNITS       "msec"
   MAX-ACCESS  read-write
   STATUS      current
   DESCRIPTION
      "Path: router.editConf.qualityMonitor.destinations.delayAlarm.jitterUpStat.table.max

       unit name = msec"
   ::= {er1645v2PRoutQmDestEntry 119828992}

er1645v2PRoutQmDestDelayAlarmJitterDownAvrgOn OBJECT-TYPE
   SYNTAX      Integer32
   UNITS       "msec"
   MAX-ACCESS  read-write
   STATUS      current
   DESCRIPTION
      "Path: router.editConf.qualityMonitor.destinations.delayAlarm.jitterDownAvrgOn

       unit name = msec"
   ::= {er1645v2PRoutQmDestEntry 118489088}

er1645v2PRoutQmDestDelayAlarmJitterDownAvrgOff OBJECT-TYPE
   SYNTAX      Integer32
   UNITS       "msec"
   MAX-ACCESS  read-write
   STATUS      current
   DESCRIPTION
      "Path: router.editConf.qualityMonitor.destinations.delayAlarm.jitterDownAvrgOff

       unit name = msec"
   ::= {er1645v2PRoutQmDestEntry 118554624}

er1645v2PRoutQmDestDelayAlarmJitterDownMaxOn OBJECT-TYPE
   SYNTAX      Integer32
   UNITS       "msec"
   MAX-ACCESS  read-write
   STATUS      current
   DESCRIPTION
      "Path: router.editConf.qualityMonitor.destinations.delayAlarm.jitterDownMaxOn

       unit name = msec"
   ::= {er1645v2PRoutQmDestEntry 118620160}

er1645v2PRoutQmDestDelayAlarmJitterDownMaxOff OBJECT-TYPE
   SYNTAX      Integer32
   UNITS       "msec"
   MAX-ACCESS  read-write
   STATUS      current
   DESCRIPTION
      "Path: router.editConf.qualityMonitor.destinations.delayAlarm.jitterDownMaxOff

       unit name = msec"
   ::= {er1645v2PRoutQmDestEntry 118685696}

er1645v2PRoutQmDestDelayAlarmJdownsN OBJECT-TYPE
   SYNTAX      INTEGER
               {
               none (0)
               }
   MAX-ACCESS  read-write
   STATUS      current
   DESCRIPTION
      "Path: router.editConf.qualityMonitor.destinations.delayAlarm.jitterDownStat.none

       Possibilities:
               none   (0)"
   ::= {er1645v2PRoutQmDestEntry 119939072}

er1645v2PRoutQmDestDelayAlarmJdownsNMn OBJECT-TYPE
   SYNTAX      Integer32
   UNITS       "msec"
   MAX-ACCESS  read-write
   STATUS      current
   DESCRIPTION
      "Path: router.editConf.qualityMonitor.destinations.delayAlarm.jitterDownStat.range.min

       unit name = msec"
   ::= {er1645v2PRoutQmDestEntry 119948288}

er1645v2PRoutQmDestDelayAlarmJdownsNMx OBJECT-TYPE
   SYNTAX      Integer32
   UNITS       "msec"
   MAX-ACCESS  read-write
   STATUS      current
   DESCRIPTION
      "Path: router.editConf.qualityMonitor.destinations.delayAlarm.jitterDownStat.range.max

       unit name = msec"
   ::= {er1645v2PRoutQmDestEntry 119949312}

er1645v2PRoutQmDestDelayAlarmJdownsTB1 OBJECT-TYPE
   SYNTAX      Integer32
   UNITS       "msec"
   MAX-ACCESS  read-write
   STATUS      current
   DESCRIPTION
      "Path: router.editConf.qualityMonitor.destinations.delayAlarm.jitterDownStat.table.bin1

       unit name = msec"
   ::= {er1645v2PRoutQmDestEntry 119955968}

er1645v2PRoutQmDestDelayAlarmJdownsTB2 OBJECT-TYPE
   SYNTAX      Integer32
   UNITS       "msec"
   MAX-ACCESS  read-write
   STATUS      current
   DESCRIPTION
      "Path: router.editConf.qualityMonitor.destinations.delayAlarm.jitterDownStat.table.bin2

       unit name = msec"
   ::= {er1645v2PRoutQmDestEntry 119956480}

er1645v2PRoutQmDestDelayAlarmJdownsTB3 OBJECT-TYPE
   SYNTAX      Integer32
   UNITS       "msec"
   MAX-ACCESS  read-write
   STATUS      current
   DESCRIPTION
      "Path: router.editConf.qualityMonitor.destinations.delayAlarm.jitterDownStat.table.bin3

       unit name = msec"
   ::= {er1645v2PRoutQmDestEntry 119956992}

er1645v2PRoutQmDestDelayAlarmJdownsTB4 OBJECT-TYPE
   SYNTAX      Integer32
   UNITS       "msec"
   MAX-ACCESS  read-write
   STATUS      current
   DESCRIPTION
      "Path: router.editConf.qualityMonitor.destinations.delayAlarm.jitterDownStat.table.bin4

       unit name = msec"
   ::= {er1645v2PRoutQmDestEntry 119957504}

er1645v2PRoutQmDestDelayAlarmJdownsTB5 OBJECT-TYPE
   SYNTAX      Integer32
   UNITS       "msec"
   MAX-ACCESS  read-write
   STATUS      current
   DESCRIPTION
      "Path: router.editConf.qualityMonitor.destinations.delayAlarm.jitterDownStat.table.bin5

       unit name = msec"
   ::= {er1645v2PRoutQmDestEntry 119958016}

er1645v2PRoutQmDestDelayAlarmJdownsTB6 OBJECT-TYPE
   SYNTAX      Integer32
   UNITS       "msec"
   MAX-ACCESS  read-write
   STATUS      current
   DESCRIPTION
      "Path: router.editConf.qualityMonitor.destinations.delayAlarm.jitterDownStat.table.bin6

       unit name = msec"
   ::= {er1645v2PRoutQmDestEntry 119958528}

er1645v2PRoutQmDestDelayAlarmJdownsTB7 OBJECT-TYPE
   SYNTAX      Integer32
   UNITS       "msec"
   MAX-ACCESS  read-write
   STATUS      current
   DESCRIPTION
      "Path: router.editConf.qualityMonitor.destinations.delayAlarm.jitterDownStat.table.bin7

       unit name = msec"
   ::= {er1645v2PRoutQmDestEntry 119959040}

er1645v2PRoutQmDestDelayAlarmJdownsTB8 OBJECT-TYPE
   SYNTAX      Integer32
   UNITS       "msec"
   MAX-ACCESS  read-write
   STATUS      current
   DESCRIPTION
      "Path: router.editConf.qualityMonitor.destinations.delayAlarm.jitterDownStat.table.bin8

       unit name = msec"
   ::= {er1645v2PRoutQmDestEntry 119959552}

er1645v2PRoutQmDestDelayAlarmJdownsTMx OBJECT-TYPE
   SYNTAX      Integer32
   UNITS       "msec"
   MAX-ACCESS  read-write
   STATUS      current
   DESCRIPTION
      "Path: router.editConf.qualityMonitor.destinations.delayAlarm.jitterDownStat.table.max

       unit name = msec"
   ::= {er1645v2PRoutQmDestEntry 119960064}

er1645v2PRoutQmDestDelayAlarmDelayUpAvrgOn OBJECT-TYPE
   SYNTAX      Integer32
   UNITS       "msec"
   MAX-ACCESS  read-write
   STATUS      current
   DESCRIPTION
      "Path: router.editConf.qualityMonitor.destinations.delayAlarm.delayUpAvrgOn

       unit name = msec"
   ::= {er1645v2PRoutQmDestEntry 118751232}

er1645v2PRoutQmDestDelayAlarmDelayUpAvrgOff OBJECT-TYPE
   SYNTAX      Integer32
   UNITS       "msec"
   MAX-ACCESS  read-write
   STATUS      current
   DESCRIPTION
      "Path: router.editConf.qualityMonitor.destinations.delayAlarm.delayUpAvrgOff

       unit name = msec"
   ::= {er1645v2PRoutQmDestEntry 118816768}

er1645v2PRoutQmDestDelayAlarmDelayUpMaxOn OBJECT-TYPE
   SYNTAX      Integer32
   UNITS       "msec"
   MAX-ACCESS  read-write
   STATUS      current
   DESCRIPTION
      "Path: router.editConf.qualityMonitor.destinations.delayAlarm.delayUpMaxOn

       unit name = msec"
   ::= {er1645v2PRoutQmDestEntry 118882304}

er1645v2PRoutQmDestDelayAlarmDelayUpMaxOff OBJECT-TYPE
   SYNTAX      Integer32
   UNITS       "msec"
   MAX-ACCESS  read-write
   STATUS      current
   DESCRIPTION
      "Path: router.editConf.qualityMonitor.destinations.delayAlarm.delayUpMaxOff

       unit name = msec"
   ::= {er1645v2PRoutQmDestEntry 118947840}

er1645v2PRoutQmDestDelayAlarmDupsType OBJECT-TYPE
   SYNTAX      INTEGER
               {
               fd (1),
               fdr (2)
               }
   MAX-ACCESS  read-write
   STATUS      current
   DESCRIPTION
      "Path: router.editConf.qualityMonitor.destinations.delayAlarm.delayUpStat.type

       Possibilities:
               fd   (1)
               fdr   (2)"
   ::= {er1645v2PRoutQmDestEntry 119414784}

er1645v2PRoutQmDestDelayAlarmDupsBinsN OBJECT-TYPE
   SYNTAX      INTEGER
               {
               none (0)
               }
   MAX-ACCESS  read-write
   STATUS      current
   DESCRIPTION
      "Path: router.editConf.qualityMonitor.destinations.delayAlarm.delayUpStat.bins.none

       Possibilities:
               none   (0)"
   ::= {er1645v2PRoutQmDestEntry 119424000}

er1645v2PRoutQmDestDelayAlarmDupsBinsNMn OBJECT-TYPE
   SYNTAX      Integer32
   UNITS       "msec"
   MAX-ACCESS  read-write
   STATUS      current
   DESCRIPTION
      "Path: router.editConf.qualityMonitor.destinations.delayAlarm.delayUpStat.bins.range.min

       unit name = msec"
   ::= {er1645v2PRoutQmDestEntry 119425152}

er1645v2PRoutQmDestDelayAlarmDupsBinsNMx OBJECT-TYPE
   SYNTAX      Integer32
   UNITS       "msec"
   MAX-ACCESS  read-write
   STATUS      current
   DESCRIPTION
      "Path: router.editConf.qualityMonitor.destinations.delayAlarm.delayUpStat.bins.range.max

       unit name = msec"
   ::= {er1645v2PRoutQmDestEntry 119425280}

er1645v2PRoutQmDestDelayAlarmDupsBinsTB1 OBJECT-TYPE
   SYNTAX      Integer32
   UNITS       "msec"
   MAX-ACCESS  read-write
   STATUS      current
   DESCRIPTION
      "Path: router.editConf.qualityMonitor.destinations.delayAlarm.delayUpStat.bins.table.bin1

       unit name = msec"
   ::= {er1645v2PRoutQmDestEntry 119426112}

er1645v2PRoutQmDestDelayAlarmDupsBinsTB2 OBJECT-TYPE
   SYNTAX      Integer32
   UNITS       "msec"
   MAX-ACCESS  read-write
   STATUS      current
   DESCRIPTION
      "Path: router.editConf.qualityMonitor.destinations.delayAlarm.delayUpStat.bins.table.bin2

       unit name = msec"
   ::= {er1645v2PRoutQmDestEntry 119426176}

er1645v2PRoutQmDestDelayAlarmDupsBinsTB3 OBJECT-TYPE
   SYNTAX      Integer32
   UNITS       "msec"
   MAX-ACCESS  read-write
   STATUS      current
   DESCRIPTION
      "Path: router.editConf.qualityMonitor.destinations.delayAlarm.delayUpStat.bins.table.bin3

       unit name = msec"
   ::= {er1645v2PRoutQmDestEntry 119426240}

er1645v2PRoutQmDestDelayAlarmDupsBinsTB4 OBJECT-TYPE
   SYNTAX      Integer32
   UNITS       "msec"
   MAX-ACCESS  read-write
   STATUS      current
   DESCRIPTION
      "Path: router.editConf.qualityMonitor.destinations.delayAlarm.delayUpStat.bins.table.bin4

       unit name = msec"
   ::= {er1645v2PRoutQmDestEntry 119426304}

er1645v2PRoutQmDestDelayAlarmDupsBinsTB5 OBJECT-TYPE
   SYNTAX      Integer32
   UNITS       "msec"
   MAX-ACCESS  read-write
   STATUS      current
   DESCRIPTION
      "Path: router.editConf.qualityMonitor.destinations.delayAlarm.delayUpStat.bins.table.bin5

       unit name = msec"
   ::= {er1645v2PRoutQmDestEntry 119426368}

er1645v2PRoutQmDestDelayAlarmDupsBinsTB6 OBJECT-TYPE
   SYNTAX      Integer32
   UNITS       "msec"
   MAX-ACCESS  read-write
   STATUS      current
   DESCRIPTION
      "Path: router.editConf.qualityMonitor.destinations.delayAlarm.delayUpStat.bins.table.bin6

       unit name = msec"
   ::= {er1645v2PRoutQmDestEntry 119426432}

er1645v2PRoutQmDestDelayAlarmDupsBinsTB7 OBJECT-TYPE
   SYNTAX      Integer32
   UNITS       "msec"
   MAX-ACCESS  read-write
   STATUS      current
   DESCRIPTION
      "Path: router.editConf.qualityMonitor.destinations.delayAlarm.delayUpStat.bins.table.bin7

       unit name = msec"
   ::= {er1645v2PRoutQmDestEntry 119426496}

er1645v2PRoutQmDestDelayAlarmDupsBinsTB8 OBJECT-TYPE
   SYNTAX      Integer32
   UNITS       "msec"
   MAX-ACCESS  read-write
   STATUS      current
   DESCRIPTION
      "Path: router.editConf.qualityMonitor.destinations.delayAlarm.delayUpStat.bins.table.bin8

       unit name = msec"
   ::= {er1645v2PRoutQmDestEntry 119426560}

er1645v2PRoutQmDestDelayAlarmDupsBinsTMx OBJECT-TYPE
   SYNTAX      Integer32
   UNITS       "msec"
   MAX-ACCESS  read-write
   STATUS      current
   DESCRIPTION
      "Path: router.editConf.qualityMonitor.destinations.delayAlarm.delayUpStat.bins.table.max

       unit name = msec"
   ::= {er1645v2PRoutQmDestEntry 119426624}

er1645v2PRoutQmDestDelayAlarmDelayDownAvrgOn OBJECT-TYPE
   SYNTAX      Integer32
   UNITS       "msec"
   MAX-ACCESS  read-write
   STATUS      current
   DESCRIPTION
      "Path: router.editConf.qualityMonitor.destinations.delayAlarm.delayDownAvrgOn

       unit name = msec"
   ::= {er1645v2PRoutQmDestEntry 119013376}

er1645v2PRoutQmDestDelayAlarmDelayDownAvrgOff OBJECT-TYPE
   SYNTAX      Integer32
   UNITS       "msec"
   MAX-ACCESS  read-write
   STATUS      current
   DESCRIPTION
      "Path: router.editConf.qualityMonitor.destinations.delayAlarm.delayDownAvrgOff

       unit name = msec"
   ::= {er1645v2PRoutQmDestEntry 119078912}

er1645v2PRoutQmDestDelayAlarmDelayDownMaxOn OBJECT-TYPE
   SYNTAX      Integer32
   UNITS       "msec"
   MAX-ACCESS  read-write
   STATUS      current
   DESCRIPTION
      "Path: router.editConf.qualityMonitor.destinations.delayAlarm.delayDownMaxOn

       unit name = msec"
   ::= {er1645v2PRoutQmDestEntry 119144448}

er1645v2PRoutQmDestDelayAlarmDelayDownMaxOff OBJECT-TYPE
   SYNTAX      Integer32
   UNITS       "msec"
   MAX-ACCESS  read-write
   STATUS      current
   DESCRIPTION
      "Path: router.editConf.qualityMonitor.destinations.delayAlarm.delayDownMaxOff

       unit name = msec"
   ::= {er1645v2PRoutQmDestEntry 119209984}

er1645v2PRoutQmDestDelayAlarmDdownsType OBJECT-TYPE
   SYNTAX      INTEGER
               {
               fd (1),
               fdr (2)
               }
   MAX-ACCESS  read-write
   STATUS      current
   DESCRIPTION
      "Path: router.editConf.qualityMonitor.destinations.delayAlarm.delayDownStat.type

       Possibilities:
               fd   (1)
               fdr   (2)"
   ::= {er1645v2PRoutQmDestEntry 119545856}

er1645v2PRoutQmDestDelayAlarmDdownsBinsN OBJECT-TYPE
   SYNTAX      INTEGER
               {
               none (0)
               }
   MAX-ACCESS  read-write
   STATUS      current
   DESCRIPTION
      "Path: router.editConf.qualityMonitor.destinations.delayAlarm.delayDownStat.bins.none

       Possibilities:
               none   (0)"
   ::= {er1645v2PRoutQmDestEntry 119555072}

er1645v2PRoutQmDestDelayAlarmDdownsBinsNMn OBJECT-TYPE
   SYNTAX      Integer32
   UNITS       "msec"
   MAX-ACCESS  read-write
   STATUS      current
   DESCRIPTION
      "Path: router.editConf.qualityMonitor.destinations.delayAlarm.delayDownStat.bins.range.min

       unit name = msec"
   ::= {er1645v2PRoutQmDestEntry 119556224}

er1645v2PRoutQmDestDelayAlarmDdownsBinsNMx OBJECT-TYPE
   SYNTAX      Integer32
   UNITS       "msec"
   MAX-ACCESS  read-write
   STATUS      current
   DESCRIPTION
      "Path: router.editConf.qualityMonitor.destinations.delayAlarm.delayDownStat.bins.range.max

       unit name = msec"
   ::= {er1645v2PRoutQmDestEntry 119556352}

er1645v2PRoutQmDestDelayAlarmDdownsBinsTB1 OBJECT-TYPE
   SYNTAX      Integer32
   UNITS       "msec"
   MAX-ACCESS  read-write
   STATUS      current
   DESCRIPTION
      "Path: router.editConf.qualityMonitor.destinations.delayAlarm.delayDownStat.bins.table.bin1

       unit name = msec"
   ::= {er1645v2PRoutQmDestEntry 119557184}

er1645v2PRoutQmDestDelayAlarmDdownsBinsTB2 OBJECT-TYPE
   SYNTAX      Integer32
   UNITS       "msec"
   MAX-ACCESS  read-write
   STATUS      current
   DESCRIPTION
      "Path: router.editConf.qualityMonitor.destinations.delayAlarm.delayDownStat.bins.table.bin2

       unit name = msec"
   ::= {er1645v2PRoutQmDestEntry 119557248}

er1645v2PRoutQmDestDelayAlarmDdownsBinsTB3 OBJECT-TYPE
   SYNTAX      Integer32
   UNITS       "msec"
   MAX-ACCESS  read-write
   STATUS      current
   DESCRIPTION
      "Path: router.editConf.qualityMonitor.destinations.delayAlarm.delayDownStat.bins.table.bin3

       unit name = msec"
   ::= {er1645v2PRoutQmDestEntry 119557312}

er1645v2PRoutQmDestDelayAlarmDdownsBinsTB4 OBJECT-TYPE
   SYNTAX      Integer32
   UNITS       "msec"
   MAX-ACCESS  read-write
   STATUS      current
   DESCRIPTION
      "Path: router.editConf.qualityMonitor.destinations.delayAlarm.delayDownStat.bins.table.bin4

       unit name = msec"
   ::= {er1645v2PRoutQmDestEntry 119557376}

er1645v2PRoutQmDestDelayAlarmDdownsBinsTB5 OBJECT-TYPE
   SYNTAX      Integer32
   UNITS       "msec"
   MAX-ACCESS  read-write
   STATUS      current
   DESCRIPTION
      "Path: router.editConf.qualityMonitor.destinations.delayAlarm.delayDownStat.bins.table.bin5

       unit name = msec"
   ::= {er1645v2PRoutQmDestEntry 119557440}

er1645v2PRoutQmDestDelayAlarmDdownsBinsTB6 OBJECT-TYPE
   SYNTAX      Integer32
   UNITS       "msec"
   MAX-ACCESS  read-write
   STATUS      current
   DESCRIPTION
      "Path: router.editConf.qualityMonitor.destinations.delayAlarm.delayDownStat.bins.table.bin6

       unit name = msec"
   ::= {er1645v2PRoutQmDestEntry 119557504}

er1645v2PRoutQmDestDelayAlarmDdownsBinsTB7 OBJECT-TYPE
   SYNTAX      Integer32
   UNITS       "msec"
   MAX-ACCESS  read-write
   STATUS      current
   DESCRIPTION
      "Path: router.editConf.qualityMonitor.destinations.delayAlarm.delayDownStat.bins.table.bin7

       unit name = msec"
   ::= {er1645v2PRoutQmDestEntry 119557568}

er1645v2PRoutQmDestDelayAlarmDdownsBinsTB8 OBJECT-TYPE
   SYNTAX      Integer32
   UNITS       "msec"
   MAX-ACCESS  read-write
   STATUS      current
   DESCRIPTION
      "Path: router.editConf.qualityMonitor.destinations.delayAlarm.delayDownStat.bins.table.bin8

       unit name = msec"
   ::= {er1645v2PRoutQmDestEntry 119557632}

er1645v2PRoutQmDestDelayAlarmDdownsBinsTMx OBJECT-TYPE
   SYNTAX      Integer32
   UNITS       "msec"
   MAX-ACCESS  read-write
   STATUS      current
   DESCRIPTION
      "Path: router.editConf.qualityMonitor.destinations.delayAlarm.delayDownStat.bins.table.max

       unit name = msec"
   ::= {er1645v2PRoutQmDestEntry 119557696}

er1645v2PRoutQmDestAlarmMask OBJECT-TYPE
   SYNTAX      Integer32
   MAX-ACCESS  read-write
   STATUS      current
   DESCRIPTION
      "Path: router.editConf.qualityMonitor.destinations.alarmMask

       Bit meanings:
               bit 0 = loss,
               bit 1 = delayAvrg,
               bit 2 = delayMax,
               bit 3 = delayMinMax,
               bit 4 = jitterAvrg,
               bit 5 = jitterPosMax,
               bit 6 = jitterNegMax,
               bit 7 = lossUp,
               bit 8 = jitterUpAvrg,
               bit 9 = jitterUpPosMax,
               bit 10 = jitterUpNegMax,
               bit 11 = lossDown,
               bit 12 = jitterDownAvrg,
               bit 13 = jitterDownPosMax,
               bit 14 = jitterDownNegMax,
               bit 15 = delayUpAvrg,
               bit 16 = delayUpMax,
               bit 17 = delayDownAvrg,
               bit 18 = delayDownMax,
               bit 19 = bfdCtrl"
   ::= {er1645v2PRoutQmDestEntry 251658240}

er1645v2PRoutQmDestLogging OBJECT-TYPE
   SYNTAX      INTEGER
               {
               disabled (0),
               s3min (3),
               s5min (5),
               s10min (10),
               s15min (15),
               s30min (30),
               s60min (60)
               }
   MAX-ACCESS  read-write
   STATUS      current
   DESCRIPTION
      "Path: router.editConf.qualityMonitor.destinations.logging

       Possibilities:
               disabled   (0)
               3min   (3)
               5min   (5)
               10min   (10)
               15min   (15)
               30min   (30)
               60min   (60)"
   ::= {er1645v2PRoutQmDestEntry 201326592}

er1645v2PRoutQmDestLoggingDepth OBJECT-TYPE
   SYNTAX      INTEGER
               {
               s2 (2),
               s4 (4),
               s8 (8),
               s16 (16),
               s32 (32),
               s128 (128),
               s512 (512),
               s1024 (1024)
               }
   MAX-ACCESS  read-write
   STATUS      current
   DESCRIPTION
      "Path: router.editConf.qualityMonitor.destinations.loggingDepth

       Possibilities:
               2   (2)
               4   (4)
               8   (8)
               16   (16)
               32   (32)
               128   (128)
               512   (512)
               1024   (1024)"
   ::= {er1645v2PRoutQmDestEntry 503316480}

er1645v2PRoutQmUdpServerPort OBJECT-TYPE
   SYNTAX      SEQUENCE OF Er1645v2PRoutQmUdpServerPortEntry
   MAX-ACCESS  not-accessible
   STATUS      current
   DESCRIPTION
      ""
   ::= {er1645v2PRoutQm 67108864}

er1645v2PRoutQmUdpServerPortEntry OBJECT-TYPE
   SYNTAX      Er1645v2PRoutQmUdpServerPortEntry
   MAX-ACCESS  not-accessible
   STATUS      current
   DESCRIPTION
      ""
   INDEX      { er1645v2PRoutQmUdpServerPortTableIx }
   ::= {er1645v2PRoutQmUdpServerPort 1}

Er1645v2PRoutQmUdpServerPortEntry ::=
   SEQUENCE
      {
      er1645v2PRoutQmUdpServerPortActions
         VariableLengthTableActions,
      er1645v2PRoutQmUdpServerPortTableIx
         TableIndex,
      er1645v2PRoutQmUdpServerPortDestinationPort
         Integer32,
      er1645v2PRoutQmUdpServerPortService
         INTEGER,
      er1645v2PRoutQmUdpServerPortPriority
         INTEGER,
      er1645v2PRoutQmUdpServerPortTos
         INTEGER
      }

er1645v2PRoutQmUdpServerPortActions OBJECT-TYPE
   SYNTAX      VariableLengthTableActions
   MAX-ACCESS  read-write
   STATUS      current
   DESCRIPTION
      "By way of this field, some manipulations
       on this table may be performed."
   ::= {er1645v2PRoutQmUdpServerPortEntry 2}

er1645v2PRoutQmUdpServerPortTableIx OBJECT-TYPE
   SYNTAX      TableIndex
   MAX-ACCESS  not-accessible
   STATUS      current
   DESCRIPTION
      ""
   ::= {er1645v2PRoutQmUdpServerPortEntry 11}

er1645v2PRoutQmUdpServerPortDestinationPort OBJECT-TYPE
   SYNTAX      Integer32
   MAX-ACCESS  read-write
   STATUS      current
   DESCRIPTION
      "Path: router.editConf.qualityMonitor.udpServerPort.destinationPort"
   ::= {er1645v2PRoutQmUdpServerPortEntry 16777216}

er1645v2PRoutQmUdpServerPortService OBJECT-TYPE
   SYNTAX      INTEGER
               {
               proprietary (1),
               twampLight (2)
               }
   MAX-ACCESS  read-write
   STATUS      current
   DESCRIPTION
      "Path: router.editConf.qualityMonitor.udpServerPort.service

       Possibilities:
               proprietary   (1)
               twampLight   (2)"
   ::= {er1645v2PRoutQmUdpServerPortEntry 234881024}

er1645v2PRoutQmUdpServerPortPriority OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: router.editConf.qualityMonitor.udpServerPort.priority

       Possibilities:
               queue1   (0)
               queue2   (1)
               queue3   (2)
               queue4   (3)
               queue5   (4)
               lowDelayQueue   (5)
               lowDelay2Queue   (6)
               systemQueue   (7)"
   ::= {er1645v2PRoutQmUdpServerPortEntry 218103808}

er1645v2PRoutQmUdpServerPortTos OBJECT-TYPE
   SYNTAX      INTEGER
               {
               keepTos (-1),
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: router.editConf.qualityMonitor.udpServerPort.tos

       Possibilities:
               keepTos   (-1)
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2PRoutQmUdpServerPortEntry 167772160}


er1645v2PRoutHosts OBJECT IDENTIFIER ::= {er1645v2PRout 49}

er1645v2PRoutHostsSSCTable OBJECT-TYPE
   SYNTAX      SEQUENCE OF Er1645v2PRoutHostsEntry
   MAX-ACCESS  not-accessible
   STATUS      current
   DESCRIPTION
      "table of hosts with their ip address"
   ::= {er1645v2PRoutHosts 1}

er1645v2PRoutHostsEntry OBJECT-TYPE
   SYNTAX      Er1645v2PRoutHostsEntry
   MAX-ACCESS  not-accessible
   STATUS      current
   DESCRIPTION
      ""
   INDEX      { er1645v2PRoutHostsTableIx }
   ::= {er1645v2PRoutHostsSSCTable 1}

Er1645v2PRoutHostsEntry ::=
   SEQUENCE
      {
      er1645v2PRoutHostsActions
         VariableLengthTableActions,
      er1645v2PRoutHostsTableIx
         TableIndex,
      er1645v2PRoutHostsHostname
         DisplayString,
      er1645v2PRoutHostsIpAddress
         IpAddress
      }

er1645v2PRoutHostsActions OBJECT-TYPE
   SYNTAX      VariableLengthTableActions
   MAX-ACCESS  read-write
   STATUS      current
   DESCRIPTION
      "By way of this field, some manipulations
       on this table may be performed."
   ::= {er1645v2PRoutHostsEntry 2}

er1645v2PRoutHostsTableIx OBJECT-TYPE
   SYNTAX      TableIndex
   MAX-ACCESS  not-accessible
   STATUS      current
   DESCRIPTION
      ""
   ::= {er1645v2PRoutHostsEntry 11}

er1645v2PRoutHostsHostname OBJECT-TYPE
   SYNTAX      DisplayString
   MAX-ACCESS  read-write
   STATUS      current
   DESCRIPTION
      "Path: router.editConf.hosts.hostname"
   ::= {er1645v2PRoutHostsEntry 16777216}

er1645v2PRoutHostsIpAddress OBJECT-TYPE
   SYNTAX      IpAddress
   MAX-ACCESS  read-write
   STATUS      current
   DESCRIPTION
      "Path: router.editConf.hosts.ipAddress"
   ::= {er1645v2PRoutHostsEntry 33554432}


er1645v2PRoutDefaultRoute OBJECT IDENTIFIER ::= {er1645v2PRout 13}

er1645v2PRoutDefaultRouteSSC OBJECT IDENTIFIER ::= {er1645v2PRoutDefaultRoute 1}

er1645v2PRoutDefaultRouteEntry OBJECT IDENTIFIER ::= {er1645v2PRoutDefaultRouteSSC 1}

er1645v2PRoutDefaultRouteGateway OBJECT-TYPE
   SYNTAX      IpAddress
   MAX-ACCESS  read-write
   STATUS      current
   DESCRIPTION
      "Path: router.editConf.defaultRoute.gateway"
   ::= {er1645v2PRoutDefaultRouteEntry 16777216}

er1645v2PRoutDefaultRouteInterface OBJECT-TYPE
   SYNTAX      DisplayString
   MAX-ACCESS  read-write
   STATUS      current
   DESCRIPTION
      "Path: router.editConf.defaultRoute.interface"
   ::= {er1645v2PRoutDefaultRouteEntry 33554432}

er1645v2PRoutDefaultRoutePreference OBJECT-TYPE
   SYNTAX      Integer32
   MAX-ACCESS  read-write
   STATUS      current
   DESCRIPTION
      "Path: router.editConf.defaultRoute.preference"
   ::= {er1645v2PRoutDefaultRouteEntry 50331648}

er1645v2PRoutDefaultRouteMetric OBJECT-TYPE
   SYNTAX      Integer32
   MAX-ACCESS  read-write
   STATUS      current
   DESCRIPTION
      "Path: router.editConf.defaultRoute.metric"
   ::= {er1645v2PRoutDefaultRouteEntry 67108864}


er1645v2PRoutRoutingTable OBJECT IDENTIFIER ::= {er1645v2PRout 14}

er1645v2PRoutRoutingTableSSCTable OBJECT-TYPE
   SYNTAX      SEQUENCE OF Er1645v2PRoutRoutingTableEntry
   MAX-ACCESS  not-accessible
   STATUS      current
   DESCRIPTION
      "routingTable"
   ::= {er1645v2PRoutRoutingTable 1}

er1645v2PRoutRoutingTableEntry OBJECT-TYPE
   SYNTAX      Er1645v2PRoutRoutingTableEntry
   MAX-ACCESS  not-accessible
   STATUS      current
   DESCRIPTION
      ""
   INDEX      { er1645v2PRoutRoutingTableTableIx }
   ::= {er1645v2PRoutRoutingTableSSCTable 1}

Er1645v2PRoutRoutingTableEntry ::=
   SEQUENCE
      {
      er1645v2PRoutRoutingTableActions
         VariableLengthTableActions,
      er1645v2PRoutRoutingTableTableIx
         TableIndex,
      er1645v2PRoutRoutingTableRemark
         DisplayString,
      er1645v2PRoutRoutingTableNetwork
         IpAddress,
      er1645v2PRoutRoutingTableMask
         IpAddress,
      er1645v2PRoutRoutingTableGateway
         IpAddress,
      er1645v2PRoutRoutingTableIf
         DisplayString,
      er1645v2PRoutRoutingTablePref
         Integer32,
      er1645v2PRoutRoutingTableMetric
         Integer32,
      er1645v2PRoutRoutingTableProxyArp
         INTEGER,
      er1645v2PRoutRoutingTableTimeWindow
         DisplayString,
      er1645v2PRoutRoutingTablePermanent
         INTEGER,
      er1645v2PRoutRoutingTableTrack
         INTEGER,
      er1645v2PRoutRoutingTableTag
         DisplayString
      }

er1645v2PRoutRoutingTableActions OBJECT-TYPE
   SYNTAX      VariableLengthTableActions
   MAX-ACCESS  read-write
   STATUS      current
   DESCRIPTION
      "By way of this field, some manipulations
       on this table may be performed."
   ::= {er1645v2PRoutRoutingTableEntry 2}

er1645v2PRoutRoutingTableTableIx OBJECT-TYPE
   SYNTAX      TableIndex
   MAX-ACCESS  not-accessible
   STATUS      current
   DESCRIPTION
      ""
   ::= {er1645v2PRoutRoutingTableEntry 11}

er1645v2PRoutRoutingTableRemark OBJECT-TYPE
   SYNTAX      DisplayString
   MAX-ACCESS  read-write
   STATUS      current
   DESCRIPTION
      "Path: router.editConf.routingTable.remark"
   ::= {er1645v2PRoutRoutingTableEntry 117440512}

er1645v2PRoutRoutingTableNetwork OBJECT-TYPE
   SYNTAX      IpAddress
   MAX-ACCESS  read-write
   STATUS      current
   DESCRIPTION
      "Path: router.editConf.routingTable.network"
   ::= {er1645v2PRoutRoutingTableEntry 16777216}

er1645v2PRoutRoutingTableMask OBJECT-TYPE
   SYNTAX      IpAddress
   MAX-ACCESS  read-write
   STATUS      current
   DESCRIPTION
      "Path: router.editConf.routingTable.mask"
   ::= {er1645v2PRoutRoutingTableEntry 33554432}

er1645v2PRoutRoutingTableGateway OBJECT-TYPE
   SYNTAX      IpAddress
   MAX-ACCESS  read-write
   STATUS      current
   DESCRIPTION
      "Path: router.editConf.routingTable.gateway"
   ::= {er1645v2PRoutRoutingTableEntry 50331648}

er1645v2PRoutRoutingTableIf OBJECT-TYPE
   SYNTAX      DisplayString
   MAX-ACCESS  read-write
   STATUS      current
   DESCRIPTION
      "Path: router.editConf.routingTable.interface"
   ::= {er1645v2PRoutRoutingTableEntry 67108864}

er1645v2PRoutRoutingTablePref OBJECT-TYPE
   SYNTAX      Integer32
   MAX-ACCESS  read-write
   STATUS      current
   DESCRIPTION
      "Path: router.editConf.routingTable.preference"
   ::= {er1645v2PRoutRoutingTableEntry 83886080}

er1645v2PRoutRoutingTableMetric OBJECT-TYPE
   SYNTAX      Integer32
   MAX-ACCESS  read-write
   STATUS      current
   DESCRIPTION
      "Path: router.editConf.routingTable.metric"
   ::= {er1645v2PRoutRoutingTableEntry 100663296}

er1645v2PRoutRoutingTableProxyArp OBJECT-TYPE
   SYNTAX      INTEGER
               {
               disabled (0),
               enabled (1)
               }
   MAX-ACCESS  read-write
   STATUS      current
   DESCRIPTION
      "Path: router.editConf.routingTable.proxyArp

       Possibilities:
               disabled   (0)
               enabled   (1)"
   ::= {er1645v2PRoutRoutingTableEntry 134217728}

er1645v2PRoutRoutingTableTimeWindow OBJECT-TYPE
   SYNTAX      DisplayString
   MAX-ACCESS  read-write
   STATUS      current
   DESCRIPTION
      "Path: router.editConf.routingTable.timeWindow"
   ::= {er1645v2PRoutRoutingTableEntry 150994944}

er1645v2PRoutRoutingTablePermanent OBJECT-TYPE
   SYNTAX      INTEGER
               {
               disabled (0),
               enabled (1)
               }
   MAX-ACCESS  read-write
   STATUS      current
   DESCRIPTION
      "Path: router.editConf.routingTable.permanent

       Possibilities:
               disabled   (0)
               enabled   (1)"
   ::= {er1645v2PRoutRoutingTableEntry 184549376}

er1645v2PRoutRoutingTableTrack OBJECT-TYPE
   SYNTAX      INTEGER
               {
               disabled (0)
               }
   MAX-ACCESS  read-write
   STATUS      current
   DESCRIPTION
      "Path: router.editConf.routingTable.track

       Possibilities:
               disabled   (0)"
   ::= {er1645v2PRoutRoutingTableEntry 167772160}

er1645v2PRoutRoutingTableTag OBJECT-TYPE
   SYNTAX      DisplayString
   MAX-ACCESS  read-write
   STATUS      current
   DESCRIPTION
      "Path: router.editConf.routingTable.tag"
   ::= {er1645v2PRoutRoutingTableEntry 201326592}


er1645v2PRoutHelperProtocols OBJECT IDENTIFIER ::= {er1645v2PRout 15}

er1645v2PRoutHelperProtocolsSSCTable OBJECT-TYPE
   SYNTAX      SEQUENCE OF Er1645v2PRoutHelperProtocolsEntry
   MAX-ACCESS  not-accessible
   STATUS      current
   DESCRIPTION
      "list of protocols to be forwarded by the IP helpers"
   ::= {er1645v2PRoutHelperProtocols 1}

er1645v2PRoutHelperProtocolsEntry OBJECT-TYPE
   SYNTAX      Er1645v2PRoutHelperProtocolsEntry
   MAX-ACCESS  not-accessible
   STATUS      current
   DESCRIPTION
      ""
   INDEX      { er1645v2PRoutHelperProtocolsTableIx }
   ::= {er1645v2PRoutHelperProtocolsSSCTable 1}

Er1645v2PRoutHelperProtocolsEntry ::=
   SEQUENCE
      {
      er1645v2PRoutHelperProtocolsActions
         VariableLengthTableActions,
      er1645v2PRoutHelperProtocolsTableIx
         TableIndex,
      er1645v2PRoutHelperProtocolsType
         Integer32
      }

er1645v2PRoutHelperProtocolsActions OBJECT-TYPE
   SYNTAX      VariableLengthTableActions
   MAX-ACCESS  read-write
   STATUS      current
   DESCRIPTION
      "By way of this field, some manipulations
       on this table may be performed."
   ::= {er1645v2PRoutHelperProtocolsEntry 2}

er1645v2PRoutHelperProtocolsTableIx OBJECT-TYPE
   SYNTAX      TableIndex
   MAX-ACCESS  not-accessible
   STATUS      current
   DESCRIPTION
      ""
   ::= {er1645v2PRoutHelperProtocolsEntry 11}

er1645v2PRoutHelperProtocolsType OBJECT-TYPE
   SYNTAX      Integer32
   MAX-ACCESS  read-write
   STATUS      current
   DESCRIPTION
      "Path: router.editConf.helperProtocols.protocol"
   ::= {er1645v2PRoutHelperProtocolsEntry 16777216}


er1645v2PRoutSendTtlExceeded OBJECT-TYPE
   SYNTAX      INTEGER
               {
               disabled (0),
               enabled (1)
               }
   MAX-ACCESS  read-write
   STATUS      current
   DESCRIPTION
      "Path: router.editConf.sendTtlExceeded
       Info: indicates if a ICMP TTL exceeded must be returned to a packet's spurce if the TTL reaches 0 

       Possibilities:
               disabled   (0)
               enabled   (1)"
   ::= {er1645v2PRout 30}


er1645v2PRoutRoutingProtocol OBJECT-TYPE
   SYNTAX      INTEGER
               {
               none (0),
               rip2 (1)
               }
   MAX-ACCESS  read-write
   STATUS      current
   DESCRIPTION
      "Path: router.editConf.routingProtocol
       Info: indicates which dynamic routing protocol should be used

       Possibilities:
               none   (0)
               rip2   (1)"
   ::= {er1645v2PRout 34}


er1645v2PRoutRipHoldDownTime OBJECT-TYPE
   SYNTAX      TimeTicks
   MAX-ACCESS  read-write
   STATUS      current
   DESCRIPTION
      "Path: router.editConf.ripHoldDownTime
       Info: Time to wait before accepting better routes in order to prevent instable route-flapping

       Time in centi-second."
   ::= {er1645v2PRout 78}


er1645v2PRoutAlarmMask OBJECT-TYPE
   SYNTAX      Integer32
   MAX-ACCESS  read-write
   STATUS      current
   DESCRIPTION
      "Path: router.editConf.alarmMask
       Info: routAlarmMask

       Bit meanings:
               bit 0 = pingActive,
               bit 1 = qMonLoss,
               bit 2 = qMonDelay,
               bit 3 = qMonJitter"
   ::= {er1645v2PRout 135}


er1645v2PRoutAlarmLev OBJECT IDENTIFIER ::= {er1645v2PRout 170}

er1645v2PRoutAlarmLevSSC OBJECT IDENTIFIER ::= {er1645v2PRoutAlarmLev 1}

er1645v2PRoutAlarmLevEntry OBJECT IDENTIFIER ::= {er1645v2PRoutAlarmLevSSC 1}

er1645v2PRoutAlarmLevPingActive OBJECT-TYPE
   SYNTAX      Integer32
   MAX-ACCESS  read-write
   STATUS      current
   DESCRIPTION
      "Path: router.editConf.alarmLevel.pingActive"
   ::= {er1645v2PRoutAlarmLevEntry 16777216}

er1645v2PRoutAlarmLevQMonLoss OBJECT-TYPE
   SYNTAX      Integer32
   MAX-ACCESS  read-write
   STATUS      current
   DESCRIPTION
      "Path: router.editConf.alarmLevel.qMonLoss"
   ::= {er1645v2PRoutAlarmLevEntry 33554432}

er1645v2PRoutAlarmLevQMonDelay OBJECT-TYPE
   SYNTAX      Integer32
   MAX-ACCESS  read-write
   STATUS      current
   DESCRIPTION
      "Path: router.editConf.alarmLevel.qMonDelay"
   ::= {er1645v2PRoutAlarmLevEntry 50331648}

er1645v2PRoutAlarmLevQMonJitter OBJECT-TYPE
   SYNTAX      Integer32
   MAX-ACCESS  read-write
   STATUS      current
   DESCRIPTION
      "Path: router.editConf.alarmLevel.qMonJitter"
   ::= {er1645v2PRoutAlarmLevEntry 67108864}


er1645v2PRoutR2ScrtTbl OBJECT IDENTIFIER ::= {er1645v2PRout 42}

er1645v2PRoutR2ScrtTblSSCTable OBJECT-TYPE
   SYNTAX      SEQUENCE OF Er1645v2PRoutR2ScrtTblEntry
   MAX-ACCESS  not-accessible
   STATUS      current
   DESCRIPTION
      "table to store secret values for RIPv2 authentication"
   ::= {er1645v2PRoutR2ScrtTbl 1}

er1645v2PRoutR2ScrtTblEntry OBJECT-TYPE
   SYNTAX      Er1645v2PRoutR2ScrtTblEntry
   MAX-ACCESS  not-accessible
   STATUS      current
   DESCRIPTION
      ""
   INDEX      { er1645v2PRoutR2ScrtTblTableIx }
   ::= {er1645v2PRoutR2ScrtTblSSCTable 1}

Er1645v2PRoutR2ScrtTblEntry ::=
   SEQUENCE
      {
      er1645v2PRoutR2ScrtTblActions
         VariableLengthTableActions,
      er1645v2PRoutR2ScrtTblTableIx
         TableIndex,
      er1645v2PRoutR2ScrtTblKeyId
         Integer32,
      er1645v2PRoutR2ScrtTblSecret
         DisplayString,
      er1645v2PRoutR2ScrtTblIf
         DisplayString
      }

er1645v2PRoutR2ScrtTblActions OBJECT-TYPE
   SYNTAX      VariableLengthTableActions
   MAX-ACCESS  read-write
   STATUS      current
   DESCRIPTION
      "By way of this field, some manipulations
       on this table may be performed."
   ::= {er1645v2PRoutR2ScrtTblEntry 2}

er1645v2PRoutR2ScrtTblTableIx OBJECT-TYPE
   SYNTAX      TableIndex
   MAX-ACCESS  not-accessible
   STATUS      current
   DESCRIPTION
      ""
   ::= {er1645v2PRoutR2ScrtTblEntry 11}

er1645v2PRoutR2ScrtTblKeyId OBJECT-TYPE
   SYNTAX      Integer32
   MAX-ACCESS  read-write
   STATUS      current
   DESCRIPTION
      "Path: router.editConf.ripv2SecretTable.keyId"
   ::= {er1645v2PRoutR2ScrtTblEntry 16777216}

er1645v2PRoutR2ScrtTblSecret OBJECT-TYPE
   SYNTAX      DisplayString
   MAX-ACCESS  read-write
   STATUS      current
   DESCRIPTION
      "Path: router.editConf.ripv2SecretTable.secret"
   ::= {er1645v2PRoutR2ScrtTblEntry 33554432}

er1645v2PRoutR2ScrtTblIf OBJECT-TYPE
   SYNTAX      DisplayString
   MAX-ACCESS  read-write
   STATUS      current
   DESCRIPTION
      "Path: router.editConf.ripv2SecretTable.interface"
   ::= {er1645v2PRoutR2ScrtTblEntry 50331648}


er1645v2PRoutAlternativeRoutes OBJECT-TYPE
   SYNTAX      INTEGER
               {
               backup (0),
               roundRobin (1)
               }
   MAX-ACCESS  read-write
   STATUS      current
   DESCRIPTION
      "Path: router.editConf.alternativeRoutes
       Info: indicates if load balancing has to be applied whenever multiple
                        routes are available

       Possibilities:
               backup   (0)
               roundRobin   (1)"
   ::= {er1645v2PRout 57}


er1645v2PRoutRadius OBJECT IDENTIFIER ::= {er1645v2PRout 59}

er1645v2PRoutRadiusSSC OBJECT IDENTIFIER ::= {er1645v2PRoutRadius 1}

er1645v2PRoutRadiusEntry OBJECT IDENTIFIER ::= {er1645v2PRoutRadiusSSC 1}

er1645v2PRoutRadiusAcctServerAddress OBJECT-TYPE
   SYNTAX      IpAddress
   MAX-ACCESS  read-write
   STATUS      current
   DESCRIPTION
      "Path: router.editConf.radius.acctServer.address"
   ::= {er1645v2PRoutRadiusEntry 1694564352}

er1645v2PRoutRadiusAcctServerSource OBJECT-TYPE
   SYNTAX      DisplayString
   MAX-ACCESS  read-write
   STATUS      current
   DESCRIPTION
      "Path: router.editConf.radius.acctServer.source"
   ::= {er1645v2PRoutRadiusEntry 1694760960}

er1645v2PRoutRadiusAcctServerSecret OBJECT-TYPE
   SYNTAX      DisplayString
   MAX-ACCESS  read-write
   STATUS      current
   DESCRIPTION
      "Path: router.editConf.radius.acctServer.secret"
   ::= {er1645v2PRoutRadiusEntry 1694629888}

er1645v2PRoutRadiusAcctServerEncModeSecret OBJECT-TYPE
   SYNTAX      INTEGER
               {
               none (1),
               encrypt (2),
               encType1 (3),
               invalid (128)
               }
   MAX-ACCESS  read-write
   STATUS      current
   DESCRIPTION
      "Path: router.editConf.radius.acctServer.encModeSecret

       Possibilities:
               none   (1)
               encrypt   (2)
               encType1   (3)
               invalid   (128)"
   ::= {er1645v2PRoutRadiusEntry 1694892032}

er1645v2PRoutRadiusAcctServerEncSecret OBJECT-TYPE
   SYNTAX      DisplayString
   MAX-ACCESS  read-write
   STATUS      current
   DESCRIPTION
      "Path: router.editConf.radius.acctServer.encSecret"
   ::= {er1645v2PRoutRadiusEntry 1694957568}

er1645v2PRoutRadiusAcctServerTimeOut OBJECT-TYPE
   SYNTAX      TimeTicks
   MAX-ACCESS  read-write
   STATUS      current
   DESCRIPTION
      "Path: router.editConf.radius.acctServer.timeOut

       Time in centi-second."
   ::= {er1645v2PRoutRadiusEntry 1694695424}

er1645v2PRoutRadiusRetries OBJECT-TYPE
   SYNTAX      Integer32
   MAX-ACCESS  read-write
   STATUS      current
   DESCRIPTION
      "Path: router.editConf.radius.retries"
   ::= {er1645v2PRoutRadiusEntry 16777216}

er1645v2PRoutRadiusAcctUpdate OBJECT-TYPE
   SYNTAX      TimeTicks
   MAX-ACCESS  read-write
   STATUS      current
   DESCRIPTION
      "Path: router.editConf.radius.acctUpdate

       Time in centi-second."
   ::= {er1645v2PRoutRadiusEntry 33554432}

er1645v2PRoutRadiusLogin OBJECT-TYPE
   SYNTAX      INTEGER
               {
               disabled (0),
               enabled (1),
               fallback (2),
               reverseFallback (3)
               }
   MAX-ACCESS  read-write
   STATUS      current
   DESCRIPTION
      "Path: router.editConf.radius.login

       Possibilities:
               disabled   (0)
               enabled   (1)
               fallback   (2)
               reverseFallback   (3)"
   ::= {er1645v2PRoutRadiusEntry 50331648}

er1645v2PRoutRadiusPpp OBJECT-TYPE
   SYNTAX      INTEGER
               {
               disabled (0),
               enabled (1),
               fallback (2),
               reverseFallback (3)
               }
   MAX-ACCESS  read-write
   STATUS      current
   DESCRIPTION
      "Path: router.editConf.radius.ppp

       Possibilities:
               disabled   (0)
               enabled   (1)
               fallback   (2)
               reverseFallback   (3)"
   ::= {er1645v2PRoutRadiusEntry 67108864}

er1645v2PRoutRadiusAuthServers OBJECT-TYPE
   SYNTAX      SEQUENCE OF Er1645v2PRoutRadiusAuthServersEntry
   MAX-ACCESS  not-accessible
   STATUS      current
   DESCRIPTION
      ""
   ::= {er1645v2PRoutRadius 1677721600}

er1645v2PRoutRadiusAuthServersEntry OBJECT-TYPE
   SYNTAX      Er1645v2PRoutRadiusAuthServersEntry
   MAX-ACCESS  not-accessible
   STATUS      current
   DESCRIPTION
      ""
   INDEX      { er1645v2PRoutRadiusAuthServersTableIx }
   ::= {er1645v2PRoutRadiusAuthServers 1}

Er1645v2PRoutRadiusAuthServersEntry ::=
   SEQUENCE
      {
      er1645v2PRoutRadiusAuthServersActions
         VariableLengthTableActions,
      er1645v2PRoutRadiusAuthServersTableIx
         TableIndex,
      er1645v2PRoutRadiusAuthServersAddress
         IpAddress,
      er1645v2PRoutRadiusAuthServersSource
         DisplayString,
      er1645v2PRoutRadiusAuthServersSecret
         DisplayString,
      er1645v2PRoutRadiusAuthServersEncModeSecret
         INTEGER,
      er1645v2PRoutRadiusAuthServersEncSecret
         DisplayString,
      er1645v2PRoutRadiusAuthServersTimeOut
         TimeTicks
      }

er1645v2PRoutRadiusAuthServersActions OBJECT-TYPE
   SYNTAX      VariableLengthTableActions
   MAX-ACCESS  read-write
   STATUS      current
   DESCRIPTION
      "By way of this field, some manipulations
       on this table may be performed."
   ::= {er1645v2PRoutRadiusAuthServersEntry 2}

er1645v2PRoutRadiusAuthServersTableIx OBJECT-TYPE
   SYNTAX      TableIndex
   MAX-ACCESS  not-accessible
   STATUS      current
   DESCRIPTION
      ""
   ::= {er1645v2PRoutRadiusAuthServersEntry 11}

er1645v2PRoutRadiusAuthServersAddress OBJECT-TYPE
   SYNTAX      IpAddress
   MAX-ACCESS  read-write
   STATUS      current
   DESCRIPTION
      "Path: router.editConf.radius.authServers.address"
   ::= {er1645v2PRoutRadiusAuthServersEntry 16777216}

er1645v2PRoutRadiusAuthServersSource OBJECT-TYPE
   SYNTAX      DisplayString
   MAX-ACCESS  read-write
   STATUS      current
   DESCRIPTION
      "Path: router.editConf.radius.authServers.source"
   ::= {er1645v2PRoutRadiusAuthServersEntry 67108864}

er1645v2PRoutRadiusAuthServersSecret OBJECT-TYPE
   SYNTAX      DisplayString
   MAX-ACCESS  read-write
   STATUS      current
   DESCRIPTION
      "Path: router.editConf.radius.authServers.secret"
   ::= {er1645v2PRoutRadiusAuthServersEntry 33554432}

er1645v2PRoutRadiusAuthServersEncModeSecret OBJECT-TYPE
   SYNTAX      INTEGER
               {
               none (1),
               encrypt (2),
               encType1 (3),
               invalid (128)
               }
   MAX-ACCESS  read-write
   STATUS      current
   DESCRIPTION
      "Path: router.editConf.radius.authServers.encModeSecret

       Possibilities:
               none   (1)
               encrypt   (2)
               encType1   (3)
               invalid   (128)"
   ::= {er1645v2PRoutRadiusAuthServersEntry 100663296}

er1645v2PRoutRadiusAuthServersEncSecret OBJECT-TYPE
   SYNTAX      DisplayString
   MAX-ACCESS  read-write
   STATUS      current
   DESCRIPTION
      "Path: router.editConf.radius.authServers.encSecret"
   ::= {er1645v2PRoutRadiusAuthServersEntry 117440512}

er1645v2PRoutRadiusAuthServersTimeOut OBJECT-TYPE
   SYNTAX      TimeTicks
   MAX-ACCESS  read-write
   STATUS      current
   DESCRIPTION
      "Path: router.editConf.radius.authServers.timeOut

       Time in centi-second."
   ::= {er1645v2PRoutRadiusAuthServersEntry 50331648}


er1645v2PRoutTacacs OBJECT IDENTIFIER ::= {er1645v2PRout 70}

er1645v2PRoutTacacsSSC OBJECT IDENTIFIER ::= {er1645v2PRoutTacacs 1}

er1645v2PRoutTacacsEntry OBJECT IDENTIFIER ::= {er1645v2PRoutTacacsSSC 1}

er1645v2PRoutTacacsLogin OBJECT-TYPE
   SYNTAX      INTEGER
               {
               disabled (0),
               enabled (1),
               fallback (2),
               reverseFallback (3)
               }
   MAX-ACCESS  read-write
   STATUS      current
   DESCRIPTION
      "Path: router.editConf.tacacs.login

       Possibilities:
               disabled   (0)
               enabled   (1)
               fallback   (2)
               reverseFallback   (3)"
   ::= {er1645v2PRoutTacacsEntry 83886080}

er1645v2PRoutTacacsAuthServers OBJECT-TYPE
   SYNTAX      SEQUENCE OF Er1645v2PRoutTacacsAuthServersEntry
   MAX-ACCESS  not-accessible
   STATUS      current
   DESCRIPTION
      ""
   ::= {er1645v2PRoutTacacs 16777216}

er1645v2PRoutTacacsAuthServersEntry OBJECT-TYPE
   SYNTAX      Er1645v2PRoutTacacsAuthServersEntry
   MAX-ACCESS  not-accessible
   STATUS      current
   DESCRIPTION
      ""
   INDEX      { er1645v2PRoutTacacsAuthServersTableIx }
   ::= {er1645v2PRoutTacacsAuthServers 1}

Er1645v2PRoutTacacsAuthServersEntry ::=
   SEQUENCE
      {
      er1645v2PRoutTacacsAuthServersActions
         VariableLengthTableActions,
      er1645v2PRoutTacacsAuthServersTableIx
         TableIndex,
      er1645v2PRoutTacacsAuthServersAddress
         IpAddress,
      er1645v2PRoutTacacsAuthServersSource
         DisplayString,
      er1645v2PRoutTacacsAuthServersSecret
         DisplayString,
      er1645v2PRoutTacacsAuthServersEncModeSecret
         INTEGER,
      er1645v2PRoutTacacsAuthServersEncSecret
         DisplayString,
      er1645v2PRoutTacacsAuthServersTimeOut
         TimeTicks
      }

er1645v2PRoutTacacsAuthServersActions OBJECT-TYPE
   SYNTAX      VariableLengthTableActions
   MAX-ACCESS  read-write
   STATUS      current
   DESCRIPTION
      "By way of this field, some manipulations
       on this table may be performed."
   ::= {er1645v2PRoutTacacsAuthServersEntry 2}

er1645v2PRoutTacacsAuthServersTableIx OBJECT-TYPE
   SYNTAX      TableIndex
   MAX-ACCESS  not-accessible
   STATUS      current
   DESCRIPTION
      ""
   ::= {er1645v2PRoutTacacsAuthServersEntry 11}

er1645v2PRoutTacacsAuthServersAddress OBJECT-TYPE
   SYNTAX      IpAddress
   MAX-ACCESS  read-write
   STATUS      current
   DESCRIPTION
      "Path: router.editConf.tacacs.authServers.address"
   ::= {er1645v2PRoutTacacsAuthServersEntry 16777216}

er1645v2PRoutTacacsAuthServersSource OBJECT-TYPE
   SYNTAX      DisplayString
   MAX-ACCESS  read-write
   STATUS      current
   DESCRIPTION
      "Path: router.editConf.tacacs.authServers.source"
   ::= {er1645v2PRoutTacacsAuthServersEntry 33554432}

er1645v2PRoutTacacsAuthServersSecret OBJECT-TYPE
   SYNTAX      DisplayString
   MAX-ACCESS  read-write
   STATUS      current
   DESCRIPTION
      "Path: router.editConf.tacacs.authServers.secret"
   ::= {er1645v2PRoutTacacsAuthServersEntry 50331648}

er1645v2PRoutTacacsAuthServersEncModeSecret OBJECT-TYPE
   SYNTAX      INTEGER
               {
               none (1),
               encrypt (2),
               encType1 (3),
               invalid (128)
               }
   MAX-ACCESS  read-write
   STATUS      current
   DESCRIPTION
      "Path: router.editConf.tacacs.authServers.encModeSecret

       Possibilities:
               none   (1)
               encrypt   (2)
               encType1   (3)
               invalid   (128)"
   ::= {er1645v2PRoutTacacsAuthServersEntry 134217728}

er1645v2PRoutTacacsAuthServersEncSecret OBJECT-TYPE
   SYNTAX      DisplayString
   MAX-ACCESS  read-write
   STATUS      current
   DESCRIPTION
      "Path: router.editConf.tacacs.authServers.encSecret"
   ::= {er1645v2PRoutTacacsAuthServersEntry 150994944}

er1645v2PRoutTacacsAuthServersTimeOut OBJECT-TYPE
   SYNTAX      TimeTicks
   MAX-ACCESS  read-write
   STATUS      current
   DESCRIPTION
      "Path: router.editConf.tacacs.authServers.timeOut

       Time in centi-second."
   ::= {er1645v2PRoutTacacsAuthServersEntry 67108864}


er1645v2PRoutDns OBJECT IDENTIFIER ::= {er1645v2PRout 64}

er1645v2PRoutDnsSSC OBJECT IDENTIFIER ::= {er1645v2PRoutDns 1}

er1645v2PRoutDnsEntry OBJECT IDENTIFIER ::= {er1645v2PRoutDnsSSC 1}

er1645v2PRoutDnsPrimaryDns OBJECT-TYPE
   SYNTAX      IpAddress
   MAX-ACCESS  read-write
   STATUS      current
   DESCRIPTION
      "Path: router.editConf.dns.primaryDns"
   ::= {er1645v2PRoutDnsEntry 16777216}

er1645v2PRoutDnsSecondaryDns OBJECT-TYPE
   SYNTAX      IpAddress
   MAX-ACCESS  read-write
   STATUS      current
   DESCRIPTION
      "Path: router.editConf.dns.secondaryDns"
   ::= {er1645v2PRoutDnsEntry 33554432}

er1645v2PRoutDnsDomainName OBJECT-TYPE
   SYNTAX      DisplayString
   MAX-ACCESS  read-write
   STATUS      current
   DESCRIPTION
      "Path: router.editConf.dns.domainName"
   ::= {er1645v2PRoutDnsEntry 50331648}

er1645v2PRoutDnsIpV6Router OBJECT-TYPE
   SYNTAX      DisplayString
   MAX-ACCESS  read-write
   STATUS      current
   DESCRIPTION
      "Path: router.editConf.dns.ipV6Router"
   ::= {er1645v2PRoutDnsEntry 67108864}

er1645v2PRoutDnsPreference OBJECT-TYPE
   SYNTAX      Integer32
   MAX-ACCESS  read-write
   STATUS      current
   DESCRIPTION
      "Path: router.editConf.dns.preference"
   ::= {er1645v2PRoutDnsEntry 83886080}

er1645v2PRoutDnsProxy OBJECT-TYPE
   SYNTAX      INTEGER
               {
               disabled (0),
               enabled (1)
               }
   MAX-ACCESS  read-write
   STATUS      current
   DESCRIPTION
      "Path: router.editConf.dns.proxy

       Possibilities:
               disabled   (0)
               enabled   (1)"
   ::= {er1645v2PRoutDnsEntry 100663296}

er1645v2PRoutDnsCacheSize OBJECT-TYPE
   SYNTAX      Integer32
   MAX-ACCESS  read-write
   STATUS      current
   DESCRIPTION
      "Path: router.editConf.dns.cacheSize"
   ::= {er1645v2PRoutDnsEntry 117440512}


er1645v2PRoutLog OBJECT IDENTIFIER ::= {er1645v2PRout 67}

er1645v2PRoutLogSSC OBJECT IDENTIFIER ::= {er1645v2PRoutLog 1}

er1645v2PRoutLogEntry OBJECT IDENTIFIER ::= {er1645v2PRoutLogSSC 1}

er1645v2PRoutLogMode OBJECT-TYPE
   SYNTAX      INTEGER
               {
               disabled (0),
               enabled (1)
               }
   MAX-ACCESS  read-write
   STATUS      current
   DESCRIPTION
      "Path: router.editConf.log.mode

       Possibilities:
               disabled   (0)
               enabled   (1)"
   ::= {er1645v2PRoutLogEntry 16777216}

er1645v2PRoutLogDhcpSyslogMask OBJECT-TYPE
   SYNTAX      Integer32
   MAX-ACCESS  read-write
   STATUS      current
   DESCRIPTION
      "Path: router.editConf.log.dhcpSyslogMask

       Bit meanings:
               bit 0 = lease,
               bit 1 = renew,
               bit 2 = rebind,
               bit 3 = expired"
   ::= {er1645v2PRoutLogEntry 33554432}


er1645v2PRoutForceMtu OBJECT-TYPE
   SYNTAX      INTEGER
               {
               disabled (0),
               enabled (1)
               }
   MAX-ACCESS  read-write
   STATUS      current
   DESCRIPTION
      "Path: router.editConf.forceMtu
       Info: force the configured mtu

       Possibilities:
               disabled   (0)
               enabled   (1)"
   ::= {er1645v2PRout 171}


er1645v2PRoutAddrPools OBJECT IDENTIFIER ::= {er1645v2PRout 108}

er1645v2PRoutAddrPoolsSSCTable OBJECT-TYPE
   SYNTAX      SEQUENCE OF Er1645v2PRoutAddrPoolsEntry
   MAX-ACCESS  not-accessible
   STATUS      current
   DESCRIPTION
      "ip address pool union"
   ::= {er1645v2PRoutAddrPools 1}

er1645v2PRoutAddrPoolsEntry OBJECT-TYPE
   SYNTAX      Er1645v2PRoutAddrPoolsEntry
   MAX-ACCESS  not-accessible
   STATUS      current
   DESCRIPTION
      ""
   INDEX      { er1645v2PRoutAddrPoolsTableIx }
   ::= {er1645v2PRoutAddrPoolsSSCTable 1}

Er1645v2PRoutAddrPoolsEntry ::=
   SEQUENCE
      {
      er1645v2PRoutAddrPoolsActions
         VariableLengthTableActions,
      er1645v2PRoutAddrPoolsTableIx
         TableIndex,
      er1645v2PRoutAddrPoolsName
         DisplayString,
      er1645v2PRoutAddrPoolsPoolIntervalFrom
         IpAddress,
      er1645v2PRoutAddrPoolsPoolIntervalTo
         IpAddress
      }

er1645v2PRoutAddrPoolsActions OBJECT-TYPE
   SYNTAX      VariableLengthTableActions
   MAX-ACCESS  read-write
   STATUS      current
   DESCRIPTION
      "By way of this field, some manipulations
       on this table may be performed."
   ::= {er1645v2PRoutAddrPoolsEntry 2}

er1645v2PRoutAddrPoolsTableIx OBJECT-TYPE
   SYNTAX      TableIndex
   MAX-ACCESS  not-accessible
   STATUS      current
   DESCRIPTION
      ""
   ::= {er1645v2PRoutAddrPoolsEntry 11}

er1645v2PRoutAddrPoolsName OBJECT-TYPE
   SYNTAX      DisplayString
   MAX-ACCESS  read-write
   STATUS      current
   DESCRIPTION
      "Path: router.editConf.addrPools.name"
   ::= {er1645v2PRoutAddrPoolsEntry 16777216}

er1645v2PRoutAddrPoolsPoolIntervalFrom OBJECT-TYPE
   SYNTAX      IpAddress
   MAX-ACCESS  read-write
   STATUS      current
   DESCRIPTION
      "Path: router.editConf.addrPools.pool.interval.from"
   ::= {er1645v2PRoutAddrPoolsEntry 33686016}

er1645v2PRoutAddrPoolsPoolIntervalTo OBJECT-TYPE
   SYNTAX      IpAddress
   MAX-ACCESS  read-write
   STATUS      current
   DESCRIPTION
      "Path: router.editConf.addrPools.pool.interval.to"
   ::= {er1645v2PRoutAddrPoolsEntry 33686272}

er1645v2PRoutAddrPoolsPoolList OBJECT-TYPE
   SYNTAX      SEQUENCE OF Er1645v2PRoutAddrPoolsPoolListEntry
   MAX-ACCESS  not-accessible
   STATUS      current
   DESCRIPTION
      ""
   ::= {er1645v2PRoutAddrPools 33619968}

er1645v2PRoutAddrPoolsPoolListEntry OBJECT-TYPE
   SYNTAX      Er1645v2PRoutAddrPoolsPoolListEntry
   MAX-ACCESS  not-accessible
   STATUS      current
   DESCRIPTION
      ""
   INDEX      { er1645v2PRoutAddrPoolsTableIx,
                er1645v2PRoutAddrPoolsPoolListTableIx }
   ::= {er1645v2PRoutAddrPoolsPoolList 1}

Er1645v2PRoutAddrPoolsPoolListEntry ::=
   SEQUENCE
      {
      er1645v2PRoutAddrPoolsPoolListActions
         VariableLengthTableActions,
      er1645v2PRoutAddrPoolsPoolListTableIx
         TableIndex,
      er1645v2PRoutAddrPoolsPoolListLocal
         IpAddress,
      er1645v2PRoutAddrPoolsPoolListRemote
         IpAddress,
      er1645v2PRoutAddrPoolsPoolListNetMask
         IpAddress
      }

er1645v2PRoutAddrPoolsPoolListActions OBJECT-TYPE
   SYNTAX      VariableLengthTableActions
   MAX-ACCESS  read-write
   STATUS      current
   DESCRIPTION
      "By way of this field, some manipulations
       on this table may be performed."
   ::= {er1645v2PRoutAddrPoolsPoolListEntry 2}

er1645v2PRoutAddrPoolsPoolListTableIx OBJECT-TYPE
   SYNTAX      TableIndex
   MAX-ACCESS  not-accessible
   STATUS      current
   DESCRIPTION
      ""
   ::= {er1645v2PRoutAddrPoolsPoolListEntry 11}

er1645v2PRoutAddrPoolsPoolListLocal OBJECT-TYPE
   SYNTAX      IpAddress
   MAX-ACCESS  read-write
   STATUS      current
   DESCRIPTION
      "Path: router.editConf.addrPools.pool.list.local"
   ::= {er1645v2PRoutAddrPoolsPoolListEntry 33554432}

er1645v2PRoutAddrPoolsPoolListRemote OBJECT-TYPE
   SYNTAX      IpAddress
   MAX-ACCESS  read-write
   STATUS      current
   DESCRIPTION
      "Path: router.editConf.addrPools.pool.list.remote"
   ::= {er1645v2PRoutAddrPoolsPoolListEntry 50331648}

er1645v2PRoutAddrPoolsPoolListNetMask OBJECT-TYPE
   SYNTAX      IpAddress
   MAX-ACCESS  read-write
   STATUS      current
   DESCRIPTION
      "Path: router.editConf.addrPools.pool.list.netMask"
   ::= {er1645v2PRoutAddrPoolsPoolListEntry 67108864}


er1645v2PRoutDnsUpdCli OBJECT IDENTIFIER ::= {er1645v2PRout 80}

er1645v2PRoutDnsUpdCliSSCTable OBJECT-TYPE
   SYNTAX      SEQUENCE OF Er1645v2PRoutDnsUpdCliEntry
   MAX-ACCESS  not-accessible
   STATUS      current
   DESCRIPTION
      "DNS Update Client config table"
   ::= {er1645v2PRoutDnsUpdCli 1}

er1645v2PRoutDnsUpdCliEntry OBJECT-TYPE
   SYNTAX      Er1645v2PRoutDnsUpdCliEntry
   MAX-ACCESS  not-accessible
   STATUS      current
   DESCRIPTION
      ""
   INDEX      { er1645v2PRoutDnsUpdCliTableIx }
   ::= {er1645v2PRoutDnsUpdCliSSCTable 1}

Er1645v2PRoutDnsUpdCliEntry ::=
   SEQUENCE
      {
      er1645v2PRoutDnsUpdCliActions
         VariableLengthTableActions,
      er1645v2PRoutDnsUpdCliTableIx
         TableIndex,
      er1645v2PRoutDnsUpdCliName
         DisplayString,
      er1645v2PRoutDnsUpdCliDnsProvDynDnsMode
         INTEGER,
      er1645v2PRoutDnsUpdCliDnsProvDynDnsSystem
         INTEGER,
      er1645v2PRoutDnsUpdCliDnsProvDynDnsHostNameFqdn
         DisplayString,
      er1645v2PRoutDnsUpdCliDnsProvDynDnsInterface
         DisplayString,
      er1645v2PRoutDnsUpdCliDnsProvDynDnsUserName
         DisplayString,
      er1645v2PRoutDnsUpdCliDnsProvDynDnsPassword
         DisplayString,
      er1645v2PRoutDnsUpdCliDnsProvDynDnsTcpPort
         INTEGER,
      er1645v2PRoutDnsUpdCliDnsProvDynDnsMxName
         DisplayString,
      er1645v2PRoutDnsUpdCliDnsProvDynDnsMxBackup
         INTEGER
      }

er1645v2PRoutDnsUpdCliActions OBJECT-TYPE
   SYNTAX      VariableLengthTableActions
   MAX-ACCESS  read-write
   STATUS      current
   DESCRIPTION
      "By way of this field, some manipulations
       on this table may be performed."
   ::= {er1645v2PRoutDnsUpdCliEntry 2}

er1645v2PRoutDnsUpdCliTableIx OBJECT-TYPE
   SYNTAX      TableIndex
   MAX-ACCESS  not-accessible
   STATUS      current
   DESCRIPTION
      ""
   ::= {er1645v2PRoutDnsUpdCliEntry 11}

er1645v2PRoutDnsUpdCliName OBJECT-TYPE
   SYNTAX      DisplayString
   MAX-ACCESS  read-write
   STATUS      current
   DESCRIPTION
      "Path: router.editConf.dnsUpdateClient.name"
   ::= {er1645v2PRoutDnsUpdCliEntry 16777216}

er1645v2PRoutDnsUpdCliDnsProvDynDnsMode OBJECT-TYPE
   SYNTAX      INTEGER
               {
               disabled (0),
               offline (1),
               online (2)
               }
   MAX-ACCESS  read-write
   STATUS      current
   DESCRIPTION
      "Path: router.editConf.dnsUpdateClient.dnsProvider.dynDns.mode

       Possibilities:
               disabled   (0)
               offline   (1)
               online   (2)"
   ::= {er1645v2PRoutDnsUpdCliEntry 33620224}

er1645v2PRoutDnsUpdCliDnsProvDynDnsSystem OBJECT-TYPE
   SYNTAX      INTEGER
               {
               dynamic (0),
               static (1),
               custom (2)
               }
   MAX-ACCESS  read-write
   STATUS      current
   DESCRIPTION
      "Path: router.editConf.dnsUpdateClient.dnsProvider.dynDns.system

       Possibilities:
               dynamic   (0)
               static   (1)
               custom   (2)"
   ::= {er1645v2PRoutDnsUpdCliEntry 33620480}

er1645v2PRoutDnsUpdCliDnsProvDynDnsHostNameFqdn OBJECT-TYPE
   SYNTAX      DisplayString
   MAX-ACCESS  read-write
   STATUS      current
   DESCRIPTION
      "Path: router.editConf.dnsUpdateClient.dnsProvider.dynDns.hostNameFqdn"
   ::= {er1645v2PRoutDnsUpdCliEntry 33620736}

er1645v2PRoutDnsUpdCliDnsProvDynDnsInterface OBJECT-TYPE
   SYNTAX      DisplayString
   MAX-ACCESS  read-write
   STATUS      current
   DESCRIPTION
      "Path: router.editConf.dnsUpdateClient.dnsProvider.dynDns.interface"
   ::= {er1645v2PRoutDnsUpdCliEntry 33620992}

er1645v2PRoutDnsUpdCliDnsProvDynDnsUserName OBJECT-TYPE
   SYNTAX      DisplayString
   MAX-ACCESS  read-write
   STATUS      current
   DESCRIPTION
      "Path: router.editConf.dnsUpdateClient.dnsProvider.dynDns.userName"
   ::= {er1645v2PRoutDnsUpdCliEntry 33621248}

er1645v2PRoutDnsUpdCliDnsProvDynDnsPassword OBJECT-TYPE
   SYNTAX      DisplayString
   MAX-ACCESS  read-write
   STATUS      current
   DESCRIPTION
      "Path: router.editConf.dnsUpdateClient.dnsProvider.dynDns.password"
   ::= {er1645v2PRoutDnsUpdCliEntry 33621504}

er1645v2PRoutDnsUpdCliDnsProvDynDnsTcpPort OBJECT-TYPE
   SYNTAX      INTEGER
               {
               http (80),
               httpProxyBypass (8245)
               }
   MAX-ACCESS  read-write
   STATUS      current
   DESCRIPTION
      "Path: router.editConf.dnsUpdateClient.dnsProvider.dynDns.tcpPort

       Possibilities:
               http   (80)
               httpProxyBypass   (8245)"
   ::= {er1645v2PRoutDnsUpdCliEntry 33621760}

er1645v2PRoutDnsUpdCliDnsProvDynDnsMxName OBJECT-TYPE
   SYNTAX      DisplayString
   MAX-ACCESS  read-write
   STATUS      current
   DESCRIPTION
      "Path: router.editConf.dnsUpdateClient.dnsProvider.dynDns.mx.name"
   ::= {er1645v2PRoutDnsUpdCliEntry 33622017}

er1645v2PRoutDnsUpdCliDnsProvDynDnsMxBackup OBJECT-TYPE
   SYNTAX      INTEGER
               {
               no (0),
               yes (1)
               }
   MAX-ACCESS  read-write
   STATUS      current
   DESCRIPTION
      "Path: router.editConf.dnsUpdateClient.dnsProvider.dynDns.mx.backup

       Possibilities:
               no   (0)
               yes   (1)"
   ::= {er1645v2PRoutDnsUpdCliEntry 33622018}



sr1645v2PRout OBJECT IDENTIFIER ::= {r1645v2PRout 14}


sr1645v2PRoutDhcpBinding OBJECT IDENTIFIER ::= {sr1645v2PRout 54}

sr1645v2PRoutDhcpBindingSSCTable OBJECT-TYPE
   SYNTAX      SEQUENCE OF Sr1645v2PRoutDhcpBindingEntry
   MAX-ACCESS  not-accessible
   STATUS      current
   DESCRIPTION
      "table containing DHCP client information"
   ::= {sr1645v2PRoutDhcpBinding 1}

sr1645v2PRoutDhcpBindingEntry OBJECT-TYPE
   SYNTAX      Sr1645v2PRoutDhcpBindingEntry
   MAX-ACCESS  not-accessible
   STATUS      current
   DESCRIPTION
      ""
   INDEX      { sr1645v2PRoutDhcpBindingTableIx }
   ::= {sr1645v2PRoutDhcpBindingSSCTable 1}

Sr1645v2PRoutDhcpBindingEntry ::=
   SEQUENCE
      {
      sr1645v2PRoutDhcpBindingTableIx
         TableIndex,
      sr1645v2PRoutDhcpBindingIpAddress
         IpAddress,
      sr1645v2PRoutDhcpBindingMacAddress
         OCTET STRING,
      sr1645v2PRoutDhcpBindingLeaseTime
         TimeTicks,
      sr1645v2PRoutDhcpBindingHostName
         DisplayString,
      sr1645v2PRoutDhcpBindingInterface
         DisplayString,
      sr1645v2PRoutDhcpBindingState
         INTEGER,
      sr1645v2PRoutDhcpBindingCheckAddress
         INTEGER
      }

sr1645v2PRoutDhcpBindingTableIx OBJECT-TYPE
   SYNTAX      TableIndex
   MAX-ACCESS  not-accessible
   STATUS      current
   DESCRIPTION
      ""
   ::= {sr1645v2PRoutDhcpBindingEntry 11}

sr1645v2PRoutDhcpBindingIpAddress OBJECT-TYPE
   SYNTAX      IpAddress
   MAX-ACCESS  read-only
   STATUS      current
   DESCRIPTION
      "Path: router.status.dhcpBinding.ipAddress"
   ::= {sr1645v2PRoutDhcpBindingEntry 16777216}

sr1645v2PRoutDhcpBindingMacAddress OBJECT-TYPE
   SYNTAX      OCTET STRING
   MAX-ACCESS  read-only
   STATUS      current
   DESCRIPTION
      "Path: router.status.dhcpBinding.macAddress

       MAC address."
   ::= {sr1645v2PRoutDhcpBindingEntry 33554432}

sr1645v2PRoutDhcpBindingLeaseTime OBJECT-TYPE
   SYNTAX      TimeTicks
   MAX-ACCESS  read-only
   STATUS      current
   DESCRIPTION
      "Path: router.status.dhcpBinding.leaseTime

       Time in centi-second."
   ::= {sr1645v2PRoutDhcpBindingEntry 50331648}

sr1645v2PRoutDhcpBindingHostName OBJECT-TYPE
   SYNTAX      DisplayString
   MAX-ACCESS  read-only
   STATUS      current
   DESCRIPTION
      "Path: router.status.dhcpBinding.hostName"
   ::= {sr1645v2PRoutDhcpBindingEntry 67108864}

sr1645v2PRoutDhcpBindingInterface OBJECT-TYPE
   SYNTAX      DisplayString
   MAX-ACCESS  read-only
   STATUS      current
   DESCRIPTION
      "Path: router.status.dhcpBinding.interface"
   ::= {sr1645v2PRoutDhcpBindingEntry 100663296}

sr1645v2PRoutDhcpBindingState OBJECT-TYPE
   SYNTAX      INTEGER
               {
               onHold (0),
               leased (1),
               reserved (2)
               }
   MAX-ACCESS  read-only
   STATUS      current
   DESCRIPTION
      "Path: router.status.dhcpBinding.state

       Possibilities:
               onHold   (0)
               leased   (1)
               reserved   (2)"
   ::= {sr1645v2PRoutDhcpBindingEntry 83886080}

sr1645v2PRoutDhcpBindingCheckAddress OBJECT-TYPE
   SYNTAX      INTEGER
               {
               idle (0),
               pending (1),
               validated (2),
               rejected (3),
               skipped (4)
               }
   MAX-ACCESS  read-only
   STATUS      current
   DESCRIPTION
      "Path: router.status.dhcpBinding.checkAddress

       Possibilities:
               idle   (0)
               pending   (1)
               validated   (2)
               rejected   (3)
               skipped   (4)"
   ::= {sr1645v2PRoutDhcpBindingEntry 117440512}


sr1645v2PRoutDhcpStat OBJECT IDENTIFIER ::= {sr1645v2PRout 55}

sr1645v2PRoutDhcpStatSSCTable OBJECT-TYPE
   SYNTAX      SEQUENCE OF Sr1645v2PRoutDhcpStatEntry
   MAX-ACCESS  not-accessible
   STATUS      current
   DESCRIPTION
      "DHCP statistics over addresses free, leased and in hold"
   ::= {sr1645v2PRoutDhcpStat 1}

sr1645v2PRoutDhcpStatEntry OBJECT-TYPE
   SYNTAX      Sr1645v2PRoutDhcpStatEntry
   MAX-ACCESS  not-accessible
   STATUS      current
   DESCRIPTION
      ""
   INDEX      { sr1645v2PRoutDhcpStatTableIx }
   ::= {sr1645v2PRoutDhcpStatSSCTable 1}

Sr1645v2PRoutDhcpStatEntry ::=
   SEQUENCE
      {
      sr1645v2PRoutDhcpStatTableIx
         TableIndex,
      sr1645v2PRoutDhcpStatStartRange
         IpAddress,
      sr1645v2PRoutDhcpStatEndRange
         IpAddress,
      sr1645v2PRoutDhcpStatInterface
         DisplayString,
      sr1645v2PRoutDhcpStatFree
         Integer32,
      sr1645v2PRoutDhcpStatLeased
         Integer32,
      sr1645v2PRoutDhcpStatHold
         Integer32
      }

sr1645v2PRoutDhcpStatTableIx OBJECT-TYPE
   SYNTAX      TableIndex
   MAX-ACCESS  not-accessible
   STATUS      current
   DESCRIPTION
      ""
   ::= {sr1645v2PRoutDhcpStatEntry 11}

sr1645v2PRoutDhcpStatStartRange OBJECT-TYPE
   SYNTAX      IpAddress
   MAX-ACCESS  read-only
   STATUS      current
   DESCRIPTION
      "Path: router.status.dhcpStatistics.startRange"
   ::= {sr1645v2PRoutDhcpStatEntry 16777216}

sr1645v2PRoutDhcpStatEndRange OBJECT-TYPE
   SYNTAX      IpAddress
   MAX-ACCESS  read-only
   STATUS      current
   DESCRIPTION
      "Path: router.status.dhcpStatistics.endRange"
   ::= {sr1645v2PRoutDhcpStatEntry 33554432}

sr1645v2PRoutDhcpStatInterface OBJECT-TYPE
   SYNTAX      DisplayString
   MAX-ACCESS  read-only
   STATUS      current
   DESCRIPTION
      "Path: router.status.dhcpStatistics.interface"
   ::= {sr1645v2PRoutDhcpStatEntry 100663296}

sr1645v2PRoutDhcpStatFree OBJECT-TYPE
   SYNTAX      Integer32
   MAX-ACCESS  read-only
   STATUS      current
   DESCRIPTION
      "Path: router.status.dhcpStatistics.free"
   ::= {sr1645v2PRoutDhcpStatEntry 50331648}

sr1645v2PRoutDhcpStatLeased OBJECT-TYPE
   SYNTAX      Integer32
   MAX-ACCESS  read-only
   STATUS      current
   DESCRIPTION
      "Path: router.status.dhcpStatistics.leased"
   ::= {sr1645v2PRoutDhcpStatEntry 67108864}

sr1645v2PRoutDhcpStatHold OBJECT-TYPE
   SYNTAX      Integer32
   MAX-ACCESS  read-only
   STATUS      current
   DESCRIPTION
      "Path: router.status.dhcpStatistics.hold"
   ::= {sr1645v2PRoutDhcpStatEntry 83886080}


sr1645v2PRoutDhcpRelay OBJECT IDENTIFIER ::= {sr1645v2PRout 71}

sr1645v2PRoutDhcpRelaySSCTable OBJECT-TYPE
   SYNTAX      SEQUENCE OF Sr1645v2PRoutDhcpRelayEntry
   MAX-ACCESS  not-accessible
   STATUS      current
   DESCRIPTION
      "dhcpRelayInfo"
   ::= {sr1645v2PRoutDhcpRelay 1}

sr1645v2PRoutDhcpRelayEntry OBJECT-TYPE
   SYNTAX      Sr1645v2PRoutDhcpRelayEntry
   MAX-ACCESS  not-accessible
   STATUS      current
   DESCRIPTION
      ""
   INDEX      { sr1645v2PRoutDhcpRelayTableIx }
   ::= {sr1645v2PRoutDhcpRelaySSCTable 1}

Sr1645v2PRoutDhcpRelayEntry ::=
   SEQUENCE
      {
      sr1645v2PRoutDhcpRelayTableIx
         TableIndex,
      sr1645v2PRoutDhcpRelaySourceIntf
         DisplayString,
      sr1645v2PRoutDhcpRelayMac
         OCTET STRING,
      sr1645v2PRoutDhcpRelayAssignedIp
         IpAddress,
      sr1645v2PRoutDhcpRelayServerIp
         IpAddress,
      sr1645v2PRoutDhcpRelayDhcpStatus
         INTEGER,
      sr1645v2PRoutDhcpRelayLeaseTime
         TimeTicks
      }

sr1645v2PRoutDhcpRelayTableIx OBJECT-TYPE
   SYNTAX      TableIndex
   MAX-ACCESS  not-accessible
   STATUS      current
   DESCRIPTION
      ""
   ::= {sr1645v2PRoutDhcpRelayEntry 11}

sr1645v2PRoutDhcpRelaySourceIntf OBJECT-TYPE
   SYNTAX      DisplayString
   MAX-ACCESS  read-only
   STATUS      current
   DESCRIPTION
      "Path: router.status.dhcpRelayInfo.sourceIntf"
   ::= {sr1645v2PRoutDhcpRelayEntry 16777216}

sr1645v2PRoutDhcpRelayMac OBJECT-TYPE
   SYNTAX      OCTET STRING
   MAX-ACCESS  read-only
   STATUS      current
   DESCRIPTION
      "Path: router.status.dhcpRelayInfo.mac

       MAC address."
   ::= {sr1645v2PRoutDhcpRelayEntry 33554432}

sr1645v2PRoutDhcpRelayAssignedIp OBJECT-TYPE
   SYNTAX      IpAddress
   MAX-ACCESS  read-only
   STATUS      current
   DESCRIPTION
      "Path: router.status.dhcpRelayInfo.assignedIp"
   ::= {sr1645v2PRoutDhcpRelayEntry 50331648}

sr1645v2PRoutDhcpRelayServerIp OBJECT-TYPE
   SYNTAX      IpAddress
   MAX-ACCESS  read-only
   STATUS      current
   DESCRIPTION
      "Path: router.status.dhcpRelayInfo.serverIp"
   ::= {sr1645v2PRoutDhcpRelayEntry 67108864}

sr1645v2PRoutDhcpRelayDhcpStatus OBJECT-TYPE
   SYNTAX      INTEGER
               {
               discover (1),
               offer (2),
               request (3),
               decline (4),
               ack (5),
               nak (6),
               release (7),
               inform (8),
               idle (9)
               }
   MAX-ACCESS  read-only
   STATUS      current
   DESCRIPTION
      "Path: router.status.dhcpRelayInfo.dhcpStatus

       Possibilities:
               discover   (1)
               offer   (2)
               request   (3)
               decline   (4)
               ack   (5)
               nak   (6)
               release   (7)
               inform   (8)
               idle   (9)"
   ::= {sr1645v2PRoutDhcpRelayEntry 83886080}

sr1645v2PRoutDhcpRelayLeaseTime OBJECT-TYPE
   SYNTAX      TimeTicks
   MAX-ACCESS  read-only
   STATUS      current
   DESCRIPTION
      "Path: router.status.dhcpRelayInfo.leaseTime

       Time in centi-second."
   ::= {sr1645v2PRoutDhcpRelayEntry 117440512}


sr1645v2PRoutDhcpBlacklist OBJECT IDENTIFIER ::= {sr1645v2PRout 75}

sr1645v2PRoutDhcpBlacklistSSCTable OBJECT-TYPE
   SYNTAX      SEQUENCE OF Sr1645v2PRoutDhcpBlacklistEntry
   MAX-ACCESS  not-accessible
   STATUS      current
   DESCRIPTION
      "table containing DHCP Blacklist information"
   ::= {sr1645v2PRoutDhcpBlacklist 1}

sr1645v2PRoutDhcpBlacklistEntry OBJECT-TYPE
   SYNTAX      Sr1645v2PRoutDhcpBlacklistEntry
   MAX-ACCESS  not-accessible
   STATUS      current
   DESCRIPTION
      ""
   INDEX      { sr1645v2PRoutDhcpBlacklistTableIx }
   ::= {sr1645v2PRoutDhcpBlacklistSSCTable 1}

Sr1645v2PRoutDhcpBlacklistEntry ::=
   SEQUENCE
      {
      sr1645v2PRoutDhcpBlacklistTableIx
         TableIndex,
      sr1645v2PRoutDhcpBlacklistIpAddress
         IpAddress,
      sr1645v2PRoutDhcpBlacklistMacAddress
         OCTET STRING,
      sr1645v2PRoutDhcpBlacklistReason
         INTEGER
      }

sr1645v2PRoutDhcpBlacklistTableIx OBJECT-TYPE
   SYNTAX      TableIndex
   MAX-ACCESS  not-accessible
   STATUS      current
   DESCRIPTION
      ""
   ::= {sr1645v2PRoutDhcpBlacklistEntry 11}

sr1645v2PRoutDhcpBlacklistIpAddress OBJECT-TYPE
   SYNTAX      IpAddress
   MAX-ACCESS  read-only
   STATUS      current
   DESCRIPTION
      "Path: router.status.dhcpBlacklist.ipAddress"
   ::= {sr1645v2PRoutDhcpBlacklistEntry 16777216}

sr1645v2PRoutDhcpBlacklistMacAddress OBJECT-TYPE
   SYNTAX      OCTET STRING
   MAX-ACCESS  read-only
   STATUS      current
   DESCRIPTION
      "Path: router.status.dhcpBlacklist.macAddress

       MAC address."
   ::= {sr1645v2PRoutDhcpBlacklistEntry 33554432}

sr1645v2PRoutDhcpBlacklistReason OBJECT-TYPE
   SYNTAX      INTEGER
               {
               none (0),
               arp (1),
               alienAck (2),
               declined (3),
               ping (4),
               networkOrBroadcast (5)
               }
   MAX-ACCESS  read-only
   STATUS      current
   DESCRIPTION
      "Path: router.status.dhcpBlacklist.reason

       Possibilities:
               none   (0)
               arp   (1)
               alienAck   (2)
               declined   (3)
               ping   (4)
               networkOrBroadcast   (5)"
   ::= {sr1645v2PRoutDhcpBlacklistEntry 50331648}


sr1645v2PRoutIgmpTable OBJECT IDENTIFIER ::= {sr1645v2PRout 58}

sr1645v2PRoutIgmpTableSSCTable OBJECT-TYPE
   SYNTAX      SEQUENCE OF Sr1645v2PRoutIgmpTableEntry
   MAX-ACCESS  not-accessible
   STATUS      current
   DESCRIPTION
      "igmpTable"
   ::= {sr1645v2PRoutIgmpTable 1}

sr1645v2PRoutIgmpTableEntry OBJECT-TYPE
   SYNTAX      Sr1645v2PRoutIgmpTableEntry
   MAX-ACCESS  not-accessible
   STATUS      current
   DESCRIPTION
      ""
   INDEX      { sr1645v2PRoutIgmpTableTableIx }
   ::= {sr1645v2PRoutIgmpTableSSCTable 1}

Sr1645v2PRoutIgmpTableEntry ::=
   SEQUENCE
      {
      sr1645v2PRoutIgmpTableTableIx
         TableIndex,
      sr1645v2PRoutIgmpTableMulticast
         IpAddress,
      sr1645v2PRoutIgmpTableMembers
         Integer32,
      sr1645v2PRoutIgmpTableIf
         DisplayString,
      sr1645v2PRoutIgmpTableSourceRecordType
         INTEGER
      }

sr1645v2PRoutIgmpTableTableIx OBJECT-TYPE
   SYNTAX      TableIndex
   MAX-ACCESS  not-accessible
   STATUS      current
   DESCRIPTION
      ""
   ::= {sr1645v2PRoutIgmpTableEntry 11}

sr1645v2PRoutIgmpTableMulticast OBJECT-TYPE
   SYNTAX      IpAddress
   MAX-ACCESS  read-only
   STATUS      current
   DESCRIPTION
      "Path: router.status.igmpTable.multicast"
   ::= {sr1645v2PRoutIgmpTableEntry 16777216}

sr1645v2PRoutIgmpTableMembers OBJECT-TYPE
   SYNTAX      Integer32
   MAX-ACCESS  read-only
   STATUS      current
   DESCRIPTION
      "Path: router.status.igmpTable.members"
   ::= {sr1645v2PRoutIgmpTableEntry 50331648}

sr1645v2PRoutIgmpTableIf OBJECT-TYPE
   SYNTAX      DisplayString
   MAX-ACCESS  read-only
   STATUS      current
   DESCRIPTION
      "Path: router.status.igmpTable.interface"
   ::= {sr1645v2PRoutIgmpTableEntry 33554432}

sr1645v2PRoutIgmpTableSourceRecordType OBJECT-TYPE
   SYNTAX      INTEGER
               {
               exclude (1),
               include (0)
               }
   MAX-ACCESS  read-only
   STATUS      current
   DESCRIPTION
      "Path: router.status.igmpTable.sourceRecordType

       Possibilities:
               exclude   (1)
               include   (0)"
   ::= {sr1645v2PRoutIgmpTableEntry 83886080}

sr1645v2PRoutIgmpTableSourceRecord OBJECT-TYPE
   SYNTAX      SEQUENCE OF Sr1645v2PRoutIgmpTableSourceRecordEntry
   MAX-ACCESS  not-accessible
   STATUS      current
   DESCRIPTION
      ""
   ::= {sr1645v2PRoutIgmpTable 67108864}

sr1645v2PRoutIgmpTableSourceRecordEntry OBJECT-TYPE
   SYNTAX      Sr1645v2PRoutIgmpTableSourceRecordEntry
   MAX-ACCESS  not-accessible
   STATUS      current
   DESCRIPTION
      ""
   INDEX      { sr1645v2PRoutIgmpTableTableIx,
                sr1645v2PRoutIgmpTableSourceRecordTableIx }
   ::= {sr1645v2PRoutIgmpTableSourceRecord 1}

Sr1645v2PRoutIgmpTableSourceRecordEntry ::=
   SEQUENCE
      {
      sr1645v2PRoutIgmpTableSourceRecordTableIx
         TableIndex,
      sr1645v2PRoutIgmpTableSourceRecordIpAddress
         IpAddress
      }

sr1645v2PRoutIgmpTableSourceRecordTableIx OBJECT-TYPE
   SYNTAX      TableIndex
   MAX-ACCESS  not-accessible
   STATUS      current
   DESCRIPTION
      ""
   ::= {sr1645v2PRoutIgmpTableSourceRecordEntry 11}

sr1645v2PRoutIgmpTableSourceRecordIpAddress OBJECT-TYPE
   SYNTAX      IpAddress
   MAX-ACCESS  read-only
   STATUS      current
   DESCRIPTION
      "Path: router.status.igmpTable.sourceRecord.ipAddress"
   ::= {sr1645v2PRoutIgmpTableSourceRecordEntry 16777216}


sr1645v2PRoutInterfaces OBJECT IDENTIFIER ::= {sr1645v2PRout 199}

sr1645v2PRoutInterfacesSSCTable OBJECT-TYPE
   SYNTAX      SEQUENCE OF Sr1645v2PRoutInterfacesEntry
   MAX-ACCESS  not-accessible
   STATUS      current
   DESCRIPTION
      "info on routing interfaces"
   ::= {sr1645v2PRoutInterfaces 1}

sr1645v2PRoutInterfacesEntry OBJECT-TYPE
   SYNTAX      Sr1645v2PRoutInterfacesEntry
   MAX-ACCESS  not-accessible
   STATUS      current
   DESCRIPTION
      ""
   INDEX      { sr1645v2PRoutInterfacesTableIx }
   ::= {sr1645v2PRoutInterfacesSSCTable 1}

Sr1645v2PRoutInterfacesEntry ::=
   SEQUENCE
      {
      sr1645v2PRoutInterfacesTableIx
         TableIndex,
      sr1645v2PRoutInterfacesIfDescr
         DisplayString,
      sr1645v2PRoutInterfacesIfType
         INTEGER,
      sr1645v2PRoutInterfacesIfOperStatus
         INTEGER,
      sr1645v2PRoutInterfacesIfLastChange
         TimeTicks,
      sr1645v2PRoutInterfacesIfLastChangeDate
         DisplayString,
      sr1645v2PRoutInterfacesAddress
         IpAddress,
      sr1645v2PRoutInterfacesMask
         IpAddress
      }

sr1645v2PRoutInterfacesTableIx OBJECT-TYPE
   SYNTAX      TableIndex
   MAX-ACCESS  not-accessible
   STATUS      current
   DESCRIPTION
      ""
   ::= {sr1645v2PRoutInterfacesEntry 11}

sr1645v2PRoutInterfacesIfDescr OBJECT-TYPE
   SYNTAX      DisplayString
   MAX-ACCESS  read-only
   STATUS      current
   DESCRIPTION
      "Path: router.status.interfaces.ifDescr"
   ::= {sr1645v2PRoutInterfacesEntry 1694498816}

sr1645v2PRoutInterfacesIfType OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: router.status.interfaces.ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1645v2PRoutInterfacesEntry 1711276032}

sr1645v2PRoutInterfacesIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: router.status.interfaces.ifOperStatus

       Possibilities:
               up   (1)
               down   (2)
               testing   (3)
               unknown   (4)
               dormant   (5)
               notPresent   (6)
               lowerLayerDown   (7)"
   ::= {sr1645v2PRoutInterfacesEntry 1795162112}

sr1645v2PRoutInterfacesIfLastChange OBJECT-TYPE
   SYNTAX      TimeTicks
   MAX-ACCESS  read-only
   STATUS      current
   DESCRIPTION
      "Path: router.status.interfaces.ifLastChange

       Time in centi-second."
   ::= {sr1645v2PRoutInterfacesEntry 1811939328}

sr1645v2PRoutInterfacesIfLastChangeDate OBJECT-TYPE
   SYNTAX      DisplayString
   MAX-ACCESS  read-only
   STATUS      current
   DESCRIPTION
      "Path: router.status.interfaces.ifLastChangeDate"
   ::= {sr1645v2PRoutInterfacesEntry 3070230528}

sr1645v2PRoutInterfacesAddress OBJECT-TYPE
   SYNTAX      IpAddress
   MAX-ACCESS  read-only
   STATUS      current
   DESCRIPTION
      "Path: router.status.interfaces.address"
   ::= {sr1645v2PRoutInterfacesEntry 2030043136}

sr1645v2PRoutInterfacesMask OBJECT-TYPE
   SYNTAX      IpAddress
   MAX-ACCESS  read-only
   STATUS      current
   DESCRIPTION
      "Path: router.status.interfaces.mask"
   ::= {sr1645v2PRoutInterfacesEntry 2063597568}

sr1645v2PRoutInterfacesSecondaryIp OBJECT-TYPE
   SYNTAX      SEQUENCE OF Sr1645v2PRoutInterfacesSecondaryIpEntry
   MAX-ACCESS  not-accessible
   STATUS      current
   DESCRIPTION
      ""
   ::= {sr1645v2PRoutInterfaces 385875968}

sr1645v2PRoutInterfacesSecondaryIpEntry OBJECT-TYPE
   SYNTAX      Sr1645v2PRoutInterfacesSecondaryIpEntry
   MAX-ACCESS  not-accessible
   STATUS      current
   DESCRIPTION
      ""
   INDEX      { sr1645v2PRoutInterfacesTableIx,
                sr1645v2PRoutInterfacesSecondaryIpTableIx }
   ::= {sr1645v2PRoutInterfacesSecondaryIp 1}

Sr1645v2PRoutInterfacesSecondaryIpEntry ::=
   SEQUENCE
      {
      sr1645v2PRoutInterfacesSecondaryIpTableIx
         TableIndex,
      sr1645v2PRoutInterfacesSecondaryIpAddress
         IpAddress,
      sr1645v2PRoutInterfacesSecondaryIpNetMask
         IpAddress
      }

sr1645v2PRoutInterfacesSecondaryIpTableIx OBJECT-TYPE
   SYNTAX      TableIndex
   MAX-ACCESS  not-accessible
   STATUS      current
   DESCRIPTION
      ""
   ::= {sr1645v2PRoutInterfacesSecondaryIpEntry 11}

sr1645v2PRoutInterfacesSecondaryIpAddress OBJECT-TYPE
   SYNTAX      IpAddress
   MAX-ACCESS  read-only
   STATUS      current
   DESCRIPTION
      "Path: router.status.interfaces.secondaryIp.address"
   ::= {sr1645v2PRoutInterfacesSecondaryIpEntry 2030043136}

sr1645v2PRoutInterfacesSecondaryIpNetMask OBJECT-TYPE
   SYNTAX      IpAddress
   MAX-ACCESS  read-only
   STATUS      current
   DESCRIPTION
      "Path: router.status.interfaces.secondaryIp.netMask"
   ::= {sr1645v2PRoutInterfacesSecondaryIpEntry 2063597568}


sr1645v2PRoutRoutingTable OBJECT IDENTIFIER ::= {sr1645v2PRout 32}

sr1645v2PRoutRoutingTableSSCTable OBJECT-TYPE
   SYNTAX      SEQUENCE OF Sr1645v2PRoutRoutingTableEntry
   MAX-ACCESS  not-accessible
   STATUS      current
   DESCRIPTION
      "routingTable"
   ::= {sr1645v2PRoutRoutingTable 1}

sr1645v2PRoutRoutingTableEntry OBJECT-TYPE
   SYNTAX      Sr1645v2PRoutRoutingTableEntry
   MAX-ACCESS  not-accessible
   STATUS      current
   DESCRIPTION
      ""
   INDEX      { sr1645v2PRoutRoutingTableTableIx }
   ::= {sr1645v2PRoutRoutingTableSSCTable 1}

Sr1645v2PRoutRoutingTableEntry ::=
   SEQUENCE
      {
      sr1645v2PRoutRoutingTableTableIx
         TableIndex,
      sr1645v2PRoutRoutingTableNetwork
         IpAddress,
      sr1645v2PRoutRoutingTableMask
         IpAddress,
      sr1645v2PRoutRoutingTableGateway
         IpAddress,
      sr1645v2PRoutRoutingTableIf
         DisplayString,
      sr1645v2PRoutRoutingTableEncap
         INTEGER,
      sr1645v2PRoutRoutingTableStatus
         INTEGER,
      sr1645v2PRoutRoutingTablePref
         Integer32,
      sr1645v2PRoutRoutingTableType
         INTEGER,
      sr1645v2PRoutRoutingTableMetric
         Integer32,
      sr1645v2PRoutRoutingTableTimeOut
         TimeTicks,
      sr1645v2PRoutRoutingTableTag
         DisplayString
      }

sr1645v2PRoutRoutingTableTableIx OBJECT-TYPE
   SYNTAX      TableIndex
   MAX-ACCESS  not-accessible
   STATUS      current
   DESCRIPTION
      ""
   ::= {sr1645v2PRoutRoutingTableEntry 11}

sr1645v2PRoutRoutingTableNetwork OBJECT-TYPE
   SYNTAX      IpAddress
   MAX-ACCESS  read-only
   STATUS      current
   DESCRIPTION
      "Path: router.status.routingTable.network"
   ::= {sr1645v2PRoutRoutingTableEntry 16777216}

sr1645v2PRoutRoutingTableMask OBJECT-TYPE
   SYNTAX      IpAddress
   MAX-ACCESS  read-only
   STATUS      current
   DESCRIPTION
      "Path: router.status.routingTable.mask"
   ::= {sr1645v2PRoutRoutingTableEntry 33554432}

sr1645v2PRoutRoutingTableGateway OBJECT-TYPE
   SYNTAX      IpAddress
   MAX-ACCESS  read-only
   STATUS      current
   DESCRIPTION
      "Path: router.status.routingTable.gateway"
   ::= {sr1645v2PRoutRoutingTableEntry 50331648}

sr1645v2PRoutRoutingTableIf OBJECT-TYPE
   SYNTAX      DisplayString
   MAX-ACCESS  read-only
   STATUS      current
   DESCRIPTION
      "Path: router.status.routingTable.interface"
   ::= {sr1645v2PRoutRoutingTableEntry 67108864}

sr1645v2PRoutRoutingTableEncap OBJECT-TYPE
   SYNTAX      INTEGER
               {
               none (0),
               framemrelay (1),
               ppp (2),
               ethernet (3),
               x25 (4),
               atm (5),
               policysdependent (6),
               pppoA (7),
               pppoE (8),
               sasdependent (9),
               gre (10)
               }
   MAX-ACCESS  read-only
   STATUS      current
   DESCRIPTION
      "Path: router.status.routingTable.encapsulation

       Possibilities:
               none   (0)
               frame-relay   (1)
               ppp   (2)
               ethernet   (3)
               x25   (4)
               atm   (5)
               policy dependent   (6)
               pppoA   (7)
               pppoE   (8)
               sa dependent   (9)
               gre   (10)"
   ::= {sr1645v2PRoutRoutingTableEntry 83886080}

sr1645v2PRoutRoutingTableStatus OBJECT-TYPE
   SYNTAX      INTEGER
               {
               down (0),
               up (1),
               discard (2),
               spoofing (3),
               holdDown (4),
               closed (5)
               }
   MAX-ACCESS  read-only
   STATUS      current
   DESCRIPTION
      "Path: router.status.routingTable.status

       Possibilities:
               down   (0)
               up   (1)
               discard   (2)
               spoofing   (3)
               holdDown   (4)
               closed   (5)"
   ::= {sr1645v2PRoutRoutingTableEntry 100663296}

sr1645v2PRoutRoutingTablePref OBJECT-TYPE
   SYNTAX      Integer32
   MAX-ACCESS  read-only
   STATUS      current
   DESCRIPTION
      "Path: router.status.routingTable.preference"
   ::= {sr1645v2PRoutRoutingTableEntry 117440512}

sr1645v2PRoutRoutingTableType OBJECT-TYPE
   SYNTAX      INTEGER
               {
               internal (0),
               local (1),
               host (2),
               static (3),
               rip (4),
               ospf (5),
               bgp (6),
               float (7),
               dial (8),
               policy (9),
               nat (10),
               radius (11),
               orchid (12),
               reject (13),
               ipsec (14),
               floatIpsec (15),
               mgmtProxy (16),
               ipV6natpt (17),
               pim (18),
               none (19),
               fixedDial (20),
               fixedOutPolicy (21),
               fixedInterface (22),
               fixedIpsec (23),
               staticTimed (24),
               staticTracked (25),
               everyCat (26)
               }
   MAX-ACCESS  read-only
   STATUS      current
   DESCRIPTION
      "Path: router.status.routingTable.type

       Possibilities:
               internal   (0)
               local   (1)
               host   (2)
               static   (3)
               rip   (4)
               ospf   (5)
               bgp   (6)
               float   (7)
               dial   (8)
               policy   (9)
               nat   (10)
               radius   (11)
               orchid   (12)
               reject   (13)
               ipsec   (14)
               floatIpsec   (15)
               mgmtProxy   (16)
               ipV6natpt   (17)
               pim   (18)
               none   (19)
               fixedDial   (20)
               fixedOutPolicy   (21)
               fixedInterface   (22)
               fixedIpsec   (23)
               staticTimed   (24)
               staticTracked   (25)
               everyCat   (26)"
   ::= {sr1645v2PRoutRoutingTableEntry 134217728}

sr1645v2PRoutRoutingTableMetric OBJECT-TYPE
   SYNTAX      Integer32
   MAX-ACCESS  read-only
   STATUS      current
   DESCRIPTION
      "Path: router.status.routingTable.metric"
   ::= {sr1645v2PRoutRoutingTableEntry 150994944}

sr1645v2PRoutRoutingTableTimeOut OBJECT-TYPE
   SYNTAX      TimeTicks
   MAX-ACCESS  read-only
   STATUS      current
   DESCRIPTION
      "Path: router.status.routingTable.timeOut

       Time in centi-second."
   ::= {sr1645v2PRoutRoutingTableEntry 167772160}

sr1645v2PRoutRoutingTableTag OBJECT-TYPE
   SYNTAX      DisplayString
   MAX-ACCESS  read-only
   STATUS      current
   DESCRIPTION
      "Path: router.status.routingTable.tag"
   ::= {sr1645v2PRoutRoutingTableEntry 201326592}


sr1645v2PRoutRadius OBJECT IDENTIFIER ::= {sr1645v2PRout 61}

sr1645v2PRoutRadiusSSC OBJECT IDENTIFIER ::= {sr1645v2PRoutRadius 1}

sr1645v2PRoutRadiusEntry OBJECT IDENTIFIER ::= {sr1645v2PRoutRadiusSSC 1}

sr1645v2PRoutRadiusAuthServer OBJECT-TYPE
   SYNTAX      IpAddress
   MAX-ACCESS  read-only
   STATUS      current
   DESCRIPTION
      "Path: router.status.radius.authServer"
   ::= {sr1645v2PRoutRadiusEntry 16777216}

sr1645v2PRoutRadiusAcctServer OBJECT-TYPE
   SYNTAX      IpAddress
   MAX-ACCESS  read-only
   STATUS      current
   DESCRIPTION
      "Path: router.status.radius.acctServer"
   ::= {sr1645v2PRoutRadiusEntry 50331648}

sr1645v2PRoutRadiusPendingRequests OBJECT-TYPE
   SYNTAX      Integer32
   MAX-ACCESS  read-only
   STATUS      current
   DESCRIPTION
      "Path: router.status.radius.pendingRequests"
   ::= {sr1645v2PRoutRadiusEntry 33554432}


sr1645v2PRoutDnsCache OBJECT IDENTIFIER ::= {sr1645v2PRout 65}

sr1645v2PRoutDnsCacheSSCTable OBJECT-TYPE
   SYNTAX      SEQUENCE OF Sr1645v2PRoutDnsCacheEntry
   MAX-ACCESS  not-accessible
   STATUS      current
   DESCRIPTION
      "DNS cache table"
   ::= {sr1645v2PRoutDnsCache 1}

sr1645v2PRoutDnsCacheEntry OBJECT-TYPE
   SYNTAX      Sr1645v2PRoutDnsCacheEntry
   MAX-ACCESS  not-accessible
   STATUS      current
   DESCRIPTION
      ""
   INDEX      { sr1645v2PRoutDnsCacheTableIx }
   ::= {sr1645v2PRoutDnsCacheSSCTable 1}

Sr1645v2PRoutDnsCacheEntry ::=
   SEQUENCE
      {
      sr1645v2PRoutDnsCacheTableIx
         TableIndex,
      sr1645v2PRoutDnsCacheIpAddress
         IpAddress,
      sr1645v2PRoutDnsCacheIpV6Address
         Ipv6Address,
      sr1645v2PRoutDnsCacheHostname
         DisplayString,
      sr1645v2PRoutDnsCacheTtl
         TimeTicks,
      sr1645v2PRoutDnsCacheInfiniteTimeOut
         INTEGER,
      sr1645v2PRoutDnsCacheMatches
         Counter32
      }

sr1645v2PRoutDnsCacheTableIx OBJECT-TYPE
   SYNTAX      TableIndex
   MAX-ACCESS  not-accessible
   STATUS      current
   DESCRIPTION
      ""
   ::= {sr1645v2PRoutDnsCacheEntry 11}

sr1645v2PRoutDnsCacheIpAddress OBJECT-TYPE
   SYNTAX      IpAddress
   MAX-ACCESS  read-only
   STATUS      current
   DESCRIPTION
      "Path: router.status.dnsCache.ipAddress"
   ::= {sr1645v2PRoutDnsCacheEntry 16777216}

sr1645v2PRoutDnsCacheIpV6Address OBJECT-TYPE
   SYNTAX      Ipv6Address
   MAX-ACCESS  read-only
   STATUS      current
   DESCRIPTION
      "Path: router.status.dnsCache.ipV6Address

       ipv6 address"
   ::= {sr1645v2PRoutDnsCacheEntry 83886080}

sr1645v2PRoutDnsCacheHostname OBJECT-TYPE
   SYNTAX      DisplayString
   MAX-ACCESS  read-only
   STATUS      current
   DESCRIPTION
      "Path: router.status.dnsCache.hostname"
   ::= {sr1645v2PRoutDnsCacheEntry 33554432}

sr1645v2PRoutDnsCacheTtl OBJECT-TYPE
   SYNTAX      TimeTicks
   MAX-ACCESS  read-only
   STATUS      current
   DESCRIPTION
      "Path: router.status.dnsCache.ttl

       Time in centi-second."
   ::= {sr1645v2PRoutDnsCacheEntry 50331648}

sr1645v2PRoutDnsCacheInfiniteTimeOut OBJECT-TYPE
   SYNTAX      INTEGER
               {
               disabled (0),
               enabled (1),
               static (2)
               }
   MAX-ACCESS  read-only
   STATUS      current
   DESCRIPTION
      "Path: router.status.dnsCache.infiniteTimeOut

       Possibilities:
               disabled   (0)
               enabled   (1)
               static   (2)"
   ::= {sr1645v2PRoutDnsCacheEntry 67108864}

sr1645v2PRoutDnsCacheMatches OBJECT-TYPE
   SYNTAX      Counter32
   MAX-ACCESS  read-only
   STATUS      current
   DESCRIPTION
      "Path: router.status.dnsCache.matches

       32 bit unsigned wrappable counter."
   ::= {sr1645v2PRoutDnsCacheEntry 100663296}


sr1645v2PRoutDnsServers OBJECT IDENTIFIER ::= {sr1645v2PRout 66}

sr1645v2PRoutDnsServersSSCTable OBJECT-TYPE
   SYNTAX      SEQUENCE OF Sr1645v2PRoutDnsServersEntry
   MAX-ACCESS  not-accessible
   STATUS      current
   DESCRIPTION
      "DNS server list"
   ::= {sr1645v2PRoutDnsServers 1}

sr1645v2PRoutDnsServersEntry OBJECT-TYPE
   SYNTAX      Sr1645v2PRoutDnsServersEntry
   MAX-ACCESS  not-accessible
   STATUS      current
   DESCRIPTION
      ""
   INDEX      { sr1645v2PRoutDnsServersTableIx }
   ::= {sr1645v2PRoutDnsServersSSCTable 1}

Sr1645v2PRoutDnsServersEntry ::=
   SEQUENCE
      {
      sr1645v2PRoutDnsServersTableIx
         TableIndex,
      sr1645v2PRoutDnsServersPrimaryDns
         IpAddress,
      sr1645v2PRoutDnsServersSecondaryDns
         IpAddress,
      sr1645v2PRoutDnsServersType
         INTEGER,
      sr1645v2PRoutDnsServersRcvdInterface
         DisplayString,
      sr1645v2PRoutDnsServersPreference
         Integer32,
      sr1645v2PRoutDnsServersStatus
         INTEGER
      }

sr1645v2PRoutDnsServersTableIx OBJECT-TYPE
   SYNTAX      TableIndex
   MAX-ACCESS  not-accessible
   STATUS      current
   DESCRIPTION
      ""
   ::= {sr1645v2PRoutDnsServersEntry 11}

sr1645v2PRoutDnsServersPrimaryDns OBJECT-TYPE
   SYNTAX      IpAddress
   MAX-ACCESS  read-only
   STATUS      current
   DESCRIPTION
      "Path: router.status.dnsServers.primaryDns"
   ::= {sr1645v2PRoutDnsServersEntry 16777216}

sr1645v2PRoutDnsServersSecondaryDns OBJECT-TYPE
   SYNTAX      IpAddress
   MAX-ACCESS  read-only
   STATUS      current
   DESCRIPTION
      "Path: router.status.dnsServers.secondaryDns"
   ::= {sr1645v2PRoutDnsServersEntry 33554432}

sr1645v2PRoutDnsServersType OBJECT-TYPE
   SYNTAX      INTEGER
               {
               static (0),
               dhcp (1),
               ppp (2)
               }
   MAX-ACCESS  read-only
   STATUS      current
   DESCRIPTION
      "Path: router.status.dnsServers.type

       Possibilities:
               static   (0)
               dhcp   (1)
               ppp   (2)"
   ::= {sr1645v2PRoutDnsServersEntry 50331648}

sr1645v2PRoutDnsServersRcvdInterface OBJECT-TYPE
   SYNTAX      DisplayString
   MAX-ACCESS  read-only
   STATUS      current
   DESCRIPTION
      "Path: router.status.dnsServers.rcvdInterface"
   ::= {sr1645v2PRoutDnsServersEntry 67108864}

sr1645v2PRoutDnsServersPreference OBJECT-TYPE
   SYNTAX      Integer32
   MAX-ACCESS  read-only
   STATUS      current
   DESCRIPTION
      "Path: router.status.dnsServers.preference"
   ::= {sr1645v2PRoutDnsServersEntry 83886080}

sr1645v2PRoutDnsServersStatus OBJECT-TYPE
   SYNTAX      INTEGER
               {
               primActive (2),
               secActive (3),
               inactive (5),
               failed (6)
               }
   MAX-ACCESS  read-only
   STATUS      current
   DESCRIPTION
      "Path: router.status.dnsServers.status

       Possibilities:
               primActive   (2)
               secActive   (3)
               inactive   (5)
               failed   (6)"
   ::= {sr1645v2PRoutDnsServersEntry 100663296}


sr1645v2PRoutDnsDomains OBJECT IDENTIFIER ::= {sr1645v2PRout 72}

sr1645v2PRoutDnsDomainsSSCTable OBJECT-TYPE
   SYNTAX      SEQUENCE OF Sr1645v2PRoutDnsDomainsEntry
   MAX-ACCESS  not-accessible
   STATUS      current
   DESCRIPTION
      "DNS domain table"
   ::= {sr1645v2PRoutDnsDomains 1}

sr1645v2PRoutDnsDomainsEntry OBJECT-TYPE
   SYNTAX      Sr1645v2PRoutDnsDomainsEntry
   MAX-ACCESS  not-accessible
   STATUS      current
   DESCRIPTION
      ""
   INDEX      { sr1645v2PRoutDnsDomainsTableIx }
   ::= {sr1645v2PRoutDnsDomainsSSCTable 1}

Sr1645v2PRoutDnsDomainsEntry ::=
   SEQUENCE
      {
      sr1645v2PRoutDnsDomainsTableIx
         TableIndex,
      sr1645v2PRoutDnsDomainsName
         DisplayString,
      sr1645v2PRoutDnsDomainsType
         INTEGER,
      sr1645v2PRoutDnsDomainsRcvdInterface
         DisplayString
      }

sr1645v2PRoutDnsDomainsTableIx OBJECT-TYPE
   SYNTAX      TableIndex
   MAX-ACCESS  not-accessible
   STATUS      current
   DESCRIPTION
      ""
   ::= {sr1645v2PRoutDnsDomainsEntry 11}

sr1645v2PRoutDnsDomainsName OBJECT-TYPE
   SYNTAX      DisplayString
   MAX-ACCESS  read-only
   STATUS      current
   DESCRIPTION
      "Path: router.status.dnsDomains.name"
   ::= {sr1645v2PRoutDnsDomainsEntry 16777216}

sr1645v2PRoutDnsDomainsType OBJECT-TYPE
   SYNTAX      INTEGER
               {
               static (0),
               dhcp (1),
               ppp (2)
               }
   MAX-ACCESS  read-only
   STATUS      current
   DESCRIPTION
      "Path: router.status.dnsDomains.type

       Possibilities:
               static   (0)
               dhcp   (1)
               ppp   (2)"
   ::= {sr1645v2PRoutDnsDomainsEntry 33554432}

sr1645v2PRoutDnsDomainsRcvdInterface OBJECT-TYPE
   SYNTAX      DisplayString
   MAX-ACCESS  read-only
   STATUS      current
   DESCRIPTION
      "Path: router.status.dnsDomains.rcvdInterface"
   ::= {sr1645v2PRoutDnsDomainsEntry 50331648}


sr1645v2PRoutAddrPools OBJECT IDENTIFIER ::= {sr1645v2PRout 109}

sr1645v2PRoutAddrPoolsSSCTable OBJECT-TYPE
   SYNTAX      SEQUENCE OF Sr1645v2PRoutAddrPoolsEntry
   MAX-ACCESS  not-accessible
   STATUS      current
   DESCRIPTION
      "ip pool status"
   ::= {sr1645v2PRoutAddrPools 1}

sr1645v2PRoutAddrPoolsEntry OBJECT-TYPE
   SYNTAX      Sr1645v2PRoutAddrPoolsEntry
   MAX-ACCESS  not-accessible
   STATUS      current
   DESCRIPTION
      ""
   INDEX      { sr1645v2PRoutAddrPoolsTableIx }
   ::= {sr1645v2PRoutAddrPoolsSSCTable 1}

Sr1645v2PRoutAddrPoolsEntry ::=
   SEQUENCE
      {
      sr1645v2PRoutAddrPoolsTableIx
         TableIndex,
      sr1645v2PRoutAddrPoolsName
         DisplayString,
      sr1645v2PRoutAddrPoolsType
         INTEGER,
      sr1645v2PRoutAddrPoolsNrOfAddresses
         Counter32,
      sr1645v2PRoutAddrPoolsAvailAddresses
         Counter32
      }

sr1645v2PRoutAddrPoolsTableIx OBJECT-TYPE
   SYNTAX      TableIndex
   MAX-ACCESS  not-accessible
   STATUS      current
   DESCRIPTION
      ""
   ::= {sr1645v2PRoutAddrPoolsEntry 11}

sr1645v2PRoutAddrPoolsName OBJECT-TYPE
   SYNTAX      DisplayString
   MAX-ACCESS  read-only
   STATUS      current
   DESCRIPTION
      "Path: router.status.addrPools.name"
   ::= {sr1645v2PRoutAddrPoolsEntry 16777216}

sr1645v2PRoutAddrPoolsType OBJECT-TYPE
   SYNTAX      INTEGER
               {
               list (1),
               interval (2)
               }
   MAX-ACCESS  read-only
   STATUS      current
   DESCRIPTION
      "Path: router.status.addrPools.type

       Possibilities:
               list   (1)
               interval   (2)"
   ::= {sr1645v2PRoutAddrPoolsEntry 33554432}

sr1645v2PRoutAddrPoolsNrOfAddresses OBJECT-TYPE
   SYNTAX      Counter32
   MAX-ACCESS  read-only
   STATUS      current
   DESCRIPTION
      "Path: router.status.addrPools.nrOfAddresses

       32 bit unsigned wrappable counter."
   ::= {sr1645v2PRoutAddrPoolsEntry 50331648}

sr1645v2PRoutAddrPoolsAvailAddresses OBJECT-TYPE
   SYNTAX      Counter32
   MAX-ACCESS  read-only
   STATUS      current
   DESCRIPTION
      "Path: router.status.addrPools.availAddresses

       32 bit unsigned wrappable counter."
   ::= {sr1645v2PRoutAddrPoolsEntry 67108864}


sr1645v2PRoutPoolReservations OBJECT IDENTIFIER ::= {sr1645v2PRout 103}

sr1645v2PRoutPoolReservationsSSCTable OBJECT-TYPE
   SYNTAX      SEQUENCE OF Sr1645v2PRoutPoolReservationsEntry
   MAX-ACCESS  not-accessible
   STATUS      current
   DESCRIPTION
      "ip pool occupied addresses"
   ::= {sr1645v2PRoutPoolReservations 1}

sr1645v2PRoutPoolReservationsEntry OBJECT-TYPE
   SYNTAX      Sr1645v2PRoutPoolReservationsEntry
   MAX-ACCESS  not-accessible
   STATUS      current
   DESCRIPTION
      ""
   INDEX      { sr1645v2PRoutPoolReservationsTableIx }
   ::= {sr1645v2PRoutPoolReservationsSSCTable 1}

Sr1645v2PRoutPoolReservationsEntry ::=
   SEQUENCE
      {
      sr1645v2PRoutPoolReservationsTableIx
         TableIndex,
      sr1645v2PRoutPoolReservationsName
         DisplayString,
      sr1645v2PRoutPoolReservationsType
         INTEGER,
      sr1645v2PRoutPoolReservationsLocal
         IpAddress,
      sr1645v2PRoutPoolReservationsRemote
         IpAddress,
      sr1645v2PRoutPoolReservationsNetMask
         IpAddress,
      sr1645v2PRoutPoolReservationsInterface
         DisplayString
      }

sr1645v2PRoutPoolReservationsTableIx OBJECT-TYPE
   SYNTAX      TableIndex
   MAX-ACCESS  not-accessible
   STATUS      current
   DESCRIPTION
      ""
   ::= {sr1645v2PRoutPoolReservationsEntry 11}

sr1645v2PRoutPoolReservationsName OBJECT-TYPE
   SYNTAX      DisplayString
   MAX-ACCESS  read-only
   STATUS      current
   DESCRIPTION
      "Path: router.status.poolReservations.name"
   ::= {sr1645v2PRoutPoolReservationsEntry 16777216}

sr1645v2PRoutPoolReservationsType OBJECT-TYPE
   SYNTAX      INTEGER
               {
               list (1),
               interval (2)
               }
   MAX-ACCESS  read-only
   STATUS      current
   DESCRIPTION
      "Path: router.status.poolReservations.type

       Possibilities:
               list   (1)
               interval   (2)"
   ::= {sr1645v2PRoutPoolReservationsEntry 33554432}

sr1645v2PRoutPoolReservationsLocal OBJECT-TYPE
   SYNTAX      IpAddress
   MAX-ACCESS  read-only
   STATUS      current
   DESCRIPTION
      "Path: router.status.poolReservations.local"
   ::= {sr1645v2PRoutPoolReservationsEntry 50331648}

sr1645v2PRoutPoolReservationsRemote OBJECT-TYPE
   SYNTAX      IpAddress
   MAX-ACCESS  read-only
   STATUS      current
   DESCRIPTION
      "Path: router.status.poolReservations.remote"
   ::= {sr1645v2PRoutPoolReservationsEntry 67108864}

sr1645v2PRoutPoolReservationsNetMask OBJECT-TYPE
   SYNTAX      IpAddress
   MAX-ACCESS  read-only
   STATUS      current
   DESCRIPTION
      "Path: router.status.poolReservations.netMask"
   ::= {sr1645v2PRoutPoolReservationsEntry 83886080}

sr1645v2PRoutPoolReservationsInterface OBJECT-TYPE
   SYNTAX      DisplayString
   MAX-ACCESS  read-only
   STATUS      current
   DESCRIPTION
      "Path: router.status.poolReservations.interface"
   ::= {sr1645v2PRoutPoolReservationsEntry 100663296}


sr1645v2PRoutDnsUpdCli OBJECT IDENTIFIER ::= {sr1645v2PRout 82}

sr1645v2PRoutDnsUpdCliSSCTable OBJECT-TYPE
   SYNTAX      SEQUENCE OF Sr1645v2PRoutDnsUpdCliEntry
   MAX-ACCESS  not-accessible
   STATUS      current
   DESCRIPTION
      "DNS Update Client status table"
   ::= {sr1645v2PRoutDnsUpdCli 1}

sr1645v2PRoutDnsUpdCliEntry OBJECT-TYPE
   SYNTAX      Sr1645v2PRoutDnsUpdCliEntry
   MAX-ACCESS  not-accessible
   STATUS      current
   DESCRIPTION
      ""
   INDEX      { sr1645v2PRoutDnsUpdCliTableIx }
   ::= {sr1645v2PRoutDnsUpdCliSSCTable 1}

Sr1645v2PRoutDnsUpdCliEntry ::=
   SEQUENCE
      {
      sr1645v2PRoutDnsUpdCliTableIx
         TableIndex,
      sr1645v2PRoutDnsUpdCliName
         DisplayString,
      sr1645v2PRoutDnsUpdCliDnsProvDynDnsState
         INTEGER,
      sr1645v2PRoutDnsUpdCliDnsProvDynDnsTcpSocket
         INTEGER,
      sr1645v2PRoutDnsUpdCliDnsProvDynDnsUpdateReturnCode
         DisplayString,
      sr1645v2PRoutDnsUpdCliDnsProvDynDnsHostName
         DisplayString,
      sr1645v2PRoutDnsUpdCliDnsProvDynDnsUpdateServer
         DisplayString,
      sr1645v2PRoutDnsUpdCliDnsProvDynDnsLastUpdateIpAddress
         IpAddress,
      sr1645v2PRoutDnsUpdCliDnsProvDynDnsLastUpdateTimePassed
         TimeTicks
      }

sr1645v2PRoutDnsUpdCliTableIx OBJECT-TYPE
   SYNTAX      TableIndex
   MAX-ACCESS  not-accessible
   STATUS      current
   DESCRIPTION
      ""
   ::= {sr1645v2PRoutDnsUpdCliEntry 11}

sr1645v2PRoutDnsUpdCliName OBJECT-TYPE
   SYNTAX      DisplayString
   MAX-ACCESS  read-only
   STATUS      current
   DESCRIPTION
      "Path: router.status.dnsUpdateClient.name"
   ::= {sr1645v2PRoutDnsUpdCliEntry 16777216}

sr1645v2PRoutDnsUpdCliDnsProvDynDnsState OBJECT-TYPE
   SYNTAX      INTEGER
               {
               disabled (0),
               enabledIdle (1),
               updating (2),
               stopped (3),
               unbound (4)
               }
   MAX-ACCESS  read-only
   STATUS      current
   DESCRIPTION
      "Path: router.status.dnsUpdateClient.dnsProvider.dynDns.state

       Possibilities:
               disabled   (0)
               enabledIdle   (1)
               updating   (2)
               stopped   (3)
               unbound   (4)"
   ::= {sr1645v2PRoutDnsUpdCliEntry 33620224}

sr1645v2PRoutDnsUpdCliDnsProvDynDnsTcpSocket OBJECT-TYPE
   SYNTAX      INTEGER
               {
               closed (0),
               listen (1),
               synSent (2),
               synReceived (3),
               established (4),
               finWait1 (5),
               finWait2 (6),
               closing (7),
               timeWait (8),
               closeWait (9),
               lastAck (10),
               notFound (11),
               dnsReqSent (12)
               }
   MAX-ACCESS  read-only
   STATUS      current
   DESCRIPTION
      "Path: router.status.dnsUpdateClient.dnsProvider.dynDns.tcpSocket

       Possibilities:
               closed   (0)
               listen   (1)
               synSent   (2)
               synReceived   (3)
               established   (4)
               finWait1   (5)
               finWait2   (6)
               closing   (7)
               timeWait   (8)
               closeWait   (9)
               lastAck   (10)
               notFound   (11)
               dnsReqSent   (12)"
   ::= {sr1645v2PRoutDnsUpdCliEntry 33620480}

sr1645v2PRoutDnsUpdCliDnsProvDynDnsUpdateReturnCode OBJECT-TYPE
   SYNTAX      DisplayString
   MAX-ACCESS  read-only
   STATUS      current
   DESCRIPTION
      "Path: router.status.dnsUpdateClient.dnsProvider.dynDns.updateReturnCode"
   ::= {sr1645v2PRoutDnsUpdCliEntry 33620736}

sr1645v2PRoutDnsUpdCliDnsProvDynDnsHostName OBJECT-TYPE
   SYNTAX      DisplayString
   MAX-ACCESS  read-only
   STATUS      current
   DESCRIPTION
      "Path: router.status.dnsUpdateClient.dnsProvider.dynDns.hostName"
   ::= {sr1645v2PRoutDnsUpdCliEntry 33620992}

sr1645v2PRoutDnsUpdCliDnsProvDynDnsUpdateServer OBJECT-TYPE
   SYNTAX      DisplayString
   MAX-ACCESS  read-only
   STATUS      current
   DESCRIPTION
      "Path: router.status.dnsUpdateClient.dnsProvider.dynDns.updateServer"
   ::= {sr1645v2PRoutDnsUpdCliEntry 33621248}

sr1645v2PRoutDnsUpdCliDnsProvDynDnsLastUpdateIpAddress OBJECT-TYPE
   SYNTAX      IpAddress
   MAX-ACCESS  read-only
   STATUS      current
   DESCRIPTION
      "Path: router.status.dnsUpdateClient.dnsProvider.dynDns.lastUpdateIpAddress"
   ::= {sr1645v2PRoutDnsUpdCliEntry 33621504}

sr1645v2PRoutDnsUpdCliDnsProvDynDnsLastUpdateTimePassed OBJECT-TYPE
   SYNTAX      TimeTicks
   MAX-ACCESS  read-only
   STATUS      current
   DESCRIPTION
      "Path: router.status.dnsUpdateClient.dnsProvider.dynDns.lastUpdateTimePassed

       Time in centi-second."
   ::= {sr1645v2PRoutDnsUpdCliEntry 33621760}



pr1645v2PRout OBJECT IDENTIFIER ::= {r1645v2PRout 12}


pr1645v2PRoutQm OBJECT IDENTIFIER ::= {pr1645v2PRout 79}

pr1645v2PRoutQmSSCTable OBJECT-TYPE
   SYNTAX      SEQUENCE OF Pr1645v2PRoutQmEntry
   MAX-ACCESS  not-accessible
   STATUS      current
   DESCRIPTION
      "quality monitor"
   ::= {pr1645v2PRoutQm 1}

pr1645v2PRoutQmEntry OBJECT-TYPE
   SYNTAX      Pr1645v2PRoutQmEntry
   MAX-ACCESS  not-accessible
   STATUS      current
   DESCRIPTION
      ""
   INDEX      { pr1645v2PRoutQmTableIx }
   ::= {pr1645v2PRoutQmSSCTable 1}

Pr1645v2PRoutQmEntry ::=
   SEQUENCE
      {
      pr1645v2PRoutQmTableIx
         TableIndex,
      pr1645v2PRoutQmName
         DisplayString,
      pr1645v2PRoutQmStatus
         INTEGER,
      pr1645v2PRoutQmIpAddress
         IpAddress,
      pr1645v2PRoutQmHostName
         DisplayString,
      pr1645v2PRoutQmSourceIp
         IpAddress,
      pr1645v2PRoutQmSourceId
         Gauge32,
      pr1645v2PRoutQmNbrTxPckt
         Counter32,
      pr1645v2PRoutQmNbrRxPckt
         Counter32,
      pr1645v2PRoutQmError
         Counter32,
      pr1645v2PRoutQmDelay
         Integer32,
      pr1645v2PRoutQmJitter
         Integer32,
      pr1645v2PRoutQmLoss
         Counter32,
      pr1645v2PRoutQmLossDelay
         Counter32,
      pr1645v2PRoutQmDelayMin
         Integer32,
      pr1645v2PRoutQmDelayAvrg
         Integer32,
      pr1645v2PRoutQmDelayMax
         Integer32,
      pr1645v2PRoutQmDelayBinsType
         INTEGER,
      pr1645v2PRoutQmDelayBinsMinMin
         Counter32,
      pr1645v2PRoutQmDelayBinsMin
         Integer32,
      pr1645v2PRoutQmDelayBinsMinBin1
         Counter32,
      pr1645v2PRoutQmDelayBinsBin2
         Counter32,
      pr1645v2PRoutQmDelayBinsBin3
         Counter32,
      pr1645v2PRoutQmDelayBinsBin4
         Counter32,
      pr1645v2PRoutQmDelayBinsBin5
         Counter32,
      pr1645v2PRoutQmDelayBinsBin6
         Counter32,
      pr1645v2PRoutQmDelayBinsBin7
         Counter32,
      pr1645v2PRoutQmDelayBinsMaxBin8
         Counter32,
      pr1645v2PRoutQmDelayBinsMax
         Integer32,
      pr1645v2PRoutQmDelayBinsPlusMax
         Counter32,
      pr1645v2PRoutQmJitterNegMax
         Integer32,
      pr1645v2PRoutQmJitterAvrg
         Integer32,
      pr1645v2PRoutQmJitterPosMax
         Integer32,
      pr1645v2PRoutQmJitterBinsType
         INTEGER,
      pr1645v2PRoutQmJitterBinsMinMin
         Counter32,
      pr1645v2PRoutQmJitterBinsMin
         Integer32,
      pr1645v2PRoutQmJitterBinsMinBin1
         Counter32,
      pr1645v2PRoutQmJitterBinsBin2
         Counter32,
      pr1645v2PRoutQmJitterBinsBin3
         Counter32,
      pr1645v2PRoutQmJitterBinsBin4
         Counter32,
      pr1645v2PRoutQmJitterBinsBin5
         Counter32,
      pr1645v2PRoutQmJitterBinsBin6
         Counter32,
      pr1645v2PRoutQmJitterBinsBin7
         Counter32,
      pr1645v2PRoutQmJitterBinsMaxBin8
         Counter32,
      pr1645v2PRoutQmJitterBinsMax
         Integer32,
      pr1645v2PRoutQmJitterBinsPlusMax
         Counter32,
      pr1645v2PRoutQmBfdCtrlOutPkts
         Integer32,
      pr1645v2PRoutQmBfdCtrlInPkts
         Integer32,
      pr1645v2PRoutQmBfdCtrlLocalState
         INTEGER,
      pr1645v2PRoutQmBfdCtrlLocalDiscriminator
         Integer32,
      pr1645v2PRoutQmBfdCtrlLocalTxInterval
         Integer32,
      pr1645v2PRoutQmBfdCtrlLocalMinTxInterval
         Integer32,
      pr1645v2PRoutQmBfdCtrlLocalDetectMultiplier
         Integer32,
      pr1645v2PRoutQmBfdCtrlRemoteState
         INTEGER,
      pr1645v2PRoutQmBfdCtrlRemoteDiscriminator
         Integer32,
      pr1645v2PRoutQmBfdCtrlRemoteMinTxInterval
         Integer32,
      pr1645v2PRoutQmBfdCtrlRemoteDetectMultiplier
         Integer32,
      pr1645v2PRoutQmBfdCtrlRemoteMinRxInterval
         Integer32,
      pr1645v2PRoutQmBfdCtrlRemoteMinRxEchoInterval
         Integer32,
      pr1645v2PRoutQmUpDownStatus
         INTEGER,
      pr1645v2PRoutQmUpDownLossUp
         Counter32,
      pr1645v2PRoutQmUpDownLossDelayUp
         Counter32,
      pr1645v2PRoutQmUpDownDelayUpMin
         Integer32,
      pr1645v2PRoutQmUpDownDelayUpAvrg
         Integer32,
      pr1645v2PRoutQmUpDownDelayUpMax
         Integer32,
      pr1645v2PRoutQmUpDownDelayUpBinsType
         INTEGER,
      pr1645v2PRoutQmUpDownDelayUpBinsMinMin
         Counter32,
      pr1645v2PRoutQmUpDownDelayUpBinsMin
         Integer32,
      pr1645v2PRoutQmUpDownDelayUpBinsMinBin1
         Counter32,
      pr1645v2PRoutQmUpDownDelayUpBinsBin2
         Counter32,
      pr1645v2PRoutQmUpDownDelayUpBinsBin3
         Counter32,
      pr1645v2PRoutQmUpDownDelayUpBinsBin4
         Counter32,
      pr1645v2PRoutQmUpDownDelayUpBinsBin5
         Counter32,
      pr1645v2PRoutQmUpDownDelayUpBinsBin6
         Counter32,
      pr1645v2PRoutQmUpDownDelayUpBinsBin7
         Counter32,
      pr1645v2PRoutQmUpDownDelayUpBinsMaxBin8
         Counter32,
      pr1645v2PRoutQmUpDownDelayUpBinsMax
         Integer32,
      pr1645v2PRoutQmUpDownDelayUpBinsPlusMax
         Counter32,
      pr1645v2PRoutQmUpDownJitterUp
         Integer32,
      pr1645v2PRoutQmUpDownJitterUpNegMax
         Integer32,
      pr1645v2PRoutQmUpDownJitterUpAvrg
         Integer32,
      pr1645v2PRoutQmUpDownJitterUpPosMax
         Integer32,
      pr1645v2PRoutQmUpDownJitterUpBinsType
         INTEGER,
      pr1645v2PRoutQmUpDownJitterUpBinsMinMin
         Counter32,
      pr1645v2PRoutQmUpDownJitterUpBinsMin
         Integer32,
      pr1645v2PRoutQmUpDownJitterUpBinsMinBin1
         Counter32,
      pr1645v2PRoutQmUpDownJitterUpBinsBin2
         Counter32,
      pr1645v2PRoutQmUpDownJitterUpBinsBin3
         Counter32,
      pr1645v2PRoutQmUpDownJitterUpBinsBin4
         Counter32,
      pr1645v2PRoutQmUpDownJitterUpBinsBin5
         Counter32,
      pr1645v2PRoutQmUpDownJitterUpBinsBin6
         Counter32,
      pr1645v2PRoutQmUpDownJitterUpBinsBin7
         Counter32,
      pr1645v2PRoutQmUpDownJitterUpBinsMaxBin8
         Counter32,
      pr1645v2PRoutQmUpDownJitterUpBinsMax
         Integer32,
      pr1645v2PRoutQmUpDownJitterUpBinsPlusMax
         Counter32,
      pr1645v2PRoutQmUpDownLossDown
         Counter32,
      pr1645v2PRoutQmUpDownLossDelayDown
         Counter32,
      pr1645v2PRoutQmUpDownDelayDownMin
         Integer32,
      pr1645v2PRoutQmUpDownDelayDownAvrg
         Integer32,
      pr1645v2PRoutQmUpDownDelayDownMax
         Integer32,
      pr1645v2PRoutQmUpDownDelayDownBinsType
         INTEGER,
      pr1645v2PRoutQmUpDownDelayDownBinsMinMin
         Counter32,
      pr1645v2PRoutQmUpDownDelayDownBinsMin
         Integer32,
      pr1645v2PRoutQmUpDownDelayDownBinsMinBin1
         Counter32,
      pr1645v2PRoutQmUpDownDelayDownBinsBin2
         Counter32,
      pr1645v2PRoutQmUpDownDelayDownBinsBin3
         Counter32,
      pr1645v2PRoutQmUpDownDelayDownBinsBin4
         Counter32,
      pr1645v2PRoutQmUpDownDelayDownBinsBin5
         Counter32,
      pr1645v2PRoutQmUpDownDelayDownBinsBin6
         Counter32,
      pr1645v2PRoutQmUpDownDelayDownBinsBin7
         Counter32,
      pr1645v2PRoutQmUpDownDelayDownBinsMaxBin8
         Counter32,
      pr1645v2PRoutQmUpDownDelayDownBinsMax
         Integer32,
      pr1645v2PRoutQmUpDownDelayDownBinsPlusMax
         Counter32,
      pr1645v2PRoutQmUpDownJitterDown
         Integer32,
      pr1645v2PRoutQmUpDownJitterDownNegMax
         Integer32,
      pr1645v2PRoutQmUpDownJitterDownAvrg
         Integer32,
      pr1645v2PRoutQmUpDownJitterDownPosMax
         Integer32,
      pr1645v2PRoutQmUpDownJitterDownBinsType
         INTEGER,
      pr1645v2PRoutQmUpDownJitterDownBinsMinMin
         Counter32,
      pr1645v2PRoutQmUpDownJitterDownBinsMin
         Integer32,
      pr1645v2PRoutQmUpDownJitterDownBinsMinBin1
         Counter32,
      pr1645v2PRoutQmUpDownJitterDownBinsBin2
         Counter32,
      pr1645v2PRoutQmUpDownJitterDownBinsBin3
         Counter32,
      pr1645v2PRoutQmUpDownJitterDownBinsBin4
         Counter32,
      pr1645v2PRoutQmUpDownJitterDownBinsBin5
         Counter32,
      pr1645v2PRoutQmUpDownJitterDownBinsBin6
         Counter32,
      pr1645v2PRoutQmUpDownJitterDownBinsBin7
         Counter32,
      pr1645v2PRoutQmUpDownJitterDownBinsMaxBin8
         Counter32,
      pr1645v2PRoutQmUpDownJitterDownBinsMax
         Integer32,
      pr1645v2PRoutQmUpDownJitterDownBinsPlusMax
         Counter32,
      pr1645v2PRoutQmLastLogSysUpTime
         TimeTicks,
      pr1645v2PRoutQmLastLogNbrTxPckt
         Counter32,
      pr1645v2PRoutQmLastLogNbrRxPckt
         Counter32,
      pr1645v2PRoutQmLastLogError
         Counter32,
      pr1645v2PRoutQmLastLogLoss
         Counter32,
      pr1645v2PRoutQmLastLogLossDelay
         Counter32,
      pr1645v2PRoutQmLastLogDelayMin
         Integer32,
      pr1645v2PRoutQmLastLogDelayAvrg
         Integer32,
      pr1645v2PRoutQmLastLogDelayMax
         Integer32,
      pr1645v2PRoutQmLastLogJitterNegMax
         Integer32,
      pr1645v2PRoutQmLastLogJitterAvrg
         Integer32,
      pr1645v2PRoutQmLastLogJitterPosMax
         Integer32,
      pr1645v2PRoutQmLastLogUpDownStatus
         INTEGER,
      pr1645v2PRoutQmLastLogUpDownLossUp
         Counter32,
      pr1645v2PRoutQmLastLogUpDownLossDelayUp
         Counter32,
      pr1645v2PRoutQmLastLogUpDownDelayUpMin
         Integer32,
      pr1645v2PRoutQmLastLogUpDownDelayUpAvrg
         Integer32,
      pr1645v2PRoutQmLastLogUpDownDelayUpMax
         Integer32,
      pr1645v2PRoutQmLastLogUpDownJitterUpNegMax
         Integer32,
      pr1645v2PRoutQmLastLogUpDownJitterUpAvrg
         Integer32,
      pr1645v2PRoutQmLastLogUpDownJitterUpPosMax
         Integer32,
      pr1645v2PRoutQmLastLogUpDownLossDown
         Counter32,
      pr1645v2PRoutQmLastLogUpDownLossDelayDown
         Counter32,
      pr1645v2PRoutQmLastLogUpDownDelayDownMin
         Integer32,
      pr1645v2PRoutQmLastLogUpDownDelayDownAvrg
         Integer32,
      pr1645v2PRoutQmLastLogUpDownDelayDownMax
         Integer32,
      pr1645v2PRoutQmLastLogUpDownJitterDownNegMax
         Integer32,
      pr1645v2PRoutQmLastLogUpDownJitterDownAvrg
         Integer32,
      pr1645v2PRoutQmLastLogUpDownJitterDownPosMax
         Integer32,
      pr1645v2PRoutQmLastLogDate
         DisplayString,
      pr1645v2PRoutQmAlarm
         Integer32,
      pr1645v2PRoutQmLastError
         DisplayString
      }

pr1645v2PRoutQmTableIx OBJECT-TYPE
   SYNTAX      TableIndex
   MAX-ACCESS  not-accessible
   STATUS      current
   DESCRIPTION
      ""
   ::= {pr1645v2PRoutQmEntry 11}

pr1645v2PRoutQmName OBJECT-TYPE
   SYNTAX      DisplayString
   MAX-ACCESS  read-only
   STATUS      current
   DESCRIPTION
      "Path: router.performance.qualityMonitor.name"
   ::= {pr1645v2PRoutQmEntry 301989888}

pr1645v2PRoutQmStatus OBJECT-TYPE
   SYNTAX      INTEGER
               {
               run (1),
               runOnDemand (3),
               halted (2),
               cleared (6),
               disabled (8),
               runIdle (9)
               }
   MAX-ACCESS  read-only
   STATUS      current
   DESCRIPTION
      "Path: router.performance.qualityMonitor.status

       Possibilities:
               run   (1)
               runOnDemand   (3)
               halted   (2)
               cleared   (6)
               disabled   (8)
               runIdle   (9)"
   ::= {pr1645v2PRoutQmEntry 369098752}

pr1645v2PRoutQmIpAddress OBJECT-TYPE
   SYNTAX      IpAddress
   MAX-ACCESS  read-only
   STATUS      current
   DESCRIPTION
      "Path: router.performance.qualityMonitor.ipAddress"
   ::= {pr1645v2PRoutQmEntry 16777216}

pr1645v2PRoutQmHostName OBJECT-TYPE
   SYNTAX      DisplayString
   MAX-ACCESS  read-only
   STATUS      current
   DESCRIPTION
      "Path: router.performance.qualityMonitor.hostName"
   ::= {pr1645v2PRoutQmEntry 33554432}

pr1645v2PRoutQmSourceIp OBJECT-TYPE
   SYNTAX      IpAddress
   MAX-ACCESS  read-only
   STATUS      current
   DESCRIPTION
      "Path: router.performance.qualityMonitor.sourceIp"
   ::= {pr1645v2PRoutQmEntry 83886080}

pr1645v2PRoutQmSourceId OBJECT-TYPE
   SYNTAX      Gauge32
   MAX-ACCESS  read-only
   STATUS      current
   DESCRIPTION
      "Path: router.performance.qualityMonitor.sourceId

       32 bit unsigned gauge value."
   ::= {pr1645v2PRoutQmEntry 352321536}

pr1645v2PRoutQmNbrTxPckt OBJECT-TYPE
   SYNTAX      Counter32
   MAX-ACCESS  read-only
   STATUS      current
   DESCRIPTION
      "Path: router.performance.qualityMonitor.nbrOfTxPackets

       32 bit unsigned wrappable counter."
   ::= {pr1645v2PRoutQmEntry 50331648}

pr1645v2PRoutQmNbrRxPckt OBJECT-TYPE
   SYNTAX      Counter32
   MAX-ACCESS  read-only
   STATUS      current
   DESCRIPTION
      "Path: router.performance.qualityMonitor.nbrOfRxPackets

       32 bit unsigned wrappable counter."
   ::= {pr1645v2PRoutQmEntry 67108864}

pr1645v2PRoutQmError OBJECT-TYPE
   SYNTAX      Counter32
   MAX-ACCESS  read-only
   STATUS      current
   DESCRIPTION
      "Path: router.performance.qualityMonitor.error

       32 bit unsigned wrappable counter."
   ::= {pr1645v2PRoutQmEntry 285212672}

pr1645v2PRoutQmDelay OBJECT-TYPE
   SYNTAX      Integer32
   MAX-ACCESS  read-only
   STATUS      current
   DESCRIPTION
      "Path: router.performance.qualityMonitor.delay

       unit name = sec
       formula = 1000 / ; 1000 *"
   ::= {pr1645v2PRoutQmEntry 201326592}

pr1645v2PRoutQmJitter OBJECT-TYPE
   SYNTAX      Integer32
   MAX-ACCESS  read-only
   STATUS      current
   DESCRIPTION
      "Path: router.performance.qualityMonitor.jitter

       unit name = sec
       formula = 1000 / ; 1000 *"
   ::= {pr1645v2PRoutQmEntry 218103808}

pr1645v2PRoutQmLoss OBJECT-TYPE
   SYNTAX      Counter32
   MAX-ACCESS  read-only
   STATUS      current
   DESCRIPTION
      "Path: router.performance.qualityMonitor.loss

       32 bit unsigned wrappable counter."
   ::= {pr1645v2PRoutQmEntry 100663296}

pr1645v2PRoutQmLossDelay OBJECT-TYPE
   SYNTAX      Counter32
   MAX-ACCESS  read-only
   STATUS      current
   DESCRIPTION
      "Path: router.performance.qualityMonitor.lossDelay

       32 bit unsigned wrappable counter."
   ::= {pr1645v2PRoutQmEntry 268435456}

pr1645v2PRoutQmDelayMin OBJECT-TYPE
   SYNTAX      Integer32
   MAX-ACCESS  read-only
   STATUS      current
   DESCRIPTION
      "Path: router.performance.qualityMonitor.delayMin

       unit name = sec
       formula = 1000 / ; 1000 *"
   ::= {pr1645v2PRoutQmEntry 184549376}

pr1645v2PRoutQmDelayAvrg OBJECT-TYPE
   SYNTAX      Integer32
   MAX-ACCESS  read-only
   STATUS      current
   DESCRIPTION
      "Path: router.performance.qualityMonitor.delayAvrg

       unit name = sec
       formula = 1000 / ; 1000 *"
   ::= {pr1645v2PRoutQmEntry 117440512}

pr1645v2PRoutQmDelayMax OBJECT-TYPE
   SYNTAX      Integer32
   MAX-ACCESS  read-only
   STATUS      current
   DESCRIPTION
      "Path: router.performance.qualityMonitor.delayMax

       unit name = sec
       formula = 1000 / ; 1000 *"
   ::= {pr1645v2PRoutQmEntry 134217728}

pr1645v2PRoutQmDelayBinsType OBJECT-TYPE
   SYNTAX      INTEGER
               {
               fd (1),
               fdr (2),
               notInUse (3),
               ifdv (4)
               }
   MAX-ACCESS  read-only
   STATUS      current
   DESCRIPTION
      "Path: router.performance.qualityMonitor.delayBins.type

       Possibilities:
               fd   (1)
               fdr   (2)
               notInUse   (3)
               ifdv   (4)"
   ::= {pr1645v2PRoutQmEntry 420937728}

pr1645v2PRoutQmDelayBinsMinMin OBJECT-TYPE
   SYNTAX      Counter32
   MAX-ACCESS  read-only
   STATUS      current
   DESCRIPTION
      "Path: router.performance.qualityMonitor.delayBins.minMin

       32 bit unsigned wrappable counter."
   ::= {pr1645v2PRoutQmEntry 419495936}

pr1645v2PRoutQmDelayBinsMin OBJECT-TYPE
   SYNTAX      Integer32
   MAX-ACCESS  read-only
   STATUS      current
   DESCRIPTION
      "Path: router.performance.qualityMonitor.delayBins.min

       unit name = sec
       formula = 1000 / ; 1000 *"
   ::= {pr1645v2PRoutQmEntry 420806656}

pr1645v2PRoutQmDelayBinsMinBin1 OBJECT-TYPE
   SYNTAX      Counter32
   MAX-ACCESS  read-only
   STATUS      current
   DESCRIPTION
      "Path: router.performance.qualityMonitor.delayBins.minBin1

       32 bit unsigned wrappable counter."
   ::= {pr1645v2PRoutQmEntry 419561472}

pr1645v2PRoutQmDelayBinsBin2 OBJECT-TYPE
   SYNTAX      Counter32
   MAX-ACCESS  read-only
   STATUS      current
   DESCRIPTION
      "Path: router.performance.qualityMonitor.delayBins.bin2

       32 bit unsigned wrappable counter."
   ::= {pr1645v2PRoutQmEntry 419627008}

pr1645v2PRoutQmDelayBinsBin3 OBJECT-TYPE
   SYNTAX      Counter32
   MAX-ACCESS  read-only
   STATUS      current
   DESCRIPTION
      "Path: router.performance.qualityMonitor.delayBins.bin3

       32 bit unsigned wrappable counter."
   ::= {pr1645v2PRoutQmEntry 419692544}

pr1645v2PRoutQmDelayBinsBin4 OBJECT-TYPE
   SYNTAX      Counter32
   MAX-ACCESS  read-only
   STATUS      current
   DESCRIPTION
      "Path: router.performance.qualityMonitor.delayBins.bin4

       32 bit unsigned wrappable counter."
   ::= {pr1645v2PRoutQmEntry 419758080}

pr1645v2PRoutQmDelayBinsBin5 OBJECT-TYPE
   SYNTAX      Counter32
   MAX-ACCESS  read-only
   STATUS      current
   DESCRIPTION
      "Path: router.performance.qualityMonitor.delayBins.bin5

       32 bit unsigned wrappable counter."
   ::= {pr1645v2PRoutQmEntry 419823616}

pr1645v2PRoutQmDelayBinsBin6 OBJECT-TYPE
   SYNTAX      Counter32
   MAX-ACCESS  read-only
   STATUS      current
   DESCRIPTION
      "Path: router.performance.qualityMonitor.delayBins.bin6

       32 bit unsigned wrappable counter."
   ::= {pr1645v2PRoutQmEntry 419889152}

pr1645v2PRoutQmDelayBinsBin7 OBJECT-TYPE
   SYNTAX      Counter32
   MAX-ACCESS  read-only
   STATUS      current
   DESCRIPTION
      "Path: router.performance.qualityMonitor.delayBins.bin7

       32 bit unsigned wrappable counter."
   ::= {pr1645v2PRoutQmEntry 419954688}

pr1645v2PRoutQmDelayBinsMaxBin8 OBJECT-TYPE
   SYNTAX      Counter32
   MAX-ACCESS  read-only
   STATUS      current
   DESCRIPTION
      "Path: router.performance.qualityMonitor.delayBins.maxBin8

       32 bit unsigned wrappable counter."
   ::= {pr1645v2PRoutQmEntry 420020224}

pr1645v2PRoutQmDelayBinsMax OBJECT-TYPE
   SYNTAX      Integer32
   MAX-ACCESS  read-only
   STATUS      current
   DESCRIPTION
      "Path: router.performance.qualityMonitor.delayBins.max

       unit name = sec
       formula = 1000 / ; 1000 *"
   ::= {pr1645v2PRoutQmEntry 420872192}

pr1645v2PRoutQmDelayBinsPlusMax OBJECT-TYPE
   SYNTAX      Counter32
   MAX-ACCESS  read-only
   STATUS      current
   DESCRIPTION
      "Path: router.performance.qualityMonitor.delayBins.plusMax

       32 bit unsigned wrappable counter."
   ::= {pr1645v2PRoutQmEntry 420085760}

pr1645v2PRoutQmJitterNegMax OBJECT-TYPE
   SYNTAX      Integer32
   MAX-ACCESS  read-only
   STATUS      current
   DESCRIPTION
      "Path: router.performance.qualityMonitor.jitterNegMax

       unit name = sec
       formula = 1000 / ; 1000 *"
   ::= {pr1645v2PRoutQmEntry 234881024}

pr1645v2PRoutQmJitterAvrg OBJECT-TYPE
   SYNTAX      Integer32
   MAX-ACCESS  read-only
   STATUS      current
   DESCRIPTION
      "Path: router.performance.qualityMonitor.jitterAvrg

       unit name = sec
       formula = 1000 / ; 1000 *"
   ::= {pr1645v2PRoutQmEntry 150994944}

pr1645v2PRoutQmJitterPosMax OBJECT-TYPE
   SYNTAX      Integer32
   MAX-ACCESS  read-only
   STATUS      current
   DESCRIPTION
      "Path: router.performance.qualityMonitor.jitterPosMax

       unit name = sec
       formula = 1000 / ; 1000 *"
   ::= {pr1645v2PRoutQmEntry 167772160}

pr1645v2PRoutQmJitterBinsType OBJECT-TYPE
   SYNTAX      INTEGER
               {
               fd (1),
               fdr (2),
               notInUse (3),
               ifdv (4)
               }
   MAX-ACCESS  read-only
   STATUS      current
   DESCRIPTION
      "Path: router.performance.qualityMonitor.jitterBins.type

       Possibilities:
               fd   (1)
               fdr   (2)
               notInUse   (3)
               ifdv   (4)"
   ::= {pr1645v2PRoutQmEntry 437714944}

pr1645v2PRoutQmJitterBinsMinMin OBJECT-TYPE
   SYNTAX      Counter32
   MAX-ACCESS  read-only
   STATUS      current
   DESCRIPTION
      "Path: router.performance.qualityMonitor.jitterBins.minMin

       32 bit unsigned wrappable counter."
   ::= {pr1645v2PRoutQmEntry 436273152}

pr1645v2PRoutQmJitterBinsMin OBJECT-TYPE
   SYNTAX      Integer32
   MAX-ACCESS  read-only
   STATUS      current
   DESCRIPTION
      "Path: router.performance.qualityMonitor.jitterBins.min

       unit name = sec
       formula = 1000 / ; 1000 *"
   ::= {pr1645v2PRoutQmEntry 437583872}

pr1645v2PRoutQmJitterBinsMinBin1 OBJECT-TYPE
   SYNTAX      Counter32
   MAX-ACCESS  read-only
   STATUS      current
   DESCRIPTION
      "Path: router.performance.qualityMonitor.jitterBins.minBin1

       32 bit unsigned wrappable counter."
   ::= {pr1645v2PRoutQmEntry 436338688}

pr1645v2PRoutQmJitterBinsBin2 OBJECT-TYPE
   SYNTAX      Counter32
   MAX-ACCESS  read-only
   STATUS      current
   DESCRIPTION
      "Path: router.performance.qualityMonitor.jitterBins.bin2

       32 bit unsigned wrappable counter."
   ::= {pr1645v2PRoutQmEntry 436404224}

pr1645v2PRoutQmJitterBinsBin3 OBJECT-TYPE
   SYNTAX      Counter32
   MAX-ACCESS  read-only
   STATUS      current
   DESCRIPTION
      "Path: router.performance.qualityMonitor.jitterBins.bin3

       32 bit unsigned wrappable counter."
   ::= {pr1645v2PRoutQmEntry 436469760}

pr1645v2PRoutQmJitterBinsBin4 OBJECT-TYPE
   SYNTAX      Counter32
   MAX-ACCESS  read-only
   STATUS      current
   DESCRIPTION
      "Path: router.performance.qualityMonitor.jitterBins.bin4

       32 bit unsigned wrappable counter."
   ::= {pr1645v2PRoutQmEntry 436535296}

pr1645v2PRoutQmJitterBinsBin5 OBJECT-TYPE
   SYNTAX      Counter32
   MAX-ACCESS  read-only
   STATUS      current
   DESCRIPTION
      "Path: router.performance.qualityMonitor.jitterBins.bin5

       32 bit unsigned wrappable counter."
   ::= {pr1645v2PRoutQmEntry 436600832}

pr1645v2PRoutQmJitterBinsBin6 OBJECT-TYPE
   SYNTAX      Counter32
   MAX-ACCESS  read-only
   STATUS      current
   DESCRIPTION
      "Path: router.performance.qualityMonitor.jitterBins.bin6

       32 bit unsigned wrappable counter."
   ::= {pr1645v2PRoutQmEntry 436666368}

pr1645v2PRoutQmJitterBinsBin7 OBJECT-TYPE
   SYNTAX      Counter32
   MAX-ACCESS  read-only
   STATUS      current
   DESCRIPTION
      "Path: router.performance.qualityMonitor.jitterBins.bin7

       32 bit unsigned wrappable counter."
   ::= {pr1645v2PRoutQmEntry 436731904}

pr1645v2PRoutQmJitterBinsMaxBin8 OBJECT-TYPE
   SYNTAX      Counter32
   MAX-ACCESS  read-only
   STATUS      current
   DESCRIPTION
      "Path: router.performance.qualityMonitor.jitterBins.maxBin8

       32 bit unsigned wrappable counter."
   ::= {pr1645v2PRoutQmEntry 436797440}

pr1645v2PRoutQmJitterBinsMax OBJECT-TYPE
   SYNTAX      Integer32
   MAX-ACCESS  read-only
   STATUS      current
   DESCRIPTION
      "Path: router.performance.qualityMonitor.jitterBins.max

       unit name = sec
       formula = 1000 / ; 1000 *"
   ::= {pr1645v2PRoutQmEntry 437649408}

pr1645v2PRoutQmJitterBinsPlusMax OBJECT-TYPE
   SYNTAX      Counter32
   MAX-ACCESS  read-only
   STATUS      current
   DESCRIPTION
      "Path: router.performance.qualityMonitor.jitterBins.plusMax

       32 bit unsigned wrappable counter."
   ::= {pr1645v2PRoutQmEntry 436862976}

pr1645v2PRoutQmBfdCtrlOutPkts OBJECT-TYPE
   SYNTAX      Integer32
   MAX-ACCESS  read-only
   STATUS      current
   DESCRIPTION
      "Path: router.performance.qualityMonitor.bfdCtrl.outPkts"
   ::= {pr1645v2PRoutQmEntry 838926336}

pr1645v2PRoutQmBfdCtrlInPkts OBJECT-TYPE
   SYNTAX      Integer32
   MAX-ACCESS  read-only
   STATUS      current
   DESCRIPTION
      "Path: router.performance.qualityMonitor.bfdCtrl.inPkts"
   ::= {pr1645v2PRoutQmEntry 838991872}

pr1645v2PRoutQmBfdCtrlLocalState OBJECT-TYPE
   SYNTAX      INTEGER
               {
               down (1),
               init (2),
               up (3)
               }
   MAX-ACCESS  read-only
   STATUS      current
   DESCRIPTION
      "Path: router.performance.qualityMonitor.bfdCtrl.localState

       Possibilities:
               down   (1)
               init   (2)
               up   (3)"
   ::= {pr1645v2PRoutQmEntry 839057408}

pr1645v2PRoutQmBfdCtrlLocalDiscriminator OBJECT-TYPE
   SYNTAX      Integer32
   MAX-ACCESS  read-only
   STATUS      current
   DESCRIPTION
      "Path: router.performance.qualityMonitor.bfdCtrl.localDiscriminator"
   ::= {pr1645v2PRoutQmEntry 839122944}

pr1645v2PRoutQmBfdCtrlLocalTxInterval OBJECT-TYPE
   SYNTAX      Integer32
   UNITS       "ms"
   MAX-ACCESS  read-only
   STATUS      current
   DESCRIPTION
      "Path: router.performance.qualityMonitor.bfdCtrl.localTxInterval

       unit name = ms"
   ::= {pr1645v2PRoutQmEntry 839712768}

pr1645v2PRoutQmBfdCtrlLocalMinTxInterval OBJECT-TYPE
   SYNTAX      Integer32
   UNITS       "ms"
   MAX-ACCESS  read-only
   STATUS      current
   DESCRIPTION
      "Path: router.performance.qualityMonitor.bfdCtrl.localMinTxInterval

       unit name = ms"
   ::= {pr1645v2PRoutQmEntry 839188480}

pr1645v2PRoutQmBfdCtrlLocalDetectMultiplier OBJECT-TYPE
   SYNTAX      Integer32
   MAX-ACCESS  read-only
   STATUS      current
   DESCRIPTION
      "Path: router.performance.qualityMonitor.bfdCtrl.localDetectMultiplier"
   ::= {pr1645v2PRoutQmEntry 839254016}

pr1645v2PRoutQmBfdCtrlRemoteState OBJECT-TYPE
   SYNTAX      INTEGER
               {
               down (1),
               init (2),
               up (3)
               }
   MAX-ACCESS  read-only
   STATUS      current
   DESCRIPTION
      "Path: router.performance.qualityMonitor.bfdCtrl.remoteState

       Possibilities:
               down   (1)
               init   (2)
               up   (3)"
   ::= {pr1645v2PRoutQmEntry 839319552}

pr1645v2PRoutQmBfdCtrlRemoteDiscriminator OBJECT-TYPE
   SYNTAX      Integer32
   MAX-ACCESS  read-only
   STATUS      current
   DESCRIPTION
      "Path: router.performance.qualityMonitor.bfdCtrl.remoteDiscriminator"
   ::= {pr1645v2PRoutQmEntry 839450624}

pr1645v2PRoutQmBfdCtrlRemoteMinTxInterval OBJECT-TYPE
   SYNTAX      Integer32
   UNITS       "ms"
   MAX-ACCESS  read-only
   STATUS      current
   DESCRIPTION
      "Path: router.performance.qualityMonitor.bfdCtrl.remoteMinTxInterval

       unit name = ms"
   ::= {pr1645v2PRoutQmEntry 839385088}

pr1645v2PRoutQmBfdCtrlRemoteDetectMultiplier OBJECT-TYPE
   SYNTAX      Integer32
   MAX-ACCESS  read-only
   STATUS      current
   DESCRIPTION
      "Path: router.performance.qualityMonitor.bfdCtrl.remoteDetectMultiplier"
   ::= {pr1645v2PRoutQmEntry 839516160}

pr1645v2PRoutQmBfdCtrlRemoteMinRxInterval OBJECT-TYPE
   SYNTAX      Integer32
   UNITS       "ms"
   MAX-ACCESS  read-only
   STATUS      current
   DESCRIPTION
      "Path: router.performance.qualityMonitor.bfdCtrl.remoteMinRxInterval

       unit name = ms"
   ::= {pr1645v2PRoutQmEntry 839581696}

pr1645v2PRoutQmBfdCtrlRemoteMinRxEchoInterval OBJECT-TYPE
   SYNTAX      Integer32
   UNITS       "ms"
   MAX-ACCESS  read-only
   STATUS      current
   DESCRIPTION
      "Path: router.performance.qualityMonitor.bfdCtrl.remoteMinRxEchoInterval

       unit name = ms"
   ::= {pr1645v2PRoutQmEntry 839647232}

pr1645v2PRoutQmUpDownStatus OBJECT-TYPE
   SYNTAX      INTEGER
               {
               notInUse (3),
               onlyJitter (1),
               jitterAndLoss (2),
               all (4),
               onlyLoss (8)
               }
   MAX-ACCESS  read-only
   STATUS      current
   DESCRIPTION
      "Path: router.performance.qualityMonitor.upDown.status

       Possibilities:
               notInUse   (3)
               onlyJitter   (1)
               jitterAndLoss   (2)
               all   (4)
               onlyLoss   (8)"
   ::= {pr1645v2PRoutQmEntry 504627200}

pr1645v2PRoutQmUpDownLossUp OBJECT-TYPE
   SYNTAX      Counter32
   MAX-ACCESS  read-only
   STATUS      current
   DESCRIPTION
      "Path: router.performance.qualityMonitor.upDown.lossUp

       32 bit unsigned wrappable counter."
   ::= {pr1645v2PRoutQmEntry 503971840}

pr1645v2PRoutQmUpDownLossDelayUp OBJECT-TYPE
   SYNTAX      Counter32
   MAX-ACCESS  read-only
   STATUS      current
   DESCRIPTION
      "Path: router.performance.qualityMonitor.upDown.lossDelayUp

       32 bit unsigned wrappable counter."
   ::= {pr1645v2PRoutQmEntry 504037376}

pr1645v2PRoutQmUpDownDelayUpMin OBJECT-TYPE
   SYNTAX      Integer32
   MAX-ACCESS  read-only
   STATUS      current
   DESCRIPTION
      "Path: router.performance.qualityMonitor.upDown.delayUpMin

       unit name = sec
       formula = 1000 / ; 1000 *"
   ::= {pr1645v2PRoutQmEntry 505282560}

pr1645v2PRoutQmUpDownDelayUpAvrg OBJECT-TYPE
   SYNTAX      Integer32
   MAX-ACCESS  read-only
   STATUS      current
   DESCRIPTION
      "Path: router.performance.qualityMonitor.upDown.delayUpAvrg

       unit name = sec
       formula = 1000 / ; 1000 *"
   ::= {pr1645v2PRoutQmEntry 505348096}

pr1645v2PRoutQmUpDownDelayUpMax OBJECT-TYPE
   SYNTAX      Integer32
   MAX-ACCESS  read-only
   STATUS      current
   DESCRIPTION
      "Path: router.performance.qualityMonitor.upDown.delayUpMax

       unit name = sec
       formula = 1000 / ; 1000 *"
   ::= {pr1645v2PRoutQmEntry 505413632}

pr1645v2PRoutQmUpDownDelayUpBinsType OBJECT-TYPE
   SYNTAX      INTEGER
               {
               fd (1),
               fdr (2),
               notInUse (3),
               ifdv (4)
               }
   MAX-ACCESS  read-only
   STATUS      current
   DESCRIPTION
      "Path: router.performance.qualityMonitor.upDown.delayUpBins.type

       Possibilities:
               fd   (1)
               fdr   (2)
               notInUse   (3)
               ifdv   (4)"
   ::= {pr1645v2PRoutQmEntry 505943808}

pr1645v2PRoutQmUpDownDelayUpBinsMinMin OBJECT-TYPE
   SYNTAX      Counter32
   MAX-ACCESS  read-only
   STATUS      current
   DESCRIPTION
      "Path: router.performance.qualityMonitor.upDown.delayUpBins.minMin

       32 bit unsigned wrappable counter."
   ::= {pr1645v2PRoutQmEntry 505938176}

pr1645v2PRoutQmUpDownDelayUpBinsMin OBJECT-TYPE
   SYNTAX      Integer32
   MAX-ACCESS  read-only
   STATUS      current
   DESCRIPTION
      "Path: router.performance.qualityMonitor.upDown.delayUpBins.min

       unit name = sec
       formula = 1000 / ; 1000 *"
   ::= {pr1645v2PRoutQmEntry 505943296}

pr1645v2PRoutQmUpDownDelayUpBinsMinBin1 OBJECT-TYPE
   SYNTAX      Counter32
   MAX-ACCESS  read-only
   STATUS      current
   DESCRIPTION
      "Path: router.performance.qualityMonitor.upDown.delayUpBins.minBin1

       32 bit unsigned wrappable counter."
   ::= {pr1645v2PRoutQmEntry 505938432}

pr1645v2PRoutQmUpDownDelayUpBinsBin2 OBJECT-TYPE
   SYNTAX      Counter32
   MAX-ACCESS  read-only
   STATUS      current
   DESCRIPTION
      "Path: router.performance.qualityMonitor.upDown.delayUpBins.bin2

       32 bit unsigned wrappable counter."
   ::= {pr1645v2PRoutQmEntry 505938688}

pr1645v2PRoutQmUpDownDelayUpBinsBin3 OBJECT-TYPE
   SYNTAX      Counter32
   MAX-ACCESS  read-only
   STATUS      current
   DESCRIPTION
      "Path: router.performance.qualityMonitor.upDown.delayUpBins.bin3

       32 bit unsigned wrappable counter."
   ::= {pr1645v2PRoutQmEntry 505938944}

pr1645v2PRoutQmUpDownDelayUpBinsBin4 OBJECT-TYPE
   SYNTAX      Counter32
   MAX-ACCESS  read-only
   STATUS      current
   DESCRIPTION
      "Path: router.performance.qualityMonitor.upDown.delayUpBins.bin4

       32 bit unsigned wrappable counter."
   ::= {pr1645v2PRoutQmEntry 505939200}

pr1645v2PRoutQmUpDownDelayUpBinsBin5 OBJECT-TYPE
   SYNTAX      Counter32
   MAX-ACCESS  read-only
   STATUS      current
   DESCRIPTION
      "Path: router.performance.qualityMonitor.upDown.delayUpBins.bin5

       32 bit unsigned wrappable counter."
   ::= {pr1645v2PRoutQmEntry 505939456}

pr1645v2PRoutQmUpDownDelayUpBinsBin6 OBJECT-TYPE
   SYNTAX      Counter32
   MAX-ACCESS  read-only
   STATUS      current
   DESCRIPTION
      "Path: router.performance.qualityMonitor.upDown.delayUpBins.bin6

       32 bit unsigned wrappable counter."
   ::= {pr1645v2PRoutQmEntry 505939712}

pr1645v2PRoutQmUpDownDelayUpBinsBin7 OBJECT-TYPE
   SYNTAX      Counter32
   MAX-ACCESS  read-only
   STATUS      current
   DESCRIPTION
      "Path: router.performance.qualityMonitor.upDown.delayUpBins.bin7

       32 bit unsigned wrappable counter."
   ::= {pr1645v2PRoutQmEntry 505939968}

pr1645v2PRoutQmUpDownDelayUpBinsMaxBin8 OBJECT-TYPE
   SYNTAX      Counter32
   MAX-ACCESS  read-only
   STATUS      current
   DESCRIPTION
      "Path: router.performance.qualityMonitor.upDown.delayUpBins.maxBin8

       32 bit unsigned wrappable counter."
   ::= {pr1645v2PRoutQmEntry 505940224}

pr1645v2PRoutQmUpDownDelayUpBinsMax OBJECT-TYPE
   SYNTAX      Integer32
   MAX-ACCESS  read-only
   STATUS      current
   DESCRIPTION
      "Path: router.performance.qualityMonitor.upDown.delayUpBins.max

       unit name = sec
       formula = 1000 / ; 1000 *"
   ::= {pr1645v2PRoutQmEntry 505943552}

pr1645v2PRoutQmUpDownDelayUpBinsPlusMax OBJECT-TYPE
   SYNTAX      Counter32
   MAX-ACCESS  read-only
   STATUS      current
   DESCRIPTION
      "Path: router.performance.qualityMonitor.upDown.delayUpBins.plusMax

       32 bit unsigned wrappable counter."
   ::= {pr1645v2PRoutQmEntry 505940480}

pr1645v2PRoutQmUpDownJitterUp OBJECT-TYPE
   SYNTAX      Integer32
   MAX-ACCESS  read-only
   STATUS      current
   DESCRIPTION
      "Path: router.performance.qualityMonitor.upDown.jitterUp

       unit name = sec
       formula = 1000 / ; 1000 *"
   ::= {pr1645v2PRoutQmEntry 503775232}

pr1645v2PRoutQmUpDownJitterUpNegMax OBJECT-TYPE
   SYNTAX      Integer32
   MAX-ACCESS  read-only
   STATUS      current
   DESCRIPTION
      "Path: router.performance.qualityMonitor.upDown.jitterUpNegMax

       unit name = sec
       formula = 1000 / ; 1000 *"
   ::= {pr1645v2PRoutQmEntry 503382016}

pr1645v2PRoutQmUpDownJitterUpAvrg OBJECT-TYPE
   SYNTAX      Integer32
   MAX-ACCESS  read-only
   STATUS      current
   DESCRIPTION
      "Path: router.performance.qualityMonitor.upDown.jitterUpAvrg

       unit name = sec
       formula = 1000 / ; 1000 *"
   ::= {pr1645v2PRoutQmEntry 503447552}

pr1645v2PRoutQmUpDownJitterUpPosMax OBJECT-TYPE
   SYNTAX      Integer32
   MAX-ACCESS  read-only
   STATUS      current
   DESCRIPTION
      "Path: router.performance.qualityMonitor.upDown.jitterUpPosMax

       unit name = sec
       formula = 1000 / ; 1000 *"
   ::= {pr1645v2PRoutQmEntry 503513088}

pr1645v2PRoutQmUpDownJitterUpBinsType OBJECT-TYPE
   SYNTAX      INTEGER
               {
               fd (1),
               fdr (2),
               notInUse (3),
               ifdv (4)
               }
   MAX-ACCESS  read-only
   STATUS      current
   DESCRIPTION
      "Path: router.performance.qualityMonitor.upDown.jitterUpBins.type

       Possibilities:
               fd   (1)
               fdr   (2)
               notInUse   (3)
               ifdv   (4)"
   ::= {pr1645v2PRoutQmEntry 506074880}

pr1645v2PRoutQmUpDownJitterUpBinsMinMin OBJECT-TYPE
   SYNTAX      Counter32
   MAX-ACCESS  read-only
   STATUS      current
   DESCRIPTION
      "Path: router.performance.qualityMonitor.upDown.jitterUpBins.minMin

       32 bit unsigned wrappable counter."
   ::= {pr1645v2PRoutQmEntry 506069248}

pr1645v2PRoutQmUpDownJitterUpBinsMin OBJECT-TYPE
   SYNTAX      Integer32
   MAX-ACCESS  read-only
   STATUS      current
   DESCRIPTION
      "Path: router.performance.qualityMonitor.upDown.jitterUpBins.min

       unit name = sec
       formula = 1000 / ; 1000 *"
   ::= {pr1645v2PRoutQmEntry 506074368}

pr1645v2PRoutQmUpDownJitterUpBinsMinBin1 OBJECT-TYPE
   SYNTAX      Counter32
   MAX-ACCESS  read-only
   STATUS      current
   DESCRIPTION
      "Path: router.performance.qualityMonitor.upDown.jitterUpBins.minBin1

       32 bit unsigned wrappable counter."
   ::= {pr1645v2PRoutQmEntry 506069504}

pr1645v2PRoutQmUpDownJitterUpBinsBin2 OBJECT-TYPE
   SYNTAX      Counter32
   MAX-ACCESS  read-only
   STATUS      current
   DESCRIPTION
      "Path: router.performance.qualityMonitor.upDown.jitterUpBins.bin2

       32 bit unsigned wrappable counter."
   ::= {pr1645v2PRoutQmEntry 506069760}

pr1645v2PRoutQmUpDownJitterUpBinsBin3 OBJECT-TYPE
   SYNTAX      Counter32
   MAX-ACCESS  read-only
   STATUS      current
   DESCRIPTION
      "Path: router.performance.qualityMonitor.upDown.jitterUpBins.bin3

       32 bit unsigned wrappable counter."
   ::= {pr1645v2PRoutQmEntry 506070016}

pr1645v2PRoutQmUpDownJitterUpBinsBin4 OBJECT-TYPE
   SYNTAX      Counter32
   MAX-ACCESS  read-only
   STATUS      current
   DESCRIPTION
      "Path: router.performance.qualityMonitor.upDown.jitterUpBins.bin4

       32 bit unsigned wrappable counter."
   ::= {pr1645v2PRoutQmEntry 506070272}

pr1645v2PRoutQmUpDownJitterUpBinsBin5 OBJECT-TYPE
   SYNTAX      Counter32
   MAX-ACCESS  read-only
   STATUS      current
   DESCRIPTION
      "Path: router.performance.qualityMonitor.upDown.jitterUpBins.bin5

       32 bit unsigned wrappable counter."
   ::= {pr1645v2PRoutQmEntry 506070528}

pr1645v2PRoutQmUpDownJitterUpBinsBin6 OBJECT-TYPE
   SYNTAX      Counter32
   MAX-ACCESS  read-only
   STATUS      current
   DESCRIPTION
      "Path: router.performance.qualityMonitor.upDown.jitterUpBins.bin6

       32 bit unsigned wrappable counter."
   ::= {pr1645v2PRoutQmEntry 506070784}

pr1645v2PRoutQmUpDownJitterUpBinsBin7 OBJECT-TYPE
   SYNTAX      Counter32
   MAX-ACCESS  read-only
   STATUS      current
   DESCRIPTION
      "Path: router.performance.qualityMonitor.upDown.jitterUpBins.bin7

       32 bit unsigned wrappable counter."
   ::= {pr1645v2PRoutQmEntry 506071040}

pr1645v2PRoutQmUpDownJitterUpBinsMaxBin8 OBJECT-TYPE
   SYNTAX      Counter32
   MAX-ACCESS  read-only
   STATUS      current
   DESCRIPTION
      "Path: router.performance.qualityMonitor.upDown.jitterUpBins.maxBin8

       32 bit unsigned wrappable counter."
   ::= {pr1645v2PRoutQmEntry 506071296}

pr1645v2PRoutQmUpDownJitterUpBinsMax OBJECT-TYPE
   SYNTAX      Integer32
   MAX-ACCESS  read-only
   STATUS      current
   DESCRIPTION
      "Path: router.performance.qualityMonitor.upDown.jitterUpBins.max

       unit name = sec
       formula = 1000 / ; 1000 *"
   ::= {pr1645v2PRoutQmEntry 506074624}

pr1645v2PRoutQmUpDownJitterUpBinsPlusMax OBJECT-TYPE
   SYNTAX      Counter32
   MAX-ACCESS  read-only
   STATUS      current
   DESCRIPTION
      "Path: router.performance.qualityMonitor.upDown.jitterUpBins.plusMax

       32 bit unsigned wrappable counter."
   ::= {pr1645v2PRoutQmEntry 506071552}

pr1645v2PRoutQmUpDownLossDown OBJECT-TYPE
   SYNTAX      Counter32
   MAX-ACCESS  read-only
   STATUS      current
   DESCRIPTION
      "Path: router.performance.qualityMonitor.upDown.lossDown

       32 bit unsigned wrappable counter."
   ::= {pr1645v2PRoutQmEntry 504102912}

pr1645v2PRoutQmUpDownLossDelayDown OBJECT-TYPE
   SYNTAX      Counter32
   MAX-ACCESS  read-only
   STATUS      current
   DESCRIPTION
      "Path: router.performance.qualityMonitor.upDown.lossDelayDown

       32 bit unsigned wrappable counter."
   ::= {pr1645v2PRoutQmEntry 504168448}

pr1645v2PRoutQmUpDownDelayDownMin OBJECT-TYPE
   SYNTAX      Integer32
   MAX-ACCESS  read-only
   STATUS      current
   DESCRIPTION
      "Path: router.performance.qualityMonitor.upDown.delayDownMin

       unit name = sec
       formula = 1000 / ; 1000 *"
   ::= {pr1645v2PRoutQmEntry 505610240}

pr1645v2PRoutQmUpDownDelayDownAvrg OBJECT-TYPE
   SYNTAX      Integer32
   MAX-ACCESS  read-only
   STATUS      current
   DESCRIPTION
      "Path: router.performance.qualityMonitor.upDown.delayDownAvrg

       unit name = sec
       formula = 1000 / ; 1000 *"
   ::= {pr1645v2PRoutQmEntry 505675776}

pr1645v2PRoutQmUpDownDelayDownMax OBJECT-TYPE
   SYNTAX      Integer32
   MAX-ACCESS  read-only
   STATUS      current
   DESCRIPTION
      "Path: router.performance.qualityMonitor.upDown.delayDownMax

       unit name = sec
       formula = 1000 / ; 1000 *"
   ::= {pr1645v2PRoutQmEntry 505741312}

pr1645v2PRoutQmUpDownDelayDownBinsType OBJECT-TYPE
   SYNTAX      INTEGER
               {
               fd (1),
               fdr (2),
               notInUse (3),
               ifdv (4)
               }
   MAX-ACCESS  read-only
   STATUS      current
   DESCRIPTION
      "Path: router.performance.qualityMonitor.upDown.delayDownBins.type

       Possibilities:
               fd   (1)
               fdr   (2)
               notInUse   (3)
               ifdv   (4)"
   ::= {pr1645v2PRoutQmEntry 506009344}

pr1645v2PRoutQmUpDownDelayDownBinsMinMin OBJECT-TYPE
   SYNTAX      Counter32
   MAX-ACCESS  read-only
   STATUS      current
   DESCRIPTION
      "Path: router.performance.qualityMonitor.upDown.delayDownBins.minMin

       32 bit unsigned wrappable counter."
   ::= {pr1645v2PRoutQmEntry 506003712}

pr1645v2PRoutQmUpDownDelayDownBinsMin OBJECT-TYPE
   SYNTAX      Integer32
   MAX-ACCESS  read-only
   STATUS      current
   DESCRIPTION
      "Path: router.performance.qualityMonitor.upDown.delayDownBins.min

       unit name = sec
       formula = 1000 / ; 1000 *"
   ::= {pr1645v2PRoutQmEntry 506008832}

pr1645v2PRoutQmUpDownDelayDownBinsMinBin1 OBJECT-TYPE
   SYNTAX      Counter32
   MAX-ACCESS  read-only
   STATUS      current
   DESCRIPTION
      "Path: router.performance.qualityMonitor.upDown.delayDownBins.minBin1

       32 bit unsigned wrappable counter."
   ::= {pr1645v2PRoutQmEntry 506003968}

pr1645v2PRoutQmUpDownDelayDownBinsBin2 OBJECT-TYPE
   SYNTAX      Counter32
   MAX-ACCESS  read-only
   STATUS      current
   DESCRIPTION
      "Path: router.performance.qualityMonitor.upDown.delayDownBins.bin2

       32 bit unsigned wrappable counter."
   ::= {pr1645v2PRoutQmEntry 506004224}

pr1645v2PRoutQmUpDownDelayDownBinsBin3 OBJECT-TYPE
   SYNTAX      Counter32
   MAX-ACCESS  read-only
   STATUS      current
   DESCRIPTION
      "Path: router.performance.qualityMonitor.upDown.delayDownBins.bin3

       32 bit unsigned wrappable counter."
   ::= {pr1645v2PRoutQmEntry 506004480}

pr1645v2PRoutQmUpDownDelayDownBinsBin4 OBJECT-TYPE
   SYNTAX      Counter32
   MAX-ACCESS  read-only
   STATUS      current
   DESCRIPTION
      "Path: router.performance.qualityMonitor.upDown.delayDownBins.bin4

       32 bit unsigned wrappable counter."
   ::= {pr1645v2PRoutQmEntry 506004736}

pr1645v2PRoutQmUpDownDelayDownBinsBin5 OBJECT-TYPE
   SYNTAX      Counter32
   MAX-ACCESS  read-only
   STATUS      current
   DESCRIPTION
      "Path: router.performance.qualityMonitor.upDown.delayDownBins.bin5

       32 bit unsigned wrappable counter."
   ::= {pr1645v2PRoutQmEntry 506004992}

pr1645v2PRoutQmUpDownDelayDownBinsBin6 OBJECT-TYPE
   SYNTAX      Counter32
   MAX-ACCESS  read-only
   STATUS      current
   DESCRIPTION
      "Path: router.performance.qualityMonitor.upDown.delayDownBins.bin6

       32 bit unsigned wrappable counter."
   ::= {pr1645v2PRoutQmEntry 506005248}

pr1645v2PRoutQmUpDownDelayDownBinsBin7 OBJECT-TYPE
   SYNTAX      Counter32
   MAX-ACCESS  read-only
   STATUS      current
   DESCRIPTION
      "Path: router.performance.qualityMonitor.upDown.delayDownBins.bin7

       32 bit unsigned wrappable counter."
   ::= {pr1645v2PRoutQmEntry 506005504}

pr1645v2PRoutQmUpDownDelayDownBinsMaxBin8 OBJECT-TYPE
   SYNTAX      Counter32
   MAX-ACCESS  read-only
   STATUS      current
   DESCRIPTION
      "Path: router.performance.qualityMonitor.upDown.delayDownBins.maxBin8

       32 bit unsigned wrappable counter."
   ::= {pr1645v2PRoutQmEntry 506005760}

pr1645v2PRoutQmUpDownDelayDownBinsMax OBJECT-TYPE
   SYNTAX      Integer32
   MAX-ACCESS  read-only
   STATUS      current
   DESCRIPTION
      "Path: router.performance.qualityMonitor.upDown.delayDownBins.max

       unit name = sec
       formula = 1000 / ; 1000 *"
   ::= {pr1645v2PRoutQmEntry 506009088}

pr1645v2PRoutQmUpDownDelayDownBinsPlusMax OBJECT-TYPE
   SYNTAX      Counter32
   MAX-ACCESS  read-only
   STATUS      current
   DESCRIPTION
      "Path: router.performance.qualityMonitor.upDown.delayDownBins.plusMax

       32 bit unsigned wrappable counter."
   ::= {pr1645v2PRoutQmEntry 506006016}

pr1645v2PRoutQmUpDownJitterDown OBJECT-TYPE
   SYNTAX      Integer32
   MAX-ACCESS  read-only
   STATUS      current
   DESCRIPTION
      "Path: router.performance.qualityMonitor.upDown.jitterDown

       unit name = sec
       formula = 1000 / ; 1000 *"
   ::= {pr1645v2PRoutQmEntry 503840768}

pr1645v2PRoutQmUpDownJitterDownNegMax OBJECT-TYPE
   SYNTAX      Integer32
   MAX-ACCESS  read-only
   STATUS      current
   DESCRIPTION
      "Path: router.performance.qualityMonitor.upDown.jitterDownNegMax

       unit name = sec
       formula = 1000 / ; 1000 *"
   ::= {pr1645v2PRoutQmEntry 503578624}

pr1645v2PRoutQmUpDownJitterDownAvrg OBJECT-TYPE
   SYNTAX      Integer32
   MAX-ACCESS  read-only
   STATUS      current
   DESCRIPTION
      "Path: router.performance.qualityMonitor.upDown.jitterDownAvrg

       unit name = sec
       formula = 1000 / ; 1000 *"
   ::= {pr1645v2PRoutQmEntry 503644160}

pr1645v2PRoutQmUpDownJitterDownPosMax OBJECT-TYPE
   SYNTAX      Integer32
   MAX-ACCESS  read-only
   STATUS      current
   DESCRIPTION
      "Path: router.performance.qualityMonitor.upDown.jitterDownPosMax

       unit name = sec
       formula = 1000 / ; 1000 *"
   ::= {pr1645v2PRoutQmEntry 503709696}

pr1645v2PRoutQmUpDownJitterDownBinsType OBJECT-TYPE
   SYNTAX      INTEGER
               {
               fd (1),
               fdr (2),
               notInUse (3),
               ifdv (4)
               }
   MAX-ACCESS  read-only
   STATUS      current
   DESCRIPTION
      "Path: router.performance.qualityMonitor.upDown.jitterDownBins.type

       Possibilities:
               fd   (1)
               fdr   (2)
               notInUse   (3)
               ifdv   (4)"
   ::= {pr1645v2PRoutQmEntry 506205952}

pr1645v2PRoutQmUpDownJitterDownBinsMinMin OBJECT-TYPE
   SYNTAX      Counter32
   MAX-ACCESS  read-only
   STATUS      current
   DESCRIPTION
      "Path: router.performance.qualityMonitor.upDown.jitterDownBins.minMin

       32 bit unsigned wrappable counter."
   ::= {pr1645v2PRoutQmEntry 506200320}

pr1645v2PRoutQmUpDownJitterDownBinsMin OBJECT-TYPE
   SYNTAX      Integer32
   MAX-ACCESS  read-only
   STATUS      current
   DESCRIPTION
      "Path: router.performance.qualityMonitor.upDown.jitterDownBins.min

       unit name = sec
       formula = 1000 / ; 1000 *"
   ::= {pr1645v2PRoutQmEntry 506205440}

pr1645v2PRoutQmUpDownJitterDownBinsMinBin1 OBJECT-TYPE
   SYNTAX      Counter32
   MAX-ACCESS  read-only
   STATUS      current
   DESCRIPTION
      "Path: router.performance.qualityMonitor.upDown.jitterDownBins.minBin1

       32 bit unsigned wrappable counter."
   ::= {pr1645v2PRoutQmEntry 506200576}

pr1645v2PRoutQmUpDownJitterDownBinsBin2 OBJECT-TYPE
   SYNTAX      Counter32
   MAX-ACCESS  read-only
   STATUS      current
   DESCRIPTION
      "Path: router.performance.qualityMonitor.upDown.jitterDownBins.bin2

       32 bit unsigned wrappable counter."
   ::= {pr1645v2PRoutQmEntry 506200832}

pr1645v2PRoutQmUpDownJitterDownBinsBin3 OBJECT-TYPE
   SYNTAX      Counter32
   MAX-ACCESS  read-only
   STATUS      current
   DESCRIPTION
      "Path: router.performance.qualityMonitor.upDown.jitterDownBins.bin3

       32 bit unsigned wrappable counter."
   ::= {pr1645v2PRoutQmEntry 506201088}

pr1645v2PRoutQmUpDownJitterDownBinsBin4 OBJECT-TYPE
   SYNTAX      Counter32
   MAX-ACCESS  read-only
   STATUS      current
   DESCRIPTION
      "Path: router.performance.qualityMonitor.upDown.jitterDownBins.bin4

       32 bit unsigned wrappable counter."
   ::= {pr1645v2PRoutQmEntry 506201344}

pr1645v2PRoutQmUpDownJitterDownBinsBin5 OBJECT-TYPE
   SYNTAX      Counter32
   MAX-ACCESS  read-only
   STATUS      current
   DESCRIPTION
      "Path: router.performance.qualityMonitor.upDown.jitterDownBins.bin5

       32 bit unsigned wrappable counter."
   ::= {pr1645v2PRoutQmEntry 506201600}

pr1645v2PRoutQmUpDownJitterDownBinsBin6 OBJECT-TYPE
   SYNTAX      Counter32
   MAX-ACCESS  read-only
   STATUS      current
   DESCRIPTION
      "Path: router.performance.qualityMonitor.upDown.jitterDownBins.bin6

       32 bit unsigned wrappable counter."
   ::= {pr1645v2PRoutQmEntry 506201856}

pr1645v2PRoutQmUpDownJitterDownBinsBin7 OBJECT-TYPE
   SYNTAX      Counter32
   MAX-ACCESS  read-only
   STATUS      current
   DESCRIPTION
      "Path: router.performance.qualityMonitor.upDown.jitterDownBins.bin7

       32 bit unsigned wrappable counter."
   ::= {pr1645v2PRoutQmEntry 506202112}

pr1645v2PRoutQmUpDownJitterDownBinsMaxBin8 OBJECT-TYPE
   SYNTAX      Counter32
   MAX-ACCESS  read-only
   STATUS      current
   DESCRIPTION
      "Path: router.performance.qualityMonitor.upDown.jitterDownBins.maxBin8

       32 bit unsigned wrappable counter."
   ::= {pr1645v2PRoutQmEntry 506202368}

pr1645v2PRoutQmUpDownJitterDownBinsMax OBJECT-TYPE
   SYNTAX      Integer32
   MAX-ACCESS  read-only
   STATUS      current
   DESCRIPTION
      "Path: router.performance.qualityMonitor.upDown.jitterDownBins.max

       unit name = sec
       formula = 1000 / ; 1000 *"
   ::= {pr1645v2PRoutQmEntry 506205696}

pr1645v2PRoutQmUpDownJitterDownBinsPlusMax OBJECT-TYPE
   SYNTAX      Counter32
   MAX-ACCESS  read-only
   STATUS      current
   DESCRIPTION
      "Path: router.performance.qualityMonitor.upDown.jitterDownBins.plusMax

       32 bit unsigned wrappable counter."
   ::= {pr1645v2PRoutQmEntry 506202624}

pr1645v2PRoutQmLastLogSysUpTime OBJECT-TYPE
   SYNTAX      TimeTicks
   MAX-ACCESS  read-only
   STATUS      current
   DESCRIPTION
      "Path: router.performance.qualityMonitor.lastLog.sysUpTime

       Time in centi-second."
   ::= {pr1645v2PRoutQmEntry 671154176}

pr1645v2PRoutQmLastLogNbrTxPckt OBJECT-TYPE
   SYNTAX      Counter32
   MAX-ACCESS  read-only
   STATUS      current
   DESCRIPTION
      "Path: router.performance.qualityMonitor.lastLog.nbrOfTxPackets

       32 bit unsigned wrappable counter."
   ::= {pr1645v2PRoutQmEntry 671285248}

pr1645v2PRoutQmLastLogNbrRxPckt OBJECT-TYPE
   SYNTAX      Counter32
   MAX-ACCESS  read-only
   STATUS      current
   DESCRIPTION
      "Path: router.performance.qualityMonitor.lastLog.nbrOfRxPackets

       32 bit unsigned wrappable counter."
   ::= {pr1645v2PRoutQmEntry 671350784}

pr1645v2PRoutQmLastLogError OBJECT-TYPE
   SYNTAX      Counter32
   MAX-ACCESS  read-only
   STATUS      current
   DESCRIPTION
      "Path: router.performance.qualityMonitor.lastLog.error

       32 bit unsigned wrappable counter."
   ::= {pr1645v2PRoutQmEntry 672202752}

pr1645v2PRoutQmLastLogLoss OBJECT-TYPE
   SYNTAX      Counter32
   MAX-ACCESS  read-only
   STATUS      current
   DESCRIPTION
      "Path: router.performance.qualityMonitor.lastLog.loss

       32 bit unsigned wrappable counter."
   ::= {pr1645v2PRoutQmEntry 671481856}

pr1645v2PRoutQmLastLogLossDelay OBJECT-TYPE
   SYNTAX      Counter32
   MAX-ACCESS  read-only
   STATUS      current
   DESCRIPTION
      "Path: router.performance.qualityMonitor.lastLog.lossDelay

       32 bit unsigned wrappable counter."
   ::= {pr1645v2PRoutQmEntry 672137216}

pr1645v2PRoutQmLastLogDelayMin OBJECT-TYPE
   SYNTAX      Integer32
   MAX-ACCESS  read-only
   STATUS      current
   DESCRIPTION
      "Path: router.performance.qualityMonitor.lastLog.delayMin

       unit name = sec
       formula = 1000 / ; 1000 *"
   ::= {pr1645v2PRoutQmEntry 671809536}

pr1645v2PRoutQmLastLogDelayAvrg OBJECT-TYPE
   SYNTAX      Integer32
   MAX-ACCESS  read-only
   STATUS      current
   DESCRIPTION
      "Path: router.performance.qualityMonitor.lastLog.delayAvrg

       unit name = sec
       formula = 1000 / ; 1000 *"
   ::= {pr1645v2PRoutQmEntry 671547392}

pr1645v2PRoutQmLastLogDelayMax OBJECT-TYPE
   SYNTAX      Integer32
   MAX-ACCESS  read-only
   STATUS      current
   DESCRIPTION
      "Path: router.performance.qualityMonitor.lastLog.delayMax

       unit name = sec
       formula = 1000 / ; 1000 *"
   ::= {pr1645v2PRoutQmEntry 671612928}

pr1645v2PRoutQmLastLogJitterNegMax OBJECT-TYPE
   SYNTAX      Integer32
   MAX-ACCESS  read-only
   STATUS      current
   DESCRIPTION
      "Path: router.performance.qualityMonitor.lastLog.jitterNegMax

       unit name = sec
       formula = 1000 / ; 1000 *"
   ::= {pr1645v2PRoutQmEntry 672006144}

pr1645v2PRoutQmLastLogJitterAvrg OBJECT-TYPE
   SYNTAX      Integer32
   MAX-ACCESS  read-only
   STATUS      current
   DESCRIPTION
      "Path: router.performance.qualityMonitor.lastLog.jitterAvrg

       unit name = sec
       formula = 1000 / ; 1000 *"
   ::= {pr1645v2PRoutQmEntry 671678464}

pr1645v2PRoutQmLastLogJitterPosMax OBJECT-TYPE
   SYNTAX      Integer32
   MAX-ACCESS  read-only
   STATUS      current
   DESCRIPTION
      "Path: router.performance.qualityMonitor.lastLog.jitterPosMax

       unit name = sec
       formula = 1000 / ; 1000 *"
   ::= {pr1645v2PRoutQmEntry 671744000}

pr1645v2PRoutQmLastLogUpDownStatus OBJECT-TYPE
   SYNTAX      INTEGER
               {
               notInUse (3),
               onlyJitter (1),
               jitterAndLoss (2),
               all (4),
               onlyLoss (8)
               }
   MAX-ACCESS  read-only
   STATUS      current
   DESCRIPTION
      "Path: router.performance.qualityMonitor.lastLog.upDown.status

       Possibilities:
               notInUse   (3)
               onlyJitter   (1)
               jitterAndLoss   (2)
               all   (4)
               onlyLoss   (8)"
   ::= {pr1645v2PRoutQmEntry 673059840}

pr1645v2PRoutQmLastLogUpDownLossUp OBJECT-TYPE
   SYNTAX      Counter32
   MAX-ACCESS  read-only
   STATUS      current
   DESCRIPTION
      "Path: router.performance.qualityMonitor.lastLog.upDown.lossUp

       32 bit unsigned wrappable counter."
   ::= {pr1645v2PRoutQmEntry 673057280}

pr1645v2PRoutQmLastLogUpDownLossDelayUp OBJECT-TYPE
   SYNTAX      Counter32
   MAX-ACCESS  read-only
   STATUS      current
   DESCRIPTION
      "Path: router.performance.qualityMonitor.lastLog.upDown.lossDelayUp

       32 bit unsigned wrappable counter."
   ::= {pr1645v2PRoutQmEntry 673057536}

pr1645v2PRoutQmLastLogUpDownDelayUpMin OBJECT-TYPE
   SYNTAX      Integer32
   MAX-ACCESS  read-only
   STATUS      current
   DESCRIPTION
      "Path: router.performance.qualityMonitor.lastLog.upDown.delayUpMin

       unit name = sec
       formula = 1000 / ; 1000 *"
   ::= {pr1645v2PRoutQmEntry 673062400}

pr1645v2PRoutQmLastLogUpDownDelayUpAvrg OBJECT-TYPE
   SYNTAX      Integer32
   MAX-ACCESS  read-only
   STATUS      current
   DESCRIPTION
      "Path: router.performance.qualityMonitor.lastLog.upDown.delayUpAvrg

       unit name = sec
       formula = 1000 / ; 1000 *"
   ::= {pr1645v2PRoutQmEntry 673062656}

pr1645v2PRoutQmLastLogUpDownDelayUpMax OBJECT-TYPE
   SYNTAX      Integer32
   MAX-ACCESS  read-only
   STATUS      current
   DESCRIPTION
      "Path: router.performance.qualityMonitor.lastLog.upDown.delayUpMax

       unit name = sec
       formula = 1000 / ; 1000 *"
   ::= {pr1645v2PRoutQmEntry 673062912}

pr1645v2PRoutQmLastLogUpDownJitterUpNegMax OBJECT-TYPE
   SYNTAX      Integer32
   MAX-ACCESS  read-only
   STATUS      current
   DESCRIPTION
      "Path: router.performance.qualityMonitor.lastLog.upDown.jitterUpNegMax

       unit name = sec
       formula = 1000 / ; 1000 *"
   ::= {pr1645v2PRoutQmEntry 673054976}

pr1645v2PRoutQmLastLogUpDownJitterUpAvrg OBJECT-TYPE
   SYNTAX      Integer32
   MAX-ACCESS  read-only
   STATUS      current
   DESCRIPTION
      "Path: router.performance.qualityMonitor.lastLog.upDown.jitterUpAvrg

       unit name = sec
       formula = 1000 / ; 1000 *"
   ::= {pr1645v2PRoutQmEntry 673055232}

pr1645v2PRoutQmLastLogUpDownJitterUpPosMax OBJECT-TYPE
   SYNTAX      Integer32
   MAX-ACCESS  read-only
   STATUS      current
   DESCRIPTION
      "Path: router.performance.qualityMonitor.lastLog.upDown.jitterUpPosMax

       unit name = sec
       formula = 1000 / ; 1000 *"
   ::= {pr1645v2PRoutQmEntry 673055488}

pr1645v2PRoutQmLastLogUpDownLossDown OBJECT-TYPE
   SYNTAX      Counter32
   MAX-ACCESS  read-only
   STATUS      current
   DESCRIPTION
      "Path: router.performance.qualityMonitor.lastLog.upDown.lossDown

       32 bit unsigned wrappable counter."
   ::= {pr1645v2PRoutQmEntry 673057792}

pr1645v2PRoutQmLastLogUpDownLossDelayDown OBJECT-TYPE
   SYNTAX      Counter32
   MAX-ACCESS  read-only
   STATUS      current
   DESCRIPTION
      "Path: router.performance.qualityMonitor.lastLog.upDown.lossDelayDown

       32 bit unsigned wrappable counter."
   ::= {pr1645v2PRoutQmEntry 673058048}

pr1645v2PRoutQmLastLogUpDownDelayDownMin OBJECT-TYPE
   SYNTAX      Integer32
   MAX-ACCESS  read-only
   STATUS      current
   DESCRIPTION
      "Path: router.performance.qualityMonitor.lastLog.upDown.delayDownMin

       unit name = sec
       formula = 1000 / ; 1000 *"
   ::= {pr1645v2PRoutQmEntry 673063680}

pr1645v2PRoutQmLastLogUpDownDelayDownAvrg OBJECT-TYPE
   SYNTAX      Integer32
   MAX-ACCESS  read-only
   STATUS      current
   DESCRIPTION
      "Path: router.performance.qualityMonitor.lastLog.upDown.delayDownAvrg

       unit name = sec
       formula = 1000 / ; 1000 *"
   ::= {pr1645v2PRoutQmEntry 673063936}

pr1645v2PRoutQmLastLogUpDownDelayDownMax OBJECT-TYPE
   SYNTAX      Integer32
   MAX-ACCESS  read-only
   STATUS      current
   DESCRIPTION
      "Path: router.performance.qualityMonitor.lastLog.upDown.delayDownMax

       unit name = sec
       formula = 1000 / ; 1000 *"
   ::= {pr1645v2PRoutQmEntry 673064192}

pr1645v2PRoutQmLastLogUpDownJitterDownNegMax OBJECT-TYPE
   SYNTAX      Integer32
   MAX-ACCESS  read-only
   STATUS      current
   DESCRIPTION
      "Path: router.performance.qualityMonitor.lastLog.upDown.jitterDownNegMax

       unit name = sec
       formula = 1000 / ; 1000 *"
   ::= {pr1645v2PRoutQmEntry 673055744}

pr1645v2PRoutQmLastLogUpDownJitterDownAvrg OBJECT-TYPE
   SYNTAX      Integer32
   MAX-ACCESS  read-only
   STATUS      current
   DESCRIPTION
      "Path: router.performance.qualityMonitor.lastLog.upDown.jitterDownAvrg

       unit name = sec
       formula = 1000 / ; 1000 *"
   ::= {pr1645v2PRoutQmEntry 673056000}

pr1645v2PRoutQmLastLogUpDownJitterDownPosMax OBJECT-TYPE
   SYNTAX      Integer32
   MAX-ACCESS  read-only
   STATUS      current
   DESCRIPTION
      "Path: router.performance.qualityMonitor.lastLog.upDown.jitterDownPosMax

       unit name = sec
       formula = 1000 / ; 1000 *"
   ::= {pr1645v2PRoutQmEntry 673056256}

pr1645v2PRoutQmLastLogDate OBJECT-TYPE
   SYNTAX      DisplayString
   MAX-ACCESS  read-only
   STATUS      current
   DESCRIPTION
      "Path: router.performance.qualityMonitor.lastLog.date"
   ::= {pr1645v2PRoutQmEntry 673120256}

pr1645v2PRoutQmAlarm OBJECT-TYPE
   SYNTAX      Integer32
   MAX-ACCESS  read-only
   STATUS      current
   DESCRIPTION
      "Path: router.performance.qualityMonitor.alarm

       Bit meanings:
               bit 0 = loss,
               bit 1 = delayAvrg,
               bit 2 = delayMax,
               bit 3 = delayMinMax,
               bit 4 = jitterAvrg,
               bit 5 = jitterPosMax,
               bit 6 = jitterNegMax,
               bit 7 = lossUp,
               bit 8 = jitterUpAvrg,
               bit 9 = jitterUpPosMax,
               bit 10 = jitterUpNegMax,
               bit 11 = lossDown,
               bit 12 = jitterDownAvrg,
               bit 13 = jitterDownPosMax,
               bit 14 = jitterDownNegMax,
               bit 15 = delayUpAvrg,
               bit 16 = delayUpMax,
               bit 17 = delayDownAvrg,
               bit 18 = delayDownMax,
               bit 19 = bfdCtrl"
   ::= {pr1645v2PRoutQmEntry 251658240}

pr1645v2PRoutQmLastError OBJECT-TYPE
   SYNTAX      DisplayString
   MAX-ACCESS  read-only
   STATUS      current
   DESCRIPTION
      "Path: router.performance.qualityMonitor.lastError"
   ::= {pr1645v2PRoutQmEntry 318767104}

pr1645v2PRoutQmLogging OBJECT-TYPE
   SYNTAX      SEQUENCE OF Pr1645v2PRoutQmLoggingEntry
   MAX-ACCESS  not-accessible
   STATUS      current
   DESCRIPTION
      ""
   ::= {pr1645v2PRoutQm 335544320}

pr1645v2PRoutQmLoggingEntry OBJECT-TYPE
   SYNTAX      Pr1645v2PRoutQmLoggingEntry
   MAX-ACCESS  not-accessible
   STATUS      current
   DESCRIPTION
      ""
   INDEX      { pr1645v2PRoutQmTableIx,
                pr1645v2PRoutQmLoggingTableIx }
   ::= {pr1645v2PRoutQmLogging 1}

Pr1645v2PRoutQmLoggingEntry ::=
   SEQUENCE
      {
      pr1645v2PRoutQmLoggingTableIx
         TableIndex,
      pr1645v2PRoutQmLoggingSysUpTime
         TimeTicks,
      pr1645v2PRoutQmLoggingNbrTxPckt
         Counter32,
      pr1645v2PRoutQmLoggingNbrRxPckt
         Counter32,
      pr1645v2PRoutQmLoggingError
         Counter32,
      pr1645v2PRoutQmLoggingLoss
         Counter32,
      pr1645v2PRoutQmLoggingLossDelay
         Counter32,
      pr1645v2PRoutQmLoggingDelayMin
         Integer32,
      pr1645v2PRoutQmLoggingDelayAvrg
         Integer32,
      pr1645v2PRoutQmLoggingDelayMax
         Integer32,
      pr1645v2PRoutQmLoggingJitterNegMax
         Integer32,
      pr1645v2PRoutQmLoggingJitterAvrg
         Integer32,
      pr1645v2PRoutQmLoggingJitterPosMax
         Integer32,
      pr1645v2PRoutQmLoggingUpDownStatus
         INTEGER,
      pr1645v2PRoutQmLoggingUpDownLossUp
         Counter32,
      pr1645v2PRoutQmLoggingUpDownLossDelayUp
         Counter32,
      pr1645v2PRoutQmLoggingUpDownDelayUpMin
         Integer32,
      pr1645v2PRoutQmLoggingUpDownDelayUpAvrg
         Integer32,
      pr1645v2PRoutQmLoggingUpDownDelayUpMax
         Integer32,
      pr1645v2PRoutQmLoggingUpDownJitterUpNegMax
         Integer32,
      pr1645v2PRoutQmLoggingUpDownJitterUpAvrg
         Integer32,
      pr1645v2PRoutQmLoggingUpDownJitterUpPosMax
         Integer32,
      pr1645v2PRoutQmLoggingUpDownLossDown
         Counter32,
      pr1645v2PRoutQmLoggingUpDownLossDelayDown
         Counter32,
      pr1645v2PRoutQmLoggingUpDownDelayDownMin
         Integer32,
      pr1645v2PRoutQmLoggingUpDownDelayDownAvrg
         Integer32,
      pr1645v2PRoutQmLoggingUpDownDelayDownMax
         Integer32,
      pr1645v2PRoutQmLoggingUpDownJitterDownNegMax
         Integer32,
      pr1645v2PRoutQmLoggingUpDownJitterDownAvrg
         Integer32,
      pr1645v2PRoutQmLoggingUpDownJitterDownPosMax
         Integer32,
      pr1645v2PRoutQmLoggingDate
         DisplayString
      }

pr1645v2PRoutQmLoggingTableIx OBJECT-TYPE
   SYNTAX      TableIndex
   MAX-ACCESS  not-accessible
   STATUS      current
   DESCRIPTION
      ""
   ::= {pr1645v2PRoutQmLoggingEntry 11}

pr1645v2PRoutQmLoggingSysUpTime OBJECT-TYPE
   SYNTAX      TimeTicks
   MAX-ACCESS  read-only
   STATUS      current
   DESCRIPTION
      "Path: router.performance.qualityMonitor.logging.sysUpTime

       Time in centi-second."
   ::= {pr1645v2PRoutQmLoggingEntry 16777216}

pr1645v2PRoutQmLoggingNbrTxPckt OBJECT-TYPE
   SYNTAX      Counter32
   MAX-ACCESS  read-only
   STATUS      current
   DESCRIPTION
      "Path: router.performance.qualityMonitor.logging.nbrOfTxPackets

       32 bit unsigned wrappable counter."
   ::= {pr1645v2PRoutQmLoggingEntry 50331648}

pr1645v2PRoutQmLoggingNbrRxPckt OBJECT-TYPE
   SYNTAX      Counter32
   MAX-ACCESS  read-only
   STATUS      current
   DESCRIPTION
      "Path: router.performance.qualityMonitor.logging.nbrOfRxPackets

       32 bit unsigned wrappable counter."
   ::= {pr1645v2PRoutQmLoggingEntry 67108864}

pr1645v2PRoutQmLoggingError OBJECT-TYPE
   SYNTAX      Counter32
   MAX-ACCESS  read-only
   STATUS      current
   DESCRIPTION
      "Path: router.performance.qualityMonitor.logging.error

       32 bit unsigned wrappable counter."
   ::= {pr1645v2PRoutQmLoggingEntry 285212672}

pr1645v2PRoutQmLoggingLoss OBJECT-TYPE
   SYNTAX      Counter32
   MAX-ACCESS  read-only
   STATUS      current
   DESCRIPTION
      "Path: router.performance.qualityMonitor.logging.loss

       32 bit unsigned wrappable counter."
   ::= {pr1645v2PRoutQmLoggingEntry 100663296}

pr1645v2PRoutQmLoggingLossDelay OBJECT-TYPE
   SYNTAX      Counter32
   MAX-ACCESS  read-only
   STATUS      current
   DESCRIPTION
      "Path: router.performance.qualityMonitor.logging.lossDelay

       32 bit unsigned wrappable counter."
   ::= {pr1645v2PRoutQmLoggingEntry 268435456}

pr1645v2PRoutQmLoggingDelayMin OBJECT-TYPE
   SYNTAX      Integer32
   MAX-ACCESS  read-only
   STATUS      current
   DESCRIPTION
      "Path: router.performance.qualityMonitor.logging.delayMin

       unit name = sec
       formula = 1000 / ; 1000 *"
   ::= {pr1645v2PRoutQmLoggingEntry 184549376}

pr1645v2PRoutQmLoggingDelayAvrg OBJECT-TYPE
   SYNTAX      Integer32
   MAX-ACCESS  read-only
   STATUS      current
   DESCRIPTION
      "Path: router.performance.qualityMonitor.logging.delayAvrg

       unit name = sec
       formula = 1000 / ; 1000 *"
   ::= {pr1645v2PRoutQmLoggingEntry 117440512}

pr1645v2PRoutQmLoggingDelayMax OBJECT-TYPE
   SYNTAX      Integer32
   MAX-ACCESS  read-only
   STATUS      current
   DESCRIPTION
      "Path: router.performance.qualityMonitor.logging.delayMax

       unit name = sec
       formula = 1000 / ; 1000 *"
   ::= {pr1645v2PRoutQmLoggingEntry 134217728}

pr1645v2PRoutQmLoggingJitterNegMax OBJECT-TYPE
   SYNTAX      Integer32
   MAX-ACCESS  read-only
   STATUS      current
   DESCRIPTION
      "Path: router.performance.qualityMonitor.logging.jitterNegMax

       unit name = sec
       formula = 1000 / ; 1000 *"
   ::= {pr1645v2PRoutQmLoggingEntry 234881024}

pr1645v2PRoutQmLoggingJitterAvrg OBJECT-TYPE
   SYNTAX      Integer32
   MAX-ACCESS  read-only
   STATUS      current
   DESCRIPTION
      "Path: router.performance.qualityMonitor.logging.jitterAvrg

       unit name = sec
       formula = 1000 / ; 1000 *"
   ::= {pr1645v2PRoutQmLoggingEntry 150994944}

pr1645v2PRoutQmLoggingJitterPosMax OBJECT-TYPE
   SYNTAX      Integer32
   MAX-ACCESS  read-only
   STATUS      current
   DESCRIPTION
      "Path: router.performance.qualityMonitor.logging.jitterPosMax

       unit name = sec
       formula = 1000 / ; 1000 *"
   ::= {pr1645v2PRoutQmLoggingEntry 167772160}

pr1645v2PRoutQmLoggingUpDownStatus OBJECT-TYPE
   SYNTAX      INTEGER
               {
               notInUse (3),
               onlyJitter (1),
               jitterAndLoss (2),
               all (4),
               onlyLoss (8)
               }
   MAX-ACCESS  read-only
   STATUS      current
   DESCRIPTION
      "Path: router.performance.qualityMonitor.logging.upDown.status

       Possibilities:
               notInUse   (3)
               onlyJitter   (1)
               jitterAndLoss   (2)
               all   (4)
               onlyLoss   (8)"
   ::= {pr1645v2PRoutQmLoggingEntry 504627200}

pr1645v2PRoutQmLoggingUpDownLossUp OBJECT-TYPE
   SYNTAX      Counter32
   MAX-ACCESS  read-only
   STATUS      current
   DESCRIPTION
      "Path: router.performance.qualityMonitor.logging.upDown.lossUp

       32 bit unsigned wrappable counter."
   ::= {pr1645v2PRoutQmLoggingEntry 503971840}

pr1645v2PRoutQmLoggingUpDownLossDelayUp OBJECT-TYPE
   SYNTAX      Counter32
   MAX-ACCESS  read-only
   STATUS      current
   DESCRIPTION
      "Path: router.performance.qualityMonitor.logging.upDown.lossDelayUp

       32 bit unsigned wrappable counter."
   ::= {pr1645v2PRoutQmLoggingEntry 504037376}

pr1645v2PRoutQmLoggingUpDownDelayUpMin OBJECT-TYPE
   SYNTAX      Integer32
   MAX-ACCESS  read-only
   STATUS      current
   DESCRIPTION
      "Path: router.performance.qualityMonitor.logging.upDown.delayUpMin

       unit name = sec
       formula = 1000 / ; 1000 *"
   ::= {pr1645v2PRoutQmLoggingEntry 505282560}

pr1645v2PRoutQmLoggingUpDownDelayUpAvrg OBJECT-TYPE
   SYNTAX      Integer32
   MAX-ACCESS  read-only
   STATUS      current
   DESCRIPTION
      "Path: router.performance.qualityMonitor.logging.upDown.delayUpAvrg

       unit name = sec
       formula = 1000 / ; 1000 *"
   ::= {pr1645v2PRoutQmLoggingEntry 505348096}

pr1645v2PRoutQmLoggingUpDownDelayUpMax OBJECT-TYPE
   SYNTAX      Integer32
   MAX-ACCESS  read-only
   STATUS      current
   DESCRIPTION
      "Path: router.performance.qualityMonitor.logging.upDown.delayUpMax

       unit name = sec
       formula = 1000 / ; 1000 *"
   ::= {pr1645v2PRoutQmLoggingEntry 505413632}

pr1645v2PRoutQmLoggingUpDownJitterUpNegMax OBJECT-TYPE
   SYNTAX      Integer32
   MAX-ACCESS  read-only
   STATUS      current
   DESCRIPTION
      "Path: router.performance.qualityMonitor.logging.upDown.jitterUpNegMax

       unit name = sec
       formula = 1000 / ; 1000 *"
   ::= {pr1645v2PRoutQmLoggingEntry 503382016}

pr1645v2PRoutQmLoggingUpDownJitterUpAvrg OBJECT-TYPE
   SYNTAX      Integer32
   MAX-ACCESS  read-only
   STATUS      current
   DESCRIPTION
      "Path: router.performance.qualityMonitor.logging.upDown.jitterUpAvrg

       unit name = sec
       formula = 1000 / ; 1000 *"
   ::= {pr1645v2PRoutQmLoggingEntry 503447552}

pr1645v2PRoutQmLoggingUpDownJitterUpPosMax OBJECT-TYPE
   SYNTAX      Integer32
   MAX-ACCESS  read-only
   STATUS      current
   DESCRIPTION
      "Path: router.performance.qualityMonitor.logging.upDown.jitterUpPosMax

       unit name = sec
       formula = 1000 / ; 1000 *"
   ::= {pr1645v2PRoutQmLoggingEntry 503513088}

pr1645v2PRoutQmLoggingUpDownLossDown OBJECT-TYPE
   SYNTAX      Counter32
   MAX-ACCESS  read-only
   STATUS      current
   DESCRIPTION
      "Path: router.performance.qualityMonitor.logging.upDown.lossDown

       32 bit unsigned wrappable counter."
   ::= {pr1645v2PRoutQmLoggingEntry 504102912}

pr1645v2PRoutQmLoggingUpDownLossDelayDown OBJECT-TYPE
   SYNTAX      Counter32
   MAX-ACCESS  read-only
   STATUS      current
   DESCRIPTION
      "Path: router.performance.qualityMonitor.logging.upDown.lossDelayDown

       32 bit unsigned wrappable counter."
   ::= {pr1645v2PRoutQmLoggingEntry 504168448}

pr1645v2PRoutQmLoggingUpDownDelayDownMin OBJECT-TYPE
   SYNTAX      Integer32
   MAX-ACCESS  read-only
   STATUS      current
   DESCRIPTION
      "Path: router.performance.qualityMonitor.logging.upDown.delayDownMin

       unit name = sec
       formula = 1000 / ; 1000 *"
   ::= {pr1645v2PRoutQmLoggingEntry 505610240}

pr1645v2PRoutQmLoggingUpDownDelayDownAvrg OBJECT-TYPE
   SYNTAX      Integer32
   MAX-ACCESS  read-only
   STATUS      current
   DESCRIPTION
      "Path: router.performance.qualityMonitor.logging.upDown.delayDownAvrg

       unit name = sec
       formula = 1000 / ; 1000 *"
   ::= {pr1645v2PRoutQmLoggingEntry 505675776}

pr1645v2PRoutQmLoggingUpDownDelayDownMax OBJECT-TYPE
   SYNTAX      Integer32
   MAX-ACCESS  read-only
   STATUS      current
   DESCRIPTION
      "Path: router.performance.qualityMonitor.logging.upDown.delayDownMax

       unit name = sec
       formula = 1000 / ; 1000 *"
   ::= {pr1645v2PRoutQmLoggingEntry 505741312}

pr1645v2PRoutQmLoggingUpDownJitterDownNegMax OBJECT-TYPE
   SYNTAX      Integer32
   MAX-ACCESS  read-only
   STATUS      current
   DESCRIPTION
      "Path: router.performance.qualityMonitor.logging.upDown.jitterDownNegMax

       unit name = sec
       formula = 1000 / ; 1000 *"
   ::= {pr1645v2PRoutQmLoggingEntry 503578624}

pr1645v2PRoutQmLoggingUpDownJitterDownAvrg OBJECT-TYPE
   SYNTAX      Integer32
   MAX-ACCESS  read-only
   STATUS      current
   DESCRIPTION
      "Path: router.performance.qualityMonitor.logging.upDown.jitterDownAvrg

       unit name = sec
       formula = 1000 / ; 1000 *"
   ::= {pr1645v2PRoutQmLoggingEntry 503644160}

pr1645v2PRoutQmLoggingUpDownJitterDownPosMax OBJECT-TYPE
   SYNTAX      Integer32
   MAX-ACCESS  read-only
   STATUS      current
   DESCRIPTION
      "Path: router.performance.qualityMonitor.logging.upDown.jitterDownPosMax

       unit name = sec
       formula = 1000 / ; 1000 *"
   ::= {pr1645v2PRoutQmLoggingEntry 503709696}

pr1645v2PRoutQmLoggingDate OBJECT-TYPE
   SYNTAX      DisplayString
   MAX-ACCESS  read-only
   STATUS      current
   DESCRIPTION
      "Path: router.performance.qualityMonitor.logging.date"
   ::= {pr1645v2PRoutQmLoggingEntry 520093696}

pr1645v2PRoutQmLoggingBin OBJECT-TYPE
   SYNTAX      SEQUENCE OF Pr1645v2PRoutQmLoggingBinEntry
   MAX-ACCESS  not-accessible
   STATUS      current
   DESCRIPTION
      ""
   ::= {pr1645v2PRoutQm 337641472}

pr1645v2PRoutQmLoggingBinEntry OBJECT-TYPE
   SYNTAX      Pr1645v2PRoutQmLoggingBinEntry
   MAX-ACCESS  not-accessible
   STATUS      current
   DESCRIPTION
      ""
   INDEX      { pr1645v2PRoutQmTableIx,
                pr1645v2PRoutQmLoggingTableIx,
                pr1645v2PRoutQmLoggingBinTableIx }
   ::= {pr1645v2PRoutQmLoggingBin 1}

Pr1645v2PRoutQmLoggingBinEntry ::=
   SEQUENCE
      {
      pr1645v2PRoutQmLoggingBinTableIx
         TableIndex,
      pr1645v2PRoutQmLoggingBinName
         INTEGER,
      pr1645v2PRoutQmLoggingBinType
         INTEGER,
      pr1645v2PRoutQmLoggingBinMinMin
         Counter32,
      pr1645v2PRoutQmLoggingBinMin
         Integer32,
      pr1645v2PRoutQmLoggingBinMinBin1
         Counter32,
      pr1645v2PRoutQmLoggingBinBin2
         Counter32,
      pr1645v2PRoutQmLoggingBinBin3
         Counter32,
      pr1645v2PRoutQmLoggingBinBin4
         Counter32,
      pr1645v2PRoutQmLoggingBinBin5
         Counter32,
      pr1645v2PRoutQmLoggingBinBin6
         Counter32,
      pr1645v2PRoutQmLoggingBinBin7
         Counter32,
      pr1645v2PRoutQmLoggingBinMaxBin8
         Counter32,
      pr1645v2PRoutQmLoggingBinMax
         Integer32,
      pr1645v2PRoutQmLoggingBinPlusMax
         Counter32
      }

pr1645v2PRoutQmLoggingBinTableIx OBJECT-TYPE
   SYNTAX      TableIndex
   MAX-ACCESS  not-accessible
   STATUS      current
   DESCRIPTION
      ""
   ::= {pr1645v2PRoutQmLoggingBinEntry 11}

pr1645v2PRoutQmLoggingBinName OBJECT-TYPE
   SYNTAX      INTEGER
               {
               delay (1),
               delayUp (2),
               delayDown (3),
               jitter (4),
               jitterUp (5),
               jitterDown (6)
               }
   MAX-ACCESS  read-only
   STATUS      current
   DESCRIPTION
      "Path: router.performance.qualityMonitor.logging.bin.name

       Possibilities:
               delay   (1)
               delayUp   (2)
               delayDown   (3)
               jitter   (4)
               jitterUp   (5)
               jitterDown   (6)"
   ::= {pr1645v2PRoutQmLoggingBinEntry 503316480}

pr1645v2PRoutQmLoggingBinType OBJECT-TYPE
   SYNTAX      INTEGER
               {
               fd (1),
               fdr (2),
               notInUse (3),
               ifdv (4)
               }
   MAX-ACCESS  read-only
   STATUS      current
   DESCRIPTION
      "Path: router.performance.qualityMonitor.logging.bin.type

       Possibilities:
               fd   (1)
               fdr   (2)
               notInUse   (3)
               ifdv   (4)"
   ::= {pr1645v2PRoutQmLoggingBinEntry 520093696}

pr1645v2PRoutQmLoggingBinMinMin OBJECT-TYPE
   SYNTAX      Counter32
   MAX-ACCESS  read-only
   STATUS      current
   DESCRIPTION
      "Path: router.performance.qualityMonitor.logging.bin.minMin

       32 bit unsigned wrappable counter."
   ::= {pr1645v2PRoutQmLoggingBinEntry 16777216}

pr1645v2PRoutQmLoggingBinMin OBJECT-TYPE
   SYNTAX      Integer32
   MAX-ACCESS  read-only
   STATUS      current
   DESCRIPTION
      "Path: router.performance.qualityMonitor.logging.bin.min

       unit name = sec
       formula = 1000 / ; 1000 *"
   ::= {pr1645v2PRoutQmLoggingBinEntry 352321536}

pr1645v2PRoutQmLoggingBinMinBin1 OBJECT-TYPE
   SYNTAX      Counter32
   MAX-ACCESS  read-only
   STATUS      current
   DESCRIPTION
      "Path: router.performance.qualityMonitor.logging.bin.minBin1

       32 bit unsigned wrappable counter."
   ::= {pr1645v2PRoutQmLoggingBinEntry 33554432}

pr1645v2PRoutQmLoggingBinBin2 OBJECT-TYPE
   SYNTAX      Counter32
   MAX-ACCESS  read-only
   STATUS      current
   DESCRIPTION
      "Path: router.performance.qualityMonitor.logging.bin.bin2

       32 bit unsigned wrappable counter."
   ::= {pr1645v2PRoutQmLoggingBinEntry 50331648}

pr1645v2PRoutQmLoggingBinBin3 OBJECT-TYPE
   SYNTAX      Counter32
   MAX-ACCESS  read-only
   STATUS      current
   DESCRIPTION
      "Path: router.performance.qualityMonitor.logging.bin.bin3

       32 bit unsigned wrappable counter."
   ::= {pr1645v2PRoutQmLoggingBinEntry 67108864}

pr1645v2PRoutQmLoggingBinBin4 OBJECT-TYPE
   SYNTAX      Counter32
   MAX-ACCESS  read-only
   STATUS      current
   DESCRIPTION
      "Path: router.performance.qualityMonitor.logging.bin.bin4

       32 bit unsigned wrappable counter."
   ::= {pr1645v2PRoutQmLoggingBinEntry 83886080}

pr1645v2PRoutQmLoggingBinBin5 OBJECT-TYPE
   SYNTAX      Counter32
   MAX-ACCESS  read-only
   STATUS      current
   DESCRIPTION
      "Path: router.performance.qualityMonitor.logging.bin.bin5

       32 bit unsigned wrappable counter."
   ::= {pr1645v2PRoutQmLoggingBinEntry 100663296}

pr1645v2PRoutQmLoggingBinBin6 OBJECT-TYPE
   SYNTAX      Counter32
   MAX-ACCESS  read-only
   STATUS      current
   DESCRIPTION
      "Path: router.performance.qualityMonitor.logging.bin.bin6

       32 bit unsigned wrappable counter."
   ::= {pr1645v2PRoutQmLoggingBinEntry 117440512}

pr1645v2PRoutQmLoggingBinBin7 OBJECT-TYPE
   SYNTAX      Counter32
   MAX-ACCESS  read-only
   STATUS      current
   DESCRIPTION
      "Path: router.performance.qualityMonitor.logging.bin.bin7

       32 bit unsigned wrappable counter."
   ::= {pr1645v2PRoutQmLoggingBinEntry 134217728}

pr1645v2PRoutQmLoggingBinMaxBin8 OBJECT-TYPE
   SYNTAX      Counter32
   MAX-ACCESS  read-only
   STATUS      current
   DESCRIPTION
      "Path: router.performance.qualityMonitor.logging.bin.maxBin8

       32 bit unsigned wrappable counter."
   ::= {pr1645v2PRoutQmLoggingBinEntry 150994944}

pr1645v2PRoutQmLoggingBinMax OBJECT-TYPE
   SYNTAX      Integer32
   MAX-ACCESS  read-only
   STATUS      current
   DESCRIPTION
      "Path: router.performance.qualityMonitor.logging.bin.max

       unit name = sec
       formula = 1000 / ; 1000 *"
   ::= {pr1645v2PRoutQmLoggingBinEntry 369098752}

pr1645v2PRoutQmLoggingBinPlusMax OBJECT-TYPE
   SYNTAX      Counter32
   MAX-ACCESS  read-only
   STATUS      current
   DESCRIPTION
      "Path: router.performance.qualityMonitor.logging.bin.plusMax

       32 bit unsigned wrappable counter."
   ::= {pr1645v2PRoutQmLoggingBinEntry 167772160}

pr1645v2PRoutQmLastLogBin OBJECT-TYPE
   SYNTAX      SEQUENCE OF Pr1645v2PRoutQmLastLogBinEntry
   MAX-ACCESS  not-accessible
   STATUS      current
   DESCRIPTION
      ""
   ::= {pr1645v2PRoutQm 673185792}

pr1645v2PRoutQmLastLogBinEntry OBJECT-TYPE
   SYNTAX      Pr1645v2PRoutQmLastLogBinEntry
   MAX-ACCESS  not-accessible
   STATUS      current
   DESCRIPTION
      ""
   INDEX      { pr1645v2PRoutQmTableIx,
                pr1645v2PRoutQmLastLogBinTableIx }
   ::= {pr1645v2PRoutQmLastLogBin 1}

Pr1645v2PRoutQmLastLogBinEntry ::=
   SEQUENCE
      {
      pr1645v2PRoutQmLastLogBinTableIx
         TableIndex,
      pr1645v2PRoutQmLastLogBinName
         INTEGER,
      pr1645v2PRoutQmLastLogBinType
         INTEGER,
      pr1645v2PRoutQmLastLogBinMinMin
         Counter32,
      pr1645v2PRoutQmLastLogBinMin
         Integer32,
      pr1645v2PRoutQmLastLogBinMinBin1
         Counter32,
      pr1645v2PRoutQmLastLogBinBin2
         Counter32,
      pr1645v2PRoutQmLastLogBinBin3
         Counter32,
      pr1645v2PRoutQmLastLogBinBin4
         Counter32,
      pr1645v2PRoutQmLastLogBinBin5
         Counter32,
      pr1645v2PRoutQmLastLogBinBin6
         Counter32,
      pr1645v2PRoutQmLastLogBinBin7
         Counter32,
      pr1645v2PRoutQmLastLogBinMaxBin8
         Counter32,
      pr1645v2PRoutQmLastLogBinMax
         Integer32,
      pr1645v2PRoutQmLastLogBinPlusMax
         Counter32
      }

pr1645v2PRoutQmLastLogBinTableIx OBJECT-TYPE
   SYNTAX      TableIndex
   MAX-ACCESS  not-accessible
   STATUS      current
   DESCRIPTION
      ""
   ::= {pr1645v2PRoutQmLastLogBinEntry 11}

pr1645v2PRoutQmLastLogBinName OBJECT-TYPE
   SYNTAX      INTEGER
               {
               delay (1),
               delayUp (2),
               delayDown (3),
               jitter (4),
               jitterUp (5),
               jitterDown (6)
               }
   MAX-ACCESS  read-only
   STATUS      current
   DESCRIPTION
      "Path: router.performance.qualityMonitor.lastLog.bin.name

       Possibilities:
               delay   (1)
               delayUp   (2)
               delayDown   (3)
               jitter   (4)
               jitterUp   (5)
               jitterDown   (6)"
   ::= {pr1645v2PRoutQmLastLogBinEntry 503316480}

pr1645v2PRoutQmLastLogBinType OBJECT-TYPE
   SYNTAX      INTEGER
               {
               fd (1),
               fdr (2),
               notInUse (3),
               ifdv (4)
               }
   MAX-ACCESS  read-only
   STATUS      current
   DESCRIPTION
      "Path: router.performance.qualityMonitor.lastLog.bin.type

       Possibilities:
               fd   (1)
               fdr   (2)
               notInUse   (3)
               ifdv   (4)"
   ::= {pr1645v2PRoutQmLastLogBinEntry 520093696}

pr1645v2PRoutQmLastLogBinMinMin OBJECT-TYPE
   SYNTAX      Counter32
   MAX-ACCESS  read-only
   STATUS      current
   DESCRIPTION
      "Path: router.performance.qualityMonitor.lastLog.bin.minMin

       32 bit unsigned wrappable counter."
   ::= {pr1645v2PRoutQmLastLogBinEntry 16777216}

pr1645v2PRoutQmLastLogBinMin OBJECT-TYPE
   SYNTAX      Integer32
   MAX-ACCESS  read-only
   STATUS      current
   DESCRIPTION
      "Path: router.performance.qualityMonitor.lastLog.bin.min

       unit name = sec
       formula = 1000 / ; 1000 *"
   ::= {pr1645v2PRoutQmLastLogBinEntry 352321536}

pr1645v2PRoutQmLastLogBinMinBin1 OBJECT-TYPE
   SYNTAX      Counter32
   MAX-ACCESS  read-only
   STATUS      current
   DESCRIPTION
      "Path: router.performance.qualityMonitor.lastLog.bin.minBin1

       32 bit unsigned wrappable counter."
   ::= {pr1645v2PRoutQmLastLogBinEntry 33554432}

pr1645v2PRoutQmLastLogBinBin2 OBJECT-TYPE
   SYNTAX      Counter32
   MAX-ACCESS  read-only
   STATUS      current
   DESCRIPTION
      "Path: router.performance.qualityMonitor.lastLog.bin.bin2

       32 bit unsigned wrappable counter."
   ::= {pr1645v2PRoutQmLastLogBinEntry 50331648}

pr1645v2PRoutQmLastLogBinBin3 OBJECT-TYPE
   SYNTAX      Counter32
   MAX-ACCESS  read-only
   STATUS      current
   DESCRIPTION
      "Path: router.performance.qualityMonitor.lastLog.bin.bin3

       32 bit unsigned wrappable counter."
   ::= {pr1645v2PRoutQmLastLogBinEntry 67108864}

pr1645v2PRoutQmLastLogBinBin4 OBJECT-TYPE
   SYNTAX      Counter32
   MAX-ACCESS  read-only
   STATUS      current
   DESCRIPTION
      "Path: router.performance.qualityMonitor.lastLog.bin.bin4

       32 bit unsigned wrappable counter."
   ::= {pr1645v2PRoutQmLastLogBinEntry 83886080}

pr1645v2PRoutQmLastLogBinBin5 OBJECT-TYPE
   SYNTAX      Counter32
   MAX-ACCESS  read-only
   STATUS      current
   DESCRIPTION
      "Path: router.performance.qualityMonitor.lastLog.bin.bin5

       32 bit unsigned wrappable counter."
   ::= {pr1645v2PRoutQmLastLogBinEntry 100663296}

pr1645v2PRoutQmLastLogBinBin6 OBJECT-TYPE
   SYNTAX      Counter32
   MAX-ACCESS  read-only
   STATUS      current
   DESCRIPTION
      "Path: router.performance.qualityMonitor.lastLog.bin.bin6

       32 bit unsigned wrappable counter."
   ::= {pr1645v2PRoutQmLastLogBinEntry 117440512}

pr1645v2PRoutQmLastLogBinBin7 OBJECT-TYPE
   SYNTAX      Counter32
   MAX-ACCESS  read-only
   STATUS      current
   DESCRIPTION
      "Path: router.performance.qualityMonitor.lastLog.bin.bin7

       32 bit unsigned wrappable counter."
   ::= {pr1645v2PRoutQmLastLogBinEntry 134217728}

pr1645v2PRoutQmLastLogBinMaxBin8 OBJECT-TYPE
   SYNTAX      Counter32
   MAX-ACCESS  read-only
   STATUS      current
   DESCRIPTION
      "Path: router.performance.qualityMonitor.lastLog.bin.maxBin8

       32 bit unsigned wrappable counter."
   ::= {pr1645v2PRoutQmLastLogBinEntry 150994944}

pr1645v2PRoutQmLastLogBinMax OBJECT-TYPE
   SYNTAX      Integer32
   MAX-ACCESS  read-only
   STATUS      current
   DESCRIPTION
      "Path: router.performance.qualityMonitor.lastLog.bin.max

       unit name = sec
       formula = 1000 / ; 1000 *"
   ::= {pr1645v2PRoutQmLastLogBinEntry 369098752}

pr1645v2PRoutQmLastLogBinPlusMax OBJECT-TYPE
   SYNTAX      Counter32
   MAX-ACCESS  read-only
   STATUS      current
   DESCRIPTION
      "Path: router.performance.qualityMonitor.lastLog.bin.plusMax

       32 bit unsigned wrappable counter."
   ::= {pr1645v2PRoutQmLastLogBinEntry 167772160}


pr1645v2PRoutUdpServer OBJECT IDENTIFIER ::= {pr1645v2PRout 16}

pr1645v2PRoutUdpServerSSCTable OBJECT-TYPE
   SYNTAX      SEQUENCE OF Pr1645v2PRoutUdpServerEntry
   MAX-ACCESS  not-accessible
   STATUS      current
   DESCRIPTION
      "udpServer"
   ::= {pr1645v2PRoutUdpServer 1}

pr1645v2PRoutUdpServerEntry OBJECT-TYPE
   SYNTAX      Pr1645v2PRoutUdpServerEntry
   MAX-ACCESS  not-accessible
   STATUS      current
   DESCRIPTION
      ""
   INDEX      { pr1645v2PRoutUdpServerTableIx }
   ::= {pr1645v2PRoutUdpServerSSCTable 1}

Pr1645v2PRoutUdpServerEntry ::=
   SEQUENCE
      {
      pr1645v2PRoutUdpServerTableIx
         TableIndex,
      pr1645v2PRoutUdpServerDestinationPort
         Integer32,
      pr1645v2PRoutUdpServerActiveSessions
         Gauge32,
      pr1645v2PRoutUdpServerNbrPckt
         Counter64
      }

pr1645v2PRoutUdpServerTableIx OBJECT-TYPE
   SYNTAX      TableIndex
   MAX-ACCESS  not-accessible
   STATUS      current
   DESCRIPTION
      ""
   ::= {pr1645v2PRoutUdpServerEntry 11}

pr1645v2PRoutUdpServerDestinationPort OBJECT-TYPE
   SYNTAX      Integer32
   MAX-ACCESS  read-only
   STATUS      current
   DESCRIPTION
      "Path: router.performance.udpServer.destinationPort"
   ::= {pr1645v2PRoutUdpServerEntry 16777216}

pr1645v2PRoutUdpServerActiveSessions OBJECT-TYPE
   SYNTAX      Gauge32
   MAX-ACCESS  read-only
   STATUS      current
   DESCRIPTION
      "Path: router.performance.udpServer.activeSessions

       32 bit unsigned gauge value."
   ::= {pr1645v2PRoutUdpServerEntry 33554432}

pr1645v2PRoutUdpServerNbrPckt OBJECT-TYPE
   SYNTAX      Counter64
   MAX-ACCESS  read-only
   STATUS      current
   DESCRIPTION
      "Path: router.performance.udpServer.nbrOfPackets

       64 bit unsigned wrappable counter."
   ::= {pr1645v2PRoutUdpServerEntry 50331648}

pr1645v2PRoutUdpServerSessions OBJECT-TYPE
   SYNTAX      SEQUENCE OF Pr1645v2PRoutUdpServerSessionsEntry
   MAX-ACCESS  not-accessible
   STATUS      current
   DESCRIPTION
      ""
   ::= {pr1645v2PRoutUdpServer 67108864}

pr1645v2PRoutUdpServerSessionsEntry OBJECT-TYPE
   SYNTAX      Pr1645v2PRoutUdpServerSessionsEntry
   MAX-ACCESS  not-accessible
   STATUS      current
   DESCRIPTION
      ""
   INDEX      { pr1645v2PRoutUdpServerTableIx,
                pr1645v2PRoutUdpServerSessionsTableIx }
   ::= {pr1645v2PRoutUdpServerSessions 1}

Pr1645v2PRoutUdpServerSessionsEntry ::=
   SEQUENCE
      {
      pr1645v2PRoutUdpServerSessionsTableIx
         TableIndex,
      pr1645v2PRoutUdpServerSessionsSourceIpAddress
         IpAddress,
      pr1645v2PRoutUdpServerSessionsSourcePort
         Integer32,
      pr1645v2PRoutUdpServerSessionsNbrPckt
         Counter64,
      pr1645v2PRoutUdpServerSessionsFirstActivityTime
         TimeTicks,
      pr1645v2PRoutUdpServerSessionsLastActivityTime
         TimeTicks,
      pr1645v2PRoutUdpServerSessionsHalfWayStatus
         INTEGER,
      pr1645v2PRoutUdpServerSessionsHalfWayReceived
         Counter64,
      pr1645v2PRoutUdpServerSessionsHalfWayPacketLoss
         Counter64,
      pr1645v2PRoutUdpServerSessionsHalfWayOutOfSequence
         Counter64,
      pr1645v2PRoutUdpServerSessionsHalfWayCrcErrors
         Counter64,
      pr1645v2PRoutUdpServerSessionsHalfWayLengthErrors
         Counter64,
      pr1645v2PRoutUdpServerSessionsHalfWayJitter
         INTEGER,
      pr1645v2PRoutUdpServerSessionsHalfWayJitterAvrg
         INTEGER,
      pr1645v2PRoutUdpServerSessionsHalfWayJitterMax
         INTEGER,
      pr1645v2PRoutUdpServerSessionsHalfWayReceivedLength
         Counter64,
      pr1645v2PRoutUdpServerSessionsHalfWayLastFault
         Counter64,
      pr1645v2PRoutUdpServerSessionsHalfWayLastSeqnr
         Counter64
      }

pr1645v2PRoutUdpServerSessionsTableIx OBJECT-TYPE
   SYNTAX      TableIndex
   MAX-ACCESS  not-accessible
   STATUS      current
   DESCRIPTION
      ""
   ::= {pr1645v2PRoutUdpServerSessionsEntry 11}

pr1645v2PRoutUdpServerSessionsSourceIpAddress OBJECT-TYPE
   SYNTAX      IpAddress
   MAX-ACCESS  read-only
   STATUS      current
   DESCRIPTION
      "Path: router.performance.udpServer.sessions.sourceIpAddress"
   ::= {pr1645v2PRoutUdpServerSessionsEntry 16777216}

pr1645v2PRoutUdpServerSessionsSourcePort OBJECT-TYPE
   SYNTAX      Integer32
   MAX-ACCESS  read-only
   STATUS      current
   DESCRIPTION
      "Path: router.performance.udpServer.sessions.sourcePort"
   ::= {pr1645v2PRoutUdpServerSessionsEntry 33554432}

pr1645v2PRoutUdpServerSessionsNbrPckt OBJECT-TYPE
   SYNTAX      Counter64
   MAX-ACCESS  read-only
   STATUS      current
   DESCRIPTION
      "Path: router.performance.udpServer.sessions.nbrOfPackets

       64 bit unsigned wrappable counter."
   ::= {pr1645v2PRoutUdpServerSessionsEntry 50331648}

pr1645v2PRoutUdpServerSessionsFirstActivityTime OBJECT-TYPE
   SYNTAX      TimeTicks
   MAX-ACCESS  read-only
   STATUS      current
   DESCRIPTION
      "Path: router.performance.udpServer.sessions.firstActivityTime

       Time in centi-second."
   ::= {pr1645v2PRoutUdpServerSessionsEntry 67108864}

pr1645v2PRoutUdpServerSessionsLastActivityTime OBJECT-TYPE
   SYNTAX      TimeTicks
   MAX-ACCESS  read-only
   STATUS      current
   DESCRIPTION
      "Path: router.performance.udpServer.sessions.lastActivityTime

       Time in centi-second."
   ::= {pr1645v2PRoutUdpServerSessionsEntry 83886080}

pr1645v2PRoutUdpServerSessionsHalfWayStatus OBJECT-TYPE
   SYNTAX      INTEGER
               {
               notInUse (1),
               inUse (2)
               }
   MAX-ACCESS  read-only
   STATUS      current
   DESCRIPTION
      "Path: router.performance.udpServer.sessions.halfWay.status

       Possibilities:
               notInUse   (1)
               inUse   (2)"
   ::= {pr1645v2PRoutUdpServerSessionsEntry 100728832}

pr1645v2PRoutUdpServerSessionsHalfWayReceived OBJECT-TYPE
   SYNTAX      Counter64
   MAX-ACCESS  read-only
   STATUS      current
   DESCRIPTION
      "Path: router.performance.udpServer.sessions.halfWay.received

       64 bit unsigned wrappable counter."
   ::= {pr1645v2PRoutUdpServerSessionsEntry 110166016}

pr1645v2PRoutUdpServerSessionsHalfWayPacketLoss OBJECT-TYPE
   SYNTAX      Counter64
   MAX-ACCESS  read-only
   STATUS      current
   DESCRIPTION
      "Path: router.performance.udpServer.sessions.halfWay.packetLoss

       64 bit unsigned wrappable counter."
   ::= {pr1645v2PRoutUdpServerSessionsEntry 110231552}

pr1645v2PRoutUdpServerSessionsHalfWayOutOfSequence OBJECT-TYPE
   SYNTAX      Counter64
   MAX-ACCESS  read-only
   STATUS      current
   DESCRIPTION
      "Path: router.performance.udpServer.sessions.halfWay.outOfSequence

       64 bit unsigned wrappable counter."
   ::= {pr1645v2PRoutUdpServerSessionsEntry 110362624}

pr1645v2PRoutUdpServerSessionsHalfWayCrcErrors OBJECT-TYPE
   SYNTAX      Counter64
   MAX-ACCESS  read-only
   STATUS      current
   DESCRIPTION
      "Path: router.performance.udpServer.sessions.halfWay.crcErrors

       64 bit unsigned wrappable counter."
   ::= {pr1645v2PRoutUdpServerSessionsEntry 110493696}

pr1645v2PRoutUdpServerSessionsHalfWayLengthErrors OBJECT-TYPE
   SYNTAX      Counter64
   MAX-ACCESS  read-only
   STATUS      current
   DESCRIPTION
      "Path: router.performance.udpServer.sessions.halfWay.lengthErrors

       64 bit unsigned wrappable counter."
   ::= {pr1645v2PRoutUdpServerSessionsEntry 110559232}

pr1645v2PRoutUdpServerSessionsHalfWayJitter OBJECT-TYPE
   SYNTAX      INTEGER
               {
               slnotsinsuseg (2147483647)
               }
   MAX-ACCESS  read-only
   STATUS      current
   DESCRIPTION
      "Path: router.performance.udpServer.sessions.halfWay.jitter

       unit name = ms
       formula = 10 / ; 10 *

       Possibilities:
               <not in use>   (2147483647)"
   ::= {pr1645v2PRoutUdpServerSessionsEntry 111280128}

pr1645v2PRoutUdpServerSessionsHalfWayJitterAvrg OBJECT-TYPE
   SYNTAX      INTEGER
               {
               slnotsinsuseg (2147483647)
               }
   MAX-ACCESS  read-only
   STATUS      current
   DESCRIPTION
      "Path: router.performance.udpServer.sessions.halfWay.jitterAvrg

       unit name = ms
       formula = 10 / ; 10 *

       Possibilities:
               <not in use>   (2147483647)"
   ::= {pr1645v2PRoutUdpServerSessionsEntry 111345664}

pr1645v2PRoutUdpServerSessionsHalfWayJitterMax OBJECT-TYPE
   SYNTAX      INTEGER
               {
               slnotsinsuseg (2147483647)
               }
   MAX-ACCESS  read-only
   STATUS      current
   DESCRIPTION
      "Path: router.performance.udpServer.sessions.halfWay.jitterMax

       unit name = ms
       formula = 10 / ; 10 *

       Possibilities:
               <not in use>   (2147483647)"
   ::= {pr1645v2PRoutUdpServerSessionsEntry 111411200}

pr1645v2PRoutUdpServerSessionsHalfWayReceivedLength OBJECT-TYPE
   SYNTAX      Counter64
   MAX-ACCESS  read-only
   STATUS      current
   DESCRIPTION
      "Path: router.performance.udpServer.sessions.halfWay.receivedLength

       64 bit unsigned wrappable counter."
   ::= {pr1645v2PRoutUdpServerSessionsEntry 111083520}

pr1645v2PRoutUdpServerSessionsHalfWayLastFault OBJECT-TYPE
   SYNTAX      Counter64
   MAX-ACCESS  read-only
   STATUS      current
   DESCRIPTION
      "Path: router.performance.udpServer.sessions.halfWay.lastFault

       64 bit unsigned wrappable counter."
   ::= {pr1645v2PRoutUdpServerSessionsEntry 111804416}

pr1645v2PRoutUdpServerSessionsHalfWayLastSeqnr OBJECT-TYPE
   SYNTAX      Counter64
   MAX-ACCESS  read-only
   STATUS      current
   DESCRIPTION
      "Path: router.performance.udpServer.sessions.halfWay.lastSeqnr

       64 bit unsigned wrappable counter."
   ::= {pr1645v2PRoutUdpServerSessionsEntry 111869952}


pr1645v2PRoutIgmpProxy OBJECT IDENTIFIER ::= {pr1645v2PRout 69}

pr1645v2PRoutIgmpProxySSC OBJECT IDENTIFIER ::= {pr1645v2PRoutIgmpProxy 1}

pr1645v2PRoutIgmpProxyEntry OBJECT IDENTIFIER ::= {pr1645v2PRoutIgmpProxySSC 1}

pr1645v2PRoutIgmpProxyInIgmp OBJECT-TYPE
   SYNTAX      Integer32
   MAX-ACCESS  read-only
   STATUS      current
   DESCRIPTION
      "Path: router.performance.igmpProxy.inIgmp"
   ::= {pr1645v2PRoutIgmpProxyEntry 16777216}

pr1645v2PRoutIgmpProxyOutIgmp OBJECT-TYPE
   SYNTAX      Integer32
   MAX-ACCESS  read-only
   STATUS      current
   DESCRIPTION
      "Path: router.performance.igmpProxy.outIgmp"
   ::= {pr1645v2PRoutIgmpProxyEntry 33554432}

pr1645v2PRoutIgmpProxyInData OBJECT-TYPE
   SYNTAX      Integer32
   MAX-ACCESS  read-only
   STATUS      current
   DESCRIPTION
      "Path: router.performance.igmpProxy.inData"
   ::= {pr1645v2PRoutIgmpProxyEntry 50331648}

pr1645v2PRoutIgmpProxyInDiscards OBJECT-TYPE
   SYNTAX      Integer32
   MAX-ACCESS  read-only
   STATUS      current
   DESCRIPTION
      "Path: router.performance.igmpProxy.inDiscards"
   ::= {pr1645v2PRoutIgmpProxyEntry 67108864}


pr1645v2PRoutIpFragments OBJECT IDENTIFIER ::= {pr1645v2PRout 87}

pr1645v2PRoutIpFragmentsSSC OBJECT IDENTIFIER ::= {pr1645v2PRoutIpFragments 1}

pr1645v2PRoutIpFragmentsEntry OBJECT IDENTIFIER ::= {pr1645v2PRoutIpFragmentsSSC 1}

pr1645v2PRoutIpFragmentsReceivedFrames OBJECT-TYPE
   SYNTAX      Counter64
   MAX-ACCESS  read-only
   STATUS      current
   DESCRIPTION
      "Path: router.performance.ipFragments.receivedFrames

       64 bit unsigned wrappable counter."
   ::= {pr1645v2PRoutIpFragmentsEntry 16777216}

pr1645v2PRoutIpFragmentsReassembledFrames OBJECT-TYPE
   SYNTAX      Counter64
   MAX-ACCESS  read-only
   STATUS      current
   DESCRIPTION
      "Path: router.performance.ipFragments.reassembledFrames

       64 bit unsigned wrappable counter."
   ::= {pr1645v2PRoutIpFragmentsEntry 33554432}

pr1645v2PRoutIpFragmentsExpiredFrames OBJECT-TYPE
   SYNTAX      Counter64
   MAX-ACCESS  read-only
   STATUS      current
   DESCRIPTION
      "Path: router.performance.ipFragments.expiredFrames

       64 bit unsigned wrappable counter."
   ::= {pr1645v2PRoutIpFragmentsEntry 50331648}

pr1645v2PRoutIpFragmentsPendingFrames OBJECT-TYPE
   SYNTAX      Gauge32
   MAX-ACCESS  read-only
   STATUS      current
   DESCRIPTION
      "Path: router.performance.ipFragments.pendingFrames

       32 bit unsigned gauge value."
   ::= {pr1645v2PRoutIpFragmentsEntry 67108864}

pr1645v2PRoutIpFragmentsReceivedPackets OBJECT-TYPE
   SYNTAX      Counter64
   MAX-ACCESS  read-only
   STATUS      current
   DESCRIPTION
      "Path: router.performance.ipFragments.receivedPackets

       64 bit unsigned wrappable counter."
   ::= {pr1645v2PRoutIpFragmentsEntry 83886080}

pr1645v2PRoutIpFragmentsExcessivelyFragPackets OBJECT-TYPE
   SYNTAX      Counter64
   MAX-ACCESS  read-only
   STATUS      current
   DESCRIPTION
      "Path: router.performance.ipFragments.excessivelyFragPackets

       64 bit unsigned wrappable counter."
   ::= {pr1645v2PRoutIpFragmentsEntry 100663296}


pr1645v2PRoutTracertResults OBJECT IDENTIFIER ::= {pr1645v2PRout 153}

pr1645v2PRoutTracertResultsSSCTable OBJECT-TYPE
   SYNTAX      SEQUENCE OF Pr1645v2PRoutTracertResultsEntry
   MAX-ACCESS  not-accessible
   STATUS      current
   DESCRIPTION
      "Traceroute statistics"
   ::= {pr1645v2PRoutTracertResults 1}

pr1645v2PRoutTracertResultsEntry OBJECT-TYPE
   SYNTAX      Pr1645v2PRoutTracertResultsEntry
   MAX-ACCESS  not-accessible
   STATUS      current
   DESCRIPTION
      ""
   INDEX      { pr1645v2PRoutTracertResultsTableIx }
   ::= {pr1645v2PRoutTracertResultsSSCTable 1}

Pr1645v2PRoutTracertResultsEntry ::=
   SEQUENCE
      {
      pr1645v2PRoutTracertResultsTableIx
         TableIndex,
      pr1645v2PRoutTracertResultsTtl
         Integer32,
      pr1645v2PRoutTracertResultsIpAddress
         IpAddress,
      pr1645v2PRoutTracertResultsHostName
         DisplayString,
      pr1645v2PRoutTracertResultsNrTx
         Counter32,
      pr1645v2PRoutTracertResultsNrRx
         Counter32,
      pr1645v2PRoutTracertResultsRepTimMin
         TimeTicks,
      pr1645v2PRoutTracertResultsRepTimMax
         TimeTicks,
      pr1645v2PRoutTracertResultsRepTimAvrg
         TimeTicks,
      pr1645v2PRoutTracertResultsSr
         Integer32,
      pr1645v2PRoutTracertResultsComment
         DisplayString
      }

pr1645v2PRoutTracertResultsTableIx OBJECT-TYPE
   SYNTAX      TableIndex
   MAX-ACCESS  not-accessible
   STATUS      current
   DESCRIPTION
      ""
   ::= {pr1645v2PRoutTracertResultsEntry 11}

pr1645v2PRoutTracertResultsTtl OBJECT-TYPE
   SYNTAX      Integer32
   MAX-ACCESS  read-only
   STATUS      current
   DESCRIPTION
      "Path: router.performance.tracertResults.ttl"
   ::= {pr1645v2PRoutTracertResultsEntry 16777216}

pr1645v2PRoutTracertResultsIpAddress OBJECT-TYPE
   SYNTAX      IpAddress
   MAX-ACCESS  read-only
   STATUS      current
   DESCRIPTION
      "Path: router.performance.tracertResults.ipAddress"
   ::= {pr1645v2PRoutTracertResultsEntry 33554432}

pr1645v2PRoutTracertResultsHostName OBJECT-TYPE
   SYNTAX      DisplayString
   MAX-ACCESS  read-only
   STATUS      current
   DESCRIPTION
      "Path: router.performance.tracertResults.hostName"
   ::= {pr1645v2PRoutTracertResultsEntry 50331648}

pr1645v2PRoutTracertResultsNrTx OBJECT-TYPE
   SYNTAX      Counter32
   MAX-ACCESS  read-only
   STATUS      current
   DESCRIPTION
      "Path: router.performance.tracertResults.numOfTxPackets

       32 bit unsigned wrappable counter."
   ::= {pr1645v2PRoutTracertResultsEntry 67108864}

pr1645v2PRoutTracertResultsNrRx OBJECT-TYPE
   SYNTAX      Counter32
   MAX-ACCESS  read-only
   STATUS      current
   DESCRIPTION
      "Path: router.performance.tracertResults.numOfRxPackets

       32 bit unsigned wrappable counter."
   ::= {pr1645v2PRoutTracertResultsEntry 83886080}

pr1645v2PRoutTracertResultsRepTimMin OBJECT-TYPE
   SYNTAX      TimeTicks
   MAX-ACCESS  read-only
   STATUS      current
   DESCRIPTION
      "Path: router.performance.tracertResults.replyTimeMin

       Time in centi-second."
   ::= {pr1645v2PRoutTracertResultsEntry 100663296}

pr1645v2PRoutTracertResultsRepTimMax OBJECT-TYPE
   SYNTAX      TimeTicks
   MAX-ACCESS  read-only
   STATUS      current
   DESCRIPTION
      "Path: router.performance.tracertResults.replyTimeMax

       Time in centi-second."
   ::= {pr1645v2PRoutTracertResultsEntry 117440512}

pr1645v2PRoutTracertResultsRepTimAvrg OBJECT-TYPE
   SYNTAX      TimeTicks
   MAX-ACCESS  read-only
   STATUS      current
   DESCRIPTION
      "Path: router.performance.tracertResults.replyTimeAvrg

       Time in centi-second."
   ::= {pr1645v2PRoutTracertResultsEntry 134217728}

pr1645v2PRoutTracertResultsSr OBJECT-TYPE
   SYNTAX      Integer32
   UNITS       "%"
   MAX-ACCESS  read-only
   STATUS      current
   DESCRIPTION
      "Path: router.performance.tracertResults.successRate

       unit name = %"
   ::= {pr1645v2PRoutTracertResultsEntry 150994944}

pr1645v2PRoutTracertResultsComment OBJECT-TYPE
   SYNTAX      DisplayString
   MAX-ACCESS  read-only
   STATUS      current
   DESCRIPTION
      "Path: router.performance.tracertResults.comment"
   ::= {pr1645v2PRoutTracertResultsEntry 167772160}


pr1645v2PRoutRoutingTable OBJECT IDENTIFIER ::= {pr1645v2PRout 33}

pr1645v2PRoutRoutingTableSSCTable OBJECT-TYPE
   SYNTAX      SEQUENCE OF Pr1645v2PRoutRoutingTableEntry
   MAX-ACCESS  not-accessible
   STATUS      current
   DESCRIPTION
      "routingTable"
   ::= {pr1645v2PRoutRoutingTable 1}

pr1645v2PRoutRoutingTableEntry OBJECT-TYPE
   SYNTAX      Pr1645v2PRoutRoutingTableEntry
   MAX-ACCESS  not-accessible
   STATUS      current
   DESCRIPTION
      ""
   INDEX      { pr1645v2PRoutRoutingTableTableIx }
   ::= {pr1645v2PRoutRoutingTableSSCTable 1}

Pr1645v2PRoutRoutingTableEntry ::=
   SEQUENCE
      {
      pr1645v2PRoutRoutingTableTableIx
         TableIndex,
      pr1645v2PRoutRoutingTableNetwork
         IpAddress,
      pr1645v2PRoutRoutingTableMask
         IpAddress,
      pr1645v2PRoutRoutingTableGateway
         IpAddress,
      pr1645v2PRoutRoutingTableIf
         DisplayString,
      pr1645v2PRoutRoutingTableUses
         Gauge32,
      pr1645v2PRoutRoutingTableOctets
         Gauge32
      }

pr1645v2PRoutRoutingTableTableIx OBJECT-TYPE
   SYNTAX      TableIndex
   MAX-ACCESS  not-accessible
   STATUS      current
   DESCRIPTION
      ""
   ::= {pr1645v2PRoutRoutingTableEntry 11}

pr1645v2PRoutRoutingTableNetwork OBJECT-TYPE
   SYNTAX      IpAddress
   MAX-ACCESS  read-only
   STATUS      current
   DESCRIPTION
      "Path: router.performance.routingTable.network"
   ::= {pr1645v2PRoutRoutingTableEntry 16777216}

pr1645v2PRoutRoutingTableMask OBJECT-TYPE
   SYNTAX      IpAddress
   MAX-ACCESS  read-only
   STATUS      current
   DESCRIPTION
      "Path: router.performance.routingTable.mask"
   ::= {pr1645v2PRoutRoutingTableEntry 33554432}

pr1645v2PRoutRoutingTableGateway OBJECT-TYPE
   SYNTAX      IpAddress
   MAX-ACCESS  read-only
   STATUS      current
   DESCRIPTION
      "Path: router.performance.routingTable.gateway"
   ::= {pr1645v2PRoutRoutingTableEntry 50331648}

pr1645v2PRoutRoutingTableIf OBJECT-TYPE
   SYNTAX      DisplayString
   MAX-ACCESS  read-only
   STATUS      current
   DESCRIPTION
      "Path: router.performance.routingTable.interface"
   ::= {pr1645v2PRoutRoutingTableEntry 67108864}

pr1645v2PRoutRoutingTableUses OBJECT-TYPE
   SYNTAX      Gauge32
   MAX-ACCESS  read-only
   STATUS      current
   DESCRIPTION
      "Path: router.performance.routingTable.uses

       32 bit unsigned gauge value."
   ::= {pr1645v2PRoutRoutingTableEntry 83886080}

pr1645v2PRoutRoutingTableOctets OBJECT-TYPE
   SYNTAX      Gauge32
   MAX-ACCESS  read-only
   STATUS      current
   DESCRIPTION
      "Path: router.performance.routingTable.octets

       32 bit unsigned gauge value."
   ::= {pr1645v2PRoutRoutingTableEntry 100663296}


pr1645v2PRoutPingResults OBJECT IDENTIFIER ::= {pr1645v2PRout 46}

pr1645v2PRoutPingResultsSSC OBJECT IDENTIFIER ::= {pr1645v2PRoutPingResults 1}

pr1645v2PRoutPingResultsEntry OBJECT IDENTIFIER ::= {pr1645v2PRoutPingResultsSSC 1}

pr1645v2PRoutPingResultsIpAddr OBJECT-TYPE
   SYNTAX      IpAddress
   MAX-ACCESS  read-only
   STATUS      current
   DESCRIPTION
      "Path: router.performance.pingResults.ipAddress"
   ::= {pr1645v2PRoutPingResultsEntry 16777216}

pr1645v2PRoutPingResultsNbrTxPckt OBJECT-TYPE
   SYNTAX      Counter32
   MAX-ACCESS  read-only
   STATUS      current
   DESCRIPTION
      "Path: router.performance.pingResults.numOfTxPackets

       32 bit unsigned wrappable counter."
   ::= {pr1645v2PRoutPingResultsEntry 33554432}

pr1645v2PRoutPingResultsNbrRxPckt OBJECT-TYPE
   SYNTAX      Counter32
   MAX-ACCESS  read-only
   STATUS      current
   DESCRIPTION
      "Path: router.performance.pingResults.numOfRxPackets

       32 bit unsigned wrappable counter."
   ::= {pr1645v2PRoutPingResultsEntry 50331648}

pr1645v2PRoutPingResultsRepTimMin OBJECT-TYPE
   SYNTAX      TimeTicks
   MAX-ACCESS  read-only
   STATUS      current
   DESCRIPTION
      "Path: router.performance.pingResults.replyTimeMin

       Time in centi-second."
   ::= {pr1645v2PRoutPingResultsEntry 67108864}

pr1645v2PRoutPingResultsRepTimMax OBJECT-TYPE
   SYNTAX      TimeTicks
   MAX-ACCESS  read-only
   STATUS      current
   DESCRIPTION
      "Path: router.performance.pingResults.replyTimeMax

       Time in centi-second."
   ::= {pr1645v2PRoutPingResultsEntry 83886080}

pr1645v2PRoutPingResultsRepTimAvrg OBJECT-TYPE
   SYNTAX      TimeTicks
   MAX-ACCESS  read-only
   STATUS      current
   DESCRIPTION
      "Path: router.performance.pingResults.replyTimeAvrg

       Time in centi-second."
   ::= {pr1645v2PRoutPingResultsEntry 100663296}

pr1645v2PRoutPingResultsLastError OBJECT-TYPE
   SYNTAX      DisplayString
   MAX-ACCESS  read-only
   STATUS      current
   DESCRIPTION
      "Path: router.performance.pingResults.lastError"
   ::= {pr1645v2PRoutPingResultsEntry 117440512}


pr1645v2PRoutRadiusAuth OBJECT IDENTIFIER ::= {pr1645v2PRout 63}

pr1645v2PRoutRadiusAuthSSCTable OBJECT-TYPE
   SYNTAX      SEQUENCE OF Pr1645v2PRoutRadiusAuthEntry
   MAX-ACCESS  not-accessible
   STATUS      current
   DESCRIPTION
      "radius statistics"
   ::= {pr1645v2PRoutRadiusAuth 1}

pr1645v2PRoutRadiusAuthEntry OBJECT-TYPE
   SYNTAX      Pr1645v2PRoutRadiusAuthEntry
   MAX-ACCESS  not-accessible
   STATUS      current
   DESCRIPTION
      ""
   INDEX      { pr1645v2PRoutRadiusAuthTableIx }
   ::= {pr1645v2PRoutRadiusAuthSSCTable 1}

Pr1645v2PRoutRadiusAuthEntry ::=
   SEQUENCE
      {
      pr1645v2PRoutRadiusAuthTableIx
         TableIndex,
      pr1645v2PRoutRadiusAuthServer
         IpAddress,
      pr1645v2PRoutRadiusAuthVrfRouter
         DisplayString,
      pr1645v2PRoutRadiusAuthRequests
         Integer32,
      pr1645v2PRoutRadiusAuthAccepts
         Integer32,
      pr1645v2PRoutRadiusAuthRejects
         Integer32,
      pr1645v2PRoutRadiusAuthChallenges
         Integer32,
      pr1645v2PRoutRadiusAuthBadAuth
         Integer32,
      pr1645v2PRoutRadiusAuthTimeOuts
         Integer32,
      pr1645v2PRoutRadiusAuthDroppedPackets
         Integer32
      }

pr1645v2PRoutRadiusAuthTableIx OBJECT-TYPE
   SYNTAX      TableIndex
   MAX-ACCESS  not-accessible
   STATUS      current
   DESCRIPTION
      ""
   ::= {pr1645v2PRoutRadiusAuthEntry 11}

pr1645v2PRoutRadiusAuthServer OBJECT-TYPE
   SYNTAX      IpAddress
   MAX-ACCESS  read-only
   STATUS      current
   DESCRIPTION
      "Path: router.performance.radiusAuth.server"
   ::= {pr1645v2PRoutRadiusAuthEntry 1677721600}

pr1645v2PRoutRadiusAuthVrfRouter OBJECT-TYPE
   SYNTAX      DisplayString
   MAX-ACCESS  read-only
   STATUS      current
   DESCRIPTION
      "Path: router.performance.radiusAuth.vrfRouter"
   ::= {pr1645v2PRoutRadiusAuthEntry 134217728}

pr1645v2PRoutRadiusAuthRequests OBJECT-TYPE
   SYNTAX      Integer32
   MAX-ACCESS  read-only
   STATUS      current
   DESCRIPTION
      "Path: router.performance.radiusAuth.requests"
   ::= {pr1645v2PRoutRadiusAuthEntry 16777216}

pr1645v2PRoutRadiusAuthAccepts OBJECT-TYPE
   SYNTAX      Integer32
   MAX-ACCESS  read-only
   STATUS      current
   DESCRIPTION
      "Path: router.performance.radiusAuth.accepts"
   ::= {pr1645v2PRoutRadiusAuthEntry 33554432}

pr1645v2PRoutRadiusAuthRejects OBJECT-TYPE
   SYNTAX      Integer32
   MAX-ACCESS  read-only
   STATUS      current
   DESCRIPTION
      "Path: router.performance.radiusAuth.rejects"
   ::= {pr1645v2PRoutRadiusAuthEntry 50331648}

pr1645v2PRoutRadiusAuthChallenges OBJECT-TYPE
   SYNTAX      Integer32
   MAX-ACCESS  read-only
   STATUS      current
   DESCRIPTION
      "Path: router.performance.radiusAuth.challenges"
   ::= {pr1645v2PRoutRadiusAuthEntry 67108864}

pr1645v2PRoutRadiusAuthBadAuth OBJECT-TYPE
   SYNTAX      Integer32
   MAX-ACCESS  read-only
   STATUS      current
   DESCRIPTION
      "Path: router.performance.radiusAuth.badAuthenticators"
   ::= {pr1645v2PRoutRadiusAuthEntry 83886080}

pr1645v2PRoutRadiusAuthTimeOuts OBJECT-TYPE
   SYNTAX      Integer32
   MAX-ACCESS  read-only
   STATUS      current
   DESCRIPTION
      "Path: router.performance.radiusAuth.timeOuts"
   ::= {pr1645v2PRoutRadiusAuthEntry 100663296}

pr1645v2PRoutRadiusAuthDroppedPackets OBJECT-TYPE
   SYNTAX      Integer32
   MAX-ACCESS  read-only
   STATUS      current
   DESCRIPTION
      "Path: router.performance.radiusAuth.droppedPackets"
   ::= {pr1645v2PRoutRadiusAuthEntry 117440512}


pr1645v2PRoutRadiusAcct OBJECT IDENTIFIER ::= {pr1645v2PRout 62}

pr1645v2PRoutRadiusAcctSSC OBJECT IDENTIFIER ::= {pr1645v2PRoutRadiusAcct 1}

pr1645v2PRoutRadiusAcctEntry OBJECT IDENTIFIER ::= {pr1645v2PRoutRadiusAcctSSC 1}

pr1645v2PRoutRadiusAcctServer OBJECT-TYPE
   SYNTAX      IpAddress
   MAX-ACCESS  read-only
   STATUS      current
   DESCRIPTION
      "Path: router.performance.radiusAcct.server"
   ::= {pr1645v2PRoutRadiusAcctEntry 1677721600}

pr1645v2PRoutRadiusAcctVrfRouter OBJECT-TYPE
   SYNTAX      DisplayString
   MAX-ACCESS  read-only
   STATUS      current
   DESCRIPTION
      "Path: router.performance.radiusAcct.vrfRouter"
   ::= {pr1645v2PRoutRadiusAcctEntry 16777216}

pr1645v2PRoutRadiusAcctRequests OBJECT-TYPE
   SYNTAX      Integer32
   MAX-ACCESS  read-only
   STATUS      current
   DESCRIPTION
      "Path: router.performance.radiusAcct.requests"
   ::= {pr1645v2PRoutRadiusAcctEntry 134217728}

pr1645v2PRoutRadiusAcctResponses OBJECT-TYPE
   SYNTAX      Integer32
   MAX-ACCESS  read-only
   STATUS      current
   DESCRIPTION
      "Path: router.performance.radiusAcct.responses"
   ::= {pr1645v2PRoutRadiusAcctEntry 150994944}

pr1645v2PRoutRadiusAcctBadAuth OBJECT-TYPE
   SYNTAX      Integer32
   MAX-ACCESS  read-only
   STATUS      current
   DESCRIPTION
      "Path: router.performance.radiusAcct.badAuthenticators"
   ::= {pr1645v2PRoutRadiusAcctEntry 83886080}

pr1645v2PRoutRadiusAcctTimeOuts OBJECT-TYPE
   SYNTAX      Integer32
   MAX-ACCESS  read-only
   STATUS      current
   DESCRIPTION
      "Path: router.performance.radiusAcct.timeOuts"
   ::= {pr1645v2PRoutRadiusAcctEntry 100663296}

pr1645v2PRoutRadiusAcctDroppedPackets OBJECT-TYPE
   SYNTAX      Integer32
   MAX-ACCESS  read-only
   STATUS      current
   DESCRIPTION
      "Path: router.performance.radiusAcct.droppedPackets"
   ::= {pr1645v2PRoutRadiusAcctEntry 117440512}


pr1645v2PRoutTacacsAuth OBJECT IDENTIFIER ::= {pr1645v2PRout 68}

pr1645v2PRoutTacacsAuthSSCTable OBJECT-TYPE
   SYNTAX      SEQUENCE OF Pr1645v2PRoutTacacsAuthEntry
   MAX-ACCESS  not-accessible
   STATUS      current
   DESCRIPTION
      "tacacs auth server perf table"
   ::= {pr1645v2PRoutTacacsAuth 1}

pr1645v2PRoutTacacsAuthEntry OBJECT-TYPE
   SYNTAX      Pr1645v2PRoutTacacsAuthEntry
   MAX-ACCESS  not-accessible
   STATUS      current
   DESCRIPTION
      ""
   INDEX      { pr1645v2PRoutTacacsAuthTableIx }
   ::= {pr1645v2PRoutTacacsAuthSSCTable 1}

Pr1645v2PRoutTacacsAuthEntry ::=
   SEQUENCE
      {
      pr1645v2PRoutTacacsAuthTableIx
         TableIndex,
      pr1645v2PRoutTacacsAuthServer
         IpAddress,
      pr1645v2PRoutTacacsAuthPort
         Integer32,
      pr1645v2PRoutTacacsAuthVrfRouter
         DisplayString,
      pr1645v2PRoutTacacsAuthRequests
         Counter32,
      pr1645v2PRoutTacacsAuthAccepts
         Counter32,
      pr1645v2PRoutTacacsAuthFails
         Counter32,
      pr1645v2PRoutTacacsAuthTimeOuts
         Counter32,
      pr1645v2PRoutTacacsAuthAuthenticationStartPkts
         Counter32,
      pr1645v2PRoutTacacsAuthAuthenticationContinuePkts
         Counter32,
      pr1645v2PRoutTacacsAuthAuthenticationReplyPkts
         Counter32,
      pr1645v2PRoutTacacsAuthAuthorizationRequestPkts
         Counter32,
      pr1645v2PRoutTacacsAuthAuthorizationResponsePkts
         Counter32,
      pr1645v2PRoutTacacsAuthDrops
         Counter32,
      pr1645v2PRoutTacacsAuthErrors
         Counter32
      }

pr1645v2PRoutTacacsAuthTableIx OBJECT-TYPE
   SYNTAX      TableIndex
   MAX-ACCESS  not-accessible
   STATUS      current
   DESCRIPTION
      ""
   ::= {pr1645v2PRoutTacacsAuthEntry 11}

pr1645v2PRoutTacacsAuthServer OBJECT-TYPE
   SYNTAX      IpAddress
   MAX-ACCESS  read-only
   STATUS      current
   DESCRIPTION
      "Path: router.performance.tacacsAuth.server"
   ::= {pr1645v2PRoutTacacsAuthEntry 16777216}

pr1645v2PRoutTacacsAuthPort OBJECT-TYPE
   SYNTAX      Integer32
   MAX-ACCESS  read-only
   STATUS      current
   DESCRIPTION
      "Path: router.performance.tacacsAuth.port"
   ::= {pr1645v2PRoutTacacsAuthEntry 33554432}

pr1645v2PRoutTacacsAuthVrfRouter OBJECT-TYPE
   SYNTAX      DisplayString
   MAX-ACCESS  read-only
   STATUS      current
   DESCRIPTION
      "Path: router.performance.tacacsAuth.vrfRouter"
   ::= {pr1645v2PRoutTacacsAuthEntry 184549376}

pr1645v2PRoutTacacsAuthRequests OBJECT-TYPE
   SYNTAX      Counter32
   MAX-ACCESS  read-only
   STATUS      current
   DESCRIPTION
      "Path: router.performance.tacacsAuth.requests

       32 bit unsigned wrappable counter."
   ::= {pr1645v2PRoutTacacsAuthEntry 50331648}

pr1645v2PRoutTacacsAuthAccepts OBJECT-TYPE
   SYNTAX      Counter32
   MAX-ACCESS  read-only
   STATUS      current
   DESCRIPTION
      "Path: router.performance.tacacsAuth.accepts

       32 bit unsigned wrappable counter."
   ::= {pr1645v2PRoutTacacsAuthEntry 67108864}

pr1645v2PRoutTacacsAuthFails OBJECT-TYPE
   SYNTAX      Counter32
   MAX-ACCESS  read-only
   STATUS      current
   DESCRIPTION
      "Path: router.performance.tacacsAuth.fails

       32 bit unsigned wrappable counter."
   ::= {pr1645v2PRoutTacacsAuthEntry 83886080}

pr1645v2PRoutTacacsAuthTimeOuts OBJECT-TYPE
   SYNTAX      Counter32
   MAX-ACCESS  read-only
   STATUS      current
   DESCRIPTION
      "Path: router.performance.tacacsAuth.timeOuts

       32 bit unsigned wrappable counter."
   ::= {pr1645v2PRoutTacacsAuthEntry 100663296}

pr1645v2PRoutTacacsAuthAuthenticationStartPkts OBJECT-TYPE
   SYNTAX      Counter32
   MAX-ACCESS  read-only
   STATUS      current
   DESCRIPTION
      "Path: router.performance.tacacsAuth.authentication.startPkts

       32 bit unsigned wrappable counter."
   ::= {pr1645v2PRoutTacacsAuthEntry 117506048}

pr1645v2PRoutTacacsAuthAuthenticationContinuePkts OBJECT-TYPE
   SYNTAX      Counter32
   MAX-ACCESS  read-only
   STATUS      current
   DESCRIPTION
      "Path: router.performance.tacacsAuth.authentication.continuePkts

       32 bit unsigned wrappable counter."
   ::= {pr1645v2PRoutTacacsAuthEntry 117571584}

pr1645v2PRoutTacacsAuthAuthenticationReplyPkts OBJECT-TYPE
   SYNTAX      Counter32
   MAX-ACCESS  read-only
   STATUS      current
   DESCRIPTION
      "Path: router.performance.tacacsAuth.authentication.replyPkts

       32 bit unsigned wrappable counter."
   ::= {pr1645v2PRoutTacacsAuthEntry 117637120}

pr1645v2PRoutTacacsAuthAuthorizationRequestPkts OBJECT-TYPE
   SYNTAX      Counter32
   MAX-ACCESS  read-only
   STATUS      current
   DESCRIPTION
      "Path: router.performance.tacacsAuth.authorization.requestPkts

       32 bit unsigned wrappable counter."
   ::= {pr1645v2PRoutTacacsAuthEntry 134283264}

pr1645v2PRoutTacacsAuthAuthorizationResponsePkts OBJECT-TYPE
   SYNTAX      Counter32
   MAX-ACCESS  read-only
   STATUS      current
   DESCRIPTION
      "Path: router.performance.tacacsAuth.authorization.responsePkts

       32 bit unsigned wrappable counter."
   ::= {pr1645v2PRoutTacacsAuthEntry 134348800}

pr1645v2PRoutTacacsAuthDrops OBJECT-TYPE
   SYNTAX      Counter32
   MAX-ACCESS  read-only
   STATUS      current
   DESCRIPTION
      "Path: router.performance.tacacsAuth.drops

       32 bit unsigned wrappable counter."
   ::= {pr1645v2PRoutTacacsAuthEntry 150994944}

pr1645v2PRoutTacacsAuthErrors OBJECT-TYPE
   SYNTAX      Counter32
   MAX-ACCESS  read-only
   STATUS      current
   DESCRIPTION
      "Path: router.performance.tacacsAuth.errors

       32 bit unsigned wrappable counter."
   ::= {pr1645v2PRoutTacacsAuthEntry 167772160}



ar1645v2PRout OBJECT IDENTIFIER ::= {r1645v2PRout 16}


ar1645v2PRoutSendIgmpLeave OBJECT-TYPE
   SYNTAX      Integer32
   MAX-ACCESS  read-write
   STATUS      current
   DESCRIPTION
      "Path: router.actions.sendIgmpLeave
       Info: send igmp leave over selected interfaces"
   ::= {ar1645v2PRout 114}


ar1645v2PRoutIgmpDataLeave OBJECT IDENTIFIER ::= {ar1645v2PRout 115}

ar1645v2PRoutIgmpDataLeaveSSC OBJECT IDENTIFIER ::= {ar1645v2PRoutIgmpDataLeave 1}

ar1645v2PRoutIgmpDataLeaveEntry OBJECT IDENTIFIER ::= {ar1645v2PRoutIgmpDataLeaveSSC 1}

ar1645v2PRoutIgmpDataLeaveInterfaces OBJECT-TYPE
   SYNTAX      DisplayString
   MAX-ACCESS  read-write
   STATUS      current
   DESCRIPTION
      "Path: router.actions.igmpDataLeave.interfaces"
   ::= {ar1645v2PRoutIgmpDataLeaveEntry 16777216}

ar1645v2PRoutIgmpDataLeaveIpAddress OBJECT-TYPE
   SYNTAX      IpAddress
   MAX-ACCESS  read-write
   STATUS      current
   DESCRIPTION
      "Path: router.actions.igmpDataLeave.ipAddress"
   ::= {ar1645v2PRoutIgmpDataLeaveEntry 33554432}


ar1645v2PRoutSendIgmpRep OBJECT-TYPE
   SYNTAX      Integer32
   MAX-ACCESS  read-write
   STATUS      current
   DESCRIPTION
      "Path: router.actions.sendIgmpRep
       Info: send igmp report over selected interfaces"
   ::= {ar1645v2PRout 112}


ar1645v2PRoutIgmpDataRep OBJECT IDENTIFIER ::= {ar1645v2PRout 113}

ar1645v2PRoutIgmpDataRepSSC OBJECT IDENTIFIER ::= {ar1645v2PRoutIgmpDataRep 1}

ar1645v2PRoutIgmpDataRepEntry OBJECT IDENTIFIER ::= {ar1645v2PRoutIgmpDataRepSSC 1}

ar1645v2PRoutIgmpDataRepInterfaces OBJECT-TYPE
   SYNTAX      DisplayString
   MAX-ACCESS  read-write
   STATUS      current
   DESCRIPTION
      "Path: router.actions.igmpDataRep.interfaces"
   ::= {ar1645v2PRoutIgmpDataRepEntry 16777216}

ar1645v2PRoutIgmpDataRepIpAddress OBJECT-TYPE
   SYNTAX      IpAddress
   MAX-ACCESS  read-write
   STATUS      current
   DESCRIPTION
      "Path: router.actions.igmpDataRep.ipAddress"
   ::= {ar1645v2PRoutIgmpDataRepEntry 33554432}


ar1645v2PRoutQmOnDemand OBJECT-TYPE
   SYNTAX      Integer32
   MAX-ACCESS  read-write
   STATUS      current
   DESCRIPTION
      "Path: router.actions.qmOnDemand
       Info: start sending pings"
   ::= {ar1645v2PRout 8043}


ar1645v2PRoutAction OBJECT IDENTIFIER ::= {ar1645v2PRout 8044}

ar1645v2PRoutActionSSC OBJECT IDENTIFIER ::= {ar1645v2PRoutAction 1}

ar1645v2PRoutActionEntry OBJECT IDENTIFIER ::= {ar1645v2PRoutActionSSC 1}

ar1645v2PRoutActionAction OBJECT-TYPE
   SYNTAX      INTEGER
               {
               restart (1),
               restartLossWindow (2),
               stop (3),
               stopAndClear (4)
               }
   MAX-ACCESS  read-write
   STATUS      current
   DESCRIPTION
      "Path: router.actions.action.action

       Possibilities:
               restart   (1)
               restartLossWindow   (2)
               stop   (3)
               stopAndClear   (4)"
   ::= {ar1645v2PRoutActionEntry 16777216}

ar1645v2PRoutActionName OBJECT-TYPE
   SYNTAX      DisplayString
   MAX-ACCESS  read-write
   STATUS      current
   DESCRIPTION
      "Path: router.actions.action.name"
   ::= {ar1645v2PRoutActionEntry 33554432}


ar1645v2PRoutClearTracert OBJECT-TYPE
   SYNTAX      Integer32
   MAX-ACCESS  read-write
   STATUS      current
   DESCRIPTION
      "Path: router.actions.clearTracert
       Info: Clear traceroute results"
   ::= {ar1645v2PRout 154}


ar1645v2PRoutStopTracert OBJECT-TYPE
   SYNTAX      Integer32
   MAX-ACCESS  read-write
   STATUS      current
   DESCRIPTION
      "Path: router.actions.stopTracert
       Info: stop ongoing traceroutes"
   ::= {ar1645v2PRout 152}


ar1645v2PRoutStartTracert OBJECT-TYPE
   SYNTAX      Integer32
   MAX-ACCESS  read-write
   STATUS      current
   DESCRIPTION
      "Path: router.actions.startTracert
       Info: start traceroute"
   ::= {ar1645v2PRout 150}


ar1645v2PRoutTracertData OBJECT IDENTIFIER ::= {ar1645v2PRout 151}

ar1645v2PRoutTracertDataSSC OBJECT IDENTIFIER ::= {ar1645v2PRoutTracertData 1}

ar1645v2PRoutTracertDataEntry OBJECT IDENTIFIER ::= {ar1645v2PRoutTracertDataSSC 1}

ar1645v2PRoutTracertDataIpAddress OBJECT-TYPE
   SYNTAX      IpAddress
   MAX-ACCESS  read-write
   STATUS      current
   DESCRIPTION
      "Path: router.actions.tracertData.ipAddress"
   ::= {ar1645v2PRoutTracertDataEntry 16777216}

ar1645v2PRoutTracertDataHostName OBJECT-TYPE
   SYNTAX      DisplayString
   MAX-ACCESS  read-write
   STATUS      current
   DESCRIPTION
      "Path: router.actions.tracertData.hostName"
   ::= {ar1645v2PRoutTracertDataEntry 33554432}

ar1645v2PRoutTracertDataSourceIp OBJECT-TYPE
   SYNTAX      IpAddress
   MAX-ACCESS  read-write
   STATUS      current
   DESCRIPTION
      "Path: router.actions.tracertData.sourceIp"
   ::= {ar1645v2PRoutTracertDataEntry 50331648}

ar1645v2PRoutTracertDataStartTtl OBJECT-TYPE
   SYNTAX      Integer32
   MAX-ACCESS  read-write
   STATUS      current
   DESCRIPTION
      "Path: router.actions.tracertData.startTtl"
   ::= {ar1645v2PRoutTracertDataEntry 67108864}

ar1645v2PRoutTracertDataMaxHops OBJECT-TYPE
   SYNTAX      Integer32
   MAX-ACCESS  read-write
   STATUS      current
   DESCRIPTION
      "Path: router.actions.tracertData.maxHops"
   ::= {ar1645v2PRoutTracertDataEntry 83886080}

ar1645v2PRoutTracertDataQueriesPerHop OBJECT-TYPE
   SYNTAX      Integer32
   MAX-ACCESS  read-write
   STATUS      current
   DESCRIPTION
      "Path: router.actions.tracertData.queriesPerHop"
   ::= {ar1645v2PRoutTracertDataEntry 100663296}

ar1645v2PRoutTracertDataResolveHosts OBJECT-TYPE
   SYNTAX      INTEGER
               {
               disabled (0),
               enabled (1)
               }
   MAX-ACCESS  read-write
   STATUS      current
   DESCRIPTION
      "Path: router.actions.tracertData.resolveHosts

       Possibilities:
               disabled   (0)
               enabled   (1)"
   ::= {ar1645v2PRoutTracertDataEntry 117440512}

ar1645v2PRoutTracertDataDnsTimeOut OBJECT-TYPE
   SYNTAX      TimeTicks
   MAX-ACCESS  read-write
   STATUS      current
   DESCRIPTION
      "Path: router.actions.tracertData.dnsTimeOut

       Time in centi-second."
   ::= {ar1645v2PRoutTracertDataEntry 134217728}

ar1645v2PRoutTracertDataIcmpTimeOut OBJECT-TYPE
   SYNTAX      TimeTicks
   MAX-ACCESS  read-write
   STATUS      current
   DESCRIPTION
      "Path: router.actions.tracertData.icmpTimeOut

       Time in centi-second."
   ::= {ar1645v2PRoutTracertDataEntry 150994944}

ar1645v2PRoutTracertDataTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: router.actions.tracertData.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {ar1645v2PRoutTracertDataEntry 167772160}

ar1645v2PRoutTracertDataDataLength OBJECT-TYPE
   SYNTAX      Integer32
   MAX-ACCESS  read-write
   STATUS      current
   DESCRIPTION
      "Path: router.actions.tracertData.dataLength"
   ::= {ar1645v2PRoutTracertDataEntry 184549376}


ar1645v2PRoutUnBlacklist OBJECT-TYPE
   SYNTAX      Integer32
   MAX-ACCESS  read-write
   STATUS      current
   DESCRIPTION
      "Path: router.actions.unBlacklist
       Info: delete an entry/range of entries from the DHCP Blacklist"
   ::= {ar1645v2PRout 47}


ar1645v2PRoutUnBlacklistData OBJECT IDENTIFIER ::= {ar1645v2PRout 48}

ar1645v2PRoutUnBlacklistDataSSC OBJECT IDENTIFIER ::= {ar1645v2PRoutUnBlacklistData 1}

ar1645v2PRoutUnBlacklistDataEntry OBJECT IDENTIFIER ::= {ar1645v2PRoutUnBlacklistDataSSC 1}

ar1645v2PRoutUnBlacklistDataStartIp OBJECT-TYPE
   SYNTAX      IpAddress
   MAX-ACCESS  read-write
   STATUS      current
   DESCRIPTION
      "Path: router.actions.unBlacklistData.startIp"
   ::= {ar1645v2PRoutUnBlacklistDataEntry 16777216}

ar1645v2PRoutUnBlacklistDataStopIp OBJECT-TYPE
   SYNTAX      IpAddress
   MAX-ACCESS  read-write
   STATUS      current
   DESCRIPTION
      "Path: router.actions.unBlacklistData.stopIp"
   ::= {ar1645v2PRoutUnBlacklistDataEntry 33554432}

ar1645v2PRoutUnBlacklistDataMac OBJECT-TYPE
   SYNTAX      OCTET STRING
   MAX-ACCESS  read-write
   STATUS      current
   DESCRIPTION
      "Path: router.actions.unBlacklistData.mac

       MAC address."
   ::= {ar1645v2PRoutUnBlacklistDataEntry 50331648}


ar1645v2PRoutStopPing OBJECT-TYPE
   SYNTAX      Integer32
   MAX-ACCESS  read-write
   STATUS      current
   DESCRIPTION
      "Path: router.actions.stopPing
       Info: stop sending pings"
   ::= {ar1645v2PRout 45}


ar1645v2PRoutStartPing OBJECT-TYPE
   SYNTAX      Integer32
   MAX-ACCESS  read-write
   STATUS      current
   DESCRIPTION
      "Path: router.actions.startPing
       Info: start sending pings"
   ::= {ar1645v2PRout 43}


ar1645v2PRoutPingData OBJECT IDENTIFIER ::= {ar1645v2PRout 44}

ar1645v2PRoutPingDataSSC OBJECT IDENTIFIER ::= {ar1645v2PRoutPingData 1}

ar1645v2PRoutPingDataEntry OBJECT IDENTIFIER ::= {ar1645v2PRoutPingDataSSC 1}

ar1645v2PRoutPingDataIpAddress OBJECT-TYPE
   SYNTAX      IpAddress
   MAX-ACCESS  read-write
   STATUS      current
   DESCRIPTION
      "Path: router.actions.pingData.ipAddress"
   ::= {ar1645v2PRoutPingDataEntry 16777216}

ar1645v2PRoutPingDataHostName OBJECT-TYPE
   SYNTAX      DisplayString
   MAX-ACCESS  read-write
   STATUS      current
   DESCRIPTION
      "Path: router.actions.pingData.hostName"
   ::= {ar1645v2PRoutPingDataEntry 100663296}

ar1645v2PRoutPingDataSourceIp OBJECT-TYPE
   SYNTAX      IpAddress
   MAX-ACCESS  read-write
   STATUS      current
   DESCRIPTION
      "Path: router.actions.pingData.sourceIp"
   ::= {ar1645v2PRoutPingDataEntry 117440512}

ar1645v2PRoutPingDataTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: router.actions.pingData.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {ar1645v2PRoutPingDataEntry 134217728}

ar1645v2PRoutPingDataFragment OBJECT-TYPE
   SYNTAX      INTEGER
               {
               yes (1),
               no (2)
               }
   MAX-ACCESS  read-write
   STATUS      current
   DESCRIPTION
      "Path: router.actions.pingData.fragment

       Possibilities:
               yes   (1)
               no   (2)"
   ::= {ar1645v2PRoutPingDataEntry 150994944}

ar1645v2PRoutPingDataTtl OBJECT-TYPE
   SYNTAX      Integer32
   MAX-ACCESS  read-write
   STATUS      current
   DESCRIPTION
      "Path: router.actions.pingData.ttl"
   ::= {ar1645v2PRoutPingDataEntry 167772160}

ar1645v2PRoutPingDataIterations OBJECT-TYPE
   SYNTAX      INTEGER
               {
               unlimited (0)
               }
   MAX-ACCESS  read-write
   STATUS      current
   DESCRIPTION
      "Path: router.actions.pingData.iterations

       Possibilities:
               unlimited   (0)"
   ::= {ar1645v2PRoutPingDataEntry 33554432}

ar1645v2PRoutPingDataInterval OBJECT-TYPE
   SYNTAX      Integer32
   MAX-ACCESS  read-write
   STATUS      current
   DESCRIPTION
      "Path: router.actions.pingData.interval"
   ::= {ar1645v2PRoutPingDataEntry 50331648}

ar1645v2PRoutPingDataDataLength OBJECT-TYPE
   SYNTAX      Integer32
   MAX-ACCESS  read-write
   STATUS      current
   DESCRIPTION
      "Path: router.actions.pingData.dataLength"
   ::= {ar1645v2PRoutPingDataEntry 67108864}

ar1645v2PRoutPingDataTimeOut OBJECT-TYPE
   SYNTAX      TimeTicks
   MAX-ACCESS  read-write
   STATUS      current
   DESCRIPTION
      "Path: router.actions.pingData.timeOut

       Time in centi-second."
   ::= {ar1645v2PRoutPingDataEntry 83886080}


ar1645v2PRoutRestartDhcpClient OBJECT-TYPE
   SYNTAX      Integer32
   MAX-ACCESS  read-write
   STATUS      current
   DESCRIPTION
      "Path: router.actions.restartDhcpClient
       Info: restart the dhcp client"
   ::= {ar1645v2PRout 88}


ar1645v2PRoutInterfaceName OBJECT-TYPE
   SYNTAX      DisplayString
   MAX-ACCESS  read-write
   STATUS      current
   DESCRIPTION
      "Path: router.actions.interfaceName
       Info: Name of the interface"
   ::= {ar1645v2PRout 89}


ar1645v2PRoutSendRipReqAction OBJECT-TYPE
   SYNTAX      Integer32
   MAX-ACCESS  read-write
   STATUS      current
   DESCRIPTION
      "Path: router.actions.sendRipReqAction
       Info: send RIP request to specific router"
   ::= {ar1645v2PRout 301}


ar1645v2PRoutRequestArguments OBJECT IDENTIFIER ::= {ar1645v2PRout 302}

ar1645v2PRoutRequestArgumentsSSC OBJECT IDENTIFIER ::= {ar1645v2PRoutRequestArguments 1}

ar1645v2PRoutRequestArgumentsEntry OBJECT IDENTIFIER ::= {ar1645v2PRoutRequestArgumentsSSC 1}

ar1645v2PRoutRequestArgumentsRouterIp OBJECT-TYPE
   SYNTAX      IpAddress
   MAX-ACCESS  read-write
   STATUS      current
   DESCRIPTION
      "Path: router.actions.requestArguments.routerIp"
   ::= {ar1645v2PRoutRequestArgumentsEntry 16777216}

ar1645v2PRoutRequestArgumentsOutIf OBJECT-TYPE
   SYNTAX      DisplayString
   MAX-ACCESS  read-write
   STATUS      current
   DESCRIPTION
      "Path: router.actions.requestArguments.outgoingInterface"
   ::= {ar1645v2PRoutRequestArgumentsEntry 33554432}


ar1645v2PRoutClearCounters OBJECT-TYPE
   SYNTAX      Integer32
   MAX-ACCESS  read-write
   STATUS      current
   DESCRIPTION
      "Path: router.actions.clearCounters
       Info: reset counters"
   ::= {ar1645v2PRout 263}


ar1645v2PRoutClearDnsCache OBJECT-TYPE
   SYNTAX      Integer32
   MAX-ACCESS  read-write
   STATUS      current
   DESCRIPTION
      "Path: router.actions.clearDnsCache
       Info: clear the DNS cache table"
   ::= {ar1645v2PRout 155}


ar1645v2PRoutFreeIpAddress OBJECT-TYPE
   SYNTAX      Integer32
   MAX-ACCESS  read-write
   STATUS      current
   DESCRIPTION
      "Path: router.actions.freeIpAddress
       Info: Free ip address"
   ::= {ar1645v2PRout 106}


ar1645v2PRoutAddr OBJECT-TYPE
   SYNTAX      IpAddress
   MAX-ACCESS  read-write
   STATUS      current
   DESCRIPTION
      "Path: router.actions.address
       Info: ip address attribute"
   ::= {ar1645v2PRout 107}


ar1645v2PRoutTakeIpAddress OBJECT-TYPE
   SYNTAX      Integer32
   MAX-ACCESS  read-write
   STATUS      current
   DESCRIPTION
      "Path: router.actions.takeIpAddress
       Info: Take ip address from pool"
   ::= {ar1645v2PRout 104}


ar1645v2PRoutPool OBJECT IDENTIFIER ::= {ar1645v2PRout 105}

ar1645v2PRoutPoolSSC OBJECT IDENTIFIER ::= {ar1645v2PRoutPool 1}

ar1645v2PRoutPoolEntry OBJECT IDENTIFIER ::= {ar1645v2PRoutPoolSSC 1}

ar1645v2PRoutPoolPoolType OBJECT-TYPE
   SYNTAX      INTEGER
               {
               list (1),
               interval (2)
               }
   MAX-ACCESS  read-write
   STATUS      current
   DESCRIPTION
      "Path: router.actions.poolTypeName.poolType

       Possibilities:
               list   (1)
               interval   (2)"
   ::= {ar1645v2PRoutPoolEntry 16777216}

ar1645v2PRoutPoolPoolName OBJECT-TYPE
   SYNTAX      DisplayString
   MAX-ACCESS  read-write
   STATUS      current
   DESCRIPTION
      "Path: router.actions.poolTypeName.poolName"
   ::= {ar1645v2PRoutPoolEntry 33554432}


ar1645v2PRoutForceDnsUpdate OBJECT-TYPE
   SYNTAX      Integer32
   MAX-ACCESS  read-write
   STATUS      current
   DESCRIPTION
      "Path: router.actions.forceDnsUpdate
       Info: Force a DNS Update"
   ::= {ar1645v2PRout 84}


ar1645v2PRoutDnsUpdateName OBJECT-TYPE
   SYNTAX      DisplayString
   MAX-ACCESS  read-write
   STATUS      current
   DESCRIPTION
      "Path: router.actions.dnsUpdateName
       Info: Name of DNS Update table entry"
   ::= {ar1645v2PRout 85}



fr1645v2PRout OBJECT IDENTIFIER ::= {r1645v2PRout 13}


fr1645v2PRoutAlarm OBJECT IDENTIFIER ::= {fr1645v2PRout 202}

fr1645v2PRoutAlarmSSC OBJECT IDENTIFIER ::= {fr1645v2PRoutAlarm 1}

fr1645v2PRoutAlarmEntry OBJECT IDENTIFIER ::= {fr1645v2PRoutAlarmSSC 1}

fr1645v2PRoutAlarmDiscriminator OBJECT-TYPE
   SYNTAX      Integer32
   MAX-ACCESS  read-only
   STATUS      current
   DESCRIPTION
      "Path: router.alarms.alarmInfo.discriminator"
   ::= {fr1645v2PRoutAlarmEntry 16777216}

fr1645v2PRoutAlarmCurrent OBJECT-TYPE
   SYNTAX      Integer32
   MAX-ACCESS  read-only
   STATUS      current
   DESCRIPTION
      "Path: router.alarms.alarmInfo.currentAlarms

       Bit meanings:
               bit 0 = pingActive,
               bit 1 = qMonLoss,
               bit 2 = qMonDelay,
               bit 3 = qMonJitter"
   ::= {fr1645v2PRoutAlarmEntry 33554432}

fr1645v2PRoutAlarmPrevious OBJECT-TYPE
   SYNTAX      Integer32
   MAX-ACCESS  read-only
   STATUS      current
   DESCRIPTION
      "Path: router.alarms.alarmInfo.previousAlarms

       Bit meanings:
               bit 0 = pingActive,
               bit 1 = qMonLoss,
               bit 2 = qMonDelay,
               bit 3 = qMonJitter"
   ::= {fr1645v2PRoutAlarmEntry 50331648}

fr1645v2PRoutAlarmMask OBJECT-TYPE
   SYNTAX      Integer32
   MAX-ACCESS  read-only
   STATUS      current
   DESCRIPTION
      "Path: router.alarms.alarmInfo.alarmMask

       Bit meanings:
               bit 0 = pingActive,
               bit 1 = qMonLoss,
               bit 2 = qMonDelay,
               bit 3 = qMonJitter"
   ::= {fr1645v2PRoutAlarmEntry 67108864}

fr1645v2PRoutAlarmLevPingActive OBJECT-TYPE
   SYNTAX      Integer32
   MAX-ACCESS  read-only
   STATUS      current
   DESCRIPTION
      "Path: router.alarms.alarmInfo.alarmLevel.pingActive"
   ::= {fr1645v2PRoutAlarmEntry 83951616}

fr1645v2PRoutAlarmLevQMonLoss OBJECT-TYPE
   SYNTAX      Integer32
   MAX-ACCESS  read-only
   STATUS      current
   DESCRIPTION
      "Path: router.alarms.alarmInfo.alarmLevel.qMonLoss"
   ::= {fr1645v2PRoutAlarmEntry 84017152}

fr1645v2PRoutAlarmLevQMonDelay OBJECT-TYPE
   SYNTAX      Integer32
   MAX-ACCESS  read-only
   STATUS      current
   DESCRIPTION
      "Path: router.alarms.alarmInfo.alarmLevel.qMonDelay"
   ::= {fr1645v2PRoutAlarmEntry 84082688}

fr1645v2PRoutAlarmLevQMonJitter OBJECT-TYPE
   SYNTAX      Integer32
   MAX-ACCESS  read-only
   STATUS      current
   DESCRIPTION
      "Path: router.alarms.alarmInfo.alarmLevel.qMonJitter"
   ::= {fr1645v2PRoutAlarmEntry 84148224}


fr1645v2PRoutAlarmE2 OBJECT IDENTIFIER ::= {fr1645v2PRoutAlarm 2}

fr1645v2PRoutAlarmE2Entry OBJECT IDENTIFIER ::= {fr1645v2PRoutAlarmE2 1}

fr1645v2PRoutAlarmE2PingActive OBJECT IDENTIFIER ::= {fr1645v2PRoutAlarmE2Entry 10}

fr1645v2PRoutAlarmE2PingActivePfx OBJECT IDENTIFIER ::= {fr1645v2PRoutAlarmE2PingActive 0}

fr1645v2PRoutAlarmE2PingActiveOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pingActive'
                representing an alarm condition in the alarm word
                of attribute 'alarmInfo' of managed object 'poolRouter2'
                (root='router1645') has changed from the ON to the OFF state."
   ::= {fr1645v2PRoutAlarmE2PingActivePfx 1}

fr1645v2PRoutAlarmE2PingActiveOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pingActive'
                representing an alarm condition in the alarm word
                of attribute 'alarmInfo' of managed object 'poolRouter2'
                (root='router1645') has changed from the OFF to the ON state."
   ::= {fr1645v2PRoutAlarmE2PingActivePfx 2}

fr1645v2PRoutAlarmE2QMonLoss OBJECT IDENTIFIER ::= {fr1645v2PRoutAlarmE2Entry 11}

fr1645v2PRoutAlarmE2QMonLossPfx OBJECT IDENTIFIER ::= {fr1645v2PRoutAlarmE2QMonLoss 0}

fr1645v2PRoutAlarmE2QMonLossOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qMonLoss'
                representing an alarm condition in the alarm word
                of attribute 'alarmInfo' of managed object 'poolRouter2'
                (root='router1645') has changed from the ON to the OFF state."
   ::= {fr1645v2PRoutAlarmE2QMonLossPfx 1}

fr1645v2PRoutAlarmE2QMonLossOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qMonLoss'
                representing an alarm condition in the alarm word
                of attribute 'alarmInfo' of managed object 'poolRouter2'
                (root='router1645') has changed from the OFF to the ON state."
   ::= {fr1645v2PRoutAlarmE2QMonLossPfx 2}

fr1645v2PRoutAlarmE2QMonDelay OBJECT IDENTIFIER ::= {fr1645v2PRoutAlarmE2Entry 12}

fr1645v2PRoutAlarmE2QMonDelayPfx OBJECT IDENTIFIER ::= {fr1645v2PRoutAlarmE2QMonDelay 0}

fr1645v2PRoutAlarmE2QMonDelayOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qMonDelay'
                representing an alarm condition in the alarm word
                of attribute 'alarmInfo' of managed object 'poolRouter2'
                (root='router1645') has changed from the ON to the OFF state."
   ::= {fr1645v2PRoutAlarmE2QMonDelayPfx 1}

fr1645v2PRoutAlarmE2QMonDelayOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qMonDelay'
                representing an alarm condition in the alarm word
                of attribute 'alarmInfo' of managed object 'poolRouter2'
                (root='router1645') has changed from the OFF to the ON state."
   ::= {fr1645v2PRoutAlarmE2QMonDelayPfx 2}

fr1645v2PRoutAlarmE2QMonJitter OBJECT IDENTIFIER ::= {fr1645v2PRoutAlarmE2Entry 13}

fr1645v2PRoutAlarmE2QMonJitterPfx OBJECT IDENTIFIER ::= {fr1645v2PRoutAlarmE2QMonJitter 0}

fr1645v2PRoutAlarmE2QMonJitterOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qMonJitter'
                representing an alarm condition in the alarm word
                of attribute 'alarmInfo' of managed object 'poolRouter2'
                (root='router1645') has changed from the ON to the OFF state."
   ::= {fr1645v2PRoutAlarmE2QMonJitterPfx 1}

fr1645v2PRoutAlarmE2QMonJitterOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'qMonJitter'
                representing an alarm condition in the alarm word
                of attribute 'alarmInfo' of managed object 'poolRouter2'
                (root='router1645') has changed from the OFF to the ON state."
   ::= {fr1645v2PRoutAlarmE2QMonJitterPfx 2}



END
