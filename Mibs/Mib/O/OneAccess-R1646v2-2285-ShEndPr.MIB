OneAccess-R1646v2-2285-ShEndPr DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1646Rootv2 MODULE-IDENTITY
   LAST-UPDATED "202107151728Z"
   ORGANIZATION "OneAccess"
   CONTACT-INFO "http://www.oneaccess-net.com/telindus/"
   DESCRIPTION
      "..."
   ::= {telindus 1132}




r1646v2ShEndPr OBJECT IDENTIFIER ::= {r1646Rootv2 2285}

r1646v2ShEndPrMOProp OBJECT-TYPE
   SYNTAX      SEQUENCE OF R1646v2ShEndPrMOPropEntry
   MAX-ACCESS  not-accessible
   STATUS      current
   DESCRIPTION
      ""
   ::= {r1646v2ShEndPr 1}

r1646v2ShEndPrMOPropEntry OBJECT-TYPE
   SYNTAX      R1646v2ShEndPrMOPropEntry
   MAX-ACCESS  not-accessible
   STATUS      current
   DESCRIPTION
      ""
   INDEX      { r1646v2ShEndPrMOPropGlobalIx }
   ::= {r1646v2ShEndPrMOProp 1}

R1646v2ShEndPrMOPropEntry ::=
   SEQUENCE
      {
      r1646v2ShEndPrMOPropPath
         ContainmentPath,
      r1646v2ShEndPrMOPropRev
         ObjectRevision,
      r1646v2ShEndPrMOPropGlobalIx
         GlobalIndex
      }

r1646v2ShEndPrMOPropPath OBJECT-TYPE
   SYNTAX      ContainmentPath
   MAX-ACCESS  read-only
   STATUS      current
   DESCRIPTION
      "Textual description of the containment tree from the instance of
       the root object down to the instance of the current object."
   ::= {r1646v2ShEndPrMOPropEntry 3}

r1646v2ShEndPrMOPropRev OBJECT-TYPE
   SYNTAX      ObjectRevision
   MAX-ACCESS  read-only
   STATUS      current
   DESCRIPTION
      "This value corresponds with the revision of the MANAGED OBJECT."
   ::= {r1646v2ShEndPrMOPropEntry 4}

r1646v2ShEndPrMOPropGlobalIx OBJECT-TYPE
   SYNTAX      GlobalIndex
   MAX-ACCESS  read-only
   STATUS      current
   DESCRIPTION
      "The value of the tlsCntTreeGlobalIndex of the MANAGED OBJECT."
   ::= {r1646v2ShEndPrMOPropEntry 10}



sr1646v2ShEndPr OBJECT IDENTIFIER ::= {r1646v2ShEndPr 14}


sr1646v2ShEndPrLineAttenuation OBJECT IDENTIFIER ::= {sr1646v2ShEndPr 8}

sr1646v2ShEndPrLineAttenuationTable OBJECT-TYPE
   SYNTAX      SEQUENCE OF Sr1646v2ShEndPrLineAttenuationEntry
   MAX-ACCESS  not-accessible
   STATUS      current
   DESCRIPTION
      "lineAttenuation"
   ::= {sr1646v2ShEndPrLineAttenuation 1}

sr1646v2ShEndPrLineAttenuationEntry OBJECT-TYPE
   SYNTAX      Sr1646v2ShEndPrLineAttenuationEntry
   MAX-ACCESS  not-accessible
   STATUS      current
   DESCRIPTION
      ""
   INDEX      { sr1646v2ShEndPrLineAttenuationGlobalIx }
   ::= {sr1646v2ShEndPrLineAttenuationTable 1}

Sr1646v2ShEndPrLineAttenuationEntry ::=
   SEQUENCE
      {
      sr1646v2ShEndPrLineAttenuationGlobalIx
         GlobalIndex,
      sr1646v2ShEndPrLineAttenuationValue
         Integer32
      }

sr1646v2ShEndPrLineAttenuationGlobalIx OBJECT-TYPE
   SYNTAX      GlobalIndex
   MAX-ACCESS  not-accessible
   STATUS      current
   DESCRIPTION
      "The value of the tlsCntTreeGlobalIndex of the MANAGED OBJECT."
   ::= {sr1646v2ShEndPrLineAttenuationEntry 10}

sr1646v2ShEndPrLineAttenuationValue OBJECT-TYPE
   SYNTAX      Integer32
   MAX-ACCESS  read-only
   STATUS      current
   DESCRIPTION
      "Path: linePair.status.lineAttenuation

       unit name = dB
       formula = 10 / ; 10 *"
   ::= {sr1646v2ShEndPrLineAttenuationEntry 2147483648}


sr1646v2ShEndPrNoiseMargin OBJECT IDENTIFIER ::= {sr1646v2ShEndPr 9}

sr1646v2ShEndPrNoiseMarginTable OBJECT-TYPE
   SYNTAX      SEQUENCE OF Sr1646v2ShEndPrNoiseMarginEntry
   MAX-ACCESS  not-accessible
   STATUS      current
   DESCRIPTION
      "noiseMargin"
   ::= {sr1646v2ShEndPrNoiseMargin 1}

sr1646v2ShEndPrNoiseMarginEntry OBJECT-TYPE
   SYNTAX      Sr1646v2ShEndPrNoiseMarginEntry
   MAX-ACCESS  not-accessible
   STATUS      current
   DESCRIPTION
      ""
   INDEX      { sr1646v2ShEndPrNoiseMarginGlobalIx }
   ::= {sr1646v2ShEndPrNoiseMarginTable 1}

Sr1646v2ShEndPrNoiseMarginEntry ::=
   SEQUENCE
      {
      sr1646v2ShEndPrNoiseMarginGlobalIx
         GlobalIndex,
      sr1646v2ShEndPrNoiseMarginValue
         Integer32
      }

sr1646v2ShEndPrNoiseMarginGlobalIx OBJECT-TYPE
   SYNTAX      GlobalIndex
   MAX-ACCESS  not-accessible
   STATUS      current
   DESCRIPTION
      "The value of the tlsCntTreeGlobalIndex of the MANAGED OBJECT."
   ::= {sr1646v2ShEndPrNoiseMarginEntry 10}

sr1646v2ShEndPrNoiseMarginValue OBJECT-TYPE
   SYNTAX      Integer32
   MAX-ACCESS  read-only
   STATUS      current
   DESCRIPTION
      "Path: linePair.status.noiseMargin

       unit name = dB
       formula = 10 / ; 10 *"
   ::= {sr1646v2ShEndPrNoiseMarginEntry 2147483648}


sr1646v2ShEndPrSnmpIndex OBJECT IDENTIFIER ::= {sr1646v2ShEndPr 269}

sr1646v2ShEndPrSnmpIndexTable OBJECT-TYPE
   SYNTAX      SEQUENCE OF Sr1646v2ShEndPrSnmpIndexEntry
   MAX-ACCESS  not-accessible
   STATUS      current
   DESCRIPTION
      "SNMP index assigned to this object"
   ::= {sr1646v2ShEndPrSnmpIndex 1}

sr1646v2ShEndPrSnmpIndexEntry OBJECT-TYPE
   SYNTAX      Sr1646v2ShEndPrSnmpIndexEntry
   MAX-ACCESS  not-accessible
   STATUS      current
   DESCRIPTION
      ""
   INDEX      { sr1646v2ShEndPrSnmpIndexGlobalIx }
   ::= {sr1646v2ShEndPrSnmpIndexTable 1}

Sr1646v2ShEndPrSnmpIndexEntry ::=
   SEQUENCE
      {
      sr1646v2ShEndPrSnmpIndexGlobalIx
         GlobalIndex,
      sr1646v2ShEndPrSnmpIndexValue
         Integer32
      }

sr1646v2ShEndPrSnmpIndexGlobalIx OBJECT-TYPE
   SYNTAX      GlobalIndex
   MAX-ACCESS  not-accessible
   STATUS      current
   DESCRIPTION
      "The value of the tlsCntTreeGlobalIndex of the MANAGED OBJECT."
   ::= {sr1646v2ShEndPrSnmpIndexEntry 10}

sr1646v2ShEndPrSnmpIndexValue OBJECT-TYPE
   SYNTAX      Integer32
   MAX-ACCESS  read-only
   STATUS      current
   DESCRIPTION
      "Path: linePair.status.snmpIndex"
   ::= {sr1646v2ShEndPrSnmpIndexEntry 2147483648}



pr1646v2ShEndPr OBJECT IDENTIFIER ::= {r1646v2ShEndPr 12}


pr1646v2ShEndPrH2Perf OBJECT IDENTIFIER ::= {pr1646v2ShEndPr 12}

pr1646v2ShEndPrH2PerfSSCTable OBJECT-TYPE
   SYNTAX      SEQUENCE OF Pr1646v2ShEndPrH2PerfEntry
   MAX-ACCESS  not-accessible
   STATUS      current
   DESCRIPTION
      "h2Performance"
   ::= {pr1646v2ShEndPrH2Perf 1}

pr1646v2ShEndPrH2PerfEntry OBJECT-TYPE
   SYNTAX      Pr1646v2ShEndPrH2PerfEntry
   MAX-ACCESS  not-accessible
   STATUS      current
   DESCRIPTION
      ""
   INDEX      { pr1646v2ShEndPrH2PerfGlobalIx,
                pr1646v2ShEndPrH2PerfTableIx }
   ::= {pr1646v2ShEndPrH2PerfSSCTable 1}

Pr1646v2ShEndPrH2PerfEntry ::=
   SEQUENCE
      {
      pr1646v2ShEndPrH2PerfGlobalIx
         GlobalIndex,
      pr1646v2ShEndPrH2PerfTableIx
         TableIndex,
      pr1646v2ShEndPrH2PerfSysUpTime
         TimeTicks,
      pr1646v2ShEndPrH2PerfCViol
         Counter32,
      pr1646v2ShEndPrH2PerfErrSec
         TimeTicks,
      pr1646v2ShEndPrH2PerfSevErrSec
         TimeTicks,
      pr1646v2ShEndPrH2PerfUnavSec
         TimeTicks,
      pr1646v2ShEndPrH2PerfLoswSec
         TimeTicks,
      pr1646v2ShEndPrH2PerfMSec
         TimeTicks
      }

pr1646v2ShEndPrH2PerfGlobalIx OBJECT-TYPE
   SYNTAX      GlobalIndex
   MAX-ACCESS  not-accessible
   STATUS      current
   DESCRIPTION
      "The value of the tlsCntTreeGlobalIndex of the MANAGED OBJECT."
   ::= {pr1646v2ShEndPrH2PerfEntry 10}

pr1646v2ShEndPrH2PerfTableIx OBJECT-TYPE
   SYNTAX      TableIndex
   MAX-ACCESS  not-accessible
   STATUS      current
   DESCRIPTION
      ""
   ::= {pr1646v2ShEndPrH2PerfEntry 11}

pr1646v2ShEndPrH2PerfSysUpTime OBJECT-TYPE
   SYNTAX      TimeTicks
   MAX-ACCESS  read-only
   STATUS      current
   DESCRIPTION
      "Path: linePair.performance.h2Performance.sysUpTime

       Time in centi-second."
   ::= {pr1646v2ShEndPrH2PerfEntry 16777216}

pr1646v2ShEndPrH2PerfCViol OBJECT-TYPE
   SYNTAX      Counter32
   MAX-ACCESS  read-only
   STATUS      current
   DESCRIPTION
      "Path: linePair.performance.h2Performance.codeViolations

       32 bit unsigned wrappable counter."
   ::= {pr1646v2ShEndPrH2PerfEntry 33554432}

pr1646v2ShEndPrH2PerfErrSec OBJECT-TYPE
   SYNTAX      TimeTicks
   MAX-ACCESS  read-only
   STATUS      current
   DESCRIPTION
      "Path: linePair.performance.h2Performance.errSec

       Time in centi-second."
   ::= {pr1646v2ShEndPrH2PerfEntry 50331648}

pr1646v2ShEndPrH2PerfSevErrSec OBJECT-TYPE
   SYNTAX      TimeTicks
   MAX-ACCESS  read-only
   STATUS      current
   DESCRIPTION
      "Path: linePair.performance.h2Performance.sevErrSec

       Time in centi-second."
   ::= {pr1646v2ShEndPrH2PerfEntry 67108864}

pr1646v2ShEndPrH2PerfUnavSec OBJECT-TYPE
   SYNTAX      TimeTicks
   MAX-ACCESS  read-only
   STATUS      current
   DESCRIPTION
      "Path: linePair.performance.h2Performance.unavailSec

       Time in centi-second."
   ::= {pr1646v2ShEndPrH2PerfEntry 83886080}

pr1646v2ShEndPrH2PerfLoswSec OBJECT-TYPE
   SYNTAX      TimeTicks
   MAX-ACCESS  read-only
   STATUS      current
   DESCRIPTION
      "Path: linePair.performance.h2Performance.loswSec

       Time in centi-second."
   ::= {pr1646v2ShEndPrH2PerfEntry 100663296}

pr1646v2ShEndPrH2PerfMSec OBJECT-TYPE
   SYNTAX      TimeTicks
   MAX-ACCESS  read-only
   STATUS      current
   DESCRIPTION
      "Path: linePair.performance.h2Performance.moniSec

       Time in centi-second."
   ::= {pr1646v2ShEndPrH2PerfEntry 134217728}


pr1646v2ShEndPrH24Perf OBJECT IDENTIFIER ::= {pr1646v2ShEndPr 15}

pr1646v2ShEndPrH24PerfSSCTable OBJECT-TYPE
   SYNTAX      SEQUENCE OF Pr1646v2ShEndPrH24PerfEntry
   MAX-ACCESS  not-accessible
   STATUS      current
   DESCRIPTION
      "h24Performance"
   ::= {pr1646v2ShEndPrH24Perf 1}

pr1646v2ShEndPrH24PerfEntry OBJECT-TYPE
   SYNTAX      Pr1646v2ShEndPrH24PerfEntry
   MAX-ACCESS  not-accessible
   STATUS      current
   DESCRIPTION
      ""
   INDEX      { pr1646v2ShEndPrH24PerfGlobalIx,
                pr1646v2ShEndPrH24PerfTableIx }
   ::= {pr1646v2ShEndPrH24PerfSSCTable 1}

Pr1646v2ShEndPrH24PerfEntry ::=
   SEQUENCE
      {
      pr1646v2ShEndPrH24PerfGlobalIx
         GlobalIndex,
      pr1646v2ShEndPrH24PerfTableIx
         TableIndex,
      pr1646v2ShEndPrH24PerfSysUpTime
         TimeTicks,
      pr1646v2ShEndPrH24PerfCViol
         Counter32,
      pr1646v2ShEndPrH24PerfErrSec
         TimeTicks,
      pr1646v2ShEndPrH24PerfSevErrSec
         TimeTicks,
      pr1646v2ShEndPrH24PerfUnavSec
         TimeTicks,
      pr1646v2ShEndPrH24PerfLoswSec
         TimeTicks,
      pr1646v2ShEndPrH24PerfMSec
         TimeTicks
      }

pr1646v2ShEndPrH24PerfGlobalIx OBJECT-TYPE
   SYNTAX      GlobalIndex
   MAX-ACCESS  not-accessible
   STATUS      current
   DESCRIPTION
      "The value of the tlsCntTreeGlobalIndex of the MANAGED OBJECT."
   ::= {pr1646v2ShEndPrH24PerfEntry 10}

pr1646v2ShEndPrH24PerfTableIx OBJECT-TYPE
   SYNTAX      TableIndex
   MAX-ACCESS  not-accessible
   STATUS      current
   DESCRIPTION
      ""
   ::= {pr1646v2ShEndPrH24PerfEntry 11}

pr1646v2ShEndPrH24PerfSysUpTime OBJECT-TYPE
   SYNTAX      TimeTicks
   MAX-ACCESS  read-only
   STATUS      current
   DESCRIPTION
      "Path: linePair.performance.h24Performance.sysUpTime

       Time in centi-second."
   ::= {pr1646v2ShEndPrH24PerfEntry 16777216}

pr1646v2ShEndPrH24PerfCViol OBJECT-TYPE
   SYNTAX      Counter32
   MAX-ACCESS  read-only
   STATUS      current
   DESCRIPTION
      "Path: linePair.performance.h24Performance.codeViolations

       32 bit unsigned wrappable counter."
   ::= {pr1646v2ShEndPrH24PerfEntry 33554432}

pr1646v2ShEndPrH24PerfErrSec OBJECT-TYPE
   SYNTAX      TimeTicks
   MAX-ACCESS  read-only
   STATUS      current
   DESCRIPTION
      "Path: linePair.performance.h24Performance.errSec

       Time in centi-second."
   ::= {pr1646v2ShEndPrH24PerfEntry 50331648}

pr1646v2ShEndPrH24PerfSevErrSec OBJECT-TYPE
   SYNTAX      TimeTicks
   MAX-ACCESS  read-only
   STATUS      current
   DESCRIPTION
      "Path: linePair.performance.h24Performance.sevErrSec

       Time in centi-second."
   ::= {pr1646v2ShEndPrH24PerfEntry 67108864}

pr1646v2ShEndPrH24PerfUnavSec OBJECT-TYPE
   SYNTAX      TimeTicks
   MAX-ACCESS  read-only
   STATUS      current
   DESCRIPTION
      "Path: linePair.performance.h24Performance.unavailSec

       Time in centi-second."
   ::= {pr1646v2ShEndPrH24PerfEntry 83886080}

pr1646v2ShEndPrH24PerfLoswSec OBJECT-TYPE
   SYNTAX      TimeTicks
   MAX-ACCESS  read-only
   STATUS      current
   DESCRIPTION
      "Path: linePair.performance.h24Performance.loswSec

       Time in centi-second."
   ::= {pr1646v2ShEndPrH24PerfEntry 100663296}

pr1646v2ShEndPrH24PerfMSec OBJECT-TYPE
   SYNTAX      TimeTicks
   MAX-ACCESS  read-only
   STATUS      current
   DESCRIPTION
      "Path: linePair.performance.h24Performance.moniSec

       Time in centi-second."
   ::= {pr1646v2ShEndPrH24PerfEntry 134217728}


pr1646v2ShEndPrD7Perf OBJECT IDENTIFIER ::= {pr1646v2ShEndPr 21}

pr1646v2ShEndPrD7PerfSSCTable OBJECT-TYPE
   SYNTAX      SEQUENCE OF Pr1646v2ShEndPrD7PerfEntry
   MAX-ACCESS  not-accessible
   STATUS      current
   DESCRIPTION
      "d7Performance"
   ::= {pr1646v2ShEndPrD7Perf 1}

pr1646v2ShEndPrD7PerfEntry OBJECT-TYPE
   SYNTAX      Pr1646v2ShEndPrD7PerfEntry
   MAX-ACCESS  not-accessible
   STATUS      current
   DESCRIPTION
      ""
   INDEX      { pr1646v2ShEndPrD7PerfGlobalIx,
                pr1646v2ShEndPrD7PerfTableIx }
   ::= {pr1646v2ShEndPrD7PerfSSCTable 1}

Pr1646v2ShEndPrD7PerfEntry ::=
   SEQUENCE
      {
      pr1646v2ShEndPrD7PerfGlobalIx
         GlobalIndex,
      pr1646v2ShEndPrD7PerfTableIx
         TableIndex,
      pr1646v2ShEndPrD7PerfSysUpTime
         TimeTicks,
      pr1646v2ShEndPrD7PerfCViol
         Counter32,
      pr1646v2ShEndPrD7PerfErrSec
         TimeTicks,
      pr1646v2ShEndPrD7PerfSevErrSec
         TimeTicks,
      pr1646v2ShEndPrD7PerfUnavSec
         TimeTicks,
      pr1646v2ShEndPrD7PerfLoswSec
         TimeTicks,
      pr1646v2ShEndPrD7PerfMSec
         TimeTicks
      }

pr1646v2ShEndPrD7PerfGlobalIx OBJECT-TYPE
   SYNTAX      GlobalIndex
   MAX-ACCESS  not-accessible
   STATUS      current
   DESCRIPTION
      "The value of the tlsCntTreeGlobalIndex of the MANAGED OBJECT."
   ::= {pr1646v2ShEndPrD7PerfEntry 10}

pr1646v2ShEndPrD7PerfTableIx OBJECT-TYPE
   SYNTAX      TableIndex
   MAX-ACCESS  not-accessible
   STATUS      current
   DESCRIPTION
      ""
   ::= {pr1646v2ShEndPrD7PerfEntry 11}

pr1646v2ShEndPrD7PerfSysUpTime OBJECT-TYPE
   SYNTAX      TimeTicks
   MAX-ACCESS  read-only
   STATUS      current
   DESCRIPTION
      "Path: linePair.performance.d7Performance.sysUpTime

       Time in centi-second."
   ::= {pr1646v2ShEndPrD7PerfEntry 16777216}

pr1646v2ShEndPrD7PerfCViol OBJECT-TYPE
   SYNTAX      Counter32
   MAX-ACCESS  read-only
   STATUS      current
   DESCRIPTION
      "Path: linePair.performance.d7Performance.codeViolations

       32 bit unsigned wrappable counter."
   ::= {pr1646v2ShEndPrD7PerfEntry 33554432}

pr1646v2ShEndPrD7PerfErrSec OBJECT-TYPE
   SYNTAX      TimeTicks
   MAX-ACCESS  read-only
   STATUS      current
   DESCRIPTION
      "Path: linePair.performance.d7Performance.errSec

       Time in centi-second."
   ::= {pr1646v2ShEndPrD7PerfEntry 50331648}

pr1646v2ShEndPrD7PerfSevErrSec OBJECT-TYPE
   SYNTAX      TimeTicks
   MAX-ACCESS  read-only
   STATUS      current
   DESCRIPTION
      "Path: linePair.performance.d7Performance.sevErrSec

       Time in centi-second."
   ::= {pr1646v2ShEndPrD7PerfEntry 67108864}

pr1646v2ShEndPrD7PerfUnavSec OBJECT-TYPE
   SYNTAX      TimeTicks
   MAX-ACCESS  read-only
   STATUS      current
   DESCRIPTION
      "Path: linePair.performance.d7Performance.unavailSec

       Time in centi-second."
   ::= {pr1646v2ShEndPrD7PerfEntry 83886080}

pr1646v2ShEndPrD7PerfLoswSec OBJECT-TYPE
   SYNTAX      TimeTicks
   MAX-ACCESS  read-only
   STATUS      current
   DESCRIPTION
      "Path: linePair.performance.d7Performance.loswSec

       Time in centi-second."
   ::= {pr1646v2ShEndPrD7PerfEntry 100663296}

pr1646v2ShEndPrD7PerfMSec OBJECT-TYPE
   SYNTAX      TimeTicks
   MAX-ACCESS  read-only
   STATUS      current
   DESCRIPTION
      "Path: linePair.performance.d7Performance.moniSec

       Time in centi-second."
   ::= {pr1646v2ShEndPrD7PerfEntry 134217728}


pr1646v2ShEndPrPerf OBJECT IDENTIFIER ::= {pr1646v2ShEndPr 26}

pr1646v2ShEndPrPerfSSCTable OBJECT-TYPE
   SYNTAX      SEQUENCE OF Pr1646v2ShEndPrPerfEntry
   MAX-ACCESS  not-accessible
   STATUS      current
   DESCRIPTION
      "linePerformance"
   ::= {pr1646v2ShEndPrPerf 1}

pr1646v2ShEndPrPerfEntry OBJECT-TYPE
   SYNTAX      Pr1646v2ShEndPrPerfEntry
   MAX-ACCESS  not-accessible
   STATUS      current
   DESCRIPTION
      ""
   INDEX      { pr1646v2ShEndPrPerfGlobalIx }
   ::= {pr1646v2ShEndPrPerfSSCTable 1}

Pr1646v2ShEndPrPerfEntry ::=
   SEQUENCE
      {
      pr1646v2ShEndPrPerfGlobalIx
         GlobalIndex,
      pr1646v2ShEndPrPerfCViol
         Counter32,
      pr1646v2ShEndPrPerfErrSec
         TimeTicks,
      pr1646v2ShEndPrPerfSevErrSec
         TimeTicks,
      pr1646v2ShEndPrPerfUnavSec
         TimeTicks,
      pr1646v2ShEndPrPerfLoswSec
         TimeTicks
      }

pr1646v2ShEndPrPerfGlobalIx OBJECT-TYPE
   SYNTAX      GlobalIndex
   MAX-ACCESS  not-accessible
   STATUS      current
   DESCRIPTION
      "The value of the tlsCntTreeGlobalIndex of the MANAGED OBJECT."
   ::= {pr1646v2ShEndPrPerfEntry 10}

pr1646v2ShEndPrPerfCViol OBJECT-TYPE
   SYNTAX      Counter32
   MAX-ACCESS  read-only
   STATUS      current
   DESCRIPTION
      "Path: linePair.performance.performance.codeViolations

       32 bit unsigned wrappable counter."
   ::= {pr1646v2ShEndPrPerfEntry 16777216}

pr1646v2ShEndPrPerfErrSec OBJECT-TYPE
   SYNTAX      TimeTicks
   MAX-ACCESS  read-only
   STATUS      current
   DESCRIPTION
      "Path: linePair.performance.performance.errSec

       Time in centi-second."
   ::= {pr1646v2ShEndPrPerfEntry 33554432}

pr1646v2ShEndPrPerfSevErrSec OBJECT-TYPE
   SYNTAX      TimeTicks
   MAX-ACCESS  read-only
   STATUS      current
   DESCRIPTION
      "Path: linePair.performance.performance.sevErrSec

       Time in centi-second."
   ::= {pr1646v2ShEndPrPerfEntry 50331648}

pr1646v2ShEndPrPerfUnavSec OBJECT-TYPE
   SYNTAX      TimeTicks
   MAX-ACCESS  read-only
   STATUS      current
   DESCRIPTION
      "Path: linePair.performance.performance.unavailSec

       Time in centi-second."
   ::= {pr1646v2ShEndPrPerfEntry 67108864}

pr1646v2ShEndPrPerfLoswSec OBJECT-TYPE
   SYNTAX      TimeTicks
   MAX-ACCESS  read-only
   STATUS      current
   DESCRIPTION
      "Path: linePair.performance.performance.loswSec

       Time in centi-second."
   ::= {pr1646v2ShEndPrPerfEntry 83886080}


pr1646v2ShEndPrH2Params OBJECT IDENTIFIER ::= {pr1646v2ShEndPr 11}

pr1646v2ShEndPrH2ParamsSSCTable OBJECT-TYPE
   SYNTAX      SEQUENCE OF Pr1646v2ShEndPrH2ParamsEntry
   MAX-ACCESS  not-accessible
   STATUS      current
   DESCRIPTION
      "h2LineParameters"
   ::= {pr1646v2ShEndPrH2Params 1}

pr1646v2ShEndPrH2ParamsEntry OBJECT-TYPE
   SYNTAX      Pr1646v2ShEndPrH2ParamsEntry
   MAX-ACCESS  not-accessible
   STATUS      current
   DESCRIPTION
      ""
   INDEX      { pr1646v2ShEndPrH2ParamsGlobalIx,
                pr1646v2ShEndPrH2ParamsTableIx }
   ::= {pr1646v2ShEndPrH2ParamsSSCTable 1}

Pr1646v2ShEndPrH2ParamsEntry ::=
   SEQUENCE
      {
      pr1646v2ShEndPrH2ParamsGlobalIx
         GlobalIndex,
      pr1646v2ShEndPrH2ParamsTableIx
         TableIndex,
      pr1646v2ShEndPrH2ParamsSysUpTime
         TimeTicks,
      pr1646v2ShEndPrH2ParamsLineAttMin
         Integer32,
      pr1646v2ShEndPrH2ParamsLineAttAvrg
         Integer32,
      pr1646v2ShEndPrH2ParamsLineAttMax
         Integer32,
      pr1646v2ShEndPrH2ParamsNmMin
         Integer32,
      pr1646v2ShEndPrH2ParamsNmAvrg
         Integer32,
      pr1646v2ShEndPrH2ParamsNmMax
         Integer32
      }

pr1646v2ShEndPrH2ParamsGlobalIx OBJECT-TYPE
   SYNTAX      GlobalIndex
   MAX-ACCESS  not-accessible
   STATUS      current
   DESCRIPTION
      "The value of the tlsCntTreeGlobalIndex of the MANAGED OBJECT."
   ::= {pr1646v2ShEndPrH2ParamsEntry 10}

pr1646v2ShEndPrH2ParamsTableIx OBJECT-TYPE
   SYNTAX      TableIndex
   MAX-ACCESS  not-accessible
   STATUS      current
   DESCRIPTION
      ""
   ::= {pr1646v2ShEndPrH2ParamsEntry 11}

pr1646v2ShEndPrH2ParamsSysUpTime OBJECT-TYPE
   SYNTAX      TimeTicks
   MAX-ACCESS  read-only
   STATUS      current
   DESCRIPTION
      "Path: linePair.performance.h2LineParameters.sysUpTime

       Time in centi-second."
   ::= {pr1646v2ShEndPrH2ParamsEntry 16777216}

pr1646v2ShEndPrH2ParamsLineAttMin OBJECT-TYPE
   SYNTAX      Integer32
   MAX-ACCESS  read-only
   STATUS      current
   DESCRIPTION
      "Path: linePair.performance.h2LineParameters.lineAttenuationMin

       unit name = dB
       formula = 10 / ; 10 *"
   ::= {pr1646v2ShEndPrH2ParamsEntry 33554432}

pr1646v2ShEndPrH2ParamsLineAttAvrg OBJECT-TYPE
   SYNTAX      Integer32
   MAX-ACCESS  read-only
   STATUS      current
   DESCRIPTION
      "Path: linePair.performance.h2LineParameters.lineAttenuationAvrg

       unit name = dB
       formula = 10 / ; 10 *"
   ::= {pr1646v2ShEndPrH2ParamsEntry 50331648}

pr1646v2ShEndPrH2ParamsLineAttMax OBJECT-TYPE
   SYNTAX      Integer32
   MAX-ACCESS  read-only
   STATUS      current
   DESCRIPTION
      "Path: linePair.performance.h2LineParameters.lineAttenuationMax

       unit name = dB
       formula = 10 / ; 10 *"
   ::= {pr1646v2ShEndPrH2ParamsEntry 67108864}

pr1646v2ShEndPrH2ParamsNmMin OBJECT-TYPE
   SYNTAX      Integer32
   MAX-ACCESS  read-only
   STATUS      current
   DESCRIPTION
      "Path: linePair.performance.h2LineParameters.noiseMarginMin

       unit name = dB
       formula = 10 / ; 10 *"
   ::= {pr1646v2ShEndPrH2ParamsEntry 83886080}

pr1646v2ShEndPrH2ParamsNmAvrg OBJECT-TYPE
   SYNTAX      Integer32
   MAX-ACCESS  read-only
   STATUS      current
   DESCRIPTION
      "Path: linePair.performance.h2LineParameters.noiseMarginAvrg

       unit name = dB
       formula = 10 / ; 10 *"
   ::= {pr1646v2ShEndPrH2ParamsEntry 100663296}

pr1646v2ShEndPrH2ParamsNmMax OBJECT-TYPE
   SYNTAX      Integer32
   MAX-ACCESS  read-only
   STATUS      current
   DESCRIPTION
      "Path: linePair.performance.h2LineParameters.noiseMarginMax

       unit name = dB
       formula = 10 / ; 10 *"
   ::= {pr1646v2ShEndPrH2ParamsEntry 117440512}


pr1646v2ShEndPrH24Params OBJECT IDENTIFIER ::= {pr1646v2ShEndPr 14}

pr1646v2ShEndPrH24ParamsSSCTable OBJECT-TYPE
   SYNTAX      SEQUENCE OF Pr1646v2ShEndPrH24ParamsEntry
   MAX-ACCESS  not-accessible
   STATUS      current
   DESCRIPTION
      "h24LineParameters"
   ::= {pr1646v2ShEndPrH24Params 1}

pr1646v2ShEndPrH24ParamsEntry OBJECT-TYPE
   SYNTAX      Pr1646v2ShEndPrH24ParamsEntry
   MAX-ACCESS  not-accessible
   STATUS      current
   DESCRIPTION
      ""
   INDEX      { pr1646v2ShEndPrH24ParamsGlobalIx,
                pr1646v2ShEndPrH24ParamsTableIx }
   ::= {pr1646v2ShEndPrH24ParamsSSCTable 1}

Pr1646v2ShEndPrH24ParamsEntry ::=
   SEQUENCE
      {
      pr1646v2ShEndPrH24ParamsGlobalIx
         GlobalIndex,
      pr1646v2ShEndPrH24ParamsTableIx
         TableIndex,
      pr1646v2ShEndPrH24ParamsSysUpTime
         TimeTicks,
      pr1646v2ShEndPrH24ParamsLineAttMin
         Integer32,
      pr1646v2ShEndPrH24ParamsLineAttAvrg
         Integer32,
      pr1646v2ShEndPrH24ParamsLineAttMax
         Integer32,
      pr1646v2ShEndPrH24ParamsNmMin
         Integer32,
      pr1646v2ShEndPrH24ParamsNmAvrg
         Integer32,
      pr1646v2ShEndPrH24ParamsNmMax
         Integer32
      }

pr1646v2ShEndPrH24ParamsGlobalIx OBJECT-TYPE
   SYNTAX      GlobalIndex
   MAX-ACCESS  not-accessible
   STATUS      current
   DESCRIPTION
      "The value of the tlsCntTreeGlobalIndex of the MANAGED OBJECT."
   ::= {pr1646v2ShEndPrH24ParamsEntry 10}

pr1646v2ShEndPrH24ParamsTableIx OBJECT-TYPE
   SYNTAX      TableIndex
   MAX-ACCESS  not-accessible
   STATUS      current
   DESCRIPTION
      ""
   ::= {pr1646v2ShEndPrH24ParamsEntry 11}

pr1646v2ShEndPrH24ParamsSysUpTime OBJECT-TYPE
   SYNTAX      TimeTicks
   MAX-ACCESS  read-only
   STATUS      current
   DESCRIPTION
      "Path: linePair.performance.h24LineParameters.sysUpTime

       Time in centi-second."
   ::= {pr1646v2ShEndPrH24ParamsEntry 16777216}

pr1646v2ShEndPrH24ParamsLineAttMin OBJECT-TYPE
   SYNTAX      Integer32
   MAX-ACCESS  read-only
   STATUS      current
   DESCRIPTION
      "Path: linePair.performance.h24LineParameters.lineAttenuationMin

       unit name = dB
       formula = 10 / ; 10 *"
   ::= {pr1646v2ShEndPrH24ParamsEntry 33554432}

pr1646v2ShEndPrH24ParamsLineAttAvrg OBJECT-TYPE
   SYNTAX      Integer32
   MAX-ACCESS  read-only
   STATUS      current
   DESCRIPTION
      "Path: linePair.performance.h24LineParameters.lineAttenuationAvrg

       unit name = dB
       formula = 10 / ; 10 *"
   ::= {pr1646v2ShEndPrH24ParamsEntry 50331648}

pr1646v2ShEndPrH24ParamsLineAttMax OBJECT-TYPE
   SYNTAX      Integer32
   MAX-ACCESS  read-only
   STATUS      current
   DESCRIPTION
      "Path: linePair.performance.h24LineParameters.lineAttenuationMax

       unit name = dB
       formula = 10 / ; 10 *"
   ::= {pr1646v2ShEndPrH24ParamsEntry 67108864}

pr1646v2ShEndPrH24ParamsNmMin OBJECT-TYPE
   SYNTAX      Integer32
   MAX-ACCESS  read-only
   STATUS      current
   DESCRIPTION
      "Path: linePair.performance.h24LineParameters.noiseMarginMin

       unit name = dB
       formula = 10 / ; 10 *"
   ::= {pr1646v2ShEndPrH24ParamsEntry 83886080}

pr1646v2ShEndPrH24ParamsNmAvrg OBJECT-TYPE
   SYNTAX      Integer32
   MAX-ACCESS  read-only
   STATUS      current
   DESCRIPTION
      "Path: linePair.performance.h24LineParameters.noiseMarginAvrg

       unit name = dB
       formula = 10 / ; 10 *"
   ::= {pr1646v2ShEndPrH24ParamsEntry 100663296}

pr1646v2ShEndPrH24ParamsNmMax OBJECT-TYPE
   SYNTAX      Integer32
   MAX-ACCESS  read-only
   STATUS      current
   DESCRIPTION
      "Path: linePair.performance.h24LineParameters.noiseMarginMax

       unit name = dB
       formula = 10 / ; 10 *"
   ::= {pr1646v2ShEndPrH24ParamsEntry 117440512}


pr1646v2ShEndPrD7Params OBJECT IDENTIFIER ::= {pr1646v2ShEndPr 17}

pr1646v2ShEndPrD7ParamsSSCTable OBJECT-TYPE
   SYNTAX      SEQUENCE OF Pr1646v2ShEndPrD7ParamsEntry
   MAX-ACCESS  not-accessible
   STATUS      current
   DESCRIPTION
      "d7LineParameters"
   ::= {pr1646v2ShEndPrD7Params 1}

pr1646v2ShEndPrD7ParamsEntry OBJECT-TYPE
   SYNTAX      Pr1646v2ShEndPrD7ParamsEntry
   MAX-ACCESS  not-accessible
   STATUS      current
   DESCRIPTION
      ""
   INDEX      { pr1646v2ShEndPrD7ParamsGlobalIx,
                pr1646v2ShEndPrD7ParamsTableIx }
   ::= {pr1646v2ShEndPrD7ParamsSSCTable 1}

Pr1646v2ShEndPrD7ParamsEntry ::=
   SEQUENCE
      {
      pr1646v2ShEndPrD7ParamsGlobalIx
         GlobalIndex,
      pr1646v2ShEndPrD7ParamsTableIx
         TableIndex,
      pr1646v2ShEndPrD7ParamsSysUpTime
         TimeTicks,
      pr1646v2ShEndPrD7ParamsLineAttMin
         Integer32,
      pr1646v2ShEndPrD7ParamsLineAttAvrg
         Integer32,
      pr1646v2ShEndPrD7ParamsLineAttMax
         Integer32,
      pr1646v2ShEndPrD7ParamsNmMin
         Integer32,
      pr1646v2ShEndPrD7ParamsNmAvrg
         Integer32,
      pr1646v2ShEndPrD7ParamsNmMax
         Integer32
      }

pr1646v2ShEndPrD7ParamsGlobalIx OBJECT-TYPE
   SYNTAX      GlobalIndex
   MAX-ACCESS  not-accessible
   STATUS      current
   DESCRIPTION
      "The value of the tlsCntTreeGlobalIndex of the MANAGED OBJECT."
   ::= {pr1646v2ShEndPrD7ParamsEntry 10}

pr1646v2ShEndPrD7ParamsTableIx OBJECT-TYPE
   SYNTAX      TableIndex
   MAX-ACCESS  not-accessible
   STATUS      current
   DESCRIPTION
      ""
   ::= {pr1646v2ShEndPrD7ParamsEntry 11}

pr1646v2ShEndPrD7ParamsSysUpTime OBJECT-TYPE
   SYNTAX      TimeTicks
   MAX-ACCESS  read-only
   STATUS      current
   DESCRIPTION
      "Path: linePair.performance.d7LineParameters.sysUpTime

       Time in centi-second."
   ::= {pr1646v2ShEndPrD7ParamsEntry 16777216}

pr1646v2ShEndPrD7ParamsLineAttMin OBJECT-TYPE
   SYNTAX      Integer32
   MAX-ACCESS  read-only
   STATUS      current
   DESCRIPTION
      "Path: linePair.performance.d7LineParameters.lineAttenuationMin

       unit name = dB
       formula = 10 / ; 10 *"
   ::= {pr1646v2ShEndPrD7ParamsEntry 33554432}

pr1646v2ShEndPrD7ParamsLineAttAvrg OBJECT-TYPE
   SYNTAX      Integer32
   MAX-ACCESS  read-only
   STATUS      current
   DESCRIPTION
      "Path: linePair.performance.d7LineParameters.lineAttenuationAvrg

       unit name = dB
       formula = 10 / ; 10 *"
   ::= {pr1646v2ShEndPrD7ParamsEntry 50331648}

pr1646v2ShEndPrD7ParamsLineAttMax OBJECT-TYPE
   SYNTAX      Integer32
   MAX-ACCESS  read-only
   STATUS      current
   DESCRIPTION
      "Path: linePair.performance.d7LineParameters.lineAttenuationMax

       unit name = dB
       formula = 10 / ; 10 *"
   ::= {pr1646v2ShEndPrD7ParamsEntry 67108864}

pr1646v2ShEndPrD7ParamsNmMin OBJECT-TYPE
   SYNTAX      Integer32
   MAX-ACCESS  read-only
   STATUS      current
   DESCRIPTION
      "Path: linePair.performance.d7LineParameters.noiseMarginMin

       unit name = dB
       formula = 10 / ; 10 *"
   ::= {pr1646v2ShEndPrD7ParamsEntry 83886080}

pr1646v2ShEndPrD7ParamsNmAvrg OBJECT-TYPE
   SYNTAX      Integer32
   MAX-ACCESS  read-only
   STATUS      current
   DESCRIPTION
      "Path: linePair.performance.d7LineParameters.noiseMarginAvrg

       unit name = dB
       formula = 10 / ; 10 *"
   ::= {pr1646v2ShEndPrD7ParamsEntry 100663296}

pr1646v2ShEndPrD7ParamsNmMax OBJECT-TYPE
   SYNTAX      Integer32
   MAX-ACCESS  read-only
   STATUS      current
   DESCRIPTION
      "Path: linePair.performance.d7LineParameters.noiseMarginMax

       unit name = dB
       formula = 10 / ; 10 *"
   ::= {pr1646v2ShEndPrD7ParamsEntry 117440512}


pr1646v2ShEndPrParams OBJECT IDENTIFIER ::= {pr1646v2ShEndPr 22}

pr1646v2ShEndPrParamsSSCTable OBJECT-TYPE
   SYNTAX      SEQUENCE OF Pr1646v2ShEndPrParamsEntry
   MAX-ACCESS  not-accessible
   STATUS      current
   DESCRIPTION
      "lineParameters"
   ::= {pr1646v2ShEndPrParams 1}

pr1646v2ShEndPrParamsEntry OBJECT-TYPE
   SYNTAX      Pr1646v2ShEndPrParamsEntry
   MAX-ACCESS  not-accessible
   STATUS      current
   DESCRIPTION
      ""
   INDEX      { pr1646v2ShEndPrParamsGlobalIx }
   ::= {pr1646v2ShEndPrParamsSSCTable 1}

Pr1646v2ShEndPrParamsEntry ::=
   SEQUENCE
      {
      pr1646v2ShEndPrParamsGlobalIx
         GlobalIndex,
      pr1646v2ShEndPrParamsLineAtt
         Integer32,
      pr1646v2ShEndPrParamsNm
         Integer32
      }

pr1646v2ShEndPrParamsGlobalIx OBJECT-TYPE
   SYNTAX      GlobalIndex
   MAX-ACCESS  not-accessible
   STATUS      current
   DESCRIPTION
      "The value of the tlsCntTreeGlobalIndex of the MANAGED OBJECT."
   ::= {pr1646v2ShEndPrParamsEntry 10}

pr1646v2ShEndPrParamsLineAtt OBJECT-TYPE
   SYNTAX      Integer32
   MAX-ACCESS  read-only
   STATUS      current
   DESCRIPTION
      "Path: linePair.performance.lineParameters.lineAttenuation

       unit name = dB
       formula = 10 / ; 10 *"
   ::= {pr1646v2ShEndPrParamsEntry 16777216}

pr1646v2ShEndPrParamsNm OBJECT-TYPE
   SYNTAX      Integer32
   MAX-ACCESS  read-only
   STATUS      current
   DESCRIPTION
      "Path: linePair.performance.lineParameters.noiseMargin

       unit name = dB
       formula = 10 / ; 10 *"
   ::= {pr1646v2ShEndPrParamsEntry 33554432}



ar1646v2ShEndPr OBJECT IDENTIFIER ::= {r1646v2ShEndPr 16}


ar1646v2ShEndPrClearCounters OBJECT IDENTIFIER ::= {ar1646v2ShEndPr 263}

ar1646v2ShEndPrClearCountersTable OBJECT-TYPE
   SYNTAX      SEQUENCE OF Ar1646v2ShEndPrClearCountersEntry
   MAX-ACCESS  not-accessible
   STATUS      current
   DESCRIPTION
      "reset counters"
   ::= {ar1646v2ShEndPrClearCounters 1}

ar1646v2ShEndPrClearCountersEntry OBJECT-TYPE
   SYNTAX      Ar1646v2ShEndPrClearCountersEntry
   MAX-ACCESS  not-accessible
   STATUS      current
   DESCRIPTION
      ""
   INDEX      { ar1646v2ShEndPrClearCountersGlobalIx }
   ::= {ar1646v2ShEndPrClearCountersTable 1}

Ar1646v2ShEndPrClearCountersEntry ::=
   SEQUENCE
      {
      ar1646v2ShEndPrClearCountersGlobalIx
         GlobalIndex,
      ar1646v2ShEndPrClearCountersValue
         Integer32
      }

ar1646v2ShEndPrClearCountersGlobalIx OBJECT-TYPE
   SYNTAX      GlobalIndex
   MAX-ACCESS  not-accessible
   STATUS      current
   DESCRIPTION
      "The value of the tlsCntTreeGlobalIndex of the MANAGED OBJECT."
   ::= {ar1646v2ShEndPrClearCountersEntry 10}

ar1646v2ShEndPrClearCountersValue OBJECT-TYPE
   SYNTAX      Integer32
   MAX-ACCESS  read-write
   STATUS      current
   DESCRIPTION
      "Path: linePair.actions.clearCounters"
   ::= {ar1646v2ShEndPrClearCountersEntry 2147483648}



fr1646v2ShEndPr OBJECT IDENTIFIER ::= {r1646v2ShEndPr 13}


fr1646v2ShEndPrAlInfo OBJECT IDENTIFIER ::= {fr1646v2ShEndPr 202}

fr1646v2ShEndPrAlInfoSSCTable OBJECT-TYPE
   SYNTAX      SEQUENCE OF Fr1646v2ShEndPrAlInfoEntry
   MAX-ACCESS  not-accessible
   STATUS      current
   DESCRIPTION
      "linePairAlarmInfo"
   ::= {fr1646v2ShEndPrAlInfo 1}

fr1646v2ShEndPrAlInfoEntry OBJECT-TYPE
   SYNTAX      Fr1646v2ShEndPrAlInfoEntry
   MAX-ACCESS  not-accessible
   STATUS      current
   DESCRIPTION
      ""
   INDEX      { fr1646v2ShEndPrAlInfoGlobalIx }
   ::= {fr1646v2ShEndPrAlInfoSSCTable 1}

Fr1646v2ShEndPrAlInfoEntry ::=
   SEQUENCE
      {
      fr1646v2ShEndPrAlInfoGlobalIx
         GlobalIndex,
      fr1646v2ShEndPrAlInfoDiscr
         Integer32,
      fr1646v2ShEndPrAlInfoCurrAlms
         Integer32,
      fr1646v2ShEndPrAlInfoPrevAlms
         Integer32,
      fr1646v2ShEndPrAlInfoAlMask
         Integer32,
      fr1646v2ShEndPrAlInfoAlLvlLpatt
         Integer32,
      fr1646v2ShEndPrAlInfoAlLvlNm
         Integer32,
      fr1646v2ShEndPrAlInfoAlLvlEsrExc
         Integer32,
      fr1646v2ShEndPrAlInfoAlLvlSesrExc
         Integer32,
      fr1646v2ShEndPrAlInfoAlLvlBberExc
         Integer32
      }

fr1646v2ShEndPrAlInfoGlobalIx OBJECT-TYPE
   SYNTAX      GlobalIndex
   MAX-ACCESS  not-accessible
   STATUS      current
   DESCRIPTION
      "The value of the tlsCntTreeGlobalIndex of the MANAGED OBJECT."
   ::= {fr1646v2ShEndPrAlInfoEntry 10}

fr1646v2ShEndPrAlInfoDiscr OBJECT-TYPE
   SYNTAX      Integer32
   MAX-ACCESS  read-only
   STATUS      current
   DESCRIPTION
      "Path: linePair.alarms.alarmInfo.discriminator"
   ::= {fr1646v2ShEndPrAlInfoEntry 16777216}

fr1646v2ShEndPrAlInfoCurrAlms OBJECT-TYPE
   SYNTAX      Integer32
   MAX-ACCESS  read-only
   STATUS      current
   DESCRIPTION
      "Path: linePair.alarms.alarmInfo.currentAlarms

       Bit meanings:
               bit 1 = lineAttenuation,
               bit 2 = noiseMargin,
               bit 3 = errSecRatioExceeded,
               bit 4 = sevErrSecRatioExceeded,
               bit 5 = bBErrRatioExceeded"
   ::= {fr1646v2ShEndPrAlInfoEntry 33554432}

fr1646v2ShEndPrAlInfoPrevAlms OBJECT-TYPE
   SYNTAX      Integer32
   MAX-ACCESS  read-only
   STATUS      current
   DESCRIPTION
      "Path: linePair.alarms.alarmInfo.previousAlarms

       Bit meanings:
               bit 1 = lineAttenuation,
               bit 2 = noiseMargin,
               bit 3 = errSecRatioExceeded,
               bit 4 = sevErrSecRatioExceeded,
               bit 5 = bBErrRatioExceeded"
   ::= {fr1646v2ShEndPrAlInfoEntry 50331648}

fr1646v2ShEndPrAlInfoAlMask OBJECT-TYPE
   SYNTAX      Integer32
   MAX-ACCESS  read-only
   STATUS      current
   DESCRIPTION
      "Path: linePair.alarms.alarmInfo.alarmMask

       Bit meanings:
               bit 1 = lineAttenuation,
               bit 2 = noiseMargin,
               bit 3 = errSecRatioExceeded,
               bit 4 = sevErrSecRatioExceeded,
               bit 5 = bBErrRatioExceeded"
   ::= {fr1646v2ShEndPrAlInfoEntry 67108864}

fr1646v2ShEndPrAlInfoAlLvlLpatt OBJECT-TYPE
   SYNTAX      Integer32
   MAX-ACCESS  read-only
   STATUS      current
   DESCRIPTION
      "Path: linePair.alarms.alarmInfo.alarmLevel.lineAttenuation"
   ::= {fr1646v2ShEndPrAlInfoEntry 84017152}

fr1646v2ShEndPrAlInfoAlLvlNm OBJECT-TYPE
   SYNTAX      Integer32
   MAX-ACCESS  read-only
   STATUS      current
   DESCRIPTION
      "Path: linePair.alarms.alarmInfo.alarmLevel.noiseMargin"
   ::= {fr1646v2ShEndPrAlInfoEntry 84082688}

fr1646v2ShEndPrAlInfoAlLvlEsrExc OBJECT-TYPE
   SYNTAX      Integer32
   MAX-ACCESS  read-only
   STATUS      current
   DESCRIPTION
      "Path: linePair.alarms.alarmInfo.alarmLevel.errSecRatioExceeded"
   ::= {fr1646v2ShEndPrAlInfoEntry 84148224}

fr1646v2ShEndPrAlInfoAlLvlSesrExc OBJECT-TYPE
   SYNTAX      Integer32
   MAX-ACCESS  read-only
   STATUS      current
   DESCRIPTION
      "Path: linePair.alarms.alarmInfo.alarmLevel.sevErrSecRatioExceeded"
   ::= {fr1646v2ShEndPrAlInfoEntry 84213760}

fr1646v2ShEndPrAlInfoAlLvlBberExc OBJECT-TYPE
   SYNTAX      Integer32
   MAX-ACCESS  read-only
   STATUS      current
   DESCRIPTION
      "Path: linePair.alarms.alarmInfo.alarmLevel.bBErrRatioExceeded"
   ::= {fr1646v2ShEndPrAlInfoEntry 84279296}


fr1646v2ShEndPrAlInfoE2 OBJECT IDENTIFIER ::= {fr1646v2ShEndPrAlInfo 2}

fr1646v2ShEndPrAlInfoE2Entry OBJECT IDENTIFIER ::= {fr1646v2ShEndPrAlInfoE2 1}

fr1646v2ShEndPrAlInfoE2Lpatt OBJECT IDENTIFIER ::= {fr1646v2ShEndPrAlInfoE2Entry 11}

fr1646v2ShEndPrAlInfoE2LpattPfx OBJECT IDENTIFIER ::= {fr1646v2ShEndPrAlInfoE2Lpatt 0}

fr1646v2ShEndPrAlInfoE2LpattOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'lineAttenuation'
                representing an alarm condition in the alarm word
                of attribute 'alarmInfo' of managed object 'shdslEndPairNm'
                (root='router1646') has changed from the ON to the OFF state."
   ::= {fr1646v2ShEndPrAlInfoE2LpattPfx 1}

fr1646v2ShEndPrAlInfoE2LpattOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'lineAttenuation'
                representing an alarm condition in the alarm word
                of attribute 'alarmInfo' of managed object 'shdslEndPairNm'
                (root='router1646') has changed from the OFF to the ON state."
   ::= {fr1646v2ShEndPrAlInfoE2LpattPfx 2}

fr1646v2ShEndPrAlInfoE2Nm OBJECT IDENTIFIER ::= {fr1646v2ShEndPrAlInfoE2Entry 12}

fr1646v2ShEndPrAlInfoE2NmPfx OBJECT IDENTIFIER ::= {fr1646v2ShEndPrAlInfoE2Nm 0}

fr1646v2ShEndPrAlInfoE2NmOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'noiseMargin'
                representing an alarm condition in the alarm word
                of attribute 'alarmInfo' of managed object 'shdslEndPairNm'
                (root='router1646') has changed from the ON to the OFF state."
   ::= {fr1646v2ShEndPrAlInfoE2NmPfx 1}

fr1646v2ShEndPrAlInfoE2NmOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'noiseMargin'
                representing an alarm condition in the alarm word
                of attribute 'alarmInfo' of managed object 'shdslEndPairNm'
                (root='router1646') has changed from the OFF to the ON state."
   ::= {fr1646v2ShEndPrAlInfoE2NmPfx 2}

fr1646v2ShEndPrAlInfoE2EsrExc OBJECT IDENTIFIER ::= {fr1646v2ShEndPrAlInfoE2Entry 13}

fr1646v2ShEndPrAlInfoE2EsrExcPfx OBJECT IDENTIFIER ::= {fr1646v2ShEndPrAlInfoE2EsrExc 0}

fr1646v2ShEndPrAlInfoE2EsrExcOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'errSecRatioExceeded'
                representing an alarm condition in the alarm word
                of attribute 'alarmInfo' of managed object 'shdslEndPairNm'
                (root='router1646') has changed from the ON to the OFF state."
   ::= {fr1646v2ShEndPrAlInfoE2EsrExcPfx 1}

fr1646v2ShEndPrAlInfoE2EsrExcOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'errSecRatioExceeded'
                representing an alarm condition in the alarm word
                of attribute 'alarmInfo' of managed object 'shdslEndPairNm'
                (root='router1646') has changed from the OFF to the ON state."
   ::= {fr1646v2ShEndPrAlInfoE2EsrExcPfx 2}

fr1646v2ShEndPrAlInfoE2SesrExc OBJECT IDENTIFIER ::= {fr1646v2ShEndPrAlInfoE2Entry 14}

fr1646v2ShEndPrAlInfoE2SesrExcPfx OBJECT IDENTIFIER ::= {fr1646v2ShEndPrAlInfoE2SesrExc 0}

fr1646v2ShEndPrAlInfoE2SesrExcOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'sevErrSecRatioExceeded'
                representing an alarm condition in the alarm word
                of attribute 'alarmInfo' of managed object 'shdslEndPairNm'
                (root='router1646') has changed from the ON to the OFF state."
   ::= {fr1646v2ShEndPrAlInfoE2SesrExcPfx 1}

fr1646v2ShEndPrAlInfoE2SesrExcOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'sevErrSecRatioExceeded'
                representing an alarm condition in the alarm word
                of attribute 'alarmInfo' of managed object 'shdslEndPairNm'
                (root='router1646') has changed from the OFF to the ON state."
   ::= {fr1646v2ShEndPrAlInfoE2SesrExcPfx 2}

fr1646v2ShEndPrAlInfoE2BberExc OBJECT IDENTIFIER ::= {fr1646v2ShEndPrAlInfoE2Entry 15}

fr1646v2ShEndPrAlInfoE2BberExcPfx OBJECT IDENTIFIER ::= {fr1646v2ShEndPrAlInfoE2BberExc 0}

fr1646v2ShEndPrAlInfoE2BberExcOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'bBErrRatioExceeded'
                representing an alarm condition in the alarm word
                of attribute 'alarmInfo' of managed object 'shdslEndPairNm'
                (root='router1646') has changed from the ON to the OFF state."
   ::= {fr1646v2ShEndPrAlInfoE2BberExcPfx 1}

fr1646v2ShEndPrAlInfoE2BberExcOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'bBErrRatioExceeded'
                representing an alarm condition in the alarm word
                of attribute 'alarmInfo' of managed object 'shdslEndPairNm'
                (root='router1646') has changed from the OFF to the ON state."
   ::= {fr1646v2ShEndPrAlInfoE2BberExcPfx 2}



END
