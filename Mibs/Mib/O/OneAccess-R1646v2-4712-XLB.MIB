OneAccess-R1646v2-4712-XLB DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1646Rootv2 MODULE-IDENTITY
   LAST-UPDATED "202107151728Z"
   ORGANIZATION "OneAccess"
   CONTACT-INFO "http://www.oneaccess-net.com/telindus/"
   DESCRIPTION
      "..."
   ::= {telindus 1132}




r1646v2XLB OBJECT IDENTIFIER ::= {r1646Rootv2 4712}

r1646v2XLBMOProp OBJECT IDENTIFIER ::= {r1646v2XLB 1}

r1646v2XLBMOPropEntry OBJECT IDENTIFIER ::= {r1646v2XLBMOProp 1}

r1646v2XLBMOPropPath OBJECT-TYPE
   SYNTAX      ContainmentPath
   MAX-ACCESS  read-only
   STATUS      current
   DESCRIPTION
      "Textual description of the containment tree from the instance of
       the root object down to the instance of the current object."
   ::= {r1646v2XLBMOPropEntry 3}

r1646v2XLBMOPropRev OBJECT-TYPE
   SYNTAX      ObjectRevision
   MAX-ACCESS  read-only
   STATUS      current
   DESCRIPTION
      "This value corresponds with the revision of the MANAGED OBJECT."
   ::= {r1646v2XLBMOPropEntry 4}



er1646v2XLB OBJECT IDENTIFIER ::= {r1646v2XLB 11}


er1646v2XLBPowerManagementControl OBJECT-TYPE
   SYNTAX      INTEGER
               {
               g997mpmsmL0 (0),
               g997mpmsmL3 (3)
               }
   MAX-ACCESS  read-write
   STATUS      current
   DESCRIPTION
      "Path: line.editConf.powerManagementControl
       Info: Power Management Control

       Possibilities:
               g997-pms-L0   (0)
               g997-pms-L3   (3)"
   ::= {er1646v2XLB 2}


er1646v2XLBLinAlmMsk OBJECT-TYPE
   SYNTAX      Integer32
   MAX-ACCESS  read-write
   STATUS      current
   DESCRIPTION
      "Path: line.editConf.alarmMask
       Info: lineAlarmMask

       Bit meanings:
               bit 0 = linkDown"
   ::= {er1646v2XLB 70}


er1646v2XLBLinAlmLev OBJECT IDENTIFIER ::= {er1646v2XLB 71}

er1646v2XLBLinAlmLevSSC OBJECT IDENTIFIER ::= {er1646v2XLBLinAlmLev 1}

er1646v2XLBLinAlmLevEntry OBJECT IDENTIFIER ::= {er1646v2XLBLinAlmLevSSC 1}

er1646v2XLBLinAlmLevLnkDwn OBJECT-TYPE
   SYNTAX      Integer32
   MAX-ACCESS  read-write
   STATUS      current
   DESCRIPTION
      "Path: line.editConf.alarmLevel.linkDown"
   ::= {er1646v2XLBLinAlmLevEntry 16777216}


er1646v2XLBFirmwareAlt OBJECT-TYPE
   SYNTAX      INTEGER
               {
               latest (0)
               }
   MAX-ACCESS  read-write
   STATUS      current
   DESCRIPTION
      "Path: line.editConf.firmwareAlt
       Info: To select an alternative bitpump DSP firmware

       Possibilities:
               latest   (0)"
   ::= {er1646v2XLB 717}


er1646v2XLBSubCarriersInfo OBJECT-TYPE
   SYNTAX      INTEGER
               {
               invisible (1),
               visible (2)
               }
   MAX-ACCESS  read-write
   STATUS      current
   DESCRIPTION
      "Path: line.editConf.subCarriersInfo
       Info: subcarrier info

       Possibilities:
               invisible   (1)
               visible   (2)"
   ::= {er1646v2XLB 720}


er1646v2XLBHsCarrierSet OBJECT IDENTIFIER ::= {er1646v2XLB 724}

er1646v2XLBHsCarrierSetSSC OBJECT IDENTIFIER ::= {er1646v2XLBHsCarrierSet 1}

er1646v2XLBHsCarrierSetEntry OBJECT IDENTIFIER ::= {er1646v2XLBHsCarrierSetSSC 1}

er1646v2XLBHsCarrierSetAuto OBJECT-TYPE
   SYNTAX      OCTET STRING
   MAX-ACCESS  read-write
   STATUS      current
   DESCRIPTION
      "Path: line.editConf.hsCarrierSet.auto"
   ::= {er1646v2XLBHsCarrierSetEntry 16777216}

er1646v2XLBHsCarrierSetDisable OBJECT-TYPE
   SYNTAX      Integer32
   MAX-ACCESS  read-write
   STATUS      current
   DESCRIPTION
      "Path: line.editConf.hsCarrierSet.disable

       Bit meanings:
               bit 0 = B43,
               bit 1 = A43,
               bit 2 = V43,
               bit 5 = C43,
               bit 6 = J43,
               bit 7 = B43C,
               bit 8 = A43C"
   ::= {er1646v2XLBHsCarrierSetEntry 33554432}


er1646v2XLBAdslInteropCmds OBJECT IDENTIFIER ::= {er1646v2XLB 726}

er1646v2XLBAdslInteropCmdsSSCTable OBJECT-TYPE
   SYNTAX      SEQUENCE OF Er1646v2XLBAdslInteropCmdsEntry
   MAX-ACCESS  not-accessible
   STATUS      current
   DESCRIPTION
      "to set the interop commands manually"
   ::= {er1646v2XLBAdslInteropCmds 1}

er1646v2XLBAdslInteropCmdsEntry OBJECT-TYPE
   SYNTAX      Er1646v2XLBAdslInteropCmdsEntry
   MAX-ACCESS  not-accessible
   STATUS      current
   DESCRIPTION
      ""
   INDEX      { er1646v2XLBAdslInteropCmdsTableIx }
   ::= {er1646v2XLBAdslInteropCmdsSSCTable 1}

Er1646v2XLBAdslInteropCmdsEntry ::=
   SEQUENCE
      {
      er1646v2XLBAdslInteropCmdsActions
         VariableLengthTableActions,
      er1646v2XLBAdslInteropCmdsTableIx
         TableIndex,
      er1646v2XLBAdslInteropCmdsSection
         INTEGER,
      er1646v2XLBAdslInteropCmdsCommand
         DisplayString
      }

er1646v2XLBAdslInteropCmdsActions OBJECT-TYPE
   SYNTAX      VariableLengthTableActions
   MAX-ACCESS  read-write
   STATUS      current
   DESCRIPTION
      "By way of this field, some manipulations
       on this table may be performed."
   ::= {er1646v2XLBAdslInteropCmdsEntry 2}

er1646v2XLBAdslInteropCmdsTableIx OBJECT-TYPE
   SYNTAX      TableIndex
   MAX-ACCESS  not-accessible
   STATUS      current
   DESCRIPTION
      ""
   ::= {er1646v2XLBAdslInteropCmdsEntry 11}

er1646v2XLBAdslInteropCmdsSection OBJECT-TYPE
   SYNTAX      INTEGER
               {
               waitForConfiguration (0),
               waitForLinkActivate (1)
               }
   MAX-ACCESS  read-write
   STATUS      current
   DESCRIPTION
      "Path: line.editConf.adslInteropCmds.section

       Possibilities:
               waitForConfiguration   (0)
               waitForLinkActivate   (1)"
   ::= {er1646v2XLBAdslInteropCmdsEntry 16777216}

er1646v2XLBAdslInteropCmdsCommand OBJECT-TYPE
   SYNTAX      DisplayString
   MAX-ACCESS  read-write
   STATUS      current
   DESCRIPTION
      "Path: line.editConf.adslInteropCmds.command"
   ::= {er1646v2XLBAdslInteropCmdsEntry 33554432}


er1646v2XLBVdslInteropCmds OBJECT IDENTIFIER ::= {er1646v2XLB 727}

er1646v2XLBVdslInteropCmdsSSCTable OBJECT-TYPE
   SYNTAX      SEQUENCE OF Er1646v2XLBVdslInteropCmdsEntry
   MAX-ACCESS  not-accessible
   STATUS      current
   DESCRIPTION
      "to set the interop commands manually"
   ::= {er1646v2XLBVdslInteropCmds 1}

er1646v2XLBVdslInteropCmdsEntry OBJECT-TYPE
   SYNTAX      Er1646v2XLBVdslInteropCmdsEntry
   MAX-ACCESS  not-accessible
   STATUS      current
   DESCRIPTION
      ""
   INDEX      { er1646v2XLBVdslInteropCmdsTableIx }
   ::= {er1646v2XLBVdslInteropCmdsSSCTable 1}

Er1646v2XLBVdslInteropCmdsEntry ::=
   SEQUENCE
      {
      er1646v2XLBVdslInteropCmdsActions
         VariableLengthTableActions,
      er1646v2XLBVdslInteropCmdsTableIx
         TableIndex,
      er1646v2XLBVdslInteropCmdsSection
         INTEGER,
      er1646v2XLBVdslInteropCmdsCommand
         DisplayString
      }

er1646v2XLBVdslInteropCmdsActions OBJECT-TYPE
   SYNTAX      VariableLengthTableActions
   MAX-ACCESS  read-write
   STATUS      current
   DESCRIPTION
      "By way of this field, some manipulations
       on this table may be performed."
   ::= {er1646v2XLBVdslInteropCmdsEntry 2}

er1646v2XLBVdslInteropCmdsTableIx OBJECT-TYPE
   SYNTAX      TableIndex
   MAX-ACCESS  not-accessible
   STATUS      current
   DESCRIPTION
      ""
   ::= {er1646v2XLBVdslInteropCmdsEntry 11}

er1646v2XLBVdslInteropCmdsSection OBJECT-TYPE
   SYNTAX      INTEGER
               {
               waitForConfiguration (0),
               waitForLinkActivate (1)
               }
   MAX-ACCESS  read-write
   STATUS      current
   DESCRIPTION
      "Path: line.editConf.vdslInteropCmds.section

       Possibilities:
               waitForConfiguration   (0)
               waitForLinkActivate   (1)"
   ::= {er1646v2XLBVdslInteropCmdsEntry 16777216}

er1646v2XLBVdslInteropCmdsCommand OBJECT-TYPE
   SYNTAX      DisplayString
   MAX-ACCESS  read-write
   STATUS      current
   DESCRIPTION
      "Path: line.editConf.vdslInteropCmds.command"
   ::= {er1646v2XLBVdslInteropCmdsEntry 33554432}


er1646v2XLBAdslDsLineFeatures OBJECT IDENTIFIER ::= {er1646v2XLB 728}

er1646v2XLBAdslDsLineFeaturesSSC OBJECT IDENTIFIER ::= {er1646v2XLBAdslDsLineFeatures 1}

er1646v2XLBAdslDsLineFeaturesEntry OBJECT IDENTIFIER ::= {er1646v2XLBAdslDsLineFeaturesSSC 1}

er1646v2XLBAdslDsLineFeaturesTrellis OBJECT-TYPE
   SYNTAX      INTEGER
               {
               disabled (0),
               enabled (1)
               }
   MAX-ACCESS  read-write
   STATUS      current
   DESCRIPTION
      "Path: line.editConf.adslDsLineFeatures.trellis

       Possibilities:
               disabled   (0)
               enabled   (1)"
   ::= {er1646v2XLBAdslDsLineFeaturesEntry 16777216}

er1646v2XLBAdslDsLineFeaturesBitSwap OBJECT-TYPE
   SYNTAX      INTEGER
               {
               disabled (0),
               enabled (1)
               }
   MAX-ACCESS  read-write
   STATUS      current
   DESCRIPTION
      "Path: line.editConf.adslDsLineFeatures.bitSwap

       Possibilities:
               disabled   (0)
               enabled   (1)"
   ::= {er1646v2XLBAdslDsLineFeaturesEntry 33554432}

er1646v2XLBAdslDsLineFeaturesReTx OBJECT-TYPE
   SYNTAX      INTEGER
               {
               disabled (0),
               enabled (1)
               }
   MAX-ACCESS  read-write
   STATUS      current
   DESCRIPTION
      "Path: line.editConf.adslDsLineFeatures.reTx

       Possibilities:
               disabled   (0)
               enabled   (1)"
   ::= {er1646v2XLBAdslDsLineFeaturesEntry 50331648}

er1646v2XLBAdslDsLineFeaturesVirtualNoiseSupport OBJECT-TYPE
   SYNTAX      INTEGER
               {
               disabled (0),
               enabled (1)
               }
   MAX-ACCESS  read-write
   STATUS      current
   DESCRIPTION
      "Path: line.editConf.adslDsLineFeatures.virtualNoiseSupport

       Possibilities:
               disabled   (0)
               enabled   (1)"
   ::= {er1646v2XLBAdslDsLineFeaturesEntry 67108864}


er1646v2XLBVdslDsLineFeatures OBJECT IDENTIFIER ::= {er1646v2XLB 729}

er1646v2XLBVdslDsLineFeaturesSSC OBJECT IDENTIFIER ::= {er1646v2XLBVdslDsLineFeatures 1}

er1646v2XLBVdslDsLineFeaturesEntry OBJECT IDENTIFIER ::= {er1646v2XLBVdslDsLineFeaturesSSC 1}

er1646v2XLBVdslDsLineFeaturesTrellis OBJECT-TYPE
   SYNTAX      INTEGER
               {
               disabled (0),
               enabled (1)
               }
   MAX-ACCESS  read-write
   STATUS      current
   DESCRIPTION
      "Path: line.editConf.vdslDsLineFeatures.trellis

       Possibilities:
               disabled   (0)
               enabled   (1)"
   ::= {er1646v2XLBVdslDsLineFeaturesEntry 16777216}

er1646v2XLBVdslDsLineFeaturesBitSwap OBJECT-TYPE
   SYNTAX      INTEGER
               {
               disabled (0),
               enabled (1)
               }
   MAX-ACCESS  read-write
   STATUS      current
   DESCRIPTION
      "Path: line.editConf.vdslDsLineFeatures.bitSwap

       Possibilities:
               disabled   (0)
               enabled   (1)"
   ::= {er1646v2XLBVdslDsLineFeaturesEntry 33554432}

er1646v2XLBVdslDsLineFeaturesReTx OBJECT-TYPE
   SYNTAX      INTEGER
               {
               disabled (0),
               enabled (1)
               }
   MAX-ACCESS  read-write
   STATUS      current
   DESCRIPTION
      "Path: line.editConf.vdslDsLineFeatures.reTx

       Possibilities:
               disabled   (0)
               enabled   (1)"
   ::= {er1646v2XLBVdslDsLineFeaturesEntry 50331648}

er1646v2XLBVdslDsLineFeaturesVirtualNoiseSupport OBJECT-TYPE
   SYNTAX      INTEGER
               {
               disabled (0),
               enabled (1)
               }
   MAX-ACCESS  read-write
   STATUS      current
   DESCRIPTION
      "Path: line.editConf.vdslDsLineFeatures.virtualNoiseSupport

       Possibilities:
               disabled   (0)
               enabled   (1)"
   ::= {er1646v2XLBVdslDsLineFeaturesEntry 67108864}


er1646v2XLBVdslUsLineFeatures OBJECT IDENTIFIER ::= {er1646v2XLB 738}

er1646v2XLBVdslUsLineFeaturesSSC OBJECT IDENTIFIER ::= {er1646v2XLBVdslUsLineFeatures 1}

er1646v2XLBVdslUsLineFeaturesEntry OBJECT IDENTIFIER ::= {er1646v2XLBVdslUsLineFeaturesSSC 1}

er1646v2XLBVdslUsLineFeaturesReTx OBJECT-TYPE
   SYNTAX      INTEGER
               {
               disabled (0),
               enabled (1)
               }
   MAX-ACCESS  read-write
   STATUS      current
   DESCRIPTION
      "Path: line.editConf.vdslUsLineFeatures.reTx

       Possibilities:
               disabled   (0)
               enabled   (1)"
   ::= {er1646v2XLBVdslUsLineFeaturesEntry 50331648}


er1646v2XLBAdslDsSraMode OBJECT-TYPE
   SYNTAX      INTEGER
               {
               atInit (2),
               dynamic (3),
               dynamicSOS (4)
               }
   MAX-ACCESS  read-write
   STATUS      current
   DESCRIPTION
      "Path: line.editConf.adslDsSraMode
       Info: specify downstream rate adaption

       Possibilities:
               atInit   (2)
               dynamic   (3)
               dynamicSOS   (4)"
   ::= {er1646v2XLB 730}


er1646v2XLBVdslDsSraMode OBJECT-TYPE
   SYNTAX      INTEGER
               {
               atInit (2),
               dynamic (3),
               dynamicSOS (4)
               }
   MAX-ACCESS  read-write
   STATUS      current
   DESCRIPTION
      "Path: line.editConf.vdslDsSraMode
       Info: specify downstream rate adaption

       Possibilities:
               atInit   (2)
               dynamic   (3)
               dynamicSOS   (4)"
   ::= {er1646v2XLB 731}


er1646v2XLBVectoringMode OBJECT-TYPE
   SYNTAX      INTEGER
               {
               off (0),
               on (1),
               friendly (2)
               }
   MAX-ACCESS  read-write
   STATUS      current
   DESCRIPTION
      "Path: line.editConf.vectoringMode
       Info: vectoring with fixed MAC

       Possibilities:
               off   (0)
               on   (1)
               friendly   (2)"
   ::= {er1646v2XLB 732}


er1646v2XLBLinkAlarmThresholds OBJECT IDENTIFIER ::= {er1646v2XLB 65}

er1646v2XLBLinkAlarmThresholdsSSC OBJECT IDENTIFIER ::= {er1646v2XLBLinkAlarmThresholds 1}

er1646v2XLBLinkAlarmThresholdsEntry OBJECT IDENTIFIER ::= {er1646v2XLBLinkAlarmThresholdsSSC 1}

er1646v2XLBLinkAlarmThresholdsLineAtt OBJECT-TYPE
   SYNTAX      Integer32
   UNITS       "dB"
   MAX-ACCESS  read-write
   STATUS      current
   DESCRIPTION
      "Path: line.editConf.linkAlarmThresholds.lineAttenuation

       unit name = dB"
   ::= {er1646v2XLBLinkAlarmThresholdsEntry 16777216}

er1646v2XLBLinkAlarmThresholdsNoiseMrgn OBJECT-TYPE
   SYNTAX      Integer32
   UNITS       "dB"
   MAX-ACCESS  read-write
   STATUS      current
   DESCRIPTION
      "Path: line.editConf.linkAlarmThresholds.noiseMargin

       unit name = dB"
   ::= {er1646v2XLBLinkAlarmThresholdsEntry 33554432}

er1646v2XLBLinkAlarmThresholdsEsrExc OBJECT-TYPE
   SYNTAX      Integer32
   MAX-ACCESS  read-write
   STATUS      current
   DESCRIPTION
      "Path: line.editConf.linkAlarmThresholds.errSecRatioExceeded

       unit name = ratio
       formula = 1000 / ; 1000 *"
   ::= {er1646v2XLBLinkAlarmThresholdsEntry 83886080}

er1646v2XLBLinkAlarmThresholdsSesrExc OBJECT-TYPE
   SYNTAX      Integer32
   MAX-ACCESS  read-write
   STATUS      current
   DESCRIPTION
      "Path: line.editConf.linkAlarmThresholds.sevErrSecRatioExceeded

       unit name = ratio
       formula = 1000 / ; 1000 *"
   ::= {er1646v2XLBLinkAlarmThresholdsEntry 100663296}

er1646v2XLBLinkAlarmThresholdsIfDsSpeed OBJECT-TYPE
   SYNTAX      INTEGER
               {
               disabled (0)
               }
   UNITS       "bps"
   MAX-ACCESS  read-write
   STATUS      current
   DESCRIPTION
      "Path: line.editConf.linkAlarmThresholds.ifDsSpeed

       unit name = bps

       Possibilities:
               disabled   (0)"
   ::= {er1646v2XLBLinkAlarmThresholdsEntry 117440512}

er1646v2XLBLinkAlarmThresholdsIfUsSpeed OBJECT-TYPE
   SYNTAX      INTEGER
               {
               disabled (0)
               }
   UNITS       "bps"
   MAX-ACCESS  read-write
   STATUS      current
   DESCRIPTION
      "Path: line.editConf.linkAlarmThresholds.ifUsSpeed

       unit name = bps

       Possibilities:
               disabled   (0)"
   ::= {er1646v2XLBLinkAlarmThresholdsEntry 134217728}


er1646v2XLBAdslMode OBJECT-TYPE
   SYNTAX      Integer32
   MAX-ACCESS  read-write
   STATUS      current
   DESCRIPTION
      "Path: line.editConf.adslMode
       Info: Configuration of ADSL ATU transmission system (ISDN)

       Bit meanings:
               bit 16 = g992.1 adsl annex B,
               bit 17 = g992.3 adsl2 annex B,
               bit 18 = g992.3 adsl2 annex J,
               bit 19 = g992.5 adsl2Plus annex B,
               bit 20 = g992.5 adsl2Plus annex J"
   ::= {er1646v2XLB 52}


er1646v2XLBVdslMode OBJECT-TYPE
   SYNTAX      Integer32
   MAX-ACCESS  read-write
   STATUS      current
   DESCRIPTION
      "Path: line.editConf.vdslMode
       Info: Configuration of VDSL ATU transmission system

       Bit meanings:
               bit 0 = g993.2 vdsl annex A,
               bit 1 = g993.2 vdsl annex B,
               bit 2 = g993.2 vdsl annex C"
   ::= {er1646v2XLB 53}



sr1646v2XLB OBJECT IDENTIFIER ::= {r1646v2XLB 14}


sr1646v2XLBIfDescr OBJECT-TYPE
   SYNTAX      DisplayString
   MAX-ACCESS  read-only
   STATUS      current
   DESCRIPTION
      "Path: line.status.ifDescr
       Info: ifDescr"
   ::= {sr1646v2XLB 101}


sr1646v2XLBIfType OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: line.status.ifType
       Info: ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1646v2XLB 102}


sr1646v2XLBIfUsSpeed OBJECT-TYPE
   SYNTAX      Gauge32
   MAX-ACCESS  read-only
   STATUS      current
   DESCRIPTION
      "Path: line.status.ifUsSpeed
       Info: ifSpeed

       32 bit unsigned gauge value."
   ::= {sr1646v2XLB 104}


sr1646v2XLBIfDsSpeed OBJECT-TYPE
   SYNTAX      Gauge32
   MAX-ACCESS  read-only
   STATUS      current
   DESCRIPTION
      "Path: line.status.ifDsSpeed
       Info: ifSpeed

       32 bit unsigned gauge value."
   ::= {sr1646v2XLB 127}


sr1646v2XLBIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: line.status.ifOperStatus
       Info: ifOperStatus

       Possibilities:
               up   (1)
               down   (2)
               testing   (3)
               unknown   (4)
               dormant   (5)
               notPresent   (6)
               lowerLayerDown   (7)"
   ::= {sr1646v2XLB 107}


sr1646v2XLBMode OBJECT-TYPE
   SYNTAX      INTEGER
               {
               t1d413 (0),
               g992d1sadslsannexsA (1),
               g992d2sadslslite (2),
               g992d3sadsl2sannexsA (3),
               g992d3sadsl2sannexsI (4),
               g992d3sadsl2sannexsL (5),
               g992d3sadsl2sannexsM (6),
               g992d4sadsl2slite (7),
               g992d4sadsl2slitesannexsI (8),
               g992d5sadsl2PlussannexsA (9),
               g992d5sadsl2PlussannexsI (10),
               g992d5sadsl2PlussannexsM (11),
               g992d1sadslsannexsB (16),
               g992d3sadsl2sannexsB (17),
               g992d3sadsl2sannexsJ (18),
               g992d5sadsl2PlussannexsB (19),
               g992d5sadsl2PlussannexsJ (20),
               g993d2svdslsannexsA (30),
               g993d2svdslsannexsB (31),
               g993d2svdslsannexsC (32),
               unknown (99)
               }
   MAX-ACCESS  read-only
   STATUS      current
   DESCRIPTION
      "Path: line.status.mode
       Info: The ADSL mode selected

       Possibilities:
               t1.413   (0)
               g992.1 adsl annex A   (1)
               g992.2 adsl lite   (2)
               g992.3 adsl2 annex A   (3)
               g992.3 adsl2 annex I   (4)
               g992.3 adsl2 annex L   (5)
               g992.3 adsl2 annex M   (6)
               g992.4 adsl2 lite   (7)
               g992.4 adsl2 lite annex I   (8)
               g992.5 adsl2Plus annex A   (9)
               g992.5 adsl2Plus annex I   (10)
               g992.5 adsl2Plus annex M   (11)
               g992.1 adsl annex B   (16)
               g992.3 adsl2 annex B   (17)
               g992.3 adsl2 annex J   (18)
               g992.5 adsl2Plus annex B   (19)
               g992.5 adsl2Plus annex J   (20)
               g993.2 vdsl annex A   (30)
               g993.2 vdsl annex B   (31)
               g993.2 vdsl annex C   (32)
               unknown   (99)"
   ::= {sr1646v2XLB 126}


sr1646v2XLBPowerManagementMode OBJECT-TYPE
   SYNTAX      INTEGER
               {
               g997mpmsmL0 (0),
               g997mpmsmL3 (3)
               }
   MAX-ACCESS  read-only
   STATUS      current
   DESCRIPTION
      "Path: line.status.powerManagementMode
       Info: Power Management Mode

       Possibilities:
               g997-pms-L0   (0)
               g997-pms-L3   (3)"
   ::= {sr1646v2XLB 128}


sr1646v2XLBDsLatency OBJECT-TYPE
   SYNTAX      INTEGER
               {
               fast (0),
               interleaved (1)
               }
   MAX-ACCESS  read-only
   STATUS      current
   DESCRIPTION
      "Path: line.status.dsLatency
       Info: Latency type

       Possibilities:
               fast   (0)
               interleaved   (1)"
   ::= {sr1646v2XLB 130}


sr1646v2XLBUsLatency OBJECT-TYPE
   SYNTAX      INTEGER
               {
               fast (0),
               interleaved (1)
               }
   MAX-ACCESS  read-only
   STATUS      current
   DESCRIPTION
      "Path: line.status.usLatency
       Info: Latency type

       Possibilities:
               fast   (0)
               interleaved   (1)"
   ::= {sr1646v2XLB 230}


sr1646v2XLBFirmwareVersion OBJECT-TYPE
   SYNTAX      DisplayString
   MAX-ACCESS  read-only
   STATUS      current
   DESCRIPTION
      "Path: line.status.firmwareVersion
       Info: Amazon firmware release"
   ::= {sr1646v2XLB 131}


sr1646v2XLBEocInfo OBJECT IDENTIFIER ::= {sr1646v2XLB 132}

sr1646v2XLBEocInfoSSC OBJECT IDENTIFIER ::= {sr1646v2XLBEocInfo 1}

sr1646v2XLBEocInfoEntry OBJECT IDENTIFIER ::= {sr1646v2XLBEocInfoSSC 1}

sr1646v2XLBEocInfoVendorID OBJECT-TYPE
   SYNTAX      OCTET STRING
   MAX-ACCESS  read-only
   STATUS      current
   DESCRIPTION
      "Path: line.status.eocInfo.vendorID"
   ::= {sr1646v2XLBEocInfoEntry 16777216}

sr1646v2XLBEocInfoVendorVersionNumber OBJECT-TYPE
   SYNTAX      OCTET STRING
   MAX-ACCESS  read-only
   STATUS      current
   DESCRIPTION
      "Path: line.status.eocInfo.vendorVersionNumber"
   ::= {sr1646v2XLBEocInfoEntry 33554432}

sr1646v2XLBEocInfoVendorSerialNumber OBJECT-TYPE
   SYNTAX      OCTET STRING
   MAX-ACCESS  read-only
   STATUS      current
   DESCRIPTION
      "Path: line.status.eocInfo.vendorSerialNumber"
   ::= {sr1646v2XLBEocInfoEntry 50331648}


sr1646v2XLBIfUsNetSpeed OBJECT-TYPE
   SYNTAX      Gauge32
   MAX-ACCESS  read-only
   STATUS      current
   DESCRIPTION
      "Path: line.status.ifUsNetSpeed
       Info: ifSpeed

       32 bit unsigned gauge value."
   ::= {sr1646v2XLB 156}


sr1646v2XLBIfDsNetSpeed OBJECT-TYPE
   SYNTAX      Gauge32
   MAX-ACCESS  read-only
   STATUS      current
   DESCRIPTION
      "Path: line.status.ifDsNetSpeed
       Info: ifSpeed

       32 bit unsigned gauge value."
   ::= {sr1646v2XLB 157}


sr1646v2XLBIfUsPrevSpeed OBJECT-TYPE
   SYNTAX      Gauge32
   MAX-ACCESS  read-only
   STATUS      current
   DESCRIPTION
      "Path: line.status.ifUsPrevSpeed
       Info: ifSpeed

       32 bit unsigned gauge value."
   ::= {sr1646v2XLB 137}


sr1646v2XLBIfDsPrevSpeed OBJECT-TYPE
   SYNTAX      Gauge32
   MAX-ACCESS  read-only
   STATUS      current
   DESCRIPTION
      "Path: line.status.ifDsPrevSpeed
       Info: ifSpeed

       32 bit unsigned gauge value."
   ::= {sr1646v2XLB 138}


sr1646v2XLBIfMaxCellRate OBJECT-TYPE
   SYNTAX      Integer32
   MAX-ACCESS  read-only
   STATUS      current
   DESCRIPTION
      "Path: line.status.ifMaxCellRate
       Info: line max cell rate"
   ::= {sr1646v2XLB 139}


sr1646v2XLBG994VendorID OBJECT-TYPE
   SYNTAX      OCTET STRING
   MAX-ACCESS  read-only
   STATUS      current
   DESCRIPTION
      "Path: line.status.g994VendorID
       Info: G994 vendor id"
   ::= {sr1646v2XLB 133}


sr1646v2XLBG997Capabilities OBJECT-TYPE
   SYNTAX      OCTET STRING
   MAX-ACCESS  read-only
   STATUS      current
   DESCRIPTION
      "Path: line.status.g997Capabilities
       Info: G997 XTSE Capabilities"
   ::= {sr1646v2XLB 134}


sr1646v2XLBLtqVersionInfo OBJECT IDENTIFIER ::= {sr1646v2XLB 142}

sr1646v2XLBLtqVersionInfoSSC OBJECT IDENTIFIER ::= {sr1646v2XLBLtqVersionInfo 1}

sr1646v2XLBLtqVersionInfoEntry OBJECT IDENTIFIER ::= {sr1646v2XLBLtqVersionInfoSSC 1}

sr1646v2XLBLtqVersionInfoDriverVersionApi OBJECT-TYPE
   SYNTAX      DisplayString
   MAX-ACCESS  read-only
   STATUS      current
   DESCRIPTION
      "Path: line.status.ltqVersionInfo.driverVersionApi"
   ::= {sr1646v2XLBLtqVersionInfoEntry 16777216}

sr1646v2XLBLtqVersionInfoDriverVersionMeiBsp OBJECT-TYPE
   SYNTAX      DisplayString
   MAX-ACCESS  read-only
   STATUS      current
   DESCRIPTION
      "Path: line.status.ltqVersionInfo.driverVersionMeiBsp"
   ::= {sr1646v2XLBLtqVersionInfoEntry 33554432}

sr1646v2XLBLtqVersionInfoChipSetFWVersion OBJECT-TYPE
   SYNTAX      DisplayString
   MAX-ACCESS  read-only
   STATUS      current
   DESCRIPTION
      "Path: line.status.ltqVersionInfo.chipSetFWVersion"
   ::= {sr1646v2XLBLtqVersionInfoEntry 50331648}

sr1646v2XLBLtqVersionInfoChipSetHWVersion OBJECT-TYPE
   SYNTAX      DisplayString
   MAX-ACCESS  read-only
   STATUS      current
   DESCRIPTION
      "Path: line.status.ltqVersionInfo.chipSetHWVersion"
   ::= {sr1646v2XLBLtqVersionInfoEntry 67108864}

sr1646v2XLBLtqVersionInfoChipSetType OBJECT-TYPE
   SYNTAX      DisplayString
   MAX-ACCESS  read-only
   STATUS      current
   DESCRIPTION
      "Path: line.status.ltqVersionInfo.chipSetType"
   ::= {sr1646v2XLBLtqVersionInfoEntry 83886080}

sr1646v2XLBLtqVersionInfoHybridType OBJECT-TYPE
   SYNTAX      INTEGER
               {
               unknown (-1),
               na (0),
               pots (1),
               isdn (2),
               invalid (3)
               }
   MAX-ACCESS  read-only
   STATUS      current
   DESCRIPTION
      "Path: line.status.ltqVersionInfo.hybridType

       Possibilities:
               unknown   (-1)
               n/a   (0)
               pots   (1)
               isdn   (2)
               invalid   (3)"
   ::= {sr1646v2XLBLtqVersionInfoEntry 100663296}

sr1646v2XLBLtqVersionInfoLoadedFW OBJECT-TYPE
   SYNTAX      DisplayString
   MAX-ACCESS  read-only
   STATUS      current
   DESCRIPTION
      "Path: line.status.ltqVersionInfo.loadedFW"
   ::= {sr1646v2XLBLtqVersionInfoEntry 117440512}


sr1646v2XLBLtqAutoBoot OBJECT IDENTIFIER ::= {sr1646v2XLB 146}

sr1646v2XLBLtqAutoBootSSC OBJECT IDENTIFIER ::= {sr1646v2XLBLtqAutoBoot 1}

sr1646v2XLBLtqAutoBootEntry OBJECT IDENTIFIER ::= {sr1646v2XLBLtqAutoBootSSC 1}

sr1646v2XLBLtqAutoBootLinuxDriver OBJECT-TYPE
   SYNTAX      INTEGER
               {
               unknown (0),
               atm (1),
               ptm (2),
               ptmForced (3)
               }
   MAX-ACCESS  read-only
   STATUS      current
   DESCRIPTION
      "Path: line.status.ltqAutoBoot.linuxDriver

       Possibilities:
               unknown   (0)
               atm   (1)
               ptm   (2)
               ptmForced   (3)"
   ::= {sr1646v2XLBLtqAutoBootEntry 16777216}

sr1646v2XLBLtqAutoBootNextMode OBJECT-TYPE
   SYNTAX      INTEGER
               {
               na (0),
               adsl (1),
               vdsl (2)
               }
   MAX-ACCESS  read-only
   STATUS      current
   DESCRIPTION
      "Path: line.status.ltqAutoBoot.nextMode

       Possibilities:
               n/a   (0)
               adsl   (1)
               vdsl   (2)"
   ::= {sr1646v2XLBLtqAutoBootEntry 33554432}

sr1646v2XLBLtqAutoBootTcLayer OBJECT-TYPE
   SYNTAX      INTEGER
               {
               unknown (0),
               atm (1),
               ptm (2),
               ptmForced (3)
               }
   MAX-ACCESS  read-only
   STATUS      current
   DESCRIPTION
      "Path: line.status.ltqAutoBoot.tcLayer

       Possibilities:
               unknown   (0)
               atm   (1)
               ptm   (2)
               ptmForced   (3)"
   ::= {sr1646v2XLBLtqAutoBootEntry 50331648}

sr1646v2XLBLtqAutoBootInitStatus OBJECT-TYPE
   SYNTAX      INTEGER
               {
               successful (0),
               configserror (1),
               configsnotsfeasible (2),
               communicationsproblem (3),
               nospeersxtu (4),
               unknown (5)
               }
   MAX-ACCESS  read-only
   STATUS      current
   DESCRIPTION
      "Path: line.status.ltqAutoBoot.initStatus

       Possibilities:
               successful   (0)
               config error   (1)
               config not feasible   (2)
               communication problem   (3)
               no peer xtu   (4)
               unknown   (5)"
   ::= {sr1646v2XLBLtqAutoBootEntry 67108864}

sr1646v2XLBLtqAutoBootInitSubStatus OBJECT-TYPE
   SYNTAX      INTEGER
               {
               none (0),
               unknown (1),
               noscommonsmode (2),
               oppositesmode (3),
               retry (4),
               hybrid (5),
               portsmode (6),
               ppsdriver (7),
               localsshutdown (8),
               timeout (9),
               fastslos (10)
               }
   MAX-ACCESS  read-only
   STATUS      current
   DESCRIPTION
      "Path: line.status.ltqAutoBoot.initSubStatus

       Possibilities:
               none   (0)
               unknown   (1)
               no common mode   (2)
               opposite mode   (3)
               retry   (4)
               hybrid   (5)
               port mode   (6)
               pp driver   (7)
               local shutdown   (8)
               timeout   (9)
               fast los   (10)"
   ::= {sr1646v2XLBLtqAutoBootEntry 83886080}


sr1646v2XLBBandPlanProfile OBJECT-TYPE
   SYNTAX      INTEGER
               {
               profiles8a (0),
               profiles8b (1),
               profiles8c (2),
               profiles8d (3),
               profiles12a (4),
               profiles12b (5),
               profiles17a (6),
               profiles30a (7),
               profiles17b (8),
               unknown (99)
               }
   MAX-ACCESS  read-only
   STATUS      current
   DESCRIPTION
      "Path: line.status.bandPlanProfile
       Info: VDSL band plan profile

       Possibilities:
               profile 8a   (0)
               profile 8b   (1)
               profile 8c   (2)
               profile 8d   (3)
               profile 12a   (4)
               profile 12b   (5)
               profile 17a   (6)
               profile 30a   (7)
               profile 17b   (8)
               unknown   (99)"
   ::= {sr1646v2XLB 145}


sr1646v2XLBVectoring OBJECT IDENTIFIER ::= {sr1646v2XLB 741}

sr1646v2XLBVectoringSSC OBJECT IDENTIFIER ::= {sr1646v2XLBVectoring 1}

sr1646v2XLBVectoringEntry OBJECT IDENTIFIER ::= {sr1646v2XLBVectoringSSC 1}

sr1646v2XLBVectoringVector OBJECT-TYPE
   SYNTAX      INTEGER
               {
               off (0),
               onDs (1),
               onDsUs (2)
               }
   MAX-ACCESS  read-only
   STATUS      current
   DESCRIPTION
      "Path: line.status.vectoring.vector

       Possibilities:
               off   (0)
               onDs   (1)
               onDsUs   (2)"
   ::= {sr1646v2XLBVectoringEntry 16777216}

sr1646v2XLBVectoringVectorFriendly OBJECT-TYPE
   SYNTAX      INTEGER
               {
               off (0),
               onDs (1),
               onDsUs (2)
               }
   MAX-ACCESS  read-only
   STATUS      current
   DESCRIPTION
      "Path: line.status.vectoring.vectorFriendly

       Possibilities:
               off   (0)
               onDs   (1)
               onDsUs   (2)"
   ::= {sr1646v2XLBVectoringEntry 33554432}


sr1646v2XLBTestMode OBJECT-TYPE
   SYNTAX      INTEGER
               {
               disable (0),
               showtimeLock (1),
               quiet (2),
               trainingLock (3),
               lock (4),
               unlock (5),
               sleep (6)
               }
   MAX-ACCESS  read-only
   STATUS      current
   DESCRIPTION
      "Path: line.status.testMode
       Info: testmode

       Possibilities:
               disable   (0)
               showtimeLock   (1)
               quiet   (2)
               trainingLock   (3)
               lock   (4)
               unlock   (5)
               sleep   (6)"
   ::= {sr1646v2XLB 735}


sr1646v2XLBDsLineFeatures OBJECT IDENTIFIER ::= {sr1646v2XLB 739}

sr1646v2XLBDsLineFeaturesSSC OBJECT IDENTIFIER ::= {sr1646v2XLBDsLineFeatures 1}

sr1646v2XLBDsLineFeaturesEntry OBJECT IDENTIFIER ::= {sr1646v2XLBDsLineFeaturesSSC 1}

sr1646v2XLBDsLineFeaturesTrellis OBJECT-TYPE
   SYNTAX      INTEGER
               {
               disabled (0),
               enabled (1)
               }
   MAX-ACCESS  read-only
   STATUS      current
   DESCRIPTION
      "Path: line.status.dsLineFeatures.trellis

       Possibilities:
               disabled   (0)
               enabled   (1)"
   ::= {sr1646v2XLBDsLineFeaturesEntry 16777216}

sr1646v2XLBDsLineFeaturesBitSwap OBJECT-TYPE
   SYNTAX      INTEGER
               {
               disabled (0),
               enabled (1)
               }
   MAX-ACCESS  read-only
   STATUS      current
   DESCRIPTION
      "Path: line.status.dsLineFeatures.bitSwap

       Possibilities:
               disabled   (0)
               enabled   (1)"
   ::= {sr1646v2XLBDsLineFeaturesEntry 33554432}

sr1646v2XLBDsLineFeaturesReTx OBJECT-TYPE
   SYNTAX      INTEGER
               {
               disabled (0),
               enabled (1)
               }
   MAX-ACCESS  read-only
   STATUS      current
   DESCRIPTION
      "Path: line.status.dsLineFeatures.reTx

       Possibilities:
               disabled   (0)
               enabled   (1)"
   ::= {sr1646v2XLBDsLineFeaturesEntry 50331648}

sr1646v2XLBDsLineFeaturesVirtualNoiseSupport OBJECT-TYPE
   SYNTAX      INTEGER
               {
               disabled (0),
               enabled (1)
               }
   MAX-ACCESS  read-only
   STATUS      current
   DESCRIPTION
      "Path: line.status.dsLineFeatures.virtualNoiseSupport

       Possibilities:
               disabled   (0)
               enabled   (1)"
   ::= {sr1646v2XLBDsLineFeaturesEntry 67108864}


sr1646v2XLBUsLineFeatures OBJECT IDENTIFIER ::= {sr1646v2XLB 740}

sr1646v2XLBUsLineFeaturesSSC OBJECT IDENTIFIER ::= {sr1646v2XLBUsLineFeatures 1}

sr1646v2XLBUsLineFeaturesEntry OBJECT IDENTIFIER ::= {sr1646v2XLBUsLineFeaturesSSC 1}

sr1646v2XLBUsLineFeaturesTrellis OBJECT-TYPE
   SYNTAX      INTEGER
               {
               disabled (0),
               enabled (1)
               }
   MAX-ACCESS  read-only
   STATUS      current
   DESCRIPTION
      "Path: line.status.usLineFeatures.trellis

       Possibilities:
               disabled   (0)
               enabled   (1)"
   ::= {sr1646v2XLBUsLineFeaturesEntry 16777216}

sr1646v2XLBUsLineFeaturesBitSwap OBJECT-TYPE
   SYNTAX      INTEGER
               {
               disabled (0),
               enabled (1)
               }
   MAX-ACCESS  read-only
   STATUS      current
   DESCRIPTION
      "Path: line.status.usLineFeatures.bitSwap

       Possibilities:
               disabled   (0)
               enabled   (1)"
   ::= {sr1646v2XLBUsLineFeaturesEntry 33554432}

sr1646v2XLBUsLineFeaturesReTx OBJECT-TYPE
   SYNTAX      INTEGER
               {
               disabled (0),
               enabled (1)
               }
   MAX-ACCESS  read-only
   STATUS      current
   DESCRIPTION
      "Path: line.status.usLineFeatures.reTx

       Possibilities:
               disabled   (0)
               enabled   (1)"
   ::= {sr1646v2XLBUsLineFeaturesEntry 50331648}

sr1646v2XLBUsLineFeaturesVirtualNoiseSupport OBJECT-TYPE
   SYNTAX      INTEGER
               {
               disabled (0),
               enabled (1)
               }
   MAX-ACCESS  read-only
   STATUS      current
   DESCRIPTION
      "Path: line.status.usLineFeatures.virtualNoiseSupport

       Possibilities:
               disabled   (0)
               enabled   (1)"
   ::= {sr1646v2XLBUsLineFeaturesEntry 67108864}


sr1646v2XLBSnmpIndex OBJECT-TYPE
   SYNTAX      Integer32
   MAX-ACCESS  read-only
   STATUS      current
   DESCRIPTION
      "Path: line.status.snmpIndex
       Info: SNMP index assigned to this object"
   ::= {sr1646v2XLB 269}



pr1646v2XLB OBJECT IDENTIFIER ::= {r1646v2XLB 12}


pr1646v2XLBH2 OBJECT IDENTIFIER ::= {pr1646v2XLB 21}

pr1646v2XLBH2SSCTable OBJECT-TYPE
   SYNTAX      SEQUENCE OF Pr1646v2XLBH2Entry
   MAX-ACCESS  not-accessible
   STATUS      current
   DESCRIPTION
      "h2Line"
   ::= {pr1646v2XLBH2 1}

pr1646v2XLBH2Entry OBJECT-TYPE
   SYNTAX      Pr1646v2XLBH2Entry
   MAX-ACCESS  not-accessible
   STATUS      current
   DESCRIPTION
      ""
   INDEX      { pr1646v2XLBH2TableIx }
   ::= {pr1646v2XLBH2SSCTable 1}

Pr1646v2XLBH2Entry ::=
   SEQUENCE
      {
      pr1646v2XLBH2TableIx
         TableIndex,
      pr1646v2XLBH2SysUpTime
         TimeTicks,
      pr1646v2XLBH2LDownCnt
         Counter32,
      pr1646v2XLBH2LDownTme
         TimeTicks,
      pr1646v2XLBH2UsSpdMin
         Integer32,
      pr1646v2XLBH2UsSpdAvrg
         Integer32,
      pr1646v2XLBH2UsSpdMax
         Integer32,
      pr1646v2XLBH2DsSpdMin
         Integer32,
      pr1646v2XLBH2DsSpdAvrg
         Integer32,
      pr1646v2XLBH2DsSpdMax
         Integer32
      }

pr1646v2XLBH2TableIx OBJECT-TYPE
   SYNTAX      TableIndex
   MAX-ACCESS  not-accessible
   STATUS      current
   DESCRIPTION
      ""
   ::= {pr1646v2XLBH2Entry 11}

pr1646v2XLBH2SysUpTime OBJECT-TYPE
   SYNTAX      TimeTicks
   MAX-ACCESS  read-only
   STATUS      current
   DESCRIPTION
      "Path: line.performance.h2Line.sysUpTime

       Time in centi-second."
   ::= {pr1646v2XLBH2Entry 16777216}

pr1646v2XLBH2LDownCnt OBJECT-TYPE
   SYNTAX      Counter32
   MAX-ACCESS  read-only
   STATUS      current
   DESCRIPTION
      "Path: line.performance.h2Line.linkDownCount

       32 bit unsigned wrappable counter."
   ::= {pr1646v2XLBH2Entry 33554432}

pr1646v2XLBH2LDownTme OBJECT-TYPE
   SYNTAX      TimeTicks
   MAX-ACCESS  read-only
   STATUS      current
   DESCRIPTION
      "Path: line.performance.h2Line.linkDownTime

       Time in centi-second."
   ::= {pr1646v2XLBH2Entry 50331648}

pr1646v2XLBH2UsSpdMin OBJECT-TYPE
   SYNTAX      Integer32
   MAX-ACCESS  read-only
   STATUS      current
   DESCRIPTION
      "Path: line.performance.h2Line.usSpeedMin

       formula = 32000 * ; 32000 /"
   ::= {pr1646v2XLBH2Entry 67108864}

pr1646v2XLBH2UsSpdAvrg OBJECT-TYPE
   SYNTAX      Integer32
   MAX-ACCESS  read-only
   STATUS      current
   DESCRIPTION
      "Path: line.performance.h2Line.usSpeedAvrg

       formula = 32000 * ; 32000 /"
   ::= {pr1646v2XLBH2Entry 83886080}

pr1646v2XLBH2UsSpdMax OBJECT-TYPE
   SYNTAX      Integer32
   MAX-ACCESS  read-only
   STATUS      current
   DESCRIPTION
      "Path: line.performance.h2Line.usSpeedMax

       formula = 32000 * ; 32000 /"
   ::= {pr1646v2XLBH2Entry 100663296}

pr1646v2XLBH2DsSpdMin OBJECT-TYPE
   SYNTAX      Integer32
   MAX-ACCESS  read-only
   STATUS      current
   DESCRIPTION
      "Path: line.performance.h2Line.dsSpeedMin

       formula = 32000 * ; 32000 /"
   ::= {pr1646v2XLBH2Entry 117440512}

pr1646v2XLBH2DsSpdAvrg OBJECT-TYPE
   SYNTAX      Integer32
   MAX-ACCESS  read-only
   STATUS      current
   DESCRIPTION
      "Path: line.performance.h2Line.dsSpeedAvrg

       formula = 32000 * ; 32000 /"
   ::= {pr1646v2XLBH2Entry 134217728}

pr1646v2XLBH2DsSpdMax OBJECT-TYPE
   SYNTAX      Integer32
   MAX-ACCESS  read-only
   STATUS      current
   DESCRIPTION
      "Path: line.performance.h2Line.dsSpeedMax

       formula = 32000 * ; 32000 /"
   ::= {pr1646v2XLBH2Entry 150994944}


pr1646v2XLBH24 OBJECT IDENTIFIER ::= {pr1646v2XLB 23}

pr1646v2XLBH24SSCTable OBJECT-TYPE
   SYNTAX      SEQUENCE OF Pr1646v2XLBH24Entry
   MAX-ACCESS  not-accessible
   STATUS      current
   DESCRIPTION
      "h24Line"
   ::= {pr1646v2XLBH24 1}

pr1646v2XLBH24Entry OBJECT-TYPE
   SYNTAX      Pr1646v2XLBH24Entry
   MAX-ACCESS  not-accessible
   STATUS      current
   DESCRIPTION
      ""
   INDEX      { pr1646v2XLBH24TableIx }
   ::= {pr1646v2XLBH24SSCTable 1}

Pr1646v2XLBH24Entry ::=
   SEQUENCE
      {
      pr1646v2XLBH24TableIx
         TableIndex,
      pr1646v2XLBH24SysUpTime
         TimeTicks,
      pr1646v2XLBH24LDownCnt
         Counter32,
      pr1646v2XLBH24LDownTme
         TimeTicks,
      pr1646v2XLBH24UsSpdMin
         Integer32,
      pr1646v2XLBH24UsSpdAvrg
         Integer32,
      pr1646v2XLBH24UsSpdMax
         Integer32,
      pr1646v2XLBH24DsSpdMin
         Integer32,
      pr1646v2XLBH24DsSpdAvrg
         Integer32,
      pr1646v2XLBH24DsSpdMax
         Integer32
      }

pr1646v2XLBH24TableIx OBJECT-TYPE
   SYNTAX      TableIndex
   MAX-ACCESS  not-accessible
   STATUS      current
   DESCRIPTION
      ""
   ::= {pr1646v2XLBH24Entry 11}

pr1646v2XLBH24SysUpTime OBJECT-TYPE
   SYNTAX      TimeTicks
   MAX-ACCESS  read-only
   STATUS      current
   DESCRIPTION
      "Path: line.performance.h24Line.sysUpTime

       Time in centi-second."
   ::= {pr1646v2XLBH24Entry 16777216}

pr1646v2XLBH24LDownCnt OBJECT-TYPE
   SYNTAX      Counter32
   MAX-ACCESS  read-only
   STATUS      current
   DESCRIPTION
      "Path: line.performance.h24Line.linkDownCount

       32 bit unsigned wrappable counter."
   ::= {pr1646v2XLBH24Entry 33554432}

pr1646v2XLBH24LDownTme OBJECT-TYPE
   SYNTAX      TimeTicks
   MAX-ACCESS  read-only
   STATUS      current
   DESCRIPTION
      "Path: line.performance.h24Line.linkDownTime

       Time in centi-second."
   ::= {pr1646v2XLBH24Entry 50331648}

pr1646v2XLBH24UsSpdMin OBJECT-TYPE
   SYNTAX      Integer32
   MAX-ACCESS  read-only
   STATUS      current
   DESCRIPTION
      "Path: line.performance.h24Line.usSpeedMin

       formula = 32000 * ; 32000 /"
   ::= {pr1646v2XLBH24Entry 67108864}

pr1646v2XLBH24UsSpdAvrg OBJECT-TYPE
   SYNTAX      Integer32
   MAX-ACCESS  read-only
   STATUS      current
   DESCRIPTION
      "Path: line.performance.h24Line.usSpeedAvrg

       formula = 32000 * ; 32000 /"
   ::= {pr1646v2XLBH24Entry 83886080}

pr1646v2XLBH24UsSpdMax OBJECT-TYPE
   SYNTAX      Integer32
   MAX-ACCESS  read-only
   STATUS      current
   DESCRIPTION
      "Path: line.performance.h24Line.usSpeedMax

       formula = 32000 * ; 32000 /"
   ::= {pr1646v2XLBH24Entry 100663296}

pr1646v2XLBH24DsSpdMin OBJECT-TYPE
   SYNTAX      Integer32
   MAX-ACCESS  read-only
   STATUS      current
   DESCRIPTION
      "Path: line.performance.h24Line.dsSpeedMin

       formula = 32000 * ; 32000 /"
   ::= {pr1646v2XLBH24Entry 117440512}

pr1646v2XLBH24DsSpdAvrg OBJECT-TYPE
   SYNTAX      Integer32
   MAX-ACCESS  read-only
   STATUS      current
   DESCRIPTION
      "Path: line.performance.h24Line.dsSpeedAvrg

       formula = 32000 * ; 32000 /"
   ::= {pr1646v2XLBH24Entry 134217728}

pr1646v2XLBH24DsSpdMax OBJECT-TYPE
   SYNTAX      Integer32
   MAX-ACCESS  read-only
   STATUS      current
   DESCRIPTION
      "Path: line.performance.h24Line.dsSpeedMax

       formula = 32000 * ; 32000 /"
   ::= {pr1646v2XLBH24Entry 150994944}


pr1646v2XLBD7 OBJECT IDENTIFIER ::= {pr1646v2XLB 26}

pr1646v2XLBD7SSCTable OBJECT-TYPE
   SYNTAX      SEQUENCE OF Pr1646v2XLBD7Entry
   MAX-ACCESS  not-accessible
   STATUS      current
   DESCRIPTION
      "d7Line"
   ::= {pr1646v2XLBD7 1}

pr1646v2XLBD7Entry OBJECT-TYPE
   SYNTAX      Pr1646v2XLBD7Entry
   MAX-ACCESS  not-accessible
   STATUS      current
   DESCRIPTION
      ""
   INDEX      { pr1646v2XLBD7TableIx }
   ::= {pr1646v2XLBD7SSCTable 1}

Pr1646v2XLBD7Entry ::=
   SEQUENCE
      {
      pr1646v2XLBD7TableIx
         TableIndex,
      pr1646v2XLBD7SysUpTime
         TimeTicks,
      pr1646v2XLBD7LDownCnt
         Counter32,
      pr1646v2XLBD7LDownTme
         TimeTicks,
      pr1646v2XLBD7UsSpdMin
         Integer32,
      pr1646v2XLBD7UsSpdAvrg
         Integer32,
      pr1646v2XLBD7UsSpdMax
         Integer32,
      pr1646v2XLBD7DsSpdMin
         Integer32,
      pr1646v2XLBD7DsSpdAvrg
         Integer32,
      pr1646v2XLBD7DsSpdMax
         Integer32
      }

pr1646v2XLBD7TableIx OBJECT-TYPE
   SYNTAX      TableIndex
   MAX-ACCESS  not-accessible
   STATUS      current
   DESCRIPTION
      ""
   ::= {pr1646v2XLBD7Entry 11}

pr1646v2XLBD7SysUpTime OBJECT-TYPE
   SYNTAX      TimeTicks
   MAX-ACCESS  read-only
   STATUS      current
   DESCRIPTION
      "Path: line.performance.d7Line.sysUpTime

       Time in centi-second."
   ::= {pr1646v2XLBD7Entry 16777216}

pr1646v2XLBD7LDownCnt OBJECT-TYPE
   SYNTAX      Counter32
   MAX-ACCESS  read-only
   STATUS      current
   DESCRIPTION
      "Path: line.performance.d7Line.linkDownCount

       32 bit unsigned wrappable counter."
   ::= {pr1646v2XLBD7Entry 33554432}

pr1646v2XLBD7LDownTme OBJECT-TYPE
   SYNTAX      TimeTicks
   MAX-ACCESS  read-only
   STATUS      current
   DESCRIPTION
      "Path: line.performance.d7Line.linkDownTime

       Time in centi-second."
   ::= {pr1646v2XLBD7Entry 50331648}

pr1646v2XLBD7UsSpdMin OBJECT-TYPE
   SYNTAX      Integer32
   MAX-ACCESS  read-only
   STATUS      current
   DESCRIPTION
      "Path: line.performance.d7Line.usSpeedMin

       formula = 32000 * ; 32000 /"
   ::= {pr1646v2XLBD7Entry 67108864}

pr1646v2XLBD7UsSpdAvrg OBJECT-TYPE
   SYNTAX      Integer32
   MAX-ACCESS  read-only
   STATUS      current
   DESCRIPTION
      "Path: line.performance.d7Line.usSpeedAvrg

       formula = 32000 * ; 32000 /"
   ::= {pr1646v2XLBD7Entry 83886080}

pr1646v2XLBD7UsSpdMax OBJECT-TYPE
   SYNTAX      Integer32
   MAX-ACCESS  read-only
   STATUS      current
   DESCRIPTION
      "Path: line.performance.d7Line.usSpeedMax

       formula = 32000 * ; 32000 /"
   ::= {pr1646v2XLBD7Entry 100663296}

pr1646v2XLBD7DsSpdMin OBJECT-TYPE
   SYNTAX      Integer32
   MAX-ACCESS  read-only
   STATUS      current
   DESCRIPTION
      "Path: line.performance.d7Line.dsSpeedMin

       formula = 32000 * ; 32000 /"
   ::= {pr1646v2XLBD7Entry 117440512}

pr1646v2XLBD7DsSpdAvrg OBJECT-TYPE
   SYNTAX      Integer32
   MAX-ACCESS  read-only
   STATUS      current
   DESCRIPTION
      "Path: line.performance.d7Line.dsSpeedAvrg

       formula = 32000 * ; 32000 /"
   ::= {pr1646v2XLBD7Entry 134217728}

pr1646v2XLBD7DsSpdMax OBJECT-TYPE
   SYNTAX      Integer32
   MAX-ACCESS  read-only
   STATUS      current
   DESCRIPTION
      "Path: line.performance.d7Line.dsSpeedMax

       formula = 32000 * ; 32000 /"
   ::= {pr1646v2XLBD7Entry 150994944}


pr1646v2XLBRel OBJECT IDENTIFIER ::= {pr1646v2XLB 30}

pr1646v2XLBRelSSC OBJECT IDENTIFIER ::= {pr1646v2XLBRel 1}

pr1646v2XLBRelEntry OBJECT IDENTIFIER ::= {pr1646v2XLBRelSSC 1}

pr1646v2XLBRelLDownCnt OBJECT-TYPE
   SYNTAX      Counter32
   MAX-ACCESS  read-only
   STATUS      current
   DESCRIPTION
      "Path: line.performance.line.linkDownCount

       32 bit unsigned wrappable counter."
   ::= {pr1646v2XLBRelEntry 16777216}

pr1646v2XLBRelLDownTme OBJECT-TYPE
   SYNTAX      TimeTicks
   MAX-ACCESS  read-only
   STATUS      current
   DESCRIPTION
      "Path: line.performance.line.linkDownTime

       Time in centi-second."
   ::= {pr1646v2XLBRelEntry 33554432}



fr1646v2XLB OBJECT IDENTIFIER ::= {r1646v2XLB 13}


fr1646v2XLBAlInfo OBJECT IDENTIFIER ::= {fr1646v2XLB 207}

fr1646v2XLBAlInfoSSC OBJECT IDENTIFIER ::= {fr1646v2XLBAlInfo 1}

fr1646v2XLBAlInfoEntry OBJECT IDENTIFIER ::= {fr1646v2XLBAlInfoSSC 1}

fr1646v2XLBAlInfoDiscr OBJECT-TYPE
   SYNTAX      Integer32
   MAX-ACCESS  read-only
   STATUS      current
   DESCRIPTION
      "Path: line.alarms.alarmInfo.discriminator"
   ::= {fr1646v2XLBAlInfoEntry 16777216}

fr1646v2XLBAlInfoCurrAlms OBJECT-TYPE
   SYNTAX      Integer32
   MAX-ACCESS  read-only
   STATUS      current
   DESCRIPTION
      "Path: line.alarms.alarmInfo.currentAlarms

       Bit meanings:
               bit 0 = linkDown"
   ::= {fr1646v2XLBAlInfoEntry 33554432}

fr1646v2XLBAlInfoPrevAlms OBJECT-TYPE
   SYNTAX      Integer32
   MAX-ACCESS  read-only
   STATUS      current
   DESCRIPTION
      "Path: line.alarms.alarmInfo.previousAlarms

       Bit meanings:
               bit 0 = linkDown"
   ::= {fr1646v2XLBAlInfoEntry 50331648}

fr1646v2XLBAlInfoAlMask OBJECT-TYPE
   SYNTAX      Integer32
   MAX-ACCESS  read-only
   STATUS      current
   DESCRIPTION
      "Path: line.alarms.alarmInfo.alarmMask

       Bit meanings:
               bit 0 = linkDown"
   ::= {fr1646v2XLBAlInfoEntry 67108864}

fr1646v2XLBAlInfoAlLvlLnkDwn OBJECT-TYPE
   SYNTAX      Integer32
   MAX-ACCESS  read-only
   STATUS      current
   DESCRIPTION
      "Path: line.alarms.alarmInfo.alarmLevel.linkDown"
   ::= {fr1646v2XLBAlInfoEntry 83951616}


fr1646v2XLBAlInfoE2 OBJECT IDENTIFIER ::= {fr1646v2XLBAlInfo 2}

fr1646v2XLBAlInfoE2Entry OBJECT IDENTIFIER ::= {fr1646v2XLBAlInfoE2 1}

fr1646v2XLBAlInfoE2LnkDwn OBJECT IDENTIFIER ::= {fr1646v2XLBAlInfoE2Entry 10}

fr1646v2XLBAlInfoE2LnkDwnPfx OBJECT IDENTIFIER ::= {fr1646v2XLBAlInfoE2LnkDwn 0}

fr1646v2XLBAlInfoE2LnkDwnOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'xdslLineAnnexB'
                (root='router1646') has changed from the ON to the OFF state."
   ::= {fr1646v2XLBAlInfoE2LnkDwnPfx 1}

fr1646v2XLBAlInfoE2LnkDwnOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'xdslLineAnnexB'
                (root='router1646') has changed from the OFF to the ON state."
   ::= {fr1646v2XLBAlInfoE2LnkDwnPfx 2}



ar1646v2XLB OBJECT IDENTIFIER ::= {r1646v2XLB 16}


ar1646v2XLBSendDebugCmd OBJECT-TYPE
   SYNTAX      Integer32
   MAX-ACCESS  read-write
   STATUS      current
   DESCRIPTION
      "Path: line.actions.sendDebugCmd
       Info: send debug command to Amazon"
   ::= {ar1646v2XLB 714}


ar1646v2XLBDebugCmd OBJECT-TYPE
   SYNTAX      DisplayString
   MAX-ACCESS  read-write
   STATUS      current
   DESCRIPTION
      "Path: line.actions.debugCmd
       Info: debug command"
   ::= {ar1646v2XLB 715}


ar1646v2XLBForceUBoot OBJECT-TYPE
   SYNTAX      Integer32
   MAX-ACCESS  read-write
   STATUS      current
   DESCRIPTION
      "Path: line.actions.forceUBoot
       Info: force DSL device in UBoot state"
   ::= {ar1646v2XLB 713}


ar1646v2XLBUpgradeAmazonFile OBJECT-TYPE
   SYNTAX      Integer32
   MAX-ACCESS  read-write
   STATUS      current
   DESCRIPTION
      "Path: line.actions.upgradeAmazonFile
       Info: upgrade file to Amazon"
   ::= {ar1646v2XLB 704}


ar1646v2XLBUpgradeFilename OBJECT IDENTIFIER ::= {ar1646v2XLB 705}

ar1646v2XLBUpgradeFilenameSSC OBJECT IDENTIFIER ::= {ar1646v2XLBUpgradeFilename 1}

ar1646v2XLBUpgradeFilenameEntry OBJECT IDENTIFIER ::= {ar1646v2XLBUpgradeFilenameSSC 1}

ar1646v2XLBUpgradeFilenameName OBJECT-TYPE
   SYNTAX      DisplayString
   MAX-ACCESS  read-write
   STATUS      current
   DESCRIPTION
      "Path: line.actions.upgradeFilename.name"
   ::= {ar1646v2XLBUpgradeFilenameEntry 16777216}


ar1646v2XLBDownloadAmazonFile OBJECT-TYPE
   SYNTAX      Integer32
   MAX-ACCESS  read-write
   STATUS      current
   DESCRIPTION
      "Path: line.actions.downloadAmazonFile
       Info: download file to Amazon"
   ::= {ar1646v2XLB 702}


ar1646v2XLBDownloadFilename OBJECT IDENTIFIER ::= {ar1646v2XLB 703}

ar1646v2XLBDownloadFilenameSSC OBJECT IDENTIFIER ::= {ar1646v2XLBDownloadFilename 1}

ar1646v2XLBDownloadFilenameEntry OBJECT IDENTIFIER ::= {ar1646v2XLBDownloadFilenameSSC 1}

ar1646v2XLBDownloadFilenameSrcName OBJECT-TYPE
   SYNTAX      DisplayString
   MAX-ACCESS  read-write
   STATUS      current
   DESCRIPTION
      "Path: line.actions.downloadFilename.srcName"
   ::= {ar1646v2XLBDownloadFilenameEntry 16777216}

ar1646v2XLBDownloadFilenameDstName OBJECT-TYPE
   SYNTAX      DisplayString
   MAX-ACCESS  read-write
   STATUS      current
   DESCRIPTION
      "Path: line.actions.downloadFilename.dstName"
   ::= {ar1646v2XLBDownloadFilenameEntry 33554432}

ar1646v2XLBDownloadFilenameOffset OBJECT-TYPE
   SYNTAX      Integer32
   MAX-ACCESS  read-write
   STATUS      current
   DESCRIPTION
      "Path: line.actions.downloadFilename.offset"
   ::= {ar1646v2XLBDownloadFilenameEntry 50331648}


ar1646v2XLBCacheResume OBJECT-TYPE
   SYNTAX      Integer32
   MAX-ACCESS  read-write
   STATUS      current
   DESCRIPTION
      "Path: line.actions.cacheResume
       Info: resume DSL cache"
   ::= {ar1646v2XLB 708}


ar1646v2XLBCacheSuspend OBJECT-TYPE
   SYNTAX      Integer32
   MAX-ACCESS  read-write
   STATUS      current
   DESCRIPTION
      "Path: line.actions.cacheSuspend
       Info: suspend DSL cache"
   ::= {ar1646v2XLB 707}


ar1646v2XLBResetAfterFailure OBJECT-TYPE
   SYNTAX      Integer32
   MAX-ACCESS  read-write
   STATUS      current
   DESCRIPTION
      "Path: line.actions.resetAfterFailure
       Info: enabled or disabled reset of Amazon"
   ::= {ar1646v2XLB 710}


ar1646v2XLBValue OBJECT-TYPE
   SYNTAX      INTEGER
               {
               disabled (0),
               enabled (1)
               }
   MAX-ACCESS  read-write
   STATUS      current
   DESCRIPTION
      "Path: line.actions.value
       Info: enabled or disabled reset of Amazon

       Possibilities:
               disabled   (0)
               enabled   (1)"
   ::= {ar1646v2XLB 711}


ar1646v2XLBForceUnReset OBJECT-TYPE
   SYNTAX      Integer32
   MAX-ACCESS  read-write
   STATUS      current
   DESCRIPTION
      "Path: line.actions.forceUnReset
       Info: reset DSL device"
   ::= {ar1646v2XLB 751}


ar1646v2XLBForceResetOnly OBJECT-TYPE
   SYNTAX      Integer32
   MAX-ACCESS  read-write
   STATUS      current
   DESCRIPTION
      "Path: line.actions.forceResetOnly
       Info: reset DSL device"
   ::= {ar1646v2XLB 750}


ar1646v2XLBForceReset OBJECT-TYPE
   SYNTAX      Integer32
   MAX-ACCESS  read-write
   STATUS      current
   DESCRIPTION
      "Path: line.actions.forceReset
       Info: reset DSL device"
   ::= {ar1646v2XLB 709}


ar1646v2XLBForceResyncCoreDump OBJECT-TYPE
   SYNTAX      Integer32
   MAX-ACCESS  read-write
   STATUS      current
   DESCRIPTION
      "Path: line.actions.forceResyncCoreDump
       Info: resync Amazon Core Dump"
   ::= {ar1646v2XLB 712}


ar1646v2XLBForceResync OBJECT-TYPE
   SYNTAX      Integer32
   MAX-ACCESS  read-write
   STATUS      current
   DESCRIPTION
      "Path: line.actions.forceResync
       Info: resync DSL cache"
   ::= {ar1646v2XLB 706}


ar1646v2XLBForceRetrain OBJECT-TYPE
   SYNTAX      Integer32
   MAX-ACCESS  read-write
   STATUS      current
   DESCRIPTION
      "Path: line.actions.forceRetrain
       Info: retrain DSL"
   ::= {ar1646v2XLB 143}


ar1646v2XLBClearCounters OBJECT-TYPE
   SYNTAX      Integer32
   MAX-ACCESS  read-write
   STATUS      current
   DESCRIPTION
      "Path: line.actions.clearCounters
       Info: reset counters"
   ::= {ar1646v2XLB 263}


ar1646v2XLBTestModeAction OBJECT-TYPE
   SYNTAX      Integer32
   MAX-ACCESS  read-write
   STATUS      current
   DESCRIPTION
      "Path: line.actions.testModeAction
       Info: set testMode"
   ::= {ar1646v2XLB 736}


ar1646v2XLBTestActivationType OBJECT-TYPE
   SYNTAX      INTEGER
               {
               disable (0),
               showtimeLock (1),
               quiet (2),
               trainingLock (3),
               lock (4),
               unlock (5),
               sleep (6)
               }
   MAX-ACCESS  read-write
   STATUS      current
   DESCRIPTION
      "Path: line.actions.testActivationType
       Info: testmode

       Possibilities:
               disable   (0)
               showtimeLock   (1)
               quiet   (2)
               trainingLock   (3)
               lock   (4)
               unlock   (5)
               sleep   (6)"
   ::= {ar1646v2XLB 737}



END
