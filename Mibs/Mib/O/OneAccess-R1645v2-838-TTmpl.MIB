OneAccess-R1645v2-838-TTmpl DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2TTmpl OBJECT IDENTIFIER ::= {r1645Rootv2 838}

r1645v2TTmplMOProp OBJECT IDENTIFIER ::= {r1645v2TTmpl 1}

r1645v2TTmplMOPropEntry OBJECT IDENTIFIER ::= {r1645v2TTmplMOProp 1}

r1645v2TTmplMOPropPath OBJECT-TYPE
   SYNTAX      ContainmentPath
   MAX-ACCESS  read-only
   STATUS      current
   DESCRIPTION
      "Textual description of the containment tree from the instance of
       the root object down to the instance of the current object."
   ::= {r1645v2TTmplMOPropEntry 3}

r1645v2TTmplMOPropRev OBJECT-TYPE
   SYNTAX      ObjectRevision
   MAX-ACCESS  read-only
   STATUS      current
   DESCRIPTION
      "This value corresponds with the revision of the MANAGED OBJECT."
   ::= {r1645v2TTmplMOPropEntry 4}



er1645v2TTmpl OBJECT IDENTIFIER ::= {r1645v2TTmpl 11}


er1645v2TTmplName OBJECT-TYPE
   SYNTAX      DisplayString
   MAX-ACCESS  read-write
   STATUS      current
   DESCRIPTION
      "Path: tunnels.editConf.name
       Info: config interface name"
   ::= {er1645v2TTmpl 7}


er1645v2TTmplIcf OBJECT IDENTIFIER ::= {er1645v2TTmpl 4}

er1645v2TTmplIcfSSCTable OBJECT-TYPE
   SYNTAX      SEQUENCE OF Er1645v2TTmplIcfEntry
   MAX-ACCESS  not-accessible
   STATUS      current
   DESCRIPTION
      ""
   ::= {er1645v2TTmplIcf 1}

er1645v2TTmplIcfEntry OBJECT-TYPE
   SYNTAX      Er1645v2TTmplIcfEntry
   MAX-ACCESS  not-accessible
   STATUS      current
   DESCRIPTION
      ""
   INDEX      { er1645v2TTmplIcfTableIx }
   ::= {er1645v2TTmplIcfSSCTable 1}

Er1645v2TTmplIcfEntry ::=
   SEQUENCE
      {
      er1645v2TTmplIcfActions
         VariableLengthTableActions,
      er1645v2TTmplIcfTableIx
         TableIndex,
      er1645v2TTmplIcfName
         DisplayString,
      er1645v2TTmplIcfRemark
         DisplayString,
      er1645v2TTmplIcfAdminStatus
         INTEGER,
      er1645v2TTmplIcfMode
         INTEGER,
      er1645v2TTmplIcfPriorityPolicy
         DisplayString,
      er1645v2TTmplIcfIpVrfRouter
         DisplayString,
      er1645v2TTmplIcfIpAdr
         IpAddress,
      er1645v2TTmplIcfIpNetm
         IpAddress,
      er1645v2TTmplIcfIpSNetName
         INTEGER,
      er1645v2TTmplIcfIpSNetCust
         DisplayString,
      er1645v2TTmplIcfIpRem
         IpAddress,
      er1645v2TTmplIcfIpUnnumbered
         DisplayString,
      er1645v2TTmplIcfIpAcceptLocAddr
         INTEGER,
      er1645v2TTmplIcfIpAcceptRemAddr
         INTEGER,
      er1645v2TTmplIcfIpGwPref
         Integer32,
      er1645v2TTmplIcfIpRsn
         INTEGER,
      er1645v2TTmplIcfIpMtu
         Integer32,
      er1645v2TTmplIcfIpMssAdjust
         INTEGER,
      er1645v2TTmplIcfIpRipMetric
         Integer32,
      er1645v2TTmplIcfIpRipMetricOut
         Integer32,
      er1645v2TTmplIcfIpRipMode
         INTEGER,
      er1645v2TTmplIcfIpRipTxVersion
         INTEGER,
      er1645v2TTmplIcfIpRipRxVersion
         INTEGER,
      er1645v2TTmplIcfIpRipSplitHorizon
         INTEGER,
      er1645v2TTmplIcfIpRipAuth
         INTEGER,
      er1645v2TTmplIcfIpRipFilter
         DisplayString,
      er1645v2TTmplIcfIpRipFilterIn
         DisplayString,
      er1645v2TTmplIcfIpRipSnapshot
         INTEGER,
      er1645v2TTmplIcfIpRipClearNextHop
         INTEGER,
      er1645v2TTmplIcfIpAccPol
         DisplayString,
      er1645v2TTmplIcfIpAB
         DisplayString,
      er1645v2TTmplIcfIpMA
         INTEGER,
      er1645v2TTmplIcfIpMF
         Integer32,
      er1645v2TTmplIcfIpDB
         INTEGER,
      er1645v2TTmplIcfIpIR
         INTEGER,
      er1645v2TTmplIcfIpIgmp
         INTEGER,
      er1645v2TTmplIcfIpNN
         DisplayString,
      er1645v2TTmplIcfIpPimMode
         INTEGER,
      er1645v2TTmplIcfIpPimDrPriority
         Counter32,
      er1645v2TTmplIcfIpPimHelloTime
         TimeTicks,
      er1645v2TTmplIcfIpPimPropagationDelay
         TimeTicks,
      er1645v2TTmplIcfIpPimOverrideInterval
         TimeTicks,
      er1645v2TTmplIcfIpPimBsrBorder
         INTEGER,
      er1645v2TTmplIcfIpPimTtlThreshold
         Integer32,
      er1645v2TTmplIcfIpIMNetworkUnreachable
         INTEGER,
      er1645v2TTmplIcfIpIMHostUnreachable
         INTEGER,
      er1645v2TTmplIcfIpIMProtocolUnreachable
         INTEGER,
      er1645v2TTmplIcfIpIMPortUnreachable
         INTEGER,
      er1645v2TTmplIcfIpIMMtuExceeded
         INTEGER,
      er1645v2TTmplIcfIpIMAdminProhibited
         INTEGER,
      er1645v2TTmplIcfIpIMTtlExceeded
         INTEGER,
      er1645v2TTmplIcfIpIMRedirect
         INTEGER,
      er1645v2TTmplIcfBridgingAccList
         DisplayString,
      er1645v2TTmplIcfBridgingInACL
         DisplayString,
      er1645v2TTmplIcfBridgingTp
         DisplayString,
      er1645v2TTmplIcfBridgingBrGrp
         DisplayString,
      er1645v2TTmplIcfBridgingLimBC
         INTEGER,
      er1645v2TTmplIcfBridgingPrivateMode
         INTEGER,
      er1645v2TTmplIcfBridgingLearning
         INTEGER,
      er1645v2TTmplIcfBridgingMaxCacheSize
         INTEGER,
      er1645v2TTmplIcfBridgingRelearnDropOnRelearn
         INTEGER,
      er1645v2TTmplIcfBridgingRelearnShutdownThreshold
         Integer32,
      er1645v2TTmplIcfBridgingRelearnShutdownTime
         TimeTicks,
      er1645v2TTmplIcfBridgingRelearnLoopDetection
         INTEGER,
      er1645v2TTmplIcfBridgingRelearnLoopDetectionInterval
         TimeTicks,
      er1645v2TTmplIcfBridgingVlanMemberShip
         INTEGER,
      er1645v2TTmplIcfBridgingVlTUntaggedAction
         INTEGER,
      er1645v2TTmplIcfBridgingVlTUntaggedTagInfoTpid
         INTEGER,
      er1645v2TTmplIcfBridgingVlTUntaggedTagInfoVid
         Integer32,
      er1645v2TTmplIcfBridgingVlTUnknownVlansAction
         INTEGER,
      er1645v2TTmplIcfBridgingVlTUnknownVlansTagInfoTpid
         INTEGER,
      er1645v2TTmplIcfBridgingVlTUnknownVlansTagInfoVid
         Integer32,
      er1645v2TTmplIcfBridgingDot1adType
         INTEGER,
      er1645v2TTmplIcfBridgingPriority
         Integer32,
      er1645v2TTmplIcfBridgingPathCost
         Integer32,
      er1645v2TTmplIcfBridgingInternalPathCost
         Integer32,
      er1645v2TTmplIcfBridgingTCD
         INTEGER,
      er1645v2TTmplIcfBridgingRestrictedRole
         INTEGER,
      er1645v2TTmplIcfBridgingAdminEdge
         INTEGER,
      er1645v2TTmplIcfBridgingOamMacDeviceMac
         DisplayString,
      er1645v2TTmplIcfBridgingOamMacUserMac
         OCTET STRING,
      er1645v2TTmplIcfBridgingOamMacBridgeMac
         DisplayString,
      er1645v2TTmplIcfBridgingMgmtInline
         INTEGER,
      er1645v2TTmplIcfBridgingL2ptMode
         INTEGER,
      er1645v2TTmplIcfBridgingL2ptProtocols
         Integer32,
      er1645v2TTmplIcfBridgingL2ptDestMac
         OCTET STRING,
      er1645v2TTmplIcfBridgingL2ptCos
         INTEGER,
      er1645v2TTmplIcfBridgingL2ptDropThrStp
         INTEGER,
      er1645v2TTmplIcfBridgingL2ptDropThrLldp
         INTEGER,
      er1645v2TTmplIcfBridgingL2ptDropThrOam
         INTEGER,
      er1645v2TTmplIcfBridgingL2ptDropThrCdp
         INTEGER,
      er1645v2TTmplIcfBridgingL2ptDropThrVtp
         INTEGER,
      er1645v2TTmplIcfBridgingL2ptDropThrLacp
         INTEGER,
      er1645v2TTmplIcfBridgingL2ptDropThrEfmOam
         INTEGER,
      er1645v2TTmplIcfBridgingL2ptDropThrPvst
         INTEGER,
      er1645v2TTmplIcfBridgingL2ptDropThrMmrp
         INTEGER,
      er1645v2TTmplIcfBridgingL2ptDropThrMvrp
         INTEGER,
      er1645v2TTmplIcfBridgingL2ptDropThrGvrp
         INTEGER,
      er1645v2TTmplIcfBridgingL2ptDropThrGmrp
         INTEGER,
      er1645v2TTmplIcfBridgingL2ptDropThrDtp
         INTEGER,
      er1645v2TTmplIcfBridgingL2ptDropThrPagp
         INTEGER,
      er1645v2TTmplIcfBridgingL2ptDropThrUdld
         INTEGER,
      er1645v2TTmplIcfL2tpLocalIpAddress
         IpAddress,
      er1645v2TTmplIcfL2tpRemoteIpAddress
         IpAddress,
      er1645v2TTmplIcfL2tpRemoteDnsName
         DisplayString,
      er1645v2TTmplIcfL2tpAuthen
         INTEGER,
      er1645v2TTmplIcfL2tpPppNam
         DisplayString,
      er1645v2TTmplIcfL2tpPppSec
         DisplayString,
      er1645v2TTmplIcfL2tpEncMPppSec
         INTEGER,
      er1645v2TTmplIcfL2tpEncPppSec
         DisplayString,
      er1645v2TTmplIcfL2tpLnkMOperation
         INTEGER,
      er1645v2TTmplIcfL2tpLnkMInterval
         TimeTicks,
      er1645v2TTmplIcfL2tpLnkMRepTimeOut
         TimeTicks,
      er1645v2TTmplIcfL2tpLnkMFailsPrmt
         Integer32,
      er1645v2TTmplIcfL2tpType
         INTEGER,
      er1645v2TTmplIcfL2tpDataseqnr
         INTEGER,
      er1645v2TTmplIcfL2tpIpsecFdx
         DisplayString,
      er1645v2TTmplIcfL2tpIpsecHdxIn
         DisplayString,
      er1645v2TTmplIcfL2tpIpsecHdxOut
         DisplayString,
      er1645v2TTmplIcfL2tpIpsecPsCfg
         DisplayString,
      er1645v2TTmplIcfL2tpIpsecPsLIdIp
         IpAddress,
      er1645v2TTmplIcfL2tpIpsecPsLIdHn
         DisplayString,
      er1645v2TTmplIcfL2tpIpsecPsLIdUn
         DisplayString,
      er1645v2TTmplIcfL2tpIpsecPsRIdIp
         IpAddress,
      er1645v2TTmplIcfL2tpIpsecPsRIdHn
         DisplayString,
      er1645v2TTmplIcfL2tpIpsecPsRIdUn
         DisplayString,
      er1645v2TTmplIcfL2tpIpsecPsKey
         DisplayString,
      er1645v2TTmplIcfL2tpIpsecPsEncMKey
         INTEGER,
      er1645v2TTmplIcfL2tpIpsecPsEncKey
         DisplayString,
      er1645v2TTmplIcfL2tpIpsecPsPIdProt
         INTEGER,
      er1645v2TTmplIcfL2tpIpsecPsPIdLocAddr
         IpAddress,
      er1645v2TTmplIcfL2tpIpsecPsPIdLocMask
         IpAddress,
      er1645v2TTmplIcfL2tpIpsecPsPIdLocPort
         INTEGER,
      er1645v2TTmplIcfL2tpIpsecPsPIdRemAddr
         IpAddress,
      er1645v2TTmplIcfL2tpIpsecPsPIdRemMask
         IpAddress,
      er1645v2TTmplIcfL2tpIpsecPsPIdRemPort
         INTEGER,
      er1645v2TTmplIcfL2tpIpsecCeCfg
         DisplayString,
      er1645v2TTmplIcfL2tpIpsecCeLIdIp
         IpAddress,
      er1645v2TTmplIcfL2tpIpsecCeLIdHn
         DisplayString,
      er1645v2TTmplIcfL2tpIpsecCeLIdUn
         DisplayString,
      er1645v2TTmplIcfL2tpIpsecCeLIdDn
         DisplayString,
      er1645v2TTmplIcfL2tpIpsecCeRIdIp
         IpAddress,
      er1645v2TTmplIcfL2tpIpsecCeRIdHn
         DisplayString,
      er1645v2TTmplIcfL2tpIpsecCeRIdUn
         DisplayString,
      er1645v2TTmplIcfL2tpIpsecCeRIdDn
         DisplayString,
      er1645v2TTmplIcfL2tpIpsecCePIdProt
         INTEGER,
      er1645v2TTmplIcfL2tpIpsecCePIdLocAddr
         IpAddress,
      er1645v2TTmplIcfL2tpIpsecCePIdLocMask
         IpAddress,
      er1645v2TTmplIcfL2tpIpsecCePIdLocPort
         INTEGER,
      er1645v2TTmplIcfL2tpIpsecCePIdRemAddr
         IpAddress,
      er1645v2TTmplIcfL2tpIpsecCePIdRemMask
         IpAddress,
      er1645v2TTmplIcfL2tpIpsecCePIdRemPort
         INTEGER,
      er1645v2TTmplIcfL2tpKeepaliveTO
         Integer32,
      er1645v2TTmplIcfL2tpNoTraffT0
         Integer32,
      er1645v2TTmplIcfL2tpMode
         INTEGER,
      er1645v2TTmplIcfL2tpAuth
         INTEGER,
      er1645v2TTmplIcfL2tpSecret
         DisplayString,
      er1645v2TTmplIcfL2tpTos
         INTEGER,
      er1645v2TTmplIcfL2tpRetrans
         Integer32,
      er1645v2TTmplIcfL2tpTransmitws
         Integer32,
      er1645v2TTmplIcfL2tpRcsws
         Integer32,
      er1645v2TTmplIcfL2tpUdpcheck
         INTEGER,
      er1645v2TTmplIcfL2tpCalledNr
         DisplayString,
      er1645v2TTmplIcfL2tpSpeed
         Integer32,
      er1645v2TTmplIcfL2tpMtu
         Integer32,
      er1645v2TTmplIcfL2tpHostName
         DisplayString,
      er1645v2TTmplIcfBackupInterface
         DisplayString,
      er1645v2TTmplIcfBackupTimeOut
         Integer32,
      er1645v2TTmplIcfBackupAutoRetry
         INTEGER,
      er1645v2TTmplIcfInbBwCir
         Integer32,
      er1645v2TTmplIcfInbBwTc
         INTEGER,
      er1645v2TTmplIcfInbBwCorrType
         INTEGER,
      er1645v2TTmplIcfInbBwCorrPredefEncapsFrameRelay
         DisplayString,
      er1645v2TTmplIcfInbBwCorrPredefEncapsPpp
         DisplayString,
      er1645v2TTmplIcfInbBwCorrPredefEncapsAtmHl
         INTEGER,
      er1645v2TTmplIcfInbBwCorrPredefEncapsAtmMp
         INTEGER,
      er1645v2TTmplIcfInbBwCorrPredefEncapsHdlc
         DisplayString,
      er1645v2TTmplIcfInbBwCorrPredefEncapsEfmFs
         Integer32,
      er1645v2TTmplIcfInbBwCorrPredefEncapsEfmIb
         Integer32,
      er1645v2TTmplIcfInbBwCorrPredefMode
         INTEGER,
      er1645v2TTmplIcfInbBwCorrManualOverhead
         Integer32,
      er1645v2TTmplIcfInbBwCorrManualFrameData
         Counter32,
      er1645v2TTmplIcfInbBwCorrManualFrameHeader
         Counter32,
      er1645v2TTmplIcfInbBwMaxFifoQLen
         Integer32,
      er1645v2TTmplIcfInbBwPriorityPolicy
         DisplayString,
      er1645v2TTmplIcfBandwidthMode
         INTEGER,
      er1645v2TTmplIcfBandwidthCir
         Integer32,
      er1645v2TTmplIcfBandwidthEir
         Integer32,
      er1645v2TTmplIcfBandwidthUnit
         INTEGER,
      er1645v2TTmplIcfBandwidthTc
         INTEGER,
      er1645v2TTmplIcfBandwidthTcFactor
         INTEGER,
      er1645v2TTmplIcfBandwidthCorrType
         INTEGER,
      er1645v2TTmplIcfBandwidthCorrPredefEncapsFrameRelay
         DisplayString,
      er1645v2TTmplIcfBandwidthCorrPredefEncapsPpp
         DisplayString,
      er1645v2TTmplIcfBandwidthCorrPredefEncapsAtmHl
         INTEGER,
      er1645v2TTmplIcfBandwidthCorrPredefEncapsAtmMp
         INTEGER,
      er1645v2TTmplIcfBandwidthCorrPredefEncapsHdlc
         DisplayString,
      er1645v2TTmplIcfBandwidthCorrPredefEncapsEfmFs
         Integer32,
      er1645v2TTmplIcfBandwidthCorrPredefEncapsEfmIb
         Integer32,
      er1645v2TTmplIcfBandwidthCorrPredefMode
         INTEGER,
      er1645v2TTmplIcfBandwidthCorrManualOverhead
         Integer32,
      er1645v2TTmplIcfBandwidthCorrManualFrameData
         Counter32,
      er1645v2TTmplIcfBandwidthCorrManualFrameHeader
         Counter32,
      er1645v2TTmplIcfBandwidthMaxFifoQLen
         Integer32,
      er1645v2TTmplIcfBandwidthDeFlagCir
         INTEGER,
      er1645v2TTmplIcfBandwidthDeFlagEir
         INTEGER,
      er1645v2TTmplIcfBandwidthDeFlagViolate
         INTEGER,
      er1645v2TTmplIcfBandwidthActCirActNone
         OCTET STRING,
      er1645v2TTmplIcfBandwidthActCirActEthCos1
         INTEGER,
      er1645v2TTmplIcfBandwidthActCirActEthDei1
         INTEGER,
      er1645v2TTmplIcfBandwidthActCirActEthCos2
         INTEGER,
      er1645v2TTmplIcfBandwidthActCirActEthDei2
         INTEGER,
      er1645v2TTmplIcfBandwidthActCirActEthCos3
         INTEGER,
      er1645v2TTmplIcfBandwidthActCirActEthDei3
         INTEGER,
      er1645v2TTmplIcfBandwidthActCirActEthCos4
         INTEGER,
      er1645v2TTmplIcfBandwidthActCirActEthDei4
         INTEGER,
      er1645v2TTmplIcfBandwidthActCirActEthCos5
         INTEGER,
      er1645v2TTmplIcfBandwidthActCirActEthDei5
         INTEGER,
      er1645v2TTmplIcfBandwidthActCirActEthCos6
         INTEGER,
      er1645v2TTmplIcfBandwidthActCirActEthDei6
         INTEGER,
      er1645v2TTmplIcfBandwidthActCirActEthCos7
         INTEGER,
      er1645v2TTmplIcfBandwidthActCirActEthDei7
         INTEGER,
      er1645v2TTmplIcfBandwidthActCirActEthCos8
         INTEGER,
      er1645v2TTmplIcfBandwidthActCirActEthDei8
         INTEGER,
      er1645v2TTmplIcfBandwidthActCirActEthTos
         INTEGER,
      er1645v2TTmplIcfBandwidthActCirActEthQueue
         INTEGER,
      er1645v2TTmplIcfBandwidthActCirActEthDrpLev
         INTEGER,
      er1645v2TTmplIcfBandwidthActCirActEthDeFlag
         INTEGER,
      er1645v2TTmplIcfBandwidthActCirActIpTos
         INTEGER,
      er1645v2TTmplIcfBandwidthActCirActIpQueue
         INTEGER,
      er1645v2TTmplIcfBandwidthActCirActIpDrpLev
         INTEGER,
      er1645v2TTmplIcfBandwidthActCirActIpDeFlag
         INTEGER,
      er1645v2TTmplIcfBandwidthActEirActNone
         OCTET STRING,
      er1645v2TTmplIcfBandwidthActEirActEthCos1
         INTEGER,
      er1645v2TTmplIcfBandwidthActEirActEthDei1
         INTEGER,
      er1645v2TTmplIcfBandwidthActEirActEthCos2
         INTEGER,
      er1645v2TTmplIcfBandwidthActEirActEthDei2
         INTEGER,
      er1645v2TTmplIcfBandwidthActEirActEthCos3
         INTEGER,
      er1645v2TTmplIcfBandwidthActEirActEthDei3
         INTEGER,
      er1645v2TTmplIcfBandwidthActEirActEthCos4
         INTEGER,
      er1645v2TTmplIcfBandwidthActEirActEthDei4
         INTEGER,
      er1645v2TTmplIcfBandwidthActEirActEthCos5
         INTEGER,
      er1645v2TTmplIcfBandwidthActEirActEthDei5
         INTEGER,
      er1645v2TTmplIcfBandwidthActEirActEthCos6
         INTEGER,
      er1645v2TTmplIcfBandwidthActEirActEthDei6
         INTEGER,
      er1645v2TTmplIcfBandwidthActEirActEthCos7
         INTEGER,
      er1645v2TTmplIcfBandwidthActEirActEthDei7
         INTEGER,
      er1645v2TTmplIcfBandwidthActEirActEthCos8
         INTEGER,
      er1645v2TTmplIcfBandwidthActEirActEthDei8
         INTEGER,
      er1645v2TTmplIcfBandwidthActEirActEthTos
         INTEGER,
      er1645v2TTmplIcfBandwidthActEirActEthQueue
         INTEGER,
      er1645v2TTmplIcfBandwidthActEirActEthDrpLev
         INTEGER,
      er1645v2TTmplIcfBandwidthActEirActEthDeFlag
         INTEGER,
      er1645v2TTmplIcfBandwidthActEirActIpTos
         INTEGER,
      er1645v2TTmplIcfBandwidthActEirActIpQueue
         INTEGER,
      er1645v2TTmplIcfBandwidthActEirActIpDrpLev
         INTEGER,
      er1645v2TTmplIcfBandwidthActEirActIpDeFlag
         INTEGER,
      er1645v2TTmplIcfBandwidthActViolActNone
         OCTET STRING,
      er1645v2TTmplIcfBandwidthActViolActDrop
         OCTET STRING,
      er1645v2TTmplIcfBandwidthActViolActEthCos1
         INTEGER,
      er1645v2TTmplIcfBandwidthActViolActEthDei1
         INTEGER,
      er1645v2TTmplIcfBandwidthActViolActEthCos2
         INTEGER,
      er1645v2TTmplIcfBandwidthActViolActEthDei2
         INTEGER,
      er1645v2TTmplIcfBandwidthActViolActEthCos3
         INTEGER,
      er1645v2TTmplIcfBandwidthActViolActEthDei3
         INTEGER,
      er1645v2TTmplIcfBandwidthActViolActEthCos4
         INTEGER,
      er1645v2TTmplIcfBandwidthActViolActEthDei4
         INTEGER,
      er1645v2TTmplIcfBandwidthActViolActEthCos5
         INTEGER,
      er1645v2TTmplIcfBandwidthActViolActEthDei5
         INTEGER,
      er1645v2TTmplIcfBandwidthActViolActEthCos6
         INTEGER,
      er1645v2TTmplIcfBandwidthActViolActEthDei6
         INTEGER,
      er1645v2TTmplIcfBandwidthActViolActEthCos7
         INTEGER,
      er1645v2TTmplIcfBandwidthActViolActEthDei7
         INTEGER,
      er1645v2TTmplIcfBandwidthActViolActEthCos8
         INTEGER,
      er1645v2TTmplIcfBandwidthActViolActEthDei8
         INTEGER,
      er1645v2TTmplIcfBandwidthActViolActEthTos
         INTEGER,
      er1645v2TTmplIcfBandwidthActViolActEthQueue
         INTEGER,
      er1645v2TTmplIcfBandwidthActViolActEthDrpLev
         INTEGER,
      er1645v2TTmplIcfBandwidthActViolActEthDeFlag
         INTEGER,
      er1645v2TTmplIcfBandwidthActViolActIpTos
         INTEGER,
      er1645v2TTmplIcfBandwidthActViolActIpQueue
         INTEGER,
      er1645v2TTmplIcfBandwidthActViolActIpDrpLev
         INTEGER,
      er1645v2TTmplIcfBandwidthActViolActIpDeFlag
         INTEGER
      }

er1645v2TTmplIcfActions OBJECT-TYPE
   SYNTAX      VariableLengthTableActions
   MAX-ACCESS  read-write
   STATUS      current
   DESCRIPTION
      "By way of this field, some manipulations
       on this table may be performed."
   ::= {er1645v2TTmplIcfEntry 2}

er1645v2TTmplIcfTableIx OBJECT-TYPE
   SYNTAX      TableIndex
   MAX-ACCESS  not-accessible
   STATUS      current
   DESCRIPTION
      ""
   ::= {er1645v2TTmplIcfEntry 11}

er1645v2TTmplIcfName OBJECT-TYPE
   SYNTAX      DisplayString
   MAX-ACCESS  read-write
   STATUS      current
   DESCRIPTION
      "Path: tunnels.editConf.ipsecL2tpTunnels.name"
   ::= {er1645v2TTmplIcfEntry 16777216}

er1645v2TTmplIcfRemark OBJECT-TYPE
   SYNTAX      DisplayString
   MAX-ACCESS  read-write
   STATUS      current
   DESCRIPTION
      "Path: tunnels.editConf.ipsecL2tpTunnels.remark"
   ::= {er1645v2TTmplIcfEntry 1157627904}

er1645v2TTmplIcfAdminStatus OBJECT-TYPE
   SYNTAX      INTEGER
               {
               up (1),
               down (2)
               }
   MAX-ACCESS  read-write
   STATUS      current
   DESCRIPTION
      "Path: tunnels.editConf.ipsecL2tpTunnels.adminStatus

       Possibilities:
               up   (1)
               down   (2)"
   ::= {er1645v2TTmplIcfEntry 33554432}

er1645v2TTmplIcfMode OBJECT-TYPE
   SYNTAX      INTEGER
               {
               routing (1),
               bridging (2),
               routingAndBridging (3)
               }
   MAX-ACCESS  read-write
   STATUS      current
   DESCRIPTION
      "Path: tunnels.editConf.ipsecL2tpTunnels.mode

       Possibilities:
               routing   (1)
               bridging   (2)
               routingAndBridging   (3)"
   ::= {er1645v2TTmplIcfEntry 67108864}

er1645v2TTmplIcfPriorityPolicy OBJECT-TYPE
   SYNTAX      DisplayString
   MAX-ACCESS  read-write
   STATUS      current
   DESCRIPTION
      "Path: tunnels.editConf.ipsecL2tpTunnels.priorityPolicy"
   ::= {er1645v2TTmplIcfEntry 83886080}

er1645v2TTmplIcfIpVrfRouter OBJECT-TYPE
   SYNTAX      DisplayString
   MAX-ACCESS  read-write
   STATUS      current
   DESCRIPTION
      "Path: tunnels.editConf.ipsecL2tpTunnels.ip.vrfRouter"
   ::= {er1645v2TTmplIcfEntry 53215232}

er1645v2TTmplIcfIpAdr OBJECT-TYPE
   SYNTAX      IpAddress
   MAX-ACCESS  read-write
   STATUS      current
   DESCRIPTION
      "Path: tunnels.editConf.ipsecL2tpTunnels.ip.address"
   ::= {er1645v2TTmplIcfEntry 58261504}

er1645v2TTmplIcfIpNetm OBJECT-TYPE
   SYNTAX      IpAddress
   MAX-ACCESS  read-write
   STATUS      current
   DESCRIPTION
      "Path: tunnels.editConf.ipsecL2tpTunnels.ip.netMask"
   ::= {er1645v2TTmplIcfEntry 58392576}

er1645v2TTmplIcfIpSNetName OBJECT-TYPE
   SYNTAX      INTEGER
               {
               slOPTg (0),
               corp (2),
               dmz (3),
               internet (1)
               }
   MAX-ACCESS  read-write
   STATUS      current
   DESCRIPTION
      "Path: tunnels.editConf.ipsecL2tpTunnels.ip.sNet.name

       Possibilities:
               <OPT>   (0)
               corp   (2)
               dmz   (3)
               internet   (1)"
   ::= {er1645v2TTmplIcfEntry 53674240}

er1645v2TTmplIcfIpSNetCust OBJECT-TYPE
   SYNTAX      DisplayString
   MAX-ACCESS  read-write
   STATUS      current
   DESCRIPTION
      "Path: tunnels.editConf.ipsecL2tpTunnels.ip.sNet.custom"
   ::= {er1645v2TTmplIcfEntry 53674496}

er1645v2TTmplIcfIpRem OBJECT-TYPE
   SYNTAX      IpAddress
   MAX-ACCESS  read-write
   STATUS      current
   DESCRIPTION
      "Path: tunnels.editConf.ipsecL2tpTunnels.ip.remote"
   ::= {er1645v2TTmplIcfEntry 58458112}

er1645v2TTmplIcfIpUnnumbered OBJECT-TYPE
   SYNTAX      DisplayString
   MAX-ACCESS  read-write
   STATUS      current
   DESCRIPTION
      "Path: tunnels.editConf.ipsecL2tpTunnels.ip.unnumbered"
   ::= {er1645v2TTmplIcfEntry 52625408}

er1645v2TTmplIcfIpAcceptLocAddr OBJECT-TYPE
   SYNTAX      INTEGER
               {
               disabled (0),
               enabled (1)
               }
   MAX-ACCESS  read-write
   STATUS      current
   DESCRIPTION
      "Path: tunnels.editConf.ipsecL2tpTunnels.ip.acceptLocAddr

       Possibilities:
               disabled   (0)
               enabled   (1)"
   ::= {er1645v2TTmplIcfEntry 50593792}

er1645v2TTmplIcfIpAcceptRemAddr OBJECT-TYPE
   SYNTAX      INTEGER
               {
               disabled (0),
               enabled (1)
               }
   MAX-ACCESS  read-write
   STATUS      current
   DESCRIPTION
      "Path: tunnels.editConf.ipsecL2tpTunnels.ip.acceptRemAddr

       Possibilities:
               disabled   (0)
               enabled   (1)"
   ::= {er1645v2TTmplIcfEntry 50724864}

er1645v2TTmplIcfIpGwPref OBJECT-TYPE
   SYNTAX      Integer32
   MAX-ACCESS  read-write
   STATUS      current
   DESCRIPTION
      "Path: tunnels.editConf.ipsecL2tpTunnels.ip.gatewayPreference"
   ::= {er1645v2TTmplIcfEntry 52690944}

er1645v2TTmplIcfIpRsn OBJECT-TYPE
   SYNTAX      INTEGER
               {
               disabled (0),
               enabled (1)
               }
   MAX-ACCESS  read-write
   STATUS      current
   DESCRIPTION
      "Path: tunnels.editConf.ipsecL2tpTunnels.ip.requestSubnet

       Possibilities:
               disabled   (0)
               enabled   (1)"
   ::= {er1645v2TTmplIcfEntry 56688640}

er1645v2TTmplIcfIpMtu OBJECT-TYPE
   SYNTAX      Integer32
   MAX-ACCESS  read-write
   STATUS      current
   DESCRIPTION
      "Path: tunnels.editConf.ipsecL2tpTunnels.ip.mtu"
   ::= {er1645v2TTmplIcfEntry 52953088}

er1645v2TTmplIcfIpMssAdjust OBJECT-TYPE
   SYNTAX      INTEGER
               {
               disabled (0),
               auto (65536)
               }
   MAX-ACCESS  read-write
   STATUS      current
   DESCRIPTION
      "Path: tunnels.editConf.ipsecL2tpTunnels.ip.mssAdjust

       Possibilities:
               disabled   (0)
               auto   (65536)"
   ::= {er1645v2TTmplIcfEntry 53280768}

er1645v2TTmplIcfIpRipMetric OBJECT-TYPE
   SYNTAX      Integer32
   MAX-ACCESS  read-write
   STATUS      current
   DESCRIPTION
      "Path: tunnels.editConf.ipsecL2tpTunnels.ip.rip.metric"
   ::= {er1645v2TTmplIcfEntry 51712768}

er1645v2TTmplIcfIpRipMetricOut OBJECT-TYPE
   SYNTAX      Integer32
   MAX-ACCESS  read-write
   STATUS      current
   DESCRIPTION
      "Path: tunnels.editConf.ipsecL2tpTunnels.ip.rip.metricOut"
   ::= {er1645v2TTmplIcfEntry 51713024}

er1645v2TTmplIcfIpRipMode OBJECT-TYPE
   SYNTAX      INTEGER
               {
               disabled (0),
               passive (1),
               active (2)
               }
   MAX-ACCESS  read-write
   STATUS      current
   DESCRIPTION
      "Path: tunnels.editConf.ipsecL2tpTunnels.ip.rip.mode

       Possibilities:
               disabled   (0)
               passive   (1)
               active   (2)"
   ::= {er1645v2TTmplIcfEntry 51713280}

er1645v2TTmplIcfIpRipTxVersion OBJECT-TYPE
   SYNTAX      INTEGER
               {
               rip1 (0),
               rip2 (1),
               rip1mcompatible (2)
               }
   MAX-ACCESS  read-write
   STATUS      current
   DESCRIPTION
      "Path: tunnels.editConf.ipsecL2tpTunnels.ip.rip.txVersion

       Possibilities:
               rip1   (0)
               rip2   (1)
               rip1-compatible   (2)"
   ::= {er1645v2TTmplIcfEntry 51716864}

er1645v2TTmplIcfIpRipRxVersion OBJECT-TYPE
   SYNTAX      INTEGER
               {
               rip1only (0),
               rip2only (1),
               rip12 (2)
               }
   MAX-ACCESS  read-write
   STATUS      current
   DESCRIPTION
      "Path: tunnels.editConf.ipsecL2tpTunnels.ip.rip.rxVersion

       Possibilities:
               rip1only   (0)
               rip2only   (1)
               rip1&2   (2)"
   ::= {er1645v2TTmplIcfEntry 51717120}

er1645v2TTmplIcfIpRipSplitHorizon OBJECT-TYPE
   SYNTAX      INTEGER
               {
               disabled (0),
               enabled (1),
               poisonedReverse (2)
               }
   MAX-ACCESS  read-write
   STATUS      current
   DESCRIPTION
      "Path: tunnels.editConf.ipsecL2tpTunnels.ip.rip.splitHorizon

       Possibilities:
               disabled   (0)
               enabled   (1)
               poisonedReverse   (2)"
   ::= {er1645v2TTmplIcfEntry 51713792}

er1645v2TTmplIcfIpRipAuth OBJECT-TYPE
   SYNTAX      INTEGER
               {
               disabled (0),
               texts (1),
               md5 (2)
               }
   MAX-ACCESS  read-write
   STATUS      current
   DESCRIPTION
      "Path: tunnels.editConf.ipsecL2tpTunnels.ip.rip.authentication

       Possibilities:
               disabled   (0)
               text    (1)
               md5   (2)"
   ::= {er1645v2TTmplIcfEntry 51712512}

er1645v2TTmplIcfIpRipFilter OBJECT-TYPE
   SYNTAX      DisplayString
   MAX-ACCESS  read-write
   STATUS      current
   DESCRIPTION
      "Path: tunnels.editConf.ipsecL2tpTunnels.ip.rip.filter"
   ::= {er1645v2TTmplIcfEntry 51716096}

er1645v2TTmplIcfIpRipFilterIn OBJECT-TYPE
   SYNTAX      DisplayString
   MAX-ACCESS  read-write
   STATUS      current
   DESCRIPTION
      "Path: tunnels.editConf.ipsecL2tpTunnels.ip.rip.filterIn"
   ::= {er1645v2TTmplIcfEntry 51716352}

er1645v2TTmplIcfIpRipSnapshot OBJECT-TYPE
   SYNTAX      INTEGER
               {
               disabled (0),
               enabled (1)
               }
   MAX-ACCESS  read-write
   STATUS      current
   DESCRIPTION
      "Path: tunnels.editConf.ipsecL2tpTunnels.ip.rip.snapshot

       Possibilities:
               disabled   (0)
               enabled   (1)"
   ::= {er1645v2TTmplIcfEntry 51708160}

er1645v2TTmplIcfIpRipClearNextHop OBJECT-TYPE
   SYNTAX      INTEGER
               {
               disabled (0),
               enabled (1)
               }
   MAX-ACCESS  read-write
   STATUS      current
   DESCRIPTION
      "Path: tunnels.editConf.ipsecL2tpTunnels.ip.rip.clearNextHop

       Possibilities:
               disabled   (0)
               enabled   (1)"
   ::= {er1645v2TTmplIcfEntry 51708416}

er1645v2TTmplIcfIpAccPol OBJECT-TYPE
   SYNTAX      DisplayString
   MAX-ACCESS  read-write
   STATUS      current
   DESCRIPTION
      "Path: tunnels.editConf.ipsecL2tpTunnels.ip.accessPolicy"
   ::= {er1645v2TTmplIcfEntry 53084160}

er1645v2TTmplIcfIpAB OBJECT-TYPE
   SYNTAX      DisplayString
   MAX-ACCESS  read-write
   STATUS      current
   DESCRIPTION
      "Path: tunnels.editConf.ipsecL2tpTunnels.ip.trafficPolicy"
   ::= {er1645v2TTmplIcfEntry 51249152}

er1645v2TTmplIcfIpMA OBJECT-TYPE
   SYNTAX      INTEGER
               {
               disabled (0),
               enabled (1)
               }
   MAX-ACCESS  read-write
   STATUS      current
   DESCRIPTION
      "Path: tunnels.editConf.ipsecL2tpTunnels.ip.mgmtAccess

       Possibilities:
               disabled   (0)
               enabled   (1)"
   ::= {er1645v2TTmplIcfEntry 51380224}

er1645v2TTmplIcfIpMF OBJECT-TYPE
   SYNTAX      Integer32
   MAX-ACCESS  read-write
   STATUS      current
   DESCRIPTION
      "Path: tunnels.editConf.ipsecL2tpTunnels.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2TTmplIcfEntry 51445760}

er1645v2TTmplIcfIpDB OBJECT-TYPE
   SYNTAX      INTEGER
               {
               disabled (0),
               enabled (1)
               }
   MAX-ACCESS  read-write
   STATUS      current
   DESCRIPTION
      "Path: tunnels.editConf.ipsecL2tpTunnels.ip.directedBroadcasts

       Possibilities:
               disabled   (0)
               enabled   (1)"
   ::= {er1645v2TTmplIcfEntry 51773440}

er1645v2TTmplIcfIpIR OBJECT-TYPE
   SYNTAX      INTEGER
               {
               disabled (0),
               enabled (1)
               }
   MAX-ACCESS  read-write
   STATUS      current
   DESCRIPTION
      "Path: tunnels.editConf.ipsecL2tpTunnels.ip.icmpRedirects

       Possibilities:
               disabled   (0)
               enabled   (1)"
   ::= {er1645v2TTmplIcfEntry 52035584}

er1645v2TTmplIcfIpIgmp OBJECT-TYPE
   SYNTAX      INTEGER
               {
               disabled (0),
               proxy (1),
               router (2),
               v3Router (5)
               }
   MAX-ACCESS  read-write
   STATUS      current
   DESCRIPTION
      "Path: tunnels.editConf.ipsecL2tpTunnels.ip.igmp

       Possibilities:
               disabled   (0)
               proxy   (1)
               router   (2)
               v3Router   (5)"
   ::= {er1645v2TTmplIcfEntry 52428800}

er1645v2TTmplIcfIpNN OBJECT-TYPE
   SYNTAX      DisplayString
   MAX-ACCESS  read-write
   STATUS      current
   DESCRIPTION
      "Path: tunnels.editConf.ipsecL2tpTunnels.ip.nat"
   ::= {er1645v2TTmplIcfEntry 52101120}

er1645v2TTmplIcfIpPimMode OBJECT-TYPE
   SYNTAX      INTEGER
               {
               disabled (0),
               sparse (1),
               passive (2)
               }
   MAX-ACCESS  read-write
   STATUS      current
   DESCRIPTION
      "Path: tunnels.editConf.ipsecL2tpTunnels.ip.pim.mode

       Possibilities:
               disabled   (0)
               sparse   (1)
               passive   (2)"
   ::= {er1645v2TTmplIcfEntry 53346560}

er1645v2TTmplIcfIpPimDrPriority OBJECT-TYPE
   SYNTAX      Counter32
   MAX-ACCESS  read-write
   STATUS      current
   DESCRIPTION
      "Path: tunnels.editConf.ipsecL2tpTunnels.ip.pim.drPriority

       32 bit unsigned wrappable counter."
   ::= {er1645v2TTmplIcfEntry 53346816}

er1645v2TTmplIcfIpPimHelloTime OBJECT-TYPE
   SYNTAX      TimeTicks
   MAX-ACCESS  read-write
   STATUS      current
   DESCRIPTION
      "Path: tunnels.editConf.ipsecL2tpTunnels.ip.pim.helloTime

       Time in centi-second."
   ::= {er1645v2TTmplIcfEntry 53347072}

er1645v2TTmplIcfIpPimPropagationDelay OBJECT-TYPE
   SYNTAX      TimeTicks
   MAX-ACCESS  read-write
   STATUS      current
   DESCRIPTION
      "Path: tunnels.editConf.ipsecL2tpTunnels.ip.pim.propagationDelay

       Time in centi-second."
   ::= {er1645v2TTmplIcfEntry 53347328}

er1645v2TTmplIcfIpPimOverrideInterval OBJECT-TYPE
   SYNTAX      TimeTicks
   MAX-ACCESS  read-write
   STATUS      current
   DESCRIPTION
      "Path: tunnels.editConf.ipsecL2tpTunnels.ip.pim.overrideInterval

       Time in centi-second."
   ::= {er1645v2TTmplIcfEntry 53347584}

er1645v2TTmplIcfIpPimBsrBorder OBJECT-TYPE
   SYNTAX      INTEGER
               {
               disabled (0),
               enabled (1)
               }
   MAX-ACCESS  read-write
   STATUS      current
   DESCRIPTION
      "Path: tunnels.editConf.ipsecL2tpTunnels.ip.pim.bsrBorder

       Possibilities:
               disabled   (0)
               enabled   (1)"
   ::= {er1645v2TTmplIcfEntry 53347840}

er1645v2TTmplIcfIpPimTtlThreshold OBJECT-TYPE
   SYNTAX      Integer32
   MAX-ACCESS  read-write
   STATUS      current
   DESCRIPTION
      "Path: tunnels.editConf.ipsecL2tpTunnels.ip.pim.ttlThreshold"
   ::= {er1645v2TTmplIcfEntry 53348096}

er1645v2TTmplIcfIpIMNetworkUnreachable OBJECT-TYPE
   SYNTAX      INTEGER
               {
               disabled (0),
               enabled (1)
               }
   MAX-ACCESS  read-write
   STATUS      current
   DESCRIPTION
      "Path: tunnels.editConf.ipsecL2tpTunnels.ip.icmpMessages.networkUnreachable

       Possibilities:
               disabled   (0)
               enabled   (1)"
   ::= {er1645v2TTmplIcfEntry 53412096}

er1645v2TTmplIcfIpIMHostUnreachable OBJECT-TYPE
   SYNTAX      INTEGER
               {
               disabled (0),
               enabled (1)
               }
   MAX-ACCESS  read-write
   STATUS      current
   DESCRIPTION
      "Path: tunnels.editConf.ipsecL2tpTunnels.ip.icmpMessages.hostUnreachable

       Possibilities:
               disabled   (0)
               enabled   (1)"
   ::= {er1645v2TTmplIcfEntry 53412352}

er1645v2TTmplIcfIpIMProtocolUnreachable OBJECT-TYPE
   SYNTAX      INTEGER
               {
               disabled (0),
               enabled (1)
               }
   MAX-ACCESS  read-write
   STATUS      current
   DESCRIPTION
      "Path: tunnels.editConf.ipsecL2tpTunnels.ip.icmpMessages.protocolUnreachable

       Possibilities:
               disabled   (0)
               enabled   (1)"
   ::= {er1645v2TTmplIcfEntry 53412608}

er1645v2TTmplIcfIpIMPortUnreachable OBJECT-TYPE
   SYNTAX      INTEGER
               {
               disabled (0),
               enabled (1)
               }
   MAX-ACCESS  read-write
   STATUS      current
   DESCRIPTION
      "Path: tunnels.editConf.ipsecL2tpTunnels.ip.icmpMessages.portUnreachable

       Possibilities:
               disabled   (0)
               enabled   (1)"
   ::= {er1645v2TTmplIcfEntry 53412864}

er1645v2TTmplIcfIpIMMtuExceeded OBJECT-TYPE
   SYNTAX      INTEGER
               {
               disabled (0),
               enabled (1)
               }
   MAX-ACCESS  read-write
   STATUS      current
   DESCRIPTION
      "Path: tunnels.editConf.ipsecL2tpTunnels.ip.icmpMessages.mtuExceeded

       Possibilities:
               disabled   (0)
               enabled   (1)"
   ::= {er1645v2TTmplIcfEntry 53413120}

er1645v2TTmplIcfIpIMAdminProhibited OBJECT-TYPE
   SYNTAX      INTEGER
               {
               disabled (0),
               enabled (1)
               }
   MAX-ACCESS  read-write
   STATUS      current
   DESCRIPTION
      "Path: tunnels.editConf.ipsecL2tpTunnels.ip.icmpMessages.adminProhibited

       Possibilities:
               disabled   (0)
               enabled   (1)"
   ::= {er1645v2TTmplIcfEntry 53413376}

er1645v2TTmplIcfIpIMTtlExceeded OBJECT-TYPE
   SYNTAX      INTEGER
               {
               disabled (0),
               enabled (1)
               }
   MAX-ACCESS  read-write
   STATUS      current
   DESCRIPTION
      "Path: tunnels.editConf.ipsecL2tpTunnels.ip.icmpMessages.ttlExceeded

       Possibilities:
               disabled   (0)
               enabled   (1)"
   ::= {er1645v2TTmplIcfEntry 53413632}

er1645v2TTmplIcfIpIMRedirect OBJECT-TYPE
   SYNTAX      INTEGER
               {
               disabled (0),
               enabled (1)
               }
   MAX-ACCESS  read-write
   STATUS      current
   DESCRIPTION
      "Path: tunnels.editConf.ipsecL2tpTunnels.ip.icmpMessages.redirect

       Possibilities:
               disabled   (0)
               enabled   (1)"
   ::= {er1645v2TTmplIcfEntry 53413888}

er1645v2TTmplIcfBridgingAccList OBJECT-TYPE
   SYNTAX      DisplayString
   MAX-ACCESS  read-write
   STATUS      current
   DESCRIPTION
      "Path: tunnels.editConf.ipsecL2tpTunnels.bridging.accessList"
   ::= {er1645v2TTmplIcfEntry 453246976}

er1645v2TTmplIcfBridgingInACL OBJECT-TYPE
   SYNTAX      DisplayString
   MAX-ACCESS  read-write
   STATUS      current
   DESCRIPTION
      "Path: tunnels.editConf.ipsecL2tpTunnels.bridging.inAccessList"
   ::= {er1645v2TTmplIcfEntry 456916992}

er1645v2TTmplIcfBridgingTp OBJECT-TYPE
   SYNTAX      DisplayString
   MAX-ACCESS  read-write
   STATUS      current
   DESCRIPTION
      "Path: tunnels.editConf.ipsecL2tpTunnels.bridging.trafficPolicy"
   ::= {er1645v2TTmplIcfEntry 454295552}

er1645v2TTmplIcfBridgingBrGrp OBJECT-TYPE
   SYNTAX      DisplayString
   MAX-ACCESS  read-write
   STATUS      current
   DESCRIPTION
      "Path: tunnels.editConf.ipsecL2tpTunnels.bridging.bridgeGroup"
   ::= {er1645v2TTmplIcfEntry 454819840}

er1645v2TTmplIcfBridgingLimBC OBJECT-TYPE
   SYNTAX      INTEGER
               {
               disabled (0),
               enabled (1)
               }
   MAX-ACCESS  read-write
   STATUS      current
   DESCRIPTION
      "Path: tunnels.editConf.ipsecL2tpTunnels.bridging.limitBroadcasts

       Possibilities:
               disabled   (0)
               enabled   (1)"
   ::= {er1645v2TTmplIcfEntry 455081984}

er1645v2TTmplIcfBridgingPrivateMode OBJECT-TYPE
   SYNTAX      INTEGER
               {
               disabled (0),
               enabled (1)
               }
   MAX-ACCESS  read-write
   STATUS      current
   DESCRIPTION
      "Path: tunnels.editConf.ipsecL2tpTunnels.bridging.privateMode

       Possibilities:
               disabled   (0)
               enabled   (1)"
   ::= {er1645v2TTmplIcfEntry 459538432}

er1645v2TTmplIcfBridgingLearning OBJECT-TYPE
   SYNTAX      INTEGER
               {
               disabled (0),
               enabled (1)
               }
   MAX-ACCESS  read-write
   STATUS      current
   DESCRIPTION
      "Path: tunnels.editConf.ipsecL2tpTunnels.bridging.learning

       Possibilities:
               disabled   (0)
               enabled   (1)"
   ::= {er1645v2TTmplIcfEntry 456130560}

er1645v2TTmplIcfBridgingMaxCacheSize OBJECT-TYPE
   SYNTAX      INTEGER
               {
               unlimited (0)
               }
   MAX-ACCESS  read-write
   STATUS      current
   DESCRIPTION
      "Path: tunnels.editConf.ipsecL2tpTunnels.bridging.maxCacheSize

       Possibilities:
               unlimited   (0)"
   ::= {er1645v2TTmplIcfEntry 456392704}

er1645v2TTmplIcfBridgingRelearnDropOnRelearn OBJECT-TYPE
   SYNTAX      INTEGER
               {
               disabled (0),
               enabled (1)
               }
   MAX-ACCESS  read-write
   STATUS      current
   DESCRIPTION
      "Path: tunnels.editConf.ipsecL2tpTunnels.bridging.relearn.dropOnRelearn

       Possibilities:
               disabled   (0)
               enabled   (1)"
   ::= {er1645v2TTmplIcfEntry 456655872}

er1645v2TTmplIcfBridgingRelearnShutdownThreshold OBJECT-TYPE
   SYNTAX      Integer32
   MAX-ACCESS  read-write
   STATUS      current
   DESCRIPTION
      "Path: tunnels.editConf.ipsecL2tpTunnels.bridging.relearn.shutdownThreshold"
   ::= {er1645v2TTmplIcfEntry 456656896}

er1645v2TTmplIcfBridgingRelearnShutdownTime OBJECT-TYPE
   SYNTAX      TimeTicks
   MAX-ACCESS  read-write
   STATUS      current
   DESCRIPTION
      "Path: tunnels.editConf.ipsecL2tpTunnels.bridging.relearn.shutdownTime

       Time in centi-second."
   ::= {er1645v2TTmplIcfEntry 456657920}

er1645v2TTmplIcfBridgingRelearnLoopDetection OBJECT-TYPE
   SYNTAX      INTEGER
               {
               disabled (0),
               passive (1),
               active (2)
               }
   MAX-ACCESS  read-write
   STATUS      current
   DESCRIPTION
      "Path: tunnels.editConf.ipsecL2tpTunnels.bridging.relearn.loopDetection

       Possibilities:
               disabled   (0)
               passive   (1)
               active   (2)"
   ::= {er1645v2TTmplIcfEntry 456658944}

er1645v2TTmplIcfBridgingRelearnLoopDetectionInterval OBJECT-TYPE
   SYNTAX      TimeTicks
   MAX-ACCESS  read-write
   STATUS      current
   DESCRIPTION
      "Path: tunnels.editConf.ipsecL2tpTunnels.bridging.relearn.loopDetectionInterval

       Time in centi-second."
   ::= {er1645v2TTmplIcfEntry 456659968}

er1645v2TTmplIcfBridgingVlanMemberShip OBJECT-TYPE
   SYNTAX      INTEGER
               {
               all (0),
               none (1),
               grouped (2)
               }
   MAX-ACCESS  read-write
   STATUS      current
   DESCRIPTION
      "Path: tunnels.editConf.ipsecL2tpTunnels.bridging.vlanMemberShip

       Possibilities:
               all   (0)
               none   (1)
               grouped   (2)"
   ::= {er1645v2TTmplIcfEntry 457965568}

er1645v2TTmplIcfBridgingVlTUntaggedAction OBJECT-TYPE
   SYNTAX      INTEGER
               {
               discard (0),
               accept (1),
               tag (2)
               }
   MAX-ACCESS  read-write
   STATUS      current
   DESCRIPTION
      "Path: tunnels.editConf.ipsecL2tpTunnels.bridging.vlanTagging.untagged.action

       Possibilities:
               discard   (0)
               accept   (1)
               tag   (2)"
   ::= {er1645v2TTmplIcfEntry 459055104}

er1645v2TTmplIcfBridgingVlTUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: tunnels.editConf.ipsecL2tpTunnels.bridging.vlanTagging.untagged.tagInfo.tpid

       Possibilities:
               dot1Q   (33024)
               dot1ad   (34984)
               0x9100   (37120)
               0x9200   (37376)
               0x9300   (37632)"
   ::= {er1645v2TTmplIcfEntry 459059712}

er1645v2TTmplIcfBridgingVlTUntaggedTagInfoVid OBJECT-TYPE
   SYNTAX      Integer32
   MAX-ACCESS  read-write
   STATUS      current
   DESCRIPTION
      "Path: tunnels.editConf.ipsecL2tpTunnels.bridging.vlanTagging.untagged.tagInfo.vid"
   ::= {er1645v2TTmplIcfEntry 459060224}

er1645v2TTmplIcfBridgingVlTUnknownVlansAction OBJECT-TYPE
   SYNTAX      INTEGER
               {
               discard (0),
               accept (1),
               tag (2)
               }
   MAX-ACCESS  read-write
   STATUS      current
   DESCRIPTION
      "Path: tunnels.editConf.ipsecL2tpTunnels.bridging.vlanTagging.unknownVlans.action

       Possibilities:
               discard   (0)
               accept   (1)
               tag   (2)"
   ::= {er1645v2TTmplIcfEntry 459120640}

er1645v2TTmplIcfBridgingVlTUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: tunnels.editConf.ipsecL2tpTunnels.bridging.vlanTagging.unknownVlans.tagInfo.tpid

       Possibilities:
               dot1Q   (33024)
               dot1ad   (34984)
               0x9100   (37120)
               0x9200   (37376)
               0x9300   (37632)"
   ::= {er1645v2TTmplIcfEntry 459125248}

er1645v2TTmplIcfBridgingVlTUnknownVlansTagInfoVid OBJECT-TYPE
   SYNTAX      Integer32
   MAX-ACCESS  read-write
   STATUS      current
   DESCRIPTION
      "Path: tunnels.editConf.ipsecL2tpTunnels.bridging.vlanTagging.unknownVlans.tagInfo.vid"
   ::= {er1645v2TTmplIcfEntry 459125760}

er1645v2TTmplIcfBridgingDot1adType OBJECT-TYPE
   SYNTAX      INTEGER
               {
               slOPTg (0),
               cPort (4),
               sPort (1),
               nni (2)
               }
   MAX-ACCESS  read-write
   STATUS      current
   DESCRIPTION
      "Path: tunnels.editConf.ipsecL2tpTunnels.bridging.dot1ad.type

       Possibilities:
               <OPT>   (0)
               cPort   (4)
               sPort   (1)
               nni   (2)"
   ::= {er1645v2TTmplIcfEntry 460850176}

er1645v2TTmplIcfBridgingPriority OBJECT-TYPE
   SYNTAX      Integer32
   MAX-ACCESS  read-write
   STATUS      current
   DESCRIPTION
      "Path: tunnels.editConf.ipsecL2tpTunnels.bridging.priority"
   ::= {er1645v2TTmplIcfEntry 453509120}

er1645v2TTmplIcfBridgingPathCost OBJECT-TYPE
   SYNTAX      Integer32
   MAX-ACCESS  read-write
   STATUS      current
   DESCRIPTION
      "Path: tunnels.editConf.ipsecL2tpTunnels.bridging.pathCost"
   ::= {er1645v2TTmplIcfEntry 453771264}

er1645v2TTmplIcfBridgingInternalPathCost OBJECT-TYPE
   SYNTAX      Integer32
   MAX-ACCESS  read-write
   STATUS      current
   DESCRIPTION
      "Path: tunnels.editConf.ipsecL2tpTunnels.bridging.internalPathCost"
   ::= {er1645v2TTmplIcfEntry 457703424}

er1645v2TTmplIcfBridgingTCD OBJECT-TYPE
   SYNTAX      INTEGER
               {
               disabled (0),
               enabled (1)
               }
   MAX-ACCESS  read-write
   STATUS      current
   DESCRIPTION
      "Path: tunnels.editConf.ipsecL2tpTunnels.bridging.topologyChangeDetection

       Possibilities:
               disabled   (0)
               enabled   (1)"
   ::= {er1645v2TTmplIcfEntry 454033408}

er1645v2TTmplIcfBridgingRestrictedRole OBJECT-TYPE
   SYNTAX      INTEGER
               {
               disabled (0),
               enabled (1)
               }
   MAX-ACCESS  read-write
   STATUS      current
   DESCRIPTION
      "Path: tunnels.editConf.ipsecL2tpTunnels.bridging.restrictedRole

       Possibilities:
               disabled   (0)
               enabled   (1)"
   ::= {er1645v2TTmplIcfEntry 458227712}

er1645v2TTmplIcfBridgingAdminEdge OBJECT-TYPE
   SYNTAX      INTEGER
               {
               disabled (0),
               enabled (1)
               }
   MAX-ACCESS  read-write
   STATUS      current
   DESCRIPTION
      "Path: tunnels.editConf.ipsecL2tpTunnels.bridging.adminEdge

       Possibilities:
               disabled   (0)
               enabled   (1)"
   ::= {er1645v2TTmplIcfEntry 457179136}

er1645v2TTmplIcfBridgingOamMacDeviceMac OBJECT-TYPE
   SYNTAX      DisplayString
   MAX-ACCESS  read-write
   STATUS      current
   DESCRIPTION
      "Path: tunnels.editConf.ipsecL2tpTunnels.bridging.ethOam.macAddress.deviceMac"
   ::= {er1645v2TTmplIcfEntry 458506496}

er1645v2TTmplIcfBridgingOamMacUserMac OBJECT-TYPE
   SYNTAX      OCTET STRING
   MAX-ACCESS  read-write
   STATUS      current
   DESCRIPTION
      "Path: tunnels.editConf.ipsecL2tpTunnels.bridging.ethOam.macAddress.userMac

       MAC address."
   ::= {er1645v2TTmplIcfEntry 458506368}

er1645v2TTmplIcfBridgingOamMacBridgeMac OBJECT-TYPE
   SYNTAX      DisplayString
   MAX-ACCESS  read-write
   STATUS      current
   DESCRIPTION
      "Path: tunnels.editConf.ipsecL2tpTunnels.bridging.ethOam.macAddress.bridgeMac"
   ::= {er1645v2TTmplIcfEntry 458506432}

er1645v2TTmplIcfBridgingMgmtInline OBJECT-TYPE
   SYNTAX      INTEGER
               {
               disabled (0),
               enabled (1)
               }
   MAX-ACCESS  read-write
   STATUS      current
   DESCRIPTION
      "Path: tunnels.editConf.ipsecL2tpTunnels.bridging.mgmtInline

       Possibilities:
               disabled   (0)
               enabled   (1)"
   ::= {er1645v2TTmplIcfEntry 458752000}

er1645v2TTmplIcfBridgingL2ptMode OBJECT-TYPE
   SYNTAX      INTEGER
               {
               disabled (0),
               enabled (1)
               }
   MAX-ACCESS  read-write
   STATUS      current
   DESCRIPTION
      "Path: tunnels.editConf.ipsecL2tpTunnels.bridging.l2ProtTunnel.mode

       Possibilities:
               disabled   (0)
               enabled   (1)"
   ::= {er1645v2TTmplIcfEntry 459292672}

er1645v2TTmplIcfBridgingL2ptProtocols OBJECT-TYPE
   SYNTAX      Integer32
   MAX-ACCESS  read-write
   STATUS      current
   DESCRIPTION
      "Path: tunnels.editConf.ipsecL2tpTunnels.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1645v2TTmplIcfEntry 459309056}

er1645v2TTmplIcfBridgingL2ptDestMac OBJECT-TYPE
   SYNTAX      OCTET STRING
   MAX-ACCESS  read-write
   STATUS      current
   DESCRIPTION
      "Path: tunnels.editConf.ipsecL2tpTunnels.bridging.l2ProtTunnel.destinationMac

       MAC address."
   ::= {er1645v2TTmplIcfEntry 459325440}

er1645v2TTmplIcfBridgingL2ptCos OBJECT-TYPE
   SYNTAX      INTEGER
               {
               unchanged (255)
               }
   MAX-ACCESS  read-write
   STATUS      current
   DESCRIPTION
      "Path: tunnels.editConf.ipsecL2tpTunnels.bridging.l2ProtTunnel.cos

       Possibilities:
               unchanged   (255)"
   ::= {er1645v2TTmplIcfEntry 459341824}

er1645v2TTmplIcfBridgingL2ptDropThrStp OBJECT-TYPE
   SYNTAX      INTEGER
               {
               unlimited (0)
               }
   UNITS       "packets/sec"
   MAX-ACCESS  read-write
   STATUS      current
   DESCRIPTION
      "Path: tunnels.editConf.ipsecL2tpTunnels.bridging.l2ProtTunnel.dropThresholds.stp

       unit name = packets/sec

       Possibilities:
               unlimited   (0)"
   ::= {er1645v2TTmplIcfEntry 459358272}

er1645v2TTmplIcfBridgingL2ptDropThrLldp OBJECT-TYPE
   SYNTAX      INTEGER
               {
               unlimited (0)
               }
   UNITS       "packets/sec"
   MAX-ACCESS  read-write
   STATUS      current
   DESCRIPTION
      "Path: tunnels.editConf.ipsecL2tpTunnels.bridging.l2ProtTunnel.dropThresholds.lldp

       unit name = packets/sec

       Possibilities:
               unlimited   (0)"
   ::= {er1645v2TTmplIcfEntry 459358336}

er1645v2TTmplIcfBridgingL2ptDropThrOam OBJECT-TYPE
   SYNTAX      INTEGER
               {
               unlimited (0)
               }
   UNITS       "packets/sec"
   MAX-ACCESS  read-write
   STATUS      current
   DESCRIPTION
      "Path: tunnels.editConf.ipsecL2tpTunnels.bridging.l2ProtTunnel.dropThresholds.oam

       unit name = packets/sec

       Possibilities:
               unlimited   (0)"
   ::= {er1645v2TTmplIcfEntry 459358400}

er1645v2TTmplIcfBridgingL2ptDropThrCdp OBJECT-TYPE
   SYNTAX      INTEGER
               {
               unlimited (0)
               }
   UNITS       "packets/sec"
   MAX-ACCESS  read-write
   STATUS      current
   DESCRIPTION
      "Path: tunnels.editConf.ipsecL2tpTunnels.bridging.l2ProtTunnel.dropThresholds.cdp

       unit name = packets/sec

       Possibilities:
               unlimited   (0)"
   ::= {er1645v2TTmplIcfEntry 459358464}

er1645v2TTmplIcfBridgingL2ptDropThrVtp OBJECT-TYPE
   SYNTAX      INTEGER
               {
               unlimited (0)
               }
   UNITS       "packets/sec"
   MAX-ACCESS  read-write
   STATUS      current
   DESCRIPTION
      "Path: tunnels.editConf.ipsecL2tpTunnels.bridging.l2ProtTunnel.dropThresholds.vtp

       unit name = packets/sec

       Possibilities:
               unlimited   (0)"
   ::= {er1645v2TTmplIcfEntry 459358528}

er1645v2TTmplIcfBridgingL2ptDropThrLacp OBJECT-TYPE
   SYNTAX      INTEGER
               {
               unlimited (0)
               }
   UNITS       "packets/sec"
   MAX-ACCESS  read-write
   STATUS      current
   DESCRIPTION
      "Path: tunnels.editConf.ipsecL2tpTunnels.bridging.l2ProtTunnel.dropThresholds.lacp

       unit name = packets/sec

       Possibilities:
               unlimited   (0)"
   ::= {er1645v2TTmplIcfEntry 459358592}

er1645v2TTmplIcfBridgingL2ptDropThrEfmOam OBJECT-TYPE
   SYNTAX      INTEGER
               {
               unlimited (0)
               }
   UNITS       "packets/sec"
   MAX-ACCESS  read-write
   STATUS      current
   DESCRIPTION
      "Path: tunnels.editConf.ipsecL2tpTunnels.bridging.l2ProtTunnel.dropThresholds.efmOam

       unit name = packets/sec

       Possibilities:
               unlimited   (0)"
   ::= {er1645v2TTmplIcfEntry 459358656}

er1645v2TTmplIcfBridgingL2ptDropThrPvst OBJECT-TYPE
   SYNTAX      INTEGER
               {
               unlimited (0)
               }
   UNITS       "packets/sec"
   MAX-ACCESS  read-write
   STATUS      current
   DESCRIPTION
      "Path: tunnels.editConf.ipsecL2tpTunnels.bridging.l2ProtTunnel.dropThresholds.pvst

       unit name = packets/sec

       Possibilities:
               unlimited   (0)"
   ::= {er1645v2TTmplIcfEntry 459358720}

er1645v2TTmplIcfBridgingL2ptDropThrMmrp OBJECT-TYPE
   SYNTAX      INTEGER
               {
               unlimited (0)
               }
   UNITS       "packets/sec"
   MAX-ACCESS  read-write
   STATUS      current
   DESCRIPTION
      "Path: tunnels.editConf.ipsecL2tpTunnels.bridging.l2ProtTunnel.dropThresholds.mmrp

       unit name = packets/sec

       Possibilities:
               unlimited   (0)"
   ::= {er1645v2TTmplIcfEntry 459358784}

er1645v2TTmplIcfBridgingL2ptDropThrMvrp OBJECT-TYPE
   SYNTAX      INTEGER
               {
               unlimited (0)
               }
   UNITS       "packets/sec"
   MAX-ACCESS  read-write
   STATUS      current
   DESCRIPTION
      "Path: tunnels.editConf.ipsecL2tpTunnels.bridging.l2ProtTunnel.dropThresholds.mvrp

       unit name = packets/sec

       Possibilities:
               unlimited   (0)"
   ::= {er1645v2TTmplIcfEntry 459358848}

er1645v2TTmplIcfBridgingL2ptDropThrGvrp OBJECT-TYPE
   SYNTAX      INTEGER
               {
               unlimited (0)
               }
   UNITS       "packets/sec"
   MAX-ACCESS  read-write
   STATUS      current
   DESCRIPTION
      "Path: tunnels.editConf.ipsecL2tpTunnels.bridging.l2ProtTunnel.dropThresholds.gvrp

       unit name = packets/sec

       Possibilities:
               unlimited   (0)"
   ::= {er1645v2TTmplIcfEntry 459358912}

er1645v2TTmplIcfBridgingL2ptDropThrGmrp OBJECT-TYPE
   SYNTAX      INTEGER
               {
               unlimited (0)
               }
   UNITS       "packets/sec"
   MAX-ACCESS  read-write
   STATUS      current
   DESCRIPTION
      "Path: tunnels.editConf.ipsecL2tpTunnels.bridging.l2ProtTunnel.dropThresholds.gmrp

       unit name = packets/sec

       Possibilities:
               unlimited   (0)"
   ::= {er1645v2TTmplIcfEntry 459358976}

er1645v2TTmplIcfBridgingL2ptDropThrDtp OBJECT-TYPE
   SYNTAX      INTEGER
               {
               unlimited (0)
               }
   UNITS       "packets/sec"
   MAX-ACCESS  read-write
   STATUS      current
   DESCRIPTION
      "Path: tunnels.editConf.ipsecL2tpTunnels.bridging.l2ProtTunnel.dropThresholds.dtp

       unit name = packets/sec

       Possibilities:
               unlimited   (0)"
   ::= {er1645v2TTmplIcfEntry 459359040}

er1645v2TTmplIcfBridgingL2ptDropThrPagp OBJECT-TYPE
   SYNTAX      INTEGER
               {
               unlimited (0)
               }
   UNITS       "packets/sec"
   MAX-ACCESS  read-write
   STATUS      current
   DESCRIPTION
      "Path: tunnels.editConf.ipsecL2tpTunnels.bridging.l2ProtTunnel.dropThresholds.pagp

       unit name = packets/sec

       Possibilities:
               unlimited   (0)"
   ::= {er1645v2TTmplIcfEntry 459359104}

er1645v2TTmplIcfBridgingL2ptDropThrUdld OBJECT-TYPE
   SYNTAX      INTEGER
               {
               unlimited (0)
               }
   UNITS       "packets/sec"
   MAX-ACCESS  read-write
   STATUS      current
   DESCRIPTION
      "Path: tunnels.editConf.ipsecL2tpTunnels.bridging.l2ProtTunnel.dropThresholds.udld

       unit name = packets/sec

       Possibilities:
               unlimited   (0)"
   ::= {er1645v2TTmplIcfEntry 459359168}

er1645v2TTmplIcfL2tpLocalIpAddress OBJECT-TYPE
   SYNTAX      IpAddress
   MAX-ACCESS  read-write
   STATUS      current
   DESCRIPTION
      "Path: tunnels.editConf.ipsecL2tpTunnels.l2tp.localIpAddress"
   ::= {er1645v2TTmplIcfEntry 302120960}

er1645v2TTmplIcfL2tpRemoteIpAddress OBJECT-TYPE
   SYNTAX      IpAddress
   MAX-ACCESS  read-write
   STATUS      current
   DESCRIPTION
      "Path: tunnels.editConf.ipsecL2tpTunnels.l2tp.remoteIpAddress"
   ::= {er1645v2TTmplIcfEntry 302252032}

er1645v2TTmplIcfL2tpRemoteDnsName OBJECT-TYPE
   SYNTAX      DisplayString
   MAX-ACCESS  read-write
   STATUS      current
   DESCRIPTION
      "Path: tunnels.editConf.ipsecL2tpTunnels.l2tp.remoteDnsName"
   ::= {er1645v2TTmplIcfEntry 305790976}

er1645v2TTmplIcfL2tpAuthen OBJECT-TYPE
   SYNTAX      INTEGER
               {
               disabled (0),
               chap (1),
               pap (2),
               chapOrPap (3),
               msChap (4),
               msChapV2 (5)
               }
   MAX-ACCESS  read-write
   STATUS      current
   DESCRIPTION
      "Path: tunnels.editConf.ipsecL2tpTunnels.l2tp.pppAuthentication

       Possibilities:
               disabled   (0)
               chap   (1)
               pap   (2)
               chapOrPap   (3)
               msChap   (4)
               msChapV2   (5)"
   ::= {er1645v2TTmplIcfEntry 303693824}

er1645v2TTmplIcfL2tpPppNam OBJECT-TYPE
   SYNTAX      DisplayString
   MAX-ACCESS  read-write
   STATUS      current
   DESCRIPTION
      "Path: tunnels.editConf.ipsecL2tpTunnels.l2tp.pppSessionName"
   ::= {er1645v2TTmplIcfEntry 304611328}

er1645v2TTmplIcfL2tpPppSec OBJECT-TYPE
   SYNTAX      DisplayString
   MAX-ACCESS  read-write
   STATUS      current
   DESCRIPTION
      "Path: tunnels.editConf.ipsecL2tpTunnels.l2tp.pppSessionSecret"
   ::= {er1645v2TTmplIcfEntry 304742400}

er1645v2TTmplIcfL2tpEncMPppSec OBJECT-TYPE
   SYNTAX      INTEGER
               {
               none (1),
               encrypt (2),
               encType1 (3),
               invalid (128)
               }
   MAX-ACCESS  read-write
   STATUS      current
   DESCRIPTION
      "Path: tunnels.editConf.ipsecL2tpTunnels.l2tp.encModePppSessionSecret

       Possibilities:
               none   (1)
               encrypt   (2)
               encType1   (3)
               invalid   (128)"
   ::= {er1645v2TTmplIcfEntry 304873472}

er1645v2TTmplIcfL2tpEncPppSec OBJECT-TYPE
   SYNTAX      DisplayString
   MAX-ACCESS  read-write
   STATUS      current
   DESCRIPTION
      "Path: tunnels.editConf.ipsecL2tpTunnels.l2tp.encPppSessionSecret"
   ::= {er1645v2TTmplIcfEntry 305004544}

er1645v2TTmplIcfL2tpLnkMOperation OBJECT-TYPE
   SYNTAX      INTEGER
               {
               disabled (0),
               enabled (1)
               }
   MAX-ACCESS  read-write
   STATUS      current
   DESCRIPTION
      "Path: tunnels.editConf.ipsecL2tpTunnels.l2tp.linkMonitoring.operation

       Possibilities:
               disabled   (0)
               enabled   (1)"
   ::= {er1645v2TTmplIcfEntry 305922560}

er1645v2TTmplIcfL2tpLnkMInterval OBJECT-TYPE
   SYNTAX      TimeTicks
   MAX-ACCESS  read-write
   STATUS      current
   DESCRIPTION
      "Path: tunnels.editConf.ipsecL2tpTunnels.l2tp.linkMonitoring.interval

       Time in centi-second."
   ::= {er1645v2TTmplIcfEntry 305923072}

er1645v2TTmplIcfL2tpLnkMRepTimeOut OBJECT-TYPE
   SYNTAX      TimeTicks
   MAX-ACCESS  read-write
   STATUS      current
   DESCRIPTION
      "Path: tunnels.editConf.ipsecL2tpTunnels.l2tp.linkMonitoring.replyTimeOut

       Time in centi-second."
   ::= {er1645v2TTmplIcfEntry 305923584}

er1645v2TTmplIcfL2tpLnkMFailsPrmt OBJECT-TYPE
   SYNTAX      Integer32
   MAX-ACCESS  read-write
   STATUS      current
   DESCRIPTION
      "Path: tunnels.editConf.ipsecL2tpTunnels.l2tp.linkMonitoring.failsPermitted"
   ::= {er1645v2TTmplIcfEntry 305924096}

er1645v2TTmplIcfL2tpType OBJECT-TYPE
   SYNTAX      INTEGER
               {
               outgoingDial (0),
               outgoingLeasedLine (1),
               incoming (2)
               }
   MAX-ACCESS  read-write
   STATUS      current
   DESCRIPTION
      "Path: tunnels.editConf.ipsecL2tpTunnels.l2tp.type

       Possibilities:
               outgoingDial   (0)
               outgoingLeasedLine   (1)
               incoming   (2)"
   ::= {er1645v2TTmplIcfEntry 303824896}

er1645v2TTmplIcfL2tpDataseqnr OBJECT-TYPE
   SYNTAX      INTEGER
               {
               off (0),
               on (1)
               }
   MAX-ACCESS  read-write
   STATUS      current
   DESCRIPTION
      "Path: tunnels.editConf.ipsecL2tpTunnels.l2tp.dataChannelSequenceNumbering

       Possibilities:
               off   (0)
               on   (1)"
   ::= {er1645v2TTmplIcfEntry 302383104}

er1645v2TTmplIcfL2tpIpsecFdx OBJECT-TYPE
   SYNTAX      DisplayString
   MAX-ACCESS  read-write
   STATUS      current
   DESCRIPTION
      "Path: tunnels.editConf.ipsecL2tpTunnels.l2tp.ipsec.fdxManualSA"
   ::= {er1645v2TTmplIcfEntry 304103424}

er1645v2TTmplIcfL2tpIpsecHdxIn OBJECT-TYPE
   SYNTAX      DisplayString
   MAX-ACCESS  read-write
   STATUS      current
   DESCRIPTION
      "Path: tunnels.editConf.ipsecL2tpTunnels.l2tp.ipsec.hdxManualSA.inbound"
   ::= {er1645v2TTmplIcfEntry 304119872}

er1645v2TTmplIcfL2tpIpsecHdxOut OBJECT-TYPE
   SYNTAX      DisplayString
   MAX-ACCESS  read-write
   STATUS      current
   DESCRIPTION
      "Path: tunnels.editConf.ipsecL2tpTunnels.l2tp.ipsec.hdxManualSA.outbound"
   ::= {er1645v2TTmplIcfEntry 304119936}

er1645v2TTmplIcfL2tpIpsecPsCfg OBJECT-TYPE
   SYNTAX      DisplayString
   MAX-ACCESS  read-write
   STATUS      current
   DESCRIPTION
      "Path: tunnels.editConf.ipsecL2tpTunnels.l2tp.ipsec.ikePresharedSA.ikeSA"
   ::= {er1645v2TTmplIcfEntry 304138240}

er1645v2TTmplIcfL2tpIpsecPsLIdIp OBJECT-TYPE
   SYNTAX      IpAddress
   MAX-ACCESS  read-write
   STATUS      current
   DESCRIPTION
      "Path: tunnels.editConf.ipsecL2tpTunnels.l2tp.ipsec.ikePresharedSA.localId.ipAddress"
   ::= {er1645v2TTmplIcfEntry 304140296}

er1645v2TTmplIcfL2tpIpsecPsLIdHn OBJECT-TYPE
   SYNTAX      DisplayString
   MAX-ACCESS  read-write
   STATUS      current
   DESCRIPTION
      "Path: tunnels.editConf.ipsecL2tpTunnels.l2tp.ipsec.ikePresharedSA.localId.hostName"
   ::= {er1645v2TTmplIcfEntry 304140304}

er1645v2TTmplIcfL2tpIpsecPsLIdUn OBJECT-TYPE
   SYNTAX      DisplayString
   MAX-ACCESS  read-write
   STATUS      current
   DESCRIPTION
      "Path: tunnels.editConf.ipsecL2tpTunnels.l2tp.ipsec.ikePresharedSA.localId.user"
   ::= {er1645v2TTmplIcfEntry 304140312}

er1645v2TTmplIcfL2tpIpsecPsRIdIp OBJECT-TYPE
   SYNTAX      IpAddress
   MAX-ACCESS  read-write
   STATUS      current
   DESCRIPTION
      "Path: tunnels.editConf.ipsecL2tpTunnels.l2tp.ipsec.ikePresharedSA.remoteId.ipAddress"
   ::= {er1645v2TTmplIcfEntry 304142344}

er1645v2TTmplIcfL2tpIpsecPsRIdHn OBJECT-TYPE
   SYNTAX      DisplayString
   MAX-ACCESS  read-write
   STATUS      current
   DESCRIPTION
      "Path: tunnels.editConf.ipsecL2tpTunnels.l2tp.ipsec.ikePresharedSA.remoteId.hostName"
   ::= {er1645v2TTmplIcfEntry 304142352}

er1645v2TTmplIcfL2tpIpsecPsRIdUn OBJECT-TYPE
   SYNTAX      DisplayString
   MAX-ACCESS  read-write
   STATUS      current
   DESCRIPTION
      "Path: tunnels.editConf.ipsecL2tpTunnels.l2tp.ipsec.ikePresharedSA.remoteId.user"
   ::= {er1645v2TTmplIcfEntry 304142360}

er1645v2TTmplIcfL2tpIpsecPsKey OBJECT-TYPE
   SYNTAX      DisplayString
   MAX-ACCESS  read-write
   STATUS      current
   DESCRIPTION
      "Path: tunnels.editConf.ipsecL2tpTunnels.l2tp.ipsec.ikePresharedSA.preSharedKey"
   ::= {er1645v2TTmplIcfEntry 304144384}

er1645v2TTmplIcfL2tpIpsecPsEncMKey OBJECT-TYPE
   SYNTAX      INTEGER
               {
               none (1),
               encrypt (2),
               encType1 (3),
               invalid (128)
               }
   MAX-ACCESS  read-write
   STATUS      current
   DESCRIPTION
      "Path: tunnels.editConf.ipsecL2tpTunnels.l2tp.ipsec.ikePresharedSA.encModePreSharedKey

       Possibilities:
               none   (1)
               encrypt   (2)
               encType1   (3)
               invalid   (128)"
   ::= {er1645v2TTmplIcfEntry 304148480}

er1645v2TTmplIcfL2tpIpsecPsEncKey OBJECT-TYPE
   SYNTAX      DisplayString
   MAX-ACCESS  read-write
   STATUS      current
   DESCRIPTION
      "Path: tunnels.editConf.ipsecL2tpTunnels.l2tp.ipsec.ikePresharedSA.encPreSharedKey"
   ::= {er1645v2TTmplIcfEntry 304150528}

er1645v2TTmplIcfL2tpIpsecPsPIdProt OBJECT-TYPE
   SYNTAX      INTEGER
               {
               any (0),
               aH (51),
               eGP (8),
               eSP (50),
               gRE (47),
               iCMP (1),
               iGP (9),
               iGMP (2),
               iGRP (88),
               iPinIP (4),
               oSPF (89),
               uDP (17),
               rSVP (46),
               tCP (6),
               tCPestablished (255)
               }
   MAX-ACCESS  read-write
   STATUS      current
   DESCRIPTION
      "Path: tunnels.editConf.ipsecL2tpTunnels.l2tp.ipsec.ikePresharedSA.proxyId.ipProtocol

       Possibilities:
               any   (0)
               AH   (51)
               EGP   (8)
               ESP   (50)
               GRE   (47)
               ICMP   (1)
               IGP   (9)
               IGMP   (2)
               IGRP   (88)
               IPinIP   (4)
               OSPF   (89)
               UDP   (17)
               RSVP   (46)
               TCP   (6)
               TCPestablished   (255)"
   ::= {er1645v2TTmplIcfEntry 304146560}

er1645v2TTmplIcfL2tpIpsecPsPIdLocAddr OBJECT-TYPE
   SYNTAX      IpAddress
   MAX-ACCESS  read-write
   STATUS      current
   DESCRIPTION
      "Path: tunnels.editConf.ipsecL2tpTunnels.l2tp.ipsec.ikePresharedSA.proxyId.localIpAddress"
   ::= {er1645v2TTmplIcfEntry 304146688}

er1645v2TTmplIcfL2tpIpsecPsPIdLocMask OBJECT-TYPE
   SYNTAX      IpAddress
   MAX-ACCESS  read-write
   STATUS      current
   DESCRIPTION
      "Path: tunnels.editConf.ipsecL2tpTunnels.l2tp.ipsec.ikePresharedSA.proxyId.localIpMask"
   ::= {er1645v2TTmplIcfEntry 304146816}

er1645v2TTmplIcfL2tpIpsecPsPIdLocPort OBJECT-TYPE
   SYNTAX      INTEGER
               {
               any (0),
               bgp (179),
               bootpmdhcpmc (68),
               bootpmdhcpms (67),
               cpudpencap (2746),
               discard (9),
               domain (53),
               echo (7),
               ftp (21),
               ftpmdata (20),
               ftps (990),
               ftpsmdata (989),
               httpmalt (8080),
               https (443),
               imap (134),
               imap3 (220),
               imaps (993),
               ipsecmnatmt (4500),
               isakmp (500),
               l2tp (1701),
               ldap (389),
               microsoftmds (445),
               msmwbtmserver (3389),
               msnp (1863),
               nameserver (42),
               netbiosmdgm (138),
               netbiosmns (137),
               netbiosmssn (139),
               nntp (119),
               ntp (123),
               pop3 (110),
               pop3s (995),
               pptp (1723),
               router (520),
               rtsp (554),
               sip (5060),
               smtp (25),
               smtps (465),
               snmp (161),
               snmptrap (162),
               socks (1080),
               ssdpmuPnP (1900),
               ssh (22),
               syslog (514),
               telindus (1728),
               telnet (23),
               telnets (992),
               tftp (69),
               whip (8700),
               wwwmhttp (80),
               z39d50 (210)
               }
   MAX-ACCESS  read-write
   STATUS      current
   DESCRIPTION
      "Path: tunnels.editConf.ipsecL2tpTunnels.l2tp.ipsec.ikePresharedSA.proxyId.localIpPort

       Possibilities:
               any   (0)
               bgp   (179)
               bootp-dhcp-c   (68)
               bootp-dhcp-s   (67)
               cpudpencap   (2746)
               discard   (9)
               domain   (53)
               echo   (7)
               ftp   (21)
               ftp-data   (20)
               ftps   (990)
               ftps-data   (989)
               http-alt   (8080)
               https   (443)
               imap   (134)
               imap3   (220)
               imaps   (993)
               ipsec-nat-t   (4500)
               isakmp   (500)
               l2tp   (1701)
               ldap   (389)
               microsoft-ds   (445)
               ms-wbt-server   (3389)
               msnp   (1863)
               nameserver   (42)
               netbios-dgm   (138)
               netbios-ns   (137)
               netbios-ssn   (139)
               nntp   (119)
               ntp   (123)
               pop3   (110)
               pop3s   (995)
               pptp   (1723)
               router   (520)
               rtsp   (554)
               sip   (5060)
               smtp   (25)
               smtps   (465)
               snmp   (161)
               snmptrap   (162)
               socks   (1080)
               ssdp-uPnP   (1900)
               ssh   (22)
               syslog   (514)
               telindus   (1728)
               telnet   (23)
               telnets   (992)
               tftp   (69)
               whip   (8700)
               www-http   (80)
               z39.50   (210)"
   ::= {er1645v2TTmplIcfEntry 304146944}

er1645v2TTmplIcfL2tpIpsecPsPIdRemAddr OBJECT-TYPE
   SYNTAX      IpAddress
   MAX-ACCESS  read-write
   STATUS      current
   DESCRIPTION
      "Path: tunnels.editConf.ipsecL2tpTunnels.l2tp.ipsec.ikePresharedSA.proxyId.remoteIpAddress"
   ::= {er1645v2TTmplIcfEntry 304147072}

er1645v2TTmplIcfL2tpIpsecPsPIdRemMask OBJECT-TYPE
   SYNTAX      IpAddress
   MAX-ACCESS  read-write
   STATUS      current
   DESCRIPTION
      "Path: tunnels.editConf.ipsecL2tpTunnels.l2tp.ipsec.ikePresharedSA.proxyId.remoteIpMask"
   ::= {er1645v2TTmplIcfEntry 304147200}

er1645v2TTmplIcfL2tpIpsecPsPIdRemPort OBJECT-TYPE
   SYNTAX      INTEGER
               {
               any (0),
               bgp (179),
               bootpmdhcpmc (68),
               bootpmdhcpms (67),
               cpudpencap (2746),
               discard (9),
               domain (53),
               echo (7),
               ftp (21),
               ftpmdata (20),
               ftps (990),
               ftpsmdata (989),
               httpmalt (8080),
               https (443),
               imap (134),
               imap3 (220),
               imaps (993),
               ipsecmnatmt (4500),
               isakmp (500),
               l2tp (1701),
               ldap (389),
               microsoftmds (445),
               msmwbtmserver (3389),
               msnp (1863),
               nameserver (42),
               netbiosmdgm (138),
               netbiosmns (137),
               netbiosmssn (139),
               nntp (119),
               ntp (123),
               pop3 (110),
               pop3s (995),
               pptp (1723),
               router (520),
               rtsp (554),
               sip (5060),
               smtp (25),
               smtps (465),
               snmp (161),
               snmptrap (162),
               socks (1080),
               ssdpmuPnP (1900),
               ssh (22),
               syslog (514),
               telindus (1728),
               telnet (23),
               telnets (992),
               tftp (69),
               whip (8700),
               wwwmhttp (80),
               z39d50 (210)
               }
   MAX-ACCESS  read-write
   STATUS      current
   DESCRIPTION
      "Path: tunnels.editConf.ipsecL2tpTunnels.l2tp.ipsec.ikePresharedSA.proxyId.remoteIpPort

       Possibilities:
               any   (0)
               bgp   (179)
               bootp-dhcp-c   (68)
               bootp-dhcp-s   (67)
               cpudpencap   (2746)
               discard   (9)
               domain   (53)
               echo   (7)
               ftp   (21)
               ftp-data   (20)
               ftps   (990)
               ftps-data   (989)
               http-alt   (8080)
               https   (443)
               imap   (134)
               imap3   (220)
               imaps   (993)
               ipsec-nat-t   (4500)
               isakmp   (500)
               l2tp   (1701)
               ldap   (389)
               microsoft-ds   (445)
               ms-wbt-server   (3389)
               msnp   (1863)
               nameserver   (42)
               netbios-dgm   (138)
               netbios-ns   (137)
               netbios-ssn   (139)
               nntp   (119)
               ntp   (123)
               pop3   (110)
               pop3s   (995)
               pptp   (1723)
               router   (520)
               rtsp   (554)
               sip   (5060)
               smtp   (25)
               smtps   (465)
               snmp   (161)
               snmptrap   (162)
               socks   (1080)
               ssdp-uPnP   (1900)
               ssh   (22)
               syslog   (514)
               telindus   (1728)
               telnet   (23)
               telnets   (992)
               tftp   (69)
               whip   (8700)
               www-http   (80)
               z39.50   (210)"
   ::= {er1645v2TTmplIcfEntry 304147328}

er1645v2TTmplIcfL2tpIpsecCeCfg OBJECT-TYPE
   SYNTAX      DisplayString
   MAX-ACCESS  read-write
   STATUS      current
   DESCRIPTION
      "Path: tunnels.editConf.ipsecL2tpTunnels.l2tp.ipsec.ikeCertificateSA.ikeSA"
   ::= {er1645v2TTmplIcfEntry 304154624}

er1645v2TTmplIcfL2tpIpsecCeLIdIp OBJECT-TYPE
   SYNTAX      IpAddress
   MAX-ACCESS  read-write
   STATUS      current
   DESCRIPTION
      "Path: tunnels.editConf.ipsecL2tpTunnels.l2tp.ipsec.ikeCertificateSA.localId.ipAddress"
   ::= {er1645v2TTmplIcfEntry 304156680}

er1645v2TTmplIcfL2tpIpsecCeLIdHn OBJECT-TYPE
   SYNTAX      DisplayString
   MAX-ACCESS  read-write
   STATUS      current
   DESCRIPTION
      "Path: tunnels.editConf.ipsecL2tpTunnels.l2tp.ipsec.ikeCertificateSA.localId.hostName"
   ::= {er1645v2TTmplIcfEntry 304156688}

er1645v2TTmplIcfL2tpIpsecCeLIdUn OBJECT-TYPE
   SYNTAX      DisplayString
   MAX-ACCESS  read-write
   STATUS      current
   DESCRIPTION
      "Path: tunnels.editConf.ipsecL2tpTunnels.l2tp.ipsec.ikeCertificateSA.localId.user"
   ::= {er1645v2TTmplIcfEntry 304156696}

er1645v2TTmplIcfL2tpIpsecCeLIdDn OBJECT-TYPE
   SYNTAX      DisplayString
   MAX-ACCESS  read-write
   STATUS      current
   DESCRIPTION
      "Path: tunnels.editConf.ipsecL2tpTunnels.l2tp.ipsec.ikeCertificateSA.localId.derAsn1Dn"
   ::= {er1645v2TTmplIcfEntry 304156704}

er1645v2TTmplIcfL2tpIpsecCeRIdIp OBJECT-TYPE
   SYNTAX      IpAddress
   MAX-ACCESS  read-write
   STATUS      current
   DESCRIPTION
      "Path: tunnels.editConf.ipsecL2tpTunnels.l2tp.ipsec.ikeCertificateSA.remoteId.ipAddress"
   ::= {er1645v2TTmplIcfEntry 304158728}

er1645v2TTmplIcfL2tpIpsecCeRIdHn OBJECT-TYPE
   SYNTAX      DisplayString
   MAX-ACCESS  read-write
   STATUS      current
   DESCRIPTION
      "Path: tunnels.editConf.ipsecL2tpTunnels.l2tp.ipsec.ikeCertificateSA.remoteId.hostName"
   ::= {er1645v2TTmplIcfEntry 304158736}

er1645v2TTmplIcfL2tpIpsecCeRIdUn OBJECT-TYPE
   SYNTAX      DisplayString
   MAX-ACCESS  read-write
   STATUS      current
   DESCRIPTION
      "Path: tunnels.editConf.ipsecL2tpTunnels.l2tp.ipsec.ikeCertificateSA.remoteId.user"
   ::= {er1645v2TTmplIcfEntry 304158744}

er1645v2TTmplIcfL2tpIpsecCeRIdDn OBJECT-TYPE
   SYNTAX      DisplayString
   MAX-ACCESS  read-write
   STATUS      current
   DESCRIPTION
      "Path: tunnels.editConf.ipsecL2tpTunnels.l2tp.ipsec.ikeCertificateSA.remoteId.derAsn1Dn"
   ::= {er1645v2TTmplIcfEntry 304158752}

er1645v2TTmplIcfL2tpIpsecCePIdProt OBJECT-TYPE
   SYNTAX      INTEGER
               {
               any (0),
               aH (51),
               eGP (8),
               eSP (50),
               gRE (47),
               iCMP (1),
               iGP (9),
               iGMP (2),
               iGRP (88),
               iPinIP (4),
               oSPF (89),
               uDP (17),
               rSVP (46),
               tCP (6),
               tCPestablished (255)
               }
   MAX-ACCESS  read-write
   STATUS      current
   DESCRIPTION
      "Path: tunnels.editConf.ipsecL2tpTunnels.l2tp.ipsec.ikeCertificateSA.proxyId.ipProtocol

       Possibilities:
               any   (0)
               AH   (51)
               EGP   (8)
               ESP   (50)
               GRE   (47)
               ICMP   (1)
               IGP   (9)
               IGMP   (2)
               IGRP   (88)
               IPinIP   (4)
               OSPF   (89)
               UDP   (17)
               RSVP   (46)
               TCP   (6)
               TCPestablished   (255)"
   ::= {er1645v2TTmplIcfEntry 304162944}

er1645v2TTmplIcfL2tpIpsecCePIdLocAddr OBJECT-TYPE
   SYNTAX      IpAddress
   MAX-ACCESS  read-write
   STATUS      current
   DESCRIPTION
      "Path: tunnels.editConf.ipsecL2tpTunnels.l2tp.ipsec.ikeCertificateSA.proxyId.localIpAddress"
   ::= {er1645v2TTmplIcfEntry 304163072}

er1645v2TTmplIcfL2tpIpsecCePIdLocMask OBJECT-TYPE
   SYNTAX      IpAddress
   MAX-ACCESS  read-write
   STATUS      current
   DESCRIPTION
      "Path: tunnels.editConf.ipsecL2tpTunnels.l2tp.ipsec.ikeCertificateSA.proxyId.localIpMask"
   ::= {er1645v2TTmplIcfEntry 304163200}

er1645v2TTmplIcfL2tpIpsecCePIdLocPort OBJECT-TYPE
   SYNTAX      INTEGER
               {
               any (0),
               bgp (179),
               bootpmdhcpmc (68),
               bootpmdhcpms (67),
               cpudpencap (2746),
               discard (9),
               domain (53),
               echo (7),
               ftp (21),
               ftpmdata (20),
               ftps (990),
               ftpsmdata (989),
               httpmalt (8080),
               https (443),
               imap (134),
               imap3 (220),
               imaps (993),
               ipsecmnatmt (4500),
               isakmp (500),
               l2tp (1701),
               ldap (389),
               microsoftmds (445),
               msmwbtmserver (3389),
               msnp (1863),
               nameserver (42),
               netbiosmdgm (138),
               netbiosmns (137),
               netbiosmssn (139),
               nntp (119),
               ntp (123),
               pop3 (110),
               pop3s (995),
               pptp (1723),
               router (520),
               rtsp (554),
               sip (5060),
               smtp (25),
               smtps (465),
               snmp (161),
               snmptrap (162),
               socks (1080),
               ssdpmuPnP (1900),
               ssh (22),
               syslog (514),
               telindus (1728),
               telnet (23),
               telnets (992),
               tftp (69),
               whip (8700),
               wwwmhttp (80),
               z39d50 (210)
               }
   MAX-ACCESS  read-write
   STATUS      current
   DESCRIPTION
      "Path: tunnels.editConf.ipsecL2tpTunnels.l2tp.ipsec.ikeCertificateSA.proxyId.localIpPort

       Possibilities:
               any   (0)
               bgp   (179)
               bootp-dhcp-c   (68)
               bootp-dhcp-s   (67)
               cpudpencap   (2746)
               discard   (9)
               domain   (53)
               echo   (7)
               ftp   (21)
               ftp-data   (20)
               ftps   (990)
               ftps-data   (989)
               http-alt   (8080)
               https   (443)
               imap   (134)
               imap3   (220)
               imaps   (993)
               ipsec-nat-t   (4500)
               isakmp   (500)
               l2tp   (1701)
               ldap   (389)
               microsoft-ds   (445)
               ms-wbt-server   (3389)
               msnp   (1863)
               nameserver   (42)
               netbios-dgm   (138)
               netbios-ns   (137)
               netbios-ssn   (139)
               nntp   (119)
               ntp   (123)
               pop3   (110)
               pop3s   (995)
               pptp   (1723)
               router   (520)
               rtsp   (554)
               sip   (5060)
               smtp   (25)
               smtps   (465)
               snmp   (161)
               snmptrap   (162)
               socks   (1080)
               ssdp-uPnP   (1900)
               ssh   (22)
               syslog   (514)
               telindus   (1728)
               telnet   (23)
               telnets   (992)
               tftp   (69)
               whip   (8700)
               www-http   (80)
               z39.50   (210)"
   ::= {er1645v2TTmplIcfEntry 304163328}

er1645v2TTmplIcfL2tpIpsecCePIdRemAddr OBJECT-TYPE
   SYNTAX      IpAddress
   MAX-ACCESS  read-write
   STATUS      current
   DESCRIPTION
      "Path: tunnels.editConf.ipsecL2tpTunnels.l2tp.ipsec.ikeCertificateSA.proxyId.remoteIpAddress"
   ::= {er1645v2TTmplIcfEntry 304163456}

er1645v2TTmplIcfL2tpIpsecCePIdRemMask OBJECT-TYPE
   SYNTAX      IpAddress
   MAX-ACCESS  read-write
   STATUS      current
   DESCRIPTION
      "Path: tunnels.editConf.ipsecL2tpTunnels.l2tp.ipsec.ikeCertificateSA.proxyId.remoteIpMask"
   ::= {er1645v2TTmplIcfEntry 304163584}

er1645v2TTmplIcfL2tpIpsecCePIdRemPort OBJECT-TYPE
   SYNTAX      INTEGER
               {
               any (0),
               bgp (179),
               bootpmdhcpmc (68),
               bootpmdhcpms (67),
               cpudpencap (2746),
               discard (9),
               domain (53),
               echo (7),
               ftp (21),
               ftpmdata (20),
               ftps (990),
               ftpsmdata (989),
               httpmalt (8080),
               https (443),
               imap (134),
               imap3 (220),
               imaps (993),
               ipsecmnatmt (4500),
               isakmp (500),
               l2tp (1701),
               ldap (389),
               microsoftmds (445),
               msmwbtmserver (3389),
               msnp (1863),
               nameserver (42),
               netbiosmdgm (138),
               netbiosmns (137),
               netbiosmssn (139),
               nntp (119),
               ntp (123),
               pop3 (110),
               pop3s (995),
               pptp (1723),
               router (520),
               rtsp (554),
               sip (5060),
               smtp (25),
               smtps (465),
               snmp (161),
               snmptrap (162),
               socks (1080),
               ssdpmuPnP (1900),
               ssh (22),
               syslog (514),
               telindus (1728),
               telnet (23),
               telnets (992),
               tftp (69),
               whip (8700),
               wwwmhttp (80),
               z39d50 (210)
               }
   MAX-ACCESS  read-write
   STATUS      current
   DESCRIPTION
      "Path: tunnels.editConf.ipsecL2tpTunnels.l2tp.ipsec.ikeCertificateSA.proxyId.remoteIpPort

       Possibilities:
               any   (0)
               bgp   (179)
               bootp-dhcp-c   (68)
               bootp-dhcp-s   (67)
               cpudpencap   (2746)
               discard   (9)
               domain   (53)
               echo   (7)
               ftp   (21)
               ftp-data   (20)
               ftps   (990)
               ftps-data   (989)
               http-alt   (8080)
               https   (443)
               imap   (134)
               imap3   (220)
               imaps   (993)
               ipsec-nat-t   (4500)
               isakmp   (500)
               l2tp   (1701)
               ldap   (389)
               microsoft-ds   (445)
               ms-wbt-server   (3389)
               msnp   (1863)
               nameserver   (42)
               netbios-dgm   (138)
               netbios-ns   (137)
               netbios-ssn   (139)
               nntp   (119)
               ntp   (123)
               pop3   (110)
               pop3s   (995)
               pptp   (1723)
               router   (520)
               rtsp   (554)
               sip   (5060)
               smtp   (25)
               smtps   (465)
               snmp   (161)
               snmptrap   (162)
               socks   (1080)
               ssdp-uPnP   (1900)
               ssh   (22)
               syslog   (514)
               telindus   (1728)
               telnet   (23)
               telnets   (992)
               tftp   (69)
               whip   (8700)
               www-http   (80)
               z39.50   (210)"
   ::= {er1645v2TTmplIcfEntry 304163712}

er1645v2TTmplIcfL2tpKeepaliveTO OBJECT-TYPE
   SYNTAX      Integer32
   MAX-ACCESS  read-write
   STATUS      current
   DESCRIPTION
      "Path: tunnels.editConf.ipsecL2tpTunnels.l2tp.keepAliveTimeOut"
   ::= {er1645v2TTmplIcfEntry 302514176}

er1645v2TTmplIcfL2tpNoTraffT0 OBJECT-TYPE
   SYNTAX      Integer32
   MAX-ACCESS  read-write
   STATUS      current
   DESCRIPTION
      "Path: tunnels.editConf.ipsecL2tpTunnels.l2tp.noTrafficTimeOut"
   ::= {er1645v2TTmplIcfEntry 304218112}

er1645v2TTmplIcfL2tpMode OBJECT-TYPE
   SYNTAX      INTEGER
               {
               lac (1),
               lns (2),
               auto (3)
               }
   MAX-ACCESS  read-write
   STATUS      current
   DESCRIPTION
      "Path: tunnels.editConf.ipsecL2tpTunnels.l2tp.l2tpMode

       Possibilities:
               lac   (1)
               lns   (2)
               auto   (3)"
   ::= {er1645v2TTmplIcfEntry 302645248}

er1645v2TTmplIcfL2tpAuth OBJECT-TYPE
   SYNTAX      INTEGER
               {
               off (0),
               on (1)
               }
   MAX-ACCESS  read-write
   STATUS      current
   DESCRIPTION
      "Path: tunnels.editConf.ipsecL2tpTunnels.l2tp.tunnelAuthentication

       Possibilities:
               off   (0)
               on   (1)"
   ::= {er1645v2TTmplIcfEntry 302776320}

er1645v2TTmplIcfL2tpSecret OBJECT-TYPE
   SYNTAX      DisplayString
   MAX-ACCESS  read-write
   STATUS      current
   DESCRIPTION
      "Path: tunnels.editConf.ipsecL2tpTunnels.l2tp.tunnelSecret"
   ::= {er1645v2TTmplIcfEntry 302907392}

er1645v2TTmplIcfL2tpTos OBJECT-TYPE
   SYNTAX      INTEGER
               {
               off (0),
               on (1)
               }
   MAX-ACCESS  read-write
   STATUS      current
   DESCRIPTION
      "Path: tunnels.editConf.ipsecL2tpTunnels.l2tp.copyTos

       Possibilities:
               off   (0)
               on   (1)"
   ::= {er1645v2TTmplIcfEntry 303955968}

er1645v2TTmplIcfL2tpRetrans OBJECT-TYPE
   SYNTAX      Integer32
   MAX-ACCESS  read-write
   STATUS      current
   DESCRIPTION
      "Path: tunnels.editConf.ipsecL2tpTunnels.l2tp.maxNrOfRetransmissions"
   ::= {er1645v2TTmplIcfEntry 303038464}

er1645v2TTmplIcfL2tpTransmitws OBJECT-TYPE
   SYNTAX      Integer32
   MAX-ACCESS  read-write
   STATUS      current
   DESCRIPTION
      "Path: tunnels.editConf.ipsecL2tpTunnels.l2tp.transmitWindowSize"
   ::= {er1645v2TTmplIcfEntry 303169536}

er1645v2TTmplIcfL2tpRcsws OBJECT-TYPE
   SYNTAX      Integer32
   MAX-ACCESS  read-write
   STATUS      current
   DESCRIPTION
      "Path: tunnels.editConf.ipsecL2tpTunnels.l2tp.receiveWindowSize"
   ::= {er1645v2TTmplIcfEntry 303300608}

er1645v2TTmplIcfL2tpUdpcheck OBJECT-TYPE
   SYNTAX      INTEGER
               {
               off (0),
               on (1)
               }
   MAX-ACCESS  read-write
   STATUS      current
   DESCRIPTION
      "Path: tunnels.editConf.ipsecL2tpTunnels.l2tp.udpChecksum

       Possibilities:
               off   (0)
               on   (1)"
   ::= {er1645v2TTmplIcfEntry 303431680}

er1645v2TTmplIcfL2tpCalledNr OBJECT-TYPE
   SYNTAX      DisplayString
   MAX-ACCESS  read-write
   STATUS      current
   DESCRIPTION
      "Path: tunnels.editConf.ipsecL2tpTunnels.l2tp.calledNr"
   ::= {er1645v2TTmplIcfEntry 303562752}

er1645v2TTmplIcfL2tpSpeed OBJECT-TYPE
   SYNTAX      Integer32
   MAX-ACCESS  read-write
   STATUS      current
   DESCRIPTION
      "Path: tunnels.editConf.ipsecL2tpTunnels.l2tp.speed"
   ::= {er1645v2TTmplIcfEntry 315621376}

er1645v2TTmplIcfL2tpMtu OBJECT-TYPE
   SYNTAX      Integer32
   MAX-ACCESS  read-write
   STATUS      current
   DESCRIPTION
      "Path: tunnels.editConf.ipsecL2tpTunnels.l2tp.mtu"
   ::= {er1645v2TTmplIcfEntry 304349184}

er1645v2TTmplIcfL2tpHostName OBJECT-TYPE
   SYNTAX      DisplayString
   MAX-ACCESS  read-write
   STATUS      current
   DESCRIPTION
      "Path: tunnels.editConf.ipsecL2tpTunnels.l2tp.hostName"
   ::= {er1645v2TTmplIcfEntry 304480256}

er1645v2TTmplIcfBackupInterface OBJECT-TYPE
   SYNTAX      DisplayString
   MAX-ACCESS  read-write
   STATUS      current
   DESCRIPTION
      "Path: tunnels.editConf.ipsecL2tpTunnels.backup.interface"
   ::= {er1645v2TTmplIcfEntry 536936448}

er1645v2TTmplIcfBackupTimeOut OBJECT-TYPE
   SYNTAX      Integer32
   MAX-ACCESS  read-write
   STATUS      current
   DESCRIPTION
      "Path: tunnels.editConf.ipsecL2tpTunnels.backup.timeOut"
   ::= {er1645v2TTmplIcfEntry 537067520}

er1645v2TTmplIcfBackupAutoRetry OBJECT-TYPE
   SYNTAX      INTEGER
               {
               no (0),
               yes (1)
               }
   MAX-ACCESS  read-write
   STATUS      current
   DESCRIPTION
      "Path: tunnels.editConf.ipsecL2tpTunnels.backup.autoRetry

       Possibilities:
               no   (0)
               yes   (1)"
   ::= {er1645v2TTmplIcfEntry 537133056}

er1645v2TTmplIcfInbBwCir OBJECT-TYPE
   SYNTAX      Integer32
   MAX-ACCESS  read-write
   STATUS      current
   DESCRIPTION
      "Path: tunnels.editConf.ipsecL2tpTunnels.inboundBandwidth.cir"
   ::= {er1645v2TTmplIcfEntry 117506048}

er1645v2TTmplIcfInbBwTc OBJECT-TYPE
   SYNTAX      INTEGER
               {
               auto (0)
               }
   MAX-ACCESS  read-write
   STATUS      current
   DESCRIPTION
      "Path: tunnels.editConf.ipsecL2tpTunnels.inboundBandwidth.tc

       Possibilities:
               auto   (0)"
   ::= {er1645v2TTmplIcfEntry 117833728}

er1645v2TTmplIcfInbBwCorrType OBJECT-TYPE
   SYNTAX      INTEGER
               {
               noCorrection (0),
               predefined (1),
               manual (2)
               }
   MAX-ACCESS  read-write
   STATUS      current
   DESCRIPTION
      "Path: tunnels.editConf.ipsecL2tpTunnels.inboundBandwidth.correction.type

       Possibilities:
               noCorrection   (0)
               predefined   (1)
               manual   (2)"
   ::= {er1645v2TTmplIcfEntry 117579776}

er1645v2TTmplIcfInbBwCorrPredefEncapsFrameRelay OBJECT-TYPE
   SYNTAX      DisplayString
   MAX-ACCESS  read-write
   STATUS      current
   DESCRIPTION
      "Path: tunnels.editConf.ipsecL2tpTunnels.inboundBandwidth.correction.predefined.encapsulation.frameRelay"
   ::= {er1645v2TTmplIcfEntry 117589056}

er1645v2TTmplIcfInbBwCorrPredefEncapsPpp OBJECT-TYPE
   SYNTAX      DisplayString
   MAX-ACCESS  read-write
   STATUS      current
   DESCRIPTION
      "Path: tunnels.editConf.ipsecL2tpTunnels.inboundBandwidth.correction.predefined.encapsulation.ppp"
   ::= {er1645v2TTmplIcfEntry 117589120}

er1645v2TTmplIcfInbBwCorrPredefEncapsAtmHl OBJECT-TYPE
   SYNTAX      INTEGER
               {
               rfc2684 (0),
               ppp (1),
               pppOverEthernet (2)
               }
   MAX-ACCESS  read-write
   STATUS      current
   DESCRIPTION
      "Path: tunnels.editConf.ipsecL2tpTunnels.inboundBandwidth.correction.predefined.encapsulation.atm.higherLayer

       Possibilities:
               rfc2684   (0)
               ppp   (1)
               pppOverEthernet   (2)"
   ::= {er1645v2TTmplIcfEntry 117589192}

er1645v2TTmplIcfInbBwCorrPredefEncapsAtmMp OBJECT-TYPE
   SYNTAX      INTEGER
               {
               llcEncapsulation (0),
               vcMultiplexing (1)
               }
   MAX-ACCESS  read-write
   STATUS      current
   DESCRIPTION
      "Path: tunnels.editConf.ipsecL2tpTunnels.inboundBandwidth.correction.predefined.encapsulation.atm.multiProtocol

       Possibilities:
               llcEncapsulation   (0)
               vcMultiplexing   (1)"
   ::= {er1645v2TTmplIcfEntry 117589200}

er1645v2TTmplIcfInbBwCorrPredefEncapsHdlc OBJECT-TYPE
   SYNTAX      DisplayString
   MAX-ACCESS  read-write
   STATUS      current
   DESCRIPTION
      "Path: tunnels.editConf.ipsecL2tpTunnels.inboundBandwidth.correction.predefined.encapsulation.hdlc"
   ::= {er1645v2TTmplIcfEntry 117589248}

er1645v2TTmplIcfInbBwCorrPredefEncapsEfmFs OBJECT-TYPE
   SYNTAX      Integer32
   MAX-ACCESS  read-write
   STATUS      current
   DESCRIPTION
      "Path: tunnels.editConf.ipsecL2tpTunnels.inboundBandwidth.correction.predefined.encapsulation.efm.fragmentSize"
   ::= {er1645v2TTmplIcfEntry 117589320}

er1645v2TTmplIcfInbBwCorrPredefEncapsEfmIb OBJECT-TYPE
   SYNTAX      Integer32
   MAX-ACCESS  read-write
   STATUS      current
   DESCRIPTION
      "Path: tunnels.editConf.ipsecL2tpTunnels.inboundBandwidth.correction.predefined.encapsulation.efm.idleBytes"
   ::= {er1645v2TTmplIcfEntry 117589328}

er1645v2TTmplIcfInbBwCorrPredefMode OBJECT-TYPE
   SYNTAX      INTEGER
               {
               routing (0),
               bridging (1)
               }
   MAX-ACCESS  read-write
   STATUS      current
   DESCRIPTION
      "Path: tunnels.editConf.ipsecL2tpTunnels.inboundBandwidth.correction.predefined.mode

       Possibilities:
               routing   (0)
               bridging   (1)"
   ::= {er1645v2TTmplIcfEntry 117590016}

er1645v2TTmplIcfInbBwCorrManualOverhead OBJECT-TYPE
   SYNTAX      Integer32
   MAX-ACCESS  read-write
   STATUS      current
   DESCRIPTION
      "Path: tunnels.editConf.ipsecL2tpTunnels.inboundBandwidth.correction.manual.overhead"
   ::= {er1645v2TTmplIcfEntry 117596192}

er1645v2TTmplIcfInbBwCorrManualFrameData OBJECT-TYPE
   SYNTAX      Counter32
   MAX-ACCESS  read-write
   STATUS      current
   DESCRIPTION
      "Path: tunnels.editConf.ipsecL2tpTunnels.inboundBandwidth.correction.manual.frameData

       32 bit unsigned wrappable counter."
   ::= {er1645v2TTmplIcfEntry 117596224}

er1645v2TTmplIcfInbBwCorrManualFrameHeader OBJECT-TYPE
   SYNTAX      Counter32
   MAX-ACCESS  read-write
   STATUS      current
   DESCRIPTION
      "Path: tunnels.editConf.ipsecL2tpTunnels.inboundBandwidth.correction.manual.frameHeader

       32 bit unsigned wrappable counter."
   ::= {er1645v2TTmplIcfEntry 117596256}

er1645v2TTmplIcfInbBwMaxFifoQLen OBJECT-TYPE
   SYNTAX      Integer32
   MAX-ACCESS  read-write
   STATUS      current
   DESCRIPTION
      "Path: tunnels.editConf.ipsecL2tpTunnels.inboundBandwidth.maxFifoQLen"
   ::= {er1645v2TTmplIcfEntry 117637120}

er1645v2TTmplIcfInbBwPriorityPolicy OBJECT-TYPE
   SYNTAX      DisplayString
   MAX-ACCESS  read-write
   STATUS      current
   DESCRIPTION
      "Path: tunnels.editConf.ipsecL2tpTunnels.inboundBandwidth.priorityPolicy"
   ::= {er1645v2TTmplIcfEntry 117702656}

er1645v2TTmplIcfBandwidthMode OBJECT-TYPE
   SYNTAX      INTEGER
               {
               reshaping (1),
               policing (2),
               policingReshape (3)
               }
   MAX-ACCESS  read-write
   STATUS      current
   DESCRIPTION
      "Path: tunnels.editConf.ipsecL2tpTunnels.bandwidth.mode

       Possibilities:
               reshaping   (1)
               policing   (2)
               policingReshape   (3)"
   ::= {er1645v2TTmplIcfEntry 148897792}

er1645v2TTmplIcfBandwidthCir OBJECT-TYPE
   SYNTAX      Integer32
   MAX-ACCESS  read-write
   STATUS      current
   DESCRIPTION
      "Path: tunnels.editConf.ipsecL2tpTunnels.bandwidth.cir"
   ::= {er1645v2TTmplIcfEntry 135266304}

er1645v2TTmplIcfBandwidthEir OBJECT-TYPE
   SYNTAX      Integer32
   MAX-ACCESS  read-write
   STATUS      current
   DESCRIPTION
      "Path: tunnels.editConf.ipsecL2tpTunnels.bandwidth.eir"
   ::= {er1645v2TTmplIcfEntry 141557760}

er1645v2TTmplIcfBandwidthUnit OBJECT-TYPE
   SYNTAX      INTEGER
               {
               bitssec (1),
               percent (2)
               }
   MAX-ACCESS  read-write
   STATUS      current
   DESCRIPTION
      "Path: tunnels.editConf.ipsecL2tpTunnels.bandwidth.unit

       Possibilities:
               bits/sec   (1)
               percent   (2)"
   ::= {er1645v2TTmplIcfEntry 139460608}

er1645v2TTmplIcfBandwidthTc OBJECT-TYPE
   SYNTAX      INTEGER
               {
               auto (0)
               }
   MAX-ACCESS  read-write
   STATUS      current
   DESCRIPTION
      "Path: tunnels.editConf.ipsecL2tpTunnels.bandwidth.tc

       Possibilities:
               auto   (0)"
   ::= {er1645v2TTmplIcfEntry 140509184}

er1645v2TTmplIcfBandwidthTcFactor OBJECT-TYPE
   SYNTAX      INTEGER
               {
               ms (10),
               s100us (1)
               }
   MAX-ACCESS  read-write
   STATUS      current
   DESCRIPTION
      "Path: tunnels.editConf.ipsecL2tpTunnels.bandwidth.tcFactor

       Possibilities:
               ms   (10)
               *100us   (1)"
   ::= {er1645v2TTmplIcfEntry 142606336}

er1645v2TTmplIcfBandwidthCorrType OBJECT-TYPE
   SYNTAX      INTEGER
               {
               noCorrection (0),
               predefined (1),
               manual (2)
               }
   MAX-ACCESS  read-write
   STATUS      current
   DESCRIPTION
      "Path: tunnels.editConf.ipsecL2tpTunnels.bandwidth.correction.type

       Possibilities:
               noCorrection   (0)
               predefined   (1)
               manual   (2)"
   ::= {er1645v2TTmplIcfEntry 136445952}

er1645v2TTmplIcfBandwidthCorrPredefEncapsFrameRelay OBJECT-TYPE
   SYNTAX      DisplayString
   MAX-ACCESS  read-write
   STATUS      current
   DESCRIPTION
      "Path: tunnels.editConf.ipsecL2tpTunnels.bandwidth.correction.predefined.encapsulation.frameRelay"
   ::= {er1645v2TTmplIcfEntry 136594432}

er1645v2TTmplIcfBandwidthCorrPredefEncapsPpp OBJECT-TYPE
   SYNTAX      DisplayString
   MAX-ACCESS  read-write
   STATUS      current
   DESCRIPTION
      "Path: tunnels.editConf.ipsecL2tpTunnels.bandwidth.correction.predefined.encapsulation.ppp"
   ::= {er1645v2TTmplIcfEntry 136595456}

er1645v2TTmplIcfBandwidthCorrPredefEncapsAtmHl OBJECT-TYPE
   SYNTAX      INTEGER
               {
               rfc2684 (0),
               ppp (1),
               pppOverEthernet (2)
               }
   MAX-ACCESS  read-write
   STATUS      current
   DESCRIPTION
      "Path: tunnels.editConf.ipsecL2tpTunnels.bandwidth.correction.predefined.encapsulation.atm.higherLayer

       Possibilities:
               rfc2684   (0)
               ppp   (1)
               pppOverEthernet   (2)"
   ::= {er1645v2TTmplIcfEntry 136596608}

er1645v2TTmplIcfBandwidthCorrPredefEncapsAtmMp OBJECT-TYPE
   SYNTAX      INTEGER
               {
               llcEncapsulation (0),
               vcMultiplexing (1)
               }
   MAX-ACCESS  read-write
   STATUS      current
   DESCRIPTION
      "Path: tunnels.editConf.ipsecL2tpTunnels.bandwidth.correction.predefined.encapsulation.atm.multiProtocol

       Possibilities:
               llcEncapsulation   (0)
               vcMultiplexing   (1)"
   ::= {er1645v2TTmplIcfEntry 136596736}

er1645v2TTmplIcfBandwidthCorrPredefEncapsHdlc OBJECT-TYPE
   SYNTAX      DisplayString
   MAX-ACCESS  read-write
   STATUS      current
   DESCRIPTION
      "Path: tunnels.editConf.ipsecL2tpTunnels.bandwidth.correction.predefined.encapsulation.hdlc"
   ::= {er1645v2TTmplIcfEntry 136597504}

er1645v2TTmplIcfBandwidthCorrPredefEncapsEfmFs OBJECT-TYPE
   SYNTAX      Integer32
   MAX-ACCESS  read-write
   STATUS      current
   DESCRIPTION
      "Path: tunnels.editConf.ipsecL2tpTunnels.bandwidth.correction.predefined.encapsulation.efm.fragmentSize"
   ::= {er1645v2TTmplIcfEntry 136598656}

er1645v2TTmplIcfBandwidthCorrPredefEncapsEfmIb OBJECT-TYPE
   SYNTAX      Integer32
   MAX-ACCESS  read-write
   STATUS      current
   DESCRIPTION
      "Path: tunnels.editConf.ipsecL2tpTunnels.bandwidth.correction.predefined.encapsulation.efm.idleBytes"
   ::= {er1645v2TTmplIcfEntry 136598784}

er1645v2TTmplIcfBandwidthCorrPredefMode OBJECT-TYPE
   SYNTAX      INTEGER
               {
               routing (0),
               bridging (1)
               }
   MAX-ACCESS  read-write
   STATUS      current
   DESCRIPTION
      "Path: tunnels.editConf.ipsecL2tpTunnels.bandwidth.correction.predefined.mode

       Possibilities:
               routing   (0)
               bridging   (1)"
   ::= {er1645v2TTmplIcfEntry 136609792}

er1645v2TTmplIcfBandwidthCorrManualOverhead OBJECT-TYPE
   SYNTAX      Integer32
   MAX-ACCESS  read-write
   STATUS      current
   DESCRIPTION
      "Path: tunnels.editConf.ipsecL2tpTunnels.bandwidth.correction.manual.overhead"
   ::= {er1645v2TTmplIcfEntry 136708608}

er1645v2TTmplIcfBandwidthCorrManualFrameData OBJECT-TYPE
   SYNTAX      Counter32
   MAX-ACCESS  read-write
   STATUS      current
   DESCRIPTION
      "Path: tunnels.editConf.ipsecL2tpTunnels.bandwidth.correction.manual.frameData

       32 bit unsigned wrappable counter."
   ::= {er1645v2TTmplIcfEntry 136709120}

er1645v2TTmplIcfBandwidthCorrManualFrameHeader OBJECT-TYPE
   SYNTAX      Counter32
   MAX-ACCESS  read-write
   STATUS      current
   DESCRIPTION
      "Path: tunnels.editConf.ipsecL2tpTunnels.bandwidth.correction.manual.frameHeader

       32 bit unsigned wrappable counter."
   ::= {er1645v2TTmplIcfEntry 136709632}

er1645v2TTmplIcfBandwidthMaxFifoQLen OBJECT-TYPE
   SYNTAX      Integer32
   MAX-ACCESS  read-write
   STATUS      current
   DESCRIPTION
      "Path: tunnels.editConf.ipsecL2tpTunnels.bandwidth.maxFifoQLen"
   ::= {er1645v2TTmplIcfEntry 137363456}

er1645v2TTmplIcfBandwidthDeFlagCir OBJECT-TYPE
   SYNTAX      INTEGER
               {
               allowed (1),
               notAllowed (2)
               }
   MAX-ACCESS  read-write
   STATUS      current
   DESCRIPTION
      "Path: tunnels.editConf.ipsecL2tpTunnels.bandwidth.deFlag.cir

       Possibilities:
               allowed   (1)
               notAllowed   (2)"
   ::= {er1645v2TTmplIcfEntry 147853312}

er1645v2TTmplIcfBandwidthDeFlagEir OBJECT-TYPE
   SYNTAX      INTEGER
               {
               allowed (1),
               notAllowed (2)
               }
   MAX-ACCESS  read-write
   STATUS      current
   DESCRIPTION
      "Path: tunnels.editConf.ipsecL2tpTunnels.bandwidth.deFlag.eir

       Possibilities:
               allowed   (1)
               notAllowed   (2)"
   ::= {er1645v2TTmplIcfEntry 147857408}

er1645v2TTmplIcfBandwidthDeFlagViolate OBJECT-TYPE
   SYNTAX      INTEGER
               {
               allowed (1),
               notAllowed (2)
               }
   MAX-ACCESS  read-write
   STATUS      current
   DESCRIPTION
      "Path: tunnels.editConf.ipsecL2tpTunnels.bandwidth.deFlag.violate

       Possibilities:
               allowed   (1)
               notAllowed   (2)"
   ::= {er1645v2TTmplIcfEntry 147861504}

er1645v2TTmplIcfBandwidthActCirActNone OBJECT-TYPE
   SYNTAX      OCTET STRING
   MAX-ACCESS  read-write
   STATUS      current
   DESCRIPTION
      "Path: tunnels.editConf.ipsecL2tpTunnels.bandwidth.action.cirAction.none"
   ::= {er1645v2TTmplIcfEntry 150085632}

er1645v2TTmplIcfBandwidthActCirActEthCos1 OBJECT-TYPE
   SYNTAX      INTEGER
               {
               unchanged (256)
               }
   MAX-ACCESS  read-write
   STATUS      current
   DESCRIPTION
      "Path: tunnels.editConf.ipsecL2tpTunnels.bandwidth.action.cirAction.ethernet.cosDepth1

       Possibilities:
               unchanged   (256)"
   ::= {er1645v2TTmplIcfEntry 150094080}

er1645v2TTmplIcfBandwidthActCirActEthDei1 OBJECT-TYPE
   SYNTAX      INTEGER
               {
               unchanged (255),
               clear (0),
               set (1)
               }
   MAX-ACCESS  read-write
   STATUS      current
   DESCRIPTION
      "Path: tunnels.editConf.ipsecL2tpTunnels.bandwidth.action.cirAction.ethernet.deiDepth1

       Possibilities:
               unchanged   (255)
               clear   (0)
               set   (1)"
   ::= {er1645v2TTmplIcfEntry 150099200}

er1645v2TTmplIcfBandwidthActCirActEthCos2 OBJECT-TYPE
   SYNTAX      INTEGER
               {
               unchanged (256)
               }
   MAX-ACCESS  read-write
   STATUS      current
   DESCRIPTION
      "Path: tunnels.editConf.ipsecL2tpTunnels.bandwidth.action.cirAction.ethernet.cosDepth2

       Possibilities:
               unchanged   (256)"
   ::= {er1645v2TTmplIcfEntry 150094336}

er1645v2TTmplIcfBandwidthActCirActEthDei2 OBJECT-TYPE
   SYNTAX      INTEGER
               {
               unchanged (255),
               clear (0),
               set (1)
               }
   MAX-ACCESS  read-write
   STATUS      current
   DESCRIPTION
      "Path: tunnels.editConf.ipsecL2tpTunnels.bandwidth.action.cirAction.ethernet.deiDepth2

       Possibilities:
               unchanged   (255)
               clear   (0)
               set   (1)"
   ::= {er1645v2TTmplIcfEntry 150099456}

er1645v2TTmplIcfBandwidthActCirActEthCos3 OBJECT-TYPE
   SYNTAX      INTEGER
               {
               unchanged (256)
               }
   MAX-ACCESS  read-write
   STATUS      current
   DESCRIPTION
      "Path: tunnels.editConf.ipsecL2tpTunnels.bandwidth.action.cirAction.ethernet.cosDepth3

       Possibilities:
               unchanged   (256)"
   ::= {er1645v2TTmplIcfEntry 150094592}

er1645v2TTmplIcfBandwidthActCirActEthDei3 OBJECT-TYPE
   SYNTAX      INTEGER
               {
               unchanged (255),
               clear (0),
               set (1)
               }
   MAX-ACCESS  read-write
   STATUS      current
   DESCRIPTION
      "Path: tunnels.editConf.ipsecL2tpTunnels.bandwidth.action.cirAction.ethernet.deiDepth3

       Possibilities:
               unchanged   (255)
               clear   (0)
               set   (1)"
   ::= {er1645v2TTmplIcfEntry 150099712}

er1645v2TTmplIcfBandwidthActCirActEthCos4 OBJECT-TYPE
   SYNTAX      INTEGER
               {
               unchanged (256)
               }
   MAX-ACCESS  read-write
   STATUS      current
   DESCRIPTION
      "Path: tunnels.editConf.ipsecL2tpTunnels.bandwidth.action.cirAction.ethernet.cosDepth4

       Possibilities:
               unchanged   (256)"
   ::= {er1645v2TTmplIcfEntry 150094848}

er1645v2TTmplIcfBandwidthActCirActEthDei4 OBJECT-TYPE
   SYNTAX      INTEGER
               {
               unchanged (255),
               clear (0),
               set (1)
               }
   MAX-ACCESS  read-write
   STATUS      current
   DESCRIPTION
      "Path: tunnels.editConf.ipsecL2tpTunnels.bandwidth.action.cirAction.ethernet.deiDepth4

       Possibilities:
               unchanged   (255)
               clear   (0)
               set   (1)"
   ::= {er1645v2TTmplIcfEntry 150099968}

er1645v2TTmplIcfBandwidthActCirActEthCos5 OBJECT-TYPE
   SYNTAX      INTEGER
               {
               unchanged (256)
               }
   MAX-ACCESS  read-write
   STATUS      current
   DESCRIPTION
      "Path: tunnels.editConf.ipsecL2tpTunnels.bandwidth.action.cirAction.ethernet.cosDepth5

       Possibilities:
               unchanged   (256)"
   ::= {er1645v2TTmplIcfEntry 150095104}

er1645v2TTmplIcfBandwidthActCirActEthDei5 OBJECT-TYPE
   SYNTAX      INTEGER
               {
               unchanged (255),
               clear (0),
               set (1)
               }
   MAX-ACCESS  read-write
   STATUS      current
   DESCRIPTION
      "Path: tunnels.editConf.ipsecL2tpTunnels.bandwidth.action.cirAction.ethernet.deiDepth5

       Possibilities:
               unchanged   (255)
               clear   (0)
               set   (1)"
   ::= {er1645v2TTmplIcfEntry 150100224}

er1645v2TTmplIcfBandwidthActCirActEthCos6 OBJECT-TYPE
   SYNTAX      INTEGER
               {
               unchanged (256)
               }
   MAX-ACCESS  read-write
   STATUS      current
   DESCRIPTION
      "Path: tunnels.editConf.ipsecL2tpTunnels.bandwidth.action.cirAction.ethernet.cosDepth6

       Possibilities:
               unchanged   (256)"
   ::= {er1645v2TTmplIcfEntry 150095360}

er1645v2TTmplIcfBandwidthActCirActEthDei6 OBJECT-TYPE
   SYNTAX      INTEGER
               {
               unchanged (255),
               clear (0),
               set (1)
               }
   MAX-ACCESS  read-write
   STATUS      current
   DESCRIPTION
      "Path: tunnels.editConf.ipsecL2tpTunnels.bandwidth.action.cirAction.ethernet.deiDepth6

       Possibilities:
               unchanged   (255)
               clear   (0)
               set   (1)"
   ::= {er1645v2TTmplIcfEntry 150100480}

er1645v2TTmplIcfBandwidthActCirActEthCos7 OBJECT-TYPE
   SYNTAX      INTEGER
               {
               unchanged (256)
               }
   MAX-ACCESS  read-write
   STATUS      current
   DESCRIPTION
      "Path: tunnels.editConf.ipsecL2tpTunnels.bandwidth.action.cirAction.ethernet.cosDepth7

       Possibilities:
               unchanged   (256)"
   ::= {er1645v2TTmplIcfEntry 150095616}

er1645v2TTmplIcfBandwidthActCirActEthDei7 OBJECT-TYPE
   SYNTAX      INTEGER
               {
               unchanged (255),
               clear (0),
               set (1)
               }
   MAX-ACCESS  read-write
   STATUS      current
   DESCRIPTION
      "Path: tunnels.editConf.ipsecL2tpTunnels.bandwidth.action.cirAction.ethernet.deiDepth7

       Possibilities:
               unchanged   (255)
               clear   (0)
               set   (1)"
   ::= {er1645v2TTmplIcfEntry 150100736}

er1645v2TTmplIcfBandwidthActCirActEthCos8 OBJECT-TYPE
   SYNTAX      INTEGER
               {
               unchanged (256)
               }
   MAX-ACCESS  read-write
   STATUS      current
   DESCRIPTION
      "Path: tunnels.editConf.ipsecL2tpTunnels.bandwidth.action.cirAction.ethernet.cosDepth8

       Possibilities:
               unchanged   (256)"
   ::= {er1645v2TTmplIcfEntry 150095872}

er1645v2TTmplIcfBandwidthActCirActEthDei8 OBJECT-TYPE
   SYNTAX      INTEGER
               {
               unchanged (255),
               clear (0),
               set (1)
               }
   MAX-ACCESS  read-write
   STATUS      current
   DESCRIPTION
      "Path: tunnels.editConf.ipsecL2tpTunnels.bandwidth.action.cirAction.ethernet.deiDepth8

       Possibilities:
               unchanged   (255)
               clear   (0)
               set   (1)"
   ::= {er1645v2TTmplIcfEntry 150100992}

er1645v2TTmplIcfBandwidthActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.ipsecL2tpTunnels.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TTmplIcfEntry 150096128}

er1645v2TTmplIcfBandwidthActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.ipsecL2tpTunnels.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2TTmplIcfEntry 150096384}

er1645v2TTmplIcfBandwidthActCirActEthDrpLev OBJECT-TYPE
   SYNTAX      INTEGER
               {
               unchanged (0)
               }
   MAX-ACCESS  read-write
   STATUS      current
   DESCRIPTION
      "Path: tunnels.editConf.ipsecL2tpTunnels.bandwidth.action.cirAction.ethernet.dropLevel

       Possibilities:
               unchanged   (0)"
   ::= {er1645v2TTmplIcfEntry 150096640}

er1645v2TTmplIcfBandwidthActCirActEthDeFlag OBJECT-TYPE
   SYNTAX      INTEGER
               {
               unchanged (255),
               clear (0),
               set (1)
               }
   MAX-ACCESS  read-write
   STATUS      current
   DESCRIPTION
      "Path: tunnels.editConf.ipsecL2tpTunnels.bandwidth.action.cirAction.ethernet.deFlag

       Possibilities:
               unchanged   (255)
               clear   (0)
               set   (1)"
   ::= {er1645v2TTmplIcfEntry 150097408}

er1645v2TTmplIcfBandwidthActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.ipsecL2tpTunnels.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TTmplIcfEntry 150120704}

er1645v2TTmplIcfBandwidthActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.ipsecL2tpTunnels.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2TTmplIcfEntry 150120960}

er1645v2TTmplIcfBandwidthActCirActIpDrpLev OBJECT-TYPE
   SYNTAX      INTEGER
               {
               unchanged (0)
               }
   MAX-ACCESS  read-write
   STATUS      current
   DESCRIPTION
      "Path: tunnels.editConf.ipsecL2tpTunnels.bandwidth.action.cirAction.ip.dropLevel

       Possibilities:
               unchanged   (0)"
   ::= {er1645v2TTmplIcfEntry 150121216}

er1645v2TTmplIcfBandwidthActCirActIpDeFlag OBJECT-TYPE
   SYNTAX      INTEGER
               {
               unchanged (255),
               clear (0),
               set (1)
               }
   MAX-ACCESS  read-write
   STATUS      current
   DESCRIPTION
      "Path: tunnels.editConf.ipsecL2tpTunnels.bandwidth.action.cirAction.ip.deFlag

       Possibilities:
               unchanged   (255)
               clear   (0)
               set   (1)"
   ::= {er1645v2TTmplIcfEntry 150121984}

er1645v2TTmplIcfBandwidthActEirActNone OBJECT-TYPE
   SYNTAX      OCTET STRING
   MAX-ACCESS  read-write
   STATUS      current
   DESCRIPTION
      "Path: tunnels.editConf.ipsecL2tpTunnels.bandwidth.action.eirAction.none"
   ::= {er1645v2TTmplIcfEntry 150216704}

er1645v2TTmplIcfBandwidthActEirActEthCos1 OBJECT-TYPE
   SYNTAX      INTEGER
               {
               unchanged (256)
               }
   MAX-ACCESS  read-write
   STATUS      current
   DESCRIPTION
      "Path: tunnels.editConf.ipsecL2tpTunnels.bandwidth.action.eirAction.ethernet.cosDepth1

       Possibilities:
               unchanged   (256)"
   ::= {er1645v2TTmplIcfEntry 150225152}

er1645v2TTmplIcfBandwidthActEirActEthDei1 OBJECT-TYPE
   SYNTAX      INTEGER
               {
               unchanged (255),
               clear (0),
               set (1)
               }
   MAX-ACCESS  read-write
   STATUS      current
   DESCRIPTION
      "Path: tunnels.editConf.ipsecL2tpTunnels.bandwidth.action.eirAction.ethernet.deiDepth1

       Possibilities:
               unchanged   (255)
               clear   (0)
               set   (1)"
   ::= {er1645v2TTmplIcfEntry 150230272}

er1645v2TTmplIcfBandwidthActEirActEthCos2 OBJECT-TYPE
   SYNTAX      INTEGER
               {
               unchanged (256)
               }
   MAX-ACCESS  read-write
   STATUS      current
   DESCRIPTION
      "Path: tunnels.editConf.ipsecL2tpTunnels.bandwidth.action.eirAction.ethernet.cosDepth2

       Possibilities:
               unchanged   (256)"
   ::= {er1645v2TTmplIcfEntry 150225408}

er1645v2TTmplIcfBandwidthActEirActEthDei2 OBJECT-TYPE
   SYNTAX      INTEGER
               {
               unchanged (255),
               clear (0),
               set (1)
               }
   MAX-ACCESS  read-write
   STATUS      current
   DESCRIPTION
      "Path: tunnels.editConf.ipsecL2tpTunnels.bandwidth.action.eirAction.ethernet.deiDepth2

       Possibilities:
               unchanged   (255)
               clear   (0)
               set   (1)"
   ::= {er1645v2TTmplIcfEntry 150230528}

er1645v2TTmplIcfBandwidthActEirActEthCos3 OBJECT-TYPE
   SYNTAX      INTEGER
               {
               unchanged (256)
               }
   MAX-ACCESS  read-write
   STATUS      current
   DESCRIPTION
      "Path: tunnels.editConf.ipsecL2tpTunnels.bandwidth.action.eirAction.ethernet.cosDepth3

       Possibilities:
               unchanged   (256)"
   ::= {er1645v2TTmplIcfEntry 150225664}

er1645v2TTmplIcfBandwidthActEirActEthDei3 OBJECT-TYPE
   SYNTAX      INTEGER
               {
               unchanged (255),
               clear (0),
               set (1)
               }
   MAX-ACCESS  read-write
   STATUS      current
   DESCRIPTION
      "Path: tunnels.editConf.ipsecL2tpTunnels.bandwidth.action.eirAction.ethernet.deiDepth3

       Possibilities:
               unchanged   (255)
               clear   (0)
               set   (1)"
   ::= {er1645v2TTmplIcfEntry 150230784}

er1645v2TTmplIcfBandwidthActEirActEthCos4 OBJECT-TYPE
   SYNTAX      INTEGER
               {
               unchanged (256)
               }
   MAX-ACCESS  read-write
   STATUS      current
   DESCRIPTION
      "Path: tunnels.editConf.ipsecL2tpTunnels.bandwidth.action.eirAction.ethernet.cosDepth4

       Possibilities:
               unchanged   (256)"
   ::= {er1645v2TTmplIcfEntry 150225920}

er1645v2TTmplIcfBandwidthActEirActEthDei4 OBJECT-TYPE
   SYNTAX      INTEGER
               {
               unchanged (255),
               clear (0),
               set (1)
               }
   MAX-ACCESS  read-write
   STATUS      current
   DESCRIPTION
      "Path: tunnels.editConf.ipsecL2tpTunnels.bandwidth.action.eirAction.ethernet.deiDepth4

       Possibilities:
               unchanged   (255)
               clear   (0)
               set   (1)"
   ::= {er1645v2TTmplIcfEntry 150231040}

er1645v2TTmplIcfBandwidthActEirActEthCos5 OBJECT-TYPE
   SYNTAX      INTEGER
               {
               unchanged (256)
               }
   MAX-ACCESS  read-write
   STATUS      current
   DESCRIPTION
      "Path: tunnels.editConf.ipsecL2tpTunnels.bandwidth.action.eirAction.ethernet.cosDepth5

       Possibilities:
               unchanged   (256)"
   ::= {er1645v2TTmplIcfEntry 150226176}

er1645v2TTmplIcfBandwidthActEirActEthDei5 OBJECT-TYPE
   SYNTAX      INTEGER
               {
               unchanged (255),
               clear (0),
               set (1)
               }
   MAX-ACCESS  read-write
   STATUS      current
   DESCRIPTION
      "Path: tunnels.editConf.ipsecL2tpTunnels.bandwidth.action.eirAction.ethernet.deiDepth5

       Possibilities:
               unchanged   (255)
               clear   (0)
               set   (1)"
   ::= {er1645v2TTmplIcfEntry 150231296}

er1645v2TTmplIcfBandwidthActEirActEthCos6 OBJECT-TYPE
   SYNTAX      INTEGER
               {
               unchanged (256)
               }
   MAX-ACCESS  read-write
   STATUS      current
   DESCRIPTION
      "Path: tunnels.editConf.ipsecL2tpTunnels.bandwidth.action.eirAction.ethernet.cosDepth6

       Possibilities:
               unchanged   (256)"
   ::= {er1645v2TTmplIcfEntry 150226432}

er1645v2TTmplIcfBandwidthActEirActEthDei6 OBJECT-TYPE
   SYNTAX      INTEGER
               {
               unchanged (255),
               clear (0),
               set (1)
               }
   MAX-ACCESS  read-write
   STATUS      current
   DESCRIPTION
      "Path: tunnels.editConf.ipsecL2tpTunnels.bandwidth.action.eirAction.ethernet.deiDepth6

       Possibilities:
               unchanged   (255)
               clear   (0)
               set   (1)"
   ::= {er1645v2TTmplIcfEntry 150231552}

er1645v2TTmplIcfBandwidthActEirActEthCos7 OBJECT-TYPE
   SYNTAX      INTEGER
               {
               unchanged (256)
               }
   MAX-ACCESS  read-write
   STATUS      current
   DESCRIPTION
      "Path: tunnels.editConf.ipsecL2tpTunnels.bandwidth.action.eirAction.ethernet.cosDepth7

       Possibilities:
               unchanged   (256)"
   ::= {er1645v2TTmplIcfEntry 150226688}

er1645v2TTmplIcfBandwidthActEirActEthDei7 OBJECT-TYPE
   SYNTAX      INTEGER
               {
               unchanged (255),
               clear (0),
               set (1)
               }
   MAX-ACCESS  read-write
   STATUS      current
   DESCRIPTION
      "Path: tunnels.editConf.ipsecL2tpTunnels.bandwidth.action.eirAction.ethernet.deiDepth7

       Possibilities:
               unchanged   (255)
               clear   (0)
               set   (1)"
   ::= {er1645v2TTmplIcfEntry 150231808}

er1645v2TTmplIcfBandwidthActEirActEthCos8 OBJECT-TYPE
   SYNTAX      INTEGER
               {
               unchanged (256)
               }
   MAX-ACCESS  read-write
   STATUS      current
   DESCRIPTION
      "Path: tunnels.editConf.ipsecL2tpTunnels.bandwidth.action.eirAction.ethernet.cosDepth8

       Possibilities:
               unchanged   (256)"
   ::= {er1645v2TTmplIcfEntry 150226944}

er1645v2TTmplIcfBandwidthActEirActEthDei8 OBJECT-TYPE
   SYNTAX      INTEGER
               {
               unchanged (255),
               clear (0),
               set (1)
               }
   MAX-ACCESS  read-write
   STATUS      current
   DESCRIPTION
      "Path: tunnels.editConf.ipsecL2tpTunnels.bandwidth.action.eirAction.ethernet.deiDepth8

       Possibilities:
               unchanged   (255)
               clear   (0)
               set   (1)"
   ::= {er1645v2TTmplIcfEntry 150232064}

er1645v2TTmplIcfBandwidthActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.ipsecL2tpTunnels.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TTmplIcfEntry 150227200}

er1645v2TTmplIcfBandwidthActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.ipsecL2tpTunnels.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2TTmplIcfEntry 150227456}

er1645v2TTmplIcfBandwidthActEirActEthDrpLev OBJECT-TYPE
   SYNTAX      INTEGER
               {
               unchanged (0)
               }
   MAX-ACCESS  read-write
   STATUS      current
   DESCRIPTION
      "Path: tunnels.editConf.ipsecL2tpTunnels.bandwidth.action.eirAction.ethernet.dropLevel

       Possibilities:
               unchanged   (0)"
   ::= {er1645v2TTmplIcfEntry 150227712}

er1645v2TTmplIcfBandwidthActEirActEthDeFlag OBJECT-TYPE
   SYNTAX      INTEGER
               {
               unchanged (255),
               clear (0),
               set (1)
               }
   MAX-ACCESS  read-write
   STATUS      current
   DESCRIPTION
      "Path: tunnels.editConf.ipsecL2tpTunnels.bandwidth.action.eirAction.ethernet.deFlag

       Possibilities:
               unchanged   (255)
               clear   (0)
               set   (1)"
   ::= {er1645v2TTmplIcfEntry 150228480}

er1645v2TTmplIcfBandwidthActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.ipsecL2tpTunnels.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TTmplIcfEntry 150251776}

er1645v2TTmplIcfBandwidthActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.ipsecL2tpTunnels.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2TTmplIcfEntry 150252032}

er1645v2TTmplIcfBandwidthActEirActIpDrpLev OBJECT-TYPE
   SYNTAX      INTEGER
               {
               unchanged (0)
               }
   MAX-ACCESS  read-write
   STATUS      current
   DESCRIPTION
      "Path: tunnels.editConf.ipsecL2tpTunnels.bandwidth.action.eirAction.ip.dropLevel

       Possibilities:
               unchanged   (0)"
   ::= {er1645v2TTmplIcfEntry 150252288}

er1645v2TTmplIcfBandwidthActEirActIpDeFlag OBJECT-TYPE
   SYNTAX      INTEGER
               {
               unchanged (255),
               clear (0),
               set (1)
               }
   MAX-ACCESS  read-write
   STATUS      current
   DESCRIPTION
      "Path: tunnels.editConf.ipsecL2tpTunnels.bandwidth.action.eirAction.ip.deFlag

       Possibilities:
               unchanged   (255)
               clear   (0)
               set   (1)"
   ::= {er1645v2TTmplIcfEntry 150253056}

er1645v2TTmplIcfBandwidthActViolActNone OBJECT-TYPE
   SYNTAX      OCTET STRING
   MAX-ACCESS  read-write
   STATUS      current
   DESCRIPTION
      "Path: tunnels.editConf.ipsecL2tpTunnels.bandwidth.action.violateAction.none"
   ::= {er1645v2TTmplIcfEntry 150347776}

er1645v2TTmplIcfBandwidthActViolActDrop OBJECT-TYPE
   SYNTAX      OCTET STRING
   MAX-ACCESS  read-write
   STATUS      current
   DESCRIPTION
      "Path: tunnels.editConf.ipsecL2tpTunnels.bandwidth.action.violateAction.drop"
   ::= {er1645v2TTmplIcfEntry 150364160}

er1645v2TTmplIcfBandwidthActViolActEthCos1 OBJECT-TYPE
   SYNTAX      INTEGER
               {
               unchanged (256)
               }
   MAX-ACCESS  read-write
   STATUS      current
   DESCRIPTION
      "Path: tunnels.editConf.ipsecL2tpTunnels.bandwidth.action.violateAction.ethernet.cosDepth1

       Possibilities:
               unchanged   (256)"
   ::= {er1645v2TTmplIcfEntry 150356224}

er1645v2TTmplIcfBandwidthActViolActEthDei1 OBJECT-TYPE
   SYNTAX      INTEGER
               {
               unchanged (255),
               clear (0),
               set (1)
               }
   MAX-ACCESS  read-write
   STATUS      current
   DESCRIPTION
      "Path: tunnels.editConf.ipsecL2tpTunnels.bandwidth.action.violateAction.ethernet.deiDepth1

       Possibilities:
               unchanged   (255)
               clear   (0)
               set   (1)"
   ::= {er1645v2TTmplIcfEntry 150361344}

er1645v2TTmplIcfBandwidthActViolActEthCos2 OBJECT-TYPE
   SYNTAX      INTEGER
               {
               unchanged (256)
               }
   MAX-ACCESS  read-write
   STATUS      current
   DESCRIPTION
      "Path: tunnels.editConf.ipsecL2tpTunnels.bandwidth.action.violateAction.ethernet.cosDepth2

       Possibilities:
               unchanged   (256)"
   ::= {er1645v2TTmplIcfEntry 150356480}

er1645v2TTmplIcfBandwidthActViolActEthDei2 OBJECT-TYPE
   SYNTAX      INTEGER
               {
               unchanged (255),
               clear (0),
               set (1)
               }
   MAX-ACCESS  read-write
   STATUS      current
   DESCRIPTION
      "Path: tunnels.editConf.ipsecL2tpTunnels.bandwidth.action.violateAction.ethernet.deiDepth2

       Possibilities:
               unchanged   (255)
               clear   (0)
               set   (1)"
   ::= {er1645v2TTmplIcfEntry 150361600}

er1645v2TTmplIcfBandwidthActViolActEthCos3 OBJECT-TYPE
   SYNTAX      INTEGER
               {
               unchanged (256)
               }
   MAX-ACCESS  read-write
   STATUS      current
   DESCRIPTION
      "Path: tunnels.editConf.ipsecL2tpTunnels.bandwidth.action.violateAction.ethernet.cosDepth3

       Possibilities:
               unchanged   (256)"
   ::= {er1645v2TTmplIcfEntry 150356736}

er1645v2TTmplIcfBandwidthActViolActEthDei3 OBJECT-TYPE
   SYNTAX      INTEGER
               {
               unchanged (255),
               clear (0),
               set (1)
               }
   MAX-ACCESS  read-write
   STATUS      current
   DESCRIPTION
      "Path: tunnels.editConf.ipsecL2tpTunnels.bandwidth.action.violateAction.ethernet.deiDepth3

       Possibilities:
               unchanged   (255)
               clear   (0)
               set   (1)"
   ::= {er1645v2TTmplIcfEntry 150361856}

er1645v2TTmplIcfBandwidthActViolActEthCos4 OBJECT-TYPE
   SYNTAX      INTEGER
               {
               unchanged (256)
               }
   MAX-ACCESS  read-write
   STATUS      current
   DESCRIPTION
      "Path: tunnels.editConf.ipsecL2tpTunnels.bandwidth.action.violateAction.ethernet.cosDepth4

       Possibilities:
               unchanged   (256)"
   ::= {er1645v2TTmplIcfEntry 150356992}

er1645v2TTmplIcfBandwidthActViolActEthDei4 OBJECT-TYPE
   SYNTAX      INTEGER
               {
               unchanged (255),
               clear (0),
               set (1)
               }
   MAX-ACCESS  read-write
   STATUS      current
   DESCRIPTION
      "Path: tunnels.editConf.ipsecL2tpTunnels.bandwidth.action.violateAction.ethernet.deiDepth4

       Possibilities:
               unchanged   (255)
               clear   (0)
               set   (1)"
   ::= {er1645v2TTmplIcfEntry 150362112}

er1645v2TTmplIcfBandwidthActViolActEthCos5 OBJECT-TYPE
   SYNTAX      INTEGER
               {
               unchanged (256)
               }
   MAX-ACCESS  read-write
   STATUS      current
   DESCRIPTION
      "Path: tunnels.editConf.ipsecL2tpTunnels.bandwidth.action.violateAction.ethernet.cosDepth5

       Possibilities:
               unchanged   (256)"
   ::= {er1645v2TTmplIcfEntry 150357248}

er1645v2TTmplIcfBandwidthActViolActEthDei5 OBJECT-TYPE
   SYNTAX      INTEGER
               {
               unchanged (255),
               clear (0),
               set (1)
               }
   MAX-ACCESS  read-write
   STATUS      current
   DESCRIPTION
      "Path: tunnels.editConf.ipsecL2tpTunnels.bandwidth.action.violateAction.ethernet.deiDepth5

       Possibilities:
               unchanged   (255)
               clear   (0)
               set   (1)"
   ::= {er1645v2TTmplIcfEntry 150362368}

er1645v2TTmplIcfBandwidthActViolActEthCos6 OBJECT-TYPE
   SYNTAX      INTEGER
               {
               unchanged (256)
               }
   MAX-ACCESS  read-write
   STATUS      current
   DESCRIPTION
      "Path: tunnels.editConf.ipsecL2tpTunnels.bandwidth.action.violateAction.ethernet.cosDepth6

       Possibilities:
               unchanged   (256)"
   ::= {er1645v2TTmplIcfEntry 150357504}

er1645v2TTmplIcfBandwidthActViolActEthDei6 OBJECT-TYPE
   SYNTAX      INTEGER
               {
               unchanged (255),
               clear (0),
               set (1)
               }
   MAX-ACCESS  read-write
   STATUS      current
   DESCRIPTION
      "Path: tunnels.editConf.ipsecL2tpTunnels.bandwidth.action.violateAction.ethernet.deiDepth6

       Possibilities:
               unchanged   (255)
               clear   (0)
               set   (1)"
   ::= {er1645v2TTmplIcfEntry 150362624}

er1645v2TTmplIcfBandwidthActViolActEthCos7 OBJECT-TYPE
   SYNTAX      INTEGER
               {
               unchanged (256)
               }
   MAX-ACCESS  read-write
   STATUS      current
   DESCRIPTION
      "Path: tunnels.editConf.ipsecL2tpTunnels.bandwidth.action.violateAction.ethernet.cosDepth7

       Possibilities:
               unchanged   (256)"
   ::= {er1645v2TTmplIcfEntry 150357760}

er1645v2TTmplIcfBandwidthActViolActEthDei7 OBJECT-TYPE
   SYNTAX      INTEGER
               {
               unchanged (255),
               clear (0),
               set (1)
               }
   MAX-ACCESS  read-write
   STATUS      current
   DESCRIPTION
      "Path: tunnels.editConf.ipsecL2tpTunnels.bandwidth.action.violateAction.ethernet.deiDepth7

       Possibilities:
               unchanged   (255)
               clear   (0)
               set   (1)"
   ::= {er1645v2TTmplIcfEntry 150362880}

er1645v2TTmplIcfBandwidthActViolActEthCos8 OBJECT-TYPE
   SYNTAX      INTEGER
               {
               unchanged (256)
               }
   MAX-ACCESS  read-write
   STATUS      current
   DESCRIPTION
      "Path: tunnels.editConf.ipsecL2tpTunnels.bandwidth.action.violateAction.ethernet.cosDepth8

       Possibilities:
               unchanged   (256)"
   ::= {er1645v2TTmplIcfEntry 150358016}

er1645v2TTmplIcfBandwidthActViolActEthDei8 OBJECT-TYPE
   SYNTAX      INTEGER
               {
               unchanged (255),
               clear (0),
               set (1)
               }
   MAX-ACCESS  read-write
   STATUS      current
   DESCRIPTION
      "Path: tunnels.editConf.ipsecL2tpTunnels.bandwidth.action.violateAction.ethernet.deiDepth8

       Possibilities:
               unchanged   (255)
               clear   (0)
               set   (1)"
   ::= {er1645v2TTmplIcfEntry 150363136}

er1645v2TTmplIcfBandwidthActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.ipsecL2tpTunnels.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TTmplIcfEntry 150358272}

er1645v2TTmplIcfBandwidthActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.ipsecL2tpTunnels.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2TTmplIcfEntry 150358528}

er1645v2TTmplIcfBandwidthActViolActEthDrpLev OBJECT-TYPE
   SYNTAX      INTEGER
               {
               unchanged (0)
               }
   MAX-ACCESS  read-write
   STATUS      current
   DESCRIPTION
      "Path: tunnels.editConf.ipsecL2tpTunnels.bandwidth.action.violateAction.ethernet.dropLevel

       Possibilities:
               unchanged   (0)"
   ::= {er1645v2TTmplIcfEntry 150358784}

er1645v2TTmplIcfBandwidthActViolActEthDeFlag OBJECT-TYPE
   SYNTAX      INTEGER
               {
               unchanged (255),
               clear (0),
               set (1)
               }
   MAX-ACCESS  read-write
   STATUS      current
   DESCRIPTION
      "Path: tunnels.editConf.ipsecL2tpTunnels.bandwidth.action.violateAction.ethernet.deFlag

       Possibilities:
               unchanged   (255)
               clear   (0)
               set   (1)"
   ::= {er1645v2TTmplIcfEntry 150359552}

er1645v2TTmplIcfBandwidthActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.ipsecL2tpTunnels.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TTmplIcfEntry 150382848}

er1645v2TTmplIcfBandwidthActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.ipsecL2tpTunnels.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2TTmplIcfEntry 150383104}

er1645v2TTmplIcfBandwidthActViolActIpDrpLev OBJECT-TYPE
   SYNTAX      INTEGER
               {
               unchanged (0)
               }
   MAX-ACCESS  read-write
   STATUS      current
   DESCRIPTION
      "Path: tunnels.editConf.ipsecL2tpTunnels.bandwidth.action.violateAction.ip.dropLevel

       Possibilities:
               unchanged   (0)"
   ::= {er1645v2TTmplIcfEntry 150383360}

er1645v2TTmplIcfBandwidthActViolActIpDeFlag OBJECT-TYPE
   SYNTAX      INTEGER
               {
               unchanged (255),
               clear (0),
               set (1)
               }
   MAX-ACCESS  read-write
   STATUS      current
   DESCRIPTION
      "Path: tunnels.editConf.ipsecL2tpTunnels.bandwidth.action.violateAction.ip.deFlag

       Possibilities:
               unchanged   (255)
               clear   (0)
               set   (1)"
   ::= {er1645v2TTmplIcfEntry 150384128}

er1645v2TTmplIcfBridgingVlTVlans OBJECT-TYPE
   SYNTAX      SEQUENCE OF Er1645v2TTmplIcfBridgingVlTVlansEntry
   MAX-ACCESS  not-accessible
   STATUS      current
   DESCRIPTION
      ""
   ::= {er1645v2TTmplIcf 459079680}

er1645v2TTmplIcfBridgingVlTVlansEntry OBJECT-TYPE
   SYNTAX      Er1645v2TTmplIcfBridgingVlTVlansEntry
   MAX-ACCESS  not-accessible
   STATUS      current
   DESCRIPTION
      ""
   INDEX      { er1645v2TTmplIcfTableIx,
                er1645v2TTmplIcfBridgingVlTVlansTableIx }
   ::= {er1645v2TTmplIcfBridgingVlTVlans 1}

Er1645v2TTmplIcfBridgingVlTVlansEntry ::=
   SEQUENCE
      {
      er1645v2TTmplIcfBridgingVlTVlansActions
         VariableLengthTableActions,
      er1645v2TTmplIcfBridgingVlTVlansTableIx
         TableIndex,
      er1645v2TTmplIcfBridgingVlTVlansVid
         Integer32,
      er1645v2TTmplIcfBridgingVlTVlansEndVid
         Integer32,
      er1645v2TTmplIcfBridgingVlTVlansAction
         INTEGER,
      er1645v2TTmplIcfBridgingVlTVlansTagInfoTpid
         INTEGER,
      er1645v2TTmplIcfBridgingVlTVlansTagInfoVid
         Integer32
      }

er1645v2TTmplIcfBridgingVlTVlansActions OBJECT-TYPE
   SYNTAX      VariableLengthTableActions
   MAX-ACCESS  read-write
   STATUS      current
   DESCRIPTION
      "By way of this field, some manipulations
       on this table may be performed."
   ::= {er1645v2TTmplIcfBridgingVlTVlansEntry 2}

er1645v2TTmplIcfBridgingVlTVlansTableIx OBJECT-TYPE
   SYNTAX      TableIndex
   MAX-ACCESS  not-accessible
   STATUS      current
   DESCRIPTION
      ""
   ::= {er1645v2TTmplIcfBridgingVlTVlansEntry 11}

er1645v2TTmplIcfBridgingVlTVlansVid OBJECT-TYPE
   SYNTAX      Integer32
   MAX-ACCESS  read-write
   STATUS      current
   DESCRIPTION
      "Path: tunnels.editConf.ipsecL2tpTunnels.bridging.vlanTagging.vlans.vid"
   ::= {er1645v2TTmplIcfBridgingVlTVlansEntry 536870912}

er1645v2TTmplIcfBridgingVlTVlansEndVid OBJECT-TYPE
   SYNTAX      Integer32
   MAX-ACCESS  read-write
   STATUS      current
   DESCRIPTION
      "Path: tunnels.editConf.ipsecL2tpTunnels.bridging.vlanTagging.vlans.endVid"
   ::= {er1645v2TTmplIcfBridgingVlTVlansEntry 2147483648}

er1645v2TTmplIcfBridgingVlTVlansAction OBJECT-TYPE
   SYNTAX      INTEGER
               {
               discard (0),
               accept (1),
               tag (2)
               }
   MAX-ACCESS  read-write
   STATUS      current
   DESCRIPTION
      "Path: tunnels.editConf.ipsecL2tpTunnels.bridging.vlanTagging.vlans.action

       Possibilities:
               discard   (0)
               accept   (1)
               tag   (2)"
   ::= {er1645v2TTmplIcfBridgingVlTVlansEntry 1073741824}

er1645v2TTmplIcfBridgingVlTVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: tunnels.editConf.ipsecL2tpTunnels.bridging.vlanTagging.vlans.tagInfo.tpid

       Possibilities:
               dot1Q   (33024)
               dot1ad   (34984)
               0x9100   (37120)
               0x9200   (37376)
               0x9300   (37632)"
   ::= {er1645v2TTmplIcfBridgingVlTVlansEntry 1677721600}

er1645v2TTmplIcfBridgingVlTVlansTagInfoVid OBJECT-TYPE
   SYNTAX      Integer32
   MAX-ACCESS  read-write
   STATUS      current
   DESCRIPTION
      "Path: tunnels.editConf.ipsecL2tpTunnels.bridging.vlanTagging.vlans.tagInfo.vid"
   ::= {er1645v2TTmplIcfBridgingVlTVlansEntry 1744830464}


er1645v2TTmplCfg OBJECT IDENTIFIER ::= {er1645v2TTmpl 1}

er1645v2TTmplCfgSSCTable OBJECT-TYPE
   SYNTAX      SEQUENCE OF Er1645v2TTmplCfgEntry
   MAX-ACCESS  not-accessible
   STATUS      current
   DESCRIPTION
      ""
   ::= {er1645v2TTmplCfg 1}

er1645v2TTmplCfgEntry OBJECT-TYPE
   SYNTAX      Er1645v2TTmplCfgEntry
   MAX-ACCESS  not-accessible
   STATUS      current
   DESCRIPTION
      ""
   INDEX      { er1645v2TTmplCfgTableIx }
   ::= {er1645v2TTmplCfgSSCTable 1}

Er1645v2TTmplCfgEntry ::=
   SEQUENCE
      {
      er1645v2TTmplCfgActions
         VariableLengthTableActions,
      er1645v2TTmplCfgTableIx
         TableIndex,
      er1645v2TTmplCfgName
         DisplayString,
      er1645v2TTmplCfgRemark
         DisplayString,
      er1645v2TTmplCfgAdminStatus
         INTEGER,
      er1645v2TTmplCfgMode
         INTEGER,
      er1645v2TTmplCfgPriorityPolicy
         DisplayString,
      er1645v2TTmplCfgIpVrfRouter
         DisplayString,
      er1645v2TTmplCfgIpAdr
         IpAddress,
      er1645v2TTmplCfgIpNetm
         IpAddress,
      er1645v2TTmplCfgIpSNetName
         INTEGER,
      er1645v2TTmplCfgIpSNetCust
         DisplayString,
      er1645v2TTmplCfgIpRem
         IpAddress,
      er1645v2TTmplCfgIpUnnumbered
         DisplayString,
      er1645v2TTmplCfgIpAcceptLocAddr
         INTEGER,
      er1645v2TTmplCfgIpAcceptRemAddr
         INTEGER,
      er1645v2TTmplCfgIpGwPref
         Integer32,
      er1645v2TTmplCfgIpRsn
         INTEGER,
      er1645v2TTmplCfgIpMtu
         Integer32,
      er1645v2TTmplCfgIpMssAdjust
         INTEGER,
      er1645v2TTmplCfgIpRipMetric
         Integer32,
      er1645v2TTmplCfgIpRipMetricOut
         Integer32,
      er1645v2TTmplCfgIpRipMode
         INTEGER,
      er1645v2TTmplCfgIpRipTxVersion
         INTEGER,
      er1645v2TTmplCfgIpRipRxVersion
         INTEGER,
      er1645v2TTmplCfgIpRipSplitHorizon
         INTEGER,
      er1645v2TTmplCfgIpRipAuth
         INTEGER,
      er1645v2TTmplCfgIpRipFilter
         DisplayString,
      er1645v2TTmplCfgIpRipFilterIn
         DisplayString,
      er1645v2TTmplCfgIpRipSnapshot
         INTEGER,
      er1645v2TTmplCfgIpRipClearNextHop
         INTEGER,
      er1645v2TTmplCfgIpAccPol
         DisplayString,
      er1645v2TTmplCfgIpAB
         DisplayString,
      er1645v2TTmplCfgIpMA
         INTEGER,
      er1645v2TTmplCfgIpMF
         Integer32,
      er1645v2TTmplCfgIpDB
         INTEGER,
      er1645v2TTmplCfgIpIR
         INTEGER,
      er1645v2TTmplCfgIpIgmp
         INTEGER,
      er1645v2TTmplCfgIpNN
         DisplayString,
      er1645v2TTmplCfgIpPimMode
         INTEGER,
      er1645v2TTmplCfgIpPimDrPriority
         Counter32,
      er1645v2TTmplCfgIpPimHelloTime
         TimeTicks,
      er1645v2TTmplCfgIpPimPropagationDelay
         TimeTicks,
      er1645v2TTmplCfgIpPimOverrideInterval
         TimeTicks,
      er1645v2TTmplCfgIpPimBsrBorder
         INTEGER,
      er1645v2TTmplCfgIpPimTtlThreshold
         Integer32,
      er1645v2TTmplCfgIpIMNetworkUnreachable
         INTEGER,
      er1645v2TTmplCfgIpIMHostUnreachable
         INTEGER,
      er1645v2TTmplCfgIpIMProtocolUnreachable
         INTEGER,
      er1645v2TTmplCfgIpIMPortUnreachable
         INTEGER,
      er1645v2TTmplCfgIpIMMtuExceeded
         INTEGER,
      er1645v2TTmplCfgIpIMAdminProhibited
         INTEGER,
      er1645v2TTmplCfgIpIMTtlExceeded
         INTEGER,
      er1645v2TTmplCfgIpIMRedirect
         INTEGER,
      er1645v2TTmplCfgBridgingAccList
         DisplayString,
      er1645v2TTmplCfgBridgingInACL
         DisplayString,
      er1645v2TTmplCfgBridgingTp
         DisplayString,
      er1645v2TTmplCfgBridgingBrGrp
         DisplayString,
      er1645v2TTmplCfgBridgingLimBC
         INTEGER,
      er1645v2TTmplCfgBridgingPrivateMode
         INTEGER,
      er1645v2TTmplCfgBridgingLearning
         INTEGER,
      er1645v2TTmplCfgBridgingMaxCacheSize
         INTEGER,
      er1645v2TTmplCfgBridgingRelearnDropOnRelearn
         INTEGER,
      er1645v2TTmplCfgBridgingRelearnShutdownThreshold
         Integer32,
      er1645v2TTmplCfgBridgingRelearnShutdownTime
         TimeTicks,
      er1645v2TTmplCfgBridgingRelearnLoopDetection
         INTEGER,
      er1645v2TTmplCfgBridgingRelearnLoopDetectionInterval
         TimeTicks,
      er1645v2TTmplCfgBridgingVlanMemberShip
         INTEGER,
      er1645v2TTmplCfgBridgingVlTUntaggedAction
         INTEGER,
      er1645v2TTmplCfgBridgingVlTUntaggedTagInfoTpid
         INTEGER,
      er1645v2TTmplCfgBridgingVlTUntaggedTagInfoVid
         Integer32,
      er1645v2TTmplCfgBridgingVlTUnknownVlansAction
         INTEGER,
      er1645v2TTmplCfgBridgingVlTUnknownVlansTagInfoTpid
         INTEGER,
      er1645v2TTmplCfgBridgingVlTUnknownVlansTagInfoVid
         Integer32,
      er1645v2TTmplCfgBridgingDot1adType
         INTEGER,
      er1645v2TTmplCfgBridgingPriority
         Integer32,
      er1645v2TTmplCfgBridgingPathCost
         Integer32,
      er1645v2TTmplCfgBridgingInternalPathCost
         Integer32,
      er1645v2TTmplCfgBridgingTCD
         INTEGER,
      er1645v2TTmplCfgBridgingRestrictedRole
         INTEGER,
      er1645v2TTmplCfgBridgingAdminEdge
         INTEGER,
      er1645v2TTmplCfgBridgingOamMacDeviceMac
         DisplayString,
      er1645v2TTmplCfgBridgingOamMacUserMac
         OCTET STRING,
      er1645v2TTmplCfgBridgingOamMacBridgeMac
         DisplayString,
      er1645v2TTmplCfgBridgingMgmtInline
         INTEGER,
      er1645v2TTmplCfgBridgingL2ptMode
         INTEGER,
      er1645v2TTmplCfgBridgingL2ptProtocols
         Integer32,
      er1645v2TTmplCfgBridgingL2ptDestMac
         OCTET STRING,
      er1645v2TTmplCfgBridgingL2ptCos
         INTEGER,
      er1645v2TTmplCfgBridgingL2ptDropThrStp
         INTEGER,
      er1645v2TTmplCfgBridgingL2ptDropThrLldp
         INTEGER,
      er1645v2TTmplCfgBridgingL2ptDropThrOam
         INTEGER,
      er1645v2TTmplCfgBridgingL2ptDropThrCdp
         INTEGER,
      er1645v2TTmplCfgBridgingL2ptDropThrVtp
         INTEGER,
      er1645v2TTmplCfgBridgingL2ptDropThrLacp
         INTEGER,
      er1645v2TTmplCfgBridgingL2ptDropThrEfmOam
         INTEGER,
      er1645v2TTmplCfgBridgingL2ptDropThrPvst
         INTEGER,
      er1645v2TTmplCfgBridgingL2ptDropThrMmrp
         INTEGER,
      er1645v2TTmplCfgBridgingL2ptDropThrMvrp
         INTEGER,
      er1645v2TTmplCfgBridgingL2ptDropThrGvrp
         INTEGER,
      er1645v2TTmplCfgBridgingL2ptDropThrGmrp
         INTEGER,
      er1645v2TTmplCfgBridgingL2ptDropThrDtp
         INTEGER,
      er1645v2TTmplCfgBridgingL2ptDropThrPagp
         INTEGER,
      er1645v2TTmplCfgBridgingL2ptDropThrUdld
         INTEGER,
      er1645v2TTmplCfgL2tpLocalIpAddress
         IpAddress,
      er1645v2TTmplCfgL2tpRemoteIpAddress
         IpAddress,
      er1645v2TTmplCfgL2tpRemoteDnsName
         DisplayString,
      er1645v2TTmplCfgL2tpAuthen
         INTEGER,
      er1645v2TTmplCfgL2tpPppNam
         DisplayString,
      er1645v2TTmplCfgL2tpPppSec
         DisplayString,
      er1645v2TTmplCfgL2tpEncMPppSec
         INTEGER,
      er1645v2TTmplCfgL2tpEncPppSec
         DisplayString,
      er1645v2TTmplCfgL2tpLnkMOperation
         INTEGER,
      er1645v2TTmplCfgL2tpLnkMInterval
         TimeTicks,
      er1645v2TTmplCfgL2tpLnkMRepTimeOut
         TimeTicks,
      er1645v2TTmplCfgL2tpLnkMFailsPrmt
         Integer32,
      er1645v2TTmplCfgL2tpType
         INTEGER,
      er1645v2TTmplCfgL2tpDataseqnr
         INTEGER,
      er1645v2TTmplCfgL2tpKeepaliveTO
         Integer32,
      er1645v2TTmplCfgL2tpNoTraffT0
         Integer32,
      er1645v2TTmplCfgL2tpMode
         INTEGER,
      er1645v2TTmplCfgL2tpAuth
         INTEGER,
      er1645v2TTmplCfgL2tpSecret
         DisplayString,
      er1645v2TTmplCfgL2tpTos
         INTEGER,
      er1645v2TTmplCfgL2tpRetrans
         Integer32,
      er1645v2TTmplCfgL2tpTransmitws
         Integer32,
      er1645v2TTmplCfgL2tpRcsws
         Integer32,
      er1645v2TTmplCfgL2tpUdpcheck
         INTEGER,
      er1645v2TTmplCfgL2tpCalledNr
         DisplayString,
      er1645v2TTmplCfgL2tpSpeed
         Integer32,
      er1645v2TTmplCfgL2tpMtu
         Integer32,
      er1645v2TTmplCfgL2tpHostName
         DisplayString,
      er1645v2TTmplCfgBackupInterface
         DisplayString,
      er1645v2TTmplCfgBackupTimeOut
         Integer32,
      er1645v2TTmplCfgBackupAutoRetry
         INTEGER,
      er1645v2TTmplCfgInbBwCir
         Integer32,
      er1645v2TTmplCfgInbBwTc
         INTEGER,
      er1645v2TTmplCfgInbBwCorrType
         INTEGER,
      er1645v2TTmplCfgInbBwCorrPredefEncapsFrameRelay
         DisplayString,
      er1645v2TTmplCfgInbBwCorrPredefEncapsPpp
         DisplayString,
      er1645v2TTmplCfgInbBwCorrPredefEncapsAtmHl
         INTEGER,
      er1645v2TTmplCfgInbBwCorrPredefEncapsAtmMp
         INTEGER,
      er1645v2TTmplCfgInbBwCorrPredefEncapsHdlc
         DisplayString,
      er1645v2TTmplCfgInbBwCorrPredefEncapsEfmFs
         Integer32,
      er1645v2TTmplCfgInbBwCorrPredefEncapsEfmIb
         Integer32,
      er1645v2TTmplCfgInbBwCorrPredefMode
         INTEGER,
      er1645v2TTmplCfgInbBwCorrManualOverhead
         Integer32,
      er1645v2TTmplCfgInbBwCorrManualFrameData
         Counter32,
      er1645v2TTmplCfgInbBwCorrManualFrameHeader
         Counter32,
      er1645v2TTmplCfgInbBwMaxFifoQLen
         Integer32,
      er1645v2TTmplCfgInbBwPriorityPolicy
         DisplayString,
      er1645v2TTmplCfgBandwidthMode
         INTEGER,
      er1645v2TTmplCfgBandwidthCir
         Integer32,
      er1645v2TTmplCfgBandwidthEir
         Integer32,
      er1645v2TTmplCfgBandwidthUnit
         INTEGER,
      er1645v2TTmplCfgBandwidthTc
         INTEGER,
      er1645v2TTmplCfgBandwidthTcFactor
         INTEGER,
      er1645v2TTmplCfgBandwidthCorrType
         INTEGER,
      er1645v2TTmplCfgBandwidthCorrPredefEncapsFrameRelay
         DisplayString,
      er1645v2TTmplCfgBandwidthCorrPredefEncapsPpp
         DisplayString,
      er1645v2TTmplCfgBandwidthCorrPredefEncapsAtmHl
         INTEGER,
      er1645v2TTmplCfgBandwidthCorrPredefEncapsAtmMp
         INTEGER,
      er1645v2TTmplCfgBandwidthCorrPredefEncapsHdlc
         DisplayString,
      er1645v2TTmplCfgBandwidthCorrPredefEncapsEfmFs
         Integer32,
      er1645v2TTmplCfgBandwidthCorrPredefEncapsEfmIb
         Integer32,
      er1645v2TTmplCfgBandwidthCorrPredefMode
         INTEGER,
      er1645v2TTmplCfgBandwidthCorrManualOverhead
         Integer32,
      er1645v2TTmplCfgBandwidthCorrManualFrameData
         Counter32,
      er1645v2TTmplCfgBandwidthCorrManualFrameHeader
         Counter32,
      er1645v2TTmplCfgBandwidthMaxFifoQLen
         Integer32,
      er1645v2TTmplCfgBandwidthDeFlagCir
         INTEGER,
      er1645v2TTmplCfgBandwidthDeFlagEir
         INTEGER,
      er1645v2TTmplCfgBandwidthDeFlagViolate
         INTEGER,
      er1645v2TTmplCfgBandwidthActCirActNone
         OCTET STRING,
      er1645v2TTmplCfgBandwidthActCirActEthCos1
         INTEGER,
      er1645v2TTmplCfgBandwidthActCirActEthDei1
         INTEGER,
      er1645v2TTmplCfgBandwidthActCirActEthCos2
         INTEGER,
      er1645v2TTmplCfgBandwidthActCirActEthDei2
         INTEGER,
      er1645v2TTmplCfgBandwidthActCirActEthCos3
         INTEGER,
      er1645v2TTmplCfgBandwidthActCirActEthDei3
         INTEGER,
      er1645v2TTmplCfgBandwidthActCirActEthCos4
         INTEGER,
      er1645v2TTmplCfgBandwidthActCirActEthDei4
         INTEGER,
      er1645v2TTmplCfgBandwidthActCirActEthCos5
         INTEGER,
      er1645v2TTmplCfgBandwidthActCirActEthDei5
         INTEGER,
      er1645v2TTmplCfgBandwidthActCirActEthCos6
         INTEGER,
      er1645v2TTmplCfgBandwidthActCirActEthDei6
         INTEGER,
      er1645v2TTmplCfgBandwidthActCirActEthCos7
         INTEGER,
      er1645v2TTmplCfgBandwidthActCirActEthDei7
         INTEGER,
      er1645v2TTmplCfgBandwidthActCirActEthCos8
         INTEGER,
      er1645v2TTmplCfgBandwidthActCirActEthDei8
         INTEGER,
      er1645v2TTmplCfgBandwidthActCirActEthTos
         INTEGER,
      er1645v2TTmplCfgBandwidthActCirActEthQueue
         INTEGER,
      er1645v2TTmplCfgBandwidthActCirActEthDrpLev
         INTEGER,
      er1645v2TTmplCfgBandwidthActCirActEthDeFlag
         INTEGER,
      er1645v2TTmplCfgBandwidthActCirActIpTos
         INTEGER,
      er1645v2TTmplCfgBandwidthActCirActIpQueue
         INTEGER,
      er1645v2TTmplCfgBandwidthActCirActIpDrpLev
         INTEGER,
      er1645v2TTmplCfgBandwidthActCirActIpDeFlag
         INTEGER,
      er1645v2TTmplCfgBandwidthActEirActNone
         OCTET STRING,
      er1645v2TTmplCfgBandwidthActEirActEthCos1
         INTEGER,
      er1645v2TTmplCfgBandwidthActEirActEthDei1
         INTEGER,
      er1645v2TTmplCfgBandwidthActEirActEthCos2
         INTEGER,
      er1645v2TTmplCfgBandwidthActEirActEthDei2
         INTEGER,
      er1645v2TTmplCfgBandwidthActEirActEthCos3
         INTEGER,
      er1645v2TTmplCfgBandwidthActEirActEthDei3
         INTEGER,
      er1645v2TTmplCfgBandwidthActEirActEthCos4
         INTEGER,
      er1645v2TTmplCfgBandwidthActEirActEthDei4
         INTEGER,
      er1645v2TTmplCfgBandwidthActEirActEthCos5
         INTEGER,
      er1645v2TTmplCfgBandwidthActEirActEthDei5
         INTEGER,
      er1645v2TTmplCfgBandwidthActEirActEthCos6
         INTEGER,
      er1645v2TTmplCfgBandwidthActEirActEthDei6
         INTEGER,
      er1645v2TTmplCfgBandwidthActEirActEthCos7
         INTEGER,
      er1645v2TTmplCfgBandwidthActEirActEthDei7
         INTEGER,
      er1645v2TTmplCfgBandwidthActEirActEthCos8
         INTEGER,
      er1645v2TTmplCfgBandwidthActEirActEthDei8
         INTEGER,
      er1645v2TTmplCfgBandwidthActEirActEthTos
         INTEGER,
      er1645v2TTmplCfgBandwidthActEirActEthQueue
         INTEGER,
      er1645v2TTmplCfgBandwidthActEirActEthDrpLev
         INTEGER,
      er1645v2TTmplCfgBandwidthActEirActEthDeFlag
         INTEGER,
      er1645v2TTmplCfgBandwidthActEirActIpTos
         INTEGER,
      er1645v2TTmplCfgBandwidthActEirActIpQueue
         INTEGER,
      er1645v2TTmplCfgBandwidthActEirActIpDrpLev
         INTEGER,
      er1645v2TTmplCfgBandwidthActEirActIpDeFlag
         INTEGER,
      er1645v2TTmplCfgBandwidthActViolActNone
         OCTET STRING,
      er1645v2TTmplCfgBandwidthActViolActDrop
         OCTET STRING,
      er1645v2TTmplCfgBandwidthActViolActEthCos1
         INTEGER,
      er1645v2TTmplCfgBandwidthActViolActEthDei1
         INTEGER,
      er1645v2TTmplCfgBandwidthActViolActEthCos2
         INTEGER,
      er1645v2TTmplCfgBandwidthActViolActEthDei2
         INTEGER,
      er1645v2TTmplCfgBandwidthActViolActEthCos3
         INTEGER,
      er1645v2TTmplCfgBandwidthActViolActEthDei3
         INTEGER,
      er1645v2TTmplCfgBandwidthActViolActEthCos4
         INTEGER,
      er1645v2TTmplCfgBandwidthActViolActEthDei4
         INTEGER,
      er1645v2TTmplCfgBandwidthActViolActEthCos5
         INTEGER,
      er1645v2TTmplCfgBandwidthActViolActEthDei5
         INTEGER,
      er1645v2TTmplCfgBandwidthActViolActEthCos6
         INTEGER,
      er1645v2TTmplCfgBandwidthActViolActEthDei6
         INTEGER,
      er1645v2TTmplCfgBandwidthActViolActEthCos7
         INTEGER,
      er1645v2TTmplCfgBandwidthActViolActEthDei7
         INTEGER,
      er1645v2TTmplCfgBandwidthActViolActEthCos8
         INTEGER,
      er1645v2TTmplCfgBandwidthActViolActEthDei8
         INTEGER,
      er1645v2TTmplCfgBandwidthActViolActEthTos
         INTEGER,
      er1645v2TTmplCfgBandwidthActViolActEthQueue
         INTEGER,
      er1645v2TTmplCfgBandwidthActViolActEthDrpLev
         INTEGER,
      er1645v2TTmplCfgBandwidthActViolActEthDeFlag
         INTEGER,
      er1645v2TTmplCfgBandwidthActViolActIpTos
         INTEGER,
      er1645v2TTmplCfgBandwidthActViolActIpQueue
         INTEGER,
      er1645v2TTmplCfgBandwidthActViolActIpDrpLev
         INTEGER,
      er1645v2TTmplCfgBandwidthActViolActIpDeFlag
         INTEGER
      }

er1645v2TTmplCfgActions OBJECT-TYPE
   SYNTAX      VariableLengthTableActions
   MAX-ACCESS  read-write
   STATUS      current
   DESCRIPTION
      "By way of this field, some manipulations
       on this table may be performed."
   ::= {er1645v2TTmplCfgEntry 2}

er1645v2TTmplCfgTableIx OBJECT-TYPE
   SYNTAX      TableIndex
   MAX-ACCESS  not-accessible
   STATUS      current
   DESCRIPTION
      ""
   ::= {er1645v2TTmplCfgEntry 11}

er1645v2TTmplCfgName OBJECT-TYPE
   SYNTAX      DisplayString
   MAX-ACCESS  read-write
   STATUS      current
   DESCRIPTION
      "Path: tunnels.editConf.l2tpTunnels.name"
   ::= {er1645v2TTmplCfgEntry 16777216}

er1645v2TTmplCfgRemark OBJECT-TYPE
   SYNTAX      DisplayString
   MAX-ACCESS  read-write
   STATUS      current
   DESCRIPTION
      "Path: tunnels.editConf.l2tpTunnels.remark"
   ::= {er1645v2TTmplCfgEntry 1157627904}

er1645v2TTmplCfgAdminStatus OBJECT-TYPE
   SYNTAX      INTEGER
               {
               up (1),
               down (2)
               }
   MAX-ACCESS  read-write
   STATUS      current
   DESCRIPTION
      "Path: tunnels.editConf.l2tpTunnels.adminStatus

       Possibilities:
               up   (1)
               down   (2)"
   ::= {er1645v2TTmplCfgEntry 33554432}

er1645v2TTmplCfgMode OBJECT-TYPE
   SYNTAX      INTEGER
               {
               routing (1),
               bridging (2),
               routingAndBridging (3)
               }
   MAX-ACCESS  read-write
   STATUS      current
   DESCRIPTION
      "Path: tunnels.editConf.l2tpTunnels.mode

       Possibilities:
               routing   (1)
               bridging   (2)
               routingAndBridging   (3)"
   ::= {er1645v2TTmplCfgEntry 67108864}

er1645v2TTmplCfgPriorityPolicy OBJECT-TYPE
   SYNTAX      DisplayString
   MAX-ACCESS  read-write
   STATUS      current
   DESCRIPTION
      "Path: tunnels.editConf.l2tpTunnels.priorityPolicy"
   ::= {er1645v2TTmplCfgEntry 83886080}

er1645v2TTmplCfgIpVrfRouter OBJECT-TYPE
   SYNTAX      DisplayString
   MAX-ACCESS  read-write
   STATUS      current
   DESCRIPTION
      "Path: tunnels.editConf.l2tpTunnels.ip.vrfRouter"
   ::= {er1645v2TTmplCfgEntry 53215232}

er1645v2TTmplCfgIpAdr OBJECT-TYPE
   SYNTAX      IpAddress
   MAX-ACCESS  read-write
   STATUS      current
   DESCRIPTION
      "Path: tunnels.editConf.l2tpTunnels.ip.address"
   ::= {er1645v2TTmplCfgEntry 58261504}

er1645v2TTmplCfgIpNetm OBJECT-TYPE
   SYNTAX      IpAddress
   MAX-ACCESS  read-write
   STATUS      current
   DESCRIPTION
      "Path: tunnels.editConf.l2tpTunnels.ip.netMask"
   ::= {er1645v2TTmplCfgEntry 58392576}

er1645v2TTmplCfgIpSNetName OBJECT-TYPE
   SYNTAX      INTEGER
               {
               slOPTg (0),
               corp (2),
               dmz (3),
               internet (1)
               }
   MAX-ACCESS  read-write
   STATUS      current
   DESCRIPTION
      "Path: tunnels.editConf.l2tpTunnels.ip.sNet.name

       Possibilities:
               <OPT>   (0)
               corp   (2)
               dmz   (3)
               internet   (1)"
   ::= {er1645v2TTmplCfgEntry 53674240}

er1645v2TTmplCfgIpSNetCust OBJECT-TYPE
   SYNTAX      DisplayString
   MAX-ACCESS  read-write
   STATUS      current
   DESCRIPTION
      "Path: tunnels.editConf.l2tpTunnels.ip.sNet.custom"
   ::= {er1645v2TTmplCfgEntry 53674496}

er1645v2TTmplCfgIpRem OBJECT-TYPE
   SYNTAX      IpAddress
   MAX-ACCESS  read-write
   STATUS      current
   DESCRIPTION
      "Path: tunnels.editConf.l2tpTunnels.ip.remote"
   ::= {er1645v2TTmplCfgEntry 58458112}

er1645v2TTmplCfgIpUnnumbered OBJECT-TYPE
   SYNTAX      DisplayString
   MAX-ACCESS  read-write
   STATUS      current
   DESCRIPTION
      "Path: tunnels.editConf.l2tpTunnels.ip.unnumbered"
   ::= {er1645v2TTmplCfgEntry 52625408}

er1645v2TTmplCfgIpAcceptLocAddr OBJECT-TYPE
   SYNTAX      INTEGER
               {
               disabled (0),
               enabled (1)
               }
   MAX-ACCESS  read-write
   STATUS      current
   DESCRIPTION
      "Path: tunnels.editConf.l2tpTunnels.ip.acceptLocAddr

       Possibilities:
               disabled   (0)
               enabled   (1)"
   ::= {er1645v2TTmplCfgEntry 50593792}

er1645v2TTmplCfgIpAcceptRemAddr OBJECT-TYPE
   SYNTAX      INTEGER
               {
               disabled (0),
               enabled (1)
               }
   MAX-ACCESS  read-write
   STATUS      current
   DESCRIPTION
      "Path: tunnels.editConf.l2tpTunnels.ip.acceptRemAddr

       Possibilities:
               disabled   (0)
               enabled   (1)"
   ::= {er1645v2TTmplCfgEntry 50724864}

er1645v2TTmplCfgIpGwPref OBJECT-TYPE
   SYNTAX      Integer32
   MAX-ACCESS  read-write
   STATUS      current
   DESCRIPTION
      "Path: tunnels.editConf.l2tpTunnels.ip.gatewayPreference"
   ::= {er1645v2TTmplCfgEntry 52690944}

er1645v2TTmplCfgIpRsn OBJECT-TYPE
   SYNTAX      INTEGER
               {
               disabled (0),
               enabled (1)
               }
   MAX-ACCESS  read-write
   STATUS      current
   DESCRIPTION
      "Path: tunnels.editConf.l2tpTunnels.ip.requestSubnet

       Possibilities:
               disabled   (0)
               enabled   (1)"
   ::= {er1645v2TTmplCfgEntry 56688640}

er1645v2TTmplCfgIpMtu OBJECT-TYPE
   SYNTAX      Integer32
   MAX-ACCESS  read-write
   STATUS      current
   DESCRIPTION
      "Path: tunnels.editConf.l2tpTunnels.ip.mtu"
   ::= {er1645v2TTmplCfgEntry 52953088}

er1645v2TTmplCfgIpMssAdjust OBJECT-TYPE
   SYNTAX      INTEGER
               {
               disabled (0),
               auto (65536)
               }
   MAX-ACCESS  read-write
   STATUS      current
   DESCRIPTION
      "Path: tunnels.editConf.l2tpTunnels.ip.mssAdjust

       Possibilities:
               disabled   (0)
               auto   (65536)"
   ::= {er1645v2TTmplCfgEntry 53280768}

er1645v2TTmplCfgIpRipMetric OBJECT-TYPE
   SYNTAX      Integer32
   MAX-ACCESS  read-write
   STATUS      current
   DESCRIPTION
      "Path: tunnels.editConf.l2tpTunnels.ip.rip.metric"
   ::= {er1645v2TTmplCfgEntry 51712768}

er1645v2TTmplCfgIpRipMetricOut OBJECT-TYPE
   SYNTAX      Integer32
   MAX-ACCESS  read-write
   STATUS      current
   DESCRIPTION
      "Path: tunnels.editConf.l2tpTunnels.ip.rip.metricOut"
   ::= {er1645v2TTmplCfgEntry 51713024}

er1645v2TTmplCfgIpRipMode OBJECT-TYPE
   SYNTAX      INTEGER
               {
               disabled (0),
               passive (1),
               active (2)
               }
   MAX-ACCESS  read-write
   STATUS      current
   DESCRIPTION
      "Path: tunnels.editConf.l2tpTunnels.ip.rip.mode

       Possibilities:
               disabled   (0)
               passive   (1)
               active   (2)"
   ::= {er1645v2TTmplCfgEntry 51713280}

er1645v2TTmplCfgIpRipTxVersion OBJECT-TYPE
   SYNTAX      INTEGER
               {
               rip1 (0),
               rip2 (1),
               rip1mcompatible (2)
               }
   MAX-ACCESS  read-write
   STATUS      current
   DESCRIPTION
      "Path: tunnels.editConf.l2tpTunnels.ip.rip.txVersion

       Possibilities:
               rip1   (0)
               rip2   (1)
               rip1-compatible   (2)"
   ::= {er1645v2TTmplCfgEntry 51716864}

er1645v2TTmplCfgIpRipRxVersion OBJECT-TYPE
   SYNTAX      INTEGER
               {
               rip1only (0),
               rip2only (1),
               rip12 (2)
               }
   MAX-ACCESS  read-write
   STATUS      current
   DESCRIPTION
      "Path: tunnels.editConf.l2tpTunnels.ip.rip.rxVersion

       Possibilities:
               rip1only   (0)
               rip2only   (1)
               rip1&2   (2)"
   ::= {er1645v2TTmplCfgEntry 51717120}

er1645v2TTmplCfgIpRipSplitHorizon OBJECT-TYPE
   SYNTAX      INTEGER
               {
               disabled (0),
               enabled (1),
               poisonedReverse (2)
               }
   MAX-ACCESS  read-write
   STATUS      current
   DESCRIPTION
      "Path: tunnels.editConf.l2tpTunnels.ip.rip.splitHorizon

       Possibilities:
               disabled   (0)
               enabled   (1)
               poisonedReverse   (2)"
   ::= {er1645v2TTmplCfgEntry 51713792}

er1645v2TTmplCfgIpRipAuth OBJECT-TYPE
   SYNTAX      INTEGER
               {
               disabled (0),
               texts (1),
               md5 (2)
               }
   MAX-ACCESS  read-write
   STATUS      current
   DESCRIPTION
      "Path: tunnels.editConf.l2tpTunnels.ip.rip.authentication

       Possibilities:
               disabled   (0)
               text    (1)
               md5   (2)"
   ::= {er1645v2TTmplCfgEntry 51712512}

er1645v2TTmplCfgIpRipFilter OBJECT-TYPE
   SYNTAX      DisplayString
   MAX-ACCESS  read-write
   STATUS      current
   DESCRIPTION
      "Path: tunnels.editConf.l2tpTunnels.ip.rip.filter"
   ::= {er1645v2TTmplCfgEntry 51716096}

er1645v2TTmplCfgIpRipFilterIn OBJECT-TYPE
   SYNTAX      DisplayString
   MAX-ACCESS  read-write
   STATUS      current
   DESCRIPTION
      "Path: tunnels.editConf.l2tpTunnels.ip.rip.filterIn"
   ::= {er1645v2TTmplCfgEntry 51716352}

er1645v2TTmplCfgIpRipSnapshot OBJECT-TYPE
   SYNTAX      INTEGER
               {
               disabled (0),
               enabled (1)
               }
   MAX-ACCESS  read-write
   STATUS      current
   DESCRIPTION
      "Path: tunnels.editConf.l2tpTunnels.ip.rip.snapshot

       Possibilities:
               disabled   (0)
               enabled   (1)"
   ::= {er1645v2TTmplCfgEntry 51708160}

er1645v2TTmplCfgIpRipClearNextHop OBJECT-TYPE
   SYNTAX      INTEGER
               {
               disabled (0),
               enabled (1)
               }
   MAX-ACCESS  read-write
   STATUS      current
   DESCRIPTION
      "Path: tunnels.editConf.l2tpTunnels.ip.rip.clearNextHop

       Possibilities:
               disabled   (0)
               enabled   (1)"
   ::= {er1645v2TTmplCfgEntry 51708416}

er1645v2TTmplCfgIpAccPol OBJECT-TYPE
   SYNTAX      DisplayString
   MAX-ACCESS  read-write
   STATUS      current
   DESCRIPTION
      "Path: tunnels.editConf.l2tpTunnels.ip.accessPolicy"
   ::= {er1645v2TTmplCfgEntry 53084160}

er1645v2TTmplCfgIpAB OBJECT-TYPE
   SYNTAX      DisplayString
   MAX-ACCESS  read-write
   STATUS      current
   DESCRIPTION
      "Path: tunnels.editConf.l2tpTunnels.ip.trafficPolicy"
   ::= {er1645v2TTmplCfgEntry 51249152}

er1645v2TTmplCfgIpMA OBJECT-TYPE
   SYNTAX      INTEGER
               {
               disabled (0),
               enabled (1)
               }
   MAX-ACCESS  read-write
   STATUS      current
   DESCRIPTION
      "Path: tunnels.editConf.l2tpTunnels.ip.mgmtAccess

       Possibilities:
               disabled   (0)
               enabled   (1)"
   ::= {er1645v2TTmplCfgEntry 51380224}

er1645v2TTmplCfgIpMF OBJECT-TYPE
   SYNTAX      Integer32
   MAX-ACCESS  read-write
   STATUS      current
   DESCRIPTION
      "Path: tunnels.editConf.l2tpTunnels.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2TTmplCfgEntry 51445760}

er1645v2TTmplCfgIpDB OBJECT-TYPE
   SYNTAX      INTEGER
               {
               disabled (0),
               enabled (1)
               }
   MAX-ACCESS  read-write
   STATUS      current
   DESCRIPTION
      "Path: tunnels.editConf.l2tpTunnels.ip.directedBroadcasts

       Possibilities:
               disabled   (0)
               enabled   (1)"
   ::= {er1645v2TTmplCfgEntry 51773440}

er1645v2TTmplCfgIpIR OBJECT-TYPE
   SYNTAX      INTEGER
               {
               disabled (0),
               enabled (1)
               }
   MAX-ACCESS  read-write
   STATUS      current
   DESCRIPTION
      "Path: tunnels.editConf.l2tpTunnels.ip.icmpRedirects

       Possibilities:
               disabled   (0)
               enabled   (1)"
   ::= {er1645v2TTmplCfgEntry 52035584}

er1645v2TTmplCfgIpIgmp OBJECT-TYPE
   SYNTAX      INTEGER
               {
               disabled (0),
               proxy (1),
               router (2),
               v3Router (5)
               }
   MAX-ACCESS  read-write
   STATUS      current
   DESCRIPTION
      "Path: tunnels.editConf.l2tpTunnels.ip.igmp

       Possibilities:
               disabled   (0)
               proxy   (1)
               router   (2)
               v3Router   (5)"
   ::= {er1645v2TTmplCfgEntry 52428800}

er1645v2TTmplCfgIpNN OBJECT-TYPE
   SYNTAX      DisplayString
   MAX-ACCESS  read-write
   STATUS      current
   DESCRIPTION
      "Path: tunnels.editConf.l2tpTunnels.ip.nat"
   ::= {er1645v2TTmplCfgEntry 52101120}

er1645v2TTmplCfgIpPimMode OBJECT-TYPE
   SYNTAX      INTEGER
               {
               disabled (0),
               sparse (1),
               passive (2)
               }
   MAX-ACCESS  read-write
   STATUS      current
   DESCRIPTION
      "Path: tunnels.editConf.l2tpTunnels.ip.pim.mode

       Possibilities:
               disabled   (0)
               sparse   (1)
               passive   (2)"
   ::= {er1645v2TTmplCfgEntry 53346560}

er1645v2TTmplCfgIpPimDrPriority OBJECT-TYPE
   SYNTAX      Counter32
   MAX-ACCESS  read-write
   STATUS      current
   DESCRIPTION
      "Path: tunnels.editConf.l2tpTunnels.ip.pim.drPriority

       32 bit unsigned wrappable counter."
   ::= {er1645v2TTmplCfgEntry 53346816}

er1645v2TTmplCfgIpPimHelloTime OBJECT-TYPE
   SYNTAX      TimeTicks
   MAX-ACCESS  read-write
   STATUS      current
   DESCRIPTION
      "Path: tunnels.editConf.l2tpTunnels.ip.pim.helloTime

       Time in centi-second."
   ::= {er1645v2TTmplCfgEntry 53347072}

er1645v2TTmplCfgIpPimPropagationDelay OBJECT-TYPE
   SYNTAX      TimeTicks
   MAX-ACCESS  read-write
   STATUS      current
   DESCRIPTION
      "Path: tunnels.editConf.l2tpTunnels.ip.pim.propagationDelay

       Time in centi-second."
   ::= {er1645v2TTmplCfgEntry 53347328}

er1645v2TTmplCfgIpPimOverrideInterval OBJECT-TYPE
   SYNTAX      TimeTicks
   MAX-ACCESS  read-write
   STATUS      current
   DESCRIPTION
      "Path: tunnels.editConf.l2tpTunnels.ip.pim.overrideInterval

       Time in centi-second."
   ::= {er1645v2TTmplCfgEntry 53347584}

er1645v2TTmplCfgIpPimBsrBorder OBJECT-TYPE
   SYNTAX      INTEGER
               {
               disabled (0),
               enabled (1)
               }
   MAX-ACCESS  read-write
   STATUS      current
   DESCRIPTION
      "Path: tunnels.editConf.l2tpTunnels.ip.pim.bsrBorder

       Possibilities:
               disabled   (0)
               enabled   (1)"
   ::= {er1645v2TTmplCfgEntry 53347840}

er1645v2TTmplCfgIpPimTtlThreshold OBJECT-TYPE
   SYNTAX      Integer32
   MAX-ACCESS  read-write
   STATUS      current
   DESCRIPTION
      "Path: tunnels.editConf.l2tpTunnels.ip.pim.ttlThreshold"
   ::= {er1645v2TTmplCfgEntry 53348096}

er1645v2TTmplCfgIpIMNetworkUnreachable OBJECT-TYPE
   SYNTAX      INTEGER
               {
               disabled (0),
               enabled (1)
               }
   MAX-ACCESS  read-write
   STATUS      current
   DESCRIPTION
      "Path: tunnels.editConf.l2tpTunnels.ip.icmpMessages.networkUnreachable

       Possibilities:
               disabled   (0)
               enabled   (1)"
   ::= {er1645v2TTmplCfgEntry 53412096}

er1645v2TTmplCfgIpIMHostUnreachable OBJECT-TYPE
   SYNTAX      INTEGER
               {
               disabled (0),
               enabled (1)
               }
   MAX-ACCESS  read-write
   STATUS      current
   DESCRIPTION
      "Path: tunnels.editConf.l2tpTunnels.ip.icmpMessages.hostUnreachable

       Possibilities:
               disabled   (0)
               enabled   (1)"
   ::= {er1645v2TTmplCfgEntry 53412352}

er1645v2TTmplCfgIpIMProtocolUnreachable OBJECT-TYPE
   SYNTAX      INTEGER
               {
               disabled (0),
               enabled (1)
               }
   MAX-ACCESS  read-write
   STATUS      current
   DESCRIPTION
      "Path: tunnels.editConf.l2tpTunnels.ip.icmpMessages.protocolUnreachable

       Possibilities:
               disabled   (0)
               enabled   (1)"
   ::= {er1645v2TTmplCfgEntry 53412608}

er1645v2TTmplCfgIpIMPortUnreachable OBJECT-TYPE
   SYNTAX      INTEGER
               {
               disabled (0),
               enabled (1)
               }
   MAX-ACCESS  read-write
   STATUS      current
   DESCRIPTION
      "Path: tunnels.editConf.l2tpTunnels.ip.icmpMessages.portUnreachable

       Possibilities:
               disabled   (0)
               enabled   (1)"
   ::= {er1645v2TTmplCfgEntry 53412864}

er1645v2TTmplCfgIpIMMtuExceeded OBJECT-TYPE
   SYNTAX      INTEGER
               {
               disabled (0),
               enabled (1)
               }
   MAX-ACCESS  read-write
   STATUS      current
   DESCRIPTION
      "Path: tunnels.editConf.l2tpTunnels.ip.icmpMessages.mtuExceeded

       Possibilities:
               disabled   (0)
               enabled   (1)"
   ::= {er1645v2TTmplCfgEntry 53413120}

er1645v2TTmplCfgIpIMAdminProhibited OBJECT-TYPE
   SYNTAX      INTEGER
               {
               disabled (0),
               enabled (1)
               }
   MAX-ACCESS  read-write
   STATUS      current
   DESCRIPTION
      "Path: tunnels.editConf.l2tpTunnels.ip.icmpMessages.adminProhibited

       Possibilities:
               disabled   (0)
               enabled   (1)"
   ::= {er1645v2TTmplCfgEntry 53413376}

er1645v2TTmplCfgIpIMTtlExceeded OBJECT-TYPE
   SYNTAX      INTEGER
               {
               disabled (0),
               enabled (1)
               }
   MAX-ACCESS  read-write
   STATUS      current
   DESCRIPTION
      "Path: tunnels.editConf.l2tpTunnels.ip.icmpMessages.ttlExceeded

       Possibilities:
               disabled   (0)
               enabled   (1)"
   ::= {er1645v2TTmplCfgEntry 53413632}

er1645v2TTmplCfgIpIMRedirect OBJECT-TYPE
   SYNTAX      INTEGER
               {
               disabled (0),
               enabled (1)
               }
   MAX-ACCESS  read-write
   STATUS      current
   DESCRIPTION
      "Path: tunnels.editConf.l2tpTunnels.ip.icmpMessages.redirect

       Possibilities:
               disabled   (0)
               enabled   (1)"
   ::= {er1645v2TTmplCfgEntry 53413888}

er1645v2TTmplCfgBridgingAccList OBJECT-TYPE
   SYNTAX      DisplayString
   MAX-ACCESS  read-write
   STATUS      current
   DESCRIPTION
      "Path: tunnels.editConf.l2tpTunnels.bridging.accessList"
   ::= {er1645v2TTmplCfgEntry 453246976}

er1645v2TTmplCfgBridgingInACL OBJECT-TYPE
   SYNTAX      DisplayString
   MAX-ACCESS  read-write
   STATUS      current
   DESCRIPTION
      "Path: tunnels.editConf.l2tpTunnels.bridging.inAccessList"
   ::= {er1645v2TTmplCfgEntry 456916992}

er1645v2TTmplCfgBridgingTp OBJECT-TYPE
   SYNTAX      DisplayString
   MAX-ACCESS  read-write
   STATUS      current
   DESCRIPTION
      "Path: tunnels.editConf.l2tpTunnels.bridging.trafficPolicy"
   ::= {er1645v2TTmplCfgEntry 454295552}

er1645v2TTmplCfgBridgingBrGrp OBJECT-TYPE
   SYNTAX      DisplayString
   MAX-ACCESS  read-write
   STATUS      current
   DESCRIPTION
      "Path: tunnels.editConf.l2tpTunnels.bridging.bridgeGroup"
   ::= {er1645v2TTmplCfgEntry 454819840}

er1645v2TTmplCfgBridgingLimBC OBJECT-TYPE
   SYNTAX      INTEGER
               {
               disabled (0),
               enabled (1)
               }
   MAX-ACCESS  read-write
   STATUS      current
   DESCRIPTION
      "Path: tunnels.editConf.l2tpTunnels.bridging.limitBroadcasts

       Possibilities:
               disabled   (0)
               enabled   (1)"
   ::= {er1645v2TTmplCfgEntry 455081984}

er1645v2TTmplCfgBridgingPrivateMode OBJECT-TYPE
   SYNTAX      INTEGER
               {
               disabled (0),
               enabled (1)
               }
   MAX-ACCESS  read-write
   STATUS      current
   DESCRIPTION
      "Path: tunnels.editConf.l2tpTunnels.bridging.privateMode

       Possibilities:
               disabled   (0)
               enabled   (1)"
   ::= {er1645v2TTmplCfgEntry 459538432}

er1645v2TTmplCfgBridgingLearning OBJECT-TYPE
   SYNTAX      INTEGER
               {
               disabled (0),
               enabled (1)
               }
   MAX-ACCESS  read-write
   STATUS      current
   DESCRIPTION
      "Path: tunnels.editConf.l2tpTunnels.bridging.learning

       Possibilities:
               disabled   (0)
               enabled   (1)"
   ::= {er1645v2TTmplCfgEntry 456130560}

er1645v2TTmplCfgBridgingMaxCacheSize OBJECT-TYPE
   SYNTAX      INTEGER
               {
               unlimited (0)
               }
   MAX-ACCESS  read-write
   STATUS      current
   DESCRIPTION
      "Path: tunnels.editConf.l2tpTunnels.bridging.maxCacheSize

       Possibilities:
               unlimited   (0)"
   ::= {er1645v2TTmplCfgEntry 456392704}

er1645v2TTmplCfgBridgingRelearnDropOnRelearn OBJECT-TYPE
   SYNTAX      INTEGER
               {
               disabled (0),
               enabled (1)
               }
   MAX-ACCESS  read-write
   STATUS      current
   DESCRIPTION
      "Path: tunnels.editConf.l2tpTunnels.bridging.relearn.dropOnRelearn

       Possibilities:
               disabled   (0)
               enabled   (1)"
   ::= {er1645v2TTmplCfgEntry 456655872}

er1645v2TTmplCfgBridgingRelearnShutdownThreshold OBJECT-TYPE
   SYNTAX      Integer32
   MAX-ACCESS  read-write
   STATUS      current
   DESCRIPTION
      "Path: tunnels.editConf.l2tpTunnels.bridging.relearn.shutdownThreshold"
   ::= {er1645v2TTmplCfgEntry 456656896}

er1645v2TTmplCfgBridgingRelearnShutdownTime OBJECT-TYPE
   SYNTAX      TimeTicks
   MAX-ACCESS  read-write
   STATUS      current
   DESCRIPTION
      "Path: tunnels.editConf.l2tpTunnels.bridging.relearn.shutdownTime

       Time in centi-second."
   ::= {er1645v2TTmplCfgEntry 456657920}

er1645v2TTmplCfgBridgingRelearnLoopDetection OBJECT-TYPE
   SYNTAX      INTEGER
               {
               disabled (0),
               passive (1),
               active (2)
               }
   MAX-ACCESS  read-write
   STATUS      current
   DESCRIPTION
      "Path: tunnels.editConf.l2tpTunnels.bridging.relearn.loopDetection

       Possibilities:
               disabled   (0)
               passive   (1)
               active   (2)"
   ::= {er1645v2TTmplCfgEntry 456658944}

er1645v2TTmplCfgBridgingRelearnLoopDetectionInterval OBJECT-TYPE
   SYNTAX      TimeTicks
   MAX-ACCESS  read-write
   STATUS      current
   DESCRIPTION
      "Path: tunnels.editConf.l2tpTunnels.bridging.relearn.loopDetectionInterval

       Time in centi-second."
   ::= {er1645v2TTmplCfgEntry 456659968}

er1645v2TTmplCfgBridgingVlanMemberShip OBJECT-TYPE
   SYNTAX      INTEGER
               {
               all (0),
               none (1),
               grouped (2)
               }
   MAX-ACCESS  read-write
   STATUS      current
   DESCRIPTION
      "Path: tunnels.editConf.l2tpTunnels.bridging.vlanMemberShip

       Possibilities:
               all   (0)
               none   (1)
               grouped   (2)"
   ::= {er1645v2TTmplCfgEntry 457965568}

er1645v2TTmplCfgBridgingVlTUntaggedAction OBJECT-TYPE
   SYNTAX      INTEGER
               {
               discard (0),
               accept (1),
               tag (2)
               }
   MAX-ACCESS  read-write
   STATUS      current
   DESCRIPTION
      "Path: tunnels.editConf.l2tpTunnels.bridging.vlanTagging.untagged.action

       Possibilities:
               discard   (0)
               accept   (1)
               tag   (2)"
   ::= {er1645v2TTmplCfgEntry 459055104}

er1645v2TTmplCfgBridgingVlTUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: tunnels.editConf.l2tpTunnels.bridging.vlanTagging.untagged.tagInfo.tpid

       Possibilities:
               dot1Q   (33024)
               dot1ad   (34984)
               0x9100   (37120)
               0x9200   (37376)
               0x9300   (37632)"
   ::= {er1645v2TTmplCfgEntry 459059712}

er1645v2TTmplCfgBridgingVlTUntaggedTagInfoVid OBJECT-TYPE
   SYNTAX      Integer32
   MAX-ACCESS  read-write
   STATUS      current
   DESCRIPTION
      "Path: tunnels.editConf.l2tpTunnels.bridging.vlanTagging.untagged.tagInfo.vid"
   ::= {er1645v2TTmplCfgEntry 459060224}

er1645v2TTmplCfgBridgingVlTUnknownVlansAction OBJECT-TYPE
   SYNTAX      INTEGER
               {
               discard (0),
               accept (1),
               tag (2)
               }
   MAX-ACCESS  read-write
   STATUS      current
   DESCRIPTION
      "Path: tunnels.editConf.l2tpTunnels.bridging.vlanTagging.unknownVlans.action

       Possibilities:
               discard   (0)
               accept   (1)
               tag   (2)"
   ::= {er1645v2TTmplCfgEntry 459120640}

er1645v2TTmplCfgBridgingVlTUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: tunnels.editConf.l2tpTunnels.bridging.vlanTagging.unknownVlans.tagInfo.tpid

       Possibilities:
               dot1Q   (33024)
               dot1ad   (34984)
               0x9100   (37120)
               0x9200   (37376)
               0x9300   (37632)"
   ::= {er1645v2TTmplCfgEntry 459125248}

er1645v2TTmplCfgBridgingVlTUnknownVlansTagInfoVid OBJECT-TYPE
   SYNTAX      Integer32
   MAX-ACCESS  read-write
   STATUS      current
   DESCRIPTION
      "Path: tunnels.editConf.l2tpTunnels.bridging.vlanTagging.unknownVlans.tagInfo.vid"
   ::= {er1645v2TTmplCfgEntry 459125760}

er1645v2TTmplCfgBridgingDot1adType OBJECT-TYPE
   SYNTAX      INTEGER
               {
               slOPTg (0),
               cPort (4),
               sPort (1),
               nni (2)
               }
   MAX-ACCESS  read-write
   STATUS      current
   DESCRIPTION
      "Path: tunnels.editConf.l2tpTunnels.bridging.dot1ad.type

       Possibilities:
               <OPT>   (0)
               cPort   (4)
               sPort   (1)
               nni   (2)"
   ::= {er1645v2TTmplCfgEntry 460850176}

er1645v2TTmplCfgBridgingPriority OBJECT-TYPE
   SYNTAX      Integer32
   MAX-ACCESS  read-write
   STATUS      current
   DESCRIPTION
      "Path: tunnels.editConf.l2tpTunnels.bridging.priority"
   ::= {er1645v2TTmplCfgEntry 453509120}

er1645v2TTmplCfgBridgingPathCost OBJECT-TYPE
   SYNTAX      Integer32
   MAX-ACCESS  read-write
   STATUS      current
   DESCRIPTION
      "Path: tunnels.editConf.l2tpTunnels.bridging.pathCost"
   ::= {er1645v2TTmplCfgEntry 453771264}

er1645v2TTmplCfgBridgingInternalPathCost OBJECT-TYPE
   SYNTAX      Integer32
   MAX-ACCESS  read-write
   STATUS      current
   DESCRIPTION
      "Path: tunnels.editConf.l2tpTunnels.bridging.internalPathCost"
   ::= {er1645v2TTmplCfgEntry 457703424}

er1645v2TTmplCfgBridgingTCD OBJECT-TYPE
   SYNTAX      INTEGER
               {
               disabled (0),
               enabled (1)
               }
   MAX-ACCESS  read-write
   STATUS      current
   DESCRIPTION
      "Path: tunnels.editConf.l2tpTunnels.bridging.topologyChangeDetection

       Possibilities:
               disabled   (0)
               enabled   (1)"
   ::= {er1645v2TTmplCfgEntry 454033408}

er1645v2TTmplCfgBridgingRestrictedRole OBJECT-TYPE
   SYNTAX      INTEGER
               {
               disabled (0),
               enabled (1)
               }
   MAX-ACCESS  read-write
   STATUS      current
   DESCRIPTION
      "Path: tunnels.editConf.l2tpTunnels.bridging.restrictedRole

       Possibilities:
               disabled   (0)
               enabled   (1)"
   ::= {er1645v2TTmplCfgEntry 458227712}

er1645v2TTmplCfgBridgingAdminEdge OBJECT-TYPE
   SYNTAX      INTEGER
               {
               disabled (0),
               enabled (1)
               }
   MAX-ACCESS  read-write
   STATUS      current
   DESCRIPTION
      "Path: tunnels.editConf.l2tpTunnels.bridging.adminEdge

       Possibilities:
               disabled   (0)
               enabled   (1)"
   ::= {er1645v2TTmplCfgEntry 457179136}

er1645v2TTmplCfgBridgingOamMacDeviceMac OBJECT-TYPE
   SYNTAX      DisplayString
   MAX-ACCESS  read-write
   STATUS      current
   DESCRIPTION
      "Path: tunnels.editConf.l2tpTunnels.bridging.ethOam.macAddress.deviceMac"
   ::= {er1645v2TTmplCfgEntry 458506496}

er1645v2TTmplCfgBridgingOamMacUserMac OBJECT-TYPE
   SYNTAX      OCTET STRING
   MAX-ACCESS  read-write
   STATUS      current
   DESCRIPTION
      "Path: tunnels.editConf.l2tpTunnels.bridging.ethOam.macAddress.userMac

       MAC address."
   ::= {er1645v2TTmplCfgEntry 458506368}

er1645v2TTmplCfgBridgingOamMacBridgeMac OBJECT-TYPE
   SYNTAX      DisplayString
   MAX-ACCESS  read-write
   STATUS      current
   DESCRIPTION
      "Path: tunnels.editConf.l2tpTunnels.bridging.ethOam.macAddress.bridgeMac"
   ::= {er1645v2TTmplCfgEntry 458506432}

er1645v2TTmplCfgBridgingMgmtInline OBJECT-TYPE
   SYNTAX      INTEGER
               {
               disabled (0),
               enabled (1)
               }
   MAX-ACCESS  read-write
   STATUS      current
   DESCRIPTION
      "Path: tunnels.editConf.l2tpTunnels.bridging.mgmtInline

       Possibilities:
               disabled   (0)
               enabled   (1)"
   ::= {er1645v2TTmplCfgEntry 458752000}

er1645v2TTmplCfgBridgingL2ptMode OBJECT-TYPE
   SYNTAX      INTEGER
               {
               disabled (0),
               enabled (1)
               }
   MAX-ACCESS  read-write
   STATUS      current
   DESCRIPTION
      "Path: tunnels.editConf.l2tpTunnels.bridging.l2ProtTunnel.mode

       Possibilities:
               disabled   (0)
               enabled   (1)"
   ::= {er1645v2TTmplCfgEntry 459292672}

er1645v2TTmplCfgBridgingL2ptProtocols OBJECT-TYPE
   SYNTAX      Integer32
   MAX-ACCESS  read-write
   STATUS      current
   DESCRIPTION
      "Path: tunnels.editConf.l2tpTunnels.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1645v2TTmplCfgEntry 459309056}

er1645v2TTmplCfgBridgingL2ptDestMac OBJECT-TYPE
   SYNTAX      OCTET STRING
   MAX-ACCESS  read-write
   STATUS      current
   DESCRIPTION
      "Path: tunnels.editConf.l2tpTunnels.bridging.l2ProtTunnel.destinationMac

       MAC address."
   ::= {er1645v2TTmplCfgEntry 459325440}

er1645v2TTmplCfgBridgingL2ptCos OBJECT-TYPE
   SYNTAX      INTEGER
               {
               unchanged (255)
               }
   MAX-ACCESS  read-write
   STATUS      current
   DESCRIPTION
      "Path: tunnels.editConf.l2tpTunnels.bridging.l2ProtTunnel.cos

       Possibilities:
               unchanged   (255)"
   ::= {er1645v2TTmplCfgEntry 459341824}

er1645v2TTmplCfgBridgingL2ptDropThrStp OBJECT-TYPE
   SYNTAX      INTEGER
               {
               unlimited (0)
               }
   UNITS       "packets/sec"
   MAX-ACCESS  read-write
   STATUS      current
   DESCRIPTION
      "Path: tunnels.editConf.l2tpTunnels.bridging.l2ProtTunnel.dropThresholds.stp

       unit name = packets/sec

       Possibilities:
               unlimited   (0)"
   ::= {er1645v2TTmplCfgEntry 459358272}

er1645v2TTmplCfgBridgingL2ptDropThrLldp OBJECT-TYPE
   SYNTAX      INTEGER
               {
               unlimited (0)
               }
   UNITS       "packets/sec"
   MAX-ACCESS  read-write
   STATUS      current
   DESCRIPTION
      "Path: tunnels.editConf.l2tpTunnels.bridging.l2ProtTunnel.dropThresholds.lldp

       unit name = packets/sec

       Possibilities:
               unlimited   (0)"
   ::= {er1645v2TTmplCfgEntry 459358336}

er1645v2TTmplCfgBridgingL2ptDropThrOam OBJECT-TYPE
   SYNTAX      INTEGER
               {
               unlimited (0)
               }
   UNITS       "packets/sec"
   MAX-ACCESS  read-write
   STATUS      current
   DESCRIPTION
      "Path: tunnels.editConf.l2tpTunnels.bridging.l2ProtTunnel.dropThresholds.oam

       unit name = packets/sec

       Possibilities:
               unlimited   (0)"
   ::= {er1645v2TTmplCfgEntry 459358400}

er1645v2TTmplCfgBridgingL2ptDropThrCdp OBJECT-TYPE
   SYNTAX      INTEGER
               {
               unlimited (0)
               }
   UNITS       "packets/sec"
   MAX-ACCESS  read-write
   STATUS      current
   DESCRIPTION
      "Path: tunnels.editConf.l2tpTunnels.bridging.l2ProtTunnel.dropThresholds.cdp

       unit name = packets/sec

       Possibilities:
               unlimited   (0)"
   ::= {er1645v2TTmplCfgEntry 459358464}

er1645v2TTmplCfgBridgingL2ptDropThrVtp OBJECT-TYPE
   SYNTAX      INTEGER
               {
               unlimited (0)
               }
   UNITS       "packets/sec"
   MAX-ACCESS  read-write
   STATUS      current
   DESCRIPTION
      "Path: tunnels.editConf.l2tpTunnels.bridging.l2ProtTunnel.dropThresholds.vtp

       unit name = packets/sec

       Possibilities:
               unlimited   (0)"
   ::= {er1645v2TTmplCfgEntry 459358528}

er1645v2TTmplCfgBridgingL2ptDropThrLacp OBJECT-TYPE
   SYNTAX      INTEGER
               {
               unlimited (0)
               }
   UNITS       "packets/sec"
   MAX-ACCESS  read-write
   STATUS      current
   DESCRIPTION
      "Path: tunnels.editConf.l2tpTunnels.bridging.l2ProtTunnel.dropThresholds.lacp

       unit name = packets/sec

       Possibilities:
               unlimited   (0)"
   ::= {er1645v2TTmplCfgEntry 459358592}

er1645v2TTmplCfgBridgingL2ptDropThrEfmOam OBJECT-TYPE
   SYNTAX      INTEGER
               {
               unlimited (0)
               }
   UNITS       "packets/sec"
   MAX-ACCESS  read-write
   STATUS      current
   DESCRIPTION
      "Path: tunnels.editConf.l2tpTunnels.bridging.l2ProtTunnel.dropThresholds.efmOam

       unit name = packets/sec

       Possibilities:
               unlimited   (0)"
   ::= {er1645v2TTmplCfgEntry 459358656}

er1645v2TTmplCfgBridgingL2ptDropThrPvst OBJECT-TYPE
   SYNTAX      INTEGER
               {
               unlimited (0)
               }
   UNITS       "packets/sec"
   MAX-ACCESS  read-write
   STATUS      current
   DESCRIPTION
      "Path: tunnels.editConf.l2tpTunnels.bridging.l2ProtTunnel.dropThresholds.pvst

       unit name = packets/sec

       Possibilities:
               unlimited   (0)"
   ::= {er1645v2TTmplCfgEntry 459358720}

er1645v2TTmplCfgBridgingL2ptDropThrMmrp OBJECT-TYPE
   SYNTAX      INTEGER
               {
               unlimited (0)
               }
   UNITS       "packets/sec"
   MAX-ACCESS  read-write
   STATUS      current
   DESCRIPTION
      "Path: tunnels.editConf.l2tpTunnels.bridging.l2ProtTunnel.dropThresholds.mmrp

       unit name = packets/sec

       Possibilities:
               unlimited   (0)"
   ::= {er1645v2TTmplCfgEntry 459358784}

er1645v2TTmplCfgBridgingL2ptDropThrMvrp OBJECT-TYPE
   SYNTAX      INTEGER
               {
               unlimited (0)
               }
   UNITS       "packets/sec"
   MAX-ACCESS  read-write
   STATUS      current
   DESCRIPTION
      "Path: tunnels.editConf.l2tpTunnels.bridging.l2ProtTunnel.dropThresholds.mvrp

       unit name = packets/sec

       Possibilities:
               unlimited   (0)"
   ::= {er1645v2TTmplCfgEntry 459358848}

er1645v2TTmplCfgBridgingL2ptDropThrGvrp OBJECT-TYPE
   SYNTAX      INTEGER
               {
               unlimited (0)
               }
   UNITS       "packets/sec"
   MAX-ACCESS  read-write
   STATUS      current
   DESCRIPTION
      "Path: tunnels.editConf.l2tpTunnels.bridging.l2ProtTunnel.dropThresholds.gvrp

       unit name = packets/sec

       Possibilities:
               unlimited   (0)"
   ::= {er1645v2TTmplCfgEntry 459358912}

er1645v2TTmplCfgBridgingL2ptDropThrGmrp OBJECT-TYPE
   SYNTAX      INTEGER
               {
               unlimited (0)
               }
   UNITS       "packets/sec"
   MAX-ACCESS  read-write
   STATUS      current
   DESCRIPTION
      "Path: tunnels.editConf.l2tpTunnels.bridging.l2ProtTunnel.dropThresholds.gmrp

       unit name = packets/sec

       Possibilities:
               unlimited   (0)"
   ::= {er1645v2TTmplCfgEntry 459358976}

er1645v2TTmplCfgBridgingL2ptDropThrDtp OBJECT-TYPE
   SYNTAX      INTEGER
               {
               unlimited (0)
               }
   UNITS       "packets/sec"
   MAX-ACCESS  read-write
   STATUS      current
   DESCRIPTION
      "Path: tunnels.editConf.l2tpTunnels.bridging.l2ProtTunnel.dropThresholds.dtp

       unit name = packets/sec

       Possibilities:
               unlimited   (0)"
   ::= {er1645v2TTmplCfgEntry 459359040}

er1645v2TTmplCfgBridgingL2ptDropThrPagp OBJECT-TYPE
   SYNTAX      INTEGER
               {
               unlimited (0)
               }
   UNITS       "packets/sec"
   MAX-ACCESS  read-write
   STATUS      current
   DESCRIPTION
      "Path: tunnels.editConf.l2tpTunnels.bridging.l2ProtTunnel.dropThresholds.pagp

       unit name = packets/sec

       Possibilities:
               unlimited   (0)"
   ::= {er1645v2TTmplCfgEntry 459359104}

er1645v2TTmplCfgBridgingL2ptDropThrUdld OBJECT-TYPE
   SYNTAX      INTEGER
               {
               unlimited (0)
               }
   UNITS       "packets/sec"
   MAX-ACCESS  read-write
   STATUS      current
   DESCRIPTION
      "Path: tunnels.editConf.l2tpTunnels.bridging.l2ProtTunnel.dropThresholds.udld

       unit name = packets/sec

       Possibilities:
               unlimited   (0)"
   ::= {er1645v2TTmplCfgEntry 459359168}

er1645v2TTmplCfgL2tpLocalIpAddress OBJECT-TYPE
   SYNTAX      IpAddress
   MAX-ACCESS  read-write
   STATUS      current
   DESCRIPTION
      "Path: tunnels.editConf.l2tpTunnels.l2tp.localIpAddress"
   ::= {er1645v2TTmplCfgEntry 302120960}

er1645v2TTmplCfgL2tpRemoteIpAddress OBJECT-TYPE
   SYNTAX      IpAddress
   MAX-ACCESS  read-write
   STATUS      current
   DESCRIPTION
      "Path: tunnels.editConf.l2tpTunnels.l2tp.remoteIpAddress"
   ::= {er1645v2TTmplCfgEntry 302252032}

er1645v2TTmplCfgL2tpRemoteDnsName OBJECT-TYPE
   SYNTAX      DisplayString
   MAX-ACCESS  read-write
   STATUS      current
   DESCRIPTION
      "Path: tunnels.editConf.l2tpTunnels.l2tp.remoteDnsName"
   ::= {er1645v2TTmplCfgEntry 305790976}

er1645v2TTmplCfgL2tpAuthen OBJECT-TYPE
   SYNTAX      INTEGER
               {
               disabled (0),
               chap (1),
               pap (2),
               chapOrPap (3),
               msChap (4),
               msChapV2 (5)
               }
   MAX-ACCESS  read-write
   STATUS      current
   DESCRIPTION
      "Path: tunnels.editConf.l2tpTunnels.l2tp.pppAuthentication

       Possibilities:
               disabled   (0)
               chap   (1)
               pap   (2)
               chapOrPap   (3)
               msChap   (4)
               msChapV2   (5)"
   ::= {er1645v2TTmplCfgEntry 303693824}

er1645v2TTmplCfgL2tpPppNam OBJECT-TYPE
   SYNTAX      DisplayString
   MAX-ACCESS  read-write
   STATUS      current
   DESCRIPTION
      "Path: tunnels.editConf.l2tpTunnels.l2tp.pppSessionName"
   ::= {er1645v2TTmplCfgEntry 304611328}

er1645v2TTmplCfgL2tpPppSec OBJECT-TYPE
   SYNTAX      DisplayString
   MAX-ACCESS  read-write
   STATUS      current
   DESCRIPTION
      "Path: tunnels.editConf.l2tpTunnels.l2tp.pppSessionSecret"
   ::= {er1645v2TTmplCfgEntry 304742400}

er1645v2TTmplCfgL2tpEncMPppSec OBJECT-TYPE
   SYNTAX      INTEGER
               {
               none (1),
               encrypt (2),
               encType1 (3),
               invalid (128)
               }
   MAX-ACCESS  read-write
   STATUS      current
   DESCRIPTION
      "Path: tunnels.editConf.l2tpTunnels.l2tp.encModePppSessionSecret

       Possibilities:
               none   (1)
               encrypt   (2)
               encType1   (3)
               invalid   (128)"
   ::= {er1645v2TTmplCfgEntry 304873472}

er1645v2TTmplCfgL2tpEncPppSec OBJECT-TYPE
   SYNTAX      DisplayString
   MAX-ACCESS  read-write
   STATUS      current
   DESCRIPTION
      "Path: tunnels.editConf.l2tpTunnels.l2tp.encPppSessionSecret"
   ::= {er1645v2TTmplCfgEntry 305004544}

er1645v2TTmplCfgL2tpLnkMOperation OBJECT-TYPE
   SYNTAX      INTEGER
               {
               disabled (0),
               enabled (1)
               }
   MAX-ACCESS  read-write
   STATUS      current
   DESCRIPTION
      "Path: tunnels.editConf.l2tpTunnels.l2tp.linkMonitoring.operation

       Possibilities:
               disabled   (0)
               enabled   (1)"
   ::= {er1645v2TTmplCfgEntry 305922560}

er1645v2TTmplCfgL2tpLnkMInterval OBJECT-TYPE
   SYNTAX      TimeTicks
   MAX-ACCESS  read-write
   STATUS      current
   DESCRIPTION
      "Path: tunnels.editConf.l2tpTunnels.l2tp.linkMonitoring.interval

       Time in centi-second."
   ::= {er1645v2TTmplCfgEntry 305923072}

er1645v2TTmplCfgL2tpLnkMRepTimeOut OBJECT-TYPE
   SYNTAX      TimeTicks
   MAX-ACCESS  read-write
   STATUS      current
   DESCRIPTION
      "Path: tunnels.editConf.l2tpTunnels.l2tp.linkMonitoring.replyTimeOut

       Time in centi-second."
   ::= {er1645v2TTmplCfgEntry 305923584}

er1645v2TTmplCfgL2tpLnkMFailsPrmt OBJECT-TYPE
   SYNTAX      Integer32
   MAX-ACCESS  read-write
   STATUS      current
   DESCRIPTION
      "Path: tunnels.editConf.l2tpTunnels.l2tp.linkMonitoring.failsPermitted"
   ::= {er1645v2TTmplCfgEntry 305924096}

er1645v2TTmplCfgL2tpType OBJECT-TYPE
   SYNTAX      INTEGER
               {
               outgoingDial (0),
               outgoingLeasedLine (1),
               incoming (2)
               }
   MAX-ACCESS  read-write
   STATUS      current
   DESCRIPTION
      "Path: tunnels.editConf.l2tpTunnels.l2tp.type

       Possibilities:
               outgoingDial   (0)
               outgoingLeasedLine   (1)
               incoming   (2)"
   ::= {er1645v2TTmplCfgEntry 303824896}

er1645v2TTmplCfgL2tpDataseqnr OBJECT-TYPE
   SYNTAX      INTEGER
               {
               off (0),
               on (1)
               }
   MAX-ACCESS  read-write
   STATUS      current
   DESCRIPTION
      "Path: tunnels.editConf.l2tpTunnels.l2tp.dataChannelSequenceNumbering

       Possibilities:
               off   (0)
               on   (1)"
   ::= {er1645v2TTmplCfgEntry 302383104}

er1645v2TTmplCfgL2tpKeepaliveTO OBJECT-TYPE
   SYNTAX      Integer32
   MAX-ACCESS  read-write
   STATUS      current
   DESCRIPTION
      "Path: tunnels.editConf.l2tpTunnels.l2tp.keepAliveTimeOut"
   ::= {er1645v2TTmplCfgEntry 302514176}

er1645v2TTmplCfgL2tpNoTraffT0 OBJECT-TYPE
   SYNTAX      Integer32
   MAX-ACCESS  read-write
   STATUS      current
   DESCRIPTION
      "Path: tunnels.editConf.l2tpTunnels.l2tp.noTrafficTimeOut"
   ::= {er1645v2TTmplCfgEntry 304218112}

er1645v2TTmplCfgL2tpMode OBJECT-TYPE
   SYNTAX      INTEGER
               {
               lac (1),
               lns (2),
               auto (3)
               }
   MAX-ACCESS  read-write
   STATUS      current
   DESCRIPTION
      "Path: tunnels.editConf.l2tpTunnels.l2tp.l2tpMode

       Possibilities:
               lac   (1)
               lns   (2)
               auto   (3)"
   ::= {er1645v2TTmplCfgEntry 302645248}

er1645v2TTmplCfgL2tpAuth OBJECT-TYPE
   SYNTAX      INTEGER
               {
               off (0),
               on (1)
               }
   MAX-ACCESS  read-write
   STATUS      current
   DESCRIPTION
      "Path: tunnels.editConf.l2tpTunnels.l2tp.tunnelAuthentication

       Possibilities:
               off   (0)
               on   (1)"
   ::= {er1645v2TTmplCfgEntry 302776320}

er1645v2TTmplCfgL2tpSecret OBJECT-TYPE
   SYNTAX      DisplayString
   MAX-ACCESS  read-write
   STATUS      current
   DESCRIPTION
      "Path: tunnels.editConf.l2tpTunnels.l2tp.tunnelSecret"
   ::= {er1645v2TTmplCfgEntry 302907392}

er1645v2TTmplCfgL2tpTos OBJECT-TYPE
   SYNTAX      INTEGER
               {
               off (0),
               on (1)
               }
   MAX-ACCESS  read-write
   STATUS      current
   DESCRIPTION
      "Path: tunnels.editConf.l2tpTunnels.l2tp.copyTos

       Possibilities:
               off   (0)
               on   (1)"
   ::= {er1645v2TTmplCfgEntry 303955968}

er1645v2TTmplCfgL2tpRetrans OBJECT-TYPE
   SYNTAX      Integer32
   MAX-ACCESS  read-write
   STATUS      current
   DESCRIPTION
      "Path: tunnels.editConf.l2tpTunnels.l2tp.maxNrOfRetransmissions"
   ::= {er1645v2TTmplCfgEntry 303038464}

er1645v2TTmplCfgL2tpTransmitws OBJECT-TYPE
   SYNTAX      Integer32
   MAX-ACCESS  read-write
   STATUS      current
   DESCRIPTION
      "Path: tunnels.editConf.l2tpTunnels.l2tp.transmitWindowSize"
   ::= {er1645v2TTmplCfgEntry 303169536}

er1645v2TTmplCfgL2tpRcsws OBJECT-TYPE
   SYNTAX      Integer32
   MAX-ACCESS  read-write
   STATUS      current
   DESCRIPTION
      "Path: tunnels.editConf.l2tpTunnels.l2tp.receiveWindowSize"
   ::= {er1645v2TTmplCfgEntry 303300608}

er1645v2TTmplCfgL2tpUdpcheck OBJECT-TYPE
   SYNTAX      INTEGER
               {
               off (0),
               on (1)
               }
   MAX-ACCESS  read-write
   STATUS      current
   DESCRIPTION
      "Path: tunnels.editConf.l2tpTunnels.l2tp.udpChecksum

       Possibilities:
               off   (0)
               on   (1)"
   ::= {er1645v2TTmplCfgEntry 303431680}

er1645v2TTmplCfgL2tpCalledNr OBJECT-TYPE
   SYNTAX      DisplayString
   MAX-ACCESS  read-write
   STATUS      current
   DESCRIPTION
      "Path: tunnels.editConf.l2tpTunnels.l2tp.calledNr"
   ::= {er1645v2TTmplCfgEntry 303562752}

er1645v2TTmplCfgL2tpSpeed OBJECT-TYPE
   SYNTAX      Integer32
   MAX-ACCESS  read-write
   STATUS      current
   DESCRIPTION
      "Path: tunnels.editConf.l2tpTunnels.l2tp.speed"
   ::= {er1645v2TTmplCfgEntry 315621376}

er1645v2TTmplCfgL2tpMtu OBJECT-TYPE
   SYNTAX      Integer32
   MAX-ACCESS  read-write
   STATUS      current
   DESCRIPTION
      "Path: tunnels.editConf.l2tpTunnels.l2tp.mtu"
   ::= {er1645v2TTmplCfgEntry 304349184}

er1645v2TTmplCfgL2tpHostName OBJECT-TYPE
   SYNTAX      DisplayString
   MAX-ACCESS  read-write
   STATUS      current
   DESCRIPTION
      "Path: tunnels.editConf.l2tpTunnels.l2tp.hostName"
   ::= {er1645v2TTmplCfgEntry 304480256}

er1645v2TTmplCfgBackupInterface OBJECT-TYPE
   SYNTAX      DisplayString
   MAX-ACCESS  read-write
   STATUS      current
   DESCRIPTION
      "Path: tunnels.editConf.l2tpTunnels.backup.interface"
   ::= {er1645v2TTmplCfgEntry 536936448}

er1645v2TTmplCfgBackupTimeOut OBJECT-TYPE
   SYNTAX      Integer32
   MAX-ACCESS  read-write
   STATUS      current
   DESCRIPTION
      "Path: tunnels.editConf.l2tpTunnels.backup.timeOut"
   ::= {er1645v2TTmplCfgEntry 537067520}

er1645v2TTmplCfgBackupAutoRetry OBJECT-TYPE
   SYNTAX      INTEGER
               {
               no (0),
               yes (1)
               }
   MAX-ACCESS  read-write
   STATUS      current
   DESCRIPTION
      "Path: tunnels.editConf.l2tpTunnels.backup.autoRetry

       Possibilities:
               no   (0)
               yes   (1)"
   ::= {er1645v2TTmplCfgEntry 537133056}

er1645v2TTmplCfgInbBwCir OBJECT-TYPE
   SYNTAX      Integer32
   MAX-ACCESS  read-write
   STATUS      current
   DESCRIPTION
      "Path: tunnels.editConf.l2tpTunnels.inboundBandwidth.cir"
   ::= {er1645v2TTmplCfgEntry 117506048}

er1645v2TTmplCfgInbBwTc OBJECT-TYPE
   SYNTAX      INTEGER
               {
               auto (0)
               }
   MAX-ACCESS  read-write
   STATUS      current
   DESCRIPTION
      "Path: tunnels.editConf.l2tpTunnels.inboundBandwidth.tc

       Possibilities:
               auto   (0)"
   ::= {er1645v2TTmplCfgEntry 117833728}

er1645v2TTmplCfgInbBwCorrType OBJECT-TYPE
   SYNTAX      INTEGER
               {
               noCorrection (0),
               predefined (1),
               manual (2)
               }
   MAX-ACCESS  read-write
   STATUS      current
   DESCRIPTION
      "Path: tunnels.editConf.l2tpTunnels.inboundBandwidth.correction.type

       Possibilities:
               noCorrection   (0)
               predefined   (1)
               manual   (2)"
   ::= {er1645v2TTmplCfgEntry 117579776}

er1645v2TTmplCfgInbBwCorrPredefEncapsFrameRelay OBJECT-TYPE
   SYNTAX      DisplayString
   MAX-ACCESS  read-write
   STATUS      current
   DESCRIPTION
      "Path: tunnels.editConf.l2tpTunnels.inboundBandwidth.correction.predefined.encapsulation.frameRelay"
   ::= {er1645v2TTmplCfgEntry 117589056}

er1645v2TTmplCfgInbBwCorrPredefEncapsPpp OBJECT-TYPE
   SYNTAX      DisplayString
   MAX-ACCESS  read-write
   STATUS      current
   DESCRIPTION
      "Path: tunnels.editConf.l2tpTunnels.inboundBandwidth.correction.predefined.encapsulation.ppp"
   ::= {er1645v2TTmplCfgEntry 117589120}

er1645v2TTmplCfgInbBwCorrPredefEncapsAtmHl OBJECT-TYPE
   SYNTAX      INTEGER
               {
               rfc2684 (0),
               ppp (1),
               pppOverEthernet (2)
               }
   MAX-ACCESS  read-write
   STATUS      current
   DESCRIPTION
      "Path: tunnels.editConf.l2tpTunnels.inboundBandwidth.correction.predefined.encapsulation.atm.higherLayer

       Possibilities:
               rfc2684   (0)
               ppp   (1)
               pppOverEthernet   (2)"
   ::= {er1645v2TTmplCfgEntry 117589192}

er1645v2TTmplCfgInbBwCorrPredefEncapsAtmMp OBJECT-TYPE
   SYNTAX      INTEGER
               {
               llcEncapsulation (0),
               vcMultiplexing (1)
               }
   MAX-ACCESS  read-write
   STATUS      current
   DESCRIPTION
      "Path: tunnels.editConf.l2tpTunnels.inboundBandwidth.correction.predefined.encapsulation.atm.multiProtocol

       Possibilities:
               llcEncapsulation   (0)
               vcMultiplexing   (1)"
   ::= {er1645v2TTmplCfgEntry 117589200}

er1645v2TTmplCfgInbBwCorrPredefEncapsHdlc OBJECT-TYPE
   SYNTAX      DisplayString
   MAX-ACCESS  read-write
   STATUS      current
   DESCRIPTION
      "Path: tunnels.editConf.l2tpTunnels.inboundBandwidth.correction.predefined.encapsulation.hdlc"
   ::= {er1645v2TTmplCfgEntry 117589248}

er1645v2TTmplCfgInbBwCorrPredefEncapsEfmFs OBJECT-TYPE
   SYNTAX      Integer32
   MAX-ACCESS  read-write
   STATUS      current
   DESCRIPTION
      "Path: tunnels.editConf.l2tpTunnels.inboundBandwidth.correction.predefined.encapsulation.efm.fragmentSize"
   ::= {er1645v2TTmplCfgEntry 117589320}

er1645v2TTmplCfgInbBwCorrPredefEncapsEfmIb OBJECT-TYPE
   SYNTAX      Integer32
   MAX-ACCESS  read-write
   STATUS      current
   DESCRIPTION
      "Path: tunnels.editConf.l2tpTunnels.inboundBandwidth.correction.predefined.encapsulation.efm.idleBytes"
   ::= {er1645v2TTmplCfgEntry 117589328}

er1645v2TTmplCfgInbBwCorrPredefMode OBJECT-TYPE
   SYNTAX      INTEGER
               {
               routing (0),
               bridging (1)
               }
   MAX-ACCESS  read-write
   STATUS      current
   DESCRIPTION
      "Path: tunnels.editConf.l2tpTunnels.inboundBandwidth.correction.predefined.mode

       Possibilities:
               routing   (0)
               bridging   (1)"
   ::= {er1645v2TTmplCfgEntry 117590016}

er1645v2TTmplCfgInbBwCorrManualOverhead OBJECT-TYPE
   SYNTAX      Integer32
   MAX-ACCESS  read-write
   STATUS      current
   DESCRIPTION
      "Path: tunnels.editConf.l2tpTunnels.inboundBandwidth.correction.manual.overhead"
   ::= {er1645v2TTmplCfgEntry 117596192}

er1645v2TTmplCfgInbBwCorrManualFrameData OBJECT-TYPE
   SYNTAX      Counter32
   MAX-ACCESS  read-write
   STATUS      current
   DESCRIPTION
      "Path: tunnels.editConf.l2tpTunnels.inboundBandwidth.correction.manual.frameData

       32 bit unsigned wrappable counter."
   ::= {er1645v2TTmplCfgEntry 117596224}

er1645v2TTmplCfgInbBwCorrManualFrameHeader OBJECT-TYPE
   SYNTAX      Counter32
   MAX-ACCESS  read-write
   STATUS      current
   DESCRIPTION
      "Path: tunnels.editConf.l2tpTunnels.inboundBandwidth.correction.manual.frameHeader

       32 bit unsigned wrappable counter."
   ::= {er1645v2TTmplCfgEntry 117596256}

er1645v2TTmplCfgInbBwMaxFifoQLen OBJECT-TYPE
   SYNTAX      Integer32
   MAX-ACCESS  read-write
   STATUS      current
   DESCRIPTION
      "Path: tunnels.editConf.l2tpTunnels.inboundBandwidth.maxFifoQLen"
   ::= {er1645v2TTmplCfgEntry 117637120}

er1645v2TTmplCfgInbBwPriorityPolicy OBJECT-TYPE
   SYNTAX      DisplayString
   MAX-ACCESS  read-write
   STATUS      current
   DESCRIPTION
      "Path: tunnels.editConf.l2tpTunnels.inboundBandwidth.priorityPolicy"
   ::= {er1645v2TTmplCfgEntry 117702656}

er1645v2TTmplCfgBandwidthMode OBJECT-TYPE
   SYNTAX      INTEGER
               {
               reshaping (1),
               policing (2),
               policingReshape (3)
               }
   MAX-ACCESS  read-write
   STATUS      current
   DESCRIPTION
      "Path: tunnels.editConf.l2tpTunnels.bandwidth.mode

       Possibilities:
               reshaping   (1)
               policing   (2)
               policingReshape   (3)"
   ::= {er1645v2TTmplCfgEntry 148897792}

er1645v2TTmplCfgBandwidthCir OBJECT-TYPE
   SYNTAX      Integer32
   MAX-ACCESS  read-write
   STATUS      current
   DESCRIPTION
      "Path: tunnels.editConf.l2tpTunnels.bandwidth.cir"
   ::= {er1645v2TTmplCfgEntry 135266304}

er1645v2TTmplCfgBandwidthEir OBJECT-TYPE
   SYNTAX      Integer32
   MAX-ACCESS  read-write
   STATUS      current
   DESCRIPTION
      "Path: tunnels.editConf.l2tpTunnels.bandwidth.eir"
   ::= {er1645v2TTmplCfgEntry 141557760}

er1645v2TTmplCfgBandwidthUnit OBJECT-TYPE
   SYNTAX      INTEGER
               {
               bitssec (1),
               percent (2)
               }
   MAX-ACCESS  read-write
   STATUS      current
   DESCRIPTION
      "Path: tunnels.editConf.l2tpTunnels.bandwidth.unit

       Possibilities:
               bits/sec   (1)
               percent   (2)"
   ::= {er1645v2TTmplCfgEntry 139460608}

er1645v2TTmplCfgBandwidthTc OBJECT-TYPE
   SYNTAX      INTEGER
               {
               auto (0)
               }
   MAX-ACCESS  read-write
   STATUS      current
   DESCRIPTION
      "Path: tunnels.editConf.l2tpTunnels.bandwidth.tc

       Possibilities:
               auto   (0)"
   ::= {er1645v2TTmplCfgEntry 140509184}

er1645v2TTmplCfgBandwidthTcFactor OBJECT-TYPE
   SYNTAX      INTEGER
               {
               ms (10),
               s100us (1)
               }
   MAX-ACCESS  read-write
   STATUS      current
   DESCRIPTION
      "Path: tunnels.editConf.l2tpTunnels.bandwidth.tcFactor

       Possibilities:
               ms   (10)
               *100us   (1)"
   ::= {er1645v2TTmplCfgEntry 142606336}

er1645v2TTmplCfgBandwidthCorrType OBJECT-TYPE
   SYNTAX      INTEGER
               {
               noCorrection (0),
               predefined (1),
               manual (2)
               }
   MAX-ACCESS  read-write
   STATUS      current
   DESCRIPTION
      "Path: tunnels.editConf.l2tpTunnels.bandwidth.correction.type

       Possibilities:
               noCorrection   (0)
               predefined   (1)
               manual   (2)"
   ::= {er1645v2TTmplCfgEntry 136445952}

er1645v2TTmplCfgBandwidthCorrPredefEncapsFrameRelay OBJECT-TYPE
   SYNTAX      DisplayString
   MAX-ACCESS  read-write
   STATUS      current
   DESCRIPTION
      "Path: tunnels.editConf.l2tpTunnels.bandwidth.correction.predefined.encapsulation.frameRelay"
   ::= {er1645v2TTmplCfgEntry 136594432}

er1645v2TTmplCfgBandwidthCorrPredefEncapsPpp OBJECT-TYPE
   SYNTAX      DisplayString
   MAX-ACCESS  read-write
   STATUS      current
   DESCRIPTION
      "Path: tunnels.editConf.l2tpTunnels.bandwidth.correction.predefined.encapsulation.ppp"
   ::= {er1645v2TTmplCfgEntry 136595456}

er1645v2TTmplCfgBandwidthCorrPredefEncapsAtmHl OBJECT-TYPE
   SYNTAX      INTEGER
               {
               rfc2684 (0),
               ppp (1),
               pppOverEthernet (2)
               }
   MAX-ACCESS  read-write
   STATUS      current
   DESCRIPTION
      "Path: tunnels.editConf.l2tpTunnels.bandwidth.correction.predefined.encapsulation.atm.higherLayer

       Possibilities:
               rfc2684   (0)
               ppp   (1)
               pppOverEthernet   (2)"
   ::= {er1645v2TTmplCfgEntry 136596608}

er1645v2TTmplCfgBandwidthCorrPredefEncapsAtmMp OBJECT-TYPE
   SYNTAX      INTEGER
               {
               llcEncapsulation (0),
               vcMultiplexing (1)
               }
   MAX-ACCESS  read-write
   STATUS      current
   DESCRIPTION
      "Path: tunnels.editConf.l2tpTunnels.bandwidth.correction.predefined.encapsulation.atm.multiProtocol

       Possibilities:
               llcEncapsulation   (0)
               vcMultiplexing   (1)"
   ::= {er1645v2TTmplCfgEntry 136596736}

er1645v2TTmplCfgBandwidthCorrPredefEncapsHdlc OBJECT-TYPE
   SYNTAX      DisplayString
   MAX-ACCESS  read-write
   STATUS      current
   DESCRIPTION
      "Path: tunnels.editConf.l2tpTunnels.bandwidth.correction.predefined.encapsulation.hdlc"
   ::= {er1645v2TTmplCfgEntry 136597504}

er1645v2TTmplCfgBandwidthCorrPredefEncapsEfmFs OBJECT-TYPE
   SYNTAX      Integer32
   MAX-ACCESS  read-write
   STATUS      current
   DESCRIPTION
      "Path: tunnels.editConf.l2tpTunnels.bandwidth.correction.predefined.encapsulation.efm.fragmentSize"
   ::= {er1645v2TTmplCfgEntry 136598656}

er1645v2TTmplCfgBandwidthCorrPredefEncapsEfmIb OBJECT-TYPE
   SYNTAX      Integer32
   MAX-ACCESS  read-write
   STATUS      current
   DESCRIPTION
      "Path: tunnels.editConf.l2tpTunnels.bandwidth.correction.predefined.encapsulation.efm.idleBytes"
   ::= {er1645v2TTmplCfgEntry 136598784}

er1645v2TTmplCfgBandwidthCorrPredefMode OBJECT-TYPE
   SYNTAX      INTEGER
               {
               routing (0),
               bridging (1)
               }
   MAX-ACCESS  read-write
   STATUS      current
   DESCRIPTION
      "Path: tunnels.editConf.l2tpTunnels.bandwidth.correction.predefined.mode

       Possibilities:
               routing   (0)
               bridging   (1)"
   ::= {er1645v2TTmplCfgEntry 136609792}

er1645v2TTmplCfgBandwidthCorrManualOverhead OBJECT-TYPE
   SYNTAX      Integer32
   MAX-ACCESS  read-write
   STATUS      current
   DESCRIPTION
      "Path: tunnels.editConf.l2tpTunnels.bandwidth.correction.manual.overhead"
   ::= {er1645v2TTmplCfgEntry 136708608}

er1645v2TTmplCfgBandwidthCorrManualFrameData OBJECT-TYPE
   SYNTAX      Counter32
   MAX-ACCESS  read-write
   STATUS      current
   DESCRIPTION
      "Path: tunnels.editConf.l2tpTunnels.bandwidth.correction.manual.frameData

       32 bit unsigned wrappable counter."
   ::= {er1645v2TTmplCfgEntry 136709120}

er1645v2TTmplCfgBandwidthCorrManualFrameHeader OBJECT-TYPE
   SYNTAX      Counter32
   MAX-ACCESS  read-write
   STATUS      current
   DESCRIPTION
      "Path: tunnels.editConf.l2tpTunnels.bandwidth.correction.manual.frameHeader

       32 bit unsigned wrappable counter."
   ::= {er1645v2TTmplCfgEntry 136709632}

er1645v2TTmplCfgBandwidthMaxFifoQLen OBJECT-TYPE
   SYNTAX      Integer32
   MAX-ACCESS  read-write
   STATUS      current
   DESCRIPTION
      "Path: tunnels.editConf.l2tpTunnels.bandwidth.maxFifoQLen"
   ::= {er1645v2TTmplCfgEntry 137363456}

er1645v2TTmplCfgBandwidthDeFlagCir OBJECT-TYPE
   SYNTAX      INTEGER
               {
               allowed (1),
               notAllowed (2)
               }
   MAX-ACCESS  read-write
   STATUS      current
   DESCRIPTION
      "Path: tunnels.editConf.l2tpTunnels.bandwidth.deFlag.cir

       Possibilities:
               allowed   (1)
               notAllowed   (2)"
   ::= {er1645v2TTmplCfgEntry 147853312}

er1645v2TTmplCfgBandwidthDeFlagEir OBJECT-TYPE
   SYNTAX      INTEGER
               {
               allowed (1),
               notAllowed (2)
               }
   MAX-ACCESS  read-write
   STATUS      current
   DESCRIPTION
      "Path: tunnels.editConf.l2tpTunnels.bandwidth.deFlag.eir

       Possibilities:
               allowed   (1)
               notAllowed   (2)"
   ::= {er1645v2TTmplCfgEntry 147857408}

er1645v2TTmplCfgBandwidthDeFlagViolate OBJECT-TYPE
   SYNTAX      INTEGER
               {
               allowed (1),
               notAllowed (2)
               }
   MAX-ACCESS  read-write
   STATUS      current
   DESCRIPTION
      "Path: tunnels.editConf.l2tpTunnels.bandwidth.deFlag.violate

       Possibilities:
               allowed   (1)
               notAllowed   (2)"
   ::= {er1645v2TTmplCfgEntry 147861504}

er1645v2TTmplCfgBandwidthActCirActNone OBJECT-TYPE
   SYNTAX      OCTET STRING
   MAX-ACCESS  read-write
   STATUS      current
   DESCRIPTION
      "Path: tunnels.editConf.l2tpTunnels.bandwidth.action.cirAction.none"
   ::= {er1645v2TTmplCfgEntry 150085632}

er1645v2TTmplCfgBandwidthActCirActEthCos1 OBJECT-TYPE
   SYNTAX      INTEGER
               {
               unchanged (256)
               }
   MAX-ACCESS  read-write
   STATUS      current
   DESCRIPTION
      "Path: tunnels.editConf.l2tpTunnels.bandwidth.action.cirAction.ethernet.cosDepth1

       Possibilities:
               unchanged   (256)"
   ::= {er1645v2TTmplCfgEntry 150094080}

er1645v2TTmplCfgBandwidthActCirActEthDei1 OBJECT-TYPE
   SYNTAX      INTEGER
               {
               unchanged (255),
               clear (0),
               set (1)
               }
   MAX-ACCESS  read-write
   STATUS      current
   DESCRIPTION
      "Path: tunnels.editConf.l2tpTunnels.bandwidth.action.cirAction.ethernet.deiDepth1

       Possibilities:
               unchanged   (255)
               clear   (0)
               set   (1)"
   ::= {er1645v2TTmplCfgEntry 150099200}

er1645v2TTmplCfgBandwidthActCirActEthCos2 OBJECT-TYPE
   SYNTAX      INTEGER
               {
               unchanged (256)
               }
   MAX-ACCESS  read-write
   STATUS      current
   DESCRIPTION
      "Path: tunnels.editConf.l2tpTunnels.bandwidth.action.cirAction.ethernet.cosDepth2

       Possibilities:
               unchanged   (256)"
   ::= {er1645v2TTmplCfgEntry 150094336}

er1645v2TTmplCfgBandwidthActCirActEthDei2 OBJECT-TYPE
   SYNTAX      INTEGER
               {
               unchanged (255),
               clear (0),
               set (1)
               }
   MAX-ACCESS  read-write
   STATUS      current
   DESCRIPTION
      "Path: tunnels.editConf.l2tpTunnels.bandwidth.action.cirAction.ethernet.deiDepth2

       Possibilities:
               unchanged   (255)
               clear   (0)
               set   (1)"
   ::= {er1645v2TTmplCfgEntry 150099456}

er1645v2TTmplCfgBandwidthActCirActEthCos3 OBJECT-TYPE
   SYNTAX      INTEGER
               {
               unchanged (256)
               }
   MAX-ACCESS  read-write
   STATUS      current
   DESCRIPTION
      "Path: tunnels.editConf.l2tpTunnels.bandwidth.action.cirAction.ethernet.cosDepth3

       Possibilities:
               unchanged   (256)"
   ::= {er1645v2TTmplCfgEntry 150094592}

er1645v2TTmplCfgBandwidthActCirActEthDei3 OBJECT-TYPE
   SYNTAX      INTEGER
               {
               unchanged (255),
               clear (0),
               set (1)
               }
   MAX-ACCESS  read-write
   STATUS      current
   DESCRIPTION
      "Path: tunnels.editConf.l2tpTunnels.bandwidth.action.cirAction.ethernet.deiDepth3

       Possibilities:
               unchanged   (255)
               clear   (0)
               set   (1)"
   ::= {er1645v2TTmplCfgEntry 150099712}

er1645v2TTmplCfgBandwidthActCirActEthCos4 OBJECT-TYPE
   SYNTAX      INTEGER
               {
               unchanged (256)
               }
   MAX-ACCESS  read-write
   STATUS      current
   DESCRIPTION
      "Path: tunnels.editConf.l2tpTunnels.bandwidth.action.cirAction.ethernet.cosDepth4

       Possibilities:
               unchanged   (256)"
   ::= {er1645v2TTmplCfgEntry 150094848}

er1645v2TTmplCfgBandwidthActCirActEthDei4 OBJECT-TYPE
   SYNTAX      INTEGER
               {
               unchanged (255),
               clear (0),
               set (1)
               }
   MAX-ACCESS  read-write
   STATUS      current
   DESCRIPTION
      "Path: tunnels.editConf.l2tpTunnels.bandwidth.action.cirAction.ethernet.deiDepth4

       Possibilities:
               unchanged   (255)
               clear   (0)
               set   (1)"
   ::= {er1645v2TTmplCfgEntry 150099968}

er1645v2TTmplCfgBandwidthActCirActEthCos5 OBJECT-TYPE
   SYNTAX      INTEGER
               {
               unchanged (256)
               }
   MAX-ACCESS  read-write
   STATUS      current
   DESCRIPTION
      "Path: tunnels.editConf.l2tpTunnels.bandwidth.action.cirAction.ethernet.cosDepth5

       Possibilities:
               unchanged   (256)"
   ::= {er1645v2TTmplCfgEntry 150095104}

er1645v2TTmplCfgBandwidthActCirActEthDei5 OBJECT-TYPE
   SYNTAX      INTEGER
               {
               unchanged (255),
               clear (0),
               set (1)
               }
   MAX-ACCESS  read-write
   STATUS      current
   DESCRIPTION
      "Path: tunnels.editConf.l2tpTunnels.bandwidth.action.cirAction.ethernet.deiDepth5

       Possibilities:
               unchanged   (255)
               clear   (0)
               set   (1)"
   ::= {er1645v2TTmplCfgEntry 150100224}

er1645v2TTmplCfgBandwidthActCirActEthCos6 OBJECT-TYPE
   SYNTAX      INTEGER
               {
               unchanged (256)
               }
   MAX-ACCESS  read-write
   STATUS      current
   DESCRIPTION
      "Path: tunnels.editConf.l2tpTunnels.bandwidth.action.cirAction.ethernet.cosDepth6

       Possibilities:
               unchanged   (256)"
   ::= {er1645v2TTmplCfgEntry 150095360}

er1645v2TTmplCfgBandwidthActCirActEthDei6 OBJECT-TYPE
   SYNTAX      INTEGER
               {
               unchanged (255),
               clear (0),
               set (1)
               }
   MAX-ACCESS  read-write
   STATUS      current
   DESCRIPTION
      "Path: tunnels.editConf.l2tpTunnels.bandwidth.action.cirAction.ethernet.deiDepth6

       Possibilities:
               unchanged   (255)
               clear   (0)
               set   (1)"
   ::= {er1645v2TTmplCfgEntry 150100480}

er1645v2TTmplCfgBandwidthActCirActEthCos7 OBJECT-TYPE
   SYNTAX      INTEGER
               {
               unchanged (256)
               }
   MAX-ACCESS  read-write
   STATUS      current
   DESCRIPTION
      "Path: tunnels.editConf.l2tpTunnels.bandwidth.action.cirAction.ethernet.cosDepth7

       Possibilities:
               unchanged   (256)"
   ::= {er1645v2TTmplCfgEntry 150095616}

er1645v2TTmplCfgBandwidthActCirActEthDei7 OBJECT-TYPE
   SYNTAX      INTEGER
               {
               unchanged (255),
               clear (0),
               set (1)
               }
   MAX-ACCESS  read-write
   STATUS      current
   DESCRIPTION
      "Path: tunnels.editConf.l2tpTunnels.bandwidth.action.cirAction.ethernet.deiDepth7

       Possibilities:
               unchanged   (255)
               clear   (0)
               set   (1)"
   ::= {er1645v2TTmplCfgEntry 150100736}

er1645v2TTmplCfgBandwidthActCirActEthCos8 OBJECT-TYPE
   SYNTAX      INTEGER
               {
               unchanged (256)
               }
   MAX-ACCESS  read-write
   STATUS      current
   DESCRIPTION
      "Path: tunnels.editConf.l2tpTunnels.bandwidth.action.cirAction.ethernet.cosDepth8

       Possibilities:
               unchanged   (256)"
   ::= {er1645v2TTmplCfgEntry 150095872}

er1645v2TTmplCfgBandwidthActCirActEthDei8 OBJECT-TYPE
   SYNTAX      INTEGER
               {
               unchanged (255),
               clear (0),
               set (1)
               }
   MAX-ACCESS  read-write
   STATUS      current
   DESCRIPTION
      "Path: tunnels.editConf.l2tpTunnels.bandwidth.action.cirAction.ethernet.deiDepth8

       Possibilities:
               unchanged   (255)
               clear   (0)
               set   (1)"
   ::= {er1645v2TTmplCfgEntry 150100992}

er1645v2TTmplCfgBandwidthActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.l2tpTunnels.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TTmplCfgEntry 150096128}

er1645v2TTmplCfgBandwidthActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.l2tpTunnels.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2TTmplCfgEntry 150096384}

er1645v2TTmplCfgBandwidthActCirActEthDrpLev OBJECT-TYPE
   SYNTAX      INTEGER
               {
               unchanged (0)
               }
   MAX-ACCESS  read-write
   STATUS      current
   DESCRIPTION
      "Path: tunnels.editConf.l2tpTunnels.bandwidth.action.cirAction.ethernet.dropLevel

       Possibilities:
               unchanged   (0)"
   ::= {er1645v2TTmplCfgEntry 150096640}

er1645v2TTmplCfgBandwidthActCirActEthDeFlag OBJECT-TYPE
   SYNTAX      INTEGER
               {
               unchanged (255),
               clear (0),
               set (1)
               }
   MAX-ACCESS  read-write
   STATUS      current
   DESCRIPTION
      "Path: tunnels.editConf.l2tpTunnels.bandwidth.action.cirAction.ethernet.deFlag

       Possibilities:
               unchanged   (255)
               clear   (0)
               set   (1)"
   ::= {er1645v2TTmplCfgEntry 150097408}

er1645v2TTmplCfgBandwidthActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.l2tpTunnels.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TTmplCfgEntry 150120704}

er1645v2TTmplCfgBandwidthActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.l2tpTunnels.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2TTmplCfgEntry 150120960}

er1645v2TTmplCfgBandwidthActCirActIpDrpLev OBJECT-TYPE
   SYNTAX      INTEGER
               {
               unchanged (0)
               }
   MAX-ACCESS  read-write
   STATUS      current
   DESCRIPTION
      "Path: tunnels.editConf.l2tpTunnels.bandwidth.action.cirAction.ip.dropLevel

       Possibilities:
               unchanged   (0)"
   ::= {er1645v2TTmplCfgEntry 150121216}

er1645v2TTmplCfgBandwidthActCirActIpDeFlag OBJECT-TYPE
   SYNTAX      INTEGER
               {
               unchanged (255),
               clear (0),
               set (1)
               }
   MAX-ACCESS  read-write
   STATUS      current
   DESCRIPTION
      "Path: tunnels.editConf.l2tpTunnels.bandwidth.action.cirAction.ip.deFlag

       Possibilities:
               unchanged   (255)
               clear   (0)
               set   (1)"
   ::= {er1645v2TTmplCfgEntry 150121984}

er1645v2TTmplCfgBandwidthActEirActNone OBJECT-TYPE
   SYNTAX      OCTET STRING
   MAX-ACCESS  read-write
   STATUS      current
   DESCRIPTION
      "Path: tunnels.editConf.l2tpTunnels.bandwidth.action.eirAction.none"
   ::= {er1645v2TTmplCfgEntry 150216704}

er1645v2TTmplCfgBandwidthActEirActEthCos1 OBJECT-TYPE
   SYNTAX      INTEGER
               {
               unchanged (256)
               }
   MAX-ACCESS  read-write
   STATUS      current
   DESCRIPTION
      "Path: tunnels.editConf.l2tpTunnels.bandwidth.action.eirAction.ethernet.cosDepth1

       Possibilities:
               unchanged   (256)"
   ::= {er1645v2TTmplCfgEntry 150225152}

er1645v2TTmplCfgBandwidthActEirActEthDei1 OBJECT-TYPE
   SYNTAX      INTEGER
               {
               unchanged (255),
               clear (0),
               set (1)
               }
   MAX-ACCESS  read-write
   STATUS      current
   DESCRIPTION
      "Path: tunnels.editConf.l2tpTunnels.bandwidth.action.eirAction.ethernet.deiDepth1

       Possibilities:
               unchanged   (255)
               clear   (0)
               set   (1)"
   ::= {er1645v2TTmplCfgEntry 150230272}

er1645v2TTmplCfgBandwidthActEirActEthCos2 OBJECT-TYPE
   SYNTAX      INTEGER
               {
               unchanged (256)
               }
   MAX-ACCESS  read-write
   STATUS      current
   DESCRIPTION
      "Path: tunnels.editConf.l2tpTunnels.bandwidth.action.eirAction.ethernet.cosDepth2

       Possibilities:
               unchanged   (256)"
   ::= {er1645v2TTmplCfgEntry 150225408}

er1645v2TTmplCfgBandwidthActEirActEthDei2 OBJECT-TYPE
   SYNTAX      INTEGER
               {
               unchanged (255),
               clear (0),
               set (1)
               }
   MAX-ACCESS  read-write
   STATUS      current
   DESCRIPTION
      "Path: tunnels.editConf.l2tpTunnels.bandwidth.action.eirAction.ethernet.deiDepth2

       Possibilities:
               unchanged   (255)
               clear   (0)
               set   (1)"
   ::= {er1645v2TTmplCfgEntry 150230528}

er1645v2TTmplCfgBandwidthActEirActEthCos3 OBJECT-TYPE
   SYNTAX      INTEGER
               {
               unchanged (256)
               }
   MAX-ACCESS  read-write
   STATUS      current
   DESCRIPTION
      "Path: tunnels.editConf.l2tpTunnels.bandwidth.action.eirAction.ethernet.cosDepth3

       Possibilities:
               unchanged   (256)"
   ::= {er1645v2TTmplCfgEntry 150225664}

er1645v2TTmplCfgBandwidthActEirActEthDei3 OBJECT-TYPE
   SYNTAX      INTEGER
               {
               unchanged (255),
               clear (0),
               set (1)
               }
   MAX-ACCESS  read-write
   STATUS      current
   DESCRIPTION
      "Path: tunnels.editConf.l2tpTunnels.bandwidth.action.eirAction.ethernet.deiDepth3

       Possibilities:
               unchanged   (255)
               clear   (0)
               set   (1)"
   ::= {er1645v2TTmplCfgEntry 150230784}

er1645v2TTmplCfgBandwidthActEirActEthCos4 OBJECT-TYPE
   SYNTAX      INTEGER
               {
               unchanged (256)
               }
   MAX-ACCESS  read-write
   STATUS      current
   DESCRIPTION
      "Path: tunnels.editConf.l2tpTunnels.bandwidth.action.eirAction.ethernet.cosDepth4

       Possibilities:
               unchanged   (256)"
   ::= {er1645v2TTmplCfgEntry 150225920}

er1645v2TTmplCfgBandwidthActEirActEthDei4 OBJECT-TYPE
   SYNTAX      INTEGER
               {
               unchanged (255),
               clear (0),
               set (1)
               }
   MAX-ACCESS  read-write
   STATUS      current
   DESCRIPTION
      "Path: tunnels.editConf.l2tpTunnels.bandwidth.action.eirAction.ethernet.deiDepth4

       Possibilities:
               unchanged   (255)
               clear   (0)
               set   (1)"
   ::= {er1645v2TTmplCfgEntry 150231040}

er1645v2TTmplCfgBandwidthActEirActEthCos5 OBJECT-TYPE
   SYNTAX      INTEGER
               {
               unchanged (256)
               }
   MAX-ACCESS  read-write
   STATUS      current
   DESCRIPTION
      "Path: tunnels.editConf.l2tpTunnels.bandwidth.action.eirAction.ethernet.cosDepth5

       Possibilities:
               unchanged   (256)"
   ::= {er1645v2TTmplCfgEntry 150226176}

er1645v2TTmplCfgBandwidthActEirActEthDei5 OBJECT-TYPE
   SYNTAX      INTEGER
               {
               unchanged (255),
               clear (0),
               set (1)
               }
   MAX-ACCESS  read-write
   STATUS      current
   DESCRIPTION
      "Path: tunnels.editConf.l2tpTunnels.bandwidth.action.eirAction.ethernet.deiDepth5

       Possibilities:
               unchanged   (255)
               clear   (0)
               set   (1)"
   ::= {er1645v2TTmplCfgEntry 150231296}

er1645v2TTmplCfgBandwidthActEirActEthCos6 OBJECT-TYPE
   SYNTAX      INTEGER
               {
               unchanged (256)
               }
   MAX-ACCESS  read-write
   STATUS      current
   DESCRIPTION
      "Path: tunnels.editConf.l2tpTunnels.bandwidth.action.eirAction.ethernet.cosDepth6

       Possibilities:
               unchanged   (256)"
   ::= {er1645v2TTmplCfgEntry 150226432}

er1645v2TTmplCfgBandwidthActEirActEthDei6 OBJECT-TYPE
   SYNTAX      INTEGER
               {
               unchanged (255),
               clear (0),
               set (1)
               }
   MAX-ACCESS  read-write
   STATUS      current
   DESCRIPTION
      "Path: tunnels.editConf.l2tpTunnels.bandwidth.action.eirAction.ethernet.deiDepth6

       Possibilities:
               unchanged   (255)
               clear   (0)
               set   (1)"
   ::= {er1645v2TTmplCfgEntry 150231552}

er1645v2TTmplCfgBandwidthActEirActEthCos7 OBJECT-TYPE
   SYNTAX      INTEGER
               {
               unchanged (256)
               }
   MAX-ACCESS  read-write
   STATUS      current
   DESCRIPTION
      "Path: tunnels.editConf.l2tpTunnels.bandwidth.action.eirAction.ethernet.cosDepth7

       Possibilities:
               unchanged   (256)"
   ::= {er1645v2TTmplCfgEntry 150226688}

er1645v2TTmplCfgBandwidthActEirActEthDei7 OBJECT-TYPE
   SYNTAX      INTEGER
               {
               unchanged (255),
               clear (0),
               set (1)
               }
   MAX-ACCESS  read-write
   STATUS      current
   DESCRIPTION
      "Path: tunnels.editConf.l2tpTunnels.bandwidth.action.eirAction.ethernet.deiDepth7

       Possibilities:
               unchanged   (255)
               clear   (0)
               set   (1)"
   ::= {er1645v2TTmplCfgEntry 150231808}

er1645v2TTmplCfgBandwidthActEirActEthCos8 OBJECT-TYPE
   SYNTAX      INTEGER
               {
               unchanged (256)
               }
   MAX-ACCESS  read-write
   STATUS      current
   DESCRIPTION
      "Path: tunnels.editConf.l2tpTunnels.bandwidth.action.eirAction.ethernet.cosDepth8

       Possibilities:
               unchanged   (256)"
   ::= {er1645v2TTmplCfgEntry 150226944}

er1645v2TTmplCfgBandwidthActEirActEthDei8 OBJECT-TYPE
   SYNTAX      INTEGER
               {
               unchanged (255),
               clear (0),
               set (1)
               }
   MAX-ACCESS  read-write
   STATUS      current
   DESCRIPTION
      "Path: tunnels.editConf.l2tpTunnels.bandwidth.action.eirAction.ethernet.deiDepth8

       Possibilities:
               unchanged   (255)
               clear   (0)
               set   (1)"
   ::= {er1645v2TTmplCfgEntry 150232064}

er1645v2TTmplCfgBandwidthActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.l2tpTunnels.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TTmplCfgEntry 150227200}

er1645v2TTmplCfgBandwidthActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.l2tpTunnels.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2TTmplCfgEntry 150227456}

er1645v2TTmplCfgBandwidthActEirActEthDrpLev OBJECT-TYPE
   SYNTAX      INTEGER
               {
               unchanged (0)
               }
   MAX-ACCESS  read-write
   STATUS      current
   DESCRIPTION
      "Path: tunnels.editConf.l2tpTunnels.bandwidth.action.eirAction.ethernet.dropLevel

       Possibilities:
               unchanged   (0)"
   ::= {er1645v2TTmplCfgEntry 150227712}

er1645v2TTmplCfgBandwidthActEirActEthDeFlag OBJECT-TYPE
   SYNTAX      INTEGER
               {
               unchanged (255),
               clear (0),
               set (1)
               }
   MAX-ACCESS  read-write
   STATUS      current
   DESCRIPTION
      "Path: tunnels.editConf.l2tpTunnels.bandwidth.action.eirAction.ethernet.deFlag

       Possibilities:
               unchanged   (255)
               clear   (0)
               set   (1)"
   ::= {er1645v2TTmplCfgEntry 150228480}

er1645v2TTmplCfgBandwidthActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.l2tpTunnels.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TTmplCfgEntry 150251776}

er1645v2TTmplCfgBandwidthActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.l2tpTunnels.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2TTmplCfgEntry 150252032}

er1645v2TTmplCfgBandwidthActEirActIpDrpLev OBJECT-TYPE
   SYNTAX      INTEGER
               {
               unchanged (0)
               }
   MAX-ACCESS  read-write
   STATUS      current
   DESCRIPTION
      "Path: tunnels.editConf.l2tpTunnels.bandwidth.action.eirAction.ip.dropLevel

       Possibilities:
               unchanged   (0)"
   ::= {er1645v2TTmplCfgEntry 150252288}

er1645v2TTmplCfgBandwidthActEirActIpDeFlag OBJECT-TYPE
   SYNTAX      INTEGER
               {
               unchanged (255),
               clear (0),
               set (1)
               }
   MAX-ACCESS  read-write
   STATUS      current
   DESCRIPTION
      "Path: tunnels.editConf.l2tpTunnels.bandwidth.action.eirAction.ip.deFlag

       Possibilities:
               unchanged   (255)
               clear   (0)
               set   (1)"
   ::= {er1645v2TTmplCfgEntry 150253056}

er1645v2TTmplCfgBandwidthActViolActNone OBJECT-TYPE
   SYNTAX      OCTET STRING
   MAX-ACCESS  read-write
   STATUS      current
   DESCRIPTION
      "Path: tunnels.editConf.l2tpTunnels.bandwidth.action.violateAction.none"
   ::= {er1645v2TTmplCfgEntry 150347776}

er1645v2TTmplCfgBandwidthActViolActDrop OBJECT-TYPE
   SYNTAX      OCTET STRING
   MAX-ACCESS  read-write
   STATUS      current
   DESCRIPTION
      "Path: tunnels.editConf.l2tpTunnels.bandwidth.action.violateAction.drop"
   ::= {er1645v2TTmplCfgEntry 150364160}

er1645v2TTmplCfgBandwidthActViolActEthCos1 OBJECT-TYPE
   SYNTAX      INTEGER
               {
               unchanged (256)
               }
   MAX-ACCESS  read-write
   STATUS      current
   DESCRIPTION
      "Path: tunnels.editConf.l2tpTunnels.bandwidth.action.violateAction.ethernet.cosDepth1

       Possibilities:
               unchanged   (256)"
   ::= {er1645v2TTmplCfgEntry 150356224}

er1645v2TTmplCfgBandwidthActViolActEthDei1 OBJECT-TYPE
   SYNTAX      INTEGER
               {
               unchanged (255),
               clear (0),
               set (1)
               }
   MAX-ACCESS  read-write
   STATUS      current
   DESCRIPTION
      "Path: tunnels.editConf.l2tpTunnels.bandwidth.action.violateAction.ethernet.deiDepth1

       Possibilities:
               unchanged   (255)
               clear   (0)
               set   (1)"
   ::= {er1645v2TTmplCfgEntry 150361344}

er1645v2TTmplCfgBandwidthActViolActEthCos2 OBJECT-TYPE
   SYNTAX      INTEGER
               {
               unchanged (256)
               }
   MAX-ACCESS  read-write
   STATUS      current
   DESCRIPTION
      "Path: tunnels.editConf.l2tpTunnels.bandwidth.action.violateAction.ethernet.cosDepth2

       Possibilities:
               unchanged   (256)"
   ::= {er1645v2TTmplCfgEntry 150356480}

er1645v2TTmplCfgBandwidthActViolActEthDei2 OBJECT-TYPE
   SYNTAX      INTEGER
               {
               unchanged (255),
               clear (0),
               set (1)
               }
   MAX-ACCESS  read-write
   STATUS      current
   DESCRIPTION
      "Path: tunnels.editConf.l2tpTunnels.bandwidth.action.violateAction.ethernet.deiDepth2

       Possibilities:
               unchanged   (255)
               clear   (0)
               set   (1)"
   ::= {er1645v2TTmplCfgEntry 150361600}

er1645v2TTmplCfgBandwidthActViolActEthCos3 OBJECT-TYPE
   SYNTAX      INTEGER
               {
               unchanged (256)
               }
   MAX-ACCESS  read-write
   STATUS      current
   DESCRIPTION
      "Path: tunnels.editConf.l2tpTunnels.bandwidth.action.violateAction.ethernet.cosDepth3

       Possibilities:
               unchanged   (256)"
   ::= {er1645v2TTmplCfgEntry 150356736}

er1645v2TTmplCfgBandwidthActViolActEthDei3 OBJECT-TYPE
   SYNTAX      INTEGER
               {
               unchanged (255),
               clear (0),
               set (1)
               }
   MAX-ACCESS  read-write
   STATUS      current
   DESCRIPTION
      "Path: tunnels.editConf.l2tpTunnels.bandwidth.action.violateAction.ethernet.deiDepth3

       Possibilities:
               unchanged   (255)
               clear   (0)
               set   (1)"
   ::= {er1645v2TTmplCfgEntry 150361856}

er1645v2TTmplCfgBandwidthActViolActEthCos4 OBJECT-TYPE
   SYNTAX      INTEGER
               {
               unchanged (256)
               }
   MAX-ACCESS  read-write
   STATUS      current
   DESCRIPTION
      "Path: tunnels.editConf.l2tpTunnels.bandwidth.action.violateAction.ethernet.cosDepth4

       Possibilities:
               unchanged   (256)"
   ::= {er1645v2TTmplCfgEntry 150356992}

er1645v2TTmplCfgBandwidthActViolActEthDei4 OBJECT-TYPE
   SYNTAX      INTEGER
               {
               unchanged (255),
               clear (0),
               set (1)
               }
   MAX-ACCESS  read-write
   STATUS      current
   DESCRIPTION
      "Path: tunnels.editConf.l2tpTunnels.bandwidth.action.violateAction.ethernet.deiDepth4

       Possibilities:
               unchanged   (255)
               clear   (0)
               set   (1)"
   ::= {er1645v2TTmplCfgEntry 150362112}

er1645v2TTmplCfgBandwidthActViolActEthCos5 OBJECT-TYPE
   SYNTAX      INTEGER
               {
               unchanged (256)
               }
   MAX-ACCESS  read-write
   STATUS      current
   DESCRIPTION
      "Path: tunnels.editConf.l2tpTunnels.bandwidth.action.violateAction.ethernet.cosDepth5

       Possibilities:
               unchanged   (256)"
   ::= {er1645v2TTmplCfgEntry 150357248}

er1645v2TTmplCfgBandwidthActViolActEthDei5 OBJECT-TYPE
   SYNTAX      INTEGER
               {
               unchanged (255),
               clear (0),
               set (1)
               }
   MAX-ACCESS  read-write
   STATUS      current
   DESCRIPTION
      "Path: tunnels.editConf.l2tpTunnels.bandwidth.action.violateAction.ethernet.deiDepth5

       Possibilities:
               unchanged   (255)
               clear   (0)
               set   (1)"
   ::= {er1645v2TTmplCfgEntry 150362368}

er1645v2TTmplCfgBandwidthActViolActEthCos6 OBJECT-TYPE
   SYNTAX      INTEGER
               {
               unchanged (256)
               }
   MAX-ACCESS  read-write
   STATUS      current
   DESCRIPTION
      "Path: tunnels.editConf.l2tpTunnels.bandwidth.action.violateAction.ethernet.cosDepth6

       Possibilities:
               unchanged   (256)"
   ::= {er1645v2TTmplCfgEntry 150357504}

er1645v2TTmplCfgBandwidthActViolActEthDei6 OBJECT-TYPE
   SYNTAX      INTEGER
               {
               unchanged (255),
               clear (0),
               set (1)
               }
   MAX-ACCESS  read-write
   STATUS      current
   DESCRIPTION
      "Path: tunnels.editConf.l2tpTunnels.bandwidth.action.violateAction.ethernet.deiDepth6

       Possibilities:
               unchanged   (255)
               clear   (0)
               set   (1)"
   ::= {er1645v2TTmplCfgEntry 150362624}

er1645v2TTmplCfgBandwidthActViolActEthCos7 OBJECT-TYPE
   SYNTAX      INTEGER
               {
               unchanged (256)
               }
   MAX-ACCESS  read-write
   STATUS      current
   DESCRIPTION
      "Path: tunnels.editConf.l2tpTunnels.bandwidth.action.violateAction.ethernet.cosDepth7

       Possibilities:
               unchanged   (256)"
   ::= {er1645v2TTmplCfgEntry 150357760}

er1645v2TTmplCfgBandwidthActViolActEthDei7 OBJECT-TYPE
   SYNTAX      INTEGER
               {
               unchanged (255),
               clear (0),
               set (1)
               }
   MAX-ACCESS  read-write
   STATUS      current
   DESCRIPTION
      "Path: tunnels.editConf.l2tpTunnels.bandwidth.action.violateAction.ethernet.deiDepth7

       Possibilities:
               unchanged   (255)
               clear   (0)
               set   (1)"
   ::= {er1645v2TTmplCfgEntry 150362880}

er1645v2TTmplCfgBandwidthActViolActEthCos8 OBJECT-TYPE
   SYNTAX      INTEGER
               {
               unchanged (256)
               }
   MAX-ACCESS  read-write
   STATUS      current
   DESCRIPTION
      "Path: tunnels.editConf.l2tpTunnels.bandwidth.action.violateAction.ethernet.cosDepth8

       Possibilities:
               unchanged   (256)"
   ::= {er1645v2TTmplCfgEntry 150358016}

er1645v2TTmplCfgBandwidthActViolActEthDei8 OBJECT-TYPE
   SYNTAX      INTEGER
               {
               unchanged (255),
               clear (0),
               set (1)
               }
   MAX-ACCESS  read-write
   STATUS      current
   DESCRIPTION
      "Path: tunnels.editConf.l2tpTunnels.bandwidth.action.violateAction.ethernet.deiDepth8

       Possibilities:
               unchanged   (255)
               clear   (0)
               set   (1)"
   ::= {er1645v2TTmplCfgEntry 150363136}

er1645v2TTmplCfgBandwidthActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.l2tpTunnels.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TTmplCfgEntry 150358272}

er1645v2TTmplCfgBandwidthActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.l2tpTunnels.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2TTmplCfgEntry 150358528}

er1645v2TTmplCfgBandwidthActViolActEthDrpLev OBJECT-TYPE
   SYNTAX      INTEGER
               {
               unchanged (0)
               }
   MAX-ACCESS  read-write
   STATUS      current
   DESCRIPTION
      "Path: tunnels.editConf.l2tpTunnels.bandwidth.action.violateAction.ethernet.dropLevel

       Possibilities:
               unchanged   (0)"
   ::= {er1645v2TTmplCfgEntry 150358784}

er1645v2TTmplCfgBandwidthActViolActEthDeFlag OBJECT-TYPE
   SYNTAX      INTEGER
               {
               unchanged (255),
               clear (0),
               set (1)
               }
   MAX-ACCESS  read-write
   STATUS      current
   DESCRIPTION
      "Path: tunnels.editConf.l2tpTunnels.bandwidth.action.violateAction.ethernet.deFlag

       Possibilities:
               unchanged   (255)
               clear   (0)
               set   (1)"
   ::= {er1645v2TTmplCfgEntry 150359552}

er1645v2TTmplCfgBandwidthActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.l2tpTunnels.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TTmplCfgEntry 150382848}

er1645v2TTmplCfgBandwidthActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.l2tpTunnels.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2TTmplCfgEntry 150383104}

er1645v2TTmplCfgBandwidthActViolActIpDrpLev OBJECT-TYPE
   SYNTAX      INTEGER
               {
               unchanged (0)
               }
   MAX-ACCESS  read-write
   STATUS      current
   DESCRIPTION
      "Path: tunnels.editConf.l2tpTunnels.bandwidth.action.violateAction.ip.dropLevel

       Possibilities:
               unchanged   (0)"
   ::= {er1645v2TTmplCfgEntry 150383360}

er1645v2TTmplCfgBandwidthActViolActIpDeFlag OBJECT-TYPE
   SYNTAX      INTEGER
               {
               unchanged (255),
               clear (0),
               set (1)
               }
   MAX-ACCESS  read-write
   STATUS      current
   DESCRIPTION
      "Path: tunnels.editConf.l2tpTunnels.bandwidth.action.violateAction.ip.deFlag

       Possibilities:
               unchanged   (255)
               clear   (0)
               set   (1)"
   ::= {er1645v2TTmplCfgEntry 150384128}

er1645v2TTmplCfgBridgingVlTVlans OBJECT-TYPE
   SYNTAX      SEQUENCE OF Er1645v2TTmplCfgBridgingVlTVlansEntry
   MAX-ACCESS  not-accessible
   STATUS      current
   DESCRIPTION
      ""
   ::= {er1645v2TTmplCfg 459079680}

er1645v2TTmplCfgBridgingVlTVlansEntry OBJECT-TYPE
   SYNTAX      Er1645v2TTmplCfgBridgingVlTVlansEntry
   MAX-ACCESS  not-accessible
   STATUS      current
   DESCRIPTION
      ""
   INDEX      { er1645v2TTmplCfgTableIx,
                er1645v2TTmplCfgBridgingVlTVlansTableIx }
   ::= {er1645v2TTmplCfgBridgingVlTVlans 1}

Er1645v2TTmplCfgBridgingVlTVlansEntry ::=
   SEQUENCE
      {
      er1645v2TTmplCfgBridgingVlTVlansActions
         VariableLengthTableActions,
      er1645v2TTmplCfgBridgingVlTVlansTableIx
         TableIndex,
      er1645v2TTmplCfgBridgingVlTVlansVid
         Integer32,
      er1645v2TTmplCfgBridgingVlTVlansEndVid
         Integer32,
      er1645v2TTmplCfgBridgingVlTVlansAction
         INTEGER,
      er1645v2TTmplCfgBridgingVlTVlansTagInfoTpid
         INTEGER,
      er1645v2TTmplCfgBridgingVlTVlansTagInfoVid
         Integer32
      }

er1645v2TTmplCfgBridgingVlTVlansActions OBJECT-TYPE
   SYNTAX      VariableLengthTableActions
   MAX-ACCESS  read-write
   STATUS      current
   DESCRIPTION
      "By way of this field, some manipulations
       on this table may be performed."
   ::= {er1645v2TTmplCfgBridgingVlTVlansEntry 2}

er1645v2TTmplCfgBridgingVlTVlansTableIx OBJECT-TYPE
   SYNTAX      TableIndex
   MAX-ACCESS  not-accessible
   STATUS      current
   DESCRIPTION
      ""
   ::= {er1645v2TTmplCfgBridgingVlTVlansEntry 11}

er1645v2TTmplCfgBridgingVlTVlansVid OBJECT-TYPE
   SYNTAX      Integer32
   MAX-ACCESS  read-write
   STATUS      current
   DESCRIPTION
      "Path: tunnels.editConf.l2tpTunnels.bridging.vlanTagging.vlans.vid"
   ::= {er1645v2TTmplCfgBridgingVlTVlansEntry 536870912}

er1645v2TTmplCfgBridgingVlTVlansEndVid OBJECT-TYPE
   SYNTAX      Integer32
   MAX-ACCESS  read-write
   STATUS      current
   DESCRIPTION
      "Path: tunnels.editConf.l2tpTunnels.bridging.vlanTagging.vlans.endVid"
   ::= {er1645v2TTmplCfgBridgingVlTVlansEntry 2147483648}

er1645v2TTmplCfgBridgingVlTVlansAction OBJECT-TYPE
   SYNTAX      INTEGER
               {
               discard (0),
               accept (1),
               tag (2)
               }
   MAX-ACCESS  read-write
   STATUS      current
   DESCRIPTION
      "Path: tunnels.editConf.l2tpTunnels.bridging.vlanTagging.vlans.action

       Possibilities:
               discard   (0)
               accept   (1)
               tag   (2)"
   ::= {er1645v2TTmplCfgBridgingVlTVlansEntry 1073741824}

er1645v2TTmplCfgBridgingVlTVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: tunnels.editConf.l2tpTunnels.bridging.vlanTagging.vlans.tagInfo.tpid

       Possibilities:
               dot1Q   (33024)
               dot1ad   (34984)
               0x9100   (37120)
               0x9200   (37376)
               0x9300   (37632)"
   ::= {er1645v2TTmplCfgBridgingVlTVlansEntry 1677721600}

er1645v2TTmplCfgBridgingVlTVlansTagInfoVid OBJECT-TYPE
   SYNTAX      Integer32
   MAX-ACCESS  read-write
   STATUS      current
   DESCRIPTION
      "Path: tunnels.editConf.l2tpTunnels.bridging.vlanTagging.vlans.tagInfo.vid"
   ::= {er1645v2TTmplCfgBridgingVlTVlansEntry 1744830464}


er1645v2TTmplCGre OBJECT IDENTIFIER ::= {er1645v2TTmpl 21}

er1645v2TTmplCGreSSCTable OBJECT-TYPE
   SYNTAX      SEQUENCE OF Er1645v2TTmplCGreEntry
   MAX-ACCESS  not-accessible
   STATUS      current
   DESCRIPTION
      ""
   ::= {er1645v2TTmplCGre 1}

er1645v2TTmplCGreEntry OBJECT-TYPE
   SYNTAX      Er1645v2TTmplCGreEntry
   MAX-ACCESS  not-accessible
   STATUS      current
   DESCRIPTION
      ""
   INDEX      { er1645v2TTmplCGreTableIx }
   ::= {er1645v2TTmplCGreSSCTable 1}

Er1645v2TTmplCGreEntry ::=
   SEQUENCE
      {
      er1645v2TTmplCGreActions
         VariableLengthTableActions,
      er1645v2TTmplCGreTableIx
         TableIndex,
      er1645v2TTmplCGreName
         DisplayString,
      er1645v2TTmplCGreRemark
         DisplayString,
      er1645v2TTmplCGreAdminStatus
         INTEGER,
      er1645v2TTmplCGreMode
         INTEGER,
      er1645v2TTmplCGrePriorityPolicy
         DisplayString,
      er1645v2TTmplCGreIpVrfRouter
         DisplayString,
      er1645v2TTmplCGreIpAdr
         IpAddress,
      er1645v2TTmplCGreIpNetm
         IpAddress,
      er1645v2TTmplCGreIpSNetName
         INTEGER,
      er1645v2TTmplCGreIpSNetCust
         DisplayString,
      er1645v2TTmplCGreIpRem
         IpAddress,
      er1645v2TTmplCGreIpGwPref
         Integer32,
      er1645v2TTmplCGreIpMtu
         Integer32,
      er1645v2TTmplCGreIpMssAdjust
         INTEGER,
      er1645v2TTmplCGreIpRipMetric
         Integer32,
      er1645v2TTmplCGreIpRipMetricOut
         Integer32,
      er1645v2TTmplCGreIpRipMode
         INTEGER,
      er1645v2TTmplCGreIpRipTxVersion
         INTEGER,
      er1645v2TTmplCGreIpRipRxVersion
         INTEGER,
      er1645v2TTmplCGreIpRipSplitHorizon
         INTEGER,
      er1645v2TTmplCGreIpRipAuth
         INTEGER,
      er1645v2TTmplCGreIpRipFilter
         DisplayString,
      er1645v2TTmplCGreIpRipFilterIn
         DisplayString,
      er1645v2TTmplCGreIpRipSnapshot
         INTEGER,
      er1645v2TTmplCGreIpRipClearNextHop
         INTEGER,
      er1645v2TTmplCGreIpAccPol
         DisplayString,
      er1645v2TTmplCGreIpAB
         DisplayString,
      er1645v2TTmplCGreIpMA
         INTEGER,
      er1645v2TTmplCGreIpMF
         Integer32,
      er1645v2TTmplCGreIpDB
         INTEGER,
      er1645v2TTmplCGreIpIR
         INTEGER,
      er1645v2TTmplCGreIpIgmp
         INTEGER,
      er1645v2TTmplCGreIpNN
         DisplayString,
      er1645v2TTmplCGreIpPimMode
         INTEGER,
      er1645v2TTmplCGreIpPimDrPriority
         Counter32,
      er1645v2TTmplCGreIpPimHelloTime
         TimeTicks,
      er1645v2TTmplCGreIpPimPropagationDelay
         TimeTicks,
      er1645v2TTmplCGreIpPimOverrideInterval
         TimeTicks,
      er1645v2TTmplCGreIpPimBsrBorder
         INTEGER,
      er1645v2TTmplCGreIpPimTtlThreshold
         Integer32,
      er1645v2TTmplCGreIpIMNetworkUnreachable
         INTEGER,
      er1645v2TTmplCGreIpIMHostUnreachable
         INTEGER,
      er1645v2TTmplCGreIpIMProtocolUnreachable
         INTEGER,
      er1645v2TTmplCGreIpIMPortUnreachable
         INTEGER,
      er1645v2TTmplCGreIpIMMtuExceeded
         INTEGER,
      er1645v2TTmplCGreIpIMAdminProhibited
         INTEGER,
      er1645v2TTmplCGreIpIMTtlExceeded
         INTEGER,
      er1645v2TTmplCGreIpIMRedirect
         INTEGER,
      er1645v2TTmplCGreBrAccList
         DisplayString,
      er1645v2TTmplCGreBrInACL
         DisplayString,
      er1645v2TTmplCGreBrTp
         DisplayString,
      er1645v2TTmplCGreBrBrGrp
         DisplayString,
      er1645v2TTmplCGreBrLimBC
         INTEGER,
      er1645v2TTmplCGreBrPrivateMode
         INTEGER,
      er1645v2TTmplCGreBrLearning
         INTEGER,
      er1645v2TTmplCGreBrMaxCacheSize
         INTEGER,
      er1645v2TTmplCGreBrRelearnDropOnRelearn
         INTEGER,
      er1645v2TTmplCGreBrRelearnShutdownThreshold
         Integer32,
      er1645v2TTmplCGreBrRelearnShutdownTime
         TimeTicks,
      er1645v2TTmplCGreBrRelearnLoopDetection
         INTEGER,
      er1645v2TTmplCGreBrRelearnLoopDetectionInterval
         TimeTicks,
      er1645v2TTmplCGreBrVlanMemberShip
         INTEGER,
      er1645v2TTmplCGreBrVlTUntaggedAction
         INTEGER,
      er1645v2TTmplCGreBrVlTUntaggedTagInfoTpid
         INTEGER,
      er1645v2TTmplCGreBrVlTUntaggedTagInfoVid
         Integer32,
      er1645v2TTmplCGreBrVlTUnknownVlansAction
         INTEGER,
      er1645v2TTmplCGreBrVlTUnknownVlansTagInfoTpid
         INTEGER,
      er1645v2TTmplCGreBrVlTUnknownVlansTagInfoVid
         Integer32,
      er1645v2TTmplCGreBrDot1adType
         INTEGER,
      er1645v2TTmplCGreBrPriority
         Integer32,
      er1645v2TTmplCGreBrPathCost
         Integer32,
      er1645v2TTmplCGreBrInternalPathCost
         Integer32,
      er1645v2TTmplCGreBrTCD
         INTEGER,
      er1645v2TTmplCGreBrRestrictedRole
         INTEGER,
      er1645v2TTmplCGreBrAdminEdge
         INTEGER,
      er1645v2TTmplCGreBrOamMacDeviceMac
         DisplayString,
      er1645v2TTmplCGreBrOamMacUserMac
         OCTET STRING,
      er1645v2TTmplCGreBrOamMacBridgeMac
         DisplayString,
      er1645v2TTmplCGreBrMgmtInline
         INTEGER,
      er1645v2TTmplCGreBrL2ptMode
         INTEGER,
      er1645v2TTmplCGreBrL2ptProtocols
         Integer32,
      er1645v2TTmplCGreBrL2ptDestMac
         OCTET STRING,
      er1645v2TTmplCGreBrL2ptCos
         INTEGER,
      er1645v2TTmplCGreBrL2ptDropThrStp
         INTEGER,
      er1645v2TTmplCGreBrL2ptDropThrLldp
         INTEGER,
      er1645v2TTmplCGreBrL2ptDropThrOam
         INTEGER,
      er1645v2TTmplCGreBrL2ptDropThrCdp
         INTEGER,
      er1645v2TTmplCGreBrL2ptDropThrVtp
         INTEGER,
      er1645v2TTmplCGreBrL2ptDropThrLacp
         INTEGER,
      er1645v2TTmplCGreBrL2ptDropThrEfmOam
         INTEGER,
      er1645v2TTmplCGreBrL2ptDropThrPvst
         INTEGER,
      er1645v2TTmplCGreBrL2ptDropThrMmrp
         INTEGER,
      er1645v2TTmplCGreBrL2ptDropThrMvrp
         INTEGER,
      er1645v2TTmplCGreBrL2ptDropThrGvrp
         INTEGER,
      er1645v2TTmplCGreBrL2ptDropThrGmrp
         INTEGER,
      er1645v2TTmplCGreBrL2ptDropThrDtp
         INTEGER,
      er1645v2TTmplCGreBrL2ptDropThrPagp
         INTEGER,
      er1645v2TTmplCGreBrL2ptDropThrUdld
         INTEGER,
      er1645v2TTmplCGreVirtEthernetVirtualEthernet
         DisplayString,
      er1645v2TTmplCGreGreLocalIpAddress
         IpAddress,
      er1645v2TTmplCGreGreLocalInterface
         DisplayString,
      er1645v2TTmplCGreGreRemoteIpAddress
         IpAddress,
      er1645v2TTmplCGreGreRemoteDnsName
         DisplayString,
      er1645v2TTmplCGreGreKey
         Integer32,
      er1645v2TTmplCGreGreKpAlMode
         INTEGER,
      er1645v2TTmplCGreGreKpAlInterval
         TimeTicks,
      er1645v2TTmplCGreGreKpAlRepTimeOut
         TimeTicks,
      er1645v2TTmplCGreGreKpAlFailsPrmt
         Integer32,
      er1645v2TTmplCGreGreRRoutDefRt
         INTEGER,
      er1645v2TTmplCGreGreTos
         INTEGER,
      er1645v2TTmplCGreGreQueueTosMapQueue1
         INTEGER,
      er1645v2TTmplCGreGreQueueTosMapQueue2
         INTEGER,
      er1645v2TTmplCGreGreQueueTosMapQueue3
         INTEGER,
      er1645v2TTmplCGreGreQueueTosMapQueue4
         INTEGER,
      er1645v2TTmplCGreGreQueueTosMapQueue5
         INTEGER,
      er1645v2TTmplCGreGreQueueTosMapLowDelayQueue
         INTEGER,
      er1645v2TTmplCGreGreQueueTosMapLowDelay2Queue
         INTEGER,
      er1645v2TTmplCGreGreQueueTosMapSystemQueue
         INTEGER,
      er1645v2TTmplCGreGreDf
         INTEGER,
      er1645v2TTmplCGreGreTtl
         INTEGER,
      er1645v2TTmplCGreGreMtu
         Integer32,
      er1645v2TTmplCGreMplsMode
         INTEGER,
      er1645v2TTmplCGreMplsInLabel
         Integer32,
      er1645v2TTmplCGreMplsOutLabel
         Integer32,
      er1645v2TTmplCGreMplsTrafficClassMode
         INTEGER,
      er1645v2TTmplCGreMplsTrafficClassFixed
         Integer32,
      er1645v2TTmplCGreMplsTrafficClassQosP0
         Integer32,
      er1645v2TTmplCGreMplsTrafficClassQosP1
         Integer32,
      er1645v2TTmplCGreMplsTrafficClassQosP2
         Integer32,
      er1645v2TTmplCGreMplsTrafficClassQosP3
         Integer32,
      er1645v2TTmplCGreMplsTrafficClassQosP4
         Integer32,
      er1645v2TTmplCGreMplsTrafficClassQosP5
         Integer32,
      er1645v2TTmplCGreMplsTrafficClassQosP6
         Integer32,
      er1645v2TTmplCGreMplsTrafficClassQosP7
         Integer32,
      er1645v2TTmplCGreMplsTtl
         INTEGER,
      er1645v2TTmplCGreInbBwCir
         Integer32,
      er1645v2TTmplCGreInbBwTc
         INTEGER,
      er1645v2TTmplCGreInbBwCorrType
         INTEGER,
      er1645v2TTmplCGreInbBwCorrPredefEncapsFrameRelay
         DisplayString,
      er1645v2TTmplCGreInbBwCorrPredefEncapsPpp
         DisplayString,
      er1645v2TTmplCGreInbBwCorrPredefEncapsAtmHl
         INTEGER,
      er1645v2TTmplCGreInbBwCorrPredefEncapsAtmMp
         INTEGER,
      er1645v2TTmplCGreInbBwCorrPredefEncapsHdlc
         DisplayString,
      er1645v2TTmplCGreInbBwCorrPredefEncapsEfmFs
         Integer32,
      er1645v2TTmplCGreInbBwCorrPredefEncapsEfmIb
         Integer32,
      er1645v2TTmplCGreInbBwCorrPredefMode
         INTEGER,
      er1645v2TTmplCGreInbBwCorrManualOverhead
         Integer32,
      er1645v2TTmplCGreInbBwCorrManualFrameData
         Counter32,
      er1645v2TTmplCGreInbBwCorrManualFrameHeader
         Counter32,
      er1645v2TTmplCGreInbBwMaxFifoQLen
         Integer32,
      er1645v2TTmplCGreInbBwPriorityPolicy
         DisplayString,
      er1645v2TTmplCGreBandwidthMode
         INTEGER,
      er1645v2TTmplCGreBandwidthCir
         Integer32,
      er1645v2TTmplCGreBandwidthEir
         Integer32,
      er1645v2TTmplCGreBandwidthUnit
         INTEGER,
      er1645v2TTmplCGreBandwidthTc
         INTEGER,
      er1645v2TTmplCGreBandwidthTcFactor
         INTEGER,
      er1645v2TTmplCGreBandwidthCorrType
         INTEGER,
      er1645v2TTmplCGreBandwidthCorrPredefEncapsFrameRelay
         DisplayString,
      er1645v2TTmplCGreBandwidthCorrPredefEncapsPpp
         DisplayString,
      er1645v2TTmplCGreBandwidthCorrPredefEncapsAtmHl
         INTEGER,
      er1645v2TTmplCGreBandwidthCorrPredefEncapsAtmMp
         INTEGER,
      er1645v2TTmplCGreBandwidthCorrPredefEncapsHdlc
         DisplayString,
      er1645v2TTmplCGreBandwidthCorrPredefEncapsEfmFs
         Integer32,
      er1645v2TTmplCGreBandwidthCorrPredefEncapsEfmIb
         Integer32,
      er1645v2TTmplCGreBandwidthCorrPredefMode
         INTEGER,
      er1645v2TTmplCGreBandwidthCorrManualOverhead
         Integer32,
      er1645v2TTmplCGreBandwidthCorrManualFrameData
         Counter32,
      er1645v2TTmplCGreBandwidthCorrManualFrameHeader
         Counter32,
      er1645v2TTmplCGreBandwidthMaxFifoQLen
         Integer32,
      er1645v2TTmplCGreBandwidthDeFlagCir
         INTEGER,
      er1645v2TTmplCGreBandwidthDeFlagEir
         INTEGER,
      er1645v2TTmplCGreBandwidthDeFlagViolate
         INTEGER,
      er1645v2TTmplCGreBandwidthActCirActNone
         OCTET STRING,
      er1645v2TTmplCGreBandwidthActCirActEthCos1
         INTEGER,
      er1645v2TTmplCGreBandwidthActCirActEthDei1
         INTEGER,
      er1645v2TTmplCGreBandwidthActCirActEthCos2
         INTEGER,
      er1645v2TTmplCGreBandwidthActCirActEthDei2
         INTEGER,
      er1645v2TTmplCGreBandwidthActCirActEthCos3
         INTEGER,
      er1645v2TTmplCGreBandwidthActCirActEthDei3
         INTEGER,
      er1645v2TTmplCGreBandwidthActCirActEthCos4
         INTEGER,
      er1645v2TTmplCGreBandwidthActCirActEthDei4
         INTEGER,
      er1645v2TTmplCGreBandwidthActCirActEthCos5
         INTEGER,
      er1645v2TTmplCGreBandwidthActCirActEthDei5
         INTEGER,
      er1645v2TTmplCGreBandwidthActCirActEthCos6
         INTEGER,
      er1645v2TTmplCGreBandwidthActCirActEthDei6
         INTEGER,
      er1645v2TTmplCGreBandwidthActCirActEthCos7
         INTEGER,
      er1645v2TTmplCGreBandwidthActCirActEthDei7
         INTEGER,
      er1645v2TTmplCGreBandwidthActCirActEthCos8
         INTEGER,
      er1645v2TTmplCGreBandwidthActCirActEthDei8
         INTEGER,
      er1645v2TTmplCGreBandwidthActCirActEthTos
         INTEGER,
      er1645v2TTmplCGreBandwidthActCirActEthQueue
         INTEGER,
      er1645v2TTmplCGreBandwidthActCirActEthDrpLev
         INTEGER,
      er1645v2TTmplCGreBandwidthActCirActEthDeFlag
         INTEGER,
      er1645v2TTmplCGreBandwidthActCirActIpTos
         INTEGER,
      er1645v2TTmplCGreBandwidthActCirActIpQueue
         INTEGER,
      er1645v2TTmplCGreBandwidthActCirActIpDrpLev
         INTEGER,
      er1645v2TTmplCGreBandwidthActCirActIpDeFlag
         INTEGER,
      er1645v2TTmplCGreBandwidthActEirActNone
         OCTET STRING,
      er1645v2TTmplCGreBandwidthActEirActEthCos1
         INTEGER,
      er1645v2TTmplCGreBandwidthActEirActEthDei1
         INTEGER,
      er1645v2TTmplCGreBandwidthActEirActEthCos2
         INTEGER,
      er1645v2TTmplCGreBandwidthActEirActEthDei2
         INTEGER,
      er1645v2TTmplCGreBandwidthActEirActEthCos3
         INTEGER,
      er1645v2TTmplCGreBandwidthActEirActEthDei3
         INTEGER,
      er1645v2TTmplCGreBandwidthActEirActEthCos4
         INTEGER,
      er1645v2TTmplCGreBandwidthActEirActEthDei4
         INTEGER,
      er1645v2TTmplCGreBandwidthActEirActEthCos5
         INTEGER,
      er1645v2TTmplCGreBandwidthActEirActEthDei5
         INTEGER,
      er1645v2TTmplCGreBandwidthActEirActEthCos6
         INTEGER,
      er1645v2TTmplCGreBandwidthActEirActEthDei6
         INTEGER,
      er1645v2TTmplCGreBandwidthActEirActEthCos7
         INTEGER,
      er1645v2TTmplCGreBandwidthActEirActEthDei7
         INTEGER,
      er1645v2TTmplCGreBandwidthActEirActEthCos8
         INTEGER,
      er1645v2TTmplCGreBandwidthActEirActEthDei8
         INTEGER,
      er1645v2TTmplCGreBandwidthActEirActEthTos
         INTEGER,
      er1645v2TTmplCGreBandwidthActEirActEthQueue
         INTEGER,
      er1645v2TTmplCGreBandwidthActEirActEthDrpLev
         INTEGER,
      er1645v2TTmplCGreBandwidthActEirActEthDeFlag
         INTEGER,
      er1645v2TTmplCGreBandwidthActEirActIpTos
         INTEGER,
      er1645v2TTmplCGreBandwidthActEirActIpQueue
         INTEGER,
      er1645v2TTmplCGreBandwidthActEirActIpDrpLev
         INTEGER,
      er1645v2TTmplCGreBandwidthActEirActIpDeFlag
         INTEGER,
      er1645v2TTmplCGreBandwidthActViolActNone
         OCTET STRING,
      er1645v2TTmplCGreBandwidthActViolActDrop
         OCTET STRING,
      er1645v2TTmplCGreBandwidthActViolActEthCos1
         INTEGER,
      er1645v2TTmplCGreBandwidthActViolActEthDei1
         INTEGER,
      er1645v2TTmplCGreBandwidthActViolActEthCos2
         INTEGER,
      er1645v2TTmplCGreBandwidthActViolActEthDei2
         INTEGER,
      er1645v2TTmplCGreBandwidthActViolActEthCos3
         INTEGER,
      er1645v2TTmplCGreBandwidthActViolActEthDei3
         INTEGER,
      er1645v2TTmplCGreBandwidthActViolActEthCos4
         INTEGER,
      er1645v2TTmplCGreBandwidthActViolActEthDei4
         INTEGER,
      er1645v2TTmplCGreBandwidthActViolActEthCos5
         INTEGER,
      er1645v2TTmplCGreBandwidthActViolActEthDei5
         INTEGER,
      er1645v2TTmplCGreBandwidthActViolActEthCos6
         INTEGER,
      er1645v2TTmplCGreBandwidthActViolActEthDei6
         INTEGER,
      er1645v2TTmplCGreBandwidthActViolActEthCos7
         INTEGER,
      er1645v2TTmplCGreBandwidthActViolActEthDei7
         INTEGER,
      er1645v2TTmplCGreBandwidthActViolActEthCos8
         INTEGER,
      er1645v2TTmplCGreBandwidthActViolActEthDei8
         INTEGER,
      er1645v2TTmplCGreBandwidthActViolActEthTos
         INTEGER,
      er1645v2TTmplCGreBandwidthActViolActEthQueue
         INTEGER,
      er1645v2TTmplCGreBandwidthActViolActEthDrpLev
         INTEGER,
      er1645v2TTmplCGreBandwidthActViolActEthDeFlag
         INTEGER,
      er1645v2TTmplCGreBandwidthActViolActIpTos
         INTEGER,
      er1645v2TTmplCGreBandwidthActViolActIpQueue
         INTEGER,
      er1645v2TTmplCGreBandwidthActViolActIpDrpLev
         INTEGER,
      er1645v2TTmplCGreBandwidthActViolActIpDeFlag
         INTEGER
      }

er1645v2TTmplCGreActions OBJECT-TYPE
   SYNTAX      VariableLengthTableActions
   MAX-ACCESS  read-write
   STATUS      current
   DESCRIPTION
      "By way of this field, some manipulations
       on this table may be performed."
   ::= {er1645v2TTmplCGreEntry 2}

er1645v2TTmplCGreTableIx OBJECT-TYPE
   SYNTAX      TableIndex
   MAX-ACCESS  not-accessible
   STATUS      current
   DESCRIPTION
      ""
   ::= {er1645v2TTmplCGreEntry 11}

er1645v2TTmplCGreName OBJECT-TYPE
   SYNTAX      DisplayString
   MAX-ACCESS  read-write
   STATUS      current
   DESCRIPTION
      "Path: tunnels.editConf.greTunnels.name"
   ::= {er1645v2TTmplCGreEntry 16777216}

er1645v2TTmplCGreRemark OBJECT-TYPE
   SYNTAX      DisplayString
   MAX-ACCESS  read-write
   STATUS      current
   DESCRIPTION
      "Path: tunnels.editConf.greTunnels.remark"
   ::= {er1645v2TTmplCGreEntry 1157627904}

er1645v2TTmplCGreAdminStatus OBJECT-TYPE
   SYNTAX      INTEGER
               {
               up (1),
               down (2)
               }
   MAX-ACCESS  read-write
   STATUS      current
   DESCRIPTION
      "Path: tunnels.editConf.greTunnels.adminStatus

       Possibilities:
               up   (1)
               down   (2)"
   ::= {er1645v2TTmplCGreEntry 33554432}

er1645v2TTmplCGreMode OBJECT-TYPE
   SYNTAX      INTEGER
               {
               routing (1),
               bridging (2),
               multilink (8),
               virtEthernet (32)
               }
   MAX-ACCESS  read-write
   STATUS      current
   DESCRIPTION
      "Path: tunnels.editConf.greTunnels.mode

       Possibilities:
               routing   (1)
               bridging   (2)
               multilink   (8)
               virtEthernet   (32)"
   ::= {er1645v2TTmplCGreEntry 67108864}

er1645v2TTmplCGrePriorityPolicy OBJECT-TYPE
   SYNTAX      DisplayString
   MAX-ACCESS  read-write
   STATUS      current
   DESCRIPTION
      "Path: tunnels.editConf.greTunnels.priorityPolicy"
   ::= {er1645v2TTmplCGreEntry 83886080}

er1645v2TTmplCGreIpVrfRouter OBJECT-TYPE
   SYNTAX      DisplayString
   MAX-ACCESS  read-write
   STATUS      current
   DESCRIPTION
      "Path: tunnels.editConf.greTunnels.ip.vrfRouter"
   ::= {er1645v2TTmplCGreEntry 53215232}

er1645v2TTmplCGreIpAdr OBJECT-TYPE
   SYNTAX      IpAddress
   MAX-ACCESS  read-write
   STATUS      current
   DESCRIPTION
      "Path: tunnels.editConf.greTunnels.ip.address"
   ::= {er1645v2TTmplCGreEntry 58261504}

er1645v2TTmplCGreIpNetm OBJECT-TYPE
   SYNTAX      IpAddress
   MAX-ACCESS  read-write
   STATUS      current
   DESCRIPTION
      "Path: tunnels.editConf.greTunnels.ip.netMask"
   ::= {er1645v2TTmplCGreEntry 58392576}

er1645v2TTmplCGreIpSNetName OBJECT-TYPE
   SYNTAX      INTEGER
               {
               slOPTg (0),
               corp (2),
               dmz (3),
               internet (1)
               }
   MAX-ACCESS  read-write
   STATUS      current
   DESCRIPTION
      "Path: tunnels.editConf.greTunnels.ip.sNet.name

       Possibilities:
               <OPT>   (0)
               corp   (2)
               dmz   (3)
               internet   (1)"
   ::= {er1645v2TTmplCGreEntry 53674240}

er1645v2TTmplCGreIpSNetCust OBJECT-TYPE
   SYNTAX      DisplayString
   MAX-ACCESS  read-write
   STATUS      current
   DESCRIPTION
      "Path: tunnels.editConf.greTunnels.ip.sNet.custom"
   ::= {er1645v2TTmplCGreEntry 53674496}

er1645v2TTmplCGreIpRem OBJECT-TYPE
   SYNTAX      IpAddress
   MAX-ACCESS  read-write
   STATUS      current
   DESCRIPTION
      "Path: tunnels.editConf.greTunnels.ip.remote"
   ::= {er1645v2TTmplCGreEntry 58458112}

er1645v2TTmplCGreIpGwPref OBJECT-TYPE
   SYNTAX      Integer32
   MAX-ACCESS  read-write
   STATUS      current
   DESCRIPTION
      "Path: tunnels.editConf.greTunnels.ip.gatewayPreference"
   ::= {er1645v2TTmplCGreEntry 52690944}

er1645v2TTmplCGreIpMtu OBJECT-TYPE
   SYNTAX      Integer32
   MAX-ACCESS  read-write
   STATUS      current
   DESCRIPTION
      "Path: tunnels.editConf.greTunnels.ip.mtu"
   ::= {er1645v2TTmplCGreEntry 52953088}

er1645v2TTmplCGreIpMssAdjust OBJECT-TYPE
   SYNTAX      INTEGER
               {
               disabled (0),
               auto (65536)
               }
   MAX-ACCESS  read-write
   STATUS      current
   DESCRIPTION
      "Path: tunnels.editConf.greTunnels.ip.mssAdjust

       Possibilities:
               disabled   (0)
               auto   (65536)"
   ::= {er1645v2TTmplCGreEntry 53280768}

er1645v2TTmplCGreIpRipMetric OBJECT-TYPE
   SYNTAX      Integer32
   MAX-ACCESS  read-write
   STATUS      current
   DESCRIPTION
      "Path: tunnels.editConf.greTunnels.ip.rip.metric"
   ::= {er1645v2TTmplCGreEntry 51712768}

er1645v2TTmplCGreIpRipMetricOut OBJECT-TYPE
   SYNTAX      Integer32
   MAX-ACCESS  read-write
   STATUS      current
   DESCRIPTION
      "Path: tunnels.editConf.greTunnels.ip.rip.metricOut"
   ::= {er1645v2TTmplCGreEntry 51713024}

er1645v2TTmplCGreIpRipMode OBJECT-TYPE
   SYNTAX      INTEGER
               {
               disabled (0),
               passive (1),
               active (2)
               }
   MAX-ACCESS  read-write
   STATUS      current
   DESCRIPTION
      "Path: tunnels.editConf.greTunnels.ip.rip.mode

       Possibilities:
               disabled   (0)
               passive   (1)
               active   (2)"
   ::= {er1645v2TTmplCGreEntry 51713280}

er1645v2TTmplCGreIpRipTxVersion OBJECT-TYPE
   SYNTAX      INTEGER
               {
               rip1 (0),
               rip2 (1),
               rip1mcompatible (2)
               }
   MAX-ACCESS  read-write
   STATUS      current
   DESCRIPTION
      "Path: tunnels.editConf.greTunnels.ip.rip.txVersion

       Possibilities:
               rip1   (0)
               rip2   (1)
               rip1-compatible   (2)"
   ::= {er1645v2TTmplCGreEntry 51716864}

er1645v2TTmplCGreIpRipRxVersion OBJECT-TYPE
   SYNTAX      INTEGER
               {
               rip1only (0),
               rip2only (1),
               rip12 (2)
               }
   MAX-ACCESS  read-write
   STATUS      current
   DESCRIPTION
      "Path: tunnels.editConf.greTunnels.ip.rip.rxVersion

       Possibilities:
               rip1only   (0)
               rip2only   (1)
               rip1&2   (2)"
   ::= {er1645v2TTmplCGreEntry 51717120}

er1645v2TTmplCGreIpRipSplitHorizon OBJECT-TYPE
   SYNTAX      INTEGER
               {
               disabled (0),
               enabled (1),
               poisonedReverse (2)
               }
   MAX-ACCESS  read-write
   STATUS      current
   DESCRIPTION
      "Path: tunnels.editConf.greTunnels.ip.rip.splitHorizon

       Possibilities:
               disabled   (0)
               enabled   (1)
               poisonedReverse   (2)"
   ::= {er1645v2TTmplCGreEntry 51713792}

er1645v2TTmplCGreIpRipAuth OBJECT-TYPE
   SYNTAX      INTEGER
               {
               disabled (0),
               texts (1),
               md5 (2)
               }
   MAX-ACCESS  read-write
   STATUS      current
   DESCRIPTION
      "Path: tunnels.editConf.greTunnels.ip.rip.authentication

       Possibilities:
               disabled   (0)
               text    (1)
               md5   (2)"
   ::= {er1645v2TTmplCGreEntry 51712512}

er1645v2TTmplCGreIpRipFilter OBJECT-TYPE
   SYNTAX      DisplayString
   MAX-ACCESS  read-write
   STATUS      current
   DESCRIPTION
      "Path: tunnels.editConf.greTunnels.ip.rip.filter"
   ::= {er1645v2TTmplCGreEntry 51716096}

er1645v2TTmplCGreIpRipFilterIn OBJECT-TYPE
   SYNTAX      DisplayString
   MAX-ACCESS  read-write
   STATUS      current
   DESCRIPTION
      "Path: tunnels.editConf.greTunnels.ip.rip.filterIn"
   ::= {er1645v2TTmplCGreEntry 51716352}

er1645v2TTmplCGreIpRipSnapshot OBJECT-TYPE
   SYNTAX      INTEGER
               {
               disabled (0),
               enabled (1)
               }
   MAX-ACCESS  read-write
   STATUS      current
   DESCRIPTION
      "Path: tunnels.editConf.greTunnels.ip.rip.snapshot

       Possibilities:
               disabled   (0)
               enabled   (1)"
   ::= {er1645v2TTmplCGreEntry 51708160}

er1645v2TTmplCGreIpRipClearNextHop OBJECT-TYPE
   SYNTAX      INTEGER
               {
               disabled (0),
               enabled (1)
               }
   MAX-ACCESS  read-write
   STATUS      current
   DESCRIPTION
      "Path: tunnels.editConf.greTunnels.ip.rip.clearNextHop

       Possibilities:
               disabled   (0)
               enabled   (1)"
   ::= {er1645v2TTmplCGreEntry 51708416}

er1645v2TTmplCGreIpAccPol OBJECT-TYPE
   SYNTAX      DisplayString
   MAX-ACCESS  read-write
   STATUS      current
   DESCRIPTION
      "Path: tunnels.editConf.greTunnels.ip.accessPolicy"
   ::= {er1645v2TTmplCGreEntry 53084160}

er1645v2TTmplCGreIpAB OBJECT-TYPE
   SYNTAX      DisplayString
   MAX-ACCESS  read-write
   STATUS      current
   DESCRIPTION
      "Path: tunnels.editConf.greTunnels.ip.trafficPolicy"
   ::= {er1645v2TTmplCGreEntry 51249152}

er1645v2TTmplCGreIpMA OBJECT-TYPE
   SYNTAX      INTEGER
               {
               disabled (0),
               enabled (1)
               }
   MAX-ACCESS  read-write
   STATUS      current
   DESCRIPTION
      "Path: tunnels.editConf.greTunnels.ip.mgmtAccess

       Possibilities:
               disabled   (0)
               enabled   (1)"
   ::= {er1645v2TTmplCGreEntry 51380224}

er1645v2TTmplCGreIpMF OBJECT-TYPE
   SYNTAX      Integer32
   MAX-ACCESS  read-write
   STATUS      current
   DESCRIPTION
      "Path: tunnels.editConf.greTunnels.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2TTmplCGreEntry 51445760}

er1645v2TTmplCGreIpDB OBJECT-TYPE
   SYNTAX      INTEGER
               {
               disabled (0),
               enabled (1)
               }
   MAX-ACCESS  read-write
   STATUS      current
   DESCRIPTION
      "Path: tunnels.editConf.greTunnels.ip.directedBroadcasts

       Possibilities:
               disabled   (0)
               enabled   (1)"
   ::= {er1645v2TTmplCGreEntry 51773440}

er1645v2TTmplCGreIpIR OBJECT-TYPE
   SYNTAX      INTEGER
               {
               disabled (0),
               enabled (1)
               }
   MAX-ACCESS  read-write
   STATUS      current
   DESCRIPTION
      "Path: tunnels.editConf.greTunnels.ip.icmpRedirects

       Possibilities:
               disabled   (0)
               enabled   (1)"
   ::= {er1645v2TTmplCGreEntry 52035584}

er1645v2TTmplCGreIpIgmp OBJECT-TYPE
   SYNTAX      INTEGER
               {
               disabled (0),
               proxy (1),
               router (2),
               v3Router (5)
               }
   MAX-ACCESS  read-write
   STATUS      current
   DESCRIPTION
      "Path: tunnels.editConf.greTunnels.ip.igmp

       Possibilities:
               disabled   (0)
               proxy   (1)
               router   (2)
               v3Router   (5)"
   ::= {er1645v2TTmplCGreEntry 52428800}

er1645v2TTmplCGreIpNN OBJECT-TYPE
   SYNTAX      DisplayString
   MAX-ACCESS  read-write
   STATUS      current
   DESCRIPTION
      "Path: tunnels.editConf.greTunnels.ip.nat"
   ::= {er1645v2TTmplCGreEntry 52101120}

er1645v2TTmplCGreIpPimMode OBJECT-TYPE
   SYNTAX      INTEGER
               {
               disabled (0),
               sparse (1),
               passive (2)
               }
   MAX-ACCESS  read-write
   STATUS      current
   DESCRIPTION
      "Path: tunnels.editConf.greTunnels.ip.pim.mode

       Possibilities:
               disabled   (0)
               sparse   (1)
               passive   (2)"
   ::= {er1645v2TTmplCGreEntry 53346560}

er1645v2TTmplCGreIpPimDrPriority OBJECT-TYPE
   SYNTAX      Counter32
   MAX-ACCESS  read-write
   STATUS      current
   DESCRIPTION
      "Path: tunnels.editConf.greTunnels.ip.pim.drPriority

       32 bit unsigned wrappable counter."
   ::= {er1645v2TTmplCGreEntry 53346816}

er1645v2TTmplCGreIpPimHelloTime OBJECT-TYPE
   SYNTAX      TimeTicks
   MAX-ACCESS  read-write
   STATUS      current
   DESCRIPTION
      "Path: tunnels.editConf.greTunnels.ip.pim.helloTime

       Time in centi-second."
   ::= {er1645v2TTmplCGreEntry 53347072}

er1645v2TTmplCGreIpPimPropagationDelay OBJECT-TYPE
   SYNTAX      TimeTicks
   MAX-ACCESS  read-write
   STATUS      current
   DESCRIPTION
      "Path: tunnels.editConf.greTunnels.ip.pim.propagationDelay

       Time in centi-second."
   ::= {er1645v2TTmplCGreEntry 53347328}

er1645v2TTmplCGreIpPimOverrideInterval OBJECT-TYPE
   SYNTAX      TimeTicks
   MAX-ACCESS  read-write
   STATUS      current
   DESCRIPTION
      "Path: tunnels.editConf.greTunnels.ip.pim.overrideInterval

       Time in centi-second."
   ::= {er1645v2TTmplCGreEntry 53347584}

er1645v2TTmplCGreIpPimBsrBorder OBJECT-TYPE
   SYNTAX      INTEGER
               {
               disabled (0),
               enabled (1)
               }
   MAX-ACCESS  read-write
   STATUS      current
   DESCRIPTION
      "Path: tunnels.editConf.greTunnels.ip.pim.bsrBorder

       Possibilities:
               disabled   (0)
               enabled   (1)"
   ::= {er1645v2TTmplCGreEntry 53347840}

er1645v2TTmplCGreIpPimTtlThreshold OBJECT-TYPE
   SYNTAX      Integer32
   MAX-ACCESS  read-write
   STATUS      current
   DESCRIPTION
      "Path: tunnels.editConf.greTunnels.ip.pim.ttlThreshold"
   ::= {er1645v2TTmplCGreEntry 53348096}

er1645v2TTmplCGreIpIMNetworkUnreachable OBJECT-TYPE
   SYNTAX      INTEGER
               {
               disabled (0),
               enabled (1)
               }
   MAX-ACCESS  read-write
   STATUS      current
   DESCRIPTION
      "Path: tunnels.editConf.greTunnels.ip.icmpMessages.networkUnreachable

       Possibilities:
               disabled   (0)
               enabled   (1)"
   ::= {er1645v2TTmplCGreEntry 53412096}

er1645v2TTmplCGreIpIMHostUnreachable OBJECT-TYPE
   SYNTAX      INTEGER
               {
               disabled (0),
               enabled (1)
               }
   MAX-ACCESS  read-write
   STATUS      current
   DESCRIPTION
      "Path: tunnels.editConf.greTunnels.ip.icmpMessages.hostUnreachable

       Possibilities:
               disabled   (0)
               enabled   (1)"
   ::= {er1645v2TTmplCGreEntry 53412352}

er1645v2TTmplCGreIpIMProtocolUnreachable OBJECT-TYPE
   SYNTAX      INTEGER
               {
               disabled (0),
               enabled (1)
               }
   MAX-ACCESS  read-write
   STATUS      current
   DESCRIPTION
      "Path: tunnels.editConf.greTunnels.ip.icmpMessages.protocolUnreachable

       Possibilities:
               disabled   (0)
               enabled   (1)"
   ::= {er1645v2TTmplCGreEntry 53412608}

er1645v2TTmplCGreIpIMPortUnreachable OBJECT-TYPE
   SYNTAX      INTEGER
               {
               disabled (0),
               enabled (1)
               }
   MAX-ACCESS  read-write
   STATUS      current
   DESCRIPTION
      "Path: tunnels.editConf.greTunnels.ip.icmpMessages.portUnreachable

       Possibilities:
               disabled   (0)
               enabled   (1)"
   ::= {er1645v2TTmplCGreEntry 53412864}

er1645v2TTmplCGreIpIMMtuExceeded OBJECT-TYPE
   SYNTAX      INTEGER
               {
               disabled (0),
               enabled (1)
               }
   MAX-ACCESS  read-write
   STATUS      current
   DESCRIPTION
      "Path: tunnels.editConf.greTunnels.ip.icmpMessages.mtuExceeded

       Possibilities:
               disabled   (0)
               enabled   (1)"
   ::= {er1645v2TTmplCGreEntry 53413120}

er1645v2TTmplCGreIpIMAdminProhibited OBJECT-TYPE
   SYNTAX      INTEGER
               {
               disabled (0),
               enabled (1)
               }
   MAX-ACCESS  read-write
   STATUS      current
   DESCRIPTION
      "Path: tunnels.editConf.greTunnels.ip.icmpMessages.adminProhibited

       Possibilities:
               disabled   (0)
               enabled   (1)"
   ::= {er1645v2TTmplCGreEntry 53413376}

er1645v2TTmplCGreIpIMTtlExceeded OBJECT-TYPE
   SYNTAX      INTEGER
               {
               disabled (0),
               enabled (1)
               }
   MAX-ACCESS  read-write
   STATUS      current
   DESCRIPTION
      "Path: tunnels.editConf.greTunnels.ip.icmpMessages.ttlExceeded

       Possibilities:
               disabled   (0)
               enabled   (1)"
   ::= {er1645v2TTmplCGreEntry 53413632}

er1645v2TTmplCGreIpIMRedirect OBJECT-TYPE
   SYNTAX      INTEGER
               {
               disabled (0),
               enabled (1)
               }
   MAX-ACCESS  read-write
   STATUS      current
   DESCRIPTION
      "Path: tunnels.editConf.greTunnels.ip.icmpMessages.redirect

       Possibilities:
               disabled   (0)
               enabled   (1)"
   ::= {er1645v2TTmplCGreEntry 53413888}

er1645v2TTmplCGreBrAccList OBJECT-TYPE
   SYNTAX      DisplayString
   MAX-ACCESS  read-write
   STATUS      current
   DESCRIPTION
      "Path: tunnels.editConf.greTunnels.bridging.accessList"
   ::= {er1645v2TTmplCGreEntry 453246976}

er1645v2TTmplCGreBrInACL OBJECT-TYPE
   SYNTAX      DisplayString
   MAX-ACCESS  read-write
   STATUS      current
   DESCRIPTION
      "Path: tunnels.editConf.greTunnels.bridging.inAccessList"
   ::= {er1645v2TTmplCGreEntry 456916992}

er1645v2TTmplCGreBrTp OBJECT-TYPE
   SYNTAX      DisplayString
   MAX-ACCESS  read-write
   STATUS      current
   DESCRIPTION
      "Path: tunnels.editConf.greTunnels.bridging.trafficPolicy"
   ::= {er1645v2TTmplCGreEntry 454295552}

er1645v2TTmplCGreBrBrGrp OBJECT-TYPE
   SYNTAX      DisplayString
   MAX-ACCESS  read-write
   STATUS      current
   DESCRIPTION
      "Path: tunnels.editConf.greTunnels.bridging.bridgeGroup"
   ::= {er1645v2TTmplCGreEntry 454819840}

er1645v2TTmplCGreBrLimBC OBJECT-TYPE
   SYNTAX      INTEGER
               {
               disabled (0),
               enabled (1)
               }
   MAX-ACCESS  read-write
   STATUS      current
   DESCRIPTION
      "Path: tunnels.editConf.greTunnels.bridging.limitBroadcasts

       Possibilities:
               disabled   (0)
               enabled   (1)"
   ::= {er1645v2TTmplCGreEntry 455081984}

er1645v2TTmplCGreBrPrivateMode OBJECT-TYPE
   SYNTAX      INTEGER
               {
               disabled (0),
               enabled (1)
               }
   MAX-ACCESS  read-write
   STATUS      current
   DESCRIPTION
      "Path: tunnels.editConf.greTunnels.bridging.privateMode

       Possibilities:
               disabled   (0)
               enabled   (1)"
   ::= {er1645v2TTmplCGreEntry 459538432}

er1645v2TTmplCGreBrLearning OBJECT-TYPE
   SYNTAX      INTEGER
               {
               disabled (0),
               enabled (1)
               }
   MAX-ACCESS  read-write
   STATUS      current
   DESCRIPTION
      "Path: tunnels.editConf.greTunnels.bridging.learning

       Possibilities:
               disabled   (0)
               enabled   (1)"
   ::= {er1645v2TTmplCGreEntry 456130560}

er1645v2TTmplCGreBrMaxCacheSize OBJECT-TYPE
   SYNTAX      INTEGER
               {
               unlimited (0)
               }
   MAX-ACCESS  read-write
   STATUS      current
   DESCRIPTION
      "Path: tunnels.editConf.greTunnels.bridging.maxCacheSize

       Possibilities:
               unlimited   (0)"
   ::= {er1645v2TTmplCGreEntry 456392704}

er1645v2TTmplCGreBrRelearnDropOnRelearn OBJECT-TYPE
   SYNTAX      INTEGER
               {
               disabled (0),
               enabled (1)
               }
   MAX-ACCESS  read-write
   STATUS      current
   DESCRIPTION
      "Path: tunnels.editConf.greTunnels.bridging.relearn.dropOnRelearn

       Possibilities:
               disabled   (0)
               enabled   (1)"
   ::= {er1645v2TTmplCGreEntry 456655872}

er1645v2TTmplCGreBrRelearnShutdownThreshold OBJECT-TYPE
   SYNTAX      Integer32
   MAX-ACCESS  read-write
   STATUS      current
   DESCRIPTION
      "Path: tunnels.editConf.greTunnels.bridging.relearn.shutdownThreshold"
   ::= {er1645v2TTmplCGreEntry 456656896}

er1645v2TTmplCGreBrRelearnShutdownTime OBJECT-TYPE
   SYNTAX      TimeTicks
   MAX-ACCESS  read-write
   STATUS      current
   DESCRIPTION
      "Path: tunnels.editConf.greTunnels.bridging.relearn.shutdownTime

       Time in centi-second."
   ::= {er1645v2TTmplCGreEntry 456657920}

er1645v2TTmplCGreBrRelearnLoopDetection OBJECT-TYPE
   SYNTAX      INTEGER
               {
               disabled (0),
               passive (1),
               active (2)
               }
   MAX-ACCESS  read-write
   STATUS      current
   DESCRIPTION
      "Path: tunnels.editConf.greTunnels.bridging.relearn.loopDetection

       Possibilities:
               disabled   (0)
               passive   (1)
               active   (2)"
   ::= {er1645v2TTmplCGreEntry 456658944}

er1645v2TTmplCGreBrRelearnLoopDetectionInterval OBJECT-TYPE
   SYNTAX      TimeTicks
   MAX-ACCESS  read-write
   STATUS      current
   DESCRIPTION
      "Path: tunnels.editConf.greTunnels.bridging.relearn.loopDetectionInterval

       Time in centi-second."
   ::= {er1645v2TTmplCGreEntry 456659968}

er1645v2TTmplCGreBrVlanMemberShip OBJECT-TYPE
   SYNTAX      INTEGER
               {
               all (0),
               none (1),
               grouped (2)
               }
   MAX-ACCESS  read-write
   STATUS      current
   DESCRIPTION
      "Path: tunnels.editConf.greTunnels.bridging.vlanMemberShip

       Possibilities:
               all   (0)
               none   (1)
               grouped   (2)"
   ::= {er1645v2TTmplCGreEntry 457965568}

er1645v2TTmplCGreBrVlTUntaggedAction OBJECT-TYPE
   SYNTAX      INTEGER
               {
               discard (0),
               accept (1),
               tag (2)
               }
   MAX-ACCESS  read-write
   STATUS      current
   DESCRIPTION
      "Path: tunnels.editConf.greTunnels.bridging.vlanTagging.untagged.action

       Possibilities:
               discard   (0)
               accept   (1)
               tag   (2)"
   ::= {er1645v2TTmplCGreEntry 459055104}

er1645v2TTmplCGreBrVlTUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: tunnels.editConf.greTunnels.bridging.vlanTagging.untagged.tagInfo.tpid

       Possibilities:
               dot1Q   (33024)
               dot1ad   (34984)
               0x9100   (37120)
               0x9200   (37376)
               0x9300   (37632)"
   ::= {er1645v2TTmplCGreEntry 459059712}

er1645v2TTmplCGreBrVlTUntaggedTagInfoVid OBJECT-TYPE
   SYNTAX      Integer32
   MAX-ACCESS  read-write
   STATUS      current
   DESCRIPTION
      "Path: tunnels.editConf.greTunnels.bridging.vlanTagging.untagged.tagInfo.vid"
   ::= {er1645v2TTmplCGreEntry 459060224}

er1645v2TTmplCGreBrVlTUnknownVlansAction OBJECT-TYPE
   SYNTAX      INTEGER
               {
               discard (0),
               accept (1),
               tag (2)
               }
   MAX-ACCESS  read-write
   STATUS      current
   DESCRIPTION
      "Path: tunnels.editConf.greTunnels.bridging.vlanTagging.unknownVlans.action

       Possibilities:
               discard   (0)
               accept   (1)
               tag   (2)"
   ::= {er1645v2TTmplCGreEntry 459120640}

er1645v2TTmplCGreBrVlTUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: tunnels.editConf.greTunnels.bridging.vlanTagging.unknownVlans.tagInfo.tpid

       Possibilities:
               dot1Q   (33024)
               dot1ad   (34984)
               0x9100   (37120)
               0x9200   (37376)
               0x9300   (37632)"
   ::= {er1645v2TTmplCGreEntry 459125248}

er1645v2TTmplCGreBrVlTUnknownVlansTagInfoVid OBJECT-TYPE
   SYNTAX      Integer32
   MAX-ACCESS  read-write
   STATUS      current
   DESCRIPTION
      "Path: tunnels.editConf.greTunnels.bridging.vlanTagging.unknownVlans.tagInfo.vid"
   ::= {er1645v2TTmplCGreEntry 459125760}

er1645v2TTmplCGreBrDot1adType OBJECT-TYPE
   SYNTAX      INTEGER
               {
               slOPTg (0),
               cPort (4),
               sPort (1),
               nni (2)
               }
   MAX-ACCESS  read-write
   STATUS      current
   DESCRIPTION
      "Path: tunnels.editConf.greTunnels.bridging.dot1ad.type

       Possibilities:
               <OPT>   (0)
               cPort   (4)
               sPort   (1)
               nni   (2)"
   ::= {er1645v2TTmplCGreEntry 460850176}

er1645v2TTmplCGreBrPriority OBJECT-TYPE
   SYNTAX      Integer32
   MAX-ACCESS  read-write
   STATUS      current
   DESCRIPTION
      "Path: tunnels.editConf.greTunnels.bridging.priority"
   ::= {er1645v2TTmplCGreEntry 453509120}

er1645v2TTmplCGreBrPathCost OBJECT-TYPE
   SYNTAX      Integer32
   MAX-ACCESS  read-write
   STATUS      current
   DESCRIPTION
      "Path: tunnels.editConf.greTunnels.bridging.pathCost"
   ::= {er1645v2TTmplCGreEntry 453771264}

er1645v2TTmplCGreBrInternalPathCost OBJECT-TYPE
   SYNTAX      Integer32
   MAX-ACCESS  read-write
   STATUS      current
   DESCRIPTION
      "Path: tunnels.editConf.greTunnels.bridging.internalPathCost"
   ::= {er1645v2TTmplCGreEntry 457703424}

er1645v2TTmplCGreBrTCD OBJECT-TYPE
   SYNTAX      INTEGER
               {
               disabled (0),
               enabled (1)
               }
   MAX-ACCESS  read-write
   STATUS      current
   DESCRIPTION
      "Path: tunnels.editConf.greTunnels.bridging.topologyChangeDetection

       Possibilities:
               disabled   (0)
               enabled   (1)"
   ::= {er1645v2TTmplCGreEntry 454033408}

er1645v2TTmplCGreBrRestrictedRole OBJECT-TYPE
   SYNTAX      INTEGER
               {
               disabled (0),
               enabled (1)
               }
   MAX-ACCESS  read-write
   STATUS      current
   DESCRIPTION
      "Path: tunnels.editConf.greTunnels.bridging.restrictedRole

       Possibilities:
               disabled   (0)
               enabled   (1)"
   ::= {er1645v2TTmplCGreEntry 458227712}

er1645v2TTmplCGreBrAdminEdge OBJECT-TYPE
   SYNTAX      INTEGER
               {
               disabled (0),
               enabled (1)
               }
   MAX-ACCESS  read-write
   STATUS      current
   DESCRIPTION
      "Path: tunnels.editConf.greTunnels.bridging.adminEdge

       Possibilities:
               disabled   (0)
               enabled   (1)"
   ::= {er1645v2TTmplCGreEntry 457179136}

er1645v2TTmplCGreBrOamMacDeviceMac OBJECT-TYPE
   SYNTAX      DisplayString
   MAX-ACCESS  read-write
   STATUS      current
   DESCRIPTION
      "Path: tunnels.editConf.greTunnels.bridging.ethOam.macAddress.deviceMac"
   ::= {er1645v2TTmplCGreEntry 458506496}

er1645v2TTmplCGreBrOamMacUserMac OBJECT-TYPE
   SYNTAX      OCTET STRING
   MAX-ACCESS  read-write
   STATUS      current
   DESCRIPTION
      "Path: tunnels.editConf.greTunnels.bridging.ethOam.macAddress.userMac

       MAC address."
   ::= {er1645v2TTmplCGreEntry 458506368}

er1645v2TTmplCGreBrOamMacBridgeMac OBJECT-TYPE
   SYNTAX      DisplayString
   MAX-ACCESS  read-write
   STATUS      current
   DESCRIPTION
      "Path: tunnels.editConf.greTunnels.bridging.ethOam.macAddress.bridgeMac"
   ::= {er1645v2TTmplCGreEntry 458506432}

er1645v2TTmplCGreBrMgmtInline OBJECT-TYPE
   SYNTAX      INTEGER
               {
               disabled (0),
               enabled (1)
               }
   MAX-ACCESS  read-write
   STATUS      current
   DESCRIPTION
      "Path: tunnels.editConf.greTunnels.bridging.mgmtInline

       Possibilities:
               disabled   (0)
               enabled   (1)"
   ::= {er1645v2TTmplCGreEntry 458752000}

er1645v2TTmplCGreBrL2ptMode OBJECT-TYPE
   SYNTAX      INTEGER
               {
               disabled (0),
               enabled (1)
               }
   MAX-ACCESS  read-write
   STATUS      current
   DESCRIPTION
      "Path: tunnels.editConf.greTunnels.bridging.l2ProtTunnel.mode

       Possibilities:
               disabled   (0)
               enabled   (1)"
   ::= {er1645v2TTmplCGreEntry 459292672}

er1645v2TTmplCGreBrL2ptProtocols OBJECT-TYPE
   SYNTAX      Integer32
   MAX-ACCESS  read-write
   STATUS      current
   DESCRIPTION
      "Path: tunnels.editConf.greTunnels.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1645v2TTmplCGreEntry 459309056}

er1645v2TTmplCGreBrL2ptDestMac OBJECT-TYPE
   SYNTAX      OCTET STRING
   MAX-ACCESS  read-write
   STATUS      current
   DESCRIPTION
      "Path: tunnels.editConf.greTunnels.bridging.l2ProtTunnel.destinationMac

       MAC address."
   ::= {er1645v2TTmplCGreEntry 459325440}

er1645v2TTmplCGreBrL2ptCos OBJECT-TYPE
   SYNTAX      INTEGER
               {
               unchanged (255)
               }
   MAX-ACCESS  read-write
   STATUS      current
   DESCRIPTION
      "Path: tunnels.editConf.greTunnels.bridging.l2ProtTunnel.cos

       Possibilities:
               unchanged   (255)"
   ::= {er1645v2TTmplCGreEntry 459341824}

er1645v2TTmplCGreBrL2ptDropThrStp OBJECT-TYPE
   SYNTAX      INTEGER
               {
               unlimited (0)
               }
   UNITS       "packets/sec"
   MAX-ACCESS  read-write
   STATUS      current
   DESCRIPTION
      "Path: tunnels.editConf.greTunnels.bridging.l2ProtTunnel.dropThresholds.stp

       unit name = packets/sec

       Possibilities:
               unlimited   (0)"
   ::= {er1645v2TTmplCGreEntry 459358272}

er1645v2TTmplCGreBrL2ptDropThrLldp OBJECT-TYPE
   SYNTAX      INTEGER
               {
               unlimited (0)
               }
   UNITS       "packets/sec"
   MAX-ACCESS  read-write
   STATUS      current
   DESCRIPTION
      "Path: tunnels.editConf.greTunnels.bridging.l2ProtTunnel.dropThresholds.lldp

       unit name = packets/sec

       Possibilities:
               unlimited   (0)"
   ::= {er1645v2TTmplCGreEntry 459358336}

er1645v2TTmplCGreBrL2ptDropThrOam OBJECT-TYPE
   SYNTAX      INTEGER
               {
               unlimited (0)
               }
   UNITS       "packets/sec"
   MAX-ACCESS  read-write
   STATUS      current
   DESCRIPTION
      "Path: tunnels.editConf.greTunnels.bridging.l2ProtTunnel.dropThresholds.oam

       unit name = packets/sec

       Possibilities:
               unlimited   (0)"
   ::= {er1645v2TTmplCGreEntry 459358400}

er1645v2TTmplCGreBrL2ptDropThrCdp OBJECT-TYPE
   SYNTAX      INTEGER
               {
               unlimited (0)
               }
   UNITS       "packets/sec"
   MAX-ACCESS  read-write
   STATUS      current
   DESCRIPTION
      "Path: tunnels.editConf.greTunnels.bridging.l2ProtTunnel.dropThresholds.cdp

       unit name = packets/sec

       Possibilities:
               unlimited   (0)"
   ::= {er1645v2TTmplCGreEntry 459358464}

er1645v2TTmplCGreBrL2ptDropThrVtp OBJECT-TYPE
   SYNTAX      INTEGER
               {
               unlimited (0)
               }
   UNITS       "packets/sec"
   MAX-ACCESS  read-write
   STATUS      current
   DESCRIPTION
      "Path: tunnels.editConf.greTunnels.bridging.l2ProtTunnel.dropThresholds.vtp

       unit name = packets/sec

       Possibilities:
               unlimited   (0)"
   ::= {er1645v2TTmplCGreEntry 459358528}

er1645v2TTmplCGreBrL2ptDropThrLacp OBJECT-TYPE
   SYNTAX      INTEGER
               {
               unlimited (0)
               }
   UNITS       "packets/sec"
   MAX-ACCESS  read-write
   STATUS      current
   DESCRIPTION
      "Path: tunnels.editConf.greTunnels.bridging.l2ProtTunnel.dropThresholds.lacp

       unit name = packets/sec

       Possibilities:
               unlimited   (0)"
   ::= {er1645v2TTmplCGreEntry 459358592}

er1645v2TTmplCGreBrL2ptDropThrEfmOam OBJECT-TYPE
   SYNTAX      INTEGER
               {
               unlimited (0)
               }
   UNITS       "packets/sec"
   MAX-ACCESS  read-write
   STATUS      current
   DESCRIPTION
      "Path: tunnels.editConf.greTunnels.bridging.l2ProtTunnel.dropThresholds.efmOam

       unit name = packets/sec

       Possibilities:
               unlimited   (0)"
   ::= {er1645v2TTmplCGreEntry 459358656}

er1645v2TTmplCGreBrL2ptDropThrPvst OBJECT-TYPE
   SYNTAX      INTEGER
               {
               unlimited (0)
               }
   UNITS       "packets/sec"
   MAX-ACCESS  read-write
   STATUS      current
   DESCRIPTION
      "Path: tunnels.editConf.greTunnels.bridging.l2ProtTunnel.dropThresholds.pvst

       unit name = packets/sec

       Possibilities:
               unlimited   (0)"
   ::= {er1645v2TTmplCGreEntry 459358720}

er1645v2TTmplCGreBrL2ptDropThrMmrp OBJECT-TYPE
   SYNTAX      INTEGER
               {
               unlimited (0)
               }
   UNITS       "packets/sec"
   MAX-ACCESS  read-write
   STATUS      current
   DESCRIPTION
      "Path: tunnels.editConf.greTunnels.bridging.l2ProtTunnel.dropThresholds.mmrp

       unit name = packets/sec

       Possibilities:
               unlimited   (0)"
   ::= {er1645v2TTmplCGreEntry 459358784}

er1645v2TTmplCGreBrL2ptDropThrMvrp OBJECT-TYPE
   SYNTAX      INTEGER
               {
               unlimited (0)
               }
   UNITS       "packets/sec"
   MAX-ACCESS  read-write
   STATUS      current
   DESCRIPTION
      "Path: tunnels.editConf.greTunnels.bridging.l2ProtTunnel.dropThresholds.mvrp

       unit name = packets/sec

       Possibilities:
               unlimited   (0)"
   ::= {er1645v2TTmplCGreEntry 459358848}

er1645v2TTmplCGreBrL2ptDropThrGvrp OBJECT-TYPE
   SYNTAX      INTEGER
               {
               unlimited (0)
               }
   UNITS       "packets/sec"
   MAX-ACCESS  read-write
   STATUS      current
   DESCRIPTION
      "Path: tunnels.editConf.greTunnels.bridging.l2ProtTunnel.dropThresholds.gvrp

       unit name = packets/sec

       Possibilities:
               unlimited   (0)"
   ::= {er1645v2TTmplCGreEntry 459358912}

er1645v2TTmplCGreBrL2ptDropThrGmrp OBJECT-TYPE
   SYNTAX      INTEGER
               {
               unlimited (0)
               }
   UNITS       "packets/sec"
   MAX-ACCESS  read-write
   STATUS      current
   DESCRIPTION
      "Path: tunnels.editConf.greTunnels.bridging.l2ProtTunnel.dropThresholds.gmrp

       unit name = packets/sec

       Possibilities:
               unlimited   (0)"
   ::= {er1645v2TTmplCGreEntry 459358976}

er1645v2TTmplCGreBrL2ptDropThrDtp OBJECT-TYPE
   SYNTAX      INTEGER
               {
               unlimited (0)
               }
   UNITS       "packets/sec"
   MAX-ACCESS  read-write
   STATUS      current
   DESCRIPTION
      "Path: tunnels.editConf.greTunnels.bridging.l2ProtTunnel.dropThresholds.dtp

       unit name = packets/sec

       Possibilities:
               unlimited   (0)"
   ::= {er1645v2TTmplCGreEntry 459359040}

er1645v2TTmplCGreBrL2ptDropThrPagp OBJECT-TYPE
   SYNTAX      INTEGER
               {
               unlimited (0)
               }
   UNITS       "packets/sec"
   MAX-ACCESS  read-write
   STATUS      current
   DESCRIPTION
      "Path: tunnels.editConf.greTunnels.bridging.l2ProtTunnel.dropThresholds.pagp

       unit name = packets/sec

       Possibilities:
               unlimited   (0)"
   ::= {er1645v2TTmplCGreEntry 459359104}

er1645v2TTmplCGreBrL2ptDropThrUdld OBJECT-TYPE
   SYNTAX      INTEGER
               {
               unlimited (0)
               }
   UNITS       "packets/sec"
   MAX-ACCESS  read-write
   STATUS      current
   DESCRIPTION
      "Path: tunnels.editConf.greTunnels.bridging.l2ProtTunnel.dropThresholds.udld

       unit name = packets/sec

       Possibilities:
               unlimited   (0)"
   ::= {er1645v2TTmplCGreEntry 459359168}

er1645v2TTmplCGreVirtEthernetVirtualEthernet OBJECT-TYPE
   SYNTAX      DisplayString
   MAX-ACCESS  read-write
   STATUS      current
   DESCRIPTION
      "Path: tunnels.editConf.greTunnels.virtEthernet.virtualEthernet"
   ::= {er1645v2TTmplCGreEntry 151060480}

er1645v2TTmplCGreGreLocalIpAddress OBJECT-TYPE
   SYNTAX      IpAddress
   MAX-ACCESS  read-write
   STATUS      current
   DESCRIPTION
      "Path: tunnels.editConf.greTunnels.gre.localIpAddress"
   ::= {er1645v2TTmplCGreEntry 587268096}

er1645v2TTmplCGreGreLocalInterface OBJECT-TYPE
   SYNTAX      DisplayString
   MAX-ACCESS  read-write
   STATUS      current
   DESCRIPTION
      "Path: tunnels.editConf.greTunnels.gre.localInterface"
   ::= {er1645v2TTmplCGreEntry 588251136}

er1645v2TTmplCGreGreRemoteIpAddress OBJECT-TYPE
   SYNTAX      IpAddress
   MAX-ACCESS  read-write
   STATUS      current
   DESCRIPTION
      "Path: tunnels.editConf.greTunnels.gre.remoteIpAddress"
   ::= {er1645v2TTmplCGreEntry 587333632}

er1645v2TTmplCGreGreRemoteDnsName OBJECT-TYPE
   SYNTAX      DisplayString
   MAX-ACCESS  read-write
   STATUS      current
   DESCRIPTION
      "Path: tunnels.editConf.greTunnels.gre.remoteDnsName"
   ::= {er1645v2TTmplCGreEntry 587399168}

er1645v2TTmplCGreGreKey OBJECT-TYPE
   SYNTAX      Integer32
   MAX-ACCESS  read-write
   STATUS      current
   DESCRIPTION
      "Path: tunnels.editConf.greTunnels.gre.key"
   ::= {er1645v2TTmplCGreEntry 587595776}

er1645v2TTmplCGreGreKpAlMode OBJECT-TYPE
   SYNTAX      INTEGER
               {
               disabled (0),
               enabled (1)
               }
   MAX-ACCESS  read-write
   STATUS      current
   DESCRIPTION
      "Path: tunnels.editConf.greTunnels.gre.keepAlive.mode

       Possibilities:
               disabled   (0)
               enabled   (1)"
   ::= {er1645v2TTmplCGreEntry 587727104}

er1645v2TTmplCGreGreKpAlInterval OBJECT-TYPE
   SYNTAX      TimeTicks
   MAX-ACCESS  read-write
   STATUS      current
   DESCRIPTION
      "Path: tunnels.editConf.greTunnels.gre.keepAlive.interval

       Time in centi-second."
   ::= {er1645v2TTmplCGreEntry 587727360}

er1645v2TTmplCGreGreKpAlRepTimeOut OBJECT-TYPE
   SYNTAX      TimeTicks
   MAX-ACCESS  read-write
   STATUS      current
   DESCRIPTION
      "Path: tunnels.editConf.greTunnels.gre.keepAlive.replyTimeOut

       Time in centi-second."
   ::= {er1645v2TTmplCGreEntry 587727616}

er1645v2TTmplCGreGreKpAlFailsPrmt OBJECT-TYPE
   SYNTAX      Integer32
   MAX-ACCESS  read-write
   STATUS      current
   DESCRIPTION
      "Path: tunnels.editConf.greTunnels.gre.keepAlive.failsPermitted"
   ::= {er1645v2TTmplCGreEntry 587727872}

er1645v2TTmplCGreGreRRoutDefRt OBJECT-TYPE
   SYNTAX      INTEGER
               {
               disabled (0),
               enabled (1)
               }
   MAX-ACCESS  read-write
   STATUS      current
   DESCRIPTION
      "Path: tunnels.editConf.greTunnels.gre.remoteRoute.useDefaultRoute

       Possibilities:
               disabled   (0)
               enabled   (1)"
   ::= {er1645v2TTmplCGreEntry 587923712}

er1645v2TTmplCGreGreTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               copy (256),
               queueTosMap (257)
               }
   MAX-ACCESS  read-write
   STATUS      current
   DESCRIPTION
      "Path: tunnels.editConf.greTunnels.gre.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               copy   (256)
               queueTosMap   (257)"
   ::= {er1645v2TTmplCGreEntry 587988992}

er1645v2TTmplCGreGreQueueTosMapQueue1 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.greTunnels.gre.queueTosMap.queue1

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TTmplCGreEntry 589168896}

er1645v2TTmplCGreGreQueueTosMapQueue2 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.greTunnels.gre.queueTosMap.queue2

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TTmplCGreEntry 589169152}

er1645v2TTmplCGreGreQueueTosMapQueue3 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.greTunnels.gre.queueTosMap.queue3

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TTmplCGreEntry 589169408}

er1645v2TTmplCGreGreQueueTosMapQueue4 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.greTunnels.gre.queueTosMap.queue4

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TTmplCGreEntry 589169664}

er1645v2TTmplCGreGreQueueTosMapQueue5 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.greTunnels.gre.queueTosMap.queue5

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TTmplCGreEntry 589169920}

er1645v2TTmplCGreGreQueueTosMapLowDelayQueue OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.greTunnels.gre.queueTosMap.lowDelayQueue

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TTmplCGreEntry 589170176}

er1645v2TTmplCGreGreQueueTosMapLowDelay2Queue OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.greTunnels.gre.queueTosMap.lowDelay2Queue

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TTmplCGreEntry 589170432}

er1645v2TTmplCGreGreQueueTosMapSystemQueue OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.greTunnels.gre.queueTosMap.systemQueue

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TTmplCGreEntry 589170688}

er1645v2TTmplCGreGreDf OBJECT-TYPE
   SYNTAX      INTEGER
               {
               clear (0),
               set (1),
               copy (2)
               }
   MAX-ACCESS  read-write
   STATUS      current
   DESCRIPTION
      "Path: tunnels.editConf.greTunnels.gre.dontFragmentBit

       Possibilities:
               clear   (0)
               set   (1)
               copy   (2)"
   ::= {er1645v2TTmplCGreEntry 588054528}

er1645v2TTmplCGreGreTtl OBJECT-TYPE
   SYNTAX      INTEGER
               {
               copy (256)
               }
   MAX-ACCESS  read-write
   STATUS      current
   DESCRIPTION
      "Path: tunnels.editConf.greTunnels.gre.ttl

       Possibilities:
               copy   (256)"
   ::= {er1645v2TTmplCGreEntry 588120064}

er1645v2TTmplCGreGreMtu OBJECT-TYPE
   SYNTAX      Integer32
   MAX-ACCESS  read-write
   STATUS      current
   DESCRIPTION
      "Path: tunnels.editConf.greTunnels.gre.mtu"
   ::= {er1645v2TTmplCGreEntry 588382208}

er1645v2TTmplCGreMplsMode OBJECT-TYPE
   SYNTAX      INTEGER
               {
               disabled (0),
               enabled (1)
               }
   MAX-ACCESS  read-write
   STATUS      current
   DESCRIPTION
      "Path: tunnels.editConf.greTunnels.mpls.mode

       Possibilities:
               disabled   (0)
               enabled   (1)"
   ::= {er1645v2TTmplCGreEntry 167837696}

er1645v2TTmplCGreMplsInLabel OBJECT-TYPE
   SYNTAX      Integer32
   MAX-ACCESS  read-write
   STATUS      current
   DESCRIPTION
      "Path: tunnels.editConf.greTunnels.mpls.inLabel"
   ::= {er1645v2TTmplCGreEntry 167903232}

er1645v2TTmplCGreMplsOutLabel OBJECT-TYPE
   SYNTAX      Integer32
   MAX-ACCESS  read-write
   STATUS      current
   DESCRIPTION
      "Path: tunnels.editConf.greTunnels.mpls.outLabel"
   ::= {er1645v2TTmplCGreEntry 168099840}

er1645v2TTmplCGreMplsTrafficClassMode OBJECT-TYPE
   SYNTAX      INTEGER
               {
               fixed (0),
               qos (1)
               }
   MAX-ACCESS  read-write
   STATUS      current
   DESCRIPTION
      "Path: tunnels.editConf.greTunnels.mpls.trafficClass.mode

       Possibilities:
               fixed   (0)
               qos   (1)"
   ::= {er1645v2TTmplCGreEntry 167969024}

er1645v2TTmplCGreMplsTrafficClassFixed OBJECT-TYPE
   SYNTAX      Integer32
   MAX-ACCESS  read-write
   STATUS      current
   DESCRIPTION
      "Path: tunnels.editConf.greTunnels.mpls.trafficClass.fixed"
   ::= {er1645v2TTmplCGreEntry 167969280}

er1645v2TTmplCGreMplsTrafficClassQosP0 OBJECT-TYPE
   SYNTAX      Integer32
   MAX-ACCESS  read-write
   STATUS      current
   DESCRIPTION
      "Path: tunnels.editConf.greTunnels.mpls.trafficClass.qos.p0"
   ::= {er1645v2TTmplCGreEntry 167969537}

er1645v2TTmplCGreMplsTrafficClassQosP1 OBJECT-TYPE
   SYNTAX      Integer32
   MAX-ACCESS  read-write
   STATUS      current
   DESCRIPTION
      "Path: tunnels.editConf.greTunnels.mpls.trafficClass.qos.p1"
   ::= {er1645v2TTmplCGreEntry 167969538}

er1645v2TTmplCGreMplsTrafficClassQosP2 OBJECT-TYPE
   SYNTAX      Integer32
   MAX-ACCESS  read-write
   STATUS      current
   DESCRIPTION
      "Path: tunnels.editConf.greTunnels.mpls.trafficClass.qos.p2"
   ::= {er1645v2TTmplCGreEntry 167969539}

er1645v2TTmplCGreMplsTrafficClassQosP3 OBJECT-TYPE
   SYNTAX      Integer32
   MAX-ACCESS  read-write
   STATUS      current
   DESCRIPTION
      "Path: tunnels.editConf.greTunnels.mpls.trafficClass.qos.p3"
   ::= {er1645v2TTmplCGreEntry 167969540}

er1645v2TTmplCGreMplsTrafficClassQosP4 OBJECT-TYPE
   SYNTAX      Integer32
   MAX-ACCESS  read-write
   STATUS      current
   DESCRIPTION
      "Path: tunnels.editConf.greTunnels.mpls.trafficClass.qos.p4"
   ::= {er1645v2TTmplCGreEntry 167969541}

er1645v2TTmplCGreMplsTrafficClassQosP5 OBJECT-TYPE
   SYNTAX      Integer32
   MAX-ACCESS  read-write
   STATUS      current
   DESCRIPTION
      "Path: tunnels.editConf.greTunnels.mpls.trafficClass.qos.p5"
   ::= {er1645v2TTmplCGreEntry 167969542}

er1645v2TTmplCGreMplsTrafficClassQosP6 OBJECT-TYPE
   SYNTAX      Integer32
   MAX-ACCESS  read-write
   STATUS      current
   DESCRIPTION
      "Path: tunnels.editConf.greTunnels.mpls.trafficClass.qos.p6"
   ::= {er1645v2TTmplCGreEntry 167969543}

er1645v2TTmplCGreMplsTrafficClassQosP7 OBJECT-TYPE
   SYNTAX      Integer32
   MAX-ACCESS  read-write
   STATUS      current
   DESCRIPTION
      "Path: tunnels.editConf.greTunnels.mpls.trafficClass.qos.p7"
   ::= {er1645v2TTmplCGreEntry 167969544}

er1645v2TTmplCGreMplsTtl OBJECT-TYPE
   SYNTAX      INTEGER
               {
               copy (256)
               }
   MAX-ACCESS  read-write
   STATUS      current
   DESCRIPTION
      "Path: tunnels.editConf.greTunnels.mpls.ttl

       Possibilities:
               copy   (256)"
   ::= {er1645v2TTmplCGreEntry 168034304}

er1645v2TTmplCGreInbBwCir OBJECT-TYPE
   SYNTAX      Integer32
   MAX-ACCESS  read-write
   STATUS      current
   DESCRIPTION
      "Path: tunnels.editConf.greTunnels.inboundBandwidth.cir"
   ::= {er1645v2TTmplCGreEntry 117506048}

er1645v2TTmplCGreInbBwTc OBJECT-TYPE
   SYNTAX      INTEGER
               {
               auto (0)
               }
   MAX-ACCESS  read-write
   STATUS      current
   DESCRIPTION
      "Path: tunnels.editConf.greTunnels.inboundBandwidth.tc

       Possibilities:
               auto   (0)"
   ::= {er1645v2TTmplCGreEntry 117833728}

er1645v2TTmplCGreInbBwCorrType OBJECT-TYPE
   SYNTAX      INTEGER
               {
               noCorrection (0),
               predefined (1),
               manual (2)
               }
   MAX-ACCESS  read-write
   STATUS      current
   DESCRIPTION
      "Path: tunnels.editConf.greTunnels.inboundBandwidth.correction.type

       Possibilities:
               noCorrection   (0)
               predefined   (1)
               manual   (2)"
   ::= {er1645v2TTmplCGreEntry 117579776}

er1645v2TTmplCGreInbBwCorrPredefEncapsFrameRelay OBJECT-TYPE
   SYNTAX      DisplayString
   MAX-ACCESS  read-write
   STATUS      current
   DESCRIPTION
      "Path: tunnels.editConf.greTunnels.inboundBandwidth.correction.predefined.encapsulation.frameRelay"
   ::= {er1645v2TTmplCGreEntry 117589056}

er1645v2TTmplCGreInbBwCorrPredefEncapsPpp OBJECT-TYPE
   SYNTAX      DisplayString
   MAX-ACCESS  read-write
   STATUS      current
   DESCRIPTION
      "Path: tunnels.editConf.greTunnels.inboundBandwidth.correction.predefined.encapsulation.ppp"
   ::= {er1645v2TTmplCGreEntry 117589120}

er1645v2TTmplCGreInbBwCorrPredefEncapsAtmHl OBJECT-TYPE
   SYNTAX      INTEGER
               {
               rfc2684 (0),
               ppp (1),
               pppOverEthernet (2)
               }
   MAX-ACCESS  read-write
   STATUS      current
   DESCRIPTION
      "Path: tunnels.editConf.greTunnels.inboundBandwidth.correction.predefined.encapsulation.atm.higherLayer

       Possibilities:
               rfc2684   (0)
               ppp   (1)
               pppOverEthernet   (2)"
   ::= {er1645v2TTmplCGreEntry 117589192}

er1645v2TTmplCGreInbBwCorrPredefEncapsAtmMp OBJECT-TYPE
   SYNTAX      INTEGER
               {
               llcEncapsulation (0),
               vcMultiplexing (1)
               }
   MAX-ACCESS  read-write
   STATUS      current
   DESCRIPTION
      "Path: tunnels.editConf.greTunnels.inboundBandwidth.correction.predefined.encapsulation.atm.multiProtocol

       Possibilities:
               llcEncapsulation   (0)
               vcMultiplexing   (1)"
   ::= {er1645v2TTmplCGreEntry 117589200}

er1645v2TTmplCGreInbBwCorrPredefEncapsHdlc OBJECT-TYPE
   SYNTAX      DisplayString
   MAX-ACCESS  read-write
   STATUS      current
   DESCRIPTION
      "Path: tunnels.editConf.greTunnels.inboundBandwidth.correction.predefined.encapsulation.hdlc"
   ::= {er1645v2TTmplCGreEntry 117589248}

er1645v2TTmplCGreInbBwCorrPredefEncapsEfmFs OBJECT-TYPE
   SYNTAX      Integer32
   MAX-ACCESS  read-write
   STATUS      current
   DESCRIPTION
      "Path: tunnels.editConf.greTunnels.inboundBandwidth.correction.predefined.encapsulation.efm.fragmentSize"
   ::= {er1645v2TTmplCGreEntry 117589320}

er1645v2TTmplCGreInbBwCorrPredefEncapsEfmIb OBJECT-TYPE
   SYNTAX      Integer32
   MAX-ACCESS  read-write
   STATUS      current
   DESCRIPTION
      "Path: tunnels.editConf.greTunnels.inboundBandwidth.correction.predefined.encapsulation.efm.idleBytes"
   ::= {er1645v2TTmplCGreEntry 117589328}

er1645v2TTmplCGreInbBwCorrPredefMode OBJECT-TYPE
   SYNTAX      INTEGER
               {
               routing (0),
               bridging (1)
               }
   MAX-ACCESS  read-write
   STATUS      current
   DESCRIPTION
      "Path: tunnels.editConf.greTunnels.inboundBandwidth.correction.predefined.mode

       Possibilities:
               routing   (0)
               bridging   (1)"
   ::= {er1645v2TTmplCGreEntry 117590016}

er1645v2TTmplCGreInbBwCorrManualOverhead OBJECT-TYPE
   SYNTAX      Integer32
   MAX-ACCESS  read-write
   STATUS      current
   DESCRIPTION
      "Path: tunnels.editConf.greTunnels.inboundBandwidth.correction.manual.overhead"
   ::= {er1645v2TTmplCGreEntry 117596192}

er1645v2TTmplCGreInbBwCorrManualFrameData OBJECT-TYPE
   SYNTAX      Counter32
   MAX-ACCESS  read-write
   STATUS      current
   DESCRIPTION
      "Path: tunnels.editConf.greTunnels.inboundBandwidth.correction.manual.frameData

       32 bit unsigned wrappable counter."
   ::= {er1645v2TTmplCGreEntry 117596224}

er1645v2TTmplCGreInbBwCorrManualFrameHeader OBJECT-TYPE
   SYNTAX      Counter32
   MAX-ACCESS  read-write
   STATUS      current
   DESCRIPTION
      "Path: tunnels.editConf.greTunnels.inboundBandwidth.correction.manual.frameHeader

       32 bit unsigned wrappable counter."
   ::= {er1645v2TTmplCGreEntry 117596256}

er1645v2TTmplCGreInbBwMaxFifoQLen OBJECT-TYPE
   SYNTAX      Integer32
   MAX-ACCESS  read-write
   STATUS      current
   DESCRIPTION
      "Path: tunnels.editConf.greTunnels.inboundBandwidth.maxFifoQLen"
   ::= {er1645v2TTmplCGreEntry 117637120}

er1645v2TTmplCGreInbBwPriorityPolicy OBJECT-TYPE
   SYNTAX      DisplayString
   MAX-ACCESS  read-write
   STATUS      current
   DESCRIPTION
      "Path: tunnels.editConf.greTunnels.inboundBandwidth.priorityPolicy"
   ::= {er1645v2TTmplCGreEntry 117702656}

er1645v2TTmplCGreBandwidthMode OBJECT-TYPE
   SYNTAX      INTEGER
               {
               reshaping (1),
               policing (2),
               policingReshape (3)
               }
   MAX-ACCESS  read-write
   STATUS      current
   DESCRIPTION
      "Path: tunnels.editConf.greTunnels.bandwidth.mode

       Possibilities:
               reshaping   (1)
               policing   (2)
               policingReshape   (3)"
   ::= {er1645v2TTmplCGreEntry 148897792}

er1645v2TTmplCGreBandwidthCir OBJECT-TYPE
   SYNTAX      Integer32
   MAX-ACCESS  read-write
   STATUS      current
   DESCRIPTION
      "Path: tunnels.editConf.greTunnels.bandwidth.cir"
   ::= {er1645v2TTmplCGreEntry 135266304}

er1645v2TTmplCGreBandwidthEir OBJECT-TYPE
   SYNTAX      Integer32
   MAX-ACCESS  read-write
   STATUS      current
   DESCRIPTION
      "Path: tunnels.editConf.greTunnels.bandwidth.eir"
   ::= {er1645v2TTmplCGreEntry 141557760}

er1645v2TTmplCGreBandwidthUnit OBJECT-TYPE
   SYNTAX      INTEGER
               {
               bitssec (1),
               percent (2)
               }
   MAX-ACCESS  read-write
   STATUS      current
   DESCRIPTION
      "Path: tunnels.editConf.greTunnels.bandwidth.unit

       Possibilities:
               bits/sec   (1)
               percent   (2)"
   ::= {er1645v2TTmplCGreEntry 139460608}

er1645v2TTmplCGreBandwidthTc OBJECT-TYPE
   SYNTAX      INTEGER
               {
               auto (0)
               }
   MAX-ACCESS  read-write
   STATUS      current
   DESCRIPTION
      "Path: tunnels.editConf.greTunnels.bandwidth.tc

       Possibilities:
               auto   (0)"
   ::= {er1645v2TTmplCGreEntry 140509184}

er1645v2TTmplCGreBandwidthTcFactor OBJECT-TYPE
   SYNTAX      INTEGER
               {
               ms (10),
               s100us (1)
               }
   MAX-ACCESS  read-write
   STATUS      current
   DESCRIPTION
      "Path: tunnels.editConf.greTunnels.bandwidth.tcFactor

       Possibilities:
               ms   (10)
               *100us   (1)"
   ::= {er1645v2TTmplCGreEntry 142606336}

er1645v2TTmplCGreBandwidthCorrType OBJECT-TYPE
   SYNTAX      INTEGER
               {
               noCorrection (0),
               predefined (1),
               manual (2)
               }
   MAX-ACCESS  read-write
   STATUS      current
   DESCRIPTION
      "Path: tunnels.editConf.greTunnels.bandwidth.correction.type

       Possibilities:
               noCorrection   (0)
               predefined   (1)
               manual   (2)"
   ::= {er1645v2TTmplCGreEntry 136445952}

er1645v2TTmplCGreBandwidthCorrPredefEncapsFrameRelay OBJECT-TYPE
   SYNTAX      DisplayString
   MAX-ACCESS  read-write
   STATUS      current
   DESCRIPTION
      "Path: tunnels.editConf.greTunnels.bandwidth.correction.predefined.encapsulation.frameRelay"
   ::= {er1645v2TTmplCGreEntry 136594432}

er1645v2TTmplCGreBandwidthCorrPredefEncapsPpp OBJECT-TYPE
   SYNTAX      DisplayString
   MAX-ACCESS  read-write
   STATUS      current
   DESCRIPTION
      "Path: tunnels.editConf.greTunnels.bandwidth.correction.predefined.encapsulation.ppp"
   ::= {er1645v2TTmplCGreEntry 136595456}

er1645v2TTmplCGreBandwidthCorrPredefEncapsAtmHl OBJECT-TYPE
   SYNTAX      INTEGER
               {
               rfc2684 (0),
               ppp (1),
               pppOverEthernet (2)
               }
   MAX-ACCESS  read-write
   STATUS      current
   DESCRIPTION
      "Path: tunnels.editConf.greTunnels.bandwidth.correction.predefined.encapsulation.atm.higherLayer

       Possibilities:
               rfc2684   (0)
               ppp   (1)
               pppOverEthernet   (2)"
   ::= {er1645v2TTmplCGreEntry 136596608}

er1645v2TTmplCGreBandwidthCorrPredefEncapsAtmMp OBJECT-TYPE
   SYNTAX      INTEGER
               {
               llcEncapsulation (0),
               vcMultiplexing (1)
               }
   MAX-ACCESS  read-write
   STATUS      current
   DESCRIPTION
      "Path: tunnels.editConf.greTunnels.bandwidth.correction.predefined.encapsulation.atm.multiProtocol

       Possibilities:
               llcEncapsulation   (0)
               vcMultiplexing   (1)"
   ::= {er1645v2TTmplCGreEntry 136596736}

er1645v2TTmplCGreBandwidthCorrPredefEncapsHdlc OBJECT-TYPE
   SYNTAX      DisplayString
   MAX-ACCESS  read-write
   STATUS      current
   DESCRIPTION
      "Path: tunnels.editConf.greTunnels.bandwidth.correction.predefined.encapsulation.hdlc"
   ::= {er1645v2TTmplCGreEntry 136597504}

er1645v2TTmplCGreBandwidthCorrPredefEncapsEfmFs OBJECT-TYPE
   SYNTAX      Integer32
   MAX-ACCESS  read-write
   STATUS      current
   DESCRIPTION
      "Path: tunnels.editConf.greTunnels.bandwidth.correction.predefined.encapsulation.efm.fragmentSize"
   ::= {er1645v2TTmplCGreEntry 136598656}

er1645v2TTmplCGreBandwidthCorrPredefEncapsEfmIb OBJECT-TYPE
   SYNTAX      Integer32
   MAX-ACCESS  read-write
   STATUS      current
   DESCRIPTION
      "Path: tunnels.editConf.greTunnels.bandwidth.correction.predefined.encapsulation.efm.idleBytes"
   ::= {er1645v2TTmplCGreEntry 136598784}

er1645v2TTmplCGreBandwidthCorrPredefMode OBJECT-TYPE
   SYNTAX      INTEGER
               {
               routing (0),
               bridging (1)
               }
   MAX-ACCESS  read-write
   STATUS      current
   DESCRIPTION
      "Path: tunnels.editConf.greTunnels.bandwidth.correction.predefined.mode

       Possibilities:
               routing   (0)
               bridging   (1)"
   ::= {er1645v2TTmplCGreEntry 136609792}

er1645v2TTmplCGreBandwidthCorrManualOverhead OBJECT-TYPE
   SYNTAX      Integer32
   MAX-ACCESS  read-write
   STATUS      current
   DESCRIPTION
      "Path: tunnels.editConf.greTunnels.bandwidth.correction.manual.overhead"
   ::= {er1645v2TTmplCGreEntry 136708608}

er1645v2TTmplCGreBandwidthCorrManualFrameData OBJECT-TYPE
   SYNTAX      Counter32
   MAX-ACCESS  read-write
   STATUS      current
   DESCRIPTION
      "Path: tunnels.editConf.greTunnels.bandwidth.correction.manual.frameData

       32 bit unsigned wrappable counter."
   ::= {er1645v2TTmplCGreEntry 136709120}

er1645v2TTmplCGreBandwidthCorrManualFrameHeader OBJECT-TYPE
   SYNTAX      Counter32
   MAX-ACCESS  read-write
   STATUS      current
   DESCRIPTION
      "Path: tunnels.editConf.greTunnels.bandwidth.correction.manual.frameHeader

       32 bit unsigned wrappable counter."
   ::= {er1645v2TTmplCGreEntry 136709632}

er1645v2TTmplCGreBandwidthMaxFifoQLen OBJECT-TYPE
   SYNTAX      Integer32
   MAX-ACCESS  read-write
   STATUS      current
   DESCRIPTION
      "Path: tunnels.editConf.greTunnels.bandwidth.maxFifoQLen"
   ::= {er1645v2TTmplCGreEntry 137363456}

er1645v2TTmplCGreBandwidthDeFlagCir OBJECT-TYPE
   SYNTAX      INTEGER
               {
               allowed (1),
               notAllowed (2)
               }
   MAX-ACCESS  read-write
   STATUS      current
   DESCRIPTION
      "Path: tunnels.editConf.greTunnels.bandwidth.deFlag.cir

       Possibilities:
               allowed   (1)
               notAllowed   (2)"
   ::= {er1645v2TTmplCGreEntry 147853312}

er1645v2TTmplCGreBandwidthDeFlagEir OBJECT-TYPE
   SYNTAX      INTEGER
               {
               allowed (1),
               notAllowed (2)
               }
   MAX-ACCESS  read-write
   STATUS      current
   DESCRIPTION
      "Path: tunnels.editConf.greTunnels.bandwidth.deFlag.eir

       Possibilities:
               allowed   (1)
               notAllowed   (2)"
   ::= {er1645v2TTmplCGreEntry 147857408}

er1645v2TTmplCGreBandwidthDeFlagViolate OBJECT-TYPE
   SYNTAX      INTEGER
               {
               allowed (1),
               notAllowed (2)
               }
   MAX-ACCESS  read-write
   STATUS      current
   DESCRIPTION
      "Path: tunnels.editConf.greTunnels.bandwidth.deFlag.violate

       Possibilities:
               allowed   (1)
               notAllowed   (2)"
   ::= {er1645v2TTmplCGreEntry 147861504}

er1645v2TTmplCGreBandwidthActCirActNone OBJECT-TYPE
   SYNTAX      OCTET STRING
   MAX-ACCESS  read-write
   STATUS      current
   DESCRIPTION
      "Path: tunnels.editConf.greTunnels.bandwidth.action.cirAction.none"
   ::= {er1645v2TTmplCGreEntry 150085632}

er1645v2TTmplCGreBandwidthActCirActEthCos1 OBJECT-TYPE
   SYNTAX      INTEGER
               {
               unchanged (256)
               }
   MAX-ACCESS  read-write
   STATUS      current
   DESCRIPTION
      "Path: tunnels.editConf.greTunnels.bandwidth.action.cirAction.ethernet.cosDepth1

       Possibilities:
               unchanged   (256)"
   ::= {er1645v2TTmplCGreEntry 150094080}

er1645v2TTmplCGreBandwidthActCirActEthDei1 OBJECT-TYPE
   SYNTAX      INTEGER
               {
               unchanged (255),
               clear (0),
               set (1)
               }
   MAX-ACCESS  read-write
   STATUS      current
   DESCRIPTION
      "Path: tunnels.editConf.greTunnels.bandwidth.action.cirAction.ethernet.deiDepth1

       Possibilities:
               unchanged   (255)
               clear   (0)
               set   (1)"
   ::= {er1645v2TTmplCGreEntry 150099200}

er1645v2TTmplCGreBandwidthActCirActEthCos2 OBJECT-TYPE
   SYNTAX      INTEGER
               {
               unchanged (256)
               }
   MAX-ACCESS  read-write
   STATUS      current
   DESCRIPTION
      "Path: tunnels.editConf.greTunnels.bandwidth.action.cirAction.ethernet.cosDepth2

       Possibilities:
               unchanged   (256)"
   ::= {er1645v2TTmplCGreEntry 150094336}

er1645v2TTmplCGreBandwidthActCirActEthDei2 OBJECT-TYPE
   SYNTAX      INTEGER
               {
               unchanged (255),
               clear (0),
               set (1)
               }
   MAX-ACCESS  read-write
   STATUS      current
   DESCRIPTION
      "Path: tunnels.editConf.greTunnels.bandwidth.action.cirAction.ethernet.deiDepth2

       Possibilities:
               unchanged   (255)
               clear   (0)
               set   (1)"
   ::= {er1645v2TTmplCGreEntry 150099456}

er1645v2TTmplCGreBandwidthActCirActEthCos3 OBJECT-TYPE
   SYNTAX      INTEGER
               {
               unchanged (256)
               }
   MAX-ACCESS  read-write
   STATUS      current
   DESCRIPTION
      "Path: tunnels.editConf.greTunnels.bandwidth.action.cirAction.ethernet.cosDepth3

       Possibilities:
               unchanged   (256)"
   ::= {er1645v2TTmplCGreEntry 150094592}

er1645v2TTmplCGreBandwidthActCirActEthDei3 OBJECT-TYPE
   SYNTAX      INTEGER
               {
               unchanged (255),
               clear (0),
               set (1)
               }
   MAX-ACCESS  read-write
   STATUS      current
   DESCRIPTION
      "Path: tunnels.editConf.greTunnels.bandwidth.action.cirAction.ethernet.deiDepth3

       Possibilities:
               unchanged   (255)
               clear   (0)
               set   (1)"
   ::= {er1645v2TTmplCGreEntry 150099712}

er1645v2TTmplCGreBandwidthActCirActEthCos4 OBJECT-TYPE
   SYNTAX      INTEGER
               {
               unchanged (256)
               }
   MAX-ACCESS  read-write
   STATUS      current
   DESCRIPTION
      "Path: tunnels.editConf.greTunnels.bandwidth.action.cirAction.ethernet.cosDepth4

       Possibilities:
               unchanged   (256)"
   ::= {er1645v2TTmplCGreEntry 150094848}

er1645v2TTmplCGreBandwidthActCirActEthDei4 OBJECT-TYPE
   SYNTAX      INTEGER
               {
               unchanged (255),
               clear (0),
               set (1)
               }
   MAX-ACCESS  read-write
   STATUS      current
   DESCRIPTION
      "Path: tunnels.editConf.greTunnels.bandwidth.action.cirAction.ethernet.deiDepth4

       Possibilities:
               unchanged   (255)
               clear   (0)
               set   (1)"
   ::= {er1645v2TTmplCGreEntry 150099968}

er1645v2TTmplCGreBandwidthActCirActEthCos5 OBJECT-TYPE
   SYNTAX      INTEGER
               {
               unchanged (256)
               }
   MAX-ACCESS  read-write
   STATUS      current
   DESCRIPTION
      "Path: tunnels.editConf.greTunnels.bandwidth.action.cirAction.ethernet.cosDepth5

       Possibilities:
               unchanged   (256)"
   ::= {er1645v2TTmplCGreEntry 150095104}

er1645v2TTmplCGreBandwidthActCirActEthDei5 OBJECT-TYPE
   SYNTAX      INTEGER
               {
               unchanged (255),
               clear (0),
               set (1)
               }
   MAX-ACCESS  read-write
   STATUS      current
   DESCRIPTION
      "Path: tunnels.editConf.greTunnels.bandwidth.action.cirAction.ethernet.deiDepth5

       Possibilities:
               unchanged   (255)
               clear   (0)
               set   (1)"
   ::= {er1645v2TTmplCGreEntry 150100224}

er1645v2TTmplCGreBandwidthActCirActEthCos6 OBJECT-TYPE
   SYNTAX      INTEGER
               {
               unchanged (256)
               }
   MAX-ACCESS  read-write
   STATUS      current
   DESCRIPTION
      "Path: tunnels.editConf.greTunnels.bandwidth.action.cirAction.ethernet.cosDepth6

       Possibilities:
               unchanged   (256)"
   ::= {er1645v2TTmplCGreEntry 150095360}

er1645v2TTmplCGreBandwidthActCirActEthDei6 OBJECT-TYPE
   SYNTAX      INTEGER
               {
               unchanged (255),
               clear (0),
               set (1)
               }
   MAX-ACCESS  read-write
   STATUS      current
   DESCRIPTION
      "Path: tunnels.editConf.greTunnels.bandwidth.action.cirAction.ethernet.deiDepth6

       Possibilities:
               unchanged   (255)
               clear   (0)
               set   (1)"
   ::= {er1645v2TTmplCGreEntry 150100480}

er1645v2TTmplCGreBandwidthActCirActEthCos7 OBJECT-TYPE
   SYNTAX      INTEGER
               {
               unchanged (256)
               }
   MAX-ACCESS  read-write
   STATUS      current
   DESCRIPTION
      "Path: tunnels.editConf.greTunnels.bandwidth.action.cirAction.ethernet.cosDepth7

       Possibilities:
               unchanged   (256)"
   ::= {er1645v2TTmplCGreEntry 150095616}

er1645v2TTmplCGreBandwidthActCirActEthDei7 OBJECT-TYPE
   SYNTAX      INTEGER
               {
               unchanged (255),
               clear (0),
               set (1)
               }
   MAX-ACCESS  read-write
   STATUS      current
   DESCRIPTION
      "Path: tunnels.editConf.greTunnels.bandwidth.action.cirAction.ethernet.deiDepth7

       Possibilities:
               unchanged   (255)
               clear   (0)
               set   (1)"
   ::= {er1645v2TTmplCGreEntry 150100736}

er1645v2TTmplCGreBandwidthActCirActEthCos8 OBJECT-TYPE
   SYNTAX      INTEGER
               {
               unchanged (256)
               }
   MAX-ACCESS  read-write
   STATUS      current
   DESCRIPTION
      "Path: tunnels.editConf.greTunnels.bandwidth.action.cirAction.ethernet.cosDepth8

       Possibilities:
               unchanged   (256)"
   ::= {er1645v2TTmplCGreEntry 150095872}

er1645v2TTmplCGreBandwidthActCirActEthDei8 OBJECT-TYPE
   SYNTAX      INTEGER
               {
               unchanged (255),
               clear (0),
               set (1)
               }
   MAX-ACCESS  read-write
   STATUS      current
   DESCRIPTION
      "Path: tunnels.editConf.greTunnels.bandwidth.action.cirAction.ethernet.deiDepth8

       Possibilities:
               unchanged   (255)
               clear   (0)
               set   (1)"
   ::= {er1645v2TTmplCGreEntry 150100992}

er1645v2TTmplCGreBandwidthActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.greTunnels.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TTmplCGreEntry 150096128}

er1645v2TTmplCGreBandwidthActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.greTunnels.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2TTmplCGreEntry 150096384}

er1645v2TTmplCGreBandwidthActCirActEthDrpLev OBJECT-TYPE
   SYNTAX      INTEGER
               {
               unchanged (0)
               }
   MAX-ACCESS  read-write
   STATUS      current
   DESCRIPTION
      "Path: tunnels.editConf.greTunnels.bandwidth.action.cirAction.ethernet.dropLevel

       Possibilities:
               unchanged   (0)"
   ::= {er1645v2TTmplCGreEntry 150096640}

er1645v2TTmplCGreBandwidthActCirActEthDeFlag OBJECT-TYPE
   SYNTAX      INTEGER
               {
               unchanged (255),
               clear (0),
               set (1)
               }
   MAX-ACCESS  read-write
   STATUS      current
   DESCRIPTION
      "Path: tunnels.editConf.greTunnels.bandwidth.action.cirAction.ethernet.deFlag

       Possibilities:
               unchanged   (255)
               clear   (0)
               set   (1)"
   ::= {er1645v2TTmplCGreEntry 150097408}

er1645v2TTmplCGreBandwidthActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.greTunnels.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TTmplCGreEntry 150120704}

er1645v2TTmplCGreBandwidthActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.greTunnels.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2TTmplCGreEntry 150120960}

er1645v2TTmplCGreBandwidthActCirActIpDrpLev OBJECT-TYPE
   SYNTAX      INTEGER
               {
               unchanged (0)
               }
   MAX-ACCESS  read-write
   STATUS      current
   DESCRIPTION
      "Path: tunnels.editConf.greTunnels.bandwidth.action.cirAction.ip.dropLevel

       Possibilities:
               unchanged   (0)"
   ::= {er1645v2TTmplCGreEntry 150121216}

er1645v2TTmplCGreBandwidthActCirActIpDeFlag OBJECT-TYPE
   SYNTAX      INTEGER
               {
               unchanged (255),
               clear (0),
               set (1)
               }
   MAX-ACCESS  read-write
   STATUS      current
   DESCRIPTION
      "Path: tunnels.editConf.greTunnels.bandwidth.action.cirAction.ip.deFlag

       Possibilities:
               unchanged   (255)
               clear   (0)
               set   (1)"
   ::= {er1645v2TTmplCGreEntry 150121984}

er1645v2TTmplCGreBandwidthActEirActNone OBJECT-TYPE
   SYNTAX      OCTET STRING
   MAX-ACCESS  read-write
   STATUS      current
   DESCRIPTION
      "Path: tunnels.editConf.greTunnels.bandwidth.action.eirAction.none"
   ::= {er1645v2TTmplCGreEntry 150216704}

er1645v2TTmplCGreBandwidthActEirActEthCos1 OBJECT-TYPE
   SYNTAX      INTEGER
               {
               unchanged (256)
               }
   MAX-ACCESS  read-write
   STATUS      current
   DESCRIPTION
      "Path: tunnels.editConf.greTunnels.bandwidth.action.eirAction.ethernet.cosDepth1

       Possibilities:
               unchanged   (256)"
   ::= {er1645v2TTmplCGreEntry 150225152}

er1645v2TTmplCGreBandwidthActEirActEthDei1 OBJECT-TYPE
   SYNTAX      INTEGER
               {
               unchanged (255),
               clear (0),
               set (1)
               }
   MAX-ACCESS  read-write
   STATUS      current
   DESCRIPTION
      "Path: tunnels.editConf.greTunnels.bandwidth.action.eirAction.ethernet.deiDepth1

       Possibilities:
               unchanged   (255)
               clear   (0)
               set   (1)"
   ::= {er1645v2TTmplCGreEntry 150230272}

er1645v2TTmplCGreBandwidthActEirActEthCos2 OBJECT-TYPE
   SYNTAX      INTEGER
               {
               unchanged (256)
               }
   MAX-ACCESS  read-write
   STATUS      current
   DESCRIPTION
      "Path: tunnels.editConf.greTunnels.bandwidth.action.eirAction.ethernet.cosDepth2

       Possibilities:
               unchanged   (256)"
   ::= {er1645v2TTmplCGreEntry 150225408}

er1645v2TTmplCGreBandwidthActEirActEthDei2 OBJECT-TYPE
   SYNTAX      INTEGER
               {
               unchanged (255),
               clear (0),
               set (1)
               }
   MAX-ACCESS  read-write
   STATUS      current
   DESCRIPTION
      "Path: tunnels.editConf.greTunnels.bandwidth.action.eirAction.ethernet.deiDepth2

       Possibilities:
               unchanged   (255)
               clear   (0)
               set   (1)"
   ::= {er1645v2TTmplCGreEntry 150230528}

er1645v2TTmplCGreBandwidthActEirActEthCos3 OBJECT-TYPE
   SYNTAX      INTEGER
               {
               unchanged (256)
               }
   MAX-ACCESS  read-write
   STATUS      current
   DESCRIPTION
      "Path: tunnels.editConf.greTunnels.bandwidth.action.eirAction.ethernet.cosDepth3

       Possibilities:
               unchanged   (256)"
   ::= {er1645v2TTmplCGreEntry 150225664}

er1645v2TTmplCGreBandwidthActEirActEthDei3 OBJECT-TYPE
   SYNTAX      INTEGER
               {
               unchanged (255),
               clear (0),
               set (1)
               }
   MAX-ACCESS  read-write
   STATUS      current
   DESCRIPTION
      "Path: tunnels.editConf.greTunnels.bandwidth.action.eirAction.ethernet.deiDepth3

       Possibilities:
               unchanged   (255)
               clear   (0)
               set   (1)"
   ::= {er1645v2TTmplCGreEntry 150230784}

er1645v2TTmplCGreBandwidthActEirActEthCos4 OBJECT-TYPE
   SYNTAX      INTEGER
               {
               unchanged (256)
               }
   MAX-ACCESS  read-write
   STATUS      current
   DESCRIPTION
      "Path: tunnels.editConf.greTunnels.bandwidth.action.eirAction.ethernet.cosDepth4

       Possibilities:
               unchanged   (256)"
   ::= {er1645v2TTmplCGreEntry 150225920}

er1645v2TTmplCGreBandwidthActEirActEthDei4 OBJECT-TYPE
   SYNTAX      INTEGER
               {
               unchanged (255),
               clear (0),
               set (1)
               }
   MAX-ACCESS  read-write
   STATUS      current
   DESCRIPTION
      "Path: tunnels.editConf.greTunnels.bandwidth.action.eirAction.ethernet.deiDepth4

       Possibilities:
               unchanged   (255)
               clear   (0)
               set   (1)"
   ::= {er1645v2TTmplCGreEntry 150231040}

er1645v2TTmplCGreBandwidthActEirActEthCos5 OBJECT-TYPE
   SYNTAX      INTEGER
               {
               unchanged (256)
               }
   MAX-ACCESS  read-write
   STATUS      current
   DESCRIPTION
      "Path: tunnels.editConf.greTunnels.bandwidth.action.eirAction.ethernet.cosDepth5

       Possibilities:
               unchanged   (256)"
   ::= {er1645v2TTmplCGreEntry 150226176}

er1645v2TTmplCGreBandwidthActEirActEthDei5 OBJECT-TYPE
   SYNTAX      INTEGER
               {
               unchanged (255),
               clear (0),
               set (1)
               }
   MAX-ACCESS  read-write
   STATUS      current
   DESCRIPTION
      "Path: tunnels.editConf.greTunnels.bandwidth.action.eirAction.ethernet.deiDepth5

       Possibilities:
               unchanged   (255)
               clear   (0)
               set   (1)"
   ::= {er1645v2TTmplCGreEntry 150231296}

er1645v2TTmplCGreBandwidthActEirActEthCos6 OBJECT-TYPE
   SYNTAX      INTEGER
               {
               unchanged (256)
               }
   MAX-ACCESS  read-write
   STATUS      current
   DESCRIPTION
      "Path: tunnels.editConf.greTunnels.bandwidth.action.eirAction.ethernet.cosDepth6

       Possibilities:
               unchanged   (256)"
   ::= {er1645v2TTmplCGreEntry 150226432}

er1645v2TTmplCGreBandwidthActEirActEthDei6 OBJECT-TYPE
   SYNTAX      INTEGER
               {
               unchanged (255),
               clear (0),
               set (1)
               }
   MAX-ACCESS  read-write
   STATUS      current
   DESCRIPTION
      "Path: tunnels.editConf.greTunnels.bandwidth.action.eirAction.ethernet.deiDepth6

       Possibilities:
               unchanged   (255)
               clear   (0)
               set   (1)"
   ::= {er1645v2TTmplCGreEntry 150231552}

er1645v2TTmplCGreBandwidthActEirActEthCos7 OBJECT-TYPE
   SYNTAX      INTEGER
               {
               unchanged (256)
               }
   MAX-ACCESS  read-write
   STATUS      current
   DESCRIPTION
      "Path: tunnels.editConf.greTunnels.bandwidth.action.eirAction.ethernet.cosDepth7

       Possibilities:
               unchanged   (256)"
   ::= {er1645v2TTmplCGreEntry 150226688}

er1645v2TTmplCGreBandwidthActEirActEthDei7 OBJECT-TYPE
   SYNTAX      INTEGER
               {
               unchanged (255),
               clear (0),
               set (1)
               }
   MAX-ACCESS  read-write
   STATUS      current
   DESCRIPTION
      "Path: tunnels.editConf.greTunnels.bandwidth.action.eirAction.ethernet.deiDepth7

       Possibilities:
               unchanged   (255)
               clear   (0)
               set   (1)"
   ::= {er1645v2TTmplCGreEntry 150231808}

er1645v2TTmplCGreBandwidthActEirActEthCos8 OBJECT-TYPE
   SYNTAX      INTEGER
               {
               unchanged (256)
               }
   MAX-ACCESS  read-write
   STATUS      current
   DESCRIPTION
      "Path: tunnels.editConf.greTunnels.bandwidth.action.eirAction.ethernet.cosDepth8

       Possibilities:
               unchanged   (256)"
   ::= {er1645v2TTmplCGreEntry 150226944}

er1645v2TTmplCGreBandwidthActEirActEthDei8 OBJECT-TYPE
   SYNTAX      INTEGER
               {
               unchanged (255),
               clear (0),
               set (1)
               }
   MAX-ACCESS  read-write
   STATUS      current
   DESCRIPTION
      "Path: tunnels.editConf.greTunnels.bandwidth.action.eirAction.ethernet.deiDepth8

       Possibilities:
               unchanged   (255)
               clear   (0)
               set   (1)"
   ::= {er1645v2TTmplCGreEntry 150232064}

er1645v2TTmplCGreBandwidthActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.greTunnels.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TTmplCGreEntry 150227200}

er1645v2TTmplCGreBandwidthActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.greTunnels.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2TTmplCGreEntry 150227456}

er1645v2TTmplCGreBandwidthActEirActEthDrpLev OBJECT-TYPE
   SYNTAX      INTEGER
               {
               unchanged (0)
               }
   MAX-ACCESS  read-write
   STATUS      current
   DESCRIPTION
      "Path: tunnels.editConf.greTunnels.bandwidth.action.eirAction.ethernet.dropLevel

       Possibilities:
               unchanged   (0)"
   ::= {er1645v2TTmplCGreEntry 150227712}

er1645v2TTmplCGreBandwidthActEirActEthDeFlag OBJECT-TYPE
   SYNTAX      INTEGER
               {
               unchanged (255),
               clear (0),
               set (1)
               }
   MAX-ACCESS  read-write
   STATUS      current
   DESCRIPTION
      "Path: tunnels.editConf.greTunnels.bandwidth.action.eirAction.ethernet.deFlag

       Possibilities:
               unchanged   (255)
               clear   (0)
               set   (1)"
   ::= {er1645v2TTmplCGreEntry 150228480}

er1645v2TTmplCGreBandwidthActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.greTunnels.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TTmplCGreEntry 150251776}

er1645v2TTmplCGreBandwidthActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.greTunnels.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2TTmplCGreEntry 150252032}

er1645v2TTmplCGreBandwidthActEirActIpDrpLev OBJECT-TYPE
   SYNTAX      INTEGER
               {
               unchanged (0)
               }
   MAX-ACCESS  read-write
   STATUS      current
   DESCRIPTION
      "Path: tunnels.editConf.greTunnels.bandwidth.action.eirAction.ip.dropLevel

       Possibilities:
               unchanged   (0)"
   ::= {er1645v2TTmplCGreEntry 150252288}

er1645v2TTmplCGreBandwidthActEirActIpDeFlag OBJECT-TYPE
   SYNTAX      INTEGER
               {
               unchanged (255),
               clear (0),
               set (1)
               }
   MAX-ACCESS  read-write
   STATUS      current
   DESCRIPTION
      "Path: tunnels.editConf.greTunnels.bandwidth.action.eirAction.ip.deFlag

       Possibilities:
               unchanged   (255)
               clear   (0)
               set   (1)"
   ::= {er1645v2TTmplCGreEntry 150253056}

er1645v2TTmplCGreBandwidthActViolActNone OBJECT-TYPE
   SYNTAX      OCTET STRING
   MAX-ACCESS  read-write
   STATUS      current
   DESCRIPTION
      "Path: tunnels.editConf.greTunnels.bandwidth.action.violateAction.none"
   ::= {er1645v2TTmplCGreEntry 150347776}

er1645v2TTmplCGreBandwidthActViolActDrop OBJECT-TYPE
   SYNTAX      OCTET STRING
   MAX-ACCESS  read-write
   STATUS      current
   DESCRIPTION
      "Path: tunnels.editConf.greTunnels.bandwidth.action.violateAction.drop"
   ::= {er1645v2TTmplCGreEntry 150364160}

er1645v2TTmplCGreBandwidthActViolActEthCos1 OBJECT-TYPE
   SYNTAX      INTEGER
               {
               unchanged (256)
               }
   MAX-ACCESS  read-write
   STATUS      current
   DESCRIPTION
      "Path: tunnels.editConf.greTunnels.bandwidth.action.violateAction.ethernet.cosDepth1

       Possibilities:
               unchanged   (256)"
   ::= {er1645v2TTmplCGreEntry 150356224}

er1645v2TTmplCGreBandwidthActViolActEthDei1 OBJECT-TYPE
   SYNTAX      INTEGER
               {
               unchanged (255),
               clear (0),
               set (1)
               }
   MAX-ACCESS  read-write
   STATUS      current
   DESCRIPTION
      "Path: tunnels.editConf.greTunnels.bandwidth.action.violateAction.ethernet.deiDepth1

       Possibilities:
               unchanged   (255)
               clear   (0)
               set   (1)"
   ::= {er1645v2TTmplCGreEntry 150361344}

er1645v2TTmplCGreBandwidthActViolActEthCos2 OBJECT-TYPE
   SYNTAX      INTEGER
               {
               unchanged (256)
               }
   MAX-ACCESS  read-write
   STATUS      current
   DESCRIPTION
      "Path: tunnels.editConf.greTunnels.bandwidth.action.violateAction.ethernet.cosDepth2

       Possibilities:
               unchanged   (256)"
   ::= {er1645v2TTmplCGreEntry 150356480}

er1645v2TTmplCGreBandwidthActViolActEthDei2 OBJECT-TYPE
   SYNTAX      INTEGER
               {
               unchanged (255),
               clear (0),
               set (1)
               }
   MAX-ACCESS  read-write
   STATUS      current
   DESCRIPTION
      "Path: tunnels.editConf.greTunnels.bandwidth.action.violateAction.ethernet.deiDepth2

       Possibilities:
               unchanged   (255)
               clear   (0)
               set   (1)"
   ::= {er1645v2TTmplCGreEntry 150361600}

er1645v2TTmplCGreBandwidthActViolActEthCos3 OBJECT-TYPE
   SYNTAX      INTEGER
               {
               unchanged (256)
               }
   MAX-ACCESS  read-write
   STATUS      current
   DESCRIPTION
      "Path: tunnels.editConf.greTunnels.bandwidth.action.violateAction.ethernet.cosDepth3

       Possibilities:
               unchanged   (256)"
   ::= {er1645v2TTmplCGreEntry 150356736}

er1645v2TTmplCGreBandwidthActViolActEthDei3 OBJECT-TYPE
   SYNTAX      INTEGER
               {
               unchanged (255),
               clear (0),
               set (1)
               }
   MAX-ACCESS  read-write
   STATUS      current
   DESCRIPTION
      "Path: tunnels.editConf.greTunnels.bandwidth.action.violateAction.ethernet.deiDepth3

       Possibilities:
               unchanged   (255)
               clear   (0)
               set   (1)"
   ::= {er1645v2TTmplCGreEntry 150361856}

er1645v2TTmplCGreBandwidthActViolActEthCos4 OBJECT-TYPE
   SYNTAX      INTEGER
               {
               unchanged (256)
               }
   MAX-ACCESS  read-write
   STATUS      current
   DESCRIPTION
      "Path: tunnels.editConf.greTunnels.bandwidth.action.violateAction.ethernet.cosDepth4

       Possibilities:
               unchanged   (256)"
   ::= {er1645v2TTmplCGreEntry 150356992}

er1645v2TTmplCGreBandwidthActViolActEthDei4 OBJECT-TYPE
   SYNTAX      INTEGER
               {
               unchanged (255),
               clear (0),
               set (1)
               }
   MAX-ACCESS  read-write
   STATUS      current
   DESCRIPTION
      "Path: tunnels.editConf.greTunnels.bandwidth.action.violateAction.ethernet.deiDepth4

       Possibilities:
               unchanged   (255)
               clear   (0)
               set   (1)"
   ::= {er1645v2TTmplCGreEntry 150362112}

er1645v2TTmplCGreBandwidthActViolActEthCos5 OBJECT-TYPE
   SYNTAX      INTEGER
               {
               unchanged (256)
               }
   MAX-ACCESS  read-write
   STATUS      current
   DESCRIPTION
      "Path: tunnels.editConf.greTunnels.bandwidth.action.violateAction.ethernet.cosDepth5

       Possibilities:
               unchanged   (256)"
   ::= {er1645v2TTmplCGreEntry 150357248}

er1645v2TTmplCGreBandwidthActViolActEthDei5 OBJECT-TYPE
   SYNTAX      INTEGER
               {
               unchanged (255),
               clear (0),
               set (1)
               }
   MAX-ACCESS  read-write
   STATUS      current
   DESCRIPTION
      "Path: tunnels.editConf.greTunnels.bandwidth.action.violateAction.ethernet.deiDepth5

       Possibilities:
               unchanged   (255)
               clear   (0)
               set   (1)"
   ::= {er1645v2TTmplCGreEntry 150362368}

er1645v2TTmplCGreBandwidthActViolActEthCos6 OBJECT-TYPE
   SYNTAX      INTEGER
               {
               unchanged (256)
               }
   MAX-ACCESS  read-write
   STATUS      current
   DESCRIPTION
      "Path: tunnels.editConf.greTunnels.bandwidth.action.violateAction.ethernet.cosDepth6

       Possibilities:
               unchanged   (256)"
   ::= {er1645v2TTmplCGreEntry 150357504}

er1645v2TTmplCGreBandwidthActViolActEthDei6 OBJECT-TYPE
   SYNTAX      INTEGER
               {
               unchanged (255),
               clear (0),
               set (1)
               }
   MAX-ACCESS  read-write
   STATUS      current
   DESCRIPTION
      "Path: tunnels.editConf.greTunnels.bandwidth.action.violateAction.ethernet.deiDepth6

       Possibilities:
               unchanged   (255)
               clear   (0)
               set   (1)"
   ::= {er1645v2TTmplCGreEntry 150362624}

er1645v2TTmplCGreBandwidthActViolActEthCos7 OBJECT-TYPE
   SYNTAX      INTEGER
               {
               unchanged (256)
               }
   MAX-ACCESS  read-write
   STATUS      current
   DESCRIPTION
      "Path: tunnels.editConf.greTunnels.bandwidth.action.violateAction.ethernet.cosDepth7

       Possibilities:
               unchanged   (256)"
   ::= {er1645v2TTmplCGreEntry 150357760}

er1645v2TTmplCGreBandwidthActViolActEthDei7 OBJECT-TYPE
   SYNTAX      INTEGER
               {
               unchanged (255),
               clear (0),
               set (1)
               }
   MAX-ACCESS  read-write
   STATUS      current
   DESCRIPTION
      "Path: tunnels.editConf.greTunnels.bandwidth.action.violateAction.ethernet.deiDepth7

       Possibilities:
               unchanged   (255)
               clear   (0)
               set   (1)"
   ::= {er1645v2TTmplCGreEntry 150362880}

er1645v2TTmplCGreBandwidthActViolActEthCos8 OBJECT-TYPE
   SYNTAX      INTEGER
               {
               unchanged (256)
               }
   MAX-ACCESS  read-write
   STATUS      current
   DESCRIPTION
      "Path: tunnels.editConf.greTunnels.bandwidth.action.violateAction.ethernet.cosDepth8

       Possibilities:
               unchanged   (256)"
   ::= {er1645v2TTmplCGreEntry 150358016}

er1645v2TTmplCGreBandwidthActViolActEthDei8 OBJECT-TYPE
   SYNTAX      INTEGER
               {
               unchanged (255),
               clear (0),
               set (1)
               }
   MAX-ACCESS  read-write
   STATUS      current
   DESCRIPTION
      "Path: tunnels.editConf.greTunnels.bandwidth.action.violateAction.ethernet.deiDepth8

       Possibilities:
               unchanged   (255)
               clear   (0)
               set   (1)"
   ::= {er1645v2TTmplCGreEntry 150363136}

er1645v2TTmplCGreBandwidthActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.greTunnels.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TTmplCGreEntry 150358272}

er1645v2TTmplCGreBandwidthActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.greTunnels.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2TTmplCGreEntry 150358528}

er1645v2TTmplCGreBandwidthActViolActEthDrpLev OBJECT-TYPE
   SYNTAX      INTEGER
               {
               unchanged (0)
               }
   MAX-ACCESS  read-write
   STATUS      current
   DESCRIPTION
      "Path: tunnels.editConf.greTunnels.bandwidth.action.violateAction.ethernet.dropLevel

       Possibilities:
               unchanged   (0)"
   ::= {er1645v2TTmplCGreEntry 150358784}

er1645v2TTmplCGreBandwidthActViolActEthDeFlag OBJECT-TYPE
   SYNTAX      INTEGER
               {
               unchanged (255),
               clear (0),
               set (1)
               }
   MAX-ACCESS  read-write
   STATUS      current
   DESCRIPTION
      "Path: tunnels.editConf.greTunnels.bandwidth.action.violateAction.ethernet.deFlag

       Possibilities:
               unchanged   (255)
               clear   (0)
               set   (1)"
   ::= {er1645v2TTmplCGreEntry 150359552}

er1645v2TTmplCGreBandwidthActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.greTunnels.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TTmplCGreEntry 150382848}

er1645v2TTmplCGreBandwidthActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.greTunnels.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2TTmplCGreEntry 150383104}

er1645v2TTmplCGreBandwidthActViolActIpDrpLev OBJECT-TYPE
   SYNTAX      INTEGER
               {
               unchanged (0)
               }
   MAX-ACCESS  read-write
   STATUS      current
   DESCRIPTION
      "Path: tunnels.editConf.greTunnels.bandwidth.action.violateAction.ip.dropLevel

       Possibilities:
               unchanged   (0)"
   ::= {er1645v2TTmplCGreEntry 150383360}

er1645v2TTmplCGreBandwidthActViolActIpDeFlag OBJECT-TYPE
   SYNTAX      INTEGER
               {
               unchanged (255),
               clear (0),
               set (1)
               }
   MAX-ACCESS  read-write
   STATUS      current
   DESCRIPTION
      "Path: tunnels.editConf.greTunnels.bandwidth.action.violateAction.ip.deFlag

       Possibilities:
               unchanged   (255)
               clear   (0)
               set   (1)"
   ::= {er1645v2TTmplCGreEntry 150384128}

er1645v2TTmplCGreBrVlTVlans OBJECT-TYPE
   SYNTAX      SEQUENCE OF Er1645v2TTmplCGreBrVlTVlansEntry
   MAX-ACCESS  not-accessible
   STATUS      current
   DESCRIPTION
      ""
   ::= {er1645v2TTmplCGre 459079680}

er1645v2TTmplCGreBrVlTVlansEntry OBJECT-TYPE
   SYNTAX      Er1645v2TTmplCGreBrVlTVlansEntry
   MAX-ACCESS  not-accessible
   STATUS      current
   DESCRIPTION
      ""
   INDEX      { er1645v2TTmplCGreTableIx,
                er1645v2TTmplCGreBrVlTVlansTableIx }
   ::= {er1645v2TTmplCGreBrVlTVlans 1}

Er1645v2TTmplCGreBrVlTVlansEntry ::=
   SEQUENCE
      {
      er1645v2TTmplCGreBrVlTVlansActions
         VariableLengthTableActions,
      er1645v2TTmplCGreBrVlTVlansTableIx
         TableIndex,
      er1645v2TTmplCGreBrVlTVlansVid
         Integer32,
      er1645v2TTmplCGreBrVlTVlansEndVid
         Integer32,
      er1645v2TTmplCGreBrVlTVlansAction
         INTEGER,
      er1645v2TTmplCGreBrVlTVlansTagInfoTpid
         INTEGER,
      er1645v2TTmplCGreBrVlTVlansTagInfoVid
         Integer32
      }

er1645v2TTmplCGreBrVlTVlansActions OBJECT-TYPE
   SYNTAX      VariableLengthTableActions
   MAX-ACCESS  read-write
   STATUS      current
   DESCRIPTION
      "By way of this field, some manipulations
       on this table may be performed."
   ::= {er1645v2TTmplCGreBrVlTVlansEntry 2}

er1645v2TTmplCGreBrVlTVlansTableIx OBJECT-TYPE
   SYNTAX      TableIndex
   MAX-ACCESS  not-accessible
   STATUS      current
   DESCRIPTION
      ""
   ::= {er1645v2TTmplCGreBrVlTVlansEntry 11}

er1645v2TTmplCGreBrVlTVlansVid OBJECT-TYPE
   SYNTAX      Integer32
   MAX-ACCESS  read-write
   STATUS      current
   DESCRIPTION
      "Path: tunnels.editConf.greTunnels.bridging.vlanTagging.vlans.vid"
   ::= {er1645v2TTmplCGreBrVlTVlansEntry 536870912}

er1645v2TTmplCGreBrVlTVlansEndVid OBJECT-TYPE
   SYNTAX      Integer32
   MAX-ACCESS  read-write
   STATUS      current
   DESCRIPTION
      "Path: tunnels.editConf.greTunnels.bridging.vlanTagging.vlans.endVid"
   ::= {er1645v2TTmplCGreBrVlTVlansEntry 2147483648}

er1645v2TTmplCGreBrVlTVlansAction OBJECT-TYPE
   SYNTAX      INTEGER
               {
               discard (0),
               accept (1),
               tag (2)
               }
   MAX-ACCESS  read-write
   STATUS      current
   DESCRIPTION
      "Path: tunnels.editConf.greTunnels.bridging.vlanTagging.vlans.action

       Possibilities:
               discard   (0)
               accept   (1)
               tag   (2)"
   ::= {er1645v2TTmplCGreBrVlTVlansEntry 1073741824}

er1645v2TTmplCGreBrVlTVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: tunnels.editConf.greTunnels.bridging.vlanTagging.vlans.tagInfo.tpid

       Possibilities:
               dot1Q   (33024)
               dot1ad   (34984)
               0x9100   (37120)
               0x9200   (37376)
               0x9300   (37632)"
   ::= {er1645v2TTmplCGreBrVlTVlansEntry 1677721600}

er1645v2TTmplCGreBrVlTVlansTagInfoVid OBJECT-TYPE
   SYNTAX      Integer32
   MAX-ACCESS  read-write
   STATUS      current
   DESCRIPTION
      "Path: tunnels.editConf.greTunnels.bridging.vlanTagging.vlans.tagInfo.vid"
   ::= {er1645v2TTmplCGreBrVlTVlansEntry 1744830464}


er1645v2TTmplCiGre OBJECT IDENTIFIER ::= {er1645v2TTmpl 24}

er1645v2TTmplCiGreSSCTable OBJECT-TYPE
   SYNTAX      SEQUENCE OF Er1645v2TTmplCiGreEntry
   MAX-ACCESS  not-accessible
   STATUS      current
   DESCRIPTION
      ""
   ::= {er1645v2TTmplCiGre 1}

er1645v2TTmplCiGreEntry OBJECT-TYPE
   SYNTAX      Er1645v2TTmplCiGreEntry
   MAX-ACCESS  not-accessible
   STATUS      current
   DESCRIPTION
      ""
   INDEX      { er1645v2TTmplCiGreTableIx }
   ::= {er1645v2TTmplCiGreSSCTable 1}

Er1645v2TTmplCiGreEntry ::=
   SEQUENCE
      {
      er1645v2TTmplCiGreActions
         VariableLengthTableActions,
      er1645v2TTmplCiGreTableIx
         TableIndex,
      er1645v2TTmplCiGreName
         DisplayString,
      er1645v2TTmplCiGreRemark
         DisplayString,
      er1645v2TTmplCiGreAdminStatus
         INTEGER,
      er1645v2TTmplCiGreMode
         INTEGER,
      er1645v2TTmplCiGrePriorityPolicy
         DisplayString,
      er1645v2TTmplCiGreIpVrfRouter
         DisplayString,
      er1645v2TTmplCiGreIpAdr
         IpAddress,
      er1645v2TTmplCiGreIpNetm
         IpAddress,
      er1645v2TTmplCiGreIpSNetName
         INTEGER,
      er1645v2TTmplCiGreIpSNetCust
         DisplayString,
      er1645v2TTmplCiGreIpRem
         IpAddress,
      er1645v2TTmplCiGreIpGwPref
         Integer32,
      er1645v2TTmplCiGreIpMtu
         Integer32,
      er1645v2TTmplCiGreIpMssAdjust
         INTEGER,
      er1645v2TTmplCiGreIpRipMetric
         Integer32,
      er1645v2TTmplCiGreIpRipMetricOut
         Integer32,
      er1645v2TTmplCiGreIpRipMode
         INTEGER,
      er1645v2TTmplCiGreIpRipTxVersion
         INTEGER,
      er1645v2TTmplCiGreIpRipRxVersion
         INTEGER,
      er1645v2TTmplCiGreIpRipSplitHorizon
         INTEGER,
      er1645v2TTmplCiGreIpRipAuth
         INTEGER,
      er1645v2TTmplCiGreIpRipFilter
         DisplayString,
      er1645v2TTmplCiGreIpRipFilterIn
         DisplayString,
      er1645v2TTmplCiGreIpRipSnapshot
         INTEGER,
      er1645v2TTmplCiGreIpRipClearNextHop
         INTEGER,
      er1645v2TTmplCiGreIpAccPol
         DisplayString,
      er1645v2TTmplCiGreIpAB
         DisplayString,
      er1645v2TTmplCiGreIpMA
         INTEGER,
      er1645v2TTmplCiGreIpMF
         Integer32,
      er1645v2TTmplCiGreIpDB
         INTEGER,
      er1645v2TTmplCiGreIpIR
         INTEGER,
      er1645v2TTmplCiGreIpIgmp
         INTEGER,
      er1645v2TTmplCiGreIpNN
         DisplayString,
      er1645v2TTmplCiGreIpPimMode
         INTEGER,
      er1645v2TTmplCiGreIpPimDrPriority
         Counter32,
      er1645v2TTmplCiGreIpPimHelloTime
         TimeTicks,
      er1645v2TTmplCiGreIpPimPropagationDelay
         TimeTicks,
      er1645v2TTmplCiGreIpPimOverrideInterval
         TimeTicks,
      er1645v2TTmplCiGreIpPimBsrBorder
         INTEGER,
      er1645v2TTmplCiGreIpPimTtlThreshold
         Integer32,
      er1645v2TTmplCiGreIpIMNetworkUnreachable
         INTEGER,
      er1645v2TTmplCiGreIpIMHostUnreachable
         INTEGER,
      er1645v2TTmplCiGreIpIMProtocolUnreachable
         INTEGER,
      er1645v2TTmplCiGreIpIMPortUnreachable
         INTEGER,
      er1645v2TTmplCiGreIpIMMtuExceeded
         INTEGER,
      er1645v2TTmplCiGreIpIMAdminProhibited
         INTEGER,
      er1645v2TTmplCiGreIpIMTtlExceeded
         INTEGER,
      er1645v2TTmplCiGreIpIMRedirect
         INTEGER,
      er1645v2TTmplCiGreBrAccList
         DisplayString,
      er1645v2TTmplCiGreBrInACL
         DisplayString,
      er1645v2TTmplCiGreBrTp
         DisplayString,
      er1645v2TTmplCiGreBrBrGrp
         DisplayString,
      er1645v2TTmplCiGreBrLimBC
         INTEGER,
      er1645v2TTmplCiGreBrPrivateMode
         INTEGER,
      er1645v2TTmplCiGreBrLearning
         INTEGER,
      er1645v2TTmplCiGreBrMaxCacheSize
         INTEGER,
      er1645v2TTmplCiGreBrRelearnDropOnRelearn
         INTEGER,
      er1645v2TTmplCiGreBrRelearnShutdownThreshold
         Integer32,
      er1645v2TTmplCiGreBrRelearnShutdownTime
         TimeTicks,
      er1645v2TTmplCiGreBrRelearnLoopDetection
         INTEGER,
      er1645v2TTmplCiGreBrRelearnLoopDetectionInterval
         TimeTicks,
      er1645v2TTmplCiGreBrVlanMemberShip
         INTEGER,
      er1645v2TTmplCiGreBrVlTUntaggedAction
         INTEGER,
      er1645v2TTmplCiGreBrVlTUntaggedTagInfoTpid
         INTEGER,
      er1645v2TTmplCiGreBrVlTUntaggedTagInfoVid
         Integer32,
      er1645v2TTmplCiGreBrVlTUnknownVlansAction
         INTEGER,
      er1645v2TTmplCiGreBrVlTUnknownVlansTagInfoTpid
         INTEGER,
      er1645v2TTmplCiGreBrVlTUnknownVlansTagInfoVid
         Integer32,
      er1645v2TTmplCiGreBrDot1adType
         INTEGER,
      er1645v2TTmplCiGreBrPriority
         Integer32,
      er1645v2TTmplCiGreBrPathCost
         Integer32,
      er1645v2TTmplCiGreBrInternalPathCost
         Integer32,
      er1645v2TTmplCiGreBrTCD
         INTEGER,
      er1645v2TTmplCiGreBrRestrictedRole
         INTEGER,
      er1645v2TTmplCiGreBrAdminEdge
         INTEGER,
      er1645v2TTmplCiGreBrOamMacDeviceMac
         DisplayString,
      er1645v2TTmplCiGreBrOamMacUserMac
         OCTET STRING,
      er1645v2TTmplCiGreBrOamMacBridgeMac
         DisplayString,
      er1645v2TTmplCiGreBrMgmtInline
         INTEGER,
      er1645v2TTmplCiGreBrL2ptMode
         INTEGER,
      er1645v2TTmplCiGreBrL2ptProtocols
         Integer32,
      er1645v2TTmplCiGreBrL2ptDestMac
         OCTET STRING,
      er1645v2TTmplCiGreBrL2ptCos
         INTEGER,
      er1645v2TTmplCiGreBrL2ptDropThrStp
         INTEGER,
      er1645v2TTmplCiGreBrL2ptDropThrLldp
         INTEGER,
      er1645v2TTmplCiGreBrL2ptDropThrOam
         INTEGER,
      er1645v2TTmplCiGreBrL2ptDropThrCdp
         INTEGER,
      er1645v2TTmplCiGreBrL2ptDropThrVtp
         INTEGER,
      er1645v2TTmplCiGreBrL2ptDropThrLacp
         INTEGER,
      er1645v2TTmplCiGreBrL2ptDropThrEfmOam
         INTEGER,
      er1645v2TTmplCiGreBrL2ptDropThrPvst
         INTEGER,
      er1645v2TTmplCiGreBrL2ptDropThrMmrp
         INTEGER,
      er1645v2TTmplCiGreBrL2ptDropThrMvrp
         INTEGER,
      er1645v2TTmplCiGreBrL2ptDropThrGvrp
         INTEGER,
      er1645v2TTmplCiGreBrL2ptDropThrGmrp
         INTEGER,
      er1645v2TTmplCiGreBrL2ptDropThrDtp
         INTEGER,
      er1645v2TTmplCiGreBrL2ptDropThrPagp
         INTEGER,
      er1645v2TTmplCiGreBrL2ptDropThrUdld
         INTEGER,
      er1645v2TTmplCiGreVirtEthernetVirtualEthernet
         DisplayString,
      er1645v2TTmplCiGreGreLocalIpAddress
         IpAddress,
      er1645v2TTmplCiGreGreLocalInterface
         DisplayString,
      er1645v2TTmplCiGreGreRemoteIpAddress
         IpAddress,
      er1645v2TTmplCiGreGreRemoteDnsName
         DisplayString,
      er1645v2TTmplCiGreGreIpsFdx
         DisplayString,
      er1645v2TTmplCiGreGreIpsHdxIn
         DisplayString,
      er1645v2TTmplCiGreGreIpsHdxOut
         DisplayString,
      er1645v2TTmplCiGreGreIpsPsCfg
         DisplayString,
      er1645v2TTmplCiGreGreIpsPsLIdIp
         IpAddress,
      er1645v2TTmplCiGreGreIpsPsLIdHn
         DisplayString,
      er1645v2TTmplCiGreGreIpsPsLIdUn
         DisplayString,
      er1645v2TTmplCiGreGreIpsPsRIdIp
         IpAddress,
      er1645v2TTmplCiGreGreIpsPsRIdHn
         DisplayString,
      er1645v2TTmplCiGreGreIpsPsRIdUn
         DisplayString,
      er1645v2TTmplCiGreGreIpsPsKey
         DisplayString,
      er1645v2TTmplCiGreGreIpsPsEncMKey
         INTEGER,
      er1645v2TTmplCiGreGreIpsPsEncKey
         DisplayString,
      er1645v2TTmplCiGreGreIpsPsPIdProt
         INTEGER,
      er1645v2TTmplCiGreGreIpsPsPIdLocAddr
         IpAddress,
      er1645v2TTmplCiGreGreIpsPsPIdLocMask
         IpAddress,
      er1645v2TTmplCiGreGreIpsPsPIdLocPort
         INTEGER,
      er1645v2TTmplCiGreGreIpsPsPIdRemAddr
         IpAddress,
      er1645v2TTmplCiGreGreIpsPsPIdRemMask
         IpAddress,
      er1645v2TTmplCiGreGreIpsPsPIdRemPort
         INTEGER,
      er1645v2TTmplCiGreGreIpsCeCfg
         DisplayString,
      er1645v2TTmplCiGreGreIpsCeLIdIp
         IpAddress,
      er1645v2TTmplCiGreGreIpsCeLIdHn
         DisplayString,
      er1645v2TTmplCiGreGreIpsCeLIdUn
         DisplayString,
      er1645v2TTmplCiGreGreIpsCeLIdDn
         DisplayString,
      er1645v2TTmplCiGreGreIpsCeRIdIp
         IpAddress,
      er1645v2TTmplCiGreGreIpsCeRIdHn
         DisplayString,
      er1645v2TTmplCiGreGreIpsCeRIdUn
         DisplayString,
      er1645v2TTmplCiGreGreIpsCeRIdDn
         DisplayString,
      er1645v2TTmplCiGreGreIpsCePIdProt
         INTEGER,
      er1645v2TTmplCiGreGreIpsCePIdLocAddr
         IpAddress,
      er1645v2TTmplCiGreGreIpsCePIdLocMask
         IpAddress,
      er1645v2TTmplCiGreGreIpsCePIdLocPort
         INTEGER,
      er1645v2TTmplCiGreGreIpsCePIdRemAddr
         IpAddress,
      er1645v2TTmplCiGreGreIpsCePIdRemMask
         IpAddress,
      er1645v2TTmplCiGreGreIpsCePIdRemPort
         INTEGER,
      er1645v2TTmplCiGreGreKpAlMode
         INTEGER,
      er1645v2TTmplCiGreGreKpAlInterval
         TimeTicks,
      er1645v2TTmplCiGreGreKpAlRepTimeOut
         TimeTicks,
      er1645v2TTmplCiGreGreKpAlFailsPrmt
         Integer32,
      er1645v2TTmplCiGreGreNoTraffTO
         TimeTicks,
      er1645v2TTmplCiGreGreNoTraffDi
         INTEGER,
      er1645v2TTmplCiGreGreType
         INTEGER,
      er1645v2TTmplCiGreGreRRoutDefRt
         INTEGER,
      er1645v2TTmplCiGreGreTos
         INTEGER,
      er1645v2TTmplCiGreGreQueueTosMapQueue1
         INTEGER,
      er1645v2TTmplCiGreGreQueueTosMapQueue2
         INTEGER,
      er1645v2TTmplCiGreGreQueueTosMapQueue3
         INTEGER,
      er1645v2TTmplCiGreGreQueueTosMapQueue4
         INTEGER,
      er1645v2TTmplCiGreGreQueueTosMapQueue5
         INTEGER,
      er1645v2TTmplCiGreGreQueueTosMapLowDelayQueue
         INTEGER,
      er1645v2TTmplCiGreGreQueueTosMapLowDelay2Queue
         INTEGER,
      er1645v2TTmplCiGreGreQueueTosMapSystemQueue
         INTEGER,
      er1645v2TTmplCiGreGreDf
         INTEGER,
      er1645v2TTmplCiGreGreTtl
         INTEGER,
      er1645v2TTmplCiGreGreMtu
         Integer32,
      er1645v2TTmplCiGreMplsMode
         INTEGER,
      er1645v2TTmplCiGreMplsInLabel
         Integer32,
      er1645v2TTmplCiGreMplsOutLabel
         Integer32,
      er1645v2TTmplCiGreMplsTrafficClassMode
         INTEGER,
      er1645v2TTmplCiGreMplsTrafficClassFixed
         Integer32,
      er1645v2TTmplCiGreMplsTrafficClassQosP0
         Integer32,
      er1645v2TTmplCiGreMplsTrafficClassQosP1
         Integer32,
      er1645v2TTmplCiGreMplsTrafficClassQosP2
         Integer32,
      er1645v2TTmplCiGreMplsTrafficClassQosP3
         Integer32,
      er1645v2TTmplCiGreMplsTrafficClassQosP4
         Integer32,
      er1645v2TTmplCiGreMplsTrafficClassQosP5
         Integer32,
      er1645v2TTmplCiGreMplsTrafficClassQosP6
         Integer32,
      er1645v2TTmplCiGreMplsTrafficClassQosP7
         Integer32,
      er1645v2TTmplCiGreMplsTtl
         INTEGER,
      er1645v2TTmplCiGreInbBwCir
         Integer32,
      er1645v2TTmplCiGreInbBwTc
         INTEGER,
      er1645v2TTmplCiGreInbBwCorrType
         INTEGER,
      er1645v2TTmplCiGreInbBwCorrPredefEncapsFrameRelay
         DisplayString,
      er1645v2TTmplCiGreInbBwCorrPredefEncapsPpp
         DisplayString,
      er1645v2TTmplCiGreInbBwCorrPredefEncapsAtmHl
         INTEGER,
      er1645v2TTmplCiGreInbBwCorrPredefEncapsAtmMp
         INTEGER,
      er1645v2TTmplCiGreInbBwCorrPredefEncapsHdlc
         DisplayString,
      er1645v2TTmplCiGreInbBwCorrPredefEncapsEfmFs
         Integer32,
      er1645v2TTmplCiGreInbBwCorrPredefEncapsEfmIb
         Integer32,
      er1645v2TTmplCiGreInbBwCorrPredefMode
         INTEGER,
      er1645v2TTmplCiGreInbBwCorrManualOverhead
         Integer32,
      er1645v2TTmplCiGreInbBwCorrManualFrameData
         Counter32,
      er1645v2TTmplCiGreInbBwCorrManualFrameHeader
         Counter32,
      er1645v2TTmplCiGreInbBwMaxFifoQLen
         Integer32,
      er1645v2TTmplCiGreInbBwPriorityPolicy
         DisplayString,
      er1645v2TTmplCiGreBandwidthMode
         INTEGER,
      er1645v2TTmplCiGreBandwidthCir
         Integer32,
      er1645v2TTmplCiGreBandwidthEir
         Integer32,
      er1645v2TTmplCiGreBandwidthUnit
         INTEGER,
      er1645v2TTmplCiGreBandwidthTc
         INTEGER,
      er1645v2TTmplCiGreBandwidthTcFactor
         INTEGER,
      er1645v2TTmplCiGreBandwidthCorrType
         INTEGER,
      er1645v2TTmplCiGreBandwidthCorrPredefEncapsFrameRelay
         DisplayString,
      er1645v2TTmplCiGreBandwidthCorrPredefEncapsPpp
         DisplayString,
      er1645v2TTmplCiGreBandwidthCorrPredefEncapsAtmHl
         INTEGER,
      er1645v2TTmplCiGreBandwidthCorrPredefEncapsAtmMp
         INTEGER,
      er1645v2TTmplCiGreBandwidthCorrPredefEncapsHdlc
         DisplayString,
      er1645v2TTmplCiGreBandwidthCorrPredefEncapsEfmFs
         Integer32,
      er1645v2TTmplCiGreBandwidthCorrPredefEncapsEfmIb
         Integer32,
      er1645v2TTmplCiGreBandwidthCorrPredefMode
         INTEGER,
      er1645v2TTmplCiGreBandwidthCorrManualOverhead
         Integer32,
      er1645v2TTmplCiGreBandwidthCorrManualFrameData
         Counter32,
      er1645v2TTmplCiGreBandwidthCorrManualFrameHeader
         Counter32,
      er1645v2TTmplCiGreBandwidthMaxFifoQLen
         Integer32,
      er1645v2TTmplCiGreBandwidthDeFlagCir
         INTEGER,
      er1645v2TTmplCiGreBandwidthDeFlagEir
         INTEGER,
      er1645v2TTmplCiGreBandwidthDeFlagViolate
         INTEGER,
      er1645v2TTmplCiGreBandwidthActCirActNone
         OCTET STRING,
      er1645v2TTmplCiGreBandwidthActCirActEthCos1
         INTEGER,
      er1645v2TTmplCiGreBandwidthActCirActEthDei1
         INTEGER,
      er1645v2TTmplCiGreBandwidthActCirActEthCos2
         INTEGER,
      er1645v2TTmplCiGreBandwidthActCirActEthDei2
         INTEGER,
      er1645v2TTmplCiGreBandwidthActCirActEthCos3
         INTEGER,
      er1645v2TTmplCiGreBandwidthActCirActEthDei3
         INTEGER,
      er1645v2TTmplCiGreBandwidthActCirActEthCos4
         INTEGER,
      er1645v2TTmplCiGreBandwidthActCirActEthDei4
         INTEGER,
      er1645v2TTmplCiGreBandwidthActCirActEthCos5
         INTEGER,
      er1645v2TTmplCiGreBandwidthActCirActEthDei5
         INTEGER,
      er1645v2TTmplCiGreBandwidthActCirActEthCos6
         INTEGER,
      er1645v2TTmplCiGreBandwidthActCirActEthDei6
         INTEGER,
      er1645v2TTmplCiGreBandwidthActCirActEthCos7
         INTEGER,
      er1645v2TTmplCiGreBandwidthActCirActEthDei7
         INTEGER,
      er1645v2TTmplCiGreBandwidthActCirActEthCos8
         INTEGER,
      er1645v2TTmplCiGreBandwidthActCirActEthDei8
         INTEGER,
      er1645v2TTmplCiGreBandwidthActCirActEthTos
         INTEGER,
      er1645v2TTmplCiGreBandwidthActCirActEthQueue
         INTEGER,
      er1645v2TTmplCiGreBandwidthActCirActEthDrpLev
         INTEGER,
      er1645v2TTmplCiGreBandwidthActCirActEthDeFlag
         INTEGER,
      er1645v2TTmplCiGreBandwidthActCirActIpTos
         INTEGER,
      er1645v2TTmplCiGreBandwidthActCirActIpQueue
         INTEGER,
      er1645v2TTmplCiGreBandwidthActCirActIpDrpLev
         INTEGER,
      er1645v2TTmplCiGreBandwidthActCirActIpDeFlag
         INTEGER,
      er1645v2TTmplCiGreBandwidthActEirActNone
         OCTET STRING,
      er1645v2TTmplCiGreBandwidthActEirActEthCos1
         INTEGER,
      er1645v2TTmplCiGreBandwidthActEirActEthDei1
         INTEGER,
      er1645v2TTmplCiGreBandwidthActEirActEthCos2
         INTEGER,
      er1645v2TTmplCiGreBandwidthActEirActEthDei2
         INTEGER,
      er1645v2TTmplCiGreBandwidthActEirActEthCos3
         INTEGER,
      er1645v2TTmplCiGreBandwidthActEirActEthDei3
         INTEGER,
      er1645v2TTmplCiGreBandwidthActEirActEthCos4
         INTEGER,
      er1645v2TTmplCiGreBandwidthActEirActEthDei4
         INTEGER,
      er1645v2TTmplCiGreBandwidthActEirActEthCos5
         INTEGER,
      er1645v2TTmplCiGreBandwidthActEirActEthDei5
         INTEGER,
      er1645v2TTmplCiGreBandwidthActEirActEthCos6
         INTEGER,
      er1645v2TTmplCiGreBandwidthActEirActEthDei6
         INTEGER,
      er1645v2TTmplCiGreBandwidthActEirActEthCos7
         INTEGER,
      er1645v2TTmplCiGreBandwidthActEirActEthDei7
         INTEGER,
      er1645v2TTmplCiGreBandwidthActEirActEthCos8
         INTEGER,
      er1645v2TTmplCiGreBandwidthActEirActEthDei8
         INTEGER,
      er1645v2TTmplCiGreBandwidthActEirActEthTos
         INTEGER,
      er1645v2TTmplCiGreBandwidthActEirActEthQueue
         INTEGER,
      er1645v2TTmplCiGreBandwidthActEirActEthDrpLev
         INTEGER,
      er1645v2TTmplCiGreBandwidthActEirActEthDeFlag
         INTEGER,
      er1645v2TTmplCiGreBandwidthActEirActIpTos
         INTEGER,
      er1645v2TTmplCiGreBandwidthActEirActIpQueue
         INTEGER,
      er1645v2TTmplCiGreBandwidthActEirActIpDrpLev
         INTEGER,
      er1645v2TTmplCiGreBandwidthActEirActIpDeFlag
         INTEGER,
      er1645v2TTmplCiGreBandwidthActViolActNone
         OCTET STRING,
      er1645v2TTmplCiGreBandwidthActViolActDrop
         OCTET STRING,
      er1645v2TTmplCiGreBandwidthActViolActEthCos1
         INTEGER,
      er1645v2TTmplCiGreBandwidthActViolActEthDei1
         INTEGER,
      er1645v2TTmplCiGreBandwidthActViolActEthCos2
         INTEGER,
      er1645v2TTmplCiGreBandwidthActViolActEthDei2
         INTEGER,
      er1645v2TTmplCiGreBandwidthActViolActEthCos3
         INTEGER,
      er1645v2TTmplCiGreBandwidthActViolActEthDei3
         INTEGER,
      er1645v2TTmplCiGreBandwidthActViolActEthCos4
         INTEGER,
      er1645v2TTmplCiGreBandwidthActViolActEthDei4
         INTEGER,
      er1645v2TTmplCiGreBandwidthActViolActEthCos5
         INTEGER,
      er1645v2TTmplCiGreBandwidthActViolActEthDei5
         INTEGER,
      er1645v2TTmplCiGreBandwidthActViolActEthCos6
         INTEGER,
      er1645v2TTmplCiGreBandwidthActViolActEthDei6
         INTEGER,
      er1645v2TTmplCiGreBandwidthActViolActEthCos7
         INTEGER,
      er1645v2TTmplCiGreBandwidthActViolActEthDei7
         INTEGER,
      er1645v2TTmplCiGreBandwidthActViolActEthCos8
         INTEGER,
      er1645v2TTmplCiGreBandwidthActViolActEthDei8
         INTEGER,
      er1645v2TTmplCiGreBandwidthActViolActEthTos
         INTEGER,
      er1645v2TTmplCiGreBandwidthActViolActEthQueue
         INTEGER,
      er1645v2TTmplCiGreBandwidthActViolActEthDrpLev
         INTEGER,
      er1645v2TTmplCiGreBandwidthActViolActEthDeFlag
         INTEGER,
      er1645v2TTmplCiGreBandwidthActViolActIpTos
         INTEGER,
      er1645v2TTmplCiGreBandwidthActViolActIpQueue
         INTEGER,
      er1645v2TTmplCiGreBandwidthActViolActIpDrpLev
         INTEGER,
      er1645v2TTmplCiGreBandwidthActViolActIpDeFlag
         INTEGER
      }

er1645v2TTmplCiGreActions OBJECT-TYPE
   SYNTAX      VariableLengthTableActions
   MAX-ACCESS  read-write
   STATUS      current
   DESCRIPTION
      "By way of this field, some manipulations
       on this table may be performed."
   ::= {er1645v2TTmplCiGreEntry 2}

er1645v2TTmplCiGreTableIx OBJECT-TYPE
   SYNTAX      TableIndex
   MAX-ACCESS  not-accessible
   STATUS      current
   DESCRIPTION
      ""
   ::= {er1645v2TTmplCiGreEntry 11}

er1645v2TTmplCiGreName OBJECT-TYPE
   SYNTAX      DisplayString
   MAX-ACCESS  read-write
   STATUS      current
   DESCRIPTION
      "Path: tunnels.editConf.ipsecGreTunnels.name"
   ::= {er1645v2TTmplCiGreEntry 16777216}

er1645v2TTmplCiGreRemark OBJECT-TYPE
   SYNTAX      DisplayString
   MAX-ACCESS  read-write
   STATUS      current
   DESCRIPTION
      "Path: tunnels.editConf.ipsecGreTunnels.remark"
   ::= {er1645v2TTmplCiGreEntry 1157627904}

er1645v2TTmplCiGreAdminStatus OBJECT-TYPE
   SYNTAX      INTEGER
               {
               up (1),
               down (2)
               }
   MAX-ACCESS  read-write
   STATUS      current
   DESCRIPTION
      "Path: tunnels.editConf.ipsecGreTunnels.adminStatus

       Possibilities:
               up   (1)
               down   (2)"
   ::= {er1645v2TTmplCiGreEntry 33554432}

er1645v2TTmplCiGreMode OBJECT-TYPE
   SYNTAX      INTEGER
               {
               routing (1),
               bridging (2),
               multilink (8),
               virtEthernet (32)
               }
   MAX-ACCESS  read-write
   STATUS      current
   DESCRIPTION
      "Path: tunnels.editConf.ipsecGreTunnels.mode

       Possibilities:
               routing   (1)
               bridging   (2)
               multilink   (8)
               virtEthernet   (32)"
   ::= {er1645v2TTmplCiGreEntry 67108864}

er1645v2TTmplCiGrePriorityPolicy OBJECT-TYPE
   SYNTAX      DisplayString
   MAX-ACCESS  read-write
   STATUS      current
   DESCRIPTION
      "Path: tunnels.editConf.ipsecGreTunnels.priorityPolicy"
   ::= {er1645v2TTmplCiGreEntry 83886080}

er1645v2TTmplCiGreIpVrfRouter OBJECT-TYPE
   SYNTAX      DisplayString
   MAX-ACCESS  read-write
   STATUS      current
   DESCRIPTION
      "Path: tunnels.editConf.ipsecGreTunnels.ip.vrfRouter"
   ::= {er1645v2TTmplCiGreEntry 53215232}

er1645v2TTmplCiGreIpAdr OBJECT-TYPE
   SYNTAX      IpAddress
   MAX-ACCESS  read-write
   STATUS      current
   DESCRIPTION
      "Path: tunnels.editConf.ipsecGreTunnels.ip.address"
   ::= {er1645v2TTmplCiGreEntry 58261504}

er1645v2TTmplCiGreIpNetm OBJECT-TYPE
   SYNTAX      IpAddress
   MAX-ACCESS  read-write
   STATUS      current
   DESCRIPTION
      "Path: tunnels.editConf.ipsecGreTunnels.ip.netMask"
   ::= {er1645v2TTmplCiGreEntry 58392576}

er1645v2TTmplCiGreIpSNetName OBJECT-TYPE
   SYNTAX      INTEGER
               {
               slOPTg (0),
               corp (2),
               dmz (3),
               internet (1)
               }
   MAX-ACCESS  read-write
   STATUS      current
   DESCRIPTION
      "Path: tunnels.editConf.ipsecGreTunnels.ip.sNet.name

       Possibilities:
               <OPT>   (0)
               corp   (2)
               dmz   (3)
               internet   (1)"
   ::= {er1645v2TTmplCiGreEntry 53674240}

er1645v2TTmplCiGreIpSNetCust OBJECT-TYPE
   SYNTAX      DisplayString
   MAX-ACCESS  read-write
   STATUS      current
   DESCRIPTION
      "Path: tunnels.editConf.ipsecGreTunnels.ip.sNet.custom"
   ::= {er1645v2TTmplCiGreEntry 53674496}

er1645v2TTmplCiGreIpRem OBJECT-TYPE
   SYNTAX      IpAddress
   MAX-ACCESS  read-write
   STATUS      current
   DESCRIPTION
      "Path: tunnels.editConf.ipsecGreTunnels.ip.remote"
   ::= {er1645v2TTmplCiGreEntry 58458112}

er1645v2TTmplCiGreIpGwPref OBJECT-TYPE
   SYNTAX      Integer32
   MAX-ACCESS  read-write
   STATUS      current
   DESCRIPTION
      "Path: tunnels.editConf.ipsecGreTunnels.ip.gatewayPreference"
   ::= {er1645v2TTmplCiGreEntry 52690944}

er1645v2TTmplCiGreIpMtu OBJECT-TYPE
   SYNTAX      Integer32
   MAX-ACCESS  read-write
   STATUS      current
   DESCRIPTION
      "Path: tunnels.editConf.ipsecGreTunnels.ip.mtu"
   ::= {er1645v2TTmplCiGreEntry 52953088}

er1645v2TTmplCiGreIpMssAdjust OBJECT-TYPE
   SYNTAX      INTEGER
               {
               disabled (0),
               auto (65536)
               }
   MAX-ACCESS  read-write
   STATUS      current
   DESCRIPTION
      "Path: tunnels.editConf.ipsecGreTunnels.ip.mssAdjust

       Possibilities:
               disabled   (0)
               auto   (65536)"
   ::= {er1645v2TTmplCiGreEntry 53280768}

er1645v2TTmplCiGreIpRipMetric OBJECT-TYPE
   SYNTAX      Integer32
   MAX-ACCESS  read-write
   STATUS      current
   DESCRIPTION
      "Path: tunnels.editConf.ipsecGreTunnels.ip.rip.metric"
   ::= {er1645v2TTmplCiGreEntry 51712768}

er1645v2TTmplCiGreIpRipMetricOut OBJECT-TYPE
   SYNTAX      Integer32
   MAX-ACCESS  read-write
   STATUS      current
   DESCRIPTION
      "Path: tunnels.editConf.ipsecGreTunnels.ip.rip.metricOut"
   ::= {er1645v2TTmplCiGreEntry 51713024}

er1645v2TTmplCiGreIpRipMode OBJECT-TYPE
   SYNTAX      INTEGER
               {
               disabled (0),
               passive (1),
               active (2)
               }
   MAX-ACCESS  read-write
   STATUS      current
   DESCRIPTION
      "Path: tunnels.editConf.ipsecGreTunnels.ip.rip.mode

       Possibilities:
               disabled   (0)
               passive   (1)
               active   (2)"
   ::= {er1645v2TTmplCiGreEntry 51713280}

er1645v2TTmplCiGreIpRipTxVersion OBJECT-TYPE
   SYNTAX      INTEGER
               {
               rip1 (0),
               rip2 (1),
               rip1mcompatible (2)
               }
   MAX-ACCESS  read-write
   STATUS      current
   DESCRIPTION
      "Path: tunnels.editConf.ipsecGreTunnels.ip.rip.txVersion

       Possibilities:
               rip1   (0)
               rip2   (1)
               rip1-compatible   (2)"
   ::= {er1645v2TTmplCiGreEntry 51716864}

er1645v2TTmplCiGreIpRipRxVersion OBJECT-TYPE
   SYNTAX      INTEGER
               {
               rip1only (0),
               rip2only (1),
               rip12 (2)
               }
   MAX-ACCESS  read-write
   STATUS      current
   DESCRIPTION
      "Path: tunnels.editConf.ipsecGreTunnels.ip.rip.rxVersion

       Possibilities:
               rip1only   (0)
               rip2only   (1)
               rip1&2   (2)"
   ::= {er1645v2TTmplCiGreEntry 51717120}

er1645v2TTmplCiGreIpRipSplitHorizon OBJECT-TYPE
   SYNTAX      INTEGER
               {
               disabled (0),
               enabled (1),
               poisonedReverse (2)
               }
   MAX-ACCESS  read-write
   STATUS      current
   DESCRIPTION
      "Path: tunnels.editConf.ipsecGreTunnels.ip.rip.splitHorizon

       Possibilities:
               disabled   (0)
               enabled   (1)
               poisonedReverse   (2)"
   ::= {er1645v2TTmplCiGreEntry 51713792}

er1645v2TTmplCiGreIpRipAuth OBJECT-TYPE
   SYNTAX      INTEGER
               {
               disabled (0),
               texts (1),
               md5 (2)
               }
   MAX-ACCESS  read-write
   STATUS      current
   DESCRIPTION
      "Path: tunnels.editConf.ipsecGreTunnels.ip.rip.authentication

       Possibilities:
               disabled   (0)
               text    (1)
               md5   (2)"
   ::= {er1645v2TTmplCiGreEntry 51712512}

er1645v2TTmplCiGreIpRipFilter OBJECT-TYPE
   SYNTAX      DisplayString
   MAX-ACCESS  read-write
   STATUS      current
   DESCRIPTION
      "Path: tunnels.editConf.ipsecGreTunnels.ip.rip.filter"
   ::= {er1645v2TTmplCiGreEntry 51716096}

er1645v2TTmplCiGreIpRipFilterIn OBJECT-TYPE
   SYNTAX      DisplayString
   MAX-ACCESS  read-write
   STATUS      current
   DESCRIPTION
      "Path: tunnels.editConf.ipsecGreTunnels.ip.rip.filterIn"
   ::= {er1645v2TTmplCiGreEntry 51716352}

er1645v2TTmplCiGreIpRipSnapshot OBJECT-TYPE
   SYNTAX      INTEGER
               {
               disabled (0),
               enabled (1)
               }
   MAX-ACCESS  read-write
   STATUS      current
   DESCRIPTION
      "Path: tunnels.editConf.ipsecGreTunnels.ip.rip.snapshot

       Possibilities:
               disabled   (0)
               enabled   (1)"
   ::= {er1645v2TTmplCiGreEntry 51708160}

er1645v2TTmplCiGreIpRipClearNextHop OBJECT-TYPE
   SYNTAX      INTEGER
               {
               disabled (0),
               enabled (1)
               }
   MAX-ACCESS  read-write
   STATUS      current
   DESCRIPTION
      "Path: tunnels.editConf.ipsecGreTunnels.ip.rip.clearNextHop

       Possibilities:
               disabled   (0)
               enabled   (1)"
   ::= {er1645v2TTmplCiGreEntry 51708416}

er1645v2TTmplCiGreIpAccPol OBJECT-TYPE
   SYNTAX      DisplayString
   MAX-ACCESS  read-write
   STATUS      current
   DESCRIPTION
      "Path: tunnels.editConf.ipsecGreTunnels.ip.accessPolicy"
   ::= {er1645v2TTmplCiGreEntry 53084160}

er1645v2TTmplCiGreIpAB OBJECT-TYPE
   SYNTAX      DisplayString
   MAX-ACCESS  read-write
   STATUS      current
   DESCRIPTION
      "Path: tunnels.editConf.ipsecGreTunnels.ip.trafficPolicy"
   ::= {er1645v2TTmplCiGreEntry 51249152}

er1645v2TTmplCiGreIpMA OBJECT-TYPE
   SYNTAX      INTEGER
               {
               disabled (0),
               enabled (1)
               }
   MAX-ACCESS  read-write
   STATUS      current
   DESCRIPTION
      "Path: tunnels.editConf.ipsecGreTunnels.ip.mgmtAccess

       Possibilities:
               disabled   (0)
               enabled   (1)"
   ::= {er1645v2TTmplCiGreEntry 51380224}

er1645v2TTmplCiGreIpMF OBJECT-TYPE
   SYNTAX      Integer32
   MAX-ACCESS  read-write
   STATUS      current
   DESCRIPTION
      "Path: tunnels.editConf.ipsecGreTunnels.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2TTmplCiGreEntry 51445760}

er1645v2TTmplCiGreIpDB OBJECT-TYPE
   SYNTAX      INTEGER
               {
               disabled (0),
               enabled (1)
               }
   MAX-ACCESS  read-write
   STATUS      current
   DESCRIPTION
      "Path: tunnels.editConf.ipsecGreTunnels.ip.directedBroadcasts

       Possibilities:
               disabled   (0)
               enabled   (1)"
   ::= {er1645v2TTmplCiGreEntry 51773440}

er1645v2TTmplCiGreIpIR OBJECT-TYPE
   SYNTAX      INTEGER
               {
               disabled (0),
               enabled (1)
               }
   MAX-ACCESS  read-write
   STATUS      current
   DESCRIPTION
      "Path: tunnels.editConf.ipsecGreTunnels.ip.icmpRedirects

       Possibilities:
               disabled   (0)
               enabled   (1)"
   ::= {er1645v2TTmplCiGreEntry 52035584}

er1645v2TTmplCiGreIpIgmp OBJECT-TYPE
   SYNTAX      INTEGER
               {
               disabled (0),
               proxy (1),
               router (2),
               v3Router (5)
               }
   MAX-ACCESS  read-write
   STATUS      current
   DESCRIPTION
      "Path: tunnels.editConf.ipsecGreTunnels.ip.igmp

       Possibilities:
               disabled   (0)
               proxy   (1)
               router   (2)
               v3Router   (5)"
   ::= {er1645v2TTmplCiGreEntry 52428800}

er1645v2TTmplCiGreIpNN OBJECT-TYPE
   SYNTAX      DisplayString
   MAX-ACCESS  read-write
   STATUS      current
   DESCRIPTION
      "Path: tunnels.editConf.ipsecGreTunnels.ip.nat"
   ::= {er1645v2TTmplCiGreEntry 52101120}

er1645v2TTmplCiGreIpPimMode OBJECT-TYPE
   SYNTAX      INTEGER
               {
               disabled (0),
               sparse (1),
               passive (2)
               }
   MAX-ACCESS  read-write
   STATUS      current
   DESCRIPTION
      "Path: tunnels.editConf.ipsecGreTunnels.ip.pim.mode

       Possibilities:
               disabled   (0)
               sparse   (1)
               passive   (2)"
   ::= {er1645v2TTmplCiGreEntry 53346560}

er1645v2TTmplCiGreIpPimDrPriority OBJECT-TYPE
   SYNTAX      Counter32
   MAX-ACCESS  read-write
   STATUS      current
   DESCRIPTION
      "Path: tunnels.editConf.ipsecGreTunnels.ip.pim.drPriority

       32 bit unsigned wrappable counter."
   ::= {er1645v2TTmplCiGreEntry 53346816}

er1645v2TTmplCiGreIpPimHelloTime OBJECT-TYPE
   SYNTAX      TimeTicks
   MAX-ACCESS  read-write
   STATUS      current
   DESCRIPTION
      "Path: tunnels.editConf.ipsecGreTunnels.ip.pim.helloTime

       Time in centi-second."
   ::= {er1645v2TTmplCiGreEntry 53347072}

er1645v2TTmplCiGreIpPimPropagationDelay OBJECT-TYPE
   SYNTAX      TimeTicks
   MAX-ACCESS  read-write
   STATUS      current
   DESCRIPTION
      "Path: tunnels.editConf.ipsecGreTunnels.ip.pim.propagationDelay

       Time in centi-second."
   ::= {er1645v2TTmplCiGreEntry 53347328}

er1645v2TTmplCiGreIpPimOverrideInterval OBJECT-TYPE
   SYNTAX      TimeTicks
   MAX-ACCESS  read-write
   STATUS      current
   DESCRIPTION
      "Path: tunnels.editConf.ipsecGreTunnels.ip.pim.overrideInterval

       Time in centi-second."
   ::= {er1645v2TTmplCiGreEntry 53347584}

er1645v2TTmplCiGreIpPimBsrBorder OBJECT-TYPE
   SYNTAX      INTEGER
               {
               disabled (0),
               enabled (1)
               }
   MAX-ACCESS  read-write
   STATUS      current
   DESCRIPTION
      "Path: tunnels.editConf.ipsecGreTunnels.ip.pim.bsrBorder

       Possibilities:
               disabled   (0)
               enabled   (1)"
   ::= {er1645v2TTmplCiGreEntry 53347840}

er1645v2TTmplCiGreIpPimTtlThreshold OBJECT-TYPE
   SYNTAX      Integer32
   MAX-ACCESS  read-write
   STATUS      current
   DESCRIPTION
      "Path: tunnels.editConf.ipsecGreTunnels.ip.pim.ttlThreshold"
   ::= {er1645v2TTmplCiGreEntry 53348096}

er1645v2TTmplCiGreIpIMNetworkUnreachable OBJECT-TYPE
   SYNTAX      INTEGER
               {
               disabled (0),
               enabled (1)
               }
   MAX-ACCESS  read-write
   STATUS      current
   DESCRIPTION
      "Path: tunnels.editConf.ipsecGreTunnels.ip.icmpMessages.networkUnreachable

       Possibilities:
               disabled   (0)
               enabled   (1)"
   ::= {er1645v2TTmplCiGreEntry 53412096}

er1645v2TTmplCiGreIpIMHostUnreachable OBJECT-TYPE
   SYNTAX      INTEGER
               {
               disabled (0),
               enabled (1)
               }
   MAX-ACCESS  read-write
   STATUS      current
   DESCRIPTION
      "Path: tunnels.editConf.ipsecGreTunnels.ip.icmpMessages.hostUnreachable

       Possibilities:
               disabled   (0)
               enabled   (1)"
   ::= {er1645v2TTmplCiGreEntry 53412352}

er1645v2TTmplCiGreIpIMProtocolUnreachable OBJECT-TYPE
   SYNTAX      INTEGER
               {
               disabled (0),
               enabled (1)
               }
   MAX-ACCESS  read-write
   STATUS      current
   DESCRIPTION
      "Path: tunnels.editConf.ipsecGreTunnels.ip.icmpMessages.protocolUnreachable

       Possibilities:
               disabled   (0)
               enabled   (1)"
   ::= {er1645v2TTmplCiGreEntry 53412608}

er1645v2TTmplCiGreIpIMPortUnreachable OBJECT-TYPE
   SYNTAX      INTEGER
               {
               disabled (0),
               enabled (1)
               }
   MAX-ACCESS  read-write
   STATUS      current
   DESCRIPTION
      "Path: tunnels.editConf.ipsecGreTunnels.ip.icmpMessages.portUnreachable

       Possibilities:
               disabled   (0)
               enabled   (1)"
   ::= {er1645v2TTmplCiGreEntry 53412864}

er1645v2TTmplCiGreIpIMMtuExceeded OBJECT-TYPE
   SYNTAX      INTEGER
               {
               disabled (0),
               enabled (1)
               }
   MAX-ACCESS  read-write
   STATUS      current
   DESCRIPTION
      "Path: tunnels.editConf.ipsecGreTunnels.ip.icmpMessages.mtuExceeded

       Possibilities:
               disabled   (0)
               enabled   (1)"
   ::= {er1645v2TTmplCiGreEntry 53413120}

er1645v2TTmplCiGreIpIMAdminProhibited OBJECT-TYPE
   SYNTAX      INTEGER
               {
               disabled (0),
               enabled (1)
               }
   MAX-ACCESS  read-write
   STATUS      current
   DESCRIPTION
      "Path: tunnels.editConf.ipsecGreTunnels.ip.icmpMessages.adminProhibited

       Possibilities:
               disabled   (0)
               enabled   (1)"
   ::= {er1645v2TTmplCiGreEntry 53413376}

er1645v2TTmplCiGreIpIMTtlExceeded OBJECT-TYPE
   SYNTAX      INTEGER
               {
               disabled (0),
               enabled (1)
               }
   MAX-ACCESS  read-write
   STATUS      current
   DESCRIPTION
      "Path: tunnels.editConf.ipsecGreTunnels.ip.icmpMessages.ttlExceeded

       Possibilities:
               disabled   (0)
               enabled   (1)"
   ::= {er1645v2TTmplCiGreEntry 53413632}

er1645v2TTmplCiGreIpIMRedirect OBJECT-TYPE
   SYNTAX      INTEGER
               {
               disabled (0),
               enabled (1)
               }
   MAX-ACCESS  read-write
   STATUS      current
   DESCRIPTION
      "Path: tunnels.editConf.ipsecGreTunnels.ip.icmpMessages.redirect

       Possibilities:
               disabled   (0)
               enabled   (1)"
   ::= {er1645v2TTmplCiGreEntry 53413888}

er1645v2TTmplCiGreBrAccList OBJECT-TYPE
   SYNTAX      DisplayString
   MAX-ACCESS  read-write
   STATUS      current
   DESCRIPTION
      "Path: tunnels.editConf.ipsecGreTunnels.bridging.accessList"
   ::= {er1645v2TTmplCiGreEntry 453246976}

er1645v2TTmplCiGreBrInACL OBJECT-TYPE
   SYNTAX      DisplayString
   MAX-ACCESS  read-write
   STATUS      current
   DESCRIPTION
      "Path: tunnels.editConf.ipsecGreTunnels.bridging.inAccessList"
   ::= {er1645v2TTmplCiGreEntry 456916992}

er1645v2TTmplCiGreBrTp OBJECT-TYPE
   SYNTAX      DisplayString
   MAX-ACCESS  read-write
   STATUS      current
   DESCRIPTION
      "Path: tunnels.editConf.ipsecGreTunnels.bridging.trafficPolicy"
   ::= {er1645v2TTmplCiGreEntry 454295552}

er1645v2TTmplCiGreBrBrGrp OBJECT-TYPE
   SYNTAX      DisplayString
   MAX-ACCESS  read-write
   STATUS      current
   DESCRIPTION
      "Path: tunnels.editConf.ipsecGreTunnels.bridging.bridgeGroup"
   ::= {er1645v2TTmplCiGreEntry 454819840}

er1645v2TTmplCiGreBrLimBC OBJECT-TYPE
   SYNTAX      INTEGER
               {
               disabled (0),
               enabled (1)
               }
   MAX-ACCESS  read-write
   STATUS      current
   DESCRIPTION
      "Path: tunnels.editConf.ipsecGreTunnels.bridging.limitBroadcasts

       Possibilities:
               disabled   (0)
               enabled   (1)"
   ::= {er1645v2TTmplCiGreEntry 455081984}

er1645v2TTmplCiGreBrPrivateMode OBJECT-TYPE
   SYNTAX      INTEGER
               {
               disabled (0),
               enabled (1)
               }
   MAX-ACCESS  read-write
   STATUS      current
   DESCRIPTION
      "Path: tunnels.editConf.ipsecGreTunnels.bridging.privateMode

       Possibilities:
               disabled   (0)
               enabled   (1)"
   ::= {er1645v2TTmplCiGreEntry 459538432}

er1645v2TTmplCiGreBrLearning OBJECT-TYPE
   SYNTAX      INTEGER
               {
               disabled (0),
               enabled (1)
               }
   MAX-ACCESS  read-write
   STATUS      current
   DESCRIPTION
      "Path: tunnels.editConf.ipsecGreTunnels.bridging.learning

       Possibilities:
               disabled   (0)
               enabled   (1)"
   ::= {er1645v2TTmplCiGreEntry 456130560}

er1645v2TTmplCiGreBrMaxCacheSize OBJECT-TYPE
   SYNTAX      INTEGER
               {
               unlimited (0)
               }
   MAX-ACCESS  read-write
   STATUS      current
   DESCRIPTION
      "Path: tunnels.editConf.ipsecGreTunnels.bridging.maxCacheSize

       Possibilities:
               unlimited   (0)"
   ::= {er1645v2TTmplCiGreEntry 456392704}

er1645v2TTmplCiGreBrRelearnDropOnRelearn OBJECT-TYPE
   SYNTAX      INTEGER
               {
               disabled (0),
               enabled (1)
               }
   MAX-ACCESS  read-write
   STATUS      current
   DESCRIPTION
      "Path: tunnels.editConf.ipsecGreTunnels.bridging.relearn.dropOnRelearn

       Possibilities:
               disabled   (0)
               enabled   (1)"
   ::= {er1645v2TTmplCiGreEntry 456655872}

er1645v2TTmplCiGreBrRelearnShutdownThreshold OBJECT-TYPE
   SYNTAX      Integer32
   MAX-ACCESS  read-write
   STATUS      current
   DESCRIPTION
      "Path: tunnels.editConf.ipsecGreTunnels.bridging.relearn.shutdownThreshold"
   ::= {er1645v2TTmplCiGreEntry 456656896}

er1645v2TTmplCiGreBrRelearnShutdownTime OBJECT-TYPE
   SYNTAX      TimeTicks
   MAX-ACCESS  read-write
   STATUS      current
   DESCRIPTION
      "Path: tunnels.editConf.ipsecGreTunnels.bridging.relearn.shutdownTime

       Time in centi-second."
   ::= {er1645v2TTmplCiGreEntry 456657920}

er1645v2TTmplCiGreBrRelearnLoopDetection OBJECT-TYPE
   SYNTAX      INTEGER
               {
               disabled (0),
               passive (1),
               active (2)
               }
   MAX-ACCESS  read-write
   STATUS      current
   DESCRIPTION
      "Path: tunnels.editConf.ipsecGreTunnels.bridging.relearn.loopDetection

       Possibilities:
               disabled   (0)
               passive   (1)
               active   (2)"
   ::= {er1645v2TTmplCiGreEntry 456658944}

er1645v2TTmplCiGreBrRelearnLoopDetectionInterval OBJECT-TYPE
   SYNTAX      TimeTicks
   MAX-ACCESS  read-write
   STATUS      current
   DESCRIPTION
      "Path: tunnels.editConf.ipsecGreTunnels.bridging.relearn.loopDetectionInterval

       Time in centi-second."
   ::= {er1645v2TTmplCiGreEntry 456659968}

er1645v2TTmplCiGreBrVlanMemberShip OBJECT-TYPE
   SYNTAX      INTEGER
               {
               all (0),
               none (1),
               grouped (2)
               }
   MAX-ACCESS  read-write
   STATUS      current
   DESCRIPTION
      "Path: tunnels.editConf.ipsecGreTunnels.bridging.vlanMemberShip

       Possibilities:
               all   (0)
               none   (1)
               grouped   (2)"
   ::= {er1645v2TTmplCiGreEntry 457965568}

er1645v2TTmplCiGreBrVlTUntaggedAction OBJECT-TYPE
   SYNTAX      INTEGER
               {
               discard (0),
               accept (1),
               tag (2)
               }
   MAX-ACCESS  read-write
   STATUS      current
   DESCRIPTION
      "Path: tunnels.editConf.ipsecGreTunnels.bridging.vlanTagging.untagged.action

       Possibilities:
               discard   (0)
               accept   (1)
               tag   (2)"
   ::= {er1645v2TTmplCiGreEntry 459055104}

er1645v2TTmplCiGreBrVlTUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: tunnels.editConf.ipsecGreTunnels.bridging.vlanTagging.untagged.tagInfo.tpid

       Possibilities:
               dot1Q   (33024)
               dot1ad   (34984)
               0x9100   (37120)
               0x9200   (37376)
               0x9300   (37632)"
   ::= {er1645v2TTmplCiGreEntry 459059712}

er1645v2TTmplCiGreBrVlTUntaggedTagInfoVid OBJECT-TYPE
   SYNTAX      Integer32
   MAX-ACCESS  read-write
   STATUS      current
   DESCRIPTION
      "Path: tunnels.editConf.ipsecGreTunnels.bridging.vlanTagging.untagged.tagInfo.vid"
   ::= {er1645v2TTmplCiGreEntry 459060224}

er1645v2TTmplCiGreBrVlTUnknownVlansAction OBJECT-TYPE
   SYNTAX      INTEGER
               {
               discard (0),
               accept (1),
               tag (2)
               }
   MAX-ACCESS  read-write
   STATUS      current
   DESCRIPTION
      "Path: tunnels.editConf.ipsecGreTunnels.bridging.vlanTagging.unknownVlans.action

       Possibilities:
               discard   (0)
               accept   (1)
               tag   (2)"
   ::= {er1645v2TTmplCiGreEntry 459120640}

er1645v2TTmplCiGreBrVlTUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: tunnels.editConf.ipsecGreTunnels.bridging.vlanTagging.unknownVlans.tagInfo.tpid

       Possibilities:
               dot1Q   (33024)
               dot1ad   (34984)
               0x9100   (37120)
               0x9200   (37376)
               0x9300   (37632)"
   ::= {er1645v2TTmplCiGreEntry 459125248}

er1645v2TTmplCiGreBrVlTUnknownVlansTagInfoVid OBJECT-TYPE
   SYNTAX      Integer32
   MAX-ACCESS  read-write
   STATUS      current
   DESCRIPTION
      "Path: tunnels.editConf.ipsecGreTunnels.bridging.vlanTagging.unknownVlans.tagInfo.vid"
   ::= {er1645v2TTmplCiGreEntry 459125760}

er1645v2TTmplCiGreBrDot1adType OBJECT-TYPE
   SYNTAX      INTEGER
               {
               slOPTg (0),
               cPort (4),
               sPort (1),
               nni (2)
               }
   MAX-ACCESS  read-write
   STATUS      current
   DESCRIPTION
      "Path: tunnels.editConf.ipsecGreTunnels.bridging.dot1ad.type

       Possibilities:
               <OPT>   (0)
               cPort   (4)
               sPort   (1)
               nni   (2)"
   ::= {er1645v2TTmplCiGreEntry 460850176}

er1645v2TTmplCiGreBrPriority OBJECT-TYPE
   SYNTAX      Integer32
   MAX-ACCESS  read-write
   STATUS      current
   DESCRIPTION
      "Path: tunnels.editConf.ipsecGreTunnels.bridging.priority"
   ::= {er1645v2TTmplCiGreEntry 453509120}

er1645v2TTmplCiGreBrPathCost OBJECT-TYPE
   SYNTAX      Integer32
   MAX-ACCESS  read-write
   STATUS      current
   DESCRIPTION
      "Path: tunnels.editConf.ipsecGreTunnels.bridging.pathCost"
   ::= {er1645v2TTmplCiGreEntry 453771264}

er1645v2TTmplCiGreBrInternalPathCost OBJECT-TYPE
   SYNTAX      Integer32
   MAX-ACCESS  read-write
   STATUS      current
   DESCRIPTION
      "Path: tunnels.editConf.ipsecGreTunnels.bridging.internalPathCost"
   ::= {er1645v2TTmplCiGreEntry 457703424}

er1645v2TTmplCiGreBrTCD OBJECT-TYPE
   SYNTAX      INTEGER
               {
               disabled (0),
               enabled (1)
               }
   MAX-ACCESS  read-write
   STATUS      current
   DESCRIPTION
      "Path: tunnels.editConf.ipsecGreTunnels.bridging.topologyChangeDetection

       Possibilities:
               disabled   (0)
               enabled   (1)"
   ::= {er1645v2TTmplCiGreEntry 454033408}

er1645v2TTmplCiGreBrRestrictedRole OBJECT-TYPE
   SYNTAX      INTEGER
               {
               disabled (0),
               enabled (1)
               }
   MAX-ACCESS  read-write
   STATUS      current
   DESCRIPTION
      "Path: tunnels.editConf.ipsecGreTunnels.bridging.restrictedRole

       Possibilities:
               disabled   (0)
               enabled   (1)"
   ::= {er1645v2TTmplCiGreEntry 458227712}

er1645v2TTmplCiGreBrAdminEdge OBJECT-TYPE
   SYNTAX      INTEGER
               {
               disabled (0),
               enabled (1)
               }
   MAX-ACCESS  read-write
   STATUS      current
   DESCRIPTION
      "Path: tunnels.editConf.ipsecGreTunnels.bridging.adminEdge

       Possibilities:
               disabled   (0)
               enabled   (1)"
   ::= {er1645v2TTmplCiGreEntry 457179136}

er1645v2TTmplCiGreBrOamMacDeviceMac OBJECT-TYPE
   SYNTAX      DisplayString
   MAX-ACCESS  read-write
   STATUS      current
   DESCRIPTION
      "Path: tunnels.editConf.ipsecGreTunnels.bridging.ethOam.macAddress.deviceMac"
   ::= {er1645v2TTmplCiGreEntry 458506496}

er1645v2TTmplCiGreBrOamMacUserMac OBJECT-TYPE
   SYNTAX      OCTET STRING
   MAX-ACCESS  read-write
   STATUS      current
   DESCRIPTION
      "Path: tunnels.editConf.ipsecGreTunnels.bridging.ethOam.macAddress.userMac

       MAC address."
   ::= {er1645v2TTmplCiGreEntry 458506368}

er1645v2TTmplCiGreBrOamMacBridgeMac OBJECT-TYPE
   SYNTAX      DisplayString
   MAX-ACCESS  read-write
   STATUS      current
   DESCRIPTION
      "Path: tunnels.editConf.ipsecGreTunnels.bridging.ethOam.macAddress.bridgeMac"
   ::= {er1645v2TTmplCiGreEntry 458506432}

er1645v2TTmplCiGreBrMgmtInline OBJECT-TYPE
   SYNTAX      INTEGER
               {
               disabled (0),
               enabled (1)
               }
   MAX-ACCESS  read-write
   STATUS      current
   DESCRIPTION
      "Path: tunnels.editConf.ipsecGreTunnels.bridging.mgmtInline

       Possibilities:
               disabled   (0)
               enabled   (1)"
   ::= {er1645v2TTmplCiGreEntry 458752000}

er1645v2TTmplCiGreBrL2ptMode OBJECT-TYPE
   SYNTAX      INTEGER
               {
               disabled (0),
               enabled (1)
               }
   MAX-ACCESS  read-write
   STATUS      current
   DESCRIPTION
      "Path: tunnels.editConf.ipsecGreTunnels.bridging.l2ProtTunnel.mode

       Possibilities:
               disabled   (0)
               enabled   (1)"
   ::= {er1645v2TTmplCiGreEntry 459292672}

er1645v2TTmplCiGreBrL2ptProtocols OBJECT-TYPE
   SYNTAX      Integer32
   MAX-ACCESS  read-write
   STATUS      current
   DESCRIPTION
      "Path: tunnels.editConf.ipsecGreTunnels.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1645v2TTmplCiGreEntry 459309056}

er1645v2TTmplCiGreBrL2ptDestMac OBJECT-TYPE
   SYNTAX      OCTET STRING
   MAX-ACCESS  read-write
   STATUS      current
   DESCRIPTION
      "Path: tunnels.editConf.ipsecGreTunnels.bridging.l2ProtTunnel.destinationMac

       MAC address."
   ::= {er1645v2TTmplCiGreEntry 459325440}

er1645v2TTmplCiGreBrL2ptCos OBJECT-TYPE
   SYNTAX      INTEGER
               {
               unchanged (255)
               }
   MAX-ACCESS  read-write
   STATUS      current
   DESCRIPTION
      "Path: tunnels.editConf.ipsecGreTunnels.bridging.l2ProtTunnel.cos

       Possibilities:
               unchanged   (255)"
   ::= {er1645v2TTmplCiGreEntry 459341824}

er1645v2TTmplCiGreBrL2ptDropThrStp OBJECT-TYPE
   SYNTAX      INTEGER
               {
               unlimited (0)
               }
   UNITS       "packets/sec"
   MAX-ACCESS  read-write
   STATUS      current
   DESCRIPTION
      "Path: tunnels.editConf.ipsecGreTunnels.bridging.l2ProtTunnel.dropThresholds.stp

       unit name = packets/sec

       Possibilities:
               unlimited   (0)"
   ::= {er1645v2TTmplCiGreEntry 459358272}

er1645v2TTmplCiGreBrL2ptDropThrLldp OBJECT-TYPE
   SYNTAX      INTEGER
               {
               unlimited (0)
               }
   UNITS       "packets/sec"
   MAX-ACCESS  read-write
   STATUS      current
   DESCRIPTION
      "Path: tunnels.editConf.ipsecGreTunnels.bridging.l2ProtTunnel.dropThresholds.lldp

       unit name = packets/sec

       Possibilities:
               unlimited   (0)"
   ::= {er1645v2TTmplCiGreEntry 459358336}

er1645v2TTmplCiGreBrL2ptDropThrOam OBJECT-TYPE
   SYNTAX      INTEGER
               {
               unlimited (0)
               }
   UNITS       "packets/sec"
   MAX-ACCESS  read-write
   STATUS      current
   DESCRIPTION
      "Path: tunnels.editConf.ipsecGreTunnels.bridging.l2ProtTunnel.dropThresholds.oam

       unit name = packets/sec

       Possibilities:
               unlimited   (0)"
   ::= {er1645v2TTmplCiGreEntry 459358400}

er1645v2TTmplCiGreBrL2ptDropThrCdp OBJECT-TYPE
   SYNTAX      INTEGER
               {
               unlimited (0)
               }
   UNITS       "packets/sec"
   MAX-ACCESS  read-write
   STATUS      current
   DESCRIPTION
      "Path: tunnels.editConf.ipsecGreTunnels.bridging.l2ProtTunnel.dropThresholds.cdp

       unit name = packets/sec

       Possibilities:
               unlimited   (0)"
   ::= {er1645v2TTmplCiGreEntry 459358464}

er1645v2TTmplCiGreBrL2ptDropThrVtp OBJECT-TYPE
   SYNTAX      INTEGER
               {
               unlimited (0)
               }
   UNITS       "packets/sec"
   MAX-ACCESS  read-write
   STATUS      current
   DESCRIPTION
      "Path: tunnels.editConf.ipsecGreTunnels.bridging.l2ProtTunnel.dropThresholds.vtp

       unit name = packets/sec

       Possibilities:
               unlimited   (0)"
   ::= {er1645v2TTmplCiGreEntry 459358528}

er1645v2TTmplCiGreBrL2ptDropThrLacp OBJECT-TYPE
   SYNTAX      INTEGER
               {
               unlimited (0)
               }
   UNITS       "packets/sec"
   MAX-ACCESS  read-write
   STATUS      current
   DESCRIPTION
      "Path: tunnels.editConf.ipsecGreTunnels.bridging.l2ProtTunnel.dropThresholds.lacp

       unit name = packets/sec

       Possibilities:
               unlimited   (0)"
   ::= {er1645v2TTmplCiGreEntry 459358592}

er1645v2TTmplCiGreBrL2ptDropThrEfmOam OBJECT-TYPE
   SYNTAX      INTEGER
               {
               unlimited (0)
               }
   UNITS       "packets/sec"
   MAX-ACCESS  read-write
   STATUS      current
   DESCRIPTION
      "Path: tunnels.editConf.ipsecGreTunnels.bridging.l2ProtTunnel.dropThresholds.efmOam

       unit name = packets/sec

       Possibilities:
               unlimited   (0)"
   ::= {er1645v2TTmplCiGreEntry 459358656}

er1645v2TTmplCiGreBrL2ptDropThrPvst OBJECT-TYPE
   SYNTAX      INTEGER
               {
               unlimited (0)
               }
   UNITS       "packets/sec"
   MAX-ACCESS  read-write
   STATUS      current
   DESCRIPTION
      "Path: tunnels.editConf.ipsecGreTunnels.bridging.l2ProtTunnel.dropThresholds.pvst

       unit name = packets/sec

       Possibilities:
               unlimited   (0)"
   ::= {er1645v2TTmplCiGreEntry 459358720}

er1645v2TTmplCiGreBrL2ptDropThrMmrp OBJECT-TYPE
   SYNTAX      INTEGER
               {
               unlimited (0)
               }
   UNITS       "packets/sec"
   MAX-ACCESS  read-write
   STATUS      current
   DESCRIPTION
      "Path: tunnels.editConf.ipsecGreTunnels.bridging.l2ProtTunnel.dropThresholds.mmrp

       unit name = packets/sec

       Possibilities:
               unlimited   (0)"
   ::= {er1645v2TTmplCiGreEntry 459358784}

er1645v2TTmplCiGreBrL2ptDropThrMvrp OBJECT-TYPE
   SYNTAX      INTEGER
               {
               unlimited (0)
               }
   UNITS       "packets/sec"
   MAX-ACCESS  read-write
   STATUS      current
   DESCRIPTION
      "Path: tunnels.editConf.ipsecGreTunnels.bridging.l2ProtTunnel.dropThresholds.mvrp

       unit name = packets/sec

       Possibilities:
               unlimited   (0)"
   ::= {er1645v2TTmplCiGreEntry 459358848}

er1645v2TTmplCiGreBrL2ptDropThrGvrp OBJECT-TYPE
   SYNTAX      INTEGER
               {
               unlimited (0)
               }
   UNITS       "packets/sec"
   MAX-ACCESS  read-write
   STATUS      current
   DESCRIPTION
      "Path: tunnels.editConf.ipsecGreTunnels.bridging.l2ProtTunnel.dropThresholds.gvrp

       unit name = packets/sec

       Possibilities:
               unlimited   (0)"
   ::= {er1645v2TTmplCiGreEntry 459358912}

er1645v2TTmplCiGreBrL2ptDropThrGmrp OBJECT-TYPE
   SYNTAX      INTEGER
               {
               unlimited (0)
               }
   UNITS       "packets/sec"
   MAX-ACCESS  read-write
   STATUS      current
   DESCRIPTION
      "Path: tunnels.editConf.ipsecGreTunnels.bridging.l2ProtTunnel.dropThresholds.gmrp

       unit name = packets/sec

       Possibilities:
               unlimited   (0)"
   ::= {er1645v2TTmplCiGreEntry 459358976}

er1645v2TTmplCiGreBrL2ptDropThrDtp OBJECT-TYPE
   SYNTAX      INTEGER
               {
               unlimited (0)
               }
   UNITS       "packets/sec"
   MAX-ACCESS  read-write
   STATUS      current
   DESCRIPTION
      "Path: tunnels.editConf.ipsecGreTunnels.bridging.l2ProtTunnel.dropThresholds.dtp

       unit name = packets/sec

       Possibilities:
               unlimited   (0)"
   ::= {er1645v2TTmplCiGreEntry 459359040}

er1645v2TTmplCiGreBrL2ptDropThrPagp OBJECT-TYPE
   SYNTAX      INTEGER
               {
               unlimited (0)
               }
   UNITS       "packets/sec"
   MAX-ACCESS  read-write
   STATUS      current
   DESCRIPTION
      "Path: tunnels.editConf.ipsecGreTunnels.bridging.l2ProtTunnel.dropThresholds.pagp

       unit name = packets/sec

       Possibilities:
               unlimited   (0)"
   ::= {er1645v2TTmplCiGreEntry 459359104}

er1645v2TTmplCiGreBrL2ptDropThrUdld OBJECT-TYPE
   SYNTAX      INTEGER
               {
               unlimited (0)
               }
   UNITS       "packets/sec"
   MAX-ACCESS  read-write
   STATUS      current
   DESCRIPTION
      "Path: tunnels.editConf.ipsecGreTunnels.bridging.l2ProtTunnel.dropThresholds.udld

       unit name = packets/sec

       Possibilities:
               unlimited   (0)"
   ::= {er1645v2TTmplCiGreEntry 459359168}

er1645v2TTmplCiGreVirtEthernetVirtualEthernet OBJECT-TYPE
   SYNTAX      DisplayString
   MAX-ACCESS  read-write
   STATUS      current
   DESCRIPTION
      "Path: tunnels.editConf.ipsecGreTunnels.virtEthernet.virtualEthernet"
   ::= {er1645v2TTmplCiGreEntry 151060480}

er1645v2TTmplCiGreGreLocalIpAddress OBJECT-TYPE
   SYNTAX      IpAddress
   MAX-ACCESS  read-write
   STATUS      current
   DESCRIPTION
      "Path: tunnels.editConf.ipsecGreTunnels.gre.localIpAddress"
   ::= {er1645v2TTmplCiGreEntry 587268096}

er1645v2TTmplCiGreGreLocalInterface OBJECT-TYPE
   SYNTAX      DisplayString
   MAX-ACCESS  read-write
   STATUS      current
   DESCRIPTION
      "Path: tunnels.editConf.ipsecGreTunnels.gre.localInterface"
   ::= {er1645v2TTmplCiGreEntry 588251136}

er1645v2TTmplCiGreGreRemoteIpAddress OBJECT-TYPE
   SYNTAX      IpAddress
   MAX-ACCESS  read-write
   STATUS      current
   DESCRIPTION
      "Path: tunnels.editConf.ipsecGreTunnels.gre.remoteIpAddress"
   ::= {er1645v2TTmplCiGreEntry 587333632}

er1645v2TTmplCiGreGreRemoteDnsName OBJECT-TYPE
   SYNTAX      DisplayString
   MAX-ACCESS  read-write
   STATUS      current
   DESCRIPTION
      "Path: tunnels.editConf.ipsecGreTunnels.gre.remoteDnsName"
   ::= {er1645v2TTmplCiGreEntry 587399168}

er1645v2TTmplCiGreGreIpsFdx OBJECT-TYPE
   SYNTAX      DisplayString
   MAX-ACCESS  read-write
   STATUS      current
   DESCRIPTION
      "Path: tunnels.editConf.ipsecGreTunnels.gre.ipsec.fdxManualSA"
   ::= {er1645v2TTmplCiGreEntry 587472896}

er1645v2TTmplCiGreGreIpsHdxIn OBJECT-TYPE
   SYNTAX      DisplayString
   MAX-ACCESS  read-write
   STATUS      current
   DESCRIPTION
      "Path: tunnels.editConf.ipsecGreTunnels.gre.ipsec.hdxManualSA.inbound"
   ::= {er1645v2TTmplCiGreEntry 587481120}

er1645v2TTmplCiGreGreIpsHdxOut OBJECT-TYPE
   SYNTAX      DisplayString
   MAX-ACCESS  read-write
   STATUS      current
   DESCRIPTION
      "Path: tunnels.editConf.ipsecGreTunnels.gre.ipsec.hdxManualSA.outbound"
   ::= {er1645v2TTmplCiGreEntry 587481152}

er1645v2TTmplCiGreGreIpsPsCfg OBJECT-TYPE
   SYNTAX      DisplayString
   MAX-ACCESS  read-write
   STATUS      current
   DESCRIPTION
      "Path: tunnels.editConf.ipsecGreTunnels.gre.ipsec.ikePresharedSA.ikeSA"
   ::= {er1645v2TTmplCiGreEntry 587489792}

er1645v2TTmplCiGreGreIpsPsLIdIp OBJECT-TYPE
   SYNTAX      IpAddress
   MAX-ACCESS  read-write
   STATUS      current
   DESCRIPTION
      "Path: tunnels.editConf.ipsecGreTunnels.gre.ipsec.ikePresharedSA.localId.ipAddress"
   ::= {er1645v2TTmplCiGreEntry 587490306}

er1645v2TTmplCiGreGreIpsPsLIdHn OBJECT-TYPE
   SYNTAX      DisplayString
   MAX-ACCESS  read-write
   STATUS      current
   DESCRIPTION
      "Path: tunnels.editConf.ipsecGreTunnels.gre.ipsec.ikePresharedSA.localId.hostName"
   ::= {er1645v2TTmplCiGreEntry 587490308}

er1645v2TTmplCiGreGreIpsPsLIdUn OBJECT-TYPE
   SYNTAX      DisplayString
   MAX-ACCESS  read-write
   STATUS      current
   DESCRIPTION
      "Path: tunnels.editConf.ipsecGreTunnels.gre.ipsec.ikePresharedSA.localId.user"
   ::= {er1645v2TTmplCiGreEntry 587490310}

er1645v2TTmplCiGreGreIpsPsRIdIp OBJECT-TYPE
   SYNTAX      IpAddress
   MAX-ACCESS  read-write
   STATUS      current
   DESCRIPTION
      "Path: tunnels.editConf.ipsecGreTunnels.gre.ipsec.ikePresharedSA.remoteId.ipAddress"
   ::= {er1645v2TTmplCiGreEntry 587490818}

er1645v2TTmplCiGreGreIpsPsRIdHn OBJECT-TYPE
   SYNTAX      DisplayString
   MAX-ACCESS  read-write
   STATUS      current
   DESCRIPTION
      "Path: tunnels.editConf.ipsecGreTunnels.gre.ipsec.ikePresharedSA.remoteId.hostName"
   ::= {er1645v2TTmplCiGreEntry 587490820}

er1645v2TTmplCiGreGreIpsPsRIdUn OBJECT-TYPE
   SYNTAX      DisplayString
   MAX-ACCESS  read-write
   STATUS      current
   DESCRIPTION
      "Path: tunnels.editConf.ipsecGreTunnels.gre.ipsec.ikePresharedSA.remoteId.user"
   ::= {er1645v2TTmplCiGreEntry 587490822}

er1645v2TTmplCiGreGreIpsPsKey OBJECT-TYPE
   SYNTAX      DisplayString
   MAX-ACCESS  read-write
   STATUS      current
   DESCRIPTION
      "Path: tunnels.editConf.ipsecGreTunnels.gre.ipsec.ikePresharedSA.preSharedKey"
   ::= {er1645v2TTmplCiGreEntry 587491328}

er1645v2TTmplCiGreGreIpsPsEncMKey OBJECT-TYPE
   SYNTAX      INTEGER
               {
               none (1),
               encrypt (2),
               encType1 (3),
               invalid (128)
               }
   MAX-ACCESS  read-write
   STATUS      current
   DESCRIPTION
      "Path: tunnels.editConf.ipsecGreTunnels.gre.ipsec.ikePresharedSA.encModePreSharedKey

       Possibilities:
               none   (1)
               encrypt   (2)
               encType1   (3)
               invalid   (128)"
   ::= {er1645v2TTmplCiGreEntry 587492352}

er1645v2TTmplCiGreGreIpsPsEncKey OBJECT-TYPE
   SYNTAX      DisplayString
   MAX-ACCESS  read-write
   STATUS      current
   DESCRIPTION
      "Path: tunnels.editConf.ipsecGreTunnels.gre.ipsec.ikePresharedSA.encPreSharedKey"
   ::= {er1645v2TTmplCiGreEntry 587492864}

er1645v2TTmplCiGreGreIpsPsPIdProt OBJECT-TYPE
   SYNTAX      INTEGER
               {
               any (0),
               aH (51),
               eGP (8),
               eSP (50),
               gRE (47),
               iCMP (1),
               iGP (9),
               iGMP (2),
               iGRP (88),
               iPinIP (4),
               oSPF (89),
               uDP (17),
               rSVP (46),
               tCP (6),
               tCPestablished (255)
               }
   MAX-ACCESS  read-write
   STATUS      current
   DESCRIPTION
      "Path: tunnels.editConf.ipsecGreTunnels.gre.ipsec.ikePresharedSA.proxyId.ipProtocol

       Possibilities:
               any   (0)
               AH   (51)
               EGP   (8)
               ESP   (50)
               GRE   (47)
               ICMP   (1)
               IGP   (9)
               IGMP   (2)
               IGRP   (88)
               IPinIP   (4)
               OSPF   (89)
               UDP   (17)
               RSVP   (46)
               TCP   (6)
               TCPestablished   (255)"
   ::= {er1645v2TTmplCiGreEntry 587491872}

er1645v2TTmplCiGreGreIpsPsPIdLocAddr OBJECT-TYPE
   SYNTAX      IpAddress
   MAX-ACCESS  read-write
   STATUS      current
   DESCRIPTION
      "Path: tunnels.editConf.ipsecGreTunnels.gre.ipsec.ikePresharedSA.proxyId.localIpAddress"
   ::= {er1645v2TTmplCiGreEntry 587491904}

er1645v2TTmplCiGreGreIpsPsPIdLocMask OBJECT-TYPE
   SYNTAX      IpAddress
   MAX-ACCESS  read-write
   STATUS      current
   DESCRIPTION
      "Path: tunnels.editConf.ipsecGreTunnels.gre.ipsec.ikePresharedSA.proxyId.localIpMask"
   ::= {er1645v2TTmplCiGreEntry 587491936}

er1645v2TTmplCiGreGreIpsPsPIdLocPort OBJECT-TYPE
   SYNTAX      INTEGER
               {
               any (0),
               bgp (179),
               bootpmdhcpmc (68),
               bootpmdhcpms (67),
               cpudpencap (2746),
               discard (9),
               domain (53),
               echo (7),
               ftp (21),
               ftpmdata (20),
               ftps (990),
               ftpsmdata (989),
               httpmalt (8080),
               https (443),
               imap (134),
               imap3 (220),
               imaps (993),
               ipsecmnatmt (4500),
               isakmp (500),
               l2tp (1701),
               ldap (389),
               microsoftmds (445),
               msmwbtmserver (3389),
               msnp (1863),
               nameserver (42),
               netbiosmdgm (138),
               netbiosmns (137),
               netbiosmssn (139),
               nntp (119),
               ntp (123),
               pop3 (110),
               pop3s (995),
               pptp (1723),
               router (520),
               rtsp (554),
               sip (5060),
               smtp (25),
               smtps (465),
               snmp (161),
               snmptrap (162),
               socks (1080),
               ssdpmuPnP (1900),
               ssh (22),
               syslog (514),
               telindus (1728),
               telnet (23),
               telnets (992),
               tftp (69),
               whip (8700),
               wwwmhttp (80),
               z39d50 (210)
               }
   MAX-ACCESS  read-write
   STATUS      current
   DESCRIPTION
      "Path: tunnels.editConf.ipsecGreTunnels.gre.ipsec.ikePresharedSA.proxyId.localIpPort

       Possibilities:
               any   (0)
               bgp   (179)
               bootp-dhcp-c   (68)
               bootp-dhcp-s   (67)
               cpudpencap   (2746)
               discard   (9)
               domain   (53)
               echo   (7)
               ftp   (21)
               ftp-data   (20)
               ftps   (990)
               ftps-data   (989)
               http-alt   (8080)
               https   (443)
               imap   (134)
               imap3   (220)
               imaps   (993)
               ipsec-nat-t   (4500)
               isakmp   (500)
               l2tp   (1701)
               ldap   (389)
               microsoft-ds   (445)
               ms-wbt-server   (3389)
               msnp   (1863)
               nameserver   (42)
               netbios-dgm   (138)
               netbios-ns   (137)
               netbios-ssn   (139)
               nntp   (119)
               ntp   (123)
               pop3   (110)
               pop3s   (995)
               pptp   (1723)
               router   (520)
               rtsp   (554)
               sip   (5060)
               smtp   (25)
               smtps   (465)
               snmp   (161)
               snmptrap   (162)
               socks   (1080)
               ssdp-uPnP   (1900)
               ssh   (22)
               syslog   (514)
               telindus   (1728)
               telnet   (23)
               telnets   (992)
               tftp   (69)
               whip   (8700)
               www-http   (80)
               z39.50   (210)"
   ::= {er1645v2TTmplCiGreEntry 587491968}

er1645v2TTmplCiGreGreIpsPsPIdRemAddr OBJECT-TYPE
   SYNTAX      IpAddress
   MAX-ACCESS  read-write
   STATUS      current
   DESCRIPTION
      "Path: tunnels.editConf.ipsecGreTunnels.gre.ipsec.ikePresharedSA.proxyId.remoteIpAddress"
   ::= {er1645v2TTmplCiGreEntry 587492000}

er1645v2TTmplCiGreGreIpsPsPIdRemMask OBJECT-TYPE
   SYNTAX      IpAddress
   MAX-ACCESS  read-write
   STATUS      current
   DESCRIPTION
      "Path: tunnels.editConf.ipsecGreTunnels.gre.ipsec.ikePresharedSA.proxyId.remoteIpMask"
   ::= {er1645v2TTmplCiGreEntry 587492032}

er1645v2TTmplCiGreGreIpsPsPIdRemPort OBJECT-TYPE
   SYNTAX      INTEGER
               {
               any (0),
               bgp (179),
               bootpmdhcpmc (68),
               bootpmdhcpms (67),
               cpudpencap (2746),
               discard (9),
               domain (53),
               echo (7),
               ftp (21),
               ftpmdata (20),
               ftps (990),
               ftpsmdata (989),
               httpmalt (8080),
               https (443),
               imap (134),
               imap3 (220),
               imaps (993),
               ipsecmnatmt (4500),
               isakmp (500),
               l2tp (1701),
               ldap (389),
               microsoftmds (445),
               msmwbtmserver (3389),
               msnp (1863),
               nameserver (42),
               netbiosmdgm (138),
               netbiosmns (137),
               netbiosmssn (139),
               nntp (119),
               ntp (123),
               pop3 (110),
               pop3s (995),
               pptp (1723),
               router (520),
               rtsp (554),
               sip (5060),
               smtp (25),
               smtps (465),
               snmp (161),
               snmptrap (162),
               socks (1080),
               ssdpmuPnP (1900),
               ssh (22),
               syslog (514),
               telindus (1728),
               telnet (23),
               telnets (992),
               tftp (69),
               whip (8700),
               wwwmhttp (80),
               z39d50 (210)
               }
   MAX-ACCESS  read-write
   STATUS      current
   DESCRIPTION
      "Path: tunnels.editConf.ipsecGreTunnels.gre.ipsec.ikePresharedSA.proxyId.remoteIpPort

       Possibilities:
               any   (0)
               bgp   (179)
               bootp-dhcp-c   (68)
               bootp-dhcp-s   (67)
               cpudpencap   (2746)
               discard   (9)
               domain   (53)
               echo   (7)
               ftp   (21)
               ftp-data   (20)
               ftps   (990)
               ftps-data   (989)
               http-alt   (8080)
               https   (443)
               imap   (134)
               imap3   (220)
               imaps   (993)
               ipsec-nat-t   (4500)
               isakmp   (500)
               l2tp   (1701)
               ldap   (389)
               microsoft-ds   (445)
               ms-wbt-server   (3389)
               msnp   (1863)
               nameserver   (42)
               netbios-dgm   (138)
               netbios-ns   (137)
               netbios-ssn   (139)
               nntp   (119)
               ntp   (123)
               pop3   (110)
               pop3s   (995)
               pptp   (1723)
               router   (520)
               rtsp   (554)
               sip   (5060)
               smtp   (25)
               smtps   (465)
               snmp   (161)
               snmptrap   (162)
               socks   (1080)
               ssdp-uPnP   (1900)
               ssh   (22)
               syslog   (514)
               telindus   (1728)
               telnet   (23)
               telnets   (992)
               tftp   (69)
               whip   (8700)
               www-http   (80)
               z39.50   (210)"
   ::= {er1645v2TTmplCiGreEntry 587492064}

er1645v2TTmplCiGreGreIpsCeCfg OBJECT-TYPE
   SYNTAX      DisplayString
   MAX-ACCESS  read-write
   STATUS      current
   DESCRIPTION
      "Path: tunnels.editConf.ipsecGreTunnels.gre.ipsec.ikeCertificateSA.ikeSA"
   ::= {er1645v2TTmplCiGreEntry 587497984}

er1645v2TTmplCiGreGreIpsCeLIdIp OBJECT-TYPE
   SYNTAX      IpAddress
   MAX-ACCESS  read-write
   STATUS      current
   DESCRIPTION
      "Path: tunnels.editConf.ipsecGreTunnels.gre.ipsec.ikeCertificateSA.localId.ipAddress"
   ::= {er1645v2TTmplCiGreEntry 587498498}

er1645v2TTmplCiGreGreIpsCeLIdHn OBJECT-TYPE
   SYNTAX      DisplayString
   MAX-ACCESS  read-write
   STATUS      current
   DESCRIPTION
      "Path: tunnels.editConf.ipsecGreTunnels.gre.ipsec.ikeCertificateSA.localId.hostName"
   ::= {er1645v2TTmplCiGreEntry 587498500}

er1645v2TTmplCiGreGreIpsCeLIdUn OBJECT-TYPE
   SYNTAX      DisplayString
   MAX-ACCESS  read-write
   STATUS      current
   DESCRIPTION
      "Path: tunnels.editConf.ipsecGreTunnels.gre.ipsec.ikeCertificateSA.localId.user"
   ::= {er1645v2TTmplCiGreEntry 587498502}

er1645v2TTmplCiGreGreIpsCeLIdDn OBJECT-TYPE
   SYNTAX      DisplayString
   MAX-ACCESS  read-write
   STATUS      current
   DESCRIPTION
      "Path: tunnels.editConf.ipsecGreTunnels.gre.ipsec.ikeCertificateSA.localId.derAsn1Dn"
   ::= {er1645v2TTmplCiGreEntry 587498504}

er1645v2TTmplCiGreGreIpsCeRIdIp OBJECT-TYPE
   SYNTAX      IpAddress
   MAX-ACCESS  read-write
   STATUS      current
   DESCRIPTION
      "Path: tunnels.editConf.ipsecGreTunnels.gre.ipsec.ikeCertificateSA.remoteId.ipAddress"
   ::= {er1645v2TTmplCiGreEntry 587499010}

er1645v2TTmplCiGreGreIpsCeRIdHn OBJECT-TYPE
   SYNTAX      DisplayString
   MAX-ACCESS  read-write
   STATUS      current
   DESCRIPTION
      "Path: tunnels.editConf.ipsecGreTunnels.gre.ipsec.ikeCertificateSA.remoteId.hostName"
   ::= {er1645v2TTmplCiGreEntry 587499012}

er1645v2TTmplCiGreGreIpsCeRIdUn OBJECT-TYPE
   SYNTAX      DisplayString
   MAX-ACCESS  read-write
   STATUS      current
   DESCRIPTION
      "Path: tunnels.editConf.ipsecGreTunnels.gre.ipsec.ikeCertificateSA.remoteId.user"
   ::= {er1645v2TTmplCiGreEntry 587499014}

er1645v2TTmplCiGreGreIpsCeRIdDn OBJECT-TYPE
   SYNTAX      DisplayString
   MAX-ACCESS  read-write
   STATUS      current
   DESCRIPTION
      "Path: tunnels.editConf.ipsecGreTunnels.gre.ipsec.ikeCertificateSA.remoteId.derAsn1Dn"
   ::= {er1645v2TTmplCiGreEntry 587499016}

er1645v2TTmplCiGreGreIpsCePIdProt OBJECT-TYPE
   SYNTAX      INTEGER
               {
               any (0),
               aH (51),
               eGP (8),
               eSP (50),
               gRE (47),
               iCMP (1),
               iGP (9),
               iGMP (2),
               iGRP (88),
               iPinIP (4),
               oSPF (89),
               uDP (17),
               rSVP (46),
               tCP (6),
               tCPestablished (255)
               }
   MAX-ACCESS  read-write
   STATUS      current
   DESCRIPTION
      "Path: tunnels.editConf.ipsecGreTunnels.gre.ipsec.ikeCertificateSA.proxyId.ipProtocol

       Possibilities:
               any   (0)
               AH   (51)
               EGP   (8)
               ESP   (50)
               GRE   (47)
               ICMP   (1)
               IGP   (9)
               IGMP   (2)
               IGRP   (88)
               IPinIP   (4)
               OSPF   (89)
               UDP   (17)
               RSVP   (46)
               TCP   (6)
               TCPestablished   (255)"
   ::= {er1645v2TTmplCiGreEntry 587500064}

er1645v2TTmplCiGreGreIpsCePIdLocAddr OBJECT-TYPE
   SYNTAX      IpAddress
   MAX-ACCESS  read-write
   STATUS      current
   DESCRIPTION
      "Path: tunnels.editConf.ipsecGreTunnels.gre.ipsec.ikeCertificateSA.proxyId.localIpAddress"
   ::= {er1645v2TTmplCiGreEntry 587500096}

er1645v2TTmplCiGreGreIpsCePIdLocMask OBJECT-TYPE
   SYNTAX      IpAddress
   MAX-ACCESS  read-write
   STATUS      current
   DESCRIPTION
      "Path: tunnels.editConf.ipsecGreTunnels.gre.ipsec.ikeCertificateSA.proxyId.localIpMask"
   ::= {er1645v2TTmplCiGreEntry 587500128}

er1645v2TTmplCiGreGreIpsCePIdLocPort OBJECT-TYPE
   SYNTAX      INTEGER
               {
               any (0),
               bgp (179),
               bootpmdhcpmc (68),
               bootpmdhcpms (67),
               cpudpencap (2746),
               discard (9),
               domain (53),
               echo (7),
               ftp (21),
               ftpmdata (20),
               ftps (990),
               ftpsmdata (989),
               httpmalt (8080),
               https (443),
               imap (134),
               imap3 (220),
               imaps (993),
               ipsecmnatmt (4500),
               isakmp (500),
               l2tp (1701),
               ldap (389),
               microsoftmds (445),
               msmwbtmserver (3389),
               msnp (1863),
               nameserver (42),
               netbiosmdgm (138),
               netbiosmns (137),
               netbiosmssn (139),
               nntp (119),
               ntp (123),
               pop3 (110),
               pop3s (995),
               pptp (1723),
               router (520),
               rtsp (554),
               sip (5060),
               smtp (25),
               smtps (465),
               snmp (161),
               snmptrap (162),
               socks (1080),
               ssdpmuPnP (1900),
               ssh (22),
               syslog (514),
               telindus (1728),
               telnet (23),
               telnets (992),
               tftp (69),
               whip (8700),
               wwwmhttp (80),
               z39d50 (210)
               }
   MAX-ACCESS  read-write
   STATUS      current
   DESCRIPTION
      "Path: tunnels.editConf.ipsecGreTunnels.gre.ipsec.ikeCertificateSA.proxyId.localIpPort

       Possibilities:
               any   (0)
               bgp   (179)
               bootp-dhcp-c   (68)
               bootp-dhcp-s   (67)
               cpudpencap   (2746)
               discard   (9)
               domain   (53)
               echo   (7)
               ftp   (21)
               ftp-data   (20)
               ftps   (990)
               ftps-data   (989)
               http-alt   (8080)
               https   (443)
               imap   (134)
               imap3   (220)
               imaps   (993)
               ipsec-nat-t   (4500)
               isakmp   (500)
               l2tp   (1701)
               ldap   (389)
               microsoft-ds   (445)
               ms-wbt-server   (3389)
               msnp   (1863)
               nameserver   (42)
               netbios-dgm   (138)
               netbios-ns   (137)
               netbios-ssn   (139)
               nntp   (119)
               ntp   (123)
               pop3   (110)
               pop3s   (995)
               pptp   (1723)
               router   (520)
               rtsp   (554)
               sip   (5060)
               smtp   (25)
               smtps   (465)
               snmp   (161)
               snmptrap   (162)
               socks   (1080)
               ssdp-uPnP   (1900)
               ssh   (22)
               syslog   (514)
               telindus   (1728)
               telnet   (23)
               telnets   (992)
               tftp   (69)
               whip   (8700)
               www-http   (80)
               z39.50   (210)"
   ::= {er1645v2TTmplCiGreEntry 587500160}

er1645v2TTmplCiGreGreIpsCePIdRemAddr OBJECT-TYPE
   SYNTAX      IpAddress
   MAX-ACCESS  read-write
   STATUS      current
   DESCRIPTION
      "Path: tunnels.editConf.ipsecGreTunnels.gre.ipsec.ikeCertificateSA.proxyId.remoteIpAddress"
   ::= {er1645v2TTmplCiGreEntry 587500192}

er1645v2TTmplCiGreGreIpsCePIdRemMask OBJECT-TYPE
   SYNTAX      IpAddress
   MAX-ACCESS  read-write
   STATUS      current
   DESCRIPTION
      "Path: tunnels.editConf.ipsecGreTunnels.gre.ipsec.ikeCertificateSA.proxyId.remoteIpMask"
   ::= {er1645v2TTmplCiGreEntry 587500224}

er1645v2TTmplCiGreGreIpsCePIdRemPort OBJECT-TYPE
   SYNTAX      INTEGER
               {
               any (0),
               bgp (179),
               bootpmdhcpmc (68),
               bootpmdhcpms (67),
               cpudpencap (2746),
               discard (9),
               domain (53),
               echo (7),
               ftp (21),
               ftpmdata (20),
               ftps (990),
               ftpsmdata (989),
               httpmalt (8080),
               https (443),
               imap (134),
               imap3 (220),
               imaps (993),
               ipsecmnatmt (4500),
               isakmp (500),
               l2tp (1701),
               ldap (389),
               microsoftmds (445),
               msmwbtmserver (3389),
               msnp (1863),
               nameserver (42),
               netbiosmdgm (138),
               netbiosmns (137),
               netbiosmssn (139),
               nntp (119),
               ntp (123),
               pop3 (110),
               pop3s (995),
               pptp (1723),
               router (520),
               rtsp (554),
               sip (5060),
               smtp (25),
               smtps (465),
               snmp (161),
               snmptrap (162),
               socks (1080),
               ssdpmuPnP (1900),
               ssh (22),
               syslog (514),
               telindus (1728),
               telnet (23),
               telnets (992),
               tftp (69),
               whip (8700),
               wwwmhttp (80),
               z39d50 (210)
               }
   MAX-ACCESS  read-write
   STATUS      current
   DESCRIPTION
      "Path: tunnels.editConf.ipsecGreTunnels.gre.ipsec.ikeCertificateSA.proxyId.remoteIpPort

       Possibilities:
               any   (0)
               bgp   (179)
               bootp-dhcp-c   (68)
               bootp-dhcp-s   (67)
               cpudpencap   (2746)
               discard   (9)
               domain   (53)
               echo   (7)
               ftp   (21)
               ftp-data   (20)
               ftps   (990)
               ftps-data   (989)
               http-alt   (8080)
               https   (443)
               imap   (134)
               imap3   (220)
               imaps   (993)
               ipsec-nat-t   (4500)
               isakmp   (500)
               l2tp   (1701)
               ldap   (389)
               microsoft-ds   (445)
               ms-wbt-server   (3389)
               msnp   (1863)
               nameserver   (42)
               netbios-dgm   (138)
               netbios-ns   (137)
               netbios-ssn   (139)
               nntp   (119)
               ntp   (123)
               pop3   (110)
               pop3s   (995)
               pptp   (1723)
               router   (520)
               rtsp   (554)
               sip   (5060)
               smtp   (25)
               smtps   (465)
               snmp   (161)
               snmptrap   (162)
               socks   (1080)
               ssdp-uPnP   (1900)
               ssh   (22)
               syslog   (514)
               telindus   (1728)
               telnet   (23)
               telnets   (992)
               tftp   (69)
               whip   (8700)
               www-http   (80)
               z39.50   (210)"
   ::= {er1645v2TTmplCiGreEntry 587500256}

er1645v2TTmplCiGreGreKpAlMode OBJECT-TYPE
   SYNTAX      INTEGER
               {
               disabled (0),
               enabled (1)
               }
   MAX-ACCESS  read-write
   STATUS      current
   DESCRIPTION
      "Path: tunnels.editConf.ipsecGreTunnels.gre.keepAlive.mode

       Possibilities:
               disabled   (0)
               enabled   (1)"
   ::= {er1645v2TTmplCiGreEntry 587727104}

er1645v2TTmplCiGreGreKpAlInterval OBJECT-TYPE
   SYNTAX      TimeTicks
   MAX-ACCESS  read-write
   STATUS      current
   DESCRIPTION
      "Path: tunnels.editConf.ipsecGreTunnels.gre.keepAlive.interval

       Time in centi-second."
   ::= {er1645v2TTmplCiGreEntry 587727360}

er1645v2TTmplCiGreGreKpAlRepTimeOut OBJECT-TYPE
   SYNTAX      TimeTicks
   MAX-ACCESS  read-write
   STATUS      current
   DESCRIPTION
      "Path: tunnels.editConf.ipsecGreTunnels.gre.keepAlive.replyTimeOut

       Time in centi-second."
   ::= {er1645v2TTmplCiGreEntry 587727616}

er1645v2TTmplCiGreGreKpAlFailsPrmt OBJECT-TYPE
   SYNTAX      Integer32
   MAX-ACCESS  read-write
   STATUS      current
   DESCRIPTION
      "Path: tunnels.editConf.ipsecGreTunnels.gre.keepAlive.failsPermitted"
   ::= {er1645v2TTmplCiGreEntry 587727872}

er1645v2TTmplCiGreGreNoTraffTO OBJECT-TYPE
   SYNTAX      TimeTicks
   MAX-ACCESS  read-write
   STATUS      current
   DESCRIPTION
      "Path: tunnels.editConf.ipsecGreTunnels.gre.noTrafficTimeOut

       Time in centi-second."
   ::= {er1645v2TTmplCiGreEntry 587792384}

er1645v2TTmplCiGreGreNoTraffDi OBJECT-TYPE
   SYNTAX      INTEGER
               {
               inbound (1),
               outbound (2),
               both (3)
               }
   MAX-ACCESS  read-write
   STATUS      current
   DESCRIPTION
      "Path: tunnels.editConf.ipsecGreTunnels.gre.noTrafficDirection

       Possibilities:
               inbound   (1)
               outbound   (2)
               both   (3)"
   ::= {er1645v2TTmplCiGreEntry 588185600}

er1645v2TTmplCiGreGreType OBJECT-TYPE
   SYNTAX      INTEGER
               {
               outgoingDial (1),
               outgoingLeasedLine (2),
               incoming (0)
               }
   MAX-ACCESS  read-write
   STATUS      current
   DESCRIPTION
      "Path: tunnels.editConf.ipsecGreTunnels.gre.type

       Possibilities:
               outgoingDial   (1)
               outgoingLeasedLine   (2)
               incoming   (0)"
   ::= {er1645v2TTmplCiGreEntry 587857920}

er1645v2TTmplCiGreGreRRoutDefRt OBJECT-TYPE
   SYNTAX      INTEGER
               {
               disabled (0),
               enabled (1)
               }
   MAX-ACCESS  read-write
   STATUS      current
   DESCRIPTION
      "Path: tunnels.editConf.ipsecGreTunnels.gre.remoteRoute.useDefaultRoute

       Possibilities:
               disabled   (0)
               enabled   (1)"
   ::= {er1645v2TTmplCiGreEntry 587923712}

er1645v2TTmplCiGreGreTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               copy (256),
               queueTosMap (257)
               }
   MAX-ACCESS  read-write
   STATUS      current
   DESCRIPTION
      "Path: tunnels.editConf.ipsecGreTunnels.gre.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               copy   (256)
               queueTosMap   (257)"
   ::= {er1645v2TTmplCiGreEntry 587988992}

er1645v2TTmplCiGreGreQueueTosMapQueue1 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.ipsecGreTunnels.gre.queueTosMap.queue1

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TTmplCiGreEntry 589168896}

er1645v2TTmplCiGreGreQueueTosMapQueue2 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.ipsecGreTunnels.gre.queueTosMap.queue2

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TTmplCiGreEntry 589169152}

er1645v2TTmplCiGreGreQueueTosMapQueue3 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.ipsecGreTunnels.gre.queueTosMap.queue3

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TTmplCiGreEntry 589169408}

er1645v2TTmplCiGreGreQueueTosMapQueue4 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.ipsecGreTunnels.gre.queueTosMap.queue4

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TTmplCiGreEntry 589169664}

er1645v2TTmplCiGreGreQueueTosMapQueue5 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.ipsecGreTunnels.gre.queueTosMap.queue5

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TTmplCiGreEntry 589169920}

er1645v2TTmplCiGreGreQueueTosMapLowDelayQueue OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.ipsecGreTunnels.gre.queueTosMap.lowDelayQueue

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TTmplCiGreEntry 589170176}

er1645v2TTmplCiGreGreQueueTosMapLowDelay2Queue OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.ipsecGreTunnels.gre.queueTosMap.lowDelay2Queue

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TTmplCiGreEntry 589170432}

er1645v2TTmplCiGreGreQueueTosMapSystemQueue OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.ipsecGreTunnels.gre.queueTosMap.systemQueue

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TTmplCiGreEntry 589170688}

er1645v2TTmplCiGreGreDf OBJECT-TYPE
   SYNTAX      INTEGER
               {
               clear (0),
               set (1),
               copy (2)
               }
   MAX-ACCESS  read-write
   STATUS      current
   DESCRIPTION
      "Path: tunnels.editConf.ipsecGreTunnels.gre.dontFragmentBit

       Possibilities:
               clear   (0)
               set   (1)
               copy   (2)"
   ::= {er1645v2TTmplCiGreEntry 588054528}

er1645v2TTmplCiGreGreTtl OBJECT-TYPE
   SYNTAX      INTEGER
               {
               copy (256)
               }
   MAX-ACCESS  read-write
   STATUS      current
   DESCRIPTION
      "Path: tunnels.editConf.ipsecGreTunnels.gre.ttl

       Possibilities:
               copy   (256)"
   ::= {er1645v2TTmplCiGreEntry 588120064}

er1645v2TTmplCiGreGreMtu OBJECT-TYPE
   SYNTAX      Integer32
   MAX-ACCESS  read-write
   STATUS      current
   DESCRIPTION
      "Path: tunnels.editConf.ipsecGreTunnels.gre.mtu"
   ::= {er1645v2TTmplCiGreEntry 588382208}

er1645v2TTmplCiGreMplsMode OBJECT-TYPE
   SYNTAX      INTEGER
               {
               disabled (0),
               enabled (1)
               }
   MAX-ACCESS  read-write
   STATUS      current
   DESCRIPTION
      "Path: tunnels.editConf.ipsecGreTunnels.mpls.mode

       Possibilities:
               disabled   (0)
               enabled   (1)"
   ::= {er1645v2TTmplCiGreEntry 167837696}

er1645v2TTmplCiGreMplsInLabel OBJECT-TYPE
   SYNTAX      Integer32
   MAX-ACCESS  read-write
   STATUS      current
   DESCRIPTION
      "Path: tunnels.editConf.ipsecGreTunnels.mpls.inLabel"
   ::= {er1645v2TTmplCiGreEntry 167903232}

er1645v2TTmplCiGreMplsOutLabel OBJECT-TYPE
   SYNTAX      Integer32
   MAX-ACCESS  read-write
   STATUS      current
   DESCRIPTION
      "Path: tunnels.editConf.ipsecGreTunnels.mpls.outLabel"
   ::= {er1645v2TTmplCiGreEntry 168099840}

er1645v2TTmplCiGreMplsTrafficClassMode OBJECT-TYPE
   SYNTAX      INTEGER
               {
               fixed (0),
               qos (1)
               }
   MAX-ACCESS  read-write
   STATUS      current
   DESCRIPTION
      "Path: tunnels.editConf.ipsecGreTunnels.mpls.trafficClass.mode

       Possibilities:
               fixed   (0)
               qos   (1)"
   ::= {er1645v2TTmplCiGreEntry 167969024}

er1645v2TTmplCiGreMplsTrafficClassFixed OBJECT-TYPE
   SYNTAX      Integer32
   MAX-ACCESS  read-write
   STATUS      current
   DESCRIPTION
      "Path: tunnels.editConf.ipsecGreTunnels.mpls.trafficClass.fixed"
   ::= {er1645v2TTmplCiGreEntry 167969280}

er1645v2TTmplCiGreMplsTrafficClassQosP0 OBJECT-TYPE
   SYNTAX      Integer32
   MAX-ACCESS  read-write
   STATUS      current
   DESCRIPTION
      "Path: tunnels.editConf.ipsecGreTunnels.mpls.trafficClass.qos.p0"
   ::= {er1645v2TTmplCiGreEntry 167969537}

er1645v2TTmplCiGreMplsTrafficClassQosP1 OBJECT-TYPE
   SYNTAX      Integer32
   MAX-ACCESS  read-write
   STATUS      current
   DESCRIPTION
      "Path: tunnels.editConf.ipsecGreTunnels.mpls.trafficClass.qos.p1"
   ::= {er1645v2TTmplCiGreEntry 167969538}

er1645v2TTmplCiGreMplsTrafficClassQosP2 OBJECT-TYPE
   SYNTAX      Integer32
   MAX-ACCESS  read-write
   STATUS      current
   DESCRIPTION
      "Path: tunnels.editConf.ipsecGreTunnels.mpls.trafficClass.qos.p2"
   ::= {er1645v2TTmplCiGreEntry 167969539}

er1645v2TTmplCiGreMplsTrafficClassQosP3 OBJECT-TYPE
   SYNTAX      Integer32
   MAX-ACCESS  read-write
   STATUS      current
   DESCRIPTION
      "Path: tunnels.editConf.ipsecGreTunnels.mpls.trafficClass.qos.p3"
   ::= {er1645v2TTmplCiGreEntry 167969540}

er1645v2TTmplCiGreMplsTrafficClassQosP4 OBJECT-TYPE
   SYNTAX      Integer32
   MAX-ACCESS  read-write
   STATUS      current
   DESCRIPTION
      "Path: tunnels.editConf.ipsecGreTunnels.mpls.trafficClass.qos.p4"
   ::= {er1645v2TTmplCiGreEntry 167969541}

er1645v2TTmplCiGreMplsTrafficClassQosP5 OBJECT-TYPE
   SYNTAX      Integer32
   MAX-ACCESS  read-write
   STATUS      current
   DESCRIPTION
      "Path: tunnels.editConf.ipsecGreTunnels.mpls.trafficClass.qos.p5"
   ::= {er1645v2TTmplCiGreEntry 167969542}

er1645v2TTmplCiGreMplsTrafficClassQosP6 OBJECT-TYPE
   SYNTAX      Integer32
   MAX-ACCESS  read-write
   STATUS      current
   DESCRIPTION
      "Path: tunnels.editConf.ipsecGreTunnels.mpls.trafficClass.qos.p6"
   ::= {er1645v2TTmplCiGreEntry 167969543}

er1645v2TTmplCiGreMplsTrafficClassQosP7 OBJECT-TYPE
   SYNTAX      Integer32
   MAX-ACCESS  read-write
   STATUS      current
   DESCRIPTION
      "Path: tunnels.editConf.ipsecGreTunnels.mpls.trafficClass.qos.p7"
   ::= {er1645v2TTmplCiGreEntry 167969544}

er1645v2TTmplCiGreMplsTtl OBJECT-TYPE
   SYNTAX      INTEGER
               {
               copy (256)
               }
   MAX-ACCESS  read-write
   STATUS      current
   DESCRIPTION
      "Path: tunnels.editConf.ipsecGreTunnels.mpls.ttl

       Possibilities:
               copy   (256)"
   ::= {er1645v2TTmplCiGreEntry 168034304}

er1645v2TTmplCiGreInbBwCir OBJECT-TYPE
   SYNTAX      Integer32
   MAX-ACCESS  read-write
   STATUS      current
   DESCRIPTION
      "Path: tunnels.editConf.ipsecGreTunnels.inboundBandwidth.cir"
   ::= {er1645v2TTmplCiGreEntry 117506048}

er1645v2TTmplCiGreInbBwTc OBJECT-TYPE
   SYNTAX      INTEGER
               {
               auto (0)
               }
   MAX-ACCESS  read-write
   STATUS      current
   DESCRIPTION
      "Path: tunnels.editConf.ipsecGreTunnels.inboundBandwidth.tc

       Possibilities:
               auto   (0)"
   ::= {er1645v2TTmplCiGreEntry 117833728}

er1645v2TTmplCiGreInbBwCorrType OBJECT-TYPE
   SYNTAX      INTEGER
               {
               noCorrection (0),
               predefined (1),
               manual (2)
               }
   MAX-ACCESS  read-write
   STATUS      current
   DESCRIPTION
      "Path: tunnels.editConf.ipsecGreTunnels.inboundBandwidth.correction.type

       Possibilities:
               noCorrection   (0)
               predefined   (1)
               manual   (2)"
   ::= {er1645v2TTmplCiGreEntry 117579776}

er1645v2TTmplCiGreInbBwCorrPredefEncapsFrameRelay OBJECT-TYPE
   SYNTAX      DisplayString
   MAX-ACCESS  read-write
   STATUS      current
   DESCRIPTION
      "Path: tunnels.editConf.ipsecGreTunnels.inboundBandwidth.correction.predefined.encapsulation.frameRelay"
   ::= {er1645v2TTmplCiGreEntry 117589056}

er1645v2TTmplCiGreInbBwCorrPredefEncapsPpp OBJECT-TYPE
   SYNTAX      DisplayString
   MAX-ACCESS  read-write
   STATUS      current
   DESCRIPTION
      "Path: tunnels.editConf.ipsecGreTunnels.inboundBandwidth.correction.predefined.encapsulation.ppp"
   ::= {er1645v2TTmplCiGreEntry 117589120}

er1645v2TTmplCiGreInbBwCorrPredefEncapsAtmHl OBJECT-TYPE
   SYNTAX      INTEGER
               {
               rfc2684 (0),
               ppp (1),
               pppOverEthernet (2)
               }
   MAX-ACCESS  read-write
   STATUS      current
   DESCRIPTION
      "Path: tunnels.editConf.ipsecGreTunnels.inboundBandwidth.correction.predefined.encapsulation.atm.higherLayer

       Possibilities:
               rfc2684   (0)
               ppp   (1)
               pppOverEthernet   (2)"
   ::= {er1645v2TTmplCiGreEntry 117589192}

er1645v2TTmplCiGreInbBwCorrPredefEncapsAtmMp OBJECT-TYPE
   SYNTAX      INTEGER
               {
               llcEncapsulation (0),
               vcMultiplexing (1)
               }
   MAX-ACCESS  read-write
   STATUS      current
   DESCRIPTION
      "Path: tunnels.editConf.ipsecGreTunnels.inboundBandwidth.correction.predefined.encapsulation.atm.multiProtocol

       Possibilities:
               llcEncapsulation   (0)
               vcMultiplexing   (1)"
   ::= {er1645v2TTmplCiGreEntry 117589200}

er1645v2TTmplCiGreInbBwCorrPredefEncapsHdlc OBJECT-TYPE
   SYNTAX      DisplayString
   MAX-ACCESS  read-write
   STATUS      current
   DESCRIPTION
      "Path: tunnels.editConf.ipsecGreTunnels.inboundBandwidth.correction.predefined.encapsulation.hdlc"
   ::= {er1645v2TTmplCiGreEntry 117589248}

er1645v2TTmplCiGreInbBwCorrPredefEncapsEfmFs OBJECT-TYPE
   SYNTAX      Integer32
   MAX-ACCESS  read-write
   STATUS      current
   DESCRIPTION
      "Path: tunnels.editConf.ipsecGreTunnels.inboundBandwidth.correction.predefined.encapsulation.efm.fragmentSize"
   ::= {er1645v2TTmplCiGreEntry 117589320}

er1645v2TTmplCiGreInbBwCorrPredefEncapsEfmIb OBJECT-TYPE
   SYNTAX      Integer32
   MAX-ACCESS  read-write
   STATUS      current
   DESCRIPTION
      "Path: tunnels.editConf.ipsecGreTunnels.inboundBandwidth.correction.predefined.encapsulation.efm.idleBytes"
   ::= {er1645v2TTmplCiGreEntry 117589328}

er1645v2TTmplCiGreInbBwCorrPredefMode OBJECT-TYPE
   SYNTAX      INTEGER
               {
               routing (0),
               bridging (1)
               }
   MAX-ACCESS  read-write
   STATUS      current
   DESCRIPTION
      "Path: tunnels.editConf.ipsecGreTunnels.inboundBandwidth.correction.predefined.mode

       Possibilities:
               routing   (0)
               bridging   (1)"
   ::= {er1645v2TTmplCiGreEntry 117590016}

er1645v2TTmplCiGreInbBwCorrManualOverhead OBJECT-TYPE
   SYNTAX      Integer32
   MAX-ACCESS  read-write
   STATUS      current
   DESCRIPTION
      "Path: tunnels.editConf.ipsecGreTunnels.inboundBandwidth.correction.manual.overhead"
   ::= {er1645v2TTmplCiGreEntry 117596192}

er1645v2TTmplCiGreInbBwCorrManualFrameData OBJECT-TYPE
   SYNTAX      Counter32
   MAX-ACCESS  read-write
   STATUS      current
   DESCRIPTION
      "Path: tunnels.editConf.ipsecGreTunnels.inboundBandwidth.correction.manual.frameData

       32 bit unsigned wrappable counter."
   ::= {er1645v2TTmplCiGreEntry 117596224}

er1645v2TTmplCiGreInbBwCorrManualFrameHeader OBJECT-TYPE
   SYNTAX      Counter32
   MAX-ACCESS  read-write
   STATUS      current
   DESCRIPTION
      "Path: tunnels.editConf.ipsecGreTunnels.inboundBandwidth.correction.manual.frameHeader

       32 bit unsigned wrappable counter."
   ::= {er1645v2TTmplCiGreEntry 117596256}

er1645v2TTmplCiGreInbBwMaxFifoQLen OBJECT-TYPE
   SYNTAX      Integer32
   MAX-ACCESS  read-write
   STATUS      current
   DESCRIPTION
      "Path: tunnels.editConf.ipsecGreTunnels.inboundBandwidth.maxFifoQLen"
   ::= {er1645v2TTmplCiGreEntry 117637120}

er1645v2TTmplCiGreInbBwPriorityPolicy OBJECT-TYPE
   SYNTAX      DisplayString
   MAX-ACCESS  read-write
   STATUS      current
   DESCRIPTION
      "Path: tunnels.editConf.ipsecGreTunnels.inboundBandwidth.priorityPolicy"
   ::= {er1645v2TTmplCiGreEntry 117702656}

er1645v2TTmplCiGreBandwidthMode OBJECT-TYPE
   SYNTAX      INTEGER
               {
               reshaping (1),
               policing (2),
               policingReshape (3)
               }
   MAX-ACCESS  read-write
   STATUS      current
   DESCRIPTION
      "Path: tunnels.editConf.ipsecGreTunnels.bandwidth.mode

       Possibilities:
               reshaping   (1)
               policing   (2)
               policingReshape   (3)"
   ::= {er1645v2TTmplCiGreEntry 148897792}

er1645v2TTmplCiGreBandwidthCir OBJECT-TYPE
   SYNTAX      Integer32
   MAX-ACCESS  read-write
   STATUS      current
   DESCRIPTION
      "Path: tunnels.editConf.ipsecGreTunnels.bandwidth.cir"
   ::= {er1645v2TTmplCiGreEntry 135266304}

er1645v2TTmplCiGreBandwidthEir OBJECT-TYPE
   SYNTAX      Integer32
   MAX-ACCESS  read-write
   STATUS      current
   DESCRIPTION
      "Path: tunnels.editConf.ipsecGreTunnels.bandwidth.eir"
   ::= {er1645v2TTmplCiGreEntry 141557760}

er1645v2TTmplCiGreBandwidthUnit OBJECT-TYPE
   SYNTAX      INTEGER
               {
               bitssec (1),
               percent (2)
               }
   MAX-ACCESS  read-write
   STATUS      current
   DESCRIPTION
      "Path: tunnels.editConf.ipsecGreTunnels.bandwidth.unit

       Possibilities:
               bits/sec   (1)
               percent   (2)"
   ::= {er1645v2TTmplCiGreEntry 139460608}

er1645v2TTmplCiGreBandwidthTc OBJECT-TYPE
   SYNTAX      INTEGER
               {
               auto (0)
               }
   MAX-ACCESS  read-write
   STATUS      current
   DESCRIPTION
      "Path: tunnels.editConf.ipsecGreTunnels.bandwidth.tc

       Possibilities:
               auto   (0)"
   ::= {er1645v2TTmplCiGreEntry 140509184}

er1645v2TTmplCiGreBandwidthTcFactor OBJECT-TYPE
   SYNTAX      INTEGER
               {
               ms (10),
               s100us (1)
               }
   MAX-ACCESS  read-write
   STATUS      current
   DESCRIPTION
      "Path: tunnels.editConf.ipsecGreTunnels.bandwidth.tcFactor

       Possibilities:
               ms   (10)
               *100us   (1)"
   ::= {er1645v2TTmplCiGreEntry 142606336}

er1645v2TTmplCiGreBandwidthCorrType OBJECT-TYPE
   SYNTAX      INTEGER
               {
               noCorrection (0),
               predefined (1),
               manual (2)
               }
   MAX-ACCESS  read-write
   STATUS      current
   DESCRIPTION
      "Path: tunnels.editConf.ipsecGreTunnels.bandwidth.correction.type

       Possibilities:
               noCorrection   (0)
               predefined   (1)
               manual   (2)"
   ::= {er1645v2TTmplCiGreEntry 136445952}

er1645v2TTmplCiGreBandwidthCorrPredefEncapsFrameRelay OBJECT-TYPE
   SYNTAX      DisplayString
   MAX-ACCESS  read-write
   STATUS      current
   DESCRIPTION
      "Path: tunnels.editConf.ipsecGreTunnels.bandwidth.correction.predefined.encapsulation.frameRelay"
   ::= {er1645v2TTmplCiGreEntry 136594432}

er1645v2TTmplCiGreBandwidthCorrPredefEncapsPpp OBJECT-TYPE
   SYNTAX      DisplayString
   MAX-ACCESS  read-write
   STATUS      current
   DESCRIPTION
      "Path: tunnels.editConf.ipsecGreTunnels.bandwidth.correction.predefined.encapsulation.ppp"
   ::= {er1645v2TTmplCiGreEntry 136595456}

er1645v2TTmplCiGreBandwidthCorrPredefEncapsAtmHl OBJECT-TYPE
   SYNTAX      INTEGER
               {
               rfc2684 (0),
               ppp (1),
               pppOverEthernet (2)
               }
   MAX-ACCESS  read-write
   STATUS      current
   DESCRIPTION
      "Path: tunnels.editConf.ipsecGreTunnels.bandwidth.correction.predefined.encapsulation.atm.higherLayer

       Possibilities:
               rfc2684   (0)
               ppp   (1)
               pppOverEthernet   (2)"
   ::= {er1645v2TTmplCiGreEntry 136596608}

er1645v2TTmplCiGreBandwidthCorrPredefEncapsAtmMp OBJECT-TYPE
   SYNTAX      INTEGER
               {
               llcEncapsulation (0),
               vcMultiplexing (1)
               }
   MAX-ACCESS  read-write
   STATUS      current
   DESCRIPTION
      "Path: tunnels.editConf.ipsecGreTunnels.bandwidth.correction.predefined.encapsulation.atm.multiProtocol

       Possibilities:
               llcEncapsulation   (0)
               vcMultiplexing   (1)"
   ::= {er1645v2TTmplCiGreEntry 136596736}

er1645v2TTmplCiGreBandwidthCorrPredefEncapsHdlc OBJECT-TYPE
   SYNTAX      DisplayString
   MAX-ACCESS  read-write
   STATUS      current
   DESCRIPTION
      "Path: tunnels.editConf.ipsecGreTunnels.bandwidth.correction.predefined.encapsulation.hdlc"
   ::= {er1645v2TTmplCiGreEntry 136597504}

er1645v2TTmplCiGreBandwidthCorrPredefEncapsEfmFs OBJECT-TYPE
   SYNTAX      Integer32
   MAX-ACCESS  read-write
   STATUS      current
   DESCRIPTION
      "Path: tunnels.editConf.ipsecGreTunnels.bandwidth.correction.predefined.encapsulation.efm.fragmentSize"
   ::= {er1645v2TTmplCiGreEntry 136598656}

er1645v2TTmplCiGreBandwidthCorrPredefEncapsEfmIb OBJECT-TYPE
   SYNTAX      Integer32
   MAX-ACCESS  read-write
   STATUS      current
   DESCRIPTION
      "Path: tunnels.editConf.ipsecGreTunnels.bandwidth.correction.predefined.encapsulation.efm.idleBytes"
   ::= {er1645v2TTmplCiGreEntry 136598784}

er1645v2TTmplCiGreBandwidthCorrPredefMode OBJECT-TYPE
   SYNTAX      INTEGER
               {
               routing (0),
               bridging (1)
               }
   MAX-ACCESS  read-write
   STATUS      current
   DESCRIPTION
      "Path: tunnels.editConf.ipsecGreTunnels.bandwidth.correction.predefined.mode

       Possibilities:
               routing   (0)
               bridging   (1)"
   ::= {er1645v2TTmplCiGreEntry 136609792}

er1645v2TTmplCiGreBandwidthCorrManualOverhead OBJECT-TYPE
   SYNTAX      Integer32
   MAX-ACCESS  read-write
   STATUS      current
   DESCRIPTION
      "Path: tunnels.editConf.ipsecGreTunnels.bandwidth.correction.manual.overhead"
   ::= {er1645v2TTmplCiGreEntry 136708608}

er1645v2TTmplCiGreBandwidthCorrManualFrameData OBJECT-TYPE
   SYNTAX      Counter32
   MAX-ACCESS  read-write
   STATUS      current
   DESCRIPTION
      "Path: tunnels.editConf.ipsecGreTunnels.bandwidth.correction.manual.frameData

       32 bit unsigned wrappable counter."
   ::= {er1645v2TTmplCiGreEntry 136709120}

er1645v2TTmplCiGreBandwidthCorrManualFrameHeader OBJECT-TYPE
   SYNTAX      Counter32
   MAX-ACCESS  read-write
   STATUS      current
   DESCRIPTION
      "Path: tunnels.editConf.ipsecGreTunnels.bandwidth.correction.manual.frameHeader

       32 bit unsigned wrappable counter."
   ::= {er1645v2TTmplCiGreEntry 136709632}

er1645v2TTmplCiGreBandwidthMaxFifoQLen OBJECT-TYPE
   SYNTAX      Integer32
   MAX-ACCESS  read-write
   STATUS      current
   DESCRIPTION
      "Path: tunnels.editConf.ipsecGreTunnels.bandwidth.maxFifoQLen"
   ::= {er1645v2TTmplCiGreEntry 137363456}

er1645v2TTmplCiGreBandwidthDeFlagCir OBJECT-TYPE
   SYNTAX      INTEGER
               {
               allowed (1),
               notAllowed (2)
               }
   MAX-ACCESS  read-write
   STATUS      current
   DESCRIPTION
      "Path: tunnels.editConf.ipsecGreTunnels.bandwidth.deFlag.cir

       Possibilities:
               allowed   (1)
               notAllowed   (2)"
   ::= {er1645v2TTmplCiGreEntry 147853312}

er1645v2TTmplCiGreBandwidthDeFlagEir OBJECT-TYPE
   SYNTAX      INTEGER
               {
               allowed (1),
               notAllowed (2)
               }
   MAX-ACCESS  read-write
   STATUS      current
   DESCRIPTION
      "Path: tunnels.editConf.ipsecGreTunnels.bandwidth.deFlag.eir

       Possibilities:
               allowed   (1)
               notAllowed   (2)"
   ::= {er1645v2TTmplCiGreEntry 147857408}

er1645v2TTmplCiGreBandwidthDeFlagViolate OBJECT-TYPE
   SYNTAX      INTEGER
               {
               allowed (1),
               notAllowed (2)
               }
   MAX-ACCESS  read-write
   STATUS      current
   DESCRIPTION
      "Path: tunnels.editConf.ipsecGreTunnels.bandwidth.deFlag.violate

       Possibilities:
               allowed   (1)
               notAllowed   (2)"
   ::= {er1645v2TTmplCiGreEntry 147861504}

er1645v2TTmplCiGreBandwidthActCirActNone OBJECT-TYPE
   SYNTAX      OCTET STRING
   MAX-ACCESS  read-write
   STATUS      current
   DESCRIPTION
      "Path: tunnels.editConf.ipsecGreTunnels.bandwidth.action.cirAction.none"
   ::= {er1645v2TTmplCiGreEntry 150085632}

er1645v2TTmplCiGreBandwidthActCirActEthCos1 OBJECT-TYPE
   SYNTAX      INTEGER
               {
               unchanged (256)
               }
   MAX-ACCESS  read-write
   STATUS      current
   DESCRIPTION
      "Path: tunnels.editConf.ipsecGreTunnels.bandwidth.action.cirAction.ethernet.cosDepth1

       Possibilities:
               unchanged   (256)"
   ::= {er1645v2TTmplCiGreEntry 150094080}

er1645v2TTmplCiGreBandwidthActCirActEthDei1 OBJECT-TYPE
   SYNTAX      INTEGER
               {
               unchanged (255),
               clear (0),
               set (1)
               }
   MAX-ACCESS  read-write
   STATUS      current
   DESCRIPTION
      "Path: tunnels.editConf.ipsecGreTunnels.bandwidth.action.cirAction.ethernet.deiDepth1

       Possibilities:
               unchanged   (255)
               clear   (0)
               set   (1)"
   ::= {er1645v2TTmplCiGreEntry 150099200}

er1645v2TTmplCiGreBandwidthActCirActEthCos2 OBJECT-TYPE
   SYNTAX      INTEGER
               {
               unchanged (256)
               }
   MAX-ACCESS  read-write
   STATUS      current
   DESCRIPTION
      "Path: tunnels.editConf.ipsecGreTunnels.bandwidth.action.cirAction.ethernet.cosDepth2

       Possibilities:
               unchanged   (256)"
   ::= {er1645v2TTmplCiGreEntry 150094336}

er1645v2TTmplCiGreBandwidthActCirActEthDei2 OBJECT-TYPE
   SYNTAX      INTEGER
               {
               unchanged (255),
               clear (0),
               set (1)
               }
   MAX-ACCESS  read-write
   STATUS      current
   DESCRIPTION
      "Path: tunnels.editConf.ipsecGreTunnels.bandwidth.action.cirAction.ethernet.deiDepth2

       Possibilities:
               unchanged   (255)
               clear   (0)
               set   (1)"
   ::= {er1645v2TTmplCiGreEntry 150099456}

er1645v2TTmplCiGreBandwidthActCirActEthCos3 OBJECT-TYPE
   SYNTAX      INTEGER
               {
               unchanged (256)
               }
   MAX-ACCESS  read-write
   STATUS      current
   DESCRIPTION
      "Path: tunnels.editConf.ipsecGreTunnels.bandwidth.action.cirAction.ethernet.cosDepth3

       Possibilities:
               unchanged   (256)"
   ::= {er1645v2TTmplCiGreEntry 150094592}

er1645v2TTmplCiGreBandwidthActCirActEthDei3 OBJECT-TYPE
   SYNTAX      INTEGER
               {
               unchanged (255),
               clear (0),
               set (1)
               }
   MAX-ACCESS  read-write
   STATUS      current
   DESCRIPTION
      "Path: tunnels.editConf.ipsecGreTunnels.bandwidth.action.cirAction.ethernet.deiDepth3

       Possibilities:
               unchanged   (255)
               clear   (0)
               set   (1)"
   ::= {er1645v2TTmplCiGreEntry 150099712}

er1645v2TTmplCiGreBandwidthActCirActEthCos4 OBJECT-TYPE
   SYNTAX      INTEGER
               {
               unchanged (256)
               }
   MAX-ACCESS  read-write
   STATUS      current
   DESCRIPTION
      "Path: tunnels.editConf.ipsecGreTunnels.bandwidth.action.cirAction.ethernet.cosDepth4

       Possibilities:
               unchanged   (256)"
   ::= {er1645v2TTmplCiGreEntry 150094848}

er1645v2TTmplCiGreBandwidthActCirActEthDei4 OBJECT-TYPE
   SYNTAX      INTEGER
               {
               unchanged (255),
               clear (0),
               set (1)
               }
   MAX-ACCESS  read-write
   STATUS      current
   DESCRIPTION
      "Path: tunnels.editConf.ipsecGreTunnels.bandwidth.action.cirAction.ethernet.deiDepth4

       Possibilities:
               unchanged   (255)
               clear   (0)
               set   (1)"
   ::= {er1645v2TTmplCiGreEntry 150099968}

er1645v2TTmplCiGreBandwidthActCirActEthCos5 OBJECT-TYPE
   SYNTAX      INTEGER
               {
               unchanged (256)
               }
   MAX-ACCESS  read-write
   STATUS      current
   DESCRIPTION
      "Path: tunnels.editConf.ipsecGreTunnels.bandwidth.action.cirAction.ethernet.cosDepth5

       Possibilities:
               unchanged   (256)"
   ::= {er1645v2TTmplCiGreEntry 150095104}

er1645v2TTmplCiGreBandwidthActCirActEthDei5 OBJECT-TYPE
   SYNTAX      INTEGER
               {
               unchanged (255),
               clear (0),
               set (1)
               }
   MAX-ACCESS  read-write
   STATUS      current
   DESCRIPTION
      "Path: tunnels.editConf.ipsecGreTunnels.bandwidth.action.cirAction.ethernet.deiDepth5

       Possibilities:
               unchanged   (255)
               clear   (0)
               set   (1)"
   ::= {er1645v2TTmplCiGreEntry 150100224}

er1645v2TTmplCiGreBandwidthActCirActEthCos6 OBJECT-TYPE
   SYNTAX      INTEGER
               {
               unchanged (256)
               }
   MAX-ACCESS  read-write
   STATUS      current
   DESCRIPTION
      "Path: tunnels.editConf.ipsecGreTunnels.bandwidth.action.cirAction.ethernet.cosDepth6

       Possibilities:
               unchanged   (256)"
   ::= {er1645v2TTmplCiGreEntry 150095360}

er1645v2TTmplCiGreBandwidthActCirActEthDei6 OBJECT-TYPE
   SYNTAX      INTEGER
               {
               unchanged (255),
               clear (0),
               set (1)
               }
   MAX-ACCESS  read-write
   STATUS      current
   DESCRIPTION
      "Path: tunnels.editConf.ipsecGreTunnels.bandwidth.action.cirAction.ethernet.deiDepth6

       Possibilities:
               unchanged   (255)
               clear   (0)
               set   (1)"
   ::= {er1645v2TTmplCiGreEntry 150100480}

er1645v2TTmplCiGreBandwidthActCirActEthCos7 OBJECT-TYPE
   SYNTAX      INTEGER
               {
               unchanged (256)
               }
   MAX-ACCESS  read-write
   STATUS      current
   DESCRIPTION
      "Path: tunnels.editConf.ipsecGreTunnels.bandwidth.action.cirAction.ethernet.cosDepth7

       Possibilities:
               unchanged   (256)"
   ::= {er1645v2TTmplCiGreEntry 150095616}

er1645v2TTmplCiGreBandwidthActCirActEthDei7 OBJECT-TYPE
   SYNTAX      INTEGER
               {
               unchanged (255),
               clear (0),
               set (1)
               }
   MAX-ACCESS  read-write
   STATUS      current
   DESCRIPTION
      "Path: tunnels.editConf.ipsecGreTunnels.bandwidth.action.cirAction.ethernet.deiDepth7

       Possibilities:
               unchanged   (255)
               clear   (0)
               set   (1)"
   ::= {er1645v2TTmplCiGreEntry 150100736}

er1645v2TTmplCiGreBandwidthActCirActEthCos8 OBJECT-TYPE
   SYNTAX      INTEGER
               {
               unchanged (256)
               }
   MAX-ACCESS  read-write
   STATUS      current
   DESCRIPTION
      "Path: tunnels.editConf.ipsecGreTunnels.bandwidth.action.cirAction.ethernet.cosDepth8

       Possibilities:
               unchanged   (256)"
   ::= {er1645v2TTmplCiGreEntry 150095872}

er1645v2TTmplCiGreBandwidthActCirActEthDei8 OBJECT-TYPE
   SYNTAX      INTEGER
               {
               unchanged (255),
               clear (0),
               set (1)
               }
   MAX-ACCESS  read-write
   STATUS      current
   DESCRIPTION
      "Path: tunnels.editConf.ipsecGreTunnels.bandwidth.action.cirAction.ethernet.deiDepth8

       Possibilities:
               unchanged   (255)
               clear   (0)
               set   (1)"
   ::= {er1645v2TTmplCiGreEntry 150100992}

er1645v2TTmplCiGreBandwidthActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.ipsecGreTunnels.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TTmplCiGreEntry 150096128}

er1645v2TTmplCiGreBandwidthActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.ipsecGreTunnels.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2TTmplCiGreEntry 150096384}

er1645v2TTmplCiGreBandwidthActCirActEthDrpLev OBJECT-TYPE
   SYNTAX      INTEGER
               {
               unchanged (0)
               }
   MAX-ACCESS  read-write
   STATUS      current
   DESCRIPTION
      "Path: tunnels.editConf.ipsecGreTunnels.bandwidth.action.cirAction.ethernet.dropLevel

       Possibilities:
               unchanged   (0)"
   ::= {er1645v2TTmplCiGreEntry 150096640}

er1645v2TTmplCiGreBandwidthActCirActEthDeFlag OBJECT-TYPE
   SYNTAX      INTEGER
               {
               unchanged (255),
               clear (0),
               set (1)
               }
   MAX-ACCESS  read-write
   STATUS      current
   DESCRIPTION
      "Path: tunnels.editConf.ipsecGreTunnels.bandwidth.action.cirAction.ethernet.deFlag

       Possibilities:
               unchanged   (255)
               clear   (0)
               set   (1)"
   ::= {er1645v2TTmplCiGreEntry 150097408}

er1645v2TTmplCiGreBandwidthActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.ipsecGreTunnels.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TTmplCiGreEntry 150120704}

er1645v2TTmplCiGreBandwidthActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.ipsecGreTunnels.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2TTmplCiGreEntry 150120960}

er1645v2TTmplCiGreBandwidthActCirActIpDrpLev OBJECT-TYPE
   SYNTAX      INTEGER
               {
               unchanged (0)
               }
   MAX-ACCESS  read-write
   STATUS      current
   DESCRIPTION
      "Path: tunnels.editConf.ipsecGreTunnels.bandwidth.action.cirAction.ip.dropLevel

       Possibilities:
               unchanged   (0)"
   ::= {er1645v2TTmplCiGreEntry 150121216}

er1645v2TTmplCiGreBandwidthActCirActIpDeFlag OBJECT-TYPE
   SYNTAX      INTEGER
               {
               unchanged (255),
               clear (0),
               set (1)
               }
   MAX-ACCESS  read-write
   STATUS      current
   DESCRIPTION
      "Path: tunnels.editConf.ipsecGreTunnels.bandwidth.action.cirAction.ip.deFlag

       Possibilities:
               unchanged   (255)
               clear   (0)
               set   (1)"
   ::= {er1645v2TTmplCiGreEntry 150121984}

er1645v2TTmplCiGreBandwidthActEirActNone OBJECT-TYPE
   SYNTAX      OCTET STRING
   MAX-ACCESS  read-write
   STATUS      current
   DESCRIPTION
      "Path: tunnels.editConf.ipsecGreTunnels.bandwidth.action.eirAction.none"
   ::= {er1645v2TTmplCiGreEntry 150216704}

er1645v2TTmplCiGreBandwidthActEirActEthCos1 OBJECT-TYPE
   SYNTAX      INTEGER
               {
               unchanged (256)
               }
   MAX-ACCESS  read-write
   STATUS      current
   DESCRIPTION
      "Path: tunnels.editConf.ipsecGreTunnels.bandwidth.action.eirAction.ethernet.cosDepth1

       Possibilities:
               unchanged   (256)"
   ::= {er1645v2TTmplCiGreEntry 150225152}

er1645v2TTmplCiGreBandwidthActEirActEthDei1 OBJECT-TYPE
   SYNTAX      INTEGER
               {
               unchanged (255),
               clear (0),
               set (1)
               }
   MAX-ACCESS  read-write
   STATUS      current
   DESCRIPTION
      "Path: tunnels.editConf.ipsecGreTunnels.bandwidth.action.eirAction.ethernet.deiDepth1

       Possibilities:
               unchanged   (255)
               clear   (0)
               set   (1)"
   ::= {er1645v2TTmplCiGreEntry 150230272}

er1645v2TTmplCiGreBandwidthActEirActEthCos2 OBJECT-TYPE
   SYNTAX      INTEGER
               {
               unchanged (256)
               }
   MAX-ACCESS  read-write
   STATUS      current
   DESCRIPTION
      "Path: tunnels.editConf.ipsecGreTunnels.bandwidth.action.eirAction.ethernet.cosDepth2

       Possibilities:
               unchanged   (256)"
   ::= {er1645v2TTmplCiGreEntry 150225408}

er1645v2TTmplCiGreBandwidthActEirActEthDei2 OBJECT-TYPE
   SYNTAX      INTEGER
               {
               unchanged (255),
               clear (0),
               set (1)
               }
   MAX-ACCESS  read-write
   STATUS      current
   DESCRIPTION
      "Path: tunnels.editConf.ipsecGreTunnels.bandwidth.action.eirAction.ethernet.deiDepth2

       Possibilities:
               unchanged   (255)
               clear   (0)
               set   (1)"
   ::= {er1645v2TTmplCiGreEntry 150230528}

er1645v2TTmplCiGreBandwidthActEirActEthCos3 OBJECT-TYPE
   SYNTAX      INTEGER
               {
               unchanged (256)
               }
   MAX-ACCESS  read-write
   STATUS      current
   DESCRIPTION
      "Path: tunnels.editConf.ipsecGreTunnels.bandwidth.action.eirAction.ethernet.cosDepth3

       Possibilities:
               unchanged   (256)"
   ::= {er1645v2TTmplCiGreEntry 150225664}

er1645v2TTmplCiGreBandwidthActEirActEthDei3 OBJECT-TYPE
   SYNTAX      INTEGER
               {
               unchanged (255),
               clear (0),
               set (1)
               }
   MAX-ACCESS  read-write
   STATUS      current
   DESCRIPTION
      "Path: tunnels.editConf.ipsecGreTunnels.bandwidth.action.eirAction.ethernet.deiDepth3

       Possibilities:
               unchanged   (255)
               clear   (0)
               set   (1)"
   ::= {er1645v2TTmplCiGreEntry 150230784}

er1645v2TTmplCiGreBandwidthActEirActEthCos4 OBJECT-TYPE
   SYNTAX      INTEGER
               {
               unchanged (256)
               }
   MAX-ACCESS  read-write
   STATUS      current
   DESCRIPTION
      "Path: tunnels.editConf.ipsecGreTunnels.bandwidth.action.eirAction.ethernet.cosDepth4

       Possibilities:
               unchanged   (256)"
   ::= {er1645v2TTmplCiGreEntry 150225920}

er1645v2TTmplCiGreBandwidthActEirActEthDei4 OBJECT-TYPE
   SYNTAX      INTEGER
               {
               unchanged (255),
               clear (0),
               set (1)
               }
   MAX-ACCESS  read-write
   STATUS      current
   DESCRIPTION
      "Path: tunnels.editConf.ipsecGreTunnels.bandwidth.action.eirAction.ethernet.deiDepth4

       Possibilities:
               unchanged   (255)
               clear   (0)
               set   (1)"
   ::= {er1645v2TTmplCiGreEntry 150231040}

er1645v2TTmplCiGreBandwidthActEirActEthCos5 OBJECT-TYPE
   SYNTAX      INTEGER
               {
               unchanged (256)
               }
   MAX-ACCESS  read-write
   STATUS      current
   DESCRIPTION
      "Path: tunnels.editConf.ipsecGreTunnels.bandwidth.action.eirAction.ethernet.cosDepth5

       Possibilities:
               unchanged   (256)"
   ::= {er1645v2TTmplCiGreEntry 150226176}

er1645v2TTmplCiGreBandwidthActEirActEthDei5 OBJECT-TYPE
   SYNTAX      INTEGER
               {
               unchanged (255),
               clear (0),
               set (1)
               }
   MAX-ACCESS  read-write
   STATUS      current
   DESCRIPTION
      "Path: tunnels.editConf.ipsecGreTunnels.bandwidth.action.eirAction.ethernet.deiDepth5

       Possibilities:
               unchanged   (255)
               clear   (0)
               set   (1)"
   ::= {er1645v2TTmplCiGreEntry 150231296}

er1645v2TTmplCiGreBandwidthActEirActEthCos6 OBJECT-TYPE
   SYNTAX      INTEGER
               {
               unchanged (256)
               }
   MAX-ACCESS  read-write
   STATUS      current
   DESCRIPTION
      "Path: tunnels.editConf.ipsecGreTunnels.bandwidth.action.eirAction.ethernet.cosDepth6

       Possibilities:
               unchanged   (256)"
   ::= {er1645v2TTmplCiGreEntry 150226432}

er1645v2TTmplCiGreBandwidthActEirActEthDei6 OBJECT-TYPE
   SYNTAX      INTEGER
               {
               unchanged (255),
               clear (0),
               set (1)
               }
   MAX-ACCESS  read-write
   STATUS      current
   DESCRIPTION
      "Path: tunnels.editConf.ipsecGreTunnels.bandwidth.action.eirAction.ethernet.deiDepth6

       Possibilities:
               unchanged   (255)
               clear   (0)
               set   (1)"
   ::= {er1645v2TTmplCiGreEntry 150231552}

er1645v2TTmplCiGreBandwidthActEirActEthCos7 OBJECT-TYPE
   SYNTAX      INTEGER
               {
               unchanged (256)
               }
   MAX-ACCESS  read-write
   STATUS      current
   DESCRIPTION
      "Path: tunnels.editConf.ipsecGreTunnels.bandwidth.action.eirAction.ethernet.cosDepth7

       Possibilities:
               unchanged   (256)"
   ::= {er1645v2TTmplCiGreEntry 150226688}

er1645v2TTmplCiGreBandwidthActEirActEthDei7 OBJECT-TYPE
   SYNTAX      INTEGER
               {
               unchanged (255),
               clear (0),
               set (1)
               }
   MAX-ACCESS  read-write
   STATUS      current
   DESCRIPTION
      "Path: tunnels.editConf.ipsecGreTunnels.bandwidth.action.eirAction.ethernet.deiDepth7

       Possibilities:
               unchanged   (255)
               clear   (0)
               set   (1)"
   ::= {er1645v2TTmplCiGreEntry 150231808}

er1645v2TTmplCiGreBandwidthActEirActEthCos8 OBJECT-TYPE
   SYNTAX      INTEGER
               {
               unchanged (256)
               }
   MAX-ACCESS  read-write
   STATUS      current
   DESCRIPTION
      "Path: tunnels.editConf.ipsecGreTunnels.bandwidth.action.eirAction.ethernet.cosDepth8

       Possibilities:
               unchanged   (256)"
   ::= {er1645v2TTmplCiGreEntry 150226944}

er1645v2TTmplCiGreBandwidthActEirActEthDei8 OBJECT-TYPE
   SYNTAX      INTEGER
               {
               unchanged (255),
               clear (0),
               set (1)
               }
   MAX-ACCESS  read-write
   STATUS      current
   DESCRIPTION
      "Path: tunnels.editConf.ipsecGreTunnels.bandwidth.action.eirAction.ethernet.deiDepth8

       Possibilities:
               unchanged   (255)
               clear   (0)
               set   (1)"
   ::= {er1645v2TTmplCiGreEntry 150232064}

er1645v2TTmplCiGreBandwidthActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.ipsecGreTunnels.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TTmplCiGreEntry 150227200}

er1645v2TTmplCiGreBandwidthActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.ipsecGreTunnels.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2TTmplCiGreEntry 150227456}

er1645v2TTmplCiGreBandwidthActEirActEthDrpLev OBJECT-TYPE
   SYNTAX      INTEGER
               {
               unchanged (0)
               }
   MAX-ACCESS  read-write
   STATUS      current
   DESCRIPTION
      "Path: tunnels.editConf.ipsecGreTunnels.bandwidth.action.eirAction.ethernet.dropLevel

       Possibilities:
               unchanged   (0)"
   ::= {er1645v2TTmplCiGreEntry 150227712}

er1645v2TTmplCiGreBandwidthActEirActEthDeFlag OBJECT-TYPE
   SYNTAX      INTEGER
               {
               unchanged (255),
               clear (0),
               set (1)
               }
   MAX-ACCESS  read-write
   STATUS      current
   DESCRIPTION
      "Path: tunnels.editConf.ipsecGreTunnels.bandwidth.action.eirAction.ethernet.deFlag

       Possibilities:
               unchanged   (255)
               clear   (0)
               set   (1)"
   ::= {er1645v2TTmplCiGreEntry 150228480}

er1645v2TTmplCiGreBandwidthActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.ipsecGreTunnels.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TTmplCiGreEntry 150251776}

er1645v2TTmplCiGreBandwidthActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.ipsecGreTunnels.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2TTmplCiGreEntry 150252032}

er1645v2TTmplCiGreBandwidthActEirActIpDrpLev OBJECT-TYPE
   SYNTAX      INTEGER
               {
               unchanged (0)
               }
   MAX-ACCESS  read-write
   STATUS      current
   DESCRIPTION
      "Path: tunnels.editConf.ipsecGreTunnels.bandwidth.action.eirAction.ip.dropLevel

       Possibilities:
               unchanged   (0)"
   ::= {er1645v2TTmplCiGreEntry 150252288}

er1645v2TTmplCiGreBandwidthActEirActIpDeFlag OBJECT-TYPE
   SYNTAX      INTEGER
               {
               unchanged (255),
               clear (0),
               set (1)
               }
   MAX-ACCESS  read-write
   STATUS      current
   DESCRIPTION
      "Path: tunnels.editConf.ipsecGreTunnels.bandwidth.action.eirAction.ip.deFlag

       Possibilities:
               unchanged   (255)
               clear   (0)
               set   (1)"
   ::= {er1645v2TTmplCiGreEntry 150253056}

er1645v2TTmplCiGreBandwidthActViolActNone OBJECT-TYPE
   SYNTAX      OCTET STRING
   MAX-ACCESS  read-write
   STATUS      current
   DESCRIPTION
      "Path: tunnels.editConf.ipsecGreTunnels.bandwidth.action.violateAction.none"
   ::= {er1645v2TTmplCiGreEntry 150347776}

er1645v2TTmplCiGreBandwidthActViolActDrop OBJECT-TYPE
   SYNTAX      OCTET STRING
   MAX-ACCESS  read-write
   STATUS      current
   DESCRIPTION
      "Path: tunnels.editConf.ipsecGreTunnels.bandwidth.action.violateAction.drop"
   ::= {er1645v2TTmplCiGreEntry 150364160}

er1645v2TTmplCiGreBandwidthActViolActEthCos1 OBJECT-TYPE
   SYNTAX      INTEGER
               {
               unchanged (256)
               }
   MAX-ACCESS  read-write
   STATUS      current
   DESCRIPTION
      "Path: tunnels.editConf.ipsecGreTunnels.bandwidth.action.violateAction.ethernet.cosDepth1

       Possibilities:
               unchanged   (256)"
   ::= {er1645v2TTmplCiGreEntry 150356224}

er1645v2TTmplCiGreBandwidthActViolActEthDei1 OBJECT-TYPE
   SYNTAX      INTEGER
               {
               unchanged (255),
               clear (0),
               set (1)
               }
   MAX-ACCESS  read-write
   STATUS      current
   DESCRIPTION
      "Path: tunnels.editConf.ipsecGreTunnels.bandwidth.action.violateAction.ethernet.deiDepth1

       Possibilities:
               unchanged   (255)
               clear   (0)
               set   (1)"
   ::= {er1645v2TTmplCiGreEntry 150361344}

er1645v2TTmplCiGreBandwidthActViolActEthCos2 OBJECT-TYPE
   SYNTAX      INTEGER
               {
               unchanged (256)
               }
   MAX-ACCESS  read-write
   STATUS      current
   DESCRIPTION
      "Path: tunnels.editConf.ipsecGreTunnels.bandwidth.action.violateAction.ethernet.cosDepth2

       Possibilities:
               unchanged   (256)"
   ::= {er1645v2TTmplCiGreEntry 150356480}

er1645v2TTmplCiGreBandwidthActViolActEthDei2 OBJECT-TYPE
   SYNTAX      INTEGER
               {
               unchanged (255),
               clear (0),
               set (1)
               }
   MAX-ACCESS  read-write
   STATUS      current
   DESCRIPTION
      "Path: tunnels.editConf.ipsecGreTunnels.bandwidth.action.violateAction.ethernet.deiDepth2

       Possibilities:
               unchanged   (255)
               clear   (0)
               set   (1)"
   ::= {er1645v2TTmplCiGreEntry 150361600}

er1645v2TTmplCiGreBandwidthActViolActEthCos3 OBJECT-TYPE
   SYNTAX      INTEGER
               {
               unchanged (256)
               }
   MAX-ACCESS  read-write
   STATUS      current
   DESCRIPTION
      "Path: tunnels.editConf.ipsecGreTunnels.bandwidth.action.violateAction.ethernet.cosDepth3

       Possibilities:
               unchanged   (256)"
   ::= {er1645v2TTmplCiGreEntry 150356736}

er1645v2TTmplCiGreBandwidthActViolActEthDei3 OBJECT-TYPE
   SYNTAX      INTEGER
               {
               unchanged (255),
               clear (0),
               set (1)
               }
   MAX-ACCESS  read-write
   STATUS      current
   DESCRIPTION
      "Path: tunnels.editConf.ipsecGreTunnels.bandwidth.action.violateAction.ethernet.deiDepth3

       Possibilities:
               unchanged   (255)
               clear   (0)
               set   (1)"
   ::= {er1645v2TTmplCiGreEntry 150361856}

er1645v2TTmplCiGreBandwidthActViolActEthCos4 OBJECT-TYPE
   SYNTAX      INTEGER
               {
               unchanged (256)
               }
   MAX-ACCESS  read-write
   STATUS      current
   DESCRIPTION
      "Path: tunnels.editConf.ipsecGreTunnels.bandwidth.action.violateAction.ethernet.cosDepth4

       Possibilities:
               unchanged   (256)"
   ::= {er1645v2TTmplCiGreEntry 150356992}

er1645v2TTmplCiGreBandwidthActViolActEthDei4 OBJECT-TYPE
   SYNTAX      INTEGER
               {
               unchanged (255),
               clear (0),
               set (1)
               }
   MAX-ACCESS  read-write
   STATUS      current
   DESCRIPTION
      "Path: tunnels.editConf.ipsecGreTunnels.bandwidth.action.violateAction.ethernet.deiDepth4

       Possibilities:
               unchanged   (255)
               clear   (0)
               set   (1)"
   ::= {er1645v2TTmplCiGreEntry 150362112}

er1645v2TTmplCiGreBandwidthActViolActEthCos5 OBJECT-TYPE
   SYNTAX      INTEGER
               {
               unchanged (256)
               }
   MAX-ACCESS  read-write
   STATUS      current
   DESCRIPTION
      "Path: tunnels.editConf.ipsecGreTunnels.bandwidth.action.violateAction.ethernet.cosDepth5

       Possibilities:
               unchanged   (256)"
   ::= {er1645v2TTmplCiGreEntry 150357248}

er1645v2TTmplCiGreBandwidthActViolActEthDei5 OBJECT-TYPE
   SYNTAX      INTEGER
               {
               unchanged (255),
               clear (0),
               set (1)
               }
   MAX-ACCESS  read-write
   STATUS      current
   DESCRIPTION
      "Path: tunnels.editConf.ipsecGreTunnels.bandwidth.action.violateAction.ethernet.deiDepth5

       Possibilities:
               unchanged   (255)
               clear   (0)
               set   (1)"
   ::= {er1645v2TTmplCiGreEntry 150362368}

er1645v2TTmplCiGreBandwidthActViolActEthCos6 OBJECT-TYPE
   SYNTAX      INTEGER
               {
               unchanged (256)
               }
   MAX-ACCESS  read-write
   STATUS      current
   DESCRIPTION
      "Path: tunnels.editConf.ipsecGreTunnels.bandwidth.action.violateAction.ethernet.cosDepth6

       Possibilities:
               unchanged   (256)"
   ::= {er1645v2TTmplCiGreEntry 150357504}

er1645v2TTmplCiGreBandwidthActViolActEthDei6 OBJECT-TYPE
   SYNTAX      INTEGER
               {
               unchanged (255),
               clear (0),
               set (1)
               }
   MAX-ACCESS  read-write
   STATUS      current
   DESCRIPTION
      "Path: tunnels.editConf.ipsecGreTunnels.bandwidth.action.violateAction.ethernet.deiDepth6

       Possibilities:
               unchanged   (255)
               clear   (0)
               set   (1)"
   ::= {er1645v2TTmplCiGreEntry 150362624}

er1645v2TTmplCiGreBandwidthActViolActEthCos7 OBJECT-TYPE
   SYNTAX      INTEGER
               {
               unchanged (256)
               }
   MAX-ACCESS  read-write
   STATUS      current
   DESCRIPTION
      "Path: tunnels.editConf.ipsecGreTunnels.bandwidth.action.violateAction.ethernet.cosDepth7

       Possibilities:
               unchanged   (256)"
   ::= {er1645v2TTmplCiGreEntry 150357760}

er1645v2TTmplCiGreBandwidthActViolActEthDei7 OBJECT-TYPE
   SYNTAX      INTEGER
               {
               unchanged (255),
               clear (0),
               set (1)
               }
   MAX-ACCESS  read-write
   STATUS      current
   DESCRIPTION
      "Path: tunnels.editConf.ipsecGreTunnels.bandwidth.action.violateAction.ethernet.deiDepth7

       Possibilities:
               unchanged   (255)
               clear   (0)
               set   (1)"
   ::= {er1645v2TTmplCiGreEntry 150362880}

er1645v2TTmplCiGreBandwidthActViolActEthCos8 OBJECT-TYPE
   SYNTAX      INTEGER
               {
               unchanged (256)
               }
   MAX-ACCESS  read-write
   STATUS      current
   DESCRIPTION
      "Path: tunnels.editConf.ipsecGreTunnels.bandwidth.action.violateAction.ethernet.cosDepth8

       Possibilities:
               unchanged   (256)"
   ::= {er1645v2TTmplCiGreEntry 150358016}

er1645v2TTmplCiGreBandwidthActViolActEthDei8 OBJECT-TYPE
   SYNTAX      INTEGER
               {
               unchanged (255),
               clear (0),
               set (1)
               }
   MAX-ACCESS  read-write
   STATUS      current
   DESCRIPTION
      "Path: tunnels.editConf.ipsecGreTunnels.bandwidth.action.violateAction.ethernet.deiDepth8

       Possibilities:
               unchanged   (255)
               clear   (0)
               set   (1)"
   ::= {er1645v2TTmplCiGreEntry 150363136}

er1645v2TTmplCiGreBandwidthActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.ipsecGreTunnels.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TTmplCiGreEntry 150358272}

er1645v2TTmplCiGreBandwidthActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.ipsecGreTunnels.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2TTmplCiGreEntry 150358528}

er1645v2TTmplCiGreBandwidthActViolActEthDrpLev OBJECT-TYPE
   SYNTAX      INTEGER
               {
               unchanged (0)
               }
   MAX-ACCESS  read-write
   STATUS      current
   DESCRIPTION
      "Path: tunnels.editConf.ipsecGreTunnels.bandwidth.action.violateAction.ethernet.dropLevel

       Possibilities:
               unchanged   (0)"
   ::= {er1645v2TTmplCiGreEntry 150358784}

er1645v2TTmplCiGreBandwidthActViolActEthDeFlag OBJECT-TYPE
   SYNTAX      INTEGER
               {
               unchanged (255),
               clear (0),
               set (1)
               }
   MAX-ACCESS  read-write
   STATUS      current
   DESCRIPTION
      "Path: tunnels.editConf.ipsecGreTunnels.bandwidth.action.violateAction.ethernet.deFlag

       Possibilities:
               unchanged   (255)
               clear   (0)
               set   (1)"
   ::= {er1645v2TTmplCiGreEntry 150359552}

er1645v2TTmplCiGreBandwidthActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.ipsecGreTunnels.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TTmplCiGreEntry 150382848}

er1645v2TTmplCiGreBandwidthActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.ipsecGreTunnels.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2TTmplCiGreEntry 150383104}

er1645v2TTmplCiGreBandwidthActViolActIpDrpLev OBJECT-TYPE
   SYNTAX      INTEGER
               {
               unchanged (0)
               }
   MAX-ACCESS  read-write
   STATUS      current
   DESCRIPTION
      "Path: tunnels.editConf.ipsecGreTunnels.bandwidth.action.violateAction.ip.dropLevel

       Possibilities:
               unchanged   (0)"
   ::= {er1645v2TTmplCiGreEntry 150383360}

er1645v2TTmplCiGreBandwidthActViolActIpDeFlag OBJECT-TYPE
   SYNTAX      INTEGER
               {
               unchanged (255),
               clear (0),
               set (1)
               }
   MAX-ACCESS  read-write
   STATUS      current
   DESCRIPTION
      "Path: tunnels.editConf.ipsecGreTunnels.bandwidth.action.violateAction.ip.deFlag

       Possibilities:
               unchanged   (255)
               clear   (0)
               set   (1)"
   ::= {er1645v2TTmplCiGreEntry 150384128}

er1645v2TTmplCiGreBrVlTVlans OBJECT-TYPE
   SYNTAX      SEQUENCE OF Er1645v2TTmplCiGreBrVlTVlansEntry
   MAX-ACCESS  not-accessible
   STATUS      current
   DESCRIPTION
      ""
   ::= {er1645v2TTmplCiGre 459079680}

er1645v2TTmplCiGreBrVlTVlansEntry OBJECT-TYPE
   SYNTAX      Er1645v2TTmplCiGreBrVlTVlansEntry
   MAX-ACCESS  not-accessible
   STATUS      current
   DESCRIPTION
      ""
   INDEX      { er1645v2TTmplCiGreTableIx,
                er1645v2TTmplCiGreBrVlTVlansTableIx }
   ::= {er1645v2TTmplCiGreBrVlTVlans 1}

Er1645v2TTmplCiGreBrVlTVlansEntry ::=
   SEQUENCE
      {
      er1645v2TTmplCiGreBrVlTVlansActions
         VariableLengthTableActions,
      er1645v2TTmplCiGreBrVlTVlansTableIx
         TableIndex,
      er1645v2TTmplCiGreBrVlTVlansVid
         Integer32,
      er1645v2TTmplCiGreBrVlTVlansEndVid
         Integer32,
      er1645v2TTmplCiGreBrVlTVlansAction
         INTEGER,
      er1645v2TTmplCiGreBrVlTVlansTagInfoTpid
         INTEGER,
      er1645v2TTmplCiGreBrVlTVlansTagInfoVid
         Integer32
      }

er1645v2TTmplCiGreBrVlTVlansActions OBJECT-TYPE
   SYNTAX      VariableLengthTableActions
   MAX-ACCESS  read-write
   STATUS      current
   DESCRIPTION
      "By way of this field, some manipulations
       on this table may be performed."
   ::= {er1645v2TTmplCiGreBrVlTVlansEntry 2}

er1645v2TTmplCiGreBrVlTVlansTableIx OBJECT-TYPE
   SYNTAX      TableIndex
   MAX-ACCESS  not-accessible
   STATUS      current
   DESCRIPTION
      ""
   ::= {er1645v2TTmplCiGreBrVlTVlansEntry 11}

er1645v2TTmplCiGreBrVlTVlansVid OBJECT-TYPE
   SYNTAX      Integer32
   MAX-ACCESS  read-write
   STATUS      current
   DESCRIPTION
      "Path: tunnels.editConf.ipsecGreTunnels.bridging.vlanTagging.vlans.vid"
   ::= {er1645v2TTmplCiGreBrVlTVlansEntry 536870912}

er1645v2TTmplCiGreBrVlTVlansEndVid OBJECT-TYPE
   SYNTAX      Integer32
   MAX-ACCESS  read-write
   STATUS      current
   DESCRIPTION
      "Path: tunnels.editConf.ipsecGreTunnels.bridging.vlanTagging.vlans.endVid"
   ::= {er1645v2TTmplCiGreBrVlTVlansEntry 2147483648}

er1645v2TTmplCiGreBrVlTVlansAction OBJECT-TYPE
   SYNTAX      INTEGER
               {
               discard (0),
               accept (1),
               tag (2)
               }
   MAX-ACCESS  read-write
   STATUS      current
   DESCRIPTION
      "Path: tunnels.editConf.ipsecGreTunnels.bridging.vlanTagging.vlans.action

       Possibilities:
               discard   (0)
               accept   (1)
               tag   (2)"
   ::= {er1645v2TTmplCiGreBrVlTVlansEntry 1073741824}

er1645v2TTmplCiGreBrVlTVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: tunnels.editConf.ipsecGreTunnels.bridging.vlanTagging.vlans.tagInfo.tpid

       Possibilities:
               dot1Q   (33024)
               dot1ad   (34984)
               0x9100   (37120)
               0x9200   (37376)
               0x9300   (37632)"
   ::= {er1645v2TTmplCiGreBrVlTVlansEntry 1677721600}

er1645v2TTmplCiGreBrVlTVlansTagInfoVid OBJECT-TYPE
   SYNTAX      Integer32
   MAX-ACCESS  read-write
   STATUS      current
   DESCRIPTION
      "Path: tunnels.editConf.ipsecGreTunnels.bridging.vlanTagging.vlans.tagInfo.vid"
   ::= {er1645v2TTmplCiGreBrVlTVlansEntry 1744830464}


er1645v2TTmplIpsTun OBJECT IDENTIFIER ::= {er1645v2TTmpl 10}

er1645v2TTmplIpsTunSSCTable OBJECT-TYPE
   SYNTAX      SEQUENCE OF Er1645v2TTmplIpsTunEntry
   MAX-ACCESS  not-accessible
   STATUS      current
   DESCRIPTION
      ""
   ::= {er1645v2TTmplIpsTun 1}

er1645v2TTmplIpsTunEntry OBJECT-TYPE
   SYNTAX      Er1645v2TTmplIpsTunEntry
   MAX-ACCESS  not-accessible
   STATUS      current
   DESCRIPTION
      ""
   INDEX      { er1645v2TTmplIpsTunTableIx }
   ::= {er1645v2TTmplIpsTunSSCTable 1}

Er1645v2TTmplIpsTunEntry ::=
   SEQUENCE
      {
      er1645v2TTmplIpsTunActions
         VariableLengthTableActions,
      er1645v2TTmplIpsTunTableIx
         TableIndex,
      er1645v2TTmplIpsTunName
         DisplayString,
      er1645v2TTmplIpsTunRemark
         DisplayString,
      er1645v2TTmplIpsTunAdminStatus
         INTEGER,
      er1645v2TTmplIpsTunLocalIpAddress
         IpAddress,
      er1645v2TTmplIpsTunLocalInterface
         DisplayString,
      er1645v2TTmplIpsTunRemoteIpAddress
         IpAddress,
      er1645v2TTmplIpsTunRemoteDnsName
         DisplayString,
      er1645v2TTmplIpsTunIpsecFdx
         DisplayString,
      er1645v2TTmplIpsTunIpsecHdxIn
         DisplayString,
      er1645v2TTmplIpsTunIpsecHdxOut
         DisplayString,
      er1645v2TTmplIpsTunIpsecPsCfg
         DisplayString,
      er1645v2TTmplIpsTunIpsecPsLIdIp
         IpAddress,
      er1645v2TTmplIpsTunIpsecPsLIdHn
         DisplayString,
      er1645v2TTmplIpsTunIpsecPsLIdUn
         DisplayString,
      er1645v2TTmplIpsTunIpsecPsRIdIp
         IpAddress,
      er1645v2TTmplIpsTunIpsecPsRIdHn
         DisplayString,
      er1645v2TTmplIpsTunIpsecPsRIdUn
         DisplayString,
      er1645v2TTmplIpsTunIpsecPsKey
         DisplayString,
      er1645v2TTmplIpsTunIpsecPsEncMKey
         INTEGER,
      er1645v2TTmplIpsTunIpsecPsEncKey
         DisplayString,
      er1645v2TTmplIpsTunIpsecPsPIdProt
         INTEGER,
      er1645v2TTmplIpsTunIpsecPsPIdLocAddr
         IpAddress,
      er1645v2TTmplIpsTunIpsecPsPIdLocMask
         IpAddress,
      er1645v2TTmplIpsTunIpsecPsPIdLocPort
         INTEGER,
      er1645v2TTmplIpsTunIpsecPsPIdRemAddr
         IpAddress,
      er1645v2TTmplIpsTunIpsecPsPIdRemMask
         IpAddress,
      er1645v2TTmplIpsTunIpsecPsPIdRemPort
         INTEGER,
      er1645v2TTmplIpsTunIpsecCeCfg
         DisplayString,
      er1645v2TTmplIpsTunIpsecCeLIdIp
         IpAddress,
      er1645v2TTmplIpsTunIpsecCeLIdHn
         DisplayString,
      er1645v2TTmplIpsTunIpsecCeLIdUn
         DisplayString,
      er1645v2TTmplIpsTunIpsecCeLIdDn
         DisplayString,
      er1645v2TTmplIpsTunIpsecCeRIdIp
         IpAddress,
      er1645v2TTmplIpsTunIpsecCeRIdHn
         DisplayString,
      er1645v2TTmplIpsTunIpsecCeRIdUn
         DisplayString,
      er1645v2TTmplIpsTunIpsecCeRIdDn
         DisplayString,
      er1645v2TTmplIpsTunIpsecCePIdProt
         INTEGER,
      er1645v2TTmplIpsTunIpsecCePIdLocAddr
         IpAddress,
      er1645v2TTmplIpsTunIpsecCePIdLocMask
         IpAddress,
      er1645v2TTmplIpsTunIpsecCePIdLocPort
         INTEGER,
      er1645v2TTmplIpsTunIpsecCePIdRemAddr
         IpAddress,
      er1645v2TTmplIpsTunIpsecCePIdRemMask
         IpAddress,
      er1645v2TTmplIpsTunIpsecCePIdRemPort
         INTEGER,
      er1645v2TTmplIpsTunType
         INTEGER,
      er1645v2TTmplIpsTunNoTraffTO
         TimeTicks,
      er1645v2TTmplIpsTunNoTraffDi
         INTEGER,
      er1645v2TTmplIpsTunRemRouteDefRt
         INTEGER,
      er1645v2TTmplIpsTunTos
         INTEGER,
      er1645v2TTmplIpsTunQueueTosMapQueue1
         INTEGER,
      er1645v2TTmplIpsTunQueueTosMapQueue2
         INTEGER,
      er1645v2TTmplIpsTunQueueTosMapQueue3
         INTEGER,
      er1645v2TTmplIpsTunQueueTosMapQueue4
         INTEGER,
      er1645v2TTmplIpsTunQueueTosMapQueue5
         INTEGER,
      er1645v2TTmplIpsTunQueueTosMapLowDelayQueue
         INTEGER,
      er1645v2TTmplIpsTunQueueTosMapLowDelay2Queue
         INTEGER,
      er1645v2TTmplIpsTunQueueTosMapSystemQueue
         INTEGER,
      er1645v2TTmplIpsTunDf
         INTEGER,
      er1645v2TTmplIpsTunMtu
         Integer32
      }

er1645v2TTmplIpsTunActions OBJECT-TYPE
   SYNTAX      VariableLengthTableActions
   MAX-ACCESS  read-write
   STATUS      current
   DESCRIPTION
      "By way of this field, some manipulations
       on this table may be performed."
   ::= {er1645v2TTmplIpsTunEntry 2}

er1645v2TTmplIpsTunTableIx OBJECT-TYPE
   SYNTAX      TableIndex
   MAX-ACCESS  not-accessible
   STATUS      current
   DESCRIPTION
      ""
   ::= {er1645v2TTmplIpsTunEntry 11}

er1645v2TTmplIpsTunName OBJECT-TYPE
   SYNTAX      DisplayString
   MAX-ACCESS  read-write
   STATUS      current
   DESCRIPTION
      "Path: tunnels.editConf.ipsecTunnels.name"
   ::= {er1645v2TTmplIpsTunEntry 16777216}

er1645v2TTmplIpsTunRemark OBJECT-TYPE
   SYNTAX      DisplayString
   MAX-ACCESS  read-write
   STATUS      current
   DESCRIPTION
      "Path: tunnels.editConf.ipsecTunnels.remark"
   ::= {er1645v2TTmplIpsTunEntry 1157627904}

er1645v2TTmplIpsTunAdminStatus OBJECT-TYPE
   SYNTAX      INTEGER
               {
               up (1),
               down (2)
               }
   MAX-ACCESS  read-write
   STATUS      current
   DESCRIPTION
      "Path: tunnels.editConf.ipsecTunnels.adminStatus

       Possibilities:
               up   (1)
               down   (2)"
   ::= {er1645v2TTmplIpsTunEntry 218103808}

er1645v2TTmplIpsTunLocalIpAddress OBJECT-TYPE
   SYNTAX      IpAddress
   MAX-ACCESS  read-write
   STATUS      current
   DESCRIPTION
      "Path: tunnels.editConf.ipsecTunnels.localIpAddress"
   ::= {er1645v2TTmplIpsTunEntry 33554432}

er1645v2TTmplIpsTunLocalInterface OBJECT-TYPE
   SYNTAX      DisplayString
   MAX-ACCESS  read-write
   STATUS      current
   DESCRIPTION
      "Path: tunnels.editConf.ipsecTunnels.localInterface"
   ::= {er1645v2TTmplIpsTunEntry 201326592}

er1645v2TTmplIpsTunRemoteIpAddress OBJECT-TYPE
   SYNTAX      IpAddress
   MAX-ACCESS  read-write
   STATUS      current
   DESCRIPTION
      "Path: tunnels.editConf.ipsecTunnels.remoteIpAddress"
   ::= {er1645v2TTmplIpsTunEntry 50331648}

er1645v2TTmplIpsTunRemoteDnsName OBJECT-TYPE
   SYNTAX      DisplayString
   MAX-ACCESS  read-write
   STATUS      current
   DESCRIPTION
      "Path: tunnels.editConf.ipsecTunnels.remoteDnsName"
   ::= {er1645v2TTmplIpsTunEntry 67108864}

er1645v2TTmplIpsTunIpsecFdx OBJECT-TYPE
   SYNTAX      DisplayString
   MAX-ACCESS  read-write
   STATUS      current
   DESCRIPTION
      "Path: tunnels.editConf.ipsecTunnels.ipsec.fdxManualSA"
   ::= {er1645v2TTmplIpsTunEntry 85983232}

er1645v2TTmplIpsTunIpsecHdxIn OBJECT-TYPE
   SYNTAX      DisplayString
   MAX-ACCESS  read-write
   STATUS      current
   DESCRIPTION
      "Path: tunnels.editConf.ipsecTunnels.ipsec.hdxManualSA.inbound"
   ::= {er1645v2TTmplIpsTunEntry 88088576}

er1645v2TTmplIpsTunIpsecHdxOut OBJECT-TYPE
   SYNTAX      DisplayString
   MAX-ACCESS  read-write
   STATUS      current
   DESCRIPTION
      "Path: tunnels.editConf.ipsecTunnels.ipsec.hdxManualSA.outbound"
   ::= {er1645v2TTmplIpsTunEntry 88096768}

er1645v2TTmplIpsTunIpsecPsCfg OBJECT-TYPE
   SYNTAX      DisplayString
   MAX-ACCESS  read-write
   STATUS      current
   DESCRIPTION
      "Path: tunnels.editConf.ipsecTunnels.ipsec.ikePresharedSA.ikeSA"
   ::= {er1645v2TTmplIpsTunEntry 90439680}

er1645v2TTmplIpsTunIpsecPsLIdIp OBJECT-TYPE
   SYNTAX      IpAddress
   MAX-ACCESS  read-write
   STATUS      current
   DESCRIPTION
      "Path: tunnels.editConf.ipsecTunnels.ipsec.ikePresharedSA.localId.ipAddress"
   ::= {er1645v2TTmplIpsTunEntry 90702848}

er1645v2TTmplIpsTunIpsecPsLIdHn OBJECT-TYPE
   SYNTAX      DisplayString
   MAX-ACCESS  read-write
   STATUS      current
   DESCRIPTION
      "Path: tunnels.editConf.ipsecTunnels.ipsec.ikePresharedSA.localId.hostName"
   ::= {er1645v2TTmplIpsTunEntry 90703872}

er1645v2TTmplIpsTunIpsecPsLIdUn OBJECT-TYPE
   SYNTAX      DisplayString
   MAX-ACCESS  read-write
   STATUS      current
   DESCRIPTION
      "Path: tunnels.editConf.ipsecTunnels.ipsec.ikePresharedSA.localId.user"
   ::= {er1645v2TTmplIpsTunEntry 90704896}

er1645v2TTmplIpsTunIpsecPsRIdIp OBJECT-TYPE
   SYNTAX      IpAddress
   MAX-ACCESS  read-write
   STATUS      current
   DESCRIPTION
      "Path: tunnels.editConf.ipsecTunnels.ipsec.ikePresharedSA.remoteId.ipAddress"
   ::= {er1645v2TTmplIpsTunEntry 90964992}

er1645v2TTmplIpsTunIpsecPsRIdHn OBJECT-TYPE
   SYNTAX      DisplayString
   MAX-ACCESS  read-write
   STATUS      current
   DESCRIPTION
      "Path: tunnels.editConf.ipsecTunnels.ipsec.ikePresharedSA.remoteId.hostName"
   ::= {er1645v2TTmplIpsTunEntry 90966016}

er1645v2TTmplIpsTunIpsecPsRIdUn OBJECT-TYPE
   SYNTAX      DisplayString
   MAX-ACCESS  read-write
   STATUS      current
   DESCRIPTION
      "Path: tunnels.editConf.ipsecTunnels.ipsec.ikePresharedSA.remoteId.user"
   ::= {er1645v2TTmplIpsTunEntry 90967040}

er1645v2TTmplIpsTunIpsecPsKey OBJECT-TYPE
   SYNTAX      DisplayString
   MAX-ACCESS  read-write
   STATUS      current
   DESCRIPTION
      "Path: tunnels.editConf.ipsecTunnels.ipsec.ikePresharedSA.preSharedKey"
   ::= {er1645v2TTmplIpsTunEntry 91226112}

er1645v2TTmplIpsTunIpsecPsEncMKey OBJECT-TYPE
   SYNTAX      INTEGER
               {
               none (1),
               encrypt (2),
               encType1 (3),
               invalid (128)
               }
   MAX-ACCESS  read-write
   STATUS      current
   DESCRIPTION
      "Path: tunnels.editConf.ipsecTunnels.ipsec.ikePresharedSA.encModePreSharedKey

       Possibilities:
               none   (1)
               encrypt   (2)
               encType1   (3)
               invalid   (128)"
   ::= {er1645v2TTmplIpsTunEntry 91750400}

er1645v2TTmplIpsTunIpsecPsEncKey OBJECT-TYPE
   SYNTAX      DisplayString
   MAX-ACCESS  read-write
   STATUS      current
   DESCRIPTION
      "Path: tunnels.editConf.ipsecTunnels.ipsec.ikePresharedSA.encPreSharedKey"
   ::= {er1645v2TTmplIpsTunEntry 92012544}

er1645v2TTmplIpsTunIpsecPsPIdProt OBJECT-TYPE
   SYNTAX      INTEGER
               {
               any (0),
               aH (51),
               eGP (8),
               eSP (50),
               gRE (47),
               iCMP (1),
               iGP (9),
               iGMP (2),
               iGRP (88),
               iPinIP (4),
               oSPF (89),
               uDP (17),
               rSVP (46),
               tCP (6),
               tCPestablished (255)
               }
   MAX-ACCESS  read-write
   STATUS      current
   DESCRIPTION
      "Path: tunnels.editConf.ipsecTunnels.ipsec.ikePresharedSA.proxyId.ipProtocol

       Possibilities:
               any   (0)
               AH   (51)
               EGP   (8)
               ESP   (50)
               GRE   (47)
               ICMP   (1)
               IGP   (9)
               IGMP   (2)
               IGRP   (88)
               IPinIP   (4)
               OSPF   (89)
               UDP   (17)
               RSVP   (46)
               TCP   (6)
               TCPestablished   (255)"
   ::= {er1645v2TTmplIpsTunEntry 91504640}

er1645v2TTmplIpsTunIpsecPsPIdLocAddr OBJECT-TYPE
   SYNTAX      IpAddress
   MAX-ACCESS  read-write
   STATUS      current
   DESCRIPTION
      "Path: tunnels.editConf.ipsecTunnels.ipsec.ikePresharedSA.proxyId.localIpAddress"
   ::= {er1645v2TTmplIpsTunEntry 91521024}

er1645v2TTmplIpsTunIpsecPsPIdLocMask OBJECT-TYPE
   SYNTAX      IpAddress
   MAX-ACCESS  read-write
   STATUS      current
   DESCRIPTION
      "Path: tunnels.editConf.ipsecTunnels.ipsec.ikePresharedSA.proxyId.localIpMask"
   ::= {er1645v2TTmplIpsTunEntry 91537408}

er1645v2TTmplIpsTunIpsecPsPIdLocPort OBJECT-TYPE
   SYNTAX      INTEGER
               {
               any (0),
               bgp (179),
               bootpmdhcpmc (68),
               bootpmdhcpms (67),
               cpudpencap (2746),
               discard (9),
               domain (53),
               echo (7),
               ftp (21),
               ftpmdata (20),
               ftps (990),
               ftpsmdata (989),
               httpmalt (8080),
               https (443),
               imap (134),
               imap3 (220),
               imaps (993),
               ipsecmnatmt (4500),
               isakmp (500),
               l2tp (1701),
               ldap (389),
               microsoftmds (445),
               msmwbtmserver (3389),
               msnp (1863),
               nameserver (42),
               netbiosmdgm (138),
               netbiosmns (137),
               netbiosmssn (139),
               nntp (119),
               ntp (123),
               pop3 (110),
               pop3s (995),
               pptp (1723),
               router (520),
               rtsp (554),
               sip (5060),
               smtp (25),
               smtps (465),
               snmp (161),
               snmptrap (162),
               socks (1080),
               ssdpmuPnP (1900),
               ssh (22),
               syslog (514),
               telindus (1728),
               telnet (23),
               telnets (992),
               tftp (69),
               whip (8700),
               wwwmhttp (80),
               z39d50 (210)
               }
   MAX-ACCESS  read-write
   STATUS      current
   DESCRIPTION
      "Path: tunnels.editConf.ipsecTunnels.ipsec.ikePresharedSA.proxyId.localIpPort

       Possibilities:
               any   (0)
               bgp   (179)
               bootp-dhcp-c   (68)
               bootp-dhcp-s   (67)
               cpudpencap   (2746)
               discard   (9)
               domain   (53)
               echo   (7)
               ftp   (21)
               ftp-data   (20)
               ftps   (990)
               ftps-data   (989)
               http-alt   (8080)
               https   (443)
               imap   (134)
               imap3   (220)
               imaps   (993)
               ipsec-nat-t   (4500)
               isakmp   (500)
               l2tp   (1701)
               ldap   (389)
               microsoft-ds   (445)
               ms-wbt-server   (3389)
               msnp   (1863)
               nameserver   (42)
               netbios-dgm   (138)
               netbios-ns   (137)
               netbios-ssn   (139)
               nntp   (119)
               ntp   (123)
               pop3   (110)
               pop3s   (995)
               pptp   (1723)
               router   (520)
               rtsp   (554)
               sip   (5060)
               smtp   (25)
               smtps   (465)
               snmp   (161)
               snmptrap   (162)
               socks   (1080)
               ssdp-uPnP   (1900)
               ssh   (22)
               syslog   (514)
               telindus   (1728)
               telnet   (23)
               telnets   (992)
               tftp   (69)
               whip   (8700)
               www-http   (80)
               z39.50   (210)"
   ::= {er1645v2TTmplIpsTunEntry 91553792}

er1645v2TTmplIpsTunIpsecPsPIdRemAddr OBJECT-TYPE
   SYNTAX      IpAddress
   MAX-ACCESS  read-write
   STATUS      current
   DESCRIPTION
      "Path: tunnels.editConf.ipsecTunnels.ipsec.ikePresharedSA.proxyId.remoteIpAddress"
   ::= {er1645v2TTmplIpsTunEntry 91570176}

er1645v2TTmplIpsTunIpsecPsPIdRemMask OBJECT-TYPE
   SYNTAX      IpAddress
   MAX-ACCESS  read-write
   STATUS      current
   DESCRIPTION
      "Path: tunnels.editConf.ipsecTunnels.ipsec.ikePresharedSA.proxyId.remoteIpMask"
   ::= {er1645v2TTmplIpsTunEntry 91586560}

er1645v2TTmplIpsTunIpsecPsPIdRemPort OBJECT-TYPE
   SYNTAX      INTEGER
               {
               any (0),
               bgp (179),
               bootpmdhcpmc (68),
               bootpmdhcpms (67),
               cpudpencap (2746),
               discard (9),
               domain (53),
               echo (7),
               ftp (21),
               ftpmdata (20),
               ftps (990),
               ftpsmdata (989),
               httpmalt (8080),
               https (443),
               imap (134),
               imap3 (220),
               imaps (993),
               ipsecmnatmt (4500),
               isakmp (500),
               l2tp (1701),
               ldap (389),
               microsoftmds (445),
               msmwbtmserver (3389),
               msnp (1863),
               nameserver (42),
               netbiosmdgm (138),
               netbiosmns (137),
               netbiosmssn (139),
               nntp (119),
               ntp (123),
               pop3 (110),
               pop3s (995),
               pptp (1723),
               router (520),
               rtsp (554),
               sip (5060),
               smtp (25),
               smtps (465),
               snmp (161),
               snmptrap (162),
               socks (1080),
               ssdpmuPnP (1900),
               ssh (22),
               syslog (514),
               telindus (1728),
               telnet (23),
               telnets (992),
               tftp (69),
               whip (8700),
               wwwmhttp (80),
               z39d50 (210)
               }
   MAX-ACCESS  read-write
   STATUS      current
   DESCRIPTION
      "Path: tunnels.editConf.ipsecTunnels.ipsec.ikePresharedSA.proxyId.remoteIpPort

       Possibilities:
               any   (0)
               bgp   (179)
               bootp-dhcp-c   (68)
               bootp-dhcp-s   (67)
               cpudpencap   (2746)
               discard   (9)
               domain   (53)
               echo   (7)
               ftp   (21)
               ftp-data   (20)
               ftps   (990)
               ftps-data   (989)
               http-alt   (8080)
               https   (443)
               imap   (134)
               imap3   (220)
               imaps   (993)
               ipsec-nat-t   (4500)
               isakmp   (500)
               l2tp   (1701)
               ldap   (389)
               microsoft-ds   (445)
               ms-wbt-server   (3389)
               msnp   (1863)
               nameserver   (42)
               netbios-dgm   (138)
               netbios-ns   (137)
               netbios-ssn   (139)
               nntp   (119)
               ntp   (123)
               pop3   (110)
               pop3s   (995)
               pptp   (1723)
               router   (520)
               rtsp   (554)
               sip   (5060)
               smtp   (25)
               smtps   (465)
               snmp   (161)
               snmptrap   (162)
               socks   (1080)
               ssdp-uPnP   (1900)
               ssh   (22)
               syslog   (514)
               telindus   (1728)
               telnet   (23)
               telnets   (992)
               tftp   (69)
               whip   (8700)
               www-http   (80)
               z39.50   (210)"
   ::= {er1645v2TTmplIpsTunEntry 91602944}

er1645v2TTmplIpsTunIpsecCeCfg OBJECT-TYPE
   SYNTAX      DisplayString
   MAX-ACCESS  read-write
   STATUS      current
   DESCRIPTION
      "Path: tunnels.editConf.ipsecTunnels.ipsec.ikeCertificateSA.ikeSA"
   ::= {er1645v2TTmplIpsTunEntry 92282880}

er1645v2TTmplIpsTunIpsecCeLIdIp OBJECT-TYPE
   SYNTAX      IpAddress
   MAX-ACCESS  read-write
   STATUS      current
   DESCRIPTION
      "Path: tunnels.editConf.ipsecTunnels.ipsec.ikeCertificateSA.localId.ipAddress"
   ::= {er1645v2TTmplIpsTunEntry 92291104}

er1645v2TTmplIpsTunIpsecCeLIdHn OBJECT-TYPE
   SYNTAX      DisplayString
   MAX-ACCESS  read-write
   STATUS      current
   DESCRIPTION
      "Path: tunnels.editConf.ipsecTunnels.ipsec.ikeCertificateSA.localId.hostName"
   ::= {er1645v2TTmplIpsTunEntry 92291136}

er1645v2TTmplIpsTunIpsecCeLIdUn OBJECT-TYPE
   SYNTAX      DisplayString
   MAX-ACCESS  read-write
   STATUS      current
   DESCRIPTION
      "Path: tunnels.editConf.ipsecTunnels.ipsec.ikeCertificateSA.localId.user"
   ::= {er1645v2TTmplIpsTunEntry 92291168}

er1645v2TTmplIpsTunIpsecCeLIdDn OBJECT-TYPE
   SYNTAX      DisplayString
   MAX-ACCESS  read-write
   STATUS      current
   DESCRIPTION
      "Path: tunnels.editConf.ipsecTunnels.ipsec.ikeCertificateSA.localId.derAsn1Dn"
   ::= {er1645v2TTmplIpsTunEntry 92291200}

er1645v2TTmplIpsTunIpsecCeRIdIp OBJECT-TYPE
   SYNTAX      IpAddress
   MAX-ACCESS  read-write
   STATUS      current
   DESCRIPTION
      "Path: tunnels.editConf.ipsecTunnels.ipsec.ikeCertificateSA.remoteId.ipAddress"
   ::= {er1645v2TTmplIpsTunEntry 92299296}

er1645v2TTmplIpsTunIpsecCeRIdHn OBJECT-TYPE
   SYNTAX      DisplayString
   MAX-ACCESS  read-write
   STATUS      current
   DESCRIPTION
      "Path: tunnels.editConf.ipsecTunnels.ipsec.ikeCertificateSA.remoteId.hostName"
   ::= {er1645v2TTmplIpsTunEntry 92299328}

er1645v2TTmplIpsTunIpsecCeRIdUn OBJECT-TYPE
   SYNTAX      DisplayString
   MAX-ACCESS  read-write
   STATUS      current
   DESCRIPTION
      "Path: tunnels.editConf.ipsecTunnels.ipsec.ikeCertificateSA.remoteId.user"
   ::= {er1645v2TTmplIpsTunEntry 92299360}

er1645v2TTmplIpsTunIpsecCeRIdDn OBJECT-TYPE
   SYNTAX      DisplayString
   MAX-ACCESS  read-write
   STATUS      current
   DESCRIPTION
      "Path: tunnels.editConf.ipsecTunnels.ipsec.ikeCertificateSA.remoteId.derAsn1Dn"
   ::= {er1645v2TTmplIpsTunEntry 92299392}

er1645v2TTmplIpsTunIpsecCePIdProt OBJECT-TYPE
   SYNTAX      INTEGER
               {
               any (0),
               aH (51),
               eGP (8),
               eSP (50),
               gRE (47),
               iCMP (1),
               iGP (9),
               iGMP (2),
               iGRP (88),
               iPinIP (4),
               oSPF (89),
               uDP (17),
               rSVP (46),
               tCP (6),
               tCPestablished (255)
               }
   MAX-ACCESS  read-write
   STATUS      current
   DESCRIPTION
      "Path: tunnels.editConf.ipsecTunnels.ipsec.ikeCertificateSA.proxyId.ipProtocol

       Possibilities:
               any   (0)
               AH   (51)
               EGP   (8)
               ESP   (50)
               GRE   (47)
               ICMP   (1)
               IGP   (9)
               IGMP   (2)
               IGRP   (88)
               IPinIP   (4)
               OSPF   (89)
               UDP   (17)
               RSVP   (46)
               TCP   (6)
               TCPestablished   (255)"
   ::= {er1645v2TTmplIpsTunEntry 92316160}

er1645v2TTmplIpsTunIpsecCePIdLocAddr OBJECT-TYPE
   SYNTAX      IpAddress
   MAX-ACCESS  read-write
   STATUS      current
   DESCRIPTION
      "Path: tunnels.editConf.ipsecTunnels.ipsec.ikeCertificateSA.proxyId.localIpAddress"
   ::= {er1645v2TTmplIpsTunEntry 92316672}

er1645v2TTmplIpsTunIpsecCePIdLocMask OBJECT-TYPE
   SYNTAX      IpAddress
   MAX-ACCESS  read-write
   STATUS      current
   DESCRIPTION
      "Path: tunnels.editConf.ipsecTunnels.ipsec.ikeCertificateSA.proxyId.localIpMask"
   ::= {er1645v2TTmplIpsTunEntry 92317184}

er1645v2TTmplIpsTunIpsecCePIdLocPort OBJECT-TYPE
   SYNTAX      INTEGER
               {
               any (0),
               bgp (179),
               bootpmdhcpmc (68),
               bootpmdhcpms (67),
               cpudpencap (2746),
               discard (9),
               domain (53),
               echo (7),
               ftp (21),
               ftpmdata (20),
               ftps (990),
               ftpsmdata (989),
               httpmalt (8080),
               https (443),
               imap (134),
               imap3 (220),
               imaps (993),
               ipsecmnatmt (4500),
               isakmp (500),
               l2tp (1701),
               ldap (389),
               microsoftmds (445),
               msmwbtmserver (3389),
               msnp (1863),
               nameserver (42),
               netbiosmdgm (138),
               netbiosmns (137),
               netbiosmssn (139),
               nntp (119),
               ntp (123),
               pop3 (110),
               pop3s (995),
               pptp (1723),
               router (520),
               rtsp (554),
               sip (5060),
               smtp (25),
               smtps (465),
               snmp (161),
               snmptrap (162),
               socks (1080),
               ssdpmuPnP (1900),
               ssh (22),
               syslog (514),
               telindus (1728),
               telnet (23),
               telnets (992),
               tftp (69),
               whip (8700),
               wwwmhttp (80),
               z39d50 (210)
               }
   MAX-ACCESS  read-write
   STATUS      current
   DESCRIPTION
      "Path: tunnels.editConf.ipsecTunnels.ipsec.ikeCertificateSA.proxyId.localIpPort

       Possibilities:
               any   (0)
               bgp   (179)
               bootp-dhcp-c   (68)
               bootp-dhcp-s   (67)
               cpudpencap   (2746)
               discard   (9)
               domain   (53)
               echo   (7)
               ftp   (21)
               ftp-data   (20)
               ftps   (990)
               ftps-data   (989)
               http-alt   (8080)
               https   (443)
               imap   (134)
               imap3   (220)
               imaps   (993)
               ipsec-nat-t   (4500)
               isakmp   (500)
               l2tp   (1701)
               ldap   (389)
               microsoft-ds   (445)
               ms-wbt-server   (3389)
               msnp   (1863)
               nameserver   (42)
               netbios-dgm   (138)
               netbios-ns   (137)
               netbios-ssn   (139)
               nntp   (119)
               ntp   (123)
               pop3   (110)
               pop3s   (995)
               pptp   (1723)
               router   (520)
               rtsp   (554)
               sip   (5060)
               smtp   (25)
               smtps   (465)
               snmp   (161)
               snmptrap   (162)
               socks   (1080)
               ssdp-uPnP   (1900)
               ssh   (22)
               syslog   (514)
               telindus   (1728)
               telnet   (23)
               telnets   (992)
               tftp   (69)
               whip   (8700)
               www-http   (80)
               z39.50   (210)"
   ::= {er1645v2TTmplIpsTunEntry 92317696}

er1645v2TTmplIpsTunIpsecCePIdRemAddr OBJECT-TYPE
   SYNTAX      IpAddress
   MAX-ACCESS  read-write
   STATUS      current
   DESCRIPTION
      "Path: tunnels.editConf.ipsecTunnels.ipsec.ikeCertificateSA.proxyId.remoteIpAddress"
   ::= {er1645v2TTmplIpsTunEntry 92318208}

er1645v2TTmplIpsTunIpsecCePIdRemMask OBJECT-TYPE
   SYNTAX      IpAddress
   MAX-ACCESS  read-write
   STATUS      current
   DESCRIPTION
      "Path: tunnels.editConf.ipsecTunnels.ipsec.ikeCertificateSA.proxyId.remoteIpMask"
   ::= {er1645v2TTmplIpsTunEntry 92318720}

er1645v2TTmplIpsTunIpsecCePIdRemPort OBJECT-TYPE
   SYNTAX      INTEGER
               {
               any (0),
               bgp (179),
               bootpmdhcpmc (68),
               bootpmdhcpms (67),
               cpudpencap (2746),
               discard (9),
               domain (53),
               echo (7),
               ftp (21),
               ftpmdata (20),
               ftps (990),
               ftpsmdata (989),
               httpmalt (8080),
               https (443),
               imap (134),
               imap3 (220),
               imaps (993),
               ipsecmnatmt (4500),
               isakmp (500),
               l2tp (1701),
               ldap (389),
               microsoftmds (445),
               msmwbtmserver (3389),
               msnp (1863),
               nameserver (42),
               netbiosmdgm (138),
               netbiosmns (137),
               netbiosmssn (139),
               nntp (119),
               ntp (123),
               pop3 (110),
               pop3s (995),
               pptp (1723),
               router (520),
               rtsp (554),
               sip (5060),
               smtp (25),
               smtps (465),
               snmp (161),
               snmptrap (162),
               socks (1080),
               ssdpmuPnP (1900),
               ssh (22),
               syslog (514),
               telindus (1728),
               telnet (23),
               telnets (992),
               tftp (69),
               whip (8700),
               wwwmhttp (80),
               z39d50 (210)
               }
   MAX-ACCESS  read-write
   STATUS      current
   DESCRIPTION
      "Path: tunnels.editConf.ipsecTunnels.ipsec.ikeCertificateSA.proxyId.remoteIpPort

       Possibilities:
               any   (0)
               bgp   (179)
               bootp-dhcp-c   (68)
               bootp-dhcp-s   (67)
               cpudpencap   (2746)
               discard   (9)
               domain   (53)
               echo   (7)
               ftp   (21)
               ftp-data   (20)
               ftps   (990)
               ftps-data   (989)
               http-alt   (8080)
               https   (443)
               imap   (134)
               imap3   (220)
               imaps   (993)
               ipsec-nat-t   (4500)
               isakmp   (500)
               l2tp   (1701)
               ldap   (389)
               microsoft-ds   (445)
               ms-wbt-server   (3389)
               msnp   (1863)
               nameserver   (42)
               netbios-dgm   (138)
               netbios-ns   (137)
               netbios-ssn   (139)
               nntp   (119)
               ntp   (123)
               pop3   (110)
               pop3s   (995)
               pptp   (1723)
               router   (520)
               rtsp   (554)
               sip   (5060)
               smtp   (25)
               smtps   (465)
               snmp   (161)
               snmptrap   (162)
               socks   (1080)
               ssdp-uPnP   (1900)
               ssh   (22)
               syslog   (514)
               telindus   (1728)
               telnet   (23)
               telnets   (992)
               tftp   (69)
               whip   (8700)
               www-http   (80)
               z39.50   (210)"
   ::= {er1645v2TTmplIpsTunEntry 92319232}

er1645v2TTmplIpsTunType OBJECT-TYPE
   SYNTAX      INTEGER
               {
               outgoingDial (1),
               outgoingLeasedLine (2),
               incoming (0)
               }
   MAX-ACCESS  read-write
   STATUS      current
   DESCRIPTION
      "Path: tunnels.editConf.ipsecTunnels.type

       Possibilities:
               outgoingDial   (1)
               outgoingLeasedLine   (2)
               incoming   (0)"
   ::= {er1645v2TTmplIpsTunEntry 134217728}

er1645v2TTmplIpsTunNoTraffTO OBJECT-TYPE
   SYNTAX      TimeTicks
   MAX-ACCESS  read-write
   STATUS      current
   DESCRIPTION
      "Path: tunnels.editConf.ipsecTunnels.noTrafficTimeOut

       Time in centi-second."
   ::= {er1645v2TTmplIpsTunEntry 150994944}

er1645v2TTmplIpsTunNoTraffDi OBJECT-TYPE
   SYNTAX      INTEGER
               {
               inbound (1),
               outbound (2),
               both (3)
               }
   MAX-ACCESS  read-write
   STATUS      current
   DESCRIPTION
      "Path: tunnels.editConf.ipsecTunnels.noTrafficDirection

       Possibilities:
               inbound   (1)
               outbound   (2)
               both   (3)"
   ::= {er1645v2TTmplIpsTunEntry 184549376}

er1645v2TTmplIpsTunRemRouteDefRt OBJECT-TYPE
   SYNTAX      INTEGER
               {
               disabled (0),
               enabled (1)
               }
   MAX-ACCESS  read-write
   STATUS      current
   DESCRIPTION
      "Path: tunnels.editConf.ipsecTunnels.remoteRoute.useDefaultRoute

       Possibilities:
               disabled   (0)
               enabled   (1)"
   ::= {er1645v2TTmplIpsTunEntry 167837696}

er1645v2TTmplIpsTunTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               copy (256),
               queueTosMap (257)
               }
   MAX-ACCESS  read-write
   STATUS      current
   DESCRIPTION
      "Path: tunnels.editConf.ipsecTunnels.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               copy   (256)
               queueTosMap   (257)"
   ::= {er1645v2TTmplIpsTunEntry 100663296}

er1645v2TTmplIpsTunQueueTosMapQueue1 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.ipsecTunnels.queueTosMap.queue1

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TTmplIpsTunEntry 503382016}

er1645v2TTmplIpsTunQueueTosMapQueue2 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.ipsecTunnels.queueTosMap.queue2

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TTmplIpsTunEntry 503447552}

er1645v2TTmplIpsTunQueueTosMapQueue3 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.ipsecTunnels.queueTosMap.queue3

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TTmplIpsTunEntry 503513088}

er1645v2TTmplIpsTunQueueTosMapQueue4 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.ipsecTunnels.queueTosMap.queue4

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TTmplIpsTunEntry 503578624}

er1645v2TTmplIpsTunQueueTosMapQueue5 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.ipsecTunnels.queueTosMap.queue5

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TTmplIpsTunEntry 503644160}

er1645v2TTmplIpsTunQueueTosMapLowDelayQueue OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.ipsecTunnels.queueTosMap.lowDelayQueue

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TTmplIpsTunEntry 503709696}

er1645v2TTmplIpsTunQueueTosMapLowDelay2Queue OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.ipsecTunnels.queueTosMap.lowDelay2Queue

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TTmplIpsTunEntry 503775232}

er1645v2TTmplIpsTunQueueTosMapSystemQueue OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.ipsecTunnels.queueTosMap.systemQueue

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TTmplIpsTunEntry 503840768}

er1645v2TTmplIpsTunDf OBJECT-TYPE
   SYNTAX      INTEGER
               {
               clear (0),
               set (1),
               copy (2)
               }
   MAX-ACCESS  read-write
   STATUS      current
   DESCRIPTION
      "Path: tunnels.editConf.ipsecTunnels.dontFragmentBit

       Possibilities:
               clear   (0)
               set   (1)
               copy   (2)"
   ::= {er1645v2TTmplIpsTunEntry 117440512}

er1645v2TTmplIpsTunMtu OBJECT-TYPE
   SYNTAX      Integer32
   MAX-ACCESS  read-write
   STATUS      current
   DESCRIPTION
      "Path: tunnels.editConf.ipsecTunnels.mtu"
   ::= {er1645v2TTmplIpsTunEntry 301989888}



sr1645v2TTmpl OBJECT IDENTIFIER ::= {r1645v2TTmpl 14}


sr1645v2TTmplDescr OBJECT-TYPE
   SYNTAX      DisplayString
   MAX-ACCESS  read-only
   STATUS      current
   DESCRIPTION
      "Path: tunnels.status.ifDescr
       Info: ifDescr"
   ::= {sr1645v2TTmpl 101}


sr1645v2TTmplType OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: tunnels.status.ifType
       Info: ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1645v2TTmpl 102}


sr1645v2TTmplOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: tunnels.status.ifOperStatus
       Info: ifOperStatus

       Possibilities:
               up   (1)
               down   (2)
               testing   (3)
               unknown   (4)
               dormant   (5)
               notPresent   (6)
               lowerLayerDown   (7)"
   ::= {sr1645v2TTmpl 107}


sr1645v2TTmplSnmpIndex OBJECT-TYPE
   SYNTAX      Integer32
   MAX-ACCESS  read-only
   STATUS      current
   DESCRIPTION
      "Path: tunnels.status.snmpIndex
       Info: SNMP index assigned to this object"
   ::= {sr1645v2TTmpl 269}


sr1645v2TTmplStat OBJECT IDENTIFIER ::= {sr1645v2TTmpl 2}

sr1645v2TTmplStatSSCTable OBJECT-TYPE
   SYNTAX      SEQUENCE OF Sr1645v2TTmplStatEntry
   MAX-ACCESS  not-accessible
   STATUS      current
   DESCRIPTION
      ""
   ::= {sr1645v2TTmplStat 1}

sr1645v2TTmplStatEntry OBJECT-TYPE
   SYNTAX      Sr1645v2TTmplStatEntry
   MAX-ACCESS  not-accessible
   STATUS      current
   DESCRIPTION
      ""
   INDEX      { sr1645v2TTmplStatTableIx }
   ::= {sr1645v2TTmplStatSSCTable 1}

Sr1645v2TTmplStatEntry ::=
   SEQUENCE
      {
      sr1645v2TTmplStatTableIx
         TableIndex,
      sr1645v2TTmplStatName
         DisplayString,
      sr1645v2TTmplStatMode
         INTEGER,
      sr1645v2TTmplStatIfOperStatus
         INTEGER,
      sr1645v2TTmplStatIfLastChange
         TimeTicks,
      sr1645v2TTmplStatIfLastChangeDate
         DisplayString,
      sr1645v2TTmplStatIpVrfRouter
         DisplayString,
      sr1645v2TTmplStatIpAddress
         IpAddress,
      sr1645v2TTmplStatIpNetMask
         IpAddress,
      sr1645v2TTmplStatIpRemote
         IpAddress,
      sr1645v2TTmplStatBridgingStatus
         INTEGER,
      sr1645v2TTmplStatBridgingSpanningTreePortRole
         INTEGER,
      sr1645v2TTmplStatBridgingSpanningTreePortId
         Integer32,
      sr1645v2TTmplStatBridgingSpanningTreePpCostExtPathCost
         Integer32,
      sr1645v2TTmplStatBridgingSpanningTreePpCostIntPathCost
         Integer32,
      sr1645v2TTmplStatBridgingSpanningTreeExtRpCost
         Integer32,
      sr1645v2TTmplStatBridgingSpanningTreeIntRpCost
         Integer32,
      sr1645v2TTmplStatBridgingSpanningTreeDesBrIdPriority
         Integer32,
      sr1645v2TTmplStatBridgingSpanningTreeDesBrIdMacAddress
         OCTET STRING,
      sr1645v2TTmplStatBridgingSpanningTreeDesPrtId
         Integer32,
      sr1645v2TTmplStatBridgingSpanningTreeDesInt
         INTEGER,
      sr1645v2TTmplStatBridgingSpanningTreeEdgeDetection
         INTEGER,
      sr1645v2TTmplStatL2tpLocalIpAddress
         IpAddress,
      sr1645v2TTmplStatL2tpRemAddr
         IpAddress,
      sr1645v2TTmplStatL2tpSendingSeqNr
         Integer32,
      sr1645v2TTmplStatL2tpReceivingSeqNr
         Integer32,
      sr1645v2TTmplStatL2tpL2tpType
         INTEGER,
      sr1645v2TTmplStatL2tpControlState
         INTEGER,
      sr1645v2TTmplStatL2tpCallState
         INTEGER,
      sr1645v2TTmplStatL2tpDeliveryState
         INTEGER,
      sr1645v2TTmplStatL2tpAuthenState
         INTEGER,
      sr1645v2TTmplStatPppLcpState
         INTEGER,
      sr1645v2TTmplStatPppIpcpState
         INTEGER,
      sr1645v2TTmplStatPppBcpState
         INTEGER,
      sr1645v2TTmplStatPppMyAutSt
         INTEGER,
      sr1645v2TTmplStatPppMyAutUsr
         DisplayString,
      sr1645v2TTmplStatPppHisAutSt
         INTEGER
      }

sr1645v2TTmplStatTableIx OBJECT-TYPE
   SYNTAX      TableIndex
   MAX-ACCESS  not-accessible
   STATUS      current
   DESCRIPTION
      ""
   ::= {sr1645v2TTmplStatEntry 11}

sr1645v2TTmplStatName OBJECT-TYPE
   SYNTAX      DisplayString
   MAX-ACCESS  read-only
   STATUS      current
   DESCRIPTION
      "Path: tunnels.status.l2tpTunnels.name"
   ::= {sr1645v2TTmplStatEntry 16777216}

sr1645v2TTmplStatMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: tunnels.status.l2tpTunnels.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1645v2TTmplStatEntry 335544320}

sr1645v2TTmplStatIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: tunnels.status.l2tpTunnels.ifOperStatus

       Possibilities:
               up   (1)
               down   (2)
               testing   (3)
               unknown   (4)
               dormant   (5)
               notPresent   (6)
               lowerLayerDown   (7)"
   ::= {sr1645v2TTmplStatEntry 1795162112}

sr1645v2TTmplStatIfLastChange OBJECT-TYPE
   SYNTAX      TimeTicks
   MAX-ACCESS  read-only
   STATUS      current
   DESCRIPTION
      "Path: tunnels.status.l2tpTunnels.ifLastChange

       Time in centi-second."
   ::= {sr1645v2TTmplStatEntry 1811939328}

sr1645v2TTmplStatIfLastChangeDate OBJECT-TYPE
   SYNTAX      DisplayString
   MAX-ACCESS  read-only
   STATUS      current
   DESCRIPTION
      "Path: tunnels.status.l2tpTunnels.ifLastChangeDate"
   ::= {sr1645v2TTmplStatEntry 3070230528}

sr1645v2TTmplStatIpVrfRouter OBJECT-TYPE
   SYNTAX      DisplayString
   MAX-ACCESS  read-only
   STATUS      current
   DESCRIPTION
      "Path: tunnels.status.l2tpTunnels.ip.vrfRouter"
   ::= {sr1645v2TTmplStatEntry 50397184}

sr1645v2TTmplStatIpAddress OBJECT-TYPE
   SYNTAX      IpAddress
   MAX-ACCESS  read-only
   STATUS      current
   DESCRIPTION
      "Path: tunnels.status.l2tpTunnels.ip.address"
   ::= {sr1645v2TTmplStatEntry 51380224}

sr1645v2TTmplStatIpNetMask OBJECT-TYPE
   SYNTAX      IpAddress
   MAX-ACCESS  read-only
   STATUS      current
   DESCRIPTION
      "Path: tunnels.status.l2tpTunnels.ip.netMask"
   ::= {sr1645v2TTmplStatEntry 51445760}

sr1645v2TTmplStatIpRemote OBJECT-TYPE
   SYNTAX      IpAddress
   MAX-ACCESS  read-only
   STATUS      current
   DESCRIPTION
      "Path: tunnels.status.l2tpTunnels.ip.remote"
   ::= {sr1645v2TTmplStatEntry 51511296}

sr1645v2TTmplStatBridgingStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: tunnels.status.l2tpTunnels.bridging.status

       Possibilities:
               disabled   (0)
               discarding   (1)
               learning   (2)
               forwarding   (3)
               backupBlockedIntfDown   (256)
               backupBlockedIntfUp   (259)
               shutdown   (255)"
   ::= {sr1645v2TTmplStatEntry 453050368}

sr1645v2TTmplStatBridgingSpanningTreePortRole OBJECT-TYPE
   SYNTAX      INTEGER
               {
               none (0),
               root (1),
               designated (2),
               alternate (3),
               backup (4),
               disabled (5),
               master (6)
               }
   MAX-ACCESS  read-only
   STATUS      current
   DESCRIPTION
      "Path: tunnels.status.l2tpTunnels.bridging.spanningTree.portRole

       Possibilities:
               none   (0)
               root   (1)
               designated   (2)
               alternate   (3)
               backup   (4)
               disabled   (5)
               master   (6)"
   ::= {sr1645v2TTmplStatEntry 453116160}

sr1645v2TTmplStatBridgingSpanningTreePortId OBJECT-TYPE
   SYNTAX      Integer32
   MAX-ACCESS  read-only
   STATUS      current
   DESCRIPTION
      "Path: tunnels.status.l2tpTunnels.bridging.spanningTree.portId"
   ::= {sr1645v2TTmplStatEntry 453116416}

sr1645v2TTmplStatBridgingSpanningTreePpCostExtPathCost OBJECT-TYPE
   SYNTAX      Integer32
   MAX-ACCESS  read-only
   STATUS      current
   DESCRIPTION
      "Path: tunnels.status.l2tpTunnels.bridging.spanningTree.portPathCosts.extPathCost"
   ::= {sr1645v2TTmplStatEntry 453116673}

sr1645v2TTmplStatBridgingSpanningTreePpCostIntPathCost OBJECT-TYPE
   SYNTAX      Integer32
   MAX-ACCESS  read-only
   STATUS      current
   DESCRIPTION
      "Path: tunnels.status.l2tpTunnels.bridging.spanningTree.portPathCosts.intPathCost"
   ::= {sr1645v2TTmplStatEntry 453116674}

sr1645v2TTmplStatBridgingSpanningTreeExtRpCost OBJECT-TYPE
   SYNTAX      Integer32
   MAX-ACCESS  read-only
   STATUS      current
   DESCRIPTION
      "Path: tunnels.status.l2tpTunnels.bridging.spanningTree.extRootPathCost"
   ::= {sr1645v2TTmplStatEntry 453116928}

sr1645v2TTmplStatBridgingSpanningTreeIntRpCost OBJECT-TYPE
   SYNTAX      Integer32
   MAX-ACCESS  read-only
   STATUS      current
   DESCRIPTION
      "Path: tunnels.status.l2tpTunnels.bridging.spanningTree.intRootPathCost"
   ::= {sr1645v2TTmplStatEntry 453117184}

sr1645v2TTmplStatBridgingSpanningTreeDesBrIdPriority OBJECT-TYPE
   SYNTAX      Integer32
   MAX-ACCESS  read-only
   STATUS      current
   DESCRIPTION
      "Path: tunnels.status.l2tpTunnels.bridging.spanningTree.designatedBridgeId.priority"
   ::= {sr1645v2TTmplStatEntry 453117441}

sr1645v2TTmplStatBridgingSpanningTreeDesBrIdMacAddress OBJECT-TYPE
   SYNTAX      OCTET STRING
   MAX-ACCESS  read-only
   STATUS      current
   DESCRIPTION
      "Path: tunnels.status.l2tpTunnels.bridging.spanningTree.designatedBridgeId.macAddress

       MAC address."
   ::= {sr1645v2TTmplStatEntry 453117442}

sr1645v2TTmplStatBridgingSpanningTreeDesPrtId OBJECT-TYPE
   SYNTAX      Integer32
   MAX-ACCESS  read-only
   STATUS      current
   DESCRIPTION
      "Path: tunnels.status.l2tpTunnels.bridging.spanningTree.designatedPortId"
   ::= {sr1645v2TTmplStatEntry 453117696}

sr1645v2TTmplStatBridgingSpanningTreeDesInt OBJECT-TYPE
   SYNTAX      INTEGER
               {
               no (0),
               yes (1)
               }
   MAX-ACCESS  read-only
   STATUS      current
   DESCRIPTION
      "Path: tunnels.status.l2tpTunnels.bridging.spanningTree.designatedOrInternal

       Possibilities:
               no   (0)
               yes   (1)"
   ::= {sr1645v2TTmplStatEntry 453117952}

sr1645v2TTmplStatBridgingSpanningTreeEdgeDetection OBJECT-TYPE
   SYNTAX      INTEGER
               {
               none (0),
               edge (1),
               notEdge (2)
               }
   MAX-ACCESS  read-only
   STATUS      current
   DESCRIPTION
      "Path: tunnels.status.l2tpTunnels.bridging.spanningTree.edgeDetection

       Possibilities:
               none   (0)
               edge   (1)
               notEdge   (2)"
   ::= {sr1645v2TTmplStatEntry 453118208}

sr1645v2TTmplStatL2tpLocalIpAddress OBJECT-TYPE
   SYNTAX      IpAddress
   MAX-ACCESS  read-only
   STATUS      current
   DESCRIPTION
      "Path: tunnels.status.l2tpTunnels.l2tp.localIpAddress"
   ::= {sr1645v2TTmplStatEntry 302579712}

sr1645v2TTmplStatL2tpRemAddr OBJECT-TYPE
   SYNTAX      IpAddress
   MAX-ACCESS  read-only
   STATUS      current
   DESCRIPTION
      "Path: tunnels.status.l2tpTunnels.l2tp.remoteIpAddress"
   ::= {sr1645v2TTmplStatEntry 302645248}

sr1645v2TTmplStatL2tpSendingSeqNr OBJECT-TYPE
   SYNTAX      Integer32
   MAX-ACCESS  read-only
   STATUS      current
   DESCRIPTION
      "Path: tunnels.status.l2tpTunnels.l2tp.sendingSeqNr"
   ::= {sr1645v2TTmplStatEntry 302055424}

sr1645v2TTmplStatL2tpReceivingSeqNr OBJECT-TYPE
   SYNTAX      Integer32
   MAX-ACCESS  read-only
   STATUS      current
   DESCRIPTION
      "Path: tunnels.status.l2tpTunnels.l2tp.receivingSeqNr"
   ::= {sr1645v2TTmplStatEntry 302120960}

sr1645v2TTmplStatL2tpL2tpType OBJECT-TYPE
   SYNTAX      INTEGER
               {
               lac (1),
               lns (2),
               auto (3)
               }
   MAX-ACCESS  read-only
   STATUS      current
   DESCRIPTION
      "Path: tunnels.status.l2tpTunnels.l2tp.l2tpType

       Possibilities:
               lac   (1)
               lns   (2)
               auto   (3)"
   ::= {sr1645v2TTmplStatEntry 302186496}

sr1645v2TTmplStatL2tpControlState OBJECT-TYPE
   SYNTAX      INTEGER
               {
               idle (1),
               waitCtlReply (2),
               waitCtlConn (3),
               established (4)
               }
   MAX-ACCESS  read-only
   STATUS      current
   DESCRIPTION
      "Path: tunnels.status.l2tpTunnels.l2tp.controlState

       Possibilities:
               idle   (1)
               waitCtlReply   (2)
               waitCtlConn   (3)
               established   (4)"
   ::= {sr1645v2TTmplStatEntry 302252032}

sr1645v2TTmplStatL2tpCallState OBJECT-TYPE
   SYNTAX      INTEGER
               {
               idle (1),
               waitTunnel (2),
               waitReply (3),
               waitConnect (4),
               established (5)
               }
   MAX-ACCESS  read-only
   STATUS      current
   DESCRIPTION
      "Path: tunnels.status.l2tpTunnels.l2tp.callState

       Possibilities:
               idle   (1)
               waitTunnel   (2)
               waitReply   (3)
               waitConnect   (4)
               established   (5)"
   ::= {sr1645v2TTmplStatEntry 302317568}

sr1645v2TTmplStatL2tpDeliveryState OBJECT-TYPE
   SYNTAX      INTEGER
               {
               idle (1),
               operating (2),
               done (3)
               }
   MAX-ACCESS  read-only
   STATUS      current
   DESCRIPTION
      "Path: tunnels.status.l2tpTunnels.l2tp.deliveryState

       Possibilities:
               idle   (1)
               operating   (2)
               done   (3)"
   ::= {sr1645v2TTmplStatEntry 302383104}

sr1645v2TTmplStatL2tpAuthenState OBJECT-TYPE
   SYNTAX      INTEGER
               {
               noAuthentication (0),
               authenFailure (1),
               authenSuccessful (2)
               }
   MAX-ACCESS  read-only
   STATUS      current
   DESCRIPTION
      "Path: tunnels.status.l2tpTunnels.l2tp.authenState

       Possibilities:
               noAuthentication   (0)
               authenFailure   (1)
               authenSuccessful   (2)"
   ::= {sr1645v2TTmplStatEntry 302448640}

sr1645v2TTmplStatPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: tunnels.status.l2tpTunnels.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2TTmplStatEntry 184614912}

sr1645v2TTmplStatPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: tunnels.status.l2tpTunnels.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2TTmplStatEntry 184680448}

sr1645v2TTmplStatPppBcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: tunnels.status.l2tpTunnels.ppp.bcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2TTmplStatEntry 184745984}

sr1645v2TTmplStatPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: tunnels.status.l2tpTunnels.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1645v2TTmplStatEntry 185204736}

sr1645v2TTmplStatPppMyAutUsr OBJECT-TYPE
   SYNTAX      DisplayString
   MAX-ACCESS  read-only
   STATUS      current
   DESCRIPTION
      "Path: tunnels.status.l2tpTunnels.ppp.myAuthenUser"
   ::= {sr1645v2TTmplStatEntry 185335808}

sr1645v2TTmplStatPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: tunnels.status.l2tpTunnels.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1645v2TTmplStatEntry 185270272}


sr1645v2TTmplStati OBJECT IDENTIFIER ::= {sr1645v2TTmpl 5}

sr1645v2TTmplStatiSSCTable OBJECT-TYPE
   SYNTAX      SEQUENCE OF Sr1645v2TTmplStatiEntry
   MAX-ACCESS  not-accessible
   STATUS      current
   DESCRIPTION
      ""
   ::= {sr1645v2TTmplStati 1}

sr1645v2TTmplStatiEntry OBJECT-TYPE
   SYNTAX      Sr1645v2TTmplStatiEntry
   MAX-ACCESS  not-accessible
   STATUS      current
   DESCRIPTION
      ""
   INDEX      { sr1645v2TTmplStatiTableIx }
   ::= {sr1645v2TTmplStatiSSCTable 1}

Sr1645v2TTmplStatiEntry ::=
   SEQUENCE
      {
      sr1645v2TTmplStatiTableIx
         TableIndex,
      sr1645v2TTmplStatiName
         DisplayString,
      sr1645v2TTmplStatiMode
         INTEGER,
      sr1645v2TTmplStatiIfOperStatus
         INTEGER,
      sr1645v2TTmplStatiIfLastChange
         TimeTicks,
      sr1645v2TTmplStatiIfLastChangeDate
         DisplayString,
      sr1645v2TTmplStatiIpVrfRouter
         DisplayString,
      sr1645v2TTmplStatiIpAddress
         IpAddress,
      sr1645v2TTmplStatiIpNetMask
         IpAddress,
      sr1645v2TTmplStatiIpRemote
         IpAddress,
      sr1645v2TTmplStatiBridgingStatus
         INTEGER,
      sr1645v2TTmplStatiBridgingSpanningTreePortRole
         INTEGER,
      sr1645v2TTmplStatiBridgingSpanningTreePortId
         Integer32,
      sr1645v2TTmplStatiBridgingSpanningTreePpCostExtPathCost
         Integer32,
      sr1645v2TTmplStatiBridgingSpanningTreePpCostIntPathCost
         Integer32,
      sr1645v2TTmplStatiBridgingSpanningTreeExtRpCost
         Integer32,
      sr1645v2TTmplStatiBridgingSpanningTreeIntRpCost
         Integer32,
      sr1645v2TTmplStatiBridgingSpanningTreeDesBrIdPriority
         Integer32,
      sr1645v2TTmplStatiBridgingSpanningTreeDesBrIdMacAddress
         OCTET STRING,
      sr1645v2TTmplStatiBridgingSpanningTreeDesPrtId
         Integer32,
      sr1645v2TTmplStatiBridgingSpanningTreeDesInt
         INTEGER,
      sr1645v2TTmplStatiBridgingSpanningTreeEdgeDetection
         INTEGER,
      sr1645v2TTmplStatiL2tpLocalIpAddress
         IpAddress,
      sr1645v2TTmplStatiL2tpRemAddr
         IpAddress,
      sr1645v2TTmplStatiL2tpSendingSeqNr
         Integer32,
      sr1645v2TTmplStatiL2tpReceivingSeqNr
         Integer32,
      sr1645v2TTmplStatiL2tpL2tpType
         INTEGER,
      sr1645v2TTmplStatiL2tpControlState
         INTEGER,
      sr1645v2TTmplStatiL2tpCallState
         INTEGER,
      sr1645v2TTmplStatiL2tpDeliveryState
         INTEGER,
      sr1645v2TTmplStatiL2tpAuthenState
         INTEGER,
      sr1645v2TTmplStatiL2tpIke
         INTEGER,
      sr1645v2TTmplStatiPppLcpState
         INTEGER,
      sr1645v2TTmplStatiPppIpcpState
         INTEGER,
      sr1645v2TTmplStatiPppBcpState
         INTEGER,
      sr1645v2TTmplStatiPppMyAutSt
         INTEGER,
      sr1645v2TTmplStatiPppMyAutUsr
         DisplayString,
      sr1645v2TTmplStatiPppHisAutSt
         INTEGER
      }

sr1645v2TTmplStatiTableIx OBJECT-TYPE
   SYNTAX      TableIndex
   MAX-ACCESS  not-accessible
   STATUS      current
   DESCRIPTION
      ""
   ::= {sr1645v2TTmplStatiEntry 11}

sr1645v2TTmplStatiName OBJECT-TYPE
   SYNTAX      DisplayString
   MAX-ACCESS  read-only
   STATUS      current
   DESCRIPTION
      "Path: tunnels.status.ipsecL2tpTunnels.name"
   ::= {sr1645v2TTmplStatiEntry 16777216}

sr1645v2TTmplStatiMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: tunnels.status.ipsecL2tpTunnels.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1645v2TTmplStatiEntry 335544320}

sr1645v2TTmplStatiIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: tunnels.status.ipsecL2tpTunnels.ifOperStatus

       Possibilities:
               up   (1)
               down   (2)
               testing   (3)
               unknown   (4)
               dormant   (5)
               notPresent   (6)
               lowerLayerDown   (7)"
   ::= {sr1645v2TTmplStatiEntry 1795162112}

sr1645v2TTmplStatiIfLastChange OBJECT-TYPE
   SYNTAX      TimeTicks
   MAX-ACCESS  read-only
   STATUS      current
   DESCRIPTION
      "Path: tunnels.status.ipsecL2tpTunnels.ifLastChange

       Time in centi-second."
   ::= {sr1645v2TTmplStatiEntry 1811939328}

sr1645v2TTmplStatiIfLastChangeDate OBJECT-TYPE
   SYNTAX      DisplayString
   MAX-ACCESS  read-only
   STATUS      current
   DESCRIPTION
      "Path: tunnels.status.ipsecL2tpTunnels.ifLastChangeDate"
   ::= {sr1645v2TTmplStatiEntry 3070230528}

sr1645v2TTmplStatiIpVrfRouter OBJECT-TYPE
   SYNTAX      DisplayString
   MAX-ACCESS  read-only
   STATUS      current
   DESCRIPTION
      "Path: tunnels.status.ipsecL2tpTunnels.ip.vrfRouter"
   ::= {sr1645v2TTmplStatiEntry 50397184}

sr1645v2TTmplStatiIpAddress OBJECT-TYPE
   SYNTAX      IpAddress
   MAX-ACCESS  read-only
   STATUS      current
   DESCRIPTION
      "Path: tunnels.status.ipsecL2tpTunnels.ip.address"
   ::= {sr1645v2TTmplStatiEntry 51380224}

sr1645v2TTmplStatiIpNetMask OBJECT-TYPE
   SYNTAX      IpAddress
   MAX-ACCESS  read-only
   STATUS      current
   DESCRIPTION
      "Path: tunnels.status.ipsecL2tpTunnels.ip.netMask"
   ::= {sr1645v2TTmplStatiEntry 51445760}

sr1645v2TTmplStatiIpRemote OBJECT-TYPE
   SYNTAX      IpAddress
   MAX-ACCESS  read-only
   STATUS      current
   DESCRIPTION
      "Path: tunnels.status.ipsecL2tpTunnels.ip.remote"
   ::= {sr1645v2TTmplStatiEntry 51511296}

sr1645v2TTmplStatiBridgingStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: tunnels.status.ipsecL2tpTunnels.bridging.status

       Possibilities:
               disabled   (0)
               discarding   (1)
               learning   (2)
               forwarding   (3)
               backupBlockedIntfDown   (256)
               backupBlockedIntfUp   (259)
               shutdown   (255)"
   ::= {sr1645v2TTmplStatiEntry 453050368}

sr1645v2TTmplStatiBridgingSpanningTreePortRole OBJECT-TYPE
   SYNTAX      INTEGER
               {
               none (0),
               root (1),
               designated (2),
               alternate (3),
               backup (4),
               disabled (5),
               master (6)
               }
   MAX-ACCESS  read-only
   STATUS      current
   DESCRIPTION
      "Path: tunnels.status.ipsecL2tpTunnels.bridging.spanningTree.portRole

       Possibilities:
               none   (0)
               root   (1)
               designated   (2)
               alternate   (3)
               backup   (4)
               disabled   (5)
               master   (6)"
   ::= {sr1645v2TTmplStatiEntry 453116160}

sr1645v2TTmplStatiBridgingSpanningTreePortId OBJECT-TYPE
   SYNTAX      Integer32
   MAX-ACCESS  read-only
   STATUS      current
   DESCRIPTION
      "Path: tunnels.status.ipsecL2tpTunnels.bridging.spanningTree.portId"
   ::= {sr1645v2TTmplStatiEntry 453116416}

sr1645v2TTmplStatiBridgingSpanningTreePpCostExtPathCost OBJECT-TYPE
   SYNTAX      Integer32
   MAX-ACCESS  read-only
   STATUS      current
   DESCRIPTION
      "Path: tunnels.status.ipsecL2tpTunnels.bridging.spanningTree.portPathCosts.extPathCost"
   ::= {sr1645v2TTmplStatiEntry 453116673}

sr1645v2TTmplStatiBridgingSpanningTreePpCostIntPathCost OBJECT-TYPE
   SYNTAX      Integer32
   MAX-ACCESS  read-only
   STATUS      current
   DESCRIPTION
      "Path: tunnels.status.ipsecL2tpTunnels.bridging.spanningTree.portPathCosts.intPathCost"
   ::= {sr1645v2TTmplStatiEntry 453116674}

sr1645v2TTmplStatiBridgingSpanningTreeExtRpCost OBJECT-TYPE
   SYNTAX      Integer32
   MAX-ACCESS  read-only
   STATUS      current
   DESCRIPTION
      "Path: tunnels.status.ipsecL2tpTunnels.bridging.spanningTree.extRootPathCost"
   ::= {sr1645v2TTmplStatiEntry 453116928}

sr1645v2TTmplStatiBridgingSpanningTreeIntRpCost OBJECT-TYPE
   SYNTAX      Integer32
   MAX-ACCESS  read-only
   STATUS      current
   DESCRIPTION
      "Path: tunnels.status.ipsecL2tpTunnels.bridging.spanningTree.intRootPathCost"
   ::= {sr1645v2TTmplStatiEntry 453117184}

sr1645v2TTmplStatiBridgingSpanningTreeDesBrIdPriority OBJECT-TYPE
   SYNTAX      Integer32
   MAX-ACCESS  read-only
   STATUS      current
   DESCRIPTION
      "Path: tunnels.status.ipsecL2tpTunnels.bridging.spanningTree.designatedBridgeId.priority"
   ::= {sr1645v2TTmplStatiEntry 453117441}

sr1645v2TTmplStatiBridgingSpanningTreeDesBrIdMacAddress OBJECT-TYPE
   SYNTAX      OCTET STRING
   MAX-ACCESS  read-only
   STATUS      current
   DESCRIPTION
      "Path: tunnels.status.ipsecL2tpTunnels.bridging.spanningTree.designatedBridgeId.macAddress

       MAC address."
   ::= {sr1645v2TTmplStatiEntry 453117442}

sr1645v2TTmplStatiBridgingSpanningTreeDesPrtId OBJECT-TYPE
   SYNTAX      Integer32
   MAX-ACCESS  read-only
   STATUS      current
   DESCRIPTION
      "Path: tunnels.status.ipsecL2tpTunnels.bridging.spanningTree.designatedPortId"
   ::= {sr1645v2TTmplStatiEntry 453117696}

sr1645v2TTmplStatiBridgingSpanningTreeDesInt OBJECT-TYPE
   SYNTAX      INTEGER
               {
               no (0),
               yes (1)
               }
   MAX-ACCESS  read-only
   STATUS      current
   DESCRIPTION
      "Path: tunnels.status.ipsecL2tpTunnels.bridging.spanningTree.designatedOrInternal

       Possibilities:
               no   (0)
               yes   (1)"
   ::= {sr1645v2TTmplStatiEntry 453117952}

sr1645v2TTmplStatiBridgingSpanningTreeEdgeDetection OBJECT-TYPE
   SYNTAX      INTEGER
               {
               none (0),
               edge (1),
               notEdge (2)
               }
   MAX-ACCESS  read-only
   STATUS      current
   DESCRIPTION
      "Path: tunnels.status.ipsecL2tpTunnels.bridging.spanningTree.edgeDetection

       Possibilities:
               none   (0)
               edge   (1)
               notEdge   (2)"
   ::= {sr1645v2TTmplStatiEntry 453118208}

sr1645v2TTmplStatiL2tpLocalIpAddress OBJECT-TYPE
   SYNTAX      IpAddress
   MAX-ACCESS  read-only
   STATUS      current
   DESCRIPTION
      "Path: tunnels.status.ipsecL2tpTunnels.l2tp.localIpAddress"
   ::= {sr1645v2TTmplStatiEntry 302579712}

sr1645v2TTmplStatiL2tpRemAddr OBJECT-TYPE
   SYNTAX      IpAddress
   MAX-ACCESS  read-only
   STATUS      current
   DESCRIPTION
      "Path: tunnels.status.ipsecL2tpTunnels.l2tp.remoteIpAddress"
   ::= {sr1645v2TTmplStatiEntry 302645248}

sr1645v2TTmplStatiL2tpSendingSeqNr OBJECT-TYPE
   SYNTAX      Integer32
   MAX-ACCESS  read-only
   STATUS      current
   DESCRIPTION
      "Path: tunnels.status.ipsecL2tpTunnels.l2tp.sendingSeqNr"
   ::= {sr1645v2TTmplStatiEntry 302055424}

sr1645v2TTmplStatiL2tpReceivingSeqNr OBJECT-TYPE
   SYNTAX      Integer32
   MAX-ACCESS  read-only
   STATUS      current
   DESCRIPTION
      "Path: tunnels.status.ipsecL2tpTunnels.l2tp.receivingSeqNr"
   ::= {sr1645v2TTmplStatiEntry 302120960}

sr1645v2TTmplStatiL2tpL2tpType OBJECT-TYPE
   SYNTAX      INTEGER
               {
               lac (1),
               lns (2),
               auto (3)
               }
   MAX-ACCESS  read-only
   STATUS      current
   DESCRIPTION
      "Path: tunnels.status.ipsecL2tpTunnels.l2tp.l2tpType

       Possibilities:
               lac   (1)
               lns   (2)
               auto   (3)"
   ::= {sr1645v2TTmplStatiEntry 302186496}

sr1645v2TTmplStatiL2tpControlState OBJECT-TYPE
   SYNTAX      INTEGER
               {
               idle (1),
               waitCtlReply (2),
               waitCtlConn (3),
               established (4)
               }
   MAX-ACCESS  read-only
   STATUS      current
   DESCRIPTION
      "Path: tunnels.status.ipsecL2tpTunnels.l2tp.controlState

       Possibilities:
               idle   (1)
               waitCtlReply   (2)
               waitCtlConn   (3)
               established   (4)"
   ::= {sr1645v2TTmplStatiEntry 302252032}

sr1645v2TTmplStatiL2tpCallState OBJECT-TYPE
   SYNTAX      INTEGER
               {
               idle (1),
               waitTunnel (2),
               waitReply (3),
               waitConnect (4),
               established (5)
               }
   MAX-ACCESS  read-only
   STATUS      current
   DESCRIPTION
      "Path: tunnels.status.ipsecL2tpTunnels.l2tp.callState

       Possibilities:
               idle   (1)
               waitTunnel   (2)
               waitReply   (3)
               waitConnect   (4)
               established   (5)"
   ::= {sr1645v2TTmplStatiEntry 302317568}

sr1645v2TTmplStatiL2tpDeliveryState OBJECT-TYPE
   SYNTAX      INTEGER
               {
               idle (1),
               operating (2),
               done (3)
               }
   MAX-ACCESS  read-only
   STATUS      current
   DESCRIPTION
      "Path: tunnels.status.ipsecL2tpTunnels.l2tp.deliveryState

       Possibilities:
               idle   (1)
               operating   (2)
               done   (3)"
   ::= {sr1645v2TTmplStatiEntry 302383104}

sr1645v2TTmplStatiL2tpAuthenState OBJECT-TYPE
   SYNTAX      INTEGER
               {
               noAuthentication (0),
               authenFailure (1),
               authenSuccessful (2)
               }
   MAX-ACCESS  read-only
   STATUS      current
   DESCRIPTION
      "Path: tunnels.status.ipsecL2tpTunnels.l2tp.authenState

       Possibilities:
               noAuthentication   (0)
               authenFailure   (1)
               authenSuccessful   (2)"
   ::= {sr1645v2TTmplStatiEntry 302448640}

sr1645v2TTmplStatiL2tpIke OBJECT-TYPE
   SYNTAX      INTEGER
               {
               idle (0),
               down (1),
               setup (2),
               up (3),
               rollOver (4)
               }
   MAX-ACCESS  read-only
   STATUS      current
   DESCRIPTION
      "Path: tunnels.status.ipsecL2tpTunnels.l2tp.ike

       Possibilities:
               idle   (0)
               down   (1)
               setup   (2)
               up   (3)
               rollOver   (4)"
   ::= {sr1645v2TTmplStatiEntry 302514176}

sr1645v2TTmplStatiPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: tunnels.status.ipsecL2tpTunnels.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2TTmplStatiEntry 184614912}

sr1645v2TTmplStatiPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: tunnels.status.ipsecL2tpTunnels.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2TTmplStatiEntry 184680448}

sr1645v2TTmplStatiPppBcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: tunnels.status.ipsecL2tpTunnels.ppp.bcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2TTmplStatiEntry 184745984}

sr1645v2TTmplStatiPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: tunnels.status.ipsecL2tpTunnels.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1645v2TTmplStatiEntry 185204736}

sr1645v2TTmplStatiPppMyAutUsr OBJECT-TYPE
   SYNTAX      DisplayString
   MAX-ACCESS  read-only
   STATUS      current
   DESCRIPTION
      "Path: tunnels.status.ipsecL2tpTunnels.ppp.myAuthenUser"
   ::= {sr1645v2TTmplStatiEntry 185335808}

sr1645v2TTmplStatiPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: tunnels.status.ipsecL2tpTunnels.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1645v2TTmplStatiEntry 185270272}


sr1645v2TTmplSGre OBJECT IDENTIFIER ::= {sr1645v2TTmpl 22}

sr1645v2TTmplSGreSSCTable OBJECT-TYPE
   SYNTAX      SEQUENCE OF Sr1645v2TTmplSGreEntry
   MAX-ACCESS  not-accessible
   STATUS      current
   DESCRIPTION
      ""
   ::= {sr1645v2TTmplSGre 1}

sr1645v2TTmplSGreEntry OBJECT-TYPE
   SYNTAX      Sr1645v2TTmplSGreEntry
   MAX-ACCESS  not-accessible
   STATUS      current
   DESCRIPTION
      ""
   INDEX      { sr1645v2TTmplSGreTableIx }
   ::= {sr1645v2TTmplSGreSSCTable 1}

Sr1645v2TTmplSGreEntry ::=
   SEQUENCE
      {
      sr1645v2TTmplSGreTableIx
         TableIndex,
      sr1645v2TTmplSGreName
         DisplayString,
      sr1645v2TTmplSGreMode
         INTEGER,
      sr1645v2TTmplSGreIfOperStatus
         INTEGER,
      sr1645v2TTmplSGreIfLastChange
         TimeTicks,
      sr1645v2TTmplSGreIfLastChangeDate
         DisplayString,
      sr1645v2TTmplSGreIpVrfRouter
         DisplayString,
      sr1645v2TTmplSGreIpAddress
         IpAddress,
      sr1645v2TTmplSGreIpNetMask
         IpAddress,
      sr1645v2TTmplSGreIpRemote
         IpAddress,
      sr1645v2TTmplSGreBrStatus
         INTEGER,
      sr1645v2TTmplSGreBrSpanningTreePortRole
         INTEGER,
      sr1645v2TTmplSGreBrSpanningTreePortId
         Integer32,
      sr1645v2TTmplSGreBrSpanningTreePpCostExtPathCost
         Integer32,
      sr1645v2TTmplSGreBrSpanningTreePpCostIntPathCost
         Integer32,
      sr1645v2TTmplSGreBrSpanningTreeExtRpCost
         Integer32,
      sr1645v2TTmplSGreBrSpanningTreeIntRpCost
         Integer32,
      sr1645v2TTmplSGreBrSpanningTreeDesBrIdPriority
         Integer32,
      sr1645v2TTmplSGreBrSpanningTreeDesBrIdMacAddress
         OCTET STRING,
      sr1645v2TTmplSGreBrSpanningTreeDesPrtId
         Integer32,
      sr1645v2TTmplSGreBrSpanningTreeDesInt
         INTEGER,
      sr1645v2TTmplSGreBrSpanningTreeEdgeDetection
         INTEGER,
      sr1645v2TTmplSGreGreLocalIpAddress
         IpAddress,
      sr1645v2TTmplSGreGreRemoteIpAddress
         IpAddress,
      sr1645v2TTmplSGreGreState
         INTEGER,
      sr1645v2TTmplSGreGreKeepAliveFails
         Counter32,
      sr1645v2TTmplSGreGreMplsMode
         INTEGER,
      sr1645v2TTmplSGreGreMplsInLabel
         Integer32,
      sr1645v2TTmplSGreGreMplsOutLabel
         Integer32
      }

sr1645v2TTmplSGreTableIx OBJECT-TYPE
   SYNTAX      TableIndex
   MAX-ACCESS  not-accessible
   STATUS      current
   DESCRIPTION
      ""
   ::= {sr1645v2TTmplSGreEntry 11}

sr1645v2TTmplSGreName OBJECT-TYPE
   SYNTAX      DisplayString
   MAX-ACCESS  read-only
   STATUS      current
   DESCRIPTION
      "Path: tunnels.status.greTunnels.name"
   ::= {sr1645v2TTmplSGreEntry 16777216}

sr1645v2TTmplSGreMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: tunnels.status.greTunnels.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1645v2TTmplSGreEntry 335544320}

sr1645v2TTmplSGreIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: tunnels.status.greTunnels.ifOperStatus

       Possibilities:
               up   (1)
               down   (2)
               testing   (3)
               unknown   (4)
               dormant   (5)
               notPresent   (6)
               lowerLayerDown   (7)"
   ::= {sr1645v2TTmplSGreEntry 1795162112}

sr1645v2TTmplSGreIfLastChange OBJECT-TYPE
   SYNTAX      TimeTicks
   MAX-ACCESS  read-only
   STATUS      current
   DESCRIPTION
      "Path: tunnels.status.greTunnels.ifLastChange

       Time in centi-second."
   ::= {sr1645v2TTmplSGreEntry 1811939328}

sr1645v2TTmplSGreIfLastChangeDate OBJECT-TYPE
   SYNTAX      DisplayString
   MAX-ACCESS  read-only
   STATUS      current
   DESCRIPTION
      "Path: tunnels.status.greTunnels.ifLastChangeDate"
   ::= {sr1645v2TTmplSGreEntry 3070230528}

sr1645v2TTmplSGreIpVrfRouter OBJECT-TYPE
   SYNTAX      DisplayString
   MAX-ACCESS  read-only
   STATUS      current
   DESCRIPTION
      "Path: tunnels.status.greTunnels.ip.vrfRouter"
   ::= {sr1645v2TTmplSGreEntry 50397184}

sr1645v2TTmplSGreIpAddress OBJECT-TYPE
   SYNTAX      IpAddress
   MAX-ACCESS  read-only
   STATUS      current
   DESCRIPTION
      "Path: tunnels.status.greTunnels.ip.address"
   ::= {sr1645v2TTmplSGreEntry 51380224}

sr1645v2TTmplSGreIpNetMask OBJECT-TYPE
   SYNTAX      IpAddress
   MAX-ACCESS  read-only
   STATUS      current
   DESCRIPTION
      "Path: tunnels.status.greTunnels.ip.netMask"
   ::= {sr1645v2TTmplSGreEntry 51445760}

sr1645v2TTmplSGreIpRemote OBJECT-TYPE
   SYNTAX      IpAddress
   MAX-ACCESS  read-only
   STATUS      current
   DESCRIPTION
      "Path: tunnels.status.greTunnels.ip.remote"
   ::= {sr1645v2TTmplSGreEntry 51511296}

sr1645v2TTmplSGreBrStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: tunnels.status.greTunnels.bridging.status

       Possibilities:
               disabled   (0)
               discarding   (1)
               learning   (2)
               forwarding   (3)
               backupBlockedIntfDown   (256)
               backupBlockedIntfUp   (259)
               shutdown   (255)"
   ::= {sr1645v2TTmplSGreEntry 453050368}

sr1645v2TTmplSGreBrSpanningTreePortRole OBJECT-TYPE
   SYNTAX      INTEGER
               {
               none (0),
               root (1),
               designated (2),
               alternate (3),
               backup (4),
               disabled (5),
               master (6)
               }
   MAX-ACCESS  read-only
   STATUS      current
   DESCRIPTION
      "Path: tunnels.status.greTunnels.bridging.spanningTree.portRole

       Possibilities:
               none   (0)
               root   (1)
               designated   (2)
               alternate   (3)
               backup   (4)
               disabled   (5)
               master   (6)"
   ::= {sr1645v2TTmplSGreEntry 453116160}

sr1645v2TTmplSGreBrSpanningTreePortId OBJECT-TYPE
   SYNTAX      Integer32
   MAX-ACCESS  read-only
   STATUS      current
   DESCRIPTION
      "Path: tunnels.status.greTunnels.bridging.spanningTree.portId"
   ::= {sr1645v2TTmplSGreEntry 453116416}

sr1645v2TTmplSGreBrSpanningTreePpCostExtPathCost OBJECT-TYPE
   SYNTAX      Integer32
   MAX-ACCESS  read-only
   STATUS      current
   DESCRIPTION
      "Path: tunnels.status.greTunnels.bridging.spanningTree.portPathCosts.extPathCost"
   ::= {sr1645v2TTmplSGreEntry 453116673}

sr1645v2TTmplSGreBrSpanningTreePpCostIntPathCost OBJECT-TYPE
   SYNTAX      Integer32
   MAX-ACCESS  read-only
   STATUS      current
   DESCRIPTION
      "Path: tunnels.status.greTunnels.bridging.spanningTree.portPathCosts.intPathCost"
   ::= {sr1645v2TTmplSGreEntry 453116674}

sr1645v2TTmplSGreBrSpanningTreeExtRpCost OBJECT-TYPE
   SYNTAX      Integer32
   MAX-ACCESS  read-only
   STATUS      current
   DESCRIPTION
      "Path: tunnels.status.greTunnels.bridging.spanningTree.extRootPathCost"
   ::= {sr1645v2TTmplSGreEntry 453116928}

sr1645v2TTmplSGreBrSpanningTreeIntRpCost OBJECT-TYPE
   SYNTAX      Integer32
   MAX-ACCESS  read-only
   STATUS      current
   DESCRIPTION
      "Path: tunnels.status.greTunnels.bridging.spanningTree.intRootPathCost"
   ::= {sr1645v2TTmplSGreEntry 453117184}

sr1645v2TTmplSGreBrSpanningTreeDesBrIdPriority OBJECT-TYPE
   SYNTAX      Integer32
   MAX-ACCESS  read-only
   STATUS      current
   DESCRIPTION
      "Path: tunnels.status.greTunnels.bridging.spanningTree.designatedBridgeId.priority"
   ::= {sr1645v2TTmplSGreEntry 453117441}

sr1645v2TTmplSGreBrSpanningTreeDesBrIdMacAddress OBJECT-TYPE
   SYNTAX      OCTET STRING
   MAX-ACCESS  read-only
   STATUS      current
   DESCRIPTION
      "Path: tunnels.status.greTunnels.bridging.spanningTree.designatedBridgeId.macAddress

       MAC address."
   ::= {sr1645v2TTmplSGreEntry 453117442}

sr1645v2TTmplSGreBrSpanningTreeDesPrtId OBJECT-TYPE
   SYNTAX      Integer32
   MAX-ACCESS  read-only
   STATUS      current
   DESCRIPTION
      "Path: tunnels.status.greTunnels.bridging.spanningTree.designatedPortId"
   ::= {sr1645v2TTmplSGreEntry 453117696}

sr1645v2TTmplSGreBrSpanningTreeDesInt OBJECT-TYPE
   SYNTAX      INTEGER
               {
               no (0),
               yes (1)
               }
   MAX-ACCESS  read-only
   STATUS      current
   DESCRIPTION
      "Path: tunnels.status.greTunnels.bridging.spanningTree.designatedOrInternal

       Possibilities:
               no   (0)
               yes   (1)"
   ::= {sr1645v2TTmplSGreEntry 453117952}

sr1645v2TTmplSGreBrSpanningTreeEdgeDetection OBJECT-TYPE
   SYNTAX      INTEGER
               {
               none (0),
               edge (1),
               notEdge (2)
               }
   MAX-ACCESS  read-only
   STATUS      current
   DESCRIPTION
      "Path: tunnels.status.greTunnels.bridging.spanningTree.edgeDetection

       Possibilities:
               none   (0)
               edge   (1)
               notEdge   (2)"
   ::= {sr1645v2TTmplSGreEntry 453118208}

sr1645v2TTmplSGreGreLocalIpAddress OBJECT-TYPE
   SYNTAX      IpAddress
   MAX-ACCESS  read-only
   STATUS      current
   DESCRIPTION
      "Path: tunnels.status.greTunnels.gre.localIpAddress"
   ::= {sr1645v2TTmplSGreEntry 587268096}

sr1645v2TTmplSGreGreRemoteIpAddress OBJECT-TYPE
   SYNTAX      IpAddress
   MAX-ACCESS  read-only
   STATUS      current
   DESCRIPTION
      "Path: tunnels.status.greTunnels.gre.remoteIpAddress"
   ::= {sr1645v2TTmplSGreEntry 587333632}

sr1645v2TTmplSGreGreState OBJECT-TYPE
   SYNTAX      INTEGER
               {
               setup (0),
               resolvingRemote (1),
               resolvingLocal (2),
               waitDnsReply (3),
               initParked (4),
               open (5),
               activated (128),
               initActivate (129),
               spoofing (130),
               down (131),
               up (132),
               park (133)
               }
   MAX-ACCESS  read-only
   STATUS      current
   DESCRIPTION
      "Path: tunnels.status.greTunnels.gre.state

       Possibilities:
               setup   (0)
               resolvingRemote   (1)
               resolvingLocal   (2)
               waitDnsReply   (3)
               initParked   (4)
               open   (5)
               activated   (128)
               initActivate   (129)
               spoofing   (130)
               down   (131)
               up   (132)
               park   (133)"
   ::= {sr1645v2TTmplSGreEntry 587464704}

sr1645v2TTmplSGreGreKeepAliveFails OBJECT-TYPE
   SYNTAX      Counter32
   MAX-ACCESS  read-only
   STATUS      current
   DESCRIPTION
      "Path: tunnels.status.greTunnels.gre.keepAlive.fails

       32 bit unsigned wrappable counter."
   ::= {sr1645v2TTmplSGreEntry 587596032}

sr1645v2TTmplSGreGreMplsMode OBJECT-TYPE
   SYNTAX      INTEGER
               {
               disabled (0),
               enabled (1)
               }
   MAX-ACCESS  read-only
   STATUS      current
   DESCRIPTION
      "Path: tunnels.status.greTunnels.gre.mpls.mode

       Possibilities:
               disabled   (0)
               enabled   (1)"
   ::= {sr1645v2TTmplSGreEntry 587530496}

sr1645v2TTmplSGreGreMplsInLabel OBJECT-TYPE
   SYNTAX      Integer32
   MAX-ACCESS  read-only
   STATUS      current
   DESCRIPTION
      "Path: tunnels.status.greTunnels.gre.mpls.inLabel"
   ::= {sr1645v2TTmplSGreEntry 587530752}

sr1645v2TTmplSGreGreMplsOutLabel OBJECT-TYPE
   SYNTAX      Integer32
   MAX-ACCESS  read-only
   STATUS      current
   DESCRIPTION
      "Path: tunnels.status.greTunnels.gre.mpls.outLabel"
   ::= {sr1645v2TTmplSGreEntry 587531008}


sr1645v2TTmplSiGre OBJECT IDENTIFIER ::= {sr1645v2TTmpl 25}

sr1645v2TTmplSiGreSSCTable OBJECT-TYPE
   SYNTAX      SEQUENCE OF Sr1645v2TTmplSiGreEntry
   MAX-ACCESS  not-accessible
   STATUS      current
   DESCRIPTION
      ""
   ::= {sr1645v2TTmplSiGre 1}

sr1645v2TTmplSiGreEntry OBJECT-TYPE
   SYNTAX      Sr1645v2TTmplSiGreEntry
   MAX-ACCESS  not-accessible
   STATUS      current
   DESCRIPTION
      ""
   INDEX      { sr1645v2TTmplSiGreTableIx }
   ::= {sr1645v2TTmplSiGreSSCTable 1}

Sr1645v2TTmplSiGreEntry ::=
   SEQUENCE
      {
      sr1645v2TTmplSiGreTableIx
         TableIndex,
      sr1645v2TTmplSiGreName
         DisplayString,
      sr1645v2TTmplSiGreMode
         INTEGER,
      sr1645v2TTmplSiGreIfOperStatus
         INTEGER,
      sr1645v2TTmplSiGreIfLastChange
         TimeTicks,
      sr1645v2TTmplSiGreIfLastChangeDate
         DisplayString,
      sr1645v2TTmplSiGreIpVrfRouter
         DisplayString,
      sr1645v2TTmplSiGreIpAddress
         IpAddress,
      sr1645v2TTmplSiGreIpNetMask
         IpAddress,
      sr1645v2TTmplSiGreIpRemote
         IpAddress,
      sr1645v2TTmplSiGreBrStatus
         INTEGER,
      sr1645v2TTmplSiGreBrSpanningTreePortRole
         INTEGER,
      sr1645v2TTmplSiGreBrSpanningTreePortId
         Integer32,
      sr1645v2TTmplSiGreBrSpanningTreePpCostExtPathCost
         Integer32,
      sr1645v2TTmplSiGreBrSpanningTreePpCostIntPathCost
         Integer32,
      sr1645v2TTmplSiGreBrSpanningTreeExtRpCost
         Integer32,
      sr1645v2TTmplSiGreBrSpanningTreeIntRpCost
         Integer32,
      sr1645v2TTmplSiGreBrSpanningTreeDesBrIdPriority
         Integer32,
      sr1645v2TTmplSiGreBrSpanningTreeDesBrIdMacAddress
         OCTET STRING,
      sr1645v2TTmplSiGreBrSpanningTreeDesPrtId
         Integer32,
      sr1645v2TTmplSiGreBrSpanningTreeDesInt
         INTEGER,
      sr1645v2TTmplSiGreBrSpanningTreeEdgeDetection
         INTEGER,
      sr1645v2TTmplSiGreGreLocalIpAddress
         IpAddress,
      sr1645v2TTmplSiGreGreRemoteIpAddress
         IpAddress,
      sr1645v2TTmplSiGreGreIke
         INTEGER,
      sr1645v2TTmplSiGreGreState
         INTEGER,
      sr1645v2TTmplSiGreGreKeepAliveFails
         Counter32,
      sr1645v2TTmplSiGreGreMplsMode
         INTEGER,
      sr1645v2TTmplSiGreGreMplsInLabel
         Integer32,
      sr1645v2TTmplSiGreGreMplsOutLabel
         Integer32
      }

sr1645v2TTmplSiGreTableIx OBJECT-TYPE
   SYNTAX      TableIndex
   MAX-ACCESS  not-accessible
   STATUS      current
   DESCRIPTION
      ""
   ::= {sr1645v2TTmplSiGreEntry 11}

sr1645v2TTmplSiGreName OBJECT-TYPE
   SYNTAX      DisplayString
   MAX-ACCESS  read-only
   STATUS      current
   DESCRIPTION
      "Path: tunnels.status.ipsecGreTunnels.name"
   ::= {sr1645v2TTmplSiGreEntry 16777216}

sr1645v2TTmplSiGreMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: tunnels.status.ipsecGreTunnels.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1645v2TTmplSiGreEntry 335544320}

sr1645v2TTmplSiGreIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: tunnels.status.ipsecGreTunnels.ifOperStatus

       Possibilities:
               up   (1)
               down   (2)
               testing   (3)
               unknown   (4)
               dormant   (5)
               notPresent   (6)
               lowerLayerDown   (7)"
   ::= {sr1645v2TTmplSiGreEntry 1795162112}

sr1645v2TTmplSiGreIfLastChange OBJECT-TYPE
   SYNTAX      TimeTicks
   MAX-ACCESS  read-only
   STATUS      current
   DESCRIPTION
      "Path: tunnels.status.ipsecGreTunnels.ifLastChange

       Time in centi-second."
   ::= {sr1645v2TTmplSiGreEntry 1811939328}

sr1645v2TTmplSiGreIfLastChangeDate OBJECT-TYPE
   SYNTAX      DisplayString
   MAX-ACCESS  read-only
   STATUS      current
   DESCRIPTION
      "Path: tunnels.status.ipsecGreTunnels.ifLastChangeDate"
   ::= {sr1645v2TTmplSiGreEntry 3070230528}

sr1645v2TTmplSiGreIpVrfRouter OBJECT-TYPE
   SYNTAX      DisplayString
   MAX-ACCESS  read-only
   STATUS      current
   DESCRIPTION
      "Path: tunnels.status.ipsecGreTunnels.ip.vrfRouter"
   ::= {sr1645v2TTmplSiGreEntry 50397184}

sr1645v2TTmplSiGreIpAddress OBJECT-TYPE
   SYNTAX      IpAddress
   MAX-ACCESS  read-only
   STATUS      current
   DESCRIPTION
      "Path: tunnels.status.ipsecGreTunnels.ip.address"
   ::= {sr1645v2TTmplSiGreEntry 51380224}

sr1645v2TTmplSiGreIpNetMask OBJECT-TYPE
   SYNTAX      IpAddress
   MAX-ACCESS  read-only
   STATUS      current
   DESCRIPTION
      "Path: tunnels.status.ipsecGreTunnels.ip.netMask"
   ::= {sr1645v2TTmplSiGreEntry 51445760}

sr1645v2TTmplSiGreIpRemote OBJECT-TYPE
   SYNTAX      IpAddress
   MAX-ACCESS  read-only
   STATUS      current
   DESCRIPTION
      "Path: tunnels.status.ipsecGreTunnels.ip.remote"
   ::= {sr1645v2TTmplSiGreEntry 51511296}

sr1645v2TTmplSiGreBrStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: tunnels.status.ipsecGreTunnels.bridging.status

       Possibilities:
               disabled   (0)
               discarding   (1)
               learning   (2)
               forwarding   (3)
               backupBlockedIntfDown   (256)
               backupBlockedIntfUp   (259)
               shutdown   (255)"
   ::= {sr1645v2TTmplSiGreEntry 453050368}

sr1645v2TTmplSiGreBrSpanningTreePortRole OBJECT-TYPE
   SYNTAX      INTEGER
               {
               none (0),
               root (1),
               designated (2),
               alternate (3),
               backup (4),
               disabled (5),
               master (6)
               }
   MAX-ACCESS  read-only
   STATUS      current
   DESCRIPTION
      "Path: tunnels.status.ipsecGreTunnels.bridging.spanningTree.portRole

       Possibilities:
               none   (0)
               root   (1)
               designated   (2)
               alternate   (3)
               backup   (4)
               disabled   (5)
               master   (6)"
   ::= {sr1645v2TTmplSiGreEntry 453116160}

sr1645v2TTmplSiGreBrSpanningTreePortId OBJECT-TYPE
   SYNTAX      Integer32
   MAX-ACCESS  read-only
   STATUS      current
   DESCRIPTION
      "Path: tunnels.status.ipsecGreTunnels.bridging.spanningTree.portId"
   ::= {sr1645v2TTmplSiGreEntry 453116416}

sr1645v2TTmplSiGreBrSpanningTreePpCostExtPathCost OBJECT-TYPE
   SYNTAX      Integer32
   MAX-ACCESS  read-only
   STATUS      current
   DESCRIPTION
      "Path: tunnels.status.ipsecGreTunnels.bridging.spanningTree.portPathCosts.extPathCost"
   ::= {sr1645v2TTmplSiGreEntry 453116673}

sr1645v2TTmplSiGreBrSpanningTreePpCostIntPathCost OBJECT-TYPE
   SYNTAX      Integer32
   MAX-ACCESS  read-only
   STATUS      current
   DESCRIPTION
      "Path: tunnels.status.ipsecGreTunnels.bridging.spanningTree.portPathCosts.intPathCost"
   ::= {sr1645v2TTmplSiGreEntry 453116674}

sr1645v2TTmplSiGreBrSpanningTreeExtRpCost OBJECT-TYPE
   SYNTAX      Integer32
   MAX-ACCESS  read-only
   STATUS      current
   DESCRIPTION
      "Path: tunnels.status.ipsecGreTunnels.bridging.spanningTree.extRootPathCost"
   ::= {sr1645v2TTmplSiGreEntry 453116928}

sr1645v2TTmplSiGreBrSpanningTreeIntRpCost OBJECT-TYPE
   SYNTAX      Integer32
   MAX-ACCESS  read-only
   STATUS      current
   DESCRIPTION
      "Path: tunnels.status.ipsecGreTunnels.bridging.spanningTree.intRootPathCost"
   ::= {sr1645v2TTmplSiGreEntry 453117184}

sr1645v2TTmplSiGreBrSpanningTreeDesBrIdPriority OBJECT-TYPE
   SYNTAX      Integer32
   MAX-ACCESS  read-only
   STATUS      current
   DESCRIPTION
      "Path: tunnels.status.ipsecGreTunnels.bridging.spanningTree.designatedBridgeId.priority"
   ::= {sr1645v2TTmplSiGreEntry 453117441}

sr1645v2TTmplSiGreBrSpanningTreeDesBrIdMacAddress OBJECT-TYPE
   SYNTAX      OCTET STRING
   MAX-ACCESS  read-only
   STATUS      current
   DESCRIPTION
      "Path: tunnels.status.ipsecGreTunnels.bridging.spanningTree.designatedBridgeId.macAddress

       MAC address."
   ::= {sr1645v2TTmplSiGreEntry 453117442}

sr1645v2TTmplSiGreBrSpanningTreeDesPrtId OBJECT-TYPE
   SYNTAX      Integer32
   MAX-ACCESS  read-only
   STATUS      current
   DESCRIPTION
      "Path: tunnels.status.ipsecGreTunnels.bridging.spanningTree.designatedPortId"
   ::= {sr1645v2TTmplSiGreEntry 453117696}

sr1645v2TTmplSiGreBrSpanningTreeDesInt OBJECT-TYPE
   SYNTAX      INTEGER
               {
               no (0),
               yes (1)
               }
   MAX-ACCESS  read-only
   STATUS      current
   DESCRIPTION
      "Path: tunnels.status.ipsecGreTunnels.bridging.spanningTree.designatedOrInternal

       Possibilities:
               no   (0)
               yes   (1)"
   ::= {sr1645v2TTmplSiGreEntry 453117952}

sr1645v2TTmplSiGreBrSpanningTreeEdgeDetection OBJECT-TYPE
   SYNTAX      INTEGER
               {
               none (0),
               edge (1),
               notEdge (2)
               }
   MAX-ACCESS  read-only
   STATUS      current
   DESCRIPTION
      "Path: tunnels.status.ipsecGreTunnels.bridging.spanningTree.edgeDetection

       Possibilities:
               none   (0)
               edge   (1)
               notEdge   (2)"
   ::= {sr1645v2TTmplSiGreEntry 453118208}

sr1645v2TTmplSiGreGreLocalIpAddress OBJECT-TYPE
   SYNTAX      IpAddress
   MAX-ACCESS  read-only
   STATUS      current
   DESCRIPTION
      "Path: tunnels.status.ipsecGreTunnels.gre.localIpAddress"
   ::= {sr1645v2TTmplSiGreEntry 587268096}

sr1645v2TTmplSiGreGreRemoteIpAddress OBJECT-TYPE
   SYNTAX      IpAddress
   MAX-ACCESS  read-only
   STATUS      current
   DESCRIPTION
      "Path: tunnels.status.ipsecGreTunnels.gre.remoteIpAddress"
   ::= {sr1645v2TTmplSiGreEntry 587333632}

sr1645v2TTmplSiGreGreIke OBJECT-TYPE
   SYNTAX      INTEGER
               {
               idle (0),
               down (1),
               setup (2),
               up (3),
               rollOver (4)
               }
   MAX-ACCESS  read-only
   STATUS      current
   DESCRIPTION
      "Path: tunnels.status.ipsecGreTunnels.gre.ike

       Possibilities:
               idle   (0)
               down   (1)
               setup   (2)
               up   (3)
               rollOver   (4)"
   ::= {sr1645v2TTmplSiGreEntry 587399168}

sr1645v2TTmplSiGreGreState OBJECT-TYPE
   SYNTAX      INTEGER
               {
               setup (0),
               resolvingRemote (1),
               resolvingLocal (2),
               waitDnsReply (3),
               initParked (4),
               open (5),
               activated (128),
               initActivate (129),
               spoofing (130),
               down (131),
               up (132),
               park (133)
               }
   MAX-ACCESS  read-only
   STATUS      current
   DESCRIPTION
      "Path: tunnels.status.ipsecGreTunnels.gre.state

       Possibilities:
               setup   (0)
               resolvingRemote   (1)
               resolvingLocal   (2)
               waitDnsReply   (3)
               initParked   (4)
               open   (5)
               activated   (128)
               initActivate   (129)
               spoofing   (130)
               down   (131)
               up   (132)
               park   (133)"
   ::= {sr1645v2TTmplSiGreEntry 587464704}

sr1645v2TTmplSiGreGreKeepAliveFails OBJECT-TYPE
   SYNTAX      Counter32
   MAX-ACCESS  read-only
   STATUS      current
   DESCRIPTION
      "Path: tunnels.status.ipsecGreTunnels.gre.keepAlive.fails

       32 bit unsigned wrappable counter."
   ::= {sr1645v2TTmplSiGreEntry 587596032}

sr1645v2TTmplSiGreGreMplsMode OBJECT-TYPE
   SYNTAX      INTEGER
               {
               disabled (0),
               enabled (1)
               }
   MAX-ACCESS  read-only
   STATUS      current
   DESCRIPTION
      "Path: tunnels.status.ipsecGreTunnels.gre.mpls.mode

       Possibilities:
               disabled   (0)
               enabled   (1)"
   ::= {sr1645v2TTmplSiGreEntry 587530496}

sr1645v2TTmplSiGreGreMplsInLabel OBJECT-TYPE
   SYNTAX      Integer32
   MAX-ACCESS  read-only
   STATUS      current
   DESCRIPTION
      "Path: tunnels.status.ipsecGreTunnels.gre.mpls.inLabel"
   ::= {sr1645v2TTmplSiGreEntry 587530752}

sr1645v2TTmplSiGreGreMplsOutLabel OBJECT-TYPE
   SYNTAX      Integer32
   MAX-ACCESS  read-only
   STATUS      current
   DESCRIPTION
      "Path: tunnels.status.ipsecGreTunnels.gre.mpls.outLabel"
   ::= {sr1645v2TTmplSiGreEntry 587531008}


sr1645v2TTmplIpsTun OBJECT IDENTIFIER ::= {sr1645v2TTmpl 11}

sr1645v2TTmplIpsTunSSCTable OBJECT-TYPE
   SYNTAX      SEQUENCE OF Sr1645v2TTmplIpsTunEntry
   MAX-ACCESS  not-accessible
   STATUS      current
   DESCRIPTION
      ""
   ::= {sr1645v2TTmplIpsTun 1}

sr1645v2TTmplIpsTunEntry OBJECT-TYPE
   SYNTAX      Sr1645v2TTmplIpsTunEntry
   MAX-ACCESS  not-accessible
   STATUS      current
   DESCRIPTION
      ""
   INDEX      { sr1645v2TTmplIpsTunTableIx }
   ::= {sr1645v2TTmplIpsTunSSCTable 1}

Sr1645v2TTmplIpsTunEntry ::=
   SEQUENCE
      {
      sr1645v2TTmplIpsTunTableIx
         TableIndex,
      sr1645v2TTmplIpsTunName
         DisplayString,
      sr1645v2TTmplIpsTunLocalIpAddress
         IpAddress,
      sr1645v2TTmplIpsTunRemoteIpAddress
         IpAddress,
      sr1645v2TTmplIpsTunOperStatus
         INTEGER,
      sr1645v2TTmplIpsTunLastChange
         TimeTicks,
      sr1645v2TTmplIpsTunLastChangeDate
         DisplayString,
      sr1645v2TTmplIpsTunIke
         INTEGER
      }

sr1645v2TTmplIpsTunTableIx OBJECT-TYPE
   SYNTAX      TableIndex
   MAX-ACCESS  not-accessible
   STATUS      current
   DESCRIPTION
      ""
   ::= {sr1645v2TTmplIpsTunEntry 11}

sr1645v2TTmplIpsTunName OBJECT-TYPE
   SYNTAX      DisplayString
   MAX-ACCESS  read-only
   STATUS      current
   DESCRIPTION
      "Path: tunnels.status.ipsecTunnels.name"
   ::= {sr1645v2TTmplIpsTunEntry 16777216}

sr1645v2TTmplIpsTunLocalIpAddress OBJECT-TYPE
   SYNTAX      IpAddress
   MAX-ACCESS  read-only
   STATUS      current
   DESCRIPTION
      "Path: tunnels.status.ipsecTunnels.localIpAddress"
   ::= {sr1645v2TTmplIpsTunEntry 33554432}

sr1645v2TTmplIpsTunRemoteIpAddress OBJECT-TYPE
   SYNTAX      IpAddress
   MAX-ACCESS  read-only
   STATUS      current
   DESCRIPTION
      "Path: tunnels.status.ipsecTunnels.remoteIpAddress"
   ::= {sr1645v2TTmplIpsTunEntry 50331648}

sr1645v2TTmplIpsTunOperStatus OBJECT-TYPE
   SYNTAX      INTEGER
               {
               down (0),
               up (1),
               resolvingRemote (2),
               resolvingLocal (3),
               setup (4),
               delete (5),
               new (6),
               waitDnsReply (7),
               spoofing (8),
               initSA (9),
               waitUp (10)
               }
   MAX-ACCESS  read-only
   STATUS      current
   DESCRIPTION
      "Path: tunnels.status.ipsecTunnels.operStatus

       Possibilities:
               down   (0)
               up   (1)
               resolvingRemote   (2)
               resolvingLocal   (3)
               setup   (4)
               delete   (5)
               new   (6)
               waitDnsReply   (7)
               spoofing   (8)
               initSA   (9)
               waitUp   (10)"
   ::= {sr1645v2TTmplIpsTunEntry 83886080}

sr1645v2TTmplIpsTunLastChange OBJECT-TYPE
   SYNTAX      TimeTicks
   MAX-ACCESS  read-only
   STATUS      current
   DESCRIPTION
      "Path: tunnels.status.ipsecTunnels.lastChange

       Time in centi-second."
   ::= {sr1645v2TTmplIpsTunEntry 100663296}

sr1645v2TTmplIpsTunLastChangeDate OBJECT-TYPE
   SYNTAX      DisplayString
   MAX-ACCESS  read-only
   STATUS      current
   DESCRIPTION
      "Path: tunnels.status.ipsecTunnels.lastChangeDate"
   ::= {sr1645v2TTmplIpsTunEntry 117440512}

sr1645v2TTmplIpsTunIke OBJECT-TYPE
   SYNTAX      INTEGER
               {
               idle (0),
               down (1),
               setup (2),
               up (3),
               rollOver (4)
               }
   MAX-ACCESS  read-only
   STATUS      current
   DESCRIPTION
      "Path: tunnels.status.ipsecTunnels.ike

       Possibilities:
               idle   (0)
               down   (1)
               setup   (2)
               up   (3)
               rollOver   (4)"
   ::= {sr1645v2TTmplIpsTunEntry 67108864}



pr1645v2TTmpl OBJECT IDENTIFIER ::= {r1645v2TTmpl 12}


pr1645v2TTmplPerf OBJECT IDENTIFIER ::= {pr1645v2TTmpl 3}

pr1645v2TTmplPerfSSCTable OBJECT-TYPE
   SYNTAX      SEQUENCE OF Pr1645v2TTmplPerfEntry
   MAX-ACCESS  not-accessible
   STATUS      current
   DESCRIPTION
      ""
   ::= {pr1645v2TTmplPerf 1}

pr1645v2TTmplPerfEntry OBJECT-TYPE
   SYNTAX      Pr1645v2TTmplPerfEntry
   MAX-ACCESS  not-accessible
   STATUS      current
   DESCRIPTION
      ""
   INDEX      { pr1645v2TTmplPerfTableIx }
   ::= {pr1645v2TTmplPerfSSCTable 1}

Pr1645v2TTmplPerfEntry ::=
   SEQUENCE
      {
      pr1645v2TTmplPerfTableIx
         TableIndex,
      pr1645v2TTmplPerfName
         DisplayString,
      pr1645v2TTmplPerfMCInOctets
         Counter64,
      pr1645v2TTmplPerfMCInUcast
         Counter64,
      pr1645v2TTmplPerfMCInNUcastPkts
         Counter64,
      pr1645v2TTmplPerfMCInBcastPkts
         Counter64,
      pr1645v2TTmplPerfMCInMcastPkts
         Counter64,
      pr1645v2TTmplPerfMCInDiscards
         Counter64,
      pr1645v2TTmplPerfMCInErrors
         Counter64,
      pr1645v2TTmplPerfMCInUnknownProtos
         Counter64,
      pr1645v2TTmplPerfMCInDropEx
         Counter64,
      pr1645v2TTmplPerfMCInDropNoMac
         Counter64,
      pr1645v2TTmplPerfMCInDropNUCast
         Counter64,
      pr1645v2TTmplPerfMCInDropFilter
         Counter64,
      pr1645v2TTmplPerfMCInBandwidth15sec
         Integer32,
      pr1645v2TTmplPerfMCInBandwidth30sec
         Integer32,
      pr1645v2TTmplPerfMCInBandwidth1min
         Integer32,
      pr1645v2TTmplPerfMCInBandwidth2min
         Integer32,
      pr1645v2TTmplPerfMCInBandwidth5min
         Integer32,
      pr1645v2TTmplPerfMCOutOctets
         Counter64,
      pr1645v2TTmplPerfMCOutUcastPkts
         Counter64,
      pr1645v2TTmplPerfMCOutNUcastPkts
         Counter64,
      pr1645v2TTmplPerfMCOutBcastPkts
         Counter64,
      pr1645v2TTmplPerfMCOutMcastPkts
         Counter64,
      pr1645v2TTmplPerfMCOutDiscards
         Counter64,
      pr1645v2TTmplPerfMCOutErrors
         Counter64,
      pr1645v2TTmplPerfMCOutQLen
         Counter32,
      pr1645v2TTmplPerfMCOutDropEx
         Counter64,
      pr1645v2TTmplPerfMCOutDropNoArp
         Counter64,
      pr1645v2TTmplPerfMCOutDropFilter
         Counter64,
      pr1645v2TTmplPerfMCOutBandwidth15sec
         Integer32,
      pr1645v2TTmplPerfMCOutBandwidth30sec
         Integer32,
      pr1645v2TTmplPerfMCOutBandwidth1min
         Integer32,
      pr1645v2TTmplPerfMCOutBandwidth2min
         Integer32,
      pr1645v2TTmplPerfMCOutBandwidth5min
         Integer32,
      pr1645v2TTmplPerfControlHelloSent
         Gauge32,
      pr1645v2TTmplPerfControlHelloRcvd
         Gauge32,
      pr1645v2TTmplPerfControlAckSent
         Gauge32,
      pr1645v2TTmplPerfControlAckRcvd
         Gauge32,
      pr1645v2TTmplPerfControlDuplicateRcvd
         Gauge32,
      pr1645v2TTmplPerfControlOutOfSeqRcvd
         Gauge32,
      pr1645v2TTmplPerfControlRetransmission
         Gauge32,
      pr1645v2TTmplPerfControlAuthenFailure
         Gauge32,
      pr1645v2TTmplPerfPppPort
         Counter32,
      pr1645v2TTmplPerfPppLcpUp
         Counter32,
      pr1645v2TTmplPerfPppLcpDown
         Counter32,
      pr1645v2TTmplPerfPppLcpOpen
         Counter32,
      pr1645v2TTmplPerfPppLcpClose
         Counter32,
      pr1645v2TTmplPerfPppLcpToP
         Counter32,
      pr1645v2TTmplPerfPppLcpToM
         Counter32,
      pr1645v2TTmplPerfPppLcpRcrP
         Counter32,
      pr1645v2TTmplPerfPppLcpRcrM
         Counter32,
      pr1645v2TTmplPerfPppLcpRca
         Counter32,
      pr1645v2TTmplPerfPppLcpRcn
         Counter32,
      pr1645v2TTmplPerfPppLcpRtr
         Counter32,
      pr1645v2TTmplPerfPppLcpRta
         Counter32,
      pr1645v2TTmplPerfPppLcpRuc
         Counter32,
      pr1645v2TTmplPerfPppLcpRxjP
         Counter32,
      pr1645v2TTmplPerfPppLcpRxjM
         Counter32,
      pr1645v2TTmplPerfPppLcpRxr
         Counter32,
      pr1645v2TTmplPerfPppLcpRrr
         Counter32,
      pr1645v2TTmplPerfPppLcpRra
         Counter32,
      pr1645v2TTmplPerfPppLcpDf
         Counter32,
      pr1645v2TTmplPerfPppLcpIntClose
         Counter32,
      pr1645v2TTmplPerfPppLcpLm
         Counter32,
      pr1645v2TTmplPerfPppLcpLmM
         Counter32,
      pr1645v2TTmplPerfPppAuthMyNegotiated
         INTEGER,
      pr1645v2TTmplPerfPppAuthMyConfigured
         INTEGER,
      pr1645v2TTmplPerfPppAuthHisRequested
         INTEGER,
      pr1645v2TTmplPerfPppAuthRxChallenge
         Counter32,
      pr1645v2TTmplPerfPppAuthRxResponse
         Counter32,
      pr1645v2TTmplPerfPppAuthRxSuccess
         Counter32,
      pr1645v2TTmplPerfPppAuthRxFailure
         Counter32,
      pr1645v2TTmplPerfPppAuthChallengeTO
         Counter32,
      pr1645v2TTmplPerfPppAuthResponseTO
         Counter32,
      pr1645v2TTmplPerfPppAuthTxChallenge
         Counter32,
      pr1645v2TTmplPerfPppAuthRxRadiusSuccess
         Counter32,
      pr1645v2TTmplPerfPppAuthRxRadiusFailure
         Counter32,
      pr1645v2TTmplPerfPppAuthTxSuccess
         Counter32,
      pr1645v2TTmplPerfPppAuthTxFailure
         Counter32,
      pr1645v2TTmplPerfPppAuthUnexpected
         Counter32,
      pr1645v2TTmplPerfPppIpcpUp
         Counter32,
      pr1645v2TTmplPerfPppIpcpDown
         Counter32,
      pr1645v2TTmplPerfPppIpcpOpen
         Counter32,
      pr1645v2TTmplPerfPppIpcpClose
         Counter32,
      pr1645v2TTmplPerfPppIpcpToP
         Counter32,
      pr1645v2TTmplPerfPppIpcpToM
         Counter32,
      pr1645v2TTmplPerfPppIpcpRcrP
         Counter32,
      pr1645v2TTmplPerfPppIpcpRcrM
         Counter32,
      pr1645v2TTmplPerfPppIpcpRca
         Counter32,
      pr1645v2TTmplPerfPppIpcpRcn
         Counter32,
      pr1645v2TTmplPerfPppIpcpRtr
         Counter32,
      pr1645v2TTmplPerfPppIpcpRta
         Counter32,
      pr1645v2TTmplPerfPppIpcpRuc
         Counter32,
      pr1645v2TTmplPerfPppIpcpRxjP
         Counter32,
      pr1645v2TTmplPerfPppIpcpRxjM
         Counter32,
      pr1645v2TTmplPerfPppIpcpRxr
         Counter32,
      pr1645v2TTmplPerfPppIpcpRrr
         Counter32,
      pr1645v2TTmplPerfPppIpcpRra
         Counter32,
      pr1645v2TTmplPerfPppIpcpDf
         Counter32,
      pr1645v2TTmplPerfPppIpcpIntClose
         Counter32,
      pr1645v2TTmplPerfPppIpcpLm
         Counter32,
      pr1645v2TTmplPerfPppIpcpLmM
         Counter32,
      pr1645v2TTmplPerfPppLinkMonitoringRequestsSent
         Gauge32,
      pr1645v2TTmplPerfPppLinkMonitoringRepliesRcvd
         Gauge32,
      pr1645v2TTmplPerfPppLinkMonitoringRequestsRcvd
         Gauge32,
      pr1645v2TTmplPerfPppLinkMonitoringRepliesSent
         Gauge32
      }

pr1645v2TTmplPerfTableIx OBJECT-TYPE
   SYNTAX      TableIndex
   MAX-ACCESS  not-accessible
   STATUS      current
   DESCRIPTION
      ""
   ::= {pr1645v2TTmplPerfEntry 11}

pr1645v2TTmplPerfName OBJECT-TYPE
   SYNTAX      DisplayString
   MAX-ACCESS  read-only
   STATUS      current
   DESCRIPTION
      "Path: tunnels.performance.l2tpTunnels.name"
   ::= {pr1645v2TTmplPerfEntry 16777216}

pr1645v2TTmplPerfMCInOctets OBJECT-TYPE
   SYNTAX      Counter64
   MAX-ACCESS  read-only
   STATUS      current
   DESCRIPTION
      "Path: tunnels.performance.l2tpTunnels.mibCounters.ifInOctets

       64 bit unsigned wrappable counter."
   ::= {pr1645v2TTmplPerfEntry 40697856}

pr1645v2TTmplPerfMCInUcast OBJECT-TYPE
   SYNTAX      Counter64
   MAX-ACCESS  read-only
   STATUS      current
   DESCRIPTION
      "Path: tunnels.performance.l2tpTunnels.mibCounters.ifInUcastPkts

       64 bit unsigned wrappable counter."
   ::= {pr1645v2TTmplPerfEntry 40763392}

pr1645v2TTmplPerfMCInNUcastPkts OBJECT-TYPE
   SYNTAX      Counter64
   MAX-ACCESS  read-only
   STATUS      current
   DESCRIPTION
      "Path: tunnels.performance.l2tpTunnels.mibCounters.ifInNUcastPkts

       64 bit unsigned wrappable counter."
   ::= {pr1645v2TTmplPerfEntry 40828928}

pr1645v2TTmplPerfMCInBcastPkts OBJECT-TYPE
   SYNTAX      Counter64
   MAX-ACCESS  read-only
   STATUS      current
   DESCRIPTION
      "Path: tunnels.performance.l2tpTunnels.mibCounters.ifInBcastPkts

       64 bit unsigned wrappable counter."
   ::= {pr1645v2TTmplPerfEntry 47382528}

pr1645v2TTmplPerfMCInMcastPkts OBJECT-TYPE
   SYNTAX      Counter64
   MAX-ACCESS  read-only
   STATUS      current
   DESCRIPTION
      "Path: tunnels.performance.l2tpTunnels.mibCounters.ifInMcastPkts

       64 bit unsigned wrappable counter."
   ::= {pr1645v2TTmplPerfEntry 48037888}

pr1645v2TTmplPerfMCInDiscards OBJECT-TYPE
   SYNTAX      Counter64
   MAX-ACCESS  read-only
   STATUS      current
   DESCRIPTION
      "Path: tunnels.performance.l2tpTunnels.mibCounters.ifInDiscards

       64 bit unsigned wrappable counter."
   ::= {pr1645v2TTmplPerfEntry 40894464}

pr1645v2TTmplPerfMCInErrors OBJECT-TYPE
   SYNTAX      Counter64
   MAX-ACCESS  read-only
   STATUS      current
   DESCRIPTION
      "Path: tunnels.performance.l2tpTunnels.mibCounters.ifInErrors

       64 bit unsigned wrappable counter."
   ::= {pr1645v2TTmplPerfEntry 40960000}

pr1645v2TTmplPerfMCInUnknownProtos OBJECT-TYPE
   SYNTAX      Counter64
   MAX-ACCESS  read-only
   STATUS      current
   DESCRIPTION
      "Path: tunnels.performance.l2tpTunnels.mibCounters.ifInUnknownProtos

       64 bit unsigned wrappable counter."
   ::= {pr1645v2TTmplPerfEntry 41025536}

pr1645v2TTmplPerfMCInDropEx OBJECT-TYPE
   SYNTAX      Counter64
   MAX-ACCESS  read-only
   STATUS      current
   DESCRIPTION
      "Path: tunnels.performance.l2tpTunnels.mibCounters.ifInDropLevelExceeded

       64 bit unsigned wrappable counter."
   ::= {pr1645v2TTmplPerfEntry 42074112}

pr1645v2TTmplPerfMCInDropNoMac OBJECT-TYPE
   SYNTAX      Counter64
   MAX-ACCESS  read-only
   STATUS      current
   DESCRIPTION
      "Path: tunnels.performance.l2tpTunnels.mibCounters.ifInDiscardsNoMacFit

       64 bit unsigned wrappable counter."
   ::= {pr1645v2TTmplPerfEntry 42270720}

pr1645v2TTmplPerfMCInDropNUCast OBJECT-TYPE
   SYNTAX      Counter64
   MAX-ACCESS  read-only
   STATUS      current
   DESCRIPTION
      "Path: tunnels.performance.l2tpTunnels.mibCounters.ifInDiscardsNUCast

       64 bit unsigned wrappable counter."
   ::= {pr1645v2TTmplPerfEntry 42467328}

pr1645v2TTmplPerfMCInDropFilter OBJECT-TYPE
   SYNTAX      Counter64
   MAX-ACCESS  read-only
   STATUS      current
   DESCRIPTION
      "Path: tunnels.performance.l2tpTunnels.mibCounters.ifInDiscardsFilter

       64 bit unsigned wrappable counter."
   ::= {pr1645v2TTmplPerfEntry 42532864}

pr1645v2TTmplPerfMCInBandwidth15sec OBJECT-TYPE
   SYNTAX      Integer32
   MAX-ACCESS  read-only
   STATUS      current
   DESCRIPTION
      "Path: tunnels.performance.l2tpTunnels.mibCounters.ifInBandwidth.15sec

       unit name = bps
       formula = 8 * ; 8 /"
   ::= {pr1645v2TTmplPerfEntry 45417728}

pr1645v2TTmplPerfMCInBandwidth30sec OBJECT-TYPE
   SYNTAX      Integer32
   MAX-ACCESS  read-only
   STATUS      current
   DESCRIPTION
      "Path: tunnels.performance.l2tpTunnels.mibCounters.ifInBandwidth.30sec

       unit name = bps
       formula = 8 * ; 8 /"
   ::= {pr1645v2TTmplPerfEntry 45419008}

pr1645v2TTmplPerfMCInBandwidth1min OBJECT-TYPE
   SYNTAX      Integer32
   MAX-ACCESS  read-only
   STATUS      current
   DESCRIPTION
      "Path: tunnels.performance.l2tpTunnels.mibCounters.ifInBandwidth.1min

       unit name = bps
       formula = 8 * ; 8 /"
   ::= {pr1645v2TTmplPerfEntry 45421568}

pr1645v2TTmplPerfMCInBandwidth2min OBJECT-TYPE
   SYNTAX      Integer32
   MAX-ACCESS  read-only
   STATUS      current
   DESCRIPTION
      "Path: tunnels.performance.l2tpTunnels.mibCounters.ifInBandwidth.2min

       unit name = bps
       formula = 8 * ; 8 /"
   ::= {pr1645v2TTmplPerfEntry 45426688}

pr1645v2TTmplPerfMCInBandwidth5min OBJECT-TYPE
   SYNTAX      Integer32
   MAX-ACCESS  read-only
   STATUS      current
   DESCRIPTION
      "Path: tunnels.performance.l2tpTunnels.mibCounters.ifInBandwidth.5min

       unit name = bps
       formula = 8 * ; 8 /"
   ::= {pr1645v2TTmplPerfEntry 45442048}

pr1645v2TTmplPerfMCOutOctets OBJECT-TYPE
   SYNTAX      Counter64
   MAX-ACCESS  read-only
   STATUS      current
   DESCRIPTION
      "Path: tunnels.performance.l2tpTunnels.mibCounters.ifOutOctets

       64 bit unsigned wrappable counter."
   ::= {pr1645v2TTmplPerfEntry 41091072}

pr1645v2TTmplPerfMCOutUcastPkts OBJECT-TYPE
   SYNTAX      Counter64
   MAX-ACCESS  read-only
   STATUS      current
   DESCRIPTION
      "Path: tunnels.performance.l2tpTunnels.mibCounters.ifOutUcastPkts

       64 bit unsigned wrappable counter."
   ::= {pr1645v2TTmplPerfEntry 41156608}

pr1645v2TTmplPerfMCOutNUcastPkts OBJECT-TYPE
   SYNTAX      Counter64
   MAX-ACCESS  read-only
   STATUS      current
   DESCRIPTION
      "Path: tunnels.performance.l2tpTunnels.mibCounters.ifOutNUcastPkts

       64 bit unsigned wrappable counter."
   ::= {pr1645v2TTmplPerfEntry 41222144}

pr1645v2TTmplPerfMCOutBcastPkts OBJECT-TYPE
   SYNTAX      Counter64
   MAX-ACCESS  read-only
   STATUS      current
   DESCRIPTION
      "Path: tunnels.performance.l2tpTunnels.mibCounters.ifOutBcastPkts

       64 bit unsigned wrappable counter."
   ::= {pr1645v2TTmplPerfEntry 47775744}

pr1645v2TTmplPerfMCOutMcastPkts OBJECT-TYPE
   SYNTAX      Counter64
   MAX-ACCESS  read-only
   STATUS      current
   DESCRIPTION
      "Path: tunnels.performance.l2tpTunnels.mibCounters.ifOutMcastPkts

       64 bit unsigned wrappable counter."
   ::= {pr1645v2TTmplPerfEntry 48431104}

pr1645v2TTmplPerfMCOutDiscards OBJECT-TYPE
   SYNTAX      Counter64
   MAX-ACCESS  read-only
   STATUS      current
   DESCRIPTION
      "Path: tunnels.performance.l2tpTunnels.mibCounters.ifOutDiscards

       64 bit unsigned wrappable counter."
   ::= {pr1645v2TTmplPerfEntry 41287680}

pr1645v2TTmplPerfMCOutErrors OBJECT-TYPE
   SYNTAX      Counter64
   MAX-ACCESS  read-only
   STATUS      current
   DESCRIPTION
      "Path: tunnels.performance.l2tpTunnels.mibCounters.ifOutErrors

       64 bit unsigned wrappable counter."
   ::= {pr1645v2TTmplPerfEntry 41353216}

pr1645v2TTmplPerfMCOutQLen OBJECT-TYPE
   SYNTAX      Counter32
   MAX-ACCESS  read-only
   STATUS      current
   DESCRIPTION
      "Path: tunnels.performance.l2tpTunnels.mibCounters.ifOutQLen

       32 bit unsigned wrappable counter."
   ::= {pr1645v2TTmplPerfEntry 41418752}

pr1645v2TTmplPerfMCOutDropEx OBJECT-TYPE
   SYNTAX      Counter64
   MAX-ACCESS  read-only
   STATUS      current
   DESCRIPTION
      "Path: tunnels.performance.l2tpTunnels.mibCounters.ifOutDropLevelExceeded

       64 bit unsigned wrappable counter."
   ::= {pr1645v2TTmplPerfEntry 41484288}

pr1645v2TTmplPerfMCOutDropNoArp OBJECT-TYPE
   SYNTAX      Counter64
   MAX-ACCESS  read-only
   STATUS      current
   DESCRIPTION
      "Path: tunnels.performance.l2tpTunnels.mibCounters.ifOutDiscardsNoArp

       64 bit unsigned wrappable counter."
   ::= {pr1645v2TTmplPerfEntry 42336256}

pr1645v2TTmplPerfMCOutDropFilter OBJECT-TYPE
   SYNTAX      Counter64
   MAX-ACCESS  read-only
   STATUS      current
   DESCRIPTION
      "Path: tunnels.performance.l2tpTunnels.mibCounters.ifOutDiscardsFilter

       64 bit unsigned wrappable counter."
   ::= {pr1645v2TTmplPerfEntry 42598400}

pr1645v2TTmplPerfMCOutBandwidth15sec OBJECT-TYPE
   SYNTAX      Integer32
   MAX-ACCESS  read-only
   STATUS      current
   DESCRIPTION
      "Path: tunnels.performance.l2tpTunnels.mibCounters.ifOutBandwidth.15sec

       unit name = bps
       formula = 8 * ; 8 /"
   ::= {pr1645v2TTmplPerfEntry 45483264}

pr1645v2TTmplPerfMCOutBandwidth30sec OBJECT-TYPE
   SYNTAX      Integer32
   MAX-ACCESS  read-only
   STATUS      current
   DESCRIPTION
      "Path: tunnels.performance.l2tpTunnels.mibCounters.ifOutBandwidth.30sec

       unit name = bps
       formula = 8 * ; 8 /"
   ::= {pr1645v2TTmplPerfEntry 45484544}

pr1645v2TTmplPerfMCOutBandwidth1min OBJECT-TYPE
   SYNTAX      Integer32
   MAX-ACCESS  read-only
   STATUS      current
   DESCRIPTION
      "Path: tunnels.performance.l2tpTunnels.mibCounters.ifOutBandwidth.1min

       unit name = bps
       formula = 8 * ; 8 /"
   ::= {pr1645v2TTmplPerfEntry 45487104}

pr1645v2TTmplPerfMCOutBandwidth2min OBJECT-TYPE
   SYNTAX      Integer32
   MAX-ACCESS  read-only
   STATUS      current
   DESCRIPTION
      "Path: tunnels.performance.l2tpTunnels.mibCounters.ifOutBandwidth.2min

       unit name = bps
       formula = 8 * ; 8 /"
   ::= {pr1645v2TTmplPerfEntry 45492224}

pr1645v2TTmplPerfMCOutBandwidth5min OBJECT-TYPE
   SYNTAX      Integer32
   MAX-ACCESS  read-only
   STATUS      current
   DESCRIPTION
      "Path: tunnels.performance.l2tpTunnels.mibCounters.ifOutBandwidth.5min

       unit name = bps
       formula = 8 * ; 8 /"
   ::= {pr1645v2TTmplPerfEntry 45507584}

pr1645v2TTmplPerfControlHelloSent OBJECT-TYPE
   SYNTAX      Gauge32
   MAX-ACCESS  read-only
   STATUS      current
   DESCRIPTION
      "Path: tunnels.performance.l2tpTunnels.control.helloSent

       32 bit unsigned gauge value."
   ::= {pr1645v2TTmplPerfEntry 117506048}

pr1645v2TTmplPerfControlHelloRcvd OBJECT-TYPE
   SYNTAX      Gauge32
   MAX-ACCESS  read-only
   STATUS      current
   DESCRIPTION
      "Path: tunnels.performance.l2tpTunnels.control.helloRcvd

       32 bit unsigned gauge value."
   ::= {pr1645v2TTmplPerfEntry 117637120}

pr1645v2TTmplPerfControlAckSent OBJECT-TYPE
   SYNTAX      Gauge32
   MAX-ACCESS  read-only
   STATUS      current
   DESCRIPTION
      "Path: tunnels.performance.l2tpTunnels.control.ackSent

       32 bit unsigned gauge value."
   ::= {pr1645v2TTmplPerfEntry 117702656}

pr1645v2TTmplPerfControlAckRcvd OBJECT-TYPE
   SYNTAX      Gauge32
   MAX-ACCESS  read-only
   STATUS      current
   DESCRIPTION
      "Path: tunnels.performance.l2tpTunnels.control.ackRcvd

       32 bit unsigned gauge value."
   ::= {pr1645v2TTmplPerfEntry 117571584}

pr1645v2TTmplPerfControlDuplicateRcvd OBJECT-TYPE
   SYNTAX      Gauge32
   MAX-ACCESS  read-only
   STATUS      current
   DESCRIPTION
      "Path: tunnels.performance.l2tpTunnels.control.duplicateRcvd

       32 bit unsigned gauge value."
   ::= {pr1645v2TTmplPerfEntry 117768192}

pr1645v2TTmplPerfControlOutOfSeqRcvd OBJECT-TYPE
   SYNTAX      Gauge32
   MAX-ACCESS  read-only
   STATUS      current
   DESCRIPTION
      "Path: tunnels.performance.l2tpTunnels.control.outOfSeqRcvd

       32 bit unsigned gauge value."
   ::= {pr1645v2TTmplPerfEntry 117833728}

pr1645v2TTmplPerfControlRetransmission OBJECT-TYPE
   SYNTAX      Gauge32
   MAX-ACCESS  read-only
   STATUS      current
   DESCRIPTION
      "Path: tunnels.performance.l2tpTunnels.control.retransmission

       32 bit unsigned gauge value."
   ::= {pr1645v2TTmplPerfEntry 117899264}

pr1645v2TTmplPerfControlAuthenFailure OBJECT-TYPE
   SYNTAX      Gauge32
   MAX-ACCESS  read-only
   STATUS      current
   DESCRIPTION
      "Path: tunnels.performance.l2tpTunnels.control.authenFailure

       32 bit unsigned gauge value."
   ::= {pr1645v2TTmplPerfEntry 117964800}

pr1645v2TTmplPerfPppPort OBJECT-TYPE
   SYNTAX      Counter32
   MAX-ACCESS  read-only
   STATUS      current
   DESCRIPTION
      "Path: tunnels.performance.l2tpTunnels.ppp.port

       32 bit unsigned wrappable counter."
   ::= {pr1645v2TTmplPerfEntry 67371008}

pr1645v2TTmplPerfPppLcpUp OBJECT-TYPE
   SYNTAX      Counter32
   MAX-ACCESS  read-only
   STATUS      current
   DESCRIPTION
      "Path: tunnels.performance.l2tpTunnels.ppp.lcp.up

       32 bit unsigned wrappable counter."
   ::= {pr1645v2TTmplPerfEntry 67174656}

pr1645v2TTmplPerfPppLcpDown OBJECT-TYPE
   SYNTAX      Counter32
   MAX-ACCESS  read-only
   STATUS      current
   DESCRIPTION
      "Path: tunnels.performance.l2tpTunnels.ppp.lcp.down

       32 bit unsigned wrappable counter."
   ::= {pr1645v2TTmplPerfEntry 67174912}

pr1645v2TTmplPerfPppLcpOpen OBJECT-TYPE
   SYNTAX      Counter32
   MAX-ACCESS  read-only
   STATUS      current
   DESCRIPTION
      "Path: tunnels.performance.l2tpTunnels.ppp.lcp.open

       32 bit unsigned wrappable counter."
   ::= {pr1645v2TTmplPerfEntry 67175168}

pr1645v2TTmplPerfPppLcpClose OBJECT-TYPE
   SYNTAX      Counter32
   MAX-ACCESS  read-only
   STATUS      current
   DESCRIPTION
      "Path: tunnels.performance.l2tpTunnels.ppp.lcp.close

       32 bit unsigned wrappable counter."
   ::= {pr1645v2TTmplPerfEntry 67175424}

pr1645v2TTmplPerfPppLcpToP OBJECT-TYPE
   SYNTAX      Counter32
   MAX-ACCESS  read-only
   STATUS      current
   DESCRIPTION
      "Path: tunnels.performance.l2tpTunnels.ppp.lcp.toP

       32 bit unsigned wrappable counter."
   ::= {pr1645v2TTmplPerfEntry 67175680}

pr1645v2TTmplPerfPppLcpToM OBJECT-TYPE
   SYNTAX      Counter32
   MAX-ACCESS  read-only
   STATUS      current
   DESCRIPTION
      "Path: tunnels.performance.l2tpTunnels.ppp.lcp.toM

       32 bit unsigned wrappable counter."
   ::= {pr1645v2TTmplPerfEntry 67175936}

pr1645v2TTmplPerfPppLcpRcrP OBJECT-TYPE
   SYNTAX      Counter32
   MAX-ACCESS  read-only
   STATUS      current
   DESCRIPTION
      "Path: tunnels.performance.l2tpTunnels.ppp.lcp.rcrP

       32 bit unsigned wrappable counter."
   ::= {pr1645v2TTmplPerfEntry 67176192}

pr1645v2TTmplPerfPppLcpRcrM OBJECT-TYPE
   SYNTAX      Counter32
   MAX-ACCESS  read-only
   STATUS      current
   DESCRIPTION
      "Path: tunnels.performance.l2tpTunnels.ppp.lcp.rcrM

       32 bit unsigned wrappable counter."
   ::= {pr1645v2TTmplPerfEntry 67176448}

pr1645v2TTmplPerfPppLcpRca OBJECT-TYPE
   SYNTAX      Counter32
   MAX-ACCESS  read-only
   STATUS      current
   DESCRIPTION
      "Path: tunnels.performance.l2tpTunnels.ppp.lcp.rca

       32 bit unsigned wrappable counter."
   ::= {pr1645v2TTmplPerfEntry 67176704}

pr1645v2TTmplPerfPppLcpRcn OBJECT-TYPE
   SYNTAX      Counter32
   MAX-ACCESS  read-only
   STATUS      current
   DESCRIPTION
      "Path: tunnels.performance.l2tpTunnels.ppp.lcp.rcn

       32 bit unsigned wrappable counter."
   ::= {pr1645v2TTmplPerfEntry 67176960}

pr1645v2TTmplPerfPppLcpRtr OBJECT-TYPE
   SYNTAX      Counter32
   MAX-ACCESS  read-only
   STATUS      current
   DESCRIPTION
      "Path: tunnels.performance.l2tpTunnels.ppp.lcp.rtr

       32 bit unsigned wrappable counter."
   ::= {pr1645v2TTmplPerfEntry 67177216}

pr1645v2TTmplPerfPppLcpRta OBJECT-TYPE
   SYNTAX      Counter32
   MAX-ACCESS  read-only
   STATUS      current
   DESCRIPTION
      "Path: tunnels.performance.l2tpTunnels.ppp.lcp.rta

       32 bit unsigned wrappable counter."
   ::= {pr1645v2TTmplPerfEntry 67177472}

pr1645v2TTmplPerfPppLcpRuc OBJECT-TYPE
   SYNTAX      Counter32
   MAX-ACCESS  read-only
   STATUS      current
   DESCRIPTION
      "Path: tunnels.performance.l2tpTunnels.ppp.lcp.ruc

       32 bit unsigned wrappable counter."
   ::= {pr1645v2TTmplPerfEntry 67177728}

pr1645v2TTmplPerfPppLcpRxjP OBJECT-TYPE
   SYNTAX      Counter32
   MAX-ACCESS  read-only
   STATUS      current
   DESCRIPTION
      "Path: tunnels.performance.l2tpTunnels.ppp.lcp.rxjP

       32 bit unsigned wrappable counter."
   ::= {pr1645v2TTmplPerfEntry 67177984}

pr1645v2TTmplPerfPppLcpRxjM OBJECT-TYPE
   SYNTAX      Counter32
   MAX-ACCESS  read-only
   STATUS      current
   DESCRIPTION
      "Path: tunnels.performance.l2tpTunnels.ppp.lcp.rxjM

       32 bit unsigned wrappable counter."
   ::= {pr1645v2TTmplPerfEntry 67178240}

pr1645v2TTmplPerfPppLcpRxr OBJECT-TYPE
   SYNTAX      Counter32
   MAX-ACCESS  read-only
   STATUS      current
   DESCRIPTION
      "Path: tunnels.performance.l2tpTunnels.ppp.lcp.rxr

       32 bit unsigned wrappable counter."
   ::= {pr1645v2TTmplPerfEntry 67178496}

pr1645v2TTmplPerfPppLcpRrr OBJECT-TYPE
   SYNTAX      Counter32
   MAX-ACCESS  read-only
   STATUS      current
   DESCRIPTION
      "Path: tunnels.performance.l2tpTunnels.ppp.lcp.rrr

       32 bit unsigned wrappable counter."
   ::= {pr1645v2TTmplPerfEntry 67178752}

pr1645v2TTmplPerfPppLcpRra OBJECT-TYPE
   SYNTAX      Counter32
   MAX-ACCESS  read-only
   STATUS      current
   DESCRIPTION
      "Path: tunnels.performance.l2tpTunnels.ppp.lcp.rra

       32 bit unsigned wrappable counter."
   ::= {pr1645v2TTmplPerfEntry 67179008}

pr1645v2TTmplPerfPppLcpDf OBJECT-TYPE
   SYNTAX      Counter32
   MAX-ACCESS  read-only
   STATUS      current
   DESCRIPTION
      "Path: tunnels.performance.l2tpTunnels.ppp.lcp.df

       32 bit unsigned wrappable counter."
   ::= {pr1645v2TTmplPerfEntry 67179264}

pr1645v2TTmplPerfPppLcpIntClose OBJECT-TYPE
   SYNTAX      Counter32
   MAX-ACCESS  read-only
   STATUS      current
   DESCRIPTION
      "Path: tunnels.performance.l2tpTunnels.ppp.lcp.intClose

       32 bit unsigned wrappable counter."
   ::= {pr1645v2TTmplPerfEntry 67179520}

pr1645v2TTmplPerfPppLcpLm OBJECT-TYPE
   SYNTAX      Counter32
   MAX-ACCESS  read-only
   STATUS      current
   DESCRIPTION
      "Path: tunnels.performance.l2tpTunnels.ppp.lcp.lm

       32 bit unsigned wrappable counter."
   ::= {pr1645v2TTmplPerfEntry 67179776}

pr1645v2TTmplPerfPppLcpLmM OBJECT-TYPE
   SYNTAX      Counter32
   MAX-ACCESS  read-only
   STATUS      current
   DESCRIPTION
      "Path: tunnels.performance.l2tpTunnels.ppp.lcp.lmM

       32 bit unsigned wrappable counter."
   ::= {pr1645v2TTmplPerfEntry 67180032}

pr1645v2TTmplPerfPppAuthMyNegotiated OBJECT-TYPE
   SYNTAX      INTEGER
               {
               none (0),
               pap (1),
               chap (2),
               msChap (3),
               msChapV2 (4),
               unknown (5),
               chapOrPap (6)
               }
   MAX-ACCESS  read-only
   STATUS      current
   DESCRIPTION
      "Path: tunnels.performance.l2tpTunnels.ppp.auth.myNegotiated

       Possibilities:
               none   (0)
               pap   (1)
               chap   (2)
               msChap   (3)
               msChapV2   (4)
               unknown   (5)
               chapOrPap   (6)"
   ::= {pr1645v2TTmplPerfEntry 67243264}

pr1645v2TTmplPerfPppAuthMyConfigured OBJECT-TYPE
   SYNTAX      INTEGER
               {
               none (0),
               pap (1),
               chap (2),
               msChap (3),
               msChapV2 (4),
               unknown (5),
               chapOrPap (6)
               }
   MAX-ACCESS  read-only
   STATUS      current
   DESCRIPTION
      "Path: tunnels.performance.l2tpTunnels.ppp.auth.myConfigured

       Possibilities:
               none   (0)
               pap   (1)
               chap   (2)
               msChap   (3)
               msChapV2   (4)
               unknown   (5)
               chapOrPap   (6)"
   ::= {pr1645v2TTmplPerfEntry 67243776}

pr1645v2TTmplPerfPppAuthHisRequested OBJECT-TYPE
   SYNTAX      INTEGER
               {
               none (0),
               pap (1),
               chap (2),
               msChap (3),
               msChapV2 (4),
               unknown (5),
               chapOrPap (6)
               }
   MAX-ACCESS  read-only
   STATUS      current
   DESCRIPTION
      "Path: tunnels.performance.l2tpTunnels.ppp.auth.hisRequested

       Possibilities:
               none   (0)
               pap   (1)
               chap   (2)
               msChap   (3)
               msChapV2   (4)
               unknown   (5)
               chapOrPap   (6)"
   ::= {pr1645v2TTmplPerfEntry 67243520}

pr1645v2TTmplPerfPppAuthRxChallenge OBJECT-TYPE
   SYNTAX      Counter32
   MAX-ACCESS  read-only
   STATUS      current
   DESCRIPTION
      "Path: tunnels.performance.l2tpTunnels.ppp.auth.rxChallenge

       32 bit unsigned wrappable counter."
   ::= {pr1645v2TTmplPerfEntry 67240192}

pr1645v2TTmplPerfPppAuthRxResponse OBJECT-TYPE
   SYNTAX      Counter32
   MAX-ACCESS  read-only
   STATUS      current
   DESCRIPTION
      "Path: tunnels.performance.l2tpTunnels.ppp.auth.rxResponse

       32 bit unsigned wrappable counter."
   ::= {pr1645v2TTmplPerfEntry 67240448}

pr1645v2TTmplPerfPppAuthRxSuccess OBJECT-TYPE
   SYNTAX      Counter32
   MAX-ACCESS  read-only
   STATUS      current
   DESCRIPTION
      "Path: tunnels.performance.l2tpTunnels.ppp.auth.rxSuccess

       32 bit unsigned wrappable counter."
   ::= {pr1645v2TTmplPerfEntry 67240704}

pr1645v2TTmplPerfPppAuthRxFailure OBJECT-TYPE
   SYNTAX      Counter32
   MAX-ACCESS  read-only
   STATUS      current
   DESCRIPTION
      "Path: tunnels.performance.l2tpTunnels.ppp.auth.rxFailure

       32 bit unsigned wrappable counter."
   ::= {pr1645v2TTmplPerfEntry 67240960}

pr1645v2TTmplPerfPppAuthChallengeTO OBJECT-TYPE
   SYNTAX      Counter32
   MAX-ACCESS  read-only
   STATUS      current
   DESCRIPTION
      "Path: tunnels.performance.l2tpTunnels.ppp.auth.challengeTO

       32 bit unsigned wrappable counter."
   ::= {pr1645v2TTmplPerfEntry 67241216}

pr1645v2TTmplPerfPppAuthResponseTO OBJECT-TYPE
   SYNTAX      Counter32
   MAX-ACCESS  read-only
   STATUS      current
   DESCRIPTION
      "Path: tunnels.performance.l2tpTunnels.ppp.auth.responseTO

       32 bit unsigned wrappable counter."
   ::= {pr1645v2TTmplPerfEntry 67241472}

pr1645v2TTmplPerfPppAuthTxChallenge OBJECT-TYPE
   SYNTAX      Counter32
   MAX-ACCESS  read-only
   STATUS      current
   DESCRIPTION
      "Path: tunnels.performance.l2tpTunnels.ppp.auth.txChallenge

       32 bit unsigned wrappable counter."
   ::= {pr1645v2TTmplPerfEntry 67241728}

pr1645v2TTmplPerfPppAuthRxRadiusSuccess OBJECT-TYPE
   SYNTAX      Counter32
   MAX-ACCESS  read-only
   STATUS      current
   DESCRIPTION
      "Path: tunnels.performance.l2tpTunnels.ppp.auth.rxRadiusSuccess

       32 bit unsigned wrappable counter."
   ::= {pr1645v2TTmplPerfEntry 67241984}

pr1645v2TTmplPerfPppAuthRxRadiusFailure OBJECT-TYPE
   SYNTAX      Counter32
   MAX-ACCESS  read-only
   STATUS      current
   DESCRIPTION
      "Path: tunnels.performance.l2tpTunnels.ppp.auth.rxRadiusFailure

       32 bit unsigned wrappable counter."
   ::= {pr1645v2TTmplPerfEntry 67242240}

pr1645v2TTmplPerfPppAuthTxSuccess OBJECT-TYPE
   SYNTAX      Counter32
   MAX-ACCESS  read-only
   STATUS      current
   DESCRIPTION
      "Path: tunnels.performance.l2tpTunnels.ppp.auth.txSuccess

       32 bit unsigned wrappable counter."
   ::= {pr1645v2TTmplPerfEntry 67242496}

pr1645v2TTmplPerfPppAuthTxFailure OBJECT-TYPE
   SYNTAX      Counter32
   MAX-ACCESS  read-only
   STATUS      current
   DESCRIPTION
      "Path: tunnels.performance.l2tpTunnels.ppp.auth.txFailure

       32 bit unsigned wrappable counter."
   ::= {pr1645v2TTmplPerfEntry 67242752}

pr1645v2TTmplPerfPppAuthUnexpected OBJECT-TYPE
   SYNTAX      Counter32
   MAX-ACCESS  read-only
   STATUS      current
   DESCRIPTION
      "Path: tunnels.performance.l2tpTunnels.ppp.auth.unexpected

       32 bit unsigned wrappable counter."
   ::= {pr1645v2TTmplPerfEntry 67243008}

pr1645v2TTmplPerfPppIpcpUp OBJECT-TYPE
   SYNTAX      Counter32
   MAX-ACCESS  read-only
   STATUS      current
   DESCRIPTION
      "Path: tunnels.performance.l2tpTunnels.ppp.ipcp.up

       32 bit unsigned wrappable counter."
   ::= {pr1645v2TTmplPerfEntry 67305728}

pr1645v2TTmplPerfPppIpcpDown OBJECT-TYPE
   SYNTAX      Counter32
   MAX-ACCESS  read-only
   STATUS      current
   DESCRIPTION
      "Path: tunnels.performance.l2tpTunnels.ppp.ipcp.down

       32 bit unsigned wrappable counter."
   ::= {pr1645v2TTmplPerfEntry 67305984}

pr1645v2TTmplPerfPppIpcpOpen OBJECT-TYPE
   SYNTAX      Counter32
   MAX-ACCESS  read-only
   STATUS      current
   DESCRIPTION
      "Path: tunnels.performance.l2tpTunnels.ppp.ipcp.open

       32 bit unsigned wrappable counter."
   ::= {pr1645v2TTmplPerfEntry 67306240}

pr1645v2TTmplPerfPppIpcpClose OBJECT-TYPE
   SYNTAX      Counter32
   MAX-ACCESS  read-only
   STATUS      current
   DESCRIPTION
      "Path: tunnels.performance.l2tpTunnels.ppp.ipcp.close

       32 bit unsigned wrappable counter."
   ::= {pr1645v2TTmplPerfEntry 67306496}

pr1645v2TTmplPerfPppIpcpToP OBJECT-TYPE
   SYNTAX      Counter32
   MAX-ACCESS  read-only
   STATUS      current
   DESCRIPTION
      "Path: tunnels.performance.l2tpTunnels.ppp.ipcp.toP

       32 bit unsigned wrappable counter."
   ::= {pr1645v2TTmplPerfEntry 67306752}

pr1645v2TTmplPerfPppIpcpToM OBJECT-TYPE
   SYNTAX      Counter32
   MAX-ACCESS  read-only
   STATUS      current
   DESCRIPTION
      "Path: tunnels.performance.l2tpTunnels.ppp.ipcp.toM

       32 bit unsigned wrappable counter."
   ::= {pr1645v2TTmplPerfEntry 67307008}

pr1645v2TTmplPerfPppIpcpRcrP OBJECT-TYPE
   SYNTAX      Counter32
   MAX-ACCESS  read-only
   STATUS      current
   DESCRIPTION
      "Path: tunnels.performance.l2tpTunnels.ppp.ipcp.rcrP

       32 bit unsigned wrappable counter."
   ::= {pr1645v2TTmplPerfEntry 67307264}

pr1645v2TTmplPerfPppIpcpRcrM OBJECT-TYPE
   SYNTAX      Counter32
   MAX-ACCESS  read-only
   STATUS      current
   DESCRIPTION
      "Path: tunnels.performance.l2tpTunnels.ppp.ipcp.rcrM

       32 bit unsigned wrappable counter."
   ::= {pr1645v2TTmplPerfEntry 67307520}

pr1645v2TTmplPerfPppIpcpRca OBJECT-TYPE
   SYNTAX      Counter32
   MAX-ACCESS  read-only
   STATUS      current
   DESCRIPTION
      "Path: tunnels.performance.l2tpTunnels.ppp.ipcp.rca

       32 bit unsigned wrappable counter."
   ::= {pr1645v2TTmplPerfEntry 67307776}

pr1645v2TTmplPerfPppIpcpRcn OBJECT-TYPE
   SYNTAX      Counter32
   MAX-ACCESS  read-only
   STATUS      current
   DESCRIPTION
      "Path: tunnels.performance.l2tpTunnels.ppp.ipcp.rcn

       32 bit unsigned wrappable counter."
   ::= {pr1645v2TTmplPerfEntry 67308032}

pr1645v2TTmplPerfPppIpcpRtr OBJECT-TYPE
   SYNTAX      Counter32
   MAX-ACCESS  read-only
   STATUS      current
   DESCRIPTION
      "Path: tunnels.performance.l2tpTunnels.ppp.ipcp.rtr

       32 bit unsigned wrappable counter."
   ::= {pr1645v2TTmplPerfEntry 67308288}

pr1645v2TTmplPerfPppIpcpRta OBJECT-TYPE
   SYNTAX      Counter32
   MAX-ACCESS  read-only
   STATUS      current
   DESCRIPTION
      "Path: tunnels.performance.l2tpTunnels.ppp.ipcp.rta

       32 bit unsigned wrappable counter."
   ::= {pr1645v2TTmplPerfEntry 67308544}

pr1645v2TTmplPerfPppIpcpRuc OBJECT-TYPE
   SYNTAX      Counter32
   MAX-ACCESS  read-only
   STATUS      current
   DESCRIPTION
      "Path: tunnels.performance.l2tpTunnels.ppp.ipcp.ruc

       32 bit unsigned wrappable counter."
   ::= {pr1645v2TTmplPerfEntry 67308800}

pr1645v2TTmplPerfPppIpcpRxjP OBJECT-TYPE
   SYNTAX      Counter32
   MAX-ACCESS  read-only
   STATUS      current
   DESCRIPTION
      "Path: tunnels.performance.l2tpTunnels.ppp.ipcp.rxjP

       32 bit unsigned wrappable counter."
   ::= {pr1645v2TTmplPerfEntry 67309056}

pr1645v2TTmplPerfPppIpcpRxjM OBJECT-TYPE
   SYNTAX      Counter32
   MAX-ACCESS  read-only
   STATUS      current
   DESCRIPTION
      "Path: tunnels.performance.l2tpTunnels.ppp.ipcp.rxjM

       32 bit unsigned wrappable counter."
   ::= {pr1645v2TTmplPerfEntry 67309312}

pr1645v2TTmplPerfPppIpcpRxr OBJECT-TYPE
   SYNTAX      Counter32
   MAX-ACCESS  read-only
   STATUS      current
   DESCRIPTION
      "Path: tunnels.performance.l2tpTunnels.ppp.ipcp.rxr

       32 bit unsigned wrappable counter."
   ::= {pr1645v2TTmplPerfEntry 67309568}

pr1645v2TTmplPerfPppIpcpRrr OBJECT-TYPE
   SYNTAX      Counter32
   MAX-ACCESS  read-only
   STATUS      current
   DESCRIPTION
      "Path: tunnels.performance.l2tpTunnels.ppp.ipcp.rrr

       32 bit unsigned wrappable counter."
   ::= {pr1645v2TTmplPerfEntry 67309824}

pr1645v2TTmplPerfPppIpcpRra OBJECT-TYPE
   SYNTAX      Counter32
   MAX-ACCESS  read-only
   STATUS      current
   DESCRIPTION
      "Path: tunnels.performance.l2tpTunnels.ppp.ipcp.rra

       32 bit unsigned wrappable counter."
   ::= {pr1645v2TTmplPerfEntry 67310080}

pr1645v2TTmplPerfPppIpcpDf OBJECT-TYPE
   SYNTAX      Counter32
   MAX-ACCESS  read-only
   STATUS      current
   DESCRIPTION
      "Path: tunnels.performance.l2tpTunnels.ppp.ipcp.df

       32 bit unsigned wrappable counter."
   ::= {pr1645v2TTmplPerfEntry 67310336}

pr1645v2TTmplPerfPppIpcpIntClose OBJECT-TYPE
   SYNTAX      Counter32
   MAX-ACCESS  read-only
   STATUS      current
   DESCRIPTION
      "Path: tunnels.performance.l2tpTunnels.ppp.ipcp.intClose

       32 bit unsigned wrappable counter."
   ::= {pr1645v2TTmplPerfEntry 67310592}

pr1645v2TTmplPerfPppIpcpLm OBJECT-TYPE
   SYNTAX      Counter32
   MAX-ACCESS  read-only
   STATUS      current
   DESCRIPTION
      "Path: tunnels.performance.l2tpTunnels.ppp.ipcp.lm

       32 bit unsigned wrappable counter."
   ::= {pr1645v2TTmplPerfEntry 67310848}

pr1645v2TTmplPerfPppIpcpLmM OBJECT-TYPE
   SYNTAX      Counter32
   MAX-ACCESS  read-only
   STATUS      current
   DESCRIPTION
      "Path: tunnels.performance.l2tpTunnels.ppp.ipcp.lmM

       32 bit unsigned wrappable counter."
   ::= {pr1645v2TTmplPerfEntry 67311104}

pr1645v2TTmplPerfPppLinkMonitoringRequestsSent OBJECT-TYPE
   SYNTAX      Gauge32
   MAX-ACCESS  read-only
   STATUS      current
   DESCRIPTION
      "Path: tunnels.performance.l2tpTunnels.ppp.linkMonitoring.requestsSent

       32 bit unsigned gauge value."
   ::= {pr1645v2TTmplPerfEntry 67436800}

pr1645v2TTmplPerfPppLinkMonitoringRepliesRcvd OBJECT-TYPE
   SYNTAX      Gauge32
   MAX-ACCESS  read-only
   STATUS      current
   DESCRIPTION
      "Path: tunnels.performance.l2tpTunnels.ppp.linkMonitoring.repliesRcvd

       32 bit unsigned gauge value."
   ::= {pr1645v2TTmplPerfEntry 67437056}

pr1645v2TTmplPerfPppLinkMonitoringRequestsRcvd OBJECT-TYPE
   SYNTAX      Gauge32
   MAX-ACCESS  read-only
   STATUS      current
   DESCRIPTION
      "Path: tunnels.performance.l2tpTunnels.ppp.linkMonitoring.requestsRcvd

       32 bit unsigned gauge value."
   ::= {pr1645v2TTmplPerfEntry 67437312}

pr1645v2TTmplPerfPppLinkMonitoringRepliesSent OBJECT-TYPE
   SYNTAX      Gauge32
   MAX-ACCESS  read-only
   STATUS      current
   DESCRIPTION
      "Path: tunnels.performance.l2tpTunnels.ppp.linkMonitoring.repliesSent

       32 bit unsigned gauge value."
   ::= {pr1645v2TTmplPerfEntry 67437568}

pr1645v2TTmplPerfMCH2P OBJECT-TYPE
   SYNTAX      SEQUENCE OF Pr1645v2TTmplPerfMCH2PEntry
   MAX-ACCESS  not-accessible
   STATUS      current
   DESCRIPTION
      ""
   ::= {pr1645v2TTmplPerf 41549824}

pr1645v2TTmplPerfMCH2PEntry OBJECT-TYPE
   SYNTAX      Pr1645v2TTmplPerfMCH2PEntry
   MAX-ACCESS  not-accessible
   STATUS      current
   DESCRIPTION
      ""
   INDEX      { pr1645v2TTmplPerfTableIx,
                pr1645v2TTmplPerfMCH2PTableIx }
   ::= {pr1645v2TTmplPerfMCH2P 1}

Pr1645v2TTmplPerfMCH2PEntry ::=
   SEQUENCE
      {
      pr1645v2TTmplPerfMCH2PTableIx
         TableIndex,
      pr1645v2TTmplPerfMCH2PSysUpTime
         TimeTicks,
      pr1645v2TTmplPerfMCH2PIfUpTime
         TimeTicks,
      pr1645v2TTmplPerfMCH2PIfStatChanges
         Counter32,
      pr1645v2TTmplPerfMCH2PIfInOctets
         Counter64,
      pr1645v2TTmplPerfMCH2PIfInUCPkts
         Counter64,
      pr1645v2TTmplPerfMCH2PIfInNUCPkts
         Counter64,
      pr1645v2TTmplPerfMCH2PIfInBCPkts
         Counter64,
      pr1645v2TTmplPerfMCH2PIfInMCPkts
         Counter64,
      pr1645v2TTmplPerfMCH2PIfInDiscards
         Counter64,
      pr1645v2TTmplPerfMCH2PIfInErrors
         Counter64,
      pr1645v2TTmplPerfMCH2PIfInUnkwn
         Counter64,
      pr1645v2TTmplPerfMCH2PInDropEx
         Counter64,
      pr1645v2TTmplPerfMCH2PInDropNoMac
         Counter64,
      pr1645v2TTmplPerfMCH2PInDropNUCast
         Counter64,
      pr1645v2TTmplPerfMCH2PInDropFilter
         Counter64,
      pr1645v2TTmplPerfMCH2PIfInBandwidth
         Integer32,
      pr1645v2TTmplPerfMCH2PIfOutOctets
         Counter64,
      pr1645v2TTmplPerfMCH2PIfOutUCPkts
         Counter64,
      pr1645v2TTmplPerfMCH2PIfOutNUCPkts
         Counter64,
      pr1645v2TTmplPerfMCH2PIfOutBCPkts
         Counter64,
      pr1645v2TTmplPerfMCH2PIfOutMCPkts
         Counter64,
      pr1645v2TTmplPerfMCH2PIfOutDiscards
         Counter64,
      pr1645v2TTmplPerfMCH2PIfOutErrors
         Counter64,
      pr1645v2TTmplPerfMCH2POutDropEx
         Counter64,
      pr1645v2TTmplPerfMCH2POutDropNoArp
         Counter64,
      pr1645v2TTmplPerfMCH2POutDropFilter
         Counter64,
      pr1645v2TTmplPerfMCH2PIfOutBandwidth
         Integer32,
      pr1645v2TTmplPerfMCH2PIfErrSec
         Counter32
      }

pr1645v2TTmplPerfMCH2PTableIx OBJECT-TYPE
   SYNTAX      TableIndex
   MAX-ACCESS  not-accessible
   STATUS      current
   DESCRIPTION
      ""
   ::= {pr1645v2TTmplPerfMCH2PEntry 11}

pr1645v2TTmplPerfMCH2PSysUpTime OBJECT-TYPE
   SYNTAX      TimeTicks
   MAX-ACCESS  read-only
   STATUS      current
   DESCRIPTION
      "Path: tunnels.performance.l2tpTunnels.mibCounters.h2Performance.sysUpTime

       Time in centi-second."
   ::= {pr1645v2TTmplPerfMCH2PEntry 16777216}

pr1645v2TTmplPerfMCH2PIfUpTime OBJECT-TYPE
   SYNTAX      TimeTicks
   MAX-ACCESS  read-only
   STATUS      current
   DESCRIPTION
      "Path: tunnels.performance.l2tpTunnels.mibCounters.h2Performance.ifUpTime

       Time in centi-second."
   ::= {pr1645v2TTmplPerfMCH2PEntry 33554432}

pr1645v2TTmplPerfMCH2PIfStatChanges OBJECT-TYPE
   SYNTAX      Counter32
   MAX-ACCESS  read-only
   STATUS      current
   DESCRIPTION
      "Path: tunnels.performance.l2tpTunnels.mibCounters.h2Performance.ifStatusChanges

       32 bit unsigned wrappable counter."
   ::= {pr1645v2TTmplPerfMCH2PEntry 50331648}

pr1645v2TTmplPerfMCH2PIfInOctets OBJECT-TYPE
   SYNTAX      Counter64
   MAX-ACCESS  read-only
   STATUS      current
   DESCRIPTION
      "Path: tunnels.performance.l2tpTunnels.mibCounters.h2Performance.ifInOctets

       64 bit unsigned wrappable counter."
   ::= {pr1645v2TTmplPerfMCH2PEntry 67108864}

pr1645v2TTmplPerfMCH2PIfInUCPkts OBJECT-TYPE
   SYNTAX      Counter64
   MAX-ACCESS  read-only
   STATUS      current
   DESCRIPTION
      "Path: tunnels.performance.l2tpTunnels.mibCounters.h2Performance.ifInUcastPkts

       64 bit unsigned wrappable counter."
   ::= {pr1645v2TTmplPerfMCH2PEntry 83886080}

pr1645v2TTmplPerfMCH2PIfInNUCPkts OBJECT-TYPE
   SYNTAX      Counter64
   MAX-ACCESS  read-only
   STATUS      current
   DESCRIPTION
      "Path: tunnels.performance.l2tpTunnels.mibCounters.h2Performance.ifInNUcastPkts

       64 bit unsigned wrappable counter."
   ::= {pr1645v2TTmplPerfMCH2PEntry 100663296}

pr1645v2TTmplPerfMCH2PIfInBCPkts OBJECT-TYPE
   SYNTAX      Counter64
   MAX-ACCESS  read-only
   STATUS      current
   DESCRIPTION
      "Path: tunnels.performance.l2tpTunnels.mibCounters.h2Performance.ifInBcastPkts

       64 bit unsigned wrappable counter."
   ::= {pr1645v2TTmplPerfMCH2PEntry 419430400}

pr1645v2TTmplPerfMCH2PIfInMCPkts OBJECT-TYPE
   SYNTAX      Counter64
   MAX-ACCESS  read-only
   STATUS      current
   DESCRIPTION
      "Path: tunnels.performance.l2tpTunnels.mibCounters.h2Performance.ifInMcastPkts

       64 bit unsigned wrappable counter."
   ::= {pr1645v2TTmplPerfMCH2PEntry 436207616}

pr1645v2TTmplPerfMCH2PIfInDiscards OBJECT-TYPE
   SYNTAX      Counter64
   MAX-ACCESS  read-only
   STATUS      current
   DESCRIPTION
      "Path: tunnels.performance.l2tpTunnels.mibCounters.h2Performance.ifInDiscards

       64 bit unsigned wrappable counter."
   ::= {pr1645v2TTmplPerfMCH2PEntry 117440512}

pr1645v2TTmplPerfMCH2PIfInErrors OBJECT-TYPE
   SYNTAX      Counter64
   MAX-ACCESS  read-only
   STATUS      current
   DESCRIPTION
      "Path: tunnels.performance.l2tpTunnels.mibCounters.h2Performance.ifInErrors

       64 bit unsigned wrappable counter."
   ::= {pr1645v2TTmplPerfMCH2PEntry 134217728}

pr1645v2TTmplPerfMCH2PIfInUnkwn OBJECT-TYPE
   SYNTAX      Counter64
   MAX-ACCESS  read-only
   STATUS      current
   DESCRIPTION
      "Path: tunnels.performance.l2tpTunnels.mibCounters.h2Performance.ifInUnknownProtos

       64 bit unsigned wrappable counter."
   ::= {pr1645v2TTmplPerfMCH2PEntry 150994944}

pr1645v2TTmplPerfMCH2PInDropEx OBJECT-TYPE
   SYNTAX      Counter64
   MAX-ACCESS  read-only
   STATUS      current
   DESCRIPTION
      "Path: tunnels.performance.l2tpTunnels.mibCounters.h2Performance.ifInDropLevelExceeded

       64 bit unsigned wrappable counter."
   ::= {pr1645v2TTmplPerfMCH2PEntry 335544320}

pr1645v2TTmplPerfMCH2PInDropNoMac OBJECT-TYPE
   SYNTAX      Counter64
   MAX-ACCESS  read-only
   STATUS      current
   DESCRIPTION
      "Path: tunnels.performance.l2tpTunnels.mibCounters.h2Performance.fInDiscardsNoMacFit

       64 bit unsigned wrappable counter."
   ::= {pr1645v2TTmplPerfMCH2PEntry 301989888}

pr1645v2TTmplPerfMCH2PInDropNUCast OBJECT-TYPE
   SYNTAX      Counter64
   MAX-ACCESS  read-only
   STATUS      current
   DESCRIPTION
      "Path: tunnels.performance.l2tpTunnels.mibCounters.h2Performance.fInDiscardsNUCast

       64 bit unsigned wrappable counter."
   ::= {pr1645v2TTmplPerfMCH2PEntry 318767104}

pr1645v2TTmplPerfMCH2PInDropFilter OBJECT-TYPE
   SYNTAX      Counter64
   MAX-ACCESS  read-only
   STATUS      current
   DESCRIPTION
      "Path: tunnels.performance.l2tpTunnels.mibCounters.h2Performance.fInDiscardsFilter

       64 bit unsigned wrappable counter."
   ::= {pr1645v2TTmplPerfMCH2PEntry 385875968}

pr1645v2TTmplPerfMCH2PIfInBandwidth OBJECT-TYPE
   SYNTAX      Integer32
   MAX-ACCESS  read-only
   STATUS      current
   DESCRIPTION
      "Path: tunnels.performance.l2tpTunnels.mibCounters.h2Performance.ifInBandwidth

       unit name = bps
       formula = 8 * ; 8 /"
   ::= {pr1645v2TTmplPerfMCH2PEntry 268435456}

pr1645v2TTmplPerfMCH2PIfOutOctets OBJECT-TYPE
   SYNTAX      Counter64
   MAX-ACCESS  read-only
   STATUS      current
   DESCRIPTION
      "Path: tunnels.performance.l2tpTunnels.mibCounters.h2Performance.ifOutOctets

       64 bit unsigned wrappable counter."
   ::= {pr1645v2TTmplPerfMCH2PEntry 167772160}

pr1645v2TTmplPerfMCH2PIfOutUCPkts OBJECT-TYPE
   SYNTAX      Counter64
   MAX-ACCESS  read-only
   STATUS      current
   DESCRIPTION
      "Path: tunnels.performance.l2tpTunnels.mibCounters.h2Performance.ifOutUcastPkts

       64 bit unsigned wrappable counter."
   ::= {pr1645v2TTmplPerfMCH2PEntry 184549376}

pr1645v2TTmplPerfMCH2PIfOutNUCPkts OBJECT-TYPE
   SYNTAX      Counter64
   MAX-ACCESS  read-only
   STATUS      current
   DESCRIPTION
      "Path: tunnels.performance.l2tpTunnels.mibCounters.h2Performance.ifOutNUcastPkts

       64 bit unsigned wrappable counter."
   ::= {pr1645v2TTmplPerfMCH2PEntry 201326592}

pr1645v2TTmplPerfMCH2PIfOutBCPkts OBJECT-TYPE
   SYNTAX      Counter64
   MAX-ACCESS  read-only
   STATUS      current
   DESCRIPTION
      "Path: tunnels.performance.l2tpTunnels.mibCounters.h2Performance.ifOutBcastPkts

       64 bit unsigned wrappable counter."
   ::= {pr1645v2TTmplPerfMCH2PEntry 452984832}

pr1645v2TTmplPerfMCH2PIfOutMCPkts OBJECT-TYPE
   SYNTAX      Counter64
   MAX-ACCESS  read-only
   STATUS      current
   DESCRIPTION
      "Path: tunnels.performance.l2tpTunnels.mibCounters.h2Performance.ifOutMcastPkts

       64 bit unsigned wrappable counter."
   ::= {pr1645v2TTmplPerfMCH2PEntry 469762048}

pr1645v2TTmplPerfMCH2PIfOutDiscards OBJECT-TYPE
   SYNTAX      Counter64
   MAX-ACCESS  read-only
   STATUS      current
   DESCRIPTION
      "Path: tunnels.performance.l2tpTunnels.mibCounters.h2Performance.ifOutDiscards

       64 bit unsigned wrappable counter."
   ::= {pr1645v2TTmplPerfMCH2PEntry 218103808}

pr1645v2TTmplPerfMCH2PIfOutErrors OBJECT-TYPE
   SYNTAX      Counter64
   MAX-ACCESS  read-only
   STATUS      current
   DESCRIPTION
      "Path: tunnels.performance.l2tpTunnels.mibCounters.h2Performance.ifOutErrors

       64 bit unsigned wrappable counter."
   ::= {pr1645v2TTmplPerfMCH2PEntry 234881024}

pr1645v2TTmplPerfMCH2POutDropEx OBJECT-TYPE
   SYNTAX      Counter64
   MAX-ACCESS  read-only
   STATUS      current
   DESCRIPTION
      "Path: tunnels.performance.l2tpTunnels.mibCounters.h2Performance.ifOutDropLevelExceeded

       64 bit unsigned wrappable counter."
   ::= {pr1645v2TTmplPerfMCH2PEntry 352321536}

pr1645v2TTmplPerfMCH2POutDropNoArp OBJECT-TYPE
   SYNTAX      Counter64
   MAX-ACCESS  read-only
   STATUS      current
   DESCRIPTION
      "Path: tunnels.performance.l2tpTunnels.mibCounters.h2Performance.ifOutDiscardsNoArp

       64 bit unsigned wrappable counter."
   ::= {pr1645v2TTmplPerfMCH2PEntry 369098752}

pr1645v2TTmplPerfMCH2POutDropFilter OBJECT-TYPE
   SYNTAX      Counter64
   MAX-ACCESS  read-only
   STATUS      current
   DESCRIPTION
      "Path: tunnels.performance.l2tpTunnels.mibCounters.h2Performance.ifOutDiscardsFilter

       64 bit unsigned wrappable counter."
   ::= {pr1645v2TTmplPerfMCH2PEntry 402653184}

pr1645v2TTmplPerfMCH2PIfOutBandwidth OBJECT-TYPE
   SYNTAX      Integer32
   MAX-ACCESS  read-only
   STATUS      current
   DESCRIPTION
      "Path: tunnels.performance.l2tpTunnels.mibCounters.h2Performance.ifOutBandwidth

       unit name = bps
       formula = 8 * ; 8 /"
   ::= {pr1645v2TTmplPerfMCH2PEntry 285212672}

pr1645v2TTmplPerfMCH2PIfErrSec OBJECT-TYPE
   SYNTAX      Counter32
   MAX-ACCESS  read-only
   STATUS      current
   DESCRIPTION
      "Path: tunnels.performance.l2tpTunnels.mibCounters.h2Performance.ifErrSec

       32 bit unsigned wrappable counter."
   ::= {pr1645v2TTmplPerfMCH2PEntry 251658240}

pr1645v2TTmplPerfMCH24P OBJECT-TYPE
   SYNTAX      SEQUENCE OF Pr1645v2TTmplPerfMCH24PEntry
   MAX-ACCESS  not-accessible
   STATUS      current
   DESCRIPTION
      ""
   ::= {pr1645v2TTmplPerf 41615360}

pr1645v2TTmplPerfMCH24PEntry OBJECT-TYPE
   SYNTAX      Pr1645v2TTmplPerfMCH24PEntry
   MAX-ACCESS  not-accessible
   STATUS      current
   DESCRIPTION
      ""
   INDEX      { pr1645v2TTmplPerfTableIx,
                pr1645v2TTmplPerfMCH24PTableIx }
   ::= {pr1645v2TTmplPerfMCH24P 1}

Pr1645v2TTmplPerfMCH24PEntry ::=
   SEQUENCE
      {
      pr1645v2TTmplPerfMCH24PTableIx
         TableIndex,
      pr1645v2TTmplPerfMCH24PSysUpTime
         TimeTicks,
      pr1645v2TTmplPerfMCH24PIfUpTime
         TimeTicks,
      pr1645v2TTmplPerfMCH24PIfStatChanges
         Counter32,
      pr1645v2TTmplPerfMCH24PIfInOctets
         Counter64,
      pr1645v2TTmplPerfMCH24PIfInUCPkts
         Counter64,
      pr1645v2TTmplPerfMCH24PIfInNUCPkts
         Counter64,
      pr1645v2TTmplPerfMCH24PIfInBCPkts
         Counter64,
      pr1645v2TTmplPerfMCH24PIfInMCPkts
         Counter64,
      pr1645v2TTmplPerfMCH24PIfInDiscards
         Counter64,
      pr1645v2TTmplPerfMCH24PIfInErrors
         Counter64,
      pr1645v2TTmplPerfMCH24PIfInUnkwn
         Counter64,
      pr1645v2TTmplPerfMCH24PInDropEx
         Counter64,
      pr1645v2TTmplPerfMCH24PInDropNoMac
         Counter64,
      pr1645v2TTmplPerfMCH24PInDropNUCast
         Counter64,
      pr1645v2TTmplPerfMCH24PInDropFilter
         Counter64,
      pr1645v2TTmplPerfMCH24PIfInBandwidth
         Integer32,
      pr1645v2TTmplPerfMCH24PIfOutOctets
         Counter64,
      pr1645v2TTmplPerfMCH24PIfOutUCPkts
         Counter64,
      pr1645v2TTmplPerfMCH24PIfOutNUCPkts
         Counter64,
      pr1645v2TTmplPerfMCH24PIfOutBCPkts
         Counter64,
      pr1645v2TTmplPerfMCH24PIfOutMCPkts
         Counter64,
      pr1645v2TTmplPerfMCH24PIfOutDiscards
         Counter64,
      pr1645v2TTmplPerfMCH24PIfOutErrors
         Counter64,
      pr1645v2TTmplPerfMCH24POutDropEx
         Counter64,
      pr1645v2TTmplPerfMCH24POutDropNoArp
         Counter64,
      pr1645v2TTmplPerfMCH24POutDropFilter
         Counter64,
      pr1645v2TTmplPerfMCH24PIfOutBandwidth
         Integer32,
      pr1645v2TTmplPerfMCH24PIfErrSec
         Counter32
      }

pr1645v2TTmplPerfMCH24PTableIx OBJECT-TYPE
   SYNTAX      TableIndex
   MAX-ACCESS  not-accessible
   STATUS      current
   DESCRIPTION
      ""
   ::= {pr1645v2TTmplPerfMCH24PEntry 11}

pr1645v2TTmplPerfMCH24PSysUpTime OBJECT-TYPE
   SYNTAX      TimeTicks
   MAX-ACCESS  read-only
   STATUS      current
   DESCRIPTION
      "Path: tunnels.performance.l2tpTunnels.mibCounters.h24Performance.sysUpTime

       Time in centi-second."
   ::= {pr1645v2TTmplPerfMCH24PEntry 16777216}

pr1645v2TTmplPerfMCH24PIfUpTime OBJECT-TYPE
   SYNTAX      TimeTicks
   MAX-ACCESS  read-only
   STATUS      current
   DESCRIPTION
      "Path: tunnels.performance.l2tpTunnels.mibCounters.h24Performance.ifUpTime

       Time in centi-second."
   ::= {pr1645v2TTmplPerfMCH24PEntry 33554432}

pr1645v2TTmplPerfMCH24PIfStatChanges OBJECT-TYPE
   SYNTAX      Counter32
   MAX-ACCESS  read-only
   STATUS      current
   DESCRIPTION
      "Path: tunnels.performance.l2tpTunnels.mibCounters.h24Performance.ifStatusChanges

       32 bit unsigned wrappable counter."
   ::= {pr1645v2TTmplPerfMCH24PEntry 50331648}

pr1645v2TTmplPerfMCH24PIfInOctets OBJECT-TYPE
   SYNTAX      Counter64
   MAX-ACCESS  read-only
   STATUS      current
   DESCRIPTION
      "Path: tunnels.performance.l2tpTunnels.mibCounters.h24Performance.ifInOctets

       64 bit unsigned wrappable counter."
   ::= {pr1645v2TTmplPerfMCH24PEntry 67108864}

pr1645v2TTmplPerfMCH24PIfInUCPkts OBJECT-TYPE
   SYNTAX      Counter64
   MAX-ACCESS  read-only
   STATUS      current
   DESCRIPTION
      "Path: tunnels.performance.l2tpTunnels.mibCounters.h24Performance.ifInUcastPkts

       64 bit unsigned wrappable counter."
   ::= {pr1645v2TTmplPerfMCH24PEntry 83886080}

pr1645v2TTmplPerfMCH24PIfInNUCPkts OBJECT-TYPE
   SYNTAX      Counter64
   MAX-ACCESS  read-only
   STATUS      current
   DESCRIPTION
      "Path: tunnels.performance.l2tpTunnels.mibCounters.h24Performance.ifInNUcastPkts

       64 bit unsigned wrappable counter."
   ::= {pr1645v2TTmplPerfMCH24PEntry 100663296}

pr1645v2TTmplPerfMCH24PIfInBCPkts OBJECT-TYPE
   SYNTAX      Counter64
   MAX-ACCESS  read-only
   STATUS      current
   DESCRIPTION
      "Path: tunnels.performance.l2tpTunnels.mibCounters.h24Performance.ifInBcastPkts

       64 bit unsigned wrappable counter."
   ::= {pr1645v2TTmplPerfMCH24PEntry 419430400}

pr1645v2TTmplPerfMCH24PIfInMCPkts OBJECT-TYPE
   SYNTAX      Counter64
   MAX-ACCESS  read-only
   STATUS      current
   DESCRIPTION
      "Path: tunnels.performance.l2tpTunnels.mibCounters.h24Performance.ifInMcastPkts

       64 bit unsigned wrappable counter."
   ::= {pr1645v2TTmplPerfMCH24PEntry 436207616}

pr1645v2TTmplPerfMCH24PIfInDiscards OBJECT-TYPE
   SYNTAX      Counter64
   MAX-ACCESS  read-only
   STATUS      current
   DESCRIPTION
      "Path: tunnels.performance.l2tpTunnels.mibCounters.h24Performance.ifInDiscards

       64 bit unsigned wrappable counter."
   ::= {pr1645v2TTmplPerfMCH24PEntry 117440512}

pr1645v2TTmplPerfMCH24PIfInErrors OBJECT-TYPE
   SYNTAX      Counter64
   MAX-ACCESS  read-only
   STATUS      current
   DESCRIPTION
      "Path: tunnels.performance.l2tpTunnels.mibCounters.h24Performance.ifInErrors

       64 bit unsigned wrappable counter."
   ::= {pr1645v2TTmplPerfMCH24PEntry 134217728}

pr1645v2TTmplPerfMCH24PIfInUnkwn OBJECT-TYPE
   SYNTAX      Counter64
   MAX-ACCESS  read-only
   STATUS      current
   DESCRIPTION
      "Path: tunnels.performance.l2tpTunnels.mibCounters.h24Performance.ifInUnknownProtos

       64 bit unsigned wrappable counter."
   ::= {pr1645v2TTmplPerfMCH24PEntry 150994944}

pr1645v2TTmplPerfMCH24PInDropEx OBJECT-TYPE
   SYNTAX      Counter64
   MAX-ACCESS  read-only
   STATUS      current
   DESCRIPTION
      "Path: tunnels.performance.l2tpTunnels.mibCounters.h24Performance.ifInDropLevelExceeded

       64 bit unsigned wrappable counter."
   ::= {pr1645v2TTmplPerfMCH24PEntry 335544320}

pr1645v2TTmplPerfMCH24PInDropNoMac OBJECT-TYPE
   SYNTAX      Counter64
   MAX-ACCESS  read-only
   STATUS      current
   DESCRIPTION
      "Path: tunnels.performance.l2tpTunnels.mibCounters.h24Performance.fInDiscardsNoMacFit

       64 bit unsigned wrappable counter."
   ::= {pr1645v2TTmplPerfMCH24PEntry 301989888}

pr1645v2TTmplPerfMCH24PInDropNUCast OBJECT-TYPE
   SYNTAX      Counter64
   MAX-ACCESS  read-only
   STATUS      current
   DESCRIPTION
      "Path: tunnels.performance.l2tpTunnels.mibCounters.h24Performance.fInDiscardsNUCast

       64 bit unsigned wrappable counter."
   ::= {pr1645v2TTmplPerfMCH24PEntry 318767104}

pr1645v2TTmplPerfMCH24PInDropFilter OBJECT-TYPE
   SYNTAX      Counter64
   MAX-ACCESS  read-only
   STATUS      current
   DESCRIPTION
      "Path: tunnels.performance.l2tpTunnels.mibCounters.h24Performance.fInDiscardsFilter

       64 bit unsigned wrappable counter."
   ::= {pr1645v2TTmplPerfMCH24PEntry 385875968}

pr1645v2TTmplPerfMCH24PIfInBandwidth OBJECT-TYPE
   SYNTAX      Integer32
   MAX-ACCESS  read-only
   STATUS      current
   DESCRIPTION
      "Path: tunnels.performance.l2tpTunnels.mibCounters.h24Performance.ifInBandwidth

       unit name = bps
       formula = 8 * ; 8 /"
   ::= {pr1645v2TTmplPerfMCH24PEntry 268435456}

pr1645v2TTmplPerfMCH24PIfOutOctets OBJECT-TYPE
   SYNTAX      Counter64
   MAX-ACCESS  read-only
   STATUS      current
   DESCRIPTION
      "Path: tunnels.performance.l2tpTunnels.mibCounters.h24Performance.ifOutOctets

       64 bit unsigned wrappable counter."
   ::= {pr1645v2TTmplPerfMCH24PEntry 167772160}

pr1645v2TTmplPerfMCH24PIfOutUCPkts OBJECT-TYPE
   SYNTAX      Counter64
   MAX-ACCESS  read-only
   STATUS      current
   DESCRIPTION
      "Path: tunnels.performance.l2tpTunnels.mibCounters.h24Performance.ifOutUcastPkts

       64 bit unsigned wrappable counter."
   ::= {pr1645v2TTmplPerfMCH24PEntry 184549376}

pr1645v2TTmplPerfMCH24PIfOutNUCPkts OBJECT-TYPE
   SYNTAX      Counter64
   MAX-ACCESS  read-only
   STATUS      current
   DESCRIPTION
      "Path: tunnels.performance.l2tpTunnels.mibCounters.h24Performance.ifOutNUcastPkts

       64 bit unsigned wrappable counter."
   ::= {pr1645v2TTmplPerfMCH24PEntry 201326592}

pr1645v2TTmplPerfMCH24PIfOutBCPkts OBJECT-TYPE
   SYNTAX      Counter64
   MAX-ACCESS  read-only
   STATUS      current
   DESCRIPTION
      "Path: tunnels.performance.l2tpTunnels.mibCounters.h24Performance.ifOutBcastPkts

       64 bit unsigned wrappable counter."
   ::= {pr1645v2TTmplPerfMCH24PEntry 452984832}

pr1645v2TTmplPerfMCH24PIfOutMCPkts OBJECT-TYPE
   SYNTAX      Counter64
   MAX-ACCESS  read-only
   STATUS      current
   DESCRIPTION
      "Path: tunnels.performance.l2tpTunnels.mibCounters.h24Performance.ifOutMcastPkts

       64 bit unsigned wrappable counter."
   ::= {pr1645v2TTmplPerfMCH24PEntry 469762048}

pr1645v2TTmplPerfMCH24PIfOutDiscards OBJECT-TYPE
   SYNTAX      Counter64
   MAX-ACCESS  read-only
   STATUS      current
   DESCRIPTION
      "Path: tunnels.performance.l2tpTunnels.mibCounters.h24Performance.ifOutDiscards

       64 bit unsigned wrappable counter."
   ::= {pr1645v2TTmplPerfMCH24PEntry 218103808}

pr1645v2TTmplPerfMCH24PIfOutErrors OBJECT-TYPE
   SYNTAX      Counter64
   MAX-ACCESS  read-only
   STATUS      current
   DESCRIPTION
      "Path: tunnels.performance.l2tpTunnels.mibCounters.h24Performance.ifOutErrors

       64 bit unsigned wrappable counter."
   ::= {pr1645v2TTmplPerfMCH24PEntry 234881024}

pr1645v2TTmplPerfMCH24POutDropEx OBJECT-TYPE
   SYNTAX      Counter64
   MAX-ACCESS  read-only
   STATUS      current
   DESCRIPTION
      "Path: tunnels.performance.l2tpTunnels.mibCounters.h24Performance.ifOutDropLevelExceeded

       64 bit unsigned wrappable counter."
   ::= {pr1645v2TTmplPerfMCH24PEntry 352321536}

pr1645v2TTmplPerfMCH24POutDropNoArp OBJECT-TYPE
   SYNTAX      Counter64
   MAX-ACCESS  read-only
   STATUS      current
   DESCRIPTION
      "Path: tunnels.performance.l2tpTunnels.mibCounters.h24Performance.ifOutDiscardsNoArp

       64 bit unsigned wrappable counter."
   ::= {pr1645v2TTmplPerfMCH24PEntry 369098752}

pr1645v2TTmplPerfMCH24POutDropFilter OBJECT-TYPE
   SYNTAX      Counter64
   MAX-ACCESS  read-only
   STATUS      current
   DESCRIPTION
      "Path: tunnels.performance.l2tpTunnels.mibCounters.h24Performance.ifOutDiscardsFilter

       64 bit unsigned wrappable counter."
   ::= {pr1645v2TTmplPerfMCH24PEntry 402653184}

pr1645v2TTmplPerfMCH24PIfOutBandwidth OBJECT-TYPE
   SYNTAX      Integer32
   MAX-ACCESS  read-only
   STATUS      current
   DESCRIPTION
      "Path: tunnels.performance.l2tpTunnels.mibCounters.h24Performance.ifOutBandwidth

       unit name = bps
       formula = 8 * ; 8 /"
   ::= {pr1645v2TTmplPerfMCH24PEntry 285212672}

pr1645v2TTmplPerfMCH24PIfErrSec OBJECT-TYPE
   SYNTAX      Counter32
   MAX-ACCESS  read-only
   STATUS      current
   DESCRIPTION
      "Path: tunnels.performance.l2tpTunnels.mibCounters.h24Performance.ifErrSec

       32 bit unsigned wrappable counter."
   ::= {pr1645v2TTmplPerfMCH24PEntry 251658240}

pr1645v2TTmplPerfMCD7P OBJECT-TYPE
   SYNTAX      SEQUENCE OF Pr1645v2TTmplPerfMCD7PEntry
   MAX-ACCESS  not-accessible
   STATUS      current
   DESCRIPTION
      ""
   ::= {pr1645v2TTmplPerf 41680896}

pr1645v2TTmplPerfMCD7PEntry OBJECT-TYPE
   SYNTAX      Pr1645v2TTmplPerfMCD7PEntry
   MAX-ACCESS  not-accessible
   STATUS      current
   DESCRIPTION
      ""
   INDEX      { pr1645v2TTmplPerfTableIx,
                pr1645v2TTmplPerfMCD7PTableIx }
   ::= {pr1645v2TTmplPerfMCD7P 1}

Pr1645v2TTmplPerfMCD7PEntry ::=
   SEQUENCE
      {
      pr1645v2TTmplPerfMCD7PTableIx
         TableIndex,
      pr1645v2TTmplPerfMCD7PSysUpTime
         TimeTicks,
      pr1645v2TTmplPerfMCD7PIfUpTime
         TimeTicks,
      pr1645v2TTmplPerfMCD7PIfStatChanges
         Counter32,
      pr1645v2TTmplPerfMCD7PIfInOctets
         Counter64,
      pr1645v2TTmplPerfMCD7PIfInUCPkts
         Counter64,
      pr1645v2TTmplPerfMCD7PIfInNUCPkts
         Counter64,
      pr1645v2TTmplPerfMCD7PIfInBCPkts
         Counter64,
      pr1645v2TTmplPerfMCD7PIfInMCPkts
         Counter64,
      pr1645v2TTmplPerfMCD7PIfInDiscards
         Counter64,
      pr1645v2TTmplPerfMCD7PIfInErrors
         Counter64,
      pr1645v2TTmplPerfMCD7PIfInUnkwn
         Counter64,
      pr1645v2TTmplPerfMCD7PInDropEx
         Counter64,
      pr1645v2TTmplPerfMCD7PInDropNoMac
         Counter64,
      pr1645v2TTmplPerfMCD7PInDropNUCast
         Counter64,
      pr1645v2TTmplPerfMCD7PInDropFilter
         Counter64,
      pr1645v2TTmplPerfMCD7PIfInBandwidth
         Integer32,
      pr1645v2TTmplPerfMCD7PIfOutOctets
         Counter64,
      pr1645v2TTmplPerfMCD7PIfOutUCPkts
         Counter64,
      pr1645v2TTmplPerfMCD7PIfOutNUCPkts
         Counter64,
      pr1645v2TTmplPerfMCD7PIfOutBCPkts
         Counter64,
      pr1645v2TTmplPerfMCD7PIfOutMCPkts
         Counter64,
      pr1645v2TTmplPerfMCD7PIfOutDiscards
         Counter64,
      pr1645v2TTmplPerfMCD7PIfOutErrors
         Counter64,
      pr1645v2TTmplPerfMCD7POutDropEx
         Counter64,
      pr1645v2TTmplPerfMCD7POutDropNoArp
         Counter64,
      pr1645v2TTmplPerfMCD7POutDropFilter
         Counter64,
      pr1645v2TTmplPerfMCD7PIfOutBandwidth
         Integer32,
      pr1645v2TTmplPerfMCD7PIfErrSec
         Counter32
      }

pr1645v2TTmplPerfMCD7PTableIx OBJECT-TYPE
   SYNTAX      TableIndex
   MAX-ACCESS  not-accessible
   STATUS      current
   DESCRIPTION
      ""
   ::= {pr1645v2TTmplPerfMCD7PEntry 11}

pr1645v2TTmplPerfMCD7PSysUpTime OBJECT-TYPE
   SYNTAX      TimeTicks
   MAX-ACCESS  read-only
   STATUS      current
   DESCRIPTION
      "Path: tunnels.performance.l2tpTunnels.mibCounters.d7Performance.sysUpTime

       Time in centi-second."
   ::= {pr1645v2TTmplPerfMCD7PEntry 16777216}

pr1645v2TTmplPerfMCD7PIfUpTime OBJECT-TYPE
   SYNTAX      TimeTicks
   MAX-ACCESS  read-only
   STATUS      current
   DESCRIPTION
      "Path: tunnels.performance.l2tpTunnels.mibCounters.d7Performance.ifUpTime

       Time in centi-second."
   ::= {pr1645v2TTmplPerfMCD7PEntry 33554432}

pr1645v2TTmplPerfMCD7PIfStatChanges OBJECT-TYPE
   SYNTAX      Counter32
   MAX-ACCESS  read-only
   STATUS      current
   DESCRIPTION
      "Path: tunnels.performance.l2tpTunnels.mibCounters.d7Performance.ifStatusChanges

       32 bit unsigned wrappable counter."
   ::= {pr1645v2TTmplPerfMCD7PEntry 50331648}

pr1645v2TTmplPerfMCD7PIfInOctets OBJECT-TYPE
   SYNTAX      Counter64
   MAX-ACCESS  read-only
   STATUS      current
   DESCRIPTION
      "Path: tunnels.performance.l2tpTunnels.mibCounters.d7Performance.ifInOctets

       64 bit unsigned wrappable counter."
   ::= {pr1645v2TTmplPerfMCD7PEntry 67108864}

pr1645v2TTmplPerfMCD7PIfInUCPkts OBJECT-TYPE
   SYNTAX      Counter64
   MAX-ACCESS  read-only
   STATUS      current
   DESCRIPTION
      "Path: tunnels.performance.l2tpTunnels.mibCounters.d7Performance.ifInUcastPkts

       64 bit unsigned wrappable counter."
   ::= {pr1645v2TTmplPerfMCD7PEntry 83886080}

pr1645v2TTmplPerfMCD7PIfInNUCPkts OBJECT-TYPE
   SYNTAX      Counter64
   MAX-ACCESS  read-only
   STATUS      current
   DESCRIPTION
      "Path: tunnels.performance.l2tpTunnels.mibCounters.d7Performance.ifInNUcastPkts

       64 bit unsigned wrappable counter."
   ::= {pr1645v2TTmplPerfMCD7PEntry 100663296}

pr1645v2TTmplPerfMCD7PIfInBCPkts OBJECT-TYPE
   SYNTAX      Counter64
   MAX-ACCESS  read-only
   STATUS      current
   DESCRIPTION
      "Path: tunnels.performance.l2tpTunnels.mibCounters.d7Performance.ifInBcastPkts

       64 bit unsigned wrappable counter."
   ::= {pr1645v2TTmplPerfMCD7PEntry 419430400}

pr1645v2TTmplPerfMCD7PIfInMCPkts OBJECT-TYPE
   SYNTAX      Counter64
   MAX-ACCESS  read-only
   STATUS      current
   DESCRIPTION
      "Path: tunnels.performance.l2tpTunnels.mibCounters.d7Performance.ifInMcastPkts

       64 bit unsigned wrappable counter."
   ::= {pr1645v2TTmplPerfMCD7PEntry 436207616}

pr1645v2TTmplPerfMCD7PIfInDiscards OBJECT-TYPE
   SYNTAX      Counter64
   MAX-ACCESS  read-only
   STATUS      current
   DESCRIPTION
      "Path: tunnels.performance.l2tpTunnels.mibCounters.d7Performance.ifInDiscards

       64 bit unsigned wrappable counter."
   ::= {pr1645v2TTmplPerfMCD7PEntry 117440512}

pr1645v2TTmplPerfMCD7PIfInErrors OBJECT-TYPE
   SYNTAX      Counter64
   MAX-ACCESS  read-only
   STATUS      current
   DESCRIPTION
      "Path: tunnels.performance.l2tpTunnels.mibCounters.d7Performance.ifInErrors

       64 bit unsigned wrappable counter."
   ::= {pr1645v2TTmplPerfMCD7PEntry 134217728}

pr1645v2TTmplPerfMCD7PIfInUnkwn OBJECT-TYPE
   SYNTAX      Counter64
   MAX-ACCESS  read-only
   STATUS      current
   DESCRIPTION
      "Path: tunnels.performance.l2tpTunnels.mibCounters.d7Performance.ifInUnknownProtos

       64 bit unsigned wrappable counter."
   ::= {pr1645v2TTmplPerfMCD7PEntry 150994944}

pr1645v2TTmplPerfMCD7PInDropEx OBJECT-TYPE
   SYNTAX      Counter64
   MAX-ACCESS  read-only
   STATUS      current
   DESCRIPTION
      "Path: tunnels.performance.l2tpTunnels.mibCounters.d7Performance.ifInDropLevelExceeded

       64 bit unsigned wrappable counter."
   ::= {pr1645v2TTmplPerfMCD7PEntry 335544320}

pr1645v2TTmplPerfMCD7PInDropNoMac OBJECT-TYPE
   SYNTAX      Counter64
   MAX-ACCESS  read-only
   STATUS      current
   DESCRIPTION
      "Path: tunnels.performance.l2tpTunnels.mibCounters.d7Performance.fInDiscardsNoMacFit

       64 bit unsigned wrappable counter."
   ::= {pr1645v2TTmplPerfMCD7PEntry 301989888}

pr1645v2TTmplPerfMCD7PInDropNUCast OBJECT-TYPE
   SYNTAX      Counter64
   MAX-ACCESS  read-only
   STATUS      current
   DESCRIPTION
      "Path: tunnels.performance.l2tpTunnels.mibCounters.d7Performance.fInDiscardsNUCast

       64 bit unsigned wrappable counter."
   ::= {pr1645v2TTmplPerfMCD7PEntry 318767104}

pr1645v2TTmplPerfMCD7PInDropFilter OBJECT-TYPE
   SYNTAX      Counter64
   MAX-ACCESS  read-only
   STATUS      current
   DESCRIPTION
      "Path: tunnels.performance.l2tpTunnels.mibCounters.d7Performance.fInDiscardsFilter

       64 bit unsigned wrappable counter."
   ::= {pr1645v2TTmplPerfMCD7PEntry 385875968}

pr1645v2TTmplPerfMCD7PIfInBandwidth OBJECT-TYPE
   SYNTAX      Integer32
   MAX-ACCESS  read-only
   STATUS      current
   DESCRIPTION
      "Path: tunnels.performance.l2tpTunnels.mibCounters.d7Performance.ifInBandwidth

       unit name = bps
       formula = 8 * ; 8 /"
   ::= {pr1645v2TTmplPerfMCD7PEntry 268435456}

pr1645v2TTmplPerfMCD7PIfOutOctets OBJECT-TYPE
   SYNTAX      Counter64
   MAX-ACCESS  read-only
   STATUS      current
   DESCRIPTION
      "Path: tunnels.performance.l2tpTunnels.mibCounters.d7Performance.ifOutOctets

       64 bit unsigned wrappable counter."
   ::= {pr1645v2TTmplPerfMCD7PEntry 167772160}

pr1645v2TTmplPerfMCD7PIfOutUCPkts OBJECT-TYPE
   SYNTAX      Counter64
   MAX-ACCESS  read-only
   STATUS      current
   DESCRIPTION
      "Path: tunnels.performance.l2tpTunnels.mibCounters.d7Performance.ifOutUcastPkts

       64 bit unsigned wrappable counter."
   ::= {pr1645v2TTmplPerfMCD7PEntry 184549376}

pr1645v2TTmplPerfMCD7PIfOutNUCPkts OBJECT-TYPE
   SYNTAX      Counter64
   MAX-ACCESS  read-only
   STATUS      current
   DESCRIPTION
      "Path: tunnels.performance.l2tpTunnels.mibCounters.d7Performance.ifOutNUcastPkts

       64 bit unsigned wrappable counter."
   ::= {pr1645v2TTmplPerfMCD7PEntry 201326592}

pr1645v2TTmplPerfMCD7PIfOutBCPkts OBJECT-TYPE
   SYNTAX      Counter64
   MAX-ACCESS  read-only
   STATUS      current
   DESCRIPTION
      "Path: tunnels.performance.l2tpTunnels.mibCounters.d7Performance.ifOutBcastPkts

       64 bit unsigned wrappable counter."
   ::= {pr1645v2TTmplPerfMCD7PEntry 452984832}

pr1645v2TTmplPerfMCD7PIfOutMCPkts OBJECT-TYPE
   SYNTAX      Counter64
   MAX-ACCESS  read-only
   STATUS      current
   DESCRIPTION
      "Path: tunnels.performance.l2tpTunnels.mibCounters.d7Performance.ifOutMcastPkts

       64 bit unsigned wrappable counter."
   ::= {pr1645v2TTmplPerfMCD7PEntry 469762048}

pr1645v2TTmplPerfMCD7PIfOutDiscards OBJECT-TYPE
   SYNTAX      Counter64
   MAX-ACCESS  read-only
   STATUS      current
   DESCRIPTION
      "Path: tunnels.performance.l2tpTunnels.mibCounters.d7Performance.ifOutDiscards

       64 bit unsigned wrappable counter."
   ::= {pr1645v2TTmplPerfMCD7PEntry 218103808}

pr1645v2TTmplPerfMCD7PIfOutErrors OBJECT-TYPE
   SYNTAX      Counter64
   MAX-ACCESS  read-only
   STATUS      current
   DESCRIPTION
      "Path: tunnels.performance.l2tpTunnels.mibCounters.d7Performance.ifOutErrors

       64 bit unsigned wrappable counter."
   ::= {pr1645v2TTmplPerfMCD7PEntry 234881024}

pr1645v2TTmplPerfMCD7POutDropEx OBJECT-TYPE
   SYNTAX      Counter64
   MAX-ACCESS  read-only
   STATUS      current
   DESCRIPTION
      "Path: tunnels.performance.l2tpTunnels.mibCounters.d7Performance.ifOutDropLevelExceeded

       64 bit unsigned wrappable counter."
   ::= {pr1645v2TTmplPerfMCD7PEntry 352321536}

pr1645v2TTmplPerfMCD7POutDropNoArp OBJECT-TYPE
   SYNTAX      Counter64
   MAX-ACCESS  read-only
   STATUS      current
   DESCRIPTION
      "Path: tunnels.performance.l2tpTunnels.mibCounters.d7Performance.ifOutDiscardsNoArp

       64 bit unsigned wrappable counter."
   ::= {pr1645v2TTmplPerfMCD7PEntry 369098752}

pr1645v2TTmplPerfMCD7POutDropFilter OBJECT-TYPE
   SYNTAX      Counter64
   MAX-ACCESS  read-only
   STATUS      current
   DESCRIPTION
      "Path: tunnels.performance.l2tpTunnels.mibCounters.d7Performance.ifOutDiscardsFilter

       64 bit unsigned wrappable counter."
   ::= {pr1645v2TTmplPerfMCD7PEntry 402653184}

pr1645v2TTmplPerfMCD7PIfOutBandwidth OBJECT-TYPE
   SYNTAX      Integer32
   MAX-ACCESS  read-only
   STATUS      current
   DESCRIPTION
      "Path: tunnels.performance.l2tpTunnels.mibCounters.d7Performance.ifOutBandwidth

       unit name = bps
       formula = 8 * ; 8 /"
   ::= {pr1645v2TTmplPerfMCD7PEntry 285212672}

pr1645v2TTmplPerfMCD7PIfErrSec OBJECT-TYPE
   SYNTAX      Counter32
   MAX-ACCESS  read-only
   STATUS      current
   DESCRIPTION
      "Path: tunnels.performance.l2tpTunnels.mibCounters.d7Performance.ifErrSec

       32 bit unsigned wrappable counter."
   ::= {pr1645v2TTmplPerfMCD7PEntry 251658240}

pr1645v2TTmplPerfInPQs OBJECT-TYPE
   SYNTAX      SEQUENCE OF Pr1645v2TTmplPerfInPQsEntry
   MAX-ACCESS  not-accessible
   STATUS      current
   DESCRIPTION
      ""
   ::= {pr1645v2TTmplPerf 100663296}

pr1645v2TTmplPerfInPQsEntry OBJECT-TYPE
   SYNTAX      Pr1645v2TTmplPerfInPQsEntry
   MAX-ACCESS  not-accessible
   STATUS      current
   DESCRIPTION
      ""
   INDEX      { pr1645v2TTmplPerfTableIx,
                pr1645v2TTmplPerfInPQsTableIx }
   ::= {pr1645v2TTmplPerfInPQs 1}

Pr1645v2TTmplPerfInPQsEntry ::=
   SEQUENCE
      {
      pr1645v2TTmplPerfInPQsTableIx
         TableIndex,
      pr1645v2TTmplPerfInPQsName
         INTEGER,
      pr1645v2TTmplPerfInPQsLength
         Integer32,
      pr1645v2TTmplPerfInPQsOctetLength
         Integer32,
      pr1645v2TTmplPerfInPQsRedLength
         Integer32,
      pr1645v2TTmplPerfInPQsPacketsTotal
         Counter64,
      pr1645v2TTmplPerfInPQsPacketsDirectTx
         Counter64,
      pr1645v2TTmplPerfInPQsPacketsQueued
         Counter64,
      pr1645v2TTmplPerfInPQsPacketsDropped
         Counter64,
      pr1645v2TTmplPerfInPQsPacketsRedDropped
         Counter64,
      pr1645v2TTmplPerfInPQsPacketsCirTx
         Counter64,
      pr1645v2TTmplPerfInPQsPacketsEirTx
         Counter64,
      pr1645v2TTmplPerfInPQsPacketsViolateTx
         Counter64,
      pr1645v2TTmplPerfInPQsOctetsTotal
         Counter64,
      pr1645v2TTmplPerfInPQsOctetsDirectTx
         Counter64,
      pr1645v2TTmplPerfInPQsOctetsQueued
         Counter64,
      pr1645v2TTmplPerfInPQsOctetsDropped
         Counter64,
      pr1645v2TTmplPerfInPQsOctetsRedDropped
         Counter64,
      pr1645v2TTmplPerfInPQsOctetsCirTx
         Counter64,
      pr1645v2TTmplPerfInPQsOctetsEirTx
         Counter64,
      pr1645v2TTmplPerfInPQsOctetsViolateTx
         Counter64,
      pr1645v2TTmplPerfInPQsOctetsBandwidth15sec
         Integer32,
      pr1645v2TTmplPerfInPQsOctetsBandwidth30sec
         Integer32,
      pr1645v2TTmplPerfInPQsOctetsBandwidth1min
         Integer32,
      pr1645v2TTmplPerfInPQsOctetsBandwidth2min
         Integer32,
      pr1645v2TTmplPerfInPQsOctetsBandwidth5min
         Integer32
      }

pr1645v2TTmplPerfInPQsTableIx OBJECT-TYPE
   SYNTAX      TableIndex
   MAX-ACCESS  not-accessible
   STATUS      current
   DESCRIPTION
      ""
   ::= {pr1645v2TTmplPerfInPQsEntry 11}

pr1645v2TTmplPerfInPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: tunnels.performance.l2tpTunnels.inPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2TTmplPerfInPQsEntry 16777216}

pr1645v2TTmplPerfInPQsLength OBJECT-TYPE
   SYNTAX      Integer32
   MAX-ACCESS  read-only
   STATUS      current
   DESCRIPTION
      "Path: tunnels.performance.l2tpTunnels.inPriorityQueues.length"
   ::= {pr1645v2TTmplPerfInPQsEntry 33554432}

pr1645v2TTmplPerfInPQsOctetLength OBJECT-TYPE
   SYNTAX      Integer32
   MAX-ACCESS  read-only
   STATUS      current
   DESCRIPTION
      "Path: tunnels.performance.l2tpTunnels.inPriorityQueues.octetLength"
   ::= {pr1645v2TTmplPerfInPQsEntry 150994944}

pr1645v2TTmplPerfInPQsRedLength OBJECT-TYPE
   SYNTAX      Integer32
   MAX-ACCESS  read-only
   STATUS      current
   DESCRIPTION
      "Path: tunnels.performance.l2tpTunnels.inPriorityQueues.redLength"
   ::= {pr1645v2TTmplPerfInPQsEntry 134217728}

pr1645v2TTmplPerfInPQsPacketsTotal OBJECT-TYPE
   SYNTAX      Counter64
   MAX-ACCESS  read-only
   STATUS      current
   DESCRIPTION
      "Path: tunnels.performance.l2tpTunnels.inPriorityQueues.packets.total

       64 bit unsigned wrappable counter."
   ::= {pr1645v2TTmplPerfInPQsEntry 50790400}

pr1645v2TTmplPerfInPQsPacketsDirectTx OBJECT-TYPE
   SYNTAX      Counter64
   MAX-ACCESS  read-only
   STATUS      current
   DESCRIPTION
      "Path: tunnels.performance.l2tpTunnels.inPriorityQueues.packets.directTx

       64 bit unsigned wrappable counter."
   ::= {pr1645v2TTmplPerfInPQsEntry 50397184}

pr1645v2TTmplPerfInPQsPacketsQueued OBJECT-TYPE
   SYNTAX      Counter64
   MAX-ACCESS  read-only
   STATUS      current
   DESCRIPTION
      "Path: tunnels.performance.l2tpTunnels.inPriorityQueues.packets.queued

       64 bit unsigned wrappable counter."
   ::= {pr1645v2TTmplPerfInPQsEntry 50462720}

pr1645v2TTmplPerfInPQsPacketsDropped OBJECT-TYPE
   SYNTAX      Counter64
   MAX-ACCESS  read-only
   STATUS      current
   DESCRIPTION
      "Path: tunnels.performance.l2tpTunnels.inPriorityQueues.packets.dropped

       64 bit unsigned wrappable counter."
   ::= {pr1645v2TTmplPerfInPQsEntry 50528256}

pr1645v2TTmplPerfInPQsPacketsRedDropped OBJECT-TYPE
   SYNTAX      Counter64
   MAX-ACCESS  read-only
   STATUS      current
   DESCRIPTION
      "Path: tunnels.performance.l2tpTunnels.inPriorityQueues.packets.redDropped

       64 bit unsigned wrappable counter."
   ::= {pr1645v2TTmplPerfInPQsEntry 50724864}

pr1645v2TTmplPerfInPQsPacketsCirTx OBJECT-TYPE
   SYNTAX      Counter64
   MAX-ACCESS  read-only
   STATUS      current
   DESCRIPTION
      "Path: tunnels.performance.l2tpTunnels.inPriorityQueues.packets.cirTx

       64 bit unsigned wrappable counter."
   ::= {pr1645v2TTmplPerfInPQsEntry 50593792}

pr1645v2TTmplPerfInPQsPacketsEirTx OBJECT-TYPE
   SYNTAX      Counter64
   MAX-ACCESS  read-only
   STATUS      current
   DESCRIPTION
      "Path: tunnels.performance.l2tpTunnels.inPriorityQueues.packets.eirTx

       64 bit unsigned wrappable counter."
   ::= {pr1645v2TTmplPerfInPQsEntry 50659328}

pr1645v2TTmplPerfInPQsPacketsViolateTx OBJECT-TYPE
   SYNTAX      Counter64
   MAX-ACCESS  read-only
   STATUS      current
   DESCRIPTION
      "Path: tunnels.performance.l2tpTunnels.inPriorityQueues.packets.violateTx

       64 bit unsigned wrappable counter."
   ::= {pr1645v2TTmplPerfInPQsEntry 50855936}

pr1645v2TTmplPerfInPQsOctetsTotal OBJECT-TYPE
   SYNTAX      Counter64
   MAX-ACCESS  read-only
   STATUS      current
   DESCRIPTION
      "Path: tunnels.performance.l2tpTunnels.inPriorityQueues.octets.total

       64 bit unsigned wrappable counter."
   ::= {pr1645v2TTmplPerfInPQsEntry 67567616}

pr1645v2TTmplPerfInPQsOctetsDirectTx OBJECT-TYPE
   SYNTAX      Counter64
   MAX-ACCESS  read-only
   STATUS      current
   DESCRIPTION
      "Path: tunnels.performance.l2tpTunnels.inPriorityQueues.octets.directTx

       64 bit unsigned wrappable counter."
   ::= {pr1645v2TTmplPerfInPQsEntry 67174400}

pr1645v2TTmplPerfInPQsOctetsQueued OBJECT-TYPE
   SYNTAX      Counter64
   MAX-ACCESS  read-only
   STATUS      current
   DESCRIPTION
      "Path: tunnels.performance.l2tpTunnels.inPriorityQueues.octets.queued

       64 bit unsigned wrappable counter."
   ::= {pr1645v2TTmplPerfInPQsEntry 67239936}

pr1645v2TTmplPerfInPQsOctetsDropped OBJECT-TYPE
   SYNTAX      Counter64
   MAX-ACCESS  read-only
   STATUS      current
   DESCRIPTION
      "Path: tunnels.performance.l2tpTunnels.inPriorityQueues.octets.dropped

       64 bit unsigned wrappable counter."
   ::= {pr1645v2TTmplPerfInPQsEntry 67305472}

pr1645v2TTmplPerfInPQsOctetsRedDropped OBJECT-TYPE
   SYNTAX      Counter64
   MAX-ACCESS  read-only
   STATUS      current
   DESCRIPTION
      "Path: tunnels.performance.l2tpTunnels.inPriorityQueues.octets.redDropped

       64 bit unsigned wrappable counter."
   ::= {pr1645v2TTmplPerfInPQsEntry 67502080}

pr1645v2TTmplPerfInPQsOctetsCirTx OBJECT-TYPE
   SYNTAX      Counter64
   MAX-ACCESS  read-only
   STATUS      current
   DESCRIPTION
      "Path: tunnels.performance.l2tpTunnels.inPriorityQueues.octets.cirTx

       64 bit unsigned wrappable counter."
   ::= {pr1645v2TTmplPerfInPQsEntry 67371008}

pr1645v2TTmplPerfInPQsOctetsEirTx OBJECT-TYPE
   SYNTAX      Counter64
   MAX-ACCESS  read-only
   STATUS      current
   DESCRIPTION
      "Path: tunnels.performance.l2tpTunnels.inPriorityQueues.octets.eirTx

       64 bit unsigned wrappable counter."
   ::= {pr1645v2TTmplPerfInPQsEntry 67436544}

pr1645v2TTmplPerfInPQsOctetsViolateTx OBJECT-TYPE
   SYNTAX      Counter64
   MAX-ACCESS  read-only
   STATUS      current
   DESCRIPTION
      "Path: tunnels.performance.l2tpTunnels.inPriorityQueues.octets.violateTx

       64 bit unsigned wrappable counter."
   ::= {pr1645v2TTmplPerfInPQsEntry 67633152}

pr1645v2TTmplPerfInPQsOctetsBandwidth15sec OBJECT-TYPE
   SYNTAX      Integer32
   MAX-ACCESS  read-only
   STATUS      current
   DESCRIPTION
      "Path: tunnels.performance.l2tpTunnels.inPriorityQueues.octets.bandwidth.15sec

       unit name = bps
       formula = 8 * ; 8 /"
   ::= {pr1645v2TTmplPerfInPQsEntry 70386944}

pr1645v2TTmplPerfInPQsOctetsBandwidth30sec OBJECT-TYPE
   SYNTAX      Integer32
   MAX-ACCESS  read-only
   STATUS      current
   DESCRIPTION
      "Path: tunnels.performance.l2tpTunnels.inPriorityQueues.octets.bandwidth.30sec

       unit name = bps
       formula = 8 * ; 8 /"
   ::= {pr1645v2TTmplPerfInPQsEntry 70388224}

pr1645v2TTmplPerfInPQsOctetsBandwidth1min OBJECT-TYPE
   SYNTAX      Integer32
   MAX-ACCESS  read-only
   STATUS      current
   DESCRIPTION
      "Path: tunnels.performance.l2tpTunnels.inPriorityQueues.octets.bandwidth.1min

       unit name = bps
       formula = 8 * ; 8 /"
   ::= {pr1645v2TTmplPerfInPQsEntry 70390784}

pr1645v2TTmplPerfInPQsOctetsBandwidth2min OBJECT-TYPE
   SYNTAX      Integer32
   MAX-ACCESS  read-only
   STATUS      current
   DESCRIPTION
      "Path: tunnels.performance.l2tpTunnels.inPriorityQueues.octets.bandwidth.2min

       unit name = bps
       formula = 8 * ; 8 /"
   ::= {pr1645v2TTmplPerfInPQsEntry 70395904}

pr1645v2TTmplPerfInPQsOctetsBandwidth5min OBJECT-TYPE
   SYNTAX      Integer32
   MAX-ACCESS  read-only
   STATUS      current
   DESCRIPTION
      "Path: tunnels.performance.l2tpTunnels.inPriorityQueues.octets.bandwidth.5min

       unit name = bps
       formula = 8 * ; 8 /"
   ::= {pr1645v2TTmplPerfInPQsEntry 70411264}

pr1645v2TTmplPerfInPQsH2Performance OBJECT-TYPE
   SYNTAX      SEQUENCE OF Pr1645v2TTmplPerfInPQsH2PerformanceEntry
   MAX-ACCESS  not-accessible
   STATUS      current
   DESCRIPTION
      ""
   ::= {pr1645v2TTmplPerf 100990976}

pr1645v2TTmplPerfInPQsH2PerformanceEntry OBJECT-TYPE
   SYNTAX      Pr1645v2TTmplPerfInPQsH2PerformanceEntry
   MAX-ACCESS  not-accessible
   STATUS      current
   DESCRIPTION
      ""
   INDEX      { pr1645v2TTmplPerfTableIx,
                pr1645v2TTmplPerfInPQsTableIx,
                pr1645v2TTmplPerfInPQsH2PerformanceTableIx }
   ::= {pr1645v2TTmplPerfInPQsH2Performance 1}

Pr1645v2TTmplPerfInPQsH2PerformanceEntry ::=
   SEQUENCE
      {
      pr1645v2TTmplPerfInPQsH2PerformanceTableIx
         TableIndex,
      pr1645v2TTmplPerfInPQsH2PerformanceSysUpTime
         TimeTicks,
      pr1645v2TTmplPerfInPQsH2PerformanceTotPkts
         Counter64,
      pr1645v2TTmplPerfInPQsH2PerformanceDirTxPkts
         Counter64,
      pr1645v2TTmplPerfInPQsH2PerformanceQdPkts
         Counter64,
      pr1645v2TTmplPerfInPQsH2PerformanceDropPkts
         Counter64,
      pr1645v2TTmplPerfInPQsH2PerformanceRDropPkts
         Counter64,
      pr1645v2TTmplPerfInPQsH2PerformanceCirTxPkts
         Counter64,
      pr1645v2TTmplPerfInPQsH2PerformanceEirTxPkts
         Counter64,
      pr1645v2TTmplPerfInPQsH2PerformanceViolTxPkts
         Counter64,
      pr1645v2TTmplPerfInPQsH2PerformanceTotOcts
         Counter64,
      pr1645v2TTmplPerfInPQsH2PerformanceDirTxOcts
         Counter64,
      pr1645v2TTmplPerfInPQsH2PerformanceQdOcts
         Counter64,
      pr1645v2TTmplPerfInPQsH2PerformanceDropOcts
         Counter64,
      pr1645v2TTmplPerfInPQsH2PerformanceRDropOcts
         Counter64,
      pr1645v2TTmplPerfInPQsH2PerformanceCirTxOcts
         Counter64,
      pr1645v2TTmplPerfInPQsH2PerformanceEirTxOcts
         Counter64,
      pr1645v2TTmplPerfInPQsH2PerformanceViolTxOcts
         Counter64,
      pr1645v2TTmplPerfInPQsH2PerformanceBandwidth
         Integer32
      }

pr1645v2TTmplPerfInPQsH2PerformanceTableIx OBJECT-TYPE
   SYNTAX      TableIndex
   MAX-ACCESS  not-accessible
   STATUS      current
   DESCRIPTION
      ""
   ::= {pr1645v2TTmplPerfInPQsH2PerformanceEntry 11}

pr1645v2TTmplPerfInPQsH2PerformanceSysUpTime OBJECT-TYPE
   SYNTAX      TimeTicks
   MAX-ACCESS  read-only
   STATUS      current
   DESCRIPTION
      "Path: tunnels.performance.l2tpTunnels.inPriorityQueues.h2Performance.sysUpTime

       Time in centi-second."
   ::= {pr1645v2TTmplPerfInPQsH2PerformanceEntry 16777216}

pr1645v2TTmplPerfInPQsH2PerformanceTotPkts OBJECT-TYPE
   SYNTAX      Counter64
   MAX-ACCESS  read-only
   STATUS      current
   DESCRIPTION
      "Path: tunnels.performance.l2tpTunnels.inPriorityQueues.h2Performance.totalPkts

       64 bit unsigned wrappable counter."
   ::= {pr1645v2TTmplPerfInPQsH2PerformanceEntry 234881024}

pr1645v2TTmplPerfInPQsH2PerformanceDirTxPkts OBJECT-TYPE
   SYNTAX      Counter64
   MAX-ACCESS  read-only
   STATUS      current
   DESCRIPTION
      "Path: tunnels.performance.l2tpTunnels.inPriorityQueues.h2Performance.directTxPkts

       64 bit unsigned wrappable counter."
   ::= {pr1645v2TTmplPerfInPQsH2PerformanceEntry 33554432}

pr1645v2TTmplPerfInPQsH2PerformanceQdPkts OBJECT-TYPE
   SYNTAX      Counter64
   MAX-ACCESS  read-only
   STATUS      current
   DESCRIPTION
      "Path: tunnels.performance.l2tpTunnels.inPriorityQueues.h2Performance.queuedPkts

       64 bit unsigned wrappable counter."
   ::= {pr1645v2TTmplPerfInPQsH2PerformanceEntry 50331648}

pr1645v2TTmplPerfInPQsH2PerformanceDropPkts OBJECT-TYPE
   SYNTAX      Counter64
   MAX-ACCESS  read-only
   STATUS      current
   DESCRIPTION
      "Path: tunnels.performance.l2tpTunnels.inPriorityQueues.h2Performance.droppedPkts

       64 bit unsigned wrappable counter."
   ::= {pr1645v2TTmplPerfInPQsH2PerformanceEntry 67108864}

pr1645v2TTmplPerfInPQsH2PerformanceRDropPkts OBJECT-TYPE
   SYNTAX      Counter64
   MAX-ACCESS  read-only
   STATUS      current
   DESCRIPTION
      "Path: tunnels.performance.l2tpTunnels.inPriorityQueues.h2Performance.redDroppedPkts

       64 bit unsigned wrappable counter."
   ::= {pr1645v2TTmplPerfInPQsH2PerformanceEntry 201326592}

pr1645v2TTmplPerfInPQsH2PerformanceCirTxPkts OBJECT-TYPE
   SYNTAX      Counter64
   MAX-ACCESS  read-only
   STATUS      current
   DESCRIPTION
      "Path: tunnels.performance.l2tpTunnels.inPriorityQueues.h2Performance.cirTxPkts

       64 bit unsigned wrappable counter."
   ::= {pr1645v2TTmplPerfInPQsH2PerformanceEntry 83886080}

pr1645v2TTmplPerfInPQsH2PerformanceEirTxPkts OBJECT-TYPE
   SYNTAX      Counter64
   MAX-ACCESS  read-only
   STATUS      current
   DESCRIPTION
      "Path: tunnels.performance.l2tpTunnels.inPriorityQueues.h2Performance.eirTxPkts

       64 bit unsigned wrappable counter."
   ::= {pr1645v2TTmplPerfInPQsH2PerformanceEntry 100663296}

pr1645v2TTmplPerfInPQsH2PerformanceViolTxPkts OBJECT-TYPE
   SYNTAX      Counter64
   MAX-ACCESS  read-only
   STATUS      current
   DESCRIPTION
      "Path: tunnels.performance.l2tpTunnels.inPriorityQueues.h2Performance.violateTxPkts

       64 bit unsigned wrappable counter."
   ::= {pr1645v2TTmplPerfInPQsH2PerformanceEntry 301989888}

pr1645v2TTmplPerfInPQsH2PerformanceTotOcts OBJECT-TYPE
   SYNTAX      Counter64
   MAX-ACCESS  read-only
   STATUS      current
   DESCRIPTION
      "Path: tunnels.performance.l2tpTunnels.inPriorityQueues.h2Performance.totalOctets

       64 bit unsigned wrappable counter."
   ::= {pr1645v2TTmplPerfInPQsH2PerformanceEntry 251658240}

pr1645v2TTmplPerfInPQsH2PerformanceDirTxOcts OBJECT-TYPE
   SYNTAX      Counter64
   MAX-ACCESS  read-only
   STATUS      current
   DESCRIPTION
      "Path: tunnels.performance.l2tpTunnels.inPriorityQueues.h2Performance.directTxOctets

       64 bit unsigned wrappable counter."
   ::= {pr1645v2TTmplPerfInPQsH2PerformanceEntry 117440512}

pr1645v2TTmplPerfInPQsH2PerformanceQdOcts OBJECT-TYPE
   SYNTAX      Counter64
   MAX-ACCESS  read-only
   STATUS      current
   DESCRIPTION
      "Path: tunnels.performance.l2tpTunnels.inPriorityQueues.h2Performance.queuedOctets

       64 bit unsigned wrappable counter."
   ::= {pr1645v2TTmplPerfInPQsH2PerformanceEntry 134217728}

pr1645v2TTmplPerfInPQsH2PerformanceDropOcts OBJECT-TYPE
   SYNTAX      Counter64
   MAX-ACCESS  read-only
   STATUS      current
   DESCRIPTION
      "Path: tunnels.performance.l2tpTunnels.inPriorityQueues.h2Performance.droppedOctets

       64 bit unsigned wrappable counter."
   ::= {pr1645v2TTmplPerfInPQsH2PerformanceEntry 150994944}

pr1645v2TTmplPerfInPQsH2PerformanceRDropOcts OBJECT-TYPE
   SYNTAX      Counter64
   MAX-ACCESS  read-only
   STATUS      current
   DESCRIPTION
      "Path: tunnels.performance.l2tpTunnels.inPriorityQueues.h2Performance.redDroppedOctets

       64 bit unsigned wrappable counter."
   ::= {pr1645v2TTmplPerfInPQsH2PerformanceEntry 218103808}

pr1645v2TTmplPerfInPQsH2PerformanceCirTxOcts OBJECT-TYPE
   SYNTAX      Counter64
   MAX-ACCESS  read-only
   STATUS      current
   DESCRIPTION
      "Path: tunnels.performance.l2tpTunnels.inPriorityQueues.h2Performance.cirTxOctets

       64 bit unsigned wrappable counter."
   ::= {pr1645v2TTmplPerfInPQsH2PerformanceEntry 167772160}

pr1645v2TTmplPerfInPQsH2PerformanceEirTxOcts OBJECT-TYPE
   SYNTAX      Counter64
   MAX-ACCESS  read-only
   STATUS      current
   DESCRIPTION
      "Path: tunnels.performance.l2tpTunnels.inPriorityQueues.h2Performance.eirTxOctets

       64 bit unsigned wrappable counter."
   ::= {pr1645v2TTmplPerfInPQsH2PerformanceEntry 184549376}

pr1645v2TTmplPerfInPQsH2PerformanceViolTxOcts OBJECT-TYPE
   SYNTAX      Counter64
   MAX-ACCESS  read-only
   STATUS      current
   DESCRIPTION
      "Path: tunnels.performance.l2tpTunnels.inPriorityQueues.h2Performance.violateTxOctets

       64 bit unsigned wrappable counter."
   ::= {pr1645v2TTmplPerfInPQsH2PerformanceEntry 318767104}

pr1645v2TTmplPerfInPQsH2PerformanceBandwidth OBJECT-TYPE
   SYNTAX      Integer32
   MAX-ACCESS  read-only
   STATUS      current
   DESCRIPTION
      "Path: tunnels.performance.l2tpTunnels.inPriorityQueues.h2Performance.bandwidth

       unit name = bps
       formula = 8 * ; 8 /"
   ::= {pr1645v2TTmplPerfInPQsH2PerformanceEntry 268435456}

pr1645v2TTmplPerfInPQsH24Performance OBJECT-TYPE
   SYNTAX      SEQUENCE OF Pr1645v2TTmplPerfInPQsH24PerformanceEntry
   MAX-ACCESS  not-accessible
   STATUS      current
   DESCRIPTION
      ""
   ::= {pr1645v2TTmplPerf 101056512}

pr1645v2TTmplPerfInPQsH24PerformanceEntry OBJECT-TYPE
   SYNTAX      Pr1645v2TTmplPerfInPQsH24PerformanceEntry
   MAX-ACCESS  not-accessible
   STATUS      current
   DESCRIPTION
      ""
   INDEX      { pr1645v2TTmplPerfTableIx,
                pr1645v2TTmplPerfInPQsTableIx,
                pr1645v2TTmplPerfInPQsH24PerformanceTableIx }
   ::= {pr1645v2TTmplPerfInPQsH24Performance 1}

Pr1645v2TTmplPerfInPQsH24PerformanceEntry ::=
   SEQUENCE
      {
      pr1645v2TTmplPerfInPQsH24PerformanceTableIx
         TableIndex,
      pr1645v2TTmplPerfInPQsH24PerformanceSysUpTime
         TimeTicks,
      pr1645v2TTmplPerfInPQsH24PerformanceTotPkts
         Counter64,
      pr1645v2TTmplPerfInPQsH24PerformanceDirTxPkts
         Counter64,
      pr1645v2TTmplPerfInPQsH24PerformanceQdPkts
         Counter64,
      pr1645v2TTmplPerfInPQsH24PerformanceDropPkts
         Counter64,
      pr1645v2TTmplPerfInPQsH24PerformanceRDropPkts
         Counter64,
      pr1645v2TTmplPerfInPQsH24PerformanceCirTxPkts
         Counter64,
      pr1645v2TTmplPerfInPQsH24PerformanceEirTxPkts
         Counter64,
      pr1645v2TTmplPerfInPQsH24PerformanceViolTxPkts
         Counter64,
      pr1645v2TTmplPerfInPQsH24PerformanceTotOcts
         Counter64,
      pr1645v2TTmplPerfInPQsH24PerformanceDirTxOcts
         Counter64,
      pr1645v2TTmplPerfInPQsH24PerformanceQdOcts
         Counter64,
      pr1645v2TTmplPerfInPQsH24PerformanceDropOcts
         Counter64,
      pr1645v2TTmplPerfInPQsH24PerformanceRDropOcts
         Counter64,
      pr1645v2TTmplPerfInPQsH24PerformanceCirTxOcts
         Counter64,
      pr1645v2TTmplPerfInPQsH24PerformanceEirTxOcts
         Counter64,
      pr1645v2TTmplPerfInPQsH24PerformanceViolTxOcts
         Counter64,
      pr1645v2TTmplPerfInPQsH24PerformanceBandwidth
         Integer32
      }

pr1645v2TTmplPerfInPQsH24PerformanceTableIx OBJECT-TYPE
   SYNTAX      TableIndex
   MAX-ACCESS  not-accessible
   STATUS      current
   DESCRIPTION
      ""
   ::= {pr1645v2TTmplPerfInPQsH24PerformanceEntry 11}

pr1645v2TTmplPerfInPQsH24PerformanceSysUpTime OBJECT-TYPE
   SYNTAX      TimeTicks
   MAX-ACCESS  read-only
   STATUS      current
   DESCRIPTION
      "Path: tunnels.performance.l2tpTunnels.inPriorityQueues.h24Performance.sysUpTime

       Time in centi-second."
   ::= {pr1645v2TTmplPerfInPQsH24PerformanceEntry 16777216}

pr1645v2TTmplPerfInPQsH24PerformanceTotPkts OBJECT-TYPE
   SYNTAX      Counter64
   MAX-ACCESS  read-only
   STATUS      current
   DESCRIPTION
      "Path: tunnels.performance.l2tpTunnels.inPriorityQueues.h24Performance.totalPkts

       64 bit unsigned wrappable counter."
   ::= {pr1645v2TTmplPerfInPQsH24PerformanceEntry 234881024}

pr1645v2TTmplPerfInPQsH24PerformanceDirTxPkts OBJECT-TYPE
   SYNTAX      Counter64
   MAX-ACCESS  read-only
   STATUS      current
   DESCRIPTION
      "Path: tunnels.performance.l2tpTunnels.inPriorityQueues.h24Performance.directTxPkts

       64 bit unsigned wrappable counter."
   ::= {pr1645v2TTmplPerfInPQsH24PerformanceEntry 33554432}

pr1645v2TTmplPerfInPQsH24PerformanceQdPkts OBJECT-TYPE
   SYNTAX      Counter64
   MAX-ACCESS  read-only
   STATUS      current
   DESCRIPTION
      "Path: tunnels.performance.l2tpTunnels.inPriorityQueues.h24Performance.queuedPkts

       64 bit unsigned wrappable counter."
   ::= {pr1645v2TTmplPerfInPQsH24PerformanceEntry 50331648}

pr1645v2TTmplPerfInPQsH24PerformanceDropPkts OBJECT-TYPE
   SYNTAX      Counter64
   MAX-ACCESS  read-only
   STATUS      current
   DESCRIPTION
      "Path: tunnels.performance.l2tpTunnels.inPriorityQueues.h24Performance.droppedPkts

       64 bit unsigned wrappable counter."
   ::= {pr1645v2TTmplPerfInPQsH24PerformanceEntry 67108864}

pr1645v2TTmplPerfInPQsH24PerformanceRDropPkts OBJECT-TYPE
   SYNTAX      Counter64
   MAX-ACCESS  read-only
   STATUS      current
   DESCRIPTION
      "Path: tunnels.performance.l2tpTunnels.inPriorityQueues.h24Performance.redDroppedPkts

       64 bit unsigned wrappable counter."
   ::= {pr1645v2TTmplPerfInPQsH24PerformanceEntry 201326592}

pr1645v2TTmplPerfInPQsH24PerformanceCirTxPkts OBJECT-TYPE
   SYNTAX      Counter64
   MAX-ACCESS  read-only
   STATUS      current
   DESCRIPTION
      "Path: tunnels.performance.l2tpTunnels.inPriorityQueues.h24Performance.cirTxPkts

       64 bit unsigned wrappable counter."
   ::= {pr1645v2TTmplPerfInPQsH24PerformanceEntry 83886080}

pr1645v2TTmplPerfInPQsH24PerformanceEirTxPkts OBJECT-TYPE
   SYNTAX      Counter64
   MAX-ACCESS  read-only
   STATUS      current
   DESCRIPTION
      "Path: tunnels.performance.l2tpTunnels.inPriorityQueues.h24Performance.eirTxPkts

       64 bit unsigned wrappable counter."
   ::= {pr1645v2TTmplPerfInPQsH24PerformanceEntry 100663296}

pr1645v2TTmplPerfInPQsH24PerformanceViolTxPkts OBJECT-TYPE
   SYNTAX      Counter64
   MAX-ACCESS  read-only
   STATUS      current
   DESCRIPTION
      "Path: tunnels.performance.l2tpTunnels.inPriorityQueues.h24Performance.violateTxPkts

       64 bit unsigned wrappable counter."
   ::= {pr1645v2TTmplPerfInPQsH24PerformanceEntry 301989888}

pr1645v2TTmplPerfInPQsH24PerformanceTotOcts OBJECT-TYPE
   SYNTAX      Counter64
   MAX-ACCESS  read-only
   STATUS      current
   DESCRIPTION
      "Path: tunnels.performance.l2tpTunnels.inPriorityQueues.h24Performance.totalOctets

       64 bit unsigned wrappable counter."
   ::= {pr1645v2TTmplPerfInPQsH24PerformanceEntry 251658240}

pr1645v2TTmplPerfInPQsH24PerformanceDirTxOcts OBJECT-TYPE
   SYNTAX      Counter64
   MAX-ACCESS  read-only
   STATUS      current
   DESCRIPTION
      "Path: tunnels.performance.l2tpTunnels.inPriorityQueues.h24Performance.directTxOctets

       64 bit unsigned wrappable counter."
   ::= {pr1645v2TTmplPerfInPQsH24PerformanceEntry 117440512}

pr1645v2TTmplPerfInPQsH24PerformanceQdOcts OBJECT-TYPE
   SYNTAX      Counter64
   MAX-ACCESS  read-only
   STATUS      current
   DESCRIPTION
      "Path: tunnels.performance.l2tpTunnels.inPriorityQueues.h24Performance.queuedOctets

       64 bit unsigned wrappable counter."
   ::= {pr1645v2TTmplPerfInPQsH24PerformanceEntry 134217728}

pr1645v2TTmplPerfInPQsH24PerformanceDropOcts OBJECT-TYPE
   SYNTAX      Counter64
   MAX-ACCESS  read-only
   STATUS      current
   DESCRIPTION
      "Path: tunnels.performance.l2tpTunnels.inPriorityQueues.h24Performance.droppedOctets

       64 bit unsigned wrappable counter."
   ::= {pr1645v2TTmplPerfInPQsH24PerformanceEntry 150994944}

pr1645v2TTmplPerfInPQsH24PerformanceRDropOcts OBJECT-TYPE
   SYNTAX      Counter64
   MAX-ACCESS  read-only
   STATUS      current
   DESCRIPTION
      "Path: tunnels.performance.l2tpTunnels.inPriorityQueues.h24Performance.redDroppedOctets

       64 bit unsigned wrappable counter."
   ::= {pr1645v2TTmplPerfInPQsH24PerformanceEntry 218103808}

pr1645v2TTmplPerfInPQsH24PerformanceCirTxOcts OBJECT-TYPE
   SYNTAX      Counter64
   MAX-ACCESS  read-only
   STATUS      current
   DESCRIPTION
      "Path: tunnels.performance.l2tpTunnels.inPriorityQueues.h24Performance.cirTxOctets

       64 bit unsigned wrappable counter."
   ::= {pr1645v2TTmplPerfInPQsH24PerformanceEntry 167772160}

pr1645v2TTmplPerfInPQsH24PerformanceEirTxOcts OBJECT-TYPE
   SYNTAX      Counter64
   MAX-ACCESS  read-only
   STATUS      current
   DESCRIPTION
      "Path: tunnels.performance.l2tpTunnels.inPriorityQueues.h24Performance.eirTxOctets

       64 bit unsigned wrappable counter."
   ::= {pr1645v2TTmplPerfInPQsH24PerformanceEntry 184549376}

pr1645v2TTmplPerfInPQsH24PerformanceViolTxOcts OBJECT-TYPE
   SYNTAX      Counter64
   MAX-ACCESS  read-only
   STATUS      current
   DESCRIPTION
      "Path: tunnels.performance.l2tpTunnels.inPriorityQueues.h24Performance.violateTxOctets

       64 bit unsigned wrappable counter."
   ::= {pr1645v2TTmplPerfInPQsH24PerformanceEntry 318767104}

pr1645v2TTmplPerfInPQsH24PerformanceBandwidth OBJECT-TYPE
   SYNTAX      Integer32
   MAX-ACCESS  read-only
   STATUS      current
   DESCRIPTION
      "Path: tunnels.performance.l2tpTunnels.inPriorityQueues.h24Performance.bandwidth

       unit name = bps
       formula = 8 * ; 8 /"
   ::= {pr1645v2TTmplPerfInPQsH24PerformanceEntry 268435456}

pr1645v2TTmplPerfInPQsD7Performance OBJECT-TYPE
   SYNTAX      SEQUENCE OF Pr1645v2TTmplPerfInPQsD7PerformanceEntry
   MAX-ACCESS  not-accessible
   STATUS      current
   DESCRIPTION
      ""
   ::= {pr1645v2TTmplPerf 101122048}

pr1645v2TTmplPerfInPQsD7PerformanceEntry OBJECT-TYPE
   SYNTAX      Pr1645v2TTmplPerfInPQsD7PerformanceEntry
   MAX-ACCESS  not-accessible
   STATUS      current
   DESCRIPTION
      ""
   INDEX      { pr1645v2TTmplPerfTableIx,
                pr1645v2TTmplPerfInPQsTableIx,
                pr1645v2TTmplPerfInPQsD7PerformanceTableIx }
   ::= {pr1645v2TTmplPerfInPQsD7Performance 1}

Pr1645v2TTmplPerfInPQsD7PerformanceEntry ::=
   SEQUENCE
      {
      pr1645v2TTmplPerfInPQsD7PerformanceTableIx
         TableIndex,
      pr1645v2TTmplPerfInPQsD7PerformanceSysUpTime
         TimeTicks,
      pr1645v2TTmplPerfInPQsD7PerformanceTotPkts
         Counter64,
      pr1645v2TTmplPerfInPQsD7PerformanceDirTxPkts
         Counter64,
      pr1645v2TTmplPerfInPQsD7PerformanceQdPkts
         Counter64,
      pr1645v2TTmplPerfInPQsD7PerformanceDropPkts
         Counter64,
      pr1645v2TTmplPerfInPQsD7PerformanceRDropPkts
         Counter64,
      pr1645v2TTmplPerfInPQsD7PerformanceCirTxPkts
         Counter64,
      pr1645v2TTmplPerfInPQsD7PerformanceEirTxPkts
         Counter64,
      pr1645v2TTmplPerfInPQsD7PerformanceViolTxPkts
         Counter64,
      pr1645v2TTmplPerfInPQsD7PerformanceTotOcts
         Counter64,
      pr1645v2TTmplPerfInPQsD7PerformanceDirTxOcts
         Counter64,
      pr1645v2TTmplPerfInPQsD7PerformanceQdOcts
         Counter64,
      pr1645v2TTmplPerfInPQsD7PerformanceDropOcts
         Counter64,
      pr1645v2TTmplPerfInPQsD7PerformanceRDropOcts
         Counter64,
      pr1645v2TTmplPerfInPQsD7PerformanceCirTxOcts
         Counter64,
      pr1645v2TTmplPerfInPQsD7PerformanceEirTxOcts
         Counter64,
      pr1645v2TTmplPerfInPQsD7PerformanceViolTxOcts
         Counter64,
      pr1645v2TTmplPerfInPQsD7PerformanceBandwidth
         Integer32
      }

pr1645v2TTmplPerfInPQsD7PerformanceTableIx OBJECT-TYPE
   SYNTAX      TableIndex
   MAX-ACCESS  not-accessible
   STATUS      current
   DESCRIPTION
      ""
   ::= {pr1645v2TTmplPerfInPQsD7PerformanceEntry 11}

pr1645v2TTmplPerfInPQsD7PerformanceSysUpTime OBJECT-TYPE
   SYNTAX      TimeTicks
   MAX-ACCESS  read-only
   STATUS      current
   DESCRIPTION
      "Path: tunnels.performance.l2tpTunnels.inPriorityQueues.d7Performance.sysUpTime

       Time in centi-second."
   ::= {pr1645v2TTmplPerfInPQsD7PerformanceEntry 16777216}

pr1645v2TTmplPerfInPQsD7PerformanceTotPkts OBJECT-TYPE
   SYNTAX      Counter64
   MAX-ACCESS  read-only
   STATUS      current
   DESCRIPTION
      "Path: tunnels.performance.l2tpTunnels.inPriorityQueues.d7Performance.totalPkts

       64 bit unsigned wrappable counter."
   ::= {pr1645v2TTmplPerfInPQsD7PerformanceEntry 234881024}

pr1645v2TTmplPerfInPQsD7PerformanceDirTxPkts OBJECT-TYPE
   SYNTAX      Counter64
   MAX-ACCESS  read-only
   STATUS      current
   DESCRIPTION
      "Path: tunnels.performance.l2tpTunnels.inPriorityQueues.d7Performance.directTxPkts

       64 bit unsigned wrappable counter."
   ::= {pr1645v2TTmplPerfInPQsD7PerformanceEntry 33554432}

pr1645v2TTmplPerfInPQsD7PerformanceQdPkts OBJECT-TYPE
   SYNTAX      Counter64
   MAX-ACCESS  read-only
   STATUS      current
   DESCRIPTION
      "Path: tunnels.performance.l2tpTunnels.inPriorityQueues.d7Performance.queuedPkts

       64 bit unsigned wrappable counter."
   ::= {pr1645v2TTmplPerfInPQsD7PerformanceEntry 50331648}

pr1645v2TTmplPerfInPQsD7PerformanceDropPkts OBJECT-TYPE
   SYNTAX      Counter64
   MAX-ACCESS  read-only
   STATUS      current
   DESCRIPTION
      "Path: tunnels.performance.l2tpTunnels.inPriorityQueues.d7Performance.droppedPkts

       64 bit unsigned wrappable counter."
   ::= {pr1645v2TTmplPerfInPQsD7PerformanceEntry 67108864}

pr1645v2TTmplPerfInPQsD7PerformanceRDropPkts OBJECT-TYPE
   SYNTAX      Counter64
   MAX-ACCESS  read-only
   STATUS      current
   DESCRIPTION
      "Path: tunnels.performance.l2tpTunnels.inPriorityQueues.d7Performance.redDroppedPkts

       64 bit unsigned wrappable counter."
   ::= {pr1645v2TTmplPerfInPQsD7PerformanceEntry 201326592}

pr1645v2TTmplPerfInPQsD7PerformanceCirTxPkts OBJECT-TYPE
   SYNTAX      Counter64
   MAX-ACCESS  read-only
   STATUS      current
   DESCRIPTION
      "Path: tunnels.performance.l2tpTunnels.inPriorityQueues.d7Performance.cirTxPkts

       64 bit unsigned wrappable counter."
   ::= {pr1645v2TTmplPerfInPQsD7PerformanceEntry 83886080}

pr1645v2TTmplPerfInPQsD7PerformanceEirTxPkts OBJECT-TYPE
   SYNTAX      Counter64
   MAX-ACCESS  read-only
   STATUS      current
   DESCRIPTION
      "Path: tunnels.performance.l2tpTunnels.inPriorityQueues.d7Performance.eirTxPkts

       64 bit unsigned wrappable counter."
   ::= {pr1645v2TTmplPerfInPQsD7PerformanceEntry 100663296}

pr1645v2TTmplPerfInPQsD7PerformanceViolTxPkts OBJECT-TYPE
   SYNTAX      Counter64
   MAX-ACCESS  read-only
   STATUS      current
   DESCRIPTION
      "Path: tunnels.performance.l2tpTunnels.inPriorityQueues.d7Performance.violateTxPkts

       64 bit unsigned wrappable counter."
   ::= {pr1645v2TTmplPerfInPQsD7PerformanceEntry 301989888}

pr1645v2TTmplPerfInPQsD7PerformanceTotOcts OBJECT-TYPE
   SYNTAX      Counter64
   MAX-ACCESS  read-only
   STATUS      current
   DESCRIPTION
      "Path: tunnels.performance.l2tpTunnels.inPriorityQueues.d7Performance.totalOctets

       64 bit unsigned wrappable counter."
   ::= {pr1645v2TTmplPerfInPQsD7PerformanceEntry 251658240}

pr1645v2TTmplPerfInPQsD7PerformanceDirTxOcts OBJECT-TYPE
   SYNTAX      Counter64
   MAX-ACCESS  read-only
   STATUS      current
   DESCRIPTION
      "Path: tunnels.performance.l2tpTunnels.inPriorityQueues.d7Performance.directTxOctets

       64 bit unsigned wrappable counter."
   ::= {pr1645v2TTmplPerfInPQsD7PerformanceEntry 117440512}

pr1645v2TTmplPerfInPQsD7PerformanceQdOcts OBJECT-TYPE
   SYNTAX      Counter64
   MAX-ACCESS  read-only
   STATUS      current
   DESCRIPTION
      "Path: tunnels.performance.l2tpTunnels.inPriorityQueues.d7Performance.queuedOctets

       64 bit unsigned wrappable counter."
   ::= {pr1645v2TTmplPerfInPQsD7PerformanceEntry 134217728}

pr1645v2TTmplPerfInPQsD7PerformanceDropOcts OBJECT-TYPE
   SYNTAX      Counter64
   MAX-ACCESS  read-only
   STATUS      current
   DESCRIPTION
      "Path: tunnels.performance.l2tpTunnels.inPriorityQueues.d7Performance.droppedOctets

       64 bit unsigned wrappable counter."
   ::= {pr1645v2TTmplPerfInPQsD7PerformanceEntry 150994944}

pr1645v2TTmplPerfInPQsD7PerformanceRDropOcts OBJECT-TYPE
   SYNTAX      Counter64
   MAX-ACCESS  read-only
   STATUS      current
   DESCRIPTION
      "Path: tunnels.performance.l2tpTunnels.inPriorityQueues.d7Performance.redDroppedOctets

       64 bit unsigned wrappable counter."
   ::= {pr1645v2TTmplPerfInPQsD7PerformanceEntry 218103808}

pr1645v2TTmplPerfInPQsD7PerformanceCirTxOcts OBJECT-TYPE
   SYNTAX      Counter64
   MAX-ACCESS  read-only
   STATUS      current
   DESCRIPTION
      "Path: tunnels.performance.l2tpTunnels.inPriorityQueues.d7Performance.cirTxOctets

       64 bit unsigned wrappable counter."
   ::= {pr1645v2TTmplPerfInPQsD7PerformanceEntry 167772160}

pr1645v2TTmplPerfInPQsD7PerformanceEirTxOcts OBJECT-TYPE
   SYNTAX      Counter64
   MAX-ACCESS  read-only
   STATUS      current
   DESCRIPTION
      "Path: tunnels.performance.l2tpTunnels.inPriorityQueues.d7Performance.eirTxOctets

       64 bit unsigned wrappable counter."
   ::= {pr1645v2TTmplPerfInPQsD7PerformanceEntry 184549376}

pr1645v2TTmplPerfInPQsD7PerformanceViolTxOcts OBJECT-TYPE
   SYNTAX      Counter64
   MAX-ACCESS  read-only
   STATUS      current
   DESCRIPTION
      "Path: tunnels.performance.l2tpTunnels.inPriorityQueues.d7Performance.violateTxOctets

       64 bit unsigned wrappable counter."
   ::= {pr1645v2TTmplPerfInPQsD7PerformanceEntry 318767104}

pr1645v2TTmplPerfInPQsD7PerformanceBandwidth OBJECT-TYPE
   SYNTAX      Integer32
   MAX-ACCESS  read-only
   STATUS      current
   DESCRIPTION
      "Path: tunnels.performance.l2tpTunnels.inPriorityQueues.d7Performance.bandwidth

       unit name = bps
       formula = 8 * ; 8 /"
   ::= {pr1645v2TTmplPerfInPQsD7PerformanceEntry 268435456}

pr1645v2TTmplPerfOutPQs OBJECT-TYPE
   SYNTAX      SEQUENCE OF Pr1645v2TTmplPerfOutPQsEntry
   MAX-ACCESS  not-accessible
   STATUS      current
   DESCRIPTION
      ""
   ::= {pr1645v2TTmplPerf 83886080}

pr1645v2TTmplPerfOutPQsEntry OBJECT-TYPE
   SYNTAX      Pr1645v2TTmplPerfOutPQsEntry
   MAX-ACCESS  not-accessible
   STATUS      current
   DESCRIPTION
      ""
   INDEX      { pr1645v2TTmplPerfTableIx,
                pr1645v2TTmplPerfOutPQsTableIx }
   ::= {pr1645v2TTmplPerfOutPQs 1}

Pr1645v2TTmplPerfOutPQsEntry ::=
   SEQUENCE
      {
      pr1645v2TTmplPerfOutPQsTableIx
         TableIndex,
      pr1645v2TTmplPerfOutPQsName
         INTEGER,
      pr1645v2TTmplPerfOutPQsLength
         Integer32,
      pr1645v2TTmplPerfOutPQsOctetLength
         Integer32,
      pr1645v2TTmplPerfOutPQsRedLength
         Integer32,
      pr1645v2TTmplPerfOutPQsPacketsTotal
         Counter64,
      pr1645v2TTmplPerfOutPQsPacketsDirectTx
         Counter64,
      pr1645v2TTmplPerfOutPQsPacketsQueued
         Counter64,
      pr1645v2TTmplPerfOutPQsPacketsDropped
         Counter64,
      pr1645v2TTmplPerfOutPQsPacketsRedDropped
         Counter64,
      pr1645v2TTmplPerfOutPQsPacketsCirTx
         Counter64,
      pr1645v2TTmplPerfOutPQsPacketsEirTx
         Counter64,
      pr1645v2TTmplPerfOutPQsPacketsViolateTx
         Counter64,
      pr1645v2TTmplPerfOutPQsOctetsTotal
         Counter64,
      pr1645v2TTmplPerfOutPQsOctetsDirectTx
         Counter64,
      pr1645v2TTmplPerfOutPQsOctetsQueued
         Counter64,
      pr1645v2TTmplPerfOutPQsOctetsDropped
         Counter64,
      pr1645v2TTmplPerfOutPQsOctetsRedDropped
         Counter64,
      pr1645v2TTmplPerfOutPQsOctetsCirTx
         Counter64,
      pr1645v2TTmplPerfOutPQsOctetsEirTx
         Counter64,
      pr1645v2TTmplPerfOutPQsOctetsViolateTx
         Counter64,
      pr1645v2TTmplPerfOutPQsOctetsBandwidth15sec
         Integer32,
      pr1645v2TTmplPerfOutPQsOctetsBandwidth30sec
         Integer32,
      pr1645v2TTmplPerfOutPQsOctetsBandwidth1min
         Integer32,
      pr1645v2TTmplPerfOutPQsOctetsBandwidth2min
         Integer32,
      pr1645v2TTmplPerfOutPQsOctetsBandwidth5min
         Integer32
      }

pr1645v2TTmplPerfOutPQsTableIx OBJECT-TYPE
   SYNTAX      TableIndex
   MAX-ACCESS  not-accessible
   STATUS      current
   DESCRIPTION
      ""
   ::= {pr1645v2TTmplPerfOutPQsEntry 11}

pr1645v2TTmplPerfOutPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: tunnels.performance.l2tpTunnels.outPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2TTmplPerfOutPQsEntry 16777216}

pr1645v2TTmplPerfOutPQsLength OBJECT-TYPE
   SYNTAX      Integer32
   MAX-ACCESS  read-only
   STATUS      current
   DESCRIPTION
      "Path: tunnels.performance.l2tpTunnels.outPriorityQueues.length"
   ::= {pr1645v2TTmplPerfOutPQsEntry 33554432}

pr1645v2TTmplPerfOutPQsOctetLength OBJECT-TYPE
   SYNTAX      Integer32
   MAX-ACCESS  read-only
   STATUS      current
   DESCRIPTION
      "Path: tunnels.performance.l2tpTunnels.outPriorityQueues.octetLength"
   ::= {pr1645v2TTmplPerfOutPQsEntry 150994944}

pr1645v2TTmplPerfOutPQsRedLength OBJECT-TYPE
   SYNTAX      Integer32
   MAX-ACCESS  read-only
   STATUS      current
   DESCRIPTION
      "Path: tunnels.performance.l2tpTunnels.outPriorityQueues.redLength"
   ::= {pr1645v2TTmplPerfOutPQsEntry 134217728}

pr1645v2TTmplPerfOutPQsPacketsTotal OBJECT-TYPE
   SYNTAX      Counter64
   MAX-ACCESS  read-only
   STATUS      current
   DESCRIPTION
      "Path: tunnels.performance.l2tpTunnels.outPriorityQueues.packets.total

       64 bit unsigned wrappable counter."
   ::= {pr1645v2TTmplPerfOutPQsEntry 50790400}

pr1645v2TTmplPerfOutPQsPacketsDirectTx OBJECT-TYPE
   SYNTAX      Counter64
   MAX-ACCESS  read-only
   STATUS      current
   DESCRIPTION
      "Path: tunnels.performance.l2tpTunnels.outPriorityQueues.packets.directTx

       64 bit unsigned wrappable counter."
   ::= {pr1645v2TTmplPerfOutPQsEntry 50397184}

pr1645v2TTmplPerfOutPQsPacketsQueued OBJECT-TYPE
   SYNTAX      Counter64
   MAX-ACCESS  read-only
   STATUS      current
   DESCRIPTION
      "Path: tunnels.performance.l2tpTunnels.outPriorityQueues.packets.queued

       64 bit unsigned wrappable counter."
   ::= {pr1645v2TTmplPerfOutPQsEntry 50462720}

pr1645v2TTmplPerfOutPQsPacketsDropped OBJECT-TYPE
   SYNTAX      Counter64
   MAX-ACCESS  read-only
   STATUS      current
   DESCRIPTION
      "Path: tunnels.performance.l2tpTunnels.outPriorityQueues.packets.dropped

       64 bit unsigned wrappable counter."
   ::= {pr1645v2TTmplPerfOutPQsEntry 50528256}

pr1645v2TTmplPerfOutPQsPacketsRedDropped OBJECT-TYPE
   SYNTAX      Counter64
   MAX-ACCESS  read-only
   STATUS      current
   DESCRIPTION
      "Path: tunnels.performance.l2tpTunnels.outPriorityQueues.packets.redDropped

       64 bit unsigned wrappable counter."
   ::= {pr1645v2TTmplPerfOutPQsEntry 50724864}

pr1645v2TTmplPerfOutPQsPacketsCirTx OBJECT-TYPE
   SYNTAX      Counter64
   MAX-ACCESS  read-only
   STATUS      current
   DESCRIPTION
      "Path: tunnels.performance.l2tpTunnels.outPriorityQueues.packets.cirTx

       64 bit unsigned wrappable counter."
   ::= {pr1645v2TTmplPerfOutPQsEntry 50593792}

pr1645v2TTmplPerfOutPQsPacketsEirTx OBJECT-TYPE
   SYNTAX      Counter64
   MAX-ACCESS  read-only
   STATUS      current
   DESCRIPTION
      "Path: tunnels.performance.l2tpTunnels.outPriorityQueues.packets.eirTx

       64 bit unsigned wrappable counter."
   ::= {pr1645v2TTmplPerfOutPQsEntry 50659328}

pr1645v2TTmplPerfOutPQsPacketsViolateTx OBJECT-TYPE
   SYNTAX      Counter64
   MAX-ACCESS  read-only
   STATUS      current
   DESCRIPTION
      "Path: tunnels.performance.l2tpTunnels.outPriorityQueues.packets.violateTx

       64 bit unsigned wrappable counter."
   ::= {pr1645v2TTmplPerfOutPQsEntry 50855936}

pr1645v2TTmplPerfOutPQsOctetsTotal OBJECT-TYPE
   SYNTAX      Counter64
   MAX-ACCESS  read-only
   STATUS      current
   DESCRIPTION
      "Path: tunnels.performance.l2tpTunnels.outPriorityQueues.octets.total

       64 bit unsigned wrappable counter."
   ::= {pr1645v2TTmplPerfOutPQsEntry 67567616}

pr1645v2TTmplPerfOutPQsOctetsDirectTx OBJECT-TYPE
   SYNTAX      Counter64
   MAX-ACCESS  read-only
   STATUS      current
   DESCRIPTION
      "Path: tunnels.performance.l2tpTunnels.outPriorityQueues.octets.directTx

       64 bit unsigned wrappable counter."
   ::= {pr1645v2TTmplPerfOutPQsEntry 67174400}

pr1645v2TTmplPerfOutPQsOctetsQueued OBJECT-TYPE
   SYNTAX      Counter64
   MAX-ACCESS  read-only
   STATUS      current
   DESCRIPTION
      "Path: tunnels.performance.l2tpTunnels.outPriorityQueues.octets.queued

       64 bit unsigned wrappable counter."
   ::= {pr1645v2TTmplPerfOutPQsEntry 67239936}

pr1645v2TTmplPerfOutPQsOctetsDropped OBJECT-TYPE
   SYNTAX      Counter64
   MAX-ACCESS  read-only
   STATUS      current
   DESCRIPTION
      "Path: tunnels.performance.l2tpTunnels.outPriorityQueues.octets.dropped

       64 bit unsigned wrappable counter."
   ::= {pr1645v2TTmplPerfOutPQsEntry 67305472}

pr1645v2TTmplPerfOutPQsOctetsRedDropped OBJECT-TYPE
   SYNTAX      Counter64
   MAX-ACCESS  read-only
   STATUS      current
   DESCRIPTION
      "Path: tunnels.performance.l2tpTunnels.outPriorityQueues.octets.redDropped

       64 bit unsigned wrappable counter."
   ::= {pr1645v2TTmplPerfOutPQsEntry 67502080}

pr1645v2TTmplPerfOutPQsOctetsCirTx OBJECT-TYPE
   SYNTAX      Counter64
   MAX-ACCESS  read-only
   STATUS      current
   DESCRIPTION
      "Path: tunnels.performance.l2tpTunnels.outPriorityQueues.octets.cirTx

       64 bit unsigned wrappable counter."
   ::= {pr1645v2TTmplPerfOutPQsEntry 67371008}

pr1645v2TTmplPerfOutPQsOctetsEirTx OBJECT-TYPE
   SYNTAX      Counter64
   MAX-ACCESS  read-only
   STATUS      current
   DESCRIPTION
      "Path: tunnels.performance.l2tpTunnels.outPriorityQueues.octets.eirTx

       64 bit unsigned wrappable counter."
   ::= {pr1645v2TTmplPerfOutPQsEntry 67436544}

pr1645v2TTmplPerfOutPQsOctetsViolateTx OBJECT-TYPE
   SYNTAX      Counter64
   MAX-ACCESS  read-only
   STATUS      current
   DESCRIPTION
      "Path: tunnels.performance.l2tpTunnels.outPriorityQueues.octets.violateTx

       64 bit unsigned wrappable counter."
   ::= {pr1645v2TTmplPerfOutPQsEntry 67633152}

pr1645v2TTmplPerfOutPQsOctetsBandwidth15sec OBJECT-TYPE
   SYNTAX      Integer32
   MAX-ACCESS  read-only
   STATUS      current
   DESCRIPTION
      "Path: tunnels.performance.l2tpTunnels.outPriorityQueues.octets.bandwidth.15sec

       unit name = bps
       formula = 8 * ; 8 /"
   ::= {pr1645v2TTmplPerfOutPQsEntry 70386944}

pr1645v2TTmplPerfOutPQsOctetsBandwidth30sec OBJECT-TYPE
   SYNTAX      Integer32
   MAX-ACCESS  read-only
   STATUS      current
   DESCRIPTION
      "Path: tunnels.performance.l2tpTunnels.outPriorityQueues.octets.bandwidth.30sec

       unit name = bps
       formula = 8 * ; 8 /"
   ::= {pr1645v2TTmplPerfOutPQsEntry 70388224}

pr1645v2TTmplPerfOutPQsOctetsBandwidth1min OBJECT-TYPE
   SYNTAX      Integer32
   MAX-ACCESS  read-only
   STATUS      current
   DESCRIPTION
      "Path: tunnels.performance.l2tpTunnels.outPriorityQueues.octets.bandwidth.1min

       unit name = bps
       formula = 8 * ; 8 /"
   ::= {pr1645v2TTmplPerfOutPQsEntry 70390784}

pr1645v2TTmplPerfOutPQsOctetsBandwidth2min OBJECT-TYPE
   SYNTAX      Integer32
   MAX-ACCESS  read-only
   STATUS      current
   DESCRIPTION
      "Path: tunnels.performance.l2tpTunnels.outPriorityQueues.octets.bandwidth.2min

       unit name = bps
       formula = 8 * ; 8 /"
   ::= {pr1645v2TTmplPerfOutPQsEntry 70395904}

pr1645v2TTmplPerfOutPQsOctetsBandwidth5min OBJECT-TYPE
   SYNTAX      Integer32
   MAX-ACCESS  read-only
   STATUS      current
   DESCRIPTION
      "Path: tunnels.performance.l2tpTunnels.outPriorityQueues.octets.bandwidth.5min

       unit name = bps
       formula = 8 * ; 8 /"
   ::= {pr1645v2TTmplPerfOutPQsEntry 70411264}

pr1645v2TTmplPerfOutPQsH2Performance OBJECT-TYPE
   SYNTAX      SEQUENCE OF Pr1645v2TTmplPerfOutPQsH2PerformanceEntry
   MAX-ACCESS  not-accessible
   STATUS      current
   DESCRIPTION
      ""
   ::= {pr1645v2TTmplPerf 84213760}

pr1645v2TTmplPerfOutPQsH2PerformanceEntry OBJECT-TYPE
   SYNTAX      Pr1645v2TTmplPerfOutPQsH2PerformanceEntry
   MAX-ACCESS  not-accessible
   STATUS      current
   DESCRIPTION
      ""
   INDEX      { pr1645v2TTmplPerfTableIx,
                pr1645v2TTmplPerfOutPQsTableIx,
                pr1645v2TTmplPerfOutPQsH2PerformanceTableIx }
   ::= {pr1645v2TTmplPerfOutPQsH2Performance 1}

Pr1645v2TTmplPerfOutPQsH2PerformanceEntry ::=
   SEQUENCE
      {
      pr1645v2TTmplPerfOutPQsH2PerformanceTableIx
         TableIndex,
      pr1645v2TTmplPerfOutPQsH2PerformanceSysUpTime
         TimeTicks,
      pr1645v2TTmplPerfOutPQsH2PerformanceTotPkts
         Counter64,
      pr1645v2TTmplPerfOutPQsH2PerformanceDirTxPkts
         Counter64,
      pr1645v2TTmplPerfOutPQsH2PerformanceQdPkts
         Counter64,
      pr1645v2TTmplPerfOutPQsH2PerformanceDropPkts
         Counter64,
      pr1645v2TTmplPerfOutPQsH2PerformanceRDropPkts
         Counter64,
      pr1645v2TTmplPerfOutPQsH2PerformanceCirTxPkts
         Counter64,
      pr1645v2TTmplPerfOutPQsH2PerformanceEirTxPkts
         Counter64,
      pr1645v2TTmplPerfOutPQsH2PerformanceViolTxPkts
         Counter64,
      pr1645v2TTmplPerfOutPQsH2PerformanceTotOcts
         Counter64,
      pr1645v2TTmplPerfOutPQsH2PerformanceDirTxOcts
         Counter64,
      pr1645v2TTmplPerfOutPQsH2PerformanceQdOcts
         Counter64,
      pr1645v2TTmplPerfOutPQsH2PerformanceDropOcts
         Counter64,
      pr1645v2TTmplPerfOutPQsH2PerformanceRDropOcts
         Counter64,
      pr1645v2TTmplPerfOutPQsH2PerformanceCirTxOcts
         Counter64,
      pr1645v2TTmplPerfOutPQsH2PerformanceEirTxOcts
         Counter64,
      pr1645v2TTmplPerfOutPQsH2PerformanceViolTxOcts
         Counter64,
      pr1645v2TTmplPerfOutPQsH2PerformanceBandwidth
         Integer32
      }

pr1645v2TTmplPerfOutPQsH2PerformanceTableIx OBJECT-TYPE
   SYNTAX      TableIndex
   MAX-ACCESS  not-accessible
   STATUS      current
   DESCRIPTION
      ""
   ::= {pr1645v2TTmplPerfOutPQsH2PerformanceEntry 11}

pr1645v2TTmplPerfOutPQsH2PerformanceSysUpTime OBJECT-TYPE
   SYNTAX      TimeTicks
   MAX-ACCESS  read-only
   STATUS      current
   DESCRIPTION
      "Path: tunnels.performance.l2tpTunnels.outPriorityQueues.h2Performance.sysUpTime

       Time in centi-second."
   ::= {pr1645v2TTmplPerfOutPQsH2PerformanceEntry 16777216}

pr1645v2TTmplPerfOutPQsH2PerformanceTotPkts OBJECT-TYPE
   SYNTAX      Counter64
   MAX-ACCESS  read-only
   STATUS      current
   DESCRIPTION
      "Path: tunnels.performance.l2tpTunnels.outPriorityQueues.h2Performance.totalPkts

       64 bit unsigned wrappable counter."
   ::= {pr1645v2TTmplPerfOutPQsH2PerformanceEntry 234881024}

pr1645v2TTmplPerfOutPQsH2PerformanceDirTxPkts OBJECT-TYPE
   SYNTAX      Counter64
   MAX-ACCESS  read-only
   STATUS      current
   DESCRIPTION
      "Path: tunnels.performance.l2tpTunnels.outPriorityQueues.h2Performance.directTxPkts

       64 bit unsigned wrappable counter."
   ::= {pr1645v2TTmplPerfOutPQsH2PerformanceEntry 33554432}

pr1645v2TTmplPerfOutPQsH2PerformanceQdPkts OBJECT-TYPE
   SYNTAX      Counter64
   MAX-ACCESS  read-only
   STATUS      current
   DESCRIPTION
      "Path: tunnels.performance.l2tpTunnels.outPriorityQueues.h2Performance.queuedPkts

       64 bit unsigned wrappable counter."
   ::= {pr1645v2TTmplPerfOutPQsH2PerformanceEntry 50331648}

pr1645v2TTmplPerfOutPQsH2PerformanceDropPkts OBJECT-TYPE
   SYNTAX      Counter64
   MAX-ACCESS  read-only
   STATUS      current
   DESCRIPTION
      "Path: tunnels.performance.l2tpTunnels.outPriorityQueues.h2Performance.droppedPkts

       64 bit unsigned wrappable counter."
   ::= {pr1645v2TTmplPerfOutPQsH2PerformanceEntry 67108864}

pr1645v2TTmplPerfOutPQsH2PerformanceRDropPkts OBJECT-TYPE
   SYNTAX      Counter64
   MAX-ACCESS  read-only
   STATUS      current
   DESCRIPTION
      "Path: tunnels.performance.l2tpTunnels.outPriorityQueues.h2Performance.redDroppedPkts

       64 bit unsigned wrappable counter."
   ::= {pr1645v2TTmplPerfOutPQsH2PerformanceEntry 201326592}

pr1645v2TTmplPerfOutPQsH2PerformanceCirTxPkts OBJECT-TYPE
   SYNTAX      Counter64
   MAX-ACCESS  read-only
   STATUS      current
   DESCRIPTION
      "Path: tunnels.performance.l2tpTunnels.outPriorityQueues.h2Performance.cirTxPkts

       64 bit unsigned wrappable counter."
   ::= {pr1645v2TTmplPerfOutPQsH2PerformanceEntry 83886080}

pr1645v2TTmplPerfOutPQsH2PerformanceEirTxPkts OBJECT-TYPE
   SYNTAX      Counter64
   MAX-ACCESS  read-only
   STATUS      current
   DESCRIPTION
      "Path: tunnels.performance.l2tpTunnels.outPriorityQueues.h2Performance.eirTxPkts

       64 bit unsigned wrappable counter."
   ::= {pr1645v2TTmplPerfOutPQsH2PerformanceEntry 100663296}

pr1645v2TTmplPerfOutPQsH2PerformanceViolTxPkts OBJECT-TYPE
   SYNTAX      Counter64
   MAX-ACCESS  read-only
   STATUS      current
   DESCRIPTION
      "Path: tunnels.performance.l2tpTunnels.outPriorityQueues.h2Performance.violateTxPkts

       64 bit unsigned wrappable counter."
   ::= {pr1645v2TTmplPerfOutPQsH2PerformanceEntry 301989888}

pr1645v2TTmplPerfOutPQsH2PerformanceTotOcts OBJECT-TYPE
   SYNTAX      Counter64
   MAX-ACCESS  read-only
   STATUS      current
   DESCRIPTION
      "Path: tunnels.performance.l2tpTunnels.outPriorityQueues.h2Performance.totalOctets

       64 bit unsigned wrappable counter."
   ::= {pr1645v2TTmplPerfOutPQsH2PerformanceEntry 251658240}

pr1645v2TTmplPerfOutPQsH2PerformanceDirTxOcts OBJECT-TYPE
   SYNTAX      Counter64
   MAX-ACCESS  read-only
   STATUS      current
   DESCRIPTION
      "Path: tunnels.performance.l2tpTunnels.outPriorityQueues.h2Performance.directTxOctets

       64 bit unsigned wrappable counter."
   ::= {pr1645v2TTmplPerfOutPQsH2PerformanceEntry 117440512}

pr1645v2TTmplPerfOutPQsH2PerformanceQdOcts OBJECT-TYPE
   SYNTAX      Counter64
   MAX-ACCESS  read-only
   STATUS      current
   DESCRIPTION
      "Path: tunnels.performance.l2tpTunnels.outPriorityQueues.h2Performance.queuedOctets

       64 bit unsigned wrappable counter."
   ::= {pr1645v2TTmplPerfOutPQsH2PerformanceEntry 134217728}

pr1645v2TTmplPerfOutPQsH2PerformanceDropOcts OBJECT-TYPE
   SYNTAX      Counter64
   MAX-ACCESS  read-only
   STATUS      current
   DESCRIPTION
      "Path: tunnels.performance.l2tpTunnels.outPriorityQueues.h2Performance.droppedOctets

       64 bit unsigned wrappable counter."
   ::= {pr1645v2TTmplPerfOutPQsH2PerformanceEntry 150994944}

pr1645v2TTmplPerfOutPQsH2PerformanceRDropOcts OBJECT-TYPE
   SYNTAX      Counter64
   MAX-ACCESS  read-only
   STATUS      current
   DESCRIPTION
      "Path: tunnels.performance.l2tpTunnels.outPriorityQueues.h2Performance.redDroppedOctets

       64 bit unsigned wrappable counter."
   ::= {pr1645v2TTmplPerfOutPQsH2PerformanceEntry 218103808}

pr1645v2TTmplPerfOutPQsH2PerformanceCirTxOcts OBJECT-TYPE
   SYNTAX      Counter64
   MAX-ACCESS  read-only
   STATUS      current
   DESCRIPTION
      "Path: tunnels.performance.l2tpTunnels.outPriorityQueues.h2Performance.cirTxOctets

       64 bit unsigned wrappable counter."
   ::= {pr1645v2TTmplPerfOutPQsH2PerformanceEntry 167772160}

pr1645v2TTmplPerfOutPQsH2PerformanceEirTxOcts OBJECT-TYPE
   SYNTAX      Counter64
   MAX-ACCESS  read-only
   STATUS      current
   DESCRIPTION
      "Path: tunnels.performance.l2tpTunnels.outPriorityQueues.h2Performance.eirTxOctets

       64 bit unsigned wrappable counter."
   ::= {pr1645v2TTmplPerfOutPQsH2PerformanceEntry 184549376}

pr1645v2TTmplPerfOutPQsH2PerformanceViolTxOcts OBJECT-TYPE
   SYNTAX      Counter64
   MAX-ACCESS  read-only
   STATUS      current
   DESCRIPTION
      "Path: tunnels.performance.l2tpTunnels.outPriorityQueues.h2Performance.violateTxOctets

       64 bit unsigned wrappable counter."
   ::= {pr1645v2TTmplPerfOutPQsH2PerformanceEntry 318767104}

pr1645v2TTmplPerfOutPQsH2PerformanceBandwidth OBJECT-TYPE
   SYNTAX      Integer32
   MAX-ACCESS  read-only
   STATUS      current
   DESCRIPTION
      "Path: tunnels.performance.l2tpTunnels.outPriorityQueues.h2Performance.bandwidth

       unit name = bps
       formula = 8 * ; 8 /"
   ::= {pr1645v2TTmplPerfOutPQsH2PerformanceEntry 268435456}

pr1645v2TTmplPerfOutPQsH24Performance OBJECT-TYPE
   SYNTAX      SEQUENCE OF Pr1645v2TTmplPerfOutPQsH24PerformanceEntry
   MAX-ACCESS  not-accessible
   STATUS      current
   DESCRIPTION
      ""
   ::= {pr1645v2TTmplPerf 84279296}

pr1645v2TTmplPerfOutPQsH24PerformanceEntry OBJECT-TYPE
   SYNTAX      Pr1645v2TTmplPerfOutPQsH24PerformanceEntry
   MAX-ACCESS  not-accessible
   STATUS      current
   DESCRIPTION
      ""
   INDEX      { pr1645v2TTmplPerfTableIx,
                pr1645v2TTmplPerfOutPQsTableIx,
                pr1645v2TTmplPerfOutPQsH24PerformanceTableIx }
   ::= {pr1645v2TTmplPerfOutPQsH24Performance 1}

Pr1645v2TTmplPerfOutPQsH24PerformanceEntry ::=
   SEQUENCE
      {
      pr1645v2TTmplPerfOutPQsH24PerformanceTableIx
         TableIndex,
      pr1645v2TTmplPerfOutPQsH24PerformanceSysUpTime
         TimeTicks,
      pr1645v2TTmplPerfOutPQsH24PerformanceTotPkts
         Counter64,
      pr1645v2TTmplPerfOutPQsH24PerformanceDirTxPkts
         Counter64,
      pr1645v2TTmplPerfOutPQsH24PerformanceQdPkts
         Counter64,
      pr1645v2TTmplPerfOutPQsH24PerformanceDropPkts
         Counter64,
      pr1645v2TTmplPerfOutPQsH24PerformanceRDropPkts
         Counter64,
      pr1645v2TTmplPerfOutPQsH24PerformanceCirTxPkts
         Counter64,
      pr1645v2TTmplPerfOutPQsH24PerformanceEirTxPkts
         Counter64,
      pr1645v2TTmplPerfOutPQsH24PerformanceViolTxPkts
         Counter64,
      pr1645v2TTmplPerfOutPQsH24PerformanceTotOcts
         Counter64,
      pr1645v2TTmplPerfOutPQsH24PerformanceDirTxOcts
         Counter64,
      pr1645v2TTmplPerfOutPQsH24PerformanceQdOcts
         Counter64,
      pr1645v2TTmplPerfOutPQsH24PerformanceDropOcts
         Counter64,
      pr1645v2TTmplPerfOutPQsH24PerformanceRDropOcts
         Counter64,
      pr1645v2TTmplPerfOutPQsH24PerformanceCirTxOcts
         Counter64,
      pr1645v2TTmplPerfOutPQsH24PerformanceEirTxOcts
         Counter64,
      pr1645v2TTmplPerfOutPQsH24PerformanceViolTxOcts
         Counter64,
      pr1645v2TTmplPerfOutPQsH24PerformanceBandwidth
         Integer32
      }

pr1645v2TTmplPerfOutPQsH24PerformanceTableIx OBJECT-TYPE
   SYNTAX      TableIndex
   MAX-ACCESS  not-accessible
   STATUS      current
   DESCRIPTION
      ""
   ::= {pr1645v2TTmplPerfOutPQsH24PerformanceEntry 11}

pr1645v2TTmplPerfOutPQsH24PerformanceSysUpTime OBJECT-TYPE
   SYNTAX      TimeTicks
   MAX-ACCESS  read-only
   STATUS      current
   DESCRIPTION
      "Path: tunnels.performance.l2tpTunnels.outPriorityQueues.h24Performance.sysUpTime

       Time in centi-second."
   ::= {pr1645v2TTmplPerfOutPQsH24PerformanceEntry 16777216}

pr1645v2TTmplPerfOutPQsH24PerformanceTotPkts OBJECT-TYPE
   SYNTAX      Counter64
   MAX-ACCESS  read-only
   STATUS      current
   DESCRIPTION
      "Path: tunnels.performance.l2tpTunnels.outPriorityQueues.h24Performance.totalPkts

       64 bit unsigned wrappable counter."
   ::= {pr1645v2TTmplPerfOutPQsH24PerformanceEntry 234881024}

pr1645v2TTmplPerfOutPQsH24PerformanceDirTxPkts OBJECT-TYPE
   SYNTAX      Counter64
   MAX-ACCESS  read-only
   STATUS      current
   DESCRIPTION
      "Path: tunnels.performance.l2tpTunnels.outPriorityQueues.h24Performance.directTxPkts

       64 bit unsigned wrappable counter."
   ::= {pr1645v2TTmplPerfOutPQsH24PerformanceEntry 33554432}

pr1645v2TTmplPerfOutPQsH24PerformanceQdPkts OBJECT-TYPE
   SYNTAX      Counter64
   MAX-ACCESS  read-only
   STATUS      current
   DESCRIPTION
      "Path: tunnels.performance.l2tpTunnels.outPriorityQueues.h24Performance.queuedPkts

       64 bit unsigned wrappable counter."
   ::= {pr1645v2TTmplPerfOutPQsH24PerformanceEntry 50331648}

pr1645v2TTmplPerfOutPQsH24PerformanceDropPkts OBJECT-TYPE
   SYNTAX      Counter64
   MAX-ACCESS  read-only
   STATUS      current
   DESCRIPTION
      "Path: tunnels.performance.l2tpTunnels.outPriorityQueues.h24Performance.droppedPkts

       64 bit unsigned wrappable counter."
   ::= {pr1645v2TTmplPerfOutPQsH24PerformanceEntry 67108864}

pr1645v2TTmplPerfOutPQsH24PerformanceRDropPkts OBJECT-TYPE
   SYNTAX      Counter64
   MAX-ACCESS  read-only
   STATUS      current
   DESCRIPTION
      "Path: tunnels.performance.l2tpTunnels.outPriorityQueues.h24Performance.redDroppedPkts

       64 bit unsigned wrappable counter."
   ::= {pr1645v2TTmplPerfOutPQsH24PerformanceEntry 201326592}

pr1645v2TTmplPerfOutPQsH24PerformanceCirTxPkts OBJECT-TYPE
   SYNTAX      Counter64
   MAX-ACCESS  read-only
   STATUS      current
   DESCRIPTION
      "Path: tunnels.performance.l2tpTunnels.outPriorityQueues.h24Performance.cirTxPkts

       64 bit unsigned wrappable counter."
   ::= {pr1645v2TTmplPerfOutPQsH24PerformanceEntry 83886080}

pr1645v2TTmplPerfOutPQsH24PerformanceEirTxPkts OBJECT-TYPE
   SYNTAX      Counter64
   MAX-ACCESS  read-only
   STATUS      current
   DESCRIPTION
      "Path: tunnels.performance.l2tpTunnels.outPriorityQueues.h24Performance.eirTxPkts

       64 bit unsigned wrappable counter."
   ::= {pr1645v2TTmplPerfOutPQsH24PerformanceEntry 100663296}

pr1645v2TTmplPerfOutPQsH24PerformanceViolTxPkts OBJECT-TYPE
   SYNTAX      Counter64
   MAX-ACCESS  read-only
   STATUS      current
   DESCRIPTION
      "Path: tunnels.performance.l2tpTunnels.outPriorityQueues.h24Performance.violateTxPkts

       64 bit unsigned wrappable counter."
   ::= {pr1645v2TTmplPerfOutPQsH24PerformanceEntry 301989888}

pr1645v2TTmplPerfOutPQsH24PerformanceTotOcts OBJECT-TYPE
   SYNTAX      Counter64
   MAX-ACCESS  read-only
   STATUS      current
   DESCRIPTION
      "Path: tunnels.performance.l2tpTunnels.outPriorityQueues.h24Performance.totalOctets

       64 bit unsigned wrappable counter."
   ::= {pr1645v2TTmplPerfOutPQsH24PerformanceEntry 251658240}

pr1645v2TTmplPerfOutPQsH24PerformanceDirTxOcts OBJECT-TYPE
   SYNTAX      Counter64
   MAX-ACCESS  read-only
   STATUS      current
   DESCRIPTION
      "Path: tunnels.performance.l2tpTunnels.outPriorityQueues.h24Performance.directTxOctets

       64 bit unsigned wrappable counter."
   ::= {pr1645v2TTmplPerfOutPQsH24PerformanceEntry 117440512}

pr1645v2TTmplPerfOutPQsH24PerformanceQdOcts OBJECT-TYPE
   SYNTAX      Counter64
   MAX-ACCESS  read-only
   STATUS      current
   DESCRIPTION
      "Path: tunnels.performance.l2tpTunnels.outPriorityQueues.h24Performance.queuedOctets

       64 bit unsigned wrappable counter."
   ::= {pr1645v2TTmplPerfOutPQsH24PerformanceEntry 134217728}

pr1645v2TTmplPerfOutPQsH24PerformanceDropOcts OBJECT-TYPE
   SYNTAX      Counter64
   MAX-ACCESS  read-only
   STATUS      current
   DESCRIPTION
      "Path: tunnels.performance.l2tpTunnels.outPriorityQueues.h24Performance.droppedOctets

       64 bit unsigned wrappable counter."
   ::= {pr1645v2TTmplPerfOutPQsH24PerformanceEntry 150994944}

pr1645v2TTmplPerfOutPQsH24PerformanceRDropOcts OBJECT-TYPE
   SYNTAX      Counter64
   MAX-ACCESS  read-only
   STATUS      current
   DESCRIPTION
      "Path: tunnels.performance.l2tpTunnels.outPriorityQueues.h24Performance.redDroppedOctets

       64 bit unsigned wrappable counter."
   ::= {pr1645v2TTmplPerfOutPQsH24PerformanceEntry 218103808}

pr1645v2TTmplPerfOutPQsH24PerformanceCirTxOcts OBJECT-TYPE
   SYNTAX      Counter64
   MAX-ACCESS  read-only
   STATUS      current
   DESCRIPTION
      "Path: tunnels.performance.l2tpTunnels.outPriorityQueues.h24Performance.cirTxOctets

       64 bit unsigned wrappable counter."
   ::= {pr1645v2TTmplPerfOutPQsH24PerformanceEntry 167772160}

pr1645v2TTmplPerfOutPQsH24PerformanceEirTxOcts OBJECT-TYPE
   SYNTAX      Counter64
   MAX-ACCESS  read-only
   STATUS      current
   DESCRIPTION
      "Path: tunnels.performance.l2tpTunnels.outPriorityQueues.h24Performance.eirTxOctets

       64 bit unsigned wrappable counter."
   ::= {pr1645v2TTmplPerfOutPQsH24PerformanceEntry 184549376}

pr1645v2TTmplPerfOutPQsH24PerformanceViolTxOcts OBJECT-TYPE
   SYNTAX      Counter64
   MAX-ACCESS  read-only
   STATUS      current
   DESCRIPTION
      "Path: tunnels.performance.l2tpTunnels.outPriorityQueues.h24Performance.violateTxOctets

       64 bit unsigned wrappable counter."
   ::= {pr1645v2TTmplPerfOutPQsH24PerformanceEntry 318767104}

pr1645v2TTmplPerfOutPQsH24PerformanceBandwidth OBJECT-TYPE
   SYNTAX      Integer32
   MAX-ACCESS  read-only
   STATUS      current
   DESCRIPTION
      "Path: tunnels.performance.l2tpTunnels.outPriorityQueues.h24Performance.bandwidth

       unit name = bps
       formula = 8 * ; 8 /"
   ::= {pr1645v2TTmplPerfOutPQsH24PerformanceEntry 268435456}

pr1645v2TTmplPerfOutPQsD7Performance OBJECT-TYPE
   SYNTAX      SEQUENCE OF Pr1645v2TTmplPerfOutPQsD7PerformanceEntry
   MAX-ACCESS  not-accessible
   STATUS      current
   DESCRIPTION
      ""
   ::= {pr1645v2TTmplPerf 84344832}

pr1645v2TTmplPerfOutPQsD7PerformanceEntry OBJECT-TYPE
   SYNTAX      Pr1645v2TTmplPerfOutPQsD7PerformanceEntry
   MAX-ACCESS  not-accessible
   STATUS      current
   DESCRIPTION
      ""
   INDEX      { pr1645v2TTmplPerfTableIx,
                pr1645v2TTmplPerfOutPQsTableIx,
                pr1645v2TTmplPerfOutPQsD7PerformanceTableIx }
   ::= {pr1645v2TTmplPerfOutPQsD7Performance 1}

Pr1645v2TTmplPerfOutPQsD7PerformanceEntry ::=
   SEQUENCE
      {
      pr1645v2TTmplPerfOutPQsD7PerformanceTableIx
         TableIndex,
      pr1645v2TTmplPerfOutPQsD7PerformanceSysUpTime
         TimeTicks,
      pr1645v2TTmplPerfOutPQsD7PerformanceTotPkts
         Counter64,
      pr1645v2TTmplPerfOutPQsD7PerformanceDirTxPkts
         Counter64,
      pr1645v2TTmplPerfOutPQsD7PerformanceQdPkts
         Counter64,
      pr1645v2TTmplPerfOutPQsD7PerformanceDropPkts
         Counter64,
      pr1645v2TTmplPerfOutPQsD7PerformanceRDropPkts
         Counter64,
      pr1645v2TTmplPerfOutPQsD7PerformanceCirTxPkts
         Counter64,
      pr1645v2TTmplPerfOutPQsD7PerformanceEirTxPkts
         Counter64,
      pr1645v2TTmplPerfOutPQsD7PerformanceViolTxPkts
         Counter64,
      pr1645v2TTmplPerfOutPQsD7PerformanceTotOcts
         Counter64,
      pr1645v2TTmplPerfOutPQsD7PerformanceDirTxOcts
         Counter64,
      pr1645v2TTmplPerfOutPQsD7PerformanceQdOcts
         Counter64,
      pr1645v2TTmplPerfOutPQsD7PerformanceDropOcts
         Counter64,
      pr1645v2TTmplPerfOutPQsD7PerformanceRDropOcts
         Counter64,
      pr1645v2TTmplPerfOutPQsD7PerformanceCirTxOcts
         Counter64,
      pr1645v2TTmplPerfOutPQsD7PerformanceEirTxOcts
         Counter64,
      pr1645v2TTmplPerfOutPQsD7PerformanceViolTxOcts
         Counter64,
      pr1645v2TTmplPerfOutPQsD7PerformanceBandwidth
         Integer32
      }

pr1645v2TTmplPerfOutPQsD7PerformanceTableIx OBJECT-TYPE
   SYNTAX      TableIndex
   MAX-ACCESS  not-accessible
   STATUS      current
   DESCRIPTION
      ""
   ::= {pr1645v2TTmplPerfOutPQsD7PerformanceEntry 11}

pr1645v2TTmplPerfOutPQsD7PerformanceSysUpTime OBJECT-TYPE
   SYNTAX      TimeTicks
   MAX-ACCESS  read-only
   STATUS      current
   DESCRIPTION
      "Path: tunnels.performance.l2tpTunnels.outPriorityQueues.d7Performance.sysUpTime

       Time in centi-second."
   ::= {pr1645v2TTmplPerfOutPQsD7PerformanceEntry 16777216}

pr1645v2TTmplPerfOutPQsD7PerformanceTotPkts OBJECT-TYPE
   SYNTAX      Counter64
   MAX-ACCESS  read-only
   STATUS      current
   DESCRIPTION
      "Path: tunnels.performance.l2tpTunnels.outPriorityQueues.d7Performance.totalPkts

       64 bit unsigned wrappable counter."
   ::= {pr1645v2TTmplPerfOutPQsD7PerformanceEntry 234881024}

pr1645v2TTmplPerfOutPQsD7PerformanceDirTxPkts OBJECT-TYPE
   SYNTAX      Counter64
   MAX-ACCESS  read-only
   STATUS      current
   DESCRIPTION
      "Path: tunnels.performance.l2tpTunnels.outPriorityQueues.d7Performance.directTxPkts

       64 bit unsigned wrappable counter."
   ::= {pr1645v2TTmplPerfOutPQsD7PerformanceEntry 33554432}

pr1645v2TTmplPerfOutPQsD7PerformanceQdPkts OBJECT-TYPE
   SYNTAX      Counter64
   MAX-ACCESS  read-only
   STATUS      current
   DESCRIPTION
      "Path: tunnels.performance.l2tpTunnels.outPriorityQueues.d7Performance.queuedPkts

       64 bit unsigned wrappable counter."
   ::= {pr1645v2TTmplPerfOutPQsD7PerformanceEntry 50331648}

pr1645v2TTmplPerfOutPQsD7PerformanceDropPkts OBJECT-TYPE
   SYNTAX      Counter64
   MAX-ACCESS  read-only
   STATUS      current
   DESCRIPTION
      "Path: tunnels.performance.l2tpTunnels.outPriorityQueues.d7Performance.droppedPkts

       64 bit unsigned wrappable counter."
   ::= {pr1645v2TTmplPerfOutPQsD7PerformanceEntry 67108864}

pr1645v2TTmplPerfOutPQsD7PerformanceRDropPkts OBJECT-TYPE
   SYNTAX      Counter64
   MAX-ACCESS  read-only
   STATUS      current
   DESCRIPTION
      "Path: tunnels.performance.l2tpTunnels.outPriorityQueues.d7Performance.redDroppedPkts

       64 bit unsigned wrappable counter."
   ::= {pr1645v2TTmplPerfOutPQsD7PerformanceEntry 201326592}

pr1645v2TTmplPerfOutPQsD7PerformanceCirTxPkts OBJECT-TYPE
   SYNTAX      Counter64
   MAX-ACCESS  read-only
   STATUS      current
   DESCRIPTION
      "Path: tunnels.performance.l2tpTunnels.outPriorityQueues.d7Performance.cirTxPkts

       64 bit unsigned wrappable counter."
   ::= {pr1645v2TTmplPerfOutPQsD7PerformanceEntry 83886080}

pr1645v2TTmplPerfOutPQsD7PerformanceEirTxPkts OBJECT-TYPE
   SYNTAX      Counter64
   MAX-ACCESS  read-only
   STATUS      current
   DESCRIPTION
      "Path: tunnels.performance.l2tpTunnels.outPriorityQueues.d7Performance.eirTxPkts

       64 bit unsigned wrappable counter."
   ::= {pr1645v2TTmplPerfOutPQsD7PerformanceEntry 100663296}

pr1645v2TTmplPerfOutPQsD7PerformanceViolTxPkts OBJECT-TYPE
   SYNTAX      Counter64
   MAX-ACCESS  read-only
   STATUS      current
   DESCRIPTION
      "Path: tunnels.performance.l2tpTunnels.outPriorityQueues.d7Performance.violateTxPkts

       64 bit unsigned wrappable counter."
   ::= {pr1645v2TTmplPerfOutPQsD7PerformanceEntry 301989888}

pr1645v2TTmplPerfOutPQsD7PerformanceTotOcts OBJECT-TYPE
   SYNTAX      Counter64
   MAX-ACCESS  read-only
   STATUS      current
   DESCRIPTION
      "Path: tunnels.performance.l2tpTunnels.outPriorityQueues.d7Performance.totalOctets

       64 bit unsigned wrappable counter."
   ::= {pr1645v2TTmplPerfOutPQsD7PerformanceEntry 251658240}

pr1645v2TTmplPerfOutPQsD7PerformanceDirTxOcts OBJECT-TYPE
   SYNTAX      Counter64
   MAX-ACCESS  read-only
   STATUS      current
   DESCRIPTION
      "Path: tunnels.performance.l2tpTunnels.outPriorityQueues.d7Performance.directTxOctets

       64 bit unsigned wrappable counter."
   ::= {pr1645v2TTmplPerfOutPQsD7PerformanceEntry 117440512}

pr1645v2TTmplPerfOutPQsD7PerformanceQdOcts OBJECT-TYPE
   SYNTAX      Counter64
   MAX-ACCESS  read-only
   STATUS      current
   DESCRIPTION
      "Path: tunnels.performance.l2tpTunnels.outPriorityQueues.d7Performance.queuedOctets

       64 bit unsigned wrappable counter."
   ::= {pr1645v2TTmplPerfOutPQsD7PerformanceEntry 134217728}

pr1645v2TTmplPerfOutPQsD7PerformanceDropOcts OBJECT-TYPE
   SYNTAX      Counter64
   MAX-ACCESS  read-only
   STATUS      current
   DESCRIPTION
      "Path: tunnels.performance.l2tpTunnels.outPriorityQueues.d7Performance.droppedOctets

       64 bit unsigned wrappable counter."
   ::= {pr1645v2TTmplPerfOutPQsD7PerformanceEntry 150994944}

pr1645v2TTmplPerfOutPQsD7PerformanceRDropOcts OBJECT-TYPE
   SYNTAX      Counter64
   MAX-ACCESS  read-only
   STATUS      current
   DESCRIPTION
      "Path: tunnels.performance.l2tpTunnels.outPriorityQueues.d7Performance.redDroppedOctets

       64 bit unsigned wrappable counter."
   ::= {pr1645v2TTmplPerfOutPQsD7PerformanceEntry 218103808}

pr1645v2TTmplPerfOutPQsD7PerformanceCirTxOcts OBJECT-TYPE
   SYNTAX      Counter64
   MAX-ACCESS  read-only
   STATUS      current
   DESCRIPTION
      "Path: tunnels.performance.l2tpTunnels.outPriorityQueues.d7Performance.cirTxOctets

       64 bit unsigned wrappable counter."
   ::= {pr1645v2TTmplPerfOutPQsD7PerformanceEntry 167772160}

pr1645v2TTmplPerfOutPQsD7PerformanceEirTxOcts OBJECT-TYPE
   SYNTAX      Counter64
   MAX-ACCESS  read-only
   STATUS      current
   DESCRIPTION
      "Path: tunnels.performance.l2tpTunnels.outPriorityQueues.d7Performance.eirTxOctets

       64 bit unsigned wrappable counter."
   ::= {pr1645v2TTmplPerfOutPQsD7PerformanceEntry 184549376}

pr1645v2TTmplPerfOutPQsD7PerformanceViolTxOcts OBJECT-TYPE
   SYNTAX      Counter64
   MAX-ACCESS  read-only
   STATUS      current
   DESCRIPTION
      "Path: tunnels.performance.l2tpTunnels.outPriorityQueues.d7Performance.violateTxOctets

       64 bit unsigned wrappable counter."
   ::= {pr1645v2TTmplPerfOutPQsD7PerformanceEntry 318767104}

pr1645v2TTmplPerfOutPQsD7PerformanceBandwidth OBJECT-TYPE
   SYNTAX      Integer32
   MAX-ACCESS  read-only
   STATUS      current
   DESCRIPTION
      "Path: tunnels.performance.l2tpTunnels.outPriorityQueues.d7Performance.bandwidth

       unit name = bps
       formula = 8 * ; 8 /"
   ::= {pr1645v2TTmplPerfOutPQsD7PerformanceEntry 268435456}


pr1645v2TTmplPerfi OBJECT IDENTIFIER ::= {pr1645v2TTmpl 6}

pr1645v2TTmplPerfiSSCTable OBJECT-TYPE
   SYNTAX      SEQUENCE OF Pr1645v2TTmplPerfiEntry
   MAX-ACCESS  not-accessible
   STATUS      current
   DESCRIPTION
      ""
   ::= {pr1645v2TTmplPerfi 1}

pr1645v2TTmplPerfiEntry OBJECT-TYPE
   SYNTAX      Pr1645v2TTmplPerfiEntry
   MAX-ACCESS  not-accessible
   STATUS      current
   DESCRIPTION
      ""
   INDEX      { pr1645v2TTmplPerfiTableIx }
   ::= {pr1645v2TTmplPerfiSSCTable 1}

Pr1645v2TTmplPerfiEntry ::=
   SEQUENCE
      {
      pr1645v2TTmplPerfiTableIx
         TableIndex,
      pr1645v2TTmplPerfiName
         DisplayString,
      pr1645v2TTmplPerfiMCInOctets
         Counter64,
      pr1645v2TTmplPerfiMCInUcast
         Counter64,
      pr1645v2TTmplPerfiMCInNUcastPkts
         Counter64,
      pr1645v2TTmplPerfiMCInBcastPkts
         Counter64,
      pr1645v2TTmplPerfiMCInMcastPkts
         Counter64,
      pr1645v2TTmplPerfiMCInDiscards
         Counter64,
      pr1645v2TTmplPerfiMCInErrors
         Counter64,
      pr1645v2TTmplPerfiMCInUnknownProtos
         Counter64,
      pr1645v2TTmplPerfiMCInDropEx
         Counter64,
      pr1645v2TTmplPerfiMCInDropNoMac
         Counter64,
      pr1645v2TTmplPerfiMCInDropNUCast
         Counter64,
      pr1645v2TTmplPerfiMCInDropFilter
         Counter64,
      pr1645v2TTmplPerfiMCInBandwidth15sec
         Integer32,
      pr1645v2TTmplPerfiMCInBandwidth30sec
         Integer32,
      pr1645v2TTmplPerfiMCInBandwidth1min
         Integer32,
      pr1645v2TTmplPerfiMCInBandwidth2min
         Integer32,
      pr1645v2TTmplPerfiMCInBandwidth5min
         Integer32,
      pr1645v2TTmplPerfiMCOutOctets
         Counter64,
      pr1645v2TTmplPerfiMCOutUcastPkts
         Counter64,
      pr1645v2TTmplPerfiMCOutNUcastPkts
         Counter64,
      pr1645v2TTmplPerfiMCOutBcastPkts
         Counter64,
      pr1645v2TTmplPerfiMCOutMcastPkts
         Counter64,
      pr1645v2TTmplPerfiMCOutDiscards
         Counter64,
      pr1645v2TTmplPerfiMCOutErrors
         Counter64,
      pr1645v2TTmplPerfiMCOutQLen
         Counter32,
      pr1645v2TTmplPerfiMCOutDropEx
         Counter64,
      pr1645v2TTmplPerfiMCOutDropNoArp
         Counter64,
      pr1645v2TTmplPerfiMCOutDropFilter
         Counter64,
      pr1645v2TTmplPerfiMCOutBandwidth15sec
         Integer32,
      pr1645v2TTmplPerfiMCOutBandwidth30sec
         Integer32,
      pr1645v2TTmplPerfiMCOutBandwidth1min
         Integer32,
      pr1645v2TTmplPerfiMCOutBandwidth2min
         Integer32,
      pr1645v2TTmplPerfiMCOutBandwidth5min
         Integer32,
      pr1645v2TTmplPerfiControlHelloSent
         Gauge32,
      pr1645v2TTmplPerfiControlHelloRcvd
         Gauge32,
      pr1645v2TTmplPerfiControlAckSent
         Gauge32,
      pr1645v2TTmplPerfiControlAckRcvd
         Gauge32,
      pr1645v2TTmplPerfiControlDuplicateRcvd
         Gauge32,
      pr1645v2TTmplPerfiControlOutOfSeqRcvd
         Gauge32,
      pr1645v2TTmplPerfiControlRetransmission
         Gauge32,
      pr1645v2TTmplPerfiControlAuthenFailure
         Gauge32,
      pr1645v2TTmplPerfiPppPort
         Counter32,
      pr1645v2TTmplPerfiPppLcpUp
         Counter32,
      pr1645v2TTmplPerfiPppLcpDown
         Counter32,
      pr1645v2TTmplPerfiPppLcpOpen
         Counter32,
      pr1645v2TTmplPerfiPppLcpClose
         Counter32,
      pr1645v2TTmplPerfiPppLcpToP
         Counter32,
      pr1645v2TTmplPerfiPppLcpToM
         Counter32,
      pr1645v2TTmplPerfiPppLcpRcrP
         Counter32,
      pr1645v2TTmplPerfiPppLcpRcrM
         Counter32,
      pr1645v2TTmplPerfiPppLcpRca
         Counter32,
      pr1645v2TTmplPerfiPppLcpRcn
         Counter32,
      pr1645v2TTmplPerfiPppLcpRtr
         Counter32,
      pr1645v2TTmplPerfiPppLcpRta
         Counter32,
      pr1645v2TTmplPerfiPppLcpRuc
         Counter32,
      pr1645v2TTmplPerfiPppLcpRxjP
         Counter32,
      pr1645v2TTmplPerfiPppLcpRxjM
         Counter32,
      pr1645v2TTmplPerfiPppLcpRxr
         Counter32,
      pr1645v2TTmplPerfiPppLcpRrr
         Counter32,
      pr1645v2TTmplPerfiPppLcpRra
         Counter32,
      pr1645v2TTmplPerfiPppLcpDf
         Counter32,
      pr1645v2TTmplPerfiPppLcpIntClose
         Counter32,
      pr1645v2TTmplPerfiPppLcpLm
         Counter32,
      pr1645v2TTmplPerfiPppLcpLmM
         Counter32,
      pr1645v2TTmplPerfiPppAuthMyNegotiated
         INTEGER,
      pr1645v2TTmplPerfiPppAuthMyConfigured
         INTEGER,
      pr1645v2TTmplPerfiPppAuthHisRequested
         INTEGER,
      pr1645v2TTmplPerfiPppAuthRxChallenge
         Counter32,
      pr1645v2TTmplPerfiPppAuthRxResponse
         Counter32,
      pr1645v2TTmplPerfiPppAuthRxSuccess
         Counter32,
      pr1645v2TTmplPerfiPppAuthRxFailure
         Counter32,
      pr1645v2TTmplPerfiPppAuthChallengeTO
         Counter32,
      pr1645v2TTmplPerfiPppAuthResponseTO
         Counter32,
      pr1645v2TTmplPerfiPppAuthTxChallenge
         Counter32,
      pr1645v2TTmplPerfiPppAuthRxRadiusSuccess
         Counter32,
      pr1645v2TTmplPerfiPppAuthRxRadiusFailure
         Counter32,
      pr1645v2TTmplPerfiPppAuthTxSuccess
         Counter32,
      pr1645v2TTmplPerfiPppAuthTxFailure
         Counter32,
      pr1645v2TTmplPerfiPppAuthUnexpected
         Counter32,
      pr1645v2TTmplPerfiPppIpcpUp
         Counter32,
      pr1645v2TTmplPerfiPppIpcpDown
         Counter32,
      pr1645v2TTmplPerfiPppIpcpOpen
         Counter32,
      pr1645v2TTmplPerfiPppIpcpClose
         Counter32,
      pr1645v2TTmplPerfiPppIpcpToP
         Counter32,
      pr1645v2TTmplPerfiPppIpcpToM
         Counter32,
      pr1645v2TTmplPerfiPppIpcpRcrP
         Counter32,
      pr1645v2TTmplPerfiPppIpcpRcrM
         Counter32,
      pr1645v2TTmplPerfiPppIpcpRca
         Counter32,
      pr1645v2TTmplPerfiPppIpcpRcn
         Counter32,
      pr1645v2TTmplPerfiPppIpcpRtr
         Counter32,
      pr1645v2TTmplPerfiPppIpcpRta
         Counter32,
      pr1645v2TTmplPerfiPppIpcpRuc
         Counter32,
      pr1645v2TTmplPerfiPppIpcpRxjP
         Counter32,
      pr1645v2TTmplPerfiPppIpcpRxjM
         Counter32,
      pr1645v2TTmplPerfiPppIpcpRxr
         Counter32,
      pr1645v2TTmplPerfiPppIpcpRrr
         Counter32,
      pr1645v2TTmplPerfiPppIpcpRra
         Counter32,
      pr1645v2TTmplPerfiPppIpcpDf
         Counter32,
      pr1645v2TTmplPerfiPppIpcpIntClose
         Counter32,
      pr1645v2TTmplPerfiPppIpcpLm
         Counter32,
      pr1645v2TTmplPerfiPppIpcpLmM
         Counter32,
      pr1645v2TTmplPerfiPppLinkMonitoringRequestsSent
         Gauge32,
      pr1645v2TTmplPerfiPppLinkMonitoringRepliesRcvd
         Gauge32,
      pr1645v2TTmplPerfiPppLinkMonitoringRequestsRcvd
         Gauge32,
      pr1645v2TTmplPerfiPppLinkMonitoringRepliesSent
         Gauge32
      }

pr1645v2TTmplPerfiTableIx OBJECT-TYPE
   SYNTAX      TableIndex
   MAX-ACCESS  not-accessible
   STATUS      current
   DESCRIPTION
      ""
   ::= {pr1645v2TTmplPerfiEntry 11}

pr1645v2TTmplPerfiName OBJECT-TYPE
   SYNTAX      DisplayString
   MAX-ACCESS  read-only
   STATUS      current
   DESCRIPTION
      "Path: tunnels.performance.ipsecL2tpTunnels.name"
   ::= {pr1645v2TTmplPerfiEntry 16777216}

pr1645v2TTmplPerfiMCInOctets OBJECT-TYPE
   SYNTAX      Counter64
   MAX-ACCESS  read-only
   STATUS      current
   DESCRIPTION
      "Path: tunnels.performance.ipsecL2tpTunnels.mibCounters.ifInOctets

       64 bit unsigned wrappable counter."
   ::= {pr1645v2TTmplPerfiEntry 40697856}

pr1645v2TTmplPerfiMCInUcast OBJECT-TYPE
   SYNTAX      Counter64
   MAX-ACCESS  read-only
   STATUS      current
   DESCRIPTION
      "Path: tunnels.performance.ipsecL2tpTunnels.mibCounters.ifInUcastPkts

       64 bit unsigned wrappable counter."
   ::= {pr1645v2TTmplPerfiEntry 40763392}

pr1645v2TTmplPerfiMCInNUcastPkts OBJECT-TYPE
   SYNTAX      Counter64
   MAX-ACCESS  read-only
   STATUS      current
   DESCRIPTION
      "Path: tunnels.performance.ipsecL2tpTunnels.mibCounters.ifInNUcastPkts

       64 bit unsigned wrappable counter."
   ::= {pr1645v2TTmplPerfiEntry 40828928}

pr1645v2TTmplPerfiMCInBcastPkts OBJECT-TYPE
   SYNTAX      Counter64
   MAX-ACCESS  read-only
   STATUS      current
   DESCRIPTION
      "Path: tunnels.performance.ipsecL2tpTunnels.mibCounters.ifInBcastPkts

       64 bit unsigned wrappable counter."
   ::= {pr1645v2TTmplPerfiEntry 47382528}

pr1645v2TTmplPerfiMCInMcastPkts OBJECT-TYPE
   SYNTAX      Counter64
   MAX-ACCESS  read-only
   STATUS      current
   DESCRIPTION
      "Path: tunnels.performance.ipsecL2tpTunnels.mibCounters.ifInMcastPkts

       64 bit unsigned wrappable counter."
   ::= {pr1645v2TTmplPerfiEntry 48037888}

pr1645v2TTmplPerfiMCInDiscards OBJECT-TYPE
   SYNTAX      Counter64
   MAX-ACCESS  read-only
   STATUS      current
   DESCRIPTION
      "Path: tunnels.performance.ipsecL2tpTunnels.mibCounters.ifInDiscards

       64 bit unsigned wrappable counter."
   ::= {pr1645v2TTmplPerfiEntry 40894464}

pr1645v2TTmplPerfiMCInErrors OBJECT-TYPE
   SYNTAX      Counter64
   MAX-ACCESS  read-only
   STATUS      current
   DESCRIPTION
      "Path: tunnels.performance.ipsecL2tpTunnels.mibCounters.ifInErrors

       64 bit unsigned wrappable counter."
   ::= {pr1645v2TTmplPerfiEntry 40960000}

pr1645v2TTmplPerfiMCInUnknownProtos OBJECT-TYPE
   SYNTAX      Counter64
   MAX-ACCESS  read-only
   STATUS      current
   DESCRIPTION
      "Path: tunnels.performance.ipsecL2tpTunnels.mibCounters.ifInUnknownProtos

       64 bit unsigned wrappable counter."
   ::= {pr1645v2TTmplPerfiEntry 41025536}

pr1645v2TTmplPerfiMCInDropEx OBJECT-TYPE
   SYNTAX      Counter64
   MAX-ACCESS  read-only
   STATUS      current
   DESCRIPTION
      "Path: tunnels.performance.ipsecL2tpTunnels.mibCounters.ifInDropLevelExceeded

       64 bit unsigned wrappable counter."
   ::= {pr1645v2TTmplPerfiEntry 42074112}

pr1645v2TTmplPerfiMCInDropNoMac OBJECT-TYPE
   SYNTAX      Counter64
   MAX-ACCESS  read-only
   STATUS      current
   DESCRIPTION
      "Path: tunnels.performance.ipsecL2tpTunnels.mibCounters.ifInDiscardsNoMacFit

       64 bit unsigned wrappable counter."
   ::= {pr1645v2TTmplPerfiEntry 42270720}

pr1645v2TTmplPerfiMCInDropNUCast OBJECT-TYPE
   SYNTAX      Counter64
   MAX-ACCESS  read-only
   STATUS      current
   DESCRIPTION
      "Path: tunnels.performance.ipsecL2tpTunnels.mibCounters.ifInDiscardsNUCast

       64 bit unsigned wrappable counter."
   ::= {pr1645v2TTmplPerfiEntry 42467328}

pr1645v2TTmplPerfiMCInDropFilter OBJECT-TYPE
   SYNTAX      Counter64
   MAX-ACCESS  read-only
   STATUS      current
   DESCRIPTION
      "Path: tunnels.performance.ipsecL2tpTunnels.mibCounters.ifInDiscardsFilter

       64 bit unsigned wrappable counter."
   ::= {pr1645v2TTmplPerfiEntry 42532864}

pr1645v2TTmplPerfiMCInBandwidth15sec OBJECT-TYPE
   SYNTAX      Integer32
   MAX-ACCESS  read-only
   STATUS      current
   DESCRIPTION
      "Path: tunnels.performance.ipsecL2tpTunnels.mibCounters.ifInBandwidth.15sec

       unit name = bps
       formula = 8 * ; 8 /"
   ::= {pr1645v2TTmplPerfiEntry 45417728}

pr1645v2TTmplPerfiMCInBandwidth30sec OBJECT-TYPE
   SYNTAX      Integer32
   MAX-ACCESS  read-only
   STATUS      current
   DESCRIPTION
      "Path: tunnels.performance.ipsecL2tpTunnels.mibCounters.ifInBandwidth.30sec

       unit name = bps
       formula = 8 * ; 8 /"
   ::= {pr1645v2TTmplPerfiEntry 45419008}

pr1645v2TTmplPerfiMCInBandwidth1min OBJECT-TYPE
   SYNTAX      Integer32
   MAX-ACCESS  read-only
   STATUS      current
   DESCRIPTION
      "Path: tunnels.performance.ipsecL2tpTunnels.mibCounters.ifInBandwidth.1min

       unit name = bps
       formula = 8 * ; 8 /"
   ::= {pr1645v2TTmplPerfiEntry 45421568}

pr1645v2TTmplPerfiMCInBandwidth2min OBJECT-TYPE
   SYNTAX      Integer32
   MAX-ACCESS  read-only
   STATUS      current
   DESCRIPTION
      "Path: tunnels.performance.ipsecL2tpTunnels.mibCounters.ifInBandwidth.2min

       unit name = bps
       formula = 8 * ; 8 /"
   ::= {pr1645v2TTmplPerfiEntry 45426688}

pr1645v2TTmplPerfiMCInBandwidth5min OBJECT-TYPE
   SYNTAX      Integer32
   MAX-ACCESS  read-only
   STATUS      current
   DESCRIPTION
      "Path: tunnels.performance.ipsecL2tpTunnels.mibCounters.ifInBandwidth.5min

       unit name = bps
       formula = 8 * ; 8 /"
   ::= {pr1645v2TTmplPerfiEntry 45442048}

pr1645v2TTmplPerfiMCOutOctets OBJECT-TYPE
   SYNTAX      Counter64
   MAX-ACCESS  read-only
   STATUS      current
   DESCRIPTION
      "Path: tunnels.performance.ipsecL2tpTunnels.mibCounters.ifOutOctets

       64 bit unsigned wrappable counter."
   ::= {pr1645v2TTmplPerfiEntry 41091072}

pr1645v2TTmplPerfiMCOutUcastPkts OBJECT-TYPE
   SYNTAX      Counter64
   MAX-ACCESS  read-only
   STATUS      current
   DESCRIPTION
      "Path: tunnels.performance.ipsecL2tpTunnels.mibCounters.ifOutUcastPkts

       64 bit unsigned wrappable counter."
   ::= {pr1645v2TTmplPerfiEntry 41156608}

pr1645v2TTmplPerfiMCOutNUcastPkts OBJECT-TYPE
   SYNTAX      Counter64
   MAX-ACCESS  read-only
   STATUS      current
   DESCRIPTION
      "Path: tunnels.performance.ipsecL2tpTunnels.mibCounters.ifOutNUcastPkts

       64 bit unsigned wrappable counter."
   ::= {pr1645v2TTmplPerfiEntry 41222144}

pr1645v2TTmplPerfiMCOutBcastPkts OBJECT-TYPE
   SYNTAX      Counter64
   MAX-ACCESS  read-only
   STATUS      current
   DESCRIPTION
      "Path: tunnels.performance.ipsecL2tpTunnels.mibCounters.ifOutBcastPkts

       64 bit unsigned wrappable counter."
   ::= {pr1645v2TTmplPerfiEntry 47775744}

pr1645v2TTmplPerfiMCOutMcastPkts OBJECT-TYPE
   SYNTAX      Counter64
   MAX-ACCESS  read-only
   STATUS      current
   DESCRIPTION
      "Path: tunnels.performance.ipsecL2tpTunnels.mibCounters.ifOutMcastPkts

       64 bit unsigned wrappable counter."
   ::= {pr1645v2TTmplPerfiEntry 48431104}

pr1645v2TTmplPerfiMCOutDiscards OBJECT-TYPE
   SYNTAX      Counter64
   MAX-ACCESS  read-only
   STATUS      current
   DESCRIPTION
      "Path: tunnels.performance.ipsecL2tpTunnels.mibCounters.ifOutDiscards

       64 bit unsigned wrappable counter."
   ::= {pr1645v2TTmplPerfiEntry 41287680}

pr1645v2TTmplPerfiMCOutErrors OBJECT-TYPE
   SYNTAX      Counter64
   MAX-ACCESS  read-only
   STATUS      current
   DESCRIPTION
      "Path: tunnels.performance.ipsecL2tpTunnels.mibCounters.ifOutErrors

       64 bit unsigned wrappable counter."
   ::= {pr1645v2TTmplPerfiEntry 41353216}

pr1645v2TTmplPerfiMCOutQLen OBJECT-TYPE
   SYNTAX      Counter32
   MAX-ACCESS  read-only
   STATUS      current
   DESCRIPTION
      "Path: tunnels.performance.ipsecL2tpTunnels.mibCounters.ifOutQLen

       32 bit unsigned wrappable counter."
   ::= {pr1645v2TTmplPerfiEntry 41418752}

pr1645v2TTmplPerfiMCOutDropEx OBJECT-TYPE
   SYNTAX      Counter64
   MAX-ACCESS  read-only
   STATUS      current
   DESCRIPTION
      "Path: tunnels.performance.ipsecL2tpTunnels.mibCounters.ifOutDropLevelExceeded

       64 bit unsigned wrappable counter."
   ::= {pr1645v2TTmplPerfiEntry 41484288}

pr1645v2TTmplPerfiMCOutDropNoArp OBJECT-TYPE
   SYNTAX      Counter64
   MAX-ACCESS  read-only
   STATUS      current
   DESCRIPTION
      "Path: tunnels.performance.ipsecL2tpTunnels.mibCounters.ifOutDiscardsNoArp

       64 bit unsigned wrappable counter."
   ::= {pr1645v2TTmplPerfiEntry 42336256}

pr1645v2TTmplPerfiMCOutDropFilter OBJECT-TYPE
   SYNTAX      Counter64
   MAX-ACCESS  read-only
   STATUS      current
   DESCRIPTION
      "Path: tunnels.performance.ipsecL2tpTunnels.mibCounters.ifOutDiscardsFilter

       64 bit unsigned wrappable counter."
   ::= {pr1645v2TTmplPerfiEntry 42598400}

pr1645v2TTmplPerfiMCOutBandwidth15sec OBJECT-TYPE
   SYNTAX      Integer32
   MAX-ACCESS  read-only
   STATUS      current
   DESCRIPTION
      "Path: tunnels.performance.ipsecL2tpTunnels.mibCounters.ifOutBandwidth.15sec

       unit name = bps
       formula = 8 * ; 8 /"
   ::= {pr1645v2TTmplPerfiEntry 45483264}

pr1645v2TTmplPerfiMCOutBandwidth30sec OBJECT-TYPE
   SYNTAX      Integer32
   MAX-ACCESS  read-only
   STATUS      current
   DESCRIPTION
      "Path: tunnels.performance.ipsecL2tpTunnels.mibCounters.ifOutBandwidth.30sec

       unit name = bps
       formula = 8 * ; 8 /"
   ::= {pr1645v2TTmplPerfiEntry 45484544}

pr1645v2TTmplPerfiMCOutBandwidth1min OBJECT-TYPE
   SYNTAX      Integer32
   MAX-ACCESS  read-only
   STATUS      current
   DESCRIPTION
      "Path: tunnels.performance.ipsecL2tpTunnels.mibCounters.ifOutBandwidth.1min

       unit name = bps
       formula = 8 * ; 8 /"
   ::= {pr1645v2TTmplPerfiEntry 45487104}

pr1645v2TTmplPerfiMCOutBandwidth2min OBJECT-TYPE
   SYNTAX      Integer32
   MAX-ACCESS  read-only
   STATUS      current
   DESCRIPTION
      "Path: tunnels.performance.ipsecL2tpTunnels.mibCounters.ifOutBandwidth.2min

       unit name = bps
       formula = 8 * ; 8 /"
   ::= {pr1645v2TTmplPerfiEntry 45492224}

pr1645v2TTmplPerfiMCOutBandwidth5min OBJECT-TYPE
   SYNTAX      Integer32
   MAX-ACCESS  read-only
   STATUS      current
   DESCRIPTION
      "Path: tunnels.performance.ipsecL2tpTunnels.mibCounters.ifOutBandwidth.5min

       unit name = bps
       formula = 8 * ; 8 /"
   ::= {pr1645v2TTmplPerfiEntry 45507584}

pr1645v2TTmplPerfiControlHelloSent OBJECT-TYPE
   SYNTAX      Gauge32
   MAX-ACCESS  read-only
   STATUS      current
   DESCRIPTION
      "Path: tunnels.performance.ipsecL2tpTunnels.control.helloSent

       32 bit unsigned gauge value."
   ::= {pr1645v2TTmplPerfiEntry 117506048}

pr1645v2TTmplPerfiControlHelloRcvd OBJECT-TYPE
   SYNTAX      Gauge32
   MAX-ACCESS  read-only
   STATUS      current
   DESCRIPTION
      "Path: tunnels.performance.ipsecL2tpTunnels.control.helloRcvd

       32 bit unsigned gauge value."
   ::= {pr1645v2TTmplPerfiEntry 117637120}

pr1645v2TTmplPerfiControlAckSent OBJECT-TYPE
   SYNTAX      Gauge32
   MAX-ACCESS  read-only
   STATUS      current
   DESCRIPTION
      "Path: tunnels.performance.ipsecL2tpTunnels.control.ackSent

       32 bit unsigned gauge value."
   ::= {pr1645v2TTmplPerfiEntry 117702656}

pr1645v2TTmplPerfiControlAckRcvd OBJECT-TYPE
   SYNTAX      Gauge32
   MAX-ACCESS  read-only
   STATUS      current
   DESCRIPTION
      "Path: tunnels.performance.ipsecL2tpTunnels.control.ackRcvd

       32 bit unsigned gauge value."
   ::= {pr1645v2TTmplPerfiEntry 117571584}

pr1645v2TTmplPerfiControlDuplicateRcvd OBJECT-TYPE
   SYNTAX      Gauge32
   MAX-ACCESS  read-only
   STATUS      current
   DESCRIPTION
      "Path: tunnels.performance.ipsecL2tpTunnels.control.duplicateRcvd

       32 bit unsigned gauge value."
   ::= {pr1645v2TTmplPerfiEntry 117768192}

pr1645v2TTmplPerfiControlOutOfSeqRcvd OBJECT-TYPE
   SYNTAX      Gauge32
   MAX-ACCESS  read-only
   STATUS      current
   DESCRIPTION
      "Path: tunnels.performance.ipsecL2tpTunnels.control.outOfSeqRcvd

       32 bit unsigned gauge value."
   ::= {pr1645v2TTmplPerfiEntry 117833728}

pr1645v2TTmplPerfiControlRetransmission OBJECT-TYPE
   SYNTAX      Gauge32
   MAX-ACCESS  read-only
   STATUS      current
   DESCRIPTION
      "Path: tunnels.performance.ipsecL2tpTunnels.control.retransmission

       32 bit unsigned gauge value."
   ::= {pr1645v2TTmplPerfiEntry 117899264}

pr1645v2TTmplPerfiControlAuthenFailure OBJECT-TYPE
   SYNTAX      Gauge32
   MAX-ACCESS  read-only
   STATUS      current
   DESCRIPTION
      "Path: tunnels.performance.ipsecL2tpTunnels.control.authenFailure

       32 bit unsigned gauge value."
   ::= {pr1645v2TTmplPerfiEntry 117964800}

pr1645v2TTmplPerfiPppPort OBJECT-TYPE
   SYNTAX      Counter32
   MAX-ACCESS  read-only
   STATUS      current
   DESCRIPTION
      "Path: tunnels.performance.ipsecL2tpTunnels.ppp.port

       32 bit unsigned wrappable counter."
   ::= {pr1645v2TTmplPerfiEntry 67371008}

pr1645v2TTmplPerfiPppLcpUp OBJECT-TYPE
   SYNTAX      Counter32
   MAX-ACCESS  read-only
   STATUS      current
   DESCRIPTION
      "Path: tunnels.performance.ipsecL2tpTunnels.ppp.lcp.up

       32 bit unsigned wrappable counter."
   ::= {pr1645v2TTmplPerfiEntry 67174656}

pr1645v2TTmplPerfiPppLcpDown OBJECT-TYPE
   SYNTAX      Counter32
   MAX-ACCESS  read-only
   STATUS      current
   DESCRIPTION
      "Path: tunnels.performance.ipsecL2tpTunnels.ppp.lcp.down

       32 bit unsigned wrappable counter."
   ::= {pr1645v2TTmplPerfiEntry 67174912}

pr1645v2TTmplPerfiPppLcpOpen OBJECT-TYPE
   SYNTAX      Counter32
   MAX-ACCESS  read-only
   STATUS      current
   DESCRIPTION
      "Path: tunnels.performance.ipsecL2tpTunnels.ppp.lcp.open

       32 bit unsigned wrappable counter."
   ::= {pr1645v2TTmplPerfiEntry 67175168}

pr1645v2TTmplPerfiPppLcpClose OBJECT-TYPE
   SYNTAX      Counter32
   MAX-ACCESS  read-only
   STATUS      current
   DESCRIPTION
      "Path: tunnels.performance.ipsecL2tpTunnels.ppp.lcp.close

       32 bit unsigned wrappable counter."
   ::= {pr1645v2TTmplPerfiEntry 67175424}

pr1645v2TTmplPerfiPppLcpToP OBJECT-TYPE
   SYNTAX      Counter32
   MAX-ACCESS  read-only
   STATUS      current
   DESCRIPTION
      "Path: tunnels.performance.ipsecL2tpTunnels.ppp.lcp.toP

       32 bit unsigned wrappable counter."
   ::= {pr1645v2TTmplPerfiEntry 67175680}

pr1645v2TTmplPerfiPppLcpToM OBJECT-TYPE
   SYNTAX      Counter32
   MAX-ACCESS  read-only
   STATUS      current
   DESCRIPTION
      "Path: tunnels.performance.ipsecL2tpTunnels.ppp.lcp.toM

       32 bit unsigned wrappable counter."
   ::= {pr1645v2TTmplPerfiEntry 67175936}

pr1645v2TTmplPerfiPppLcpRcrP OBJECT-TYPE
   SYNTAX      Counter32
   MAX-ACCESS  read-only
   STATUS      current
   DESCRIPTION
      "Path: tunnels.performance.ipsecL2tpTunnels.ppp.lcp.rcrP

       32 bit unsigned wrappable counter."
   ::= {pr1645v2TTmplPerfiEntry 67176192}

pr1645v2TTmplPerfiPppLcpRcrM OBJECT-TYPE
   SYNTAX      Counter32
   MAX-ACCESS  read-only
   STATUS      current
   DESCRIPTION
      "Path: tunnels.performance.ipsecL2tpTunnels.ppp.lcp.rcrM

       32 bit unsigned wrappable counter."
   ::= {pr1645v2TTmplPerfiEntry 67176448}

pr1645v2TTmplPerfiPppLcpRca OBJECT-TYPE
   SYNTAX      Counter32
   MAX-ACCESS  read-only
   STATUS      current
   DESCRIPTION
      "Path: tunnels.performance.ipsecL2tpTunnels.ppp.lcp.rca

       32 bit unsigned wrappable counter."
   ::= {pr1645v2TTmplPerfiEntry 67176704}

pr1645v2TTmplPerfiPppLcpRcn OBJECT-TYPE
   SYNTAX      Counter32
   MAX-ACCESS  read-only
   STATUS      current
   DESCRIPTION
      "Path: tunnels.performance.ipsecL2tpTunnels.ppp.lcp.rcn

       32 bit unsigned wrappable counter."
   ::= {pr1645v2TTmplPerfiEntry 67176960}

pr1645v2TTmplPerfiPppLcpRtr OBJECT-TYPE
   SYNTAX      Counter32
   MAX-ACCESS  read-only
   STATUS      current
   DESCRIPTION
      "Path: tunnels.performance.ipsecL2tpTunnels.ppp.lcp.rtr

       32 bit unsigned wrappable counter."
   ::= {pr1645v2TTmplPerfiEntry 67177216}

pr1645v2TTmplPerfiPppLcpRta OBJECT-TYPE
   SYNTAX      Counter32
   MAX-ACCESS  read-only
   STATUS      current
   DESCRIPTION
      "Path: tunnels.performance.ipsecL2tpTunnels.ppp.lcp.rta

       32 bit unsigned wrappable counter."
   ::= {pr1645v2TTmplPerfiEntry 67177472}

pr1645v2TTmplPerfiPppLcpRuc OBJECT-TYPE
   SYNTAX      Counter32
   MAX-ACCESS  read-only
   STATUS      current
   DESCRIPTION
      "Path: tunnels.performance.ipsecL2tpTunnels.ppp.lcp.ruc

       32 bit unsigned wrappable counter."
   ::= {pr1645v2TTmplPerfiEntry 67177728}

pr1645v2TTmplPerfiPppLcpRxjP OBJECT-TYPE
   SYNTAX      Counter32
   MAX-ACCESS  read-only
   STATUS      current
   DESCRIPTION
      "Path: tunnels.performance.ipsecL2tpTunnels.ppp.lcp.rxjP

       32 bit unsigned wrappable counter."
   ::= {pr1645v2TTmplPerfiEntry 67177984}

pr1645v2TTmplPerfiPppLcpRxjM OBJECT-TYPE
   SYNTAX      Counter32
   MAX-ACCESS  read-only
   STATUS      current
   DESCRIPTION
      "Path: tunnels.performance.ipsecL2tpTunnels.ppp.lcp.rxjM

       32 bit unsigned wrappable counter."
   ::= {pr1645v2TTmplPerfiEntry 67178240}

pr1645v2TTmplPerfiPppLcpRxr OBJECT-TYPE
   SYNTAX      Counter32
   MAX-ACCESS  read-only
   STATUS      current
   DESCRIPTION
      "Path: tunnels.performance.ipsecL2tpTunnels.ppp.lcp.rxr

       32 bit unsigned wrappable counter."
   ::= {pr1645v2TTmplPerfiEntry 67178496}

pr1645v2TTmplPerfiPppLcpRrr OBJECT-TYPE
   SYNTAX      Counter32
   MAX-ACCESS  read-only
   STATUS      current
   DESCRIPTION
      "Path: tunnels.performance.ipsecL2tpTunnels.ppp.lcp.rrr

       32 bit unsigned wrappable counter."
   ::= {pr1645v2TTmplPerfiEntry 67178752}

pr1645v2TTmplPerfiPppLcpRra OBJECT-TYPE
   SYNTAX      Counter32
   MAX-ACCESS  read-only
   STATUS      current
   DESCRIPTION
      "Path: tunnels.performance.ipsecL2tpTunnels.ppp.lcp.rra

       32 bit unsigned wrappable counter."
   ::= {pr1645v2TTmplPerfiEntry 67179008}

pr1645v2TTmplPerfiPppLcpDf OBJECT-TYPE
   SYNTAX      Counter32
   MAX-ACCESS  read-only
   STATUS      current
   DESCRIPTION
      "Path: tunnels.performance.ipsecL2tpTunnels.ppp.lcp.df

       32 bit unsigned wrappable counter."
   ::= {pr1645v2TTmplPerfiEntry 67179264}

pr1645v2TTmplPerfiPppLcpIntClose OBJECT-TYPE
   SYNTAX      Counter32
   MAX-ACCESS  read-only
   STATUS      current
   DESCRIPTION
      "Path: tunnels.performance.ipsecL2tpTunnels.ppp.lcp.intClose

       32 bit unsigned wrappable counter."
   ::= {pr1645v2TTmplPerfiEntry 67179520}

pr1645v2TTmplPerfiPppLcpLm OBJECT-TYPE
   SYNTAX      Counter32
   MAX-ACCESS  read-only
   STATUS      current
   DESCRIPTION
      "Path: tunnels.performance.ipsecL2tpTunnels.ppp.lcp.lm

       32 bit unsigned wrappable counter."
   ::= {pr1645v2TTmplPerfiEntry 67179776}

pr1645v2TTmplPerfiPppLcpLmM OBJECT-TYPE
   SYNTAX      Counter32
   MAX-ACCESS  read-only
   STATUS      current
   DESCRIPTION
      "Path: tunnels.performance.ipsecL2tpTunnels.ppp.lcp.lmM

       32 bit unsigned wrappable counter."
   ::= {pr1645v2TTmplPerfiEntry 67180032}

pr1645v2TTmplPerfiPppAuthMyNegotiated OBJECT-TYPE
   SYNTAX      INTEGER
               {
               none (0),
               pap (1),
               chap (2),
               msChap (3),
               msChapV2 (4),
               unknown (5),
               chapOrPap (6)
               }
   MAX-ACCESS  read-only
   STATUS      current
   DESCRIPTION
      "Path: tunnels.performance.ipsecL2tpTunnels.ppp.auth.myNegotiated

       Possibilities:
               none   (0)
               pap   (1)
               chap   (2)
               msChap   (3)
               msChapV2   (4)
               unknown   (5)
               chapOrPap   (6)"
   ::= {pr1645v2TTmplPerfiEntry 67243264}

pr1645v2TTmplPerfiPppAuthMyConfigured OBJECT-TYPE
   SYNTAX      INTEGER
               {
               none (0),
               pap (1),
               chap (2),
               msChap (3),
               msChapV2 (4),
               unknown (5),
               chapOrPap (6)
               }
   MAX-ACCESS  read-only
   STATUS      current
   DESCRIPTION
      "Path: tunnels.performance.ipsecL2tpTunnels.ppp.auth.myConfigured

       Possibilities:
               none   (0)
               pap   (1)
               chap   (2)
               msChap   (3)
               msChapV2   (4)
               unknown   (5)
               chapOrPap   (6)"
   ::= {pr1645v2TTmplPerfiEntry 67243776}

pr1645v2TTmplPerfiPppAuthHisRequested OBJECT-TYPE
   SYNTAX      INTEGER
               {
               none (0),
               pap (1),
               chap (2),
               msChap (3),
               msChapV2 (4),
               unknown (5),
               chapOrPap (6)
               }
   MAX-ACCESS  read-only
   STATUS      current
   DESCRIPTION
      "Path: tunnels.performance.ipsecL2tpTunnels.ppp.auth.hisRequested

       Possibilities:
               none   (0)
               pap   (1)
               chap   (2)
               msChap   (3)
               msChapV2   (4)
               unknown   (5)
               chapOrPap   (6)"
   ::= {pr1645v2TTmplPerfiEntry 67243520}

pr1645v2TTmplPerfiPppAuthRxChallenge OBJECT-TYPE
   SYNTAX      Counter32
   MAX-ACCESS  read-only
   STATUS      current
   DESCRIPTION
      "Path: tunnels.performance.ipsecL2tpTunnels.ppp.auth.rxChallenge

       32 bit unsigned wrappable counter."
   ::= {pr1645v2TTmplPerfiEntry 67240192}

pr1645v2TTmplPerfiPppAuthRxResponse OBJECT-TYPE
   SYNTAX      Counter32
   MAX-ACCESS  read-only
   STATUS      current
   DESCRIPTION
      "Path: tunnels.performance.ipsecL2tpTunnels.ppp.auth.rxResponse

       32 bit unsigned wrappable counter."
   ::= {pr1645v2TTmplPerfiEntry 67240448}

pr1645v2TTmplPerfiPppAuthRxSuccess OBJECT-TYPE
   SYNTAX      Counter32
   MAX-ACCESS  read-only
   STATUS      current
   DESCRIPTION
      "Path: tunnels.performance.ipsecL2tpTunnels.ppp.auth.rxSuccess

       32 bit unsigned wrappable counter."
   ::= {pr1645v2TTmplPerfiEntry 67240704}

pr1645v2TTmplPerfiPppAuthRxFailure OBJECT-TYPE
   SYNTAX      Counter32
   MAX-ACCESS  read-only
   STATUS      current
   DESCRIPTION
      "Path: tunnels.performance.ipsecL2tpTunnels.ppp.auth.rxFailure

       32 bit unsigned wrappable counter."
   ::= {pr1645v2TTmplPerfiEntry 67240960}

pr1645v2TTmplPerfiPppAuthChallengeTO OBJECT-TYPE
   SYNTAX      Counter32
   MAX-ACCESS  read-only
   STATUS      current
   DESCRIPTION
      "Path: tunnels.performance.ipsecL2tpTunnels.ppp.auth.challengeTO

       32 bit unsigned wrappable counter."
   ::= {pr1645v2TTmplPerfiEntry 67241216}

pr1645v2TTmplPerfiPppAuthResponseTO OBJECT-TYPE
   SYNTAX      Counter32
   MAX-ACCESS  read-only
   STATUS      current
   DESCRIPTION
      "Path: tunnels.performance.ipsecL2tpTunnels.ppp.auth.responseTO

       32 bit unsigned wrappable counter."
   ::= {pr1645v2TTmplPerfiEntry 67241472}

pr1645v2TTmplPerfiPppAuthTxChallenge OBJECT-TYPE
   SYNTAX      Counter32
   MAX-ACCESS  read-only
   STATUS      current
   DESCRIPTION
      "Path: tunnels.performance.ipsecL2tpTunnels.ppp.auth.txChallenge

       32 bit unsigned wrappable counter."
   ::= {pr1645v2TTmplPerfiEntry 67241728}

pr1645v2TTmplPerfiPppAuthRxRadiusSuccess OBJECT-TYPE
   SYNTAX      Counter32
   MAX-ACCESS  read-only
   STATUS      current
   DESCRIPTION
      "Path: tunnels.performance.ipsecL2tpTunnels.ppp.auth.rxRadiusSuccess

       32 bit unsigned wrappable counter."
   ::= {pr1645v2TTmplPerfiEntry 67241984}

pr1645v2TTmplPerfiPppAuthRxRadiusFailure OBJECT-TYPE
   SYNTAX      Counter32
   MAX-ACCESS  read-only
   STATUS      current
   DESCRIPTION
      "Path: tunnels.performance.ipsecL2tpTunnels.ppp.auth.rxRadiusFailure

       32 bit unsigned wrappable counter."
   ::= {pr1645v2TTmplPerfiEntry 67242240}

pr1645v2TTmplPerfiPppAuthTxSuccess OBJECT-TYPE
   SYNTAX      Counter32
   MAX-ACCESS  read-only
   STATUS      current
   DESCRIPTION
      "Path: tunnels.performance.ipsecL2tpTunnels.ppp.auth.txSuccess

       32 bit unsigned wrappable counter."
   ::= {pr1645v2TTmplPerfiEntry 67242496}

pr1645v2TTmplPerfiPppAuthTxFailure OBJECT-TYPE
   SYNTAX      Counter32
   MAX-ACCESS  read-only
   STATUS      current
   DESCRIPTION
      "Path: tunnels.performance.ipsecL2tpTunnels.ppp.auth.txFailure

       32 bit unsigned wrappable counter."
   ::= {pr1645v2TTmplPerfiEntry 67242752}

pr1645v2TTmplPerfiPppAuthUnexpected OBJECT-TYPE
   SYNTAX      Counter32
   MAX-ACCESS  read-only
   STATUS      current
   DESCRIPTION
      "Path: tunnels.performance.ipsecL2tpTunnels.ppp.auth.unexpected

       32 bit unsigned wrappable counter."
   ::= {pr1645v2TTmplPerfiEntry 67243008}

pr1645v2TTmplPerfiPppIpcpUp OBJECT-TYPE
   SYNTAX      Counter32
   MAX-ACCESS  read-only
   STATUS      current
   DESCRIPTION
      "Path: tunnels.performance.ipsecL2tpTunnels.ppp.ipcp.up

       32 bit unsigned wrappable counter."
   ::= {pr1645v2TTmplPerfiEntry 67305728}

pr1645v2TTmplPerfiPppIpcpDown OBJECT-TYPE
   SYNTAX      Counter32
   MAX-ACCESS  read-only
   STATUS      current
   DESCRIPTION
      "Path: tunnels.performance.ipsecL2tpTunnels.ppp.ipcp.down

       32 bit unsigned wrappable counter."
   ::= {pr1645v2TTmplPerfiEntry 67305984}

pr1645v2TTmplPerfiPppIpcpOpen OBJECT-TYPE
   SYNTAX      Counter32
   MAX-ACCESS  read-only
   STATUS      current
   DESCRIPTION
      "Path: tunnels.performance.ipsecL2tpTunnels.ppp.ipcp.open

       32 bit unsigned wrappable counter."
   ::= {pr1645v2TTmplPerfiEntry 67306240}

pr1645v2TTmplPerfiPppIpcpClose OBJECT-TYPE
   SYNTAX      Counter32
   MAX-ACCESS  read-only
   STATUS      current
   DESCRIPTION
      "Path: tunnels.performance.ipsecL2tpTunnels.ppp.ipcp.close

       32 bit unsigned wrappable counter."
   ::= {pr1645v2TTmplPerfiEntry 67306496}

pr1645v2TTmplPerfiPppIpcpToP OBJECT-TYPE
   SYNTAX      Counter32
   MAX-ACCESS  read-only
   STATUS      current
   DESCRIPTION
      "Path: tunnels.performance.ipsecL2tpTunnels.ppp.ipcp.toP

       32 bit unsigned wrappable counter."
   ::= {pr1645v2TTmplPerfiEntry 67306752}

pr1645v2TTmplPerfiPppIpcpToM OBJECT-TYPE
   SYNTAX      Counter32
   MAX-ACCESS  read-only
   STATUS      current
   DESCRIPTION
      "Path: tunnels.performance.ipsecL2tpTunnels.ppp.ipcp.toM

       32 bit unsigned wrappable counter."
   ::= {pr1645v2TTmplPerfiEntry 67307008}

pr1645v2TTmplPerfiPppIpcpRcrP OBJECT-TYPE
   SYNTAX      Counter32
   MAX-ACCESS  read-only
   STATUS      current
   DESCRIPTION
      "Path: tunnels.performance.ipsecL2tpTunnels.ppp.ipcp.rcrP

       32 bit unsigned wrappable counter."
   ::= {pr1645v2TTmplPerfiEntry 67307264}

pr1645v2TTmplPerfiPppIpcpRcrM OBJECT-TYPE
   SYNTAX      Counter32
   MAX-ACCESS  read-only
   STATUS      current
   DESCRIPTION
      "Path: tunnels.performance.ipsecL2tpTunnels.ppp.ipcp.rcrM

       32 bit unsigned wrappable counter."
   ::= {pr1645v2TTmplPerfiEntry 67307520}

pr1645v2TTmplPerfiPppIpcpRca OBJECT-TYPE
   SYNTAX      Counter32
   MAX-ACCESS  read-only
   STATUS      current
   DESCRIPTION
      "Path: tunnels.performance.ipsecL2tpTunnels.ppp.ipcp.rca

       32 bit unsigned wrappable counter."
   ::= {pr1645v2TTmplPerfiEntry 67307776}

pr1645v2TTmplPerfiPppIpcpRcn OBJECT-TYPE
   SYNTAX      Counter32
   MAX-ACCESS  read-only
   STATUS      current
   DESCRIPTION
      "Path: tunnels.performance.ipsecL2tpTunnels.ppp.ipcp.rcn

       32 bit unsigned wrappable counter."
   ::= {pr1645v2TTmplPerfiEntry 67308032}

pr1645v2TTmplPerfiPppIpcpRtr OBJECT-TYPE
   SYNTAX      Counter32
   MAX-ACCESS  read-only
   STATUS      current
   DESCRIPTION
      "Path: tunnels.performance.ipsecL2tpTunnels.ppp.ipcp.rtr

       32 bit unsigned wrappable counter."
   ::= {pr1645v2TTmplPerfiEntry 67308288}

pr1645v2TTmplPerfiPppIpcpRta OBJECT-TYPE
   SYNTAX      Counter32
   MAX-ACCESS  read-only
   STATUS      current
   DESCRIPTION
      "Path: tunnels.performance.ipsecL2tpTunnels.ppp.ipcp.rta

       32 bit unsigned wrappable counter."
   ::= {pr1645v2TTmplPerfiEntry 67308544}

pr1645v2TTmplPerfiPppIpcpRuc OBJECT-TYPE
   SYNTAX      Counter32
   MAX-ACCESS  read-only
   STATUS      current
   DESCRIPTION
      "Path: tunnels.performance.ipsecL2tpTunnels.ppp.ipcp.ruc

       32 bit unsigned wrappable counter."
   ::= {pr1645v2TTmplPerfiEntry 67308800}

pr1645v2TTmplPerfiPppIpcpRxjP OBJECT-TYPE
   SYNTAX      Counter32
   MAX-ACCESS  read-only
   STATUS      current
   DESCRIPTION
      "Path: tunnels.performance.ipsecL2tpTunnels.ppp.ipcp.rxjP

       32 bit unsigned wrappable counter."
   ::= {pr1645v2TTmplPerfiEntry 67309056}

pr1645v2TTmplPerfiPppIpcpRxjM OBJECT-TYPE
   SYNTAX      Counter32
   MAX-ACCESS  read-only
   STATUS      current
   DESCRIPTION
      "Path: tunnels.performance.ipsecL2tpTunnels.ppp.ipcp.rxjM

       32 bit unsigned wrappable counter."
   ::= {pr1645v2TTmplPerfiEntry 67309312}

pr1645v2TTmplPerfiPppIpcpRxr OBJECT-TYPE
   SYNTAX      Counter32
   MAX-ACCESS  read-only
   STATUS      current
   DESCRIPTION
      "Path: tunnels.performance.ipsecL2tpTunnels.ppp.ipcp.rxr

       32 bit unsigned wrappable counter."
   ::= {pr1645v2TTmplPerfiEntry 67309568}

pr1645v2TTmplPerfiPppIpcpRrr OBJECT-TYPE
   SYNTAX      Counter32
   MAX-ACCESS  read-only
   STATUS      current
   DESCRIPTION
      "Path: tunnels.performance.ipsecL2tpTunnels.ppp.ipcp.rrr

       32 bit unsigned wrappable counter."
   ::= {pr1645v2TTmplPerfiEntry 67309824}

pr1645v2TTmplPerfiPppIpcpRra OBJECT-TYPE
   SYNTAX      Counter32
   MAX-ACCESS  read-only
   STATUS      current
   DESCRIPTION
      "Path: tunnels.performance.ipsecL2tpTunnels.ppp.ipcp.rra

       32 bit unsigned wrappable counter."
   ::= {pr1645v2TTmplPerfiEntry 67310080}

pr1645v2TTmplPerfiPppIpcpDf OBJECT-TYPE
   SYNTAX      Counter32
   MAX-ACCESS  read-only
   STATUS      current
   DESCRIPTION
      "Path: tunnels.performance.ipsecL2tpTunnels.ppp.ipcp.df

       32 bit unsigned wrappable counter."
   ::= {pr1645v2TTmplPerfiEntry 67310336}

pr1645v2TTmplPerfiPppIpcpIntClose OBJECT-TYPE
   SYNTAX      Counter32
   MAX-ACCESS  read-only
   STATUS      current
   DESCRIPTION
      "Path: tunnels.performance.ipsecL2tpTunnels.ppp.ipcp.intClose

       32 bit unsigned wrappable counter."
   ::= {pr1645v2TTmplPerfiEntry 67310592}

pr1645v2TTmplPerfiPppIpcpLm OBJECT-TYPE
   SYNTAX      Counter32
   MAX-ACCESS  read-only
   STATUS      current
   DESCRIPTION
      "Path: tunnels.performance.ipsecL2tpTunnels.ppp.ipcp.lm

       32 bit unsigned wrappable counter."
   ::= {pr1645v2TTmplPerfiEntry 67310848}

pr1645v2TTmplPerfiPppIpcpLmM OBJECT-TYPE
   SYNTAX      Counter32
   MAX-ACCESS  read-only
   STATUS      current
   DESCRIPTION
      "Path: tunnels.performance.ipsecL2tpTunnels.ppp.ipcp.lmM

       32 bit unsigned wrappable counter."
   ::= {pr1645v2TTmplPerfiEntry 67311104}

pr1645v2TTmplPerfiPppLinkMonitoringRequestsSent OBJECT-TYPE
   SYNTAX      Gauge32
   MAX-ACCESS  read-only
   STATUS      current
   DESCRIPTION
      "Path: tunnels.performance.ipsecL2tpTunnels.ppp.linkMonitoring.requestsSent

       32 bit unsigned gauge value."
   ::= {pr1645v2TTmplPerfiEntry 67436800}

pr1645v2TTmplPerfiPppLinkMonitoringRepliesRcvd OBJECT-TYPE
   SYNTAX      Gauge32
   MAX-ACCESS  read-only
   STATUS      current
   DESCRIPTION
      "Path: tunnels.performance.ipsecL2tpTunnels.ppp.linkMonitoring.repliesRcvd

       32 bit unsigned gauge value."
   ::= {pr1645v2TTmplPerfiEntry 67437056}

pr1645v2TTmplPerfiPppLinkMonitoringRequestsRcvd OBJECT-TYPE
   SYNTAX      Gauge32
   MAX-ACCESS  read-only
   STATUS      current
   DESCRIPTION
      "Path: tunnels.performance.ipsecL2tpTunnels.ppp.linkMonitoring.requestsRcvd

       32 bit unsigned gauge value."
   ::= {pr1645v2TTmplPerfiEntry 67437312}

pr1645v2TTmplPerfiPppLinkMonitoringRepliesSent OBJECT-TYPE
   SYNTAX      Gauge32
   MAX-ACCESS  read-only
   STATUS      current
   DESCRIPTION
      "Path: tunnels.performance.ipsecL2tpTunnels.ppp.linkMonitoring.repliesSent

       32 bit unsigned gauge value."
   ::= {pr1645v2TTmplPerfiEntry 67437568}

pr1645v2TTmplPerfiMCH2P OBJECT-TYPE
   SYNTAX      SEQUENCE OF Pr1645v2TTmplPerfiMCH2PEntry
   MAX-ACCESS  not-accessible
   STATUS      current
   DESCRIPTION
      ""
   ::= {pr1645v2TTmplPerfi 41549824}

pr1645v2TTmplPerfiMCH2PEntry OBJECT-TYPE
   SYNTAX      Pr1645v2TTmplPerfiMCH2PEntry
   MAX-ACCESS  not-accessible
   STATUS      current
   DESCRIPTION
      ""
   INDEX      { pr1645v2TTmplPerfiTableIx,
                pr1645v2TTmplPerfiMCH2PTableIx }
   ::= {pr1645v2TTmplPerfiMCH2P 1}

Pr1645v2TTmplPerfiMCH2PEntry ::=
   SEQUENCE
      {
      pr1645v2TTmplPerfiMCH2PTableIx
         TableIndex,
      pr1645v2TTmplPerfiMCH2PSysUpTime
         TimeTicks,
      pr1645v2TTmplPerfiMCH2PIfUpTime
         TimeTicks,
      pr1645v2TTmplPerfiMCH2PIfStatChanges
         Counter32,
      pr1645v2TTmplPerfiMCH2PIfInOctets
         Counter64,
      pr1645v2TTmplPerfiMCH2PIfInUCPkts
         Counter64,
      pr1645v2TTmplPerfiMCH2PIfInNUCPkts
         Counter64,
      pr1645v2TTmplPerfiMCH2PIfInBCPkts
         Counter64,
      pr1645v2TTmplPerfiMCH2PIfInMCPkts
         Counter64,
      pr1645v2TTmplPerfiMCH2PIfInDiscards
         Counter64,
      pr1645v2TTmplPerfiMCH2PIfInErrors
         Counter64,
      pr1645v2TTmplPerfiMCH2PIfInUnkwn
         Counter64,
      pr1645v2TTmplPerfiMCH2PInDropEx
         Counter64,
      pr1645v2TTmplPerfiMCH2PInDropNoMac
         Counter64,
      pr1645v2TTmplPerfiMCH2PInDropNUCast
         Counter64,
      pr1645v2TTmplPerfiMCH2PInDropFilter
         Counter64,
      pr1645v2TTmplPerfiMCH2PIfInBandwidth
         Integer32,
      pr1645v2TTmplPerfiMCH2PIfOutOctets
         Counter64,
      pr1645v2TTmplPerfiMCH2PIfOutUCPkts
         Counter64,
      pr1645v2TTmplPerfiMCH2PIfOutNUCPkts
         Counter64,
      pr1645v2TTmplPerfiMCH2PIfOutBCPkts
         Counter64,
      pr1645v2TTmplPerfiMCH2PIfOutMCPkts
         Counter64,
      pr1645v2TTmplPerfiMCH2PIfOutDiscards
         Counter64,
      pr1645v2TTmplPerfiMCH2PIfOutErrors
         Counter64,
      pr1645v2TTmplPerfiMCH2POutDropEx
         Counter64,
      pr1645v2TTmplPerfiMCH2POutDropNoArp
         Counter64,
      pr1645v2TTmplPerfiMCH2POutDropFilter
         Counter64,
      pr1645v2TTmplPerfiMCH2PIfOutBandwidth
         Integer32,
      pr1645v2TTmplPerfiMCH2PIfErrSec
         Counter32
      }

pr1645v2TTmplPerfiMCH2PTableIx OBJECT-TYPE
   SYNTAX      TableIndex
   MAX-ACCESS  not-accessible
   STATUS      current
   DESCRIPTION
      ""
   ::= {pr1645v2TTmplPerfiMCH2PEntry 11}

pr1645v2TTmplPerfiMCH2PSysUpTime OBJECT-TYPE
   SYNTAX      TimeTicks
   MAX-ACCESS  read-only
   STATUS      current
   DESCRIPTION
      "Path: tunnels.performance.ipsecL2tpTunnels.mibCounters.h2Performance.sysUpTime

       Time in centi-second."
   ::= {pr1645v2TTmplPerfiMCH2PEntry 16777216}

pr1645v2TTmplPerfiMCH2PIfUpTime OBJECT-TYPE
   SYNTAX      TimeTicks
   MAX-ACCESS  read-only
   STATUS      current
   DESCRIPTION
      "Path: tunnels.performance.ipsecL2tpTunnels.mibCounters.h2Performance.ifUpTime

       Time in centi-second."
   ::= {pr1645v2TTmplPerfiMCH2PEntry 33554432}

pr1645v2TTmplPerfiMCH2PIfStatChanges OBJECT-TYPE
   SYNTAX      Counter32
   MAX-ACCESS  read-only
   STATUS      current
   DESCRIPTION
      "Path: tunnels.performance.ipsecL2tpTunnels.mibCounters.h2Performance.ifStatusChanges

       32 bit unsigned wrappable counter."
   ::= {pr1645v2TTmplPerfiMCH2PEntry 50331648}

pr1645v2TTmplPerfiMCH2PIfInOctets OBJECT-TYPE
   SYNTAX      Counter64
   MAX-ACCESS  read-only
   STATUS      current
   DESCRIPTION
      "Path: tunnels.performance.ipsecL2tpTunnels.mibCounters.h2Performance.ifInOctets

       64 bit unsigned wrappable counter."
   ::= {pr1645v2TTmplPerfiMCH2PEntry 67108864}

pr1645v2TTmplPerfiMCH2PIfInUCPkts OBJECT-TYPE
   SYNTAX      Counter64
   MAX-ACCESS  read-only
   STATUS      current
   DESCRIPTION
      "Path: tunnels.performance.ipsecL2tpTunnels.mibCounters.h2Performance.ifInUcastPkts

       64 bit unsigned wrappable counter."
   ::= {pr1645v2TTmplPerfiMCH2PEntry 83886080}

pr1645v2TTmplPerfiMCH2PIfInNUCPkts OBJECT-TYPE
   SYNTAX      Counter64
   MAX-ACCESS  read-only
   STATUS      current
   DESCRIPTION
      "Path: tunnels.performance.ipsecL2tpTunnels.mibCounters.h2Performance.ifInNUcastPkts

       64 bit unsigned wrappable counter."
   ::= {pr1645v2TTmplPerfiMCH2PEntry 100663296}

pr1645v2TTmplPerfiMCH2PIfInBCPkts OBJECT-TYPE
   SYNTAX      Counter64
   MAX-ACCESS  read-only
   STATUS      current
   DESCRIPTION
      "Path: tunnels.performance.ipsecL2tpTunnels.mibCounters.h2Performance.ifInBcastPkts

       64 bit unsigned wrappable counter."
   ::= {pr1645v2TTmplPerfiMCH2PEntry 419430400}

pr1645v2TTmplPerfiMCH2PIfInMCPkts OBJECT-TYPE
   SYNTAX      Counter64
   MAX-ACCESS  read-only
   STATUS      current
   DESCRIPTION
      "Path: tunnels.performance.ipsecL2tpTunnels.mibCounters.h2Performance.ifInMcastPkts

       64 bit unsigned wrappable counter."
   ::= {pr1645v2TTmplPerfiMCH2PEntry 436207616}

pr1645v2TTmplPerfiMCH2PIfInDiscards OBJECT-TYPE
   SYNTAX      Counter64
   MAX-ACCESS  read-only
   STATUS      current
   DESCRIPTION
      "Path: tunnels.performance.ipsecL2tpTunnels.mibCounters.h2Performance.ifInDiscards

       64 bit unsigned wrappable counter."
   ::= {pr1645v2TTmplPerfiMCH2PEntry 117440512}

pr1645v2TTmplPerfiMCH2PIfInErrors OBJECT-TYPE
   SYNTAX      Counter64
   MAX-ACCESS  read-only
   STATUS      current
   DESCRIPTION
      "Path: tunnels.performance.ipsecL2tpTunnels.mibCounters.h2Performance.ifInErrors

       64 bit unsigned wrappable counter."
   ::= {pr1645v2TTmplPerfiMCH2PEntry 134217728}

pr1645v2TTmplPerfiMCH2PIfInUnkwn OBJECT-TYPE
   SYNTAX      Counter64
   MAX-ACCESS  read-only
   STATUS      current
   DESCRIPTION
      "Path: tunnels.performance.ipsecL2tpTunnels.mibCounters.h2Performance.ifInUnknownProtos

       64 bit unsigned wrappable counter."
   ::= {pr1645v2TTmplPerfiMCH2PEntry 150994944}

pr1645v2TTmplPerfiMCH2PInDropEx OBJECT-TYPE
   SYNTAX      Counter64
   MAX-ACCESS  read-only
   STATUS      current
   DESCRIPTION
      "Path: tunnels.performance.ipsecL2tpTunnels.mibCounters.h2Performance.ifInDropLevelExceeded

       64 bit unsigned wrappable counter."
   ::= {pr1645v2TTmplPerfiMCH2PEntry 335544320}

pr1645v2TTmplPerfiMCH2PInDropNoMac OBJECT-TYPE
   SYNTAX      Counter64
   MAX-ACCESS  read-only
   STATUS      current
   DESCRIPTION
      "Path: tunnels.performance.ipsecL2tpTunnels.mibCounters.h2Performance.fInDiscardsNoMacFit

       64 bit unsigned wrappable counter."
   ::= {pr1645v2TTmplPerfiMCH2PEntry 301989888}

pr1645v2TTmplPerfiMCH2PInDropNUCast OBJECT-TYPE
   SYNTAX      Counter64
   MAX-ACCESS  read-only
   STATUS      current
   DESCRIPTION
      "Path: tunnels.performance.ipsecL2tpTunnels.mibCounters.h2Performance.fInDiscardsNUCast

       64 bit unsigned wrappable counter."
   ::= {pr1645v2TTmplPerfiMCH2PEntry 318767104}

pr1645v2TTmplPerfiMCH2PInDropFilter OBJECT-TYPE
   SYNTAX      Counter64
   MAX-ACCESS  read-only
   STATUS      current
   DESCRIPTION
      "Path: tunnels.performance.ipsecL2tpTunnels.mibCounters.h2Performance.fInDiscardsFilter

       64 bit unsigned wrappable counter."
   ::= {pr1645v2TTmplPerfiMCH2PEntry 385875968}

pr1645v2TTmplPerfiMCH2PIfInBandwidth OBJECT-TYPE
   SYNTAX      Integer32
   MAX-ACCESS  read-only
   STATUS      current
   DESCRIPTION
      "Path: tunnels.performance.ipsecL2tpTunnels.mibCounters.h2Performance.ifInBandwidth

       unit name = bps
       formula = 8 * ; 8 /"
   ::= {pr1645v2TTmplPerfiMCH2PEntry 268435456}

pr1645v2TTmplPerfiMCH2PIfOutOctets OBJECT-TYPE
   SYNTAX      Counter64
   MAX-ACCESS  read-only
   STATUS      current
   DESCRIPTION
      "Path: tunnels.performance.ipsecL2tpTunnels.mibCounters.h2Performance.ifOutOctets

       64 bit unsigned wrappable counter."
   ::= {pr1645v2TTmplPerfiMCH2PEntry 167772160}

pr1645v2TTmplPerfiMCH2PIfOutUCPkts OBJECT-TYPE
   SYNTAX      Counter64
   MAX-ACCESS  read-only
   STATUS      current
   DESCRIPTION
      "Path: tunnels.performance.ipsecL2tpTunnels.mibCounters.h2Performance.ifOutUcastPkts

       64 bit unsigned wrappable counter."
   ::= {pr1645v2TTmplPerfiMCH2PEntry 184549376}

pr1645v2TTmplPerfiMCH2PIfOutNUCPkts OBJECT-TYPE
   SYNTAX      Counter64
   MAX-ACCESS  read-only
   STATUS      current
   DESCRIPTION
      "Path: tunnels.performance.ipsecL2tpTunnels.mibCounters.h2Performance.ifOutNUcastPkts

       64 bit unsigned wrappable counter."
   ::= {pr1645v2TTmplPerfiMCH2PEntry 201326592}

pr1645v2TTmplPerfiMCH2PIfOutBCPkts OBJECT-TYPE
   SYNTAX      Counter64
   MAX-ACCESS  read-only
   STATUS      current
   DESCRIPTION
      "Path: tunnels.performance.ipsecL2tpTunnels.mibCounters.h2Performance.ifOutBcastPkts

       64 bit unsigned wrappable counter."
   ::= {pr1645v2TTmplPerfiMCH2PEntry 452984832}

pr1645v2TTmplPerfiMCH2PIfOutMCPkts OBJECT-TYPE
   SYNTAX      Counter64
   MAX-ACCESS  read-only
   STATUS      current
   DESCRIPTION
      "Path: tunnels.performance.ipsecL2tpTunnels.mibCounters.h2Performance.ifOutMcastPkts

       64 bit unsigned wrappable counter."
   ::= {pr1645v2TTmplPerfiMCH2PEntry 469762048}

pr1645v2TTmplPerfiMCH2PIfOutDiscards OBJECT-TYPE
   SYNTAX      Counter64
   MAX-ACCESS  read-only
   STATUS      current
   DESCRIPTION
      "Path: tunnels.performance.ipsecL2tpTunnels.mibCounters.h2Performance.ifOutDiscards

       64 bit unsigned wrappable counter."
   ::= {pr1645v2TTmplPerfiMCH2PEntry 218103808}

pr1645v2TTmplPerfiMCH2PIfOutErrors OBJECT-TYPE
   SYNTAX      Counter64
   MAX-ACCESS  read-only
   STATUS      current
   DESCRIPTION
      "Path: tunnels.performance.ipsecL2tpTunnels.mibCounters.h2Performance.ifOutErrors

       64 bit unsigned wrappable counter."
   ::= {pr1645v2TTmplPerfiMCH2PEntry 234881024}

pr1645v2TTmplPerfiMCH2POutDropEx OBJECT-TYPE
   SYNTAX      Counter64
   MAX-ACCESS  read-only
   STATUS      current
   DESCRIPTION
      "Path: tunnels.performance.ipsecL2tpTunnels.mibCounters.h2Performance.ifOutDropLevelExceeded

       64 bit unsigned wrappable counter."
   ::= {pr1645v2TTmplPerfiMCH2PEntry 352321536}

pr1645v2TTmplPerfiMCH2POutDropNoArp OBJECT-TYPE
   SYNTAX      Counter64
   MAX-ACCESS  read-only
   STATUS      current
   DESCRIPTION
      "Path: tunnels.performance.ipsecL2tpTunnels.mibCounters.h2Performance.ifOutDiscardsNoArp

       64 bit unsigned wrappable counter."
   ::= {pr1645v2TTmplPerfiMCH2PEntry 369098752}

pr1645v2TTmplPerfiMCH2POutDropFilter OBJECT-TYPE
   SYNTAX      Counter64
   MAX-ACCESS  read-only
   STATUS      current
   DESCRIPTION
      "Path: tunnels.performance.ipsecL2tpTunnels.mibCounters.h2Performance.ifOutDiscardsFilter

       64 bit unsigned wrappable counter."
   ::= {pr1645v2TTmplPerfiMCH2PEntry 402653184}

pr1645v2TTmplPerfiMCH2PIfOutBandwidth OBJECT-TYPE
   SYNTAX      Integer32
   MAX-ACCESS  read-only
   STATUS      current
   DESCRIPTION
      "Path: tunnels.performance.ipsecL2tpTunnels.mibCounters.h2Performance.ifOutBandwidth

       unit name = bps
       formula = 8 * ; 8 /"
   ::= {pr1645v2TTmplPerfiMCH2PEntry 285212672}

pr1645v2TTmplPerfiMCH2PIfErrSec OBJECT-TYPE
   SYNTAX      Counter32
   MAX-ACCESS  read-only
   STATUS      current
   DESCRIPTION
      "Path: tunnels.performance.ipsecL2tpTunnels.mibCounters.h2Performance.ifErrSec

       32 bit unsigned wrappable counter."
   ::= {pr1645v2TTmplPerfiMCH2PEntry 251658240}

pr1645v2TTmplPerfiMCH24P OBJECT-TYPE
   SYNTAX      SEQUENCE OF Pr1645v2TTmplPerfiMCH24PEntry
   MAX-ACCESS  not-accessible
   STATUS      current
   DESCRIPTION
      ""
   ::= {pr1645v2TTmplPerfi 41615360}

pr1645v2TTmplPerfiMCH24PEntry OBJECT-TYPE
   SYNTAX      Pr1645v2TTmplPerfiMCH24PEntry
   MAX-ACCESS  not-accessible
   STATUS      current
   DESCRIPTION
      ""
   INDEX      { pr1645v2TTmplPerfiTableIx,
                pr1645v2TTmplPerfiMCH24PTableIx }
   ::= {pr1645v2TTmplPerfiMCH24P 1}

Pr1645v2TTmplPerfiMCH24PEntry ::=
   SEQUENCE
      {
      pr1645v2TTmplPerfiMCH24PTableIx
         TableIndex,
      pr1645v2TTmplPerfiMCH24PSysUpTime
         TimeTicks,
      pr1645v2TTmplPerfiMCH24PIfUpTime
         TimeTicks,
      pr1645v2TTmplPerfiMCH24PIfStatChanges
         Counter32,
      pr1645v2TTmplPerfiMCH24PIfInOctets
         Counter64,
      pr1645v2TTmplPerfiMCH24PIfInUCPkts
         Counter64,
      pr1645v2TTmplPerfiMCH24PIfInNUCPkts
         Counter64,
      pr1645v2TTmplPerfiMCH24PIfInBCPkts
         Counter64,
      pr1645v2TTmplPerfiMCH24PIfInMCPkts
         Counter64,
      pr1645v2TTmplPerfiMCH24PIfInDiscards
         Counter64,
      pr1645v2TTmplPerfiMCH24PIfInErrors
         Counter64,
      pr1645v2TTmplPerfiMCH24PIfInUnkwn
         Counter64,
      pr1645v2TTmplPerfiMCH24PInDropEx
         Counter64,
      pr1645v2TTmplPerfiMCH24PInDropNoMac
         Counter64,
      pr1645v2TTmplPerfiMCH24PInDropNUCast
         Counter64,
      pr1645v2TTmplPerfiMCH24PInDropFilter
         Counter64,
      pr1645v2TTmplPerfiMCH24PIfInBandwidth
         Integer32,
      pr1645v2TTmplPerfiMCH24PIfOutOctets
         Counter64,
      pr1645v2TTmplPerfiMCH24PIfOutUCPkts
         Counter64,
      pr1645v2TTmplPerfiMCH24PIfOutNUCPkts
         Counter64,
      pr1645v2TTmplPerfiMCH24PIfOutBCPkts
         Counter64,
      pr1645v2TTmplPerfiMCH24PIfOutMCPkts
         Counter64,
      pr1645v2TTmplPerfiMCH24PIfOutDiscards
         Counter64,
      pr1645v2TTmplPerfiMCH24PIfOutErrors
         Counter64,
      pr1645v2TTmplPerfiMCH24POutDropEx
         Counter64,
      pr1645v2TTmplPerfiMCH24POutDropNoArp
         Counter64,
      pr1645v2TTmplPerfiMCH24POutDropFilter
         Counter64,
      pr1645v2TTmplPerfiMCH24PIfOutBandwidth
         Integer32,
      pr1645v2TTmplPerfiMCH24PIfErrSec
         Counter32
      }

pr1645v2TTmplPerfiMCH24PTableIx OBJECT-TYPE
   SYNTAX      TableIndex
   MAX-ACCESS  not-accessible
   STATUS      current
   DESCRIPTION
      ""
   ::= {pr1645v2TTmplPerfiMCH24PEntry 11}

pr1645v2TTmplPerfiMCH24PSysUpTime OBJECT-TYPE
   SYNTAX      TimeTicks
   MAX-ACCESS  read-only
   STATUS      current
   DESCRIPTION
      "Path: tunnels.performance.ipsecL2tpTunnels.mibCounters.h24Performance.sysUpTime

       Time in centi-second."
   ::= {pr1645v2TTmplPerfiMCH24PEntry 16777216}

pr1645v2TTmplPerfiMCH24PIfUpTime OBJECT-TYPE
   SYNTAX      TimeTicks
   MAX-ACCESS  read-only
   STATUS      current
   DESCRIPTION
      "Path: tunnels.performance.ipsecL2tpTunnels.mibCounters.h24Performance.ifUpTime

       Time in centi-second."
   ::= {pr1645v2TTmplPerfiMCH24PEntry 33554432}

pr1645v2TTmplPerfiMCH24PIfStatChanges OBJECT-TYPE
   SYNTAX      Counter32
   MAX-ACCESS  read-only
   STATUS      current
   DESCRIPTION
      "Path: tunnels.performance.ipsecL2tpTunnels.mibCounters.h24Performance.ifStatusChanges

       32 bit unsigned wrappable counter."
   ::= {pr1645v2TTmplPerfiMCH24PEntry 50331648}

pr1645v2TTmplPerfiMCH24PIfInOctets OBJECT-TYPE
   SYNTAX      Counter64
   MAX-ACCESS  read-only
   STATUS      current
   DESCRIPTION
      "Path: tunnels.performance.ipsecL2tpTunnels.mibCounters.h24Performance.ifInOctets

       64 bit unsigned wrappable counter."
   ::= {pr1645v2TTmplPerfiMCH24PEntry 67108864}

pr1645v2TTmplPerfiMCH24PIfInUCPkts OBJECT-TYPE
   SYNTAX      Counter64
   MAX-ACCESS  read-only
   STATUS      current
   DESCRIPTION
      "Path: tunnels.performance.ipsecL2tpTunnels.mibCounters.h24Performance.ifInUcastPkts

       64 bit unsigned wrappable counter."
   ::= {pr1645v2TTmplPerfiMCH24PEntry 83886080}

pr1645v2TTmplPerfiMCH24PIfInNUCPkts OBJECT-TYPE
   SYNTAX      Counter64
   MAX-ACCESS  read-only
   STATUS      current
   DESCRIPTION
      "Path: tunnels.performance.ipsecL2tpTunnels.mibCounters.h24Performance.ifInNUcastPkts

       64 bit unsigned wrappable counter."
   ::= {pr1645v2TTmplPerfiMCH24PEntry 100663296}

pr1645v2TTmplPerfiMCH24PIfInBCPkts OBJECT-TYPE
   SYNTAX      Counter64
   MAX-ACCESS  read-only
   STATUS      current
   DESCRIPTION
      "Path: tunnels.performance.ipsecL2tpTunnels.mibCounters.h24Performance.ifInBcastPkts

       64 bit unsigned wrappable counter."
   ::= {pr1645v2TTmplPerfiMCH24PEntry 419430400}

pr1645v2TTmplPerfiMCH24PIfInMCPkts OBJECT-TYPE
   SYNTAX      Counter64
   MAX-ACCESS  read-only
   STATUS      current
   DESCRIPTION
      "Path: tunnels.performance.ipsecL2tpTunnels.mibCounters.h24Performance.ifInMcastPkts

       64 bit unsigned wrappable counter."
   ::= {pr1645v2TTmplPerfiMCH24PEntry 436207616}

pr1645v2TTmplPerfiMCH24PIfInDiscards OBJECT-TYPE
   SYNTAX      Counter64
   MAX-ACCESS  read-only
   STATUS      current
   DESCRIPTION
      "Path: tunnels.performance.ipsecL2tpTunnels.mibCounters.h24Performance.ifInDiscards

       64 bit unsigned wrappable counter."
   ::= {pr1645v2TTmplPerfiMCH24PEntry 117440512}

pr1645v2TTmplPerfiMCH24PIfInErrors OBJECT-TYPE
   SYNTAX      Counter64
   MAX-ACCESS  read-only
   STATUS      current
   DESCRIPTION
      "Path: tunnels.performance.ipsecL2tpTunnels.mibCounters.h24Performance.ifInErrors

       64 bit unsigned wrappable counter."
   ::= {pr1645v2TTmplPerfiMCH24PEntry 134217728}

pr1645v2TTmplPerfiMCH24PIfInUnkwn OBJECT-TYPE
   SYNTAX      Counter64
   MAX-ACCESS  read-only
   STATUS      current
   DESCRIPTION
      "Path: tunnels.performance.ipsecL2tpTunnels.mibCounters.h24Performance.ifInUnknownProtos

       64 bit unsigned wrappable counter."
   ::= {pr1645v2TTmplPerfiMCH24PEntry 150994944}

pr1645v2TTmplPerfiMCH24PInDropEx OBJECT-TYPE
   SYNTAX      Counter64
   MAX-ACCESS  read-only
   STATUS      current
   DESCRIPTION
      "Path: tunnels.performance.ipsecL2tpTunnels.mibCounters.h24Performance.ifInDropLevelExceeded

       64 bit unsigned wrappable counter."
   ::= {pr1645v2TTmplPerfiMCH24PEntry 335544320}

pr1645v2TTmplPerfiMCH24PInDropNoMac OBJECT-TYPE
   SYNTAX      Counter64
   MAX-ACCESS  read-only
   STATUS      current
   DESCRIPTION
      "Path: tunnels.performance.ipsecL2tpTunnels.mibCounters.h24Performance.fInDiscardsNoMacFit

       64 bit unsigned wrappable counter."
   ::= {pr1645v2TTmplPerfiMCH24PEntry 301989888}

pr1645v2TTmplPerfiMCH24PInDropNUCast OBJECT-TYPE
   SYNTAX      Counter64
   MAX-ACCESS  read-only
   STATUS      current
   DESCRIPTION
      "Path: tunnels.performance.ipsecL2tpTunnels.mibCounters.h24Performance.fInDiscardsNUCast

       64 bit unsigned wrappable counter."
   ::= {pr1645v2TTmplPerfiMCH24PEntry 318767104}

pr1645v2TTmplPerfiMCH24PInDropFilter OBJECT-TYPE
   SYNTAX      Counter64
   MAX-ACCESS  read-only
   STATUS      current
   DESCRIPTION
      "Path: tunnels.performance.ipsecL2tpTunnels.mibCounters.h24Performance.fInDiscardsFilter

       64 bit unsigned wrappable counter."
   ::= {pr1645v2TTmplPerfiMCH24PEntry 385875968}

pr1645v2TTmplPerfiMCH24PIfInBandwidth OBJECT-TYPE
   SYNTAX      Integer32
   MAX-ACCESS  read-only
   STATUS      current
   DESCRIPTION
      "Path: tunnels.performance.ipsecL2tpTunnels.mibCounters.h24Performance.ifInBandwidth

       unit name = bps
       formula = 8 * ; 8 /"
   ::= {pr1645v2TTmplPerfiMCH24PEntry 268435456}

pr1645v2TTmplPerfiMCH24PIfOutOctets OBJECT-TYPE
   SYNTAX      Counter64
   MAX-ACCESS  read-only
   STATUS      current
   DESCRIPTION
      "Path: tunnels.performance.ipsecL2tpTunnels.mibCounters.h24Performance.ifOutOctets

       64 bit unsigned wrappable counter."
   ::= {pr1645v2TTmplPerfiMCH24PEntry 167772160}

pr1645v2TTmplPerfiMCH24PIfOutUCPkts OBJECT-TYPE
   SYNTAX      Counter64
   MAX-ACCESS  read-only
   STATUS      current
   DESCRIPTION
      "Path: tunnels.performance.ipsecL2tpTunnels.mibCounters.h24Performance.ifOutUcastPkts

       64 bit unsigned wrappable counter."
   ::= {pr1645v2TTmplPerfiMCH24PEntry 184549376}

pr1645v2TTmplPerfiMCH24PIfOutNUCPkts OBJECT-TYPE
   SYNTAX      Counter64
   MAX-ACCESS  read-only
   STATUS      current
   DESCRIPTION
      "Path: tunnels.performance.ipsecL2tpTunnels.mibCounters.h24Performance.ifOutNUcastPkts

       64 bit unsigned wrappable counter."
   ::= {pr1645v2TTmplPerfiMCH24PEntry 201326592}

pr1645v2TTmplPerfiMCH24PIfOutBCPkts OBJECT-TYPE
   SYNTAX      Counter64
   MAX-ACCESS  read-only
   STATUS      current
   DESCRIPTION
      "Path: tunnels.performance.ipsecL2tpTunnels.mibCounters.h24Performance.ifOutBcastPkts

       64 bit unsigned wrappable counter."
   ::= {pr1645v2TTmplPerfiMCH24PEntry 452984832}

pr1645v2TTmplPerfiMCH24PIfOutMCPkts OBJECT-TYPE
   SYNTAX      Counter64
   MAX-ACCESS  read-only
   STATUS      current
   DESCRIPTION
      "Path: tunnels.performance.ipsecL2tpTunnels.mibCounters.h24Performance.ifOutMcastPkts

       64 bit unsigned wrappable counter."
   ::= {pr1645v2TTmplPerfiMCH24PEntry 469762048}

pr1645v2TTmplPerfiMCH24PIfOutDiscards OBJECT-TYPE
   SYNTAX      Counter64
   MAX-ACCESS  read-only
   STATUS      current
   DESCRIPTION
      "Path: tunnels.performance.ipsecL2tpTunnels.mibCounters.h24Performance.ifOutDiscards

       64 bit unsigned wrappable counter."
   ::= {pr1645v2TTmplPerfiMCH24PEntry 218103808}

pr1645v2TTmplPerfiMCH24PIfOutErrors OBJECT-TYPE
   SYNTAX      Counter64
   MAX-ACCESS  read-only
   STATUS      current
   DESCRIPTION
      "Path: tunnels.performance.ipsecL2tpTunnels.mibCounters.h24Performance.ifOutErrors

       64 bit unsigned wrappable counter."
   ::= {pr1645v2TTmplPerfiMCH24PEntry 234881024}

pr1645v2TTmplPerfiMCH24POutDropEx OBJECT-TYPE
   SYNTAX      Counter64
   MAX-ACCESS  read-only
   STATUS      current
   DESCRIPTION
      "Path: tunnels.performance.ipsecL2tpTunnels.mibCounters.h24Performance.ifOutDropLevelExceeded

       64 bit unsigned wrappable counter."
   ::= {pr1645v2TTmplPerfiMCH24PEntry 352321536}

pr1645v2TTmplPerfiMCH24POutDropNoArp OBJECT-TYPE
   SYNTAX      Counter64
   MAX-ACCESS  read-only
   STATUS      current
   DESCRIPTION
      "Path: tunnels.performance.ipsecL2tpTunnels.mibCounters.h24Performance.ifOutDiscardsNoArp

       64 bit unsigned wrappable counter."
   ::= {pr1645v2TTmplPerfiMCH24PEntry 369098752}

pr1645v2TTmplPerfiMCH24POutDropFilter OBJECT-TYPE
   SYNTAX      Counter64
   MAX-ACCESS  read-only
   STATUS      current
   DESCRIPTION
      "Path: tunnels.performance.ipsecL2tpTunnels.mibCounters.h24Performance.ifOutDiscardsFilter

       64 bit unsigned wrappable counter."
   ::= {pr1645v2TTmplPerfiMCH24PEntry 402653184}

pr1645v2TTmplPerfiMCH24PIfOutBandwidth OBJECT-TYPE
   SYNTAX      Integer32
   MAX-ACCESS  read-only
   STATUS      current
   DESCRIPTION
      "Path: tunnels.performance.ipsecL2tpTunnels.mibCounters.h24Performance.ifOutBandwidth

       unit name = bps
       formula = 8 * ; 8 /"
   ::= {pr1645v2TTmplPerfiMCH24PEntry 285212672}

pr1645v2TTmplPerfiMCH24PIfErrSec OBJECT-TYPE
   SYNTAX      Counter32
   MAX-ACCESS  read-only
   STATUS      current
   DESCRIPTION
      "Path: tunnels.performance.ipsecL2tpTunnels.mibCounters.h24Performance.ifErrSec

       32 bit unsigned wrappable counter."
   ::= {pr1645v2TTmplPerfiMCH24PEntry 251658240}

pr1645v2TTmplPerfiMCD7P OBJECT-TYPE
   SYNTAX      SEQUENCE OF Pr1645v2TTmplPerfiMCD7PEntry
   MAX-ACCESS  not-accessible
   STATUS      current
   DESCRIPTION
      ""
   ::= {pr1645v2TTmplPerfi 41680896}

pr1645v2TTmplPerfiMCD7PEntry OBJECT-TYPE
   SYNTAX      Pr1645v2TTmplPerfiMCD7PEntry
   MAX-ACCESS  not-accessible
   STATUS      current
   DESCRIPTION
      ""
   INDEX      { pr1645v2TTmplPerfiTableIx,
                pr1645v2TTmplPerfiMCD7PTableIx }
   ::= {pr1645v2TTmplPerfiMCD7P 1}

Pr1645v2TTmplPerfiMCD7PEntry ::=
   SEQUENCE
      {
      pr1645v2TTmplPerfiMCD7PTableIx
         TableIndex,
      pr1645v2TTmplPerfiMCD7PSysUpTime
         TimeTicks,
      pr1645v2TTmplPerfiMCD7PIfUpTime
         TimeTicks,
      pr1645v2TTmplPerfiMCD7PIfStatChanges
         Counter32,
      pr1645v2TTmplPerfiMCD7PIfInOctets
         Counter64,
      pr1645v2TTmplPerfiMCD7PIfInUCPkts
         Counter64,
      pr1645v2TTmplPerfiMCD7PIfInNUCPkts
         Counter64,
      pr1645v2TTmplPerfiMCD7PIfInBCPkts
         Counter64,
      pr1645v2TTmplPerfiMCD7PIfInMCPkts
         Counter64,
      pr1645v2TTmplPerfiMCD7PIfInDiscards
         Counter64,
      pr1645v2TTmplPerfiMCD7PIfInErrors
         Counter64,
      pr1645v2TTmplPerfiMCD7PIfInUnkwn
         Counter64,
      pr1645v2TTmplPerfiMCD7PInDropEx
         Counter64,
      pr1645v2TTmplPerfiMCD7PInDropNoMac
         Counter64,
      pr1645v2TTmplPerfiMCD7PInDropNUCast
         Counter64,
      pr1645v2TTmplPerfiMCD7PInDropFilter
         Counter64,
      pr1645v2TTmplPerfiMCD7PIfInBandwidth
         Integer32,
      pr1645v2TTmplPerfiMCD7PIfOutOctets
         Counter64,
      pr1645v2TTmplPerfiMCD7PIfOutUCPkts
         Counter64,
      pr1645v2TTmplPerfiMCD7PIfOutNUCPkts
         Counter64,
      pr1645v2TTmplPerfiMCD7PIfOutBCPkts
         Counter64,
      pr1645v2TTmplPerfiMCD7PIfOutMCPkts
         Counter64,
      pr1645v2TTmplPerfiMCD7PIfOutDiscards
         Counter64,
      pr1645v2TTmplPerfiMCD7PIfOutErrors
         Counter64,
      pr1645v2TTmplPerfiMCD7POutDropEx
         Counter64,
      pr1645v2TTmplPerfiMCD7POutDropNoArp
         Counter64,
      pr1645v2TTmplPerfiMCD7POutDropFilter
         Counter64,
      pr1645v2TTmplPerfiMCD7PIfOutBandwidth
         Integer32,
      pr1645v2TTmplPerfiMCD7PIfErrSec
         Counter32
      }

pr1645v2TTmplPerfiMCD7PTableIx OBJECT-TYPE
   SYNTAX      TableIndex
   MAX-ACCESS  not-accessible
   STATUS      current
   DESCRIPTION
      ""
   ::= {pr1645v2TTmplPerfiMCD7PEntry 11}

pr1645v2TTmplPerfiMCD7PSysUpTime OBJECT-TYPE
   SYNTAX      TimeTicks
   MAX-ACCESS  read-only
   STATUS      current
   DESCRIPTION
      "Path: tunnels.performance.ipsecL2tpTunnels.mibCounters.d7Performance.sysUpTime

       Time in centi-second."
   ::= {pr1645v2TTmplPerfiMCD7PEntry 16777216}

pr1645v2TTmplPerfiMCD7PIfUpTime OBJECT-TYPE
   SYNTAX      TimeTicks
   MAX-ACCESS  read-only
   STATUS      current
   DESCRIPTION
      "Path: tunnels.performance.ipsecL2tpTunnels.mibCounters.d7Performance.ifUpTime

       Time in centi-second."
   ::= {pr1645v2TTmplPerfiMCD7PEntry 33554432}

pr1645v2TTmplPerfiMCD7PIfStatChanges OBJECT-TYPE
   SYNTAX      Counter32
   MAX-ACCESS  read-only
   STATUS      current
   DESCRIPTION
      "Path: tunnels.performance.ipsecL2tpTunnels.mibCounters.d7Performance.ifStatusChanges

       32 bit unsigned wrappable counter."
   ::= {pr1645v2TTmplPerfiMCD7PEntry 50331648}

pr1645v2TTmplPerfiMCD7PIfInOctets OBJECT-TYPE
   SYNTAX      Counter64
   MAX-ACCESS  read-only
   STATUS      current
   DESCRIPTION
      "Path: tunnels.performance.ipsecL2tpTunnels.mibCounters.d7Performance.ifInOctets

       64 bit unsigned wrappable counter."
   ::= {pr1645v2TTmplPerfiMCD7PEntry 67108864}

pr1645v2TTmplPerfiMCD7PIfInUCPkts OBJECT-TYPE
   SYNTAX      Counter64
   MAX-ACCESS  read-only
   STATUS      current
   DESCRIPTION
      "Path: tunnels.performance.ipsecL2tpTunnels.mibCounters.d7Performance.ifInUcastPkts

       64 bit unsigned wrappable counter."
   ::= {pr1645v2TTmplPerfiMCD7PEntry 83886080}

pr1645v2TTmplPerfiMCD7PIfInNUCPkts OBJECT-TYPE
   SYNTAX      Counter64
   MAX-ACCESS  read-only
   STATUS      current
   DESCRIPTION
      "Path: tunnels.performance.ipsecL2tpTunnels.mibCounters.d7Performance.ifInNUcastPkts

       64 bit unsigned wrappable counter."
   ::= {pr1645v2TTmplPerfiMCD7PEntry 100663296}

pr1645v2TTmplPerfiMCD7PIfInBCPkts OBJECT-TYPE
   SYNTAX      Counter64
   MAX-ACCESS  read-only
   STATUS      current
   DESCRIPTION
      "Path: tunnels.performance.ipsecL2tpTunnels.mibCounters.d7Performance.ifInBcastPkts

       64 bit unsigned wrappable counter."
   ::= {pr1645v2TTmplPerfiMCD7PEntry 419430400}

pr1645v2TTmplPerfiMCD7PIfInMCPkts OBJECT-TYPE
   SYNTAX      Counter64
   MAX-ACCESS  read-only
   STATUS      current
   DESCRIPTION
      "Path: tunnels.performance.ipsecL2tpTunnels.mibCounters.d7Performance.ifInMcastPkts

       64 bit unsigned wrappable counter."
   ::= {pr1645v2TTmplPerfiMCD7PEntry 436207616}

pr1645v2TTmplPerfiMCD7PIfInDiscards OBJECT-TYPE
   SYNTAX      Counter64
   MAX-ACCESS  read-only
   STATUS      current
   DESCRIPTION
      "Path: tunnels.performance.ipsecL2tpTunnels.mibCounters.d7Performance.ifInDiscards

       64 bit unsigned wrappable counter."
   ::= {pr1645v2TTmplPerfiMCD7PEntry 117440512}

pr1645v2TTmplPerfiMCD7PIfInErrors OBJECT-TYPE
   SYNTAX      Counter64
   MAX-ACCESS  read-only
   STATUS      current
   DESCRIPTION
      "Path: tunnels.performance.ipsecL2tpTunnels.mibCounters.d7Performance.ifInErrors

       64 bit unsigned wrappable counter."
   ::= {pr1645v2TTmplPerfiMCD7PEntry 134217728}

pr1645v2TTmplPerfiMCD7PIfInUnkwn OBJECT-TYPE
   SYNTAX      Counter64
   MAX-ACCESS  read-only
   STATUS      current
   DESCRIPTION
      "Path: tunnels.performance.ipsecL2tpTunnels.mibCounters.d7Performance.ifInUnknownProtos

       64 bit unsigned wrappable counter."
   ::= {pr1645v2TTmplPerfiMCD7PEntry 150994944}

pr1645v2TTmplPerfiMCD7PInDropEx OBJECT-TYPE
   SYNTAX      Counter64
   MAX-ACCESS  read-only
   STATUS      current
   DESCRIPTION
      "Path: tunnels.performance.ipsecL2tpTunnels.mibCounters.d7Performance.ifInDropLevelExceeded

       64 bit unsigned wrappable counter."
   ::= {pr1645v2TTmplPerfiMCD7PEntry 335544320}

pr1645v2TTmplPerfiMCD7PInDropNoMac OBJECT-TYPE
   SYNTAX      Counter64
   MAX-ACCESS  read-only
   STATUS      current
   DESCRIPTION
      "Path: tunnels.performance.ipsecL2tpTunnels.mibCounters.d7Performance.fInDiscardsNoMacFit

       64 bit unsigned wrappable counter."
   ::= {pr1645v2TTmplPerfiMCD7PEntry 301989888}

pr1645v2TTmplPerfiMCD7PInDropNUCast OBJECT-TYPE
   SYNTAX      Counter64
   MAX-ACCESS  read-only
   STATUS      current
   DESCRIPTION
      "Path: tunnels.performance.ipsecL2tpTunnels.mibCounters.d7Performance.fInDiscardsNUCast

       64 bit unsigned wrappable counter."
   ::= {pr1645v2TTmplPerfiMCD7PEntry 318767104}

pr1645v2TTmplPerfiMCD7PInDropFilter OBJECT-TYPE
   SYNTAX      Counter64
   MAX-ACCESS  read-only
   STATUS      current
   DESCRIPTION
      "Path: tunnels.performance.ipsecL2tpTunnels.mibCounters.d7Performance.fInDiscardsFilter

       64 bit unsigned wrappable counter."
   ::= {pr1645v2TTmplPerfiMCD7PEntry 385875968}

pr1645v2TTmplPerfiMCD7PIfInBandwidth OBJECT-TYPE
   SYNTAX      Integer32
   MAX-ACCESS  read-only
   STATUS      current
   DESCRIPTION
      "Path: tunnels.performance.ipsecL2tpTunnels.mibCounters.d7Performance.ifInBandwidth

       unit name = bps
       formula = 8 * ; 8 /"
   ::= {pr1645v2TTmplPerfiMCD7PEntry 268435456}

pr1645v2TTmplPerfiMCD7PIfOutOctets OBJECT-TYPE
   SYNTAX      Counter64
   MAX-ACCESS  read-only
   STATUS      current
   DESCRIPTION
      "Path: tunnels.performance.ipsecL2tpTunnels.mibCounters.d7Performance.ifOutOctets

       64 bit unsigned wrappable counter."
   ::= {pr1645v2TTmplPerfiMCD7PEntry 167772160}

pr1645v2TTmplPerfiMCD7PIfOutUCPkts OBJECT-TYPE
   SYNTAX      Counter64
   MAX-ACCESS  read-only
   STATUS      current
   DESCRIPTION
      "Path: tunnels.performance.ipsecL2tpTunnels.mibCounters.d7Performance.ifOutUcastPkts

       64 bit unsigned wrappable counter."
   ::= {pr1645v2TTmplPerfiMCD7PEntry 184549376}

pr1645v2TTmplPerfiMCD7PIfOutNUCPkts OBJECT-TYPE
   SYNTAX      Counter64
   MAX-ACCESS  read-only
   STATUS      current
   DESCRIPTION
      "Path: tunnels.performance.ipsecL2tpTunnels.mibCounters.d7Performance.ifOutNUcastPkts

       64 bit unsigned wrappable counter."
   ::= {pr1645v2TTmplPerfiMCD7PEntry 201326592}

pr1645v2TTmplPerfiMCD7PIfOutBCPkts OBJECT-TYPE
   SYNTAX      Counter64
   MAX-ACCESS  read-only
   STATUS      current
   DESCRIPTION
      "Path: tunnels.performance.ipsecL2tpTunnels.mibCounters.d7Performance.ifOutBcastPkts

       64 bit unsigned wrappable counter."
   ::= {pr1645v2TTmplPerfiMCD7PEntry 452984832}

pr1645v2TTmplPerfiMCD7PIfOutMCPkts OBJECT-TYPE
   SYNTAX      Counter64
   MAX-ACCESS  read-only
   STATUS      current
   DESCRIPTION
      "Path: tunnels.performance.ipsecL2tpTunnels.mibCounters.d7Performance.ifOutMcastPkts

       64 bit unsigned wrappable counter."
   ::= {pr1645v2TTmplPerfiMCD7PEntry 469762048}

pr1645v2TTmplPerfiMCD7PIfOutDiscards OBJECT-TYPE
   SYNTAX      Counter64
   MAX-ACCESS  read-only
   STATUS      current
   DESCRIPTION
      "Path: tunnels.performance.ipsecL2tpTunnels.mibCounters.d7Performance.ifOutDiscards

       64 bit unsigned wrappable counter."
   ::= {pr1645v2TTmplPerfiMCD7PEntry 218103808}

pr1645v2TTmplPerfiMCD7PIfOutErrors OBJECT-TYPE
   SYNTAX      Counter64
   MAX-ACCESS  read-only
   STATUS      current
   DESCRIPTION
      "Path: tunnels.performance.ipsecL2tpTunnels.mibCounters.d7Performance.ifOutErrors

       64 bit unsigned wrappable counter."
   ::= {pr1645v2TTmplPerfiMCD7PEntry 234881024}

pr1645v2TTmplPerfiMCD7POutDropEx OBJECT-TYPE
   SYNTAX      Counter64
   MAX-ACCESS  read-only
   STATUS      current
   DESCRIPTION
      "Path: tunnels.performance.ipsecL2tpTunnels.mibCounters.d7Performance.ifOutDropLevelExceeded

       64 bit unsigned wrappable counter."
   ::= {pr1645v2TTmplPerfiMCD7PEntry 352321536}

pr1645v2TTmplPerfiMCD7POutDropNoArp OBJECT-TYPE
   SYNTAX      Counter64
   MAX-ACCESS  read-only
   STATUS      current
   DESCRIPTION
      "Path: tunnels.performance.ipsecL2tpTunnels.mibCounters.d7Performance.ifOutDiscardsNoArp

       64 bit unsigned wrappable counter."
   ::= {pr1645v2TTmplPerfiMCD7PEntry 369098752}

pr1645v2TTmplPerfiMCD7POutDropFilter OBJECT-TYPE
   SYNTAX      Counter64
   MAX-ACCESS  read-only
   STATUS      current
   DESCRIPTION
      "Path: tunnels.performance.ipsecL2tpTunnels.mibCounters.d7Performance.ifOutDiscardsFilter

       64 bit unsigned wrappable counter."
   ::= {pr1645v2TTmplPerfiMCD7PEntry 402653184}

pr1645v2TTmplPerfiMCD7PIfOutBandwidth OBJECT-TYPE
   SYNTAX      Integer32
   MAX-ACCESS  read-only
   STATUS      current
   DESCRIPTION
      "Path: tunnels.performance.ipsecL2tpTunnels.mibCounters.d7Performance.ifOutBandwidth

       unit name = bps
       formula = 8 * ; 8 /"
   ::= {pr1645v2TTmplPerfiMCD7PEntry 285212672}

pr1645v2TTmplPerfiMCD7PIfErrSec OBJECT-TYPE
   SYNTAX      Counter32
   MAX-ACCESS  read-only
   STATUS      current
   DESCRIPTION
      "Path: tunnels.performance.ipsecL2tpTunnels.mibCounters.d7Performance.ifErrSec

       32 bit unsigned wrappable counter."
   ::= {pr1645v2TTmplPerfiMCD7PEntry 251658240}

pr1645v2TTmplPerfiInPQs OBJECT-TYPE
   SYNTAX      SEQUENCE OF Pr1645v2TTmplPerfiInPQsEntry
   MAX-ACCESS  not-accessible
   STATUS      current
   DESCRIPTION
      ""
   ::= {pr1645v2TTmplPerfi 100663296}

pr1645v2TTmplPerfiInPQsEntry OBJECT-TYPE
   SYNTAX      Pr1645v2TTmplPerfiInPQsEntry
   MAX-ACCESS  not-accessible
   STATUS      current
   DESCRIPTION
      ""
   INDEX      { pr1645v2TTmplPerfiTableIx,
                pr1645v2TTmplPerfiInPQsTableIx }
   ::= {pr1645v2TTmplPerfiInPQs 1}

Pr1645v2TTmplPerfiInPQsEntry ::=
   SEQUENCE
      {
      pr1645v2TTmplPerfiInPQsTableIx
         TableIndex,
      pr1645v2TTmplPerfiInPQsName
         INTEGER,
      pr1645v2TTmplPerfiInPQsLength
         Integer32,
      pr1645v2TTmplPerfiInPQsOctetLength
         Integer32,
      pr1645v2TTmplPerfiInPQsRedLength
         Integer32,
      pr1645v2TTmplPerfiInPQsPacketsTotal
         Counter64,
      pr1645v2TTmplPerfiInPQsPacketsDirectTx
         Counter64,
      pr1645v2TTmplPerfiInPQsPacketsQueued
         Counter64,
      pr1645v2TTmplPerfiInPQsPacketsDropped
         Counter64,
      pr1645v2TTmplPerfiInPQsPacketsRedDropped
         Counter64,
      pr1645v2TTmplPerfiInPQsPacketsCirTx
         Counter64,
      pr1645v2TTmplPerfiInPQsPacketsEirTx
         Counter64,
      pr1645v2TTmplPerfiInPQsPacketsViolateTx
         Counter64,
      pr1645v2TTmplPerfiInPQsOctetsTotal
         Counter64,
      pr1645v2TTmplPerfiInPQsOctetsDirectTx
         Counter64,
      pr1645v2TTmplPerfiInPQsOctetsQueued
         Counter64,
      pr1645v2TTmplPerfiInPQsOctetsDropped
         Counter64,
      pr1645v2TTmplPerfiInPQsOctetsRedDropped
         Counter64,
      pr1645v2TTmplPerfiInPQsOctetsCirTx
         Counter64,
      pr1645v2TTmplPerfiInPQsOctetsEirTx
         Counter64,
      pr1645v2TTmplPerfiInPQsOctetsViolateTx
         Counter64,
      pr1645v2TTmplPerfiInPQsOctetsBandwidth15sec
         Integer32,
      pr1645v2TTmplPerfiInPQsOctetsBandwidth30sec
         Integer32,
      pr1645v2TTmplPerfiInPQsOctetsBandwidth1min
         Integer32,
      pr1645v2TTmplPerfiInPQsOctetsBandwidth2min
         Integer32,
      pr1645v2TTmplPerfiInPQsOctetsBandwidth5min
         Integer32
      }

pr1645v2TTmplPerfiInPQsTableIx OBJECT-TYPE
   SYNTAX      TableIndex
   MAX-ACCESS  not-accessible
   STATUS      current
   DESCRIPTION
      ""
   ::= {pr1645v2TTmplPerfiInPQsEntry 11}

pr1645v2TTmplPerfiInPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: tunnels.performance.ipsecL2tpTunnels.inPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2TTmplPerfiInPQsEntry 16777216}

pr1645v2TTmplPerfiInPQsLength OBJECT-TYPE
   SYNTAX      Integer32
   MAX-ACCESS  read-only
   STATUS      current
   DESCRIPTION
      "Path: tunnels.performance.ipsecL2tpTunnels.inPriorityQueues.length"
   ::= {pr1645v2TTmplPerfiInPQsEntry 33554432}

pr1645v2TTmplPerfiInPQsOctetLength OBJECT-TYPE
   SYNTAX      Integer32
   MAX-ACCESS  read-only
   STATUS      current
   DESCRIPTION
      "Path: tunnels.performance.ipsecL2tpTunnels.inPriorityQueues.octetLength"
   ::= {pr1645v2TTmplPerfiInPQsEntry 150994944}

pr1645v2TTmplPerfiInPQsRedLength OBJECT-TYPE
   SYNTAX      Integer32
   MAX-ACCESS  read-only
   STATUS      current
   DESCRIPTION
      "Path: tunnels.performance.ipsecL2tpTunnels.inPriorityQueues.redLength"
   ::= {pr1645v2TTmplPerfiInPQsEntry 134217728}

pr1645v2TTmplPerfiInPQsPacketsTotal OBJECT-TYPE
   SYNTAX      Counter64
   MAX-ACCESS  read-only
   STATUS      current
   DESCRIPTION
      "Path: tunnels.performance.ipsecL2tpTunnels.inPriorityQueues.packets.total

       64 bit unsigned wrappable counter."
   ::= {pr1645v2TTmplPerfiInPQsEntry 50790400}

pr1645v2TTmplPerfiInPQsPacketsDirectTx OBJECT-TYPE
   SYNTAX      Counter64
   MAX-ACCESS  read-only
   STATUS      current
   DESCRIPTION
      "Path: tunnels.performance.ipsecL2tpTunnels.inPriorityQueues.packets.directTx

       64 bit unsigned wrappable counter."
   ::= {pr1645v2TTmplPerfiInPQsEntry 50397184}

pr1645v2TTmplPerfiInPQsPacketsQueued OBJECT-TYPE
   SYNTAX      Counter64
   MAX-ACCESS  read-only
   STATUS      current
   DESCRIPTION
      "Path: tunnels.performance.ipsecL2tpTunnels.inPriorityQueues.packets.queued

       64 bit unsigned wrappable counter."
   ::= {pr1645v2TTmplPerfiInPQsEntry 50462720}

pr1645v2TTmplPerfiInPQsPacketsDropped OBJECT-TYPE
   SYNTAX      Counter64
   MAX-ACCESS  read-only
   STATUS      current
   DESCRIPTION
      "Path: tunnels.performance.ipsecL2tpTunnels.inPriorityQueues.packets.dropped

       64 bit unsigned wrappable counter."
   ::= {pr1645v2TTmplPerfiInPQsEntry 50528256}

pr1645v2TTmplPerfiInPQsPacketsRedDropped OBJECT-TYPE
   SYNTAX      Counter64
   MAX-ACCESS  read-only
   STATUS      current
   DESCRIPTION
      "Path: tunnels.performance.ipsecL2tpTunnels.inPriorityQueues.packets.redDropped

       64 bit unsigned wrappable counter."
   ::= {pr1645v2TTmplPerfiInPQsEntry 50724864}

pr1645v2TTmplPerfiInPQsPacketsCirTx OBJECT-TYPE
   SYNTAX      Counter64
   MAX-ACCESS  read-only
   STATUS      current
   DESCRIPTION
      "Path: tunnels.performance.ipsecL2tpTunnels.inPriorityQueues.packets.cirTx

       64 bit unsigned wrappable counter."
   ::= {pr1645v2TTmplPerfiInPQsEntry 50593792}

pr1645v2TTmplPerfiInPQsPacketsEirTx OBJECT-TYPE
   SYNTAX      Counter64
   MAX-ACCESS  read-only
   STATUS      current
   DESCRIPTION
      "Path: tunnels.performance.ipsecL2tpTunnels.inPriorityQueues.packets.eirTx

       64 bit unsigned wrappable counter."
   ::= {pr1645v2TTmplPerfiInPQsEntry 50659328}

pr1645v2TTmplPerfiInPQsPacketsViolateTx OBJECT-TYPE
   SYNTAX      Counter64
   MAX-ACCESS  read-only
   STATUS      current
   DESCRIPTION
      "Path: tunnels.performance.ipsecL2tpTunnels.inPriorityQueues.packets.violateTx

       64 bit unsigned wrappable counter."
   ::= {pr1645v2TTmplPerfiInPQsEntry 50855936}

pr1645v2TTmplPerfiInPQsOctetsTotal OBJECT-TYPE
   SYNTAX      Counter64
   MAX-ACCESS  read-only
   STATUS      current
   DESCRIPTION
      "Path: tunnels.performance.ipsecL2tpTunnels.inPriorityQueues.octets.total

       64 bit unsigned wrappable counter."
   ::= {pr1645v2TTmplPerfiInPQsEntry 67567616}

pr1645v2TTmplPerfiInPQsOctetsDirectTx OBJECT-TYPE
   SYNTAX      Counter64
   MAX-ACCESS  read-only
   STATUS      current
   DESCRIPTION
      "Path: tunnels.performance.ipsecL2tpTunnels.inPriorityQueues.octets.directTx

       64 bit unsigned wrappable counter."
   ::= {pr1645v2TTmplPerfiInPQsEntry 67174400}

pr1645v2TTmplPerfiInPQsOctetsQueued OBJECT-TYPE
   SYNTAX      Counter64
   MAX-ACCESS  read-only
   STATUS      current
   DESCRIPTION
      "Path: tunnels.performance.ipsecL2tpTunnels.inPriorityQueues.octets.queued

       64 bit unsigned wrappable counter."
   ::= {pr1645v2TTmplPerfiInPQsEntry 67239936}

pr1645v2TTmplPerfiInPQsOctetsDropped OBJECT-TYPE
   SYNTAX      Counter64
   MAX-ACCESS  read-only
   STATUS      current
   DESCRIPTION
      "Path: tunnels.performance.ipsecL2tpTunnels.inPriorityQueues.octets.dropped

       64 bit unsigned wrappable counter."
   ::= {pr1645v2TTmplPerfiInPQsEntry 67305472}

pr1645v2TTmplPerfiInPQsOctetsRedDropped OBJECT-TYPE
   SYNTAX      Counter64
   MAX-ACCESS  read-only
   STATUS      current
   DESCRIPTION
      "Path: tunnels.performance.ipsecL2tpTunnels.inPriorityQueues.octets.redDropped

       64 bit unsigned wrappable counter."
   ::= {pr1645v2TTmplPerfiInPQsEntry 67502080}

pr1645v2TTmplPerfiInPQsOctetsCirTx OBJECT-TYPE
   SYNTAX      Counter64
   MAX-ACCESS  read-only
   STATUS      current
   DESCRIPTION
      "Path: tunnels.performance.ipsecL2tpTunnels.inPriorityQueues.octets.cirTx

       64 bit unsigned wrappable counter."
   ::= {pr1645v2TTmplPerfiInPQsEntry 67371008}

pr1645v2TTmplPerfiInPQsOctetsEirTx OBJECT-TYPE
   SYNTAX      Counter64
   MAX-ACCESS  read-only
   STATUS      current
   DESCRIPTION
      "Path: tunnels.performance.ipsecL2tpTunnels.inPriorityQueues.octets.eirTx

       64 bit unsigned wrappable counter."
   ::= {pr1645v2TTmplPerfiInPQsEntry 67436544}

pr1645v2TTmplPerfiInPQsOctetsViolateTx OBJECT-TYPE
   SYNTAX      Counter64
   MAX-ACCESS  read-only
   STATUS      current
   DESCRIPTION
      "Path: tunnels.performance.ipsecL2tpTunnels.inPriorityQueues.octets.violateTx

       64 bit unsigned wrappable counter."
   ::= {pr1645v2TTmplPerfiInPQsEntry 67633152}

pr1645v2TTmplPerfiInPQsOctetsBandwidth15sec OBJECT-TYPE
   SYNTAX      Integer32
   MAX-ACCESS  read-only
   STATUS      current
   DESCRIPTION
      "Path: tunnels.performance.ipsecL2tpTunnels.inPriorityQueues.octets.bandwidth.15sec

       unit name = bps
       formula = 8 * ; 8 /"
   ::= {pr1645v2TTmplPerfiInPQsEntry 70386944}

pr1645v2TTmplPerfiInPQsOctetsBandwidth30sec OBJECT-TYPE
   SYNTAX      Integer32
   MAX-ACCESS  read-only
   STATUS      current
   DESCRIPTION
      "Path: tunnels.performance.ipsecL2tpTunnels.inPriorityQueues.octets.bandwidth.30sec

       unit name = bps
       formula = 8 * ; 8 /"
   ::= {pr1645v2TTmplPerfiInPQsEntry 70388224}

pr1645v2TTmplPerfiInPQsOctetsBandwidth1min OBJECT-TYPE
   SYNTAX      Integer32
   MAX-ACCESS  read-only
   STATUS      current
   DESCRIPTION
      "Path: tunnels.performance.ipsecL2tpTunnels.inPriorityQueues.octets.bandwidth.1min

       unit name = bps
       formula = 8 * ; 8 /"
   ::= {pr1645v2TTmplPerfiInPQsEntry 70390784}

pr1645v2TTmplPerfiInPQsOctetsBandwidth2min OBJECT-TYPE
   SYNTAX      Integer32
   MAX-ACCESS  read-only
   STATUS      current
   DESCRIPTION
      "Path: tunnels.performance.ipsecL2tpTunnels.inPriorityQueues.octets.bandwidth.2min

       unit name = bps
       formula = 8 * ; 8 /"
   ::= {pr1645v2TTmplPerfiInPQsEntry 70395904}

pr1645v2TTmplPerfiInPQsOctetsBandwidth5min OBJECT-TYPE
   SYNTAX      Integer32
   MAX-ACCESS  read-only
   STATUS      current
   DESCRIPTION
      "Path: tunnels.performance.ipsecL2tpTunnels.inPriorityQueues.octets.bandwidth.5min

       unit name = bps
       formula = 8 * ; 8 /"
   ::= {pr1645v2TTmplPerfiInPQsEntry 70411264}

pr1645v2TTmplPerfiInPQsH2Performance OBJECT-TYPE
   SYNTAX      SEQUENCE OF Pr1645v2TTmplPerfiInPQsH2PerformanceEntry
   MAX-ACCESS  not-accessible
   STATUS      current
   DESCRIPTION
      ""
   ::= {pr1645v2TTmplPerfi 100990976}

pr1645v2TTmplPerfiInPQsH2PerformanceEntry OBJECT-TYPE
   SYNTAX      Pr1645v2TTmplPerfiInPQsH2PerformanceEntry
   MAX-ACCESS  not-accessible
   STATUS      current
   DESCRIPTION
      ""
   INDEX      { pr1645v2TTmplPerfiTableIx,
                pr1645v2TTmplPerfiInPQsTableIx,
                pr1645v2TTmplPerfiInPQsH2PerformanceTableIx }
   ::= {pr1645v2TTmplPerfiInPQsH2Performance 1}

Pr1645v2TTmplPerfiInPQsH2PerformanceEntry ::=
   SEQUENCE
      {
      pr1645v2TTmplPerfiInPQsH2PerformanceTableIx
         TableIndex,
      pr1645v2TTmplPerfiInPQsH2PerformanceSysUpTime
         TimeTicks,
      pr1645v2TTmplPerfiInPQsH2PerformanceTotPkts
         Counter64,
      pr1645v2TTmplPerfiInPQsH2PerformanceDirTxPkts
         Counter64,
      pr1645v2TTmplPerfiInPQsH2PerformanceQdPkts
         Counter64,
      pr1645v2TTmplPerfiInPQsH2PerformanceDropPkts
         Counter64,
      pr1645v2TTmplPerfiInPQsH2PerformanceRDropPkts
         Counter64,
      pr1645v2TTmplPerfiInPQsH2PerformanceCirTxPkts
         Counter64,
      pr1645v2TTmplPerfiInPQsH2PerformanceEirTxPkts
         Counter64,
      pr1645v2TTmplPerfiInPQsH2PerformanceViolTxPkts
         Counter64,
      pr1645v2TTmplPerfiInPQsH2PerformanceTotOcts
         Counter64,
      pr1645v2TTmplPerfiInPQsH2PerformanceDirTxOcts
         Counter64,
      pr1645v2TTmplPerfiInPQsH2PerformanceQdOcts
         Counter64,
      pr1645v2TTmplPerfiInPQsH2PerformanceDropOcts
         Counter64,
      pr1645v2TTmplPerfiInPQsH2PerformanceRDropOcts
         Counter64,
      pr1645v2TTmplPerfiInPQsH2PerformanceCirTxOcts
         Counter64,
      pr1645v2TTmplPerfiInPQsH2PerformanceEirTxOcts
         Counter64,
      pr1645v2TTmplPerfiInPQsH2PerformanceViolTxOcts
         Counter64,
      pr1645v2TTmplPerfiInPQsH2PerformanceBandwidth
         Integer32
      }

pr1645v2TTmplPerfiInPQsH2PerformanceTableIx OBJECT-TYPE
   SYNTAX      TableIndex
   MAX-ACCESS  not-accessible
   STATUS      current
   DESCRIPTION
      ""
   ::= {pr1645v2TTmplPerfiInPQsH2PerformanceEntry 11}

pr1645v2TTmplPerfiInPQsH2PerformanceSysUpTime OBJECT-TYPE
   SYNTAX      TimeTicks
   MAX-ACCESS  read-only
   STATUS      current
   DESCRIPTION
      "Path: tunnels.performance.ipsecL2tpTunnels.inPriorityQueues.h2Performance.sysUpTime

       Time in centi-second."
   ::= {pr1645v2TTmplPerfiInPQsH2PerformanceEntry 16777216}

pr1645v2TTmplPerfiInPQsH2PerformanceTotPkts OBJECT-TYPE
   SYNTAX      Counter64
   MAX-ACCESS  read-only
   STATUS      current
   DESCRIPTION
      "Path: tunnels.performance.ipsecL2tpTunnels.inPriorityQueues.h2Performance.totalPkts

       64 bit unsigned wrappable counter."
   ::= {pr1645v2TTmplPerfiInPQsH2PerformanceEntry 234881024}

pr1645v2TTmplPerfiInPQsH2PerformanceDirTxPkts OBJECT-TYPE
   SYNTAX      Counter64
   MAX-ACCESS  read-only
   STATUS      current
   DESCRIPTION
      "Path: tunnels.performance.ipsecL2tpTunnels.inPriorityQueues.h2Performance.directTxPkts

       64 bit unsigned wrappable counter."
   ::= {pr1645v2TTmplPerfiInPQsH2PerformanceEntry 33554432}

pr1645v2TTmplPerfiInPQsH2PerformanceQdPkts OBJECT-TYPE
   SYNTAX      Counter64
   MAX-ACCESS  read-only
   STATUS      current
   DESCRIPTION
      "Path: tunnels.performance.ipsecL2tpTunnels.inPriorityQueues.h2Performance.queuedPkts

       64 bit unsigned wrappable counter."
   ::= {pr1645v2TTmplPerfiInPQsH2PerformanceEntry 50331648}

pr1645v2TTmplPerfiInPQsH2PerformanceDropPkts OBJECT-TYPE
   SYNTAX      Counter64
   MAX-ACCESS  read-only
   STATUS      current
   DESCRIPTION
      "Path: tunnels.performance.ipsecL2tpTunnels.inPriorityQueues.h2Performance.droppedPkts

       64 bit unsigned wrappable counter."
   ::= {pr1645v2TTmplPerfiInPQsH2PerformanceEntry 67108864}

pr1645v2TTmplPerfiInPQsH2PerformanceRDropPkts OBJECT-TYPE
   SYNTAX      Counter64
   MAX-ACCESS  read-only
   STATUS      current
   DESCRIPTION
      "Path: tunnels.performance.ipsecL2tpTunnels.inPriorityQueues.h2Performance.redDroppedPkts

       64 bit unsigned wrappable counter."
   ::= {pr1645v2TTmplPerfiInPQsH2PerformanceEntry 201326592}

pr1645v2TTmplPerfiInPQsH2PerformanceCirTxPkts OBJECT-TYPE
   SYNTAX      Counter64
   MAX-ACCESS  read-only
   STATUS      current
   DESCRIPTION
      "Path: tunnels.performance.ipsecL2tpTunnels.inPriorityQueues.h2Performance.cirTxPkts

       64 bit unsigned wrappable counter."
   ::= {pr1645v2TTmplPerfiInPQsH2PerformanceEntry 83886080}

pr1645v2TTmplPerfiInPQsH2PerformanceEirTxPkts OBJECT-TYPE
   SYNTAX      Counter64
   MAX-ACCESS  read-only
   STATUS      current
   DESCRIPTION
      "Path: tunnels.performance.ipsecL2tpTunnels.inPriorityQueues.h2Performance.eirTxPkts

       64 bit unsigned wrappable counter."
   ::= {pr1645v2TTmplPerfiInPQsH2PerformanceEntry 100663296}

pr1645v2TTmplPerfiInPQsH2PerformanceViolTxPkts OBJECT-TYPE
   SYNTAX      Counter64
   MAX-ACCESS  read-only
   STATUS      current
   DESCRIPTION
      "Path: tunnels.performance.ipsecL2tpTunnels.inPriorityQueues.h2Performance.violateTxPkts

       64 bit unsigned wrappable counter."
   ::= {pr1645v2TTmplPerfiInPQsH2PerformanceEntry 301989888}

pr1645v2TTmplPerfiInPQsH2PerformanceTotOcts OBJECT-TYPE
   SYNTAX      Counter64
   MAX-ACCESS  read-only
   STATUS      current
   DESCRIPTION
      "Path: tunnels.performance.ipsecL2tpTunnels.inPriorityQueues.h2Performance.totalOctets

       64 bit unsigned wrappable counter."
   ::= {pr1645v2TTmplPerfiInPQsH2PerformanceEntry 251658240}

pr1645v2TTmplPerfiInPQsH2PerformanceDirTxOcts OBJECT-TYPE
   SYNTAX      Counter64
   MAX-ACCESS  read-only
   STATUS      current
   DESCRIPTION
      "Path: tunnels.performance.ipsecL2tpTunnels.inPriorityQueues.h2Performance.directTxOctets

       64 bit unsigned wrappable counter."
   ::= {pr1645v2TTmplPerfiInPQsH2PerformanceEntry 117440512}

pr1645v2TTmplPerfiInPQsH2PerformanceQdOcts OBJECT-TYPE
   SYNTAX      Counter64
   MAX-ACCESS  read-only
   STATUS      current
   DESCRIPTION
      "Path: tunnels.performance.ipsecL2tpTunnels.inPriorityQueues.h2Performance.queuedOctets

       64 bit unsigned wrappable counter."
   ::= {pr1645v2TTmplPerfiInPQsH2PerformanceEntry 134217728}

pr1645v2TTmplPerfiInPQsH2PerformanceDropOcts OBJECT-TYPE
   SYNTAX      Counter64
   MAX-ACCESS  read-only
   STATUS      current
   DESCRIPTION
      "Path: tunnels.performance.ipsecL2tpTunnels.inPriorityQueues.h2Performance.droppedOctets

       64 bit unsigned wrappable counter."
   ::= {pr1645v2TTmplPerfiInPQsH2PerformanceEntry 150994944}

pr1645v2TTmplPerfiInPQsH2PerformanceRDropOcts OBJECT-TYPE
   SYNTAX      Counter64
   MAX-ACCESS  read-only
   STATUS      current
   DESCRIPTION
      "Path: tunnels.performance.ipsecL2tpTunnels.inPriorityQueues.h2Performance.redDroppedOctets

       64 bit unsigned wrappable counter."
   ::= {pr1645v2TTmplPerfiInPQsH2PerformanceEntry 218103808}

pr1645v2TTmplPerfiInPQsH2PerformanceCirTxOcts OBJECT-TYPE
   SYNTAX      Counter64
   MAX-ACCESS  read-only
   STATUS      current
   DESCRIPTION
      "Path: tunnels.performance.ipsecL2tpTunnels.inPriorityQueues.h2Performance.cirTxOctets

       64 bit unsigned wrappable counter."
   ::= {pr1645v2TTmplPerfiInPQsH2PerformanceEntry 167772160}

pr1645v2TTmplPerfiInPQsH2PerformanceEirTxOcts OBJECT-TYPE
   SYNTAX      Counter64
   MAX-ACCESS  read-only
   STATUS      current
   DESCRIPTION
      "Path: tunnels.performance.ipsecL2tpTunnels.inPriorityQueues.h2Performance.eirTxOctets

       64 bit unsigned wrappable counter."
   ::= {pr1645v2TTmplPerfiInPQsH2PerformanceEntry 184549376}

pr1645v2TTmplPerfiInPQsH2PerformanceViolTxOcts OBJECT-TYPE
   SYNTAX      Counter64
   MAX-ACCESS  read-only
   STATUS      current
   DESCRIPTION
      "Path: tunnels.performance.ipsecL2tpTunnels.inPriorityQueues.h2Performance.violateTxOctets

       64 bit unsigned wrappable counter."
   ::= {pr1645v2TTmplPerfiInPQsH2PerformanceEntry 318767104}

pr1645v2TTmplPerfiInPQsH2PerformanceBandwidth OBJECT-TYPE
   SYNTAX      Integer32
   MAX-ACCESS  read-only
   STATUS      current
   DESCRIPTION
      "Path: tunnels.performance.ipsecL2tpTunnels.inPriorityQueues.h2Performance.bandwidth

       unit name = bps
       formula = 8 * ; 8 /"
   ::= {pr1645v2TTmplPerfiInPQsH2PerformanceEntry 268435456}

pr1645v2TTmplPerfiInPQsH24Performance OBJECT-TYPE
   SYNTAX      SEQUENCE OF Pr1645v2TTmplPerfiInPQsH24PerformanceEntry
   MAX-ACCESS  not-accessible
   STATUS      current
   DESCRIPTION
      ""
   ::= {pr1645v2TTmplPerfi 101056512}

pr1645v2TTmplPerfiInPQsH24PerformanceEntry OBJECT-TYPE
   SYNTAX      Pr1645v2TTmplPerfiInPQsH24PerformanceEntry
   MAX-ACCESS  not-accessible
   STATUS      current
   DESCRIPTION
      ""
   INDEX      { pr1645v2TTmplPerfiTableIx,
                pr1645v2TTmplPerfiInPQsTableIx,
                pr1645v2TTmplPerfiInPQsH24PerformanceTableIx }
   ::= {pr1645v2TTmplPerfiInPQsH24Performance 1}

Pr1645v2TTmplPerfiInPQsH24PerformanceEntry ::=
   SEQUENCE
      {
      pr1645v2TTmplPerfiInPQsH24PerformanceTableIx
         TableIndex,
      pr1645v2TTmplPerfiInPQsH24PerformanceSysUpTime
         TimeTicks,
      pr1645v2TTmplPerfiInPQsH24PerformanceTotPkts
         Counter64,
      pr1645v2TTmplPerfiInPQsH24PerformanceDirTxPkts
         Counter64,
      pr1645v2TTmplPerfiInPQsH24PerformanceQdPkts
         Counter64,
      pr1645v2TTmplPerfiInPQsH24PerformanceDropPkts
         Counter64,
      pr1645v2TTmplPerfiInPQsH24PerformanceRDropPkts
         Counter64,
      pr1645v2TTmplPerfiInPQsH24PerformanceCirTxPkts
         Counter64,
      pr1645v2TTmplPerfiInPQsH24PerformanceEirTxPkts
         Counter64,
      pr1645v2TTmplPerfiInPQsH24PerformanceViolTxPkts
         Counter64,
      pr1645v2TTmplPerfiInPQsH24PerformanceTotOcts
         Counter64,
      pr1645v2TTmplPerfiInPQsH24PerformanceDirTxOcts
         Counter64,
      pr1645v2TTmplPerfiInPQsH24PerformanceQdOcts
         Counter64,
      pr1645v2TTmplPerfiInPQsH24PerformanceDropOcts
         Counter64,
      pr1645v2TTmplPerfiInPQsH24PerformanceRDropOcts
         Counter64,
      pr1645v2TTmplPerfiInPQsH24PerformanceCirTxOcts
         Counter64,
      pr1645v2TTmplPerfiInPQsH24PerformanceEirTxOcts
         Counter64,
      pr1645v2TTmplPerfiInPQsH24PerformanceViolTxOcts
         Counter64,
      pr1645v2TTmplPerfiInPQsH24PerformanceBandwidth
         Integer32
      }

pr1645v2TTmplPerfiInPQsH24PerformanceTableIx OBJECT-TYPE
   SYNTAX      TableIndex
   MAX-ACCESS  not-accessible
   STATUS      current
   DESCRIPTION
      ""
   ::= {pr1645v2TTmplPerfiInPQsH24PerformanceEntry 11}

pr1645v2TTmplPerfiInPQsH24PerformanceSysUpTime OBJECT-TYPE
   SYNTAX      TimeTicks
   MAX-ACCESS  read-only
   STATUS      current
   DESCRIPTION
      "Path: tunnels.performance.ipsecL2tpTunnels.inPriorityQueues.h24Performance.sysUpTime

       Time in centi-second."
   ::= {pr1645v2TTmplPerfiInPQsH24PerformanceEntry 16777216}

pr1645v2TTmplPerfiInPQsH24PerformanceTotPkts OBJECT-TYPE
   SYNTAX      Counter64
   MAX-ACCESS  read-only
   STATUS      current
   DESCRIPTION
      "Path: tunnels.performance.ipsecL2tpTunnels.inPriorityQueues.h24Performance.totalPkts

       64 bit unsigned wrappable counter."
   ::= {pr1645v2TTmplPerfiInPQsH24PerformanceEntry 234881024}

pr1645v2TTmplPerfiInPQsH24PerformanceDirTxPkts OBJECT-TYPE
   SYNTAX      Counter64
   MAX-ACCESS  read-only
   STATUS      current
   DESCRIPTION
      "Path: tunnels.performance.ipsecL2tpTunnels.inPriorityQueues.h24Performance.directTxPkts

       64 bit unsigned wrappable counter."
   ::= {pr1645v2TTmplPerfiInPQsH24PerformanceEntry 33554432}

pr1645v2TTmplPerfiInPQsH24PerformanceQdPkts OBJECT-TYPE
   SYNTAX      Counter64
   MAX-ACCESS  read-only
   STATUS      current
   DESCRIPTION
      "Path: tunnels.performance.ipsecL2tpTunnels.inPriorityQueues.h24Performance.queuedPkts

       64 bit unsigned wrappable counter."
   ::= {pr1645v2TTmplPerfiInPQsH24PerformanceEntry 50331648}

pr1645v2TTmplPerfiInPQsH24PerformanceDropPkts OBJECT-TYPE
   SYNTAX      Counter64
   MAX-ACCESS  read-only
   STATUS      current
   DESCRIPTION
      "Path: tunnels.performance.ipsecL2tpTunnels.inPriorityQueues.h24Performance.droppedPkts

       64 bit unsigned wrappable counter."
   ::= {pr1645v2TTmplPerfiInPQsH24PerformanceEntry 67108864}

pr1645v2TTmplPerfiInPQsH24PerformanceRDropPkts OBJECT-TYPE
   SYNTAX      Counter64
   MAX-ACCESS  read-only
   STATUS      current
   DESCRIPTION
      "Path: tunnels.performance.ipsecL2tpTunnels.inPriorityQueues.h24Performance.redDroppedPkts

       64 bit unsigned wrappable counter."
   ::= {pr1645v2TTmplPerfiInPQsH24PerformanceEntry 201326592}

pr1645v2TTmplPerfiInPQsH24PerformanceCirTxPkts OBJECT-TYPE
   SYNTAX      Counter64
   MAX-ACCESS  read-only
   STATUS      current
   DESCRIPTION
      "Path: tunnels.performance.ipsecL2tpTunnels.inPriorityQueues.h24Performance.cirTxPkts

       64 bit unsigned wrappable counter."
   ::= {pr1645v2TTmplPerfiInPQsH24PerformanceEntry 83886080}

pr1645v2TTmplPerfiInPQsH24PerformanceEirTxPkts OBJECT-TYPE
   SYNTAX      Counter64
   MAX-ACCESS  read-only
   STATUS      current
   DESCRIPTION
      "Path: tunnels.performance.ipsecL2tpTunnels.inPriorityQueues.h24Performance.eirTxPkts

       64 bit unsigned wrappable counter."
   ::= {pr1645v2TTmplPerfiInPQsH24PerformanceEntry 100663296}

pr1645v2TTmplPerfiInPQsH24PerformanceViolTxPkts OBJECT-TYPE
   SYNTAX      Counter64
   MAX-ACCESS  read-only
   STATUS      current
   DESCRIPTION
      "Path: tunnels.performance.ipsecL2tpTunnels.inPriorityQueues.h24Performance.violateTxPkts

       64 bit unsigned wrappable counter."
   ::= {pr1645v2TTmplPerfiInPQsH24PerformanceEntry 301989888}

pr1645v2TTmplPerfiInPQsH24PerformanceTotOcts OBJECT-TYPE
   SYNTAX      Counter64
   MAX-ACCESS  read-only
   STATUS      current
   DESCRIPTION
      "Path: tunnels.performance.ipsecL2tpTunnels.inPriorityQueues.h24Performance.totalOctets

       64 bit unsigned wrappable counter."
   ::= {pr1645v2TTmplPerfiInPQsH24PerformanceEntry 251658240}

pr1645v2TTmplPerfiInPQsH24PerformanceDirTxOcts OBJECT-TYPE
   SYNTAX      Counter64
   MAX-ACCESS  read-only
   STATUS      current
   DESCRIPTION
      "Path: tunnels.performance.ipsecL2tpTunnels.inPriorityQueues.h24Performance.directTxOctets

       64 bit unsigned wrappable counter."
   ::= {pr1645v2TTmplPerfiInPQsH24PerformanceEntry 117440512}

pr1645v2TTmplPerfiInPQsH24PerformanceQdOcts OBJECT-TYPE
   SYNTAX      Counter64
   MAX-ACCESS  read-only
   STATUS      current
   DESCRIPTION
      "Path: tunnels.performance.ipsecL2tpTunnels.inPriorityQueues.h24Performance.queuedOctets

       64 bit unsigned wrappable counter."
   ::= {pr1645v2TTmplPerfiInPQsH24PerformanceEntry 134217728}

pr1645v2TTmplPerfiInPQsH24PerformanceDropOcts OBJECT-TYPE
   SYNTAX      Counter64
   MAX-ACCESS  read-only
   STATUS      current
   DESCRIPTION
      "Path: tunnels.performance.ipsecL2tpTunnels.inPriorityQueues.h24Performance.droppedOctets

       64 bit unsigned wrappable counter."
   ::= {pr1645v2TTmplPerfiInPQsH24PerformanceEntry 150994944}

pr1645v2TTmplPerfiInPQsH24PerformanceRDropOcts OBJECT-TYPE
   SYNTAX      Counter64
   MAX-ACCESS  read-only
   STATUS      current
   DESCRIPTION
      "Path: tunnels.performance.ipsecL2tpTunnels.inPriorityQueues.h24Performance.redDroppedOctets

       64 bit unsigned wrappable counter."
   ::= {pr1645v2TTmplPerfiInPQsH24PerformanceEntry 218103808}

pr1645v2TTmplPerfiInPQsH24PerformanceCirTxOcts OBJECT-TYPE
   SYNTAX      Counter64
   MAX-ACCESS  read-only
   STATUS      current
   DESCRIPTION
      "Path: tunnels.performance.ipsecL2tpTunnels.inPriorityQueues.h24Performance.cirTxOctets

       64 bit unsigned wrappable counter."
   ::= {pr1645v2TTmplPerfiInPQsH24PerformanceEntry 167772160}

pr1645v2TTmplPerfiInPQsH24PerformanceEirTxOcts OBJECT-TYPE
   SYNTAX      Counter64
   MAX-ACCESS  read-only
   STATUS      current
   DESCRIPTION
      "Path: tunnels.performance.ipsecL2tpTunnels.inPriorityQueues.h24Performance.eirTxOctets

       64 bit unsigned wrappable counter."
   ::= {pr1645v2TTmplPerfiInPQsH24PerformanceEntry 184549376}

pr1645v2TTmplPerfiInPQsH24PerformanceViolTxOcts OBJECT-TYPE
   SYNTAX      Counter64
   MAX-ACCESS  read-only
   STATUS      current
   DESCRIPTION
      "Path: tunnels.performance.ipsecL2tpTunnels.inPriorityQueues.h24Performance.violateTxOctets

       64 bit unsigned wrappable counter."
   ::= {pr1645v2TTmplPerfiInPQsH24PerformanceEntry 318767104}

pr1645v2TTmplPerfiInPQsH24PerformanceBandwidth OBJECT-TYPE
   SYNTAX      Integer32
   MAX-ACCESS  read-only
   STATUS      current
   DESCRIPTION
      "Path: tunnels.performance.ipsecL2tpTunnels.inPriorityQueues.h24Performance.bandwidth

       unit name = bps
       formula = 8 * ; 8 /"
   ::= {pr1645v2TTmplPerfiInPQsH24PerformanceEntry 268435456}

pr1645v2TTmplPerfiInPQsD7Performance OBJECT-TYPE
   SYNTAX      SEQUENCE OF Pr1645v2TTmplPerfiInPQsD7PerformanceEntry
   MAX-ACCESS  not-accessible
   STATUS      current
   DESCRIPTION
      ""
   ::= {pr1645v2TTmplPerfi 101122048}

pr1645v2TTmplPerfiInPQsD7PerformanceEntry OBJECT-TYPE
   SYNTAX      Pr1645v2TTmplPerfiInPQsD7PerformanceEntry
   MAX-ACCESS  not-accessible
   STATUS      current
   DESCRIPTION
      ""
   INDEX      { pr1645v2TTmplPerfiTableIx,
                pr1645v2TTmplPerfiInPQsTableIx,
                pr1645v2TTmplPerfiInPQsD7PerformanceTableIx }
   ::= {pr1645v2TTmplPerfiInPQsD7Performance 1}

Pr1645v2TTmplPerfiInPQsD7PerformanceEntry ::=
   SEQUENCE
      {
      pr1645v2TTmplPerfiInPQsD7PerformanceTableIx
         TableIndex,
      pr1645v2TTmplPerfiInPQsD7PerformanceSysUpTime
         TimeTicks,
      pr1645v2TTmplPerfiInPQsD7PerformanceTotPkts
         Counter64,
      pr1645v2TTmplPerfiInPQsD7PerformanceDirTxPkts
         Counter64,
      pr1645v2TTmplPerfiInPQsD7PerformanceQdPkts
         Counter64,
      pr1645v2TTmplPerfiInPQsD7PerformanceDropPkts
         Counter64,
      pr1645v2TTmplPerfiInPQsD7PerformanceRDropPkts
         Counter64,
      pr1645v2TTmplPerfiInPQsD7PerformanceCirTxPkts
         Counter64,
      pr1645v2TTmplPerfiInPQsD7PerformanceEirTxPkts
         Counter64,
      pr1645v2TTmplPerfiInPQsD7PerformanceViolTxPkts
         Counter64,
      pr1645v2TTmplPerfiInPQsD7PerformanceTotOcts
         Counter64,
      pr1645v2TTmplPerfiInPQsD7PerformanceDirTxOcts
         Counter64,
      pr1645v2TTmplPerfiInPQsD7PerformanceQdOcts
         Counter64,
      pr1645v2TTmplPerfiInPQsD7PerformanceDropOcts
         Counter64,
      pr1645v2TTmplPerfiInPQsD7PerformanceRDropOcts
         Counter64,
      pr1645v2TTmplPerfiInPQsD7PerformanceCirTxOcts
         Counter64,
      pr1645v2TTmplPerfiInPQsD7PerformanceEirTxOcts
         Counter64,
      pr1645v2TTmplPerfiInPQsD7PerformanceViolTxOcts
         Counter64,
      pr1645v2TTmplPerfiInPQsD7PerformanceBandwidth
         Integer32
      }

pr1645v2TTmplPerfiInPQsD7PerformanceTableIx OBJECT-TYPE
   SYNTAX      TableIndex
   MAX-ACCESS  not-accessible
   STATUS      current
   DESCRIPTION
      ""
   ::= {pr1645v2TTmplPerfiInPQsD7PerformanceEntry 11}

pr1645v2TTmplPerfiInPQsD7PerformanceSysUpTime OBJECT-TYPE
   SYNTAX      TimeTicks
   MAX-ACCESS  read-only
   STATUS      current
   DESCRIPTION
      "Path: tunnels.performance.ipsecL2tpTunnels.inPriorityQueues.d7Performance.sysUpTime

       Time in centi-second."
   ::= {pr1645v2TTmplPerfiInPQsD7PerformanceEntry 16777216}

pr1645v2TTmplPerfiInPQsD7PerformanceTotPkts OBJECT-TYPE
   SYNTAX      Counter64
   MAX-ACCESS  read-only
   STATUS      current
   DESCRIPTION
      "Path: tunnels.performance.ipsecL2tpTunnels.inPriorityQueues.d7Performance.totalPkts

       64 bit unsigned wrappable counter."
   ::= {pr1645v2TTmplPerfiInPQsD7PerformanceEntry 234881024}

pr1645v2TTmplPerfiInPQsD7PerformanceDirTxPkts OBJECT-TYPE
   SYNTAX      Counter64
   MAX-ACCESS  read-only
   STATUS      current
   DESCRIPTION
      "Path: tunnels.performance.ipsecL2tpTunnels.inPriorityQueues.d7Performance.directTxPkts

       64 bit unsigned wrappable counter."
   ::= {pr1645v2TTmplPerfiInPQsD7PerformanceEntry 33554432}

pr1645v2TTmplPerfiInPQsD7PerformanceQdPkts OBJECT-TYPE
   SYNTAX      Counter64
   MAX-ACCESS  read-only
   STATUS      current
   DESCRIPTION
      "Path: tunnels.performance.ipsecL2tpTunnels.inPriorityQueues.d7Performance.queuedPkts

       64 bit unsigned wrappable counter."
   ::= {pr1645v2TTmplPerfiInPQsD7PerformanceEntry 50331648}

pr1645v2TTmplPerfiInPQsD7PerformanceDropPkts OBJECT-TYPE
   SYNTAX      Counter64
   MAX-ACCESS  read-only
   STATUS      current
   DESCRIPTION
      "Path: tunnels.performance.ipsecL2tpTunnels.inPriorityQueues.d7Performance.droppedPkts

       64 bit unsigned wrappable counter."
   ::= {pr1645v2TTmplPerfiInPQsD7PerformanceEntry 67108864}

pr1645v2TTmplPerfiInPQsD7PerformanceRDropPkts OBJECT-TYPE
   SYNTAX      Counter64
   MAX-ACCESS  read-only
   STATUS      current
   DESCRIPTION
      "Path: tunnels.performance.ipsecL2tpTunnels.inPriorityQueues.d7Performance.redDroppedPkts

       64 bit unsigned wrappable counter."
   ::= {pr1645v2TTmplPerfiInPQsD7PerformanceEntry 201326592}

pr1645v2TTmplPerfiInPQsD7PerformanceCirTxPkts OBJECT-TYPE
   SYNTAX      Counter64
   MAX-ACCESS  read-only
   STATUS      current
   DESCRIPTION
      "Path: tunnels.performance.ipsecL2tpTunnels.inPriorityQueues.d7Performance.cirTxPkts

       64 bit unsigned wrappable counter."
   ::= {pr1645v2TTmplPerfiInPQsD7PerformanceEntry 83886080}

pr1645v2TTmplPerfiInPQsD7PerformanceEirTxPkts OBJECT-TYPE
   SYNTAX      Counter64
   MAX-ACCESS  read-only
   STATUS      current
   DESCRIPTION
      "Path: tunnels.performance.ipsecL2tpTunnels.inPriorityQueues.d7Performance.eirTxPkts

       64 bit unsigned wrappable counter."
   ::= {pr1645v2TTmplPerfiInPQsD7PerformanceEntry 100663296}

pr1645v2TTmplPerfiInPQsD7PerformanceViolTxPkts OBJECT-TYPE
   SYNTAX      Counter64
   MAX-ACCESS  read-only
   STATUS      current
   DESCRIPTION
      "Path: tunnels.performance.ipsecL2tpTunnels.inPriorityQueues.d7Performance.violateTxPkts

       64 bit unsigned wrappable counter."
   ::= {pr1645v2TTmplPerfiInPQsD7PerformanceEntry 301989888}

pr1645v2TTmplPerfiInPQsD7PerformanceTotOcts OBJECT-TYPE
   SYNTAX      Counter64
   MAX-ACCESS  read-only
   STATUS      current
   DESCRIPTION
      "Path: tunnels.performance.ipsecL2tpTunnels.inPriorityQueues.d7Performance.totalOctets

       64 bit unsigned wrappable counter."
   ::= {pr1645v2TTmplPerfiInPQsD7PerformanceEntry 251658240}

pr1645v2TTmplPerfiInPQsD7PerformanceDirTxOcts OBJECT-TYPE
   SYNTAX      Counter64
   MAX-ACCESS  read-only
   STATUS      current
   DESCRIPTION
      "Path: tunnels.performance.ipsecL2tpTunnels.inPriorityQueues.d7Performance.directTxOctets

       64 bit unsigned wrappable counter."
   ::= {pr1645v2TTmplPerfiInPQsD7PerformanceEntry 117440512}

pr1645v2TTmplPerfiInPQsD7PerformanceQdOcts OBJECT-TYPE
   SYNTAX      Counter64
   MAX-ACCESS  read-only
   STATUS      current
   DESCRIPTION
      "Path: tunnels.performance.ipsecL2tpTunnels.inPriorityQueues.d7Performance.queuedOctets

       64 bit unsigned wrappable counter."
   ::= {pr1645v2TTmplPerfiInPQsD7PerformanceEntry 134217728}

pr1645v2TTmplPerfiInPQsD7PerformanceDropOcts OBJECT-TYPE
   SYNTAX      Counter64
   MAX-ACCESS  read-only
   STATUS      current
   DESCRIPTION
      "Path: tunnels.performance.ipsecL2tpTunnels.inPriorityQueues.d7Performance.droppedOctets

       64 bit unsigned wrappable counter."
   ::= {pr1645v2TTmplPerfiInPQsD7PerformanceEntry 150994944}

pr1645v2TTmplPerfiInPQsD7PerformanceRDropOcts OBJECT-TYPE
   SYNTAX      Counter64
   MAX-ACCESS  read-only
   STATUS      current
   DESCRIPTION
      "Path: tunnels.performance.ipsecL2tpTunnels.inPriorityQueues.d7Performance.redDroppedOctets

       64 bit unsigned wrappable counter."
   ::= {pr1645v2TTmplPerfiInPQsD7PerformanceEntry 218103808}

pr1645v2TTmplPerfiInPQsD7PerformanceCirTxOcts OBJECT-TYPE
   SYNTAX      Counter64
   MAX-ACCESS  read-only
   STATUS      current
   DESCRIPTION
      "Path: tunnels.performance.ipsecL2tpTunnels.inPriorityQueues.d7Performance.cirTxOctets

       64 bit unsigned wrappable counter."
   ::= {pr1645v2TTmplPerfiInPQsD7PerformanceEntry 167772160}

pr1645v2TTmplPerfiInPQsD7PerformanceEirTxOcts OBJECT-TYPE
   SYNTAX      Counter64
   MAX-ACCESS  read-only
   STATUS      current
   DESCRIPTION
      "Path: tunnels.performance.ipsecL2tpTunnels.inPriorityQueues.d7Performance.eirTxOctets

       64 bit unsigned wrappable counter."
   ::= {pr1645v2TTmplPerfiInPQsD7PerformanceEntry 184549376}

pr1645v2TTmplPerfiInPQsD7PerformanceViolTxOcts OBJECT-TYPE
   SYNTAX      Counter64
   MAX-ACCESS  read-only
   STATUS      current
   DESCRIPTION
      "Path: tunnels.performance.ipsecL2tpTunnels.inPriorityQueues.d7Performance.violateTxOctets

       64 bit unsigned wrappable counter."
   ::= {pr1645v2TTmplPerfiInPQsD7PerformanceEntry 318767104}

pr1645v2TTmplPerfiInPQsD7PerformanceBandwidth OBJECT-TYPE
   SYNTAX      Integer32
   MAX-ACCESS  read-only
   STATUS      current
   DESCRIPTION
      "Path: tunnels.performance.ipsecL2tpTunnels.inPriorityQueues.d7Performance.bandwidth

       unit name = bps
       formula = 8 * ; 8 /"
   ::= {pr1645v2TTmplPerfiInPQsD7PerformanceEntry 268435456}

pr1645v2TTmplPerfiOutPQs OBJECT-TYPE
   SYNTAX      SEQUENCE OF Pr1645v2TTmplPerfiOutPQsEntry
   MAX-ACCESS  not-accessible
   STATUS      current
   DESCRIPTION
      ""
   ::= {pr1645v2TTmplPerfi 83886080}

pr1645v2TTmplPerfiOutPQsEntry OBJECT-TYPE
   SYNTAX      Pr1645v2TTmplPerfiOutPQsEntry
   MAX-ACCESS  not-accessible
   STATUS      current
   DESCRIPTION
      ""
   INDEX      { pr1645v2TTmplPerfiTableIx,
                pr1645v2TTmplPerfiOutPQsTableIx }
   ::= {pr1645v2TTmplPerfiOutPQs 1}

Pr1645v2TTmplPerfiOutPQsEntry ::=
   SEQUENCE
      {
      pr1645v2TTmplPerfiOutPQsTableIx
         TableIndex,
      pr1645v2TTmplPerfiOutPQsName
         INTEGER,
      pr1645v2TTmplPerfiOutPQsLength
         Integer32,
      pr1645v2TTmplPerfiOutPQsOctetLength
         Integer32,
      pr1645v2TTmplPerfiOutPQsRedLength
         Integer32,
      pr1645v2TTmplPerfiOutPQsPacketsTotal
         Counter64,
      pr1645v2TTmplPerfiOutPQsPacketsDirectTx
         Counter64,
      pr1645v2TTmplPerfiOutPQsPacketsQueued
         Counter64,
      pr1645v2TTmplPerfiOutPQsPacketsDropped
         Counter64,
      pr1645v2TTmplPerfiOutPQsPacketsRedDropped
         Counter64,
      pr1645v2TTmplPerfiOutPQsPacketsCirTx
         Counter64,
      pr1645v2TTmplPerfiOutPQsPacketsEirTx
         Counter64,
      pr1645v2TTmplPerfiOutPQsPacketsViolateTx
         Counter64,
      pr1645v2TTmplPerfiOutPQsOctetsTotal
         Counter64,
      pr1645v2TTmplPerfiOutPQsOctetsDirectTx
         Counter64,
      pr1645v2TTmplPerfiOutPQsOctetsQueued
         Counter64,
      pr1645v2TTmplPerfiOutPQsOctetsDropped
         Counter64,
      pr1645v2TTmplPerfiOutPQsOctetsRedDropped
         Counter64,
      pr1645v2TTmplPerfiOutPQsOctetsCirTx
         Counter64,
      pr1645v2TTmplPerfiOutPQsOctetsEirTx
         Counter64,
      pr1645v2TTmplPerfiOutPQsOctetsViolateTx
         Counter64,
      pr1645v2TTmplPerfiOutPQsOctetsBandwidth15sec
         Integer32,
      pr1645v2TTmplPerfiOutPQsOctetsBandwidth30sec
         Integer32,
      pr1645v2TTmplPerfiOutPQsOctetsBandwidth1min
         Integer32,
      pr1645v2TTmplPerfiOutPQsOctetsBandwidth2min
         Integer32,
      pr1645v2TTmplPerfiOutPQsOctetsBandwidth5min
         Integer32
      }

pr1645v2TTmplPerfiOutPQsTableIx OBJECT-TYPE
   SYNTAX      TableIndex
   MAX-ACCESS  not-accessible
   STATUS      current
   DESCRIPTION
      ""
   ::= {pr1645v2TTmplPerfiOutPQsEntry 11}

pr1645v2TTmplPerfiOutPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: tunnels.performance.ipsecL2tpTunnels.outPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2TTmplPerfiOutPQsEntry 16777216}

pr1645v2TTmplPerfiOutPQsLength OBJECT-TYPE
   SYNTAX      Integer32
   MAX-ACCESS  read-only
   STATUS      current
   DESCRIPTION
      "Path: tunnels.performance.ipsecL2tpTunnels.outPriorityQueues.length"
   ::= {pr1645v2TTmplPerfiOutPQsEntry 33554432}

pr1645v2TTmplPerfiOutPQsOctetLength OBJECT-TYPE
   SYNTAX      Integer32
   MAX-ACCESS  read-only
   STATUS      current
   DESCRIPTION
      "Path: tunnels.performance.ipsecL2tpTunnels.outPriorityQueues.octetLength"
   ::= {pr1645v2TTmplPerfiOutPQsEntry 150994944}

pr1645v2TTmplPerfiOutPQsRedLength OBJECT-TYPE
   SYNTAX      Integer32
   MAX-ACCESS  read-only
   STATUS      current
   DESCRIPTION
      "Path: tunnels.performance.ipsecL2tpTunnels.outPriorityQueues.redLength"
   ::= {pr1645v2TTmplPerfiOutPQsEntry 134217728}

pr1645v2TTmplPerfiOutPQsPacketsTotal OBJECT-TYPE
   SYNTAX      Counter64
   MAX-ACCESS  read-only
   STATUS      current
   DESCRIPTION
      "Path: tunnels.performance.ipsecL2tpTunnels.outPriorityQueues.packets.total

       64 bit unsigned wrappable counter."
   ::= {pr1645v2TTmplPerfiOutPQsEntry 50790400}

pr1645v2TTmplPerfiOutPQsPacketsDirectTx OBJECT-TYPE
   SYNTAX      Counter64
   MAX-ACCESS  read-only
   STATUS      current
   DESCRIPTION
      "Path: tunnels.performance.ipsecL2tpTunnels.outPriorityQueues.packets.directTx

       64 bit unsigned wrappable counter."
   ::= {pr1645v2TTmplPerfiOutPQsEntry 50397184}

pr1645v2TTmplPerfiOutPQsPacketsQueued OBJECT-TYPE
   SYNTAX      Counter64
   MAX-ACCESS  read-only
   STATUS      current
   DESCRIPTION
      "Path: tunnels.performance.ipsecL2tpTunnels.outPriorityQueues.packets.queued

       64 bit unsigned wrappable counter."
   ::= {pr1645v2TTmplPerfiOutPQsEntry 50462720}

pr1645v2TTmplPerfiOutPQsPacketsDropped OBJECT-TYPE
   SYNTAX      Counter64
   MAX-ACCESS  read-only
   STATUS      current
   DESCRIPTION
      "Path: tunnels.performance.ipsecL2tpTunnels.outPriorityQueues.packets.dropped

       64 bit unsigned wrappable counter."
   ::= {pr1645v2TTmplPerfiOutPQsEntry 50528256}

pr1645v2TTmplPerfiOutPQsPacketsRedDropped OBJECT-TYPE
   SYNTAX      Counter64
   MAX-ACCESS  read-only
   STATUS      current
   DESCRIPTION
      "Path: tunnels.performance.ipsecL2tpTunnels.outPriorityQueues.packets.redDropped

       64 bit unsigned wrappable counter."
   ::= {pr1645v2TTmplPerfiOutPQsEntry 50724864}

pr1645v2TTmplPerfiOutPQsPacketsCirTx OBJECT-TYPE
   SYNTAX      Counter64
   MAX-ACCESS  read-only
   STATUS      current
   DESCRIPTION
      "Path: tunnels.performance.ipsecL2tpTunnels.outPriorityQueues.packets.cirTx

       64 bit unsigned wrappable counter."
   ::= {pr1645v2TTmplPerfiOutPQsEntry 50593792}

pr1645v2TTmplPerfiOutPQsPacketsEirTx OBJECT-TYPE
   SYNTAX      Counter64
   MAX-ACCESS  read-only
   STATUS      current
   DESCRIPTION
      "Path: tunnels.performance.ipsecL2tpTunnels.outPriorityQueues.packets.eirTx

       64 bit unsigned wrappable counter."
   ::= {pr1645v2TTmplPerfiOutPQsEntry 50659328}

pr1645v2TTmplPerfiOutPQsPacketsViolateTx OBJECT-TYPE
   SYNTAX      Counter64
   MAX-ACCESS  read-only
   STATUS      current
   DESCRIPTION
      "Path: tunnels.performance.ipsecL2tpTunnels.outPriorityQueues.packets.violateTx

       64 bit unsigned wrappable counter."
   ::= {pr1645v2TTmplPerfiOutPQsEntry 50855936}

pr1645v2TTmplPerfiOutPQsOctetsTotal OBJECT-TYPE
   SYNTAX      Counter64
   MAX-ACCESS  read-only
   STATUS      current
   DESCRIPTION
      "Path: tunnels.performance.ipsecL2tpTunnels.outPriorityQueues.octets.total

       64 bit unsigned wrappable counter."
   ::= {pr1645v2TTmplPerfiOutPQsEntry 67567616}

pr1645v2TTmplPerfiOutPQsOctetsDirectTx OBJECT-TYPE
   SYNTAX      Counter64
   MAX-ACCESS  read-only
   STATUS      current
   DESCRIPTION
      "Path: tunnels.performance.ipsecL2tpTunnels.outPriorityQueues.octets.directTx

       64 bit unsigned wrappable counter."
   ::= {pr1645v2TTmplPerfiOutPQsEntry 67174400}

pr1645v2TTmplPerfiOutPQsOctetsQueued OBJECT-TYPE
   SYNTAX      Counter64
   MAX-ACCESS  read-only
   STATUS      current
   DESCRIPTION
      "Path: tunnels.performance.ipsecL2tpTunnels.outPriorityQueues.octets.queued

       64 bit unsigned wrappable counter."
   ::= {pr1645v2TTmplPerfiOutPQsEntry 67239936}

pr1645v2TTmplPerfiOutPQsOctetsDropped OBJECT-TYPE
   SYNTAX      Counter64
   MAX-ACCESS  read-only
   STATUS      current
   DESCRIPTION
      "Path: tunnels.performance.ipsecL2tpTunnels.outPriorityQueues.octets.dropped

       64 bit unsigned wrappable counter."
   ::= {pr1645v2TTmplPerfiOutPQsEntry 67305472}

pr1645v2TTmplPerfiOutPQsOctetsRedDropped OBJECT-TYPE
   SYNTAX      Counter64
   MAX-ACCESS  read-only
   STATUS      current
   DESCRIPTION
      "Path: tunnels.performance.ipsecL2tpTunnels.outPriorityQueues.octets.redDropped

       64 bit unsigned wrappable counter."
   ::= {pr1645v2TTmplPerfiOutPQsEntry 67502080}

pr1645v2TTmplPerfiOutPQsOctetsCirTx OBJECT-TYPE
   SYNTAX      Counter64
   MAX-ACCESS  read-only
   STATUS      current
   DESCRIPTION
      "Path: tunnels.performance.ipsecL2tpTunnels.outPriorityQueues.octets.cirTx

       64 bit unsigned wrappable counter."
   ::= {pr1645v2TTmplPerfiOutPQsEntry 67371008}

pr1645v2TTmplPerfiOutPQsOctetsEirTx OBJECT-TYPE
   SYNTAX      Counter64
   MAX-ACCESS  read-only
   STATUS      current
   DESCRIPTION
      "Path: tunnels.performance.ipsecL2tpTunnels.outPriorityQueues.octets.eirTx

       64 bit unsigned wrappable counter."
   ::= {pr1645v2TTmplPerfiOutPQsEntry 67436544}

pr1645v2TTmplPerfiOutPQsOctetsViolateTx OBJECT-TYPE
   SYNTAX      Counter64
   MAX-ACCESS  read-only
   STATUS      current
   DESCRIPTION
      "Path: tunnels.performance.ipsecL2tpTunnels.outPriorityQueues.octets.violateTx

       64 bit unsigned wrappable counter."
   ::= {pr1645v2TTmplPerfiOutPQsEntry 67633152}

pr1645v2TTmplPerfiOutPQsOctetsBandwidth15sec OBJECT-TYPE
   SYNTAX      Integer32
   MAX-ACCESS  read-only
   STATUS      current
   DESCRIPTION
      "Path: tunnels.performance.ipsecL2tpTunnels.outPriorityQueues.octets.bandwidth.15sec

       unit name = bps
       formula = 8 * ; 8 /"
   ::= {pr1645v2TTmplPerfiOutPQsEntry 70386944}

pr1645v2TTmplPerfiOutPQsOctetsBandwidth30sec OBJECT-TYPE
   SYNTAX      Integer32
   MAX-ACCESS  read-only
   STATUS      current
   DESCRIPTION
      "Path: tunnels.performance.ipsecL2tpTunnels.outPriorityQueues.octets.bandwidth.30sec

       unit name = bps
       formula = 8 * ; 8 /"
   ::= {pr1645v2TTmplPerfiOutPQsEntry 70388224}

pr1645v2TTmplPerfiOutPQsOctetsBandwidth1min OBJECT-TYPE
   SYNTAX      Integer32
   MAX-ACCESS  read-only
   STATUS      current
   DESCRIPTION
      "Path: tunnels.performance.ipsecL2tpTunnels.outPriorityQueues.octets.bandwidth.1min

       unit name = bps
       formula = 8 * ; 8 /"
   ::= {pr1645v2TTmplPerfiOutPQsEntry 70390784}

pr1645v2TTmplPerfiOutPQsOctetsBandwidth2min OBJECT-TYPE
   SYNTAX      Integer32
   MAX-ACCESS  read-only
   STATUS      current
   DESCRIPTION
      "Path: tunnels.performance.ipsecL2tpTunnels.outPriorityQueues.octets.bandwidth.2min

       unit name = bps
       formula = 8 * ; 8 /"
   ::= {pr1645v2TTmplPerfiOutPQsEntry 70395904}

pr1645v2TTmplPerfiOutPQsOctetsBandwidth5min OBJECT-TYPE
   SYNTAX      Integer32
   MAX-ACCESS  read-only
   STATUS      current
   DESCRIPTION
      "Path: tunnels.performance.ipsecL2tpTunnels.outPriorityQueues.octets.bandwidth.5min

       unit name = bps
       formula = 8 * ; 8 /"
   ::= {pr1645v2TTmplPerfiOutPQsEntry 70411264}

pr1645v2TTmplPerfiOutPQsH2Performance OBJECT-TYPE
   SYNTAX      SEQUENCE OF Pr1645v2TTmplPerfiOutPQsH2PerformanceEntry
   MAX-ACCESS  not-accessible
   STATUS      current
   DESCRIPTION
      ""
   ::= {pr1645v2TTmplPerfi 84213760}

pr1645v2TTmplPerfiOutPQsH2PerformanceEntry OBJECT-TYPE
   SYNTAX      Pr1645v2TTmplPerfiOutPQsH2PerformanceEntry
   MAX-ACCESS  not-accessible
   STATUS      current
   DESCRIPTION
      ""
   INDEX      { pr1645v2TTmplPerfiTableIx,
                pr1645v2TTmplPerfiOutPQsTableIx,
                pr1645v2TTmplPerfiOutPQsH2PerformanceTableIx }
   ::= {pr1645v2TTmplPerfiOutPQsH2Performance 1}

Pr1645v2TTmplPerfiOutPQsH2PerformanceEntry ::=
   SEQUENCE
      {
      pr1645v2TTmplPerfiOutPQsH2PerformanceTableIx
         TableIndex,
      pr1645v2TTmplPerfiOutPQsH2PerformanceSysUpTime
         TimeTicks,
      pr1645v2TTmplPerfiOutPQsH2PerformanceTotPkts
         Counter64,
      pr1645v2TTmplPerfiOutPQsH2PerformanceDirTxPkts
         Counter64,
      pr1645v2TTmplPerfiOutPQsH2PerformanceQdPkts
         Counter64,
      pr1645v2TTmplPerfiOutPQsH2PerformanceDropPkts
         Counter64,
      pr1645v2TTmplPerfiOutPQsH2PerformanceRDropPkts
         Counter64,
      pr1645v2TTmplPerfiOutPQsH2PerformanceCirTxPkts
         Counter64,
      pr1645v2TTmplPerfiOutPQsH2PerformanceEirTxPkts
         Counter64,
      pr1645v2TTmplPerfiOutPQsH2PerformanceViolTxPkts
         Counter64,
      pr1645v2TTmplPerfiOutPQsH2PerformanceTotOcts
         Counter64,
      pr1645v2TTmplPerfiOutPQsH2PerformanceDirTxOcts
         Counter64,
      pr1645v2TTmplPerfiOutPQsH2PerformanceQdOcts
         Counter64,
      pr1645v2TTmplPerfiOutPQsH2PerformanceDropOcts
         Counter64,
      pr1645v2TTmplPerfiOutPQsH2PerformanceRDropOcts
         Counter64,
      pr1645v2TTmplPerfiOutPQsH2PerformanceCirTxOcts
         Counter64,
      pr1645v2TTmplPerfiOutPQsH2PerformanceEirTxOcts
         Counter64,
      pr1645v2TTmplPerfiOutPQsH2PerformanceViolTxOcts
         Counter64,
      pr1645v2TTmplPerfiOutPQsH2PerformanceBandwidth
         Integer32
      }

pr1645v2TTmplPerfiOutPQsH2PerformanceTableIx OBJECT-TYPE
   SYNTAX      TableIndex
   MAX-ACCESS  not-accessible
   STATUS      current
   DESCRIPTION
      ""
   ::= {pr1645v2TTmplPerfiOutPQsH2PerformanceEntry 11}

pr1645v2TTmplPerfiOutPQsH2PerformanceSysUpTime OBJECT-TYPE
   SYNTAX      TimeTicks
   MAX-ACCESS  read-only
   STATUS      current
   DESCRIPTION
      "Path: tunnels.performance.ipsecL2tpTunnels.outPriorityQueues.h2Performance.sysUpTime

       Time in centi-second."
   ::= {pr1645v2TTmplPerfiOutPQsH2PerformanceEntry 16777216}

pr1645v2TTmplPerfiOutPQsH2PerformanceTotPkts OBJECT-TYPE
   SYNTAX      Counter64
   MAX-ACCESS  read-only
   STATUS      current
   DESCRIPTION
      "Path: tunnels.performance.ipsecL2tpTunnels.outPriorityQueues.h2Performance.totalPkts

       64 bit unsigned wrappable counter."
   ::= {pr1645v2TTmplPerfiOutPQsH2PerformanceEntry 234881024}

pr1645v2TTmplPerfiOutPQsH2PerformanceDirTxPkts OBJECT-TYPE
   SYNTAX      Counter64
   MAX-ACCESS  read-only
   STATUS      current
   DESCRIPTION
      "Path: tunnels.performance.ipsecL2tpTunnels.outPriorityQueues.h2Performance.directTxPkts

       64 bit unsigned wrappable counter."
   ::= {pr1645v2TTmplPerfiOutPQsH2PerformanceEntry 33554432}

pr1645v2TTmplPerfiOutPQsH2PerformanceQdPkts OBJECT-TYPE
   SYNTAX      Counter64
   MAX-ACCESS  read-only
   STATUS      current
   DESCRIPTION
      "Path: tunnels.performance.ipsecL2tpTunnels.outPriorityQueues.h2Performance.queuedPkts

       64 bit unsigned wrappable counter."
   ::= {pr1645v2TTmplPerfiOutPQsH2PerformanceEntry 50331648}

pr1645v2TTmplPerfiOutPQsH2PerformanceDropPkts OBJECT-TYPE
   SYNTAX      Counter64
   MAX-ACCESS  read-only
   STATUS      current
   DESCRIPTION
      "Path: tunnels.performance.ipsecL2tpTunnels.outPriorityQueues.h2Performance.droppedPkts

       64 bit unsigned wrappable counter."
   ::= {pr1645v2TTmplPerfiOutPQsH2PerformanceEntry 67108864}

pr1645v2TTmplPerfiOutPQsH2PerformanceRDropPkts OBJECT-TYPE
   SYNTAX      Counter64
   MAX-ACCESS  read-only
   STATUS      current
   DESCRIPTION
      "Path: tunnels.performance.ipsecL2tpTunnels.outPriorityQueues.h2Performance.redDroppedPkts

       64 bit unsigned wrappable counter."
   ::= {pr1645v2TTmplPerfiOutPQsH2PerformanceEntry 201326592}

pr1645v2TTmplPerfiOutPQsH2PerformanceCirTxPkts OBJECT-TYPE
   SYNTAX      Counter64
   MAX-ACCESS  read-only
   STATUS      current
   DESCRIPTION
      "Path: tunnels.performance.ipsecL2tpTunnels.outPriorityQueues.h2Performance.cirTxPkts

       64 bit unsigned wrappable counter."
   ::= {pr1645v2TTmplPerfiOutPQsH2PerformanceEntry 83886080}

pr1645v2TTmplPerfiOutPQsH2PerformanceEirTxPkts OBJECT-TYPE
   SYNTAX      Counter64
   MAX-ACCESS  read-only
   STATUS      current
   DESCRIPTION
      "Path: tunnels.performance.ipsecL2tpTunnels.outPriorityQueues.h2Performance.eirTxPkts

       64 bit unsigned wrappable counter."
   ::= {pr1645v2TTmplPerfiOutPQsH2PerformanceEntry 100663296}

pr1645v2TTmplPerfiOutPQsH2PerformanceViolTxPkts OBJECT-TYPE
   SYNTAX      Counter64
   MAX-ACCESS  read-only
   STATUS      current
   DESCRIPTION
      "Path: tunnels.performance.ipsecL2tpTunnels.outPriorityQueues.h2Performance.violateTxPkts

       64 bit unsigned wrappable counter."
   ::= {pr1645v2TTmplPerfiOutPQsH2PerformanceEntry 301989888}

pr1645v2TTmplPerfiOutPQsH2PerformanceTotOcts OBJECT-TYPE
   SYNTAX      Counter64
   MAX-ACCESS  read-only
   STATUS      current
   DESCRIPTION
      "Path: tunnels.performance.ipsecL2tpTunnels.outPriorityQueues.h2Performance.totalOctets

       64 bit unsigned wrappable counter."
   ::= {pr1645v2TTmplPerfiOutPQsH2PerformanceEntry 251658240}

pr1645v2TTmplPerfiOutPQsH2PerformanceDirTxOcts OBJECT-TYPE
   SYNTAX      Counter64
   MAX-ACCESS  read-only
   STATUS      current
   DESCRIPTION
      "Path: tunnels.performance.ipsecL2tpTunnels.outPriorityQueues.h2Performance.directTxOctets

       64 bit unsigned wrappable counter."
   ::= {pr1645v2TTmplPerfiOutPQsH2PerformanceEntry 117440512}

pr1645v2TTmplPerfiOutPQsH2PerformanceQdOcts OBJECT-TYPE
   SYNTAX      Counter64
   MAX-ACCESS  read-only
   STATUS      current
   DESCRIPTION
      "Path: tunnels.performance.ipsecL2tpTunnels.outPriorityQueues.h2Performance.queuedOctets

       64 bit unsigned wrappable counter."
   ::= {pr1645v2TTmplPerfiOutPQsH2PerformanceEntry 134217728}

pr1645v2TTmplPerfiOutPQsH2PerformanceDropOcts OBJECT-TYPE
   SYNTAX      Counter64
   MAX-ACCESS  read-only
   STATUS      current
   DESCRIPTION
      "Path: tunnels.performance.ipsecL2tpTunnels.outPriorityQueues.h2Performance.droppedOctets

       64 bit unsigned wrappable counter."
   ::= {pr1645v2TTmplPerfiOutPQsH2PerformanceEntry 150994944}

pr1645v2TTmplPerfiOutPQsH2PerformanceRDropOcts OBJECT-TYPE
   SYNTAX      Counter64
   MAX-ACCESS  read-only
   STATUS      current
   DESCRIPTION
      "Path: tunnels.performance.ipsecL2tpTunnels.outPriorityQueues.h2Performance.redDroppedOctets

       64 bit unsigned wrappable counter."
   ::= {pr1645v2TTmplPerfiOutPQsH2PerformanceEntry 218103808}

pr1645v2TTmplPerfiOutPQsH2PerformanceCirTxOcts OBJECT-TYPE
   SYNTAX      Counter64
   MAX-ACCESS  read-only
   STATUS      current
   DESCRIPTION
      "Path: tunnels.performance.ipsecL2tpTunnels.outPriorityQueues.h2Performance.cirTxOctets

       64 bit unsigned wrappable counter."
   ::= {pr1645v2TTmplPerfiOutPQsH2PerformanceEntry 167772160}

pr1645v2TTmplPerfiOutPQsH2PerformanceEirTxOcts OBJECT-TYPE
   SYNTAX      Counter64
   MAX-ACCESS  read-only
   STATUS      current
   DESCRIPTION
      "Path: tunnels.performance.ipsecL2tpTunnels.outPriorityQueues.h2Performance.eirTxOctets

       64 bit unsigned wrappable counter."
   ::= {pr1645v2TTmplPerfiOutPQsH2PerformanceEntry 184549376}

pr1645v2TTmplPerfiOutPQsH2PerformanceViolTxOcts OBJECT-TYPE
   SYNTAX      Counter64
   MAX-ACCESS  read-only
   STATUS      current
   DESCRIPTION
      "Path: tunnels.performance.ipsecL2tpTunnels.outPriorityQueues.h2Performance.violateTxOctets

       64 bit unsigned wrappable counter."
   ::= {pr1645v2TTmplPerfiOutPQsH2PerformanceEntry 318767104}

pr1645v2TTmplPerfiOutPQsH2PerformanceBandwidth OBJECT-TYPE
   SYNTAX      Integer32
   MAX-ACCESS  read-only
   STATUS      current
   DESCRIPTION
      "Path: tunnels.performance.ipsecL2tpTunnels.outPriorityQueues.h2Performance.bandwidth

       unit name = bps
       formula = 8 * ; 8 /"
   ::= {pr1645v2TTmplPerfiOutPQsH2PerformanceEntry 268435456}

pr1645v2TTmplPerfiOutPQsH24Performance OBJECT-TYPE
   SYNTAX      SEQUENCE OF Pr1645v2TTmplPerfiOutPQsH24PerformanceEntry
   MAX-ACCESS  not-accessible
   STATUS      current
   DESCRIPTION
      ""
   ::= {pr1645v2TTmplPerfi 84279296}

pr1645v2TTmplPerfiOutPQsH24PerformanceEntry OBJECT-TYPE
   SYNTAX      Pr1645v2TTmplPerfiOutPQsH24PerformanceEntry
   MAX-ACCESS  not-accessible
   STATUS      current
   DESCRIPTION
      ""
   INDEX      { pr1645v2TTmplPerfiTableIx,
                pr1645v2TTmplPerfiOutPQsTableIx,
                pr1645v2TTmplPerfiOutPQsH24PerformanceTableIx }
   ::= {pr1645v2TTmplPerfiOutPQsH24Performance 1}

Pr1645v2TTmplPerfiOutPQsH24PerformanceEntry ::=
   SEQUENCE
      {
      pr1645v2TTmplPerfiOutPQsH24PerformanceTableIx
         TableIndex,
      pr1645v2TTmplPerfiOutPQsH24PerformanceSysUpTime
         TimeTicks,
      pr1645v2TTmplPerfiOutPQsH24PerformanceTotPkts
         Counter64,
      pr1645v2TTmplPerfiOutPQsH24PerformanceDirTxPkts
         Counter64,
      pr1645v2TTmplPerfiOutPQsH24PerformanceQdPkts
         Counter64,
      pr1645v2TTmplPerfiOutPQsH24PerformanceDropPkts
         Counter64,
      pr1645v2TTmplPerfiOutPQsH24PerformanceRDropPkts
         Counter64,
      pr1645v2TTmplPerfiOutPQsH24PerformanceCirTxPkts
         Counter64,
      pr1645v2TTmplPerfiOutPQsH24PerformanceEirTxPkts
         Counter64,
      pr1645v2TTmplPerfiOutPQsH24PerformanceViolTxPkts
         Counter64,
      pr1645v2TTmplPerfiOutPQsH24PerformanceTotOcts
         Counter64,
      pr1645v2TTmplPerfiOutPQsH24PerformanceDirTxOcts
         Counter64,
      pr1645v2TTmplPerfiOutPQsH24PerformanceQdOcts
         Counter64,
      pr1645v2TTmplPerfiOutPQsH24PerformanceDropOcts
         Counter64,
      pr1645v2TTmplPerfiOutPQsH24PerformanceRDropOcts
         Counter64,
      pr1645v2TTmplPerfiOutPQsH24PerformanceCirTxOcts
         Counter64,
      pr1645v2TTmplPerfiOutPQsH24PerformanceEirTxOcts
         Counter64,
      pr1645v2TTmplPerfiOutPQsH24PerformanceViolTxOcts
         Counter64,
      pr1645v2TTmplPerfiOutPQsH24PerformanceBandwidth
         Integer32
      }

pr1645v2TTmplPerfiOutPQsH24PerformanceTableIx OBJECT-TYPE
   SYNTAX      TableIndex
   MAX-ACCESS  not-accessible
   STATUS      current
   DESCRIPTION
      ""
   ::= {pr1645v2TTmplPerfiOutPQsH24PerformanceEntry 11}

pr1645v2TTmplPerfiOutPQsH24PerformanceSysUpTime OBJECT-TYPE
   SYNTAX      TimeTicks
   MAX-ACCESS  read-only
   STATUS      current
   DESCRIPTION
      "Path: tunnels.performance.ipsecL2tpTunnels.outPriorityQueues.h24Performance.sysUpTime

       Time in centi-second."
   ::= {pr1645v2TTmplPerfiOutPQsH24PerformanceEntry 16777216}

pr1645v2TTmplPerfiOutPQsH24PerformanceTotPkts OBJECT-TYPE
   SYNTAX      Counter64
   MAX-ACCESS  read-only
   STATUS      current
   DESCRIPTION
      "Path: tunnels.performance.ipsecL2tpTunnels.outPriorityQueues.h24Performance.totalPkts

       64 bit unsigned wrappable counter."
   ::= {pr1645v2TTmplPerfiOutPQsH24PerformanceEntry 234881024}

pr1645v2TTmplPerfiOutPQsH24PerformanceDirTxPkts OBJECT-TYPE
   SYNTAX      Counter64
   MAX-ACCESS  read-only
   STATUS      current
   DESCRIPTION
      "Path: tunnels.performance.ipsecL2tpTunnels.outPriorityQueues.h24Performance.directTxPkts

       64 bit unsigned wrappable counter."
   ::= {pr1645v2TTmplPerfiOutPQsH24PerformanceEntry 33554432}

pr1645v2TTmplPerfiOutPQsH24PerformanceQdPkts OBJECT-TYPE
   SYNTAX      Counter64
   MAX-ACCESS  read-only
   STATUS      current
   DESCRIPTION
      "Path: tunnels.performance.ipsecL2tpTunnels.outPriorityQueues.h24Performance.queuedPkts

       64 bit unsigned wrappable counter."
   ::= {pr1645v2TTmplPerfiOutPQsH24PerformanceEntry 50331648}

pr1645v2TTmplPerfiOutPQsH24PerformanceDropPkts OBJECT-TYPE
   SYNTAX      Counter64
   MAX-ACCESS  read-only
   STATUS      current
   DESCRIPTION
      "Path: tunnels.performance.ipsecL2tpTunnels.outPriorityQueues.h24Performance.droppedPkts

       64 bit unsigned wrappable counter."
   ::= {pr1645v2TTmplPerfiOutPQsH24PerformanceEntry 67108864}

pr1645v2TTmplPerfiOutPQsH24PerformanceRDropPkts OBJECT-TYPE
   SYNTAX      Counter64
   MAX-ACCESS  read-only
   STATUS      current
   DESCRIPTION
      "Path: tunnels.performance.ipsecL2tpTunnels.outPriorityQueues.h24Performance.redDroppedPkts

       64 bit unsigned wrappable counter."
   ::= {pr1645v2TTmplPerfiOutPQsH24PerformanceEntry 201326592}

pr1645v2TTmplPerfiOutPQsH24PerformanceCirTxPkts OBJECT-TYPE
   SYNTAX      Counter64
   MAX-ACCESS  read-only
   STATUS      current
   DESCRIPTION
      "Path: tunnels.performance.ipsecL2tpTunnels.outPriorityQueues.h24Performance.cirTxPkts

       64 bit unsigned wrappable counter."
   ::= {pr1645v2TTmplPerfiOutPQsH24PerformanceEntry 83886080}

pr1645v2TTmplPerfiOutPQsH24PerformanceEirTxPkts OBJECT-TYPE
   SYNTAX      Counter64
   MAX-ACCESS  read-only
   STATUS      current
   DESCRIPTION
      "Path: tunnels.performance.ipsecL2tpTunnels.outPriorityQueues.h24Performance.eirTxPkts

       64 bit unsigned wrappable counter."
   ::= {pr1645v2TTmplPerfiOutPQsH24PerformanceEntry 100663296}

pr1645v2TTmplPerfiOutPQsH24PerformanceViolTxPkts OBJECT-TYPE
   SYNTAX      Counter64
   MAX-ACCESS  read-only
   STATUS      current
   DESCRIPTION
      "Path: tunnels.performance.ipsecL2tpTunnels.outPriorityQueues.h24Performance.violateTxPkts

       64 bit unsigned wrappable counter."
   ::= {pr1645v2TTmplPerfiOutPQsH24PerformanceEntry 301989888}

pr1645v2TTmplPerfiOutPQsH24PerformanceTotOcts OBJECT-TYPE
   SYNTAX      Counter64
   MAX-ACCESS  read-only
   STATUS      current
   DESCRIPTION
      "Path: tunnels.performance.ipsecL2tpTunnels.outPriorityQueues.h24Performance.totalOctets

       64 bit unsigned wrappable counter."
   ::= {pr1645v2TTmplPerfiOutPQsH24PerformanceEntry 251658240}

pr1645v2TTmplPerfiOutPQsH24PerformanceDirTxOcts OBJECT-TYPE
   SYNTAX      Counter64
   MAX-ACCESS  read-only
   STATUS      current
   DESCRIPTION
      "Path: tunnels.performance.ipsecL2tpTunnels.outPriorityQueues.h24Performance.directTxOctets

       64 bit unsigned wrappable counter."
   ::= {pr1645v2TTmplPerfiOutPQsH24PerformanceEntry 117440512}

pr1645v2TTmplPerfiOutPQsH24PerformanceQdOcts OBJECT-TYPE
   SYNTAX      Counter64
   MAX-ACCESS  read-only
   STATUS      current
   DESCRIPTION
      "Path: tunnels.performance.ipsecL2tpTunnels.outPriorityQueues.h24Performance.queuedOctets

       64 bit unsigned wrappable counter."
   ::= {pr1645v2TTmplPerfiOutPQsH24PerformanceEntry 134217728}

pr1645v2TTmplPerfiOutPQsH24PerformanceDropOcts OBJECT-TYPE
   SYNTAX      Counter64
   MAX-ACCESS  read-only
   STATUS      current
   DESCRIPTION
      "Path: tunnels.performance.ipsecL2tpTunnels.outPriorityQueues.h24Performance.droppedOctets

       64 bit unsigned wrappable counter."
   ::= {pr1645v2TTmplPerfiOutPQsH24PerformanceEntry 150994944}

pr1645v2TTmplPerfiOutPQsH24PerformanceRDropOcts OBJECT-TYPE
   SYNTAX      Counter64
   MAX-ACCESS  read-only
   STATUS      current
   DESCRIPTION
      "Path: tunnels.performance.ipsecL2tpTunnels.outPriorityQueues.h24Performance.redDroppedOctets

       64 bit unsigned wrappable counter."
   ::= {pr1645v2TTmplPerfiOutPQsH24PerformanceEntry 218103808}

pr1645v2TTmplPerfiOutPQsH24PerformanceCirTxOcts OBJECT-TYPE
   SYNTAX      Counter64
   MAX-ACCESS  read-only
   STATUS      current
   DESCRIPTION
      "Path: tunnels.performance.ipsecL2tpTunnels.outPriorityQueues.h24Performance.cirTxOctets

       64 bit unsigned wrappable counter."
   ::= {pr1645v2TTmplPerfiOutPQsH24PerformanceEntry 167772160}

pr1645v2TTmplPerfiOutPQsH24PerformanceEirTxOcts OBJECT-TYPE
   SYNTAX      Counter64
   MAX-ACCESS  read-only
   STATUS      current
   DESCRIPTION
      "Path: tunnels.performance.ipsecL2tpTunnels.outPriorityQueues.h24Performance.eirTxOctets

       64 bit unsigned wrappable counter."
   ::= {pr1645v2TTmplPerfiOutPQsH24PerformanceEntry 184549376}

pr1645v2TTmplPerfiOutPQsH24PerformanceViolTxOcts OBJECT-TYPE
   SYNTAX      Counter64
   MAX-ACCESS  read-only
   STATUS      current
   DESCRIPTION
      "Path: tunnels.performance.ipsecL2tpTunnels.outPriorityQueues.h24Performance.violateTxOctets

       64 bit unsigned wrappable counter."
   ::= {pr1645v2TTmplPerfiOutPQsH24PerformanceEntry 318767104}

pr1645v2TTmplPerfiOutPQsH24PerformanceBandwidth OBJECT-TYPE
   SYNTAX      Integer32
   MAX-ACCESS  read-only
   STATUS      current
   DESCRIPTION
      "Path: tunnels.performance.ipsecL2tpTunnels.outPriorityQueues.h24Performance.bandwidth

       unit name = bps
       formula = 8 * ; 8 /"
   ::= {pr1645v2TTmplPerfiOutPQsH24PerformanceEntry 268435456}

pr1645v2TTmplPerfiOutPQsD7Performance OBJECT-TYPE
   SYNTAX      SEQUENCE OF Pr1645v2TTmplPerfiOutPQsD7PerformanceEntry
   MAX-ACCESS  not-accessible
   STATUS      current
   DESCRIPTION
      ""
   ::= {pr1645v2TTmplPerfi 84344832}

pr1645v2TTmplPerfiOutPQsD7PerformanceEntry OBJECT-TYPE
   SYNTAX      Pr1645v2TTmplPerfiOutPQsD7PerformanceEntry
   MAX-ACCESS  not-accessible
   STATUS      current
   DESCRIPTION
      ""
   INDEX      { pr1645v2TTmplPerfiTableIx,
                pr1645v2TTmplPerfiOutPQsTableIx,
                pr1645v2TTmplPerfiOutPQsD7PerformanceTableIx }
   ::= {pr1645v2TTmplPerfiOutPQsD7Performance 1}

Pr1645v2TTmplPerfiOutPQsD7PerformanceEntry ::=
   SEQUENCE
      {
      pr1645v2TTmplPerfiOutPQsD7PerformanceTableIx
         TableIndex,
      pr1645v2TTmplPerfiOutPQsD7PerformanceSysUpTime
         TimeTicks,
      pr1645v2TTmplPerfiOutPQsD7PerformanceTotPkts
         Counter64,
      pr1645v2TTmplPerfiOutPQsD7PerformanceDirTxPkts
         Counter64,
      pr1645v2TTmplPerfiOutPQsD7PerformanceQdPkts
         Counter64,
      pr1645v2TTmplPerfiOutPQsD7PerformanceDropPkts
         Counter64,
      pr1645v2TTmplPerfiOutPQsD7PerformanceRDropPkts
         Counter64,
      pr1645v2TTmplPerfiOutPQsD7PerformanceCirTxPkts
         Counter64,
      pr1645v2TTmplPerfiOutPQsD7PerformanceEirTxPkts
         Counter64,
      pr1645v2TTmplPerfiOutPQsD7PerformanceViolTxPkts
         Counter64,
      pr1645v2TTmplPerfiOutPQsD7PerformanceTotOcts
         Counter64,
      pr1645v2TTmplPerfiOutPQsD7PerformanceDirTxOcts
         Counter64,
      pr1645v2TTmplPerfiOutPQsD7PerformanceQdOcts
         Counter64,
      pr1645v2TTmplPerfiOutPQsD7PerformanceDropOcts
         Counter64,
      pr1645v2TTmplPerfiOutPQsD7PerformanceRDropOcts
         Counter64,
      pr1645v2TTmplPerfiOutPQsD7PerformanceCirTxOcts
         Counter64,
      pr1645v2TTmplPerfiOutPQsD7PerformanceEirTxOcts
         Counter64,
      pr1645v2TTmplPerfiOutPQsD7PerformanceViolTxOcts
         Counter64,
      pr1645v2TTmplPerfiOutPQsD7PerformanceBandwidth
         Integer32
      }

pr1645v2TTmplPerfiOutPQsD7PerformanceTableIx OBJECT-TYPE
   SYNTAX      TableIndex
   MAX-ACCESS  not-accessible
   STATUS      current
   DESCRIPTION
      ""
   ::= {pr1645v2TTmplPerfiOutPQsD7PerformanceEntry 11}

pr1645v2TTmplPerfiOutPQsD7PerformanceSysUpTime OBJECT-TYPE
   SYNTAX      TimeTicks
   MAX-ACCESS  read-only
   STATUS      current
   DESCRIPTION
      "Path: tunnels.performance.ipsecL2tpTunnels.outPriorityQueues.d7Performance.sysUpTime

       Time in centi-second."
   ::= {pr1645v2TTmplPerfiOutPQsD7PerformanceEntry 16777216}

pr1645v2TTmplPerfiOutPQsD7PerformanceTotPkts OBJECT-TYPE
   SYNTAX      Counter64
   MAX-ACCESS  read-only
   STATUS      current
   DESCRIPTION
      "Path: tunnels.performance.ipsecL2tpTunnels.outPriorityQueues.d7Performance.totalPkts

       64 bit unsigned wrappable counter."
   ::= {pr1645v2TTmplPerfiOutPQsD7PerformanceEntry 234881024}

pr1645v2TTmplPerfiOutPQsD7PerformanceDirTxPkts OBJECT-TYPE
   SYNTAX      Counter64
   MAX-ACCESS  read-only
   STATUS      current
   DESCRIPTION
      "Path: tunnels.performance.ipsecL2tpTunnels.outPriorityQueues.d7Performance.directTxPkts

       64 bit unsigned wrappable counter."
   ::= {pr1645v2TTmplPerfiOutPQsD7PerformanceEntry 33554432}

pr1645v2TTmplPerfiOutPQsD7PerformanceQdPkts OBJECT-TYPE
   SYNTAX      Counter64
   MAX-ACCESS  read-only
   STATUS      current
   DESCRIPTION
      "Path: tunnels.performance.ipsecL2tpTunnels.outPriorityQueues.d7Performance.queuedPkts

       64 bit unsigned wrappable counter."
   ::= {pr1645v2TTmplPerfiOutPQsD7PerformanceEntry 50331648}

pr1645v2TTmplPerfiOutPQsD7PerformanceDropPkts OBJECT-TYPE
   SYNTAX      Counter64
   MAX-ACCESS  read-only
   STATUS      current
   DESCRIPTION
      "Path: tunnels.performance.ipsecL2tpTunnels.outPriorityQueues.d7Performance.droppedPkts

       64 bit unsigned wrappable counter."
   ::= {pr1645v2TTmplPerfiOutPQsD7PerformanceEntry 67108864}

pr1645v2TTmplPerfiOutPQsD7PerformanceRDropPkts OBJECT-TYPE
   SYNTAX      Counter64
   MAX-ACCESS  read-only
   STATUS      current
   DESCRIPTION
      "Path: tunnels.performance.ipsecL2tpTunnels.outPriorityQueues.d7Performance.redDroppedPkts

       64 bit unsigned wrappable counter."
   ::= {pr1645v2TTmplPerfiOutPQsD7PerformanceEntry 201326592}

pr1645v2TTmplPerfiOutPQsD7PerformanceCirTxPkts OBJECT-TYPE
   SYNTAX      Counter64
   MAX-ACCESS  read-only
   STATUS      current
   DESCRIPTION
      "Path: tunnels.performance.ipsecL2tpTunnels.outPriorityQueues.d7Performance.cirTxPkts

       64 bit unsigned wrappable counter."
   ::= {pr1645v2TTmplPerfiOutPQsD7PerformanceEntry 83886080}

pr1645v2TTmplPerfiOutPQsD7PerformanceEirTxPkts OBJECT-TYPE
   SYNTAX      Counter64
   MAX-ACCESS  read-only
   STATUS      current
   DESCRIPTION
      "Path: tunnels.performance.ipsecL2tpTunnels.outPriorityQueues.d7Performance.eirTxPkts

       64 bit unsigned wrappable counter."
   ::= {pr1645v2TTmplPerfiOutPQsD7PerformanceEntry 100663296}

pr1645v2TTmplPerfiOutPQsD7PerformanceViolTxPkts OBJECT-TYPE
   SYNTAX      Counter64
   MAX-ACCESS  read-only
   STATUS      current
   DESCRIPTION
      "Path: tunnels.performance.ipsecL2tpTunnels.outPriorityQueues.d7Performance.violateTxPkts

       64 bit unsigned wrappable counter."
   ::= {pr1645v2TTmplPerfiOutPQsD7PerformanceEntry 301989888}

pr1645v2TTmplPerfiOutPQsD7PerformanceTotOcts OBJECT-TYPE
   SYNTAX      Counter64
   MAX-ACCESS  read-only
   STATUS      current
   DESCRIPTION
      "Path: tunnels.performance.ipsecL2tpTunnels.outPriorityQueues.d7Performance.totalOctets

       64 bit unsigned wrappable counter."
   ::= {pr1645v2TTmplPerfiOutPQsD7PerformanceEntry 251658240}

pr1645v2TTmplPerfiOutPQsD7PerformanceDirTxOcts OBJECT-TYPE
   SYNTAX      Counter64
   MAX-ACCESS  read-only
   STATUS      current
   DESCRIPTION
      "Path: tunnels.performance.ipsecL2tpTunnels.outPriorityQueues.d7Performance.directTxOctets

       64 bit unsigned wrappable counter."
   ::= {pr1645v2TTmplPerfiOutPQsD7PerformanceEntry 117440512}

pr1645v2TTmplPerfiOutPQsD7PerformanceQdOcts OBJECT-TYPE
   SYNTAX      Counter64
   MAX-ACCESS  read-only
   STATUS      current
   DESCRIPTION
      "Path: tunnels.performance.ipsecL2tpTunnels.outPriorityQueues.d7Performance.queuedOctets

       64 bit unsigned wrappable counter."
   ::= {pr1645v2TTmplPerfiOutPQsD7PerformanceEntry 134217728}

pr1645v2TTmplPerfiOutPQsD7PerformanceDropOcts OBJECT-TYPE
   SYNTAX      Counter64
   MAX-ACCESS  read-only
   STATUS      current
   DESCRIPTION
      "Path: tunnels.performance.ipsecL2tpTunnels.outPriorityQueues.d7Performance.droppedOctets

       64 bit unsigned wrappable counter."
   ::= {pr1645v2TTmplPerfiOutPQsD7PerformanceEntry 150994944}

pr1645v2TTmplPerfiOutPQsD7PerformanceRDropOcts OBJECT-TYPE
   SYNTAX      Counter64
   MAX-ACCESS  read-only
   STATUS      current
   DESCRIPTION
      "Path: tunnels.performance.ipsecL2tpTunnels.outPriorityQueues.d7Performance.redDroppedOctets

       64 bit unsigned wrappable counter."
   ::= {pr1645v2TTmplPerfiOutPQsD7PerformanceEntry 218103808}

pr1645v2TTmplPerfiOutPQsD7PerformanceCirTxOcts OBJECT-TYPE
   SYNTAX      Counter64
   MAX-ACCESS  read-only
   STATUS      current
   DESCRIPTION
      "Path: tunnels.performance.ipsecL2tpTunnels.outPriorityQueues.d7Performance.cirTxOctets

       64 bit unsigned wrappable counter."
   ::= {pr1645v2TTmplPerfiOutPQsD7PerformanceEntry 167772160}

pr1645v2TTmplPerfiOutPQsD7PerformanceEirTxOcts OBJECT-TYPE
   SYNTAX      Counter64
   MAX-ACCESS  read-only
   STATUS      current
   DESCRIPTION
      "Path: tunnels.performance.ipsecL2tpTunnels.outPriorityQueues.d7Performance.eirTxOctets

       64 bit unsigned wrappable counter."
   ::= {pr1645v2TTmplPerfiOutPQsD7PerformanceEntry 184549376}

pr1645v2TTmplPerfiOutPQsD7PerformanceViolTxOcts OBJECT-TYPE
   SYNTAX      Counter64
   MAX-ACCESS  read-only
   STATUS      current
   DESCRIPTION
      "Path: tunnels.performance.ipsecL2tpTunnels.outPriorityQueues.d7Performance.violateTxOctets

       64 bit unsigned wrappable counter."
   ::= {pr1645v2TTmplPerfiOutPQsD7PerformanceEntry 318767104}

pr1645v2TTmplPerfiOutPQsD7PerformanceBandwidth OBJECT-TYPE
   SYNTAX      Integer32
   MAX-ACCESS  read-only
   STATUS      current
   DESCRIPTION
      "Path: tunnels.performance.ipsecL2tpTunnels.outPriorityQueues.d7Performance.bandwidth

       unit name = bps
       formula = 8 * ; 8 /"
   ::= {pr1645v2TTmplPerfiOutPQsD7PerformanceEntry 268435456}


pr1645v2TTmplPGre OBJECT IDENTIFIER ::= {pr1645v2TTmpl 23}

pr1645v2TTmplPGreSSCTable OBJECT-TYPE
   SYNTAX      SEQUENCE OF Pr1645v2TTmplPGreEntry
   MAX-ACCESS  not-accessible
   STATUS      current
   DESCRIPTION
      ""
   ::= {pr1645v2TTmplPGre 1}

pr1645v2TTmplPGreEntry OBJECT-TYPE
   SYNTAX      Pr1645v2TTmplPGreEntry
   MAX-ACCESS  not-accessible
   STATUS      current
   DESCRIPTION
      ""
   INDEX      { pr1645v2TTmplPGreTableIx }
   ::= {pr1645v2TTmplPGreSSCTable 1}

Pr1645v2TTmplPGreEntry ::=
   SEQUENCE
      {
      pr1645v2TTmplPGreTableIx
         TableIndex,
      pr1645v2TTmplPGreName
         DisplayString,
      pr1645v2TTmplPGreMCInOctets
         Counter64,
      pr1645v2TTmplPGreMCInUcast
         Counter64,
      pr1645v2TTmplPGreMCInNUcastPkts
         Counter64,
      pr1645v2TTmplPGreMCInBcastPkts
         Counter64,
      pr1645v2TTmplPGreMCInMcastPkts
         Counter64,
      pr1645v2TTmplPGreMCInDiscards
         Counter64,
      pr1645v2TTmplPGreMCInErrors
         Counter64,
      pr1645v2TTmplPGreMCInUnknownProtos
         Counter64,
      pr1645v2TTmplPGreMCInDropEx
         Counter64,
      pr1645v2TTmplPGreMCInDropNoMac
         Counter64,
      pr1645v2TTmplPGreMCInDropNUCast
         Counter64,
      pr1645v2TTmplPGreMCInDropFilter
         Counter64,
      pr1645v2TTmplPGreMCInBandwidth15sec
         Integer32,
      pr1645v2TTmplPGreMCInBandwidth30sec
         Integer32,
      pr1645v2TTmplPGreMCInBandwidth1min
         Integer32,
      pr1645v2TTmplPGreMCInBandwidth2min
         Integer32,
      pr1645v2TTmplPGreMCInBandwidth5min
         Integer32,
      pr1645v2TTmplPGreMCOutOctets
         Counter64,
      pr1645v2TTmplPGreMCOutUcastPkts
         Counter64,
      pr1645v2TTmplPGreMCOutNUcastPkts
         Counter64,
      pr1645v2TTmplPGreMCOutBcastPkts
         Counter64,
      pr1645v2TTmplPGreMCOutMcastPkts
         Counter64,
      pr1645v2TTmplPGreMCOutDiscards
         Counter64,
      pr1645v2TTmplPGreMCOutErrors
         Counter64,
      pr1645v2TTmplPGreMCOutQLen
         Counter32,
      pr1645v2TTmplPGreMCOutDropEx
         Counter64,
      pr1645v2TTmplPGreMCOutDropNoArp
         Counter64,
      pr1645v2TTmplPGreMCOutDropFilter
         Counter64,
      pr1645v2TTmplPGreMCOutBandwidth15sec
         Integer32,
      pr1645v2TTmplPGreMCOutBandwidth30sec
         Integer32,
      pr1645v2TTmplPGreMCOutBandwidth1min
         Integer32,
      pr1645v2TTmplPGreMCOutBandwidth2min
         Integer32,
      pr1645v2TTmplPGreMCOutBandwidth5min
         Integer32,
      pr1645v2TTmplPGreGreKeepAliveRequestsSent
         Counter32,
      pr1645v2TTmplPGreGreKeepAliveRepliesRcvd
         Counter32
      }

pr1645v2TTmplPGreTableIx OBJECT-TYPE
   SYNTAX      TableIndex
   MAX-ACCESS  not-accessible
   STATUS      current
   DESCRIPTION
      ""
   ::= {pr1645v2TTmplPGreEntry 11}

pr1645v2TTmplPGreName OBJECT-TYPE
   SYNTAX      DisplayString
   MAX-ACCESS  read-only
   STATUS      current
   DESCRIPTION
      "Path: tunnels.performance.greTunnels.name"
   ::= {pr1645v2TTmplPGreEntry 16777216}

pr1645v2TTmplPGreMCInOctets OBJECT-TYPE
   SYNTAX      Counter64
   MAX-ACCESS  read-only
   STATUS      current
   DESCRIPTION
      "Path: tunnels.performance.greTunnels.mibCounters.ifInOctets

       64 bit unsigned wrappable counter."
   ::= {pr1645v2TTmplPGreEntry 40697856}

pr1645v2TTmplPGreMCInUcast OBJECT-TYPE
   SYNTAX      Counter64
   MAX-ACCESS  read-only
   STATUS      current
   DESCRIPTION
      "Path: tunnels.performance.greTunnels.mibCounters.ifInUcastPkts

       64 bit unsigned wrappable counter."
   ::= {pr1645v2TTmplPGreEntry 40763392}

pr1645v2TTmplPGreMCInNUcastPkts OBJECT-TYPE
   SYNTAX      Counter64
   MAX-ACCESS  read-only
   STATUS      current
   DESCRIPTION
      "Path: tunnels.performance.greTunnels.mibCounters.ifInNUcastPkts

       64 bit unsigned wrappable counter."
   ::= {pr1645v2TTmplPGreEntry 40828928}

pr1645v2TTmplPGreMCInBcastPkts OBJECT-TYPE
   SYNTAX      Counter64
   MAX-ACCESS  read-only
   STATUS      current
   DESCRIPTION
      "Path: tunnels.performance.greTunnels.mibCounters.ifInBcastPkts

       64 bit unsigned wrappable counter."
   ::= {pr1645v2TTmplPGreEntry 47382528}

pr1645v2TTmplPGreMCInMcastPkts OBJECT-TYPE
   SYNTAX      Counter64
   MAX-ACCESS  read-only
   STATUS      current
   DESCRIPTION
      "Path: tunnels.performance.greTunnels.mibCounters.ifInMcastPkts

       64 bit unsigned wrappable counter."
   ::= {pr1645v2TTmplPGreEntry 48037888}

pr1645v2TTmplPGreMCInDiscards OBJECT-TYPE
   SYNTAX      Counter64
   MAX-ACCESS  read-only
   STATUS      current
   DESCRIPTION
      "Path: tunnels.performance.greTunnels.mibCounters.ifInDiscards

       64 bit unsigned wrappable counter."
   ::= {pr1645v2TTmplPGreEntry 40894464}

pr1645v2TTmplPGreMCInErrors OBJECT-TYPE
   SYNTAX      Counter64
   MAX-ACCESS  read-only
   STATUS      current
   DESCRIPTION
      "Path: tunnels.performance.greTunnels.mibCounters.ifInErrors

       64 bit unsigned wrappable counter."
   ::= {pr1645v2TTmplPGreEntry 40960000}

pr1645v2TTmplPGreMCInUnknownProtos OBJECT-TYPE
   SYNTAX      Counter64
   MAX-ACCESS  read-only
   STATUS      current
   DESCRIPTION
      "Path: tunnels.performance.greTunnels.mibCounters.ifInUnknownProtos

       64 bit unsigned wrappable counter."
   ::= {pr1645v2TTmplPGreEntry 41025536}

pr1645v2TTmplPGreMCInDropEx OBJECT-TYPE
   SYNTAX      Counter64
   MAX-ACCESS  read-only
   STATUS      current
   DESCRIPTION
      "Path: tunnels.performance.greTunnels.mibCounters.ifInDropLevelExceeded

       64 bit unsigned wrappable counter."
   ::= {pr1645v2TTmplPGreEntry 42074112}

pr1645v2TTmplPGreMCInDropNoMac OBJECT-TYPE
   SYNTAX      Counter64
   MAX-ACCESS  read-only
   STATUS      current
   DESCRIPTION
      "Path: tunnels.performance.greTunnels.mibCounters.ifInDiscardsNoMacFit

       64 bit unsigned wrappable counter."
   ::= {pr1645v2TTmplPGreEntry 42270720}

pr1645v2TTmplPGreMCInDropNUCast OBJECT-TYPE
   SYNTAX      Counter64
   MAX-ACCESS  read-only
   STATUS      current
   DESCRIPTION
      "Path: tunnels.performance.greTunnels.mibCounters.ifInDiscardsNUCast

       64 bit unsigned wrappable counter."
   ::= {pr1645v2TTmplPGreEntry 42467328}

pr1645v2TTmplPGreMCInDropFilter OBJECT-TYPE
   SYNTAX      Counter64
   MAX-ACCESS  read-only
   STATUS      current
   DESCRIPTION
      "Path: tunnels.performance.greTunnels.mibCounters.ifInDiscardsFilter

       64 bit unsigned wrappable counter."
   ::= {pr1645v2TTmplPGreEntry 42532864}

pr1645v2TTmplPGreMCInBandwidth15sec OBJECT-TYPE
   SYNTAX      Integer32
   MAX-ACCESS  read-only
   STATUS      current
   DESCRIPTION
      "Path: tunnels.performance.greTunnels.mibCounters.ifInBandwidth.15sec

       unit name = bps
       formula = 8 * ; 8 /"
   ::= {pr1645v2TTmplPGreEntry 45417728}

pr1645v2TTmplPGreMCInBandwidth30sec OBJECT-TYPE
   SYNTAX      Integer32
   MAX-ACCESS  read-only
   STATUS      current
   DESCRIPTION
      "Path: tunnels.performance.greTunnels.mibCounters.ifInBandwidth.30sec

       unit name = bps
       formula = 8 * ; 8 /"
   ::= {pr1645v2TTmplPGreEntry 45419008}

pr1645v2TTmplPGreMCInBandwidth1min OBJECT-TYPE
   SYNTAX      Integer32
   MAX-ACCESS  read-only
   STATUS      current
   DESCRIPTION
      "Path: tunnels.performance.greTunnels.mibCounters.ifInBandwidth.1min

       unit name = bps
       formula = 8 * ; 8 /"
   ::= {pr1645v2TTmplPGreEntry 45421568}

pr1645v2TTmplPGreMCInBandwidth2min OBJECT-TYPE
   SYNTAX      Integer32
   MAX-ACCESS  read-only
   STATUS      current
   DESCRIPTION
      "Path: tunnels.performance.greTunnels.mibCounters.ifInBandwidth.2min

       unit name = bps
       formula = 8 * ; 8 /"
   ::= {pr1645v2TTmplPGreEntry 45426688}

pr1645v2TTmplPGreMCInBandwidth5min OBJECT-TYPE
   SYNTAX      Integer32
   MAX-ACCESS  read-only
   STATUS      current
   DESCRIPTION
      "Path: tunnels.performance.greTunnels.mibCounters.ifInBandwidth.5min

       unit name = bps
       formula = 8 * ; 8 /"
   ::= {pr1645v2TTmplPGreEntry 45442048}

pr1645v2TTmplPGreMCOutOctets OBJECT-TYPE
   SYNTAX      Counter64
   MAX-ACCESS  read-only
   STATUS      current
   DESCRIPTION
      "Path: tunnels.performance.greTunnels.mibCounters.ifOutOctets

       64 bit unsigned wrappable counter."
   ::= {pr1645v2TTmplPGreEntry 41091072}

pr1645v2TTmplPGreMCOutUcastPkts OBJECT-TYPE
   SYNTAX      Counter64
   MAX-ACCESS  read-only
   STATUS      current
   DESCRIPTION
      "Path: tunnels.performance.greTunnels.mibCounters.ifOutUcastPkts

       64 bit unsigned wrappable counter."
   ::= {pr1645v2TTmplPGreEntry 41156608}

pr1645v2TTmplPGreMCOutNUcastPkts OBJECT-TYPE
   SYNTAX      Counter64
   MAX-ACCESS  read-only
   STATUS      current
   DESCRIPTION
      "Path: tunnels.performance.greTunnels.mibCounters.ifOutNUcastPkts

       64 bit unsigned wrappable counter."
   ::= {pr1645v2TTmplPGreEntry 41222144}

pr1645v2TTmplPGreMCOutBcastPkts OBJECT-TYPE
   SYNTAX      Counter64
   MAX-ACCESS  read-only
   STATUS      current
   DESCRIPTION
      "Path: tunnels.performance.greTunnels.mibCounters.ifOutBcastPkts

       64 bit unsigned wrappable counter."
   ::= {pr1645v2TTmplPGreEntry 47775744}

pr1645v2TTmplPGreMCOutMcastPkts OBJECT-TYPE
   SYNTAX      Counter64
   MAX-ACCESS  read-only
   STATUS      current
   DESCRIPTION
      "Path: tunnels.performance.greTunnels.mibCounters.ifOutMcastPkts

       64 bit unsigned wrappable counter."
   ::= {pr1645v2TTmplPGreEntry 48431104}

pr1645v2TTmplPGreMCOutDiscards OBJECT-TYPE
   SYNTAX      Counter64
   MAX-ACCESS  read-only
   STATUS      current
   DESCRIPTION
      "Path: tunnels.performance.greTunnels.mibCounters.ifOutDiscards

       64 bit unsigned wrappable counter."
   ::= {pr1645v2TTmplPGreEntry 41287680}

pr1645v2TTmplPGreMCOutErrors OBJECT-TYPE
   SYNTAX      Counter64
   MAX-ACCESS  read-only
   STATUS      current
   DESCRIPTION
      "Path: tunnels.performance.greTunnels.mibCounters.ifOutErrors

       64 bit unsigned wrappable counter."
   ::= {pr1645v2TTmplPGreEntry 41353216}

pr1645v2TTmplPGreMCOutQLen OBJECT-TYPE
   SYNTAX      Counter32
   MAX-ACCESS  read-only
   STATUS      current
   DESCRIPTION
      "Path: tunnels.performance.greTunnels.mibCounters.ifOutQLen

       32 bit unsigned wrappable counter."
   ::= {pr1645v2TTmplPGreEntry 41418752}

pr1645v2TTmplPGreMCOutDropEx OBJECT-TYPE
   SYNTAX      Counter64
   MAX-ACCESS  read-only
   STATUS      current
   DESCRIPTION
      "Path: tunnels.performance.greTunnels.mibCounters.ifOutDropLevelExceeded

       64 bit unsigned wrappable counter."
   ::= {pr1645v2TTmplPGreEntry 41484288}

pr1645v2TTmplPGreMCOutDropNoArp OBJECT-TYPE
   SYNTAX      Counter64
   MAX-ACCESS  read-only
   STATUS      current
   DESCRIPTION
      "Path: tunnels.performance.greTunnels.mibCounters.ifOutDiscardsNoArp

       64 bit unsigned wrappable counter."
   ::= {pr1645v2TTmplPGreEntry 42336256}

pr1645v2TTmplPGreMCOutDropFilter OBJECT-TYPE
   SYNTAX      Counter64
   MAX-ACCESS  read-only
   STATUS      current
   DESCRIPTION
      "Path: tunnels.performance.greTunnels.mibCounters.ifOutDiscardsFilter

       64 bit unsigned wrappable counter."
   ::= {pr1645v2TTmplPGreEntry 42598400}

pr1645v2TTmplPGreMCOutBandwidth15sec OBJECT-TYPE
   SYNTAX      Integer32
   MAX-ACCESS  read-only
   STATUS      current
   DESCRIPTION
      "Path: tunnels.performance.greTunnels.mibCounters.ifOutBandwidth.15sec

       unit name = bps
       formula = 8 * ; 8 /"
   ::= {pr1645v2TTmplPGreEntry 45483264}

pr1645v2TTmplPGreMCOutBandwidth30sec OBJECT-TYPE
   SYNTAX      Integer32
   MAX-ACCESS  read-only
   STATUS      current
   DESCRIPTION
      "Path: tunnels.performance.greTunnels.mibCounters.ifOutBandwidth.30sec

       unit name = bps
       formula = 8 * ; 8 /"
   ::= {pr1645v2TTmplPGreEntry 45484544}

pr1645v2TTmplPGreMCOutBandwidth1min OBJECT-TYPE
   SYNTAX      Integer32
   MAX-ACCESS  read-only
   STATUS      current
   DESCRIPTION
      "Path: tunnels.performance.greTunnels.mibCounters.ifOutBandwidth.1min

       unit name = bps
       formula = 8 * ; 8 /"
   ::= {pr1645v2TTmplPGreEntry 45487104}

pr1645v2TTmplPGreMCOutBandwidth2min OBJECT-TYPE
   SYNTAX      Integer32
   MAX-ACCESS  read-only
   STATUS      current
   DESCRIPTION
      "Path: tunnels.performance.greTunnels.mibCounters.ifOutBandwidth.2min

       unit name = bps
       formula = 8 * ; 8 /"
   ::= {pr1645v2TTmplPGreEntry 45492224}

pr1645v2TTmplPGreMCOutBandwidth5min OBJECT-TYPE
   SYNTAX      Integer32
   MAX-ACCESS  read-only
   STATUS      current
   DESCRIPTION
      "Path: tunnels.performance.greTunnels.mibCounters.ifOutBandwidth.5min

       unit name = bps
       formula = 8 * ; 8 /"
   ::= {pr1645v2TTmplPGreEntry 45507584}

pr1645v2TTmplPGreGreKeepAliveRequestsSent OBJECT-TYPE
   SYNTAX      Counter32
   MAX-ACCESS  read-only
   STATUS      current
   DESCRIPTION
      "Path: tunnels.performance.greTunnels.gre.keepAlive.requestsSent

       32 bit unsigned wrappable counter."
   ::= {pr1645v2TTmplPGreEntry 117506304}

pr1645v2TTmplPGreGreKeepAliveRepliesRcvd OBJECT-TYPE
   SYNTAX      Counter32
   MAX-ACCESS  read-only
   STATUS      current
   DESCRIPTION
      "Path: tunnels.performance.greTunnels.gre.keepAlive.repliesRcvd

       32 bit unsigned wrappable counter."
   ::= {pr1645v2TTmplPGreEntry 117506560}

pr1645v2TTmplPGreMCH2P OBJECT-TYPE
   SYNTAX      SEQUENCE OF Pr1645v2TTmplPGreMCH2PEntry
   MAX-ACCESS  not-accessible
   STATUS      current
   DESCRIPTION
      ""
   ::= {pr1645v2TTmplPGre 41549824}

pr1645v2TTmplPGreMCH2PEntry OBJECT-TYPE
   SYNTAX      Pr1645v2TTmplPGreMCH2PEntry
   MAX-ACCESS  not-accessible
   STATUS      current
   DESCRIPTION
      ""
   INDEX      { pr1645v2TTmplPGreTableIx,
                pr1645v2TTmplPGreMCH2PTableIx }
   ::= {pr1645v2TTmplPGreMCH2P 1}

Pr1645v2TTmplPGreMCH2PEntry ::=
   SEQUENCE
      {
      pr1645v2TTmplPGreMCH2PTableIx
         TableIndex,
      pr1645v2TTmplPGreMCH2PSysUpTime
         TimeTicks,
      pr1645v2TTmplPGreMCH2PIfUpTime
         TimeTicks,
      pr1645v2TTmplPGreMCH2PIfStatChanges
         Counter32,
      pr1645v2TTmplPGreMCH2PIfInOctets
         Counter64,
      pr1645v2TTmplPGreMCH2PIfInUCPkts
         Counter64,
      pr1645v2TTmplPGreMCH2PIfInNUCPkts
         Counter64,
      pr1645v2TTmplPGreMCH2PIfInBCPkts
         Counter64,
      pr1645v2TTmplPGreMCH2PIfInMCPkts
         Counter64,
      pr1645v2TTmplPGreMCH2PIfInDiscards
         Counter64,
      pr1645v2TTmplPGreMCH2PIfInErrors
         Counter64,
      pr1645v2TTmplPGreMCH2PIfInUnkwn
         Counter64,
      pr1645v2TTmplPGreMCH2PInDropEx
         Counter64,
      pr1645v2TTmplPGreMCH2PInDropNoMac
         Counter64,
      pr1645v2TTmplPGreMCH2PInDropNUCast
         Counter64,
      pr1645v2TTmplPGreMCH2PInDropFilter
         Counter64,
      pr1645v2TTmplPGreMCH2PIfInBandwidth
         Integer32,
      pr1645v2TTmplPGreMCH2PIfOutOctets
         Counter64,
      pr1645v2TTmplPGreMCH2PIfOutUCPkts
         Counter64,
      pr1645v2TTmplPGreMCH2PIfOutNUCPkts
         Counter64,
      pr1645v2TTmplPGreMCH2PIfOutBCPkts
         Counter64,
      pr1645v2TTmplPGreMCH2PIfOutMCPkts
         Counter64,
      pr1645v2TTmplPGreMCH2PIfOutDiscards
         Counter64,
      pr1645v2TTmplPGreMCH2PIfOutErrors
         Counter64,
      pr1645v2TTmplPGreMCH2POutDropEx
         Counter64,
      pr1645v2TTmplPGreMCH2POutDropNoArp
         Counter64,
      pr1645v2TTmplPGreMCH2POutDropFilter
         Counter64,
      pr1645v2TTmplPGreMCH2PIfOutBandwidth
         Integer32,
      pr1645v2TTmplPGreMCH2PIfErrSec
         Counter32
      }

pr1645v2TTmplPGreMCH2PTableIx OBJECT-TYPE
   SYNTAX      TableIndex
   MAX-ACCESS  not-accessible
   STATUS      current
   DESCRIPTION
      ""
   ::= {pr1645v2TTmplPGreMCH2PEntry 11}

pr1645v2TTmplPGreMCH2PSysUpTime OBJECT-TYPE
   SYNTAX      TimeTicks
   MAX-ACCESS  read-only
   STATUS      current
   DESCRIPTION
      "Path: tunnels.performance.greTunnels.mibCounters.h2Performance.sysUpTime

       Time in centi-second."
   ::= {pr1645v2TTmplPGreMCH2PEntry 16777216}

pr1645v2TTmplPGreMCH2PIfUpTime OBJECT-TYPE
   SYNTAX      TimeTicks
   MAX-ACCESS  read-only
   STATUS      current
   DESCRIPTION
      "Path: tunnels.performance.greTunnels.mibCounters.h2Performance.ifUpTime

       Time in centi-second."
   ::= {pr1645v2TTmplPGreMCH2PEntry 33554432}

pr1645v2TTmplPGreMCH2PIfStatChanges OBJECT-TYPE
   SYNTAX      Counter32
   MAX-ACCESS  read-only
   STATUS      current
   DESCRIPTION
      "Path: tunnels.performance.greTunnels.mibCounters.h2Performance.ifStatusChanges

       32 bit unsigned wrappable counter."
   ::= {pr1645v2TTmplPGreMCH2PEntry 50331648}

pr1645v2TTmplPGreMCH2PIfInOctets OBJECT-TYPE
   SYNTAX      Counter64
   MAX-ACCESS  read-only
   STATUS      current
   DESCRIPTION
      "Path: tunnels.performance.greTunnels.mibCounters.h2Performance.ifInOctets

       64 bit unsigned wrappable counter."
   ::= {pr1645v2TTmplPGreMCH2PEntry 67108864}

pr1645v2TTmplPGreMCH2PIfInUCPkts OBJECT-TYPE
   SYNTAX      Counter64
   MAX-ACCESS  read-only
   STATUS      current
   DESCRIPTION
      "Path: tunnels.performance.greTunnels.mibCounters.h2Performance.ifInUcastPkts

       64 bit unsigned wrappable counter."
   ::= {pr1645v2TTmplPGreMCH2PEntry 83886080}

pr1645v2TTmplPGreMCH2PIfInNUCPkts OBJECT-TYPE
   SYNTAX      Counter64
   MAX-ACCESS  read-only
   STATUS      current
   DESCRIPTION
      "Path: tunnels.performance.greTunnels.mibCounters.h2Performance.ifInNUcastPkts

       64 bit unsigned wrappable counter."
   ::= {pr1645v2TTmplPGreMCH2PEntry 100663296}

pr1645v2TTmplPGreMCH2PIfInBCPkts OBJECT-TYPE
   SYNTAX      Counter64
   MAX-ACCESS  read-only
   STATUS      current
   DESCRIPTION
      "Path: tunnels.performance.greTunnels.mibCounters.h2Performance.ifInBcastPkts

       64 bit unsigned wrappable counter."
   ::= {pr1645v2TTmplPGreMCH2PEntry 419430400}

pr1645v2TTmplPGreMCH2PIfInMCPkts OBJECT-TYPE
   SYNTAX      Counter64
   MAX-ACCESS  read-only
   STATUS      current
   DESCRIPTION
      "Path: tunnels.performance.greTunnels.mibCounters.h2Performance.ifInMcastPkts

       64 bit unsigned wrappable counter."
   ::= {pr1645v2TTmplPGreMCH2PEntry 436207616}

pr1645v2TTmplPGreMCH2PIfInDiscards OBJECT-TYPE
   SYNTAX      Counter64
   MAX-ACCESS  read-only
   STATUS      current
   DESCRIPTION
      "Path: tunnels.performance.greTunnels.mibCounters.h2Performance.ifInDiscards

       64 bit unsigned wrappable counter."
   ::= {pr1645v2TTmplPGreMCH2PEntry 117440512}

pr1645v2TTmplPGreMCH2PIfInErrors OBJECT-TYPE
   SYNTAX      Counter64
   MAX-ACCESS  read-only
   STATUS      current
   DESCRIPTION
      "Path: tunnels.performance.greTunnels.mibCounters.h2Performance.ifInErrors

       64 bit unsigned wrappable counter."
   ::= {pr1645v2TTmplPGreMCH2PEntry 134217728}

pr1645v2TTmplPGreMCH2PIfInUnkwn OBJECT-TYPE
   SYNTAX      Counter64
   MAX-ACCESS  read-only
   STATUS      current
   DESCRIPTION
      "Path: tunnels.performance.greTunnels.mibCounters.h2Performance.ifInUnknownProtos

       64 bit unsigned wrappable counter."
   ::= {pr1645v2TTmplPGreMCH2PEntry 150994944}

pr1645v2TTmplPGreMCH2PInDropEx OBJECT-TYPE
   SYNTAX      Counter64
   MAX-ACCESS  read-only
   STATUS      current
   DESCRIPTION
      "Path: tunnels.performance.greTunnels.mibCounters.h2Performance.ifInDropLevelExceeded

       64 bit unsigned wrappable counter."
   ::= {pr1645v2TTmplPGreMCH2PEntry 335544320}

pr1645v2TTmplPGreMCH2PInDropNoMac OBJECT-TYPE
   SYNTAX      Counter64
   MAX-ACCESS  read-only
   STATUS      current
   DESCRIPTION
      "Path: tunnels.performance.greTunnels.mibCounters.h2Performance.fInDiscardsNoMacFit

       64 bit unsigned wrappable counter."
   ::= {pr1645v2TTmplPGreMCH2PEntry 301989888}

pr1645v2TTmplPGreMCH2PInDropNUCast OBJECT-TYPE
   SYNTAX      Counter64
   MAX-ACCESS  read-only
   STATUS      current
   DESCRIPTION
      "Path: tunnels.performance.greTunnels.mibCounters.h2Performance.fInDiscardsNUCast

       64 bit unsigned wrappable counter."
   ::= {pr1645v2TTmplPGreMCH2PEntry 318767104}

pr1645v2TTmplPGreMCH2PInDropFilter OBJECT-TYPE
   SYNTAX      Counter64
   MAX-ACCESS  read-only
   STATUS      current
   DESCRIPTION
      "Path: tunnels.performance.greTunnels.mibCounters.h2Performance.fInDiscardsFilter

       64 bit unsigned wrappable counter."
   ::= {pr1645v2TTmplPGreMCH2PEntry 385875968}

pr1645v2TTmplPGreMCH2PIfInBandwidth OBJECT-TYPE
   SYNTAX      Integer32
   MAX-ACCESS  read-only
   STATUS      current
   DESCRIPTION
      "Path: tunnels.performance.greTunnels.mibCounters.h2Performance.ifInBandwidth

       unit name = bps
       formula = 8 * ; 8 /"
   ::= {pr1645v2TTmplPGreMCH2PEntry 268435456}

pr1645v2TTmplPGreMCH2PIfOutOctets OBJECT-TYPE
   SYNTAX      Counter64
   MAX-ACCESS  read-only
   STATUS      current
   DESCRIPTION
      "Path: tunnels.performance.greTunnels.mibCounters.h2Performance.ifOutOctets

       64 bit unsigned wrappable counter."
   ::= {pr1645v2TTmplPGreMCH2PEntry 167772160}

pr1645v2TTmplPGreMCH2PIfOutUCPkts OBJECT-TYPE
   SYNTAX      Counter64
   MAX-ACCESS  read-only
   STATUS      current
   DESCRIPTION
      "Path: tunnels.performance.greTunnels.mibCounters.h2Performance.ifOutUcastPkts

       64 bit unsigned wrappable counter."
   ::= {pr1645v2TTmplPGreMCH2PEntry 184549376}

pr1645v2TTmplPGreMCH2PIfOutNUCPkts OBJECT-TYPE
   SYNTAX      Counter64
   MAX-ACCESS  read-only
   STATUS      current
   DESCRIPTION
      "Path: tunnels.performance.greTunnels.mibCounters.h2Performance.ifOutNUcastPkts

       64 bit unsigned wrappable counter."
   ::= {pr1645v2TTmplPGreMCH2PEntry 201326592}

pr1645v2TTmplPGreMCH2PIfOutBCPkts OBJECT-TYPE
   SYNTAX      Counter64
   MAX-ACCESS  read-only
   STATUS      current
   DESCRIPTION
      "Path: tunnels.performance.greTunnels.mibCounters.h2Performance.ifOutBcastPkts

       64 bit unsigned wrappable counter."
   ::= {pr1645v2TTmplPGreMCH2PEntry 452984832}

pr1645v2TTmplPGreMCH2PIfOutMCPkts OBJECT-TYPE
   SYNTAX      Counter64
   MAX-ACCESS  read-only
   STATUS      current
   DESCRIPTION
      "Path: tunnels.performance.greTunnels.mibCounters.h2Performance.ifOutMcastPkts

       64 bit unsigned wrappable counter."
   ::= {pr1645v2TTmplPGreMCH2PEntry 469762048}

pr1645v2TTmplPGreMCH2PIfOutDiscards OBJECT-TYPE
   SYNTAX      Counter64
   MAX-ACCESS  read-only
   STATUS      current
   DESCRIPTION
      "Path: tunnels.performance.greTunnels.mibCounters.h2Performance.ifOutDiscards

       64 bit unsigned wrappable counter."
   ::= {pr1645v2TTmplPGreMCH2PEntry 218103808}

pr1645v2TTmplPGreMCH2PIfOutErrors OBJECT-TYPE
   SYNTAX      Counter64
   MAX-ACCESS  read-only
   STATUS      current
   DESCRIPTION
      "Path: tunnels.performance.greTunnels.mibCounters.h2Performance.ifOutErrors

       64 bit unsigned wrappable counter."
   ::= {pr1645v2TTmplPGreMCH2PEntry 234881024}

pr1645v2TTmplPGreMCH2POutDropEx OBJECT-TYPE
   SYNTAX      Counter64
   MAX-ACCESS  read-only
   STATUS      current
   DESCRIPTION
      "Path: tunnels.performance.greTunnels.mibCounters.h2Performance.ifOutDropLevelExceeded

       64 bit unsigned wrappable counter."
   ::= {pr1645v2TTmplPGreMCH2PEntry 352321536}

pr1645v2TTmplPGreMCH2POutDropNoArp OBJECT-TYPE
   SYNTAX      Counter64
   MAX-ACCESS  read-only
   STATUS      current
   DESCRIPTION
      "Path: tunnels.performance.greTunnels.mibCounters.h2Performance.ifOutDiscardsNoArp

       64 bit unsigned wrappable counter."
   ::= {pr1645v2TTmplPGreMCH2PEntry 369098752}

pr1645v2TTmplPGreMCH2POutDropFilter OBJECT-TYPE
   SYNTAX      Counter64
   MAX-ACCESS  read-only
   STATUS      current
   DESCRIPTION
      "Path: tunnels.performance.greTunnels.mibCounters.h2Performance.ifOutDiscardsFilter

       64 bit unsigned wrappable counter."
   ::= {pr1645v2TTmplPGreMCH2PEntry 402653184}

pr1645v2TTmplPGreMCH2PIfOutBandwidth OBJECT-TYPE
   SYNTAX      Integer32
   MAX-ACCESS  read-only
   STATUS      current
   DESCRIPTION
      "Path: tunnels.performance.greTunnels.mibCounters.h2Performance.ifOutBandwidth

       unit name = bps
       formula = 8 * ; 8 /"
   ::= {pr1645v2TTmplPGreMCH2PEntry 285212672}

pr1645v2TTmplPGreMCH2PIfErrSec OBJECT-TYPE
   SYNTAX      Counter32
   MAX-ACCESS  read-only
   STATUS      current
   DESCRIPTION
      "Path: tunnels.performance.greTunnels.mibCounters.h2Performance.ifErrSec

       32 bit unsigned wrappable counter."
   ::= {pr1645v2TTmplPGreMCH2PEntry 251658240}

pr1645v2TTmplPGreMCH24P OBJECT-TYPE
   SYNTAX      SEQUENCE OF Pr1645v2TTmplPGreMCH24PEntry
   MAX-ACCESS  not-accessible
   STATUS      current
   DESCRIPTION
      ""
   ::= {pr1645v2TTmplPGre 41615360}

pr1645v2TTmplPGreMCH24PEntry OBJECT-TYPE
   SYNTAX      Pr1645v2TTmplPGreMCH24PEntry
   MAX-ACCESS  not-accessible
   STATUS      current
   DESCRIPTION
      ""
   INDEX      { pr1645v2TTmplPGreTableIx,
                pr1645v2TTmplPGreMCH24PTableIx }
   ::= {pr1645v2TTmplPGreMCH24P 1}

Pr1645v2TTmplPGreMCH24PEntry ::=
   SEQUENCE
      {
      pr1645v2TTmplPGreMCH24PTableIx
         TableIndex,
      pr1645v2TTmplPGreMCH24PSysUpTime
         TimeTicks,
      pr1645v2TTmplPGreMCH24PIfUpTime
         TimeTicks,
      pr1645v2TTmplPGreMCH24PIfStatChanges
         Counter32,
      pr1645v2TTmplPGreMCH24PIfInOctets
         Counter64,
      pr1645v2TTmplPGreMCH24PIfInUCPkts
         Counter64,
      pr1645v2TTmplPGreMCH24PIfInNUCPkts
         Counter64,
      pr1645v2TTmplPGreMCH24PIfInBCPkts
         Counter64,
      pr1645v2TTmplPGreMCH24PIfInMCPkts
         Counter64,
      pr1645v2TTmplPGreMCH24PIfInDiscards
         Counter64,
      pr1645v2TTmplPGreMCH24PIfInErrors
         Counter64,
      pr1645v2TTmplPGreMCH24PIfInUnkwn
         Counter64,
      pr1645v2TTmplPGreMCH24PInDropEx
         Counter64,
      pr1645v2TTmplPGreMCH24PInDropNoMac
         Counter64,
      pr1645v2TTmplPGreMCH24PInDropNUCast
         Counter64,
      pr1645v2TTmplPGreMCH24PInDropFilter
         Counter64,
      pr1645v2TTmplPGreMCH24PIfInBandwidth
         Integer32,
      pr1645v2TTmplPGreMCH24PIfOutOctets
         Counter64,
      pr1645v2TTmplPGreMCH24PIfOutUCPkts
         Counter64,
      pr1645v2TTmplPGreMCH24PIfOutNUCPkts
         Counter64,
      pr1645v2TTmplPGreMCH24PIfOutBCPkts
         Counter64,
      pr1645v2TTmplPGreMCH24PIfOutMCPkts
         Counter64,
      pr1645v2TTmplPGreMCH24PIfOutDiscards
         Counter64,
      pr1645v2TTmplPGreMCH24PIfOutErrors
         Counter64,
      pr1645v2TTmplPGreMCH24POutDropEx
         Counter64,
      pr1645v2TTmplPGreMCH24POutDropNoArp
         Counter64,
      pr1645v2TTmplPGreMCH24POutDropFilter
         Counter64,
      pr1645v2TTmplPGreMCH24PIfOutBandwidth
         Integer32,
      pr1645v2TTmplPGreMCH24PIfErrSec
         Counter32
      }

pr1645v2TTmplPGreMCH24PTableIx OBJECT-TYPE
   SYNTAX      TableIndex
   MAX-ACCESS  not-accessible
   STATUS      current
   DESCRIPTION
      ""
   ::= {pr1645v2TTmplPGreMCH24PEntry 11}

pr1645v2TTmplPGreMCH24PSysUpTime OBJECT-TYPE
   SYNTAX      TimeTicks
   MAX-ACCESS  read-only
   STATUS      current
   DESCRIPTION
      "Path: tunnels.performance.greTunnels.mibCounters.h24Performance.sysUpTime

       Time in centi-second."
   ::= {pr1645v2TTmplPGreMCH24PEntry 16777216}

pr1645v2TTmplPGreMCH24PIfUpTime OBJECT-TYPE
   SYNTAX      TimeTicks
   MAX-ACCESS  read-only
   STATUS      current
   DESCRIPTION
      "Path: tunnels.performance.greTunnels.mibCounters.h24Performance.ifUpTime

       Time in centi-second."
   ::= {pr1645v2TTmplPGreMCH24PEntry 33554432}

pr1645v2TTmplPGreMCH24PIfStatChanges OBJECT-TYPE
   SYNTAX      Counter32
   MAX-ACCESS  read-only
   STATUS      current
   DESCRIPTION
      "Path: tunnels.performance.greTunnels.mibCounters.h24Performance.ifStatusChanges

       32 bit unsigned wrappable counter."
   ::= {pr1645v2TTmplPGreMCH24PEntry 50331648}

pr1645v2TTmplPGreMCH24PIfInOctets OBJECT-TYPE
   SYNTAX      Counter64
   MAX-ACCESS  read-only
   STATUS      current
   DESCRIPTION
      "Path: tunnels.performance.greTunnels.mibCounters.h24Performance.ifInOctets

       64 bit unsigned wrappable counter."
   ::= {pr1645v2TTmplPGreMCH24PEntry 67108864}

pr1645v2TTmplPGreMCH24PIfInUCPkts OBJECT-TYPE
   SYNTAX      Counter64
   MAX-ACCESS  read-only
   STATUS      current
   DESCRIPTION
      "Path: tunnels.performance.greTunnels.mibCounters.h24Performance.ifInUcastPkts

       64 bit unsigned wrappable counter."
   ::= {pr1645v2TTmplPGreMCH24PEntry 83886080}

pr1645v2TTmplPGreMCH24PIfInNUCPkts OBJECT-TYPE
   SYNTAX      Counter64
   MAX-ACCESS  read-only
   STATUS      current
   DESCRIPTION
      "Path: tunnels.performance.greTunnels.mibCounters.h24Performance.ifInNUcastPkts

       64 bit unsigned wrappable counter."
   ::= {pr1645v2TTmplPGreMCH24PEntry 100663296}

pr1645v2TTmplPGreMCH24PIfInBCPkts OBJECT-TYPE
   SYNTAX      Counter64
   MAX-ACCESS  read-only
   STATUS      current
   DESCRIPTION
      "Path: tunnels.performance.greTunnels.mibCounters.h24Performance.ifInBcastPkts

       64 bit unsigned wrappable counter."
   ::= {pr1645v2TTmplPGreMCH24PEntry 419430400}

pr1645v2TTmplPGreMCH24PIfInMCPkts OBJECT-TYPE
   SYNTAX      Counter64
   MAX-ACCESS  read-only
   STATUS      current
   DESCRIPTION
      "Path: tunnels.performance.greTunnels.mibCounters.h24Performance.ifInMcastPkts

       64 bit unsigned wrappable counter."
   ::= {pr1645v2TTmplPGreMCH24PEntry 436207616}

pr1645v2TTmplPGreMCH24PIfInDiscards OBJECT-TYPE
   SYNTAX      Counter64
   MAX-ACCESS  read-only
   STATUS      current
   DESCRIPTION
      "Path: tunnels.performance.greTunnels.mibCounters.h24Performance.ifInDiscards

       64 bit unsigned wrappable counter."
   ::= {pr1645v2TTmplPGreMCH24PEntry 117440512}

pr1645v2TTmplPGreMCH24PIfInErrors OBJECT-TYPE
   SYNTAX      Counter64
   MAX-ACCESS  read-only
   STATUS      current
   DESCRIPTION
      "Path: tunnels.performance.greTunnels.mibCounters.h24Performance.ifInErrors

       64 bit unsigned wrappable counter."
   ::= {pr1645v2TTmplPGreMCH24PEntry 134217728}

pr1645v2TTmplPGreMCH24PIfInUnkwn OBJECT-TYPE
   SYNTAX      Counter64
   MAX-ACCESS  read-only
   STATUS      current
   DESCRIPTION
      "Path: tunnels.performance.greTunnels.mibCounters.h24Performance.ifInUnknownProtos

       64 bit unsigned wrappable counter."
   ::= {pr1645v2TTmplPGreMCH24PEntry 150994944}

pr1645v2TTmplPGreMCH24PInDropEx OBJECT-TYPE
   SYNTAX      Counter64
   MAX-ACCESS  read-only
   STATUS      current
   DESCRIPTION
      "Path: tunnels.performance.greTunnels.mibCounters.h24Performance.ifInDropLevelExceeded

       64 bit unsigned wrappable counter."
   ::= {pr1645v2TTmplPGreMCH24PEntry 335544320}

pr1645v2TTmplPGreMCH24PInDropNoMac OBJECT-TYPE
   SYNTAX      Counter64
   MAX-ACCESS  read-only
   STATUS      current
   DESCRIPTION
      "Path: tunnels.performance.greTunnels.mibCounters.h24Performance.fInDiscardsNoMacFit

       64 bit unsigned wrappable counter."
   ::= {pr1645v2TTmplPGreMCH24PEntry 301989888}

pr1645v2TTmplPGreMCH24PInDropNUCast OBJECT-TYPE
   SYNTAX      Counter64
   MAX-ACCESS  read-only
   STATUS      current
   DESCRIPTION
      "Path: tunnels.performance.greTunnels.mibCounters.h24Performance.fInDiscardsNUCast

       64 bit unsigned wrappable counter."
   ::= {pr1645v2TTmplPGreMCH24PEntry 318767104}

pr1645v2TTmplPGreMCH24PInDropFilter OBJECT-TYPE
   SYNTAX      Counter64
   MAX-ACCESS  read-only
   STATUS      current
   DESCRIPTION
      "Path: tunnels.performance.greTunnels.mibCounters.h24Performance.fInDiscardsFilter

       64 bit unsigned wrappable counter."
   ::= {pr1645v2TTmplPGreMCH24PEntry 385875968}

pr1645v2TTmplPGreMCH24PIfInBandwidth OBJECT-TYPE
   SYNTAX      Integer32
   MAX-ACCESS  read-only
   STATUS      current
   DESCRIPTION
      "Path: tunnels.performance.greTunnels.mibCounters.h24Performance.ifInBandwidth

       unit name = bps
       formula = 8 * ; 8 /"
   ::= {pr1645v2TTmplPGreMCH24PEntry 268435456}

pr1645v2TTmplPGreMCH24PIfOutOctets OBJECT-TYPE
   SYNTAX      Counter64
   MAX-ACCESS  read-only
   STATUS      current
   DESCRIPTION
      "Path: tunnels.performance.greTunnels.mibCounters.h24Performance.ifOutOctets

       64 bit unsigned wrappable counter."
   ::= {pr1645v2TTmplPGreMCH24PEntry 167772160}

pr1645v2TTmplPGreMCH24PIfOutUCPkts OBJECT-TYPE
   SYNTAX      Counter64
   MAX-ACCESS  read-only
   STATUS      current
   DESCRIPTION
      "Path: tunnels.performance.greTunnels.mibCounters.h24Performance.ifOutUcastPkts

       64 bit unsigned wrappable counter."
   ::= {pr1645v2TTmplPGreMCH24PEntry 184549376}

pr1645v2TTmplPGreMCH24PIfOutNUCPkts OBJECT-TYPE
   SYNTAX      Counter64
   MAX-ACCESS  read-only
   STATUS      current
   DESCRIPTION
      "Path: tunnels.performance.greTunnels.mibCounters.h24Performance.ifOutNUcastPkts

       64 bit unsigned wrappable counter."
   ::= {pr1645v2TTmplPGreMCH24PEntry 201326592}

pr1645v2TTmplPGreMCH24PIfOutBCPkts OBJECT-TYPE
   SYNTAX      Counter64
   MAX-ACCESS  read-only
   STATUS      current
   DESCRIPTION
      "Path: tunnels.performance.greTunnels.mibCounters.h24Performance.ifOutBcastPkts

       64 bit unsigned wrappable counter."
   ::= {pr1645v2TTmplPGreMCH24PEntry 452984832}

pr1645v2TTmplPGreMCH24PIfOutMCPkts OBJECT-TYPE
   SYNTAX      Counter64
   MAX-ACCESS  read-only
   STATUS      current
   DESCRIPTION
      "Path: tunnels.performance.greTunnels.mibCounters.h24Performance.ifOutMcastPkts

       64 bit unsigned wrappable counter."
   ::= {pr1645v2TTmplPGreMCH24PEntry 469762048}

pr1645v2TTmplPGreMCH24PIfOutDiscards OBJECT-TYPE
   SYNTAX      Counter64
   MAX-ACCESS  read-only
   STATUS      current
   DESCRIPTION
      "Path: tunnels.performance.greTunnels.mibCounters.h24Performance.ifOutDiscards

       64 bit unsigned wrappable counter."
   ::= {pr1645v2TTmplPGreMCH24PEntry 218103808}

pr1645v2TTmplPGreMCH24PIfOutErrors OBJECT-TYPE
   SYNTAX      Counter64
   MAX-ACCESS  read-only
   STATUS      current
   DESCRIPTION
      "Path: tunnels.performance.greTunnels.mibCounters.h24Performance.ifOutErrors

       64 bit unsigned wrappable counter."
   ::= {pr1645v2TTmplPGreMCH24PEntry 234881024}

pr1645v2TTmplPGreMCH24POutDropEx OBJECT-TYPE
   SYNTAX      Counter64
   MAX-ACCESS  read-only
   STATUS      current
   DESCRIPTION
      "Path: tunnels.performance.greTunnels.mibCounters.h24Performance.ifOutDropLevelExceeded

       64 bit unsigned wrappable counter."
   ::= {pr1645v2TTmplPGreMCH24PEntry 352321536}

pr1645v2TTmplPGreMCH24POutDropNoArp OBJECT-TYPE
   SYNTAX      Counter64
   MAX-ACCESS  read-only
   STATUS      current
   DESCRIPTION
      "Path: tunnels.performance.greTunnels.mibCounters.h24Performance.ifOutDiscardsNoArp

       64 bit unsigned wrappable counter."
   ::= {pr1645v2TTmplPGreMCH24PEntry 369098752}

pr1645v2TTmplPGreMCH24POutDropFilter OBJECT-TYPE
   SYNTAX      Counter64
   MAX-ACCESS  read-only
   STATUS      current
   DESCRIPTION
      "Path: tunnels.performance.greTunnels.mibCounters.h24Performance.ifOutDiscardsFilter

       64 bit unsigned wrappable counter."
   ::= {pr1645v2TTmplPGreMCH24PEntry 402653184}

pr1645v2TTmplPGreMCH24PIfOutBandwidth OBJECT-TYPE
   SYNTAX      Integer32
   MAX-ACCESS  read-only
   STATUS      current
   DESCRIPTION
      "Path: tunnels.performance.greTunnels.mibCounters.h24Performance.ifOutBandwidth

       unit name = bps
       formula = 8 * ; 8 /"
   ::= {pr1645v2TTmplPGreMCH24PEntry 285212672}

pr1645v2TTmplPGreMCH24PIfErrSec OBJECT-TYPE
   SYNTAX      Counter32
   MAX-ACCESS  read-only
   STATUS      current
   DESCRIPTION
      "Path: tunnels.performance.greTunnels.mibCounters.h24Performance.ifErrSec

       32 bit unsigned wrappable counter."
   ::= {pr1645v2TTmplPGreMCH24PEntry 251658240}

pr1645v2TTmplPGreMCD7P OBJECT-TYPE
   SYNTAX      SEQUENCE OF Pr1645v2TTmplPGreMCD7PEntry
   MAX-ACCESS  not-accessible
   STATUS      current
   DESCRIPTION
      ""
   ::= {pr1645v2TTmplPGre 41680896}

pr1645v2TTmplPGreMCD7PEntry OBJECT-TYPE
   SYNTAX      Pr1645v2TTmplPGreMCD7PEntry
   MAX-ACCESS  not-accessible
   STATUS      current
   DESCRIPTION
      ""
   INDEX      { pr1645v2TTmplPGreTableIx,
                pr1645v2TTmplPGreMCD7PTableIx }
   ::= {pr1645v2TTmplPGreMCD7P 1}

Pr1645v2TTmplPGreMCD7PEntry ::=
   SEQUENCE
      {
      pr1645v2TTmplPGreMCD7PTableIx
         TableIndex,
      pr1645v2TTmplPGreMCD7PSysUpTime
         TimeTicks,
      pr1645v2TTmplPGreMCD7PIfUpTime
         TimeTicks,
      pr1645v2TTmplPGreMCD7PIfStatChanges
         Counter32,
      pr1645v2TTmplPGreMCD7PIfInOctets
         Counter64,
      pr1645v2TTmplPGreMCD7PIfInUCPkts
         Counter64,
      pr1645v2TTmplPGreMCD7PIfInNUCPkts
         Counter64,
      pr1645v2TTmplPGreMCD7PIfInBCPkts
         Counter64,
      pr1645v2TTmplPGreMCD7PIfInMCPkts
         Counter64,
      pr1645v2TTmplPGreMCD7PIfInDiscards
         Counter64,
      pr1645v2TTmplPGreMCD7PIfInErrors
         Counter64,
      pr1645v2TTmplPGreMCD7PIfInUnkwn
         Counter64,
      pr1645v2TTmplPGreMCD7PInDropEx
         Counter64,
      pr1645v2TTmplPGreMCD7PInDropNoMac
         Counter64,
      pr1645v2TTmplPGreMCD7PInDropNUCast
         Counter64,
      pr1645v2TTmplPGreMCD7PInDropFilter
         Counter64,
      pr1645v2TTmplPGreMCD7PIfInBandwidth
         Integer32,
      pr1645v2TTmplPGreMCD7PIfOutOctets
         Counter64,
      pr1645v2TTmplPGreMCD7PIfOutUCPkts
         Counter64,
      pr1645v2TTmplPGreMCD7PIfOutNUCPkts
         Counter64,
      pr1645v2TTmplPGreMCD7PIfOutBCPkts
         Counter64,
      pr1645v2TTmplPGreMCD7PIfOutMCPkts
         Counter64,
      pr1645v2TTmplPGreMCD7PIfOutDiscards
         Counter64,
      pr1645v2TTmplPGreMCD7PIfOutErrors
         Counter64,
      pr1645v2TTmplPGreMCD7POutDropEx
         Counter64,
      pr1645v2TTmplPGreMCD7POutDropNoArp
         Counter64,
      pr1645v2TTmplPGreMCD7POutDropFilter
         Counter64,
      pr1645v2TTmplPGreMCD7PIfOutBandwidth
         Integer32,
      pr1645v2TTmplPGreMCD7PIfErrSec
         Counter32
      }

pr1645v2TTmplPGreMCD7PTableIx OBJECT-TYPE
   SYNTAX      TableIndex
   MAX-ACCESS  not-accessible
   STATUS      current
   DESCRIPTION
      ""
   ::= {pr1645v2TTmplPGreMCD7PEntry 11}

pr1645v2TTmplPGreMCD7PSysUpTime OBJECT-TYPE
   SYNTAX      TimeTicks
   MAX-ACCESS  read-only
   STATUS      current
   DESCRIPTION
      "Path: tunnels.performance.greTunnels.mibCounters.d7Performance.sysUpTime

       Time in centi-second."
   ::= {pr1645v2TTmplPGreMCD7PEntry 16777216}

pr1645v2TTmplPGreMCD7PIfUpTime OBJECT-TYPE
   SYNTAX      TimeTicks
   MAX-ACCESS  read-only
   STATUS      current
   DESCRIPTION
      "Path: tunnels.performance.greTunnels.mibCounters.d7Performance.ifUpTime

       Time in centi-second."
   ::= {pr1645v2TTmplPGreMCD7PEntry 33554432}

pr1645v2TTmplPGreMCD7PIfStatChanges OBJECT-TYPE
   SYNTAX      Counter32
   MAX-ACCESS  read-only
   STATUS      current
   DESCRIPTION
      "Path: tunnels.performance.greTunnels.mibCounters.d7Performance.ifStatusChanges

       32 bit unsigned wrappable counter."
   ::= {pr1645v2TTmplPGreMCD7PEntry 50331648}

pr1645v2TTmplPGreMCD7PIfInOctets OBJECT-TYPE
   SYNTAX      Counter64
   MAX-ACCESS  read-only
   STATUS      current
   DESCRIPTION
      "Path: tunnels.performance.greTunnels.mibCounters.d7Performance.ifInOctets

       64 bit unsigned wrappable counter."
   ::= {pr1645v2TTmplPGreMCD7PEntry 67108864}

pr1645v2TTmplPGreMCD7PIfInUCPkts OBJECT-TYPE
   SYNTAX      Counter64
   MAX-ACCESS  read-only
   STATUS      current
   DESCRIPTION
      "Path: tunnels.performance.greTunnels.mibCounters.d7Performance.ifInUcastPkts

       64 bit unsigned wrappable counter."
   ::= {pr1645v2TTmplPGreMCD7PEntry 83886080}

pr1645v2TTmplPGreMCD7PIfInNUCPkts OBJECT-TYPE
   SYNTAX      Counter64
   MAX-ACCESS  read-only
   STATUS      current
   DESCRIPTION
      "Path: tunnels.performance.greTunnels.mibCounters.d7Performance.ifInNUcastPkts

       64 bit unsigned wrappable counter."
   ::= {pr1645v2TTmplPGreMCD7PEntry 100663296}

pr1645v2TTmplPGreMCD7PIfInBCPkts OBJECT-TYPE
   SYNTAX      Counter64
   MAX-ACCESS  read-only
   STATUS      current
   DESCRIPTION
      "Path: tunnels.performance.greTunnels.mibCounters.d7Performance.ifInBcastPkts

       64 bit unsigned wrappable counter."
   ::= {pr1645v2TTmplPGreMCD7PEntry 419430400}

pr1645v2TTmplPGreMCD7PIfInMCPkts OBJECT-TYPE
   SYNTAX      Counter64
   MAX-ACCESS  read-only
   STATUS      current
   DESCRIPTION
      "Path: tunnels.performance.greTunnels.mibCounters.d7Performance.ifInMcastPkts

       64 bit unsigned wrappable counter."
   ::= {pr1645v2TTmplPGreMCD7PEntry 436207616}

pr1645v2TTmplPGreMCD7PIfInDiscards OBJECT-TYPE
   SYNTAX      Counter64
   MAX-ACCESS  read-only
   STATUS      current
   DESCRIPTION
      "Path: tunnels.performance.greTunnels.mibCounters.d7Performance.ifInDiscards

       64 bit unsigned wrappable counter."
   ::= {pr1645v2TTmplPGreMCD7PEntry 117440512}

pr1645v2TTmplPGreMCD7PIfInErrors OBJECT-TYPE
   SYNTAX      Counter64
   MAX-ACCESS  read-only
   STATUS      current
   DESCRIPTION
      "Path: tunnels.performance.greTunnels.mibCounters.d7Performance.ifInErrors

       64 bit unsigned wrappable counter."
   ::= {pr1645v2TTmplPGreMCD7PEntry 134217728}

pr1645v2TTmplPGreMCD7PIfInUnkwn OBJECT-TYPE
   SYNTAX      Counter64
   MAX-ACCESS  read-only
   STATUS      current
   DESCRIPTION
      "Path: tunnels.performance.greTunnels.mibCounters.d7Performance.ifInUnknownProtos

       64 bit unsigned wrappable counter."
   ::= {pr1645v2TTmplPGreMCD7PEntry 150994944}

pr1645v2TTmplPGreMCD7PInDropEx OBJECT-TYPE
   SYNTAX      Counter64
   MAX-ACCESS  read-only
   STATUS      current
   DESCRIPTION
      "Path: tunnels.performance.greTunnels.mibCounters.d7Performance.ifInDropLevelExceeded

       64 bit unsigned wrappable counter."
   ::= {pr1645v2TTmplPGreMCD7PEntry 335544320}

pr1645v2TTmplPGreMCD7PInDropNoMac OBJECT-TYPE
   SYNTAX      Counter64
   MAX-ACCESS  read-only
   STATUS      current
   DESCRIPTION
      "Path: tunnels.performance.greTunnels.mibCounters.d7Performance.fInDiscardsNoMacFit

       64 bit unsigned wrappable counter."
   ::= {pr1645v2TTmplPGreMCD7PEntry 301989888}

pr1645v2TTmplPGreMCD7PInDropNUCast OBJECT-TYPE
   SYNTAX      Counter64
   MAX-ACCESS  read-only
   STATUS      current
   DESCRIPTION
      "Path: tunnels.performance.greTunnels.mibCounters.d7Performance.fInDiscardsNUCast

       64 bit unsigned wrappable counter."
   ::= {pr1645v2TTmplPGreMCD7PEntry 318767104}

pr1645v2TTmplPGreMCD7PInDropFilter OBJECT-TYPE
   SYNTAX      Counter64
   MAX-ACCESS  read-only
   STATUS      current
   DESCRIPTION
      "Path: tunnels.performance.greTunnels.mibCounters.d7Performance.fInDiscardsFilter

       64 bit unsigned wrappable counter."
   ::= {pr1645v2TTmplPGreMCD7PEntry 385875968}

pr1645v2TTmplPGreMCD7PIfInBandwidth OBJECT-TYPE
   SYNTAX      Integer32
   MAX-ACCESS  read-only
   STATUS      current
   DESCRIPTION
      "Path: tunnels.performance.greTunnels.mibCounters.d7Performance.ifInBandwidth

       unit name = bps
       formula = 8 * ; 8 /"
   ::= {pr1645v2TTmplPGreMCD7PEntry 268435456}

pr1645v2TTmplPGreMCD7PIfOutOctets OBJECT-TYPE
   SYNTAX      Counter64
   MAX-ACCESS  read-only
   STATUS      current
   DESCRIPTION
      "Path: tunnels.performance.greTunnels.mibCounters.d7Performance.ifOutOctets

       64 bit unsigned wrappable counter."
   ::= {pr1645v2TTmplPGreMCD7PEntry 167772160}

pr1645v2TTmplPGreMCD7PIfOutUCPkts OBJECT-TYPE
   SYNTAX      Counter64
   MAX-ACCESS  read-only
   STATUS      current
   DESCRIPTION
      "Path: tunnels.performance.greTunnels.mibCounters.d7Performance.ifOutUcastPkts

       64 bit unsigned wrappable counter."
   ::= {pr1645v2TTmplPGreMCD7PEntry 184549376}

pr1645v2TTmplPGreMCD7PIfOutNUCPkts OBJECT-TYPE
   SYNTAX      Counter64
   MAX-ACCESS  read-only
   STATUS      current
   DESCRIPTION
      "Path: tunnels.performance.greTunnels.mibCounters.d7Performance.ifOutNUcastPkts

       64 bit unsigned wrappable counter."
   ::= {pr1645v2TTmplPGreMCD7PEntry 201326592}

pr1645v2TTmplPGreMCD7PIfOutBCPkts OBJECT-TYPE
   SYNTAX      Counter64
   MAX-ACCESS  read-only
   STATUS      current
   DESCRIPTION
      "Path: tunnels.performance.greTunnels.mibCounters.d7Performance.ifOutBcastPkts

       64 bit unsigned wrappable counter."
   ::= {pr1645v2TTmplPGreMCD7PEntry 452984832}

pr1645v2TTmplPGreMCD7PIfOutMCPkts OBJECT-TYPE
   SYNTAX      Counter64
   MAX-ACCESS  read-only
   STATUS      current
   DESCRIPTION
      "Path: tunnels.performance.greTunnels.mibCounters.d7Performance.ifOutMcastPkts

       64 bit unsigned wrappable counter."
   ::= {pr1645v2TTmplPGreMCD7PEntry 469762048}

pr1645v2TTmplPGreMCD7PIfOutDiscards OBJECT-TYPE
   SYNTAX      Counter64
   MAX-ACCESS  read-only
   STATUS      current
   DESCRIPTION
      "Path: tunnels.performance.greTunnels.mibCounters.d7Performance.ifOutDiscards

       64 bit unsigned wrappable counter."
   ::= {pr1645v2TTmplPGreMCD7PEntry 218103808}

pr1645v2TTmplPGreMCD7PIfOutErrors OBJECT-TYPE
   SYNTAX      Counter64
   MAX-ACCESS  read-only
   STATUS      current
   DESCRIPTION
      "Path: tunnels.performance.greTunnels.mibCounters.d7Performance.ifOutErrors

       64 bit unsigned wrappable counter."
   ::= {pr1645v2TTmplPGreMCD7PEntry 234881024}

pr1645v2TTmplPGreMCD7POutDropEx OBJECT-TYPE
   SYNTAX      Counter64
   MAX-ACCESS  read-only
   STATUS      current
   DESCRIPTION
      "Path: tunnels.performance.greTunnels.mibCounters.d7Performance.ifOutDropLevelExceeded

       64 bit unsigned wrappable counter."
   ::= {pr1645v2TTmplPGreMCD7PEntry 352321536}

pr1645v2TTmplPGreMCD7POutDropNoArp OBJECT-TYPE
   SYNTAX      Counter64
   MAX-ACCESS  read-only
   STATUS      current
   DESCRIPTION
      "Path: tunnels.performance.greTunnels.mibCounters.d7Performance.ifOutDiscardsNoArp

       64 bit unsigned wrappable counter."
   ::= {pr1645v2TTmplPGreMCD7PEntry 369098752}

pr1645v2TTmplPGreMCD7POutDropFilter OBJECT-TYPE
   SYNTAX      Counter64
   MAX-ACCESS  read-only
   STATUS      current
   DESCRIPTION
      "Path: tunnels.performance.greTunnels.mibCounters.d7Performance.ifOutDiscardsFilter

       64 bit unsigned wrappable counter."
   ::= {pr1645v2TTmplPGreMCD7PEntry 402653184}

pr1645v2TTmplPGreMCD7PIfOutBandwidth OBJECT-TYPE
   SYNTAX      Integer32
   MAX-ACCESS  read-only
   STATUS      current
   DESCRIPTION
      "Path: tunnels.performance.greTunnels.mibCounters.d7Performance.ifOutBandwidth

       unit name = bps
       formula = 8 * ; 8 /"
   ::= {pr1645v2TTmplPGreMCD7PEntry 285212672}

pr1645v2TTmplPGreMCD7PIfErrSec OBJECT-TYPE
   SYNTAX      Counter32
   MAX-ACCESS  read-only
   STATUS      current
   DESCRIPTION
      "Path: tunnels.performance.greTunnels.mibCounters.d7Performance.ifErrSec

       32 bit unsigned wrappable counter."
   ::= {pr1645v2TTmplPGreMCD7PEntry 251658240}

pr1645v2TTmplPGreInPQs OBJECT-TYPE
   SYNTAX      SEQUENCE OF Pr1645v2TTmplPGreInPQsEntry
   MAX-ACCESS  not-accessible
   STATUS      current
   DESCRIPTION
      ""
   ::= {pr1645v2TTmplPGre 100663296}

pr1645v2TTmplPGreInPQsEntry OBJECT-TYPE
   SYNTAX      Pr1645v2TTmplPGreInPQsEntry
   MAX-ACCESS  not-accessible
   STATUS      current
   DESCRIPTION
      ""
   INDEX      { pr1645v2TTmplPGreTableIx,
                pr1645v2TTmplPGreInPQsTableIx }
   ::= {pr1645v2TTmplPGreInPQs 1}

Pr1645v2TTmplPGreInPQsEntry ::=
   SEQUENCE
      {
      pr1645v2TTmplPGreInPQsTableIx
         TableIndex,
      pr1645v2TTmplPGreInPQsName
         INTEGER,
      pr1645v2TTmplPGreInPQsLength
         Integer32,
      pr1645v2TTmplPGreInPQsOctetLength
         Integer32,
      pr1645v2TTmplPGreInPQsRedLength
         Integer32,
      pr1645v2TTmplPGreInPQsPacketsTotal
         Counter64,
      pr1645v2TTmplPGreInPQsPacketsDirectTx
         Counter64,
      pr1645v2TTmplPGreInPQsPacketsQueued
         Counter64,
      pr1645v2TTmplPGreInPQsPacketsDropped
         Counter64,
      pr1645v2TTmplPGreInPQsPacketsRedDropped
         Counter64,
      pr1645v2TTmplPGreInPQsPacketsCirTx
         Counter64,
      pr1645v2TTmplPGreInPQsPacketsEirTx
         Counter64,
      pr1645v2TTmplPGreInPQsPacketsViolateTx
         Counter64,
      pr1645v2TTmplPGreInPQsOctetsTotal
         Counter64,
      pr1645v2TTmplPGreInPQsOctetsDirectTx
         Counter64,
      pr1645v2TTmplPGreInPQsOctetsQueued
         Counter64,
      pr1645v2TTmplPGreInPQsOctetsDropped
         Counter64,
      pr1645v2TTmplPGreInPQsOctetsRedDropped
         Counter64,
      pr1645v2TTmplPGreInPQsOctetsCirTx
         Counter64,
      pr1645v2TTmplPGreInPQsOctetsEirTx
         Counter64,
      pr1645v2TTmplPGreInPQsOctetsViolateTx
         Counter64,
      pr1645v2TTmplPGreInPQsOctetsBandwidth15sec
         Integer32,
      pr1645v2TTmplPGreInPQsOctetsBandwidth30sec
         Integer32,
      pr1645v2TTmplPGreInPQsOctetsBandwidth1min
         Integer32,
      pr1645v2TTmplPGreInPQsOctetsBandwidth2min
         Integer32,
      pr1645v2TTmplPGreInPQsOctetsBandwidth5min
         Integer32
      }

pr1645v2TTmplPGreInPQsTableIx OBJECT-TYPE
   SYNTAX      TableIndex
   MAX-ACCESS  not-accessible
   STATUS      current
   DESCRIPTION
      ""
   ::= {pr1645v2TTmplPGreInPQsEntry 11}

pr1645v2TTmplPGreInPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: tunnels.performance.greTunnels.inPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2TTmplPGreInPQsEntry 16777216}

pr1645v2TTmplPGreInPQsLength OBJECT-TYPE
   SYNTAX      Integer32
   MAX-ACCESS  read-only
   STATUS      current
   DESCRIPTION
      "Path: tunnels.performance.greTunnels.inPriorityQueues.length"
   ::= {pr1645v2TTmplPGreInPQsEntry 33554432}

pr1645v2TTmplPGreInPQsOctetLength OBJECT-TYPE
   SYNTAX      Integer32
   MAX-ACCESS  read-only
   STATUS      current
   DESCRIPTION
      "Path: tunnels.performance.greTunnels.inPriorityQueues.octetLength"
   ::= {pr1645v2TTmplPGreInPQsEntry 150994944}

pr1645v2TTmplPGreInPQsRedLength OBJECT-TYPE
   SYNTAX      Integer32
   MAX-ACCESS  read-only
   STATUS      current
   DESCRIPTION
      "Path: tunnels.performance.greTunnels.inPriorityQueues.redLength"
   ::= {pr1645v2TTmplPGreInPQsEntry 134217728}

pr1645v2TTmplPGreInPQsPacketsTotal OBJECT-TYPE
   SYNTAX      Counter64
   MAX-ACCESS  read-only
   STATUS      current
   DESCRIPTION
      "Path: tunnels.performance.greTunnels.inPriorityQueues.packets.total

       64 bit unsigned wrappable counter."
   ::= {pr1645v2TTmplPGreInPQsEntry 50790400}

pr1645v2TTmplPGreInPQsPacketsDirectTx OBJECT-TYPE
   SYNTAX      Counter64
   MAX-ACCESS  read-only
   STATUS      current
   DESCRIPTION
      "Path: tunnels.performance.greTunnels.inPriorityQueues.packets.directTx

       64 bit unsigned wrappable counter."
   ::= {pr1645v2TTmplPGreInPQsEntry 50397184}

pr1645v2TTmplPGreInPQsPacketsQueued OBJECT-TYPE
   SYNTAX      Counter64
   MAX-ACCESS  read-only
   STATUS      current
   DESCRIPTION
      "Path: tunnels.performance.greTunnels.inPriorityQueues.packets.queued

       64 bit unsigned wrappable counter."
   ::= {pr1645v2TTmplPGreInPQsEntry 50462720}

pr1645v2TTmplPGreInPQsPacketsDropped OBJECT-TYPE
   SYNTAX      Counter64
   MAX-ACCESS  read-only
   STATUS      current
   DESCRIPTION
      "Path: tunnels.performance.greTunnels.inPriorityQueues.packets.dropped

       64 bit unsigned wrappable counter."
   ::= {pr1645v2TTmplPGreInPQsEntry 50528256}

pr1645v2TTmplPGreInPQsPacketsRedDropped OBJECT-TYPE
   SYNTAX      Counter64
   MAX-ACCESS  read-only
   STATUS      current
   DESCRIPTION
      "Path: tunnels.performance.greTunnels.inPriorityQueues.packets.redDropped

       64 bit unsigned wrappable counter."
   ::= {pr1645v2TTmplPGreInPQsEntry 50724864}

pr1645v2TTmplPGreInPQsPacketsCirTx OBJECT-TYPE
   SYNTAX      Counter64
   MAX-ACCESS  read-only
   STATUS      current
   DESCRIPTION
      "Path: tunnels.performance.greTunnels.inPriorityQueues.packets.cirTx

       64 bit unsigned wrappable counter."
   ::= {pr1645v2TTmplPGreInPQsEntry 50593792}

pr1645v2TTmplPGreInPQsPacketsEirTx OBJECT-TYPE
   SYNTAX      Counter64
   MAX-ACCESS  read-only
   STATUS      current
   DESCRIPTION
      "Path: tunnels.performance.greTunnels.inPriorityQueues.packets.eirTx

       64 bit unsigned wrappable counter."
   ::= {pr1645v2TTmplPGreInPQsEntry 50659328}

pr1645v2TTmplPGreInPQsPacketsViolateTx OBJECT-TYPE
   SYNTAX      Counter64
   MAX-ACCESS  read-only
   STATUS      current
   DESCRIPTION
      "Path: tunnels.performance.greTunnels.inPriorityQueues.packets.violateTx

       64 bit unsigned wrappable counter."
   ::= {pr1645v2TTmplPGreInPQsEntry 50855936}

pr1645v2TTmplPGreInPQsOctetsTotal OBJECT-TYPE
   SYNTAX      Counter64
   MAX-ACCESS  read-only
   STATUS      current
   DESCRIPTION
      "Path: tunnels.performance.greTunnels.inPriorityQueues.octets.total

       64 bit unsigned wrappable counter."
   ::= {pr1645v2TTmplPGreInPQsEntry 67567616}

pr1645v2TTmplPGreInPQsOctetsDirectTx OBJECT-TYPE
   SYNTAX      Counter64
   MAX-ACCESS  read-only
   STATUS      current
   DESCRIPTION
      "Path: tunnels.performance.greTunnels.inPriorityQueues.octets.directTx

       64 bit unsigned wrappable counter."
   ::= {pr1645v2TTmplPGreInPQsEntry 67174400}

pr1645v2TTmplPGreInPQsOctetsQueued OBJECT-TYPE
   SYNTAX      Counter64
   MAX-ACCESS  read-only
   STATUS      current
   DESCRIPTION
      "Path: tunnels.performance.greTunnels.inPriorityQueues.octets.queued

       64 bit unsigned wrappable counter."
   ::= {pr1645v2TTmplPGreInPQsEntry 67239936}

pr1645v2TTmplPGreInPQsOctetsDropped OBJECT-TYPE
   SYNTAX      Counter64
   MAX-ACCESS  read-only
   STATUS      current
   DESCRIPTION
      "Path: tunnels.performance.greTunnels.inPriorityQueues.octets.dropped

       64 bit unsigned wrappable counter."
   ::= {pr1645v2TTmplPGreInPQsEntry 67305472}

pr1645v2TTmplPGreInPQsOctetsRedDropped OBJECT-TYPE
   SYNTAX      Counter64
   MAX-ACCESS  read-only
   STATUS      current
   DESCRIPTION
      "Path: tunnels.performance.greTunnels.inPriorityQueues.octets.redDropped

       64 bit unsigned wrappable counter."
   ::= {pr1645v2TTmplPGreInPQsEntry 67502080}

pr1645v2TTmplPGreInPQsOctetsCirTx OBJECT-TYPE
   SYNTAX      Counter64
   MAX-ACCESS  read-only
   STATUS      current
   DESCRIPTION
      "Path: tunnels.performance.greTunnels.inPriorityQueues.octets.cirTx

       64 bit unsigned wrappable counter."
   ::= {pr1645v2TTmplPGreInPQsEntry 67371008}

pr1645v2TTmplPGreInPQsOctetsEirTx OBJECT-TYPE
   SYNTAX      Counter64
   MAX-ACCESS  read-only
   STATUS      current
   DESCRIPTION
      "Path: tunnels.performance.greTunnels.inPriorityQueues.octets.eirTx

       64 bit unsigned wrappable counter."
   ::= {pr1645v2TTmplPGreInPQsEntry 67436544}

pr1645v2TTmplPGreInPQsOctetsViolateTx OBJECT-TYPE
   SYNTAX      Counter64
   MAX-ACCESS  read-only
   STATUS      current
   DESCRIPTION
      "Path: tunnels.performance.greTunnels.inPriorityQueues.octets.violateTx

       64 bit unsigned wrappable counter."
   ::= {pr1645v2TTmplPGreInPQsEntry 67633152}

pr1645v2TTmplPGreInPQsOctetsBandwidth15sec OBJECT-TYPE
   SYNTAX      Integer32
   MAX-ACCESS  read-only
   STATUS      current
   DESCRIPTION
      "Path: tunnels.performance.greTunnels.inPriorityQueues.octets.bandwidth.15sec

       unit name = bps
       formula = 8 * ; 8 /"
   ::= {pr1645v2TTmplPGreInPQsEntry 70386944}

pr1645v2TTmplPGreInPQsOctetsBandwidth30sec OBJECT-TYPE
   SYNTAX      Integer32
   MAX-ACCESS  read-only
   STATUS      current
   DESCRIPTION
      "Path: tunnels.performance.greTunnels.inPriorityQueues.octets.bandwidth.30sec

       unit name = bps
       formula = 8 * ; 8 /"
   ::= {pr1645v2TTmplPGreInPQsEntry 70388224}

pr1645v2TTmplPGreInPQsOctetsBandwidth1min OBJECT-TYPE
   SYNTAX      Integer32
   MAX-ACCESS  read-only
   STATUS      current
   DESCRIPTION
      "Path: tunnels.performance.greTunnels.inPriorityQueues.octets.bandwidth.1min

       unit name = bps
       formula = 8 * ; 8 /"
   ::= {pr1645v2TTmplPGreInPQsEntry 70390784}

pr1645v2TTmplPGreInPQsOctetsBandwidth2min OBJECT-TYPE
   SYNTAX      Integer32
   MAX-ACCESS  read-only
   STATUS      current
   DESCRIPTION
      "Path: tunnels.performance.greTunnels.inPriorityQueues.octets.bandwidth.2min

       unit name = bps
       formula = 8 * ; 8 /"
   ::= {pr1645v2TTmplPGreInPQsEntry 70395904}

pr1645v2TTmplPGreInPQsOctetsBandwidth5min OBJECT-TYPE
   SYNTAX      Integer32
   MAX-ACCESS  read-only
   STATUS      current
   DESCRIPTION
      "Path: tunnels.performance.greTunnels.inPriorityQueues.octets.bandwidth.5min

       unit name = bps
       formula = 8 * ; 8 /"
   ::= {pr1645v2TTmplPGreInPQsEntry 70411264}

pr1645v2TTmplPGreInPQsH2Performance OBJECT-TYPE
   SYNTAX      SEQUENCE OF Pr1645v2TTmplPGreInPQsH2PerformanceEntry
   MAX-ACCESS  not-accessible
   STATUS      current
   DESCRIPTION
      ""
   ::= {pr1645v2TTmplPGre 100990976}

pr1645v2TTmplPGreInPQsH2PerformanceEntry OBJECT-TYPE
   SYNTAX      Pr1645v2TTmplPGreInPQsH2PerformanceEntry
   MAX-ACCESS  not-accessible
   STATUS      current
   DESCRIPTION
      ""
   INDEX      { pr1645v2TTmplPGreTableIx,
                pr1645v2TTmplPGreInPQsTableIx,
                pr1645v2TTmplPGreInPQsH2PerformanceTableIx }
   ::= {pr1645v2TTmplPGreInPQsH2Performance 1}

Pr1645v2TTmplPGreInPQsH2PerformanceEntry ::=
   SEQUENCE
      {
      pr1645v2TTmplPGreInPQsH2PerformanceTableIx
         TableIndex,
      pr1645v2TTmplPGreInPQsH2PerformanceSysUpTime
         TimeTicks,
      pr1645v2TTmplPGreInPQsH2PerformanceTotPkts
         Counter64,
      pr1645v2TTmplPGreInPQsH2PerformanceDirTxPkts
         Counter64,
      pr1645v2TTmplPGreInPQsH2PerformanceQdPkts
         Counter64,
      pr1645v2TTmplPGreInPQsH2PerformanceDropPkts
         Counter64,
      pr1645v2TTmplPGreInPQsH2PerformanceRDropPkts
         Counter64,
      pr1645v2TTmplPGreInPQsH2PerformanceCirTxPkts
         Counter64,
      pr1645v2TTmplPGreInPQsH2PerformanceEirTxPkts
         Counter64,
      pr1645v2TTmplPGreInPQsH2PerformanceViolTxPkts
         Counter64,
      pr1645v2TTmplPGreInPQsH2PerformanceTotOcts
         Counter64,
      pr1645v2TTmplPGreInPQsH2PerformanceDirTxOcts
         Counter64,
      pr1645v2TTmplPGreInPQsH2PerformanceQdOcts
         Counter64,
      pr1645v2TTmplPGreInPQsH2PerformanceDropOcts
         Counter64,
      pr1645v2TTmplPGreInPQsH2PerformanceRDropOcts
         Counter64,
      pr1645v2TTmplPGreInPQsH2PerformanceCirTxOcts
         Counter64,
      pr1645v2TTmplPGreInPQsH2PerformanceEirTxOcts
         Counter64,
      pr1645v2TTmplPGreInPQsH2PerformanceViolTxOcts
         Counter64,
      pr1645v2TTmplPGreInPQsH2PerformanceBandwidth
         Integer32
      }

pr1645v2TTmplPGreInPQsH2PerformanceTableIx OBJECT-TYPE
   SYNTAX      TableIndex
   MAX-ACCESS  not-accessible
   STATUS      current
   DESCRIPTION
      ""
   ::= {pr1645v2TTmplPGreInPQsH2PerformanceEntry 11}

pr1645v2TTmplPGreInPQsH2PerformanceSysUpTime OBJECT-TYPE
   SYNTAX      TimeTicks
   MAX-ACCESS  read-only
   STATUS      current
   DESCRIPTION
      "Path: tunnels.performance.greTunnels.inPriorityQueues.h2Performance.sysUpTime

       Time in centi-second."
   ::= {pr1645v2TTmplPGreInPQsH2PerformanceEntry 16777216}

pr1645v2TTmplPGreInPQsH2PerformanceTotPkts OBJECT-TYPE
   SYNTAX      Counter64
   MAX-ACCESS  read-only
   STATUS      current
   DESCRIPTION
      "Path: tunnels.performance.greTunnels.inPriorityQueues.h2Performance.totalPkts

       64 bit unsigned wrappable counter."
   ::= {pr1645v2TTmplPGreInPQsH2PerformanceEntry 234881024}

pr1645v2TTmplPGreInPQsH2PerformanceDirTxPkts OBJECT-TYPE
   SYNTAX      Counter64
   MAX-ACCESS  read-only
   STATUS      current
   DESCRIPTION
      "Path: tunnels.performance.greTunnels.inPriorityQueues.h2Performance.directTxPkts

       64 bit unsigned wrappable counter."
   ::= {pr1645v2TTmplPGreInPQsH2PerformanceEntry 33554432}

pr1645v2TTmplPGreInPQsH2PerformanceQdPkts OBJECT-TYPE
   SYNTAX      Counter64
   MAX-ACCESS  read-only
   STATUS      current
   DESCRIPTION
      "Path: tunnels.performance.greTunnels.inPriorityQueues.h2Performance.queuedPkts

       64 bit unsigned wrappable counter."
   ::= {pr1645v2TTmplPGreInPQsH2PerformanceEntry 50331648}

pr1645v2TTmplPGreInPQsH2PerformanceDropPkts OBJECT-TYPE
   SYNTAX      Counter64
   MAX-ACCESS  read-only
   STATUS      current
   DESCRIPTION
      "Path: tunnels.performance.greTunnels.inPriorityQueues.h2Performance.droppedPkts

       64 bit unsigned wrappable counter."
   ::= {pr1645v2TTmplPGreInPQsH2PerformanceEntry 67108864}

pr1645v2TTmplPGreInPQsH2PerformanceRDropPkts OBJECT-TYPE
   SYNTAX      Counter64
   MAX-ACCESS  read-only
   STATUS      current
   DESCRIPTION
      "Path: tunnels.performance.greTunnels.inPriorityQueues.h2Performance.redDroppedPkts

       64 bit unsigned wrappable counter."
   ::= {pr1645v2TTmplPGreInPQsH2PerformanceEntry 201326592}

pr1645v2TTmplPGreInPQsH2PerformanceCirTxPkts OBJECT-TYPE
   SYNTAX      Counter64
   MAX-ACCESS  read-only
   STATUS      current
   DESCRIPTION
      "Path: tunnels.performance.greTunnels.inPriorityQueues.h2Performance.cirTxPkts

       64 bit unsigned wrappable counter."
   ::= {pr1645v2TTmplPGreInPQsH2PerformanceEntry 83886080}

pr1645v2TTmplPGreInPQsH2PerformanceEirTxPkts OBJECT-TYPE
   SYNTAX      Counter64
   MAX-ACCESS  read-only
   STATUS      current
   DESCRIPTION
      "Path: tunnels.performance.greTunnels.inPriorityQueues.h2Performance.eirTxPkts

       64 bit unsigned wrappable counter."
   ::= {pr1645v2TTmplPGreInPQsH2PerformanceEntry 100663296}

pr1645v2TTmplPGreInPQsH2PerformanceViolTxPkts OBJECT-TYPE
   SYNTAX      Counter64
   MAX-ACCESS  read-only
   STATUS      current
   DESCRIPTION
      "Path: tunnels.performance.greTunnels.inPriorityQueues.h2Performance.violateTxPkts

       64 bit unsigned wrappable counter."
   ::= {pr1645v2TTmplPGreInPQsH2PerformanceEntry 301989888}

pr1645v2TTmplPGreInPQsH2PerformanceTotOcts OBJECT-TYPE
   SYNTAX      Counter64
   MAX-ACCESS  read-only
   STATUS      current
   DESCRIPTION
      "Path: tunnels.performance.greTunnels.inPriorityQueues.h2Performance.totalOctets

       64 bit unsigned wrappable counter."
   ::= {pr1645v2TTmplPGreInPQsH2PerformanceEntry 251658240}

pr1645v2TTmplPGreInPQsH2PerformanceDirTxOcts OBJECT-TYPE
   SYNTAX      Counter64
   MAX-ACCESS  read-only
   STATUS      current
   DESCRIPTION
      "Path: tunnels.performance.greTunnels.inPriorityQueues.h2Performance.directTxOctets

       64 bit unsigned wrappable counter."
   ::= {pr1645v2TTmplPGreInPQsH2PerformanceEntry 117440512}

pr1645v2TTmplPGreInPQsH2PerformanceQdOcts OBJECT-TYPE
   SYNTAX      Counter64
   MAX-ACCESS  read-only
   STATUS      current
   DESCRIPTION
      "Path: tunnels.performance.greTunnels.inPriorityQueues.h2Performance.queuedOctets

       64 bit unsigned wrappable counter."
   ::= {pr1645v2TTmplPGreInPQsH2PerformanceEntry 134217728}

pr1645v2TTmplPGreInPQsH2PerformanceDropOcts OBJECT-TYPE
   SYNTAX      Counter64
   MAX-ACCESS  read-only
   STATUS      current
   DESCRIPTION
      "Path: tunnels.performance.greTunnels.inPriorityQueues.h2Performance.droppedOctets

       64 bit unsigned wrappable counter."
   ::= {pr1645v2TTmplPGreInPQsH2PerformanceEntry 150994944}

pr1645v2TTmplPGreInPQsH2PerformanceRDropOcts OBJECT-TYPE
   SYNTAX      Counter64
   MAX-ACCESS  read-only
   STATUS      current
   DESCRIPTION
      "Path: tunnels.performance.greTunnels.inPriorityQueues.h2Performance.redDroppedOctets

       64 bit unsigned wrappable counter."
   ::= {pr1645v2TTmplPGreInPQsH2PerformanceEntry 218103808}

pr1645v2TTmplPGreInPQsH2PerformanceCirTxOcts OBJECT-TYPE
   SYNTAX      Counter64
   MAX-ACCESS  read-only
   STATUS      current
   DESCRIPTION
      "Path: tunnels.performance.greTunnels.inPriorityQueues.h2Performance.cirTxOctets

       64 bit unsigned wrappable counter."
   ::= {pr1645v2TTmplPGreInPQsH2PerformanceEntry 167772160}

pr1645v2TTmplPGreInPQsH2PerformanceEirTxOcts OBJECT-TYPE
   SYNTAX      Counter64
   MAX-ACCESS  read-only
   STATUS      current
   DESCRIPTION
      "Path: tunnels.performance.greTunnels.inPriorityQueues.h2Performance.eirTxOctets

       64 bit unsigned wrappable counter."
   ::= {pr1645v2TTmplPGreInPQsH2PerformanceEntry 184549376}

pr1645v2TTmplPGreInPQsH2PerformanceViolTxOcts OBJECT-TYPE
   SYNTAX      Counter64
   MAX-ACCESS  read-only
   STATUS      current
   DESCRIPTION
      "Path: tunnels.performance.greTunnels.inPriorityQueues.h2Performance.violateTxOctets

       64 bit unsigned wrappable counter."
   ::= {pr1645v2TTmplPGreInPQsH2PerformanceEntry 318767104}

pr1645v2TTmplPGreInPQsH2PerformanceBandwidth OBJECT-TYPE
   SYNTAX      Integer32
   MAX-ACCESS  read-only
   STATUS      current
   DESCRIPTION
      "Path: tunnels.performance.greTunnels.inPriorityQueues.h2Performance.bandwidth

       unit name = bps
       formula = 8 * ; 8 /"
   ::= {pr1645v2TTmplPGreInPQsH2PerformanceEntry 268435456}

pr1645v2TTmplPGreInPQsH24Performance OBJECT-TYPE
   SYNTAX      SEQUENCE OF Pr1645v2TTmplPGreInPQsH24PerformanceEntry
   MAX-ACCESS  not-accessible
   STATUS      current
   DESCRIPTION
      ""
   ::= {pr1645v2TTmplPGre 101056512}

pr1645v2TTmplPGreInPQsH24PerformanceEntry OBJECT-TYPE
   SYNTAX      Pr1645v2TTmplPGreInPQsH24PerformanceEntry
   MAX-ACCESS  not-accessible
   STATUS      current
   DESCRIPTION
      ""
   INDEX      { pr1645v2TTmplPGreTableIx,
                pr1645v2TTmplPGreInPQsTableIx,
                pr1645v2TTmplPGreInPQsH24PerformanceTableIx }
   ::= {pr1645v2TTmplPGreInPQsH24Performance 1}

Pr1645v2TTmplPGreInPQsH24PerformanceEntry ::=
   SEQUENCE
      {
      pr1645v2TTmplPGreInPQsH24PerformanceTableIx
         TableIndex,
      pr1645v2TTmplPGreInPQsH24PerformanceSysUpTime
         TimeTicks,
      pr1645v2TTmplPGreInPQsH24PerformanceTotPkts
         Counter64,
      pr1645v2TTmplPGreInPQsH24PerformanceDirTxPkts
         Counter64,
      pr1645v2TTmplPGreInPQsH24PerformanceQdPkts
         Counter64,
      pr1645v2TTmplPGreInPQsH24PerformanceDropPkts
         Counter64,
      pr1645v2TTmplPGreInPQsH24PerformanceRDropPkts
         Counter64,
      pr1645v2TTmplPGreInPQsH24PerformanceCirTxPkts
         Counter64,
      pr1645v2TTmplPGreInPQsH24PerformanceEirTxPkts
         Counter64,
      pr1645v2TTmplPGreInPQsH24PerformanceViolTxPkts
         Counter64,
      pr1645v2TTmplPGreInPQsH24PerformanceTotOcts
         Counter64,
      pr1645v2TTmplPGreInPQsH24PerformanceDirTxOcts
         Counter64,
      pr1645v2TTmplPGreInPQsH24PerformanceQdOcts
         Counter64,
      pr1645v2TTmplPGreInPQsH24PerformanceDropOcts
         Counter64,
      pr1645v2TTmplPGreInPQsH24PerformanceRDropOcts
         Counter64,
      pr1645v2TTmplPGreInPQsH24PerformanceCirTxOcts
         Counter64,
      pr1645v2TTmplPGreInPQsH24PerformanceEirTxOcts
         Counter64,
      pr1645v2TTmplPGreInPQsH24PerformanceViolTxOcts
         Counter64,
      pr1645v2TTmplPGreInPQsH24PerformanceBandwidth
         Integer32
      }

pr1645v2TTmplPGreInPQsH24PerformanceTableIx OBJECT-TYPE
   SYNTAX      TableIndex
   MAX-ACCESS  not-accessible
   STATUS      current
   DESCRIPTION
      ""
   ::= {pr1645v2TTmplPGreInPQsH24PerformanceEntry 11}

pr1645v2TTmplPGreInPQsH24PerformanceSysUpTime OBJECT-TYPE
   SYNTAX      TimeTicks
   MAX-ACCESS  read-only
   STATUS      current
   DESCRIPTION
      "Path: tunnels.performance.greTunnels.inPriorityQueues.h24Performance.sysUpTime

       Time in centi-second."
   ::= {pr1645v2TTmplPGreInPQsH24PerformanceEntry 16777216}

pr1645v2TTmplPGreInPQsH24PerformanceTotPkts OBJECT-TYPE
   SYNTAX      Counter64
   MAX-ACCESS  read-only
   STATUS      current
   DESCRIPTION
      "Path: tunnels.performance.greTunnels.inPriorityQueues.h24Performance.totalPkts

       64 bit unsigned wrappable counter."
   ::= {pr1645v2TTmplPGreInPQsH24PerformanceEntry 234881024}

pr1645v2TTmplPGreInPQsH24PerformanceDirTxPkts OBJECT-TYPE
   SYNTAX      Counter64
   MAX-ACCESS  read-only
   STATUS      current
   DESCRIPTION
      "Path: tunnels.performance.greTunnels.inPriorityQueues.h24Performance.directTxPkts

       64 bit unsigned wrappable counter."
   ::= {pr1645v2TTmplPGreInPQsH24PerformanceEntry 33554432}

pr1645v2TTmplPGreInPQsH24PerformanceQdPkts OBJECT-TYPE
   SYNTAX      Counter64
   MAX-ACCESS  read-only
   STATUS      current
   DESCRIPTION
      "Path: tunnels.performance.greTunnels.inPriorityQueues.h24Performance.queuedPkts

       64 bit unsigned wrappable counter."
   ::= {pr1645v2TTmplPGreInPQsH24PerformanceEntry 50331648}

pr1645v2TTmplPGreInPQsH24PerformanceDropPkts OBJECT-TYPE
   SYNTAX      Counter64
   MAX-ACCESS  read-only
   STATUS      current
   DESCRIPTION
      "Path: tunnels.performance.greTunnels.inPriorityQueues.h24Performance.droppedPkts

       64 bit unsigned wrappable counter."
   ::= {pr1645v2TTmplPGreInPQsH24PerformanceEntry 67108864}

pr1645v2TTmplPGreInPQsH24PerformanceRDropPkts OBJECT-TYPE
   SYNTAX      Counter64
   MAX-ACCESS  read-only
   STATUS      current
   DESCRIPTION
      "Path: tunnels.performance.greTunnels.inPriorityQueues.h24Performance.redDroppedPkts

       64 bit unsigned wrappable counter."
   ::= {pr1645v2TTmplPGreInPQsH24PerformanceEntry 201326592}

pr1645v2TTmplPGreInPQsH24PerformanceCirTxPkts OBJECT-TYPE
   SYNTAX      Counter64
   MAX-ACCESS  read-only
   STATUS      current
   DESCRIPTION
      "Path: tunnels.performance.greTunnels.inPriorityQueues.h24Performance.cirTxPkts

       64 bit unsigned wrappable counter."
   ::= {pr1645v2TTmplPGreInPQsH24PerformanceEntry 83886080}

pr1645v2TTmplPGreInPQsH24PerformanceEirTxPkts OBJECT-TYPE
   SYNTAX      Counter64
   MAX-ACCESS  read-only
   STATUS      current
   DESCRIPTION
      "Path: tunnels.performance.greTunnels.inPriorityQueues.h24Performance.eirTxPkts

       64 bit unsigned wrappable counter."
   ::= {pr1645v2TTmplPGreInPQsH24PerformanceEntry 100663296}

pr1645v2TTmplPGreInPQsH24PerformanceViolTxPkts OBJECT-TYPE
   SYNTAX      Counter64
   MAX-ACCESS  read-only
   STATUS      current
   DESCRIPTION
      "Path: tunnels.performance.greTunnels.inPriorityQueues.h24Performance.violateTxPkts

       64 bit unsigned wrappable counter."
   ::= {pr1645v2TTmplPGreInPQsH24PerformanceEntry 301989888}

pr1645v2TTmplPGreInPQsH24PerformanceTotOcts OBJECT-TYPE
   SYNTAX      Counter64
   MAX-ACCESS  read-only
   STATUS      current
   DESCRIPTION
      "Path: tunnels.performance.greTunnels.inPriorityQueues.h24Performance.totalOctets

       64 bit unsigned wrappable counter."
   ::= {pr1645v2TTmplPGreInPQsH24PerformanceEntry 251658240}

pr1645v2TTmplPGreInPQsH24PerformanceDirTxOcts OBJECT-TYPE
   SYNTAX      Counter64
   MAX-ACCESS  read-only
   STATUS      current
   DESCRIPTION
      "Path: tunnels.performance.greTunnels.inPriorityQueues.h24Performance.directTxOctets

       64 bit unsigned wrappable counter."
   ::= {pr1645v2TTmplPGreInPQsH24PerformanceEntry 117440512}

pr1645v2TTmplPGreInPQsH24PerformanceQdOcts OBJECT-TYPE
   SYNTAX      Counter64
   MAX-ACCESS  read-only
   STATUS      current
   DESCRIPTION
      "Path: tunnels.performance.greTunnels.inPriorityQueues.h24Performance.queuedOctets

       64 bit unsigned wrappable counter."
   ::= {pr1645v2TTmplPGreInPQsH24PerformanceEntry 134217728}

pr1645v2TTmplPGreInPQsH24PerformanceDropOcts OBJECT-TYPE
   SYNTAX      Counter64
   MAX-ACCESS  read-only
   STATUS      current
   DESCRIPTION
      "Path: tunnels.performance.greTunnels.inPriorityQueues.h24Performance.droppedOctets

       64 bit unsigned wrappable counter."
   ::= {pr1645v2TTmplPGreInPQsH24PerformanceEntry 150994944}

pr1645v2TTmplPGreInPQsH24PerformanceRDropOcts OBJECT-TYPE
   SYNTAX      Counter64
   MAX-ACCESS  read-only
   STATUS      current
   DESCRIPTION
      "Path: tunnels.performance.greTunnels.inPriorityQueues.h24Performance.redDroppedOctets

       64 bit unsigned wrappable counter."
   ::= {pr1645v2TTmplPGreInPQsH24PerformanceEntry 218103808}

pr1645v2TTmplPGreInPQsH24PerformanceCirTxOcts OBJECT-TYPE
   SYNTAX      Counter64
   MAX-ACCESS  read-only
   STATUS      current
   DESCRIPTION
      "Path: tunnels.performance.greTunnels.inPriorityQueues.h24Performance.cirTxOctets

       64 bit unsigned wrappable counter."
   ::= {pr1645v2TTmplPGreInPQsH24PerformanceEntry 167772160}

pr1645v2TTmplPGreInPQsH24PerformanceEirTxOcts OBJECT-TYPE
   SYNTAX      Counter64
   MAX-ACCESS  read-only
   STATUS      current
   DESCRIPTION
      "Path: tunnels.performance.greTunnels.inPriorityQueues.h24Performance.eirTxOctets

       64 bit unsigned wrappable counter."
   ::= {pr1645v2TTmplPGreInPQsH24PerformanceEntry 184549376}

pr1645v2TTmplPGreInPQsH24PerformanceViolTxOcts OBJECT-TYPE
   SYNTAX      Counter64
   MAX-ACCESS  read-only
   STATUS      current
   DESCRIPTION
      "Path: tunnels.performance.greTunnels.inPriorityQueues.h24Performance.violateTxOctets

       64 bit unsigned wrappable counter."
   ::= {pr1645v2TTmplPGreInPQsH24PerformanceEntry 318767104}

pr1645v2TTmplPGreInPQsH24PerformanceBandwidth OBJECT-TYPE
   SYNTAX      Integer32
   MAX-ACCESS  read-only
   STATUS      current
   DESCRIPTION
      "Path: tunnels.performance.greTunnels.inPriorityQueues.h24Performance.bandwidth

       unit name = bps
       formula = 8 * ; 8 /"
   ::= {pr1645v2TTmplPGreInPQsH24PerformanceEntry 268435456}

pr1645v2TTmplPGreInPQsD7Performance OBJECT-TYPE
   SYNTAX      SEQUENCE OF Pr1645v2TTmplPGreInPQsD7PerformanceEntry
   MAX-ACCESS  not-accessible
   STATUS      current
   DESCRIPTION
      ""
   ::= {pr1645v2TTmplPGre 101122048}

pr1645v2TTmplPGreInPQsD7PerformanceEntry OBJECT-TYPE
   SYNTAX      Pr1645v2TTmplPGreInPQsD7PerformanceEntry
   MAX-ACCESS  not-accessible
   STATUS      current
   DESCRIPTION
      ""
   INDEX      { pr1645v2TTmplPGreTableIx,
                pr1645v2TTmplPGreInPQsTableIx,
                pr1645v2TTmplPGreInPQsD7PerformanceTableIx }
   ::= {pr1645v2TTmplPGreInPQsD7Performance 1}

Pr1645v2TTmplPGreInPQsD7PerformanceEntry ::=
   SEQUENCE
      {
      pr1645v2TTmplPGreInPQsD7PerformanceTableIx
         TableIndex,
      pr1645v2TTmplPGreInPQsD7PerformanceSysUpTime
         TimeTicks,
      pr1645v2TTmplPGreInPQsD7PerformanceTotPkts
         Counter64,
      pr1645v2TTmplPGreInPQsD7PerformanceDirTxPkts
         Counter64,
      pr1645v2TTmplPGreInPQsD7PerformanceQdPkts
         Counter64,
      pr1645v2TTmplPGreInPQsD7PerformanceDropPkts
         Counter64,
      pr1645v2TTmplPGreInPQsD7PerformanceRDropPkts
         Counter64,
      pr1645v2TTmplPGreInPQsD7PerformanceCirTxPkts
         Counter64,
      pr1645v2TTmplPGreInPQsD7PerformanceEirTxPkts
         Counter64,
      pr1645v2TTmplPGreInPQsD7PerformanceViolTxPkts
         Counter64,
      pr1645v2TTmplPGreInPQsD7PerformanceTotOcts
         Counter64,
      pr1645v2TTmplPGreInPQsD7PerformanceDirTxOcts
         Counter64,
      pr1645v2TTmplPGreInPQsD7PerformanceQdOcts
         Counter64,
      pr1645v2TTmplPGreInPQsD7PerformanceDropOcts
         Counter64,
      pr1645v2TTmplPGreInPQsD7PerformanceRDropOcts
         Counter64,
      pr1645v2TTmplPGreInPQsD7PerformanceCirTxOcts
         Counter64,
      pr1645v2TTmplPGreInPQsD7PerformanceEirTxOcts
         Counter64,
      pr1645v2TTmplPGreInPQsD7PerformanceViolTxOcts
         Counter64,
      pr1645v2TTmplPGreInPQsD7PerformanceBandwidth
         Integer32
      }

pr1645v2TTmplPGreInPQsD7PerformanceTableIx OBJECT-TYPE
   SYNTAX      TableIndex
   MAX-ACCESS  not-accessible
   STATUS      current
   DESCRIPTION
      ""
   ::= {pr1645v2TTmplPGreInPQsD7PerformanceEntry 11}

pr1645v2TTmplPGreInPQsD7PerformanceSysUpTime OBJECT-TYPE
   SYNTAX      TimeTicks
   MAX-ACCESS  read-only
   STATUS      current
   DESCRIPTION
      "Path: tunnels.performance.greTunnels.inPriorityQueues.d7Performance.sysUpTime

       Time in centi-second."
   ::= {pr1645v2TTmplPGreInPQsD7PerformanceEntry 16777216}

pr1645v2TTmplPGreInPQsD7PerformanceTotPkts OBJECT-TYPE
   SYNTAX      Counter64
   MAX-ACCESS  read-only
   STATUS      current
   DESCRIPTION
      "Path: tunnels.performance.greTunnels.inPriorityQueues.d7Performance.totalPkts

       64 bit unsigned wrappable counter."
   ::= {pr1645v2TTmplPGreInPQsD7PerformanceEntry 234881024}

pr1645v2TTmplPGreInPQsD7PerformanceDirTxPkts OBJECT-TYPE
   SYNTAX      Counter64
   MAX-ACCESS  read-only
   STATUS      current
   DESCRIPTION
      "Path: tunnels.performance.greTunnels.inPriorityQueues.d7Performance.directTxPkts

       64 bit unsigned wrappable counter."
   ::= {pr1645v2TTmplPGreInPQsD7PerformanceEntry 33554432}

pr1645v2TTmplPGreInPQsD7PerformanceQdPkts OBJECT-TYPE
   SYNTAX      Counter64
   MAX-ACCESS  read-only
   STATUS      current
   DESCRIPTION
      "Path: tunnels.performance.greTunnels.inPriorityQueues.d7Performance.queuedPkts

       64 bit unsigned wrappable counter."
   ::= {pr1645v2TTmplPGreInPQsD7PerformanceEntry 50331648}

pr1645v2TTmplPGreInPQsD7PerformanceDropPkts OBJECT-TYPE
   SYNTAX      Counter64
   MAX-ACCESS  read-only
   STATUS      current
   DESCRIPTION
      "Path: tunnels.performance.greTunnels.inPriorityQueues.d7Performance.droppedPkts

       64 bit unsigned wrappable counter."
   ::= {pr1645v2TTmplPGreInPQsD7PerformanceEntry 67108864}

pr1645v2TTmplPGreInPQsD7PerformanceRDropPkts OBJECT-TYPE
   SYNTAX      Counter64
   MAX-ACCESS  read-only
   STATUS      current
   DESCRIPTION
      "Path: tunnels.performance.greTunnels.inPriorityQueues.d7Performance.redDroppedPkts

       64 bit unsigned wrappable counter."
   ::= {pr1645v2TTmplPGreInPQsD7PerformanceEntry 201326592}

pr1645v2TTmplPGreInPQsD7PerformanceCirTxPkts OBJECT-TYPE
   SYNTAX      Counter64
   MAX-ACCESS  read-only
   STATUS      current
   DESCRIPTION
      "Path: tunnels.performance.greTunnels.inPriorityQueues.d7Performance.cirTxPkts

       64 bit unsigned wrappable counter."
   ::= {pr1645v2TTmplPGreInPQsD7PerformanceEntry 83886080}

pr1645v2TTmplPGreInPQsD7PerformanceEirTxPkts OBJECT-TYPE
   SYNTAX      Counter64
   MAX-ACCESS  read-only
   STATUS      current
   DESCRIPTION
      "Path: tunnels.performance.greTunnels.inPriorityQueues.d7Performance.eirTxPkts

       64 bit unsigned wrappable counter."
   ::= {pr1645v2TTmplPGreInPQsD7PerformanceEntry 100663296}

pr1645v2TTmplPGreInPQsD7PerformanceViolTxPkts OBJECT-TYPE
   SYNTAX      Counter64
   MAX-ACCESS  read-only
   STATUS      current
   DESCRIPTION
      "Path: tunnels.performance.greTunnels.inPriorityQueues.d7Performance.violateTxPkts

       64 bit unsigned wrappable counter."
   ::= {pr1645v2TTmplPGreInPQsD7PerformanceEntry 301989888}

pr1645v2TTmplPGreInPQsD7PerformanceTotOcts OBJECT-TYPE
   SYNTAX      Counter64
   MAX-ACCESS  read-only
   STATUS      current
   DESCRIPTION
      "Path: tunnels.performance.greTunnels.inPriorityQueues.d7Performance.totalOctets

       64 bit unsigned wrappable counter."
   ::= {pr1645v2TTmplPGreInPQsD7PerformanceEntry 251658240}

pr1645v2TTmplPGreInPQsD7PerformanceDirTxOcts OBJECT-TYPE
   SYNTAX      Counter64
   MAX-ACCESS  read-only
   STATUS      current
   DESCRIPTION
      "Path: tunnels.performance.greTunnels.inPriorityQueues.d7Performance.directTxOctets

       64 bit unsigned wrappable counter."
   ::= {pr1645v2TTmplPGreInPQsD7PerformanceEntry 117440512}

pr1645v2TTmplPGreInPQsD7PerformanceQdOcts OBJECT-TYPE
   SYNTAX      Counter64
   MAX-ACCESS  read-only
   STATUS      current
   DESCRIPTION
      "Path: tunnels.performance.greTunnels.inPriorityQueues.d7Performance.queuedOctets

       64 bit unsigned wrappable counter."
   ::= {pr1645v2TTmplPGreInPQsD7PerformanceEntry 134217728}

pr1645v2TTmplPGreInPQsD7PerformanceDropOcts OBJECT-TYPE
   SYNTAX      Counter64
   MAX-ACCESS  read-only
   STATUS      current
   DESCRIPTION
      "Path: tunnels.performance.greTunnels.inPriorityQueues.d7Performance.droppedOctets

       64 bit unsigned wrappable counter."
   ::= {pr1645v2TTmplPGreInPQsD7PerformanceEntry 150994944}

pr1645v2TTmplPGreInPQsD7PerformanceRDropOcts OBJECT-TYPE
   SYNTAX      Counter64
   MAX-ACCESS  read-only
   STATUS      current
   DESCRIPTION
      "Path: tunnels.performance.greTunnels.inPriorityQueues.d7Performance.redDroppedOctets

       64 bit unsigned wrappable counter."
   ::= {pr1645v2TTmplPGreInPQsD7PerformanceEntry 218103808}

pr1645v2TTmplPGreInPQsD7PerformanceCirTxOcts OBJECT-TYPE
   SYNTAX      Counter64
   MAX-ACCESS  read-only
   STATUS      current
   DESCRIPTION
      "Path: tunnels.performance.greTunnels.inPriorityQueues.d7Performance.cirTxOctets

       64 bit unsigned wrappable counter."
   ::= {pr1645v2TTmplPGreInPQsD7PerformanceEntry 167772160}

pr1645v2TTmplPGreInPQsD7PerformanceEirTxOcts OBJECT-TYPE
   SYNTAX      Counter64
   MAX-ACCESS  read-only
   STATUS      current
   DESCRIPTION
      "Path: tunnels.performance.greTunnels.inPriorityQueues.d7Performance.eirTxOctets

       64 bit unsigned wrappable counter."
   ::= {pr1645v2TTmplPGreInPQsD7PerformanceEntry 184549376}

pr1645v2TTmplPGreInPQsD7PerformanceViolTxOcts OBJECT-TYPE
   SYNTAX      Counter64
   MAX-ACCESS  read-only
   STATUS      current
   DESCRIPTION
      "Path: tunnels.performance.greTunnels.inPriorityQueues.d7Performance.violateTxOctets

       64 bit unsigned wrappable counter."
   ::= {pr1645v2TTmplPGreInPQsD7PerformanceEntry 318767104}

pr1645v2TTmplPGreInPQsD7PerformanceBandwidth OBJECT-TYPE
   SYNTAX      Integer32
   MAX-ACCESS  read-only
   STATUS      current
   DESCRIPTION
      "Path: tunnels.performance.greTunnels.inPriorityQueues.d7Performance.bandwidth

       unit name = bps
       formula = 8 * ; 8 /"
   ::= {pr1645v2TTmplPGreInPQsD7PerformanceEntry 268435456}

pr1645v2TTmplPGreOutPQs OBJECT-TYPE
   SYNTAX      SEQUENCE OF Pr1645v2TTmplPGreOutPQsEntry
   MAX-ACCESS  not-accessible
   STATUS      current
   DESCRIPTION
      ""
   ::= {pr1645v2TTmplPGre 83886080}

pr1645v2TTmplPGreOutPQsEntry OBJECT-TYPE
   SYNTAX      Pr1645v2TTmplPGreOutPQsEntry
   MAX-ACCESS  not-accessible
   STATUS      current
   DESCRIPTION
      ""
   INDEX      { pr1645v2TTmplPGreTableIx,
                pr1645v2TTmplPGreOutPQsTableIx }
   ::= {pr1645v2TTmplPGreOutPQs 1}

Pr1645v2TTmplPGreOutPQsEntry ::=
   SEQUENCE
      {
      pr1645v2TTmplPGreOutPQsTableIx
         TableIndex,
      pr1645v2TTmplPGreOutPQsName
         INTEGER,
      pr1645v2TTmplPGreOutPQsLength
         Integer32,
      pr1645v2TTmplPGreOutPQsOctetLength
         Integer32,
      pr1645v2TTmplPGreOutPQsRedLength
         Integer32,
      pr1645v2TTmplPGreOutPQsPacketsTotal
         Counter64,
      pr1645v2TTmplPGreOutPQsPacketsDirectTx
         Counter64,
      pr1645v2TTmplPGreOutPQsPacketsQueued
         Counter64,
      pr1645v2TTmplPGreOutPQsPacketsDropped
         Counter64,
      pr1645v2TTmplPGreOutPQsPacketsRedDropped
         Counter64,
      pr1645v2TTmplPGreOutPQsPacketsCirTx
         Counter64,
      pr1645v2TTmplPGreOutPQsPacketsEirTx
         Counter64,
      pr1645v2TTmplPGreOutPQsPacketsViolateTx
         Counter64,
      pr1645v2TTmplPGreOutPQsOctetsTotal
         Counter64,
      pr1645v2TTmplPGreOutPQsOctetsDirectTx
         Counter64,
      pr1645v2TTmplPGreOutPQsOctetsQueued
         Counter64,
      pr1645v2TTmplPGreOutPQsOctetsDropped
         Counter64,
      pr1645v2TTmplPGreOutPQsOctetsRedDropped
         Counter64,
      pr1645v2TTmplPGreOutPQsOctetsCirTx
         Counter64,
      pr1645v2TTmplPGreOutPQsOctetsEirTx
         Counter64,
      pr1645v2TTmplPGreOutPQsOctetsViolateTx
         Counter64,
      pr1645v2TTmplPGreOutPQsOctetsBandwidth15sec
         Integer32,
      pr1645v2TTmplPGreOutPQsOctetsBandwidth30sec
         Integer32,
      pr1645v2TTmplPGreOutPQsOctetsBandwidth1min
         Integer32,
      pr1645v2TTmplPGreOutPQsOctetsBandwidth2min
         Integer32,
      pr1645v2TTmplPGreOutPQsOctetsBandwidth5min
         Integer32
      }

pr1645v2TTmplPGreOutPQsTableIx OBJECT-TYPE
   SYNTAX      TableIndex
   MAX-ACCESS  not-accessible
   STATUS      current
   DESCRIPTION
      ""
   ::= {pr1645v2TTmplPGreOutPQsEntry 11}

pr1645v2TTmplPGreOutPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: tunnels.performance.greTunnels.outPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2TTmplPGreOutPQsEntry 16777216}

pr1645v2TTmplPGreOutPQsLength OBJECT-TYPE
   SYNTAX      Integer32
   MAX-ACCESS  read-only
   STATUS      current
   DESCRIPTION
      "Path: tunnels.performance.greTunnels.outPriorityQueues.length"
   ::= {pr1645v2TTmplPGreOutPQsEntry 33554432}

pr1645v2TTmplPGreOutPQsOctetLength OBJECT-TYPE
   SYNTAX      Integer32
   MAX-ACCESS  read-only
   STATUS      current
   DESCRIPTION
      "Path: tunnels.performance.greTunnels.outPriorityQueues.octetLength"
   ::= {pr1645v2TTmplPGreOutPQsEntry 150994944}

pr1645v2TTmplPGreOutPQsRedLength OBJECT-TYPE
   SYNTAX      Integer32
   MAX-ACCESS  read-only
   STATUS      current
   DESCRIPTION
      "Path: tunnels.performance.greTunnels.outPriorityQueues.redLength"
   ::= {pr1645v2TTmplPGreOutPQsEntry 134217728}

pr1645v2TTmplPGreOutPQsPacketsTotal OBJECT-TYPE
   SYNTAX      Counter64
   MAX-ACCESS  read-only
   STATUS      current
   DESCRIPTION
      "Path: tunnels.performance.greTunnels.outPriorityQueues.packets.total

       64 bit unsigned wrappable counter."
   ::= {pr1645v2TTmplPGreOutPQsEntry 50790400}

pr1645v2TTmplPGreOutPQsPacketsDirectTx OBJECT-TYPE
   SYNTAX      Counter64
   MAX-ACCESS  read-only
   STATUS      current
   DESCRIPTION
      "Path: tunnels.performance.greTunnels.outPriorityQueues.packets.directTx

       64 bit unsigned wrappable counter."
   ::= {pr1645v2TTmplPGreOutPQsEntry 50397184}

pr1645v2TTmplPGreOutPQsPacketsQueued OBJECT-TYPE
   SYNTAX      Counter64
   MAX-ACCESS  read-only
   STATUS      current
   DESCRIPTION
      "Path: tunnels.performance.greTunnels.outPriorityQueues.packets.queued

       64 bit unsigned wrappable counter."
   ::= {pr1645v2TTmplPGreOutPQsEntry 50462720}

pr1645v2TTmplPGreOutPQsPacketsDropped OBJECT-TYPE
   SYNTAX      Counter64
   MAX-ACCESS  read-only
   STATUS      current
   DESCRIPTION
      "Path: tunnels.performance.greTunnels.outPriorityQueues.packets.dropped

       64 bit unsigned wrappable counter."
   ::= {pr1645v2TTmplPGreOutPQsEntry 50528256}

pr1645v2TTmplPGreOutPQsPacketsRedDropped OBJECT-TYPE
   SYNTAX      Counter64
   MAX-ACCESS  read-only
   STATUS      current
   DESCRIPTION
      "Path: tunnels.performance.greTunnels.outPriorityQueues.packets.redDropped

       64 bit unsigned wrappable counter."
   ::= {pr1645v2TTmplPGreOutPQsEntry 50724864}

pr1645v2TTmplPGreOutPQsPacketsCirTx OBJECT-TYPE
   SYNTAX      Counter64
   MAX-ACCESS  read-only
   STATUS      current
   DESCRIPTION
      "Path: tunnels.performance.greTunnels.outPriorityQueues.packets.cirTx

       64 bit unsigned wrappable counter."
   ::= {pr1645v2TTmplPGreOutPQsEntry 50593792}

pr1645v2TTmplPGreOutPQsPacketsEirTx OBJECT-TYPE
   SYNTAX      Counter64
   MAX-ACCESS  read-only
   STATUS      current
   DESCRIPTION
      "Path: tunnels.performance.greTunnels.outPriorityQueues.packets.eirTx

       64 bit unsigned wrappable counter."
   ::= {pr1645v2TTmplPGreOutPQsEntry 50659328}

pr1645v2TTmplPGreOutPQsPacketsViolateTx OBJECT-TYPE
   SYNTAX      Counter64
   MAX-ACCESS  read-only
   STATUS      current
   DESCRIPTION
      "Path: tunnels.performance.greTunnels.outPriorityQueues.packets.violateTx

       64 bit unsigned wrappable counter."
   ::= {pr1645v2TTmplPGreOutPQsEntry 50855936}

pr1645v2TTmplPGreOutPQsOctetsTotal OBJECT-TYPE
   SYNTAX      Counter64
   MAX-ACCESS  read-only
   STATUS      current
   DESCRIPTION
      "Path: tunnels.performance.greTunnels.outPriorityQueues.octets.total

       64 bit unsigned wrappable counter."
   ::= {pr1645v2TTmplPGreOutPQsEntry 67567616}

pr1645v2TTmplPGreOutPQsOctetsDirectTx OBJECT-TYPE
   SYNTAX      Counter64
   MAX-ACCESS  read-only
   STATUS      current
   DESCRIPTION
      "Path: tunnels.performance.greTunnels.outPriorityQueues.octets.directTx

       64 bit unsigned wrappable counter."
   ::= {pr1645v2TTmplPGreOutPQsEntry 67174400}

pr1645v2TTmplPGreOutPQsOctetsQueued OBJECT-TYPE
   SYNTAX      Counter64
   MAX-ACCESS  read-only
   STATUS      current
   DESCRIPTION
      "Path: tunnels.performance.greTunnels.outPriorityQueues.octets.queued

       64 bit unsigned wrappable counter."
   ::= {pr1645v2TTmplPGreOutPQsEntry 67239936}

pr1645v2TTmplPGreOutPQsOctetsDropped OBJECT-TYPE
   SYNTAX      Counter64
   MAX-ACCESS  read-only
   STATUS      current
   DESCRIPTION
      "Path: tunnels.performance.greTunnels.outPriorityQueues.octets.dropped

       64 bit unsigned wrappable counter."
   ::= {pr1645v2TTmplPGreOutPQsEntry 67305472}

pr1645v2TTmplPGreOutPQsOctetsRedDropped OBJECT-TYPE
   SYNTAX      Counter64
   MAX-ACCESS  read-only
   STATUS      current
   DESCRIPTION
      "Path: tunnels.performance.greTunnels.outPriorityQueues.octets.redDropped

       64 bit unsigned wrappable counter."
   ::= {pr1645v2TTmplPGreOutPQsEntry 67502080}

pr1645v2TTmplPGreOutPQsOctetsCirTx OBJECT-TYPE
   SYNTAX      Counter64
   MAX-ACCESS  read-only
   STATUS      current
   DESCRIPTION
      "Path: tunnels.performance.greTunnels.outPriorityQueues.octets.cirTx

       64 bit unsigned wrappable counter."
   ::= {pr1645v2TTmplPGreOutPQsEntry 67371008}

pr1645v2TTmplPGreOutPQsOctetsEirTx OBJECT-TYPE
   SYNTAX      Counter64
   MAX-ACCESS  read-only
   STATUS      current
   DESCRIPTION
      "Path: tunnels.performance.greTunnels.outPriorityQueues.octets.eirTx

       64 bit unsigned wrappable counter."
   ::= {pr1645v2TTmplPGreOutPQsEntry 67436544}

pr1645v2TTmplPGreOutPQsOctetsViolateTx OBJECT-TYPE
   SYNTAX      Counter64
   MAX-ACCESS  read-only
   STATUS      current
   DESCRIPTION
      "Path: tunnels.performance.greTunnels.outPriorityQueues.octets.violateTx

       64 bit unsigned wrappable counter."
   ::= {pr1645v2TTmplPGreOutPQsEntry 67633152}

pr1645v2TTmplPGreOutPQsOctetsBandwidth15sec OBJECT-TYPE
   SYNTAX      Integer32
   MAX-ACCESS  read-only
   STATUS      current
   DESCRIPTION
      "Path: tunnels.performance.greTunnels.outPriorityQueues.octets.bandwidth.15sec

       unit name = bps
       formula = 8 * ; 8 /"
   ::= {pr1645v2TTmplPGreOutPQsEntry 70386944}

pr1645v2TTmplPGreOutPQsOctetsBandwidth30sec OBJECT-TYPE
   SYNTAX      Integer32
   MAX-ACCESS  read-only
   STATUS      current
   DESCRIPTION
      "Path: tunnels.performance.greTunnels.outPriorityQueues.octets.bandwidth.30sec

       unit name = bps
       formula = 8 * ; 8 /"
   ::= {pr1645v2TTmplPGreOutPQsEntry 70388224}

pr1645v2TTmplPGreOutPQsOctetsBandwidth1min OBJECT-TYPE
   SYNTAX      Integer32
   MAX-ACCESS  read-only
   STATUS      current
   DESCRIPTION
      "Path: tunnels.performance.greTunnels.outPriorityQueues.octets.bandwidth.1min

       unit name = bps
       formula = 8 * ; 8 /"
   ::= {pr1645v2TTmplPGreOutPQsEntry 70390784}

pr1645v2TTmplPGreOutPQsOctetsBandwidth2min OBJECT-TYPE
   SYNTAX      Integer32
   MAX-ACCESS  read-only
   STATUS      current
   DESCRIPTION
      "Path: tunnels.performance.greTunnels.outPriorityQueues.octets.bandwidth.2min

       unit name = bps
       formula = 8 * ; 8 /"
   ::= {pr1645v2TTmplPGreOutPQsEntry 70395904}

pr1645v2TTmplPGreOutPQsOctetsBandwidth5min OBJECT-TYPE
   SYNTAX      Integer32
   MAX-ACCESS  read-only
   STATUS      current
   DESCRIPTION
      "Path: tunnels.performance.greTunnels.outPriorityQueues.octets.bandwidth.5min

       unit name = bps
       formula = 8 * ; 8 /"
   ::= {pr1645v2TTmplPGreOutPQsEntry 70411264}

pr1645v2TTmplPGreOutPQsH2Performance OBJECT-TYPE
   SYNTAX      SEQUENCE OF Pr1645v2TTmplPGreOutPQsH2PerformanceEntry
   MAX-ACCESS  not-accessible
   STATUS      current
   DESCRIPTION
      ""
   ::= {pr1645v2TTmplPGre 84213760}

pr1645v2TTmplPGreOutPQsH2PerformanceEntry OBJECT-TYPE
   SYNTAX      Pr1645v2TTmplPGreOutPQsH2PerformanceEntry
   MAX-ACCESS  not-accessible
   STATUS      current
   DESCRIPTION
      ""
   INDEX      { pr1645v2TTmplPGreTableIx,
                pr1645v2TTmplPGreOutPQsTableIx,
                pr1645v2TTmplPGreOutPQsH2PerformanceTableIx }
   ::= {pr1645v2TTmplPGreOutPQsH2Performance 1}

Pr1645v2TTmplPGreOutPQsH2PerformanceEntry ::=
   SEQUENCE
      {
      pr1645v2TTmplPGreOutPQsH2PerformanceTableIx
         TableIndex,
      pr1645v2TTmplPGreOutPQsH2PerformanceSysUpTime
         TimeTicks,
      pr1645v2TTmplPGreOutPQsH2PerformanceTotPkts
         Counter64,
      pr1645v2TTmplPGreOutPQsH2PerformanceDirTxPkts
         Counter64,
      pr1645v2TTmplPGreOutPQsH2PerformanceQdPkts
         Counter64,
      pr1645v2TTmplPGreOutPQsH2PerformanceDropPkts
         Counter64,
      pr1645v2TTmplPGreOutPQsH2PerformanceRDropPkts
         Counter64,
      pr1645v2TTmplPGreOutPQsH2PerformanceCirTxPkts
         Counter64,
      pr1645v2TTmplPGreOutPQsH2PerformanceEirTxPkts
         Counter64,
      pr1645v2TTmplPGreOutPQsH2PerformanceViolTxPkts
         Counter64,
      pr1645v2TTmplPGreOutPQsH2PerformanceTotOcts
         Counter64,
      pr1645v2TTmplPGreOutPQsH2PerformanceDirTxOcts
         Counter64,
      pr1645v2TTmplPGreOutPQsH2PerformanceQdOcts
         Counter64,
      pr1645v2TTmplPGreOutPQsH2PerformanceDropOcts
         Counter64,
      pr1645v2TTmplPGreOutPQsH2PerformanceRDropOcts
         Counter64,
      pr1645v2TTmplPGreOutPQsH2PerformanceCirTxOcts
         Counter64,
      pr1645v2TTmplPGreOutPQsH2PerformanceEirTxOcts
         Counter64,
      pr1645v2TTmplPGreOutPQsH2PerformanceViolTxOcts
         Counter64,
      pr1645v2TTmplPGreOutPQsH2PerformanceBandwidth
         Integer32
      }

pr1645v2TTmplPGreOutPQsH2PerformanceTableIx OBJECT-TYPE
   SYNTAX      TableIndex
   MAX-ACCESS  not-accessible
   STATUS      current
   DESCRIPTION
      ""
   ::= {pr1645v2TTmplPGreOutPQsH2PerformanceEntry 11}

pr1645v2TTmplPGreOutPQsH2PerformanceSysUpTime OBJECT-TYPE
   SYNTAX      TimeTicks
   MAX-ACCESS  read-only
   STATUS      current
   DESCRIPTION
      "Path: tunnels.performance.greTunnels.outPriorityQueues.h2Performance.sysUpTime

       Time in centi-second."
   ::= {pr1645v2TTmplPGreOutPQsH2PerformanceEntry 16777216}

pr1645v2TTmplPGreOutPQsH2PerformanceTotPkts OBJECT-TYPE
   SYNTAX      Counter64
   MAX-ACCESS  read-only
   STATUS      current
   DESCRIPTION
      "Path: tunnels.performance.greTunnels.outPriorityQueues.h2Performance.totalPkts

       64 bit unsigned wrappable counter."
   ::= {pr1645v2TTmplPGreOutPQsH2PerformanceEntry 234881024}

pr1645v2TTmplPGreOutPQsH2PerformanceDirTxPkts OBJECT-TYPE
   SYNTAX      Counter64
   MAX-ACCESS  read-only
   STATUS      current
   DESCRIPTION
      "Path: tunnels.performance.greTunnels.outPriorityQueues.h2Performance.directTxPkts

       64 bit unsigned wrappable counter."
   ::= {pr1645v2TTmplPGreOutPQsH2PerformanceEntry 33554432}

pr1645v2TTmplPGreOutPQsH2PerformanceQdPkts OBJECT-TYPE
   SYNTAX      Counter64
   MAX-ACCESS  read-only
   STATUS      current
   DESCRIPTION
      "Path: tunnels.performance.greTunnels.outPriorityQueues.h2Performance.queuedPkts

       64 bit unsigned wrappable counter."
   ::= {pr1645v2TTmplPGreOutPQsH2PerformanceEntry 50331648}

pr1645v2TTmplPGreOutPQsH2PerformanceDropPkts OBJECT-TYPE
   SYNTAX      Counter64
   MAX-ACCESS  read-only
   STATUS      current
   DESCRIPTION
      "Path: tunnels.performance.greTunnels.outPriorityQueues.h2Performance.droppedPkts

       64 bit unsigned wrappable counter."
   ::= {pr1645v2TTmplPGreOutPQsH2PerformanceEntry 67108864}

pr1645v2TTmplPGreOutPQsH2PerformanceRDropPkts OBJECT-TYPE
   SYNTAX      Counter64
   MAX-ACCESS  read-only
   STATUS      current
   DESCRIPTION
      "Path: tunnels.performance.greTunnels.outPriorityQueues.h2Performance.redDroppedPkts

       64 bit unsigned wrappable counter."
   ::= {pr1645v2TTmplPGreOutPQsH2PerformanceEntry 201326592}

pr1645v2TTmplPGreOutPQsH2PerformanceCirTxPkts OBJECT-TYPE
   SYNTAX      Counter64
   MAX-ACCESS  read-only
   STATUS      current
   DESCRIPTION
      "Path: tunnels.performance.greTunnels.outPriorityQueues.h2Performance.cirTxPkts

       64 bit unsigned wrappable counter."
   ::= {pr1645v2TTmplPGreOutPQsH2PerformanceEntry 83886080}

pr1645v2TTmplPGreOutPQsH2PerformanceEirTxPkts OBJECT-TYPE
   SYNTAX      Counter64
   MAX-ACCESS  read-only
   STATUS      current
   DESCRIPTION
      "Path: tunnels.performance.greTunnels.outPriorityQueues.h2Performance.eirTxPkts

       64 bit unsigned wrappable counter."
   ::= {pr1645v2TTmplPGreOutPQsH2PerformanceEntry 100663296}

pr1645v2TTmplPGreOutPQsH2PerformanceViolTxPkts OBJECT-TYPE
   SYNTAX      Counter64
   MAX-ACCESS  read-only
   STATUS      current
   DESCRIPTION
      "Path: tunnels.performance.greTunnels.outPriorityQueues.h2Performance.violateTxPkts

       64 bit unsigned wrappable counter."
   ::= {pr1645v2TTmplPGreOutPQsH2PerformanceEntry 301989888}

pr1645v2TTmplPGreOutPQsH2PerformanceTotOcts OBJECT-TYPE
   SYNTAX      Counter64
   MAX-ACCESS  read-only
   STATUS      current
   DESCRIPTION
      "Path: tunnels.performance.greTunnels.outPriorityQueues.h2Performance.totalOctets

       64 bit unsigned wrappable counter."
   ::= {pr1645v2TTmplPGreOutPQsH2PerformanceEntry 251658240}

pr1645v2TTmplPGreOutPQsH2PerformanceDirTxOcts OBJECT-TYPE
   SYNTAX      Counter64
   MAX-ACCESS  read-only
   STATUS      current
   DESCRIPTION
      "Path: tunnels.performance.greTunnels.outPriorityQueues.h2Performance.directTxOctets

       64 bit unsigned wrappable counter."
   ::= {pr1645v2TTmplPGreOutPQsH2PerformanceEntry 117440512}

pr1645v2TTmplPGreOutPQsH2PerformanceQdOcts OBJECT-TYPE
   SYNTAX      Counter64
   MAX-ACCESS  read-only
   STATUS      current
   DESCRIPTION
      "Path: tunnels.performance.greTunnels.outPriorityQueues.h2Performance.queuedOctets

       64 bit unsigned wrappable counter."
   ::= {pr1645v2TTmplPGreOutPQsH2PerformanceEntry 134217728}

pr1645v2TTmplPGreOutPQsH2PerformanceDropOcts OBJECT-TYPE
   SYNTAX      Counter64
   MAX-ACCESS  read-only
   STATUS      current
   DESCRIPTION
      "Path: tunnels.performance.greTunnels.outPriorityQueues.h2Performance.droppedOctets

       64 bit unsigned wrappable counter."
   ::= {pr1645v2TTmplPGreOutPQsH2PerformanceEntry 150994944}

pr1645v2TTmplPGreOutPQsH2PerformanceRDropOcts OBJECT-TYPE
   SYNTAX      Counter64
   MAX-ACCESS  read-only
   STATUS      current
   DESCRIPTION
      "Path: tunnels.performance.greTunnels.outPriorityQueues.h2Performance.redDroppedOctets

       64 bit unsigned wrappable counter."
   ::= {pr1645v2TTmplPGreOutPQsH2PerformanceEntry 218103808}

pr1645v2TTmplPGreOutPQsH2PerformanceCirTxOcts OBJECT-TYPE
   SYNTAX      Counter64
   MAX-ACCESS  read-only
   STATUS      current
   DESCRIPTION
      "Path: tunnels.performance.greTunnels.outPriorityQueues.h2Performance.cirTxOctets

       64 bit unsigned wrappable counter."
   ::= {pr1645v2TTmplPGreOutPQsH2PerformanceEntry 167772160}

pr1645v2TTmplPGreOutPQsH2PerformanceEirTxOcts OBJECT-TYPE
   SYNTAX      Counter64
   MAX-ACCESS  read-only
   STATUS      current
   DESCRIPTION
      "Path: tunnels.performance.greTunnels.outPriorityQueues.h2Performance.eirTxOctets

       64 bit unsigned wrappable counter."
   ::= {pr1645v2TTmplPGreOutPQsH2PerformanceEntry 184549376}

pr1645v2TTmplPGreOutPQsH2PerformanceViolTxOcts OBJECT-TYPE
   SYNTAX      Counter64
   MAX-ACCESS  read-only
   STATUS      current
   DESCRIPTION
      "Path: tunnels.performance.greTunnels.outPriorityQueues.h2Performance.violateTxOctets

       64 bit unsigned wrappable counter."
   ::= {pr1645v2TTmplPGreOutPQsH2PerformanceEntry 318767104}

pr1645v2TTmplPGreOutPQsH2PerformanceBandwidth OBJECT-TYPE
   SYNTAX      Integer32
   MAX-ACCESS  read-only
   STATUS      current
   DESCRIPTION
      "Path: tunnels.performance.greTunnels.outPriorityQueues.h2Performance.bandwidth

       unit name = bps
       formula = 8 * ; 8 /"
   ::= {pr1645v2TTmplPGreOutPQsH2PerformanceEntry 268435456}

pr1645v2TTmplPGreOutPQsH24Performance OBJECT-TYPE
   SYNTAX      SEQUENCE OF Pr1645v2TTmplPGreOutPQsH24PerformanceEntry
   MAX-ACCESS  not-accessible
   STATUS      current
   DESCRIPTION
      ""
   ::= {pr1645v2TTmplPGre 84279296}

pr1645v2TTmplPGreOutPQsH24PerformanceEntry OBJECT-TYPE
   SYNTAX      Pr1645v2TTmplPGreOutPQsH24PerformanceEntry
   MAX-ACCESS  not-accessible
   STATUS      current
   DESCRIPTION
      ""
   INDEX      { pr1645v2TTmplPGreTableIx,
                pr1645v2TTmplPGreOutPQsTableIx,
                pr1645v2TTmplPGreOutPQsH24PerformanceTableIx }
   ::= {pr1645v2TTmplPGreOutPQsH24Performance 1}

Pr1645v2TTmplPGreOutPQsH24PerformanceEntry ::=
   SEQUENCE
      {
      pr1645v2TTmplPGreOutPQsH24PerformanceTableIx
         TableIndex,
      pr1645v2TTmplPGreOutPQsH24PerformanceSysUpTime
         TimeTicks,
      pr1645v2TTmplPGreOutPQsH24PerformanceTotPkts
         Counter64,
      pr1645v2TTmplPGreOutPQsH24PerformanceDirTxPkts
         Counter64,
      pr1645v2TTmplPGreOutPQsH24PerformanceQdPkts
         Counter64,
      pr1645v2TTmplPGreOutPQsH24PerformanceDropPkts
         Counter64,
      pr1645v2TTmplPGreOutPQsH24PerformanceRDropPkts
         Counter64,
      pr1645v2TTmplPGreOutPQsH24PerformanceCirTxPkts
         Counter64,
      pr1645v2TTmplPGreOutPQsH24PerformanceEirTxPkts
         Counter64,
      pr1645v2TTmplPGreOutPQsH24PerformanceViolTxPkts
         Counter64,
      pr1645v2TTmplPGreOutPQsH24PerformanceTotOcts
         Counter64,
      pr1645v2TTmplPGreOutPQsH24PerformanceDirTxOcts
         Counter64,
      pr1645v2TTmplPGreOutPQsH24PerformanceQdOcts
         Counter64,
      pr1645v2TTmplPGreOutPQsH24PerformanceDropOcts
         Counter64,
      pr1645v2TTmplPGreOutPQsH24PerformanceRDropOcts
         Counter64,
      pr1645v2TTmplPGreOutPQsH24PerformanceCirTxOcts
         Counter64,
      pr1645v2TTmplPGreOutPQsH24PerformanceEirTxOcts
         Counter64,
      pr1645v2TTmplPGreOutPQsH24PerformanceViolTxOcts
         Counter64,
      pr1645v2TTmplPGreOutPQsH24PerformanceBandwidth
         Integer32
      }

pr1645v2TTmplPGreOutPQsH24PerformanceTableIx OBJECT-TYPE
   SYNTAX      TableIndex
   MAX-ACCESS  not-accessible
   STATUS      current
   DESCRIPTION
      ""
   ::= {pr1645v2TTmplPGreOutPQsH24PerformanceEntry 11}

pr1645v2TTmplPGreOutPQsH24PerformanceSysUpTime OBJECT-TYPE
   SYNTAX      TimeTicks
   MAX-ACCESS  read-only
   STATUS      current
   DESCRIPTION
      "Path: tunnels.performance.greTunnels.outPriorityQueues.h24Performance.sysUpTime

       Time in centi-second."
   ::= {pr1645v2TTmplPGreOutPQsH24PerformanceEntry 16777216}

pr1645v2TTmplPGreOutPQsH24PerformanceTotPkts OBJECT-TYPE
   SYNTAX      Counter64
   MAX-ACCESS  read-only
   STATUS      current
   DESCRIPTION
      "Path: tunnels.performance.greTunnels.outPriorityQueues.h24Performance.totalPkts

       64 bit unsigned wrappable counter."
   ::= {pr1645v2TTmplPGreOutPQsH24PerformanceEntry 234881024}

pr1645v2TTmplPGreOutPQsH24PerformanceDirTxPkts OBJECT-TYPE
   SYNTAX      Counter64
   MAX-ACCESS  read-only
   STATUS      current
   DESCRIPTION
      "Path: tunnels.performance.greTunnels.outPriorityQueues.h24Performance.directTxPkts

       64 bit unsigned wrappable counter."
   ::= {pr1645v2TTmplPGreOutPQsH24PerformanceEntry 33554432}

pr1645v2TTmplPGreOutPQsH24PerformanceQdPkts OBJECT-TYPE
   SYNTAX      Counter64
   MAX-ACCESS  read-only
   STATUS      current
   DESCRIPTION
      "Path: tunnels.performance.greTunnels.outPriorityQueues.h24Performance.queuedPkts

       64 bit unsigned wrappable counter."
   ::= {pr1645v2TTmplPGreOutPQsH24PerformanceEntry 50331648}

pr1645v2TTmplPGreOutPQsH24PerformanceDropPkts OBJECT-TYPE
   SYNTAX      Counter64
   MAX-ACCESS  read-only
   STATUS      current
   DESCRIPTION
      "Path: tunnels.performance.greTunnels.outPriorityQueues.h24Performance.droppedPkts

       64 bit unsigned wrappable counter."
   ::= {pr1645v2TTmplPGreOutPQsH24PerformanceEntry 67108864}

pr1645v2TTmplPGreOutPQsH24PerformanceRDropPkts OBJECT-TYPE
   SYNTAX      Counter64
   MAX-ACCESS  read-only
   STATUS      current
   DESCRIPTION
      "Path: tunnels.performance.greTunnels.outPriorityQueues.h24Performance.redDroppedPkts

       64 bit unsigned wrappable counter."
   ::= {pr1645v2TTmplPGreOutPQsH24PerformanceEntry 201326592}

pr1645v2TTmplPGreOutPQsH24PerformanceCirTxPkts OBJECT-TYPE
   SYNTAX      Counter64
   MAX-ACCESS  read-only
   STATUS      current
   DESCRIPTION
      "Path: tunnels.performance.greTunnels.outPriorityQueues.h24Performance.cirTxPkts

       64 bit unsigned wrappable counter."
   ::= {pr1645v2TTmplPGreOutPQsH24PerformanceEntry 83886080}

pr1645v2TTmplPGreOutPQsH24PerformanceEirTxPkts OBJECT-TYPE
   SYNTAX      Counter64
   MAX-ACCESS  read-only
   STATUS      current
   DESCRIPTION
      "Path: tunnels.performance.greTunnels.outPriorityQueues.h24Performance.eirTxPkts

       64 bit unsigned wrappable counter."
   ::= {pr1645v2TTmplPGreOutPQsH24PerformanceEntry 100663296}

pr1645v2TTmplPGreOutPQsH24PerformanceViolTxPkts OBJECT-TYPE
   SYNTAX      Counter64
   MAX-ACCESS  read-only
   STATUS      current
   DESCRIPTION
      "Path: tunnels.performance.greTunnels.outPriorityQueues.h24Performance.violateTxPkts

       64 bit unsigned wrappable counter."
   ::= {pr1645v2TTmplPGreOutPQsH24PerformanceEntry 301989888}

pr1645v2TTmplPGreOutPQsH24PerformanceTotOcts OBJECT-TYPE
   SYNTAX      Counter64
   MAX-ACCESS  read-only
   STATUS      current
   DESCRIPTION
      "Path: tunnels.performance.greTunnels.outPriorityQueues.h24Performance.totalOctets

       64 bit unsigned wrappable counter."
   ::= {pr1645v2TTmplPGreOutPQsH24PerformanceEntry 251658240}

pr1645v2TTmplPGreOutPQsH24PerformanceDirTxOcts OBJECT-TYPE
   SYNTAX      Counter64
   MAX-ACCESS  read-only
   STATUS      current
   DESCRIPTION
      "Path: tunnels.performance.greTunnels.outPriorityQueues.h24Performance.directTxOctets

       64 bit unsigned wrappable counter."
   ::= {pr1645v2TTmplPGreOutPQsH24PerformanceEntry 117440512}

pr1645v2TTmplPGreOutPQsH24PerformanceQdOcts OBJECT-TYPE
   SYNTAX      Counter64
   MAX-ACCESS  read-only
   STATUS      current
   DESCRIPTION
      "Path: tunnels.performance.greTunnels.outPriorityQueues.h24Performance.queuedOctets

       64 bit unsigned wrappable counter."
   ::= {pr1645v2TTmplPGreOutPQsH24PerformanceEntry 134217728}

pr1645v2TTmplPGreOutPQsH24PerformanceDropOcts OBJECT-TYPE
   SYNTAX      Counter64
   MAX-ACCESS  read-only
   STATUS      current
   DESCRIPTION
      "Path: tunnels.performance.greTunnels.outPriorityQueues.h24Performance.droppedOctets

       64 bit unsigned wrappable counter."
   ::= {pr1645v2TTmplPGreOutPQsH24PerformanceEntry 150994944}

pr1645v2TTmplPGreOutPQsH24PerformanceRDropOcts OBJECT-TYPE
   SYNTAX      Counter64
   MAX-ACCESS  read-only
   STATUS      current
   DESCRIPTION
      "Path: tunnels.performance.greTunnels.outPriorityQueues.h24Performance.redDroppedOctets

       64 bit unsigned wrappable counter."
   ::= {pr1645v2TTmplPGreOutPQsH24PerformanceEntry 218103808}

pr1645v2TTmplPGreOutPQsH24PerformanceCirTxOcts OBJECT-TYPE
   SYNTAX      Counter64
   MAX-ACCESS  read-only
   STATUS      current
   DESCRIPTION
      "Path: tunnels.performance.greTunnels.outPriorityQueues.h24Performance.cirTxOctets

       64 bit unsigned wrappable counter."
   ::= {pr1645v2TTmplPGreOutPQsH24PerformanceEntry 167772160}

pr1645v2TTmplPGreOutPQsH24PerformanceEirTxOcts OBJECT-TYPE
   SYNTAX      Counter64
   MAX-ACCESS  read-only
   STATUS      current
   DESCRIPTION
      "Path: tunnels.performance.greTunnels.outPriorityQueues.h24Performance.eirTxOctets

       64 bit unsigned wrappable counter."
   ::= {pr1645v2TTmplPGreOutPQsH24PerformanceEntry 184549376}

pr1645v2TTmplPGreOutPQsH24PerformanceViolTxOcts OBJECT-TYPE
   SYNTAX      Counter64
   MAX-ACCESS  read-only
   STATUS      current
   DESCRIPTION
      "Path: tunnels.performance.greTunnels.outPriorityQueues.h24Performance.violateTxOctets

       64 bit unsigned wrappable counter."
   ::= {pr1645v2TTmplPGreOutPQsH24PerformanceEntry 318767104}

pr1645v2TTmplPGreOutPQsH24PerformanceBandwidth OBJECT-TYPE
   SYNTAX      Integer32
   MAX-ACCESS  read-only
   STATUS      current
   DESCRIPTION
      "Path: tunnels.performance.greTunnels.outPriorityQueues.h24Performance.bandwidth

       unit name = bps
       formula = 8 * ; 8 /"
   ::= {pr1645v2TTmplPGreOutPQsH24PerformanceEntry 268435456}

pr1645v2TTmplPGreOutPQsD7Performance OBJECT-TYPE
   SYNTAX      SEQUENCE OF Pr1645v2TTmplPGreOutPQsD7PerformanceEntry
   MAX-ACCESS  not-accessible
   STATUS      current
   DESCRIPTION
      ""
   ::= {pr1645v2TTmplPGre 84344832}

pr1645v2TTmplPGreOutPQsD7PerformanceEntry OBJECT-TYPE
   SYNTAX      Pr1645v2TTmplPGreOutPQsD7PerformanceEntry
   MAX-ACCESS  not-accessible
   STATUS      current
   DESCRIPTION
      ""
   INDEX      { pr1645v2TTmplPGreTableIx,
                pr1645v2TTmplPGreOutPQsTableIx,
                pr1645v2TTmplPGreOutPQsD7PerformanceTableIx }
   ::= {pr1645v2TTmplPGreOutPQsD7Performance 1}

Pr1645v2TTmplPGreOutPQsD7PerformanceEntry ::=
   SEQUENCE
      {
      pr1645v2TTmplPGreOutPQsD7PerformanceTableIx
         TableIndex,
      pr1645v2TTmplPGreOutPQsD7PerformanceSysUpTime
         TimeTicks,
      pr1645v2TTmplPGreOutPQsD7PerformanceTotPkts
         Counter64,
      pr1645v2TTmplPGreOutPQsD7PerformanceDirTxPkts
         Counter64,
      pr1645v2TTmplPGreOutPQsD7PerformanceQdPkts
         Counter64,
      pr1645v2TTmplPGreOutPQsD7PerformanceDropPkts
         Counter64,
      pr1645v2TTmplPGreOutPQsD7PerformanceRDropPkts
         Counter64,
      pr1645v2TTmplPGreOutPQsD7PerformanceCirTxPkts
         Counter64,
      pr1645v2TTmplPGreOutPQsD7PerformanceEirTxPkts
         Counter64,
      pr1645v2TTmplPGreOutPQsD7PerformanceViolTxPkts
         Counter64,
      pr1645v2TTmplPGreOutPQsD7PerformanceTotOcts
         Counter64,
      pr1645v2TTmplPGreOutPQsD7PerformanceDirTxOcts
         Counter64,
      pr1645v2TTmplPGreOutPQsD7PerformanceQdOcts
         Counter64,
      pr1645v2TTmplPGreOutPQsD7PerformanceDropOcts
         Counter64,
      pr1645v2TTmplPGreOutPQsD7PerformanceRDropOcts
         Counter64,
      pr1645v2TTmplPGreOutPQsD7PerformanceCirTxOcts
         Counter64,
      pr1645v2TTmplPGreOutPQsD7PerformanceEirTxOcts
         Counter64,
      pr1645v2TTmplPGreOutPQsD7PerformanceViolTxOcts
         Counter64,
      pr1645v2TTmplPGreOutPQsD7PerformanceBandwidth
         Integer32
      }

pr1645v2TTmplPGreOutPQsD7PerformanceTableIx OBJECT-TYPE
   SYNTAX      TableIndex
   MAX-ACCESS  not-accessible
   STATUS      current
   DESCRIPTION
      ""
   ::= {pr1645v2TTmplPGreOutPQsD7PerformanceEntry 11}

pr1645v2TTmplPGreOutPQsD7PerformanceSysUpTime OBJECT-TYPE
   SYNTAX      TimeTicks
   MAX-ACCESS  read-only
   STATUS      current
   DESCRIPTION
      "Path: tunnels.performance.greTunnels.outPriorityQueues.d7Performance.sysUpTime

       Time in centi-second."
   ::= {pr1645v2TTmplPGreOutPQsD7PerformanceEntry 16777216}

pr1645v2TTmplPGreOutPQsD7PerformanceTotPkts OBJECT-TYPE
   SYNTAX      Counter64
   MAX-ACCESS  read-only
   STATUS      current
   DESCRIPTION
      "Path: tunnels.performance.greTunnels.outPriorityQueues.d7Performance.totalPkts

       64 bit unsigned wrappable counter."
   ::= {pr1645v2TTmplPGreOutPQsD7PerformanceEntry 234881024}

pr1645v2TTmplPGreOutPQsD7PerformanceDirTxPkts OBJECT-TYPE
   SYNTAX      Counter64
   MAX-ACCESS  read-only
   STATUS      current
   DESCRIPTION
      "Path: tunnels.performance.greTunnels.outPriorityQueues.d7Performance.directTxPkts

       64 bit unsigned wrappable counter."
   ::= {pr1645v2TTmplPGreOutPQsD7PerformanceEntry 33554432}

pr1645v2TTmplPGreOutPQsD7PerformanceQdPkts OBJECT-TYPE
   SYNTAX      Counter64
   MAX-ACCESS  read-only
   STATUS      current
   DESCRIPTION
      "Path: tunnels.performance.greTunnels.outPriorityQueues.d7Performance.queuedPkts

       64 bit unsigned wrappable counter."
   ::= {pr1645v2TTmplPGreOutPQsD7PerformanceEntry 50331648}

pr1645v2TTmplPGreOutPQsD7PerformanceDropPkts OBJECT-TYPE
   SYNTAX      Counter64
   MAX-ACCESS  read-only
   STATUS      current
   DESCRIPTION
      "Path: tunnels.performance.greTunnels.outPriorityQueues.d7Performance.droppedPkts

       64 bit unsigned wrappable counter."
   ::= {pr1645v2TTmplPGreOutPQsD7PerformanceEntry 67108864}

pr1645v2TTmplPGreOutPQsD7PerformanceRDropPkts OBJECT-TYPE
   SYNTAX      Counter64
   MAX-ACCESS  read-only
   STATUS      current
   DESCRIPTION
      "Path: tunnels.performance.greTunnels.outPriorityQueues.d7Performance.redDroppedPkts

       64 bit unsigned wrappable counter."
   ::= {pr1645v2TTmplPGreOutPQsD7PerformanceEntry 201326592}

pr1645v2TTmplPGreOutPQsD7PerformanceCirTxPkts OBJECT-TYPE
   SYNTAX      Counter64
   MAX-ACCESS  read-only
   STATUS      current
   DESCRIPTION
      "Path: tunnels.performance.greTunnels.outPriorityQueues.d7Performance.cirTxPkts

       64 bit unsigned wrappable counter."
   ::= {pr1645v2TTmplPGreOutPQsD7PerformanceEntry 83886080}

pr1645v2TTmplPGreOutPQsD7PerformanceEirTxPkts OBJECT-TYPE
   SYNTAX      Counter64
   MAX-ACCESS  read-only
   STATUS      current
   DESCRIPTION
      "Path: tunnels.performance.greTunnels.outPriorityQueues.d7Performance.eirTxPkts

       64 bit unsigned wrappable counter."
   ::= {pr1645v2TTmplPGreOutPQsD7PerformanceEntry 100663296}

pr1645v2TTmplPGreOutPQsD7PerformanceViolTxPkts OBJECT-TYPE
   SYNTAX      Counter64
   MAX-ACCESS  read-only
   STATUS      current
   DESCRIPTION
      "Path: tunnels.performance.greTunnels.outPriorityQueues.d7Performance.violateTxPkts

       64 bit unsigned wrappable counter."
   ::= {pr1645v2TTmplPGreOutPQsD7PerformanceEntry 301989888}

pr1645v2TTmplPGreOutPQsD7PerformanceTotOcts OBJECT-TYPE
   SYNTAX      Counter64
   MAX-ACCESS  read-only
   STATUS      current
   DESCRIPTION
      "Path: tunnels.performance.greTunnels.outPriorityQueues.d7Performance.totalOctets

       64 bit unsigned wrappable counter."
   ::= {pr1645v2TTmplPGreOutPQsD7PerformanceEntry 251658240}

pr1645v2TTmplPGreOutPQsD7PerformanceDirTxOcts OBJECT-TYPE
   SYNTAX      Counter64
   MAX-ACCESS  read-only
   STATUS      current
   DESCRIPTION
      "Path: tunnels.performance.greTunnels.outPriorityQueues.d7Performance.directTxOctets

       64 bit unsigned wrappable counter."
   ::= {pr1645v2TTmplPGreOutPQsD7PerformanceEntry 117440512}

pr1645v2TTmplPGreOutPQsD7PerformanceQdOcts OBJECT-TYPE
   SYNTAX      Counter64
   MAX-ACCESS  read-only
   STATUS      current
   DESCRIPTION
      "Path: tunnels.performance.greTunnels.outPriorityQueues.d7Performance.queuedOctets

       64 bit unsigned wrappable counter."
   ::= {pr1645v2TTmplPGreOutPQsD7PerformanceEntry 134217728}

pr1645v2TTmplPGreOutPQsD7PerformanceDropOcts OBJECT-TYPE
   SYNTAX      Counter64
   MAX-ACCESS  read-only
   STATUS      current
   DESCRIPTION
      "Path: tunnels.performance.greTunnels.outPriorityQueues.d7Performance.droppedOctets

       64 bit unsigned wrappable counter."
   ::= {pr1645v2TTmplPGreOutPQsD7PerformanceEntry 150994944}

pr1645v2TTmplPGreOutPQsD7PerformanceRDropOcts OBJECT-TYPE
   SYNTAX      Counter64
   MAX-ACCESS  read-only
   STATUS      current
   DESCRIPTION
      "Path: tunnels.performance.greTunnels.outPriorityQueues.d7Performance.redDroppedOctets

       64 bit unsigned wrappable counter."
   ::= {pr1645v2TTmplPGreOutPQsD7PerformanceEntry 218103808}

pr1645v2TTmplPGreOutPQsD7PerformanceCirTxOcts OBJECT-TYPE
   SYNTAX      Counter64
   MAX-ACCESS  read-only
   STATUS      current
   DESCRIPTION
      "Path: tunnels.performance.greTunnels.outPriorityQueues.d7Performance.cirTxOctets

       64 bit unsigned wrappable counter."
   ::= {pr1645v2TTmplPGreOutPQsD7PerformanceEntry 167772160}

pr1645v2TTmplPGreOutPQsD7PerformanceEirTxOcts OBJECT-TYPE
   SYNTAX      Counter64
   MAX-ACCESS  read-only
   STATUS      current
   DESCRIPTION
      "Path: tunnels.performance.greTunnels.outPriorityQueues.d7Performance.eirTxOctets

       64 bit unsigned wrappable counter."
   ::= {pr1645v2TTmplPGreOutPQsD7PerformanceEntry 184549376}

pr1645v2TTmplPGreOutPQsD7PerformanceViolTxOcts OBJECT-TYPE
   SYNTAX      Counter64
   MAX-ACCESS  read-only
   STATUS      current
   DESCRIPTION
      "Path: tunnels.performance.greTunnels.outPriorityQueues.d7Performance.violateTxOctets

       64 bit unsigned wrappable counter."
   ::= {pr1645v2TTmplPGreOutPQsD7PerformanceEntry 318767104}

pr1645v2TTmplPGreOutPQsD7PerformanceBandwidth OBJECT-TYPE
   SYNTAX      Integer32
   MAX-ACCESS  read-only
   STATUS      current
   DESCRIPTION
      "Path: tunnels.performance.greTunnels.outPriorityQueues.d7Performance.bandwidth

       unit name = bps
       formula = 8 * ; 8 /"
   ::= {pr1645v2TTmplPGreOutPQsD7PerformanceEntry 268435456}


pr1645v2TTmplPiGre OBJECT IDENTIFIER ::= {pr1645v2TTmpl 26}

pr1645v2TTmplPiGreSSCTable OBJECT-TYPE
   SYNTAX      SEQUENCE OF Pr1645v2TTmplPiGreEntry
   MAX-ACCESS  not-accessible
   STATUS      current
   DESCRIPTION
      ""
   ::= {pr1645v2TTmplPiGre 1}

pr1645v2TTmplPiGreEntry OBJECT-TYPE
   SYNTAX      Pr1645v2TTmplPiGreEntry
   MAX-ACCESS  not-accessible
   STATUS      current
   DESCRIPTION
      ""
   INDEX      { pr1645v2TTmplPiGreTableIx }
   ::= {pr1645v2TTmplPiGreSSCTable 1}

Pr1645v2TTmplPiGreEntry ::=
   SEQUENCE
      {
      pr1645v2TTmplPiGreTableIx
         TableIndex,
      pr1645v2TTmplPiGreName
         DisplayString,
      pr1645v2TTmplPiGreMCInOctets
         Counter64,
      pr1645v2TTmplPiGreMCInUcast
         Counter64,
      pr1645v2TTmplPiGreMCInNUcastPkts
         Counter64,
      pr1645v2TTmplPiGreMCInBcastPkts
         Counter64,
      pr1645v2TTmplPiGreMCInMcastPkts
         Counter64,
      pr1645v2TTmplPiGreMCInDiscards
         Counter64,
      pr1645v2TTmplPiGreMCInErrors
         Counter64,
      pr1645v2TTmplPiGreMCInUnknownProtos
         Counter64,
      pr1645v2TTmplPiGreMCInDropEx
         Counter64,
      pr1645v2TTmplPiGreMCInDropNoMac
         Counter64,
      pr1645v2TTmplPiGreMCInDropNUCast
         Counter64,
      pr1645v2TTmplPiGreMCInDropFilter
         Counter64,
      pr1645v2TTmplPiGreMCInBandwidth15sec
         Integer32,
      pr1645v2TTmplPiGreMCInBandwidth30sec
         Integer32,
      pr1645v2TTmplPiGreMCInBandwidth1min
         Integer32,
      pr1645v2TTmplPiGreMCInBandwidth2min
         Integer32,
      pr1645v2TTmplPiGreMCInBandwidth5min
         Integer32,
      pr1645v2TTmplPiGreMCOutOctets
         Counter64,
      pr1645v2TTmplPiGreMCOutUcastPkts
         Counter64,
      pr1645v2TTmplPiGreMCOutNUcastPkts
         Counter64,
      pr1645v2TTmplPiGreMCOutBcastPkts
         Counter64,
      pr1645v2TTmplPiGreMCOutMcastPkts
         Counter64,
      pr1645v2TTmplPiGreMCOutDiscards
         Counter64,
      pr1645v2TTmplPiGreMCOutErrors
         Counter64,
      pr1645v2TTmplPiGreMCOutQLen
         Counter32,
      pr1645v2TTmplPiGreMCOutDropEx
         Counter64,
      pr1645v2TTmplPiGreMCOutDropNoArp
         Counter64,
      pr1645v2TTmplPiGreMCOutDropFilter
         Counter64,
      pr1645v2TTmplPiGreMCOutBandwidth15sec
         Integer32,
      pr1645v2TTmplPiGreMCOutBandwidth30sec
         Integer32,
      pr1645v2TTmplPiGreMCOutBandwidth1min
         Integer32,
      pr1645v2TTmplPiGreMCOutBandwidth2min
         Integer32,
      pr1645v2TTmplPiGreMCOutBandwidth5min
         Integer32,
      pr1645v2TTmplPiGreGreKeepAliveRequestsSent
         Counter32,
      pr1645v2TTmplPiGreGreKeepAliveRepliesRcvd
         Counter32
      }

pr1645v2TTmplPiGreTableIx OBJECT-TYPE
   SYNTAX      TableIndex
   MAX-ACCESS  not-accessible
   STATUS      current
   DESCRIPTION
      ""
   ::= {pr1645v2TTmplPiGreEntry 11}

pr1645v2TTmplPiGreName OBJECT-TYPE
   SYNTAX      DisplayString
   MAX-ACCESS  read-only
   STATUS      current
   DESCRIPTION
      "Path: tunnels.performance.ipsecGreTunnels.name"
   ::= {pr1645v2TTmplPiGreEntry 16777216}

pr1645v2TTmplPiGreMCInOctets OBJECT-TYPE
   SYNTAX      Counter64
   MAX-ACCESS  read-only
   STATUS      current
   DESCRIPTION
      "Path: tunnels.performance.ipsecGreTunnels.mibCounters.ifInOctets

       64 bit unsigned wrappable counter."
   ::= {pr1645v2TTmplPiGreEntry 40697856}

pr1645v2TTmplPiGreMCInUcast OBJECT-TYPE
   SYNTAX      Counter64
   MAX-ACCESS  read-only
   STATUS      current
   DESCRIPTION
      "Path: tunnels.performance.ipsecGreTunnels.mibCounters.ifInUcastPkts

       64 bit unsigned wrappable counter."
   ::= {pr1645v2TTmplPiGreEntry 40763392}

pr1645v2TTmplPiGreMCInNUcastPkts OBJECT-TYPE
   SYNTAX      Counter64
   MAX-ACCESS  read-only
   STATUS      current
   DESCRIPTION
      "Path: tunnels.performance.ipsecGreTunnels.mibCounters.ifInNUcastPkts

       64 bit unsigned wrappable counter."
   ::= {pr1645v2TTmplPiGreEntry 40828928}

pr1645v2TTmplPiGreMCInBcastPkts OBJECT-TYPE
   SYNTAX      Counter64
   MAX-ACCESS  read-only
   STATUS      current
   DESCRIPTION
      "Path: tunnels.performance.ipsecGreTunnels.mibCounters.ifInBcastPkts

       64 bit unsigned wrappable counter."
   ::= {pr1645v2TTmplPiGreEntry 47382528}

pr1645v2TTmplPiGreMCInMcastPkts OBJECT-TYPE
   SYNTAX      Counter64
   MAX-ACCESS  read-only
   STATUS      current
   DESCRIPTION
      "Path: tunnels.performance.ipsecGreTunnels.mibCounters.ifInMcastPkts

       64 bit unsigned wrappable counter."
   ::= {pr1645v2TTmplPiGreEntry 48037888}

pr1645v2TTmplPiGreMCInDiscards OBJECT-TYPE
   SYNTAX      Counter64
   MAX-ACCESS  read-only
   STATUS      current
   DESCRIPTION
      "Path: tunnels.performance.ipsecGreTunnels.mibCounters.ifInDiscards

       64 bit unsigned wrappable counter."
   ::= {pr1645v2TTmplPiGreEntry 40894464}

pr1645v2TTmplPiGreMCInErrors OBJECT-TYPE
   SYNTAX      Counter64
   MAX-ACCESS  read-only
   STATUS      current
   DESCRIPTION
      "Path: tunnels.performance.ipsecGreTunnels.mibCounters.ifInErrors

       64 bit unsigned wrappable counter."
   ::= {pr1645v2TTmplPiGreEntry 40960000}

pr1645v2TTmplPiGreMCInUnknownProtos OBJECT-TYPE
   SYNTAX      Counter64
   MAX-ACCESS  read-only
   STATUS      current
   DESCRIPTION
      "Path: tunnels.performance.ipsecGreTunnels.mibCounters.ifInUnknownProtos

       64 bit unsigned wrappable counter."
   ::= {pr1645v2TTmplPiGreEntry 41025536}

pr1645v2TTmplPiGreMCInDropEx OBJECT-TYPE
   SYNTAX      Counter64
   MAX-ACCESS  read-only
   STATUS      current
   DESCRIPTION
      "Path: tunnels.performance.ipsecGreTunnels.mibCounters.ifInDropLevelExceeded

       64 bit unsigned wrappable counter."
   ::= {pr1645v2TTmplPiGreEntry 42074112}

pr1645v2TTmplPiGreMCInDropNoMac OBJECT-TYPE
   SYNTAX      Counter64
   MAX-ACCESS  read-only
   STATUS      current
   DESCRIPTION
      "Path: tunnels.performance.ipsecGreTunnels.mibCounters.ifInDiscardsNoMacFit

       64 bit unsigned wrappable counter."
   ::= {pr1645v2TTmplPiGreEntry 42270720}

pr1645v2TTmplPiGreMCInDropNUCast OBJECT-TYPE
   SYNTAX      Counter64
   MAX-ACCESS  read-only
   STATUS      current
   DESCRIPTION
      "Path: tunnels.performance.ipsecGreTunnels.mibCounters.ifInDiscardsNUCast

       64 bit unsigned wrappable counter."
   ::= {pr1645v2TTmplPiGreEntry 42467328}

pr1645v2TTmplPiGreMCInDropFilter OBJECT-TYPE
   SYNTAX      Counter64
   MAX-ACCESS  read-only
   STATUS      current
   DESCRIPTION
      "Path: tunnels.performance.ipsecGreTunnels.mibCounters.ifInDiscardsFilter

       64 bit unsigned wrappable counter."
   ::= {pr1645v2TTmplPiGreEntry 42532864}

pr1645v2TTmplPiGreMCInBandwidth15sec OBJECT-TYPE
   SYNTAX      Integer32
   MAX-ACCESS  read-only
   STATUS      current
   DESCRIPTION
      "Path: tunnels.performance.ipsecGreTunnels.mibCounters.ifInBandwidth.15sec

       unit name = bps
       formula = 8 * ; 8 /"
   ::= {pr1645v2TTmplPiGreEntry 45417728}

pr1645v2TTmplPiGreMCInBandwidth30sec OBJECT-TYPE
   SYNTAX      Integer32
   MAX-ACCESS  read-only
   STATUS      current
   DESCRIPTION
      "Path: tunnels.performance.ipsecGreTunnels.mibCounters.ifInBandwidth.30sec

       unit name = bps
       formula = 8 * ; 8 /"
   ::= {pr1645v2TTmplPiGreEntry 45419008}

pr1645v2TTmplPiGreMCInBandwidth1min OBJECT-TYPE
   SYNTAX      Integer32
   MAX-ACCESS  read-only
   STATUS      current
   DESCRIPTION
      "Path: tunnels.performance.ipsecGreTunnels.mibCounters.ifInBandwidth.1min

       unit name = bps
       formula = 8 * ; 8 /"
   ::= {pr1645v2TTmplPiGreEntry 45421568}

pr1645v2TTmplPiGreMCInBandwidth2min OBJECT-TYPE
   SYNTAX      Integer32
   MAX-ACCESS  read-only
   STATUS      current
   DESCRIPTION
      "Path: tunnels.performance.ipsecGreTunnels.mibCounters.ifInBandwidth.2min

       unit name = bps
       formula = 8 * ; 8 /"
   ::= {pr1645v2TTmplPiGreEntry 45426688}

pr1645v2TTmplPiGreMCInBandwidth5min OBJECT-TYPE
   SYNTAX      Integer32
   MAX-ACCESS  read-only
   STATUS      current
   DESCRIPTION
      "Path: tunnels.performance.ipsecGreTunnels.mibCounters.ifInBandwidth.5min

       unit name = bps
       formula = 8 * ; 8 /"
   ::= {pr1645v2TTmplPiGreEntry 45442048}

pr1645v2TTmplPiGreMCOutOctets OBJECT-TYPE
   SYNTAX      Counter64
   MAX-ACCESS  read-only
   STATUS      current
   DESCRIPTION
      "Path: tunnels.performance.ipsecGreTunnels.mibCounters.ifOutOctets

       64 bit unsigned wrappable counter."
   ::= {pr1645v2TTmplPiGreEntry 41091072}

pr1645v2TTmplPiGreMCOutUcastPkts OBJECT-TYPE
   SYNTAX      Counter64
   MAX-ACCESS  read-only
   STATUS      current
   DESCRIPTION
      "Path: tunnels.performance.ipsecGreTunnels.mibCounters.ifOutUcastPkts

       64 bit unsigned wrappable counter."
   ::= {pr1645v2TTmplPiGreEntry 41156608}

pr1645v2TTmplPiGreMCOutNUcastPkts OBJECT-TYPE
   SYNTAX      Counter64
   MAX-ACCESS  read-only
   STATUS      current
   DESCRIPTION
      "Path: tunnels.performance.ipsecGreTunnels.mibCounters.ifOutNUcastPkts

       64 bit unsigned wrappable counter."
   ::= {pr1645v2TTmplPiGreEntry 41222144}

pr1645v2TTmplPiGreMCOutBcastPkts OBJECT-TYPE
   SYNTAX      Counter64
   MAX-ACCESS  read-only
   STATUS      current
   DESCRIPTION
      "Path: tunnels.performance.ipsecGreTunnels.mibCounters.ifOutBcastPkts

       64 bit unsigned wrappable counter."
   ::= {pr1645v2TTmplPiGreEntry 47775744}

pr1645v2TTmplPiGreMCOutMcastPkts OBJECT-TYPE
   SYNTAX      Counter64
   MAX-ACCESS  read-only
   STATUS      current
   DESCRIPTION
      "Path: tunnels.performance.ipsecGreTunnels.mibCounters.ifOutMcastPkts

       64 bit unsigned wrappable counter."
   ::= {pr1645v2TTmplPiGreEntry 48431104}

pr1645v2TTmplPiGreMCOutDiscards OBJECT-TYPE
   SYNTAX      Counter64
   MAX-ACCESS  read-only
   STATUS      current
   DESCRIPTION
      "Path: tunnels.performance.ipsecGreTunnels.mibCounters.ifOutDiscards

       64 bit unsigned wrappable counter."
   ::= {pr1645v2TTmplPiGreEntry 41287680}

pr1645v2TTmplPiGreMCOutErrors OBJECT-TYPE
   SYNTAX      Counter64
   MAX-ACCESS  read-only
   STATUS      current
   DESCRIPTION
      "Path: tunnels.performance.ipsecGreTunnels.mibCounters.ifOutErrors

       64 bit unsigned wrappable counter."
   ::= {pr1645v2TTmplPiGreEntry 41353216}

pr1645v2TTmplPiGreMCOutQLen OBJECT-TYPE
   SYNTAX      Counter32
   MAX-ACCESS  read-only
   STATUS      current
   DESCRIPTION
      "Path: tunnels.performance.ipsecGreTunnels.mibCounters.ifOutQLen

       32 bit unsigned wrappable counter."
   ::= {pr1645v2TTmplPiGreEntry 41418752}

pr1645v2TTmplPiGreMCOutDropEx OBJECT-TYPE
   SYNTAX      Counter64
   MAX-ACCESS  read-only
   STATUS      current
   DESCRIPTION
      "Path: tunnels.performance.ipsecGreTunnels.mibCounters.ifOutDropLevelExceeded

       64 bit unsigned wrappable counter."
   ::= {pr1645v2TTmplPiGreEntry 41484288}

pr1645v2TTmplPiGreMCOutDropNoArp OBJECT-TYPE
   SYNTAX      Counter64
   MAX-ACCESS  read-only
   STATUS      current
   DESCRIPTION
      "Path: tunnels.performance.ipsecGreTunnels.mibCounters.ifOutDiscardsNoArp

       64 bit unsigned wrappable counter."
   ::= {pr1645v2TTmplPiGreEntry 42336256}

pr1645v2TTmplPiGreMCOutDropFilter OBJECT-TYPE
   SYNTAX      Counter64
   MAX-ACCESS  read-only
   STATUS      current
   DESCRIPTION
      "Path: tunnels.performance.ipsecGreTunnels.mibCounters.ifOutDiscardsFilter

       64 bit unsigned wrappable counter."
   ::= {pr1645v2TTmplPiGreEntry 42598400}

pr1645v2TTmplPiGreMCOutBandwidth15sec OBJECT-TYPE
   SYNTAX      Integer32
   MAX-ACCESS  read-only
   STATUS      current
   DESCRIPTION
      "Path: tunnels.performance.ipsecGreTunnels.mibCounters.ifOutBandwidth.15sec

       unit name = bps
       formula = 8 * ; 8 /"
   ::= {pr1645v2TTmplPiGreEntry 45483264}

pr1645v2TTmplPiGreMCOutBandwidth30sec OBJECT-TYPE
   SYNTAX      Integer32
   MAX-ACCESS  read-only
   STATUS      current
   DESCRIPTION
      "Path: tunnels.performance.ipsecGreTunnels.mibCounters.ifOutBandwidth.30sec

       unit name = bps
       formula = 8 * ; 8 /"
   ::= {pr1645v2TTmplPiGreEntry 45484544}

pr1645v2TTmplPiGreMCOutBandwidth1min OBJECT-TYPE
   SYNTAX      Integer32
   MAX-ACCESS  read-only
   STATUS      current
   DESCRIPTION
      "Path: tunnels.performance.ipsecGreTunnels.mibCounters.ifOutBandwidth.1min

       unit name = bps
       formula = 8 * ; 8 /"
   ::= {pr1645v2TTmplPiGreEntry 45487104}

pr1645v2TTmplPiGreMCOutBandwidth2min OBJECT-TYPE
   SYNTAX      Integer32
   MAX-ACCESS  read-only
   STATUS      current
   DESCRIPTION
      "Path: tunnels.performance.ipsecGreTunnels.mibCounters.ifOutBandwidth.2min

       unit name = bps
       formula = 8 * ; 8 /"
   ::= {pr1645v2TTmplPiGreEntry 45492224}

pr1645v2TTmplPiGreMCOutBandwidth5min OBJECT-TYPE
   SYNTAX      Integer32
   MAX-ACCESS  read-only
   STATUS      current
   DESCRIPTION
      "Path: tunnels.performance.ipsecGreTunnels.mibCounters.ifOutBandwidth.5min

       unit name = bps
       formula = 8 * ; 8 /"
   ::= {pr1645v2TTmplPiGreEntry 45507584}

pr1645v2TTmplPiGreGreKeepAliveRequestsSent OBJECT-TYPE
   SYNTAX      Counter32
   MAX-ACCESS  read-only
   STATUS      current
   DESCRIPTION
      "Path: tunnels.performance.ipsecGreTunnels.gre.keepAlive.requestsSent

       32 bit unsigned wrappable counter."
   ::= {pr1645v2TTmplPiGreEntry 117506304}

pr1645v2TTmplPiGreGreKeepAliveRepliesRcvd OBJECT-TYPE
   SYNTAX      Counter32
   MAX-ACCESS  read-only
   STATUS      current
   DESCRIPTION
      "Path: tunnels.performance.ipsecGreTunnels.gre.keepAlive.repliesRcvd

       32 bit unsigned wrappable counter."
   ::= {pr1645v2TTmplPiGreEntry 117506560}

pr1645v2TTmplPiGreMCH2P OBJECT-TYPE
   SYNTAX      SEQUENCE OF Pr1645v2TTmplPiGreMCH2PEntry
   MAX-ACCESS  not-accessible
   STATUS      current
   DESCRIPTION
      ""
   ::= {pr1645v2TTmplPiGre 41549824}

pr1645v2TTmplPiGreMCH2PEntry OBJECT-TYPE
   SYNTAX      Pr1645v2TTmplPiGreMCH2PEntry
   MAX-ACCESS  not-accessible
   STATUS      current
   DESCRIPTION
      ""
   INDEX      { pr1645v2TTmplPiGreTableIx,
                pr1645v2TTmplPiGreMCH2PTableIx }
   ::= {pr1645v2TTmplPiGreMCH2P 1}

Pr1645v2TTmplPiGreMCH2PEntry ::=
   SEQUENCE
      {
      pr1645v2TTmplPiGreMCH2PTableIx
         TableIndex,
      pr1645v2TTmplPiGreMCH2PSysUpTime
         TimeTicks,
      pr1645v2TTmplPiGreMCH2PIfUpTime
         TimeTicks,
      pr1645v2TTmplPiGreMCH2PIfStatChanges
         Counter32,
      pr1645v2TTmplPiGreMCH2PIfInOctets
         Counter64,
      pr1645v2TTmplPiGreMCH2PIfInUCPkts
         Counter64,
      pr1645v2TTmplPiGreMCH2PIfInNUCPkts
         Counter64,
      pr1645v2TTmplPiGreMCH2PIfInBCPkts
         Counter64,
      pr1645v2TTmplPiGreMCH2PIfInMCPkts
         Counter64,
      pr1645v2TTmplPiGreMCH2PIfInDiscards
         Counter64,
      pr1645v2TTmplPiGreMCH2PIfInErrors
         Counter64,
      pr1645v2TTmplPiGreMCH2PIfInUnkwn
         Counter64,
      pr1645v2TTmplPiGreMCH2PInDropEx
         Counter64,
      pr1645v2TTmplPiGreMCH2PInDropNoMac
         Counter64,
      pr1645v2TTmplPiGreMCH2PInDropNUCast
         Counter64,
      pr1645v2TTmplPiGreMCH2PInDropFilter
         Counter64,
      pr1645v2TTmplPiGreMCH2PIfInBandwidth
         Integer32,
      pr1645v2TTmplPiGreMCH2PIfOutOctets
         Counter64,
      pr1645v2TTmplPiGreMCH2PIfOutUCPkts
         Counter64,
      pr1645v2TTmplPiGreMCH2PIfOutNUCPkts
         Counter64,
      pr1645v2TTmplPiGreMCH2PIfOutBCPkts
         Counter64,
      pr1645v2TTmplPiGreMCH2PIfOutMCPkts
         Counter64,
      pr1645v2TTmplPiGreMCH2PIfOutDiscards
         Counter64,
      pr1645v2TTmplPiGreMCH2PIfOutErrors
         Counter64,
      pr1645v2TTmplPiGreMCH2POutDropEx
         Counter64,
      pr1645v2TTmplPiGreMCH2POutDropNoArp
         Counter64,
      pr1645v2TTmplPiGreMCH2POutDropFilter
         Counter64,
      pr1645v2TTmplPiGreMCH2PIfOutBandwidth
         Integer32,
      pr1645v2TTmplPiGreMCH2PIfErrSec
         Counter32
      }

pr1645v2TTmplPiGreMCH2PTableIx OBJECT-TYPE
   SYNTAX      TableIndex
   MAX-ACCESS  not-accessible
   STATUS      current
   DESCRIPTION
      ""
   ::= {pr1645v2TTmplPiGreMCH2PEntry 11}

pr1645v2TTmplPiGreMCH2PSysUpTime OBJECT-TYPE
   SYNTAX      TimeTicks
   MAX-ACCESS  read-only
   STATUS      current
   DESCRIPTION
      "Path: tunnels.performance.ipsecGreTunnels.mibCounters.h2Performance.sysUpTime

       Time in centi-second."
   ::= {pr1645v2TTmplPiGreMCH2PEntry 16777216}

pr1645v2TTmplPiGreMCH2PIfUpTime OBJECT-TYPE
   SYNTAX      TimeTicks
   MAX-ACCESS  read-only
   STATUS      current
   DESCRIPTION
      "Path: tunnels.performance.ipsecGreTunnels.mibCounters.h2Performance.ifUpTime

       Time in centi-second."
   ::= {pr1645v2TTmplPiGreMCH2PEntry 33554432}

pr1645v2TTmplPiGreMCH2PIfStatChanges OBJECT-TYPE
   SYNTAX      Counter32
   MAX-ACCESS  read-only
   STATUS      current
   DESCRIPTION
      "Path: tunnels.performance.ipsecGreTunnels.mibCounters.h2Performance.ifStatusChanges

       32 bit unsigned wrappable counter."
   ::= {pr1645v2TTmplPiGreMCH2PEntry 50331648}

pr1645v2TTmplPiGreMCH2PIfInOctets OBJECT-TYPE
   SYNTAX      Counter64
   MAX-ACCESS  read-only
   STATUS      current
   DESCRIPTION
      "Path: tunnels.performance.ipsecGreTunnels.mibCounters.h2Performance.ifInOctets

       64 bit unsigned wrappable counter."
   ::= {pr1645v2TTmplPiGreMCH2PEntry 67108864}

pr1645v2TTmplPiGreMCH2PIfInUCPkts OBJECT-TYPE
   SYNTAX      Counter64
   MAX-ACCESS  read-only
   STATUS      current
   DESCRIPTION
      "Path: tunnels.performance.ipsecGreTunnels.mibCounters.h2Performance.ifInUcastPkts

       64 bit unsigned wrappable counter."
   ::= {pr1645v2TTmplPiGreMCH2PEntry 83886080}

pr1645v2TTmplPiGreMCH2PIfInNUCPkts OBJECT-TYPE
   SYNTAX      Counter64
   MAX-ACCESS  read-only
   STATUS      current
   DESCRIPTION
      "Path: tunnels.performance.ipsecGreTunnels.mibCounters.h2Performance.ifInNUcastPkts

       64 bit unsigned wrappable counter."
   ::= {pr1645v2TTmplPiGreMCH2PEntry 100663296}

pr1645v2TTmplPiGreMCH2PIfInBCPkts OBJECT-TYPE
   SYNTAX      Counter64
   MAX-ACCESS  read-only
   STATUS      current
   DESCRIPTION
      "Path: tunnels.performance.ipsecGreTunnels.mibCounters.h2Performance.ifInBcastPkts

       64 bit unsigned wrappable counter."
   ::= {pr1645v2TTmplPiGreMCH2PEntry 419430400}

pr1645v2TTmplPiGreMCH2PIfInMCPkts OBJECT-TYPE
   SYNTAX      Counter64
   MAX-ACCESS  read-only
   STATUS      current
   DESCRIPTION
      "Path: tunnels.performance.ipsecGreTunnels.mibCounters.h2Performance.ifInMcastPkts

       64 bit unsigned wrappable counter."
   ::= {pr1645v2TTmplPiGreMCH2PEntry 436207616}

pr1645v2TTmplPiGreMCH2PIfInDiscards OBJECT-TYPE
   SYNTAX      Counter64
   MAX-ACCESS  read-only
   STATUS      current
   DESCRIPTION
      "Path: tunnels.performance.ipsecGreTunnels.mibCounters.h2Performance.ifInDiscards

       64 bit unsigned wrappable counter."
   ::= {pr1645v2TTmplPiGreMCH2PEntry 117440512}

pr1645v2TTmplPiGreMCH2PIfInErrors OBJECT-TYPE
   SYNTAX      Counter64
   MAX-ACCESS  read-only
   STATUS      current
   DESCRIPTION
      "Path: tunnels.performance.ipsecGreTunnels.mibCounters.h2Performance.ifInErrors

       64 bit unsigned wrappable counter."
   ::= {pr1645v2TTmplPiGreMCH2PEntry 134217728}

pr1645v2TTmplPiGreMCH2PIfInUnkwn OBJECT-TYPE
   SYNTAX      Counter64
   MAX-ACCESS  read-only
   STATUS      current
   DESCRIPTION
      "Path: tunnels.performance.ipsecGreTunnels.mibCounters.h2Performance.ifInUnknownProtos

       64 bit unsigned wrappable counter."
   ::= {pr1645v2TTmplPiGreMCH2PEntry 150994944}

pr1645v2TTmplPiGreMCH2PInDropEx OBJECT-TYPE
   SYNTAX      Counter64
   MAX-ACCESS  read-only
   STATUS      current
   DESCRIPTION
      "Path: tunnels.performance.ipsecGreTunnels.mibCounters.h2Performance.ifInDropLevelExceeded

       64 bit unsigned wrappable counter."
   ::= {pr1645v2TTmplPiGreMCH2PEntry 335544320}

pr1645v2TTmplPiGreMCH2PInDropNoMac OBJECT-TYPE
   SYNTAX      Counter64
   MAX-ACCESS  read-only
   STATUS      current
   DESCRIPTION
      "Path: tunnels.performance.ipsecGreTunnels.mibCounters.h2Performance.fInDiscardsNoMacFit

       64 bit unsigned wrappable counter."
   ::= {pr1645v2TTmplPiGreMCH2PEntry 301989888}

pr1645v2TTmplPiGreMCH2PInDropNUCast OBJECT-TYPE
   SYNTAX      Counter64
   MAX-ACCESS  read-only
   STATUS      current
   DESCRIPTION
      "Path: tunnels.performance.ipsecGreTunnels.mibCounters.h2Performance.fInDiscardsNUCast

       64 bit unsigned wrappable counter."
   ::= {pr1645v2TTmplPiGreMCH2PEntry 318767104}

pr1645v2TTmplPiGreMCH2PInDropFilter OBJECT-TYPE
   SYNTAX      Counter64
   MAX-ACCESS  read-only
   STATUS      current
   DESCRIPTION
      "Path: tunnels.performance.ipsecGreTunnels.mibCounters.h2Performance.fInDiscardsFilter

       64 bit unsigned wrappable counter."
   ::= {pr1645v2TTmplPiGreMCH2PEntry 385875968}

pr1645v2TTmplPiGreMCH2PIfInBandwidth OBJECT-TYPE
   SYNTAX      Integer32
   MAX-ACCESS  read-only
   STATUS      current
   DESCRIPTION
      "Path: tunnels.performance.ipsecGreTunnels.mibCounters.h2Performance.ifInBandwidth

       unit name = bps
       formula = 8 * ; 8 /"
   ::= {pr1645v2TTmplPiGreMCH2PEntry 268435456}

pr1645v2TTmplPiGreMCH2PIfOutOctets OBJECT-TYPE
   SYNTAX      Counter64
   MAX-ACCESS  read-only
   STATUS      current
   DESCRIPTION
      "Path: tunnels.performance.ipsecGreTunnels.mibCounters.h2Performance.ifOutOctets

       64 bit unsigned wrappable counter."
   ::= {pr1645v2TTmplPiGreMCH2PEntry 167772160}

pr1645v2TTmplPiGreMCH2PIfOutUCPkts OBJECT-TYPE
   SYNTAX      Counter64
   MAX-ACCESS  read-only
   STATUS      current
   DESCRIPTION
      "Path: tunnels.performance.ipsecGreTunnels.mibCounters.h2Performance.ifOutUcastPkts

       64 bit unsigned wrappable counter."
   ::= {pr1645v2TTmplPiGreMCH2PEntry 184549376}

pr1645v2TTmplPiGreMCH2PIfOutNUCPkts OBJECT-TYPE
   SYNTAX      Counter64
   MAX-ACCESS  read-only
   STATUS      current
   DESCRIPTION
      "Path: tunnels.performance.ipsecGreTunnels.mibCounters.h2Performance.ifOutNUcastPkts

       64 bit unsigned wrappable counter."
   ::= {pr1645v2TTmplPiGreMCH2PEntry 201326592}

pr1645v2TTmplPiGreMCH2PIfOutBCPkts OBJECT-TYPE
   SYNTAX      Counter64
   MAX-ACCESS  read-only
   STATUS      current
   DESCRIPTION
      "Path: tunnels.performance.ipsecGreTunnels.mibCounters.h2Performance.ifOutBcastPkts

       64 bit unsigned wrappable counter."
   ::= {pr1645v2TTmplPiGreMCH2PEntry 452984832}

pr1645v2TTmplPiGreMCH2PIfOutMCPkts OBJECT-TYPE
   SYNTAX      Counter64
   MAX-ACCESS  read-only
   STATUS      current
   DESCRIPTION
      "Path: tunnels.performance.ipsecGreTunnels.mibCounters.h2Performance.ifOutMcastPkts

       64 bit unsigned wrappable counter."
   ::= {pr1645v2TTmplPiGreMCH2PEntry 469762048}

pr1645v2TTmplPiGreMCH2PIfOutDiscards OBJECT-TYPE
   SYNTAX      Counter64
   MAX-ACCESS  read-only
   STATUS      current
   DESCRIPTION
      "Path: tunnels.performance.ipsecGreTunnels.mibCounters.h2Performance.ifOutDiscards

       64 bit unsigned wrappable counter."
   ::= {pr1645v2TTmplPiGreMCH2PEntry 218103808}

pr1645v2TTmplPiGreMCH2PIfOutErrors OBJECT-TYPE
   SYNTAX      Counter64
   MAX-ACCESS  read-only
   STATUS      current
   DESCRIPTION
      "Path: tunnels.performance.ipsecGreTunnels.mibCounters.h2Performance.ifOutErrors

       64 bit unsigned wrappable counter."
   ::= {pr1645v2TTmplPiGreMCH2PEntry 234881024}

pr1645v2TTmplPiGreMCH2POutDropEx OBJECT-TYPE
   SYNTAX      Counter64
   MAX-ACCESS  read-only
   STATUS      current
   DESCRIPTION
      "Path: tunnels.performance.ipsecGreTunnels.mibCounters.h2Performance.ifOutDropLevelExceeded

       64 bit unsigned wrappable counter."
   ::= {pr1645v2TTmplPiGreMCH2PEntry 352321536}

pr1645v2TTmplPiGreMCH2POutDropNoArp OBJECT-TYPE
   SYNTAX      Counter64
   MAX-ACCESS  read-only
   STATUS      current
   DESCRIPTION
      "Path: tunnels.performance.ipsecGreTunnels.mibCounters.h2Performance.ifOutDiscardsNoArp

       64 bit unsigned wrappable counter."
   ::= {pr1645v2TTmplPiGreMCH2PEntry 369098752}

pr1645v2TTmplPiGreMCH2POutDropFilter OBJECT-TYPE
   SYNTAX      Counter64
   MAX-ACCESS  read-only
   STATUS      current
   DESCRIPTION
      "Path: tunnels.performance.ipsecGreTunnels.mibCounters.h2Performance.ifOutDiscardsFilter

       64 bit unsigned wrappable counter."
   ::= {pr1645v2TTmplPiGreMCH2PEntry 402653184}

pr1645v2TTmplPiGreMCH2PIfOutBandwidth OBJECT-TYPE
   SYNTAX      Integer32
   MAX-ACCESS  read-only
   STATUS      current
   DESCRIPTION
      "Path: tunnels.performance.ipsecGreTunnels.mibCounters.h2Performance.ifOutBandwidth

       unit name = bps
       formula = 8 * ; 8 /"
   ::= {pr1645v2TTmplPiGreMCH2PEntry 285212672}

pr1645v2TTmplPiGreMCH2PIfErrSec OBJECT-TYPE
   SYNTAX      Counter32
   MAX-ACCESS  read-only
   STATUS      current
   DESCRIPTION
      "Path: tunnels.performance.ipsecGreTunnels.mibCounters.h2Performance.ifErrSec

       32 bit unsigned wrappable counter."
   ::= {pr1645v2TTmplPiGreMCH2PEntry 251658240}

pr1645v2TTmplPiGreMCH24P OBJECT-TYPE
   SYNTAX      SEQUENCE OF Pr1645v2TTmplPiGreMCH24PEntry
   MAX-ACCESS  not-accessible
   STATUS      current
   DESCRIPTION
      ""
   ::= {pr1645v2TTmplPiGre 41615360}

pr1645v2TTmplPiGreMCH24PEntry OBJECT-TYPE
   SYNTAX      Pr1645v2TTmplPiGreMCH24PEntry
   MAX-ACCESS  not-accessible
   STATUS      current
   DESCRIPTION
      ""
   INDEX      { pr1645v2TTmplPiGreTableIx,
                pr1645v2TTmplPiGreMCH24PTableIx }
   ::= {pr1645v2TTmplPiGreMCH24P 1}

Pr1645v2TTmplPiGreMCH24PEntry ::=
   SEQUENCE
      {
      pr1645v2TTmplPiGreMCH24PTableIx
         TableIndex,
      pr1645v2TTmplPiGreMCH24PSysUpTime
         TimeTicks,
      pr1645v2TTmplPiGreMCH24PIfUpTime
         TimeTicks,
      pr1645v2TTmplPiGreMCH24PIfStatChanges
         Counter32,
      pr1645v2TTmplPiGreMCH24PIfInOctets
         Counter64,
      pr1645v2TTmplPiGreMCH24PIfInUCPkts
         Counter64,
      pr1645v2TTmplPiGreMCH24PIfInNUCPkts
         Counter64,
      pr1645v2TTmplPiGreMCH24PIfInBCPkts
         Counter64,
      pr1645v2TTmplPiGreMCH24PIfInMCPkts
         Counter64,
      pr1645v2TTmplPiGreMCH24PIfInDiscards
         Counter64,
      pr1645v2TTmplPiGreMCH24PIfInErrors
         Counter64,
      pr1645v2TTmplPiGreMCH24PIfInUnkwn
         Counter64,
      pr1645v2TTmplPiGreMCH24PInDropEx
         Counter64,
      pr1645v2TTmplPiGreMCH24PInDropNoMac
         Counter64,
      pr1645v2TTmplPiGreMCH24PInDropNUCast
         Counter64,
      pr1645v2TTmplPiGreMCH24PInDropFilter
         Counter64,
      pr1645v2TTmplPiGreMCH24PIfInBandwidth
         Integer32,
      pr1645v2TTmplPiGreMCH24PIfOutOctets
         Counter64,
      pr1645v2TTmplPiGreMCH24PIfOutUCPkts
         Counter64,
      pr1645v2TTmplPiGreMCH24PIfOutNUCPkts
         Counter64,
      pr1645v2TTmplPiGreMCH24PIfOutBCPkts
         Counter64,
      pr1645v2TTmplPiGreMCH24PIfOutMCPkts
         Counter64,
      pr1645v2TTmplPiGreMCH24PIfOutDiscards
         Counter64,
      pr1645v2TTmplPiGreMCH24PIfOutErrors
         Counter64,
      pr1645v2TTmplPiGreMCH24POutDropEx
         Counter64,
      pr1645v2TTmplPiGreMCH24POutDropNoArp
         Counter64,
      pr1645v2TTmplPiGreMCH24POutDropFilter
         Counter64,
      pr1645v2TTmplPiGreMCH24PIfOutBandwidth
         Integer32,
      pr1645v2TTmplPiGreMCH24PIfErrSec
         Counter32
      }

pr1645v2TTmplPiGreMCH24PTableIx OBJECT-TYPE
   SYNTAX      TableIndex
   MAX-ACCESS  not-accessible
   STATUS      current
   DESCRIPTION
      ""
   ::= {pr1645v2TTmplPiGreMCH24PEntry 11}

pr1645v2TTmplPiGreMCH24PSysUpTime OBJECT-TYPE
   SYNTAX      TimeTicks
   MAX-ACCESS  read-only
   STATUS      current
   DESCRIPTION
      "Path: tunnels.performance.ipsecGreTunnels.mibCounters.h24Performance.sysUpTime

       Time in centi-second."
   ::= {pr1645v2TTmplPiGreMCH24PEntry 16777216}

pr1645v2TTmplPiGreMCH24PIfUpTime OBJECT-TYPE
   SYNTAX      TimeTicks
   MAX-ACCESS  read-only
   STATUS      current
   DESCRIPTION
      "Path: tunnels.performance.ipsecGreTunnels.mibCounters.h24Performance.ifUpTime

       Time in centi-second."
   ::= {pr1645v2TTmplPiGreMCH24PEntry 33554432}

pr1645v2TTmplPiGreMCH24PIfStatChanges OBJECT-TYPE
   SYNTAX      Counter32
   MAX-ACCESS  read-only
   STATUS      current
   DESCRIPTION
      "Path: tunnels.performance.ipsecGreTunnels.mibCounters.h24Performance.ifStatusChanges

       32 bit unsigned wrappable counter."
   ::= {pr1645v2TTmplPiGreMCH24PEntry 50331648}

pr1645v2TTmplPiGreMCH24PIfInOctets OBJECT-TYPE
   SYNTAX      Counter64
   MAX-ACCESS  read-only
   STATUS      current
   DESCRIPTION
      "Path: tunnels.performance.ipsecGreTunnels.mibCounters.h24Performance.ifInOctets

       64 bit unsigned wrappable counter."
   ::= {pr1645v2TTmplPiGreMCH24PEntry 67108864}

pr1645v2TTmplPiGreMCH24PIfInUCPkts OBJECT-TYPE
   SYNTAX      Counter64
   MAX-ACCESS  read-only
   STATUS      current
   DESCRIPTION
      "Path: tunnels.performance.ipsecGreTunnels.mibCounters.h24Performance.ifInUcastPkts

       64 bit unsigned wrappable counter."
   ::= {pr1645v2TTmplPiGreMCH24PEntry 83886080}

pr1645v2TTmplPiGreMCH24PIfInNUCPkts OBJECT-TYPE
   SYNTAX      Counter64
   MAX-ACCESS  read-only
   STATUS      current
   DESCRIPTION
      "Path: tunnels.performance.ipsecGreTunnels.mibCounters.h24Performance.ifInNUcastPkts

       64 bit unsigned wrappable counter."
   ::= {pr1645v2TTmplPiGreMCH24PEntry 100663296}

pr1645v2TTmplPiGreMCH24PIfInBCPkts OBJECT-TYPE
   SYNTAX      Counter64
   MAX-ACCESS  read-only
   STATUS      current
   DESCRIPTION
      "Path: tunnels.performance.ipsecGreTunnels.mibCounters.h24Performance.ifInBcastPkts

       64 bit unsigned wrappable counter."
   ::= {pr1645v2TTmplPiGreMCH24PEntry 419430400}

pr1645v2TTmplPiGreMCH24PIfInMCPkts OBJECT-TYPE
   SYNTAX      Counter64
   MAX-ACCESS  read-only
   STATUS      current
   DESCRIPTION
      "Path: tunnels.performance.ipsecGreTunnels.mibCounters.h24Performance.ifInMcastPkts

       64 bit unsigned wrappable counter."
   ::= {pr1645v2TTmplPiGreMCH24PEntry 436207616}

pr1645v2TTmplPiGreMCH24PIfInDiscards OBJECT-TYPE
   SYNTAX      Counter64
   MAX-ACCESS  read-only
   STATUS      current
   DESCRIPTION
      "Path: tunnels.performance.ipsecGreTunnels.mibCounters.h24Performance.ifInDiscards

       64 bit unsigned wrappable counter."
   ::= {pr1645v2TTmplPiGreMCH24PEntry 117440512}

pr1645v2TTmplPiGreMCH24PIfInErrors OBJECT-TYPE
   SYNTAX      Counter64
   MAX-ACCESS  read-only
   STATUS      current
   DESCRIPTION
      "Path: tunnels.performance.ipsecGreTunnels.mibCounters.h24Performance.ifInErrors

       64 bit unsigned wrappable counter."
   ::= {pr1645v2TTmplPiGreMCH24PEntry 134217728}

pr1645v2TTmplPiGreMCH24PIfInUnkwn OBJECT-TYPE
   SYNTAX      Counter64
   MAX-ACCESS  read-only
   STATUS      current
   DESCRIPTION
      "Path: tunnels.performance.ipsecGreTunnels.mibCounters.h24Performance.ifInUnknownProtos

       64 bit unsigned wrappable counter."
   ::= {pr1645v2TTmplPiGreMCH24PEntry 150994944}

pr1645v2TTmplPiGreMCH24PInDropEx OBJECT-TYPE
   SYNTAX      Counter64
   MAX-ACCESS  read-only
   STATUS      current
   DESCRIPTION
      "Path: tunnels.performance.ipsecGreTunnels.mibCounters.h24Performance.ifInDropLevelExceeded

       64 bit unsigned wrappable counter."
   ::= {pr1645v2TTmplPiGreMCH24PEntry 335544320}

pr1645v2TTmplPiGreMCH24PInDropNoMac OBJECT-TYPE
   SYNTAX      Counter64
   MAX-ACCESS  read-only
   STATUS      current
   DESCRIPTION
      "Path: tunnels.performance.ipsecGreTunnels.mibCounters.h24Performance.fInDiscardsNoMacFit

       64 bit unsigned wrappable counter."
   ::= {pr1645v2TTmplPiGreMCH24PEntry 301989888}

pr1645v2TTmplPiGreMCH24PInDropNUCast OBJECT-TYPE
   SYNTAX      Counter64
   MAX-ACCESS  read-only
   STATUS      current
   DESCRIPTION
      "Path: tunnels.performance.ipsecGreTunnels.mibCounters.h24Performance.fInDiscardsNUCast

       64 bit unsigned wrappable counter."
   ::= {pr1645v2TTmplPiGreMCH24PEntry 318767104}

pr1645v2TTmplPiGreMCH24PInDropFilter OBJECT-TYPE
   SYNTAX      Counter64
   MAX-ACCESS  read-only
   STATUS      current
   DESCRIPTION
      "Path: tunnels.performance.ipsecGreTunnels.mibCounters.h24Performance.fInDiscardsFilter

       64 bit unsigned wrappable counter."
   ::= {pr1645v2TTmplPiGreMCH24PEntry 385875968}

pr1645v2TTmplPiGreMCH24PIfInBandwidth OBJECT-TYPE
   SYNTAX      Integer32
   MAX-ACCESS  read-only
   STATUS      current
   DESCRIPTION
      "Path: tunnels.performance.ipsecGreTunnels.mibCounters.h24Performance.ifInBandwidth

       unit name = bps
       formula = 8 * ; 8 /"
   ::= {pr1645v2TTmplPiGreMCH24PEntry 268435456}

pr1645v2TTmplPiGreMCH24PIfOutOctets OBJECT-TYPE
   SYNTAX      Counter64
   MAX-ACCESS  read-only
   STATUS      current
   DESCRIPTION
      "Path: tunnels.performance.ipsecGreTunnels.mibCounters.h24Performance.ifOutOctets

       64 bit unsigned wrappable counter."
   ::= {pr1645v2TTmplPiGreMCH24PEntry 167772160}

pr1645v2TTmplPiGreMCH24PIfOutUCPkts OBJECT-TYPE
   SYNTAX      Counter64
   MAX-ACCESS  read-only
   STATUS      current
   DESCRIPTION
      "Path: tunnels.performance.ipsecGreTunnels.mibCounters.h24Performance.ifOutUcastPkts

       64 bit unsigned wrappable counter."
   ::= {pr1645v2TTmplPiGreMCH24PEntry 184549376}

pr1645v2TTmplPiGreMCH24PIfOutNUCPkts OBJECT-TYPE
   SYNTAX      Counter64
   MAX-ACCESS  read-only
   STATUS      current
   DESCRIPTION
      "Path: tunnels.performance.ipsecGreTunnels.mibCounters.h24Performance.ifOutNUcastPkts

       64 bit unsigned wrappable counter."
   ::= {pr1645v2TTmplPiGreMCH24PEntry 201326592}

pr1645v2TTmplPiGreMCH24PIfOutBCPkts OBJECT-TYPE
   SYNTAX      Counter64
   MAX-ACCESS  read-only
   STATUS      current
   DESCRIPTION
      "Path: tunnels.performance.ipsecGreTunnels.mibCounters.h24Performance.ifOutBcastPkts

       64 bit unsigned wrappable counter."
   ::= {pr1645v2TTmplPiGreMCH24PEntry 452984832}

pr1645v2TTmplPiGreMCH24PIfOutMCPkts OBJECT-TYPE
   SYNTAX      Counter64
   MAX-ACCESS  read-only
   STATUS      current
   DESCRIPTION
      "Path: tunnels.performance.ipsecGreTunnels.mibCounters.h24Performance.ifOutMcastPkts

       64 bit unsigned wrappable counter."
   ::= {pr1645v2TTmplPiGreMCH24PEntry 469762048}

pr1645v2TTmplPiGreMCH24PIfOutDiscards OBJECT-TYPE
   SYNTAX      Counter64
   MAX-ACCESS  read-only
   STATUS      current
   DESCRIPTION
      "Path: tunnels.performance.ipsecGreTunnels.mibCounters.h24Performance.ifOutDiscards

       64 bit unsigned wrappable counter."
   ::= {pr1645v2TTmplPiGreMCH24PEntry 218103808}

pr1645v2TTmplPiGreMCH24PIfOutErrors OBJECT-TYPE
   SYNTAX      Counter64
   MAX-ACCESS  read-only
   STATUS      current
   DESCRIPTION
      "Path: tunnels.performance.ipsecGreTunnels.mibCounters.h24Performance.ifOutErrors

       64 bit unsigned wrappable counter."
   ::= {pr1645v2TTmplPiGreMCH24PEntry 234881024}

pr1645v2TTmplPiGreMCH24POutDropEx OBJECT-TYPE
   SYNTAX      Counter64
   MAX-ACCESS  read-only
   STATUS      current
   DESCRIPTION
      "Path: tunnels.performance.ipsecGreTunnels.mibCounters.h24Performance.ifOutDropLevelExceeded

       64 bit unsigned wrappable counter."
   ::= {pr1645v2TTmplPiGreMCH24PEntry 352321536}

pr1645v2TTmplPiGreMCH24POutDropNoArp OBJECT-TYPE
   SYNTAX      Counter64
   MAX-ACCESS  read-only
   STATUS      current
   DESCRIPTION
      "Path: tunnels.performance.ipsecGreTunnels.mibCounters.h24Performance.ifOutDiscardsNoArp

       64 bit unsigned wrappable counter."
   ::= {pr1645v2TTmplPiGreMCH24PEntry 369098752}

pr1645v2TTmplPiGreMCH24POutDropFilter OBJECT-TYPE
   SYNTAX      Counter64
   MAX-ACCESS  read-only
   STATUS      current
   DESCRIPTION
      "Path: tunnels.performance.ipsecGreTunnels.mibCounters.h24Performance.ifOutDiscardsFilter

       64 bit unsigned wrappable counter."
   ::= {pr1645v2TTmplPiGreMCH24PEntry 402653184}

pr1645v2TTmplPiGreMCH24PIfOutBandwidth OBJECT-TYPE
   SYNTAX      Integer32
   MAX-ACCESS  read-only
   STATUS      current
   DESCRIPTION
      "Path: tunnels.performance.ipsecGreTunnels.mibCounters.h24Performance.ifOutBandwidth

       unit name = bps
       formula = 8 * ; 8 /"
   ::= {pr1645v2TTmplPiGreMCH24PEntry 285212672}

pr1645v2TTmplPiGreMCH24PIfErrSec OBJECT-TYPE
   SYNTAX      Counter32
   MAX-ACCESS  read-only
   STATUS      current
   DESCRIPTION
      "Path: tunnels.performance.ipsecGreTunnels.mibCounters.h24Performance.ifErrSec

       32 bit unsigned wrappable counter."
   ::= {pr1645v2TTmplPiGreMCH24PEntry 251658240}

pr1645v2TTmplPiGreMCD7P OBJECT-TYPE
   SYNTAX      SEQUENCE OF Pr1645v2TTmplPiGreMCD7PEntry
   MAX-ACCESS  not-accessible
   STATUS      current
   DESCRIPTION
      ""
   ::= {pr1645v2TTmplPiGre 41680896}

pr1645v2TTmplPiGreMCD7PEntry OBJECT-TYPE
   SYNTAX      Pr1645v2TTmplPiGreMCD7PEntry
   MAX-ACCESS  not-accessible
   STATUS      current
   DESCRIPTION
      ""
   INDEX      { pr1645v2TTmplPiGreTableIx,
                pr1645v2TTmplPiGreMCD7PTableIx }
   ::= {pr1645v2TTmplPiGreMCD7P 1}

Pr1645v2TTmplPiGreMCD7PEntry ::=
   SEQUENCE
      {
      pr1645v2TTmplPiGreMCD7PTableIx
         TableIndex,
      pr1645v2TTmplPiGreMCD7PSysUpTime
         TimeTicks,
      pr1645v2TTmplPiGreMCD7PIfUpTime
         TimeTicks,
      pr1645v2TTmplPiGreMCD7PIfStatChanges
         Counter32,
      pr1645v2TTmplPiGreMCD7PIfInOctets
         Counter64,
      pr1645v2TTmplPiGreMCD7PIfInUCPkts
         Counter64,
      pr1645v2TTmplPiGreMCD7PIfInNUCPkts
         Counter64,
      pr1645v2TTmplPiGreMCD7PIfInBCPkts
         Counter64,
      pr1645v2TTmplPiGreMCD7PIfInMCPkts
         Counter64,
      pr1645v2TTmplPiGreMCD7PIfInDiscards
         Counter64,
      pr1645v2TTmplPiGreMCD7PIfInErrors
         Counter64,
      pr1645v2TTmplPiGreMCD7PIfInUnkwn
         Counter64,
      pr1645v2TTmplPiGreMCD7PInDropEx
         Counter64,
      pr1645v2TTmplPiGreMCD7PInDropNoMac
         Counter64,
      pr1645v2TTmplPiGreMCD7PInDropNUCast
         Counter64,
      pr1645v2TTmplPiGreMCD7PInDropFilter
         Counter64,
      pr1645v2TTmplPiGreMCD7PIfInBandwidth
         Integer32,
      pr1645v2TTmplPiGreMCD7PIfOutOctets
         Counter64,
      pr1645v2TTmplPiGreMCD7PIfOutUCPkts
         Counter64,
      pr1645v2TTmplPiGreMCD7PIfOutNUCPkts
         Counter64,
      pr1645v2TTmplPiGreMCD7PIfOutBCPkts
         Counter64,
      pr1645v2TTmplPiGreMCD7PIfOutMCPkts
         Counter64,
      pr1645v2TTmplPiGreMCD7PIfOutDiscards
         Counter64,
      pr1645v2TTmplPiGreMCD7PIfOutErrors
         Counter64,
      pr1645v2TTmplPiGreMCD7POutDropEx
         Counter64,
      pr1645v2TTmplPiGreMCD7POutDropNoArp
         Counter64,
      pr1645v2TTmplPiGreMCD7POutDropFilter
         Counter64,
      pr1645v2TTmplPiGreMCD7PIfOutBandwidth
         Integer32,
      pr1645v2TTmplPiGreMCD7PIfErrSec
         Counter32
      }

pr1645v2TTmplPiGreMCD7PTableIx OBJECT-TYPE
   SYNTAX      TableIndex
   MAX-ACCESS  not-accessible
   STATUS      current
   DESCRIPTION
      ""
   ::= {pr1645v2TTmplPiGreMCD7PEntry 11}

pr1645v2TTmplPiGreMCD7PSysUpTime OBJECT-TYPE
   SYNTAX      TimeTicks
   MAX-ACCESS  read-only
   STATUS      current
   DESCRIPTION
      "Path: tunnels.performance.ipsecGreTunnels.mibCounters.d7Performance.sysUpTime

       Time in centi-second."
   ::= {pr1645v2TTmplPiGreMCD7PEntry 16777216}

pr1645v2TTmplPiGreMCD7PIfUpTime OBJECT-TYPE
   SYNTAX      TimeTicks
   MAX-ACCESS  read-only
   STATUS      current
   DESCRIPTION
      "Path: tunnels.performance.ipsecGreTunnels.mibCounters.d7Performance.ifUpTime

       Time in centi-second."
   ::= {pr1645v2TTmplPiGreMCD7PEntry 33554432}

pr1645v2TTmplPiGreMCD7PIfStatChanges OBJECT-TYPE
   SYNTAX      Counter32
   MAX-ACCESS  read-only
   STATUS      current
   DESCRIPTION
      "Path: tunnels.performance.ipsecGreTunnels.mibCounters.d7Performance.ifStatusChanges

       32 bit unsigned wrappable counter."
   ::= {pr1645v2TTmplPiGreMCD7PEntry 50331648}

pr1645v2TTmplPiGreMCD7PIfInOctets OBJECT-TYPE
   SYNTAX      Counter64
   MAX-ACCESS  read-only
   STATUS      current
   DESCRIPTION
      "Path: tunnels.performance.ipsecGreTunnels.mibCounters.d7Performance.ifInOctets

       64 bit unsigned wrappable counter."
   ::= {pr1645v2TTmplPiGreMCD7PEntry 67108864}

pr1645v2TTmplPiGreMCD7PIfInUCPkts OBJECT-TYPE
   SYNTAX      Counter64
   MAX-ACCESS  read-only
   STATUS      current
   DESCRIPTION
      "Path: tunnels.performance.ipsecGreTunnels.mibCounters.d7Performance.ifInUcastPkts

       64 bit unsigned wrappable counter."
   ::= {pr1645v2TTmplPiGreMCD7PEntry 83886080}

pr1645v2TTmplPiGreMCD7PIfInNUCPkts OBJECT-TYPE
   SYNTAX      Counter64
   MAX-ACCESS  read-only
   STATUS      current
   DESCRIPTION
      "Path: tunnels.performance.ipsecGreTunnels.mibCounters.d7Performance.ifInNUcastPkts

       64 bit unsigned wrappable counter."
   ::= {pr1645v2TTmplPiGreMCD7PEntry 100663296}

pr1645v2TTmplPiGreMCD7PIfInBCPkts OBJECT-TYPE
   SYNTAX      Counter64
   MAX-ACCESS  read-only
   STATUS      current
   DESCRIPTION
      "Path: tunnels.performance.ipsecGreTunnels.mibCounters.d7Performance.ifInBcastPkts

       64 bit unsigned wrappable counter."
   ::= {pr1645v2TTmplPiGreMCD7PEntry 419430400}

pr1645v2TTmplPiGreMCD7PIfInMCPkts OBJECT-TYPE
   SYNTAX      Counter64
   MAX-ACCESS  read-only
   STATUS      current
   DESCRIPTION
      "Path: tunnels.performance.ipsecGreTunnels.mibCounters.d7Performance.ifInMcastPkts

       64 bit unsigned wrappable counter."
   ::= {pr1645v2TTmplPiGreMCD7PEntry 436207616}

pr1645v2TTmplPiGreMCD7PIfInDiscards OBJECT-TYPE
   SYNTAX      Counter64
   MAX-ACCESS  read-only
   STATUS      current
   DESCRIPTION
      "Path: tunnels.performance.ipsecGreTunnels.mibCounters.d7Performance.ifInDiscards

       64 bit unsigned wrappable counter."
   ::= {pr1645v2TTmplPiGreMCD7PEntry 117440512}

pr1645v2TTmplPiGreMCD7PIfInErrors OBJECT-TYPE
   SYNTAX      Counter64
   MAX-ACCESS  read-only
   STATUS      current
   DESCRIPTION
      "Path: tunnels.performance.ipsecGreTunnels.mibCounters.d7Performance.ifInErrors

       64 bit unsigned wrappable counter."
   ::= {pr1645v2TTmplPiGreMCD7PEntry 134217728}

pr1645v2TTmplPiGreMCD7PIfInUnkwn OBJECT-TYPE
   SYNTAX      Counter64
   MAX-ACCESS  read-only
   STATUS      current
   DESCRIPTION
      "Path: tunnels.performance.ipsecGreTunnels.mibCounters.d7Performance.ifInUnknownProtos

       64 bit unsigned wrappable counter."
   ::= {pr1645v2TTmplPiGreMCD7PEntry 150994944}

pr1645v2TTmplPiGreMCD7PInDropEx OBJECT-TYPE
   SYNTAX      Counter64
   MAX-ACCESS  read-only
   STATUS      current
   DESCRIPTION
      "Path: tunnels.performance.ipsecGreTunnels.mibCounters.d7Performance.ifInDropLevelExceeded

       64 bit unsigned wrappable counter."
   ::= {pr1645v2TTmplPiGreMCD7PEntry 335544320}

pr1645v2TTmplPiGreMCD7PInDropNoMac OBJECT-TYPE
   SYNTAX      Counter64
   MAX-ACCESS  read-only
   STATUS      current
   DESCRIPTION
      "Path: tunnels.performance.ipsecGreTunnels.mibCounters.d7Performance.fInDiscardsNoMacFit

       64 bit unsigned wrappable counter."
   ::= {pr1645v2TTmplPiGreMCD7PEntry 301989888}

pr1645v2TTmplPiGreMCD7PInDropNUCast OBJECT-TYPE
   SYNTAX      Counter64
   MAX-ACCESS  read-only
   STATUS      current
   DESCRIPTION
      "Path: tunnels.performance.ipsecGreTunnels.mibCounters.d7Performance.fInDiscardsNUCast

       64 bit unsigned wrappable counter."
   ::= {pr1645v2TTmplPiGreMCD7PEntry 318767104}

pr1645v2TTmplPiGreMCD7PInDropFilter OBJECT-TYPE
   SYNTAX      Counter64
   MAX-ACCESS  read-only
   STATUS      current
   DESCRIPTION
      "Path: tunnels.performance.ipsecGreTunnels.mibCounters.d7Performance.fInDiscardsFilter

       64 bit unsigned wrappable counter."
   ::= {pr1645v2TTmplPiGreMCD7PEntry 385875968}

pr1645v2TTmplPiGreMCD7PIfInBandwidth OBJECT-TYPE
   SYNTAX      Integer32
   MAX-ACCESS  read-only
   STATUS      current
   DESCRIPTION
      "Path: tunnels.performance.ipsecGreTunnels.mibCounters.d7Performance.ifInBandwidth

       unit name = bps
       formula = 8 * ; 8 /"
   ::= {pr1645v2TTmplPiGreMCD7PEntry 268435456}

pr1645v2TTmplPiGreMCD7PIfOutOctets OBJECT-TYPE
   SYNTAX      Counter64
   MAX-ACCESS  read-only
   STATUS      current
   DESCRIPTION
      "Path: tunnels.performance.ipsecGreTunnels.mibCounters.d7Performance.ifOutOctets

       64 bit unsigned wrappable counter."
   ::= {pr1645v2TTmplPiGreMCD7PEntry 167772160}

pr1645v2TTmplPiGreMCD7PIfOutUCPkts OBJECT-TYPE
   SYNTAX      Counter64
   MAX-ACCESS  read-only
   STATUS      current
   DESCRIPTION
      "Path: tunnels.performance.ipsecGreTunnels.mibCounters.d7Performance.ifOutUcastPkts

       64 bit unsigned wrappable counter."
   ::= {pr1645v2TTmplPiGreMCD7PEntry 184549376}

pr1645v2TTmplPiGreMCD7PIfOutNUCPkts OBJECT-TYPE
   SYNTAX      Counter64
   MAX-ACCESS  read-only
   STATUS      current
   DESCRIPTION
      "Path: tunnels.performance.ipsecGreTunnels.mibCounters.d7Performance.ifOutNUcastPkts

       64 bit unsigned wrappable counter."
   ::= {pr1645v2TTmplPiGreMCD7PEntry 201326592}

pr1645v2TTmplPiGreMCD7PIfOutBCPkts OBJECT-TYPE
   SYNTAX      Counter64
   MAX-ACCESS  read-only
   STATUS      current
   DESCRIPTION
      "Path: tunnels.performance.ipsecGreTunnels.mibCounters.d7Performance.ifOutBcastPkts

       64 bit unsigned wrappable counter."
   ::= {pr1645v2TTmplPiGreMCD7PEntry 452984832}

pr1645v2TTmplPiGreMCD7PIfOutMCPkts OBJECT-TYPE
   SYNTAX      Counter64
   MAX-ACCESS  read-only
   STATUS      current
   DESCRIPTION
      "Path: tunnels.performance.ipsecGreTunnels.mibCounters.d7Performance.ifOutMcastPkts

       64 bit unsigned wrappable counter."
   ::= {pr1645v2TTmplPiGreMCD7PEntry 469762048}

pr1645v2TTmplPiGreMCD7PIfOutDiscards OBJECT-TYPE
   SYNTAX      Counter64
   MAX-ACCESS  read-only
   STATUS      current
   DESCRIPTION
      "Path: tunnels.performance.ipsecGreTunnels.mibCounters.d7Performance.ifOutDiscards

       64 bit unsigned wrappable counter."
   ::= {pr1645v2TTmplPiGreMCD7PEntry 218103808}

pr1645v2TTmplPiGreMCD7PIfOutErrors OBJECT-TYPE
   SYNTAX      Counter64
   MAX-ACCESS  read-only
   STATUS      current
   DESCRIPTION
      "Path: tunnels.performance.ipsecGreTunnels.mibCounters.d7Performance.ifOutErrors

       64 bit unsigned wrappable counter."
   ::= {pr1645v2TTmplPiGreMCD7PEntry 234881024}

pr1645v2TTmplPiGreMCD7POutDropEx OBJECT-TYPE
   SYNTAX      Counter64
   MAX-ACCESS  read-only
   STATUS      current
   DESCRIPTION
      "Path: tunnels.performance.ipsecGreTunnels.mibCounters.d7Performance.ifOutDropLevelExceeded

       64 bit unsigned wrappable counter."
   ::= {pr1645v2TTmplPiGreMCD7PEntry 352321536}

pr1645v2TTmplPiGreMCD7POutDropNoArp OBJECT-TYPE
   SYNTAX      Counter64
   MAX-ACCESS  read-only
   STATUS      current
   DESCRIPTION
      "Path: tunnels.performance.ipsecGreTunnels.mibCounters.d7Performance.ifOutDiscardsNoArp

       64 bit unsigned wrappable counter."
   ::= {pr1645v2TTmplPiGreMCD7PEntry 369098752}

pr1645v2TTmplPiGreMCD7POutDropFilter OBJECT-TYPE
   SYNTAX      Counter64
   MAX-ACCESS  read-only
   STATUS      current
   DESCRIPTION
      "Path: tunnels.performance.ipsecGreTunnels.mibCounters.d7Performance.ifOutDiscardsFilter

       64 bit unsigned wrappable counter."
   ::= {pr1645v2TTmplPiGreMCD7PEntry 402653184}

pr1645v2TTmplPiGreMCD7PIfOutBandwidth OBJECT-TYPE
   SYNTAX      Integer32
   MAX-ACCESS  read-only
   STATUS      current
   DESCRIPTION
      "Path: tunnels.performance.ipsecGreTunnels.mibCounters.d7Performance.ifOutBandwidth

       unit name = bps
       formula = 8 * ; 8 /"
   ::= {pr1645v2TTmplPiGreMCD7PEntry 285212672}

pr1645v2TTmplPiGreMCD7PIfErrSec OBJECT-TYPE
   SYNTAX      Counter32
   MAX-ACCESS  read-only
   STATUS      current
   DESCRIPTION
      "Path: tunnels.performance.ipsecGreTunnels.mibCounters.d7Performance.ifErrSec

       32 bit unsigned wrappable counter."
   ::= {pr1645v2TTmplPiGreMCD7PEntry 251658240}

pr1645v2TTmplPiGreInPQs OBJECT-TYPE
   SYNTAX      SEQUENCE OF Pr1645v2TTmplPiGreInPQsEntry
   MAX-ACCESS  not-accessible
   STATUS      current
   DESCRIPTION
      ""
   ::= {pr1645v2TTmplPiGre 100663296}

pr1645v2TTmplPiGreInPQsEntry OBJECT-TYPE
   SYNTAX      Pr1645v2TTmplPiGreInPQsEntry
   MAX-ACCESS  not-accessible
   STATUS      current
   DESCRIPTION
      ""
   INDEX      { pr1645v2TTmplPiGreTableIx,
                pr1645v2TTmplPiGreInPQsTableIx }
   ::= {pr1645v2TTmplPiGreInPQs 1}

Pr1645v2TTmplPiGreInPQsEntry ::=
   SEQUENCE
      {
      pr1645v2TTmplPiGreInPQsTableIx
         TableIndex,
      pr1645v2TTmplPiGreInPQsName
         INTEGER,
      pr1645v2TTmplPiGreInPQsLength
         Integer32,
      pr1645v2TTmplPiGreInPQsOctetLength
         Integer32,
      pr1645v2TTmplPiGreInPQsRedLength
         Integer32,
      pr1645v2TTmplPiGreInPQsPacketsTotal
         Counter64,
      pr1645v2TTmplPiGreInPQsPacketsDirectTx
         Counter64,
      pr1645v2TTmplPiGreInPQsPacketsQueued
         Counter64,
      pr1645v2TTmplPiGreInPQsPacketsDropped
         Counter64,
      pr1645v2TTmplPiGreInPQsPacketsRedDropped
         Counter64,
      pr1645v2TTmplPiGreInPQsPacketsCirTx
         Counter64,
      pr1645v2TTmplPiGreInPQsPacketsEirTx
         Counter64,
      pr1645v2TTmplPiGreInPQsPacketsViolateTx
         Counter64,
      pr1645v2TTmplPiGreInPQsOctetsTotal
         Counter64,
      pr1645v2TTmplPiGreInPQsOctetsDirectTx
         Counter64,
      pr1645v2TTmplPiGreInPQsOctetsQueued
         Counter64,
      pr1645v2TTmplPiGreInPQsOctetsDropped
         Counter64,
      pr1645v2TTmplPiGreInPQsOctetsRedDropped
         Counter64,
      pr1645v2TTmplPiGreInPQsOctetsCirTx
         Counter64,
      pr1645v2TTmplPiGreInPQsOctetsEirTx
         Counter64,
      pr1645v2TTmplPiGreInPQsOctetsViolateTx
         Counter64,
      pr1645v2TTmplPiGreInPQsOctetsBandwidth15sec
         Integer32,
      pr1645v2TTmplPiGreInPQsOctetsBandwidth30sec
         Integer32,
      pr1645v2TTmplPiGreInPQsOctetsBandwidth1min
         Integer32,
      pr1645v2TTmplPiGreInPQsOctetsBandwidth2min
         Integer32,
      pr1645v2TTmplPiGreInPQsOctetsBandwidth5min
         Integer32
      }

pr1645v2TTmplPiGreInPQsTableIx OBJECT-TYPE
   SYNTAX      TableIndex
   MAX-ACCESS  not-accessible
   STATUS      current
   DESCRIPTION
      ""
   ::= {pr1645v2TTmplPiGreInPQsEntry 11}

pr1645v2TTmplPiGreInPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: tunnels.performance.ipsecGreTunnels.inPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2TTmplPiGreInPQsEntry 16777216}

pr1645v2TTmplPiGreInPQsLength OBJECT-TYPE
   SYNTAX      Integer32
   MAX-ACCESS  read-only
   STATUS      current
   DESCRIPTION
      "Path: tunnels.performance.ipsecGreTunnels.inPriorityQueues.length"
   ::= {pr1645v2TTmplPiGreInPQsEntry 33554432}

pr1645v2TTmplPiGreInPQsOctetLength OBJECT-TYPE
   SYNTAX      Integer32
   MAX-ACCESS  read-only
   STATUS      current
   DESCRIPTION
      "Path: tunnels.performance.ipsecGreTunnels.inPriorityQueues.octetLength"
   ::= {pr1645v2TTmplPiGreInPQsEntry 150994944}

pr1645v2TTmplPiGreInPQsRedLength OBJECT-TYPE
   SYNTAX      Integer32
   MAX-ACCESS  read-only
   STATUS      current
   DESCRIPTION
      "Path: tunnels.performance.ipsecGreTunnels.inPriorityQueues.redLength"
   ::= {pr1645v2TTmplPiGreInPQsEntry 134217728}

pr1645v2TTmplPiGreInPQsPacketsTotal OBJECT-TYPE
   SYNTAX      Counter64
   MAX-ACCESS  read-only
   STATUS      current
   DESCRIPTION
      "Path: tunnels.performance.ipsecGreTunnels.inPriorityQueues.packets.total

       64 bit unsigned wrappable counter."
   ::= {pr1645v2TTmplPiGreInPQsEntry 50790400}

pr1645v2TTmplPiGreInPQsPacketsDirectTx OBJECT-TYPE
   SYNTAX      Counter64
   MAX-ACCESS  read-only
   STATUS      current
   DESCRIPTION
      "Path: tunnels.performance.ipsecGreTunnels.inPriorityQueues.packets.directTx

       64 bit unsigned wrappable counter."
   ::= {pr1645v2TTmplPiGreInPQsEntry 50397184}

pr1645v2TTmplPiGreInPQsPacketsQueued OBJECT-TYPE
   SYNTAX      Counter64
   MAX-ACCESS  read-only
   STATUS      current
   DESCRIPTION
      "Path: tunnels.performance.ipsecGreTunnels.inPriorityQueues.packets.queued

       64 bit unsigned wrappable counter."
   ::= {pr1645v2TTmplPiGreInPQsEntry 50462720}

pr1645v2TTmplPiGreInPQsPacketsDropped OBJECT-TYPE
   SYNTAX      Counter64
   MAX-ACCESS  read-only
   STATUS      current
   DESCRIPTION
      "Path: tunnels.performance.ipsecGreTunnels.inPriorityQueues.packets.dropped

       64 bit unsigned wrappable counter."
   ::= {pr1645v2TTmplPiGreInPQsEntry 50528256}

pr1645v2TTmplPiGreInPQsPacketsRedDropped OBJECT-TYPE
   SYNTAX      Counter64
   MAX-ACCESS  read-only
   STATUS      current
   DESCRIPTION
      "Path: tunnels.performance.ipsecGreTunnels.inPriorityQueues.packets.redDropped

       64 bit unsigned wrappable counter."
   ::= {pr1645v2TTmplPiGreInPQsEntry 50724864}

pr1645v2TTmplPiGreInPQsPacketsCirTx OBJECT-TYPE
   SYNTAX      Counter64
   MAX-ACCESS  read-only
   STATUS      current
   DESCRIPTION
      "Path: tunnels.performance.ipsecGreTunnels.inPriorityQueues.packets.cirTx

       64 bit unsigned wrappable counter."
   ::= {pr1645v2TTmplPiGreInPQsEntry 50593792}

pr1645v2TTmplPiGreInPQsPacketsEirTx OBJECT-TYPE
   SYNTAX      Counter64
   MAX-ACCESS  read-only
   STATUS      current
   DESCRIPTION
      "Path: tunnels.performance.ipsecGreTunnels.inPriorityQueues.packets.eirTx

       64 bit unsigned wrappable counter."
   ::= {pr1645v2TTmplPiGreInPQsEntry 50659328}

pr1645v2TTmplPiGreInPQsPacketsViolateTx OBJECT-TYPE
   SYNTAX      Counter64
   MAX-ACCESS  read-only
   STATUS      current
   DESCRIPTION
      "Path: tunnels.performance.ipsecGreTunnels.inPriorityQueues.packets.violateTx

       64 bit unsigned wrappable counter."
   ::= {pr1645v2TTmplPiGreInPQsEntry 50855936}

pr1645v2TTmplPiGreInPQsOctetsTotal OBJECT-TYPE
   SYNTAX      Counter64
   MAX-ACCESS  read-only
   STATUS      current
   DESCRIPTION
      "Path: tunnels.performance.ipsecGreTunnels.inPriorityQueues.octets.total

       64 bit unsigned wrappable counter."
   ::= {pr1645v2TTmplPiGreInPQsEntry 67567616}

pr1645v2TTmplPiGreInPQsOctetsDirectTx OBJECT-TYPE
   SYNTAX      Counter64
   MAX-ACCESS  read-only
   STATUS      current
   DESCRIPTION
      "Path: tunnels.performance.ipsecGreTunnels.inPriorityQueues.octets.directTx

       64 bit unsigned wrappable counter."
   ::= {pr1645v2TTmplPiGreInPQsEntry 67174400}

pr1645v2TTmplPiGreInPQsOctetsQueued OBJECT-TYPE
   SYNTAX      Counter64
   MAX-ACCESS  read-only
   STATUS      current
   DESCRIPTION
      "Path: tunnels.performance.ipsecGreTunnels.inPriorityQueues.octets.queued

       64 bit unsigned wrappable counter."
   ::= {pr1645v2TTmplPiGreInPQsEntry 67239936}

pr1645v2TTmplPiGreInPQsOctetsDropped OBJECT-TYPE
   SYNTAX      Counter64
   MAX-ACCESS  read-only
   STATUS      current
   DESCRIPTION
      "Path: tunnels.performance.ipsecGreTunnels.inPriorityQueues.octets.dropped

       64 bit unsigned wrappable counter."
   ::= {pr1645v2TTmplPiGreInPQsEntry 67305472}

pr1645v2TTmplPiGreInPQsOctetsRedDropped OBJECT-TYPE
   SYNTAX      Counter64
   MAX-ACCESS  read-only
   STATUS      current
   DESCRIPTION
      "Path: tunnels.performance.ipsecGreTunnels.inPriorityQueues.octets.redDropped

       64 bit unsigned wrappable counter."
   ::= {pr1645v2TTmplPiGreInPQsEntry 67502080}

pr1645v2TTmplPiGreInPQsOctetsCirTx OBJECT-TYPE
   SYNTAX      Counter64
   MAX-ACCESS  read-only
   STATUS      current
   DESCRIPTION
      "Path: tunnels.performance.ipsecGreTunnels.inPriorityQueues.octets.cirTx

       64 bit unsigned wrappable counter."
   ::= {pr1645v2TTmplPiGreInPQsEntry 67371008}

pr1645v2TTmplPiGreInPQsOctetsEirTx OBJECT-TYPE
   SYNTAX      Counter64
   MAX-ACCESS  read-only
   STATUS      current
   DESCRIPTION
      "Path: tunnels.performance.ipsecGreTunnels.inPriorityQueues.octets.eirTx

       64 bit unsigned wrappable counter."
   ::= {pr1645v2TTmplPiGreInPQsEntry 67436544}

pr1645v2TTmplPiGreInPQsOctetsViolateTx OBJECT-TYPE
   SYNTAX      Counter64
   MAX-ACCESS  read-only
   STATUS      current
   DESCRIPTION
      "Path: tunnels.performance.ipsecGreTunnels.inPriorityQueues.octets.violateTx

       64 bit unsigned wrappable counter."
   ::= {pr1645v2TTmplPiGreInPQsEntry 67633152}

pr1645v2TTmplPiGreInPQsOctetsBandwidth15sec OBJECT-TYPE
   SYNTAX      Integer32
   MAX-ACCESS  read-only
   STATUS      current
   DESCRIPTION
      "Path: tunnels.performance.ipsecGreTunnels.inPriorityQueues.octets.bandwidth.15sec

       unit name = bps
       formula = 8 * ; 8 /"
   ::= {pr1645v2TTmplPiGreInPQsEntry 70386944}

pr1645v2TTmplPiGreInPQsOctetsBandwidth30sec OBJECT-TYPE
   SYNTAX      Integer32
   MAX-ACCESS  read-only
   STATUS      current
   DESCRIPTION
      "Path: tunnels.performance.ipsecGreTunnels.inPriorityQueues.octets.bandwidth.30sec

       unit name = bps
       formula = 8 * ; 8 /"
   ::= {pr1645v2TTmplPiGreInPQsEntry 70388224}

pr1645v2TTmplPiGreInPQsOctetsBandwidth1min OBJECT-TYPE
   SYNTAX      Integer32
   MAX-ACCESS  read-only
   STATUS      current
   DESCRIPTION
      "Path: tunnels.performance.ipsecGreTunnels.inPriorityQueues.octets.bandwidth.1min

       unit name = bps
       formula = 8 * ; 8 /"
   ::= {pr1645v2TTmplPiGreInPQsEntry 70390784}

pr1645v2TTmplPiGreInPQsOctetsBandwidth2min OBJECT-TYPE
   SYNTAX      Integer32
   MAX-ACCESS  read-only
   STATUS      current
   DESCRIPTION
      "Path: tunnels.performance.ipsecGreTunnels.inPriorityQueues.octets.bandwidth.2min

       unit name = bps
       formula = 8 * ; 8 /"
   ::= {pr1645v2TTmplPiGreInPQsEntry 70395904}

pr1645v2TTmplPiGreInPQsOctetsBandwidth5min OBJECT-TYPE
   SYNTAX      Integer32
   MAX-ACCESS  read-only
   STATUS      current
   DESCRIPTION
      "Path: tunnels.performance.ipsecGreTunnels.inPriorityQueues.octets.bandwidth.5min

       unit name = bps
       formula = 8 * ; 8 /"
   ::= {pr1645v2TTmplPiGreInPQsEntry 70411264}

pr1645v2TTmplPiGreInPQsH2Performance OBJECT-TYPE
   SYNTAX      SEQUENCE OF Pr1645v2TTmplPiGreInPQsH2PerformanceEntry
   MAX-ACCESS  not-accessible
   STATUS      current
   DESCRIPTION
      ""
   ::= {pr1645v2TTmplPiGre 100990976}

pr1645v2TTmplPiGreInPQsH2PerformanceEntry OBJECT-TYPE
   SYNTAX      Pr1645v2TTmplPiGreInPQsH2PerformanceEntry
   MAX-ACCESS  not-accessible
   STATUS      current
   DESCRIPTION
      ""
   INDEX      { pr1645v2TTmplPiGreTableIx,
                pr1645v2TTmplPiGreInPQsTableIx,
                pr1645v2TTmplPiGreInPQsH2PerformanceTableIx }
   ::= {pr1645v2TTmplPiGreInPQsH2Performance 1}

Pr1645v2TTmplPiGreInPQsH2PerformanceEntry ::=
   SEQUENCE
      {
      pr1645v2TTmplPiGreInPQsH2PerformanceTableIx
         TableIndex,
      pr1645v2TTmplPiGreInPQsH2PerformanceSysUpTime
         TimeTicks,
      pr1645v2TTmplPiGreInPQsH2PerformanceTotPkts
         Counter64,
      pr1645v2TTmplPiGreInPQsH2PerformanceDirTxPkts
         Counter64,
      pr1645v2TTmplPiGreInPQsH2PerformanceQdPkts
         Counter64,
      pr1645v2TTmplPiGreInPQsH2PerformanceDropPkts
         Counter64,
      pr1645v2TTmplPiGreInPQsH2PerformanceRDropPkts
         Counter64,
      pr1645v2TTmplPiGreInPQsH2PerformanceCirTxPkts
         Counter64,
      pr1645v2TTmplPiGreInPQsH2PerformanceEirTxPkts
         Counter64,
      pr1645v2TTmplPiGreInPQsH2PerformanceViolTxPkts
         Counter64,
      pr1645v2TTmplPiGreInPQsH2PerformanceTotOcts
         Counter64,
      pr1645v2TTmplPiGreInPQsH2PerformanceDirTxOcts
         Counter64,
      pr1645v2TTmplPiGreInPQsH2PerformanceQdOcts
         Counter64,
      pr1645v2TTmplPiGreInPQsH2PerformanceDropOcts
         Counter64,
      pr1645v2TTmplPiGreInPQsH2PerformanceRDropOcts
         Counter64,
      pr1645v2TTmplPiGreInPQsH2PerformanceCirTxOcts
         Counter64,
      pr1645v2TTmplPiGreInPQsH2PerformanceEirTxOcts
         Counter64,
      pr1645v2TTmplPiGreInPQsH2PerformanceViolTxOcts
         Counter64,
      pr1645v2TTmplPiGreInPQsH2PerformanceBandwidth
         Integer32
      }

pr1645v2TTmplPiGreInPQsH2PerformanceTableIx OBJECT-TYPE
   SYNTAX      TableIndex
   MAX-ACCESS  not-accessible
   STATUS      current
   DESCRIPTION
      ""
   ::= {pr1645v2TTmplPiGreInPQsH2PerformanceEntry 11}

pr1645v2TTmplPiGreInPQsH2PerformanceSysUpTime OBJECT-TYPE
   SYNTAX      TimeTicks
   MAX-ACCESS  read-only
   STATUS      current
   DESCRIPTION
      "Path: tunnels.performance.ipsecGreTunnels.inPriorityQueues.h2Performance.sysUpTime

       Time in centi-second."
   ::= {pr1645v2TTmplPiGreInPQsH2PerformanceEntry 16777216}

pr1645v2TTmplPiGreInPQsH2PerformanceTotPkts OBJECT-TYPE
   SYNTAX      Counter64
   MAX-ACCESS  read-only
   STATUS      current
   DESCRIPTION
      "Path: tunnels.performance.ipsecGreTunnels.inPriorityQueues.h2Performance.totalPkts

       64 bit unsigned wrappable counter."
   ::= {pr1645v2TTmplPiGreInPQsH2PerformanceEntry 234881024}

pr1645v2TTmplPiGreInPQsH2PerformanceDirTxPkts OBJECT-TYPE
   SYNTAX      Counter64
   MAX-ACCESS  read-only
   STATUS      current
   DESCRIPTION
      "Path: tunnels.performance.ipsecGreTunnels.inPriorityQueues.h2Performance.directTxPkts

       64 bit unsigned wrappable counter."
   ::= {pr1645v2TTmplPiGreInPQsH2PerformanceEntry 33554432}

pr1645v2TTmplPiGreInPQsH2PerformanceQdPkts OBJECT-TYPE
   SYNTAX      Counter64
   MAX-ACCESS  read-only
   STATUS      current
   DESCRIPTION
      "Path: tunnels.performance.ipsecGreTunnels.inPriorityQueues.h2Performance.queuedPkts

       64 bit unsigned wrappable counter."
   ::= {pr1645v2TTmplPiGreInPQsH2PerformanceEntry 50331648}

pr1645v2TTmplPiGreInPQsH2PerformanceDropPkts OBJECT-TYPE
   SYNTAX      Counter64
   MAX-ACCESS  read-only
   STATUS      current
   DESCRIPTION
      "Path: tunnels.performance.ipsecGreTunnels.inPriorityQueues.h2Performance.droppedPkts

       64 bit unsigned wrappable counter."
   ::= {pr1645v2TTmplPiGreInPQsH2PerformanceEntry 67108864}

pr1645v2TTmplPiGreInPQsH2PerformanceRDropPkts OBJECT-TYPE
   SYNTAX      Counter64
   MAX-ACCESS  read-only
   STATUS      current
   DESCRIPTION
      "Path: tunnels.performance.ipsecGreTunnels.inPriorityQueues.h2Performance.redDroppedPkts

       64 bit unsigned wrappable counter."
   ::= {pr1645v2TTmplPiGreInPQsH2PerformanceEntry 201326592}

pr1645v2TTmplPiGreInPQsH2PerformanceCirTxPkts OBJECT-TYPE
   SYNTAX      Counter64
   MAX-ACCESS  read-only
   STATUS      current
   DESCRIPTION
      "Path: tunnels.performance.ipsecGreTunnels.inPriorityQueues.h2Performance.cirTxPkts

       64 bit unsigned wrappable counter."
   ::= {pr1645v2TTmplPiGreInPQsH2PerformanceEntry 83886080}

pr1645v2TTmplPiGreInPQsH2PerformanceEirTxPkts OBJECT-TYPE
   SYNTAX      Counter64
   MAX-ACCESS  read-only
   STATUS      current
   DESCRIPTION
      "Path: tunnels.performance.ipsecGreTunnels.inPriorityQueues.h2Performance.eirTxPkts

       64 bit unsigned wrappable counter."
   ::= {pr1645v2TTmplPiGreInPQsH2PerformanceEntry 100663296}

pr1645v2TTmplPiGreInPQsH2PerformanceViolTxPkts OBJECT-TYPE
   SYNTAX      Counter64
   MAX-ACCESS  read-only
   STATUS      current
   DESCRIPTION
      "Path: tunnels.performance.ipsecGreTunnels.inPriorityQueues.h2Performance.violateTxPkts

       64 bit unsigned wrappable counter."
   ::= {pr1645v2TTmplPiGreInPQsH2PerformanceEntry 301989888}

pr1645v2TTmplPiGreInPQsH2PerformanceTotOcts OBJECT-TYPE
   SYNTAX      Counter64
   MAX-ACCESS  read-only
   STATUS      current
   DESCRIPTION
      "Path: tunnels.performance.ipsecGreTunnels.inPriorityQueues.h2Performance.totalOctets

       64 bit unsigned wrappable counter."
   ::= {pr1645v2TTmplPiGreInPQsH2PerformanceEntry 251658240}

pr1645v2TTmplPiGreInPQsH2PerformanceDirTxOcts OBJECT-TYPE
   SYNTAX      Counter64
   MAX-ACCESS  read-only
   STATUS      current
   DESCRIPTION
      "Path: tunnels.performance.ipsecGreTunnels.inPriorityQueues.h2Performance.directTxOctets

       64 bit unsigned wrappable counter."
   ::= {pr1645v2TTmplPiGreInPQsH2PerformanceEntry 117440512}

pr1645v2TTmplPiGreInPQsH2PerformanceQdOcts OBJECT-TYPE
   SYNTAX      Counter64
   MAX-ACCESS  read-only
   STATUS      current
   DESCRIPTION
      "Path: tunnels.performance.ipsecGreTunnels.inPriorityQueues.h2Performance.queuedOctets

       64 bit unsigned wrappable counter."
   ::= {pr1645v2TTmplPiGreInPQsH2PerformanceEntry 134217728}

pr1645v2TTmplPiGreInPQsH2PerformanceDropOcts OBJECT-TYPE
   SYNTAX      Counter64
   MAX-ACCESS  read-only
   STATUS      current
   DESCRIPTION
      "Path: tunnels.performance.ipsecGreTunnels.inPriorityQueues.h2Performance.droppedOctets

       64 bit unsigned wrappable counter."
   ::= {pr1645v2TTmplPiGreInPQsH2PerformanceEntry 150994944}

pr1645v2TTmplPiGreInPQsH2PerformanceRDropOcts OBJECT-TYPE
   SYNTAX      Counter64
   MAX-ACCESS  read-only
   STATUS      current
   DESCRIPTION
      "Path: tunnels.performance.ipsecGreTunnels.inPriorityQueues.h2Performance.redDroppedOctets

       64 bit unsigned wrappable counter."
   ::= {pr1645v2TTmplPiGreInPQsH2PerformanceEntry 218103808}

pr1645v2TTmplPiGreInPQsH2PerformanceCirTxOcts OBJECT-TYPE
   SYNTAX      Counter64
   MAX-ACCESS  read-only
   STATUS      current
   DESCRIPTION
      "Path: tunnels.performance.ipsecGreTunnels.inPriorityQueues.h2Performance.cirTxOctets

       64 bit unsigned wrappable counter."
   ::= {pr1645v2TTmplPiGreInPQsH2PerformanceEntry 167772160}

pr1645v2TTmplPiGreInPQsH2PerformanceEirTxOcts OBJECT-TYPE
   SYNTAX      Counter64
   MAX-ACCESS  read-only
   STATUS      current
   DESCRIPTION
      "Path: tunnels.performance.ipsecGreTunnels.inPriorityQueues.h2Performance.eirTxOctets

       64 bit unsigned wrappable counter."
   ::= {pr1645v2TTmplPiGreInPQsH2PerformanceEntry 184549376}

pr1645v2TTmplPiGreInPQsH2PerformanceViolTxOcts OBJECT-TYPE
   SYNTAX      Counter64
   MAX-ACCESS  read-only
   STATUS      current
   DESCRIPTION
      "Path: tunnels.performance.ipsecGreTunnels.inPriorityQueues.h2Performance.violateTxOctets

       64 bit unsigned wrappable counter."
   ::= {pr1645v2TTmplPiGreInPQsH2PerformanceEntry 318767104}

pr1645v2TTmplPiGreInPQsH2PerformanceBandwidth OBJECT-TYPE
   SYNTAX      Integer32
   MAX-ACCESS  read-only
   STATUS      current
   DESCRIPTION
      "Path: tunnels.performance.ipsecGreTunnels.inPriorityQueues.h2Performance.bandwidth

       unit name = bps
       formula = 8 * ; 8 /"
   ::= {pr1645v2TTmplPiGreInPQsH2PerformanceEntry 268435456}

pr1645v2TTmplPiGreInPQsH24Performance OBJECT-TYPE
   SYNTAX      SEQUENCE OF Pr1645v2TTmplPiGreInPQsH24PerformanceEntry
   MAX-ACCESS  not-accessible
   STATUS      current
   DESCRIPTION
      ""
   ::= {pr1645v2TTmplPiGre 101056512}

pr1645v2TTmplPiGreInPQsH24PerformanceEntry OBJECT-TYPE
   SYNTAX      Pr1645v2TTmplPiGreInPQsH24PerformanceEntry
   MAX-ACCESS  not-accessible
   STATUS      current
   DESCRIPTION
      ""
   INDEX      { pr1645v2TTmplPiGreTableIx,
                pr1645v2TTmplPiGreInPQsTableIx,
                pr1645v2TTmplPiGreInPQsH24PerformanceTableIx }
   ::= {pr1645v2TTmplPiGreInPQsH24Performance 1}

Pr1645v2TTmplPiGreInPQsH24PerformanceEntry ::=
   SEQUENCE
      {
      pr1645v2TTmplPiGreInPQsH24PerformanceTableIx
         TableIndex,
      pr1645v2TTmplPiGreInPQsH24PerformanceSysUpTime
         TimeTicks,
      pr1645v2TTmplPiGreInPQsH24PerformanceTotPkts
         Counter64,
      pr1645v2TTmplPiGreInPQsH24PerformanceDirTxPkts
         Counter64,
      pr1645v2TTmplPiGreInPQsH24PerformanceQdPkts
         Counter64,
      pr1645v2TTmplPiGreInPQsH24PerformanceDropPkts
         Counter64,
      pr1645v2TTmplPiGreInPQsH24PerformanceRDropPkts
         Counter64,
      pr1645v2TTmplPiGreInPQsH24PerformanceCirTxPkts
         Counter64,
      pr1645v2TTmplPiGreInPQsH24PerformanceEirTxPkts
         Counter64,
      pr1645v2TTmplPiGreInPQsH24PerformanceViolTxPkts
         Counter64,
      pr1645v2TTmplPiGreInPQsH24PerformanceTotOcts
         Counter64,
      pr1645v2TTmplPiGreInPQsH24PerformanceDirTxOcts
         Counter64,
      pr1645v2TTmplPiGreInPQsH24PerformanceQdOcts
         Counter64,
      pr1645v2TTmplPiGreInPQsH24PerformanceDropOcts
         Counter64,
      pr1645v2TTmplPiGreInPQsH24PerformanceRDropOcts
         Counter64,
      pr1645v2TTmplPiGreInPQsH24PerformanceCirTxOcts
         Counter64,
      pr1645v2TTmplPiGreInPQsH24PerformanceEirTxOcts
         Counter64,
      pr1645v2TTmplPiGreInPQsH24PerformanceViolTxOcts
         Counter64,
      pr1645v2TTmplPiGreInPQsH24PerformanceBandwidth
         Integer32
      }

pr1645v2TTmplPiGreInPQsH24PerformanceTableIx OBJECT-TYPE
   SYNTAX      TableIndex
   MAX-ACCESS  not-accessible
   STATUS      current
   DESCRIPTION
      ""
   ::= {pr1645v2TTmplPiGreInPQsH24PerformanceEntry 11}

pr1645v2TTmplPiGreInPQsH24PerformanceSysUpTime OBJECT-TYPE
   SYNTAX      TimeTicks
   MAX-ACCESS  read-only
   STATUS      current
   DESCRIPTION
      "Path: tunnels.performance.ipsecGreTunnels.inPriorityQueues.h24Performance.sysUpTime

       Time in centi-second."
   ::= {pr1645v2TTmplPiGreInPQsH24PerformanceEntry 16777216}

pr1645v2TTmplPiGreInPQsH24PerformanceTotPkts OBJECT-TYPE
   SYNTAX      Counter64
   MAX-ACCESS  read-only
   STATUS      current
   DESCRIPTION
      "Path: tunnels.performance.ipsecGreTunnels.inPriorityQueues.h24Performance.totalPkts

       64 bit unsigned wrappable counter."
   ::= {pr1645v2TTmplPiGreInPQsH24PerformanceEntry 234881024}

pr1645v2TTmplPiGreInPQsH24PerformanceDirTxPkts OBJECT-TYPE
   SYNTAX      Counter64
   MAX-ACCESS  read-only
   STATUS      current
   DESCRIPTION
      "Path: tunnels.performance.ipsecGreTunnels.inPriorityQueues.h24Performance.directTxPkts

       64 bit unsigned wrappable counter."
   ::= {pr1645v2TTmplPiGreInPQsH24PerformanceEntry 33554432}

pr1645v2TTmplPiGreInPQsH24PerformanceQdPkts OBJECT-TYPE
   SYNTAX      Counter64
   MAX-ACCESS  read-only
   STATUS      current
   DESCRIPTION
      "Path: tunnels.performance.ipsecGreTunnels.inPriorityQueues.h24Performance.queuedPkts

       64 bit unsigned wrappable counter."
   ::= {pr1645v2TTmplPiGreInPQsH24PerformanceEntry 50331648}

pr1645v2TTmplPiGreInPQsH24PerformanceDropPkts OBJECT-TYPE
   SYNTAX      Counter64
   MAX-ACCESS  read-only
   STATUS      current
   DESCRIPTION
      "Path: tunnels.performance.ipsecGreTunnels.inPriorityQueues.h24Performance.droppedPkts

       64 bit unsigned wrappable counter."
   ::= {pr1645v2TTmplPiGreInPQsH24PerformanceEntry 67108864}

pr1645v2TTmplPiGreInPQsH24PerformanceRDropPkts OBJECT-TYPE
   SYNTAX      Counter64
   MAX-ACCESS  read-only
   STATUS      current
   DESCRIPTION
      "Path: tunnels.performance.ipsecGreTunnels.inPriorityQueues.h24Performance.redDroppedPkts

       64 bit unsigned wrappable counter."
   ::= {pr1645v2TTmplPiGreInPQsH24PerformanceEntry 201326592}

pr1645v2TTmplPiGreInPQsH24PerformanceCirTxPkts OBJECT-TYPE
   SYNTAX      Counter64
   MAX-ACCESS  read-only
   STATUS      current
   DESCRIPTION
      "Path: tunnels.performance.ipsecGreTunnels.inPriorityQueues.h24Performance.cirTxPkts

       64 bit unsigned wrappable counter."
   ::= {pr1645v2TTmplPiGreInPQsH24PerformanceEntry 83886080}

pr1645v2TTmplPiGreInPQsH24PerformanceEirTxPkts OBJECT-TYPE
   SYNTAX      Counter64
   MAX-ACCESS  read-only
   STATUS      current
   DESCRIPTION
      "Path: tunnels.performance.ipsecGreTunnels.inPriorityQueues.h24Performance.eirTxPkts

       64 bit unsigned wrappable counter."
   ::= {pr1645v2TTmplPiGreInPQsH24PerformanceEntry 100663296}

pr1645v2TTmplPiGreInPQsH24PerformanceViolTxPkts OBJECT-TYPE
   SYNTAX      Counter64
   MAX-ACCESS  read-only
   STATUS      current
   DESCRIPTION
      "Path: tunnels.performance.ipsecGreTunnels.inPriorityQueues.h24Performance.violateTxPkts

       64 bit unsigned wrappable counter."
   ::= {pr1645v2TTmplPiGreInPQsH24PerformanceEntry 301989888}

pr1645v2TTmplPiGreInPQsH24PerformanceTotOcts OBJECT-TYPE
   SYNTAX      Counter64
   MAX-ACCESS  read-only
   STATUS      current
   DESCRIPTION
      "Path: tunnels.performance.ipsecGreTunnels.inPriorityQueues.h24Performance.totalOctets

       64 bit unsigned wrappable counter."
   ::= {pr1645v2TTmplPiGreInPQsH24PerformanceEntry 251658240}

pr1645v2TTmplPiGreInPQsH24PerformanceDirTxOcts OBJECT-TYPE
   SYNTAX      Counter64
   MAX-ACCESS  read-only
   STATUS      current
   DESCRIPTION
      "Path: tunnels.performance.ipsecGreTunnels.inPriorityQueues.h24Performance.directTxOctets

       64 bit unsigned wrappable counter."
   ::= {pr1645v2TTmplPiGreInPQsH24PerformanceEntry 117440512}

pr1645v2TTmplPiGreInPQsH24PerformanceQdOcts OBJECT-TYPE
   SYNTAX      Counter64
   MAX-ACCESS  read-only
   STATUS      current
   DESCRIPTION
      "Path: tunnels.performance.ipsecGreTunnels.inPriorityQueues.h24Performance.queuedOctets

       64 bit unsigned wrappable counter."
   ::= {pr1645v2TTmplPiGreInPQsH24PerformanceEntry 134217728}

pr1645v2TTmplPiGreInPQsH24PerformanceDropOcts OBJECT-TYPE
   SYNTAX      Counter64
   MAX-ACCESS  read-only
   STATUS      current
   DESCRIPTION
      "Path: tunnels.performance.ipsecGreTunnels.inPriorityQueues.h24Performance.droppedOctets

       64 bit unsigned wrappable counter."
   ::= {pr1645v2TTmplPiGreInPQsH24PerformanceEntry 150994944}

pr1645v2TTmplPiGreInPQsH24PerformanceRDropOcts OBJECT-TYPE
   SYNTAX      Counter64
   MAX-ACCESS  read-only
   STATUS      current
   DESCRIPTION
      "Path: tunnels.performance.ipsecGreTunnels.inPriorityQueues.h24Performance.redDroppedOctets

       64 bit unsigned wrappable counter."
   ::= {pr1645v2TTmplPiGreInPQsH24PerformanceEntry 218103808}

pr1645v2TTmplPiGreInPQsH24PerformanceCirTxOcts OBJECT-TYPE
   SYNTAX      Counter64
   MAX-ACCESS  read-only
   STATUS      current
   DESCRIPTION
      "Path: tunnels.performance.ipsecGreTunnels.inPriorityQueues.h24Performance.cirTxOctets

       64 bit unsigned wrappable counter."
   ::= {pr1645v2TTmplPiGreInPQsH24PerformanceEntry 167772160}

pr1645v2TTmplPiGreInPQsH24PerformanceEirTxOcts OBJECT-TYPE
   SYNTAX      Counter64
   MAX-ACCESS  read-only
   STATUS      current
   DESCRIPTION
      "Path: tunnels.performance.ipsecGreTunnels.inPriorityQueues.h24Performance.eirTxOctets

       64 bit unsigned wrappable counter."
   ::= {pr1645v2TTmplPiGreInPQsH24PerformanceEntry 184549376}

pr1645v2TTmplPiGreInPQsH24PerformanceViolTxOcts OBJECT-TYPE
   SYNTAX      Counter64
   MAX-ACCESS  read-only
   STATUS      current
   DESCRIPTION
      "Path: tunnels.performance.ipsecGreTunnels.inPriorityQueues.h24Performance.violateTxOctets

       64 bit unsigned wrappable counter."
   ::= {pr1645v2TTmplPiGreInPQsH24PerformanceEntry 318767104}

pr1645v2TTmplPiGreInPQsH24PerformanceBandwidth OBJECT-TYPE
   SYNTAX      Integer32
   MAX-ACCESS  read-only
   STATUS      current
   DESCRIPTION
      "Path: tunnels.performance.ipsecGreTunnels.inPriorityQueues.h24Performance.bandwidth

       unit name = bps
       formula = 8 * ; 8 /"
   ::= {pr1645v2TTmplPiGreInPQsH24PerformanceEntry 268435456}

pr1645v2TTmplPiGreInPQsD7Performance OBJECT-TYPE
   SYNTAX      SEQUENCE OF Pr1645v2TTmplPiGreInPQsD7PerformanceEntry
   MAX-ACCESS  not-accessible
   STATUS      current
   DESCRIPTION
      ""
   ::= {pr1645v2TTmplPiGre 101122048}

pr1645v2TTmplPiGreInPQsD7PerformanceEntry OBJECT-TYPE
   SYNTAX      Pr1645v2TTmplPiGreInPQsD7PerformanceEntry
   MAX-ACCESS  not-accessible
   STATUS      current
   DESCRIPTION
      ""
   INDEX      { pr1645v2TTmplPiGreTableIx,
                pr1645v2TTmplPiGreInPQsTableIx,
                pr1645v2TTmplPiGreInPQsD7PerformanceTableIx }
   ::= {pr1645v2TTmplPiGreInPQsD7Performance 1}

Pr1645v2TTmplPiGreInPQsD7PerformanceEntry ::=
   SEQUENCE
      {
      pr1645v2TTmplPiGreInPQsD7PerformanceTableIx
         TableIndex,
      pr1645v2TTmplPiGreInPQsD7PerformanceSysUpTime
         TimeTicks,
      pr1645v2TTmplPiGreInPQsD7PerformanceTotPkts
         Counter64,
      pr1645v2TTmplPiGreInPQsD7PerformanceDirTxPkts
         Counter64,
      pr1645v2TTmplPiGreInPQsD7PerformanceQdPkts
         Counter64,
      pr1645v2TTmplPiGreInPQsD7PerformanceDropPkts
         Counter64,
      pr1645v2TTmplPiGreInPQsD7PerformanceRDropPkts
         Counter64,
      pr1645v2TTmplPiGreInPQsD7PerformanceCirTxPkts
         Counter64,
      pr1645v2TTmplPiGreInPQsD7PerformanceEirTxPkts
         Counter64,
      pr1645v2TTmplPiGreInPQsD7PerformanceViolTxPkts
         Counter64,
      pr1645v2TTmplPiGreInPQsD7PerformanceTotOcts
         Counter64,
      pr1645v2TTmplPiGreInPQsD7PerformanceDirTxOcts
         Counter64,
      pr1645v2TTmplPiGreInPQsD7PerformanceQdOcts
         Counter64,
      pr1645v2TTmplPiGreInPQsD7PerformanceDropOcts
         Counter64,
      pr1645v2TTmplPiGreInPQsD7PerformanceRDropOcts
         Counter64,
      pr1645v2TTmplPiGreInPQsD7PerformanceCirTxOcts
         Counter64,
      pr1645v2TTmplPiGreInPQsD7PerformanceEirTxOcts
         Counter64,
      pr1645v2TTmplPiGreInPQsD7PerformanceViolTxOcts
         Counter64,
      pr1645v2TTmplPiGreInPQsD7PerformanceBandwidth
         Integer32
      }

pr1645v2TTmplPiGreInPQsD7PerformanceTableIx OBJECT-TYPE
   SYNTAX      TableIndex
   MAX-ACCESS  not-accessible
   STATUS      current
   DESCRIPTION
      ""
   ::= {pr1645v2TTmplPiGreInPQsD7PerformanceEntry 11}

pr1645v2TTmplPiGreInPQsD7PerformanceSysUpTime OBJECT-TYPE
   SYNTAX      TimeTicks
   MAX-ACCESS  read-only
   STATUS      current
   DESCRIPTION
      "Path: tunnels.performance.ipsecGreTunnels.inPriorityQueues.d7Performance.sysUpTime

       Time in centi-second."
   ::= {pr1645v2TTmplPiGreInPQsD7PerformanceEntry 16777216}

pr1645v2TTmplPiGreInPQsD7PerformanceTotPkts OBJECT-TYPE
   SYNTAX      Counter64
   MAX-ACCESS  read-only
   STATUS      current
   DESCRIPTION
      "Path: tunnels.performance.ipsecGreTunnels.inPriorityQueues.d7Performance.totalPkts

       64 bit unsigned wrappable counter."
   ::= {pr1645v2TTmplPiGreInPQsD7PerformanceEntry 234881024}

pr1645v2TTmplPiGreInPQsD7PerformanceDirTxPkts OBJECT-TYPE
   SYNTAX      Counter64
   MAX-ACCESS  read-only
   STATUS      current
   DESCRIPTION
      "Path: tunnels.performance.ipsecGreTunnels.inPriorityQueues.d7Performance.directTxPkts

       64 bit unsigned wrappable counter."
   ::= {pr1645v2TTmplPiGreInPQsD7PerformanceEntry 33554432}

pr1645v2TTmplPiGreInPQsD7PerformanceQdPkts OBJECT-TYPE
   SYNTAX      Counter64
   MAX-ACCESS  read-only
   STATUS      current
   DESCRIPTION
      "Path: tunnels.performance.ipsecGreTunnels.inPriorityQueues.d7Performance.queuedPkts

       64 bit unsigned wrappable counter."
   ::= {pr1645v2TTmplPiGreInPQsD7PerformanceEntry 50331648}

pr1645v2TTmplPiGreInPQsD7PerformanceDropPkts OBJECT-TYPE
   SYNTAX      Counter64
   MAX-ACCESS  read-only
   STATUS      current
   DESCRIPTION
      "Path: tunnels.performance.ipsecGreTunnels.inPriorityQueues.d7Performance.droppedPkts

       64 bit unsigned wrappable counter."
   ::= {pr1645v2TTmplPiGreInPQsD7PerformanceEntry 67108864}

pr1645v2TTmplPiGreInPQsD7PerformanceRDropPkts OBJECT-TYPE
   SYNTAX      Counter64
   MAX-ACCESS  read-only
   STATUS      current
   DESCRIPTION
      "Path: tunnels.performance.ipsecGreTunnels.inPriorityQueues.d7Performance.redDroppedPkts

       64 bit unsigned wrappable counter."
   ::= {pr1645v2TTmplPiGreInPQsD7PerformanceEntry 201326592}

pr1645v2TTmplPiGreInPQsD7PerformanceCirTxPkts OBJECT-TYPE
   SYNTAX      Counter64
   MAX-ACCESS  read-only
   STATUS      current
   DESCRIPTION
      "Path: tunnels.performance.ipsecGreTunnels.inPriorityQueues.d7Performance.cirTxPkts

       64 bit unsigned wrappable counter."
   ::= {pr1645v2TTmplPiGreInPQsD7PerformanceEntry 83886080}

pr1645v2TTmplPiGreInPQsD7PerformanceEirTxPkts OBJECT-TYPE
   SYNTAX      Counter64
   MAX-ACCESS  read-only
   STATUS      current
   DESCRIPTION
      "Path: tunnels.performance.ipsecGreTunnels.inPriorityQueues.d7Performance.eirTxPkts

       64 bit unsigned wrappable counter."
   ::= {pr1645v2TTmplPiGreInPQsD7PerformanceEntry 100663296}

pr1645v2TTmplPiGreInPQsD7PerformanceViolTxPkts OBJECT-TYPE
   SYNTAX      Counter64
   MAX-ACCESS  read-only
   STATUS      current
   DESCRIPTION
      "Path: tunnels.performance.ipsecGreTunnels.inPriorityQueues.d7Performance.violateTxPkts

       64 bit unsigned wrappable counter."
   ::= {pr1645v2TTmplPiGreInPQsD7PerformanceEntry 301989888}

pr1645v2TTmplPiGreInPQsD7PerformanceTotOcts OBJECT-TYPE
   SYNTAX      Counter64
   MAX-ACCESS  read-only
   STATUS      current
   DESCRIPTION
      "Path: tunnels.performance.ipsecGreTunnels.inPriorityQueues.d7Performance.totalOctets

       64 bit unsigned wrappable counter."
   ::= {pr1645v2TTmplPiGreInPQsD7PerformanceEntry 251658240}

pr1645v2TTmplPiGreInPQsD7PerformanceDirTxOcts OBJECT-TYPE
   SYNTAX      Counter64
   MAX-ACCESS  read-only
   STATUS      current
   DESCRIPTION
      "Path: tunnels.performance.ipsecGreTunnels.inPriorityQueues.d7Performance.directTxOctets

       64 bit unsigned wrappable counter."
   ::= {pr1645v2TTmplPiGreInPQsD7PerformanceEntry 117440512}

pr1645v2TTmplPiGreInPQsD7PerformanceQdOcts OBJECT-TYPE
   SYNTAX      Counter64
   MAX-ACCESS  read-only
   STATUS      current
   DESCRIPTION
      "Path: tunnels.performance.ipsecGreTunnels.inPriorityQueues.d7Performance.queuedOctets

       64 bit unsigned wrappable counter."
   ::= {pr1645v2TTmplPiGreInPQsD7PerformanceEntry 134217728}

pr1645v2TTmplPiGreInPQsD7PerformanceDropOcts OBJECT-TYPE
   SYNTAX      Counter64
   MAX-ACCESS  read-only
   STATUS      current
   DESCRIPTION
      "Path: tunnels.performance.ipsecGreTunnels.inPriorityQueues.d7Performance.droppedOctets

       64 bit unsigned wrappable counter."
   ::= {pr1645v2TTmplPiGreInPQsD7PerformanceEntry 150994944}

pr1645v2TTmplPiGreInPQsD7PerformanceRDropOcts OBJECT-TYPE
   SYNTAX      Counter64
   MAX-ACCESS  read-only
   STATUS      current
   DESCRIPTION
      "Path: tunnels.performance.ipsecGreTunnels.inPriorityQueues.d7Performance.redDroppedOctets

       64 bit unsigned wrappable counter."
   ::= {pr1645v2TTmplPiGreInPQsD7PerformanceEntry 218103808}

pr1645v2TTmplPiGreInPQsD7PerformanceCirTxOcts OBJECT-TYPE
   SYNTAX      Counter64
   MAX-ACCESS  read-only
   STATUS      current
   DESCRIPTION
      "Path: tunnels.performance.ipsecGreTunnels.inPriorityQueues.d7Performance.cirTxOctets

       64 bit unsigned wrappable counter."
   ::= {pr1645v2TTmplPiGreInPQsD7PerformanceEntry 167772160}

pr1645v2TTmplPiGreInPQsD7PerformanceEirTxOcts OBJECT-TYPE
   SYNTAX      Counter64
   MAX-ACCESS  read-only
   STATUS      current
   DESCRIPTION
      "Path: tunnels.performance.ipsecGreTunnels.inPriorityQueues.d7Performance.eirTxOctets

       64 bit unsigned wrappable counter."
   ::= {pr1645v2TTmplPiGreInPQsD7PerformanceEntry 184549376}

pr1645v2TTmplPiGreInPQsD7PerformanceViolTxOcts OBJECT-TYPE
   SYNTAX      Counter64
   MAX-ACCESS  read-only
   STATUS      current
   DESCRIPTION
      "Path: tunnels.performance.ipsecGreTunnels.inPriorityQueues.d7Performance.violateTxOctets

       64 bit unsigned wrappable counter."
   ::= {pr1645v2TTmplPiGreInPQsD7PerformanceEntry 318767104}

pr1645v2TTmplPiGreInPQsD7PerformanceBandwidth OBJECT-TYPE
   SYNTAX      Integer32
   MAX-ACCESS  read-only
   STATUS      current
   DESCRIPTION
      "Path: tunnels.performance.ipsecGreTunnels.inPriorityQueues.d7Performance.bandwidth

       unit name = bps
       formula = 8 * ; 8 /"
   ::= {pr1645v2TTmplPiGreInPQsD7PerformanceEntry 268435456}

pr1645v2TTmplPiGreOutPQs OBJECT-TYPE
   SYNTAX      SEQUENCE OF Pr1645v2TTmplPiGreOutPQsEntry
   MAX-ACCESS  not-accessible
   STATUS      current
   DESCRIPTION
      ""
   ::= {pr1645v2TTmplPiGre 83886080}

pr1645v2TTmplPiGreOutPQsEntry OBJECT-TYPE
   SYNTAX      Pr1645v2TTmplPiGreOutPQsEntry
   MAX-ACCESS  not-accessible
   STATUS      current
   DESCRIPTION
      ""
   INDEX      { pr1645v2TTmplPiGreTableIx,
                pr1645v2TTmplPiGreOutPQsTableIx }
   ::= {pr1645v2TTmplPiGreOutPQs 1}

Pr1645v2TTmplPiGreOutPQsEntry ::=
   SEQUENCE
      {
      pr1645v2TTmplPiGreOutPQsTableIx
         TableIndex,
      pr1645v2TTmplPiGreOutPQsName
         INTEGER,
      pr1645v2TTmplPiGreOutPQsLength
         Integer32,
      pr1645v2TTmplPiGreOutPQsOctetLength
         Integer32,
      pr1645v2TTmplPiGreOutPQsRedLength
         Integer32,
      pr1645v2TTmplPiGreOutPQsPacketsTotal
         Counter64,
      pr1645v2TTmplPiGreOutPQsPacketsDirectTx
         Counter64,
      pr1645v2TTmplPiGreOutPQsPacketsQueued
         Counter64,
      pr1645v2TTmplPiGreOutPQsPacketsDropped
         Counter64,
      pr1645v2TTmplPiGreOutPQsPacketsRedDropped
         Counter64,
      pr1645v2TTmplPiGreOutPQsPacketsCirTx
         Counter64,
      pr1645v2TTmplPiGreOutPQsPacketsEirTx
         Counter64,
      pr1645v2TTmplPiGreOutPQsPacketsViolateTx
         Counter64,
      pr1645v2TTmplPiGreOutPQsOctetsTotal
         Counter64,
      pr1645v2TTmplPiGreOutPQsOctetsDirectTx
         Counter64,
      pr1645v2TTmplPiGreOutPQsOctetsQueued
         Counter64,
      pr1645v2TTmplPiGreOutPQsOctetsDropped
         Counter64,
      pr1645v2TTmplPiGreOutPQsOctetsRedDropped
         Counter64,
      pr1645v2TTmplPiGreOutPQsOctetsCirTx
         Counter64,
      pr1645v2TTmplPiGreOutPQsOctetsEirTx
         Counter64,
      pr1645v2TTmplPiGreOutPQsOctetsViolateTx
         Counter64,
      pr1645v2TTmplPiGreOutPQsOctetsBandwidth15sec
         Integer32,
      pr1645v2TTmplPiGreOutPQsOctetsBandwidth30sec
         Integer32,
      pr1645v2TTmplPiGreOutPQsOctetsBandwidth1min
         Integer32,
      pr1645v2TTmplPiGreOutPQsOctetsBandwidth2min
         Integer32,
      pr1645v2TTmplPiGreOutPQsOctetsBandwidth5min
         Integer32
      }

pr1645v2TTmplPiGreOutPQsTableIx OBJECT-TYPE
   SYNTAX      TableIndex
   MAX-ACCESS  not-accessible
   STATUS      current
   DESCRIPTION
      ""
   ::= {pr1645v2TTmplPiGreOutPQsEntry 11}

pr1645v2TTmplPiGreOutPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: tunnels.performance.ipsecGreTunnels.outPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2TTmplPiGreOutPQsEntry 16777216}

pr1645v2TTmplPiGreOutPQsLength OBJECT-TYPE
   SYNTAX      Integer32
   MAX-ACCESS  read-only
   STATUS      current
   DESCRIPTION
      "Path: tunnels.performance.ipsecGreTunnels.outPriorityQueues.length"
   ::= {pr1645v2TTmplPiGreOutPQsEntry 33554432}

pr1645v2TTmplPiGreOutPQsOctetLength OBJECT-TYPE
   SYNTAX      Integer32
   MAX-ACCESS  read-only
   STATUS      current
   DESCRIPTION
      "Path: tunnels.performance.ipsecGreTunnels.outPriorityQueues.octetLength"
   ::= {pr1645v2TTmplPiGreOutPQsEntry 150994944}

pr1645v2TTmplPiGreOutPQsRedLength OBJECT-TYPE
   SYNTAX      Integer32
   MAX-ACCESS  read-only
   STATUS      current
   DESCRIPTION
      "Path: tunnels.performance.ipsecGreTunnels.outPriorityQueues.redLength"
   ::= {pr1645v2TTmplPiGreOutPQsEntry 134217728}

pr1645v2TTmplPiGreOutPQsPacketsTotal OBJECT-TYPE
   SYNTAX      Counter64
   MAX-ACCESS  read-only
   STATUS      current
   DESCRIPTION
      "Path: tunnels.performance.ipsecGreTunnels.outPriorityQueues.packets.total

       64 bit unsigned wrappable counter."
   ::= {pr1645v2TTmplPiGreOutPQsEntry 50790400}

pr1645v2TTmplPiGreOutPQsPacketsDirectTx OBJECT-TYPE
   SYNTAX      Counter64
   MAX-ACCESS  read-only
   STATUS      current
   DESCRIPTION
      "Path: tunnels.performance.ipsecGreTunnels.outPriorityQueues.packets.directTx

       64 bit unsigned wrappable counter."
   ::= {pr1645v2TTmplPiGreOutPQsEntry 50397184}

pr1645v2TTmplPiGreOutPQsPacketsQueued OBJECT-TYPE
   SYNTAX      Counter64
   MAX-ACCESS  read-only
   STATUS      current
   DESCRIPTION
      "Path: tunnels.performance.ipsecGreTunnels.outPriorityQueues.packets.queued

       64 bit unsigned wrappable counter."
   ::= {pr1645v2TTmplPiGreOutPQsEntry 50462720}

pr1645v2TTmplPiGreOutPQsPacketsDropped OBJECT-TYPE
   SYNTAX      Counter64
   MAX-ACCESS  read-only
   STATUS      current
   DESCRIPTION
      "Path: tunnels.performance.ipsecGreTunnels.outPriorityQueues.packets.dropped

       64 bit unsigned wrappable counter."
   ::= {pr1645v2TTmplPiGreOutPQsEntry 50528256}

pr1645v2TTmplPiGreOutPQsPacketsRedDropped OBJECT-TYPE
   SYNTAX      Counter64
   MAX-ACCESS  read-only
   STATUS      current
   DESCRIPTION
      "Path: tunnels.performance.ipsecGreTunnels.outPriorityQueues.packets.redDropped

       64 bit unsigned wrappable counter."
   ::= {pr1645v2TTmplPiGreOutPQsEntry 50724864}

pr1645v2TTmplPiGreOutPQsPacketsCirTx OBJECT-TYPE
   SYNTAX      Counter64
   MAX-ACCESS  read-only
   STATUS      current
   DESCRIPTION
      "Path: tunnels.performance.ipsecGreTunnels.outPriorityQueues.packets.cirTx

       64 bit unsigned wrappable counter."
   ::= {pr1645v2TTmplPiGreOutPQsEntry 50593792}

pr1645v2TTmplPiGreOutPQsPacketsEirTx OBJECT-TYPE
   SYNTAX      Counter64
   MAX-ACCESS  read-only
   STATUS      current
   DESCRIPTION
      "Path: tunnels.performance.ipsecGreTunnels.outPriorityQueues.packets.eirTx

       64 bit unsigned wrappable counter."
   ::= {pr1645v2TTmplPiGreOutPQsEntry 50659328}

pr1645v2TTmplPiGreOutPQsPacketsViolateTx OBJECT-TYPE
   SYNTAX      Counter64
   MAX-ACCESS  read-only
   STATUS      current
   DESCRIPTION
      "Path: tunnels.performance.ipsecGreTunnels.outPriorityQueues.packets.violateTx

       64 bit unsigned wrappable counter."
   ::= {pr1645v2TTmplPiGreOutPQsEntry 50855936}

pr1645v2TTmplPiGreOutPQsOctetsTotal OBJECT-TYPE
   SYNTAX      Counter64
   MAX-ACCESS  read-only
   STATUS      current
   DESCRIPTION
      "Path: tunnels.performance.ipsecGreTunnels.outPriorityQueues.octets.total

       64 bit unsigned wrappable counter."
   ::= {pr1645v2TTmplPiGreOutPQsEntry 67567616}

pr1645v2TTmplPiGreOutPQsOctetsDirectTx OBJECT-TYPE
   SYNTAX      Counter64
   MAX-ACCESS  read-only
   STATUS      current
   DESCRIPTION
      "Path: tunnels.performance.ipsecGreTunnels.outPriorityQueues.octets.directTx

       64 bit unsigned wrappable counter."
   ::= {pr1645v2TTmplPiGreOutPQsEntry 67174400}

pr1645v2TTmplPiGreOutPQsOctetsQueued OBJECT-TYPE
   SYNTAX      Counter64
   MAX-ACCESS  read-only
   STATUS      current
   DESCRIPTION
      "Path: tunnels.performance.ipsecGreTunnels.outPriorityQueues.octets.queued

       64 bit unsigned wrappable counter."
   ::= {pr1645v2TTmplPiGreOutPQsEntry 67239936}

pr1645v2TTmplPiGreOutPQsOctetsDropped OBJECT-TYPE
   SYNTAX      Counter64
   MAX-ACCESS  read-only
   STATUS      current
   DESCRIPTION
      "Path: tunnels.performance.ipsecGreTunnels.outPriorityQueues.octets.dropped

       64 bit unsigned wrappable counter."
   ::= {pr1645v2TTmplPiGreOutPQsEntry 67305472}

pr1645v2TTmplPiGreOutPQsOctetsRedDropped OBJECT-TYPE
   SYNTAX      Counter64
   MAX-ACCESS  read-only
   STATUS      current
   DESCRIPTION
      "Path: tunnels.performance.ipsecGreTunnels.outPriorityQueues.octets.redDropped

       64 bit unsigned wrappable counter."
   ::= {pr1645v2TTmplPiGreOutPQsEntry 67502080}

pr1645v2TTmplPiGreOutPQsOctetsCirTx OBJECT-TYPE
   SYNTAX      Counter64
   MAX-ACCESS  read-only
   STATUS      current
   DESCRIPTION
      "Path: tunnels.performance.ipsecGreTunnels.outPriorityQueues.octets.cirTx

       64 bit unsigned wrappable counter."
   ::= {pr1645v2TTmplPiGreOutPQsEntry 67371008}

pr1645v2TTmplPiGreOutPQsOctetsEirTx OBJECT-TYPE
   SYNTAX      Counter64
   MAX-ACCESS  read-only
   STATUS      current
   DESCRIPTION
      "Path: tunnels.performance.ipsecGreTunnels.outPriorityQueues.octets.eirTx

       64 bit unsigned wrappable counter."
   ::= {pr1645v2TTmplPiGreOutPQsEntry 67436544}

pr1645v2TTmplPiGreOutPQsOctetsViolateTx OBJECT-TYPE
   SYNTAX      Counter64
   MAX-ACCESS  read-only
   STATUS      current
   DESCRIPTION
      "Path: tunnels.performance.ipsecGreTunnels.outPriorityQueues.octets.violateTx

       64 bit unsigned wrappable counter."
   ::= {pr1645v2TTmplPiGreOutPQsEntry 67633152}

pr1645v2TTmplPiGreOutPQsOctetsBandwidth15sec OBJECT-TYPE
   SYNTAX      Integer32
   MAX-ACCESS  read-only
   STATUS      current
   DESCRIPTION
      "Path: tunnels.performance.ipsecGreTunnels.outPriorityQueues.octets.bandwidth.15sec

       unit name = bps
       formula = 8 * ; 8 /"
   ::= {pr1645v2TTmplPiGreOutPQsEntry 70386944}

pr1645v2TTmplPiGreOutPQsOctetsBandwidth30sec OBJECT-TYPE
   SYNTAX      Integer32
   MAX-ACCESS  read-only
   STATUS      current
   DESCRIPTION
      "Path: tunnels.performance.ipsecGreTunnels.outPriorityQueues.octets.bandwidth.30sec

       unit name = bps
       formula = 8 * ; 8 /"
   ::= {pr1645v2TTmplPiGreOutPQsEntry 70388224}

pr1645v2TTmplPiGreOutPQsOctetsBandwidth1min OBJECT-TYPE
   SYNTAX      Integer32
   MAX-ACCESS  read-only
   STATUS      current
   DESCRIPTION
      "Path: tunnels.performance.ipsecGreTunnels.outPriorityQueues.octets.bandwidth.1min

       unit name = bps
       formula = 8 * ; 8 /"
   ::= {pr1645v2TTmplPiGreOutPQsEntry 70390784}

pr1645v2TTmplPiGreOutPQsOctetsBandwidth2min OBJECT-TYPE
   SYNTAX      Integer32
   MAX-ACCESS  read-only
   STATUS      current
   DESCRIPTION
      "Path: tunnels.performance.ipsecGreTunnels.outPriorityQueues.octets.bandwidth.2min

       unit name = bps
       formula = 8 * ; 8 /"
   ::= {pr1645v2TTmplPiGreOutPQsEntry 70395904}

pr1645v2TTmplPiGreOutPQsOctetsBandwidth5min OBJECT-TYPE
   SYNTAX      Integer32
   MAX-ACCESS  read-only
   STATUS      current
   DESCRIPTION
      "Path: tunnels.performance.ipsecGreTunnels.outPriorityQueues.octets.bandwidth.5min

       unit name = bps
       formula = 8 * ; 8 /"
   ::= {pr1645v2TTmplPiGreOutPQsEntry 70411264}

pr1645v2TTmplPiGreOutPQsH2Performance OBJECT-TYPE
   SYNTAX      SEQUENCE OF Pr1645v2TTmplPiGreOutPQsH2PerformanceEntry
   MAX-ACCESS  not-accessible
   STATUS      current
   DESCRIPTION
      ""
   ::= {pr1645v2TTmplPiGre 84213760}

pr1645v2TTmplPiGreOutPQsH2PerformanceEntry OBJECT-TYPE
   SYNTAX      Pr1645v2TTmplPiGreOutPQsH2PerformanceEntry
   MAX-ACCESS  not-accessible
   STATUS      current
   DESCRIPTION
      ""
   INDEX      { pr1645v2TTmplPiGreTableIx,
                pr1645v2TTmplPiGreOutPQsTableIx,
                pr1645v2TTmplPiGreOutPQsH2PerformanceTableIx }
   ::= {pr1645v2TTmplPiGreOutPQsH2Performance 1}

Pr1645v2TTmplPiGreOutPQsH2PerformanceEntry ::=
   SEQUENCE
      {
      pr1645v2TTmplPiGreOutPQsH2PerformanceTableIx
         TableIndex,
      pr1645v2TTmplPiGreOutPQsH2PerformanceSysUpTime
         TimeTicks,
      pr1645v2TTmplPiGreOutPQsH2PerformanceTotPkts
         Counter64,
      pr1645v2TTmplPiGreOutPQsH2PerformanceDirTxPkts
         Counter64,
      pr1645v2TTmplPiGreOutPQsH2PerformanceQdPkts
         Counter64,
      pr1645v2TTmplPiGreOutPQsH2PerformanceDropPkts
         Counter64,
      pr1645v2TTmplPiGreOutPQsH2PerformanceRDropPkts
         Counter64,
      pr1645v2TTmplPiGreOutPQsH2PerformanceCirTxPkts
         Counter64,
      pr1645v2TTmplPiGreOutPQsH2PerformanceEirTxPkts
         Counter64,
      pr1645v2TTmplPiGreOutPQsH2PerformanceViolTxPkts
         Counter64,
      pr1645v2TTmplPiGreOutPQsH2PerformanceTotOcts
         Counter64,
      pr1645v2TTmplPiGreOutPQsH2PerformanceDirTxOcts
         Counter64,
      pr1645v2TTmplPiGreOutPQsH2PerformanceQdOcts
         Counter64,
      pr1645v2TTmplPiGreOutPQsH2PerformanceDropOcts
         Counter64,
      pr1645v2TTmplPiGreOutPQsH2PerformanceRDropOcts
         Counter64,
      pr1645v2TTmplPiGreOutPQsH2PerformanceCirTxOcts
         Counter64,
      pr1645v2TTmplPiGreOutPQsH2PerformanceEirTxOcts
         Counter64,
      pr1645v2TTmplPiGreOutPQsH2PerformanceViolTxOcts
         Counter64,
      pr1645v2TTmplPiGreOutPQsH2PerformanceBandwidth
         Integer32
      }

pr1645v2TTmplPiGreOutPQsH2PerformanceTableIx OBJECT-TYPE
   SYNTAX      TableIndex
   MAX-ACCESS  not-accessible
   STATUS      current
   DESCRIPTION
      ""
   ::= {pr1645v2TTmplPiGreOutPQsH2PerformanceEntry 11}

pr1645v2TTmplPiGreOutPQsH2PerformanceSysUpTime OBJECT-TYPE
   SYNTAX      TimeTicks
   MAX-ACCESS  read-only
   STATUS      current
   DESCRIPTION
      "Path: tunnels.performance.ipsecGreTunnels.outPriorityQueues.h2Performance.sysUpTime

       Time in centi-second."
   ::= {pr1645v2TTmplPiGreOutPQsH2PerformanceEntry 16777216}

pr1645v2TTmplPiGreOutPQsH2PerformanceTotPkts OBJECT-TYPE
   SYNTAX      Counter64
   MAX-ACCESS  read-only
   STATUS      current
   DESCRIPTION
      "Path: tunnels.performance.ipsecGreTunnels.outPriorityQueues.h2Performance.totalPkts

       64 bit unsigned wrappable counter."
   ::= {pr1645v2TTmplPiGreOutPQsH2PerformanceEntry 234881024}

pr1645v2TTmplPiGreOutPQsH2PerformanceDirTxPkts OBJECT-TYPE
   SYNTAX      Counter64
   MAX-ACCESS  read-only
   STATUS      current
   DESCRIPTION
      "Path: tunnels.performance.ipsecGreTunnels.outPriorityQueues.h2Performance.directTxPkts

       64 bit unsigned wrappable counter."
   ::= {pr1645v2TTmplPiGreOutPQsH2PerformanceEntry 33554432}

pr1645v2TTmplPiGreOutPQsH2PerformanceQdPkts OBJECT-TYPE
   SYNTAX      Counter64
   MAX-ACCESS  read-only
   STATUS      current
   DESCRIPTION
      "Path: tunnels.performance.ipsecGreTunnels.outPriorityQueues.h2Performance.queuedPkts

       64 bit unsigned wrappable counter."
   ::= {pr1645v2TTmplPiGreOutPQsH2PerformanceEntry 50331648}

pr1645v2TTmplPiGreOutPQsH2PerformanceDropPkts OBJECT-TYPE
   SYNTAX      Counter64
   MAX-ACCESS  read-only
   STATUS      current
   DESCRIPTION
      "Path: tunnels.performance.ipsecGreTunnels.outPriorityQueues.h2Performance.droppedPkts

       64 bit unsigned wrappable counter."
   ::= {pr1645v2TTmplPiGreOutPQsH2PerformanceEntry 67108864}

pr1645v2TTmplPiGreOutPQsH2PerformanceRDropPkts OBJECT-TYPE
   SYNTAX      Counter64
   MAX-ACCESS  read-only
   STATUS      current
   DESCRIPTION
      "Path: tunnels.performance.ipsecGreTunnels.outPriorityQueues.h2Performance.redDroppedPkts

       64 bit unsigned wrappable counter."
   ::= {pr1645v2TTmplPiGreOutPQsH2PerformanceEntry 201326592}

pr1645v2TTmplPiGreOutPQsH2PerformanceCirTxPkts OBJECT-TYPE
   SYNTAX      Counter64
   MAX-ACCESS  read-only
   STATUS      current
   DESCRIPTION
      "Path: tunnels.performance.ipsecGreTunnels.outPriorityQueues.h2Performance.cirTxPkts

       64 bit unsigned wrappable counter."
   ::= {pr1645v2TTmplPiGreOutPQsH2PerformanceEntry 83886080}

pr1645v2TTmplPiGreOutPQsH2PerformanceEirTxPkts OBJECT-TYPE
   SYNTAX      Counter64
   MAX-ACCESS  read-only
   STATUS      current
   DESCRIPTION
      "Path: tunnels.performance.ipsecGreTunnels.outPriorityQueues.h2Performance.eirTxPkts

       64 bit unsigned wrappable counter."
   ::= {pr1645v2TTmplPiGreOutPQsH2PerformanceEntry 100663296}

pr1645v2TTmplPiGreOutPQsH2PerformanceViolTxPkts OBJECT-TYPE
   SYNTAX      Counter64
   MAX-ACCESS  read-only
   STATUS      current
   DESCRIPTION
      "Path: tunnels.performance.ipsecGreTunnels.outPriorityQueues.h2Performance.violateTxPkts

       64 bit unsigned wrappable counter."
   ::= {pr1645v2TTmplPiGreOutPQsH2PerformanceEntry 301989888}

pr1645v2TTmplPiGreOutPQsH2PerformanceTotOcts OBJECT-TYPE
   SYNTAX      Counter64
   MAX-ACCESS  read-only
   STATUS      current
   DESCRIPTION
      "Path: tunnels.performance.ipsecGreTunnels.outPriorityQueues.h2Performance.totalOctets

       64 bit unsigned wrappable counter."
   ::= {pr1645v2TTmplPiGreOutPQsH2PerformanceEntry 251658240}

pr1645v2TTmplPiGreOutPQsH2PerformanceDirTxOcts OBJECT-TYPE
   SYNTAX      Counter64
   MAX-ACCESS  read-only
   STATUS      current
   DESCRIPTION
      "Path: tunnels.performance.ipsecGreTunnels.outPriorityQueues.h2Performance.directTxOctets

       64 bit unsigned wrappable counter."
   ::= {pr1645v2TTmplPiGreOutPQsH2PerformanceEntry 117440512}

pr1645v2TTmplPiGreOutPQsH2PerformanceQdOcts OBJECT-TYPE
   SYNTAX      Counter64
   MAX-ACCESS  read-only
   STATUS      current
   DESCRIPTION
      "Path: tunnels.performance.ipsecGreTunnels.outPriorityQueues.h2Performance.queuedOctets

       64 bit unsigned wrappable counter."
   ::= {pr1645v2TTmplPiGreOutPQsH2PerformanceEntry 134217728}

pr1645v2TTmplPiGreOutPQsH2PerformanceDropOcts OBJECT-TYPE
   SYNTAX      Counter64
   MAX-ACCESS  read-only
   STATUS      current
   DESCRIPTION
      "Path: tunnels.performance.ipsecGreTunnels.outPriorityQueues.h2Performance.droppedOctets

       64 bit unsigned wrappable counter."
   ::= {pr1645v2TTmplPiGreOutPQsH2PerformanceEntry 150994944}

pr1645v2TTmplPiGreOutPQsH2PerformanceRDropOcts OBJECT-TYPE
   SYNTAX      Counter64
   MAX-ACCESS  read-only
   STATUS      current
   DESCRIPTION
      "Path: tunnels.performance.ipsecGreTunnels.outPriorityQueues.h2Performance.redDroppedOctets

       64 bit unsigned wrappable counter."
   ::= {pr1645v2TTmplPiGreOutPQsH2PerformanceEntry 218103808}

pr1645v2TTmplPiGreOutPQsH2PerformanceCirTxOcts OBJECT-TYPE
   SYNTAX      Counter64
   MAX-ACCESS  read-only
   STATUS      current
   DESCRIPTION
      "Path: tunnels.performance.ipsecGreTunnels.outPriorityQueues.h2Performance.cirTxOctets

       64 bit unsigned wrappable counter."
   ::= {pr1645v2TTmplPiGreOutPQsH2PerformanceEntry 167772160}

pr1645v2TTmplPiGreOutPQsH2PerformanceEirTxOcts OBJECT-TYPE
   SYNTAX      Counter64
   MAX-ACCESS  read-only
   STATUS      current
   DESCRIPTION
      "Path: tunnels.performance.ipsecGreTunnels.outPriorityQueues.h2Performance.eirTxOctets

       64 bit unsigned wrappable counter."
   ::= {pr1645v2TTmplPiGreOutPQsH2PerformanceEntry 184549376}

pr1645v2TTmplPiGreOutPQsH2PerformanceViolTxOcts OBJECT-TYPE
   SYNTAX      Counter64
   MAX-ACCESS  read-only
   STATUS      current
   DESCRIPTION
      "Path: tunnels.performance.ipsecGreTunnels.outPriorityQueues.h2Performance.violateTxOctets

       64 bit unsigned wrappable counter."
   ::= {pr1645v2TTmplPiGreOutPQsH2PerformanceEntry 318767104}

pr1645v2TTmplPiGreOutPQsH2PerformanceBandwidth OBJECT-TYPE
   SYNTAX      Integer32
   MAX-ACCESS  read-only
   STATUS      current
   DESCRIPTION
      "Path: tunnels.performance.ipsecGreTunnels.outPriorityQueues.h2Performance.bandwidth

       unit name = bps
       formula = 8 * ; 8 /"
   ::= {pr1645v2TTmplPiGreOutPQsH2PerformanceEntry 268435456}

pr1645v2TTmplPiGreOutPQsH24Performance OBJECT-TYPE
   SYNTAX      SEQUENCE OF Pr1645v2TTmplPiGreOutPQsH24PerformanceEntry
   MAX-ACCESS  not-accessible
   STATUS      current
   DESCRIPTION
      ""
   ::= {pr1645v2TTmplPiGre 84279296}

pr1645v2TTmplPiGreOutPQsH24PerformanceEntry OBJECT-TYPE
   SYNTAX      Pr1645v2TTmplPiGreOutPQsH24PerformanceEntry
   MAX-ACCESS  not-accessible
   STATUS      current
   DESCRIPTION
      ""
   INDEX      { pr1645v2TTmplPiGreTableIx,
                pr1645v2TTmplPiGreOutPQsTableIx,
                pr1645v2TTmplPiGreOutPQsH24PerformanceTableIx }
   ::= {pr1645v2TTmplPiGreOutPQsH24Performance 1}

Pr1645v2TTmplPiGreOutPQsH24PerformanceEntry ::=
   SEQUENCE
      {
      pr1645v2TTmplPiGreOutPQsH24PerformanceTableIx
         TableIndex,
      pr1645v2TTmplPiGreOutPQsH24PerformanceSysUpTime
         TimeTicks,
      pr1645v2TTmplPiGreOutPQsH24PerformanceTotPkts
         Counter64,
      pr1645v2TTmplPiGreOutPQsH24PerformanceDirTxPkts
         Counter64,
      pr1645v2TTmplPiGreOutPQsH24PerformanceQdPkts
         Counter64,
      pr1645v2TTmplPiGreOutPQsH24PerformanceDropPkts
         Counter64,
      pr1645v2TTmplPiGreOutPQsH24PerformanceRDropPkts
         Counter64,
      pr1645v2TTmplPiGreOutPQsH24PerformanceCirTxPkts
         Counter64,
      pr1645v2TTmplPiGreOutPQsH24PerformanceEirTxPkts
         Counter64,
      pr1645v2TTmplPiGreOutPQsH24PerformanceViolTxPkts
         Counter64,
      pr1645v2TTmplPiGreOutPQsH24PerformanceTotOcts
         Counter64,
      pr1645v2TTmplPiGreOutPQsH24PerformanceDirTxOcts
         Counter64,
      pr1645v2TTmplPiGreOutPQsH24PerformanceQdOcts
         Counter64,
      pr1645v2TTmplPiGreOutPQsH24PerformanceDropOcts
         Counter64,
      pr1645v2TTmplPiGreOutPQsH24PerformanceRDropOcts
         Counter64,
      pr1645v2TTmplPiGreOutPQsH24PerformanceCirTxOcts
         Counter64,
      pr1645v2TTmplPiGreOutPQsH24PerformanceEirTxOcts
         Counter64,
      pr1645v2TTmplPiGreOutPQsH24PerformanceViolTxOcts
         Counter64,
      pr1645v2TTmplPiGreOutPQsH24PerformanceBandwidth
         Integer32
      }

pr1645v2TTmplPiGreOutPQsH24PerformanceTableIx OBJECT-TYPE
   SYNTAX      TableIndex
   MAX-ACCESS  not-accessible
   STATUS      current
   DESCRIPTION
      ""
   ::= {pr1645v2TTmplPiGreOutPQsH24PerformanceEntry 11}

pr1645v2TTmplPiGreOutPQsH24PerformanceSysUpTime OBJECT-TYPE
   SYNTAX      TimeTicks
   MAX-ACCESS  read-only
   STATUS      current
   DESCRIPTION
      "Path: tunnels.performance.ipsecGreTunnels.outPriorityQueues.h24Performance.sysUpTime

       Time in centi-second."
   ::= {pr1645v2TTmplPiGreOutPQsH24PerformanceEntry 16777216}

pr1645v2TTmplPiGreOutPQsH24PerformanceTotPkts OBJECT-TYPE
   SYNTAX      Counter64
   MAX-ACCESS  read-only
   STATUS      current
   DESCRIPTION
      "Path: tunnels.performance.ipsecGreTunnels.outPriorityQueues.h24Performance.totalPkts

       64 bit unsigned wrappable counter."
   ::= {pr1645v2TTmplPiGreOutPQsH24PerformanceEntry 234881024}

pr1645v2TTmplPiGreOutPQsH24PerformanceDirTxPkts OBJECT-TYPE
   SYNTAX      Counter64
   MAX-ACCESS  read-only
   STATUS      current
   DESCRIPTION
      "Path: tunnels.performance.ipsecGreTunnels.outPriorityQueues.h24Performance.directTxPkts

       64 bit unsigned wrappable counter."
   ::= {pr1645v2TTmplPiGreOutPQsH24PerformanceEntry 33554432}

pr1645v2TTmplPiGreOutPQsH24PerformanceQdPkts OBJECT-TYPE
   SYNTAX      Counter64
   MAX-ACCESS  read-only
   STATUS      current
   DESCRIPTION
      "Path: tunnels.performance.ipsecGreTunnels.outPriorityQueues.h24Performance.queuedPkts

       64 bit unsigned wrappable counter."
   ::= {pr1645v2TTmplPiGreOutPQsH24PerformanceEntry 50331648}

pr1645v2TTmplPiGreOutPQsH24PerformanceDropPkts OBJECT-TYPE
   SYNTAX      Counter64
   MAX-ACCESS  read-only
   STATUS      current
   DESCRIPTION
      "Path: tunnels.performance.ipsecGreTunnels.outPriorityQueues.h24Performance.droppedPkts

       64 bit unsigned wrappable counter."
   ::= {pr1645v2TTmplPiGreOutPQsH24PerformanceEntry 67108864}

pr1645v2TTmplPiGreOutPQsH24PerformanceRDropPkts OBJECT-TYPE
   SYNTAX      Counter64
   MAX-ACCESS  read-only
   STATUS      current
   DESCRIPTION
      "Path: tunnels.performance.ipsecGreTunnels.outPriorityQueues.h24Performance.redDroppedPkts

       64 bit unsigned wrappable counter."
   ::= {pr1645v2TTmplPiGreOutPQsH24PerformanceEntry 201326592}

pr1645v2TTmplPiGreOutPQsH24PerformanceCirTxPkts OBJECT-TYPE
   SYNTAX      Counter64
   MAX-ACCESS  read-only
   STATUS      current
   DESCRIPTION
      "Path: tunnels.performance.ipsecGreTunnels.outPriorityQueues.h24Performance.cirTxPkts

       64 bit unsigned wrappable counter."
   ::= {pr1645v2TTmplPiGreOutPQsH24PerformanceEntry 83886080}

pr1645v2TTmplPiGreOutPQsH24PerformanceEirTxPkts OBJECT-TYPE
   SYNTAX      Counter64
   MAX-ACCESS  read-only
   STATUS      current
   DESCRIPTION
      "Path: tunnels.performance.ipsecGreTunnels.outPriorityQueues.h24Performance.eirTxPkts

       64 bit unsigned wrappable counter."
   ::= {pr1645v2TTmplPiGreOutPQsH24PerformanceEntry 100663296}

pr1645v2TTmplPiGreOutPQsH24PerformanceViolTxPkts OBJECT-TYPE
   SYNTAX      Counter64
   MAX-ACCESS  read-only
   STATUS      current
   DESCRIPTION
      "Path: tunnels.performance.ipsecGreTunnels.outPriorityQueues.h24Performance.violateTxPkts

       64 bit unsigned wrappable counter."
   ::= {pr1645v2TTmplPiGreOutPQsH24PerformanceEntry 301989888}

pr1645v2TTmplPiGreOutPQsH24PerformanceTotOcts OBJECT-TYPE
   SYNTAX      Counter64
   MAX-ACCESS  read-only
   STATUS      current
   DESCRIPTION
      "Path: tunnels.performance.ipsecGreTunnels.outPriorityQueues.h24Performance.totalOctets

       64 bit unsigned wrappable counter."
   ::= {pr1645v2TTmplPiGreOutPQsH24PerformanceEntry 251658240}

pr1645v2TTmplPiGreOutPQsH24PerformanceDirTxOcts OBJECT-TYPE
   SYNTAX      Counter64
   MAX-ACCESS  read-only
   STATUS      current
   DESCRIPTION
      "Path: tunnels.performance.ipsecGreTunnels.outPriorityQueues.h24Performance.directTxOctets

       64 bit unsigned wrappable counter."
   ::= {pr1645v2TTmplPiGreOutPQsH24PerformanceEntry 117440512}

pr1645v2TTmplPiGreOutPQsH24PerformanceQdOcts OBJECT-TYPE
   SYNTAX      Counter64
   MAX-ACCESS  read-only
   STATUS      current
   DESCRIPTION
      "Path: tunnels.performance.ipsecGreTunnels.outPriorityQueues.h24Performance.queuedOctets

       64 bit unsigned wrappable counter."
   ::= {pr1645v2TTmplPiGreOutPQsH24PerformanceEntry 134217728}

pr1645v2TTmplPiGreOutPQsH24PerformanceDropOcts OBJECT-TYPE
   SYNTAX      Counter64
   MAX-ACCESS  read-only
   STATUS      current
   DESCRIPTION
      "Path: tunnels.performance.ipsecGreTunnels.outPriorityQueues.h24Performance.droppedOctets

       64 bit unsigned wrappable counter."
   ::= {pr1645v2TTmplPiGreOutPQsH24PerformanceEntry 150994944}

pr1645v2TTmplPiGreOutPQsH24PerformanceRDropOcts OBJECT-TYPE
   SYNTAX      Counter64
   MAX-ACCESS  read-only
   STATUS      current
   DESCRIPTION
      "Path: tunnels.performance.ipsecGreTunnels.outPriorityQueues.h24Performance.redDroppedOctets

       64 bit unsigned wrappable counter."
   ::= {pr1645v2TTmplPiGreOutPQsH24PerformanceEntry 218103808}

pr1645v2TTmplPiGreOutPQsH24PerformanceCirTxOcts OBJECT-TYPE
   SYNTAX      Counter64
   MAX-ACCESS  read-only
   STATUS      current
   DESCRIPTION
      "Path: tunnels.performance.ipsecGreTunnels.outPriorityQueues.h24Performance.cirTxOctets

       64 bit unsigned wrappable counter."
   ::= {pr1645v2TTmplPiGreOutPQsH24PerformanceEntry 167772160}

pr1645v2TTmplPiGreOutPQsH24PerformanceEirTxOcts OBJECT-TYPE
   SYNTAX      Counter64
   MAX-ACCESS  read-only
   STATUS      current
   DESCRIPTION
      "Path: tunnels.performance.ipsecGreTunnels.outPriorityQueues.h24Performance.eirTxOctets

       64 bit unsigned wrappable counter."
   ::= {pr1645v2TTmplPiGreOutPQsH24PerformanceEntry 184549376}

pr1645v2TTmplPiGreOutPQsH24PerformanceViolTxOcts OBJECT-TYPE
   SYNTAX      Counter64
   MAX-ACCESS  read-only
   STATUS      current
   DESCRIPTION
      "Path: tunnels.performance.ipsecGreTunnels.outPriorityQueues.h24Performance.violateTxOctets

       64 bit unsigned wrappable counter."
   ::= {pr1645v2TTmplPiGreOutPQsH24PerformanceEntry 318767104}

pr1645v2TTmplPiGreOutPQsH24PerformanceBandwidth OBJECT-TYPE
   SYNTAX      Integer32
   MAX-ACCESS  read-only
   STATUS      current
   DESCRIPTION
      "Path: tunnels.performance.ipsecGreTunnels.outPriorityQueues.h24Performance.bandwidth

       unit name = bps
       formula = 8 * ; 8 /"
   ::= {pr1645v2TTmplPiGreOutPQsH24PerformanceEntry 268435456}

pr1645v2TTmplPiGreOutPQsD7Performance OBJECT-TYPE
   SYNTAX      SEQUENCE OF Pr1645v2TTmplPiGreOutPQsD7PerformanceEntry
   MAX-ACCESS  not-accessible
   STATUS      current
   DESCRIPTION
      ""
   ::= {pr1645v2TTmplPiGre 84344832}

pr1645v2TTmplPiGreOutPQsD7PerformanceEntry OBJECT-TYPE
   SYNTAX      Pr1645v2TTmplPiGreOutPQsD7PerformanceEntry
   MAX-ACCESS  not-accessible
   STATUS      current
   DESCRIPTION
      ""
   INDEX      { pr1645v2TTmplPiGreTableIx,
                pr1645v2TTmplPiGreOutPQsTableIx,
                pr1645v2TTmplPiGreOutPQsD7PerformanceTableIx }
   ::= {pr1645v2TTmplPiGreOutPQsD7Performance 1}

Pr1645v2TTmplPiGreOutPQsD7PerformanceEntry ::=
   SEQUENCE
      {
      pr1645v2TTmplPiGreOutPQsD7PerformanceTableIx
         TableIndex,
      pr1645v2TTmplPiGreOutPQsD7PerformanceSysUpTime
         TimeTicks,
      pr1645v2TTmplPiGreOutPQsD7PerformanceTotPkts
         Counter64,
      pr1645v2TTmplPiGreOutPQsD7PerformanceDirTxPkts
         Counter64,
      pr1645v2TTmplPiGreOutPQsD7PerformanceQdPkts
         Counter64,
      pr1645v2TTmplPiGreOutPQsD7PerformanceDropPkts
         Counter64,
      pr1645v2TTmplPiGreOutPQsD7PerformanceRDropPkts
         Counter64,
      pr1645v2TTmplPiGreOutPQsD7PerformanceCirTxPkts
         Counter64,
      pr1645v2TTmplPiGreOutPQsD7PerformanceEirTxPkts
         Counter64,
      pr1645v2TTmplPiGreOutPQsD7PerformanceViolTxPkts
         Counter64,
      pr1645v2TTmplPiGreOutPQsD7PerformanceTotOcts
         Counter64,
      pr1645v2TTmplPiGreOutPQsD7PerformanceDirTxOcts
         Counter64,
      pr1645v2TTmplPiGreOutPQsD7PerformanceQdOcts
         Counter64,
      pr1645v2TTmplPiGreOutPQsD7PerformanceDropOcts
         Counter64,
      pr1645v2TTmplPiGreOutPQsD7PerformanceRDropOcts
         Counter64,
      pr1645v2TTmplPiGreOutPQsD7PerformanceCirTxOcts
         Counter64,
      pr1645v2TTmplPiGreOutPQsD7PerformanceEirTxOcts
         Counter64,
      pr1645v2TTmplPiGreOutPQsD7PerformanceViolTxOcts
         Counter64,
      pr1645v2TTmplPiGreOutPQsD7PerformanceBandwidth
         Integer32
      }

pr1645v2TTmplPiGreOutPQsD7PerformanceTableIx OBJECT-TYPE
   SYNTAX      TableIndex
   MAX-ACCESS  not-accessible
   STATUS      current
   DESCRIPTION
      ""
   ::= {pr1645v2TTmplPiGreOutPQsD7PerformanceEntry 11}

pr1645v2TTmplPiGreOutPQsD7PerformanceSysUpTime OBJECT-TYPE
   SYNTAX      TimeTicks
   MAX-ACCESS  read-only
   STATUS      current
   DESCRIPTION
      "Path: tunnels.performance.ipsecGreTunnels.outPriorityQueues.d7Performance.sysUpTime

       Time in centi-second."
   ::= {pr1645v2TTmplPiGreOutPQsD7PerformanceEntry 16777216}

pr1645v2TTmplPiGreOutPQsD7PerformanceTotPkts OBJECT-TYPE
   SYNTAX      Counter64
   MAX-ACCESS  read-only
   STATUS      current
   DESCRIPTION
      "Path: tunnels.performance.ipsecGreTunnels.outPriorityQueues.d7Performance.totalPkts

       64 bit unsigned wrappable counter."
   ::= {pr1645v2TTmplPiGreOutPQsD7PerformanceEntry 234881024}

pr1645v2TTmplPiGreOutPQsD7PerformanceDirTxPkts OBJECT-TYPE
   SYNTAX      Counter64
   MAX-ACCESS  read-only
   STATUS      current
   DESCRIPTION
      "Path: tunnels.performance.ipsecGreTunnels.outPriorityQueues.d7Performance.directTxPkts

       64 bit unsigned wrappable counter."
   ::= {pr1645v2TTmplPiGreOutPQsD7PerformanceEntry 33554432}

pr1645v2TTmplPiGreOutPQsD7PerformanceQdPkts OBJECT-TYPE
   SYNTAX      Counter64
   MAX-ACCESS  read-only
   STATUS      current
   DESCRIPTION
      "Path: tunnels.performance.ipsecGreTunnels.outPriorityQueues.d7Performance.queuedPkts

       64 bit unsigned wrappable counter."
   ::= {pr1645v2TTmplPiGreOutPQsD7PerformanceEntry 50331648}

pr1645v2TTmplPiGreOutPQsD7PerformanceDropPkts OBJECT-TYPE
   SYNTAX      Counter64
   MAX-ACCESS  read-only
   STATUS      current
   DESCRIPTION
      "Path: tunnels.performance.ipsecGreTunnels.outPriorityQueues.d7Performance.droppedPkts

       64 bit unsigned wrappable counter."
   ::= {pr1645v2TTmplPiGreOutPQsD7PerformanceEntry 67108864}

pr1645v2TTmplPiGreOutPQsD7PerformanceRDropPkts OBJECT-TYPE
   SYNTAX      Counter64
   MAX-ACCESS  read-only
   STATUS      current
   DESCRIPTION
      "Path: tunnels.performance.ipsecGreTunnels.outPriorityQueues.d7Performance.redDroppedPkts

       64 bit unsigned wrappable counter."
   ::= {pr1645v2TTmplPiGreOutPQsD7PerformanceEntry 201326592}

pr1645v2TTmplPiGreOutPQsD7PerformanceCirTxPkts OBJECT-TYPE
   SYNTAX      Counter64
   MAX-ACCESS  read-only
   STATUS      current
   DESCRIPTION
      "Path: tunnels.performance.ipsecGreTunnels.outPriorityQueues.d7Performance.cirTxPkts

       64 bit unsigned wrappable counter."
   ::= {pr1645v2TTmplPiGreOutPQsD7PerformanceEntry 83886080}

pr1645v2TTmplPiGreOutPQsD7PerformanceEirTxPkts OBJECT-TYPE
   SYNTAX      Counter64
   MAX-ACCESS  read-only
   STATUS      current
   DESCRIPTION
      "Path: tunnels.performance.ipsecGreTunnels.outPriorityQueues.d7Performance.eirTxPkts

       64 bit unsigned wrappable counter."
   ::= {pr1645v2TTmplPiGreOutPQsD7PerformanceEntry 100663296}

pr1645v2TTmplPiGreOutPQsD7PerformanceViolTxPkts OBJECT-TYPE
   SYNTAX      Counter64
   MAX-ACCESS  read-only
   STATUS      current
   DESCRIPTION
      "Path: tunnels.performance.ipsecGreTunnels.outPriorityQueues.d7Performance.violateTxPkts

       64 bit unsigned wrappable counter."
   ::= {pr1645v2TTmplPiGreOutPQsD7PerformanceEntry 301989888}

pr1645v2TTmplPiGreOutPQsD7PerformanceTotOcts OBJECT-TYPE
   SYNTAX      Counter64
   MAX-ACCESS  read-only
   STATUS      current
   DESCRIPTION
      "Path: tunnels.performance.ipsecGreTunnels.outPriorityQueues.d7Performance.totalOctets

       64 bit unsigned wrappable counter."
   ::= {pr1645v2TTmplPiGreOutPQsD7PerformanceEntry 251658240}

pr1645v2TTmplPiGreOutPQsD7PerformanceDirTxOcts OBJECT-TYPE
   SYNTAX      Counter64
   MAX-ACCESS  read-only
   STATUS      current
   DESCRIPTION
      "Path: tunnels.performance.ipsecGreTunnels.outPriorityQueues.d7Performance.directTxOctets

       64 bit unsigned wrappable counter."
   ::= {pr1645v2TTmplPiGreOutPQsD7PerformanceEntry 117440512}

pr1645v2TTmplPiGreOutPQsD7PerformanceQdOcts OBJECT-TYPE
   SYNTAX      Counter64
   MAX-ACCESS  read-only
   STATUS      current
   DESCRIPTION
      "Path: tunnels.performance.ipsecGreTunnels.outPriorityQueues.d7Performance.queuedOctets

       64 bit unsigned wrappable counter."
   ::= {pr1645v2TTmplPiGreOutPQsD7PerformanceEntry 134217728}

pr1645v2TTmplPiGreOutPQsD7PerformanceDropOcts OBJECT-TYPE
   SYNTAX      Counter64
   MAX-ACCESS  read-only
   STATUS      current
   DESCRIPTION
      "Path: tunnels.performance.ipsecGreTunnels.outPriorityQueues.d7Performance.droppedOctets

       64 bit unsigned wrappable counter."
   ::= {pr1645v2TTmplPiGreOutPQsD7PerformanceEntry 150994944}

pr1645v2TTmplPiGreOutPQsD7PerformanceRDropOcts OBJECT-TYPE
   SYNTAX      Counter64
   MAX-ACCESS  read-only
   STATUS      current
   DESCRIPTION
      "Path: tunnels.performance.ipsecGreTunnels.outPriorityQueues.d7Performance.redDroppedOctets

       64 bit unsigned wrappable counter."
   ::= {pr1645v2TTmplPiGreOutPQsD7PerformanceEntry 218103808}

pr1645v2TTmplPiGreOutPQsD7PerformanceCirTxOcts OBJECT-TYPE
   SYNTAX      Counter64
   MAX-ACCESS  read-only
   STATUS      current
   DESCRIPTION
      "Path: tunnels.performance.ipsecGreTunnels.outPriorityQueues.d7Performance.cirTxOctets

       64 bit unsigned wrappable counter."
   ::= {pr1645v2TTmplPiGreOutPQsD7PerformanceEntry 167772160}

pr1645v2TTmplPiGreOutPQsD7PerformanceEirTxOcts OBJECT-TYPE
   SYNTAX      Counter64
   MAX-ACCESS  read-only
   STATUS      current
   DESCRIPTION
      "Path: tunnels.performance.ipsecGreTunnels.outPriorityQueues.d7Performance.eirTxOctets

       64 bit unsigned wrappable counter."
   ::= {pr1645v2TTmplPiGreOutPQsD7PerformanceEntry 184549376}

pr1645v2TTmplPiGreOutPQsD7PerformanceViolTxOcts OBJECT-TYPE
   SYNTAX      Counter64
   MAX-ACCESS  read-only
   STATUS      current
   DESCRIPTION
      "Path: tunnels.performance.ipsecGreTunnels.outPriorityQueues.d7Performance.violateTxOctets

       64 bit unsigned wrappable counter."
   ::= {pr1645v2TTmplPiGreOutPQsD7PerformanceEntry 318767104}

pr1645v2TTmplPiGreOutPQsD7PerformanceBandwidth OBJECT-TYPE
   SYNTAX      Integer32
   MAX-ACCESS  read-only
   STATUS      current
   DESCRIPTION
      "Path: tunnels.performance.ipsecGreTunnels.outPriorityQueues.d7Performance.bandwidth

       unit name = bps
       formula = 8 * ; 8 /"
   ::= {pr1645v2TTmplPiGreOutPQsD7PerformanceEntry 268435456}


pr1645v2TTmplPerfin OBJECT IDENTIFIER ::= {pr1645v2TTmpl 12}

pr1645v2TTmplPerfinSSCTable OBJECT-TYPE
   SYNTAX      SEQUENCE OF Pr1645v2TTmplPerfinEntry
   MAX-ACCESS  not-accessible
   STATUS      current
   DESCRIPTION
      ""
   ::= {pr1645v2TTmplPerfin 1}

pr1645v2TTmplPerfinEntry OBJECT-TYPE
   SYNTAX      Pr1645v2TTmplPerfinEntry
   MAX-ACCESS  not-accessible
   STATUS      current
   DESCRIPTION
      ""
   INDEX      { pr1645v2TTmplPerfinTableIx }
   ::= {pr1645v2TTmplPerfinSSCTable 1}

Pr1645v2TTmplPerfinEntry ::=
   SEQUENCE
      {
      pr1645v2TTmplPerfinTableIx
         TableIndex,
      pr1645v2TTmplPerfinName
         DisplayString,
      pr1645v2TTmplPerfinMCInOctets
         Counter64,
      pr1645v2TTmplPerfinMCInUcast
         Counter64,
      pr1645v2TTmplPerfinMCInNUcastPkts
         Counter64,
      pr1645v2TTmplPerfinMCInBcastPkts
         Counter64,
      pr1645v2TTmplPerfinMCInMcastPkts
         Counter64,
      pr1645v2TTmplPerfinMCInDiscards
         Counter64,
      pr1645v2TTmplPerfinMCInErrors
         Counter64,
      pr1645v2TTmplPerfinMCInUnknownProtos
         Counter64,
      pr1645v2TTmplPerfinMCInDropEx
         Counter64,
      pr1645v2TTmplPerfinMCInDropNoMac
         Counter64,
      pr1645v2TTmplPerfinMCInDropNUCast
         Counter64,
      pr1645v2TTmplPerfinMCInDropFilter
         Counter64,
      pr1645v2TTmplPerfinMCInBandwidth15sec
         Integer32,
      pr1645v2TTmplPerfinMCInBandwidth30sec
         Integer32,
      pr1645v2TTmplPerfinMCInBandwidth1min
         Integer32,
      pr1645v2TTmplPerfinMCInBandwidth2min
         Integer32,
      pr1645v2TTmplPerfinMCInBandwidth5min
         Integer32,
      pr1645v2TTmplPerfinMCOutOctets
         Counter64,
      pr1645v2TTmplPerfinMCOutUcastPkts
         Counter64,
      pr1645v2TTmplPerfinMCOutNUcastPkts
         Counter64,
      pr1645v2TTmplPerfinMCOutBcastPkts
         Counter64,
      pr1645v2TTmplPerfinMCOutMcastPkts
         Counter64,
      pr1645v2TTmplPerfinMCOutDiscards
         Counter64,
      pr1645v2TTmplPerfinMCOutErrors
         Counter64,
      pr1645v2TTmplPerfinMCOutQLen
         Counter32,
      pr1645v2TTmplPerfinMCOutDropEx
         Counter64,
      pr1645v2TTmplPerfinMCOutDropNoArp
         Counter64,
      pr1645v2TTmplPerfinMCOutDropFilter
         Counter64,
      pr1645v2TTmplPerfinMCOutBandwidth15sec
         Integer32,
      pr1645v2TTmplPerfinMCOutBandwidth30sec
         Integer32,
      pr1645v2TTmplPerfinMCOutBandwidth1min
         Integer32,
      pr1645v2TTmplPerfinMCOutBandwidth2min
         Integer32,
      pr1645v2TTmplPerfinMCOutBandwidth5min
         Integer32
      }

pr1645v2TTmplPerfinTableIx OBJECT-TYPE
   SYNTAX      TableIndex
   MAX-ACCESS  not-accessible
   STATUS      current
   DESCRIPTION
      ""
   ::= {pr1645v2TTmplPerfinEntry 11}

pr1645v2TTmplPerfinName OBJECT-TYPE
   SYNTAX      DisplayString
   MAX-ACCESS  read-only
   STATUS      current
   DESCRIPTION
      "Path: tunnels.performance.ipsecTunnels.name"
   ::= {pr1645v2TTmplPerfinEntry 16777216}

pr1645v2TTmplPerfinMCInOctets OBJECT-TYPE
   SYNTAX      Counter64
   MAX-ACCESS  read-only
   STATUS      current
   DESCRIPTION
      "Path: tunnels.performance.ipsecTunnels.mibCounters.ifInOctets

       64 bit unsigned wrappable counter."
   ::= {pr1645v2TTmplPerfinEntry 40697856}

pr1645v2TTmplPerfinMCInUcast OBJECT-TYPE
   SYNTAX      Counter64
   MAX-ACCESS  read-only
   STATUS      current
   DESCRIPTION
      "Path: tunnels.performance.ipsecTunnels.mibCounters.ifInUcastPkts

       64 bit unsigned wrappable counter."
   ::= {pr1645v2TTmplPerfinEntry 40763392}

pr1645v2TTmplPerfinMCInNUcastPkts OBJECT-TYPE
   SYNTAX      Counter64
   MAX-ACCESS  read-only
   STATUS      current
   DESCRIPTION
      "Path: tunnels.performance.ipsecTunnels.mibCounters.ifInNUcastPkts

       64 bit unsigned wrappable counter."
   ::= {pr1645v2TTmplPerfinEntry 40828928}

pr1645v2TTmplPerfinMCInBcastPkts OBJECT-TYPE
   SYNTAX      Counter64
   MAX-ACCESS  read-only
   STATUS      current
   DESCRIPTION
      "Path: tunnels.performance.ipsecTunnels.mibCounters.ifInBcastPkts

       64 bit unsigned wrappable counter."
   ::= {pr1645v2TTmplPerfinEntry 47382528}

pr1645v2TTmplPerfinMCInMcastPkts OBJECT-TYPE
   SYNTAX      Counter64
   MAX-ACCESS  read-only
   STATUS      current
   DESCRIPTION
      "Path: tunnels.performance.ipsecTunnels.mibCounters.ifInMcastPkts

       64 bit unsigned wrappable counter."
   ::= {pr1645v2TTmplPerfinEntry 48037888}

pr1645v2TTmplPerfinMCInDiscards OBJECT-TYPE
   SYNTAX      Counter64
   MAX-ACCESS  read-only
   STATUS      current
   DESCRIPTION
      "Path: tunnels.performance.ipsecTunnels.mibCounters.ifInDiscards

       64 bit unsigned wrappable counter."
   ::= {pr1645v2TTmplPerfinEntry 40894464}

pr1645v2TTmplPerfinMCInErrors OBJECT-TYPE
   SYNTAX      Counter64
   MAX-ACCESS  read-only
   STATUS      current
   DESCRIPTION
      "Path: tunnels.performance.ipsecTunnels.mibCounters.ifInErrors

       64 bit unsigned wrappable counter."
   ::= {pr1645v2TTmplPerfinEntry 40960000}

pr1645v2TTmplPerfinMCInUnknownProtos OBJECT-TYPE
   SYNTAX      Counter64
   MAX-ACCESS  read-only
   STATUS      current
   DESCRIPTION
      "Path: tunnels.performance.ipsecTunnels.mibCounters.ifInUnknownProtos

       64 bit unsigned wrappable counter."
   ::= {pr1645v2TTmplPerfinEntry 41025536}

pr1645v2TTmplPerfinMCInDropEx OBJECT-TYPE
   SYNTAX      Counter64
   MAX-ACCESS  read-only
   STATUS      current
   DESCRIPTION
      "Path: tunnels.performance.ipsecTunnels.mibCounters.ifInDropLevelExceeded

       64 bit unsigned wrappable counter."
   ::= {pr1645v2TTmplPerfinEntry 42074112}

pr1645v2TTmplPerfinMCInDropNoMac OBJECT-TYPE
   SYNTAX      Counter64
   MAX-ACCESS  read-only
   STATUS      current
   DESCRIPTION
      "Path: tunnels.performance.ipsecTunnels.mibCounters.ifInDiscardsNoMacFit

       64 bit unsigned wrappable counter."
   ::= {pr1645v2TTmplPerfinEntry 42270720}

pr1645v2TTmplPerfinMCInDropNUCast OBJECT-TYPE
   SYNTAX      Counter64
   MAX-ACCESS  read-only
   STATUS      current
   DESCRIPTION
      "Path: tunnels.performance.ipsecTunnels.mibCounters.ifInDiscardsNUCast

       64 bit unsigned wrappable counter."
   ::= {pr1645v2TTmplPerfinEntry 42467328}

pr1645v2TTmplPerfinMCInDropFilter OBJECT-TYPE
   SYNTAX      Counter64
   MAX-ACCESS  read-only
   STATUS      current
   DESCRIPTION
      "Path: tunnels.performance.ipsecTunnels.mibCounters.ifInDiscardsFilter

       64 bit unsigned wrappable counter."
   ::= {pr1645v2TTmplPerfinEntry 42532864}

pr1645v2TTmplPerfinMCInBandwidth15sec OBJECT-TYPE
   SYNTAX      Integer32
   MAX-ACCESS  read-only
   STATUS      current
   DESCRIPTION
      "Path: tunnels.performance.ipsecTunnels.mibCounters.ifInBandwidth.15sec

       unit name = bps
       formula = 8 * ; 8 /"
   ::= {pr1645v2TTmplPerfinEntry 45417728}

pr1645v2TTmplPerfinMCInBandwidth30sec OBJECT-TYPE
   SYNTAX      Integer32
   MAX-ACCESS  read-only
   STATUS      current
   DESCRIPTION
      "Path: tunnels.performance.ipsecTunnels.mibCounters.ifInBandwidth.30sec

       unit name = bps
       formula = 8 * ; 8 /"
   ::= {pr1645v2TTmplPerfinEntry 45419008}

pr1645v2TTmplPerfinMCInBandwidth1min OBJECT-TYPE
   SYNTAX      Integer32
   MAX-ACCESS  read-only
   STATUS      current
   DESCRIPTION
      "Path: tunnels.performance.ipsecTunnels.mibCounters.ifInBandwidth.1min

       unit name = bps
       formula = 8 * ; 8 /"
   ::= {pr1645v2TTmplPerfinEntry 45421568}

pr1645v2TTmplPerfinMCInBandwidth2min OBJECT-TYPE
   SYNTAX      Integer32
   MAX-ACCESS  read-only
   STATUS      current
   DESCRIPTION
      "Path: tunnels.performance.ipsecTunnels.mibCounters.ifInBandwidth.2min

       unit name = bps
       formula = 8 * ; 8 /"
   ::= {pr1645v2TTmplPerfinEntry 45426688}

pr1645v2TTmplPerfinMCInBandwidth5min OBJECT-TYPE
   SYNTAX      Integer32
   MAX-ACCESS  read-only
   STATUS      current
   DESCRIPTION
      "Path: tunnels.performance.ipsecTunnels.mibCounters.ifInBandwidth.5min

       unit name = bps
       formula = 8 * ; 8 /"
   ::= {pr1645v2TTmplPerfinEntry 45442048}

pr1645v2TTmplPerfinMCOutOctets OBJECT-TYPE
   SYNTAX      Counter64
   MAX-ACCESS  read-only
   STATUS      current
   DESCRIPTION
      "Path: tunnels.performance.ipsecTunnels.mibCounters.ifOutOctets

       64 bit unsigned wrappable counter."
   ::= {pr1645v2TTmplPerfinEntry 41091072}

pr1645v2TTmplPerfinMCOutUcastPkts OBJECT-TYPE
   SYNTAX      Counter64
   MAX-ACCESS  read-only
   STATUS      current
   DESCRIPTION
      "Path: tunnels.performance.ipsecTunnels.mibCounters.ifOutUcastPkts

       64 bit unsigned wrappable counter."
   ::= {pr1645v2TTmplPerfinEntry 41156608}

pr1645v2TTmplPerfinMCOutNUcastPkts OBJECT-TYPE
   SYNTAX      Counter64
   MAX-ACCESS  read-only
   STATUS      current
   DESCRIPTION
      "Path: tunnels.performance.ipsecTunnels.mibCounters.ifOutNUcastPkts

       64 bit unsigned wrappable counter."
   ::= {pr1645v2TTmplPerfinEntry 41222144}

pr1645v2TTmplPerfinMCOutBcastPkts OBJECT-TYPE
   SYNTAX      Counter64
   MAX-ACCESS  read-only
   STATUS      current
   DESCRIPTION
      "Path: tunnels.performance.ipsecTunnels.mibCounters.ifOutBcastPkts

       64 bit unsigned wrappable counter."
   ::= {pr1645v2TTmplPerfinEntry 47775744}

pr1645v2TTmplPerfinMCOutMcastPkts OBJECT-TYPE
   SYNTAX      Counter64
   MAX-ACCESS  read-only
   STATUS      current
   DESCRIPTION
      "Path: tunnels.performance.ipsecTunnels.mibCounters.ifOutMcastPkts

       64 bit unsigned wrappable counter."
   ::= {pr1645v2TTmplPerfinEntry 48431104}

pr1645v2TTmplPerfinMCOutDiscards OBJECT-TYPE
   SYNTAX      Counter64
   MAX-ACCESS  read-only
   STATUS      current
   DESCRIPTION
      "Path: tunnels.performance.ipsecTunnels.mibCounters.ifOutDiscards

       64 bit unsigned wrappable counter."
   ::= {pr1645v2TTmplPerfinEntry 41287680}

pr1645v2TTmplPerfinMCOutErrors OBJECT-TYPE
   SYNTAX      Counter64
   MAX-ACCESS  read-only
   STATUS      current
   DESCRIPTION
      "Path: tunnels.performance.ipsecTunnels.mibCounters.ifOutErrors

       64 bit unsigned wrappable counter."
   ::= {pr1645v2TTmplPerfinEntry 41353216}

pr1645v2TTmplPerfinMCOutQLen OBJECT-TYPE
   SYNTAX      Counter32
   MAX-ACCESS  read-only
   STATUS      current
   DESCRIPTION
      "Path: tunnels.performance.ipsecTunnels.mibCounters.ifOutQLen

       32 bit unsigned wrappable counter."
   ::= {pr1645v2TTmplPerfinEntry 41418752}

pr1645v2TTmplPerfinMCOutDropEx OBJECT-TYPE
   SYNTAX      Counter64
   MAX-ACCESS  read-only
   STATUS      current
   DESCRIPTION
      "Path: tunnels.performance.ipsecTunnels.mibCounters.ifOutDropLevelExceeded

       64 bit unsigned wrappable counter."
   ::= {pr1645v2TTmplPerfinEntry 41484288}

pr1645v2TTmplPerfinMCOutDropNoArp OBJECT-TYPE
   SYNTAX      Counter64
   MAX-ACCESS  read-only
   STATUS      current
   DESCRIPTION
      "Path: tunnels.performance.ipsecTunnels.mibCounters.ifOutDiscardsNoArp

       64 bit unsigned wrappable counter."
   ::= {pr1645v2TTmplPerfinEntry 42336256}

pr1645v2TTmplPerfinMCOutDropFilter OBJECT-TYPE
   SYNTAX      Counter64
   MAX-ACCESS  read-only
   STATUS      current
   DESCRIPTION
      "Path: tunnels.performance.ipsecTunnels.mibCounters.ifOutDiscardsFilter

       64 bit unsigned wrappable counter."
   ::= {pr1645v2TTmplPerfinEntry 42598400}

pr1645v2TTmplPerfinMCOutBandwidth15sec OBJECT-TYPE
   SYNTAX      Integer32
   MAX-ACCESS  read-only
   STATUS      current
   DESCRIPTION
      "Path: tunnels.performance.ipsecTunnels.mibCounters.ifOutBandwidth.15sec

       unit name = bps
       formula = 8 * ; 8 /"
   ::= {pr1645v2TTmplPerfinEntry 45483264}

pr1645v2TTmplPerfinMCOutBandwidth30sec OBJECT-TYPE
   SYNTAX      Integer32
   MAX-ACCESS  read-only
   STATUS      current
   DESCRIPTION
      "Path: tunnels.performance.ipsecTunnels.mibCounters.ifOutBandwidth.30sec

       unit name = bps
       formula = 8 * ; 8 /"
   ::= {pr1645v2TTmplPerfinEntry 45484544}

pr1645v2TTmplPerfinMCOutBandwidth1min OBJECT-TYPE
   SYNTAX      Integer32
   MAX-ACCESS  read-only
   STATUS      current
   DESCRIPTION
      "Path: tunnels.performance.ipsecTunnels.mibCounters.ifOutBandwidth.1min

       unit name = bps
       formula = 8 * ; 8 /"
   ::= {pr1645v2TTmplPerfinEntry 45487104}

pr1645v2TTmplPerfinMCOutBandwidth2min OBJECT-TYPE
   SYNTAX      Integer32
   MAX-ACCESS  read-only
   STATUS      current
   DESCRIPTION
      "Path: tunnels.performance.ipsecTunnels.mibCounters.ifOutBandwidth.2min

       unit name = bps
       formula = 8 * ; 8 /"
   ::= {pr1645v2TTmplPerfinEntry 45492224}

pr1645v2TTmplPerfinMCOutBandwidth5min OBJECT-TYPE
   SYNTAX      Integer32
   MAX-ACCESS  read-only
   STATUS      current
   DESCRIPTION
      "Path: tunnels.performance.ipsecTunnels.mibCounters.ifOutBandwidth.5min

       unit name = bps
       formula = 8 * ; 8 /"
   ::= {pr1645v2TTmplPerfinEntry 45507584}

pr1645v2TTmplPerfinMCH2P OBJECT-TYPE
   SYNTAX      SEQUENCE OF Pr1645v2TTmplPerfinMCH2PEntry
   MAX-ACCESS  not-accessible
   STATUS      current
   DESCRIPTION
      ""
   ::= {pr1645v2TTmplPerfin 41549824}

pr1645v2TTmplPerfinMCH2PEntry OBJECT-TYPE
   SYNTAX      Pr1645v2TTmplPerfinMCH2PEntry
   MAX-ACCESS  not-accessible
   STATUS      current
   DESCRIPTION
      ""
   INDEX      { pr1645v2TTmplPerfinTableIx,
                pr1645v2TTmplPerfinMCH2PTableIx }
   ::= {pr1645v2TTmplPerfinMCH2P 1}

Pr1645v2TTmplPerfinMCH2PEntry ::=
   SEQUENCE
      {
      pr1645v2TTmplPerfinMCH2PTableIx
         TableIndex,
      pr1645v2TTmplPerfinMCH2PSysUpTime
         TimeTicks,
      pr1645v2TTmplPerfinMCH2PIfUpTime
         TimeTicks,
      pr1645v2TTmplPerfinMCH2PIfStatChanges
         Counter32,
      pr1645v2TTmplPerfinMCH2PIfInOctets
         Counter64,
      pr1645v2TTmplPerfinMCH2PIfInUCPkts
         Counter64,
      pr1645v2TTmplPerfinMCH2PIfInNUCPkts
         Counter64,
      pr1645v2TTmplPerfinMCH2PIfInBCPkts
         Counter64,
      pr1645v2TTmplPerfinMCH2PIfInMCPkts
         Counter64,
      pr1645v2TTmplPerfinMCH2PIfInDiscards
         Counter64,
      pr1645v2TTmplPerfinMCH2PIfInErrors
         Counter64,
      pr1645v2TTmplPerfinMCH2PIfInUnkwn
         Counter64,
      pr1645v2TTmplPerfinMCH2PInDropEx
         Counter64,
      pr1645v2TTmplPerfinMCH2PInDropNoMac
         Counter64,
      pr1645v2TTmplPerfinMCH2PInDropNUCast
         Counter64,
      pr1645v2TTmplPerfinMCH2PInDropFilter
         Counter64,
      pr1645v2TTmplPerfinMCH2PIfInBandwidth
         Integer32,
      pr1645v2TTmplPerfinMCH2PIfOutOctets
         Counter64,
      pr1645v2TTmplPerfinMCH2PIfOutUCPkts
         Counter64,
      pr1645v2TTmplPerfinMCH2PIfOutNUCPkts
         Counter64,
      pr1645v2TTmplPerfinMCH2PIfOutBCPkts
         Counter64,
      pr1645v2TTmplPerfinMCH2PIfOutMCPkts
         Counter64,
      pr1645v2TTmplPerfinMCH2PIfOutDiscards
         Counter64,
      pr1645v2TTmplPerfinMCH2PIfOutErrors
         Counter64,
      pr1645v2TTmplPerfinMCH2POutDropEx
         Counter64,
      pr1645v2TTmplPerfinMCH2POutDropNoArp
         Counter64,
      pr1645v2TTmplPerfinMCH2POutDropFilter
         Counter64,
      pr1645v2TTmplPerfinMCH2PIfOutBandwidth
         Integer32,
      pr1645v2TTmplPerfinMCH2PIfErrSec
         Counter32
      }

pr1645v2TTmplPerfinMCH2PTableIx OBJECT-TYPE
   SYNTAX      TableIndex
   MAX-ACCESS  not-accessible
   STATUS      current
   DESCRIPTION
      ""
   ::= {pr1645v2TTmplPerfinMCH2PEntry 11}

pr1645v2TTmplPerfinMCH2PSysUpTime OBJECT-TYPE
   SYNTAX      TimeTicks
   MAX-ACCESS  read-only
   STATUS      current
   DESCRIPTION
      "Path: tunnels.performance.ipsecTunnels.mibCounters.h2Performance.sysUpTime

       Time in centi-second."
   ::= {pr1645v2TTmplPerfinMCH2PEntry 16777216}

pr1645v2TTmplPerfinMCH2PIfUpTime OBJECT-TYPE
   SYNTAX      TimeTicks
   MAX-ACCESS  read-only
   STATUS      current
   DESCRIPTION
      "Path: tunnels.performance.ipsecTunnels.mibCounters.h2Performance.ifUpTime

       Time in centi-second."
   ::= {pr1645v2TTmplPerfinMCH2PEntry 33554432}

pr1645v2TTmplPerfinMCH2PIfStatChanges OBJECT-TYPE
   SYNTAX      Counter32
   MAX-ACCESS  read-only
   STATUS      current
   DESCRIPTION
      "Path: tunnels.performance.ipsecTunnels.mibCounters.h2Performance.ifStatusChanges

       32 bit unsigned wrappable counter."
   ::= {pr1645v2TTmplPerfinMCH2PEntry 50331648}

pr1645v2TTmplPerfinMCH2PIfInOctets OBJECT-TYPE
   SYNTAX      Counter64
   MAX-ACCESS  read-only
   STATUS      current
   DESCRIPTION
      "Path: tunnels.performance.ipsecTunnels.mibCounters.h2Performance.ifInOctets

       64 bit unsigned wrappable counter."
   ::= {pr1645v2TTmplPerfinMCH2PEntry 67108864}

pr1645v2TTmplPerfinMCH2PIfInUCPkts OBJECT-TYPE
   SYNTAX      Counter64
   MAX-ACCESS  read-only
   STATUS      current
   DESCRIPTION
      "Path: tunnels.performance.ipsecTunnels.mibCounters.h2Performance.ifInUcastPkts

       64 bit unsigned wrappable counter."
   ::= {pr1645v2TTmplPerfinMCH2PEntry 83886080}

pr1645v2TTmplPerfinMCH2PIfInNUCPkts OBJECT-TYPE
   SYNTAX      Counter64
   MAX-ACCESS  read-only
   STATUS      current
   DESCRIPTION
      "Path: tunnels.performance.ipsecTunnels.mibCounters.h2Performance.ifInNUcastPkts

       64 bit unsigned wrappable counter."
   ::= {pr1645v2TTmplPerfinMCH2PEntry 100663296}

pr1645v2TTmplPerfinMCH2PIfInBCPkts OBJECT-TYPE
   SYNTAX      Counter64
   MAX-ACCESS  read-only
   STATUS      current
   DESCRIPTION
      "Path: tunnels.performance.ipsecTunnels.mibCounters.h2Performance.ifInBcastPkts

       64 bit unsigned wrappable counter."
   ::= {pr1645v2TTmplPerfinMCH2PEntry 419430400}

pr1645v2TTmplPerfinMCH2PIfInMCPkts OBJECT-TYPE
   SYNTAX      Counter64
   MAX-ACCESS  read-only
   STATUS      current
   DESCRIPTION
      "Path: tunnels.performance.ipsecTunnels.mibCounters.h2Performance.ifInMcastPkts

       64 bit unsigned wrappable counter."
   ::= {pr1645v2TTmplPerfinMCH2PEntry 436207616}

pr1645v2TTmplPerfinMCH2PIfInDiscards OBJECT-TYPE
   SYNTAX      Counter64
   MAX-ACCESS  read-only
   STATUS      current
   DESCRIPTION
      "Path: tunnels.performance.ipsecTunnels.mibCounters.h2Performance.ifInDiscards

       64 bit unsigned wrappable counter."
   ::= {pr1645v2TTmplPerfinMCH2PEntry 117440512}

pr1645v2TTmplPerfinMCH2PIfInErrors OBJECT-TYPE
   SYNTAX      Counter64
   MAX-ACCESS  read-only
   STATUS      current
   DESCRIPTION
      "Path: tunnels.performance.ipsecTunnels.mibCounters.h2Performance.ifInErrors

       64 bit unsigned wrappable counter."
   ::= {pr1645v2TTmplPerfinMCH2PEntry 134217728}

pr1645v2TTmplPerfinMCH2PIfInUnkwn OBJECT-TYPE
   SYNTAX      Counter64
   MAX-ACCESS  read-only
   STATUS      current
   DESCRIPTION
      "Path: tunnels.performance.ipsecTunnels.mibCounters.h2Performance.ifInUnknownProtos

       64 bit unsigned wrappable counter."
   ::= {pr1645v2TTmplPerfinMCH2PEntry 150994944}

pr1645v2TTmplPerfinMCH2PInDropEx OBJECT-TYPE
   SYNTAX      Counter64
   MAX-ACCESS  read-only
   STATUS      current
   DESCRIPTION
      "Path: tunnels.performance.ipsecTunnels.mibCounters.h2Performance.ifInDropLevelExceeded

       64 bit unsigned wrappable counter."
   ::= {pr1645v2TTmplPerfinMCH2PEntry 335544320}

pr1645v2TTmplPerfinMCH2PInDropNoMac OBJECT-TYPE
   SYNTAX      Counter64
   MAX-ACCESS  read-only
   STATUS      current
   DESCRIPTION
      "Path: tunnels.performance.ipsecTunnels.mibCounters.h2Performance.fInDiscardsNoMacFit

       64 bit unsigned wrappable counter."
   ::= {pr1645v2TTmplPerfinMCH2PEntry 301989888}

pr1645v2TTmplPerfinMCH2PInDropNUCast OBJECT-TYPE
   SYNTAX      Counter64
   MAX-ACCESS  read-only
   STATUS      current
   DESCRIPTION
      "Path: tunnels.performance.ipsecTunnels.mibCounters.h2Performance.fInDiscardsNUCast

       64 bit unsigned wrappable counter."
   ::= {pr1645v2TTmplPerfinMCH2PEntry 318767104}

pr1645v2TTmplPerfinMCH2PInDropFilter OBJECT-TYPE
   SYNTAX      Counter64
   MAX-ACCESS  read-only
   STATUS      current
   DESCRIPTION
      "Path: tunnels.performance.ipsecTunnels.mibCounters.h2Performance.fInDiscardsFilter

       64 bit unsigned wrappable counter."
   ::= {pr1645v2TTmplPerfinMCH2PEntry 385875968}

pr1645v2TTmplPerfinMCH2PIfInBandwidth OBJECT-TYPE
   SYNTAX      Integer32
   MAX-ACCESS  read-only
   STATUS      current
   DESCRIPTION
      "Path: tunnels.performance.ipsecTunnels.mibCounters.h2Performance.ifInBandwidth

       unit name = bps
       formula = 8 * ; 8 /"
   ::= {pr1645v2TTmplPerfinMCH2PEntry 268435456}

pr1645v2TTmplPerfinMCH2PIfOutOctets OBJECT-TYPE
   SYNTAX      Counter64
   MAX-ACCESS  read-only
   STATUS      current
   DESCRIPTION
      "Path: tunnels.performance.ipsecTunnels.mibCounters.h2Performance.ifOutOctets

       64 bit unsigned wrappable counter."
   ::= {pr1645v2TTmplPerfinMCH2PEntry 167772160}

pr1645v2TTmplPerfinMCH2PIfOutUCPkts OBJECT-TYPE
   SYNTAX      Counter64
   MAX-ACCESS  read-only
   STATUS      current
   DESCRIPTION
      "Path: tunnels.performance.ipsecTunnels.mibCounters.h2Performance.ifOutUcastPkts

       64 bit unsigned wrappable counter."
   ::= {pr1645v2TTmplPerfinMCH2PEntry 184549376}

pr1645v2TTmplPerfinMCH2PIfOutNUCPkts OBJECT-TYPE
   SYNTAX      Counter64
   MAX-ACCESS  read-only
   STATUS      current
   DESCRIPTION
      "Path: tunnels.performance.ipsecTunnels.mibCounters.h2Performance.ifOutNUcastPkts

       64 bit unsigned wrappable counter."
   ::= {pr1645v2TTmplPerfinMCH2PEntry 201326592}

pr1645v2TTmplPerfinMCH2PIfOutBCPkts OBJECT-TYPE
   SYNTAX      Counter64
   MAX-ACCESS  read-only
   STATUS      current
   DESCRIPTION
      "Path: tunnels.performance.ipsecTunnels.mibCounters.h2Performance.ifOutBcastPkts

       64 bit unsigned wrappable counter."
   ::= {pr1645v2TTmplPerfinMCH2PEntry 452984832}

pr1645v2TTmplPerfinMCH2PIfOutMCPkts OBJECT-TYPE
   SYNTAX      Counter64
   MAX-ACCESS  read-only
   STATUS      current
   DESCRIPTION
      "Path: tunnels.performance.ipsecTunnels.mibCounters.h2Performance.ifOutMcastPkts

       64 bit unsigned wrappable counter."
   ::= {pr1645v2TTmplPerfinMCH2PEntry 469762048}

pr1645v2TTmplPerfinMCH2PIfOutDiscards OBJECT-TYPE
   SYNTAX      Counter64
   MAX-ACCESS  read-only
   STATUS      current
   DESCRIPTION
      "Path: tunnels.performance.ipsecTunnels.mibCounters.h2Performance.ifOutDiscards

       64 bit unsigned wrappable counter."
   ::= {pr1645v2TTmplPerfinMCH2PEntry 218103808}

pr1645v2TTmplPerfinMCH2PIfOutErrors OBJECT-TYPE
   SYNTAX      Counter64
   MAX-ACCESS  read-only
   STATUS      current
   DESCRIPTION
      "Path: tunnels.performance.ipsecTunnels.mibCounters.h2Performance.ifOutErrors

       64 bit unsigned wrappable counter."
   ::= {pr1645v2TTmplPerfinMCH2PEntry 234881024}

pr1645v2TTmplPerfinMCH2POutDropEx OBJECT-TYPE
   SYNTAX      Counter64
   MAX-ACCESS  read-only
   STATUS      current
   DESCRIPTION
      "Path: tunnels.performance.ipsecTunnels.mibCounters.h2Performance.ifOutDropLevelExceeded

       64 bit unsigned wrappable counter."
   ::= {pr1645v2TTmplPerfinMCH2PEntry 352321536}

pr1645v2TTmplPerfinMCH2POutDropNoArp OBJECT-TYPE
   SYNTAX      Counter64
   MAX-ACCESS  read-only
   STATUS      current
   DESCRIPTION
      "Path: tunnels.performance.ipsecTunnels.mibCounters.h2Performance.ifOutDiscardsNoArp

       64 bit unsigned wrappable counter."
   ::= {pr1645v2TTmplPerfinMCH2PEntry 369098752}

pr1645v2TTmplPerfinMCH2POutDropFilter OBJECT-TYPE
   SYNTAX      Counter64
   MAX-ACCESS  read-only
   STATUS      current
   DESCRIPTION
      "Path: tunnels.performance.ipsecTunnels.mibCounters.h2Performance.ifOutDiscardsFilter

       64 bit unsigned wrappable counter."
   ::= {pr1645v2TTmplPerfinMCH2PEntry 402653184}

pr1645v2TTmplPerfinMCH2PIfOutBandwidth OBJECT-TYPE
   SYNTAX      Integer32
   MAX-ACCESS  read-only
   STATUS      current
   DESCRIPTION
      "Path: tunnels.performance.ipsecTunnels.mibCounters.h2Performance.ifOutBandwidth

       unit name = bps
       formula = 8 * ; 8 /"
   ::= {pr1645v2TTmplPerfinMCH2PEntry 285212672}

pr1645v2TTmplPerfinMCH2PIfErrSec OBJECT-TYPE
   SYNTAX      Counter32
   MAX-ACCESS  read-only
   STATUS      current
   DESCRIPTION
      "Path: tunnels.performance.ipsecTunnels.mibCounters.h2Performance.ifErrSec

       32 bit unsigned wrappable counter."
   ::= {pr1645v2TTmplPerfinMCH2PEntry 251658240}

pr1645v2TTmplPerfinMCH24P OBJECT-TYPE
   SYNTAX      SEQUENCE OF Pr1645v2TTmplPerfinMCH24PEntry
   MAX-ACCESS  not-accessible
   STATUS      current
   DESCRIPTION
      ""
   ::= {pr1645v2TTmplPerfin 41615360}

pr1645v2TTmplPerfinMCH24PEntry OBJECT-TYPE
   SYNTAX      Pr1645v2TTmplPerfinMCH24PEntry
   MAX-ACCESS  not-accessible
   STATUS      current
   DESCRIPTION
      ""
   INDEX      { pr1645v2TTmplPerfinTableIx,
                pr1645v2TTmplPerfinMCH24PTableIx }
   ::= {pr1645v2TTmplPerfinMCH24P 1}

Pr1645v2TTmplPerfinMCH24PEntry ::=
   SEQUENCE
      {
      pr1645v2TTmplPerfinMCH24PTableIx
         TableIndex,
      pr1645v2TTmplPerfinMCH24PSysUpTime
         TimeTicks,
      pr1645v2TTmplPerfinMCH24PIfUpTime
         TimeTicks,
      pr1645v2TTmplPerfinMCH24PIfStatChanges
         Counter32,
      pr1645v2TTmplPerfinMCH24PIfInOctets
         Counter64,
      pr1645v2TTmplPerfinMCH24PIfInUCPkts
         Counter64,
      pr1645v2TTmplPerfinMCH24PIfInNUCPkts
         Counter64,
      pr1645v2TTmplPerfinMCH24PIfInBCPkts
         Counter64,
      pr1645v2TTmplPerfinMCH24PIfInMCPkts
         Counter64,
      pr1645v2TTmplPerfinMCH24PIfInDiscards
         Counter64,
      pr1645v2TTmplPerfinMCH24PIfInErrors
         Counter64,
      pr1645v2TTmplPerfinMCH24PIfInUnkwn
         Counter64,
      pr1645v2TTmplPerfinMCH24PInDropEx
         Counter64,
      pr1645v2TTmplPerfinMCH24PInDropNoMac
         Counter64,
      pr1645v2TTmplPerfinMCH24PInDropNUCast
         Counter64,
      pr1645v2TTmplPerfinMCH24PInDropFilter
         Counter64,
      pr1645v2TTmplPerfinMCH24PIfInBandwidth
         Integer32,
      pr1645v2TTmplPerfinMCH24PIfOutOctets
         Counter64,
      pr1645v2TTmplPerfinMCH24PIfOutUCPkts
         Counter64,
      pr1645v2TTmplPerfinMCH24PIfOutNUCPkts
         Counter64,
      pr1645v2TTmplPerfinMCH24PIfOutBCPkts
         Counter64,
      pr1645v2TTmplPerfinMCH24PIfOutMCPkts
         Counter64,
      pr1645v2TTmplPerfinMCH24PIfOutDiscards
         Counter64,
      pr1645v2TTmplPerfinMCH24PIfOutErrors
         Counter64,
      pr1645v2TTmplPerfinMCH24POutDropEx
         Counter64,
      pr1645v2TTmplPerfinMCH24POutDropNoArp
         Counter64,
      pr1645v2TTmplPerfinMCH24POutDropFilter
         Counter64,
      pr1645v2TTmplPerfinMCH24PIfOutBandwidth
         Integer32,
      pr1645v2TTmplPerfinMCH24PIfErrSec
         Counter32
      }

pr1645v2TTmplPerfinMCH24PTableIx OBJECT-TYPE
   SYNTAX      TableIndex
   MAX-ACCESS  not-accessible
   STATUS      current
   DESCRIPTION
      ""
   ::= {pr1645v2TTmplPerfinMCH24PEntry 11}

pr1645v2TTmplPerfinMCH24PSysUpTime OBJECT-TYPE
   SYNTAX      TimeTicks
   MAX-ACCESS  read-only
   STATUS      current
   DESCRIPTION
      "Path: tunnels.performance.ipsecTunnels.mibCounters.h24Performance.sysUpTime

       Time in centi-second."
   ::= {pr1645v2TTmplPerfinMCH24PEntry 16777216}

pr1645v2TTmplPerfinMCH24PIfUpTime OBJECT-TYPE
   SYNTAX      TimeTicks
   MAX-ACCESS  read-only
   STATUS      current
   DESCRIPTION
      "Path: tunnels.performance.ipsecTunnels.mibCounters.h24Performance.ifUpTime

       Time in centi-second."
   ::= {pr1645v2TTmplPerfinMCH24PEntry 33554432}

pr1645v2TTmplPerfinMCH24PIfStatChanges OBJECT-TYPE
   SYNTAX      Counter32
   MAX-ACCESS  read-only
   STATUS      current
   DESCRIPTION
      "Path: tunnels.performance.ipsecTunnels.mibCounters.h24Performance.ifStatusChanges

       32 bit unsigned wrappable counter."
   ::= {pr1645v2TTmplPerfinMCH24PEntry 50331648}

pr1645v2TTmplPerfinMCH24PIfInOctets OBJECT-TYPE
   SYNTAX      Counter64
   MAX-ACCESS  read-only
   STATUS      current
   DESCRIPTION
      "Path: tunnels.performance.ipsecTunnels.mibCounters.h24Performance.ifInOctets

       64 bit unsigned wrappable counter."
   ::= {pr1645v2TTmplPerfinMCH24PEntry 67108864}

pr1645v2TTmplPerfinMCH24PIfInUCPkts OBJECT-TYPE
   SYNTAX      Counter64
   MAX-ACCESS  read-only
   STATUS      current
   DESCRIPTION
      "Path: tunnels.performance.ipsecTunnels.mibCounters.h24Performance.ifInUcastPkts

       64 bit unsigned wrappable counter."
   ::= {pr1645v2TTmplPerfinMCH24PEntry 83886080}

pr1645v2TTmplPerfinMCH24PIfInNUCPkts OBJECT-TYPE
   SYNTAX      Counter64
   MAX-ACCESS  read-only
   STATUS      current
   DESCRIPTION
      "Path: tunnels.performance.ipsecTunnels.mibCounters.h24Performance.ifInNUcastPkts

       64 bit unsigned wrappable counter."
   ::= {pr1645v2TTmplPerfinMCH24PEntry 100663296}

pr1645v2TTmplPerfinMCH24PIfInBCPkts OBJECT-TYPE
   SYNTAX      Counter64
   MAX-ACCESS  read-only
   STATUS      current
   DESCRIPTION
      "Path: tunnels.performance.ipsecTunnels.mibCounters.h24Performance.ifInBcastPkts

       64 bit unsigned wrappable counter."
   ::= {pr1645v2TTmplPerfinMCH24PEntry 419430400}

pr1645v2TTmplPerfinMCH24PIfInMCPkts OBJECT-TYPE
   SYNTAX      Counter64
   MAX-ACCESS  read-only
   STATUS      current
   DESCRIPTION
      "Path: tunnels.performance.ipsecTunnels.mibCounters.h24Performance.ifInMcastPkts

       64 bit unsigned wrappable counter."
   ::= {pr1645v2TTmplPerfinMCH24PEntry 436207616}

pr1645v2TTmplPerfinMCH24PIfInDiscards OBJECT-TYPE
   SYNTAX      Counter64
   MAX-ACCESS  read-only
   STATUS      current
   DESCRIPTION
      "Path: tunnels.performance.ipsecTunnels.mibCounters.h24Performance.ifInDiscards

       64 bit unsigned wrappable counter."
   ::= {pr1645v2TTmplPerfinMCH24PEntry 117440512}

pr1645v2TTmplPerfinMCH24PIfInErrors OBJECT-TYPE
   SYNTAX      Counter64
   MAX-ACCESS  read-only
   STATUS      current
   DESCRIPTION
      "Path: tunnels.performance.ipsecTunnels.mibCounters.h24Performance.ifInErrors

       64 bit unsigned wrappable counter."
   ::= {pr1645v2TTmplPerfinMCH24PEntry 134217728}

pr1645v2TTmplPerfinMCH24PIfInUnkwn OBJECT-TYPE
   SYNTAX      Counter64
   MAX-ACCESS  read-only
   STATUS      current
   DESCRIPTION
      "Path: tunnels.performance.ipsecTunnels.mibCounters.h24Performance.ifInUnknownProtos

       64 bit unsigned wrappable counter."
   ::= {pr1645v2TTmplPerfinMCH24PEntry 150994944}

pr1645v2TTmplPerfinMCH24PInDropEx OBJECT-TYPE
   SYNTAX      Counter64
   MAX-ACCESS  read-only
   STATUS      current
   DESCRIPTION
      "Path: tunnels.performance.ipsecTunnels.mibCounters.h24Performance.ifInDropLevelExceeded

       64 bit unsigned wrappable counter."
   ::= {pr1645v2TTmplPerfinMCH24PEntry 335544320}

pr1645v2TTmplPerfinMCH24PInDropNoMac OBJECT-TYPE
   SYNTAX      Counter64
   MAX-ACCESS  read-only
   STATUS      current
   DESCRIPTION
      "Path: tunnels.performance.ipsecTunnels.mibCounters.h24Performance.fInDiscardsNoMacFit

       64 bit unsigned wrappable counter."
   ::= {pr1645v2TTmplPerfinMCH24PEntry 301989888}

pr1645v2TTmplPerfinMCH24PInDropNUCast OBJECT-TYPE
   SYNTAX      Counter64
   MAX-ACCESS  read-only
   STATUS      current
   DESCRIPTION
      "Path: tunnels.performance.ipsecTunnels.mibCounters.h24Performance.fInDiscardsNUCast

       64 bit unsigned wrappable counter."
   ::= {pr1645v2TTmplPerfinMCH24PEntry 318767104}

pr1645v2TTmplPerfinMCH24PInDropFilter OBJECT-TYPE
   SYNTAX      Counter64
   MAX-ACCESS  read-only
   STATUS      current
   DESCRIPTION
      "Path: tunnels.performance.ipsecTunnels.mibCounters.h24Performance.fInDiscardsFilter

       64 bit unsigned wrappable counter."
   ::= {pr1645v2TTmplPerfinMCH24PEntry 385875968}

pr1645v2TTmplPerfinMCH24PIfInBandwidth OBJECT-TYPE
   SYNTAX      Integer32
   MAX-ACCESS  read-only
   STATUS      current
   DESCRIPTION
      "Path: tunnels.performance.ipsecTunnels.mibCounters.h24Performance.ifInBandwidth

       unit name = bps
       formula = 8 * ; 8 /"
   ::= {pr1645v2TTmplPerfinMCH24PEntry 268435456}

pr1645v2TTmplPerfinMCH24PIfOutOctets OBJECT-TYPE
   SYNTAX      Counter64
   MAX-ACCESS  read-only
   STATUS      current
   DESCRIPTION
      "Path: tunnels.performance.ipsecTunnels.mibCounters.h24Performance.ifOutOctets

       64 bit unsigned wrappable counter."
   ::= {pr1645v2TTmplPerfinMCH24PEntry 167772160}

pr1645v2TTmplPerfinMCH24PIfOutUCPkts OBJECT-TYPE
   SYNTAX      Counter64
   MAX-ACCESS  read-only
   STATUS      current
   DESCRIPTION
      "Path: tunnels.performance.ipsecTunnels.mibCounters.h24Performance.ifOutUcastPkts

       64 bit unsigned wrappable counter."
   ::= {pr1645v2TTmplPerfinMCH24PEntry 184549376}

pr1645v2TTmplPerfinMCH24PIfOutNUCPkts OBJECT-TYPE
   SYNTAX      Counter64
   MAX-ACCESS  read-only
   STATUS      current
   DESCRIPTION
      "Path: tunnels.performance.ipsecTunnels.mibCounters.h24Performance.ifOutNUcastPkts

       64 bit unsigned wrappable counter."
   ::= {pr1645v2TTmplPerfinMCH24PEntry 201326592}

pr1645v2TTmplPerfinMCH24PIfOutBCPkts OBJECT-TYPE
   SYNTAX      Counter64
   MAX-ACCESS  read-only
   STATUS      current
   DESCRIPTION
      "Path: tunnels.performance.ipsecTunnels.mibCounters.h24Performance.ifOutBcastPkts

       64 bit unsigned wrappable counter."
   ::= {pr1645v2TTmplPerfinMCH24PEntry 452984832}

pr1645v2TTmplPerfinMCH24PIfOutMCPkts OBJECT-TYPE
   SYNTAX      Counter64
   MAX-ACCESS  read-only
   STATUS      current
   DESCRIPTION
      "Path: tunnels.performance.ipsecTunnels.mibCounters.h24Performance.ifOutMcastPkts

       64 bit unsigned wrappable counter."
   ::= {pr1645v2TTmplPerfinMCH24PEntry 469762048}

pr1645v2TTmplPerfinMCH24PIfOutDiscards OBJECT-TYPE
   SYNTAX      Counter64
   MAX-ACCESS  read-only
   STATUS      current
   DESCRIPTION
      "Path: tunnels.performance.ipsecTunnels.mibCounters.h24Performance.ifOutDiscards

       64 bit unsigned wrappable counter."
   ::= {pr1645v2TTmplPerfinMCH24PEntry 218103808}

pr1645v2TTmplPerfinMCH24PIfOutErrors OBJECT-TYPE
   SYNTAX      Counter64
   MAX-ACCESS  read-only
   STATUS      current
   DESCRIPTION
      "Path: tunnels.performance.ipsecTunnels.mibCounters.h24Performance.ifOutErrors

       64 bit unsigned wrappable counter."
   ::= {pr1645v2TTmplPerfinMCH24PEntry 234881024}

pr1645v2TTmplPerfinMCH24POutDropEx OBJECT-TYPE
   SYNTAX      Counter64
   MAX-ACCESS  read-only
   STATUS      current
   DESCRIPTION
      "Path: tunnels.performance.ipsecTunnels.mibCounters.h24Performance.ifOutDropLevelExceeded

       64 bit unsigned wrappable counter."
   ::= {pr1645v2TTmplPerfinMCH24PEntry 352321536}

pr1645v2TTmplPerfinMCH24POutDropNoArp OBJECT-TYPE
   SYNTAX      Counter64
   MAX-ACCESS  read-only
   STATUS      current
   DESCRIPTION
      "Path: tunnels.performance.ipsecTunnels.mibCounters.h24Performance.ifOutDiscardsNoArp

       64 bit unsigned wrappable counter."
   ::= {pr1645v2TTmplPerfinMCH24PEntry 369098752}

pr1645v2TTmplPerfinMCH24POutDropFilter OBJECT-TYPE
   SYNTAX      Counter64
   MAX-ACCESS  read-only
   STATUS      current
   DESCRIPTION
      "Path: tunnels.performance.ipsecTunnels.mibCounters.h24Performance.ifOutDiscardsFilter

       64 bit unsigned wrappable counter."
   ::= {pr1645v2TTmplPerfinMCH24PEntry 402653184}

pr1645v2TTmplPerfinMCH24PIfOutBandwidth OBJECT-TYPE
   SYNTAX      Integer32
   MAX-ACCESS  read-only
   STATUS      current
   DESCRIPTION
      "Path: tunnels.performance.ipsecTunnels.mibCounters.h24Performance.ifOutBandwidth

       unit name = bps
       formula = 8 * ; 8 /"
   ::= {pr1645v2TTmplPerfinMCH24PEntry 285212672}

pr1645v2TTmplPerfinMCH24PIfErrSec OBJECT-TYPE
   SYNTAX      Counter32
   MAX-ACCESS  read-only
   STATUS      current
   DESCRIPTION
      "Path: tunnels.performance.ipsecTunnels.mibCounters.h24Performance.ifErrSec

       32 bit unsigned wrappable counter."
   ::= {pr1645v2TTmplPerfinMCH24PEntry 251658240}

pr1645v2TTmplPerfinMCD7P OBJECT-TYPE
   SYNTAX      SEQUENCE OF Pr1645v2TTmplPerfinMCD7PEntry
   MAX-ACCESS  not-accessible
   STATUS      current
   DESCRIPTION
      ""
   ::= {pr1645v2TTmplPerfin 41680896}

pr1645v2TTmplPerfinMCD7PEntry OBJECT-TYPE
   SYNTAX      Pr1645v2TTmplPerfinMCD7PEntry
   MAX-ACCESS  not-accessible
   STATUS      current
   DESCRIPTION
      ""
   INDEX      { pr1645v2TTmplPerfinTableIx,
                pr1645v2TTmplPerfinMCD7PTableIx }
   ::= {pr1645v2TTmplPerfinMCD7P 1}

Pr1645v2TTmplPerfinMCD7PEntry ::=
   SEQUENCE
      {
      pr1645v2TTmplPerfinMCD7PTableIx
         TableIndex,
      pr1645v2TTmplPerfinMCD7PSysUpTime
         TimeTicks,
      pr1645v2TTmplPerfinMCD7PIfUpTime
         TimeTicks,
      pr1645v2TTmplPerfinMCD7PIfStatChanges
         Counter32,
      pr1645v2TTmplPerfinMCD7PIfInOctets
         Counter64,
      pr1645v2TTmplPerfinMCD7PIfInUCPkts
         Counter64,
      pr1645v2TTmplPerfinMCD7PIfInNUCPkts
         Counter64,
      pr1645v2TTmplPerfinMCD7PIfInBCPkts
         Counter64,
      pr1645v2TTmplPerfinMCD7PIfInMCPkts
         Counter64,
      pr1645v2TTmplPerfinMCD7PIfInDiscards
         Counter64,
      pr1645v2TTmplPerfinMCD7PIfInErrors
         Counter64,
      pr1645v2TTmplPerfinMCD7PIfInUnkwn
         Counter64,
      pr1645v2TTmplPerfinMCD7PInDropEx
         Counter64,
      pr1645v2TTmplPerfinMCD7PInDropNoMac
         Counter64,
      pr1645v2TTmplPerfinMCD7PInDropNUCast
         Counter64,
      pr1645v2TTmplPerfinMCD7PInDropFilter
         Counter64,
      pr1645v2TTmplPerfinMCD7PIfInBandwidth
         Integer32,
      pr1645v2TTmplPerfinMCD7PIfOutOctets
         Counter64,
      pr1645v2TTmplPerfinMCD7PIfOutUCPkts
         Counter64,
      pr1645v2TTmplPerfinMCD7PIfOutNUCPkts
         Counter64,
      pr1645v2TTmplPerfinMCD7PIfOutBCPkts
         Counter64,
      pr1645v2TTmplPerfinMCD7PIfOutMCPkts
         Counter64,
      pr1645v2TTmplPerfinMCD7PIfOutDiscards
         Counter64,
      pr1645v2TTmplPerfinMCD7PIfOutErrors
         Counter64,
      pr1645v2TTmplPerfinMCD7POutDropEx
         Counter64,
      pr1645v2TTmplPerfinMCD7POutDropNoArp
         Counter64,
      pr1645v2TTmplPerfinMCD7POutDropFilter
         Counter64,
      pr1645v2TTmplPerfinMCD7PIfOutBandwidth
         Integer32,
      pr1645v2TTmplPerfinMCD7PIfErrSec
         Counter32
      }

pr1645v2TTmplPerfinMCD7PTableIx OBJECT-TYPE
   SYNTAX      TableIndex
   MAX-ACCESS  not-accessible
   STATUS      current
   DESCRIPTION
      ""
   ::= {pr1645v2TTmplPerfinMCD7PEntry 11}

pr1645v2TTmplPerfinMCD7PSysUpTime OBJECT-TYPE
   SYNTAX      TimeTicks
   MAX-ACCESS  read-only
   STATUS      current
   DESCRIPTION
      "Path: tunnels.performance.ipsecTunnels.mibCounters.d7Performance.sysUpTime

       Time in centi-second."
   ::= {pr1645v2TTmplPerfinMCD7PEntry 16777216}

pr1645v2TTmplPerfinMCD7PIfUpTime OBJECT-TYPE
   SYNTAX      TimeTicks
   MAX-ACCESS  read-only
   STATUS      current
   DESCRIPTION
      "Path: tunnels.performance.ipsecTunnels.mibCounters.d7Performance.ifUpTime

       Time in centi-second."
   ::= {pr1645v2TTmplPerfinMCD7PEntry 33554432}

pr1645v2TTmplPerfinMCD7PIfStatChanges OBJECT-TYPE
   SYNTAX      Counter32
   MAX-ACCESS  read-only
   STATUS      current
   DESCRIPTION
      "Path: tunnels.performance.ipsecTunnels.mibCounters.d7Performance.ifStatusChanges

       32 bit unsigned wrappable counter."
   ::= {pr1645v2TTmplPerfinMCD7PEntry 50331648}

pr1645v2TTmplPerfinMCD7PIfInOctets OBJECT-TYPE
   SYNTAX      Counter64
   MAX-ACCESS  read-only
   STATUS      current
   DESCRIPTION
      "Path: tunnels.performance.ipsecTunnels.mibCounters.d7Performance.ifInOctets

       64 bit unsigned wrappable counter."
   ::= {pr1645v2TTmplPerfinMCD7PEntry 67108864}

pr1645v2TTmplPerfinMCD7PIfInUCPkts OBJECT-TYPE
   SYNTAX      Counter64
   MAX-ACCESS  read-only
   STATUS      current
   DESCRIPTION
      "Path: tunnels.performance.ipsecTunnels.mibCounters.d7Performance.ifInUcastPkts

       64 bit unsigned wrappable counter."
   ::= {pr1645v2TTmplPerfinMCD7PEntry 83886080}

pr1645v2TTmplPerfinMCD7PIfInNUCPkts OBJECT-TYPE
   SYNTAX      Counter64
   MAX-ACCESS  read-only
   STATUS      current
   DESCRIPTION
      "Path: tunnels.performance.ipsecTunnels.mibCounters.d7Performance.ifInNUcastPkts

       64 bit unsigned wrappable counter."
   ::= {pr1645v2TTmplPerfinMCD7PEntry 100663296}

pr1645v2TTmplPerfinMCD7PIfInBCPkts OBJECT-TYPE
   SYNTAX      Counter64
   MAX-ACCESS  read-only
   STATUS      current
   DESCRIPTION
      "Path: tunnels.performance.ipsecTunnels.mibCounters.d7Performance.ifInBcastPkts

       64 bit unsigned wrappable counter."
   ::= {pr1645v2TTmplPerfinMCD7PEntry 419430400}

pr1645v2TTmplPerfinMCD7PIfInMCPkts OBJECT-TYPE
   SYNTAX      Counter64
   MAX-ACCESS  read-only
   STATUS      current
   DESCRIPTION
      "Path: tunnels.performance.ipsecTunnels.mibCounters.d7Performance.ifInMcastPkts

       64 bit unsigned wrappable counter."
   ::= {pr1645v2TTmplPerfinMCD7PEntry 436207616}

pr1645v2TTmplPerfinMCD7PIfInDiscards OBJECT-TYPE
   SYNTAX      Counter64
   MAX-ACCESS  read-only
   STATUS      current
   DESCRIPTION
      "Path: tunnels.performance.ipsecTunnels.mibCounters.d7Performance.ifInDiscards

       64 bit unsigned wrappable counter."
   ::= {pr1645v2TTmplPerfinMCD7PEntry 117440512}

pr1645v2TTmplPerfinMCD7PIfInErrors OBJECT-TYPE
   SYNTAX      Counter64
   MAX-ACCESS  read-only
   STATUS      current
   DESCRIPTION
      "Path: tunnels.performance.ipsecTunnels.mibCounters.d7Performance.ifInErrors

       64 bit unsigned wrappable counter."
   ::= {pr1645v2TTmplPerfinMCD7PEntry 134217728}

pr1645v2TTmplPerfinMCD7PIfInUnkwn OBJECT-TYPE
   SYNTAX      Counter64
   MAX-ACCESS  read-only
   STATUS      current
   DESCRIPTION
      "Path: tunnels.performance.ipsecTunnels.mibCounters.d7Performance.ifInUnknownProtos

       64 bit unsigned wrappable counter."
   ::= {pr1645v2TTmplPerfinMCD7PEntry 150994944}

pr1645v2TTmplPerfinMCD7PInDropEx OBJECT-TYPE
   SYNTAX      Counter64
   MAX-ACCESS  read-only
   STATUS      current
   DESCRIPTION
      "Path: tunnels.performance.ipsecTunnels.mibCounters.d7Performance.ifInDropLevelExceeded

       64 bit unsigned wrappable counter."
   ::= {pr1645v2TTmplPerfinMCD7PEntry 335544320}

pr1645v2TTmplPerfinMCD7PInDropNoMac OBJECT-TYPE
   SYNTAX      Counter64
   MAX-ACCESS  read-only
   STATUS      current
   DESCRIPTION
      "Path: tunnels.performance.ipsecTunnels.mibCounters.d7Performance.fInDiscardsNoMacFit

       64 bit unsigned wrappable counter."
   ::= {pr1645v2TTmplPerfinMCD7PEntry 301989888}

pr1645v2TTmplPerfinMCD7PInDropNUCast OBJECT-TYPE
   SYNTAX      Counter64
   MAX-ACCESS  read-only
   STATUS      current
   DESCRIPTION
      "Path: tunnels.performance.ipsecTunnels.mibCounters.d7Performance.fInDiscardsNUCast

       64 bit unsigned wrappable counter."
   ::= {pr1645v2TTmplPerfinMCD7PEntry 318767104}

pr1645v2TTmplPerfinMCD7PInDropFilter OBJECT-TYPE
   SYNTAX      Counter64
   MAX-ACCESS  read-only
   STATUS      current
   DESCRIPTION
      "Path: tunnels.performance.ipsecTunnels.mibCounters.d7Performance.fInDiscardsFilter

       64 bit unsigned wrappable counter."
   ::= {pr1645v2TTmplPerfinMCD7PEntry 385875968}

pr1645v2TTmplPerfinMCD7PIfInBandwidth OBJECT-TYPE
   SYNTAX      Integer32
   MAX-ACCESS  read-only
   STATUS      current
   DESCRIPTION
      "Path: tunnels.performance.ipsecTunnels.mibCounters.d7Performance.ifInBandwidth

       unit name = bps
       formula = 8 * ; 8 /"
   ::= {pr1645v2TTmplPerfinMCD7PEntry 268435456}

pr1645v2TTmplPerfinMCD7PIfOutOctets OBJECT-TYPE
   SYNTAX      Counter64
   MAX-ACCESS  read-only
   STATUS      current
   DESCRIPTION
      "Path: tunnels.performance.ipsecTunnels.mibCounters.d7Performance.ifOutOctets

       64 bit unsigned wrappable counter."
   ::= {pr1645v2TTmplPerfinMCD7PEntry 167772160}

pr1645v2TTmplPerfinMCD7PIfOutUCPkts OBJECT-TYPE
   SYNTAX      Counter64
   MAX-ACCESS  read-only
   STATUS      current
   DESCRIPTION
      "Path: tunnels.performance.ipsecTunnels.mibCounters.d7Performance.ifOutUcastPkts

       64 bit unsigned wrappable counter."
   ::= {pr1645v2TTmplPerfinMCD7PEntry 184549376}

pr1645v2TTmplPerfinMCD7PIfOutNUCPkts OBJECT-TYPE
   SYNTAX      Counter64
   MAX-ACCESS  read-only
   STATUS      current
   DESCRIPTION
      "Path: tunnels.performance.ipsecTunnels.mibCounters.d7Performance.ifOutNUcastPkts

       64 bit unsigned wrappable counter."
   ::= {pr1645v2TTmplPerfinMCD7PEntry 201326592}

pr1645v2TTmplPerfinMCD7PIfOutBCPkts OBJECT-TYPE
   SYNTAX      Counter64
   MAX-ACCESS  read-only
   STATUS      current
   DESCRIPTION
      "Path: tunnels.performance.ipsecTunnels.mibCounters.d7Performance.ifOutBcastPkts

       64 bit unsigned wrappable counter."
   ::= {pr1645v2TTmplPerfinMCD7PEntry 452984832}

pr1645v2TTmplPerfinMCD7PIfOutMCPkts OBJECT-TYPE
   SYNTAX      Counter64
   MAX-ACCESS  read-only
   STATUS      current
   DESCRIPTION
      "Path: tunnels.performance.ipsecTunnels.mibCounters.d7Performance.ifOutMcastPkts

       64 bit unsigned wrappable counter."
   ::= {pr1645v2TTmplPerfinMCD7PEntry 469762048}

pr1645v2TTmplPerfinMCD7PIfOutDiscards OBJECT-TYPE
   SYNTAX      Counter64
   MAX-ACCESS  read-only
   STATUS      current
   DESCRIPTION
      "Path: tunnels.performance.ipsecTunnels.mibCounters.d7Performance.ifOutDiscards

       64 bit unsigned wrappable counter."
   ::= {pr1645v2TTmplPerfinMCD7PEntry 218103808}

pr1645v2TTmplPerfinMCD7PIfOutErrors OBJECT-TYPE
   SYNTAX      Counter64
   MAX-ACCESS  read-only
   STATUS      current
   DESCRIPTION
      "Path: tunnels.performance.ipsecTunnels.mibCounters.d7Performance.ifOutErrors

       64 bit unsigned wrappable counter."
   ::= {pr1645v2TTmplPerfinMCD7PEntry 234881024}

pr1645v2TTmplPerfinMCD7POutDropEx OBJECT-TYPE
   SYNTAX      Counter64
   MAX-ACCESS  read-only
   STATUS      current
   DESCRIPTION
      "Path: tunnels.performance.ipsecTunnels.mibCounters.d7Performance.ifOutDropLevelExceeded

       64 bit unsigned wrappable counter."
   ::= {pr1645v2TTmplPerfinMCD7PEntry 352321536}

pr1645v2TTmplPerfinMCD7POutDropNoArp OBJECT-TYPE
   SYNTAX      Counter64
   MAX-ACCESS  read-only
   STATUS      current
   DESCRIPTION
      "Path: tunnels.performance.ipsecTunnels.mibCounters.d7Performance.ifOutDiscardsNoArp

       64 bit unsigned wrappable counter."
   ::= {pr1645v2TTmplPerfinMCD7PEntry 369098752}

pr1645v2TTmplPerfinMCD7POutDropFilter OBJECT-TYPE
   SYNTAX      Counter64
   MAX-ACCESS  read-only
   STATUS      current
   DESCRIPTION
      "Path: tunnels.performance.ipsecTunnels.mibCounters.d7Performance.ifOutDiscardsFilter

       64 bit unsigned wrappable counter."
   ::= {pr1645v2TTmplPerfinMCD7PEntry 402653184}

pr1645v2TTmplPerfinMCD7PIfOutBandwidth OBJECT-TYPE
   SYNTAX      Integer32
   MAX-ACCESS  read-only
   STATUS      current
   DESCRIPTION
      "Path: tunnels.performance.ipsecTunnels.mibCounters.d7Performance.ifOutBandwidth

       unit name = bps
       formula = 8 * ; 8 /"
   ::= {pr1645v2TTmplPerfinMCD7PEntry 285212672}

pr1645v2TTmplPerfinMCD7PIfErrSec OBJECT-TYPE
   SYNTAX      Counter32
   MAX-ACCESS  read-only
   STATUS      current
   DESCRIPTION
      "Path: tunnels.performance.ipsecTunnels.mibCounters.d7Performance.ifErrSec

       32 bit unsigned wrappable counter."
   ::= {pr1645v2TTmplPerfinMCD7PEntry 251658240}



ar1645v2TTmpl OBJECT IDENTIFIER ::= {r1645v2TTmpl 16}


ar1645v2TTmplClearCounters OBJECT-TYPE
   SYNTAX      Integer32
   MAX-ACCESS  read-write
   STATUS      current
   DESCRIPTION
      "Path: tunnels.actions.clearCounters
       Info: reset counters"
   ::= {ar1645v2TTmpl 263}



END
